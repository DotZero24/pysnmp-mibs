LANCOM-GS-2326PPLUS-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2326Pplus                                               OBJECT IDENTIFIER ::= { gigabitEthernetSwitches 2328 }

gs2326pplusSystem                                                OBJECT IDENTIFIER ::= { lancomGS2326Pplus  1 }

gs2326pplusSystemInformation                                     OBJECT IDENTIFIER ::= { gs2326pplusSystem 1 }

gs2326pplusModelName OBJECT-TYPE
   SYNTAX       DisplayString
   MAX-ACCESS   read-only
   STATUS       current
   DESCRIPTION
       ""
 ::= { gs2326pplusSystemInformation 1 }

gs2326pplusBIOSVersion OBJECT-TYPE
   SYNTAX       DisplayString
   MAX-ACCESS   read-only
   STATUS       current
   DESCRIPTION
       ""
   ::= { gs2326pplusSystemInformation 2 }

gs2326pplusFirmwareVersion OBJECT-TYPE
   SYNTAX       DisplayString
   MAX-ACCESS   read-only
   STATUS       current
   DESCRIPTION
       ""
   ::= { gs2326pplusSystemInformation 3 }

gs2326pplusHardwareMechanicalVersion OBJECT-TYPE
   SYNTAX       DisplayString
   MAX-ACCESS   read-only
   STATUS       current
   DESCRIPTION
       ""
   ::= { gs2326pplusSystemInformation 4 }

gs2326pplusSerialNumber OBJECT-TYPE
   SYNTAX       DisplayString
   MAX-ACCESS   read-only
   STATUS       current
   DESCRIPTION
       ""
   ::= { gs2326pplusSystemInformation 5 }

gs2326pplusHostMACAddress OBJECT-TYPE
   SYNTAX       MacAddress
   MAX-ACCESS   read-only
   STATUS       current
   DESCRIPTION
       ""
   ::= { gs2326pplusSystemInformation 6 }

gs2326pplusConsoleBaudrate OBJECT-TYPE
   SYNTAX       DisplayString
   MAX-ACCESS   read-only
   STATUS       current
   DESCRIPTION
       ""
   ::= { gs2326pplusSystemInformation 7 }

gs2326pplusRAMSize OBJECT-TYPE
   SYNTAX       DisplayString
   MAX-ACCESS   read-only
   STATUS       current
   DESCRIPTION
       ""
   ::= { gs2326pplusSystemInformation 8 }

gs2326pplusFlashSize OBJECT-TYPE
   SYNTAX       DisplayString
   MAX-ACCESS   read-only
   STATUS       current
   DESCRIPTION
       ""
   ::= { gs2326pplusSystemInformation 9 }

gs2326pplusBridgeFDBSize OBJECT-TYPE
   SYNTAX       DisplayString
   MAX-ACCESS   read-only
   STATUS       current
   DESCRIPTION
       ""
   ::= { gs2326pplusSystemInformation 10 }

gs2326pplusTransmitQueue OBJECT-TYPE
   SYNTAX       DisplayString
   MAX-ACCESS   read-only
   STATUS       current
   DESCRIPTION
       ""
   ::= { gs2326pplusSystemInformation 11 }

gs2326pplusMaximumFrameSize OBJECT-TYPE
   SYNTAX       DisplayString
   MAX-ACCESS   read-only
   STATUS       current
   DESCRIPTION
       ""
   ::= { gs2326pplusSystemInformation 12 }

gs2326pplusCPULoad OBJECT-TYPE
   SYNTAX       DisplayString
   MAX-ACCESS   read-only
   STATUS       current
   DESCRIPTION
       ""
   ::= { gs2326pplusSystemInformation 13 }

gs2326pplusSystemDescription OBJECT-TYPE
   SYNTAX       DisplayString
   MAX-ACCESS   read-only
   STATUS       current
   DESCRIPTION
       ""
   ::= { gs2326pplusSystemInformation 21 }

gs2326pplusLocation OBJECT-TYPE
   SYNTAX       DisplayString
   MAX-ACCESS   read-only
   STATUS       current
   DESCRIPTION
       ""
   ::= { gs2326pplusSystemInformation 22 }

gs2326pplusContact OBJECT-TYPE
   SYNTAX       DisplayString
   MAX-ACCESS   read-only
   STATUS       current
   DESCRIPTION
       ""
   ::= { gs2326pplusSystemInformation 23 }

gs2326pplusDeviceName OBJECT-TYPE
   SYNTAX       DisplayString
   MAX-ACCESS   read-only
   STATUS       current
   DESCRIPTION
       ""
   ::= { gs2326pplusSystemInformation 24 }

gs2326pplusSystemDate OBJECT-TYPE
   SYNTAX       DisplayString
   MAX-ACCESS   read-only
   STATUS       current
   DESCRIPTION
       ""
   ::= { gs2326pplusSystemInformation 25 }

gs2326pplusSystemUptime OBJECT-TYPE
   SYNTAX       DisplayString
   MAX-ACCESS   read-only
   STATUS       current
   DESCRIPTION
       ""
   ::= { gs2326pplusSystemInformation 26 }

gs2326pplusSystemIPv4Address OBJECT-TYPE
   SYNTAX       DisplayString
   MAX-ACCESS   read-only
   STATUS       current
   DESCRIPTION
       ""
   ::= { gs2326pplusSystemInformation 27 }

gs2326pplusSystemIPv4SubnetMask OBJECT-TYPE
   SYNTAX       DisplayString
   MAX-ACCESS   read-only
   STATUS       current
   DESCRIPTION
       ""
   ::= { gs2326pplusSystemInformation 28 }

gs2326pplusSystemIPv4Gateway OBJECT-TYPE
   SYNTAX       DisplayString
   MAX-ACCESS   read-only
   STATUS       current
   DESCRIPTION
       ""
   ::= { gs2326pplusSystemInformation 29 }

gs2326pplusIPv6LinkLocalAddress OBJECT-TYPE
   SYNTAX       DisplayString
   MAX-ACCESS   read-only
   STATUS       current
   DESCRIPTION
       ""
   ::= { gs2326pplusSystemInformation 30 }

gs2326pplusIPv6Address OBJECT-TYPE
   SYNTAX       DisplayString
   MAX-ACCESS   read-only
   STATUS       current
   DESCRIPTION
       ""
   ::= { gs2326pplusSystemInformation 31 }

gs2326pplusIPv6Prefix OBJECT-TYPE
   SYNTAX       DisplayString
   MAX-ACCESS   read-only
   STATUS       current
   DESCRIPTION
       ""
   ::= { gs2326pplusSystemInformation 32 }

gs2326pplusIPv6Gateway OBJECT-TYPE
   SYNTAX       DisplayString
   MAX-ACCESS   read-only
   STATUS       current
   DESCRIPTION
       ""
   ::= { gs2326pplusSystemInformation 33 }

gs2326pplusLargestFreeMemBlock OBJECT-TYPE
   SYNTAX       Integer32
   MAX-ACCESS   read-only
   STATUS       current
   DESCRIPTION
       "Largest free memory block in Kb"
   ::= { gs2326pplusSystemInformation 1500 }

gs2326pplusMemFree  OBJECT-TYPE
   SYNTAX       Integer32
   MAX-ACCESS   read-only
   STATUS       current
   DESCRIPTION
       "Free memory in Kb"
   ::= { gs2326pplusSystemInformation 1501 }

gs2326pplusSystemTime                                            OBJECT IDENTIFIER ::= { gs2326pplusSystem 2 }

gs2326pplusSystemTimeManual                                      OBJECT IDENTIFIER ::= { gs2326pplusSystemTime 1 }

gs2326pplusSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2326pplusSystemTimeManual 1 }

gs2326pplusSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2326pplusSystemTimeManual 2 }

gs2326pplusSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2326pplusSystemTimeManual 3 }

gs2326pplusSystemTimeManualDaylightSavings OBJECT-TYPE
   SYNTAX       INTEGER { disable(0), enable(1) }
   MAX-ACCESS   read-write
   STATUS       current
   DESCRIPTION
       "default: 0,
        0 : Disable,
        1 : Enable."
   ::= { gs2326pplusSystemTimeManual 4 }

gs2326pplusSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2326pplusSystemTimeManual 5 }

gs2326pplusSystemTimeManualDaylightSavingsType OBJECT-TYPE
   SYNTAX       INTEGER { byDates(0), recurring(1) }
   MAX-ACCESS   read-write
   STATUS       current
   DESCRIPTION
       "default: 0,
        0 : By dates,
        1 : Recurring."
   ::= { gs2326pplusSystemTimeManual 6 }

gs2326pplusSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326pplusSystemTimeManual 7 }

gs2326pplusSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326pplusSystemTimeManual 8 }

gs2326pplusSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2326pplusSystemTimeManual 9 }

gs2326pplusSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2326pplusSystemTimeManual 10 }

gs2326pplusSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2326pplusSystemTimeManual 11 }

gs2326pplusSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326pplusSystemTimeManual 12 }

gs2326pplusSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2326pplusSystemTimeManual 13 }

gs2326pplusSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2326pplusSystemTimeManual 14 }

gs2326pplusSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2326pplusSystemTimeManual 15 }

gs2326pplusSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326pplusSystemTimeManual 16 }

gs2326pplusSystemTimeNTP                                     OBJECT IDENTIFIER ::= { gs2326pplusSystemTime 2 }

gs2326pplusSystemTimeNTPTable OBJECT-TYPE
   SYNTAX      SEQUENCE OF GS2326PPLUSSystemTimeNTPEntry
   MAX-ACCESS  not-accessible
   STATUS      current
   DESCRIPTION
       " "
   ::= { gs2326pplusSystemTimeNTP 1 }

gs2326pplusSystemTimeNTPEntry OBJECT-TYPE
   SYNTAX      GS2326PPLUSSystemTimeNTPEntry
   MAX-ACCESS  not-accessible
   STATUS      current
   DESCRIPTION
       ""
   INDEX    { gs2326pplusSystemTimeNTPIndex  }
   ::= { gs2326pplusSystemTimeNTPTable 1 }

GS2326PPLUSSystemTimeNTPEntry ::= SEQUENCE {
   gs2326pplusSystemTimeNTPIndex             Integer32,
   gs2326pplusSystemTimeNTPServerIPType      INTEGER,
   gs2326pplusSystemTimeNTPServer            DisplayString,
   gs2326pplusSystemTimeNTPCurrentMode       INTEGER
}

gs2326pplusSystemTimeNTPIndex OBJECT-TYPE
   SYNTAX      Integer32(1..5)
   MAX-ACCESS  not-accessible
   STATUS      current
   DESCRIPTION
       " The index of the ntp entry. "
   ::= { gs2326pplusSystemTimeNTPEntry 1 }

gs2326pplusSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2326pplusSystemTimeNTPEntry 2 }

gs2326pplusSystemTimeNTPServer OBJECT-TYPE
   SYNTAX       DisplayString
   MAX-ACCESS   read-write
   STATUS       current
   DESCRIPTION
       "Get/Set the NTP Time Server1. You can use the IP address or domain name."
   ::= { gs2326pplusSystemTimeNTPEntry 3 }

gs2326pplusSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2326pplusSystemTimeNTPEntry 4 }

gs2326pplusSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2326pplusSystemTimeNTP 2 }

gs2326pplusSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2326pplusSystemTimeNTP 3 }


gs2326pplusSystemAccount                                         OBJECT IDENTIFIER ::= { gs2326pplusSystem 3 }

gs2326pplusSystemAccountUsers                                    OBJECT IDENTIFIER ::= { gs2326pplusSystemAccount 1 }

gs2326pplusSystemAccountUserCreate OBJECT-TYPE
   SYNTAX       INTEGER { none(0), create(1) }
   MAX-ACCESS   read-write
   STATUS       current
   DESCRIPTION
       "default: 0
        0 : None  (read only)
        1 : Create a user account"
   ::= { gs2326pplusSystemAccountUsers 1 }

gs2326pplusSystemAccountUsersTable OBJECT-TYPE
   SYNTAX      SEQUENCE OF GS2326PPLUSSystemAccountUsersEntry
   MAX-ACCESS  not-accessible
   STATUS      current
   DESCRIPTION
       " "
   ::= { gs2326pplusSystemAccountUsers 2 }

gs2326pplusSystemAccountUsersEntry OBJECT-TYPE
   SYNTAX      GS2326PPLUSSystemAccountUsersEntry
   MAX-ACCESS  not-accessible
   STATUS      current
   DESCRIPTION
       ""
   INDEX    { gs2326pplusUserIndex  }
   ::= { gs2326pplusSystemAccountUsersTable 1 }


GS2326PPLUSSystemAccountUsersEntry ::= SEQUENCE {
   gs2326pplusUserIndex              Integer32 ,
   gs2326pplusUserName               DisplayString,
   gs2326pplusPassword               DisplayString,
   gs2326pplusUserPrivilegeLevel     Integer32 ,
   gs2326pplusAccountUserRowStatus   INTEGER
}


gs2326pplusUserIndex OBJECT-TYPE
   SYNTAX      Integer32 (1..20)
   MAX-ACCESS  not-accessible
   STATUS      current
   DESCRIPTION
       " "
   ::= { gs2326pplusSystemAccountUsersEntry 1 }

gs2326pplusUserName OBJECT-TYPE
   SYNTAX      DisplayString (SIZE (1..32))
   MAX-ACCESS  read-write
   STATUS      current
   DESCRIPTION
       "Please use a combination of letters, numbers and underscores"
   ::= { gs2326pplusSystemAccountUsersEntry 2 }

gs2326pplusPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2326pplusSystemAccountUsersEntry 3 }

gs2326pplusUserPrivilegeLevel OBJECT-TYPE
   SYNTAX      Integer32 (1..15)
   MAX-ACCESS  read-write
   STATUS      current
   DESCRIPTION
       "default:1
        User privilege level range : 1 - 15"
   ::= { gs2326pplusSystemAccountUsersEntry 4 }

gs2326pplusAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2326pplusSystemAccountUsersEntry 5 }

gs2326pplusSystemAccountUsersSuperUserPassword OBJECT-TYPE
   SYNTAX      OCTET STRING (SIZE (0..32))
   MAX-ACCESS read-write
   STATUS      current
   DESCRIPTION
        "Super-User Password"
   ::= { gs2326pplusSystemAccountUsers 1500 }

gs2326pplusSystemAccountEnforcePasswordRules OBJECT-TYPE
   SYNTAX       INTEGER { yes(0), no(1) }
   MAX-ACCESS   read-write
   STATUS       current
   DESCRIPTION
       "default: 0
        0 : Do not enforce rules
        1 : enforce rules"
   ::= { gs2326pplusSystemAccountUsers 1501 }

gs2326pplusSystemAccountPrivilegeLevel                           OBJECT IDENTIFIER ::= { gs2326pplusSystemAccount 2 }

gs2326pplusAccountPrivilegeLevel OBJECT-TYPE
   SYNTAX      Integer32 (1..15)
   MAX-ACCESS  read-write
   STATUS      current
   DESCRIPTION
       "Default:15, Range : 1-15. "
   ::= { gs2326pplusSystemAccountPrivilegeLevel 1 }

gs2326pplusAggregationPrivilegeLevel OBJECT-TYPE
   SYNTAX      Integer32 (1..15)
   MAX-ACCESS  read-write
   STATUS      current
   DESCRIPTION
       "Default:15, Range : 1-15. "
   ::= { gs2326pplusSystemAccountPrivilegeLevel 2 }

gs2326pplusDiagnosticsPrivilegeLevel OBJECT-TYPE
   SYNTAX      Integer32 (1..15)
   MAX-ACCESS  read-write
   STATUS      current
   DESCRIPTION
       "Default:15, Range : 1-15. "
   ::= { gs2326pplusSystemAccountPrivilegeLevel 3 }

gs2326pplusEEEPrivilegeLevel OBJECT-TYPE
   SYNTAX      Integer32 (1..15)
   MAX-ACCESS  read-write
   STATUS      current
   DESCRIPTION
       "Default:15, Range : 1-15. "
   ::= { gs2326pplusSystemAccountPrivilegeLevel 4 }

gs2326pplusEasyportPrivilegeLevel OBJECT-TYPE
   SYNTAX      Integer32 (1..15)
   MAX-ACCESS  read-write
   STATUS      current
   DESCRIPTION
       "Default:15, Range : 1-15. "
   ::= { gs2326pplusSystemAccountPrivilegeLevel 9 }

gs2326pplusGARPPrivilegeLevel OBJECT-TYPE
   SYNTAX      Integer32 (1..15)
   MAX-ACCESS  read-write
   STATUS      current
   DESCRIPTION
       "Default:15, Range : 1-15. "
   ::= { gs2326pplusSystemAccountPrivilegeLevel 10 }

gs2326pplusGVRPPrivilegeLevel OBJECT-TYPE
   SYNTAX      Integer32 (1..15)
   MAX-ACCESS  read-write
   STATUS      current
   DESCRIPTION
       "Default:15, Range : 1-15. "
   ::= { gs2326pplusSystemAccountPrivilegeLevel 11 }

gs2326pplusIPPrivilegeLevel OBJECT-TYPE
   SYNTAX      Integer32 (1..15)
   MAX-ACCESS  read-write
   STATUS      current
   DESCRIPTION
       "Default:15, Range : 1-15. "
   ::= { gs2326pplusSystemAccountPrivilegeLevel 12 }

gs2326pplusIPMCSnoopingPrivilegeLevel OBJECT-TYPE
   SYNTAX      Integer32 (1..15)
   MAX-ACCESS  read-write
   STATUS      current
   DESCRIPTION
       "Default:15, Range : 1-15. "
   ::= { gs2326pplusSystemAccountPrivilegeLevel 13 }

gs2326pplusLACPPrivilegeLevel OBJECT-TYPE
   SYNTAX      Integer32 (1..15)
   MAX-ACCESS  read-write
   STATUS      current
   DESCRIPTION
       "Default:15, Range : 1-15. "
   ::= { gs2326pplusSystemAccountPrivilegeLevel 14 }

gs2326pplusLLDPPrivilegeLevel OBJECT-TYPE
   SYNTAX      Integer32 (1..15)
   MAX-ACCESS  read-write
   STATUS      current
   DESCRIPTION
       "Default:15, Range : 1-15. "
   ::= { gs2326pplusSystemAccountPrivilegeLevel 15 }

gs2326pplusLLDPMEDPrivilegeLevel OBJECT-TYPE
   SYNTAX      Integer32 (1..15)
   MAX-ACCESS  read-write
   STATUS      current
   DESCRIPTION
       "Default:15, Range : 1-15. "
   ::= { gs2326pplusSystemAccountPrivilegeLevel 16 }

gs2326pplusLoopProtectPrivilegeLevel OBJECT-TYPE
   SYNTAX      Integer32 (1..15)
   MAX-ACCESS  read-write
   STATUS      current
   DESCRIPTION
       "Default:15, Range : 1-15. "
   ::= { gs2326pplusSystemAccountPrivilegeLevel 17 }

gs2326pplusMACTablePrivilegeLevel OBJECT-TYPE
   SYNTAX      Integer32 (1..15)
   MAX-ACCESS  read-write
   STATUS      current
   DESCRIPTION
       "Default:15, Range : 1-15. "
   ::= { gs2326pplusSystemAccountPrivilegeLevel 18 }

gs2326pplusMVRPrivilegeLevel OBJECT-TYPE
   SYNTAX      Integer32 (1..15)
   MAX-ACCESS  read-write
   STATUS      current
   DESCRIPTION
       "Default:15, Range : 1-15. "
   ::= { gs2326pplusSystemAccountPrivilegeLevel 22 }

gs2326pplusMaintenancePrivilegeLevel OBJECT-TYPE
   SYNTAX      Integer32 (1..15)
   MAX-ACCESS  read-write
   STATUS      current
   DESCRIPTION
       "Default:15, Range : 1-15. "
   ::= { gs2326pplusSystemAccountPrivilegeLevel 24 }

gs2326pplusMirroringPrivilegeLevel OBJECT-TYPE
   SYNTAX      Integer32 (1..15)
   MAX-ACCESS  read-write
   STATUS      current
   DESCRIPTION
       "Default:15, Range : 1-15. "
   ::= { gs2326pplusSystemAccountPrivilegeLevel 25 }

gs2326pplusPortsPrivilegeLevel OBJECT-TYPE
   SYNTAX      Integer32 (1..15)
   MAX-ACCESS  read-write
   STATUS      current
   DESCRIPTION
       "Default:15, Range : 1-15. "
   ::= { gs2326pplusSystemAccountPrivilegeLevel 27 }

gs2326pplusPrivateVLANsPrivilegeLevel OBJECT-TYPE
   SYNTAX      Integer32 (1..15)
   MAX-ACCESS  read-write
   STATUS      current
   DESCRIPTION
       "Default:15, Range : 1-15. "
   ::= { gs2326pplusSystemAccountPrivilegeLevel 28 }

gs2326pplusQoSPrivilegeLevel OBJECT-TYPE
   SYNTAX      Integer32 (1..15)
   MAX-ACCESS  read-write
   STATUS      current
   DESCRIPTION
       "Default:15, Range : 1-15. "
   ::= { gs2326pplusSystemAccountPrivilegeLevel 29 }

gs2326pplusSFlowPrivilegeLevel OBJECT-TYPE
   SYNTAX      Integer32 (1..15)
   MAX-ACCESS  read-write
   STATUS      current
   DESCRIPTION
       "Default:15, Range : 1-15. "
   ::= { gs2326pplusSystemAccountPrivilegeLevel 30 }

gs2326pplusSMTPPrivilegeLevel OBJECT-TYPE
   SYNTAX      Integer32 (1..15)
   MAX-ACCESS  read-write
   STATUS      current
   DESCRIPTION
       "Default:15, Range : 1-15. "
   ::= { gs2326pplusSystemAccountPrivilegeLevel 31 }

gs2326pplusSNMPPrivilegeLevel OBJECT-TYPE
   SYNTAX      Integer32 (1..15)
   MAX-ACCESS  read-write
   STATUS      current
   DESCRIPTION
       "Default:15, Range : 1-15. "
   ::= { gs2326pplusSystemAccountPrivilegeLevel 32 }

gs2326pplusSecurityPrivilegeLevel OBJECT-TYPE
   SYNTAX      Integer32 (1..15)
   MAX-ACCESS  read-write
   STATUS      current
   DESCRIPTION
       "Default:15, Range : 1-15. "
   ::= { gs2326pplusSystemAccountPrivilegeLevel 33 }

gs2326pplusSingleIPPrivilegeLevel OBJECT-TYPE
   SYNTAX      Integer32 (1..15)
   MAX-ACCESS  read-write
   STATUS      current
   DESCRIPTION
       "Default:15, Range : 1-15. "
   ::= { gs2326pplusSystemAccountPrivilegeLevel 34 }

gs2326pplusSpanningTreePrivilegeLevel OBJECT-TYPE
   SYNTAX      Integer32 (1..15)
   MAX-ACCESS  read-write
   STATUS      current
   DESCRIPTION
       "Default:15, Range : 1-15. "
   ::= { gs2326pplusSystemAccountPrivilegeLevel 35 }

gs2326pplusSystemPrivilegeLevel OBJECT-TYPE
   SYNTAX      Integer32 (1..15)
   MAX-ACCESS  read-write
   STATUS      current
   DESCRIPTION
       "Default:15, Range : 1-15. "
   ::= { gs2326pplusSystemAccountPrivilegeLevel 36 }

gs2326pplusTrapEventPrivilegeLevel OBJECT-TYPE
   SYNTAX      Integer32 (1..15)
   MAX-ACCESS  read-write
   STATUS      current
   DESCRIPTION
       "Default:15, Range : 1-15. "
   ::= { gs2326pplusSystemAccountPrivilegeLevel 37 }

gs2326pplusUPnPPrivilegeLevel OBJECT-TYPE
   SYNTAX      Integer32 (1..15)
   MAX-ACCESS  read-write
   STATUS      current
   DESCRIPTION
       "Default:15, Range : 1-15. "
   ::= { gs2326pplusSystemAccountPrivilegeLevel 38 }

gs2326pplusVCLPrivilegeLevel OBJECT-TYPE
   SYNTAX      Integer32 (1..15)
   MAX-ACCESS  read-write
   STATUS      current
   DESCRIPTION
       "Default:15, Range : 1-15. "
   ::= { gs2326pplusSystemAccountPrivilegeLevel 39 }

gs2326pplusVLANsPrivilegeLevel OBJECT-TYPE
   SYNTAX      Integer32 (1..15)
   MAX-ACCESS  read-write
   STATUS      current
   DESCRIPTION
       "Default:15, Range : 1-15. "
   ::= { gs2326pplusSystemAccountPrivilegeLevel 41 }

gs2326pplusVoiceVLANPrivilegeLevel OBJECT-TYPE
   SYNTAX      Integer32 (1..15)
   MAX-ACCESS  read-write
   STATUS      current
   DESCRIPTION
       "Default:15, Range : 1-15. "
   ::= { gs2326pplusSystemAccountPrivilegeLevel 42 }

gs2326pplusPOEPrivilegeLevel OBJECT-TYPE
   SYNTAX      Integer32 (1..15)
   MAX-ACCESS  read-write
   STATUS      current
   DESCRIPTION
       "Default:15, Range : 1-15. "
   ::= { gs2326pplusSystemAccountPrivilegeLevel 43 }


gs2326pplusIP                                                    OBJECT IDENTIFIER ::= { gs2326pplusSystem 4 }

gs2326pplusIPv4                                                  OBJECT IDENTIFIER ::= { gs2326pplusIP 1 }

gs2326pplusIPv4Configured                                                  OBJECT IDENTIFIER ::= { gs2326pplusIPv4 1 }

gs2326pplusIpv4DHCPClient OBJECT-TYPE
   SYNTAX      INTEGER { disable(0), enable(1) }
   MAX-ACCESS  read-write
   STATUS      current
   DESCRIPTION
       "default:0
       0: disable
       1: enable"
   ::= { gs2326pplusIPv4Configured 1 }

gs2326pplusIPv4Address OBJECT-TYPE
   SYNTAX      IpAddress
   MAX-ACCESS  read-write
   STATUS      current
   DESCRIPTION
       ""
   ::= { gs2326pplusIPv4Configured 2 }

gs2326pplusIPv4Mask OBJECT-TYPE
   SYNTAX      IpAddress
   MAX-ACCESS  read-write
   STATUS      current
   DESCRIPTION
       ""
   ::= { gs2326pplusIPv4Configured 3 }

gs2326pplusIPv4Gateway OBJECT-TYPE
   SYNTAX      IpAddress
   MAX-ACCESS  read-write
   STATUS      current
   DESCRIPTION
       ""
   ::= { gs2326pplusIPv4Configured 4 }

gs2326pplusIPv4VLANId OBJECT-TYPE
   SYNTAX      Integer32(1..4094)
   MAX-ACCESS  read-write
   STATUS      current
   DESCRIPTION
       "default:1"
   ::= { gs2326pplusIPv4Configured 5 }

gs2326pplusIPv4DNSServer OBJECT-TYPE
   SYNTAX      IpAddress
   MAX-ACCESS  read-write
   STATUS      current
   DESCRIPTION
       ""
   ::= { gs2326pplusIPv4Configured 6 }

gs2326pplusIPv4DNSProxy OBJECT-TYPE
   SYNTAX      INTEGER { disable(0), enable(1) }
   MAX-ACCESS  read-write
   STATUS      current
   DESCRIPTION
       "0:disable, 1:enable "
   ::= { gs2326pplusIPv4Configured 7 }

gs2326pplusIPv4Current                                                  OBJECT IDENTIFIER ::= { gs2326pplusIPv4 2 }

gs2326pplusIpv4CurrentDHCPClient OBJECT-TYPE
   SYNTAX      INTEGER { none(0), renew(1) }
   MAX-ACCESS  read-write
   STATUS      current
   DESCRIPTION
       "default:0
       0: none (for read)
       1: renew"
   ::= { gs2326pplusIPv4Current 1 }

gs2326pplusIPv4CurrentAddress OBJECT-TYPE
   SYNTAX      IpAddress
   MAX-ACCESS  read-only
   STATUS      current
   DESCRIPTION
       ""
   ::= { gs2326pplusIPv4Current 2 }

gs2326pplusIPv4CurrentMask OBJECT-TYPE
   SYNTAX      IpAddress
   MAX-ACCESS  read-only
   STATUS      current
   DESCRIPTION
       ""
   ::= { gs2326pplusIPv4Current 3 }

gs2326pplusIPv4CurrentGateway OBJECT-TYPE
   SYNTAX      IpAddress
   MAX-ACCESS  read-only
   STATUS      current
   DESCRIPTION
       ""
   ::= { gs2326pplusIPv4Current 4 }

gs2326pplusIPv4CurrentVLANId OBJECT-TYPE
   SYNTAX      Integer32(1..4094)
   MAX-ACCESS  read-only
   STATUS      current
   DESCRIPTION
       "default:1"
   ::= { gs2326pplusIPv4Current 5 }

gs2326pplusIPv4CurrentDNSServer OBJECT-TYPE
   SYNTAX      IpAddress
   MAX-ACCESS  read-only
   STATUS      current
   DESCRIPTION
       ""
   ::= { gs2326pplusIPv4Current 6 }


gs2326pplusIPv6                                                  OBJECT IDENTIFIER ::= { gs2326pplusIP 2 }

gs2326pplusIPv6Configured                                                  OBJECT IDENTIFIER ::= { gs2326pplusIPv6 1 }

gs2326pplusIpv6AutoConfiguration OBJECT-TYPE
   SYNTAX      INTEGER { disable(0), enable(1) }
   MAX-ACCESS  read-write
   STATUS      current
   DESCRIPTION
       "default:0
       0: disable
       1: enable"
   ::= { gs2326pplusIPv6Configured 1 }

gs2326pplusIpv6Address OBJECT-TYPE
   SYNTAX      DisplayString (SIZE (0..30))
   MAX-ACCESS  read-write
   STATUS      current
   DESCRIPTION
       ""
   ::= { gs2326pplusIPv6Configured 2 }

gs2326pplusIpv6Prefix OBJECT-TYPE
   SYNTAX      Integer32 (1..128)
   MAX-ACCESS  read-write
   STATUS      current
   DESCRIPTION
       "default: 96"
   ::= { gs2326pplusIPv6Configured 3 }

gs2326pplusIpv6Gateway OBJECT-TYPE
   SYNTAX      DisplayString (SIZE (0..30))
   MAX-ACCESS  read-write
   STATUS      current
   DESCRIPTION
       " "
   ::= { gs2326pplusIPv6Configured 4 }

gs2326pplusIPv6Current                                                  OBJECT IDENTIFIER ::= { gs2326pplusIPv6 2 }

gs2326pplusIpv6CurrentAutoConfiguration OBJECT-TYPE
   SYNTAX      INTEGER { disable(0), enable(1) }
   MAX-ACCESS  read-only
   STATUS      current
   DESCRIPTION
       "default:0
       0: disable
       1: enable"
   ::= { gs2326pplusIPv6Current 1 }

gs2326pplusIpv6CurrentAddress OBJECT-TYPE
   SYNTAX      DisplayString (SIZE (0..30))
   MAX-ACCESS  read-only
   STATUS      current
   DESCRIPTION
       ""
   ::= { gs2326pplusIPv6Current 2 }


gs2326pplusIpv6CurrentLinkLocalAddress OBJECT-TYPE
   SYNTAX      DisplayString(SIZE (0..30))
   MAX-ACCESS  read-only
   STATUS      current
   DESCRIPTION
       ""
   ::= { gs2326pplusIPv6Current 3 }


gs2326pplusIpv6CurrentPrefix OBJECT-TYPE
   SYNTAX      DisplayString(SIZE (0..64))
   MAX-ACCESS  read-only
   STATUS      current
   DESCRIPTION
       ""
   ::= { gs2326pplusIPv6Current 4 }

gs2326pplusIpv6CurrentGateway OBJECT-TYPE
   SYNTAX      DisplayString (SIZE (0..30))
   MAX-ACCESS  read-only
   STATUS      current
   DESCRIPTION
       " "
   ::= { gs2326pplusIPv6Current 5 }

gs2326pplusSyslog                                                OBJECT IDENTIFIER ::= { gs2326pplusSystem 5 }

gs2326pplusSyslogConf                                            OBJECT IDENTIFIER ::= { gs2326pplusSyslog 1 }

gs2326pplusServerMode OBJECT-TYPE
   SYNTAX      INTEGER { disable(0), enable(1) }
   MAX-ACCESS  read-write
   STATUS      current
   DESCRIPTION
       "default: 0
       0: disable
       1: enable "
   ::= { gs2326pplusSyslogConf 1 }

gs2326pplusServerAddress1 OBJECT-TYPE
   SYNTAX      IpAddress
   MAX-ACCESS  read-write
   STATUS      current
   DESCRIPTION
       " "
   ::= { gs2326pplusSyslogConf 2 }

gs2326pplusServerAddress2 OBJECT-TYPE
   SYNTAX      IpAddress
   MAX-ACCESS  read-write
   STATUS      current
   DESCRIPTION
       " "
   ::= { gs2326pplusSyslogConf 3 }

gs2326pplusSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2326pplusSyslogConf 4 }

gs2326pplusSyslogDetailedInfo                                    OBJECT IDENTIFIER ::= { gs2326pplusSyslog 2 }

gs2326pplusSyslogDetailedInfoClear OBJECT-TYPE
   SYNTAX      INTEGER { none(0), clear(1) }
   MAX-ACCESS  read-write
   STATUS      current
   DESCRIPTION
      "default: 0
       0 : None  (read only)
       1 : Clear Syslog"
   ::= { gs2326pplusSyslogDetailedInfo 1 }

gs2326pplusSyslogDetailedInfoTable OBJECT-TYPE
  SYNTAX      SEQUENCE OF GS2326PPLUSSyslogDetailedInfoEntry
  MAX-ACCESS  not-accessible
  STATUS      current
  DESCRIPTION
           " "
       ::= { gs2326pplusSyslogDetailedInfo 2 }

gs2326pplusSyslogDetailedInfoEntry OBJECT-TYPE
   SYNTAX      GS2326PPLUSSyslogDetailedInfoEntry
   MAX-ACCESS  not-accessible
   STATUS      current
   DESCRIPTION
           ""
   INDEX    { gs2326pplusSyslogDetailedInfoIndex  }
   ::= { gs2326pplusSyslogDetailedInfoTable 1 }

GS2326PPLUSSyslogDetailedInfoEntry ::= SEQUENCE {
   gs2326pplusSyslogDetailedInfoIndex       Integer32,
   gs2326pplusSyslogDetailedInfoLevel       DisplayString,
   gs2326pplusSyslogDetailedInfoTime        DisplayString,
   gs2326pplusSyslogDetailedInfoMessage     DisplayString
}

gs2326pplusSyslogDetailedInfoIndex OBJECT-TYPE
   SYNTAX      Integer32(1..1024)
   MAX-ACCESS  not-accessible
   STATUS      current
   DESCRIPTION
       " "
   ::= { gs2326pplusSyslogDetailedInfoEntry 1 }

gs2326pplusSyslogDetailedInfoLevel OBJECT-TYPE
   SYNTAX      DisplayString
   MAX-ACCESS  read-only
   STATUS      current
   DESCRIPTION
       " "
   ::= { gs2326pplusSyslogDetailedInfoEntry 2 }

gs2326pplusSyslogDetailedInfoTime OBJECT-TYPE
   SYNTAX      DisplayString(SIZE (0..20))
   MAX-ACCESS  read-only
   STATUS      current
   DESCRIPTION
       " "
   ::= { gs2326pplusSyslogDetailedInfoEntry 3 }

gs2326pplusSyslogDetailedInfoMessage OBJECT-TYPE
   SYNTAX      DisplayString
   MAX-ACCESS  read-only
   STATUS      current
   DESCRIPTION
       " "
   ::= { gs2326pplusSyslogDetailedInfoEntry 4 }


gs2326pplusSnmp                                                OBJECT IDENTIFIER ::= { gs2326pplusSystem 6 }

gs2326pplusSnmpConf                                            OBJECT IDENTIFIER ::= { gs2326pplusSnmp 1 }

gs2326pplusGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2326pplusSnmpConf 1 }

gs2326pplusGetCommunity OBJECT-TYPE
   SYNTAX       DisplayString
   MAX-ACCESS   read-write
   STATUS       current
   DESCRIPTION
       "Get/Set the get-community of the SNMP."
   ::= { gs2326pplusSnmpConf 2 }

gs2326pplusSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2326pplusSnmpConf 3 }

gs2326pplusSetCommunity OBJECT-TYPE
   SYNTAX       DisplayString
   MAX-ACCESS   read-write
   STATUS       current
   DESCRIPTION
       "Get/Set the set-community of the SNMP."
   ::= { gs2326pplusSnmpConf 4 }

gs2326pplusGetCommunityConfTable OBJECT-TYPE
   SYNTAX      SEQUENCE OF GS2326PPLUSGetCommunityConfEntry
   MAX-ACCESS  not-accessible
   STATUS      current
   DESCRIPTION
       " Show get-community of the SNMP. "
   ::= { gs2326pplusSnmpConf 5 }

gs2326pplusGetCommunityConfEntry OBJECT-TYPE
   SYNTAX      GS2326PPLUSGetCommunityConfEntry
   MAX-ACCESS  not-accessible
   STATUS      current
   DESCRIPTION
       ""
   INDEX    { gs2326pplusCommunityConfIndex  }
   ::= { gs2326pplusGetCommunityConfTable 1 }

GS2326PPLUSGetCommunityConfEntry ::= SEQUENCE {
   gs2326pplusCommunityConfIndex				Integer32,
   gs2326pplusCommunityConfGetCommunity			DisplayString
}

gs2326pplusCommunityConfIndex OBJECT-TYPE
   SYNTAX      Integer32(1..4095)
   MAX-ACCESS  not-accessible
   STATUS      current
   DESCRIPTION
       " index, range : 1 - 5. "
   ::= { gs2326pplusGetCommunityConfEntry 1 }

gs2326pplusCommunityConfGetCommunity OBJECT-TYPE
   SYNTAX      DisplayString
   MAX-ACCESS  read-write
   STATUS      current
   DESCRIPTION
       " Get/Set the get-community of the SNMP."
   ::= { gs2326pplusGetCommunityConfEntry 2 }

gs2326pplusTrapHostConfTable OBJECT-TYPE
   SYNTAX      SEQUENCE OF GS2326PPLUSTrapHostConfEntry
   MAX-ACCESS  not-accessible
   STATUS      current
   DESCRIPTION
       "A list of trap host entry. The numbers of entries are given by the value of gs2326pplusTrapHostConfNumber."
   ::= { gs2326pplusSnmpConf 6 }

gs2326pplusTrapHostConfEntry OBJECT-TYPE
   SYNTAX      GS2326PPLUSTrapHostConfEntry
   MAX-ACCESS  not-accessible
   STATUS      current
   DESCRIPTION
       "This is the entry information for trap host."
   INDEX    { gs2326pplusTrapHostConfIndex  }
   ::= { gs2326pplusTrapHostConfTable 1 }

GS2326PPLUSTrapHostConfEntry ::= SEQUENCE {
    gs2326pplusTrapHostConfIndex             Integer32,
    gs2326pplusTrapHostConfVersion           INTEGER,
    gs2326pplusTrapHostConfIPType            INTEGER,
    gs2326pplusTrapHostConfIP                DisplayString,
    gs2326pplusTrapHostConfPort              Integer32,
    gs2326pplusTrapHostConfCommunity         DisplayString,
    gs2326pplusTrapHostConfSeverityLevel     INTEGER,
    gs2326pplusTrapHostConfSecurityLevel     INTEGER,
    gs2326pplusTrapHostConfAuthPtc           INTEGER,
    gs2326pplusTrapHostConfAuthPassword      DisplayString,
    gs2326pplusTrapHostConfPrivPtc           INTEGER,
    gs2326pplusTrapHostConfPrivPassword      DisplayString,
    gs2326pplusTrapHostConfCurrentMode       INTEGER
}

gs2326pplusTrapHostConfIndex OBJECT-TYPE
   SYNTAX      Integer32(1..6)
   MAX-ACCESS  not-accessible
   STATUS      current
   DESCRIPTION
       " The index of the trap host entry. "
   ::= { gs2326pplusTrapHostConfEntry 1 }

gs2326pplusTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2326pplusTrapHostConfEntry 2 }

gs2326pplusTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2326pplusTrapHostConfEntry 3 }

gs2326pplusTrapHostConfIP OBJECT-TYPE
   SYNTAX       DisplayString
   MAX-ACCESS   read-write
   STATUS       current
   DESCRIPTION
       "This is the IP of the trap host."
   ::= { gs2326pplusTrapHostConfEntry 4 }

gs2326pplusTrapHostConfPort OBJECT-TYPE
   SYNTAX       Integer32(1..65535)
   MAX-ACCESS   read-write
   STATUS       current
   DESCRIPTION
       "This is the receiving-port number of the trap host.
        range : 1 - 65535."
   ::= { gs2326pplusTrapHostConfEntry 5 }

gs2326pplusTrapHostConfCommunity OBJECT-TYPE
   SYNTAX       DisplayString (SIZE (1..32))
   MAX-ACCESS   read-write
   STATUS       current
   DESCRIPTION
       "The community/security name for the trap PDU."
   ::= { gs2326pplusTrapHostConfEntry 6 }

gs2326pplusTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2326pplusTrapHostConfEntry 7 }

gs2326pplusTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2326pplusTrapHostConfEntry 8 }

gs2326pplusTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2326pplusTrapHostConfEntry 9 }

gs2326pplusTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2326pplusTrapHostConfEntry 10 }

gs2326pplusTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2326pplusTrapHostConfEntry 11 }

gs2326pplusTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2326pplusTrapHostConfEntry 12 }

gs2326pplusTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2326pplusTrapHostConfEntry 13 }


gs2326pplusSnmpSystem                                          OBJECT IDENTIFIER ::= { gs2326pplusSnmp 2 }

gs2326pplusSnmpState OBJECT-TYPE
   SYNTAX       INTEGER { disable(0), enable(1) }
   MAX-ACCESS   read-write
   STATUS       current
   DESCRIPTION
       "Get/Set the state of the SNMP.
        default : 1, 0: disable, 1: enable. "
   ::= { gs2326pplusSnmpSystem 1 }

gs2326pplusSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2326pplusSnmpSystem 2 }

gs2326pplusSnmpCommunities                                          OBJECT IDENTIFIER ::= { gs2326pplusSnmp 3 }

gs2326pplusSnmpCommunitiesCreate OBJECT-TYPE
   SYNTAX       INTEGER { none(0), create(1) }
   MAX-ACCESS   read-write
   STATUS       current
   DESCRIPTION
       "default: 0
        0 : None  (read only)
        1 : Create entry"
   ::= { gs2326pplusSnmpCommunities 1 }

gs2326pplusSnmpCommunitiesTable OBJECT-TYPE
   SYNTAX      SEQUENCE OF GS2326PPLUSSnmpCommunitiesEntry
   MAX-ACCESS  not-accessible
   STATUS      current
   DESCRIPTION
       " Create SNMPv1/v2 Communities entry."
   ::= { gs2326pplusSnmpCommunities 2 }

gs2326pplusSnmpCommunitiesEntry OBJECT-TYPE
   SYNTAX      GS2326PPLUSSnmpCommunitiesEntry
   MAX-ACCESS  not-accessible
   STATUS      current
   DESCRIPTION
       ""
   INDEX    { gs2326pplusSnmpCommunitiesIndex  }
   ::= { gs2326pplusSnmpCommunitiesTable 1 }

GS2326PPLUSSnmpCommunitiesEntry ::= SEQUENCE {
   gs2326pplusSnmpCommunitiesIndex          Integer32,
   gs2326pplusSnmpCommunitiesCommunity      DisplayString,
   gs2326pplusSnmpCommunitiesUserName       DisplayString,
   gs2326pplusSnmpCommunitiesSourceIP       IpAddress,
   gs2326pplusSnmpCommunitiesSourceMask     IpAddress,
   gs2326pplusSnmpCommunitiesRowStatus      INTEGER
}

gs2326pplusSnmpCommunitiesIndex OBJECT-TYPE
   SYNTAX      Integer32(1..4)
   MAX-ACCESS  not-accessible
   STATUS      current
   DESCRIPTION
       " "
   ::= { gs2326pplusSnmpCommunitiesEntry 1 }

gs2326pplusSnmpCommunitiesCommunity OBJECT-TYPE
   SYNTAX      DisplayString (SIZE (1..32))
   MAX-ACCESS  read-write
   STATUS      current
   DESCRIPTION
       "Up to 32 characters describing Community."
   ::= { gs2326pplusSnmpCommunitiesEntry 2 }

gs2326pplusSnmpCommunitiesUserName OBJECT-TYPE
   SYNTAX      DisplayString (SIZE (1..32))
   MAX-ACCESS  read-write
   STATUS      current
   DESCRIPTION
       " Up to 32 characters describing User Name. "
   ::= { gs2326pplusSnmpCommunitiesEntry 3 }

gs2326pplusSnmpCommunitiesSourceIP OBJECT-TYPE
   SYNTAX      IpAddress
   MAX-ACCESS  read-write
   STATUS      current
   DESCRIPTION
       " SNMP access source ip. "
   ::= { gs2326pplusSnmpCommunitiesEntry 4 }

gs2326pplusSnmpCommunitiesSourceMask OBJECT-TYPE
   SYNTAX      IpAddress
   MAX-ACCESS  read-write
   STATUS      current
   DESCRIPTION
       " SNMP access source address mask. "
   ::= { gs2326pplusSnmpCommunitiesEntry 5 }

gs2326pplusSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusSnmpCommunitiesEntry 6 }


gs2326pplusSnmpUsers                                          OBJECT IDENTIFIER ::= { gs2326pplusSnmp 4 }

gs2326pplusSnmpUsersCreate OBJECT-TYPE
   SYNTAX       INTEGER { none(0), create(1) }
   MAX-ACCESS   read-write
   STATUS       current
   DESCRIPTION
       "default: 0
        0 : None  (read only)
        1 : Create entry"
   ::= { gs2326pplusSnmpUsers 1 }

gs2326pplusSnmpUsersTable OBJECT-TYPE
   SYNTAX      SEQUENCE OF GS2326PPLUSSnmpUsersEntry
   MAX-ACCESS  not-accessible
   STATUS      current
   DESCRIPTION
       " Create SNMPv3 users entry."
   ::= { gs2326pplusSnmpUsers 2 }

gs2326pplusSnmpUsersEntry OBJECT-TYPE
   SYNTAX      GS2326PPLUSSnmpUsersEntry
   MAX-ACCESS  not-accessible
   STATUS      current
   DESCRIPTION
       ""
   INDEX    { gs2326pplusSnmpUsersIndex  }
   ::= { gs2326pplusSnmpUsersTable 1 }

GS2326PPLUSSnmpUsersEntry ::= SEQUENCE {
   gs2326pplusSnmpUsersIndex                    Integer32,
   gs2326pplusSnmpUsersUserName                 DisplayString,
   gs2326pplusSnmpUsersSecurityLevel            INTEGER,
   gs2326pplusSnmpUsersAuthenticationProtocol   INTEGER,
   gs2326pplusSnmpUsersAuthenticationPassword   DisplayString,
   gs2326pplusSnmpUsersPrivacyProtocol          INTEGER,
   gs2326pplusSnmpUsersPrivacyPassword          DisplayString,
   gs2326pplusSnmpUsersRowStatus                INTEGER
}

gs2326pplusSnmpUsersIndex OBJECT-TYPE
   SYNTAX      Integer32(1..10)
   MAX-ACCESS  not-accessible
   STATUS      current
   DESCRIPTION
       " "
   ::= { gs2326pplusSnmpUsersEntry 1 }

gs2326pplusSnmpUsersUserName OBJECT-TYPE
   SYNTAX      DisplayString (SIZE (1..32))
   MAX-ACCESS  read-write
   STATUS      current
   DESCRIPTION
       "Up to 32 characters describing User Name."
   ::= { gs2326pplusSnmpUsersEntry 2 }

gs2326pplusSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2326pplusSnmpUsersEntry 3 }

gs2326pplusSnmpUsersAuthenticationProtocol OBJECT-TYPE
   SYNTAX      INTEGER { none(0), md5(1), sha(2) }
   MAX-ACCESS  read-write
   STATUS      current
   DESCRIPTION
       " 0: None.
         1: MD5.
         2: SHA "
   ::= { gs2326pplusSnmpUsersEntry 4 }

gs2326pplusSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2326pplusSnmpUsersEntry 5 }

gs2326pplusSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2326pplusSnmpUsersEntry 6 }

gs2326pplusSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2326pplusSnmpUsersEntry 7 }

gs2326pplusSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusSnmpUsersEntry 8 }


gs2326pplusSnmpGroups                                          OBJECT IDENTIFIER ::= { gs2326pplusSnmp 5 }

gs2326pplusSnmpGroupsCreate OBJECT-TYPE
   SYNTAX       INTEGER { none(0), create(1) }
   MAX-ACCESS   read-write
   STATUS       current
   DESCRIPTION
       "default: 0
        0 : None  (read only)
        1 : Create entry"
   ::= { gs2326pplusSnmpGroups 1 }

gs2326pplusSnmpGroupsTable OBJECT-TYPE
   SYNTAX      SEQUENCE OF GS2326PPLUSSnmpGroupsEntry
   MAX-ACCESS  not-accessible
   STATUS      current
   DESCRIPTION
       " Create SNMPv3 groups entry."
   ::= { gs2326pplusSnmpGroups 2 }

gs2326pplusSnmpGroupsEntry OBJECT-TYPE
   SYNTAX      GS2326PPLUSSnmpGroupsEntry
   MAX-ACCESS  not-accessible
   STATUS      current
   DESCRIPTION
       ""
   INDEX    { gs2326pplusSnmpGroupsIndex  }
   ::= { gs2326pplusSnmpGroupsTable 1 }

GS2326PPLUSSnmpGroupsEntry ::= SEQUENCE {
   gs2326pplusSnmpGroupsIndex           Integer32,
   gs2326pplusSnmpGroupsSecurityModel   INTEGER,
   gs2326pplusSnmpGroupsSecurityName    DisplayString,
   gs2326pplusSnmpGroupsGroupName       DisplayString,
   gs2326pplusSnmpGroupsRowStatus       INTEGER
}

gs2326pplusSnmpGroupsIndex OBJECT-TYPE
   SYNTAX      Integer32(1..14)
   MAX-ACCESS  not-accessible
   STATUS      current
   DESCRIPTION
       " "
   ::= { gs2326pplusSnmpGroupsEntry 1 }

gs2326pplusSnmpGroupsSecurityModel OBJECT-TYPE
   SYNTAX      INTEGER { v1(1), v2c(2), usm(3) }
   MAX-ACCESS  read-write
   STATUS      current
   DESCRIPTION
       " 1: v1.
         2: v2c.
         3: usm."
   ::= { gs2326pplusSnmpGroupsEntry 2 }

gs2326pplusSnmpGroupsSecurityName OBJECT-TYPE
   SYNTAX      DisplayString (SIZE (1..32))
   MAX-ACCESS  read-write
   STATUS      current
   DESCRIPTION
       "Up to 32 characters describing User Name."
   ::= { gs2326pplusSnmpGroupsEntry 3 }

gs2326pplusSnmpGroupsGroupName OBJECT-TYPE
   SYNTAX      DisplayString (SIZE (1..32))
   MAX-ACCESS  read-write
   STATUS      current
   DESCRIPTION
       "Up to 32 characters describing Group Name."
   ::= { gs2326pplusSnmpGroupsEntry 4 }

gs2326pplusSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusSnmpGroupsEntry 5 }

gs2326pplusSnmpViews                                              OBJECT IDENTIFIER ::= { gs2326pplusSnmp 6 }

gs2326pplusSnmpViewsCreate OBJECT-TYPE
   SYNTAX       INTEGER { none(0), create(1) }
   MAX-ACCESS   read-write
   STATUS       current
   DESCRIPTION
       "default: 0
        0 : None  (read only)
        1 : Create entry"
   ::= { gs2326pplusSnmpViews 1 }

gs2326pplusSnmpViewsTable OBJECT-TYPE
   SYNTAX      SEQUENCE OF GS2326PPLUSSnmpViewsEntry
   MAX-ACCESS  not-accessible
   STATUS      current
   DESCRIPTION
       " Create SNMPv1/v2 Views entry."
   ::= { gs2326pplusSnmpViews 2 }

gs2326pplusSnmpViewsEntry OBJECT-TYPE
   SYNTAX      GS2326PPLUSSnmpViewsEntry
   MAX-ACCESS  not-accessible
   STATUS      current
   DESCRIPTION
       ""
   INDEX    { gs2326pplusSnmpViewsIndex  }
   ::= { gs2326pplusSnmpViewsTable 1 }

GS2326PPLUSSnmpViewsEntry ::= SEQUENCE {
   gs2326pplusSnmpViewsIndex        Integer32,
   gs2326pplusSnmpViewsName         DisplayString,
   gs2326pplusSnmpViewsType         INTEGER,
   gs2326pplusSnmpViewsOIDSubtree   DisplayString,
   gs2326pplusSnmpViewsRowStatus    INTEGER
}

gs2326pplusSnmpViewsIndex OBJECT-TYPE
   SYNTAX      Integer32(1..4)
   MAX-ACCESS  not-accessible
   STATUS      current
   DESCRIPTION
       " "
   ::= { gs2326pplusSnmpViewsEntry 1 }

gs2326pplusSnmpViewsName OBJECT-TYPE
   SYNTAX      DisplayString (SIZE (1..32))
   MAX-ACCESS  read-write
   STATUS      current
   DESCRIPTION
       "Up to 32 characters describing view Name."
   ::= { gs2326pplusSnmpViewsEntry 2 }

gs2326pplusSnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2326pplusSnmpViewsEntry 3 }

gs2326pplusSnmpViewsOIDSubtree OBJECT-TYPE
   SYNTAX      DisplayString (SIZE (1..128))
   MAX-ACCESS  read-write
   STATUS      current
   DESCRIPTION
       "The OID defining the root of the subtree to add to the named view."
   ::= { gs2326pplusSnmpViewsEntry 4 }

gs2326pplusSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusSnmpViewsEntry 5 }


gs2326pplusSnmpAccess                                          OBJECT IDENTIFIER ::= { gs2326pplusSnmp 7 }

gs2326pplusSnmpAccessCreate OBJECT-TYPE
   SYNTAX       INTEGER { none(0), create(1) }
   MAX-ACCESS   read-write
   STATUS       current
   DESCRIPTION
       "default: 0
        0 : None  (read only)
        1 : Create entry"
   ::= { gs2326pplusSnmpAccess 1 }

gs2326pplusSnmpAccessTable OBJECT-TYPE
   SYNTAX      SEQUENCE OF GS2326PPLUSSnmpAccessEntry
   MAX-ACCESS  not-accessible
   STATUS      current
   DESCRIPTION
       " Create SNMPv3 Access entry."
   ::= { gs2326pplusSnmpAccess 2 }

gs2326pplusSnmpAccessEntry OBJECT-TYPE
   SYNTAX      GS2326PPLUSSnmpAccessEntry
   MAX-ACCESS  not-accessible
   STATUS      current
   DESCRIPTION
       ""
   INDEX    { gs2326pplusSnmpAccessIndex  }
   ::= { gs2326pplusSnmpAccessTable 1 }

GS2326PPLUSSnmpAccessEntry ::= SEQUENCE {
   gs2326pplusSnmpAccessIndex             Integer32,
   gs2326pplusSnmpAccessGroupName         DisplayString,
   gs2326pplusSnmpAccessSecurityModel     INTEGER,
   gs2326pplusSnmpAccessSecurityLevel     INTEGER,
   gs2326pplusSnmpAccessReadViewName      DisplayString,
   gs2326pplusSnmpAccessWriteViewName     DisplayString,
   gs2326pplusSnmpAccessRowStatus         INTEGER
}

gs2326pplusSnmpAccessIndex OBJECT-TYPE
   SYNTAX      Integer32(1..14)
   MAX-ACCESS  not-accessible
   STATUS      current
   DESCRIPTION
       " "
   ::= { gs2326pplusSnmpAccessEntry 1 }

gs2326pplusSnmpAccessGroupName OBJECT-TYPE
   SYNTAX      DisplayString (SIZE (1..32))
   MAX-ACCESS  read-write
   STATUS      current
   DESCRIPTION
       "Up to 32 characters describing Group Name."
   ::= { gs2326pplusSnmpAccessEntry 2 }

gs2326pplusSnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2326pplusSnmpAccessEntry 3 }

gs2326pplusSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2326pplusSnmpAccessEntry 4 }

gs2326pplusSnmpAccessReadViewName OBJECT-TYPE
   SYNTAX      DisplayString (SIZE (1..32))
   MAX-ACCESS  read-write
   STATUS      current
   DESCRIPTION
       "Up to 32 characters describing Read View Name.
        None is reserved for Empty."
   ::= { gs2326pplusSnmpAccessEntry 5 }

gs2326pplusSnmpAccessWriteViewName OBJECT-TYPE
   SYNTAX      DisplayString (SIZE (1..32))
   MAX-ACCESS  read-write
   STATUS      current
   DESCRIPTION
       "Up to 32 characters describing Write View Name.
        None is reserved for Empty."
   ::= { gs2326pplusSnmpAccessEntry 6 }

gs2326pplusSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusSnmpAccessEntry 7 }


----------------------------------------------------------------------------------------------------

gs2326pplusConfiguration                                         OBJECT IDENTIFIER ::= { lancomGS2326Pplus  2 }

gs2326pplusPort                                                  OBJECT IDENTIFIER ::= { gs2326pplusConfiguration 1 }

gs2326pplusPortConfigurationTable OBJECT-TYPE
   SYNTAX      SEQUENCE OF GS2326PPLUSPortConfigurationEntry
   MAX-ACCESS  not-accessible
   STATUS      current
   DESCRIPTION
       " Show port configurations. "
   ::= { gs2326pplusPort 1 }

gs2326pplusPortConfigurationEntry OBJECT-TYPE
   SYNTAX      GS2326PPLUSPortConfigurationEntry
   MAX-ACCESS  not-accessible
   STATUS      current
   DESCRIPTION
       ""
   INDEX    { gs2326pplusPortConfPort  }
   ::= { gs2326pplusPortConfigurationTable 1 }

GS2326PPLUSPortConfigurationEntry ::= SEQUENCE {
   gs2326pplusPortConfPort                     Integer32,
   gs2326pplusPortConfPortMedia                DisplayString,
   gs2326pplusPortConfLink                     DisplayString,
   gs2326pplusPortConfCurrentSpeed             DisplayString,
   gs2326pplusPortConfSpeed                    INTEGER,
   gs2326pplusPortConfCurrentFlowControlRx     INTEGER,
   gs2326pplusPortConfCurrentFlowControlTx     INTEGER,
   gs2326pplusPortConfFlowControl              INTEGER,
   gs2326pplusPortConfMaxFrameSize             Integer32,
   gs2326pplusPortConfExcessiveCollisionMode   INTEGER,
   gs2326pplusPortConfPowerControl             INTEGER,
   gs2326pplusPortConfDescription              DisplayString
}

gs2326pplusPortConfPort OBJECT-TYPE
   SYNTAX      Integer32(1..4095)
   MAX-ACCESS  not-accessible
   STATUS      current
   DESCRIPTION
       " port, range : 1 - port number. "
   ::= { gs2326pplusPortConfigurationEntry 1 }

gs2326pplusPortConfPortMedia OBJECT-TYPE
   SYNTAX      DisplayString(SIZE (1..4))
   MAX-ACCESS  read-only
   STATUS      current
   DESCRIPTION
       " Show port media. "
   ::= { gs2326pplusPortConfigurationEntry 2 }

gs2326pplusPortConfLink OBJECT-TYPE
   SYNTAX      DisplayString(SIZE (2..4))
   MAX-ACCESS  read-only
   STATUS      current
   DESCRIPTION
       " The current link state. "
   ::= { gs2326pplusPortConfigurationEntry 3 }

gs2326pplusPortConfCurrentSpeed OBJECT-TYPE
   SYNTAX      DisplayString(SIZE (6..12))
   MAX-ACCESS  read-only
   STATUS      current
   DESCRIPTION
       " The current link speed of the port. "
   ::= { gs2326pplusPortConfigurationEntry 4 }

gs2326pplusPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { gs2326pplusPortConfigurationEntry 5 }

gs2326pplusPortConfCurrentFlowControlRx OBJECT-TYPE
   SYNTAX      INTEGER { disable(0), enable(1), noSupport(2) }
   MAX-ACCESS  read-only
   STATUS      current
   DESCRIPTION
       "0: disable
        1: enable
        2: no support.  "
   ::= { gs2326pplusPortConfigurationEntry 6 }

gs2326pplusPortConfCurrentFlowControlTx OBJECT-TYPE
   SYNTAX      INTEGER { disable(0), enable(1), noSupport(2) }
   MAX-ACCESS  read-only
   STATUS      current
   DESCRIPTION
       "0: disable
        1: enable
        2: no support.  "
   ::= { gs2326pplusPortConfigurationEntry 7 }

gs2326pplusPortConfFlowControl OBJECT-TYPE
   SYNTAX      INTEGER { disable(0), enable(1), noSupport(2) }
   MAX-ACCESS  read-write
   STATUS      current
   DESCRIPTION
       "default: 0,
        0: disable
        1: enable
        2: no support. "
   ::= { gs2326pplusPortConfigurationEntry 8 }

gs2326pplusPortConfMaxFrameSize OBJECT-TYPE
   SYNTAX      Integer32 (1518..9600)
   MAX-ACCESS  read-write
   STATUS      current
   DESCRIPTION
       "default: 9600 , range : 1518 - 9600 "
   ::= { gs2326pplusPortConfigurationEntry 9 }

gs2326pplusPortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2326pplusPortConfigurationEntry 10 }

gs2326pplusPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2326pplusPortConfigurationEntry 11 }

gs2326pplusPortConfDescription OBJECT-TYPE
   SYNTAX      DisplayString
   MAX-ACCESS  read-write
   STATUS      current
   DESCRIPTION
       " Interface specific description.
         Up to 47 characters describing this interface. "
   ::= { gs2326pplusPortConfigurationEntry 12 }


gs2326pplusPortTrafficStatisticsTable OBJECT-TYPE
   SYNTAX      SEQUENCE OF GS2326PPLUSPortTrafficStatisticsEntry
   MAX-ACCESS  not-accessible
   STATUS      current
   DESCRIPTION
       " "
   ::= { gs2326pplusPort 2 }

gs2326pplusPortTrafficStatisticsEntry OBJECT-TYPE
   SYNTAX      GS2326PPLUSPortTrafficStatisticsEntry
   MAX-ACCESS  not-accessible
   STATUS      current
   DESCRIPTION
       ""
   INDEX    { gs2326pplusPortTrafficStatisticsPort  }
   ::= { gs2326pplusPortTrafficStatisticsTable 1 }

GS2326PPLUSPortTrafficStatisticsEntry ::= SEQUENCE {
   gs2326pplusPortTrafficStatisticsPort          Integer32,
   gs2326pplusPortTrafficStatisticsClear         INTEGER,
   gs2326pplusPortTrafficRxPackets               Counter64,
   gs2326pplusPortTrafficRxOctets                Counter64,
   gs2326pplusPortTrafficRxUnicast               Counter64,
   gs2326pplusPortTrafficRxMulticast             Counter64,
   gs2326pplusPortTrafficRxBroadcast             Counter64,
   gs2326pplusPortTrafficRxPause                 Counter64,
   gs2326pplusPortTrafficRx64Bytes               Counter64,
   gs2326pplusPortTrafficRx65to127Bytes          Counter64,
   gs2326pplusPortTrafficRx128to255Bytes         Counter64,
   gs2326pplusPortTrafficRx256to511Bytes         Counter64,
   gs2326pplusPortTrafficRx512to1023Bytes        Counter64,
   gs2326pplusPortTrafficRx1024to1526Bytes       Counter64,
   gs2326pplusPortTrafficRxExceecd1527Bytes      Counter64,
   gs2326pplusPortTrafficRxQ0                    Counter64,
   gs2326pplusPortTrafficRxQ1                    Counter64,
   gs2326pplusPortTrafficRxQ2                    Counter64,
   gs2326pplusPortTrafficRxQ3                    Counter64,
   gs2326pplusPortTrafficRxQ4                    Counter64,
   gs2326pplusPortTrafficRxQ5                    Counter64,
   gs2326pplusPortTrafficRxQ6                    Counter64,
   gs2326pplusPortTrafficRxQ7                    Counter64,
   gs2326pplusPortTrafficRxDrops                 Counter64,
   gs2326pplusPortTrafficRxCRCorAlignment        Counter64,
   gs2326pplusPortTrafficRxUndersize             Counter64,
   gs2326pplusPortTrafficRxOversize              Counter64,
   gs2326pplusPortTrafficRxFragments             Counter64,
   gs2326pplusPortTrafficRxJabber                Counter64,
   gs2326pplusPortTrafficRxFiltered              Counter64,
   gs2326pplusPortTrafficTxPackets               Counter64,
   gs2326pplusPortTrafficTxOctets                Counter64,
   gs2326pplusPortTrafficTxUnicast               Counter64,
   gs2326pplusPortTrafficTxMulticast             Counter64,
   gs2326pplusPortTrafficTxBroadcast             Counter64,
   gs2326pplusPortTrafficTxPause                 Counter64,
   gs2326pplusPortTrafficTx64Bytes               Counter64,
   gs2326pplusPortTrafficTx65to127Bytes          Counter64,
   gs2326pplusPortTrafficTx128to255Bytes         Counter64,
   gs2326pplusPortTrafficTx256to511Bytes         Counter64,
   gs2326pplusPortTrafficTx512to1023Bytes        Counter64,
   gs2326pplusPortTrafficTx1024to1526Bytes       Counter64,
   gs2326pplusPortTrafficTxExceecd1527Bytes      Counter64,
   gs2326pplusPortTrafficTxQ0                    Counter64,
   gs2326pplusPortTrafficTxQ1                    Counter64,
   gs2326pplusPortTrafficTxQ2                    Counter64,
   gs2326pplusPortTrafficTxQ3                    Counter64,
   gs2326pplusPortTrafficTxQ4                    Counter64,
   gs2326pplusPortTrafficTxQ5                    Counter64,
   gs2326pplusPortTrafficTxQ6                    Counter64,
   gs2326pplusPortTrafficTxQ7                    Counter64,
   gs2326pplusPortTrafficTxDrops                 Counter64,
   gs2326pplusPortTrafficTxLateOrExcColl         Counter64
}

gs2326pplusPortTrafficStatisticsPort OBJECT-TYPE
   SYNTAX      Integer32 (1..4095)
   MAX-ACCESS  not-accessible
   STATUS      current
   DESCRIPTION
       " "
   ::= { gs2326pplusPortTrafficStatisticsEntry 1 }

gs2326pplusPortTrafficStatisticsClear OBJECT-TYPE
   SYNTAX      INTEGER { disable(0), enable(1) }
   MAX-ACCESS  read-write
   STATUS      current
   DESCRIPTION
       " "
   ::= { gs2326pplusPortTrafficStatisticsEntry 2 }

gs2326pplusPortTrafficRxPackets OBJECT-TYPE
   SYNTAX      Counter64
   MAX-ACCESS  read-only
   STATUS      current
   DESCRIPTION
       " "
   ::= { gs2326pplusPortTrafficStatisticsEntry 3 }

gs2326pplusPortTrafficRxOctets OBJECT-TYPE
   SYNTAX      Counter64
   MAX-ACCESS  read-only
   STATUS      current
   DESCRIPTION
       " "
   ::= { gs2326pplusPortTrafficStatisticsEntry 4 }

gs2326pplusPortTrafficRxUnicast OBJECT-TYPE
   SYNTAX      Counter64
   MAX-ACCESS  read-only
   STATUS      current
   DESCRIPTION
       " "
   ::= { gs2326pplusPortTrafficStatisticsEntry 5 }

gs2326pplusPortTrafficRxMulticast OBJECT-TYPE
   SYNTAX      Counter64
   MAX-ACCESS  read-only
   STATUS      current
   DESCRIPTION
       " "
   ::= { gs2326pplusPortTrafficStatisticsEntry 6 }

gs2326pplusPortTrafficRxBroadcast OBJECT-TYPE
   SYNTAX      Counter64
   MAX-ACCESS  read-only
   STATUS      current
   DESCRIPTION
       " "
   ::= { gs2326pplusPortTrafficStatisticsEntry 7 }

gs2326pplusPortTrafficRxPause OBJECT-TYPE
   SYNTAX      Counter64
   MAX-ACCESS  read-only
   STATUS      current
   DESCRIPTION
       " "
   ::= { gs2326pplusPortTrafficStatisticsEntry 8 }

gs2326pplusPortTrafficRx64Bytes OBJECT-TYPE
   SYNTAX      Counter64
   MAX-ACCESS  read-only
   STATUS      current
   DESCRIPTION
       " "
   ::= { gs2326pplusPortTrafficStatisticsEntry 9 }

gs2326pplusPortTrafficRx65to127Bytes OBJECT-TYPE
   SYNTAX      Counter64
   MAX-ACCESS  read-only
   STATUS      current
   DESCRIPTION
       " "
   ::= { gs2326pplusPortTrafficStatisticsEntry 10 }

gs2326pplusPortTrafficRx128to255Bytes OBJECT-TYPE
   SYNTAX      Counter64
   MAX-ACCESS  read-only
   STATUS      current
   DESCRIPTION
       " "
   ::= { gs2326pplusPortTrafficStatisticsEntry 11 }

gs2326pplusPortTrafficRx256to511Bytes OBJECT-TYPE
   SYNTAX      Counter64
   MAX-ACCESS  read-only
   STATUS      current
   DESCRIPTION
       " "
   ::= { gs2326pplusPortTrafficStatisticsEntry 12 }

gs2326pplusPortTrafficRx512to1023Bytes OBJECT-TYPE
   SYNTAX      Counter64
   MAX-ACCESS  read-only
   STATUS      current
   DESCRIPTION
       " "
   ::= { gs2326pplusPortTrafficStatisticsEntry 13 }

gs2326pplusPortTrafficRx1024to1526Bytes OBJECT-TYPE
   SYNTAX      Counter64
   MAX-ACCESS  read-only
   STATUS      current
   DESCRIPTION
       " "
   ::= { gs2326pplusPortTrafficStatisticsEntry 14 }

gs2326pplusPortTrafficRxExceecd1527Bytes OBJECT-TYPE
   SYNTAX      Counter64
   MAX-ACCESS  read-only
   STATUS      current
   DESCRIPTION
       " "
   ::= { gs2326pplusPortTrafficStatisticsEntry 15 }

gs2326pplusPortTrafficRxQ0 OBJECT-TYPE
   SYNTAX      Counter64
   MAX-ACCESS  read-only
   STATUS      current
   DESCRIPTION
       " "
   ::= { gs2326pplusPortTrafficStatisticsEntry 16 }

gs2326pplusPortTrafficRxQ1 OBJECT-TYPE
   SYNTAX      Counter64
   MAX-ACCESS  read-only
   STATUS      current
   DESCRIPTION
       " "
   ::= { gs2326pplusPortTrafficStatisticsEntry 17 }

gs2326pplusPortTrafficRxQ2 OBJECT-TYPE
   SYNTAX      Counter64
   MAX-ACCESS  read-only
   STATUS      current
   DESCRIPTION
       " "
   ::= { gs2326pplusPortTrafficStatisticsEntry 18 }

gs2326pplusPortTrafficRxQ3 OBJECT-TYPE
   SYNTAX      Counter64
   MAX-ACCESS  read-only
   STATUS      current
   DESCRIPTION
       " "
   ::= { gs2326pplusPortTrafficStatisticsEntry 19 }

gs2326pplusPortTrafficRxQ4 OBJECT-TYPE
   SYNTAX      Counter64
   MAX-ACCESS  read-only
   STATUS      current
   DESCRIPTION
       " "
   ::= { gs2326pplusPortTrafficStatisticsEntry 20 }

gs2326pplusPortTrafficRxQ5 OBJECT-TYPE
   SYNTAX      Counter64
   MAX-ACCESS  read-only
   STATUS      current
   DESCRIPTION
       " "
   ::= { gs2326pplusPortTrafficStatisticsEntry 21 }

gs2326pplusPortTrafficRxQ6 OBJECT-TYPE
   SYNTAX      Counter64
   MAX-ACCESS  read-only
   STATUS      current
   DESCRIPTION
       " "
   ::= { gs2326pplusPortTrafficStatisticsEntry 22 }

gs2326pplusPortTrafficRxQ7 OBJECT-TYPE
   SYNTAX      Counter64
   MAX-ACCESS  read-only
   STATUS      current
   DESCRIPTION
       " "
   ::= { gs2326pplusPortTrafficStatisticsEntry 23 }

gs2326pplusPortTrafficRxDrops OBJECT-TYPE
   SYNTAX      Counter64
   MAX-ACCESS  read-only
   STATUS      current
   DESCRIPTION
       " "
   ::= { gs2326pplusPortTrafficStatisticsEntry 24 }

gs2326pplusPortTrafficRxCRCorAlignment OBJECT-TYPE
   SYNTAX      Counter64
   MAX-ACCESS  read-only
   STATUS      current
   DESCRIPTION
       " "
   ::= { gs2326pplusPortTrafficStatisticsEntry 25 }

gs2326pplusPortTrafficRxUndersize OBJECT-TYPE
   SYNTAX      Counter64
   MAX-ACCESS  read-only
   STATUS      current
   DESCRIPTION
       " "
   ::= { gs2326pplusPortTrafficStatisticsEntry 26 }

gs2326pplusPortTrafficRxOversize OBJECT-TYPE
   SYNTAX      Counter64
   MAX-ACCESS  read-only
   STATUS      current
   DESCRIPTION
       " "
   ::= { gs2326pplusPortTrafficStatisticsEntry 27 }

gs2326pplusPortTrafficRxFragments OBJECT-TYPE
   SYNTAX      Counter64
   MAX-ACCESS  read-only
   STATUS      current
   DESCRIPTION
       " "
   ::= { gs2326pplusPortTrafficStatisticsEntry 28 }

gs2326pplusPortTrafficRxJabber OBJECT-TYPE
   SYNTAX      Counter64
   MAX-ACCESS  read-only
   STATUS      current
   DESCRIPTION
       " "
   ::= { gs2326pplusPortTrafficStatisticsEntry 29 }

gs2326pplusPortTrafficRxFiltered OBJECT-TYPE
   SYNTAX      Counter64
   MAX-ACCESS  read-only
   STATUS      current
   DESCRIPTION
       " "
   ::= { gs2326pplusPortTrafficStatisticsEntry 30 }

gs2326pplusPortTrafficTxPackets OBJECT-TYPE
   SYNTAX      Counter64
   MAX-ACCESS  read-only
   STATUS      current
   DESCRIPTION
       " "
   ::= { gs2326pplusPortTrafficStatisticsEntry 31 }

gs2326pplusPortTrafficTxOctets OBJECT-TYPE
   SYNTAX      Counter64
   MAX-ACCESS  read-only
   STATUS      current
   DESCRIPTION
       " "
   ::= { gs2326pplusPortTrafficStatisticsEntry 32 }

gs2326pplusPortTrafficTxUnicast OBJECT-TYPE
   SYNTAX      Counter64
   MAX-ACCESS  read-only
   STATUS      current
   DESCRIPTION
       " "
   ::= { gs2326pplusPortTrafficStatisticsEntry 33 }

gs2326pplusPortTrafficTxMulticast OBJECT-TYPE
   SYNTAX      Counter64
   MAX-ACCESS  read-only
   STATUS      current
   DESCRIPTION
       " "
   ::= { gs2326pplusPortTrafficStatisticsEntry 34 }

gs2326pplusPortTrafficTxBroadcast OBJECT-TYPE
   SYNTAX      Counter64
   MAX-ACCESS  read-only
   STATUS      current
   DESCRIPTION
       " "
   ::= { gs2326pplusPortTrafficStatisticsEntry 35 }

gs2326pplusPortTrafficTxPause OBJECT-TYPE
   SYNTAX      Counter64
   MAX-ACCESS  read-only
   STATUS      current
   DESCRIPTION
       " "
   ::= { gs2326pplusPortTrafficStatisticsEntry 36 }

gs2326pplusPortTrafficTx64Bytes OBJECT-TYPE
   SYNTAX      Counter64
   MAX-ACCESS  read-only
   STATUS      current
   DESCRIPTION
       " "
   ::= { gs2326pplusPortTrafficStatisticsEntry 37 }

gs2326pplusPortTrafficTx65to127Bytes OBJECT-TYPE
   SYNTAX      Counter64
   MAX-ACCESS  read-only
   STATUS      current
   DESCRIPTION
       " "
   ::= { gs2326pplusPortTrafficStatisticsEntry 38 }

gs2326pplusPortTrafficTx128to255Bytes OBJECT-TYPE
   SYNTAX      Counter64
   MAX-ACCESS  read-only
   STATUS      current
   DESCRIPTION
       " "
   ::= { gs2326pplusPortTrafficStatisticsEntry 39 }

gs2326pplusPortTrafficTx256to511Bytes OBJECT-TYPE
   SYNTAX      Counter64
   MAX-ACCESS  read-only
   STATUS      current
   DESCRIPTION
       " "
   ::= { gs2326pplusPortTrafficStatisticsEntry 40 }

gs2326pplusPortTrafficTx512to1023Bytes OBJECT-TYPE
   SYNTAX      Counter64
   MAX-ACCESS  read-only
   STATUS      current
   DESCRIPTION
       " "
   ::= { gs2326pplusPortTrafficStatisticsEntry 41 }

gs2326pplusPortTrafficTx1024to1526Bytes OBJECT-TYPE
   SYNTAX      Counter64
   MAX-ACCESS  read-only
   STATUS      current
   DESCRIPTION
       " "
   ::= { gs2326pplusPortTrafficStatisticsEntry 42 }

gs2326pplusPortTrafficTxExceecd1527Bytes OBJECT-TYPE
   SYNTAX      Counter64
   MAX-ACCESS  read-only
   STATUS      current
   DESCRIPTION
       " "
   ::= { gs2326pplusPortTrafficStatisticsEntry 43 }

gs2326pplusPortTrafficTxQ0 OBJECT-TYPE
   SYNTAX      Counter64
   MAX-ACCESS  read-only
   STATUS      current
   DESCRIPTION
       " "
   ::= { gs2326pplusPortTrafficStatisticsEntry 44 }

gs2326pplusPortTrafficTxQ1 OBJECT-TYPE
   SYNTAX      Counter64
   MAX-ACCESS  read-only
   STATUS      current
   DESCRIPTION
       " "
   ::= { gs2326pplusPortTrafficStatisticsEntry 45 }

gs2326pplusPortTrafficTxQ2 OBJECT-TYPE
   SYNTAX      Counter64
   MAX-ACCESS  read-only
   STATUS      current
   DESCRIPTION
       " "
   ::= { gs2326pplusPortTrafficStatisticsEntry 46 }

gs2326pplusPortTrafficTxQ3 OBJECT-TYPE
   SYNTAX      Counter64
   MAX-ACCESS  read-only
   STATUS      current
   DESCRIPTION
       " "
   ::= { gs2326pplusPortTrafficStatisticsEntry 47 }

gs2326pplusPortTrafficTxQ4 OBJECT-TYPE
   SYNTAX      Counter64
   MAX-ACCESS  read-only
   STATUS      current
   DESCRIPTION
       " "
   ::= { gs2326pplusPortTrafficStatisticsEntry 48 }

gs2326pplusPortTrafficTxQ5 OBJECT-TYPE
   SYNTAX      Counter64
   MAX-ACCESS  read-only
   STATUS      current
   DESCRIPTION
       " "
   ::= { gs2326pplusPortTrafficStatisticsEntry 49 }

gs2326pplusPortTrafficTxQ6 OBJECT-TYPE
   SYNTAX      Counter64
   MAX-ACCESS  read-only
   STATUS      current
   DESCRIPTION
       " "
   ::= { gs2326pplusPortTrafficStatisticsEntry 50 }


gs2326pplusPortTrafficTxQ7 OBJECT-TYPE
   SYNTAX      Counter64
   MAX-ACCESS  read-only
   STATUS      current
   DESCRIPTION
       " "
   ::= { gs2326pplusPortTrafficStatisticsEntry 51 }

gs2326pplusPortTrafficTxDrops OBJECT-TYPE
   SYNTAX      Counter64
   MAX-ACCESS  read-only
   STATUS      current
   DESCRIPTION
       " "
   ::= { gs2326pplusPortTrafficStatisticsEntry 52 }

gs2326pplusPortTrafficTxLateOrExcColl OBJECT-TYPE
   SYNTAX      Counter64
   MAX-ACCESS  read-only
   STATUS      current
   DESCRIPTION
       " "
   ::= { gs2326pplusPortTrafficStatisticsEntry 53 }


gs2326pplusPortQoSStatistics                                     OBJECT IDENTIFIER ::= { gs2326pplusPort 3 }

gs2326pplusPortQoSStatisticsClear OBJECT-TYPE
   SYNTAX      INTEGER { none(0), clear(1) }
   MAX-ACCESS  read-only
   STATUS      current
   DESCRIPTION
       "default: 0
       0: none
       1: clear "
   ::= { gs2326pplusPortQoSStatistics 1 }

gs2326pplusPortQoSStatisticsTable OBJECT-TYPE
   SYNTAX      SEQUENCE OF GS2326PPLUSPortQoSStatisticsEntry
   MAX-ACCESS  not-accessible
   STATUS      current
   DESCRIPTION
       " "
   ::= { gs2326pplusPortQoSStatistics 2 }

gs2326pplusPortQoSStatisticsEntry OBJECT-TYPE
   SYNTAX      GS2326PPLUSPortQoSStatisticsEntry
   MAX-ACCESS  not-accessible
   STATUS      current
   DESCRIPTION
       ""
   INDEX    { gs2326pplusPortQoSStatisticsPort  }
   ::= { gs2326pplusPortQoSStatisticsTable 1 }

GS2326PPLUSPortQoSStatisticsEntry ::= SEQUENCE {
   gs2326pplusPortQoSStatisticsPort      Integer32,
   gs2326pplusPortQoSQ0Rx                Counter64,
   gs2326pplusPortQoSQ0Tx                Counter64,
   gs2326pplusPortQoSQ1Rx                Counter64,
   gs2326pplusPortQoSQ1Tx                Counter64,
   gs2326pplusPortQoSQ2Rx                Counter64,
   gs2326pplusPortQoSQ2Tx                Counter64,
   gs2326pplusPortQoSQ3Rx                Counter64,
   gs2326pplusPortQoSQ3Tx                Counter64,
   gs2326pplusPortQoSQ4Rx                Counter64,
   gs2326pplusPortQoSQ4Tx                Counter64,
   gs2326pplusPortQoSQ5Rx                Counter64,
   gs2326pplusPortQoSQ5Tx                Counter64,
   gs2326pplusPortQoSQ6Rx                Counter64,
   gs2326pplusPortQoSQ6Tx                Counter64,
   gs2326pplusPortQoSQ7Rx                Counter64,
   gs2326pplusPortQoSQ7Tx                Counter64
}

gs2326pplusPortQoSStatisticsPort OBJECT-TYPE
   SYNTAX      Integer32(1..4095)
   MAX-ACCESS  not-accessible
   STATUS      current
   DESCRIPTION
       " "
   ::= { gs2326pplusPortQoSStatisticsEntry 1 }

gs2326pplusPortQoSQ0Rx OBJECT-TYPE
   SYNTAX      Counter64
   MAX-ACCESS  read-only
   STATUS      current
   DESCRIPTION
       " "
   ::= { gs2326pplusPortQoSStatisticsEntry 2 }

gs2326pplusPortQoSQ0Tx OBJECT-TYPE
   SYNTAX      Counter64
   MAX-ACCESS  read-only
   STATUS      current
   DESCRIPTION
       " "
   ::= { gs2326pplusPortQoSStatisticsEntry 3 }

gs2326pplusPortQoSQ1Rx OBJECT-TYPE
   SYNTAX      Counter64
   MAX-ACCESS  read-only
   STATUS      current
   DESCRIPTION
       " "
   ::= { gs2326pplusPortQoSStatisticsEntry 4 }

gs2326pplusPortQoSQ1Tx OBJECT-TYPE
   SYNTAX      Counter64
   MAX-ACCESS  read-only
   STATUS      current
   DESCRIPTION
       " "
   ::= { gs2326pplusPortQoSStatisticsEntry 5 }

gs2326pplusPortQoSQ2Rx OBJECT-TYPE
   SYNTAX      Counter64
   MAX-ACCESS  read-only
   STATUS      current
   DESCRIPTION
       " "
   ::= { gs2326pplusPortQoSStatisticsEntry 6 }

gs2326pplusPortQoSQ2Tx OBJECT-TYPE
   SYNTAX      Counter64
   MAX-ACCESS  read-only
   STATUS      current
   DESCRIPTION
       " "
   ::= { gs2326pplusPortQoSStatisticsEntry 7 }

gs2326pplusPortQoSQ3Rx OBJECT-TYPE
   SYNTAX      Counter64
   MAX-ACCESS  read-only
   STATUS      current
   DESCRIPTION
       " "
   ::= { gs2326pplusPortQoSStatisticsEntry 8 }

gs2326pplusPortQoSQ3Tx OBJECT-TYPE
   SYNTAX      Counter64
   MAX-ACCESS  read-only
   STATUS      current
   DESCRIPTION
       " "
   ::= { gs2326pplusPortQoSStatisticsEntry 9 }

gs2326pplusPortQoSQ4Rx OBJECT-TYPE
   SYNTAX      Counter64
   MAX-ACCESS  read-only
   STATUS      current
   DESCRIPTION
       " "
   ::= { gs2326pplusPortQoSStatisticsEntry 10 }

gs2326pplusPortQoSQ4Tx OBJECT-TYPE
   SYNTAX      Counter64
   MAX-ACCESS  read-only
   STATUS      current
   DESCRIPTION
       " "
   ::= { gs2326pplusPortQoSStatisticsEntry 11 }

gs2326pplusPortQoSQ5Rx OBJECT-TYPE
   SYNTAX      Counter64
   MAX-ACCESS  read-only
   STATUS      current
   DESCRIPTION
       " "
   ::= { gs2326pplusPortQoSStatisticsEntry 12 }

gs2326pplusPortQoSQ5Tx OBJECT-TYPE
   SYNTAX      Counter64
   MAX-ACCESS  read-only
   STATUS      current
   DESCRIPTION
       " "
   ::= { gs2326pplusPortQoSStatisticsEntry 13 }

gs2326pplusPortQoSQ6Rx OBJECT-TYPE
   SYNTAX      Counter64
   MAX-ACCESS  read-only
   STATUS      current
   DESCRIPTION
       " "
   ::= { gs2326pplusPortQoSStatisticsEntry 14 }

gs2326pplusPortQoSQ6Tx OBJECT-TYPE
   SYNTAX      Counter64
   MAX-ACCESS  read-only
   STATUS      current
   DESCRIPTION
       " "
   ::= { gs2326pplusPortQoSStatisticsEntry 15 }

gs2326pplusPortQoSQ7Rx OBJECT-TYPE
   SYNTAX      Counter64
   MAX-ACCESS  read-only
   STATUS      current
   DESCRIPTION
       " "
   ::= { gs2326pplusPortQoSStatisticsEntry 16 }

gs2326pplusPortQoSQ7Tx OBJECT-TYPE
   SYNTAX      Counter64
   MAX-ACCESS  read-only
   STATUS      current
   DESCRIPTION
       " "
   ::= { gs2326pplusPortQoSStatisticsEntry 17 }

gs2326pplusSFPInfoTable OBJECT-TYPE
   SYNTAX      SEQUENCE OF GS2326PPLUSSFPInfoEntry
   MAX-ACCESS  not-accessible
   STATUS      current
   DESCRIPTION
       " "
   ::= { gs2326pplusPort 4 }

gs2326pplusSFPInfoEntry OBJECT-TYPE
   SYNTAX      GS2326PPLUSSFPInfoEntry
   MAX-ACCESS  not-accessible
   STATUS      current
   DESCRIPTION
       ""
   INDEX    { gs2326pplusSFPInfoIndex }
   ::= { gs2326pplusSFPInfoTable 1 }

GS2326PPLUSSFPInfoEntry ::= SEQUENCE {
   gs2326pplusSFPInfoIndex               Integer32,
   gs2326pplusSFPInfoPort                DisplayString,
   gs2326pplusSFPConnectorType           DisplayString,
   gs2326pplusSFPFiberType               DisplayString,
   gs2326pplusSFPTxCentralWavelength     DisplayString,
   gs2326pplusSFPBaudRate                DisplayString,
   gs2326pplusSFPVendorOUI               DisplayString,
   gs2326pplusSFPVendorName              DisplayString,
   gs2326pplusSFPVendorPN                DisplayString,
   gs2326pplusSFPVendorRev               DisplayString,
   gs2326pplusSFPVendorSN                DisplayString,
   gs2326pplusSFPDateCode                DisplayString,
   gs2326pplusSFPTemperature             DisplayString,
   gs2326pplusSFPVcc                     DisplayString,
   gs2326pplusSFPMon1Bias                DisplayString,
   gs2326pplusSFPMon2TxPWR               DisplayString,
   gs2326pplusSFPMon3RxPWR               DisplayString
}

gs2326pplusSFPInfoIndex OBJECT-TYPE
   SYNTAX      Integer32(1..4095)
   MAX-ACCESS  not-accessible
   STATUS      current
   DESCRIPTION
       " "
   ::= { gs2326pplusSFPInfoEntry 1 }

gs2326pplusSFPInfoPort OBJECT-TYPE
   SYNTAX      DisplayString
   MAX-ACCESS  read-only
   STATUS      current
   DESCRIPTION
       " "
   ::= { gs2326pplusSFPInfoEntry 2 }

gs2326pplusSFPConnectorType OBJECT-TYPE
   SYNTAX      DisplayString
   MAX-ACCESS  read-only
   STATUS      current
   DESCRIPTION
       " "
   ::= { gs2326pplusSFPInfoEntry 3 }

gs2326pplusSFPFiberType OBJECT-TYPE
   SYNTAX      DisplayString
   MAX-ACCESS  read-only
   STATUS      current
   DESCRIPTION
       " "
   ::= { gs2326pplusSFPInfoEntry 4 }

gs2326pplusSFPTxCentralWavelength OBJECT-TYPE
   SYNTAX      DisplayString
   MAX-ACCESS  read-only
   STATUS      current
   DESCRIPTION
       " "
   ::= { gs2326pplusSFPInfoEntry 5 }

gs2326pplusSFPBaudRate OBJECT-TYPE
   SYNTAX      DisplayString
   MAX-ACCESS  read-only
   STATUS      current
   DESCRIPTION
       " "
   ::= { gs2326pplusSFPInfoEntry 6 }

gs2326pplusSFPVendorOUI OBJECT-TYPE
   SYNTAX      DisplayString
   MAX-ACCESS  read-only
   STATUS      current
   DESCRIPTION
       " "
   ::= { gs2326pplusSFPInfoEntry 7 }

gs2326pplusSFPVendorName OBJECT-TYPE
   SYNTAX      DisplayString
   MAX-ACCESS  read-only
   STATUS      current
   DESCRIPTION
       " "
   ::= { gs2326pplusSFPInfoEntry 8 }

gs2326pplusSFPVendorPN OBJECT-TYPE
   SYNTAX      DisplayString
   MAX-ACCESS  read-only
   STATUS      current
   DESCRIPTION
       " "
   ::= { gs2326pplusSFPInfoEntry 9 }

gs2326pplusSFPVendorRev OBJECT-TYPE
   SYNTAX      DisplayString
   MAX-ACCESS  read-only
   STATUS      current
   DESCRIPTION
       " "
   ::= { gs2326pplusSFPInfoEntry 10 }

gs2326pplusSFPVendorSN OBJECT-TYPE
   SYNTAX      DisplayString
   MAX-ACCESS  read-only
   STATUS      current
   DESCRIPTION
       " "
   ::= { gs2326pplusSFPInfoEntry 11 }

gs2326pplusSFPDateCode OBJECT-TYPE
   SYNTAX      DisplayString
   MAX-ACCESS  read-only
   STATUS      current
   DESCRIPTION
       " "
   ::= { gs2326pplusSFPInfoEntry 12 }

gs2326pplusSFPTemperature OBJECT-TYPE
   SYNTAX      DisplayString
   MAX-ACCESS  read-only
   STATUS      current
   DESCRIPTION
       " "
   ::= { gs2326pplusSFPInfoEntry 13 }

gs2326pplusSFPVcc OBJECT-TYPE
   SYNTAX      DisplayString
   MAX-ACCESS  read-only
   STATUS      current
   DESCRIPTION
       " "
   ::= { gs2326pplusSFPInfoEntry 14 }

gs2326pplusSFPMon1Bias OBJECT-TYPE
   SYNTAX      DisplayString
   MAX-ACCESS  read-only
   STATUS      current
   DESCRIPTION
       " "
   ::= { gs2326pplusSFPInfoEntry 15 }

gs2326pplusSFPMon2TxPWR OBJECT-TYPE
   SYNTAX      DisplayString
   MAX-ACCESS  read-only
   STATUS      current
   DESCRIPTION
       " "
   ::= { gs2326pplusSFPInfoEntry 16 }

gs2326pplusSFPMon3RxPWR OBJECT-TYPE
   SYNTAX      DisplayString
   MAX-ACCESS  read-only
   STATUS      current
   DESCRIPTION
       " "
   ::= { gs2326pplusSFPInfoEntry 17 }


gs2326pplusPortEEETable OBJECT-TYPE
   SYNTAX      SEQUENCE OF GS2326PPLUSPortEEEEntry
   MAX-ACCESS  not-accessible
   STATUS      current
   DESCRIPTION
      " "
   ::= { gs2326pplusPort 5 }

gs2326pplusPortEEEEntry OBJECT-TYPE
   SYNTAX      GS2326PPLUSPortEEEEntry
   MAX-ACCESS  not-accessible
   STATUS      current
   DESCRIPTION
       ""
   INDEX    { gs2326pplusPortEEEPort }
   ::= { gs2326pplusPortEEETable 1 }

GS2326PPLUSPortEEEEntry ::= SEQUENCE {
   gs2326pplusPortEEEPort		        Integer32,
   gs2326pplusPortEEEMode		        INTEGER,
   gs2326pplusPortEEEUrgentQueue1		INTEGER,
   gs2326pplusPortEEEUrgentQueue2		INTEGER,
   gs2326pplusPortEEEUrgentQueue3		INTEGER,
   gs2326pplusPortEEEUrgentQueue4		INTEGER,
   gs2326pplusPortEEEUrgentQueue5		INTEGER,
   gs2326pplusPortEEEUrgentQueue6		INTEGER,
   gs2326pplusPortEEEUrgentQueue7		INTEGER,
   gs2326pplusPortEEEUrgentQueue8		INTEGER
}

gs2326pplusPortEEEPort OBJECT-TYPE
   SYNTAX      Integer32(1..4095)
   MAX-ACCESS  not-accessible
   STATUS      current
   DESCRIPTION
       " "
   ::= { gs2326pplusPortEEEEntry 1 }

gs2326pplusPortEEEMode OBJECT-TYPE
   SYNTAX      INTEGER { disable(0), enable(1) }
   MAX-ACCESS  read-write
   STATUS      current
   DESCRIPTION
       "default: 0
       0:disable
       1:enable "
   ::= { gs2326pplusPortEEEEntry 2 }

gs2326pplusPortEEEUrgentQueue1 OBJECT-TYPE
   SYNTAX      INTEGER { disable(0), enable(1) }
   MAX-ACCESS  read-write
   STATUS      current
   DESCRIPTION
       "default: 0
       0:disable
       1:enable "
   ::= { gs2326pplusPortEEEEntry 3 }

gs2326pplusPortEEEUrgentQueue2 OBJECT-TYPE
   SYNTAX      INTEGER { disable(0), enable(1) }
   MAX-ACCESS  read-write
   STATUS      current
   DESCRIPTION
       "default: 0
       0:disable
       1:enable "
   ::= { gs2326pplusPortEEEEntry 4 }

gs2326pplusPortEEEUrgentQueue3 OBJECT-TYPE
   SYNTAX      INTEGER { disable(0), enable(1) }
   MAX-ACCESS  read-write
   STATUS      current
   DESCRIPTION
       "default: 0
       0:disable
       1:enable "
   ::= { gs2326pplusPortEEEEntry 5 }

gs2326pplusPortEEEUrgentQueue4 OBJECT-TYPE
   SYNTAX      INTEGER { disable(0), enable(1) }
   MAX-ACCESS  read-write
   STATUS      current
   DESCRIPTION
       "default: 0
       0:disable
       1:enable "
   ::= { gs2326pplusPortEEEEntry 6 }

gs2326pplusPortEEEUrgentQueue5 OBJECT-TYPE
   SYNTAX      INTEGER { disable(0), enable(1) }
   MAX-ACCESS  read-write
   STATUS      current
   DESCRIPTION
       "default: 0
       0:disable
       1:enable "
   ::= { gs2326pplusPortEEEEntry 7 }

gs2326pplusPortEEEUrgentQueue6 OBJECT-TYPE
   SYNTAX      INTEGER { disable(0), enable(1) }
   MAX-ACCESS  read-write
   STATUS      current
   DESCRIPTION
       "default: 0
       0:disable
       1:enable "
   ::= { gs2326pplusPortEEEEntry 8 }

gs2326pplusPortEEEUrgentQueue7 OBJECT-TYPE
   SYNTAX      INTEGER { disable(0), enable(1) }
   MAX-ACCESS  read-write
   STATUS      current
   DESCRIPTION
       "default: 0
       0:disable
       1:enable "
   ::= { gs2326pplusPortEEEEntry 9 }

gs2326pplusPortEEEUrgentQueue8 OBJECT-TYPE
   SYNTAX      INTEGER { disable(0), enable(1) }
   MAX-ACCESS  read-write
   STATUS      current
   DESCRIPTION
       "default: 0
       0:disable
       1:enable "
   ::= { gs2326pplusPortEEEEntry 10 }


gs2326pplusVoiceVLAN                                             OBJECT IDENTIFIER ::= { gs2326pplusConfiguration 2 }

gs2326pplusVoiceVLANConf                                         OBJECT IDENTIFIER ::= { gs2326pplusVoiceVLAN 1 }

gs2326pplusVoiceVLANMode OBJECT-TYPE
   SYNTAX      INTEGER { disable(0), enable(1) }
   MAX-ACCESS  read-write
   STATUS      current
   DESCRIPTION
       " Voice VLAN mode operation.
       default: 0,
       0: disable
       1: enable"
   ::= { gs2326pplusVoiceVLANConf 1 }

gs2326pplusVoiceVLANVLANId OBJECT-TYPE
   SYNTAX      Integer32(1..4094)
   MAX-ACCESS  read-write
   STATUS      current
   DESCRIPTION
       "Voice VLAN ID.
        default: 1000,
        range : 1-4094. "
   ::= { gs2326pplusVoiceVLANConf 2 }

gs2326pplusVoiceVLANAgingTime OBJECT-TYPE
   SYNTAX      Integer32(10..1000000)
   MAX-ACCESS  read-write
   STATUS      current
   DESCRIPTION
       " Voice VLAN secure learning aging time.
         default: 86400,
         range : 10 - 10000000. "
   ::= { gs2326pplusVoiceVLANConf 3 }

gs2326pplusVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2326pplusVoiceVLANConf 4 }


gs2326pplusVoiceVLANPortTable OBJECT-TYPE
   SYNTAX      SEQUENCE OF GS2326PPLUSVoiceVLANPortEntry
   MAX-ACCESS  not-accessible
   STATUS      current
   DESCRIPTION
       " Show Voice Vlan configuration. "
   ::= { gs2326pplusVoiceVLANConf 5 }

gs2326pplusVoiceVLANPortEntry OBJECT-TYPE
   SYNTAX      GS2326PPLUSVoiceVLANPortEntry
   MAX-ACCESS  not-accessible
   STATUS      current
   DESCRIPTION
       ""
   INDEX    { gs2326pplusVoiceVLANPort  }
   ::= { gs2326pplusVoiceVLANPortTable 1 }

GS2326PPLUSVoiceVLANPortEntry ::= SEQUENCE {
   gs2326pplusVoiceVLANPort                    Integer32,
   gs2326pplusVoiceVLANPortMode                INTEGER,
   gs2326pplusVoiceVLANPortSecurity            INTEGER,
   gs2326pplusVoiceVLANPortDiscoveryProtocol   INTEGER
}

gs2326pplusVoiceVLANPort OBJECT-TYPE
   SYNTAX      Integer32(1..4095)
   MAX-ACCESS  not-accessible
   STATUS      current
   DESCRIPTION
       " port, range : 1 - port number. "
   ::= { gs2326pplusVoiceVLANPortEntry 1 }

gs2326pplusVoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2326pplusVoiceVLANPortEntry 2 }

gs2326pplusVoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2326pplusVoiceVLANPortEntry 3 }

gs2326pplusVoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2326pplusVoiceVLANPortEntry 4 }

gs2326pplusVoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2326pplusVoiceVLANPortEntry 5 }


gs2326pplusVoiceVLANOUI                                          OBJECT IDENTIFIER ::= { gs2326pplusVoiceVLAN 2 }

gs2326pplusVoiceVLANOUICreate OBJECT-TYPE
   SYNTAX       INTEGER { none(0), create(1) }
   MAX-ACCESS   read-write
   STATUS       current
   DESCRIPTION
       "default: 0
        0 : None  (read only)
        1 : Create an OUI entry"
   ::= { gs2326pplusVoiceVLANOUI 1 }

gs2326pplusVoiceVLANOUITable OBJECT-TYPE
   SYNTAX      SEQUENCE OF GS2326PPLUSVoiceVLANOUIEntry
   MAX-ACCESS  not-accessible
   STATUS      current
   DESCRIPTION
       " Create Voice VLAN OUI entry. Modify OUI table will
         restart auto detect OUI process. "
   ::= { gs2326pplusVoiceVLANOUI 2 }

gs2326pplusVoiceVLANOUIEntry OBJECT-TYPE
   SYNTAX      GS2326PPLUSVoiceVLANOUIEntry
   MAX-ACCESS  not-accessible
   STATUS      current
   DESCRIPTION
       ""
   INDEX    { gs2326pplusVoiceVLANOUIIndex  }
   ::= { gs2326pplusVoiceVLANOUITable 1 }

GS2326PPLUSVoiceVLANOUIEntry ::= SEQUENCE {
   gs2326pplusVoiceVLANOUIIndex         Integer32,
   gs2326pplusVoiceVLANTelephonyOUI     OCTET STRING,
   gs2326pplusVoiceVLANDescription      DisplayString,
   gs2326pplusVoiceVLANOUIRowStatus     INTEGER
}

gs2326pplusVoiceVLANOUIIndex OBJECT-TYPE
   SYNTAX      Integer32(1..16)
   MAX-ACCESS  not-accessible
   STATUS      current
   DESCRIPTION
       " "
   ::= { gs2326pplusVoiceVLANOUIEntry 1 }

gs2326pplusVoiceVLANTelephonyOUI OBJECT-TYPE
   SYNTAX      OCTET STRING (SIZE (1..32))
   MAX-ACCESS  read-write
   STATUS      current
   DESCRIPTION
       "OUI address, format : 0a 1b 2c "
   ::= { gs2326pplusVoiceVLANOUIEntry 2 }

gs2326pplusVoiceVLANDescription OBJECT-TYPE
   SYNTAX      DisplayString (SIZE (1..32))
   MAX-ACCESS  read-write
   STATUS      current
   DESCRIPTION
       " Up to 32 characters describing OUI address. "
   ::= { gs2326pplusVoiceVLANOUIEntry 3 }

gs2326pplusVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusVoiceVLANOUIEntry 4 }

gs2326pplusGARP                                                   OBJECT IDENTIFIER ::= { gs2326pplusConfiguration 3 }

gs2326pplusGARPConfTable OBJECT-TYPE
   SYNTAX      SEQUENCE OF GS2326PPLUSGARPConfEntry
   MAX-ACCESS  not-accessible
   STATUS      current
   DESCRIPTION
       " "
   ::= { gs2326pplusGARP 1 }

gs2326pplusGARPConfEntry OBJECT-TYPE
   SYNTAX      GS2326PPLUSGARPConfEntry
   MAX-ACCESS  not-accessible
   STATUS      current
   DESCRIPTION
       ""
   INDEX    { gs2326pplusGARPConfPort  }
   ::= { gs2326pplusGARPConfTable 1 }

GS2326PPLUSGARPConfEntry ::= SEQUENCE {
   gs2326pplusGARPConfPort           Integer32,
   gs2326pplusGARPJoinTimer          Integer32,
   gs2326pplusGARPLeaveTimer         Integer32,
   gs2326pplusGARPLeaveAllTimer      Integer32,
   gs2326pplusGARPApplicantion       INTEGER,
   gs2326pplusGARPAttributeType      INTEGER,
   gs2326pplusGARPApplicant          INTEGER
}

gs2326pplusGARPConfPort OBJECT-TYPE
   SYNTAX      Integer32(1..4095)
   MAX-ACCESS  not-accessible
   STATUS      current
   DESCRIPTION
       " "
   ::= { gs2326pplusGARPConfEntry 1 }

gs2326pplusGARPJoinTimer OBJECT-TYPE
   SYNTAX      Integer32(200..1000)
   MAX-ACCESS  read-write
   STATUS      current
   DESCRIPTION
       "default: 200, range : 200 - 1000 "
   ::= { gs2326pplusGARPConfEntry 2 }

gs2326pplusGARPLeaveTimer OBJECT-TYPE
   SYNTAX      Integer32(600..3000)
   MAX-ACCESS  read-write
   STATUS      current
   DESCRIPTION
       "default: 600 , range : 600 - 3000"
   ::= { gs2326pplusGARPConfEntry 3 }

gs2326pplusGARPLeaveAllTimer OBJECT-TYPE
   SYNTAX      Integer32(10000..50000)
   MAX-ACCESS  read-write
   STATUS      current
   DESCRIPTION
       "default: 10000, range : 10000 - 50000 "
   ::= { gs2326pplusGARPConfEntry 4 }

gs2326pplusGARPApplicantion OBJECT-TYPE
   SYNTAX      INTEGER { gvrp(1)}
   MAX-ACCESS  read-write
   STATUS      current
   DESCRIPTION
       "default: 1
       1: GVRP"
   ::= { gs2326pplusGARPConfEntry 5 }

gs2326pplusGARPAttributeType OBJECT-TYPE
   SYNTAX      INTEGER { vlan(1)}
   MAX-ACCESS  read-write
   STATUS      current
   DESCRIPTION
       "default: 1
       1: VLAN"
   ::= { gs2326pplusGARPConfEntry 6 }

gs2326pplusGARPApplicant OBJECT-TYPE
   SYNTAX      INTEGER { participant(0), nonParticipant(1) }
   MAX-ACCESS  read-write
   STATUS      current
   DESCRIPTION
       "default: 0
       0: normal-participant
       1: non-participant"
   ::= { gs2326pplusGARPConfEntry 7 }

gs2326pplusGARPStatisticsTable OBJECT-TYPE
   SYNTAX      SEQUENCE OF GS2326PPLUSGARPStatisticsEntry
   MAX-ACCESS  not-accessible
   STATUS      current
   DESCRIPTION
       " Show the basic GARP port statistics. "
   ::= { gs2326pplusGARP 2 }

gs2326pplusGARPStatisticsEntry OBJECT-TYPE
   SYNTAX      GS2326PPLUSGARPStatisticsEntry
   MAX-ACCESS  not-accessible
   STATUS      current
   DESCRIPTION
       ""
   INDEX    { gs2326pplusGARPStatisticsPort  }
   ::= { gs2326pplusGARPStatisticsTable 1 }

GS2326PPLUSGARPStatisticsEntry ::= SEQUENCE {
   gs2326pplusGARPStatisticsPort             Integer32,
   gs2326pplusGARPStatisticsPeerMAC          DisplayString,
   gs2326pplusGARPStatisticsFailedCount      Counter32
}

gs2326pplusGARPStatisticsPort OBJECT-TYPE
   SYNTAX      Integer32(1..4095)
   MAX-ACCESS  not-accessible
   STATUS      current
   DESCRIPTION
       " port, range : 1 - port number. "
   ::= { gs2326pplusGARPStatisticsEntry 1 }

gs2326pplusGARPStatisticsPeerMAC OBJECT-TYPE
   SYNTAX      DisplayString
   MAX-ACCESS  read-only
   STATUS      current
   DESCRIPTION
       " Peer MAC is MAC address of the neighbour Switch from with GARP frame is received.  "
   ::= { gs2326pplusGARPStatisticsEntry 2 }

gs2326pplusGARPStatisticsFailedCount OBJECT-TYPE
   SYNTAX      Counter32
   MAX-ACCESS  read-only
   STATUS      current
   DESCRIPTION
       " explain Failed count here. "
   ::= { gs2326pplusGARPStatisticsEntry 3 }

gs2326pplusGVRP                                                   OBJECT IDENTIFIER ::= { gs2326pplusConfiguration 4 }

gs2326pplusGVRPConf                                                   OBJECT IDENTIFIER ::= { gs2326pplusGVRP 1 }

gs2326pplusGVRPMode OBJECT-TYPE
   SYNTAX      INTEGER { disable(0), enable(1) }
   MAX-ACCESS  read-write
   STATUS      current
   DESCRIPTION
       "default: 0,
        0: disable,
        1: enable. "
   ::= { gs2326pplusGVRPConf 1 }

gs2326pplusGVRPConfTable OBJECT-TYPE
   SYNTAX      SEQUENCE OF GS2326PPLUSGVRPConfEntry
   MAX-ACCESS  not-accessible
   STATUS      current
   DESCRIPTION
       " "
   ::= { gs2326pplusGVRPConf 2 }

gs2326pplusGVRPConfEntry OBJECT-TYPE
   SYNTAX      GS2326PPLUSGVRPConfEntry
   MAX-ACCESS  not-accessible
   STATUS      current
   DESCRIPTION
       ""
   INDEX    { gs2326pplusGVRPConfPort  }
   ::= { gs2326pplusGVRPConfTable 1 }

GS2326PPLUSGVRPConfEntry ::= SEQUENCE {
   gs2326pplusGVRPConfPort           Integer32,
   gs2326pplusGVRPConfPortMode       INTEGER,
   gs2326pplusGVRPConfPortRRole      INTEGER
}

gs2326pplusGVRPConfPort OBJECT-TYPE
   SYNTAX      Integer32(1..4095)
   MAX-ACCESS  not-accessible
   STATUS      current
   DESCRIPTION
       " "
   ::= { gs2326pplusGVRPConfEntry 1 }

gs2326pplusGVRPConfPortMode OBJECT-TYPE
   SYNTAX      INTEGER { disable(0), enable(1) }
   MAX-ACCESS  read-write
   STATUS      current
   DESCRIPTION
       "default: 0
       1: enable
       0: disable"
   ::= { gs2326pplusGVRPConfEntry 2 }

gs2326pplusGVRPConfPortRRole OBJECT-TYPE
   SYNTAX      INTEGER { disable(0), enable(1) }
   MAX-ACCESS  read-write
   STATUS      current
   DESCRIPTION
       "default: 0
       1: enable
       0: disable"
   ::= { gs2326pplusGVRPConfEntry 3 }

gs2326pplusGVRPStatisticsTable OBJECT-TYPE
   SYNTAX      SEQUENCE OF GS2326PPLUSGVRPStatisticsEntry
   MAX-ACCESS  not-accessible
   STATUS      current
   DESCRIPTION
       " "
   ::= { gs2326pplusGVRP 2 }

gs2326pplusGVRPStatisticsEntry OBJECT-TYPE
   SYNTAX      GS2326PPLUSGVRPStatisticsEntry
   MAX-ACCESS  not-accessible
   STATUS      current
   DESCRIPTION
       ""
   INDEX    { gs2326pplusGVRPStatisticsPort  }
   ::= { gs2326pplusGVRPStatisticsTable 1 }

GS2326PPLUSGVRPStatisticsEntry ::= SEQUENCE {
   gs2326pplusGVRPStatisticsPort         Integer32,
   gs2326pplusGVRPStatisticsJoinTxCnt    Counter32,
   gs2326pplusGVRPStatisticsLeaveTxCnt   Counter32
}

gs2326pplusGVRPStatisticsPort OBJECT-TYPE
   SYNTAX      Integer32(1..4095)
   MAX-ACCESS  not-accessible
   STATUS      current
   DESCRIPTION
       " "
   ::= { gs2326pplusGVRPStatisticsEntry 1 }

gs2326pplusGVRPStatisticsJoinTxCnt OBJECT-TYPE
   SYNTAX      Counter32
   MAX-ACCESS  read-only
   STATUS      current
   DESCRIPTION
       ""
   ::= { gs2326pplusGVRPStatisticsEntry 2 }

gs2326pplusGVRPStatisticsLeaveTxCnt OBJECT-TYPE
   SYNTAX      Counter32
   MAX-ACCESS  read-only
   STATUS      current
   DESCRIPTION
       ""
   ::= { gs2326pplusGVRPStatisticsEntry 3 }


gs2326pplusMirroring                                             OBJECT IDENTIFIER ::= { gs2326pplusConfiguration 6 }

gs2326pplusPortToMirrorOn OBJECT-TYPE
   SYNTAX      Integer32(0..10)
   MAX-ACCESS  read-write
   STATUS      current
   DESCRIPTION
       "default: 0
        0: disable,
        range : 1 - port number. "
   ::= { gs2326pplusMirroring 1 }

gs2326pplusMirrorTable OBJECT-TYPE
   SYNTAX      SEQUENCE OF GS2326PPLUSMirrorEntry
   MAX-ACCESS  not-accessible
   STATUS      current
   DESCRIPTION
       " "
   ::= { gs2326pplusMirroring 2 }

gs2326pplusMirrorEntry OBJECT-TYPE
   SYNTAX      GS2326PPLUSMirrorEntry
   MAX-ACCESS  not-accessible
   STATUS      current
   DESCRIPTION
       ""
   INDEX    { gs2326pplusMirrorPort  }
   ::= { gs2326pplusMirrorTable 1 }

GS2326PPLUSMirrorEntry ::= SEQUENCE {
   gs2326pplusMirrorPort		Integer32,
   gs2326pplusMirrorMode		INTEGER
}

gs2326pplusMirrorPort OBJECT-TYPE
   SYNTAX      Integer32(1..4095)
   MAX-ACCESS  not-accessible
   STATUS      current
   DESCRIPTION
       " "
   ::= { gs2326pplusMirrorEntry 1 }

gs2326pplusMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2326pplusMirrorEntry 2 }

gs2326pplusTrapEventSeverity                                             OBJECT IDENTIFIER ::= { gs2326pplusConfiguration 7 }

gs2326pplusTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 1 }

gs2326pplusTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2326pplusTrapEventSeverity 2 }

gs2326pplusTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 3 }

gs2326pplusTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 4 }

gs2326pplusTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 5 }

gs2326pplusTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 6 }

gs2326pplusTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 7 }

gs2326pplusTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 8 }

gs2326pplusTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 9 }

gs2326pplusTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 10 }

gs2326pplusTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 11 }

gs2326pplusTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 12 }

gs2326pplusTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 13 }

gs2326pplusTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 14 }

gs2326pplusTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2326pplusTrapEventSeverity 15 }

gs2326pplusTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 16 }

gs2326pplusTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 17 }

gs2326pplusTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 18 }

gs2326pplusTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pplusTrapEventSeverity 20 }

gs2326pplusTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 21 }

gs2326pplusTrapEventSeverityPoEAutoCheck OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 22 }

gs2326pplusTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 25 }

gs2326pplusTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 27 }

gs2326pplusTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pplusTrapEventSeverity 28 }

gs2326pplusSMTP                                             OBJECT IDENTIFIER ::= { gs2326pplusConfiguration 8 }

gs2326pplusSMTPMailServer OBJECT-TYPE
   SYNTAX      DisplayString
   MAX-ACCESS  read-write
   STATUS      current
   DESCRIPTION
       " Up to 47 characters describing email server. "
   ::= { gs2326pplusSMTP 1 }

gs2326pplusSMTPUserName OBJECT-TYPE
   SYNTAX      DisplayString
   MAX-ACCESS  read-write
   STATUS      current
   DESCRIPTION
       " Up to 47 characters describing user name. "
   ::= { gs2326pplusSMTP 2 }

gs2326pplusSMTPPassword OBJECT-TYPE
   SYNTAX      DisplayString
   MAX-ACCESS  read-write
   STATUS      current
   DESCRIPTION
       " Up to 47 characters describing password. "
   ::= { gs2326pplusSMTP 3 }

gs2326pplusSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2326pplusSMTP 4 }

gs2326pplusSMTPSender OBJECT-TYPE
   SYNTAX      DisplayString
   MAX-ACCESS  read-write
   STATUS      current
   DESCRIPTION
       " Up to 47 characters describing sender. "
   ::= { gs2326pplusSMTP 5 }

gs2326pplusSMTPReturnPath OBJECT-TYPE
   SYNTAX      DisplayString
   MAX-ACCESS  read-write
   STATUS      current
   DESCRIPTION
       " Up to 47 characters describing return path. "
   ::= { gs2326pplusSMTP 6 }

gs2326pplusSMTPEmailAddress1 OBJECT-TYPE
   SYNTAX      DisplayString
   MAX-ACCESS  read-write
   STATUS      current
   DESCRIPTION
       " Up to 47 characters describing mail address. "
   ::= { gs2326pplusSMTP 7 }

gs2326pplusSMTPEmailAddress2 OBJECT-TYPE
   SYNTAX      DisplayString
   MAX-ACCESS  read-write
   STATUS      current
   DESCRIPTION
       " Up to 47 characters describing mail address. "
   ::= { gs2326pplusSMTP 8 }

gs2326pplusSMTPEmailAddress3 OBJECT-TYPE
   SYNTAX      DisplayString
   MAX-ACCESS  read-write
   STATUS      current
   DESCRIPTION
       " Up to 47 characters describing mail address. "
   ::= { gs2326pplusSMTP 9 }

gs2326pplusSMTPEmailAddress4 OBJECT-TYPE
   SYNTAX      DisplayString
   MAX-ACCESS  read-write
   STATUS      current
   DESCRIPTION
       " Up to 47 characters describing mail address. "
   ::= { gs2326pplusSMTP 10 }

gs2326pplusSMTPEmailAddress5 OBJECT-TYPE
   SYNTAX      DisplayString
   MAX-ACCESS  read-write
   STATUS      current
   DESCRIPTION
       " Up to 47 characters describing mail address. "
   ::= { gs2326pplusSMTP 11 }

gs2326pplusSMTPEmailAddress6 OBJECT-TYPE
   SYNTAX      DisplayString
   MAX-ACCESS  read-write
   STATUS      current
   DESCRIPTION
       " Up to 47 characters describing mail address. "
   ::= { gs2326pplusSMTP 12 }


gs2326pplusACL                                                   OBJECT IDENTIFIER ::= { gs2326pplusConfiguration 9 }

gs2326pplusACLPortsConfTable OBJECT-TYPE
   SYNTAX      SEQUENCE OF GS2326PPLUSACLPortsConfEntry
   MAX-ACCESS  not-accessible
   STATUS      current
   DESCRIPTION
       " "
   ::= { gs2326pplusACL 1 }

gs2326pplusACLPortsConfEntry OBJECT-TYPE
   SYNTAX      GS2326PPLUSACLPortsConfEntry
   MAX-ACCESS  not-accessible
   STATUS      current
   DESCRIPTION
       ""
   INDEX    { gs2326pplusACLPortsConfPort  }
   ::= { gs2326pplusACLPortsConfTable 1 }

GS2326PPLUSACLPortsConfEntry ::= SEQUENCE {
   gs2326pplusACLPortsConfPort               Integer32,
   gs2326pplusACLPortsConfPolicyID           Integer32,
   gs2326pplusACLPortsConfAction             INTEGER,
   gs2326pplusACLPortsConfRateLimiterID      Integer32,
   gs2326pplusACLPortsConfPortRedirect       Integer32,
   gs2326pplusACLPortsConfMirror             INTEGER,
   gs2326pplusACLPortsConfLogging            INTEGER,
   gs2326pplusACLPortsConfShutdown           INTEGER,
   gs2326pplusACLPortsConfState              INTEGER,
   gs2326pplusACLPortsConfCounter            Counter32
}

gs2326pplusACLPortsConfPort OBJECT-TYPE
   SYNTAX      Integer32 (1..4095)
   MAX-ACCESS  not-accessible
   STATUS      current
   DESCRIPTION
       " "
   ::= { gs2326pplusACLPortsConfEntry 1 }

gs2326pplusACLPortsConfPolicyID OBJECT-TYPE
   SYNTAX      Integer32 (0..255)
   MAX-ACCESS  read-write
   STATUS      current
   DESCRIPTION
       "default: 0, range : 0 - 255 "
   ::= { gs2326pplusACLPortsConfEntry 2 }

gs2326pplusACLPortsConfAction OBJECT-TYPE
   SYNTAX      INTEGER { deny(0), permit(1) }
   MAX-ACCESS  read-write
   STATUS      current
   DESCRIPTION
       "default: 1,
        0: Deny
        1: Permit"
   ::= { gs2326pplusACLPortsConfEntry 3 }

gs2326pplusACLPortsConfRateLimiterID OBJECT-TYPE
   SYNTAX      Integer32 (0..12)
   MAX-ACCESS  read-write
   STATUS      current
   DESCRIPTION
       "default: 0,
        0: Disable
        range : 0 - 12 "
   ::= { gs2326pplusACLPortsConfEntry 4 }

gs2326pplusACLPortsConfPortRedirect OBJECT-TYPE
   SYNTAX      Integer32 (0..4095)
   MAX-ACCESS  read-write
   STATUS      current
   DESCRIPTION
       "default: 0
        0: Disable
        range : 0 - end port number "
   ::= { gs2326pplusACLPortsConfEntry 5 }

gs2326pplusACLPortsConfMirror OBJECT-TYPE
   SYNTAX      INTEGER { disable(0), enable(1) }
   MAX-ACCESS  read-write
   STATUS      current
   DESCRIPTION
       "default: 0
        0: Disable
        1: Enable "
   ::= { gs2326pplusACLPortsConfEntry 6 }

gs2326pplusACLPortsConfLogging OBJECT-TYPE
   SYNTAX      INTEGER { disable(0), enable(1) }
   MAX-ACCESS  read-write
   STATUS      current
   DESCRIPTION
       "default: 0
        0: Disable
        1: Enable "
   ::= { gs2326pplusACLPortsConfEntry 7 }

gs2326pplusACLPortsConfShutdown OBJECT-TYPE
   SYNTAX      INTEGER { disable(0), enable(1) }
   MAX-ACCESS  read-write
   STATUS      current
   DESCRIPTION
       "default: 0
        0: Disable
        1: Enable "
   ::= { gs2326pplusACLPortsConfEntry 8 }

gs2326pplusACLPortsConfState OBJECT-TYPE
   SYNTAX      INTEGER { disable(0), enable(1) }
   MAX-ACCESS  read-write
   STATUS      current
   DESCRIPTION
       "default: 1
        0: Disable
        1: Enable "
   ::= { gs2326pplusACLPortsConfEntry 9 }

gs2326pplusACLPortsConfCounter OBJECT-TYPE
   SYNTAX      Counter32
   MAX-ACCESS  read-only
   STATUS      current
   DESCRIPTION
       "Counts the number of frames that match this ACE. "
   ::= { gs2326pplusACLPortsConfEntry 10 }


gs2326pplusACLRateLimiterTable OBJECT-TYPE
   SYNTAX      SEQUENCE OF GS2326PPLUSACLRateLimiterEntry
   MAX-ACCESS  not-accessible
   STATUS      current
   DESCRIPTION
       " "
   ::= { gs2326pplusACL 2 }

gs2326pplusACLRateLimiterEntry OBJECT-TYPE
   SYNTAX      GS2326PPLUSACLRateLimiterEntry
   MAX-ACCESS  not-accessible
   STATUS      current
   DESCRIPTION
       ""
   INDEX    { gs2326pplusACLRateLimiterID  }
   ::= { gs2326pplusACLRateLimiterTable 1 }

GS2326PPLUSACLRateLimiterEntry ::= SEQUENCE {
   gs2326pplusACLRateLimiterID       Integer32,
   gs2326pplusACLRateLimiterUnit     INTEGER,
   gs2326pplusACLRateLimiterRate     Integer32
}

gs2326pplusACLRateLimiterID OBJECT-TYPE
   SYNTAX      Integer32 (1..12)
   MAX-ACCESS  not-accessible
   STATUS      current
   DESCRIPTION
       " Rate Limiter ID.
         range : 1-12 "
   ::= { gs2326pplusACLRateLimiterEntry 1 }

gs2326pplusACLRateLimiterUnit OBJECT-TYPE
   SYNTAX      INTEGER { pps(0), kbps(1) }
   MAX-ACCESS  read-write
   STATUS      current
   DESCRIPTION
       "default: 0,
        0: pps
        1: kbps"
   ::= { gs2326pplusACLRateLimiterEntry 2 }

gs2326pplusACLRateLimiterRate OBJECT-TYPE
   SYNTAX      Integer32(0..3276700)
   MAX-ACCESS  read-write
   STATUS      current
   DESCRIPTION
       "default: 1,
        range : <0-3276700> pps
                <0-10000> kbps"
   ::= { gs2326pplusACLRateLimiterEntry 3 }


gs2326pplusACLACE                                          OBJECT IDENTIFIER ::= { gs2326pplusACL 3 }

gs2326pplusACLACECreate OBJECT-TYPE
   SYNTAX       INTEGER { none(0), create(1) }
   MAX-ACCESS   read-write
   STATUS       current
   DESCRIPTION
       "default: 0
        0 : None  (read only)
        1 : Create an ACE entry"
   ::= { gs2326pplusACLACE 1 }

gs2326pplusACLACETable OBJECT-TYPE
   SYNTAX      SEQUENCE OF GS2326PPLUSACLACEEntry
   MAX-ACCESS  not-accessible
   STATUS      current
   DESCRIPTION
       " Create ACL ACE entry. "
   ::= { gs2326pplusACLACE 2 }

gs2326pplusACLACEEntry OBJECT-TYPE
   SYNTAX      GS2326PPLUSACLACEEntry
   MAX-ACCESS  not-accessible
   STATUS      current
   DESCRIPTION
       ""
   INDEX    { gs2326pplusACLACEIndex  }
   ::= { gs2326pplusACLACETable 1 }

GS2326PPLUSACLACEEntry ::= SEQUENCE {
   gs2326pplusACLACEIndex                Integer32,
   gs2326pplusACLACEID                   Integer32,
   gs2326pplusACLACENextID               Integer32,
   gs2326pplusACLACEIngressPort          DisplayString,
   gs2326pplusACLACEPortPolicyNumber     Integer32,

   gs2326pplusACLACEPortPolicyBitmask    Integer32,
   gs2326pplusACLACEFrameType            INTEGER,
   gs2326pplusACLACEAction               INTEGER,
   gs2326pplusACLACEDenyPortRedirect     DisplayString,
   gs2326pplusACLACELogging              INTEGER,

   gs2326pplusACLACEMirror               INTEGER,
   gs2326pplusACLACERateLimiter          Integer32,
   gs2326pplusACLACEShutdown             INTEGER,
   gs2326pplusACLACEVLAN8021QTagged      INTEGER,
   gs2326pplusACLACEVLANTagPriority      Integer32,

   gs2326pplusACLACEVLANVID              Integer32,
   gs2326pplusACLACEEtherType            Integer32,
   gs2326pplusACLACESMAC                 DisplayString,
   gs2326pplusACLACEDMACType             INTEGER,
   gs2326pplusACLACEDMAC                 DisplayString,

   gs2326pplusACLACEArpOpcode            INTEGER,
   gs2326pplusACLACEArpFlagsRequestReply INTEGER,
   gs2326pplusACLACEArpFlagsArpSmac      INTEGER,
   gs2326pplusACLACEArpFlagsRarpDmac     INTEGER,
   gs2326pplusACLACEArpFlagsLength       INTEGER,

   gs2326pplusACLACEArpFlagsIp           INTEGER,
   gs2326pplusACLACEArpFlagsEthernet     INTEGER,
   gs2326pplusACLACESIPType              INTEGER,
   gs2326pplusACLACESIPIPAddress         IpAddress,
   gs2326pplusACLACESIPNetworkPrefix     Integer32,

   gs2326pplusACLACEDIPType              INTEGER,
   gs2326pplusACLACEDIPIPAddress         IpAddress,
   gs2326pplusACLACEDIPNetworkPrefix     Integer32,

   gs2326pplusACLACEIPProtocol           Integer32,
   gs2326pplusACLACEIPFlagsTTL           INTEGER,
   gs2326pplusACLACEIPFlagsOptions       INTEGER,
   gs2326pplusACLACEIPFlagsFragment      INTEGER,
   gs2326pplusACLACEICMPType             Integer32,

   gs2326pplusACLACEICMPCode             Integer32,
   gs2326pplusACLACESourcePortMin        Integer32,
   gs2326pplusACLACESourcePortMax        Integer32,
   gs2326pplusACLACEDestPortMin          Integer32,
   gs2326pplusACLACEDestPortMax          Integer32,

   gs2326pplusACLACETCPFlagsFin          INTEGER,
   gs2326pplusACLACETCPFlagsSyn          INTEGER,
   gs2326pplusACLACETCPFlagsRst          INTEGER,
   gs2326pplusACLACETCPFlagsPsh          INTEGER,
   gs2326pplusACLACETCPFlagsAck          INTEGER,

   gs2326pplusACLACETCPFlagsUrg          INTEGER,

   gs2326pplusACLACERowStatus            INTEGER
}

gs2326pplusACLACEIndex OBJECT-TYPE
   SYNTAX      Integer32(1..256)
   MAX-ACCESS  not-accessible
   STATUS      current
   DESCRIPTION
       " "
   ::= { gs2326pplusACLACEEntry 1 }

gs2326pplusACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2326pplusACLACEEntry 2 }

gs2326pplusACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2326pplusACLACEEntry 3 }

gs2326pplusACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2326pplusACLACEEntry 4 }

gs2326pplusACLACEPortPolicyNumber OBJECT-TYPE
   SYNTAX      Integer32(0..255)
   MAX-ACCESS  read-write
   STATUS      current
   DESCRIPTION
       " policy value.
         range : 0 - 255. "
   ::= { gs2326pplusACLACEEntry 5 }

gs2326pplusACLACEPortPolicyBitmask OBJECT-TYPE
   SYNTAX      Integer32(0..255)
   MAX-ACCESS  read-write
   STATUS      current
   DESCRIPTION
       " policy bitmask.
         range : 0 - 255(0xff). "
   ::= { gs2326pplusACLACEEntry 6 }

gs2326pplusACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2326pplusACLACEEntry 7 }

gs2326pplusACLACEAction OBJECT-TYPE
   SYNTAX      INTEGER { deny(0), permit(1) }
   MAX-ACCESS  read-write
   STATUS      current
   DESCRIPTION
       "default: 1,
        0: Deny
        1: Permit"
   ::= { gs2326pplusACLACEEntry 8 }

gs2326pplusACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2326pplusACLACEEntry 9 }

gs2326pplusACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2326pplusACLACEEntry 10 }

gs2326pplusACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2326pplusACLACEEntry 11 }

gs2326pplusACLACERateLimiter OBJECT-TYPE
   SYNTAX      Integer32(0..12)
   MAX-ACCESS  read-write
   STATUS      current
   DESCRIPTION
       "default: 0,
        0: Disable
        range : 0 - 12 "
   ::= { gs2326pplusACLACEEntry 12 }

gs2326pplusACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2326pplusACLACEEntry 13 }

gs2326pplusACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { gs2326pplusACLACEEntry 14 }

gs2326pplusACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2326pplusACLACEEntry 15 }

gs2326pplusACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2326pplusACLACEEntry 16 }

gs2326pplusACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2326pplusACLACEEntry 17 }

gs2326pplusACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2326pplusACLACEEntry 18 }

gs2326pplusACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2326pplusACLACEEntry 19 }

gs2326pplusACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2326pplusACLACEEntry 20 }

gs2326pplusACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2326pplusACLACEEntry 21 }

gs2326pplusACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2326pplusACLACEEntry 22 }

gs2326pplusACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2326pplusACLACEEntry 23 }

gs2326pplusACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2326pplusACLACEEntry 24 }

gs2326pplusACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2326pplusACLACEEntry 25 }

gs2326pplusACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2326pplusACLACEEntry 26 }

gs2326pplusACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2326pplusACLACEEntry 27 }

gs2326pplusACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2326pplusACLACEEntry 28 }

gs2326pplusACLACESIPIPAddress OBJECT-TYPE
   SYNTAX      IpAddress
   MAX-ACCESS  read-write
   STATUS      current
   DESCRIPTION
       "A frame that hits this ACE matches this source IP address value."
   ::= { gs2326pplusACLACEEntry 29 }

gs2326pplusACLACESIPNetworkPrefix OBJECT-TYPE
   SYNTAX      Integer32(0..32)
   MAX-ACCESS  read-write
   STATUS      current
   DESCRIPTION
       "Network prefix.
        default: 32,
        0: No data.
        range : 1 - 32"
   ::= { gs2326pplusACLACEEntry 30 }


gs2326pplusACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2326pplusACLACEEntry 32 }

gs2326pplusACLACEDIPIPAddress OBJECT-TYPE
   SYNTAX      IpAddress
   MAX-ACCESS  read-write
   STATUS      current
   DESCRIPTION
       "A frame that hits this ACE matches this destination IP address value."
   ::= { gs2326pplusACLACEEntry 33 }

gs2326pplusACLACEDIPNetworkPrefix OBJECT-TYPE
   SYNTAX      Integer32(0..32)
   MAX-ACCESS  read-write
   STATUS      current
   DESCRIPTION
       "Network prefix.
        default: 32,
        0: No data.
        range : 1 - 32"
   ::= { gs2326pplusACLACEEntry 34 }


gs2326pplusACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2326pplusACLACEEntry 36 }

gs2326pplusACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2326pplusACLACEEntry 37 }

gs2326pplusACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2326pplusACLACEEntry 38 }

gs2326pplusACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2326pplusACLACEEntry 39 }

gs2326pplusACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2326pplusACLACEEntry 40 }

gs2326pplusACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2326pplusACLACEEntry 41 }

gs2326pplusACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2326pplusACLACEEntry 42 }

gs2326pplusACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2326pplusACLACEEntry 43 }

gs2326pplusACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2326pplusACLACEEntry 44 }

gs2326pplusACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2326pplusACLACEEntry 45 }

gs2326pplusACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2326pplusACLACEEntry 46 }

gs2326pplusACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2326pplusACLACEEntry 47 }

gs2326pplusACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2326pplusACLACEEntry 48 }

gs2326pplusACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2326pplusACLACEEntry 49 }

gs2326pplusACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2326pplusACLACEEntry 50 }

gs2326pplusACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2326pplusACLACEEntry 51 }

gs2326pplusACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2326pplusACLACEEntry 66 }


gs2326pplusACLACEClear OBJECT-TYPE
   SYNTAX       INTEGER { noAction(0), clear(1) }
   MAX-ACCESS   read-write
   STATUS       current
   DESCRIPTION
       "default: 0
        0 : No action
        1 : Clear all ACL counters."
   ::= { gs2326pplusACLACE 3 }

gs2326pplusACLACEMoveACEID OBJECT-TYPE
   SYNTAX       Integer32(0..256)
   MAX-ACCESS   read-write
   STATUS       current
   DESCRIPTION
       "Move ACE,
        default: 0
        ACE ID must be exist.
        range : 1 - 256."
   ::= { gs2326pplusACLACE 4 }

gs2326pplusACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2326pplusACLACE 5 }

gs2326pplusACLACEStatusTable OBJECT-TYPE
   SYNTAX      SEQUENCE OF GS2326PPLUSACLACEStatusEntry
   MAX-ACCESS  not-accessible
   STATUS      current
   DESCRIPTION
       " ACL ACE Status entry. "
   ::= { gs2326pplusACLACE 6 }

gs2326pplusACLACEStatusEntry OBJECT-TYPE
   SYNTAX      GS2326PPLUSACLACEStatusEntry
   MAX-ACCESS  not-accessible
   STATUS      current
   DESCRIPTION
       ""
   INDEX    { gs2326pplusACLACEStatusIndex  }
   ::= { gs2326pplusACLACEStatusTable 1 }

GS2326PPLUSACLACEStatusEntry ::= SEQUENCE {
   gs2326pplusACLACEStatusIndex          Integer32,
   gs2326pplusACLACEStatusUser           DisplayString,
   gs2326pplusACLACEStatusID             Integer32,
   gs2326pplusACLACEStatusIngressPort    DisplayString,
   gs2326pplusACLACEStatusFrameType      DisplayString,
   gs2326pplusACLACEStatusAction         DisplayString,
   gs2326pplusACLACEStatusRateLimiter    DisplayString,
   gs2326pplusACLACEStatusPortCopy       DisplayString,
   gs2326pplusACLACEStatusMirror         DisplayString,
   gs2326pplusACLACEStatusCPU            DisplayString,
   gs2326pplusACLACEStatusCounter        Counter32,
   gs2326pplusACLACEStatusConflict       DisplayString
}

gs2326pplusACLACEStatusIndex OBJECT-TYPE
   SYNTAX      Integer32(1..256)
   MAX-ACCESS  not-accessible
   STATUS      current
   DESCRIPTION
       " "
   ::= { gs2326pplusACLACEStatusEntry 1 }

gs2326pplusACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2326pplusACLACEStatusEntry 2 }

gs2326pplusACLACEStatusID OBJECT-TYPE
   SYNTAX      Integer32(1..256)
   MAX-ACCESS  read-only
   STATUS      current
   DESCRIPTION
       " ACE ID.
         range : 1 - 256. "
   ::= { gs2326pplusACLACEStatusEntry 3 }

gs2326pplusACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2326pplusACLACEStatusEntry 4 }

gs2326pplusACLACEStatusFrameType OBJECT-TYPE
   SYNTAX      DisplayString
   MAX-ACCESS  read-only
   STATUS      current
   DESCRIPTION
       " Indicates the frame type of the ACE. "
   ::= { gs2326pplusACLACEStatusEntry 5 }

gs2326pplusACLACEStatusAction OBJECT-TYPE
   SYNTAX      DisplayString
   MAX-ACCESS  read-only
   STATUS      current
   DESCRIPTION
       " Indicates the forwarding action of the ACE. "
   ::= { gs2326pplusACLACEStatusEntry 6 }

gs2326pplusACLACEStatusRateLimiter OBJECT-TYPE
   SYNTAX      DisplayString
   MAX-ACCESS  read-only
   STATUS      current
   DESCRIPTION
       " Indicates the rate limiter number of the ACE. "
   ::= { gs2326pplusACLACEStatusEntry 7 }

gs2326pplusACLACEStatusPortCopy OBJECT-TYPE
   SYNTAX      DisplayString
   MAX-ACCESS  read-only
   STATUS      current
   DESCRIPTION
       " Indicates the port redirect operation of the ACE. Frames matching the ACE are redirected to the port number. "
   ::= { gs2326pplusACLACEStatusEntry 8 }

gs2326pplusACLACEStatusMirror OBJECT-TYPE
   SYNTAX      DisplayString
   MAX-ACCESS  read-only
   STATUS      current
   DESCRIPTION
       " Specify the mirror operation of this port. "
   ::= { gs2326pplusACLACEStatusEntry 9 }

gs2326pplusACLACEStatusCPU OBJECT-TYPE
   SYNTAX      DisplayString
   MAX-ACCESS  read-only
   STATUS      current
   DESCRIPTION
       " Forward packet that matched the specific ACE to CPU. "
   ::= { gs2326pplusACLACEStatusEntry 10 }

gs2326pplusACLACEStatusCounter OBJECT-TYPE
   SYNTAX      Counter32
   MAX-ACCESS  read-only
   STATUS      current
   DESCRIPTION
       " The counter indicates the number of times the ACE was hit by a frame. "
   ::= { gs2326pplusACLACEStatusEntry 11 }

gs2326pplusACLACEStatusConflict OBJECT-TYPE
   SYNTAX      DisplayString
   MAX-ACCESS  read-only
   STATUS      current
   DESCRIPTION
       " Indicates the hardware status of the specific ACE. The specific ACE is not applied to the hardware due to hardware limitations. "
   ::= { gs2326pplusACLACEStatusEntry 12 }

gs2326pplusLoopProtection                                                  OBJECT IDENTIFIER ::= { gs2326pplusConfiguration 12 }

gs2326pplusLoopProtectionConfig                                            OBJECT IDENTIFIER ::= { gs2326pplusLoopProtection 1 }

gs2326pplusLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2326pplusLoopProtectionConfig 1 }

gs2326pplusLoopProtectionTranmisstionTime OBJECT-TYPE
   SYNTAX      Integer32(1..10)
   MAX-ACCESS  read-write
   STATUS      current
   DESCRIPTION
       "Configure loop protection transmit interval.
        default: 5,
        range: 1-10. "
   ::= { gs2326pplusLoopProtectionConfig 2 }

gs2326pplusLoopProtectionShutdownTime OBJECT-TYPE
   SYNTAX      Integer32(0..604800)
   MAX-ACCESS  read-write
   STATUS      current
   DESCRIPTION
       "Configure loop protection shutdown time.
        default: 180,
        range: 0-604800. "
   ::= { gs2326pplusLoopProtectionConfig 3 }

gs2326pplusLoopProtectionConfigurationTable OBJECT-TYPE
   SYNTAX      SEQUENCE OF GS2326PPLUSLoopProtectionConfigurationEntry
   MAX-ACCESS  not-accessible
   STATUS      current
   DESCRIPTION
       " Show Loop Protection configurations. "
   ::= { gs2326pplusLoopProtectionConfig 4 }

gs2326pplusLoopProtectionConfigurationEntry OBJECT-TYPE
   SYNTAX      GS2326PPLUSLoopProtectionConfigurationEntry
   MAX-ACCESS  not-accessible
   STATUS      current
   DESCRIPTION
       ""
   INDEX    { gs2326pplusLoopProtectionConfPort  }
   ::= { gs2326pplusLoopProtectionConfigurationTable 1 }

GS2326PPLUSLoopProtectionConfigurationEntry ::= SEQUENCE {
   gs2326pplusLoopProtectionConfPort	    Integer32,
   gs2326pplusLoopProtectionConfEnable	INTEGER,
   gs2326pplusLoopProtectionConfAction	INTEGER,
   gs2326pplusLoopProtectionConfTxmode	INTEGER
}

gs2326pplusLoopProtectionConfPort OBJECT-TYPE
   SYNTAX      Integer32(1..4095)
   MAX-ACCESS  not-accessible
   STATUS      current
   DESCRIPTION
       " port, range : 1 - port number. "
   ::= { gs2326pplusLoopProtectionConfigurationEntry 1 }

gs2326pplusLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2326pplusLoopProtectionConfigurationEntry 2 }

gs2326pplusLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2326pplusLoopProtectionConfigurationEntry 3 }

gs2326pplusLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2326pplusLoopProtectionConfigurationEntry 4 }

gs2326pplusLoopProtectionStatusTable OBJECT-TYPE
   SYNTAX      SEQUENCE OF GS2326PPLUSLoopProtectionStatusEntry
   MAX-ACCESS  not-accessible
   STATUS      current
   DESCRIPTION
       " Show Loop Protection Status. "
   ::= { gs2326pplusLoopProtection 2 }

gs2326pplusLoopProtectionStatusEntry OBJECT-TYPE
   SYNTAX      GS2326PPLUSLoopProtectionStatusEntry
   MAX-ACCESS  not-accessible
   STATUS      current
   DESCRIPTION
       ""
   INDEX    { gs2326pplusLoopProtectionStatusPort  }
   ::= { gs2326pplusLoopProtectionStatusTable 1 }

GS2326PPLUSLoopProtectionStatusEntry ::= SEQUENCE {
   gs2326pplusLoopProtectionStatusPort	       Integer32,
   gs2326pplusLoopProtectionStatusAction	       DisplayString,
   gs2326pplusLoopProtectionStatusTransmit	   DisplayString,
   gs2326pplusLoopProtectionStatusLoops	       Integer32,
   gs2326pplusLoopProtectionStatusStatus	       DisplayString,
   gs2326pplusLoopProtectionStatusLoop	       DisplayString,
   gs2326pplusLoopProtectionStatusTimeLastLoop  DisplayString
}

gs2326pplusLoopProtectionStatusPort OBJECT-TYPE
   SYNTAX      Integer32(1..4095)
   MAX-ACCESS  not-accessible
   STATUS      current
   DESCRIPTION
       " port, range : 1 - port number. "
   ::= { gs2326pplusLoopProtectionStatusEntry 1 }

gs2326pplusLoopProtectionStatusAction OBJECT-TYPE
   SYNTAX      DisplayString
   MAX-ACCESS  read-only
   STATUS      current
   DESCRIPTION
       " The currently configured port action. "
   ::= { gs2326pplusLoopProtectionStatusEntry 2 }

gs2326pplusLoopProtectionStatusTransmit OBJECT-TYPE
   SYNTAX      DisplayString
   MAX-ACCESS  read-only
   STATUS      current
   DESCRIPTION
       " The currently configured port transmit mode. "
   ::= { gs2326pplusLoopProtectionStatusEntry 3 }

gs2326pplusLoopProtectionStatusLoops OBJECT-TYPE
   SYNTAX      Integer32(0..1000000)
   MAX-ACCESS  read-only
   STATUS      current
   DESCRIPTION
       " The number of loops detected on this port. "
   ::= { gs2326pplusLoopProtectionStatusEntry 4 }

gs2326pplusLoopProtectionStatusStatus OBJECT-TYPE
   SYNTAX      DisplayString
   MAX-ACCESS  read-only
   STATUS      current
   DESCRIPTION
       " The current loop protection status of the port. "
   ::= { gs2326pplusLoopProtectionStatusEntry 5 }

gs2326pplusLoopProtectionStatusLoop OBJECT-TYPE
   SYNTAX      DisplayString
   MAX-ACCESS  read-only
   STATUS      current
   DESCRIPTION
       " Whether a loop is currently detected on the port. "
   ::= { gs2326pplusLoopProtectionStatusEntry 6 }

gs2326pplusLoopProtectionStatusTimeLastLoop OBJECT-TYPE
   SYNTAX      DisplayString
   MAX-ACCESS  read-only
   STATUS      current
   DESCRIPTION
       " The time of the last loop event detected. "
   ::= { gs2326pplusLoopProtectionStatusEntry 7 }

gs2326pplusPoe                                                           OBJECT IDENTIFIER ::= { gs2326pplusConfiguration 13 }

gs2326pplusPoeStatus                                            OBJECT IDENTIFIER ::= { gs2326pplusPoe 1 }

gs2326pplusPoeStatusTable OBJECT-TYPE
   SYNTAX      SEQUENCE OF GS2326PPLUSPoeStatusEntry
   MAX-ACCESS  not-accessible
   STATUS      current
   DESCRIPTION
       " Configure PoE Scheduling Table. "
   ::= { gs2326pplusPoeStatus 1 }

gs2326pplusPoeStatusEntry OBJECT-TYPE
   SYNTAX      GS2326PPLUSPoeStatusEntry
   MAX-ACCESS  not-accessible
   STATUS      current
   DESCRIPTION
       ""
   INDEX    { gs2326pplusPoeStatusLocalPort }
   ::= { gs2326pplusPoeStatusTable 1 }

GS2326PPLUSPoeStatusEntry ::= SEQUENCE {
   gs2326pplusPoeStatusLocalPort	        Integer32,
   gs2326pplusPoeStatusPDclass	        INTEGER,
   gs2326pplusPoeStatusPowerRequested	    DisplayString,
   gs2326pplusPoeStatusPowerAllocated     DisplayString,
   gs2326pplusPoeStatusPowerUsed          DisplayString,
   gs2326pplusPoeStatusCurrentUsed        DisplayString,
   gs2326pplusPoeStatusPriority           DisplayString,
   gs2326pplusPoeStatusPortStatus         DisplayString
}

gs2326pplusPoeStatusLocalPort OBJECT-TYPE
   SYNTAX      Integer32(1..4094)
   MAX-ACCESS  not-accessible
   STATUS      current
   DESCRIPTION
       " port, range : 1 - port number. "
   ::= { gs2326pplusPoeStatusEntry 1}

gs2326pplusPoeStatusPDclass OBJECT-TYPE
   SYNTAX      INTEGER (0..4)
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { gs2326pplusPoeStatusEntry 2 }

gs2326pplusPoeStatusPowerRequested OBJECT-TYPE
   SYNTAX      DisplayString
   MAX-ACCESS  read-only
   STATUS      current
   DESCRIPTION
      " The Power Requested shows the requested amount of power the PD wants to be reserved. "
   ::= { gs2326pplusPoeStatusEntry 3}

gs2326pplusPoeStatusPowerAllocated OBJECT-TYPE
   SYNTAX      DisplayString
   MAX-ACCESS  read-only
   STATUS      current
   DESCRIPTION
      " The Power Allocated shows the amount of power the switch has allocated for the PD. "
   ::= { gs2326pplusPoeStatusEntry 4}

gs2326pplusPoeStatusPowerUsed OBJECT-TYPE
   SYNTAX      DisplayString
   MAX-ACCESS  read-only
   STATUS      current
   DESCRIPTION
      " The Power Used shows how much power the PD currently is using. "
   ::= { gs2326pplusPoeStatusEntry 5}

gs2326pplusPoeStatusCurrentUsed OBJECT-TYPE
   SYNTAX      DisplayString
   MAX-ACCESS  read-only
   STATUS      current
   DESCRIPTION
      " The Power Used shows how much current the PD currently is using. "
   ::= { gs2326pplusPoeStatusEntry 6}

gs2326pplusPoeStatusPriority OBJECT-TYPE
   SYNTAX      DisplayString
   MAX-ACCESS  read-only
   STATUS      current
   DESCRIPTION
      " The Priority shows the port's priority configured by the user.  "
   ::= { gs2326pplusPoeStatusEntry 7}

gs2326pplusPoeStatusPortStatus OBJECT-TYPE
   SYNTAX      DisplayString
   MAX-ACCESS  read-only
   STATUS      current
   DESCRIPTION
      " The Port Status shows the port's status.  "
   ::= { gs2326pplusPoeStatusEntry 8}


gs2326pplusPoeStatusTotalPowerRequested OBJECT-TYPE
   SYNTAX      DisplayString
   MAX-ACCESS  read-only
   STATUS      current
   DESCRIPTION
      " Total Power Requested."
   ::= { gs2326pplusPoeStatus 2}

gs2326pplusPoeStatusTotalPowerAllocated OBJECT-TYPE
   SYNTAX      DisplayString
   MAX-ACCESS  read-only
   STATUS      current
   DESCRIPTION
      " Total Power allocated."
   ::= { gs2326pplusPoeStatus 3}

gs2326pplusPoeStatusTotalPowerUsed OBJECT-TYPE
   SYNTAX      DisplayString
   MAX-ACCESS  read-only
   STATUS      current
   DESCRIPTION
      " Total Power Used."
   ::= { gs2326pplusPoeStatus 4}

gs2326pplusPoeStatusTotalCurrentUsed OBJECT-TYPE
   SYNTAX      DisplayString
   MAX-ACCESS  read-only
   STATUS      current
   DESCRIPTION
      " Total Current Used."
   ::= { gs2326pplusPoeStatus 5}

gs2326pplusPoeMcuVersion OBJECT-TYPE
   SYNTAX      DisplayString
   MAX-ACCESS  read-only
   STATUS      current
   DESCRIPTION
      " PoE MCU version."
   ::= { gs2326pplusPoeStatus 6 }

gs2326pplusPoePowerDelay                                                 OBJECT IDENTIFIER ::= { gs2326pplusPoe 2 }

gs2326pplusPoePowerDelayTable OBJECT-TYPE
   SYNTAX      SEQUENCE OF GS2326PPLUSPoePowerDelayEntry
   MAX-ACCESS  not-accessible
   STATUS      current
   DESCRIPTION
       " Configure PoE Power Delay mode. "
   ::= { gs2326pplusPoePowerDelay 1 }

gs2326pplusPoePowerDelayEntry OBJECT-TYPE
   SYNTAX      GS2326PPLUSPoePowerDelayEntry
   MAX-ACCESS  not-accessible
   STATUS      current
   DESCRIPTION
       ""
   INDEX    { gs2326pplusPoePowerDelayPort  }
   ::= { gs2326pplusPoePowerDelayTable 1 }

GS2326PPLUSPoePowerDelayEntry ::= SEQUENCE {
   gs2326pplusPoePowerDelayPort	        Integer32,
   gs2326pplusPoePowerDelayMode	        INTEGER,
   gs2326pplusPoePowerDelayTime         Integer32
}

gs2326pplusPoePowerDelayPort OBJECT-TYPE
   SYNTAX      Integer32(1..4094)
   MAX-ACCESS  not-accessible
   STATUS      current
   DESCRIPTION
       " port, range : 1 - port number. "
   ::= { gs2326pplusPoePowerDelayEntry 1 }

gs2326pplusPoePowerDelayMode OBJECT-TYPE
   SYNTAX      INTEGER { disable(0), enable(1) }
   MAX-ACCESS  read-write
   STATUS      current
   DESCRIPTION
       "Turn on / off the power delay function,
        0: disable,
        1: enable,
        default: disable. "
   ::= { gs2326pplusPoePowerDelayEntry 2 }

gs2326pplusPoePowerDelayTime OBJECT-TYPE
   SYNTAX      Integer32(0..300)
   MAX-ACCESS  read-write
   STATUS      current
   DESCRIPTION
       "set Delay Time,
        default: 0,
        range: 0-300 sec. "
   ::= { gs2326pplusPoePowerDelayEntry 3 }

gs2326pplusPoeAutoCheck                                                 OBJECT IDENTIFIER ::= { gs2326pplusPoe 3 }

gs2326pplusPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { gs2326pplusPoeAutoCheck 1 }

gs2326pplusPoeAutoCheckTable OBJECT-TYPE
   SYNTAX      SEQUENCE OF GS2326PPLUSPoeAutoCheckEntry
   MAX-ACCESS  not-accessible
   STATUS      current
   DESCRIPTION
       " Configure PoE Power Delay mode. "
   ::= { gs2326pplusPoeAutoCheck 2 }

gs2326pplusPoeAutoCheckEntry OBJECT-TYPE
   SYNTAX      GS2326PPLUSPoeAutoCheckEntry
   MAX-ACCESS  not-accessible
   STATUS      current
   DESCRIPTION
       ""
   INDEX    { gs2326pplusPoeAutoCheckPort  }
   ::= { gs2326pplusPoeAutoCheckTable 1 }

GS2326PPLUSPoeAutoCheckEntry ::= SEQUENCE {
   gs2326pplusPoeAutoCheckPort	       Integer32,
   gs2326pplusPoeAutoCheckPingIPAddress  DisplayString,
   gs2326pplusPoeAutoCheckIntervalTime   Integer32,
   gs2326pplusPoeAutoCheckRetryTime      Integer32,
   gs2326pplusPoeAutoCheckFailureLog     DisplayString,
   gs2326pplusPoeAutoCheckFailureAction  INTEGER,
   gs2326pplusPoeAutoCheckRebootTime     Integer32
}

gs2326pplusPoeAutoCheckPort OBJECT-TYPE
   SYNTAX      Integer32(1..4094)
   MAX-ACCESS  not-accessible
   STATUS      current
   DESCRIPTION
       " port, range : 1 - port number. "
   ::= { gs2326pplusPoeAutoCheckEntry 1 }

gs2326pplusPoeAutoCheckPingIPAddress OBJECT-TYPE
   SYNTAX      DisplayString
   MAX-ACCESS  read-write
   STATUS      current
   DESCRIPTION
       "IP Address the system should ping.
        default: 0.0.0.0 . "
   ::= { gs2326pplusPoeAutoCheckEntry 2 }

gs2326pplusPoeAutoCheckIntervalTime OBJECT-TYPE
   SYNTAX      Integer32(10..120)
   MAX-ACCESS  read-write
   STATUS      current
   DESCRIPTION
       "Device will send checking message to PD each interval time.
        default: 30,
        range: 10-120 sec.  "
   ::= { gs2326pplusPoeAutoCheckEntry 3 }

gs2326pplusPoeAutoCheckRetryTime OBJECT-TYPE
   SYNTAX      Integer32(1..5)
   MAX-ACCESS  read-write
   STATUS      current
   DESCRIPTION
       "It will retry to send detection again.
        default: 3,
        range: 1-5.  "
   ::= { gs2326pplusPoeAutoCheckEntry 4 }

gs2326pplusPoeAutoCheckFailureLog OBJECT-TYPE
   SYNTAX      DisplayString
   MAX-ACCESS  read-only
   STATUS      current
   DESCRIPTION
       "Failure loggings counter. "
   ::= { gs2326pplusPoeAutoCheckEntry 5 }

gs2326pplusPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { gs2326pplusPoeAutoCheckEntry 6 }

gs2326pplusPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { gs2326pplusPoeAutoCheckEntry 7 }

gs2326pplusPoeScheduling                                                 OBJECT IDENTIFIER ::= { gs2326pplusPoe 4 }

gs2326pplusPoeSchedulingTable OBJECT-TYPE
   SYNTAX      SEQUENCE OF GS2326PPLUSPoeSchedulingEntry
   MAX-ACCESS  not-accessible
   STATUS      current
   DESCRIPTION
       " Configure PoE Scheduling Table. "
   ::= { gs2326pplusPoeScheduling 1 }

gs2326pplusPoeSchedulingEntry OBJECT-TYPE
   SYNTAX      GS2326PPLUSPoeSchedulingEntry
   MAX-ACCESS  not-accessible
   STATUS      current
   DESCRIPTION
       ""
   INDEX    { gs2326pplusPoeSchedulingPort }
   ::= { gs2326pplusPoeSchedulingTable 1 }

GS2326PPLUSPoeSchedulingEntry ::= SEQUENCE {
   gs2326pplusPoeSchedulingPort	        Integer32,
   gs2326pplusPoeSchedulingStatus	        INTEGER
}

gs2326pplusPoeSchedulingPort OBJECT-TYPE
   SYNTAX      Integer32(1..4094)
   MAX-ACCESS  not-accessible
   STATUS      current
   DESCRIPTION
       " port, range : 1 - port number. "
   ::= { gs2326pplusPoeSchedulingEntry 1 }

gs2326pplusPoeSchedulingStatus OBJECT-TYPE
   SYNTAX      INTEGER { disable(0), enable(1) }
   MAX-ACCESS  read-write
   STATUS      current
   DESCRIPTION
       "PoE Scheduling Status.
        0: Disable,
        1: Enable,
        default: Disable. "
   ::= { gs2326pplusPoeSchedulingEntry 2 }

gs2326pplusPoeSchedulingTimeTable OBJECT-TYPE
   SYNTAX      SEQUENCE OF GS2326PPLUSPoeSchedulingTimeEntry
   MAX-ACCESS  not-accessible
   STATUS      current
   DESCRIPTION
       " Show Poe Scheduling Time Config. "
   ::= { gs2326pplusPoeScheduling 2 }

gs2326pplusPoeSchedulingTimeEntry OBJECT-TYPE
   SYNTAX      GS2326PPLUSPoeSchedulingTimeEntry
   MAX-ACCESS  not-accessible
   STATUS      current
   DESCRIPTION
       ""
   INDEX    { gs2326pplusPoeSchedulingTimePort, gs2326pplusPoeSchedulingTimeWeek, gs2326pplusPoeSchedulingTimeHour  }
   ::= { gs2326pplusPoeSchedulingTimeTable 1 }

GS2326PPLUSPoeSchedulingTimeEntry ::= SEQUENCE {
   gs2326pplusPoeSchedulingTimePort		Integer32,
   gs2326pplusPoeSchedulingTimeWeek		INTEGER,
   gs2326pplusPoeSchedulingTimeHour		Integer32,
   gs2326pplusPoeSchedulingProvidePower	INTEGER
}

gs2326pplusPoeSchedulingTimePort OBJECT-TYPE
   SYNTAX      Integer32(1..4095)
   MAX-ACCESS  not-accessible
   STATUS      current
   DESCRIPTION
       " port, range : 1 - port number. "
   ::= { gs2326pplusPoeSchedulingTimeEntry 1 }

gs2326pplusPoeSchedulingTimeWeek OBJECT-TYPE
   SYNTAX      INTEGER {
                        monday(1),
                        tuseday(2),
                        wednesday(3),
                        thursday(4),
                        friday(5),
                        saturday(6),
                        sunday(7)
                        }
   MAX-ACCESS  not-accessible
   STATUS      current
   DESCRIPTION
       " range: 1-7,
         Sunday:7, Monday:1, Tuseday:2, Wednesday:3, Thursday:4, Friday:5, Saturday:6.  "
   ::= { gs2326pplusPoeSchedulingTimeEntry 2 }

gs2326pplusPoeSchedulingTimeHour OBJECT-TYPE
   SYNTAX      Integer32(1..24)
   MAX-ACCESS  not-accessible
   STATUS      current
   DESCRIPTION
       " range: 1-24,
         24: hour 0, 1: hour 1, 2: hour2..."
   ::= { gs2326pplusPoeSchedulingTimeEntry 3 }

gs2326pplusPoeSchedulingProvidePower OBJECT-TYPE
   SYNTAX      INTEGER { disable(0), enable(1) }
   MAX-ACCESS  read-write
   STATUS      current
   DESCRIPTION
       " 0: disable,
         1: enable,
         default: disable.  "
   ::= { gs2326pplusPoeSchedulingTimeEntry 4 }

gs2326pplusPoeConfiguration                                                 OBJECT IDENTIFIER ::= { gs2326pplusPoe 5 }

gs2326pplusPoeConfigurationPrimaryPowerSupply  OBJECT-TYPE
   SYNTAX      Integer32(0..1000)
   MAX-ACCESS  read-only
   STATUS      current
   DESCRIPTION
       "It must be defined what amount of power the primary and backup power sources
        can deliver. "
   ::= { gs2326pplusPoeConfiguration 1 }

gs2326pplusPoeConfigurationRetryTime OBJECT-TYPE
   SYNTAX      Integer32(0|5|10|20|30|40|50|60)
   MAX-ACCESS  read-write
   STATUS      current
   DESCRIPTION
       "The period (in seconds) for trying to turn on an overloaded PoE port.
        0: disable,
        5 sec,10 sec,20 sec,30 sec,40 sec,50 sec,60 sec,
        default: 60 sec. "
   ::= { gs2326pplusPoeConfiguration 2 }

gs2326pplusPoeConfigurationTable OBJECT-TYPE
   SYNTAX      SEQUENCE OF GS2326PPLUSPoeConfigurationEntry
   MAX-ACCESS  not-accessible
   STATUS      current
   DESCRIPTION
       " Configure PoE Configuration mode. "
   ::= { gs2326pplusPoeConfiguration 3 }

gs2326pplusPoeConfigurationEntry OBJECT-TYPE
   SYNTAX      GS2326PPLUSPoeConfigurationEntry
   MAX-ACCESS  not-accessible
   STATUS      current
   DESCRIPTION
       ""
   INDEX    { gs2326pplusPoeConfigurationPort  }
   ::= { gs2326pplusPoeConfigurationTable 1 }

GS2326PPLUSPoeConfigurationEntry ::= SEQUENCE {
   gs2326pplusPoeConfigurationPort	       Integer32,
   gs2326pplusPoeConfigurationPoEMode       INTEGER,
   gs2326pplusPoeConfigurationPriority      INTEGER,
   gs2326pplusPoeConfigurationMaximumPower  DisplayString,
   gs2326pplusPoeConfigurationDetection     INTEGER,
   gs2326pplusPoeConfigurationReset         INTEGER
}

gs2326pplusPoeConfigurationPort OBJECT-TYPE
   SYNTAX      Integer32(1..4094)
   MAX-ACCESS  not-accessible
   STATUS      current
   DESCRIPTION
       " port, range : 1 - port number. "
   ::= { gs2326pplusPoeConfigurationEntry 1 }

gs2326pplusPoeConfigurationPoEMode OBJECT-TYPE
   SYNTAX      INTEGER { disable(0), enable(1) }
   MAX-ACCESS  read-write
   STATUS      current
   DESCRIPTION
       "The PoE Mode represents the PoE operating mode for the port.
        0: Disable,
        1: Enable,
        default: Enable. "
   ::= { gs2326pplusPoeConfigurationEntry 2 }

gs2326pplusPoeConfigurationPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { gs2326pplusPoeConfigurationEntry 3 }

gs2326pplusPoeConfigurationMaximumPower OBJECT-TYPE
   SYNTAX      DisplayString
   MAX-ACCESS  read-write
   STATUS      current
   DESCRIPTION
       "The Maximum Power value contains a numerical value that indicates the maximum
        power in watts that can be delivered to a remote device.
        default: 15.4[W],
        max: 30[W]. "
   ::= { gs2326pplusPoeConfigurationEntry 4 }

gs2326pplusPoeConfigurationDetection OBJECT-TYPE
   SYNTAX      INTEGER(0..5)
   MAX-ACCESS  read-write
   STATUS      current
   DESCRIPTION
       "Configure PoE port capacitor detection.
        0: No Detection(read only),
        1: legacy,
        2: 4-point,
        3: 4-point-legacy,
        4: 2-point,
        5: 2-point-legacy,
        default: 4-point. "
   ::= { gs2326pplusPoeConfigurationEntry 5 }

gs2326pplusPoeConfigurationReset OBJECT-TYPE
   SYNTAX      INTEGER { disable(0), enable(1) }
   MAX-ACCESS  read-write
   STATUS      current
   DESCRIPTION
       "Reset the specific PoE port.
        0: Disable,
        1: Enable,
        default: Disable. "
   ::= { gs2326pplusPoeConfigurationEntry 6 }

gs2326pplusPoeConfigurationLegacyMode  OBJECT-TYPE
   SYNTAX      INTEGER { disable(0), enable(1) }
   MAX-ACCESS  read-write
   STATUS      current
   DESCRIPTION
       "Legacy Detection.
        0: Disable,
        1: Enable,
        default: Disable. "
   ::= { gs2326pplusPoeConfiguration 4 }


gs2326pplusQos                                                             OBJECT IDENTIFIER ::= { gs2326pplusConfiguration 14 }

gs2326pplusQosPortClassification                                           OBJECT IDENTIFIER ::= { gs2326pplusQos 1 }

gs2326pplusQosPortClassificationTable OBJECT-TYPE
   SYNTAX      SEQUENCE OF GS2326PPLUSQosPortClassificationEntry
   MAX-ACCESS  not-accessible
   STATUS      current
   DESCRIPTION
       " QoS Ingress Port Classification . "
   ::= { gs2326pplusQosPortClassification  1 }

gs2326pplusQosPortClassificationEntry OBJECT-TYPE
   SYNTAX      GS2326PPLUSQosPortClassificationEntry
   MAX-ACCESS  not-accessible
   STATUS      current
   DESCRIPTION
       ""
   INDEX    { gs2326pplusQosPortClassificationPort  }
   ::= { gs2326pplusQosPortClassificationTable 1 }

GS2326PPLUSQosPortClassificationEntry ::= SEQUENCE {
   gs2326pplusQosPortClassificationPort	        Integer32,
   gs2326pplusQosPortClassificationQoSclass       Integer32,
   gs2326pplusQosPortClassificationDPlevel	    Integer32,
   gs2326pplusQosPortClassificationPCP	        Integer32,
   gs2326pplusQosPortClassificationDEI	        INTEGER,
   gs2326pplusQosPortClassificationTagClass	    INTEGER,
   gs2326pplusQosPortClassificationDSCPBased    INTEGER,
   gs2326pplusQosPortClassificationAddressMode  INTEGER
}

gs2326pplusQosPortClassificationPort OBJECT-TYPE
   SYNTAX      Integer32(1..4095)
   MAX-ACCESS  not-accessible
   STATUS      current
   DESCRIPTION
       " port, range : 1 - port number. "
   ::= { gs2326pplusQosPortClassificationEntry 1 }

gs2326pplusQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2326pplusQosPortClassificationEntry 2 }

gs2326pplusQosPortClassificationDPlevel OBJECT-TYPE
   SYNTAX      Integer32(0|1)
   MAX-ACCESS  read-write
   STATUS      current
   DESCRIPTION
       " DP level for frames not classified in any other way.
         range: 0-1,
         default: 0. "
   ::= { gs2326pplusQosPortClassificationEntry 3 }

gs2326pplusQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2326pplusQosPortClassificationEntry 4 }

gs2326pplusQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2326pplusQosPortClassificationEntry 5 }

gs2326pplusQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2326pplusQosPortClassificationEntry 6 }

gs2326pplusQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2326pplusQosPortClassificationEntry 7 }

gs2326pplusQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2326pplusQosPortClassificationEntry 8 }

gs2326pplusQoSIngressPortTagClassificationTable OBJECT-TYPE
   SYNTAX      SEQUENCE OF GS2326PPLUSQoSIngressPortTagClassificationEntry
   MAX-ACCESS  not-accessible
   STATUS      current
   DESCRIPTION
       " Show QoS Ingress Port Tag Classification. "
   ::= { gs2326pplusQosPortClassification 2 }

gs2326pplusQoSIngressPortTagClassificationEntry OBJECT-TYPE
   SYNTAX      GS2326PPLUSQoSIngressPortTagClassificationEntry
   MAX-ACCESS  not-accessible
   STATUS      current
   DESCRIPTION
       ""
   INDEX    { gs2326pplusQoSIngressPortTagClassificationPort, gs2326pplusQoSIngressPortTagPCP, gs2326pplusQoSIngressPortTagDEI  }
   ::= { gs2326pplusQoSIngressPortTagClassificationTable 1 }

GS2326PPLUSQoSIngressPortTagClassificationEntry ::= SEQUENCE {
   gs2326pplusQoSIngressPortTagClassificationPort	Integer32,
   gs2326pplusQoSIngressPortTagPCP					INTEGER,
   gs2326pplusQoSIngressPortTagDEI					INTEGER,
   gs2326pplusQoSIngressPortTagQosClass				Integer32,
   gs2326pplusQoSIngressPortTagDPLevel				Integer32
}

gs2326pplusQoSIngressPortTagClassificationPort OBJECT-TYPE
   SYNTAX      Integer32(1..4095)
   MAX-ACCESS  not-accessible
   STATUS      current
   DESCRIPTION
       " port, range : 1 - port number. "
   ::= { gs2326pplusQoSIngressPortTagClassificationEntry 1 }

gs2326pplusQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2326pplusQoSIngressPortTagClassificationEntry 2 }

gs2326pplusQoSIngressPortTagDEI OBJECT-TYPE
   SYNTAX      INTEGER { dei0(1), dei1(2) }
   MAX-ACCESS  not-accessible
   STATUS      current
   DESCRIPTION
       " range: 1-2,
         DEI0:1, DEI1:2. "
   ::= { gs2326pplusQoSIngressPortTagClassificationEntry 3 }

gs2326pplusQoSIngressPortTagQosClass OBJECT-TYPE
   SYNTAX      Integer32 (0..7)
   MAX-ACCESS  read-write
   STATUS      current
   DESCRIPTION
       " range: 0-7.  "
   ::= { gs2326pplusQoSIngressPortTagClassificationEntry 4 }

gs2326pplusQoSIngressPortTagDPLevel OBJECT-TYPE
   SYNTAX      Integer32 (0|1)
   MAX-ACCESS  read-write
   STATUS      current
   DESCRIPTION
       " range: 0-1.  "
   ::= { gs2326pplusQoSIngressPortTagClassificationEntry 5 }


gs2326pplusQosPortPolicingTable OBJECT-TYPE
   SYNTAX      SEQUENCE OF GS2326PPLUSQosPortPolicingEntry
   MAX-ACCESS  not-accessible
   STATUS      current
   DESCRIPTION
       "  configure the Policer settings for all switch ports. "
   ::= { gs2326pplusQos  2 }

gs2326pplusQosPortPolicingEntry OBJECT-TYPE
   SYNTAX      GS2326PPLUSQosPortPolicingEntry
   MAX-ACCESS  not-accessible
   STATUS      current
   DESCRIPTION
       ""
   INDEX    { gs2326pplusQosPortPolicingPort  }
   ::= { gs2326pplusQosPortPolicingTable 1 }

GS2326PPLUSQosPortPolicingEntry ::= SEQUENCE {
   gs2326pplusQosPortPolicingPort	        Integer32,
   gs2326pplusQosPortPolicingMode           INTEGER,
   gs2326pplusQosPortPolicingRate	        Integer32,
   gs2326pplusQosPortPolicingUnit	        INTEGER,
   gs2326pplusQosPortPolicingFlowControl	INTEGER
}

gs2326pplusQosPortPolicingPort OBJECT-TYPE
   SYNTAX      Integer32 (1..4095)
   MAX-ACCESS  not-accessible
   STATUS      current
   DESCRIPTION
       " port, range : 1 - port number. "
   ::= { gs2326pplusQosPortPolicingEntry 1 }

gs2326pplusQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2326pplusQosPortPolicingEntry 2 }

gs2326pplusQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2326pplusQosPortPolicingEntry 3 }

gs2326pplusQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2326pplusQosPortPolicingEntry 4 }

gs2326pplusQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2326pplusQosPortPolicingEntry 5 }

gs2326pplusQosPortScheduler                                           OBJECT IDENTIFIER ::= { gs2326pplusQos 3 }

gs2326pplusQosPortSchedulerModeTable OBJECT-TYPE
   SYNTAX      SEQUENCE OF GS2326PPLUSQosPortSchedulerModeEntry
   MAX-ACCESS  not-accessible
   STATUS      current
   DESCRIPTION
       " configure the basic QoS Port Scheduler Mode settings for all switch ports. "
   ::= { gs2326pplusQosPortScheduler  1 }

gs2326pplusQosPortSchedulerModeEntry OBJECT-TYPE
   SYNTAX      GS2326PPLUSQosPortSchedulerModeEntry
   MAX-ACCESS  not-accessible
   STATUS      current
   DESCRIPTION
       ""
   INDEX    { gs2326pplusQosSchedulerModePort  }
   ::= { gs2326pplusQosPortSchedulerModeTable 1 }

GS2326PPLUSQosPortSchedulerModeEntry ::= SEQUENCE {
   gs2326pplusQosSchedulerModePort	                Integer32,
   gs2326pplusQosSchedulerMode                        INTEGER,
   gs2326pplusQosSchedulerShaper	                    INTEGER,
   gs2326pplusQosSchedulerShaperRate	                Integer32
}

gs2326pplusQosSchedulerModePort OBJECT-TYPE
   SYNTAX      Integer32 (1..4095)
   MAX-ACCESS  not-accessible
   STATUS      current
   DESCRIPTION
       " port, range : 1 - port number. "
   ::= { gs2326pplusQosPortSchedulerModeEntry 1 }

gs2326pplusQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2326pplusQosPortSchedulerModeEntry 2 }

gs2326pplusQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2326pplusQosPortSchedulerModeEntry 3 }

gs2326pplusQosSchedulerShaperRate OBJECT-TYPE
   SYNTAX      Integer32(100..1000000)
   MAX-ACCESS  read-write
   STATUS      current
   DESCRIPTION
       " Controls the rate for the port shaper.
         range: 100-1000000
         default: 500 kbps. "
   ::= { gs2326pplusQosPortSchedulerModeEntry 4 }

gs2326pplusQosPortSchedulerTable OBJECT-TYPE
   SYNTAX      SEQUENCE OF GS2326PPLUSQosPortSchedulerEntry
   MAX-ACCESS  not-accessible
   STATUS      current
   DESCRIPTION
       " Show Qos Port Scheduler. "
   ::= { gs2326pplusQosPortScheduler 2 }

gs2326pplusQosPortSchedulerEntry OBJECT-TYPE
   SYNTAX      GS2326PPLUSQosPortSchedulerEntry
   MAX-ACCESS  not-accessible
   STATUS      current
   DESCRIPTION
       ""
   INDEX    { gs2326pplusQosSchedulerPort, gs2326pplusQosSchedulerPortQueue}
   ::= { gs2326pplusQosPortSchedulerTable 1 }

GS2326PPLUSQosPortSchedulerEntry ::= SEQUENCE {
   gs2326pplusQosSchedulerPort						Integer32,
   gs2326pplusQosSchedulerPortQueue					INTEGER,
   gs2326pplusQosSchedulerPortQueueShaper				INTEGER,
   gs2326pplusQosSchedulerPortQueueShaperRate			Integer32,
   gs2326pplusQosSchedulerPortQueueShaperExcess		INTEGER,
   gs2326pplusQosSchedulerPortQueueSchedulerWeight	Integer32,
   gs2326pplusQosSchedulerPortQueueSchedulerPercent	DisplayString
}

gs2326pplusQosSchedulerPort OBJECT-TYPE
   SYNTAX      Integer32 (1..4095)
   MAX-ACCESS  not-accessible
   STATUS      current
   DESCRIPTION
       " port, range : 1 - port number. "
   ::= { gs2326pplusQosPortSchedulerEntry 1 }

gs2326pplusQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2326pplusQosPortSchedulerEntry 2 }

gs2326pplusQosSchedulerPortQueueShaper OBJECT-TYPE
   SYNTAX      INTEGER { disable(0), enable(1) }
   MAX-ACCESS  read-write
   STATUS      current
   DESCRIPTION
       " 0: disable  1:enable,
         default: 0.  "
   ::= { gs2326pplusQosPortSchedulerEntry 3 }

gs2326pplusQosSchedulerPortQueueShaperRate OBJECT-TYPE
   SYNTAX      Integer32(100..1000000)
   MAX-ACCESS  read-write
   STATUS      current
   DESCRIPTION
       " range: 100..1000000 kbps.  "
   ::= { gs2326pplusQosPortSchedulerEntry 4 }

gs2326pplusQosSchedulerPortQueueShaperExcess OBJECT-TYPE
   SYNTAX      INTEGER { disable(0), enable(1) }
   MAX-ACCESS  read-write
   STATUS      current
   DESCRIPTION
       " 0: disable  1:enable,
         default: 0.  "
   ::= { gs2326pplusQosPortSchedulerEntry 5 }

gs2326pplusQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2326pplusQosPortSchedulerEntry 6 }

gs2326pplusQosSchedulerPortQueueSchedulerPercent OBJECT-TYPE
   SYNTAX      DisplayString
   MAX-ACCESS  read-only
   STATUS      current
   DESCRIPTION
       " Only use in Q0 - Q5. Q6 & Q7 show empty "
   ::= { gs2326pplusQosPortSchedulerEntry 7 }

gs2326pplusQosPortEgressTagRemarking                                           OBJECT IDENTIFIER ::= { gs2326pplusQos 4 }

gs2326pplusQosPortEgressTagRemarkingTable OBJECT-TYPE
   SYNTAX      SEQUENCE OF GS2326PPLUSQosPortEgressTagRemarkingEntry
   MAX-ACCESS  not-accessible
   STATUS      current
   DESCRIPTION
       " configure the basic QoS Port Egress Tag Remark Configuration settings for all switch ports. "
   ::= { gs2326pplusQosPortEgressTagRemarking  1 }

gs2326pplusQosPortEgressTagRemarkingEntry OBJECT-TYPE
   SYNTAX      GS2326PPLUSQosPortEgressTagRemarkingEntry
   MAX-ACCESS  not-accessible
   STATUS      current
   DESCRIPTION
       ""
   INDEX    { gs2326pplusQosEgressTagRemarkingPort  }
   ::= { gs2326pplusQosPortEgressTagRemarkingTable 1 }

GS2326PPLUSQosPortEgressTagRemarkingEntry ::= SEQUENCE {
   gs2326pplusQosEgressTagRemarkingPort	                Integer32,
   gs2326pplusQosEgressTagRemarkingMode	                INTEGER
}

gs2326pplusQosEgressTagRemarkingPort OBJECT-TYPE
   SYNTAX      Integer32 (1..4095)
   MAX-ACCESS  not-accessible
   STATUS      current
   DESCRIPTION
       " port, range : 1 - port number. "
   ::= { gs2326pplusQosPortEgressTagRemarkingEntry 1 }

gs2326pplusQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2326pplusQosPortEgressTagRemarkingEntry 2 }


gs2326pplusQosPortEgressTagRemarkingDefTable OBJECT-TYPE
   SYNTAX      SEQUENCE OF GS2326PPLUSQosPortEgressTagRemarkingDefEntry
   MAX-ACCESS  not-accessible
   STATUS      current
   DESCRIPTION
       " configure the basic QoS Port Egress Tag Remark Configuration settings for all switch ports. "
   ::= { gs2326pplusQosPortEgressTagRemarking  2 }

gs2326pplusQosPortEgressTagRemarkingDefEntry OBJECT-TYPE
   SYNTAX      GS2326PPLUSQosPortEgressTagRemarkingDefEntry
   MAX-ACCESS  not-accessible
   STATUS      current
   DESCRIPTION
       ""
   INDEX    { gs2326pplusQosEgressTagRemarkingDefPort  }
   ::= { gs2326pplusQosPortEgressTagRemarkingDefTable 1 }

GS2326PPLUSQosPortEgressTagRemarkingDefEntry ::= SEQUENCE {
   gs2326pplusQosEgressTagRemarkingDefPort	            Integer32,
   gs2326pplusQosEgressTagRemarkingDefPCP	                Integer32,
   gs2326pplusQosEgressTagRemarkingDefDEI	                INTEGER
}

gs2326pplusQosEgressTagRemarkingDefPort OBJECT-TYPE
   SYNTAX      Integer32(1..4095)
   MAX-ACCESS  not-accessible
   STATUS      current
   DESCRIPTION
       " port, range : 1 - port number. "
   ::= { gs2326pplusQosPortEgressTagRemarkingDefEntry 1 }

gs2326pplusQosEgressTagRemarkingDefPCP OBJECT-TYPE
   SYNTAX      Integer32(0..7)
   MAX-ACCESS  read-write
   STATUS      current
   DESCRIPTION
       " Controls the default PCP
       Range : 0-7"
   ::= { gs2326pplusQosPortEgressTagRemarkingDefEntry 2 }

gs2326pplusQosEgressTagRemarkingDefDEI OBJECT-TYPE
   SYNTAX      INTEGER { disable(0), enable(1) }
   MAX-ACCESS  read-write
   STATUS      current
   DESCRIPTION
       " controls the DEI
       Range 0-1"
   ::= { gs2326pplusQosPortEgressTagRemarkingDefEntry 3 }

gs2326pplusQosPortEgressTagRemarkingMapTable OBJECT-TYPE
   SYNTAX      SEQUENCE OF GS2326PPLUSQosPortEgressTagRemarkingMapEntry
   MAX-ACCESS  not-accessible
   STATUS      current
   DESCRIPTION
       " Show Qos Port Egress Tag Remarking Map. "
   ::= { gs2326pplusQosPortEgressTagRemarking 4 }

gs2326pplusQosPortEgressTagRemarkingMapEntry OBJECT-TYPE
   SYNTAX      GS2326PPLUSQosPortEgressTagRemarkingMapEntry
   MAX-ACCESS  not-accessible
   STATUS      current
   DESCRIPTION
       ""
   INDEX    { gs2326pplusQosPortEgressTagRemarkingMapPort, gs2326pplusQosTagRemarkingQoSClass, gs2326pplusQosTagRemarkingDPLevel  }
   ::= { gs2326pplusQosPortEgressTagRemarkingMapTable 1 }

GS2326PPLUSQosPortEgressTagRemarkingMapEntry ::= SEQUENCE {
   gs2326pplusQosPortEgressTagRemarkingMapPort	Integer32,
   gs2326pplusQosTagRemarkingQoSClass			INTEGER,
   gs2326pplusQosTagRemarkingDPLevel				INTEGER,
   gs2326pplusQosTagRemarkingPCP					Integer32,
   gs2326pplusQosTagRemarkingDEI					INTEGER
}

gs2326pplusQosPortEgressTagRemarkingMapPort OBJECT-TYPE
   SYNTAX      Integer32 (1..4095)
   MAX-ACCESS  not-accessible
   STATUS      current
   DESCRIPTION
       " port, range : 1 - port number. "
   ::= { gs2326pplusQosPortEgressTagRemarkingMapEntry 1 }

gs2326pplusQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2326pplusQosPortEgressTagRemarkingMapEntry 2 }

gs2326pplusQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2326pplusQosPortEgressTagRemarkingMapEntry 3 }

gs2326pplusQosTagRemarkingPCP OBJECT-TYPE
   SYNTAX      Integer32 (0..7)
   MAX-ACCESS  read-write
   STATUS      current
   DESCRIPTION
       " range: 0-7.  "
   ::= { gs2326pplusQosPortEgressTagRemarkingMapEntry 4 }

gs2326pplusQosTagRemarkingDEI OBJECT-TYPE
   SYNTAX      INTEGER (0|1)
   MAX-ACCESS  read-write
   STATUS      current
   DESCRIPTION
       " range: 0-1.  "
   ::= { gs2326pplusQosPortEgressTagRemarkingMapEntry 5 }


gs2326pplusQosPortDSCPTable OBJECT-TYPE
   SYNTAX      SEQUENCE OF GS2326PPLUSQosPortDSCPEntry
   MAX-ACCESS  not-accessible
   STATUS      current
   DESCRIPTION
       " configure the basic QoS Port DSCP Configuration settings for all switch ports. "
   ::= { gs2326pplusQos  5 }

gs2326pplusQosPortDSCPEntry OBJECT-TYPE
   SYNTAX      GS2326PPLUSQosPortDSCPEntry
   MAX-ACCESS  not-accessible
   STATUS      current
   DESCRIPTION
       ""
   INDEX    { gs2326pplusQosPortDSCPPort  }
   ::= { gs2326pplusQosPortDSCPTable 1 }

GS2326PPLUSQosPortDSCPEntry ::= SEQUENCE {
   gs2326pplusQosPortDSCPPort	                Integer32,
   gs2326pplusQosPortDSCPIngressTranslate       INTEGER,
   gs2326pplusQosPortDSCPIngressClassify	    INTEGER,
   gs2326pplusQosPortDSCPEgressRewrite	        INTEGER
}

gs2326pplusQosPortDSCPPort OBJECT-TYPE
   SYNTAX      Integer32 (1..4095)
   MAX-ACCESS  not-accessible
   STATUS      current
   DESCRIPTION
       " port, range : 1 - port number. "
   ::= { gs2326pplusQosPortDSCPEntry 1 }

gs2326pplusQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2326pplusQosPortDSCPEntry 2 }

gs2326pplusQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2326pplusQosPortDSCPEntry 3 }

gs2326pplusQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2326pplusQosPortDSCPEntry 4 }


gs2326pplusQosDSCPTable OBJECT-TYPE
   SYNTAX      SEQUENCE OF GS2326PPLUSQosDSCPEntry
   MAX-ACCESS  not-accessible
   STATUS      current
   DESCRIPTION
       " configure the basic QoS DSCP based QoS Ingress Classification settings for all switches. "
   ::= { gs2326pplusQos  6 }

gs2326pplusQosDSCPEntry OBJECT-TYPE
   SYNTAX      GS2326PPLUSQosDSCPEntry
   MAX-ACCESS  not-accessible
   STATUS      current
   DESCRIPTION
       ""
   INDEX    { gs2326pplusQosDSCPList  }
   ::= { gs2326pplusQosDSCPTable 1 }

GS2326PPLUSQosDSCPEntry ::= SEQUENCE {
   gs2326pplusQosDSCPList       Integer32,
   gs2326pplusQosDSCP           DisplayString,
   gs2326pplusQosDSCPTrust      INTEGER,
   gs2326pplusQosDSCPQosClass	  Integer32,
   gs2326pplusQosDSCPDPL	      INTEGER
}

gs2326pplusQosDSCPList OBJECT-TYPE
   SYNTAX      Integer32(1..64)
   MAX-ACCESS  not-accessible
   STATUS      current
   DESCRIPTION
      " DSCP mapping table index(1-64). "
   ::= { gs2326pplusQosDSCPEntry 1 }

gs2326pplusQosDSCP OBJECT-TYPE
   SYNTAX      DisplayString
   MAX-ACCESS  read-only
   STATUS      current
   DESCRIPTION
      "Maximum number of supported DSCP values are 64."
   ::= { gs2326pplusQosDSCPEntry 2 }

gs2326pplusQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2326pplusQosDSCPEntry 3 }

gs2326pplusQosDSCPQosClass OBJECT-TYPE
   SYNTAX      Integer32(0..7)
   MAX-ACCESS  read-write
   STATUS      current
   DESCRIPTION
      " QoS class.
        range: 0-7,
        default: 0. "
   ::= { gs2326pplusQosDSCPEntry 4 }

gs2326pplusQosDSCPDPL OBJECT-TYPE
   SYNTAX      INTEGER(0|1)
   MAX-ACCESS  read-write
   STATUS      current
   DESCRIPTION
      " Drop Precedence Level.
        range: 0-1,
        default: disable. "
   ::= { gs2326pplusQosDSCPEntry 5 }

gs2326pplusQosDSCPTranslationTable OBJECT-TYPE
   SYNTAX      SEQUENCE OF GS2326PPLUSQosDSCPTranslationEntry
   MAX-ACCESS  not-accessible
   STATUS      current
   DESCRIPTION
       "  configure the basic QoS DSCP Translation settings for all switches. "
   ::= { gs2326pplusQos  7 }

gs2326pplusQosDSCPTranslationEntry OBJECT-TYPE
   SYNTAX      GS2326PPLUSQosDSCPTranslationEntry
   MAX-ACCESS  not-accessible
   STATUS      current
   DESCRIPTION
       ""
   INDEX    { gs2326pplusQosDSCPTranslationList  }
   ::= { gs2326pplusQosDSCPTranslationTable 1 }

GS2326PPLUSQosDSCPTranslationEntry ::= SEQUENCE {
   gs2326pplusQosDSCPTranslationList                 Integer32,
   gs2326pplusQosDSCPTranslationDSCPBasedId          DisplayString,
   gs2326pplusQosDSCPTranslationIngressTranslate     Integer32,
   gs2326pplusQosDSCPTranslationIngressClassify      INTEGER,
   gs2326pplusQosDSCPTranslationEgressRemapDP0       Integer32,
   gs2326pplusQosDSCPTranslationEgressRemapDP1       Integer32
}

gs2326pplusQosDSCPTranslationList OBJECT-TYPE
   SYNTAX      Integer32(1..64)
   MAX-ACCESS  not-accessible
   STATUS      current
   DESCRIPTION
      " DSCP translation table index(1-64). "
   ::= { gs2326pplusQosDSCPTranslationEntry 1 }

gs2326pplusQosDSCPTranslationDSCPBasedId OBJECT-TYPE
   SYNTAX      DisplayString
   MAX-ACCESS  read-write
   STATUS      current
   DESCRIPTION
      " Configure global ingress DSCP translation table. "
   ::= { gs2326pplusQosDSCPTranslationEntry 2 }

gs2326pplusQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2326pplusQosDSCPTranslationEntry 3 }

gs2326pplusQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2326pplusQosDSCPTranslationEntry 4 }

gs2326pplusQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2326pplusQosDSCPTranslationEntry 5 }

gs2326pplusQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2326pplusQosDSCPTranslationEntry 6 }


gs2326pplusQosDSCPClassificationTable OBJECT-TYPE
   SYNTAX      SEQUENCE OF GS2326PPLUSQosDSCPClassificationEntry
   MAX-ACCESS  not-accessible
   STATUS      current
   DESCRIPTION
       "   configure the mapping of QoS class  to DSCP value. "
   ::= { gs2326pplusQos  8 }

gs2326pplusQosDSCPClassificationEntry OBJECT-TYPE
   SYNTAX      GS2326PPLUSQosDSCPClassificationEntry
   MAX-ACCESS  not-accessible
   STATUS      current
   DESCRIPTION
       ""
   INDEX    { gs2326pplusQosDSCPClassificationQoSClass, gs2326pplusQosDSCPClassificationDPL }
   ::= { gs2326pplusQosDSCPClassificationTable 1 }

GS2326PPLUSQosDSCPClassificationEntry ::= SEQUENCE {
   gs2326pplusQosDSCPClassificationQoSClass		INTEGER,
   gs2326pplusQosDSCPClassificationDPL			INTEGER,
   gs2326pplusQosDSCPClassificationDSCP			Integer32
}

gs2326pplusQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2326pplusQosDSCPClassificationEntry 1 }

gs2326pplusQosDSCPClassificationDPL OBJECT-TYPE
   SYNTAX      INTEGER(1|2)
   MAX-ACCESS  not-accessible
   STATUS      current
   DESCRIPTION
      " DPL. Index 1~2 mean DPL 0~1."
   ::= { gs2326pplusQosDSCPClassificationEntry 2 }

gs2326pplusQosDSCPClassificationDSCP OBJECT-TYPE
   SYNTAX      Integer32(0..63)
   MAX-ACCESS  read-write
   STATUS      current
   DESCRIPTION
      " Select the classified DSCP value.
        range: 0-63,
        default: 0. "
   ::= { gs2326pplusQosDSCPClassificationEntry 3 }

gs2326pplusQosControlList                                         OBJECT IDENTIFIER ::= { gs2326pplusQos 9 }

gs2326pplusQosQceCreate OBJECT-TYPE
   SYNTAX       INTEGER { none(0), create(1) }
   MAX-ACCESS   read-write
   STATUS       current
   DESCRIPTION
       "default: 0
        0 : None  (read only)
        1 : Create an Qos entry"
   ::= { gs2326pplusQosControlList 1 }

gs2326pplusQosQceTable OBJECT-TYPE
   SYNTAX      SEQUENCE OF GS2326PPLUSQosQceEntry
   MAX-ACCESS  not-accessible
   STATUS      current
   DESCRIPTION
       " Create Qos QCE entry. "
   ::= { gs2326pplusQosControlList 2 }

gs2326pplusQosQceEntry OBJECT-TYPE
   SYNTAX      GS2326PPLUSQosQceEntry
   MAX-ACCESS  not-accessible
   STATUS      current
   DESCRIPTION
       ""
   INDEX    { gs2326pplusQosQceIndex  }
   ::= { gs2326pplusQosQceTable 1 }

GS2326PPLUSQosQceEntry ::= SEQUENCE {
   gs2326pplusQosQceIndex                Integer32,
   gs2326pplusQosQceID                   Integer32,
   gs2326pplusQosQceNextID               Integer32,
   gs2326pplusQosQcePortMembers          DisplayString,

   gs2326pplusQosQceTag                  DisplayString,
   gs2326pplusQosQceVID                  DisplayString,
   gs2326pplusQosPCP                     DisplayString,
   gs2326pplusQosDEI                     DisplayString,
   gs2326pplusQosSMAC                    DisplayString,
   gs2326pplusQosDMACType                DisplayString,
   gs2326pplusQosFrameType               INTEGER,

   gs2326pplusQosMacEtherType            DisplayString,

   gs2326pplusQosLLCSSAPAddr             DisplayString,
   gs2326pplusQosLLCDSAPAddr             DisplayString,
   gs2326pplusQosLLCControl              DisplayString,

   gs2326pplusQosSNAPPID                 DisplayString,

   gs2326pplusQosIpv4Protocol            DisplayString,
   gs2326pplusQosIpv4ProtocolValue       Integer32,
   gs2326pplusQosIpv4ProtocolUDPSport    DisplayString,
   gs2326pplusQosIpv4ProtocolUDPDport    DisplayString,
   gs2326pplusQosIpv4ProtocolTCPSport    DisplayString,
   gs2326pplusQosIpv4ProtocolTCPDport    DisplayString,
   gs2326pplusQosIpv4Ip                  DisplayString,
   gs2326pplusQosIpv4Mask                DisplayString,
   gs2326pplusQosIpv4IPFragment          INTEGER,
   gs2326pplusQosIpv4DSCP                DisplayString,


   gs2326pplusQosIpv6Protocol            DisplayString,
   gs2326pplusQosIpv6ProtocolValue       Integer32,
   gs2326pplusQosIpv6ProtocolUDPSport    DisplayString,
   gs2326pplusQosIpv6ProtocolUDPDport    DisplayString,
   gs2326pplusQosIpv6ProtocolTCPSport    DisplayString,
   gs2326pplusQosIpv6ProtocolTCPDport    DisplayString,
   gs2326pplusQosIpv6Ip                  DisplayString,
   gs2326pplusQosIpv6Mask                DisplayString,
   gs2326pplusQosIpv6DSCP                DisplayString,

   gs2326pplusQosActionClass             Integer32,
   gs2326pplusQosActionDPL               INTEGER,
   gs2326pplusQosActionDSCP              Integer32,
   gs2326pplusQosQceRowStatus            INTEGER
}

gs2326pplusQosQceIndex OBJECT-TYPE
   SYNTAX      Integer32(1..256)
   MAX-ACCESS  not-accessible
   STATUS      current
   DESCRIPTION
       " "
   ::= { gs2326pplusQosQceEntry 1 }

gs2326pplusQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2326pplusQosQceEntry 2 }

gs2326pplusQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2326pplusQosQceEntry 3 }

gs2326pplusQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2326pplusQosQceEntry 4 }

gs2326pplusQosQceTag OBJECT-TYPE
   SYNTAX      DisplayString
   MAX-ACCESS  read-write
   STATUS      current
   DESCRIPTION
       " Value of Tag field can be 'Any', 'Untag' or 'Tag'. "
   ::= { gs2326pplusQosQceEntry 5 }

gs2326pplusQosQceVID OBJECT-TYPE
   SYNTAX      DisplayString
   MAX-ACCESS  read-write
   STATUS      current
   DESCRIPTION
       " Valid value of VLAN ID can be any value in 'Specific 1~4094' or 'range 1-4094' or 'Any'. "
   ::= { gs2326pplusQosQceEntry 6 }

gs2326pplusQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2326pplusQosQceEntry 7 }

gs2326pplusQosDEI OBJECT-TYPE
   SYNTAX      DisplayString
   MAX-ACCESS  read-write
   STATUS      current
   DESCRIPTION
       " Drop Eligible Indicator: Valid value of DEI can be any of values between 0, 1 or 'Any'. "
   ::= { gs2326pplusQosQceEntry 8 }

gs2326pplusQosSMAC  OBJECT-TYPE
   SYNTAX      DisplayString
   MAX-ACCESS  read-write
   STATUS      current
   DESCRIPTION
       "  Source MAC address: 24 MS bits OUI(00-00-00 ~ FF-FF-FF) or 'Any'. "
   ::= { gs2326pplusQosQceEntry 9 }

gs2326pplusQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2326pplusQosQceEntry 10 }

gs2326pplusQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2326pplusQosQceEntry 11 }

gs2326pplusQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2326pplusQosQceEntry 12 }

gs2326pplusQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2326pplusQosQceEntry 13 }

gs2326pplusQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2326pplusQosQceEntry 14 }

gs2326pplusQosLLCControl OBJECT-TYPE
   SYNTAX      DisplayString
   MAX-ACCESS  read-write
   STATUS      current
   DESCRIPTION
       " Valid Control field can vary from 0x00 to 0xFF or 'Any',
         range: 00-FF,
         default: Any. "
   ::= { gs2326pplusQosQceEntry 15 }

gs2326pplusQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2326pplusQosQceEntry 16 }

gs2326pplusQosIpv4Protocol OBJECT-TYPE
   SYNTAX      DisplayString
   MAX-ACCESS  read-write
   STATUS      current
   DESCRIPTION
       " IP protocol number: (Other, TCP or UDP) or 'Any'. "
   ::= { gs2326pplusQosQceEntry 17 }

gs2326pplusQosIpv4ProtocolValue  OBJECT-TYPE
   SYNTAX      Integer32(0..255)
   MAX-ACCESS  read-write
   STATUS      current
   DESCRIPTION
       " Ipv4 Protocol is Other.
         range: 0-255
         default: 0. "
   ::= { gs2326pplusQosQceEntry 18 }

gs2326pplusQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2326pplusQosQceEntry 19 }

gs2326pplusQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326pplusQosQceEntry 20 }

gs2326pplusQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326pplusQosQceEntry 21 }

gs2326pplusQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326pplusQosQceEntry 22 }

gs2326pplusQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2326pplusQosQceEntry 23 }

gs2326pplusQosIpv4Mask OBJECT-TYPE
   SYNTAX      DisplayString
   MAX-ACCESS  read-write
   STATUS      current
   DESCRIPTION
       " Specific IP address in mask format or value 0.0.0.0 is 'Any'. "
   ::= { gs2326pplusQosQceEntry 24 }

gs2326pplusQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2326pplusQosQceEntry 25 }

gs2326pplusQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2326pplusQosQceEntry 26 }

gs2326pplusQosIpv6Protocol OBJECT-TYPE
   SYNTAX      DisplayString
   MAX-ACCESS  read-write
   STATUS      current
   DESCRIPTION
       " IP protocol number: (Other, TCP or UDP) or 'Any'. "
   ::= { gs2326pplusQosQceEntry 27 }

gs2326pplusQosIpv6ProtocolValue OBJECT-TYPE
   SYNTAX      Integer32(0..255)
   MAX-ACCESS  read-write
   STATUS      current
   DESCRIPTION
       " when IPv6 protocol is Other ,
         range: 0-255. "
   ::= { gs2326pplusQosQceEntry 28 }

gs2326pplusQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2326pplusQosQceEntry 29 }

gs2326pplusQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326pplusQosQceEntry 30 }

gs2326pplusQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326pplusQosQceEntry 31 }


gs2326pplusQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326pplusQosQceEntry 32 }

gs2326pplusQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2326pplusQosQceEntry 33 }

gs2326pplusQosIpv6Mask OBJECT-TYPE
   SYNTAX      DisplayString
   MAX-ACCESS  read-write
   STATUS      current
   DESCRIPTION
       " IPv6 mask address: (a.b.c.d) or value 0.0.0.0 is 'Any', 32 LS bits. "
   ::= { gs2326pplusQosQceEntry 34 }

gs2326pplusQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2326pplusQosQceEntry 35 }

gs2326pplusQosActionClass  OBJECT-TYPE
   SYNTAX      Integer32(0..8)
   MAX-ACCESS  read-write
   STATUS      current
   DESCRIPTION
       " QoS class: (0-7) or 8: Default."
   ::= { gs2326pplusQosQceEntry 36 }

gs2326pplusQosActionDPL OBJECT-TYPE
   SYNTAX      INTEGER (0..4)
   MAX-ACCESS  read-write
   STATUS      current
   DESCRIPTION
       " DP Valid Drop Precedence Level can be (0-3) or 4: Default. "
   ::= { gs2326pplusQosQceEntry 37 }

gs2326pplusQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2326pplusQosQceEntry 38 }

gs2326pplusQosQceRowStatus OBJECT-TYPE
   SYNTAX      INTEGER { active(1), notInservice(2), destroy(4) }
   MAX-ACCESS  read-write
   STATUS      current
   DESCRIPTION
       "  1: active2: notInservice 4: destroy"
   ::= { gs2326pplusQosQceEntry 39 }

gs2326pplusQosQceMoveID OBJECT-TYPE
   SYNTAX       Integer32(0..256)
   MAX-ACCESS   read-write
   STATUS       current
   DESCRIPTION
       " Move Qos,
         default: 0
         Qos ID must be exist.
         range : 0 - 256."
   ::= { gs2326pplusQosControlList 3 }

gs2326pplusQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2326pplusQosControlList 4 }


gs2326pplusQosQCLStatusTable OBJECT-TYPE
   SYNTAX      SEQUENCE OF GS2326PPLUSQosQCLStatusEntry
   MAX-ACCESS  not-accessible
   STATUS      current
   DESCRIPTION
       "  configure the basic QoS DSCP Translation settings for all switches. "
   ::= { gs2326pplusQos  10 }

gs2326pplusQosQCLStatusEntry OBJECT-TYPE
   SYNTAX      GS2326PPLUSQosQCLStatusEntry
   MAX-ACCESS  not-accessible
   STATUS      current
   DESCRIPTION
       ""
   INDEX    { gs2326pplusQosQCLStatusList  }
   ::= { gs2326pplusQosQCLStatusTable 1 }

GS2326PPLUSQosQCLStatusEntry ::= SEQUENCE {
   gs2326pplusQosQCLStatusList               Integer32,
   gs2326pplusQosQCLStatusUser               DisplayString,
   gs2326pplusQosQCLStatusQCEId              DisplayString,
   gs2326pplusQosQCLStatusFrameType          DisplayString,
   gs2326pplusQosQCLStatusPortlist           DisplayString,
   gs2326pplusQosQCLStatusActionClass	       DisplayString,
   gs2326pplusQosQCLStatusActionDPL	       DisplayString,
   gs2326pplusQosQCLStatusActionDSCP	       DisplayString,
   gs2326pplusQosQCLStatusActionConflict     DisplayString
}

gs2326pplusQosQCLStatusList OBJECT-TYPE
   SYNTAX      Integer32(1..4095)
   MAX-ACCESS  not-accessible
   STATUS      current
   DESCRIPTION
       " QCL table index. "
   ::= { gs2326pplusQosQCLStatusEntry 1}

gs2326pplusQosQCLStatusUser OBJECT-TYPE
   SYNTAX      DisplayString
   MAX-ACCESS  read-only
   STATUS      current
   DESCRIPTION
       " Indicates the QCL user. "
   ::= { gs2326pplusQosQCLStatusEntry 2 }

gs2326pplusQosQCLStatusQCEId OBJECT-TYPE
   SYNTAX      DisplayString
   MAX-ACCESS  read-only
   STATUS      current
   DESCRIPTION
      " Indicates the index of QCE. "
   ::= { gs2326pplusQosQCLStatusEntry 3}

gs2326pplusQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2326pplusQosQCLStatusEntry 4}

gs2326pplusQosQCLStatusPortlist OBJECT-TYPE
   SYNTAX      DisplayString
   MAX-ACCESS  read-only
   STATUS      current
   DESCRIPTION
       " Indicates the list of ports configured with the QCE. "
   ::= { gs2326pplusQosQCLStatusEntry 5}

gs2326pplusQosQCLStatusActionClass OBJECT-TYPE
   SYNTAX      DisplayString
   MAX-ACCESS  read-only
   STATUS      current
   DESCRIPTION
       " Classified QoS class; if a frame matches the QCE it will be put in the
       queue. "
   ::= { gs2326pplusQosQCLStatusEntry 6}

gs2326pplusQosQCLStatusActionDPL OBJECT-TYPE
   SYNTAX      DisplayString
   MAX-ACCESS  read-only
   STATUS      current
   DESCRIPTION
       " Drop Precedence Level; if a frame matches the QCE then DP level will
       set to value displayed under DPL column."
   ::= { gs2326pplusQosQCLStatusEntry 7}

gs2326pplusQosQCLStatusActionDSCP OBJECT-TYPE
   SYNTAX      DisplayString
   MAX-ACCESS  read-only
   STATUS      current
   DESCRIPTION
       " If a frame matches the QCE then DSCP will be classified with the value
       displayed under DSCP column."
   ::= { gs2326pplusQosQCLStatusEntry 8}

gs2326pplusQosQCLStatusActionConflict OBJECT-TYPE
   SYNTAX      DisplayString
   MAX-ACCESS  read-only
   STATUS      current
   DESCRIPTION
       " If a frame matches the QCE then DSCP will be classified with the value
        displayed under DSCP column. "
   ::= { gs2326pplusQosQCLStatusEntry 9}


gs2326pplusQosStormControl                                           OBJECT IDENTIFIER ::= { gs2326pplusQos 11 }

gs2326pplusQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2326pplusQosStormControl 2 }

gs2326pplusQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326pplusQosStormControl 3 }

gs2326pplusQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2326pplusQosStormControl 4 }

gs2326pplusQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326pplusQosStormControl 5 }

gs2326pplusQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2326pplusQosStormControl 6 }

gs2326pplusQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326pplusQosStormControl 7 }


gs2326pplusVlan                                                           OBJECT IDENTIFIER ::= { gs2326pplusConfiguration 15 }

gs2326pplusVlanPorts                                                      OBJECT IDENTIFIER ::= { gs2326pplusVlan 1 }

gs2326pplusVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2326pplusVlanPorts 1 }

gs2326pplusVlanPortsTable OBJECT-TYPE
   SYNTAX      SEQUENCE OF GS2326PPLUSVlanPortsEntry
   MAX-ACCESS  not-accessible
   STATUS      current
   DESCRIPTION
       " Configure Vlan ports Configuration mode. "
   ::= { gs2326pplusVlanPorts 2 }

gs2326pplusVlanPortsEntry OBJECT-TYPE
   SYNTAX      GS2326PPLUSVlanPortsEntry
   MAX-ACCESS  not-accessible
   STATUS      current
   DESCRIPTION
       ""
   INDEX    { gs2326pplusVlanPortsPort  }
   ::= { gs2326pplusVlanPortsTable 1 }

GS2326PPLUSVlanPortsEntry ::= SEQUENCE {
   gs2326pplusVlanPortsPort	         Integer32,
   gs2326pplusVlanPortsPVID     Integer32,
   gs2326pplusVlanPortsFrameType      INTEGER,
   gs2326pplusVlanPortsIngressFilter  INTEGER,
   gs2326pplusVlanPortsEgressRule     INTEGER,
   gs2326pplusVlanPortsPortType       INTEGER
}

gs2326pplusVlanPortsPort OBJECT-TYPE
   SYNTAX      Integer32(1..4094)
   MAX-ACCESS  not-accessible
   STATUS      current
   DESCRIPTION
       " port, range : 1 - port number. "
   ::= { gs2326pplusVlanPortsEntry 1 }

gs2326pplusVlanPortsPVID OBJECT-TYPE
   SYNTAX      Integer32(1..4094)
   MAX-ACCESS  read-write
   STATUS      current
   DESCRIPTION
       "Configure PVID.
        range: 1-4094,
        default: 1. "
   ::= { gs2326pplusVlanPortsEntry 2 }

gs2326pplusVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2326pplusVlanPortsEntry 3 }

gs2326pplusVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2326pplusVlanPortsEntry 4 }

gs2326pplusVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2326pplusVlanPortsEntry 5 }

gs2326pplusVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2326pplusVlanPortsEntry 6 }

gs2326pplusVlanPrivateVLAN                                                              OBJECT IDENTIFIER ::= { gs2326pplusVlan 2 }

gs2326pplusVlanPrivateVLANMembership                                                    OBJECT IDENTIFIER ::= { gs2326pplusVlanPrivateVLAN 1 }

gs2326pplusVlanPrivateVLANMembershipCreate OBJECT-TYPE
   SYNTAX       Integer32(1..4094)
   MAX-ACCESS   read-write
   STATUS       current
   DESCRIPTION
       "default: 0
        0 : None  (read only)
        1 : Create a pvlan"
   ::= { gs2326pplusVlanPrivateVLANMembership 1 }

gs2326pplusVlanPrivateVLANMembershipTable OBJECT-TYPE
   SYNTAX      SEQUENCE OF Gs2326pplusVlanPrivateVLANMembershipEntry
   MAX-ACCESS  not-accessible
   STATUS      current
   DESCRIPTION
       " Configure Private Vlan Configuration. "
   ::= { gs2326pplusVlanPrivateVLANMembership 2 }

gs2326pplusVlanPrivateVLANMembershipEntry OBJECT-TYPE
   SYNTAX      Gs2326pplusVlanPrivateVLANMembershipEntry
   MAX-ACCESS  not-accessible
   STATUS      current
   DESCRIPTION
       ""
   INDEX    { gs2326pplusVlanPrivateVLANIndex  }
   ::= { gs2326pplusVlanPrivateVLANMembershipTable 1 }

Gs2326pplusVlanPrivateVLANMembershipEntry ::= SEQUENCE {
   gs2326pplusVlanPrivateVLANIndex          Integer32,
   gs2326pplusVlanPrivateVLANID             Integer32,
   gs2326pplusVlanPrivateVLANMemberships    DisplayString,
   gs2326pplusVlanPrivateVLANRowStatus      INTEGER
}

gs2326pplusVlanPrivateVLANIndex OBJECT-TYPE
   SYNTAX      Integer32(1..52)
   MAX-ACCESS  not-accessible
   STATUS      current
   DESCRIPTION
       "private VLAN Index. "
   ::= { gs2326pplusVlanPrivateVLANMembershipEntry 1 }

gs2326pplusVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2326pplusVlanPrivateVLANMembershipEntry 2 }

gs2326pplusVlanPrivateVLANMemberships OBJECT-TYPE
   SYNTAX      DisplayString
   MAX-ACCESS  read-write
   STATUS      current
   DESCRIPTION
       "To include the ports in a Private VLAN"
   ::= { gs2326pplusVlanPrivateVLANMembershipEntry 3 }

gs2326pplusVlanPrivateVLANRowStatus OBJECT-TYPE
   SYNTAX      INTEGER { active(1), notInservice(2), destroy(4) }
   MAX-ACCESS  read-write
   STATUS      current
   DESCRIPTION
       "1: active
        2: notInservice
        4: destroy"
   ::= { gs2326pplusVlanPrivateVLANMembershipEntry 4 }

gs2326pplusVlanPortIsolationTable OBJECT-TYPE
   SYNTAX      SEQUENCE OF Gs2326pplusVlanPortIsolationEntry
   MAX-ACCESS  not-accessible
   STATUS      current
   DESCRIPTION
       " Configure Vlan Port Isolation Configuration. "
   ::= { gs2326pplusVlanPrivateVLAN 2 }

gs2326pplusVlanPortIsolationEntry OBJECT-TYPE
   SYNTAX      Gs2326pplusVlanPortIsolationEntry
   MAX-ACCESS  not-accessible
   STATUS      current
   DESCRIPTION
       ""
   INDEX    { gs2326pplusVlanPortIsolationPort  }
   ::= { gs2326pplusVlanPortIsolationTable 1 }

Gs2326pplusVlanPortIsolationEntry ::= SEQUENCE {
   gs2326pplusVlanPortIsolationPort Integer32,
   gs2326pplusVlanPortIsolation     INTEGER
}

gs2326pplusVlanPortIsolationPort OBJECT-TYPE
   SYNTAX      Integer32(1..4094)
   MAX-ACCESS  not-accessible
   STATUS      current
   DESCRIPTION
       " port, range : 1 - port number. "
   ::= { gs2326pplusVlanPortIsolationEntry 1 }

gs2326pplusVlanPortIsolation OBJECT-TYPE
   SYNTAX      INTEGER{ disable(0), enable(1) }
   MAX-ACCESS  read-write
   STATUS      current
   DESCRIPTION
       "default: 0
        0:disable
        1:enable"
   ::= { gs2326pplusVlanPortIsolationEntry 2 }


gs2326pplusMACbasedVLAN                                                      OBJECT IDENTIFIER ::= { gs2326pplusVlan 3 }

gs2326pplusMACbasedVLANConf                                                      OBJECT IDENTIFIER ::= { gs2326pplusMACbasedVLAN 1 }

gs2326pplusMACbasedVLANConfCreate OBJECT-TYPE
   SYNTAX       Integer32
   MAX-ACCESS   read-write
   STATUS       current
   DESCRIPTION
       "default: 0
       0 : None  (read only) 1 : Create MAC base vlan"
   ::= { gs2326pplusMACbasedVLANConf 1 }

gs2326pplusMACbasedVLANConfTable OBJECT-TYPE
   SYNTAX      SEQUENCE OF Gs2326pplusMACbasedVLANConfEntry
   MAX-ACCESS  not-accessible
   STATUS      current
   DESCRIPTION
       " Configure Vlan Port Isolation Configuration. "
   ::= { gs2326pplusMACbasedVLANConf 2 }

gs2326pplusMACbasedVLANConfEntry OBJECT-TYPE
   SYNTAX      Gs2326pplusMACbasedVLANConfEntry
   MAX-ACCESS  not-accessible
   STATUS      current
   DESCRIPTION
       ""
   INDEX    { gs2326pplusMACbasedVLANIndex  }
   ::= { gs2326pplusMACbasedVLANConfTable 1 }

Gs2326pplusMACbasedVLANConfEntry ::= SEQUENCE {
   gs2326pplusMACbasedVLANIndex         Integer32,
   gs2326pplusMACbasedVLANMACAddress    MacAddress,
   gs2326pplusMACbasedVLANID            Integer32,
   gs2326pplusMACbasedMemberships       DisplayString,
   gs2326pplusMACbaseRowStatus          INTEGER
}

gs2326pplusMACbasedVLANIndex OBJECT-TYPE
   SYNTAX      Integer32(1..256)
   MAX-ACCESS  read-write
   STATUS      current
   DESCRIPTION
       "Indicates the VLAN ID. "
   ::= { gs2326pplusMACbasedVLANConfEntry 1 }

gs2326pplusMACbasedVLANMACAddress OBJECT-TYPE
   SYNTAX      MacAddress
   MAX-ACCESS  read-write
   STATUS      current
   DESCRIPTION
       "Indicates the MAC address.
       The CreateEntry can be modify, the other entry can't be modify."
   ::= { gs2326pplusMACbasedVLANConfEntry 2 }

gs2326pplusMACbasedVLANID OBJECT-TYPE
   SYNTAX      Integer32(1..4094)
   MAX-ACCESS  read-write
   STATUS      current
   DESCRIPTION
       "Indicates the VLAN ID. "
   ::= { gs2326pplusMACbasedVLANConfEntry 3 }

gs2326pplusMACbasedMemberships OBJECT-TYPE
   SYNTAX      DisplayString
   MAX-ACCESS  read-write
   STATUS      current
   DESCRIPTION
       "The ports are displayed for each MAC-based VLAN entry.
        To include the port in a MAC-based VLAN"
   ::= { gs2326pplusMACbasedVLANConfEntry 4 }


gs2326pplusMACbaseRowStatus OBJECT-TYPE
   SYNTAX      INTEGER { active(1), notInservice(2), destroy(4)}
   MAX-ACCESS  read-write
   STATUS      current
   DESCRIPTION
       "1: active
        2: notInservice
        4: destroy"
   ::= { gs2326pplusMACbasedVLANConfEntry 5 }

gs2326pplusIGMPSnooping                                                           OBJECT IDENTIFIER ::= { gs2326pplusConfiguration 16 }

gs2326pplusIGMPSnoopingBasic                                                      OBJECT IDENTIFIER ::= { gs2326pplusIGMPSnooping 1 }

gs2326pplusIGMPSnoopingEnable  OBJECT-TYPE
   SYNTAX      INTEGER { disable(0), enable(1) }
   MAX-ACCESS  read-write
   STATUS      current
   DESCRIPTION
       "Enable/Disable the Global IGMP Snooping"
   ::= { gs2326pplusIGMPSnoopingBasic 1 }

gs2326pplusIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2326pplusIGMPSnoopingBasic 2 }

gs2326pplusIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326pplusIGMPSnoopingBasic 3 }

gs2326pplusIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2326pplusIGMPSnoopingBasic 4 }

gs2326pplusIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2326pplusIGMPSnoopingBasic 5 }

gs2326pplusIGMPSnoopingPortRelatedTable OBJECT-TYPE
   SYNTAX      SEQUENCE OF Gs2326pplusIGMPSnoopingPortRelatedEntry
   MAX-ACCESS  not-accessible
   STATUS      current
   DESCRIPTION
       " Configure IGMP Snooping Port Related Configuration. "
   ::= { gs2326pplusIGMPSnoopingBasic 6 }

gs2326pplusIGMPSnoopingPortRelatedEntry OBJECT-TYPE
   SYNTAX      Gs2326pplusIGMPSnoopingPortRelatedEntry
   MAX-ACCESS  not-accessible
   STATUS      current
   DESCRIPTION
       ""
   INDEX    { ifIndex  }
   ::= { gs2326pplusIGMPSnoopingPortRelatedTable 1 }

Gs2326pplusIGMPSnoopingPortRelatedEntry ::= SEQUENCE {
   gs2326pplusIGMPSnoopingRouterPort	INTEGER,
   gs2326pplusIGMPSnoopingFastLeave  	INTEGER,
   gs2326pplusIGMPSnoopingThrottling    Integer32
}

gs2326pplusIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326pplusIGMPSnoopingPortRelatedEntry 1 }

gs2326pplusIGMPSnoopingFastLeave OBJECT-TYPE
   SYNTAX      INTEGER { disable(0), enable(1) }
   MAX-ACCESS  read-write
   STATUS      current
   DESCRIPTION
       "Enable/Disable the fast leave on the port. "
   ::= { gs2326pplusIGMPSnoopingPortRelatedEntry 2 }

gs2326pplusIGMPSnoopingThrottling OBJECT-TYPE
   SYNTAX      Integer32(0..10)
   MAX-ACCESS  read-write
   STATUS      current
   DESCRIPTION
       "Enable to limit the number of multicast groups to which a switch port can belong.
       0: unlimited"
   ::= { gs2326pplusIGMPSnoopingPortRelatedEntry 3 }

gs2326pplusIGMPSnoopingVLANTable OBJECT-TYPE
   SYNTAX      SEQUENCE OF Gs2326pplusIGMPSnoopingVLANEntry
   MAX-ACCESS  not-accessible
   STATUS      current
   DESCRIPTION
       " Configure IGMP Snooping Vlan Configuration. "
   ::= { gs2326pplusIGMPSnooping 2 }

gs2326pplusIGMPSnoopingVLANEntry OBJECT-TYPE
   SYNTAX      Gs2326pplusIGMPSnoopingVLANEntry
   MAX-ACCESS  not-accessible
   STATUS      current
   DESCRIPTION
       ""
   INDEX    { gs2326pplusIGMPSnoopingVLANID  }
   ::= { gs2326pplusIGMPSnoopingVLANTable 1 }

Gs2326pplusIGMPSnoopingVLANEntry ::= SEQUENCE {
   gs2326pplusIGMPSnoopingVLANID        	Integer32,
   gs2326pplusIGMPSnoopingVLANEnable    	INTEGER,
   gs2326pplusIGMPSnoopingVLANIGMPQuerier   INTEGER,
   gs2326pplusIGMPSnoopingVLANCompatibility INTEGER,
   gs2326pplusIGMPSnoopingVLANRV        	Integer32,
   gs2326pplusIGMPSnoopingVLANQI      	    Integer32,
   gs2326pplusIGMPSnoopingVLANQRI   	    Integer32,
   gs2326pplusIGMPSnoopingVLANLLQI   	    Integer32,
   gs2326pplusIGMPSnoopingVLANURI    	    Integer32
}

gs2326pplusIGMPSnoopingVLANID OBJECT-TYPE
   SYNTAX      Integer32(1..4095)
   MAX-ACCESS  read-write
   STATUS      current
   DESCRIPTION
       "The VLAN ID of the entry"
   ::= { gs2326pplusIGMPSnoopingVLANEntry 1 }

gs2326pplusIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2326pplusIGMPSnoopingVLANEntry 2 }

gs2326pplusIGMPSnoopingVLANIGMPQuerier OBJECT-TYPE
   SYNTAX      INTEGER { disable(0), enable(1) }
   MAX-ACCESS  read-write
   STATUS      current
   DESCRIPTION
       "Enable/Disable the IGMP Querier in the VLAN. "
   ::= { gs2326pplusIGMPSnoopingVLANEntry 3 }

gs2326pplusIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2326pplusIGMPSnoopingVLANEntry 4 }

gs2326pplusIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326pplusIGMPSnoopingVLANEntry 5 }

gs2326pplusIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326pplusIGMPSnoopingVLANEntry 6 }

gs2326pplusIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326pplusIGMPSnoopingVLANEntry 7 }

gs2326pplusIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326pplusIGMPSnoopingVLANEntry 8 }

gs2326pplusIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326pplusIGMPSnoopingVLANEntry 9 }

gs2326pplusIGMPSnoopingPortGroupFiltering                                                      OBJECT IDENTIFIER ::= { gs2326pplusIGMPSnooping 3 }

gs2326pplusIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2326pplusIGMPSnoopingPortGroupFiltering 1 }

gs2326pplusIGMPSnoopingPortGroupFilteringTable OBJECT-TYPE
   SYNTAX      SEQUENCE OF Gs2326pplusIGMPSnoopingPortGroupFilteringEntry
   MAX-ACCESS  not-accessible
   STATUS      current
   DESCRIPTION
       " Configure IGMP Snooping port group filtering. "
   ::= { gs2326pplusIGMPSnoopingPortGroupFiltering 2 }

gs2326pplusIGMPSnoopingPortGroupFilteringEntry OBJECT-TYPE
   SYNTAX      Gs2326pplusIGMPSnoopingPortGroupFilteringEntry
   MAX-ACCESS  not-accessible
   STATUS      current
   DESCRIPTION
       ""
   INDEX    { gs2326pplusIGMPSnoopingPortGroupFilteringIndex  }
   ::= { gs2326pplusIGMPSnoopingPortGroupFilteringTable 1 }

Gs2326pplusIGMPSnoopingPortGroupFilteringEntry ::= SEQUENCE {
   gs2326pplusIGMPSnoopingPortGroupFilteringIndex         Integer32,
   gs2326pplusIGMPSnoopingPortGroupFilteringPort          Integer32,
   gs2326pplusIGMPSnoopingPortGroupFilteringGroups        DisplayString,
   gs2326pplusIGMPSnoopingPortGroupFilteringRowStatus     INTEGER
}

gs2326pplusIGMPSnoopingPortGroupFilteringIndex OBJECT-TYPE
   SYNTAX      Integer32(1..65535)
   MAX-ACCESS  not-accessible
   STATUS      current
   DESCRIPTION
       "IGMP Snooping Port Group Filtering Configuration Index. "
   ::= { gs2326pplusIGMPSnoopingPortGroupFilteringEntry 1 }

gs2326pplusIGMPSnoopingPortGroupFilteringPort OBJECT-TYPE
   SYNTAX      Integer32(1..65535)
   MAX-ACCESS  read-write
   STATUS      current
   DESCRIPTION
       "The logical port for the settings. "
   ::= { gs2326pplusIGMPSnoopingPortGroupFilteringEntry 2 }

gs2326pplusIGMPSnoopingPortGroupFilteringGroups OBJECT-TYPE
   SYNTAX      DisplayString
   MAX-ACCESS  read-write
   STATUS      current
   DESCRIPTION
       "The IP Multicast Group that will be filtered. "
   ::= { gs2326pplusIGMPSnoopingPortGroupFilteringEntry 3 }

gs2326pplusIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326pplusIGMPSnoopingPortGroupFilteringEntry 4 }

gs2326pplusIGMPSnoopingStatus                                                      OBJECT IDENTIFIER ::= { gs2326pplusIGMPSnooping 4 }

gs2326pplusIGMPSnoopingstatisticClear OBJECT-TYPE
   SYNTAX      INTEGER { none(0), clear(1)}
   MAX-ACCESS  read-write
   STATUS      current
   DESCRIPTION
       "Clears all Statistics counters."
   ::= { gs2326pplusIGMPSnoopingStatus 1 }


gs2326pplusIGMPSnoopingstatisticTable OBJECT-TYPE
   SYNTAX      SEQUENCE OF Gs2326pplusIGMPSnoopingstatisticEntry
   MAX-ACCESS  not-accessible
   STATUS      current
   DESCRIPTION
       " Configure Vlan Port Isolation Configuration. "
   ::= { gs2326pplusIGMPSnoopingStatus 2 }

gs2326pplusIGMPSnoopingstatisticEntry OBJECT-TYPE
   SYNTAX      Gs2326pplusIGMPSnoopingstatisticEntry
   MAX-ACCESS  not-accessible
   STATUS      current
   DESCRIPTION
       ""
   INDEX    { gs2326pplusIGMPSnoopingstatisticVLANID  }
   ::= { gs2326pplusIGMPSnoopingstatisticTable 1 }

Gs2326pplusIGMPSnoopingstatisticEntry ::= SEQUENCE {
   gs2326pplusIGMPSnoopingstatisticVLANID              Integer32,
   gs2326pplusIGMPSnoopingstatisticQuerierVersion      DisplayString,
   gs2326pplusIGMPSnoopingstatisticHostVersion         DisplayString,
   gs2326pplusIGMPSnoopingstatisticQuerierStatus       DisplayString,
   gs2326pplusIGMPSnoopingstatisticQueriesTransmitted  Counter32,
   gs2326pplusIGMPSnoopingstatisticQueriesReceived     Counter32,
   gs2326pplusIGMPSnoopingstatisticV1ReportsReceived   Counter32,
   gs2326pplusIGMPSnoopingstatisticV2ReportsReceived   Counter32,
   gs2326pplusIGMPSnoopingstatisticV3ReportsReceived   Counter32,
   gs2326pplusIGMPSnoopingstatisticV2LeavesReceived    Counter32
}


gs2326pplusIGMPSnoopingstatisticVLANID OBJECT-TYPE
   SYNTAX      Integer32(1..4095)
   MAX-ACCESS  read-only
   STATUS      current
   DESCRIPTION
       "The VLAN ID of the entry. "
   ::= { gs2326pplusIGMPSnoopingstatisticEntry 1 }

gs2326pplusIGMPSnoopingstatisticQuerierVersion OBJECT-TYPE
   SYNTAX      DisplayString
   MAX-ACCESS  read-only
   STATUS      current
   DESCRIPTION
       "Working Querier Version currently. "
   ::= { gs2326pplusIGMPSnoopingstatisticEntry 2 }

gs2326pplusIGMPSnoopingstatisticHostVersion OBJECT-TYPE
   SYNTAX      DisplayString
   MAX-ACCESS  read-only
   STATUS      current
   DESCRIPTION
       "Working Host Version currently. "
   ::= { gs2326pplusIGMPSnoopingstatisticEntry 3 }

gs2326pplusIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326pplusIGMPSnoopingstatisticEntry 4 }

gs2326pplusIGMPSnoopingstatisticQueriesTransmitted OBJECT-TYPE
   SYNTAX      Counter32
   MAX-ACCESS  read-only
   STATUS      current
   DESCRIPTION
       "The number of Transmitted Queries. "
   ::= { gs2326pplusIGMPSnoopingstatisticEntry 5 }

gs2326pplusIGMPSnoopingstatisticQueriesReceived OBJECT-TYPE
   SYNTAX      Counter32
   MAX-ACCESS  read-only
   STATUS      current
   DESCRIPTION
       "The number of Received Queries. "
   ::= { gs2326pplusIGMPSnoopingstatisticEntry 6 }

gs2326pplusIGMPSnoopingstatisticV1ReportsReceived OBJECT-TYPE
   SYNTAX      Counter32
   MAX-ACCESS  read-only
   STATUS      current
   DESCRIPTION
       "The number of Received V1 Reports. "
   ::= { gs2326pplusIGMPSnoopingstatisticEntry 7 }

gs2326pplusIGMPSnoopingstatisticV2ReportsReceived OBJECT-TYPE
   SYNTAX      Counter32
   MAX-ACCESS  read-only
   STATUS      current
   DESCRIPTION
       "The number of Received V2 Reports. "
   ::= { gs2326pplusIGMPSnoopingstatisticEntry 8 }

gs2326pplusIGMPSnoopingstatisticV3ReportsReceived OBJECT-TYPE
   SYNTAX      Counter32
   MAX-ACCESS  read-only
   STATUS      current
   DESCRIPTION
       "The number of Received V3 Reports. "
   ::= { gs2326pplusIGMPSnoopingstatisticEntry 9 }

gs2326pplusIGMPSnoopingstatisticV2LeavesReceived OBJECT-TYPE
   SYNTAX      Counter32
   MAX-ACCESS  read-only
   STATUS      current
   DESCRIPTION
       "The number of Received V2 Leaves. "
   ::= { gs2326pplusIGMPSnoopingstatisticEntry 10 }

gs2326pplusIGMPSnoopingRouterPortTable OBJECT-TYPE
   SYNTAX      SEQUENCE OF Gs2326pplusIGMPSnoopingRouterPortEntry
   MAX-ACCESS  not-accessible
   STATUS      current
   DESCRIPTION
       " Configure Vlan Port Isolation Configuration. "
   ::= { gs2326pplusIGMPSnoopingStatus 3 }

gs2326pplusIGMPSnoopingRouterPortEntry OBJECT-TYPE
   SYNTAX      Gs2326pplusIGMPSnoopingRouterPortEntry
   MAX-ACCESS  not-accessible
   STATUS      current
   DESCRIPTION
       ""
   INDEX    { ifIndex  }
   ::= { gs2326pplusIGMPSnoopingRouterPortTable 1 }

Gs2326pplusIGMPSnoopingRouterPortEntry ::= SEQUENCE {
   gs2326pplusIGMPSnoopingRouterPortStatus            DisplayString
}

gs2326pplusIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326pplusIGMPSnoopingRouterPortEntry 1 }

gs2326pplusIGMPSnoopingGroupsTable OBJECT-TYPE
   SYNTAX      SEQUENCE OF Gs2326pplusIGMPSnoopingGroupsEntry
   MAX-ACCESS  not-accessible
   STATUS      current
   DESCRIPTION
       "IGMP Snooping Groups Information . "
   ::= { gs2326pplusIGMPSnooping 5 }

gs2326pplusIGMPSnoopingGroupsEntry OBJECT-TYPE
   SYNTAX      Gs2326pplusIGMPSnoopingGroupsEntry
   MAX-ACCESS  not-accessible
   STATUS      current
   DESCRIPTION
       ""
   INDEX    { gs2326pplusIGMPSnoopingGroupsIndex  }
   ::= { gs2326pplusIGMPSnoopingGroupsTable 1 }

Gs2326pplusIGMPSnoopingGroupsEntry ::= SEQUENCE {
   gs2326pplusIGMPSnoopingGroupsIndex          Integer32,
   gs2326pplusIGMPSnoopingGroupsVLANID         Integer32,
   gs2326pplusIGMPSnoopingGroups               InetAddress,
   gs2326pplusIGMPSnoopingGroupsMemberships    DisplayString
}

gs2326pplusIGMPSnoopingGroupsIndex OBJECT-TYPE
   SYNTAX      Integer32(1..65535)
   MAX-ACCESS  not-accessible
   STATUS      current
   DESCRIPTION
       "IGMP Snooping Groups Index"
   ::= { gs2326pplusIGMPSnoopingGroupsEntry 1 }

gs2326pplusIGMPSnoopingGroupsVLANID OBJECT-TYPE
   SYNTAX      Integer32(1..4095)
   MAX-ACCESS  read-only
   STATUS      current
   DESCRIPTION
       "VLAN ID of the group. "
   ::= { gs2326pplusIGMPSnoopingGroupsEntry 2 }

gs2326pplusIGMPSnoopingGroups OBJECT-TYPE
   SYNTAX      DisplayString
   MAX-ACCESS  read-only
   STATUS      current
   DESCRIPTION
       "Group address of the group displayed."
   ::= { gs2326pplusIGMPSnoopingGroupsEntry 3 }

gs2326pplusIGMPSnoopingGroupsMemberships OBJECT-TYPE
   SYNTAX      DisplayString
   MAX-ACCESS  read-only
   STATUS      current
   DESCRIPTION
       "Ports under this group."
   ::= { gs2326pplusIGMPSnoopingGroupsEntry 4 }

gs2326pplusIGMPSnoopingSSMTable OBJECT-TYPE
   SYNTAX      SEQUENCE OF Gs2326pplusIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2326pplusIGMPSnooping 6 }

gs2326pplusIGMPSnoopingSSMEntry OBJECT-TYPE
   SYNTAX      Gs2326pplusIGMPSnoopingSSMEntry
   MAX-ACCESS  not-accessible
   STATUS      current
   DESCRIPTION
       ""
   INDEX    { gs2326pplusIGMPSnoopingSSMIndex  }
   ::= { gs2326pplusIGMPSnoopingSSMTable 1 }

Gs2326pplusIGMPSnoopingSSMEntry ::= SEQUENCE {
   gs2326pplusIGMPSnoopingSSMIndex          Integer32,
   gs2326pplusIGMPSnoopingSSMVLANID         Integer32,
   gs2326pplusIGMPSnoopingSSMGroup          DisplayString,
   gs2326pplusIGMPSnoopingSSMPort           Integer32,
   gs2326pplusIGMPSnoopingSSMMode           DisplayString,
   gs2326pplusIGMPSnoopingSSMSourceAddress  DisplayString,
   gs2326pplusIGMPSnoopingSSMType           DisplayString
}

gs2326pplusIGMPSnoopingSSMIndex OBJECT-TYPE
   SYNTAX      Integer32(1..65535)
   MAX-ACCESS  not-accessible
   STATUS      current
   DESCRIPTION
       "IGMP Snooping SSM Index"
   ::= { gs2326pplusIGMPSnoopingSSMEntry 1 }

gs2326pplusIGMPSnoopingSSMVLANID OBJECT-TYPE
   SYNTAX      Integer32(1..4095)
   MAX-ACCESS  read-only
   STATUS      current
   DESCRIPTION
       "VLAN ID of the group. "
   ::= { gs2326pplusIGMPSnoopingSSMEntry 2 }

gs2326pplusIGMPSnoopingSSMGroup OBJECT-TYPE
   SYNTAX      DisplayString
   MAX-ACCESS  read-only
   STATUS      current
   DESCRIPTION
       "Group address of the group displayed."
   ::= { gs2326pplusIGMPSnoopingSSMEntry 3 }

gs2326pplusIGMPSnoopingSSMPort OBJECT-TYPE
   SYNTAX      Integer32(1..65535)
   MAX-ACCESS  read-only
   STATUS      current
   DESCRIPTION
       "Ports under this group."
   ::= { gs2326pplusIGMPSnoopingSSMEntry 4 }

gs2326pplusIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326pplusIGMPSnoopingSSMEntry 5 }

gs2326pplusIGMPSnoopingSSMSourceAddress OBJECT-TYPE
   SYNTAX      DisplayString
   MAX-ACCESS  read-only
   STATUS      current
   DESCRIPTION
       "IP Address of the source. Currently, system limits the total number of
       IP source addresses for filtering to be 128."
   ::= { gs2326pplusIGMPSnoopingSSMEntry 6 }

gs2326pplusIGMPSnoopingSSMType OBJECT-TYPE
   SYNTAX      DisplayString
   MAX-ACCESS  read-only
   STATUS      current
   DESCRIPTION
       "Indicates the Type. It can be either Allow or Deny."
   ::= { gs2326pplusIGMPSnoopingSSMEntry 7 }

gs2326pplusMLDSnooping                                                           OBJECT IDENTIFIER ::= { gs2326pplusConfiguration 17 }

gs2326pplusMLDSnoopingBasic                                                      OBJECT IDENTIFIER ::= { gs2326pplusMLDSnooping 1 }

gs2326pplusMLDSnoopingEnable  OBJECT-TYPE
   SYNTAX      INTEGER { disable(0), enable(1) }
   MAX-ACCESS  read-write
   STATUS      current
   DESCRIPTION
       "Enable/Disable the Global MLD Snooping"
   ::= { gs2326pplusMLDSnoopingBasic 1 }

gs2326pplusMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2326pplusMLDSnoopingBasic 2 }

gs2326pplusMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326pplusMLDSnoopingBasic 3 }

gs2326pplusMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2326pplusMLDSnoopingBasic 4 }

gs2326pplusMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2326pplusMLDSnoopingBasic 5 }

gs2326pplusMLDSnoopingPortRelatedTable OBJECT-TYPE
   SYNTAX      SEQUENCE OF Gs2326pplusMLDSnoopingPortRelatedEntry
   MAX-ACCESS  not-accessible
   STATUS      current
   DESCRIPTION
       " Configure MLD Snooping Port Related Configuration. "
   ::= { gs2326pplusMLDSnoopingBasic 6 }

gs2326pplusMLDSnoopingPortRelatedEntry OBJECT-TYPE
   SYNTAX      Gs2326pplusMLDSnoopingPortRelatedEntry
   MAX-ACCESS  not-accessible
   STATUS      current
   DESCRIPTION
       ""
   INDEX    { ifIndex  }
   ::= { gs2326pplusMLDSnoopingPortRelatedTable 1 }

Gs2326pplusMLDSnoopingPortRelatedEntry ::= SEQUENCE {
   gs2326pplusMLDSnoopingRouterPort	INTEGER,
   gs2326pplusMLDSnoopingFastLeave  	INTEGER,
   gs2326pplusMLDSnoopingThrottling    Integer32
}

gs2326pplusMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326pplusMLDSnoopingPortRelatedEntry 1 }

gs2326pplusMLDSnoopingFastLeave OBJECT-TYPE
   SYNTAX      INTEGER { disable(0), enable(1) }
   MAX-ACCESS  read-write
   STATUS      current
   DESCRIPTION
       "Enable/Disable the fast leave on the port. "
   ::= { gs2326pplusMLDSnoopingPortRelatedEntry 2 }

gs2326pplusMLDSnoopingThrottling OBJECT-TYPE
   SYNTAX      Integer32(0..10)
   MAX-ACCESS  read-write
   STATUS      current
   DESCRIPTION
       "Enable to limit the number of multicast groups to which a switch port can belong.
       0: unlimited"
   ::= { gs2326pplusMLDSnoopingPortRelatedEntry 3 }

gs2326pplusMLDSnoopingVLANTable OBJECT-TYPE
   SYNTAX      SEQUENCE OF Gs2326pplusMLDSnoopingVLANEntry
   MAX-ACCESS  not-accessible
   STATUS      current
   DESCRIPTION
       " Configure MLD Snooping Vlan Configuration. "
   ::= { gs2326pplusMLDSnooping 2 }

gs2326pplusMLDSnoopingVLANEntry OBJECT-TYPE
   SYNTAX      Gs2326pplusMLDSnoopingVLANEntry
   MAX-ACCESS  not-accessible
   STATUS      current
   DESCRIPTION
       ""
   INDEX    { gs2326pplusMLDSnoopingVLANID  }
   ::= { gs2326pplusMLDSnoopingVLANTable 1 }

Gs2326pplusMLDSnoopingVLANEntry ::= SEQUENCE {
   gs2326pplusMLDSnoopingVLANID        	Integer32,
   gs2326pplusMLDSnoopingVLANEnable    	INTEGER,
   gs2326pplusMLDSnoopingVLANIGMPQuerier   INTEGER,
   gs2326pplusMLDSnoopingVLANCompatibility INTEGER,
   gs2326pplusMLDSnoopingVLANRV        	Integer32,
   gs2326pplusMLDSnoopingVLANQI      	    Integer32,
   gs2326pplusMLDSnoopingVLANQRI   	    Integer32,
   gs2326pplusMLDSnoopingVLANLLQI   	    Integer32,
   gs2326pplusMLDSnoopingVLANURI    	    Integer32
}

gs2326pplusMLDSnoopingVLANID OBJECT-TYPE
   SYNTAX      Integer32(1..4095)
   MAX-ACCESS  read-write
   STATUS      current
   DESCRIPTION
       "The VLAN ID of the entry"
   ::= { gs2326pplusMLDSnoopingVLANEntry 1 }

gs2326pplusMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2326pplusMLDSnoopingVLANEntry 2 }

gs2326pplusMLDSnoopingVLANIGMPQuerier OBJECT-TYPE
   SYNTAX      INTEGER { disable(0), enable(1) }
   MAX-ACCESS  read-write
   STATUS      current
   DESCRIPTION
       "Enable/Disable the MLD Querier in the VLAN. "
   ::= { gs2326pplusMLDSnoopingVLANEntry 3 }

gs2326pplusMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2326pplusMLDSnoopingVLANEntry 4 }

gs2326pplusMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326pplusMLDSnoopingVLANEntry 5 }

gs2326pplusMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326pplusMLDSnoopingVLANEntry 6 }

gs2326pplusMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326pplusMLDSnoopingVLANEntry 7 }

gs2326pplusMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326pplusMLDSnoopingVLANEntry 8 }

gs2326pplusMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326pplusMLDSnoopingVLANEntry 9 }

gs2326pplusMLDSnoopingPortGroupFiltering                                                      OBJECT IDENTIFIER ::= { gs2326pplusMLDSnooping 3 }

gs2326pplusMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2326pplusMLDSnoopingPortGroupFiltering 1 }

gs2326pplusMLDSnoopingPortGroupFilteringTable OBJECT-TYPE
   SYNTAX      SEQUENCE OF Gs2326pplusMLDSnoopingPortGroupFilteringEntry
   MAX-ACCESS  not-accessible
   STATUS      current
   DESCRIPTION
       " Configure MLD Snooping port group filtering. "
   ::= { gs2326pplusMLDSnoopingPortGroupFiltering 2 }

gs2326pplusMLDSnoopingPortGroupFilteringEntry OBJECT-TYPE
   SYNTAX      Gs2326pplusMLDSnoopingPortGroupFilteringEntry
   MAX-ACCESS  not-accessible
   STATUS      current
   DESCRIPTION
       ""
   INDEX    { gs2326pplusMLDSnoopingPortGroupFilteringIndex  }
   ::= { gs2326pplusMLDSnoopingPortGroupFilteringTable 1 }

Gs2326pplusMLDSnoopingPortGroupFilteringEntry ::= SEQUENCE {
   gs2326pplusMLDSnoopingPortGroupFilteringIndex         Integer32,
   gs2326pplusMLDSnoopingPortGroupFilteringPort          Integer32,
   gs2326pplusMLDSnoopingPortGroupFilteringGroups        DisplayString,
   gs2326pplusMLDSnoopingPortGroupFilteringRowStatus     INTEGER
}

gs2326pplusMLDSnoopingPortGroupFilteringIndex OBJECT-TYPE
   SYNTAX      Integer32(1..65535)
   MAX-ACCESS  not-accessible
   STATUS      current
   DESCRIPTION
       "MLD Snooping Port Group Filtering Configuration Index. "
   ::= { gs2326pplusMLDSnoopingPortGroupFilteringEntry 1 }

gs2326pplusMLDSnoopingPortGroupFilteringPort OBJECT-TYPE
   SYNTAX      Integer32(1..65535)
   MAX-ACCESS  read-write
   STATUS      current
   DESCRIPTION
       "The logical port for the settings. "
   ::= { gs2326pplusMLDSnoopingPortGroupFilteringEntry 2 }

gs2326pplusMLDSnoopingPortGroupFilteringGroups OBJECT-TYPE
   SYNTAX      DisplayString
   MAX-ACCESS  read-write
   STATUS      current
   DESCRIPTION
       "The IP Multicast Group that will be filtered. "
   ::= { gs2326pplusMLDSnoopingPortGroupFilteringEntry 3 }

gs2326pplusMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326pplusMLDSnoopingPortGroupFilteringEntry 4 }

gs2326pplusMLDSnoopingStatus                                                      OBJECT IDENTIFIER ::= { gs2326pplusMLDSnooping 4 }

gs2326pplusMLDSnoopingstatisticClear OBJECT-TYPE
   SYNTAX      INTEGER { none(0), clear(1)}
   MAX-ACCESS  read-write
   STATUS      current
   DESCRIPTION
       "Clears all Statistics counters."
   ::= { gs2326pplusMLDSnoopingStatus 1 }


gs2326pplusMLDSnoopingstatisticTable OBJECT-TYPE
   SYNTAX      SEQUENCE OF Gs2326pplusMLDSnoopingstatisticEntry
   MAX-ACCESS  not-accessible
   STATUS      current
   DESCRIPTION
       " Configure Vlan Port Isolation Configuration. "
   ::= { gs2326pplusMLDSnoopingStatus 2 }

gs2326pplusMLDSnoopingstatisticEntry OBJECT-TYPE
   SYNTAX      Gs2326pplusMLDSnoopingstatisticEntry
   MAX-ACCESS  not-accessible
   STATUS      current
   DESCRIPTION
       ""
   INDEX    { gs2326pplusMLDSnoopingstatisticVLANID  }
   ::= { gs2326pplusMLDSnoopingstatisticTable 1 }

Gs2326pplusMLDSnoopingstatisticEntry ::= SEQUENCE {
   gs2326pplusMLDSnoopingstatisticVLANID              Integer32,
   gs2326pplusMLDSnoopingstatisticQuerierVersion      DisplayString,
   gs2326pplusMLDSnoopingstatisticHostVersion         DisplayString,
   gs2326pplusMLDSnoopingstatisticQuerierStatus       DisplayString,
   gs2326pplusMLDSnoopingstatisticQueriesTransmitted  Counter32,
   gs2326pplusMLDSnoopingstatisticQueriesReceived     Counter32,
   gs2326pplusMLDSnoopingstatisticV1ReportsReceived   Counter32,
   gs2326pplusMLDSnoopingstatisticV2ReportsReceived   Counter32,
   gs2326pplusMLDSnoopingstatisticV1LeavesReceived    Counter32
}


gs2326pplusMLDSnoopingstatisticVLANID OBJECT-TYPE
   SYNTAX      Integer32(1..4095)
   MAX-ACCESS  read-only
   STATUS      current
   DESCRIPTION
       "The VLAN ID of the entry. "
   ::= { gs2326pplusMLDSnoopingstatisticEntry 1 }

gs2326pplusMLDSnoopingstatisticQuerierVersion OBJECT-TYPE
   SYNTAX      DisplayString
   MAX-ACCESS  read-only
   STATUS      current
   DESCRIPTION
       "Working Querier Version currently. "
   ::= { gs2326pplusMLDSnoopingstatisticEntry 2 }

gs2326pplusMLDSnoopingstatisticHostVersion OBJECT-TYPE
   SYNTAX      DisplayString
   MAX-ACCESS  read-only
   STATUS      current
   DESCRIPTION
       "Working Host Version currently. "
   ::= { gs2326pplusMLDSnoopingstatisticEntry 3 }

gs2326pplusMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326pplusMLDSnoopingstatisticEntry 4 }

gs2326pplusMLDSnoopingstatisticQueriesTransmitted OBJECT-TYPE
   SYNTAX      Counter32
   MAX-ACCESS  read-only
   STATUS      current
   DESCRIPTION
       "The number of Transmitted Queries. "
   ::= { gs2326pplusMLDSnoopingstatisticEntry 5 }

gs2326pplusMLDSnoopingstatisticQueriesReceived OBJECT-TYPE
   SYNTAX      Counter32
   MAX-ACCESS  read-only
   STATUS      current
   DESCRIPTION
       "The number of Received Queries. "
   ::= { gs2326pplusMLDSnoopingstatisticEntry 6 }

gs2326pplusMLDSnoopingstatisticV1ReportsReceived OBJECT-TYPE
   SYNTAX      Counter32
   MAX-ACCESS  read-only
   STATUS      current
   DESCRIPTION
       "The number of Received V1 Reports. "
   ::= { gs2326pplusMLDSnoopingstatisticEntry 7 }

gs2326pplusMLDSnoopingstatisticV2ReportsReceived OBJECT-TYPE
   SYNTAX      Counter32
   MAX-ACCESS  read-only
   STATUS      current
   DESCRIPTION
       "The number of Received V2 Reports. "
   ::= { gs2326pplusMLDSnoopingstatisticEntry 8 }

gs2326pplusMLDSnoopingstatisticV1LeavesReceived OBJECT-TYPE
   SYNTAX      Counter32
   MAX-ACCESS  read-only
   STATUS      current
   DESCRIPTION
       "The number of Received V1 Leaves. "
   ::= { gs2326pplusMLDSnoopingstatisticEntry 9 }

gs2326pplusMLDSnoopingRouterPortTable OBJECT-TYPE
   SYNTAX      SEQUENCE OF Gs2326pplusMLDSnoopingRouterPortEntry
   MAX-ACCESS  not-accessible
   STATUS      current
   DESCRIPTION
       " Configure Vlan Port Isolation Configuration. "
   ::= { gs2326pplusMLDSnoopingStatus 3 }

gs2326pplusMLDSnoopingRouterPortEntry OBJECT-TYPE
   SYNTAX      Gs2326pplusMLDSnoopingRouterPortEntry
   MAX-ACCESS  not-accessible
   STATUS      current
   DESCRIPTION
       ""
   INDEX    { ifIndex  }
   ::= { gs2326pplusMLDSnoopingRouterPortTable 1 }

Gs2326pplusMLDSnoopingRouterPortEntry ::= SEQUENCE {
   gs2326pplusMLDSnoopingRouterPortStatus            DisplayString
}

gs2326pplusMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326pplusMLDSnoopingRouterPortEntry 1 }

gs2326pplusMLDSnoopingGroupsTable OBJECT-TYPE
   SYNTAX      SEQUENCE OF Gs2326pplusMLDSnoopingGroupsEntry
   MAX-ACCESS  not-accessible
   STATUS      current
   DESCRIPTION
       "MLD Snooping Groups Information . "
   ::= { gs2326pplusMLDSnooping 5 }

gs2326pplusMLDSnoopingGroupsEntry OBJECT-TYPE
   SYNTAX      Gs2326pplusMLDSnoopingGroupsEntry
   MAX-ACCESS  not-accessible
   STATUS      current
   DESCRIPTION
       ""
   INDEX    { gs2326pplusMLDSnoopingGroupsIndex  }
   ::= { gs2326pplusMLDSnoopingGroupsTable 1 }

Gs2326pplusMLDSnoopingGroupsEntry ::= SEQUENCE {
   gs2326pplusMLDSnoopingGroupsIndex          Integer32,
   gs2326pplusMLDSnoopingGroupsVLANID         Integer32,
   gs2326pplusMLDSnoopingGroups               InetAddress,
   gs2326pplusMLDSnoopingGroupsMemberships    DisplayString
}

gs2326pplusMLDSnoopingGroupsIndex OBJECT-TYPE
   SYNTAX      Integer32(1..65535)
   MAX-ACCESS  not-accessible
   STATUS      current
   DESCRIPTION
       "MLD Snooping Groups Index"
   ::= { gs2326pplusMLDSnoopingGroupsEntry 1 }

gs2326pplusMLDSnoopingGroupsVLANID OBJECT-TYPE
   SYNTAX      Integer32(1..4095)
   MAX-ACCESS  read-only
   STATUS      current
   DESCRIPTION
       "VLAN ID of the group. "
   ::= { gs2326pplusMLDSnoopingGroupsEntry 2 }

gs2326pplusMLDSnoopingGroups OBJECT-TYPE
   SYNTAX      DisplayString
   MAX-ACCESS  read-only
   STATUS      current
   DESCRIPTION
       "Group address of the group displayed."
   ::= { gs2326pplusMLDSnoopingGroupsEntry 3 }

gs2326pplusMLDSnoopingGroupsMemberships OBJECT-TYPE
   SYNTAX      DisplayString
   MAX-ACCESS  read-only
   STATUS      current
   DESCRIPTION
       "Ports under this group."
   ::= { gs2326pplusMLDSnoopingGroupsEntry 4 }

gs2326pplusMLDSnoopingSSMTable OBJECT-TYPE
   SYNTAX      SEQUENCE OF Gs2326pplusMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2326pplusMLDSnooping 6 }

gs2326pplusMLDSnoopingSSMEntry OBJECT-TYPE
   SYNTAX      Gs2326pplusMLDSnoopingSSMEntry
   MAX-ACCESS  not-accessible
   STATUS      current
   DESCRIPTION
       ""
   INDEX    { gs2326pplusMLDSnoopingSSMIndex  }
   ::= { gs2326pplusMLDSnoopingSSMTable 1 }

Gs2326pplusMLDSnoopingSSMEntry ::= SEQUENCE {
   gs2326pplusMLDSnoopingSSMIndex          Integer32,
   gs2326pplusMLDSnoopingSSMVLANID         Integer32,
   gs2326pplusMLDSnoopingSSMGroup          DisplayString,
   gs2326pplusMLDSnoopingSSMPort           Integer32,
   gs2326pplusMLDSnoopingSSMMode           DisplayString,
   gs2326pplusMLDSnoopingSSMSourceAddress  DisplayString,
   gs2326pplusMLDSnoopingSSMType           DisplayString
}

gs2326pplusMLDSnoopingSSMIndex OBJECT-TYPE
   SYNTAX      Integer32(1..65535)
   MAX-ACCESS  not-accessible
   STATUS      current
   DESCRIPTION
       "MLD Snooping SSM Index"
   ::= { gs2326pplusMLDSnoopingSSMEntry 1 }

gs2326pplusMLDSnoopingSSMVLANID OBJECT-TYPE
   SYNTAX      Integer32(1..4095)
   MAX-ACCESS  read-only
   STATUS      current
   DESCRIPTION
       "VLAN ID of the group. "
   ::= { gs2326pplusMLDSnoopingSSMEntry 2 }

gs2326pplusMLDSnoopingSSMGroup OBJECT-TYPE
   SYNTAX      DisplayString
   MAX-ACCESS  read-only
   STATUS      current
   DESCRIPTION
       "Group address of the group displayed."
   ::= { gs2326pplusMLDSnoopingSSMEntry 3 }

gs2326pplusMLDSnoopingSSMPort OBJECT-TYPE
   SYNTAX      Integer32(1..65535)
   MAX-ACCESS  read-only
   STATUS      current
   DESCRIPTION
       "Ports under this group."
   ::= { gs2326pplusMLDSnoopingSSMEntry 4 }

gs2326pplusMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326pplusMLDSnoopingSSMEntry 5 }

gs2326pplusMLDSnoopingSSMSourceAddress OBJECT-TYPE
   SYNTAX      DisplayString
   MAX-ACCESS  read-only
   STATUS      current
   DESCRIPTION
       "IP Address of the source. Currently, system limits the total number of
       IP source addresses for filtering to be 128."
   ::= { gs2326pplusMLDSnoopingSSMEntry 6 }

gs2326pplusMLDSnoopingSSMType OBJECT-TYPE
   SYNTAX      DisplayString
   MAX-ACCESS  read-only
   STATUS      current
   DESCRIPTION
       "Indicates the Type. It can be either Allow or Deny."
   ::= { gs2326pplusMLDSnoopingSSMEntry 7 }


gs2326pplusMVR                                                                   OBJECT IDENTIFIER ::= { gs2326pplusConfiguration 18 }

gs2326pplusMVRConfiguration                                                      OBJECT IDENTIFIER ::= { gs2326pplusMVR 1 }

gs2326pplusMVRMode  OBJECT-TYPE
   SYNTAX      INTEGER { disable(0), enable(1) }
   MAX-ACCESS  read-write
   STATUS      current
   DESCRIPTION
       "Enable/Disable the Global MVR. "
   ::= { gs2326pplusMVRConfiguration 1 }

gs2326pplusMVRVLANId  OBJECT-TYPE
   SYNTAX      Integer32(1..4094)
   MAX-ACCESS  read-write
   STATUS      current
   DESCRIPTION
       "Specify the Multicast VLAN ID. "
   ::= { gs2326pplusMVRConfiguration 2 }

gs2326pplusMVRPortConfigurationTable OBJECT-TYPE
   SYNTAX      SEQUENCE OF Gs2326pplusMVRPortConfigurationEntry
   MAX-ACCESS  not-accessible
   STATUS      current
   DESCRIPTION
       " Configure MVR Port Configuration. "
   ::= { gs2326pplusMVRConfiguration 3 }

gs2326pplusMVRPortConfigurationEntry OBJECT-TYPE
   SYNTAX      Gs2326pplusMVRPortConfigurationEntry
   MAX-ACCESS  not-accessible
   STATUS      current
   DESCRIPTION
       ""
   INDEX    { ifIndex  }
   ::= { gs2326pplusMVRPortConfigurationTable 1 }

Gs2326pplusMVRPortConfigurationEntry ::= SEQUENCE {
   gs2326pplusMVRPortConfigurationMode	INTEGER,
   gs2326pplusMVRPortConfigurationType  	INTEGER,
   gs2326pplusMVRPortConfigurationImmediateLeave    INTEGER
}

gs2326pplusMVRPortConfigurationMode OBJECT-TYPE
   SYNTAX      INTEGER { disable(0), enable(1) }
   MAX-ACCESS  read-write
   STATUS      current
   DESCRIPTION
       "Enable MVR on the port. "
   ::= { gs2326pplusMVRPortConfigurationEntry 1 }

gs2326pplusMVRPortConfigurationType OBJECT-TYPE
   SYNTAX      INTEGER { receiver(0), source(1) }
   MAX-ACCESS  read-write
   STATUS      current
   DESCRIPTION
       "Specify the MVR port type on the port. "
   ::= { gs2326pplusMVRPortConfigurationEntry 2 }

gs2326pplusMVRPortConfigurationImmediateLeave OBJECT-TYPE
   SYNTAX      INTEGER { disable(0), enable(1) }
   MAX-ACCESS  read-write
   STATUS      current
   DESCRIPTION
       "Enable the fast leave on the port. "
   ::= { gs2326pplusMVRPortConfigurationEntry 3 }


gs2326pplusMVRPortGroupFiltering                                                      OBJECT IDENTIFIER ::= { gs2326pplusMVR 2 }

gs2326pplusMVRPortGroupFilteringCreate OBJECT-TYPE
   SYNTAX       Integer32
   MAX-ACCESS   read-write
   STATUS       current
   DESCRIPTION
       "default: 0
       0 : None  (read only) 1 : Create MLD Snooping Port Group Filtering "
   ::= { gs2326pplusMVRPortGroupFiltering 1 }

gs2326pplusMVRPortGroupFilteringTable OBJECT-TYPE
   SYNTAX      SEQUENCE OF Gs2326pplusMVRPortGroupFilteringEntry
   MAX-ACCESS  not-accessible
   STATUS      current
   DESCRIPTION
       " Configure MVR port group filtering. "
   ::= { gs2326pplusMVRPortGroupFiltering 2 }

gs2326pplusMVRPortGroupFilteringEntry OBJECT-TYPE
   SYNTAX      Gs2326pplusMVRPortGroupFilteringEntry
   MAX-ACCESS  not-accessible
   STATUS      current
   DESCRIPTION
       ""
   INDEX    { gs2326pplusMVRPortGroupFilteringIndex  }
   ::= { gs2326pplusMVRPortGroupFilteringTable 1 }

Gs2326pplusMVRPortGroupFilteringEntry ::= SEQUENCE {
   gs2326pplusMVRPortGroupFilteringIndex         Integer32,
   gs2326pplusMVRPortGroupFilteringPort          Integer32,
   gs2326pplusMVRPortGroupFilteringStartGroups   DisplayString,
   gs2326pplusMVRPortGroupFilteringEndGroups     DisplayString,
   gs2326pplusMVRPortGroupFilteringRowStatus     INTEGER
}

gs2326pplusMVRPortGroupFilteringIndex OBJECT-TYPE
   SYNTAX      Integer32(1..65535)
   MAX-ACCESS  not-accessible
   STATUS      current
   DESCRIPTION
       "MVR Port Group Filtering Configuration Index. "
   ::= { gs2326pplusMVRPortGroupFilteringEntry 1 }

gs2326pplusMVRPortGroupFilteringPort OBJECT-TYPE
   SYNTAX      Integer32(1..65535)
   MAX-ACCESS  read-write
   STATUS      current
   DESCRIPTION
       "The logical port for the settings. "
   ::= { gs2326pplusMVRPortGroupFilteringEntry 2 }

gs2326pplusMVRPortGroupFilteringStartGroups OBJECT-TYPE
   SYNTAX      DisplayString
   MAX-ACCESS  read-write
   STATUS      current
   DESCRIPTION
       "The IP Multicast Group that will be allowed. "
   ::= { gs2326pplusMVRPortGroupFilteringEntry 3 }

gs2326pplusMVRPortGroupFilteringEndGroups OBJECT-TYPE
   SYNTAX      DisplayString
   MAX-ACCESS  read-write
   STATUS      current
   DESCRIPTION
       "The IP Multicast Group that will be allowed. "
   ::= { gs2326pplusMVRPortGroupFilteringEntry 4 }

gs2326pplusMVRPortGroupFilteringRowStatus OBJECT-TYPE
   SYNTAX      INTEGER { active(1), notInservice(2), destroy(4)}
   MAX-ACCESS  read-write
   STATUS      current
   DESCRIPTION
       "1: active
        2: notInservice
        4: destroy"
   ::= { gs2326pplusMVRPortGroupFilteringEntry 5 }

gs2326pplusMVRGroupsTable OBJECT-TYPE
   SYNTAX      SEQUENCE OF Gs2326pplusMVRGroupsEntry
   MAX-ACCESS  not-accessible
   STATUS      current
   DESCRIPTION
       "MVR Groups Information . "
   ::= { gs2326pplusMVR 3 }

gs2326pplusMVRGroupsEntry OBJECT-TYPE
   SYNTAX      Gs2326pplusMVRGroupsEntry
   MAX-ACCESS  not-accessible
   STATUS      current
   DESCRIPTION
       ""
   INDEX    { gs2326pplusMVRGroupsIndex  }
   ::= { gs2326pplusMVRGroupsTable 1 }

Gs2326pplusMVRGroupsEntry ::= SEQUENCE {
   gs2326pplusMVRGroupsIndex          Integer32,
   gs2326pplusMVRGroupsVLANID         Integer32,
   gs2326pplusMVRGroups               InetAddress,
   gs2326pplusMVRGroupsMemberships    DisplayString
}

gs2326pplusMVRGroupsIndex OBJECT-TYPE
   SYNTAX      Integer32(1..65535)
   MAX-ACCESS  not-accessible
   STATUS      current
   DESCRIPTION
       "MVR Groups Index"
   ::= { gs2326pplusMVRGroupsEntry 1 }

gs2326pplusMVRGroupsVLANID OBJECT-TYPE
   SYNTAX      Integer32(1..4095)
   MAX-ACCESS  read-only
   STATUS      current
   DESCRIPTION
       "VLAN ID of the group. "
   ::= { gs2326pplusMVRGroupsEntry 2 }

gs2326pplusMVRGroups OBJECT-TYPE
   SYNTAX      DisplayString
   MAX-ACCESS  read-only
   STATUS      current
   DESCRIPTION
       "Group address of the group displayed."
   ::= { gs2326pplusMVRGroupsEntry 3 }

gs2326pplusMVRGroupsMemberships OBJECT-TYPE
   SYNTAX      DisplayString
   MAX-ACCESS  read-only
   STATUS      current
   DESCRIPTION
       "Ports under this group."
   ::= { gs2326pplusMVRGroupsEntry 4 }


gs2326pplusMVRStatus                                                      OBJECT IDENTIFIER ::= { gs2326pplusMVR 4 }

gs2326pplusMVRstatisticClear OBJECT-TYPE
   SYNTAX      INTEGER { none(0), clear(1)}
   MAX-ACCESS  read-write
   STATUS      current
   DESCRIPTION
       "Clears all Statistics counters."
   ::= { gs2326pplusMVRStatus 1 }

gs2326pplusMVRstatisticVLANID OBJECT-TYPE
   SYNTAX      Integer32(1..4095)
   MAX-ACCESS  read-only
   STATUS      current
   DESCRIPTION
       "The VLAN ID of the entry. "
   ::= { gs2326pplusMVRStatus 2 }

gs2326pplusMVRstatisticV1ReportsReceived OBJECT-TYPE
   SYNTAX      Counter32
   MAX-ACCESS  read-only
   STATUS      current
   DESCRIPTION
       "The number of Received V1 Reports. "
   ::= { gs2326pplusMVRStatus 3 }

gs2326pplusMVRstatisticV2ReportsReceived OBJECT-TYPE
   SYNTAX      Counter32
   MAX-ACCESS  read-only
   STATUS      current
   DESCRIPTION
       "The number of Received V2 Reports. "
   ::= { gs2326pplusMVRStatus 4 }

gs2326pplusMVRstatisticV3ReportsReceived OBJECT-TYPE
   SYNTAX      Counter32
   MAX-ACCESS  read-only
   STATUS      current
   DESCRIPTION
       "The number of Received V3 Reports. "
   ::= { gs2326pplusMVRStatus 5 }

gs2326pplusMVRstatisticV2LeavesReceived OBJECT-TYPE
   SYNTAX      Counter32
   MAX-ACCESS  read-only
   STATUS      current
   DESCRIPTION
       "The number of Received V2 Leaves. "
   ::= { gs2326pplusMVRStatus 6 }

gs2326pplusLACP                                                     OBJECT IDENTIFIER ::= { gs2326pplusConfiguration 19 }

gs2326pplusLACPConf                                                 OBJECT IDENTIFIER ::= { gs2326pplusLACP 1 }

gs2326pplusLACPPortConfigurationTable OBJECT-TYPE
   SYNTAX      SEQUENCE OF Gs2326pplusLACPPortConfigurationEntry
   MAX-ACCESS  not-accessible
   STATUS      current
   DESCRIPTION
       " "
   ::= { gs2326pplusLACPConf 1 }

gs2326pplusLACPPortConfigurationEntry OBJECT-TYPE
   SYNTAX      Gs2326pplusLACPPortConfigurationEntry
   MAX-ACCESS  not-accessible
   STATUS      current
   DESCRIPTION
       ""
   INDEX    { gs2326pplusLACPPortConfigurationPort  }
   ::= { gs2326pplusLACPPortConfigurationTable 1 }

Gs2326pplusLACPPortConfigurationEntry ::= SEQUENCE {
    gs2326pplusLACPPortConfigurationPort         Integer32,
    gs2326pplusLACPPortConfigurationMode         INTEGER,
    gs2326pplusLACPPortConfigurationKey          Integer32,
    gs2326pplusLACPPortConfigurationRole         INTEGER
}

gs2326pplusLACPPortConfigurationPort OBJECT-TYPE
   SYNTAX      Integer32(1..4095)
   MAX-ACCESS  not-accessible
   STATUS      current
   DESCRIPTION
       " "
   ::= { gs2326pplusLACPPortConfigurationEntry 1 }

gs2326pplusLACPPortConfigurationMode OBJECT-TYPE
   SYNTAX      INTEGER { disable(0), enable(1) }
   MAX-ACCESS  read-write
   STATUS      current
   DESCRIPTION
       "Enable/Disable LACP Mode."
   ::= { gs2326pplusLACPPortConfigurationEntry 2 }

gs2326pplusLACPPortConfigurationKey OBJECT-TYPE
   SYNTAX      Integer32(0..65535)
   MAX-ACCESS  read-write
   STATUS      current
   DESCRIPTION
       "LACP key : 1-65535. 0 : Auto"
   ::= { gs2326pplusLACPPortConfigurationEntry 3 }

gs2326pplusLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2326pplusLACPPortConfigurationEntry 4 }

gs2326pplusLACPSystemStatusTable OBJECT-TYPE
   SYNTAX      SEQUENCE OF Gs2326pplusLACPSystemStatusEntry
   MAX-ACCESS  not-accessible
   STATUS      current
   DESCRIPTION
       " "
   ::= { gs2326pplusLACP 2 }

gs2326pplusLACPSystemStatusEntry OBJECT-TYPE
   SYNTAX      Gs2326pplusLACPSystemStatusEntry
   MAX-ACCESS  not-accessible
   STATUS      current
   DESCRIPTION
       ""
   INDEX    { gs2326pplusLACPSystemStatusIndex  }
   ::= { gs2326pplusLACPSystemStatusTable 1 }

Gs2326pplusLACPSystemStatusEntry ::= SEQUENCE {
   gs2326pplusLACPSystemStatusIndex             Integer32,
   gs2326pplusLACPSystemStatusAggrID            DisplayString,
   gs2326pplusLACPSystemStatusPartnerSystemID   MacAddress,
   gs2326pplusLACPSystemStatusPartnerKey        DisplayString,
   gs2326pplusLACPSystemStatusLastchanged       DisplayString,
   gs2326pplusLACPSystemStatusLocalPorts        DisplayString
}

gs2326pplusLACPSystemStatusIndex OBJECT-TYPE
   SYNTAX      Integer32(1..12)
   MAX-ACCESS  not-accessible
   STATUS      current
   DESCRIPTION
       " "
   ::= { gs2326pplusLACPSystemStatusEntry 1 }

gs2326pplusLACPSystemStatusAggrID OBJECT-TYPE
   SYNTAX      DisplayString
   MAX-ACCESS  read-only
   STATUS      current
   DESCRIPTION
       "The Aggregation ID associated with this aggregation instance."
   ::= { gs2326pplusLACPSystemStatusEntry 2 }

gs2326pplusLACPSystemStatusPartnerSystemID OBJECT-TYPE
   SYNTAX      MacAddress
   MAX-ACCESS  read-only
   STATUS      current
   DESCRIPTION
       "The system ID (MAC address) of the aggregation partner."
   ::= { gs2326pplusLACPSystemStatusEntry 3 }

gs2326pplusLACPSystemStatusPartnerKey OBJECT-TYPE
   SYNTAX      DisplayString
   MAX-ACCESS  read-only
   STATUS      current
   DESCRIPTION
       " The Key that the partner has assigned to this aggregation ID. "
   ::= { gs2326pplusLACPSystemStatusEntry 4 }

gs2326pplusLACPSystemStatusLastchanged OBJECT-TYPE
   SYNTAX      DisplayString
   MAX-ACCESS  read-only
   STATUS      current
   DESCRIPTION
       " The time since this aggregation changed. "
   ::= { gs2326pplusLACPSystemStatusEntry 5 }

gs2326pplusLACPSystemStatusLocalPorts OBJECT-TYPE
   SYNTAX      DisplayString
   MAX-ACCESS  read-only
   STATUS      current
   DESCRIPTION
       " Shows which ports are a part of this aggregation for this switch. "
   ::= { gs2326pplusLACPSystemStatusEntry 6 }

gs2326pplusLACPStatusTable OBJECT-TYPE
   SYNTAX      SEQUENCE OF Gs2326pplusLACPStatusEntry
   MAX-ACCESS  not-accessible
   STATUS      current
   DESCRIPTION
       " "
   ::= { gs2326pplusLACP 3 }

gs2326pplusLACPStatusEntry OBJECT-TYPE
   SYNTAX      Gs2326pplusLACPStatusEntry
   MAX-ACCESS  not-accessible
   STATUS      current
   DESCRIPTION
       ""
   INDEX    { gs2326pplusLACPStatusPort  }
   ::= { gs2326pplusLACPStatusTable 1 }

Gs2326pplusLACPStatusEntry ::= SEQUENCE {
   gs2326pplusLACPStatusPort                Integer32,
   gs2326pplusLACPStatusLACP                DisplayString,
   gs2326pplusLACPStatusKey                 DisplayString,
   gs2326pplusLACPStatusAggrID              DisplayString,
   gs2326pplusLACPStatusPartnerSystemID     DisplayString,
   gs2326pplusLACPStatusPartnerPort         DisplayString
}

gs2326pplusLACPStatusPort OBJECT-TYPE
   SYNTAX      Integer32(1..4095)
   MAX-ACCESS  not-accessible
   STATUS      current
   DESCRIPTION
       " "
   ::= { gs2326pplusLACPStatusEntry 1 }

gs2326pplusLACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2326pplusLACPStatusEntry 2 }

gs2326pplusLACPStatusKey OBJECT-TYPE
   SYNTAX      DisplayString
   MAX-ACCESS  read-only
   STATUS      current
   DESCRIPTION
       "The key assigned to this port. Only ports with the same key can aggregate together."
   ::= { gs2326pplusLACPStatusEntry 3 }

gs2326pplusLACPStatusAggrID	 OBJECT-TYPE
   SYNTAX      DisplayString
   MAX-ACCESS  read-only
   STATUS      current
   DESCRIPTION
       " The Aggregation ID assigned to this aggregation group. "
   ::= { gs2326pplusLACPStatusEntry 4 }

gs2326pplusLACPStatusPartnerSystemID OBJECT-TYPE
   SYNTAX      DisplayString
   MAX-ACCESS  read-only
   STATUS      current
   DESCRIPTION
       " The partner's System ID. "
   ::= { gs2326pplusLACPStatusEntry 5 }

gs2326pplusLACPStatusPartnerPort OBJECT-TYPE
   SYNTAX      DisplayString
   MAX-ACCESS  read-only
   STATUS      current
   DESCRIPTION
       " The partner's port number connected to this port. "
   ::= { gs2326pplusLACPStatusEntry 6 }


gs2326pplusLACPStatisticsTable OBJECT-TYPE
   SYNTAX      SEQUENCE OF Gs2326pplusLACPStatisticsEntry
   MAX-ACCESS  not-accessible
   STATUS      current
   DESCRIPTION
       " "
   ::= { gs2326pplusLACP 4 }

gs2326pplusLACPStatisticsEntry OBJECT-TYPE
   SYNTAX      Gs2326pplusLACPStatisticsEntry
   MAX-ACCESS  not-accessible
   STATUS      current
   DESCRIPTION
       ""
   INDEX    { gs2326pplusLACPStatisticsPort  }
   ::= { gs2326pplusLACPStatisticsTable 1 }

Gs2326pplusLACPStatisticsEntry ::= SEQUENCE {
   gs2326pplusLACPStatisticsPort        Integer32,
   gs2326pplusLACPReceived              Counter32,
   gs2326pplusLACPTransmitted           Counter32,
   gs2326pplusLACPDiscardedUnknown      Counter32,
   gs2326pplusLACPDiscardedIllegal      Counter32
}

gs2326pplusLACPStatisticsPort OBJECT-TYPE
   SYNTAX      Integer32(1..4095)
   MAX-ACCESS  not-accessible
   STATUS      current
   DESCRIPTION
       " "
   ::= { gs2326pplusLACPStatisticsEntry 1 }

gs2326pplusLACPReceived OBJECT-TYPE
   SYNTAX      Counter32
   MAX-ACCESS  read-only
   STATUS      current
   DESCRIPTION
       "Shows how many LACP frames have been received at each port. "
   ::= { gs2326pplusLACPStatisticsEntry 2 }

gs2326pplusLACPTransmitted OBJECT-TYPE
   SYNTAX      Counter32
   MAX-ACCESS  read-only
   STATUS      current
   DESCRIPTION
       " Shows how many LACP frames have been sent from each port. "
   ::= { gs2326pplusLACPStatisticsEntry 3 }

gs2326pplusLACPDiscardedUnknown OBJECT-TYPE
   SYNTAX      Counter32
   MAX-ACCESS  read-only
   STATUS      current
   DESCRIPTION
       " Shows how many unknown LACP frames have been discarded at each port. "
   ::= { gs2326pplusLACPStatisticsEntry 4 }

gs2326pplusLACPDiscardedIllegal OBJECT-TYPE
   SYNTAX      Counter32
   MAX-ACCESS  read-only
   STATUS      current
   DESCRIPTION
       " Shows how many illegal LACP frames have been discarded at each port. "
   ::= { gs2326pplusLACPStatisticsEntry 5 }

gs2326pplusLACPStatisticsClear OBJECT-TYPE
   SYNTAX      INTEGER { none(0), clear(1) }
   MAX-ACCESS  read-write
   STATUS      current
   DESCRIPTION
       "default: 0
       0: none
       1: clear"
   ::= { gs2326pplusLACP 5 }

gs2326pplusSTP                                                     OBJECT IDENTIFIER ::= { gs2326pplusConfiguration 20 }

gs2326pplusSTPBridgeBasicConf                                                 OBJECT IDENTIFIER ::= { gs2326pplusSTP 1 }

gs2326pplusSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2326pplusSTPBridgeBasicConf 1 }

gs2326pplusSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2326pplusSTPBridgeBasicConf 2 }

gs2326pplusSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2326pplusSTPBridgeBasicConf 3 }

gs2326pplusSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2326pplusSTPBridgeBasicConf 4 }

gs2326pplusSTPBridgeMaximumHopCount OBJECT-TYPE
   SYNTAX      Integer32(6..40)
   MAX-ACCESS  read-write
   STATUS      current
   DESCRIPTION
       " Maximum Hop Count default: 20, range: 6 - 40."
   ::= { gs2326pplusSTPBridgeBasicConf 5 }

gs2326pplusSTPBridgeTransmitHoldCount OBJECT-TYPE
   SYNTAX      Integer32(1..10)
   MAX-ACCESS  read-write
   STATUS      current
   DESCRIPTION
       " Transmit Hold Count default: 6, range: 1 - 10."
   ::= { gs2326pplusSTPBridgeBasicConf 6 }

gs2326pplusSTPBridgeAdvancedConf                                                 OBJECT IDENTIFIER ::= { gs2326pplusSTP 2 }

gs2326pplusSTPBridgeEdgePortBPDUFiltering OBJECT-TYPE
   SYNTAX      INTEGER { disable(0), enable(1) }
   MAX-ACCESS  read-write
   STATUS      current
   DESCRIPTION
       " default: 0,
        0: disable
        1: enable"
   ::= { gs2326pplusSTPBridgeAdvancedConf 1 }

gs2326pplusSTPBridgeEdgePortBPDUGuard OBJECT-TYPE
   SYNTAX      INTEGER { disable(0), enable(1) }
   MAX-ACCESS  read-write
   STATUS      current
   DESCRIPTION
       " default: 0,
        0: disable
        1: enable"
   ::= { gs2326pplusSTPBridgeAdvancedConf 2 }

gs2326pplusSTPBridgePortErrorRecoveryTimeout OBJECT-TYPE
   SYNTAX      Integer32(0..86400)
   MAX-ACCESS  read-write
   STATUS      current
   DESCRIPTION
       " Port Error Recovery Timeout disable: 0, range: 30 - 86400."
   ::= { gs2326pplusSTPBridgeAdvancedConf 3 }

gs2326pplusSTPMSTIConf                                                 OBJECT IDENTIFIER ::= { gs2326pplusSTP 3 }

gs2326pplusSTPMSTIConfigurationName OBJECT-TYPE
   SYNTAX      DisplayString (SIZE (1..32))
   MAX-ACCESS  read-write
   STATUS      current
   DESCRIPTION
       "A text string up to 32 characters long."
   ::= { gs2326pplusSTPMSTIConf 1 }

gs2326pplusSTPMSTIConfigurationRevision   OBJECT-TYPE
   SYNTAX      Integer32(0..65535)
   MAX-ACCESS  read-write
   STATUS      current
   DESCRIPTION
       " Configuration Revision default: 0, range: 0 - 65535."
   ::= { gs2326pplusSTPMSTIConf 2 }

gs2326pplusSTPMSTIMappingConf                                                 OBJECT IDENTIFIER ::= { gs2326pplusSTP 4 }

gs2326pplusSTPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2326pplusSTPMSTIMappingConf 1 }

gs2326pplusSTPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2326pplusSTPMSTIMappingConf 2 }

gs2326pplusSTPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2326pplusSTPMSTIMappingConf 3 }

gs2326pplusSTPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2326pplusSTPMSTIMappingConf 4 }

gs2326pplusSTPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2326pplusSTPMSTIMappingConf 5 }

gs2326pplusSTPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2326pplusSTPMSTIMappingConf 6 }

gs2326pplusSTPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2326pplusSTPMSTIMappingConf 7 }

gs2326pplusSTPMSTIPriority                                                 OBJECT IDENTIFIER ::= { gs2326pplusSTP 5 }

gs2326pplusSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 1 }

gs2326pplusSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 2 }

gs2326pplusSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 3 }

gs2326pplusSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 4 }

gs2326pplusSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 5 }

gs2326pplusSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 6 }

gs2326pplusSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 7 }

gs2326pplusSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pplusSTPMSTIPriority 8 }

gs2326pplusSTPCISTPort                                                          OBJECT IDENTIFIER ::= { gs2326pplusSTP 6 }

gs2326pplusSTPCISTAggregatedPort                                                OBJECT IDENTIFIER ::= { gs2326pplusSTPCISTPort 1 }

gs2326pplusSTPCISTAggregatedPortSTPEnabled OBJECT-TYPE
   SYNTAX      INTEGER { disable(0), enable(1) }
   MAX-ACCESS  read-write
   STATUS      current
   DESCRIPTION
       " default: 0,
        0: disable
        1: enable"
   ::= { gs2326pplusSTPCISTAggregatedPort 1 }

gs2326pplusSTPCISTAggregatedPortPathCost OBJECT-TYPE
   SYNTAX      Integer32(0..200000000)
   MAX-ACCESS  read-write
   STATUS      current
   DESCRIPTION
       " Auto: 0,
        Specific Path Cost range: 1 - 200000000."
   ::= { gs2326pplusSTPCISTAggregatedPort 2 }

gs2326pplusSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326pplusSTPCISTAggregatedPort 3 }

gs2326pplusSTPCISTAggregatedPortAdminEdge OBJECT-TYPE
   SYNTAX      INTEGER { non-edge(0), edge(1) }
   MAX-ACCESS  read-write
   STATUS      current
   DESCRIPTION
       " default: 0,
        0: non-edge
        1: edge"
   ::= { gs2326pplusSTPCISTAggregatedPort 4 }

gs2326pplusSTPCISTAggregatedPortAutoEdge OBJECT-TYPE
   SYNTAX      INTEGER { disable(0), enable(1) }
   MAX-ACCESS  read-write
   STATUS      current
   DESCRIPTION
       " default: 1,
        0: disable
        1: enable"
   ::= { gs2326pplusSTPCISTAggregatedPort 5 }

gs2326pplusSTPCISTAggregatedPortRestrictedRole OBJECT-TYPE
   SYNTAX      INTEGER { disable(0), enable(1) }
   MAX-ACCESS  read-write
   STATUS      current
   DESCRIPTION
       " default: 0,
        0: disable
        1: enable"
   ::= { gs2326pplusSTPCISTAggregatedPort 6 }

gs2326pplusSTPCISTAggregatedPortRestrictedTCN OBJECT-TYPE
   SYNTAX      INTEGER { disable(0), enable(1) }
   MAX-ACCESS  read-write
   STATUS      current
   DESCRIPTION
       " default: 0,
        0: disable
        1: enable"
   ::= { gs2326pplusSTPCISTAggregatedPort 7 }

gs2326pplusSTPCISTAggregatedPortBPDUGuard OBJECT-TYPE
   SYNTAX      INTEGER { disable(0), enable(1) }
   MAX-ACCESS  read-write
   STATUS      current
   DESCRIPTION
       " default: 0,
        0: disable
        1: enable"
   ::= { gs2326pplusSTPCISTAggregatedPort 8 }

gs2326pplusSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2326pplusSTPCISTAggregatedPort 9 }

gs2326pplusSTPCISTNormalPortTable OBJECT-TYPE
   SYNTAX      SEQUENCE OF Gs2326pplusSTPCISTNormalPortEntry
   MAX-ACCESS  not-accessible
   STATUS      current
   DESCRIPTION
       " Show CIST Normal Port Configurations. "
   ::= { gs2326pplusSTPCISTPort 2 }

gs2326pplusSTPCISTNormalPortEntry OBJECT-TYPE
   SYNTAX      Gs2326pplusSTPCISTNormalPortEntry
   MAX-ACCESS  not-accessible
   STATUS      current
   DESCRIPTION
       ""
   INDEX    { gs2326pplusSTPCISTNormalPortConfPort  }
   ::= { gs2326pplusSTPCISTNormalPortTable 1 }

Gs2326pplusSTPCISTNormalPortEntry ::= SEQUENCE {
   gs2326pplusSTPCISTNormalPortConfPort         Integer32,
   gs2326pplusSTPCISTNormalPortSTPEnabled       INTEGER,
   gs2326pplusSTPCISTNormalPortPathCost         Integer32,
   gs2326pplusSTPCISTNormalPortPriority         Integer32,
   gs2326pplusSTPCISTNormalPortAdminEdge        INTEGER,
   gs2326pplusSTPCISTNormalPortAutoEdge         INTEGER,
   gs2326pplusSTPCISTNormalPortRestrictedRole   INTEGER,
   gs2326pplusSTPCISTNormalPortRestrictedTCN    INTEGER,
   gs2326pplusSTPCISTNormalPortBPDUGuard        INTEGER,
   gs2326pplusSTPCISTNormalPortPointtoPoint     INTEGER
}

gs2326pplusSTPCISTNormalPortConfPort OBJECT-TYPE
   SYNTAX      Integer32(1..4095)
   MAX-ACCESS  not-accessible
   STATUS      current
   DESCRIPTION
       " port, range : 1 - port number. "
   ::= { gs2326pplusSTPCISTNormalPortEntry 1 }

gs2326pplusSTPCISTNormalPortSTPEnabled OBJECT-TYPE
   SYNTAX      INTEGER { disable(0), enable(1) }
   MAX-ACCESS  read-write
   STATUS      current
   DESCRIPTION
       " default: 0,
        0: disable
        1: enable"
   ::= { gs2326pplusSTPCISTNormalPortEntry 2 }

gs2326pplusSTPCISTNormalPortPathCost OBJECT-TYPE
   SYNTAX      Integer32(0..200000000)
   MAX-ACCESS  read-write
   STATUS      current
   DESCRIPTION
       " Auto: 0,
        Specific Path Cost range: 1 - 200000000."
   ::= { gs2326pplusSTPCISTNormalPortEntry 3 }

gs2326pplusSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326pplusSTPCISTNormalPortEntry 4 }

gs2326pplusSTPCISTNormalPortAdminEdge OBJECT-TYPE
   SYNTAX      INTEGER { non-edge(0), edge(1) }
   MAX-ACCESS  read-write
   STATUS      current
   DESCRIPTION
       " default: 0,
        0: non-edge
        1: edge"
   ::= { gs2326pplusSTPCISTNormalPortEntry 5 }

gs2326pplusSTPCISTNormalPortAutoEdge OBJECT-TYPE
   SYNTAX      INTEGER { disable(0), enable(1) }
   MAX-ACCESS  read-write
   STATUS      current
   DESCRIPTION
       " default: 1,
        0: disable
        1: enable"
   ::= { gs2326pplusSTPCISTNormalPortEntry 6 }

gs2326pplusSTPCISTNormalPortRestrictedRole OBJECT-TYPE
   SYNTAX      INTEGER { disable(0), enable(1) }
   MAX-ACCESS  read-write
   STATUS      current
   DESCRIPTION
       " default: 0,
        0: disable
        1: enable"
   ::= { gs2326pplusSTPCISTNormalPortEntry 7 }

gs2326pplusSTPCISTNormalPortRestrictedTCN OBJECT-TYPE
   SYNTAX      INTEGER { disable(0), enable(1) }
   MAX-ACCESS  read-write
   STATUS      current
   DESCRIPTION
       " default: 0,
        0: disable
        1: enable"
   ::= { gs2326pplusSTPCISTNormalPortEntry 8 }

gs2326pplusSTPCISTNormalPortBPDUGuard OBJECT-TYPE
   SYNTAX      INTEGER { disable(0), enable(1) }
   MAX-ACCESS  read-write
   STATUS      current
   DESCRIPTION
       " default: 0,
        0: disable
        1: enable"
   ::= { gs2326pplusSTPCISTNormalPortEntry 9 }

gs2326pplusSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2326pplusSTPCISTNormalPortEntry 10 }


gs2326pplusSTPMSTIPort                                                          OBJECT IDENTIFIER ::= { gs2326pplusSTP 7 }

gs2326pplusSTPMSTI1Port                                                         OBJECT IDENTIFIER ::= { gs2326pplusSTPMSTIPort 1 }

gs2326pplusSTPMSTI1AggregatedPort                                                OBJECT IDENTIFIER ::= { gs2326pplusSTPMSTI1Port 1 }

gs2326pplusSTPMSTI1AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI1AggregatedPort 1 }

gs2326pplusSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI1AggregatedPort 2 }

gs2326pplusSTPMSTI1NormalPortTable OBJECT-TYPE
   SYNTAX      SEQUENCE OF Gs2326pplusSTPMSTI1NormalPortEntry
   MAX-ACCESS  not-accessible
   STATUS      current
   DESCRIPTION
       " Show MSTI1 Normal Port Configurations. "
   ::= { gs2326pplusSTPMSTI1Port 2 }

gs2326pplusSTPMSTI1NormalPortEntry OBJECT-TYPE
   SYNTAX      Gs2326pplusSTPMSTI1NormalPortEntry
   MAX-ACCESS  not-accessible
   STATUS      current
   DESCRIPTION
       ""
   INDEX    { gs2326pplusSTPMSTI1NormalPortConfPort  }
   ::= { gs2326pplusSTPMSTI1NormalPortTable 1 }

Gs2326pplusSTPMSTI1NormalPortEntry ::= SEQUENCE {
   gs2326pplusSTPMSTI1NormalPortConfPort         Integer32,
   gs2326pplusSTPMSTI1NormalPortPathCost         Integer32,
   gs2326pplusSTPMSTI1NormalPortPriority         Integer32
}

gs2326pplusSTPMSTI1NormalPortConfPort OBJECT-TYPE
   SYNTAX      Integer32(1..4095)
   MAX-ACCESS  not-accessible
   STATUS      current
   DESCRIPTION
       " port, range : 1 - port number. "
   ::= { gs2326pplusSTPMSTI1NormalPortEntry 1 }

gs2326pplusSTPMSTI1NormalPortPathCost OBJECT-TYPE
   SYNTAX      Integer32(0..200000000)
   MAX-ACCESS  read-write
   STATUS      current
   DESCRIPTION
       " Auto: 0,
        Specific Path Cost range: 1 - 200000000."
   ::= { gs2326pplusSTPMSTI1NormalPortEntry 2 }

gs2326pplusSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI1NormalPortEntry 3 }

gs2326pplusSTPMSTI2Port                                                          OBJECT IDENTIFIER ::= { gs2326pplusSTPMSTIPort 2 }

gs2326pplusSTPMSTI2AggregatedPort                                                OBJECT IDENTIFIER ::= { gs2326pplusSTPMSTI2Port 1 }

gs2326pplusSTPMSTI2AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI2AggregatedPort 1 }

gs2326pplusSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI2AggregatedPort 2 }

gs2326pplusSTPMSTI2NormalPortTable OBJECT-TYPE
   SYNTAX      SEQUENCE OF Gs2326pplusSTPMSTI2NormalPortEntry
   MAX-ACCESS  not-accessible
   STATUS      current
   DESCRIPTION
       " Show MSTI2 Normal Port Configurations. "
   ::= { gs2326pplusSTPMSTI2Port 2 }

gs2326pplusSTPMSTI2NormalPortEntry OBJECT-TYPE
   SYNTAX      Gs2326pplusSTPMSTI2NormalPortEntry
   MAX-ACCESS  not-accessible
   STATUS      current
   DESCRIPTION
       ""
   INDEX    { gs2326pplusSTPMSTI2NormalPortConfPort  }
   ::= { gs2326pplusSTPMSTI2NormalPortTable 1 }

Gs2326pplusSTPMSTI2NormalPortEntry ::= SEQUENCE {
   gs2326pplusSTPMSTI2NormalPortConfPort         Integer32,
   gs2326pplusSTPMSTI2NormalPortPathCost         Integer32,
   gs2326pplusSTPMSTI2NormalPortPriority         Integer32
}

gs2326pplusSTPMSTI2NormalPortConfPort OBJECT-TYPE
   SYNTAX      Integer32(1..4095)
   MAX-ACCESS  not-accessible
   STATUS      current
   DESCRIPTION
       " port, range : 1 - port number. "
   ::= { gs2326pplusSTPMSTI2NormalPortEntry 1 }

gs2326pplusSTPMSTI2NormalPortPathCost OBJECT-TYPE
   SYNTAX      Integer32(0..200000000)
   MAX-ACCESS  read-write
   STATUS      current
   DESCRIPTION
       " Auto: 0,
        Specific Path Cost range: 1 - 200000000."
   ::= { gs2326pplusSTPMSTI2NormalPortEntry 2 }

gs2326pplusSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI2NormalPortEntry 3 }

gs2326pplusSTPMSTI3Port                                                          OBJECT IDENTIFIER ::= { gs2326pplusSTPMSTIPort 3 }

gs2326pplusSTPMSTI3AggregatedPort                                                OBJECT IDENTIFIER ::= { gs2326pplusSTPMSTI3Port 1 }

gs2326pplusSTPMSTI3AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI3AggregatedPort 1 }

gs2326pplusSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI3AggregatedPort 2 }

gs2326pplusSTPMSTI3NormalPortTable OBJECT-TYPE
   SYNTAX      SEQUENCE OF Gs2326pplusSTPMSTI3NormalPortEntry
   MAX-ACCESS  not-accessible
   STATUS      current
   DESCRIPTION
       " Show MSTI3 Normal Port Configurations. "
   ::= { gs2326pplusSTPMSTI3Port 2 }

gs2326pplusSTPMSTI3NormalPortEntry OBJECT-TYPE
   SYNTAX      Gs2326pplusSTPMSTI3NormalPortEntry
   MAX-ACCESS  not-accessible
   STATUS      current
   DESCRIPTION
       ""
   INDEX    { gs2326pplusSTPMSTI3NormalPortConfPort  }
   ::= { gs2326pplusSTPMSTI3NormalPortTable 1 }

Gs2326pplusSTPMSTI3NormalPortEntry ::= SEQUENCE {
   gs2326pplusSTPMSTI3NormalPortConfPort         Integer32,
   gs2326pplusSTPMSTI3NormalPortPathCost         Integer32,
   gs2326pplusSTPMSTI3NormalPortPriority         Integer32
}

gs2326pplusSTPMSTI3NormalPortConfPort OBJECT-TYPE
   SYNTAX      Integer32(1..4095)
   MAX-ACCESS  not-accessible
   STATUS      current
   DESCRIPTION
       " port, range : 1 - port number. "
   ::= { gs2326pplusSTPMSTI3NormalPortEntry 1 }

gs2326pplusSTPMSTI3NormalPortPathCost OBJECT-TYPE
   SYNTAX      Integer32(0..200000000)
   MAX-ACCESS  read-write
   STATUS      current
   DESCRIPTION
       " Auto: 0,
        Specific Path Cost range: 1 - 200000000."
   ::= { gs2326pplusSTPMSTI3NormalPortEntry 2 }

gs2326pplusSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI3NormalPortEntry 3 }

gs2326pplusSTPMSTI4Port                                                          OBJECT IDENTIFIER ::= { gs2326pplusSTPMSTIPort 4 }

gs2326pplusSTPMSTI4AggregatedPort                                                OBJECT IDENTIFIER ::= { gs2326pplusSTPMSTI4Port 1 }

gs2326pplusSTPMSTI4AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI4AggregatedPort 1 }

gs2326pplusSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI4AggregatedPort 2 }

gs2326pplusSTPMSTI4NormalPortTable OBJECT-TYPE
   SYNTAX      SEQUENCE OF Gs2326pplusSTPMSTI4NormalPortEntry
   MAX-ACCESS  not-accessible
   STATUS      current
   DESCRIPTION
       " Show MSTI4 Normal Port Configurations. "
   ::= { gs2326pplusSTPMSTI4Port 2 }

gs2326pplusSTPMSTI4NormalPortEntry OBJECT-TYPE
   SYNTAX      Gs2326pplusSTPMSTI4NormalPortEntry
   MAX-ACCESS  not-accessible
   STATUS      current
   DESCRIPTION
       ""
   INDEX    { gs2326pplusSTPMSTI4NormalPortConfPort  }
   ::= { gs2326pplusSTPMSTI4NormalPortTable 1 }

Gs2326pplusSTPMSTI4NormalPortEntry ::= SEQUENCE {
   gs2326pplusSTPMSTI4NormalPortConfPort         Integer32,
   gs2326pplusSTPMSTI4NormalPortPathCost         Integer32,
   gs2326pplusSTPMSTI4NormalPortPriority         Integer32
}

gs2326pplusSTPMSTI4NormalPortConfPort OBJECT-TYPE
   SYNTAX      Integer32(1..4095)
   MAX-ACCESS  not-accessible
   STATUS      current
   DESCRIPTION
       " port, range : 1 - port number. "
   ::= { gs2326pplusSTPMSTI4NormalPortEntry 1 }

gs2326pplusSTPMSTI4NormalPortPathCost OBJECT-TYPE
   SYNTAX      Integer32(0..200000000)
   MAX-ACCESS  read-write
   STATUS      current
   DESCRIPTION
       " Auto: 0,
        Specific Path Cost range: 1 - 200000000."
   ::= { gs2326pplusSTPMSTI4NormalPortEntry 2 }

gs2326pplusSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI4NormalPortEntry 3 }

gs2326pplusSTPMSTI5Port                                                          OBJECT IDENTIFIER ::= { gs2326pplusSTPMSTIPort 5 }

gs2326pplusSTPMSTI5AggregatedPort                                                OBJECT IDENTIFIER ::= { gs2326pplusSTPMSTI5Port 1 }

gs2326pplusSTPMSTI5AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI5AggregatedPort 1 }

gs2326pplusSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI5AggregatedPort 2 }

gs2326pplusSTPMSTI5NormalPortTable OBJECT-TYPE
   SYNTAX      SEQUENCE OF Gs2326pplusSTPMSTI5NormalPortEntry
   MAX-ACCESS  not-accessible
   STATUS      current
   DESCRIPTION
       " Show MSTI5 Normal Port Configurations. "
   ::= { gs2326pplusSTPMSTI5Port 2 }

gs2326pplusSTPMSTI5NormalPortEntry OBJECT-TYPE
   SYNTAX      Gs2326pplusSTPMSTI5NormalPortEntry
   MAX-ACCESS  not-accessible
   STATUS      current
   DESCRIPTION
       ""
   INDEX    { gs2326pplusSTPMSTI5NormalPortConfPort  }
   ::= { gs2326pplusSTPMSTI5NormalPortTable 1 }

Gs2326pplusSTPMSTI5NormalPortEntry ::= SEQUENCE {
   gs2326pplusSTPMSTI5NormalPortConfPort         Integer32,
   gs2326pplusSTPMSTI5NormalPortPathCost         Integer32,
   gs2326pplusSTPMSTI5NormalPortPriority         Integer32
}

gs2326pplusSTPMSTI5NormalPortConfPort OBJECT-TYPE
   SYNTAX      Integer32(1..4095)
   MAX-ACCESS  not-accessible
   STATUS      current
   DESCRIPTION
       " port, range : 1 - port number. "
   ::= { gs2326pplusSTPMSTI5NormalPortEntry 1 }

gs2326pplusSTPMSTI5NormalPortPathCost OBJECT-TYPE
   SYNTAX      Integer32(0..200000000)
   MAX-ACCESS  read-write
   STATUS      current
   DESCRIPTION
       " Auto: 0,
        Specific Path Cost range: 1 - 200000000."
   ::= { gs2326pplusSTPMSTI5NormalPortEntry 2 }

gs2326pplusSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI5NormalPortEntry 3 }

gs2326pplusSTPMSTI6Port                                                          OBJECT IDENTIFIER ::= { gs2326pplusSTPMSTIPort 6 }

gs2326pplusSTPMSTI6AggregatedPort                                                OBJECT IDENTIFIER ::= { gs2326pplusSTPMSTI6Port 1 }

gs2326pplusSTPMSTI6AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI6AggregatedPort 1 }

gs2326pplusSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI6AggregatedPort 2 }

gs2326pplusSTPMSTI6NormalPortTable OBJECT-TYPE
   SYNTAX      SEQUENCE OF Gs2326pplusSTPMSTI6NormalPortEntry
   MAX-ACCESS  not-accessible
   STATUS      current
   DESCRIPTION
       " Show MSTI6 Normal Port Configurations. "
   ::= { gs2326pplusSTPMSTI6Port 2 }

gs2326pplusSTPMSTI6NormalPortEntry OBJECT-TYPE
   SYNTAX      Gs2326pplusSTPMSTI6NormalPortEntry
   MAX-ACCESS  not-accessible
   STATUS      current
   DESCRIPTION
       ""
   INDEX    { gs2326pplusSTPMSTI6NormalPortConfPort  }
   ::= { gs2326pplusSTPMSTI6NormalPortTable 1 }

Gs2326pplusSTPMSTI6NormalPortEntry ::= SEQUENCE {
   gs2326pplusSTPMSTI6NormalPortConfPort         Integer32,
   gs2326pplusSTPMSTI6NormalPortPathCost         Integer32,
   gs2326pplusSTPMSTI6NormalPortPriority         Integer32
}

gs2326pplusSTPMSTI6NormalPortConfPort OBJECT-TYPE
   SYNTAX      Integer32(1..4095)
   MAX-ACCESS  not-accessible
   STATUS      current
   DESCRIPTION
       " port, range : 1 - port number. "
   ::= { gs2326pplusSTPMSTI6NormalPortEntry 1 }

gs2326pplusSTPMSTI6NormalPortPathCost OBJECT-TYPE
   SYNTAX      Integer32(0..200000000)
   MAX-ACCESS  read-write
   STATUS      current
   DESCRIPTION
       " Auto: 0,
        Specific Path Cost range: 1 - 200000000."
   ::= { gs2326pplusSTPMSTI6NormalPortEntry 2 }

gs2326pplusSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI6NormalPortEntry 3 }

gs2326pplusSTPMSTI7Port                                                          OBJECT IDENTIFIER ::= { gs2326pplusSTPMSTIPort 7 }

gs2326pplusSTPMSTI7AggregatedPort                                                OBJECT IDENTIFIER ::= { gs2326pplusSTPMSTI7Port 1 }

gs2326pplusSTPMSTI7AggregatedPortPathCost OBJECT-TYPE
   SYNTAX      Integer32(0..200000000)
   MAX-ACCESS  read-write
   STATUS      current
   DESCRIPTION
       " Auto: 0,
        Specific Path Cost range: 1 - 200000000."
   ::= { gs2326pplusSTPMSTI7AggregatedPort 1 }

gs2326pplusSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI7AggregatedPort 2 }

gs2326pplusSTPMSTI7NormalPortTable OBJECT-TYPE
   SYNTAX      SEQUENCE OF Gs2326pplusSTPMSTI7NormalPortEntry
   MAX-ACCESS  not-accessible
   STATUS      current
   DESCRIPTION
       " Show MSTI7 Normal Port Configurations. "
   ::= { gs2326pplusSTPMSTI7Port 2 }

gs2326pplusSTPMSTI7NormalPortEntry OBJECT-TYPE
   SYNTAX      Gs2326pplusSTPMSTI7NormalPortEntry
   MAX-ACCESS  not-accessible
   STATUS      current
   DESCRIPTION
       ""
   INDEX    { gs2326pplusSTPMSTI7NormalPortConfPort  }
   ::= { gs2326pplusSTPMSTI7NormalPortTable 1 }

Gs2326pplusSTPMSTI7NormalPortEntry ::= SEQUENCE {
   gs2326pplusSTPMSTI7NormalPortConfPort         Integer32,
   gs2326pplusSTPMSTI7NormalPortPathCost         Integer32,
   gs2326pplusSTPMSTI7NormalPortPriority         Integer32
}

gs2326pplusSTPMSTI7NormalPortConfPort OBJECT-TYPE
   SYNTAX      Integer32(1..4095)
   MAX-ACCESS  not-accessible
   STATUS      current
   DESCRIPTION
       " port, range : 1 - port number. "
   ::= { gs2326pplusSTPMSTI7NormalPortEntry 1 }

gs2326pplusSTPMSTI7NormalPortPathCost OBJECT-TYPE
   SYNTAX      Integer32(0..200000000)
   MAX-ACCESS  read-write
   STATUS      current
   DESCRIPTION
       " Auto: 0,
        Specific Path Cost range: 1 - 200000000."
   ::= { gs2326pplusSTPMSTI7NormalPortEntry 2 }

gs2326pplusSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pplusSTPMSTI7NormalPortEntry 3 }


gs2326pplusSTPBridgeStatus                                                      OBJECT IDENTIFIER ::= { gs2326pplusSTP 8 }

gs2326pplusCISTBridgeSTP                                                        OBJECT IDENTIFIER ::= { gs2326pplusSTPBridgeStatus 1 }

gs2326pplusCISTBridgeSTPStatus                                                  OBJECT IDENTIFIER ::= { gs2326pplusCISTBridgeSTP 1 }

gs2326pplusCISTBridgeInstance OBJECT-TYPE
   SYNTAX       DisplayString
   MAX-ACCESS   read-only
   STATUS       current
   DESCRIPTION
       "The Bridge instance - CIST, MST1, ..."
   ::= { gs2326pplusCISTBridgeSTPStatus 1 }

gs2326pplusCISTBridgeID OBJECT-TYPE
   SYNTAX       DisplayString
   MAX-ACCESS   read-only
   STATUS       current
   DESCRIPTION
       "The Bridge ID of this Bridge instance."
   ::= { gs2326pplusCISTBridgeSTPStatus 2 }

gs2326pplusCISTRootID OBJECT-TYPE
   SYNTAX       DisplayString
   MAX-ACCESS   read-only
   STATUS       current
   DESCRIPTION
       "The Bridge ID of the currently elected root bridge."
   ::= { gs2326pplusCISTBridgeSTPStatus 3 }

gs2326pplusCISTRootPort OBJECT-TYPE
   SYNTAX       DisplayString
   MAX-ACCESS   read-only
   STATUS       current
   DESCRIPTION
       "The switch port currently assigned the root port role."
   ::= { gs2326pplusCISTBridgeSTPStatus 4 }

gs2326pplusCISTRootCost OBJECT-TYPE
   SYNTAX       Integer32(0..200000000)
   MAX-ACCESS   read-only
   STATUS       current
   DESCRIPTION
       "Root Path Cost."
   ::= { gs2326pplusCISTBridgeSTPStatus 5 }

gs2326pplusCISTRegionalRoot OBJECT-TYPE
   SYNTAX       DisplayString
   MAX-ACCESS   read-only
   STATUS       current
   DESCRIPTION
       "The Bridge ID of the currently elected regional root bridge, inside the MSTP region of this bridge."
   ::= { gs2326pplusCISTBridgeSTPStatus 6 }

gs2326pplusCISTInternalRootCost OBJECT-TYPE
   SYNTAX       Integer32(0..200000000)
   MAX-ACCESS   read-only
   STATUS       current
   DESCRIPTION
       "The Regional Root Path Cost."
   ::= { gs2326pplusCISTBridgeSTPStatus 7 }

gs2326pplusCISTTopologyFlag OBJECT-TYPE
   SYNTAX       DisplayString
   MAX-ACCESS   read-only
   STATUS       current
   DESCRIPTION
       "The current state of the Topology Change Flag of this Bridge instance."
   ::= { gs2326pplusCISTBridgeSTPStatus 8 }

gs2326pplusCISTTopologyChangeCount OBJECT-TYPE
   SYNTAX       Counter32
   MAX-ACCESS   read-only
   STATUS       current
   DESCRIPTION
       "The number of times where the topology change flag has been set."
   ::= { gs2326pplusCISTBridgeSTPStatus 9 }

gs2326pplusCISTTopologyChangeLast OBJECT-TYPE
   SYNTAX       DisplayString
   MAX-ACCESS   read-only
   STATUS       current
   DESCRIPTION
       "The time passed since the Topology Flag was last set."
   ::= { gs2326pplusCISTBridgeSTPStatus 10 }

gs2326pplusCISTPortStateTable OBJECT-TYPE
   SYNTAX      SEQUENCE OF Gs2326pplusCISTPortStateEntry
   MAX-ACCESS  not-accessible
   STATUS      current
   DESCRIPTION
       " Show CIST Ports and Aggregations State Configurations. "
   ::= { gs2326pplusCISTBridgeSTP 2 }

gs2326pplusCISTPortStateEntry OBJECT-TYPE
   SYNTAX      Gs2326pplusCISTPortStateEntry
   MAX-ACCESS  not-accessible
   STATUS      current
   DESCRIPTION
       ""
   INDEX    { gs2326pplusCISTPortStateIndex  }
   ::= { gs2326pplusCISTPortStateTable 1 }

Gs2326pplusCISTPortStateEntry ::= SEQUENCE {
   gs2326pplusCISTPortStateIndex        Integer32,
   gs2326pplusCISTPortStatePort         DisplayString,
   gs2326pplusCISTPortStatePortID       DisplayString,
   gs2326pplusCISTPortStateRole         DisplayString,
   gs2326pplusCISTPortStateState        DisplayString,
   gs2326pplusCISTPortStatePathCost     Integer32,
   gs2326pplusCISTPortStateEdge         DisplayString,
   gs2326pplusCISTPortStatePoint2Point  DisplayString,
   gs2326pplusCISTPortStateUptime       DisplayString
}

gs2326pplusCISTPortStateIndex OBJECT-TYPE
   SYNTAX      Integer32(1..4095)
   MAX-ACCESS  not-accessible
   STATUS      current
   DESCRIPTION
       "table index."
   ::= { gs2326pplusCISTPortStateEntry 1 }

gs2326pplusCISTPortStatePort OBJECT-TYPE
   SYNTAX      DisplayString
   MAX-ACCESS  read-only
   STATUS      current
   DESCRIPTION
       "The switch port number of the logical STP port."
   ::= { gs2326pplusCISTPortStateEntry 2 }

gs2326pplusCISTPortStatePortID OBJECT-TYPE
   SYNTAX      DisplayString
   MAX-ACCESS  read-only
   STATUS      current
   DESCRIPTION
       "The port id as used by the STP protocol.
        This is the priority part and the logical port index of the bridge port."
   ::= { gs2326pplusCISTPortStateEntry 3 }

gs2326pplusCISTPortStateRole OBJECT-TYPE
   SYNTAX      DisplayString
   MAX-ACCESS  read-only
   STATUS      current
   DESCRIPTION
       "The current STP port role."
   ::= { gs2326pplusCISTPortStateEntry 4 }

gs2326pplusCISTPortStateState OBJECT-TYPE
   SYNTAX      DisplayString
   MAX-ACCESS  read-only
   STATUS      current
   DESCRIPTION
       "The current STP port state."
   ::= { gs2326pplusCISTPortStateEntry 5 }

gs2326pplusCISTPortStatePathCost OBJECT-TYPE
   SYNTAX      Integer32(0..200000000)
   MAX-ACCESS  read-only
   STATUS      current
   DESCRIPTION
       "The current STP port path cost."
   ::= { gs2326pplusCISTPortStateEntry 6 }

gs2326pplusCISTPortStateEdge OBJECT-TYPE
   SYNTAX      DisplayString
   MAX-ACCESS  read-only
   STATUS      current
   DESCRIPTION
       "The current STP port Edge Flag."
   ::= { gs2326pplusCISTPortStateEntry 7 }

gs2326pplusCISTPortStatePoint2Point OBJECT-TYPE
   SYNTAX      DisplayString
   MAX-ACCESS  read-only
   STATUS      current
   DESCRIPTION
       "The current STP port point-to-point flag."
   ::= { gs2326pplusCISTPortStateEntry 8 }

gs2326pplusCISTPortStateUptime OBJECT-TYPE
   SYNTAX      DisplayString
   MAX-ACCESS  read-only
   STATUS      current
   DESCRIPTION
       "The time since the bridge port was last initialized."
   ::= { gs2326pplusCISTPortStateEntry 9 }

gs2326pplusMSTI1BridgeSTP                                                        OBJECT IDENTIFIER ::= { gs2326pplusSTPBridgeStatus 2 }

gs2326pplusMSTI1BridgeSTPStatus                                                  OBJECT IDENTIFIER ::= { gs2326pplusMSTI1BridgeSTP 1 }

gs2326pplusMSTI1BridgeInstance OBJECT-TYPE
   SYNTAX       DisplayString
   MAX-ACCESS   read-only
   STATUS       current
   DESCRIPTION
       "The Bridge instance - CIST, MST1, ..."
   ::= { gs2326pplusMSTI1BridgeSTPStatus 1 }

gs2326pplusMSTI1BridgeID OBJECT-TYPE
   SYNTAX       DisplayString
   MAX-ACCESS   read-only
   STATUS       current
   DESCRIPTION
       "The Bridge ID of this Bridge instance."
   ::= { gs2326pplusMSTI1BridgeSTPStatus 2 }

gs2326pplusMSTI1RootID OBJECT-TYPE
   SYNTAX       DisplayString
   MAX-ACCESS   read-only
   STATUS       current
   DESCRIPTION
       "The Bridge ID of the currently elected root bridge."
   ::= { gs2326pplusMSTI1BridgeSTPStatus 3 }

gs2326pplusMSTI1RootPort OBJECT-TYPE
   SYNTAX       DisplayString
   MAX-ACCESS   read-only
   STATUS       current
   DESCRIPTION
       "The switch port currently assigned the root port role."
   ::= { gs2326pplusMSTI1BridgeSTPStatus 4 }

gs2326pplusMSTI1RootCost OBJECT-TYPE
   SYNTAX       Integer32(0..200000000)
   MAX-ACCESS   read-only
   STATUS       current
   DESCRIPTION
       "Root Path Cost."
   ::= { gs2326pplusMSTI1BridgeSTPStatus 5 }

gs2326pplusMSTI1TopologyFlag OBJECT-TYPE
   SYNTAX       DisplayString
   MAX-ACCESS   read-only
   STATUS       current
   DESCRIPTION
       "The current state of the Topology Change Flag of this Bridge instance."
   ::= { gs2326pplusMSTI1BridgeSTPStatus 8 }

gs2326pplusMSTI1TopologyChangeCount OBJECT-TYPE
   SYNTAX       Counter32
   MAX-ACCESS   read-only
   STATUS       current
   DESCRIPTION
       "The number of times where the topology change flag has been set."
   ::= { gs2326pplusMSTI1BridgeSTPStatus 9 }

gs2326pplusMSTI1TopologyChangeLast OBJECT-TYPE
   SYNTAX       DisplayString
   MAX-ACCESS   read-only
   STATUS       current
   DESCRIPTION
       "The time passed since the Topology Flag was last set."
   ::= { gs2326pplusMSTI1BridgeSTPStatus 10 }

gs2326pplusMSTI1PortStateTable OBJECT-TYPE
   SYNTAX      SEQUENCE OF Gs2326pplusMSTI1PortStateEntry
   MAX-ACCESS  not-accessible
   STATUS      current
   DESCRIPTION
       " Show MSTI1 Ports and Aggregations State Configurations. "
   ::= { gs2326pplusMSTI1BridgeSTP 2 }

gs2326pplusMSTI1PortStateEntry OBJECT-TYPE
   SYNTAX      Gs2326pplusMSTI1PortStateEntry
   MAX-ACCESS  not-accessible
   STATUS      current
   DESCRIPTION
       ""
   INDEX    { gs2326pplusMSTI1PortStateIndex  }
   ::= { gs2326pplusMSTI1PortStateTable 1 }

Gs2326pplusMSTI1PortStateEntry ::= SEQUENCE {
   gs2326pplusMSTI1PortStateIndex        Integer32,
   gs2326pplusMSTI1PortStatePort         DisplayString,
   gs2326pplusMSTI1PortStatePortID       DisplayString,
   gs2326pplusMSTI1PortStateRole         DisplayString,
   gs2326pplusMSTI1PortStateState        DisplayString,
   gs2326pplusMSTI1PortStatePathCost     Integer32,
   gs2326pplusMSTI1PortStateEdge         DisplayString,
   gs2326pplusMSTI1PortStatePoint2Point  DisplayString,
   gs2326pplusMSTI1PortStateUptime       DisplayString
}

gs2326pplusMSTI1PortStateIndex OBJECT-TYPE
   SYNTAX      Integer32(1..4095)
   MAX-ACCESS  not-accessible
   STATUS      current
   DESCRIPTION
       "table index."
   ::= { gs2326pplusMSTI1PortStateEntry 1 }

gs2326pplusMSTI1PortStatePort OBJECT-TYPE
   SYNTAX      DisplayString
   MAX-ACCESS  read-only
   STATUS      current
   DESCRIPTION
       "The switch port number of the logical STP port."
   ::= { gs2326pplusMSTI1PortStateEntry 2 }

gs2326pplusMSTI1PortStatePortID OBJECT-TYPE
   SYNTAX      DisplayString
   MAX-ACCESS  read-only
   STATUS      current
   DESCRIPTION
       "The port id as used by the STP protocol.
        This is the priority part and the logical port index of the bridge port."
   ::= { gs2326pplusMSTI1PortStateEntry 3 }

gs2326pplusMSTI1PortStateRole OBJECT-TYPE
   SYNTAX      DisplayString
   MAX-ACCESS  read-only
   STATUS      current
   DESCRIPTION
       "The current STP port role."
   ::= { gs2326pplusMSTI1PortStateEntry 4 }

gs2326pplusMSTI1PortStateState OBJECT-TYPE
   SYNTAX      DisplayString
   MAX-ACCESS  read-only
   STATUS      current
   DESCRIPTION
       "The current STP port state."
   ::= { gs2326pplusMSTI1PortStateEntry 5 }

gs2326pplusMSTI1PortStatePathCost OBJECT-TYPE
   SYNTAX      Integer32(0..200000000)
   MAX-ACCESS  read-only
   STATUS      current
   DESCRIPTION
       "The current STP port path cost."
   ::= { gs2326pplusMSTI1PortStateEntry 6 }

gs2326pplusMSTI1PortStateEdge OBJECT-TYPE
   SYNTAX      DisplayString
   MAX-ACCESS  read-only
   STATUS      current
   DESCRIPTION
       "The current STP port Edge Flag."
   ::= { gs2326pplusMSTI1PortStateEntry 7 }

gs2326pplusMSTI1PortStatePoint2Point OBJECT-TYPE
   SYNTAX      DisplayString
   MAX-ACCESS  read-only
   STATUS      current
   DESCRIPTION
       "The current STP port point-to-point flag."
   ::= { gs2326pplusMSTI1PortStateEntry 8 }

gs2326pplusMSTI1PortStateUptime OBJECT-TYPE
   SYNTAX      DisplayString
   MAX-ACCESS  read-only
   STATUS      current
   DESCRIPTION
       "The time since the bridge port was last initialized."
   ::= { gs2326pplusMSTI1PortStateEntry 9 }

gs2326pplusMSTI2BridgeSTP                                                        OBJECT IDENTIFIER ::= { gs2326pplusSTPBridgeStatus 3 }

gs2326pplusMSTI2BridgeSTPStatus                                                  OBJECT IDENTIFIER ::= { gs2326pplusMSTI2BridgeSTP 1 }

gs2326pplusMSTI2BridgeInstance OBJECT-TYPE
   SYNTAX       DisplayString
   MAX-ACCESS   read-only
   STATUS       current
   DESCRIPTION
       "The Bridge instance - CIST, MST1, ..."
   ::= { gs2326pplusMSTI2BridgeSTPStatus 1 }

gs2326pplusMSTI2BridgeID OBJECT-TYPE
   SYNTAX       DisplayString
   MAX-ACCESS   read-only
   STATUS       current
   DESCRIPTION
       "The Bridge ID of this Bridge instance."
   ::= { gs2326pplusMSTI2BridgeSTPStatus 2 }

gs2326pplusMSTI2RootID OBJECT-TYPE
   SYNTAX       DisplayString
   MAX-ACCESS   read-only
   STATUS       current
   DESCRIPTION
       "The Bridge ID of the currently elected root bridge."
   ::= { gs2326pplusMSTI2BridgeSTPStatus 3 }

gs2326pplusMSTI2RootPort OBJECT-TYPE
   SYNTAX       DisplayString
   MAX-ACCESS   read-only
   STATUS       current
   DESCRIPTION
       "The switch port currently assigned the root port role."
   ::= { gs2326pplusMSTI2BridgeSTPStatus 4 }

gs2326pplusMSTI2RootCost OBJECT-TYPE
   SYNTAX       Integer32(0..200000000)
   MAX-ACCESS   read-only
   STATUS       current
   DESCRIPTION
       "Root Path Cost."
   ::= { gs2326pplusMSTI2BridgeSTPStatus 5 }

gs2326pplusMSTI2TopologyFlag OBJECT-TYPE
   SYNTAX       DisplayString
   MAX-ACCESS   read-only
   STATUS       current
   DESCRIPTION
       "The current state of the Topology Change Flag of this Bridge instance."
   ::= { gs2326pplusMSTI2BridgeSTPStatus 8 }

gs2326pplusMSTI2TopologyChangeCount OBJECT-TYPE
   SYNTAX       Counter32
   MAX-ACCESS   read-only
   STATUS       current
   DESCRIPTION
       "The number of times where the topology change flag has been set."
   ::= { gs2326pplusMSTI2BridgeSTPStatus 9 }

gs2326pplusMSTI2TopologyChangeLast OBJECT-TYPE
   SYNTAX       DisplayString
   MAX-ACCESS   read-only
   STATUS       current
   DESCRIPTION
       "The time passed since the Topology Flag was last set."
   ::= { gs2326pplusMSTI2BridgeSTPStatus 10 }

gs2326pplusMSTI2PortStateTable OBJECT-TYPE
   SYNTAX      SEQUENCE OF Gs2326pplusMSTI2PortStateEntry
   MAX-ACCESS  not-accessible
   STATUS      current
   DESCRIPTION
       " Show MSTI2 Ports and Aggregations State Configurations. "
   ::= { gs2326pplusMSTI2BridgeSTP 2 }

gs2326pplusMSTI2PortStateEntry OBJECT-TYPE
   SYNTAX      Gs2326pplusMSTI2PortStateEntry
   MAX-ACCESS  not-accessible
   STATUS      current
   DESCRIPTION
       ""
   INDEX    { gs2326pplusMSTI2PortStateIndex  }
   ::= { gs2326pplusMSTI2PortStateTable 1 }

Gs2326pplusMSTI2PortStateEntry ::= SEQUENCE {
   gs2326pplusMSTI2PortStateIndex        Integer32,
   gs2326pplusMSTI2PortStatePort         DisplayString,
   gs2326pplusMSTI2PortStatePortID       DisplayString,
   gs2326pplusMSTI2PortStateRole         DisplayString,
   gs2326pplusMSTI2PortStateState        DisplayString,
   gs2326pplusMSTI2PortStatePathCost     Integer32,
   gs2326pplusMSTI2PortStateEdge         DisplayString,
   gs2326pplusMSTI2PortStatePoint2Point  DisplayString,
   gs2326pplusMSTI2PortStateUptime       DisplayString
}

gs2326pplusMSTI2PortStateIndex OBJECT-TYPE
   SYNTAX      Integer32(1..4095)
   MAX-ACCESS  not-accessible
   STATUS      current
   DESCRIPTION
       "table index."
   ::= { gs2326pplusMSTI2PortStateEntry 1 }

gs2326pplusMSTI2PortStatePort OBJECT-TYPE
   SYNTAX      DisplayString
   MAX-ACCESS  read-only
   STATUS      current
   DESCRIPTION
       "The switch port number of the logical STP port."
   ::= { gs2326pplusMSTI2PortStateEntry 2 }

gs2326pplusMSTI2PortStatePortID OBJECT-TYPE
   SYNTAX      DisplayString
   MAX-ACCESS  read-only
   STATUS      current
   DESCRIPTION
       "The port id as used by the STP protocol.
        This is the priority part and the logical port index of the bridge port."
   ::= { gs2326pplusMSTI2PortStateEntry 3 }

gs2326pplusMSTI2PortStateRole OBJECT-TYPE
   SYNTAX      DisplayString
   MAX-ACCESS  read-only
   STATUS      current
   DESCRIPTION
       "The current STP port role."
   ::= { gs2326pplusMSTI2PortStateEntry 4 }

gs2326pplusMSTI2PortStateState OBJECT-TYPE
   SYNTAX      DisplayString
   MAX-ACCESS  read-only
   STATUS      current
   DESCRIPTION
       "The current STP port state."
   ::= { gs2326pplusMSTI2PortStateEntry 5 }

gs2326pplusMSTI2PortStatePathCost OBJECT-TYPE
   SYNTAX      Integer32(0..200000000)
   MAX-ACCESS  read-only
   STATUS      current
   DESCRIPTION
       "The current STP port path cost."
   ::= { gs2326pplusMSTI2PortStateEntry 6 }

gs2326pplusMSTI2PortStateEdge OBJECT-TYPE
   SYNTAX      DisplayString
   MAX-ACCESS  read-only
   STATUS      current
   DESCRIPTION
       "The current STP port Edge Flag."
   ::= { gs2326pplusMSTI2PortStateEntry 7 }

gs2326pplusMSTI2PortStatePoint2Point OBJECT-TYPE
   SYNTAX      DisplayString
   MAX-ACCESS  read-only
   STATUS      current
   DESCRIPTION
       "The current STP port point-to-point flag."
   ::= { gs2326pplusMSTI2PortStateEntry 8 }

gs2326pplusMSTI2PortStateUptime OBJECT-TYPE
   SYNTAX      DisplayString
   MAX-ACCESS  read-only
   STATUS      current
   DESCRIPTION
       "The time since the bridge port was last initialized."
   ::= { gs2326pplusMSTI2PortStateEntry 9 }

gs2326pplusMSTI3BridgeSTP                                                        OBJECT IDENTIFIER ::= { gs2326pplusSTPBridgeStatus 4 }

gs2326pplusMSTI3BridgeSTPStatus                                                  OBJECT IDENTIFIER ::= { gs2326pplusMSTI3BridgeSTP 1 }

gs2326pplusMSTI3BridgeInstance OBJECT-TYPE
   SYNTAX       DisplayString
   MAX-ACCESS   read-only
   STATUS       current
   DESCRIPTION
       "The Bridge instance - CIST, MST1, ..."
   ::= { gs2326pplusMSTI3BridgeSTPStatus 1 }

gs2326pplusMSTI3BridgeID OBJECT-TYPE
   SYNTAX       DisplayString
   MAX-ACCESS   read-only
   STATUS       current
   DESCRIPTION
       "The Bridge ID of this Bridge instance."
   ::= { gs2326pplusMSTI3BridgeSTPStatus 2 }

gs2326pplusMSTI3RootID OBJECT-TYPE
   SYNTAX       DisplayString
   MAX-ACCESS   read-only
   STATUS       current
   DESCRIPTION
       "The Bridge ID of the currently elected root bridge."
   ::= { gs2326pplusMSTI3BridgeSTPStatus 3 }

gs2326pplusMSTI3RootPort OBJECT-TYPE
   SYNTAX       DisplayString
   MAX-ACCESS   read-only
   STATUS       current
   DESCRIPTION
       "The switch port currently assigned the root port role."
   ::= { gs2326pplusMSTI3BridgeSTPStatus 4 }

gs2326pplusMSTI3RootCost OBJECT-TYPE
   SYNTAX       Integer32(0..200000000)
   MAX-ACCESS   read-only
   STATUS       current
   DESCRIPTION
       "Root Path Cost."
   ::= { gs2326pplusMSTI3BridgeSTPStatus 5 }

gs2326pplusMSTI3TopologyFlag OBJECT-TYPE
   SYNTAX       DisplayString
   MAX-ACCESS   read-only
   STATUS       current
   DESCRIPTION
       "The current state of the Topology Change Flag of this Bridge instance."
   ::= { gs2326pplusMSTI3BridgeSTPStatus 8 }

gs2326pplusMSTI3TopologyChangeCount OBJECT-TYPE
   SYNTAX       Counter32
   MAX-ACCESS   read-only
   STATUS       current
   DESCRIPTION
       "The number of times where the topology change flag has been set."
   ::= { gs2326pplusMSTI3BridgeSTPStatus 9 }

gs2326pplusMSTI3TopologyChangeLast OBJECT-TYPE
   SYNTAX       DisplayString
   MAX-ACCESS   read-only
   STATUS       current
   DESCRIPTION
       "The time passed since the Topology Flag was last set."
   ::= { gs2326pplusMSTI3BridgeSTPStatus 10 }

gs2326pplusMSTI3PortStateTable OBJECT-TYPE
   SYNTAX      SEQUENCE OF Gs2326pplusMSTI3PortStateEntry
   MAX-ACCESS  not-accessible
   STATUS      current
   DESCRIPTION
       " Show MSTI3 Ports and Aggregations State Configurations. "
   ::= { gs2326pplusMSTI3BridgeSTP 2 }

gs2326pplusMSTI3PortStateEntry OBJECT-TYPE
   SYNTAX      Gs2326pplusMSTI3PortStateEntry
   MAX-ACCESS  not-accessible
   STATUS      current
   DESCRIPTION
       ""
   INDEX    { gs2326pplusMSTI3PortStateIndex  }
   ::= { gs2326pplusMSTI3PortStateTable 1 }

Gs2326pplusMSTI3PortStateEntry ::= SEQUENCE {
   gs2326pplusMSTI3PortStateIndex        Integer32,
   gs2326pplusMSTI3PortStatePort         DisplayString,
   gs2326pplusMSTI3PortStatePortID       DisplayString,
   gs2326pplusMSTI3PortStateRole         DisplayString,
   gs2326pplusMSTI3PortStateState        DisplayString,
   gs2326pplusMSTI3PortStatePathCost     Integer32,
   gs2326pplusMSTI3PortStateEdge         DisplayString,
   gs2326pplusMSTI3PortStatePoint2Point  DisplayString,
   gs2326pplusMSTI3PortStateUptime       DisplayString
}

gs2326pplusMSTI3PortStateIndex OBJECT-TYPE
   SYNTAX      Integer32(1..4095)
   MAX-ACCESS  not-accessible
   STATUS      current
   DESCRIPTION
       "table index."
   ::= { gs2326pplusMSTI3PortStateEntry 1 }

gs2326pplusMSTI3PortStatePort OBJECT-TYPE
   SYNTAX      DisplayString
   MAX-ACCESS  read-only
   STATUS      current
   DESCRIPTION
       "The switch port number of the logical STP port."
   ::= { gs2326pplusMSTI3PortStateEntry 2 }

gs2326pplusMSTI3PortStatePortID OBJECT-TYPE
   SYNTAX      DisplayString
   MAX-ACCESS  read-only
   STATUS      current
   DESCRIPTION
       "The port id as used by the STP protocol.
        This is the priority part and the logical port index of the bridge port."
   ::= { gs2326pplusMSTI3PortStateEntry 3 }

gs2326pplusMSTI3PortStateRole OBJECT-TYPE
   SYNTAX      DisplayString
   MAX-ACCESS  read-only
   STATUS      current
   DESCRIPTION
       "The current STP port role."
   ::= { gs2326pplusMSTI3PortStateEntry 4 }

gs2326pplusMSTI3PortStateState OBJECT-TYPE
   SYNTAX      DisplayString
   MAX-ACCESS  read-only
   STATUS      current
   DESCRIPTION
       "The current STP port state."
   ::= { gs2326pplusMSTI3PortStateEntry 5 }

gs2326pplusMSTI3PortStatePathCost OBJECT-TYPE
   SYNTAX      Integer32(0..200000000)
   MAX-ACCESS  read-only
   STATUS      current
   DESCRIPTION
       "The current STP port path cost."
   ::= { gs2326pplusMSTI3PortStateEntry 6 }

gs2326pplusMSTI3PortStateEdge OBJECT-TYPE
   SYNTAX      DisplayString
   MAX-ACCESS  read-only
   STATUS      current
   DESCRIPTION
       "The current STP port Edge Flag."
   ::= { gs2326pplusMSTI3PortStateEntry 7 }

gs2326pplusMSTI3PortStatePoint2Point OBJECT-TYPE
   SYNTAX      DisplayString
   MAX-ACCESS  read-only
   STATUS      current
   DESCRIPTION
       "The current STP port point-to-point flag."
   ::= { gs2326pplusMSTI3PortStateEntry 8 }

gs2326pplusMSTI3PortStateUptime OBJECT-TYPE
   SYNTAX      DisplayString
   MAX-ACCESS  read-only
   STATUS      current
   DESCRIPTION
       "The time since the bridge port was last initialized."
   ::= { gs2326pplusMSTI3PortStateEntry 9 }

gs2326pplusMSTI4BridgeSTP                                                        OBJECT IDENTIFIER ::= { gs2326pplusSTPBridgeStatus 5 }

gs2326pplusMSTI4BridgeSTPStatus                                                  OBJECT IDENTIFIER ::= { gs2326pplusMSTI4BridgeSTP 1 }

gs2326pplusMSTI4BridgeInstance OBJECT-TYPE
   SYNTAX       DisplayString
   MAX-ACCESS   read-only
   STATUS       current
   DESCRIPTION
       "The Bridge instance - CIST, MST1, ..."
   ::= { gs2326pplusMSTI4BridgeSTPStatus 1 }

gs2326pplusMSTI4BridgeID OBJECT-TYPE
   SYNTAX       DisplayString
   MAX-ACCESS   read-only
   STATUS       current
   DESCRIPTION
       "The Bridge ID of this Bridge instance."
   ::= { gs2326pplusMSTI4BridgeSTPStatus 2 }

gs2326pplusMSTI4RootID OBJECT-TYPE
   SYNTAX       DisplayString
   MAX-ACCESS   read-only
   STATUS       current
   DESCRIPTION
       "The Bridge ID of the currently elected root bridge."
   ::= { gs2326pplusMSTI4BridgeSTPStatus 3 }

gs2326pplusMSTI4RootPort OBJECT-TYPE
   SYNTAX       DisplayString
   MAX-ACCESS   read-only
   STATUS       current
   DESCRIPTION
       "The switch port currently assigned the root port role."
   ::= { gs2326pplusMSTI4BridgeSTPStatus 4 }

gs2326pplusMSTI4RootCost OBJECT-TYPE
   SYNTAX       Integer32(0..200000000)
   MAX-ACCESS   read-only
   STATUS       current
   DESCRIPTION
       "Root Path Cost."
   ::= { gs2326pplusMSTI4BridgeSTPStatus 5 }

gs2326pplusMSTI4TopologyFlag OBJECT-TYPE
   SYNTAX       DisplayString
   MAX-ACCESS   read-only
   STATUS       current
   DESCRIPTION
       "The current state of the Topology Change Flag of this Bridge instance."
   ::= { gs2326pplusMSTI4BridgeSTPStatus 8 }

gs2326pplusMSTI4TopologyChangeCount OBJECT-TYPE
   SYNTAX       Counter32
   MAX-ACCESS   read-only
   STATUS       current
   DESCRIPTION
       "The number of times where the topology change flag has been set."
   ::= { gs2326pplusMSTI4BridgeSTPStatus 9 }

gs2326pplusMSTI4TopologyChangeLast OBJECT-TYPE
   SYNTAX       DisplayString
   MAX-ACCESS   read-only
   STATUS       current
   DESCRIPTION
       "The time passed since the Topology Flag was last set."
   ::= { gs2326pplusMSTI4BridgeSTPStatus 10 }

gs2326pplusMSTI4PortStateTable OBJECT-TYPE
   SYNTAX      SEQUENCE OF Gs2326pplusMSTI4PortStateEntry
   MAX-ACCESS  not-accessible
   STATUS      current
   DESCRIPTION
       " Show MSTI4 Ports and Aggregations State Configurations. "
   ::= { gs2326pplusMSTI4BridgeSTP 2 }

gs2326pplusMSTI4PortStateEntry OBJECT-TYPE
   SYNTAX      Gs2326pplusMSTI4PortStateEntry
   MAX-ACCESS  not-accessible
   STATUS      current
   DESCRIPTION
       ""
   INDEX    { gs2326pplusMSTI4PortStateIndex  }
   ::= { gs2326pplusMSTI4PortStateTable 1 }

Gs2326pplusMSTI4PortStateEntry ::= SEQUENCE {
   gs2326pplusMSTI4PortStateIndex        Integer32,
   gs2326pplusMSTI4PortStatePort         DisplayString,
   gs2326pplusMSTI4PortStatePortID       DisplayString,
   gs2326pplusMSTI4PortStateRole         DisplayString,
   gs2326pplusMSTI4PortStateState        DisplayString,
   gs2326pplusMSTI4PortStatePathCost     Integer32,
   gs2326pplusMSTI4PortStateEdge         DisplayString,
   gs2326pplusMSTI4PortStatePoint2Point  DisplayString,
   gs2326pplusMSTI4PortStateUptime       DisplayString
}

gs2326pplusMSTI4PortStateIndex OBJECT-TYPE
   SYNTAX      Integer32(1..4095)
   MAX-ACCESS  not-accessible
   STATUS      current
   DESCRIPTION
       "table index."
   ::= { gs2326pplusMSTI4PortStateEntry 1 }

gs2326pplusMSTI4PortStatePort OBJECT-TYPE
   SYNTAX      DisplayString
   MAX-ACCESS  read-only
   STATUS      current
   DESCRIPTION
       "The switch port number of the logical STP port."
   ::= { gs2326pplusMSTI4PortStateEntry 2 }

gs2326pplusMSTI4PortStatePortID OBJECT-TYPE
   SYNTAX      DisplayString
   MAX-ACCESS  read-only
   STATUS      current
   DESCRIPTION
       "The port id as used by the STP protocol.
        This is the priority part and the logical port index of the bridge port."
   ::= { gs2326pplusMSTI4PortStateEntry 3 }

gs2326pplusMSTI4PortStateRole OBJECT-TYPE
   SYNTAX      DisplayString
   MAX-ACCESS  read-only
   STATUS      current
   DESCRIPTION
       "The current STP port role."
   ::= { gs2326pplusMSTI4PortStateEntry 4 }

gs2326pplusMSTI4PortStateState OBJECT-TYPE
   SYNTAX      DisplayString
   MAX-ACCESS  read-only
   STATUS      current
   DESCRIPTION
       "The current STP port state."
   ::= { gs2326pplusMSTI4PortStateEntry 5 }

gs2326pplusMSTI4PortStatePathCost OBJECT-TYPE
   SYNTAX      Integer32(0..200000000)
   MAX-ACCESS  read-only
   STATUS      current
   DESCRIPTION
       "The current STP port path cost."
   ::= { gs2326pplusMSTI4PortStateEntry 6 }

gs2326pplusMSTI4PortStateEdge OBJECT-TYPE
   SYNTAX      DisplayString
   MAX-ACCESS  read-only
   STATUS      current
   DESCRIPTION
       "The current STP port Edge Flag."
   ::= { gs2326pplusMSTI4PortStateEntry 7 }

gs2326pplusMSTI4PortStatePoint2Point OBJECT-TYPE
   SYNTAX      DisplayString
   MAX-ACCESS  read-only
   STATUS      current
   DESCRIPTION
       "The current STP port point-to-point flag."
   ::= { gs2326pplusMSTI4PortStateEntry 8 }

gs2326pplusMSTI4PortStateUptime OBJECT-TYPE
   SYNTAX      DisplayString
   MAX-ACCESS  read-only
   STATUS      current
   DESCRIPTION
       "The time since the bridge port was last initialized."
   ::= { gs2326pplusMSTI4PortStateEntry 9 }

gs2326pplusMSTI5BridgeSTP                                                        OBJECT IDENTIFIER ::= { gs2326pplusSTPBridgeStatus 6 }

gs2326pplusMSTI5BridgeSTPStatus                                                  OBJECT IDENTIFIER ::= { gs2326pplusMSTI5BridgeSTP 1 }

gs2326pplusMSTI5BridgeInstance OBJECT-TYPE
   SYNTAX       DisplayString
   MAX-ACCESS   read-only
   STATUS       current
   DESCRIPTION
       "The Bridge instance - CIST, MST1, ..."
   ::= { gs2326pplusMSTI5BridgeSTPStatus 1 }

gs2326pplusMSTI5BridgeID OBJECT-TYPE
   SYNTAX       DisplayString
   MAX-ACCESS   read-only
   STATUS       current
   DESCRIPTION
       "The Bridge ID of this Bridge instance."
   ::= { gs2326pplusMSTI5BridgeSTPStatus 2 }

gs2326pplusMSTI5RootID OBJECT-TYPE
   SYNTAX       DisplayString
   MAX-ACCESS   read-only
   STATUS       current
   DESCRIPTION
       "The Bridge ID of the currently elected root bridge."
   ::= { gs2326pplusMSTI5BridgeSTPStatus 3 }

gs2326pplusMSTI5RootPort OBJECT-TYPE
   SYNTAX       DisplayString
   MAX-ACCESS   read-only
   STATUS       current
   DESCRIPTION
       "The switch port currently assigned the root port role."
   ::= { gs2326pplusMSTI5BridgeSTPStatus 4 }

gs2326pplusMSTI5RootCost OBJECT-TYPE
   SYNTAX       Integer32(0..200000000)
   MAX-ACCESS   read-only
   STATUS       current
   DESCRIPTION
       "Root Path Cost."
   ::= { gs2326pplusMSTI5BridgeSTPStatus 5 }

gs2326pplusMSTI5TopologyFlag OBJECT-TYPE
   SYNTAX       DisplayString
   MAX-ACCESS   read-only
   STATUS       current
   DESCRIPTION
       "The current state of the Topology Change Flag of this Bridge instance."
   ::= { gs2326pplusMSTI5BridgeSTPStatus 8 }

gs2326pplusMSTI5TopologyChangeCount OBJECT-TYPE
   SYNTAX       Counter32
   MAX-ACCESS   read-only
   STATUS       current
   DESCRIPTION
       "The number of times where the topology change flag has been set."
   ::= { gs2326pplusMSTI5BridgeSTPStatus 9 }

gs2326pplusMSTI5TopologyChangeLast OBJECT-TYPE
   SYNTAX       DisplayString
   MAX-ACCESS   read-only
   STATUS       current
   DESCRIPTION
       "The time passed since the Topology Flag was last set."
   ::= { gs2326pplusMSTI5BridgeSTPStatus 10 }

gs2326pplusMSTI5PortStateTable OBJECT-TYPE
   SYNTAX      SEQUENCE OF Gs2326pplusMSTI5PortStateEntry
   MAX-ACCESS  not-accessible
   STATUS      current
   DESCRIPTION
       " Show MSTI5 Ports and Aggregations State Configurations. "
   ::= { gs2326pplusMSTI5BridgeSTP 2 }

gs2326pplusMSTI5PortStateEntry OBJECT-TYPE
   SYNTAX      Gs2326pplusMSTI5PortStateEntry
   MAX-ACCESS  not-accessible
   STATUS      current
   DESCRIPTION
       ""
   INDEX    { gs2326pplusMSTI5PortStateIndex  }
   ::= { gs2326pplusMSTI5PortStateTable 1 }

Gs2326pplusMSTI5PortStateEntry ::= SEQUENCE {
   gs2326pplusMSTI5PortStateIndex        Integer32,
   gs2326pplusMSTI5PortStatePort         DisplayString,
   gs2326pplusMSTI5PortStatePortID       DisplayString,
   gs2326pplusMSTI5PortStateRole         DisplayString,
   gs2326pplusMSTI5PortStateState        DisplayString,
   gs2326pplusMSTI5PortStatePathCost     Integer32,
   gs2326pplusMSTI5PortStateEdge         DisplayString,
   gs2326pplusMSTI5PortStatePoint2Point  DisplayString,
   gs2326pplusMSTI5PortStateUptime       DisplayString
}

gs2326pplusMSTI5PortStateIndex OBJECT-TYPE
   SYNTAX      Integer32(1..4095)
   MAX-ACCESS  not-accessible
   STATUS      current
   DESCRIPTION
       "table index."
   ::= { gs2326pplusMSTI5PortStateEntry 1 }

gs2326pplusMSTI5PortStatePort OBJECT-TYPE
   SYNTAX      DisplayString
   MAX-ACCESS  read-only
   STATUS      current
   DESCRIPTION
       "The switch port number of the logical STP port."
   ::= { gs2326pplusMSTI5PortStateEntry 2 }

gs2326pplusMSTI5PortStatePortID OBJECT-TYPE
   SYNTAX      DisplayString
   MAX-ACCESS  read-only
   STATUS      current
   DESCRIPTION
       "The port id as used by the STP protocol.
        This is the priority part and the logical port index of the bridge port."
   ::= { gs2326pplusMSTI5PortStateEntry 3 }

gs2326pplusMSTI5PortStateRole OBJECT-TYPE
   SYNTAX      DisplayString
   MAX-ACCESS  read-only
   STATUS      current
   DESCRIPTION
       "The current STP port role."
   ::= { gs2326pplusMSTI5PortStateEntry 4 }

gs2326pplusMSTI5PortStateState OBJECT-TYPE
   SYNTAX      DisplayString
   MAX-ACCESS  read-only
   STATUS      current
   DESCRIPTION
       "The current STP port state."
   ::= { gs2326pplusMSTI5PortStateEntry 5 }

gs2326pplusMSTI5PortStatePathCost OBJECT-TYPE
   SYNTAX      Integer32(0..200000000)
   MAX-ACCESS  read-only
   STATUS      current
   DESCRIPTION
       "The current STP port path cost."
   ::= { gs2326pplusMSTI5PortStateEntry 6 }

gs2326pplusMSTI5PortStateEdge OBJECT-TYPE
   SYNTAX      DisplayString
   MAX-ACCESS  read-only
   STATUS      current
   DESCRIPTION
       "The current STP port Edge Flag."
   ::= { gs2326pplusMSTI5PortStateEntry 7 }

gs2326pplusMSTI5PortStatePoint2Point OBJECT-TYPE
   SYNTAX      DisplayString
   MAX-ACCESS  read-only
   STATUS      current
   DESCRIPTION
       "The current STP port point-to-point flag."
   ::= { gs2326pplusMSTI5PortStateEntry 8 }

gs2326pplusMSTI5PortStateUptime OBJECT-TYPE
   SYNTAX      DisplayString
   MAX-ACCESS  read-only
   STATUS      current
   DESCRIPTION
       "The time since the bridge port was last initialized."
   ::= { gs2326pplusMSTI5PortStateEntry 9 }

gs2326pplusMSTI6BridgeSTP                                                        OBJECT IDENTIFIER ::= { gs2326pplusSTPBridgeStatus 7 }

gs2326pplusMSTI6BridgeSTPStatus                                                  OBJECT IDENTIFIER ::= { gs2326pplusMSTI6BridgeSTP 1 }

gs2326pplusMSTI6BridgeInstance OBJECT-TYPE
   SYNTAX       DisplayString
   MAX-ACCESS   read-only
   STATUS       current
   DESCRIPTION
       "The Bridge instance - CIST, MST1, ..."
   ::= { gs2326pplusMSTI6BridgeSTPStatus 1 }

gs2326pplusMSTI6BridgeID OBJECT-TYPE
   SYNTAX       DisplayString
   MAX-ACCESS   read-only
   STATUS       current
   DESCRIPTION
       "The Bridge ID of this Bridge instance."
   ::= { gs2326pplusMSTI6BridgeSTPStatus 2 }

gs2326pplusMSTI6RootID OBJECT-TYPE
   SYNTAX       DisplayString
   MAX-ACCESS   read-only
   STATUS       current
   DESCRIPTION
       "The Bridge ID of the currently elected root bridge."
   ::= { gs2326pplusMSTI6BridgeSTPStatus 3 }

gs2326pplusMSTI6RootPort OBJECT-TYPE
   SYNTAX       DisplayString
   MAX-ACCESS   read-only
   STATUS       current
   DESCRIPTION
       "The switch port currently assigned the root port role."
   ::= { gs2326pplusMSTI6BridgeSTPStatus 4 }

gs2326pplusMSTI6RootCost OBJECT-TYPE
   SYNTAX       Integer32(0..200000000)
   MAX-ACCESS   read-only
   STATUS       current
   DESCRIPTION
       "Root Path Cost."
   ::= { gs2326pplusMSTI6BridgeSTPStatus 5 }

gs2326pplusMSTI6TopologyFlag OBJECT-TYPE
   SYNTAX       DisplayString
   MAX-ACCESS   read-only
   STATUS       current
   DESCRIPTION
       "The current state of the Topology Change Flag of this Bridge instance."
   ::= { gs2326pplusMSTI6BridgeSTPStatus 8 }

gs2326pplusMSTI6TopologyChangeCount OBJECT-TYPE
   SYNTAX       Counter32
   MAX-ACCESS   read-only
   STATUS       current
   DESCRIPTION
       "The number of times where the topology change flag has been set."
   ::= { gs2326pplusMSTI6BridgeSTPStatus 9 }

gs2326pplusMSTI6TopologyChangeLast OBJECT-TYPE
   SYNTAX       DisplayString
   MAX-ACCESS   read-only
   STATUS       current
   DESCRIPTION
       "The time passed since the Topology Flag was last set."
   ::= { gs2326pplusMSTI6BridgeSTPStatus 10 }

gs2326pplusMSTI6PortStateTable OBJECT-TYPE
   SYNTAX      SEQUENCE OF Gs2326pplusMSTI6PortStateEntry
   MAX-ACCESS  not-accessible
   STATUS      current
   DESCRIPTION
       " Show MSTI6 Ports and Aggregations State Configurations. "
   ::= { gs2326pplusMSTI6BridgeSTP 2 }

gs2326pplusMSTI6PortStateEntry OBJECT-TYPE
   SYNTAX      Gs2326pplusMSTI6PortStateEntry
   MAX-ACCESS  not-accessible
   STATUS      current
   DESCRIPTION
       ""
   INDEX    { gs2326pplusMSTI6PortStateIndex  }
   ::= { gs2326pplusMSTI6PortStateTable 1 }

Gs2326pplusMSTI6PortStateEntry ::= SEQUENCE {
   gs2326pplusMSTI6PortStateIndex        Integer32,
   gs2326pplusMSTI6PortStatePort         DisplayString,
   gs2326pplusMSTI6PortStatePortID       DisplayString,
   gs2326pplusMSTI6PortStateRole         DisplayString,
   gs2326pplusMSTI6PortStateState        DisplayString,
   gs2326pplusMSTI6PortStatePathCost     Integer32,
   gs2326pplusMSTI6PortStateEdge         DisplayString,
   gs2326pplusMSTI6PortStatePoint2Point  DisplayString,
   gs2326pplusMSTI6PortStateUptime       DisplayString
}

gs2326pplusMSTI6PortStateIndex OBJECT-TYPE
   SYNTAX      Integer32(1..4095)
   MAX-ACCESS  not-accessible
   STATUS      current
   DESCRIPTION
       "table index."
   ::= { gs2326pplusMSTI6PortStateEntry 1 }

gs2326pplusMSTI6PortStatePort OBJECT-TYPE
   SYNTAX      DisplayString
   MAX-ACCESS  read-only
   STATUS      current
   DESCRIPTION
       "The switch port number of the logical STP port."
   ::= { gs2326pplusMSTI6PortStateEntry 2 }

gs2326pplusMSTI6PortStatePortID OBJECT-TYPE
   SYNTAX      DisplayString
   MAX-ACCESS  read-only
   STATUS      current
   DESCRIPTION
       "The port id as used by the STP protocol.
        This is the priority part and the logical port index of the bridge port."
   ::= { gs2326pplusMSTI6PortStateEntry 3 }

gs2326pplusMSTI6PortStateRole OBJECT-TYPE
   SYNTAX      DisplayString
   MAX-ACCESS  read-only
   STATUS      current
   DESCRIPTION
       "The current STP port role."
   ::= { gs2326pplusMSTI6PortStateEntry 4 }

gs2326pplusMSTI6PortStateState OBJECT-TYPE
   SYNTAX      DisplayString
   MAX-ACCESS  read-only
   STATUS      current
   DESCRIPTION
       "The current STP port state."
   ::= { gs2326pplusMSTI6PortStateEntry 5 }

gs2326pplusMSTI6PortStatePathCost OBJECT-TYPE
   SYNTAX      Integer32(0..200000000)
   MAX-ACCESS  read-only
   STATUS      current
   DESCRIPTION
       "The current STP port path cost."
   ::= { gs2326pplusMSTI6PortStateEntry 6 }

gs2326pplusMSTI6PortStateEdge OBJECT-TYPE
   SYNTAX      DisplayString
   MAX-ACCESS  read-only
   STATUS      current
   DESCRIPTION
       "The current STP port Edge Flag."
   ::= { gs2326pplusMSTI6PortStateEntry 7 }

gs2326pplusMSTI6PortStatePoint2Point OBJECT-TYPE
   SYNTAX      DisplayString
   MAX-ACCESS  read-only
   STATUS      current
   DESCRIPTION
       "The current STP port point-to-point flag."
   ::= { gs2326pplusMSTI6PortStateEntry 8 }

gs2326pplusMSTI6PortStateUptime OBJECT-TYPE
   SYNTAX      DisplayString
   MAX-ACCESS  read-only
   STATUS      current
   DESCRIPTION
       "The time since the bridge port was last initialized."
   ::= { gs2326pplusMSTI6PortStateEntry 9 }

gs2326pplusMSTI7BridgeSTP                                                        OBJECT IDENTIFIER ::= { gs2326pplusSTPBridgeStatus 8 }

gs2326pplusMSTI7BridgeSTPStatus                                                  OBJECT IDENTIFIER ::= { gs2326pplusMSTI7BridgeSTP 1 }

gs2326pplusMSTI7BridgeInstance OBJECT-TYPE
   SYNTAX       DisplayString
   MAX-ACCESS   read-only
   STATUS       current
   DESCRIPTION
       "The Bridge instance - CIST, MST1, ..."
   ::= { gs2326pplusMSTI7BridgeSTPStatus 1 }

gs2326pplusMSTI7BridgeID OBJECT-TYPE
   SYNTAX       DisplayString
   MAX-ACCESS   read-only
   STATUS       current
   DESCRIPTION
       "The Bridge ID of this Bridge instance."
   ::= { gs2326pplusMSTI7BridgeSTPStatus 2 }

gs2326pplusMSTI7RootID OBJECT-TYPE
   SYNTAX       DisplayString
   MAX-ACCESS   read-only
   STATUS       current
   DESCRIPTION
       "The Bridge ID of the currently elected root bridge."
   ::= { gs2326pplusMSTI7BridgeSTPStatus 3 }

gs2326pplusMSTI7RootPort OBJECT-TYPE
   SYNTAX       DisplayString
   MAX-ACCESS   read-only
   STATUS       current
   DESCRIPTION
       "The switch port currently assigned the root port role."
   ::= { gs2326pplusMSTI7BridgeSTPStatus 4 }

gs2326pplusMSTI7RootCost OBJECT-TYPE
   SYNTAX       Integer32(0..200000000)
   MAX-ACCESS   read-only
   STATUS       current
   DESCRIPTION
       "Root Path Cost."
   ::= { gs2326pplusMSTI7BridgeSTPStatus 5 }

gs2326pplusMSTI7TopologyFlag OBJECT-TYPE
   SYNTAX       DisplayString
   MAX-ACCESS   read-only
   STATUS       current
   DESCRIPTION
       "The current state of the Topology Change Flag of this Bridge instance."
   ::= { gs2326pplusMSTI7BridgeSTPStatus 8 }

gs2326pplusMSTI7TopologyChangeCount OBJECT-TYPE
   SYNTAX       Counter32
   MAX-ACCESS   read-only
   STATUS       current
   DESCRIPTION
       "The number of times where the topology change flag has been set."
   ::= { gs2326pplusMSTI7BridgeSTPStatus 9 }

gs2326pplusMSTI7TopologyChangeLast OBJECT-TYPE
   SYNTAX       DisplayString
   MAX-ACCESS   read-only
   STATUS       current
   DESCRIPTION
       "The time passed since the Topology Flag was last set."
   ::= { gs2326pplusMSTI7BridgeSTPStatus 10 }

gs2326pplusMSTI7PortStateTable OBJECT-TYPE
   SYNTAX      SEQUENCE OF Gs2326pplusMSTI7PortStateEntry
   MAX-ACCESS  not-accessible
   STATUS      current
   DESCRIPTION
       " Show MSTI7 Ports and Aggregations State Configurations. "
   ::= { gs2326pplusMSTI7BridgeSTP 2 }

gs2326pplusMSTI7PortStateEntry OBJECT-TYPE
   SYNTAX      Gs2326pplusMSTI7PortStateEntry
   MAX-ACCESS  not-accessible
   STATUS      current
   DESCRIPTION
       ""
   INDEX    { gs2326pplusMSTI7PortStateIndex  }
   ::= { gs2326pplusMSTI7PortStateTable 1 }

Gs2326pplusMSTI7PortStateEntry ::= SEQUENCE {
   gs2326pplusMSTI7PortStateIndex        Integer32,
   gs2326pplusMSTI7PortStatePort         DisplayString,
   gs2326pplusMSTI7PortStatePortID       DisplayString,
   gs2326pplusMSTI7PortStateRole         DisplayString,
   gs2326pplusMSTI7PortStateState        DisplayString,
   gs2326pplusMSTI7PortStatePathCost     Integer32,
   gs2326pplusMSTI7PortStateEdge         DisplayString,
   gs2326pplusMSTI7PortStatePoint2Point  DisplayString,
   gs2326pplusMSTI7PortStateUptime       DisplayString
}

gs2326pplusMSTI7PortStateIndex OBJECT-TYPE
   SYNTAX      Integer32(1..4095)
   MAX-ACCESS  not-accessible
   STATUS      current
   DESCRIPTION
       "table index."
   ::= { gs2326pplusMSTI7PortStateEntry 1 }

gs2326pplusMSTI7PortStatePort OBJECT-TYPE
   SYNTAX      DisplayString
   MAX-ACCESS  read-only
   STATUS      current
   DESCRIPTION
       "The switch port number of the logical STP port."
   ::= { gs2326pplusMSTI7PortStateEntry 2 }

gs2326pplusMSTI7PortStatePortID OBJECT-TYPE
   SYNTAX      DisplayString
   MAX-ACCESS  read-only
   STATUS      current
   DESCRIPTION
       "The port id as used by the STP protocol.
        This is the priority part and the logical port index of the bridge port."
   ::= { gs2326pplusMSTI7PortStateEntry 3 }

gs2326pplusMSTI7PortStateRole OBJECT-TYPE
   SYNTAX      DisplayString
   MAX-ACCESS  read-only
   STATUS      current
   DESCRIPTION
       "The current STP port role."
   ::= { gs2326pplusMSTI7PortStateEntry 4 }

gs2326pplusMSTI7PortStateState OBJECT-TYPE
   SYNTAX      DisplayString
   MAX-ACCESS  read-only
   STATUS      current
   DESCRIPTION
       "The current STP port state."
   ::= { gs2326pplusMSTI7PortStateEntry 5 }

gs2326pplusMSTI7PortStatePathCost OBJECT-TYPE
   SYNTAX      Integer32(0..200000000)
   MAX-ACCESS  read-only
   STATUS      current
   DESCRIPTION
       "The current STP port path cost."
   ::= { gs2326pplusMSTI7PortStateEntry 6 }

gs2326pplusMSTI7PortStateEdge OBJECT-TYPE
   SYNTAX      DisplayString
   MAX-ACCESS  read-only
   STATUS      current
   DESCRIPTION
       "The current STP port Edge Flag."
   ::= { gs2326pplusMSTI7PortStateEntry 7 }

gs2326pplusMSTI7PortStatePoint2Point OBJECT-TYPE
   SYNTAX      DisplayString
   MAX-ACCESS  read-only
   STATUS      current
   DESCRIPTION
       "The current STP port point-to-point flag."
   ::= { gs2326pplusMSTI7PortStateEntry 8 }

gs2326pplusMSTI7PortStateUptime OBJECT-TYPE
   SYNTAX      DisplayString
   MAX-ACCESS  read-only
   STATUS      current
   DESCRIPTION
       "The time since the bridge port was last initialized."
   ::= { gs2326pplusMSTI7PortStateEntry 9 }

gs2326pplusSTPPortStatusTable OBJECT-TYPE
   SYNTAX      SEQUENCE OF Gs2326pplusSTPPortStatusEntry
   MAX-ACCESS  not-accessible
   STATUS      current
   DESCRIPTION
       " Show STP Port Status."
   ::= { gs2326pplusSTP 9 }

gs2326pplusSTPPortStatusEntry OBJECT-TYPE
   SYNTAX      Gs2326pplusSTPPortStatusEntry
   MAX-ACCESS  not-accessible
   STATUS      current
   DESCRIPTION
       ""
   INDEX    { gs2326pplusSTPPortStatusPort  }
   ::= { gs2326pplusSTPPortStatusTable 1 }

Gs2326pplusSTPPortStatusEntry ::= SEQUENCE {
   gs2326pplusSTPPortStatusPort         Integer32,
   gs2326pplusSTPPortStatusCISTRole     DisplayString,
   gs2326pplusSTPPortStatusCISTState    DisplayString,
   gs2326pplusSTPPortStatusUptime       DisplayString
}

gs2326pplusSTPPortStatusPort OBJECT-TYPE
   SYNTAX      Integer32(1..4095)
   MAX-ACCESS  not-accessible
   STATUS      current
   DESCRIPTION
       " port, range : 1 - port number. "
   ::= { gs2326pplusSTPPortStatusEntry 1 }

gs2326pplusSTPPortStatusCISTRole OBJECT-TYPE
   SYNTAX      DisplayString
   MAX-ACCESS  read-only
   STATUS      current
   DESCRIPTION
       " The current STP port role of the CIST port. "
   ::= { gs2326pplusSTPPortStatusEntry 2 }

gs2326pplusSTPPortStatusCISTState OBJECT-TYPE
   SYNTAX      DisplayString
   MAX-ACCESS  read-only
   STATUS      current
   DESCRIPTION
       " The current STP port state of the CIST port. "
   ::= { gs2326pplusSTPPortStatusEntry 3 }

gs2326pplusSTPPortStatusUptime OBJECT-TYPE
   SYNTAX      DisplayString
   MAX-ACCESS  read-only
   STATUS      current
   DESCRIPTION
       " The time since the bridge port was last initialized. "
   ::= { gs2326pplusSTPPortStatusEntry 4 }

gs2326pplusSTPPortStatisticsTable OBJECT-TYPE
   SYNTAX      SEQUENCE OF Gs2326pplusSTPPortStatisticsEntry
   MAX-ACCESS  not-accessible
   STATUS      current
   DESCRIPTION
       " Show STP Port Statistics."
   ::= { gs2326pplusSTP 10 }

gs2326pplusSTPPortStatisticsEntry OBJECT-TYPE
   SYNTAX      Gs2326pplusSTPPortStatisticsEntry
   MAX-ACCESS  not-accessible
   STATUS      current
   DESCRIPTION
       ""
   INDEX    { gs2326pplusSTPStatisticsIndex  }
   ::= { gs2326pplusSTPPortStatisticsTable 1 }

Gs2326pplusSTPPortStatisticsEntry ::= SEQUENCE {
   gs2326pplusSTPStatisticsIndex            Integer32,
   gs2326pplusSTPStatisticsPort             DisplayString,
   gs2326pplusSTPStatisticsTxMSTP           Counter32,
   gs2326pplusSTPStatisticsTxRSTP           Counter32,
   gs2326pplusSTPStatisticsTxSTP            Counter32,
   gs2326pplusSTPStatisticsTxTCN            Counter32,
   gs2326pplusSTPStatisticsRxMSTP           Counter32,
   gs2326pplusSTPStatisticsRxRSTP           Counter32,
   gs2326pplusSTPStatisticsRxSTP            Counter32,
   gs2326pplusSTPStatisticsRxTCN            Counter32,
   gs2326pplusSTPStatisticsDiscardedUnknown Counter32,
   gs2326pplusSTPStatisticsDiscardedIllegal Counter32
}

gs2326pplusSTPStatisticsIndex OBJECT-TYPE
   SYNTAX      Integer32(1..4095)
   MAX-ACCESS  not-accessible
   STATUS      current
   DESCRIPTION
       "table index."
   ::= { gs2326pplusSTPPortStatisticsEntry 1 }

gs2326pplusSTPStatisticsPort OBJECT-TYPE
   SYNTAX      DisplayString
   MAX-ACCESS  not-accessible
   STATUS      current
   DESCRIPTION
       " port, range : 1 - port number. "
   ::= { gs2326pplusSTPPortStatisticsEntry 2 }

gs2326pplusSTPStatisticsTxMSTP OBJECT-TYPE
   SYNTAX      Counter32
   MAX-ACCESS  read-only
   STATUS      current
   DESCRIPTION
       " The number of MSTP Configuration BPDU's received/transmitted on the port."
   ::= { gs2326pplusSTPPortStatisticsEntry 3 }

gs2326pplusSTPStatisticsTxRSTP OBJECT-TYPE
   SYNTAX      Counter32
   MAX-ACCESS  read-only
   STATUS      current
   DESCRIPTION
       " The number of RSTP Configuration BPDU's received/transmitted on the port. "
   ::= { gs2326pplusSTPPortStatisticsEntry 4 }

gs2326pplusSTPStatisticsTxSTP OBJECT-TYPE
   SYNTAX      Counter32
   MAX-ACCESS  read-only
   STATUS      current
   DESCRIPTION
       " The number of legacy STP Configuration BPDU's received/transmitted on the port. "
   ::= { gs2326pplusSTPPortStatisticsEntry 5 }

gs2326pplusSTPStatisticsTxTCN OBJECT-TYPE
   SYNTAX      Counter32
   MAX-ACCESS  read-only
   STATUS      current
   DESCRIPTION
       " The number of Topology Change Notification BPDU's received/transmitted on the port. "
   ::= { gs2326pplusSTPPortStatisticsEntry 6 }

gs2326pplusSTPStatisticsRxMSTP OBJECT-TYPE
   SYNTAX      Counter32
   MAX-ACCESS  read-only
   STATUS      current
   DESCRIPTION
       " The number of MSTP Configuration BPDU's received/transmitted on the port."
   ::= { gs2326pplusSTPPortStatisticsEntry 7 }

gs2326pplusSTPStatisticsRxRSTP OBJECT-TYPE
   SYNTAX      Counter32
   MAX-ACCESS  read-only
   STATUS      current
   DESCRIPTION
       " The number of RSTP Configuration BPDU's received/transmitted on the port. "
   ::= { gs2326pplusSTPPortStatisticsEntry 8 }

gs2326pplusSTPStatisticsRxSTP OBJECT-TYPE
   SYNTAX      Counter32
   MAX-ACCESS  read-only
   STATUS      current
   DESCRIPTION
       " The number of legacy STP Configuration BPDU's received/transmitted on the port. "
   ::= { gs2326pplusSTPPortStatisticsEntry 9 }

gs2326pplusSTPStatisticsRxTCN OBJECT-TYPE
   SYNTAX      Counter32
   MAX-ACCESS  read-only
   STATUS      current
   DESCRIPTION
       " The number of Topology Change Notification BPDU's received/transmitted on the port. "
   ::= { gs2326pplusSTPPortStatisticsEntry 10 }

gs2326pplusSTPStatisticsDiscardedUnknown OBJECT-TYPE
   SYNTAX      Counter32
   MAX-ACCESS  read-only
   STATUS      current
   DESCRIPTION
       " The number of unknown Spanning Tree BPDU's received and discarded on the port. "
   ::= { gs2326pplusSTPPortStatisticsEntry 11 }

gs2326pplusSTPStatisticsDiscardedIllegal OBJECT-TYPE
   SYNTAX      Counter32
   MAX-ACCESS  read-only
   STATUS      current
   DESCRIPTION
       " The number of illegal Spanning Tree BPDU's received and discarded on the port. "
   ::= { gs2326pplusSTPPortStatisticsEntry 12 }


gs2326pplusFilteringDataBase                                                  OBJECT IDENTIFIER ::= { gs2326pplusConfiguration 21 }

gs2326pplusFilteringDataBaseConfig                                            OBJECT IDENTIFIER ::= { gs2326pplusFilteringDataBase 1 }

gs2326pplusFilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2326pplusFilteringDataBaseConfig 1 }

gs2326pplusFilteringDataBaseConfigTable OBJECT-TYPE
   SYNTAX      SEQUENCE OF GS2326PPLUSFilteringDataBaseConfigEntry
   MAX-ACCESS  not-accessible
   STATUS      current
   DESCRIPTION
       " "
   ::= { gs2326pplusFilteringDataBaseConfig 2 }

gs2326pplusFilteringDataBaseConfigEntry OBJECT-TYPE
   SYNTAX      GS2326PPLUSFilteringDataBaseConfigEntry
   MAX-ACCESS  not-accessible
   STATUS      current
   DESCRIPTION
       ""
   INDEX    { gs2326pplusFilteringDataBaseConfigPort  }
   ::= { gs2326pplusFilteringDataBaseConfigTable 1 }

GS2326PPLUSFilteringDataBaseConfigEntry ::= SEQUENCE {
   gs2326pplusFilteringDataBaseConfigPort        Integer32,
   gs2326pplusFilteringDataBaseConfigLearning    INTEGER
}

gs2326pplusFilteringDataBaseConfigPort OBJECT-TYPE
   SYNTAX      Integer32(1..4095)
   MAX-ACCESS  not-accessible
   STATUS      current
   DESCRIPTION
       " "
   ::= { gs2326pplusFilteringDataBaseConfigEntry 1 }

gs2326pplusFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2326pplusFilteringDataBaseConfigEntry 2 }


gs2326pplusFilteringDataBaseStaticMAC                                OBJECT IDENTIFIER ::= { gs2326pplusFilteringDataBaseConfig 3 }

gs2326pplusFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2326pplusFilteringDataBaseStaticMAC 1 }

gs2326pplusFilteringDataBaseStaticMACTable OBJECT-TYPE
   SYNTAX      SEQUENCE OF GS2326PPLUSFilteringDataBaseStaticMACEntry
   MAX-ACCESS  not-accessible
   STATUS      current
   DESCRIPTION
       " "
   ::= { gs2326pplusFilteringDataBaseStaticMAC 2 }

gs2326pplusFilteringDataBaseStaticMACEntry OBJECT-TYPE
   SYNTAX      GS2326PPLUSFilteringDataBaseStaticMACEntry
   MAX-ACCESS  not-accessible
   STATUS      current
   DESCRIPTION
       ""
   INDEX    { gs2326pplusFilteringDataBaseStaticMACIndex  }
   ::= { gs2326pplusFilteringDataBaseStaticMACTable 1 }

GS2326PPLUSFilteringDataBaseStaticMACEntry ::= SEQUENCE {
   gs2326pplusFilteringDataBaseStaticMACIndex	    Integer32,
   gs2326pplusFilteringDataBaseStaticMACVLANId	    Integer32,
   gs2326pplusFilteringDataBaseStaticMACAddress      MacAddress,
   gs2326pplusFilteringDataBaseStaticMACPortMembers  DisplayString,
   gs2326pplusFilteringDataBaseStaticMACRowStatus	INTEGER
}

gs2326pplusFilteringDataBaseStaticMACIndex OBJECT-TYPE
   SYNTAX      Integer32(1..4095)
   MAX-ACCESS  not-accessible
   STATUS      current
   DESCRIPTION
       " "
   ::= { gs2326pplusFilteringDataBaseStaticMACEntry 1 }

gs2326pplusFilteringDataBaseStaticMACVLANId OBJECT-TYPE
   SYNTAX      Integer32(1..4094)
   MAX-ACCESS  read-write
   STATUS      current
   DESCRIPTION
       " VLAN ID, range: 1 - 4094. "
   ::= { gs2326pplusFilteringDataBaseStaticMACEntry 2 }

gs2326pplusFilteringDataBaseStaticMACAddress OBJECT-TYPE
   SYNTAX      MacAddress
   MAX-ACCESS  read-write
   STATUS      current
   DESCRIPTION
       " MAC address, format 0a 1b 2c 3d 4e 5f "
   ::= { gs2326pplusFilteringDataBaseStaticMACEntry 3 }

gs2326pplusFilteringDataBaseStaticMACPortMembers OBJECT-TYPE
   SYNTAX      DisplayString
   MAX-ACCESS  read-write
   STATUS      current
   DESCRIPTION
       "To include the ports in a Static MAC Table"
   ::= { gs2326pplusFilteringDataBaseStaticMACEntry 4 }

gs2326pplusFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusFilteringDataBaseStaticMACEntry 5 }


gs2326pplusFilteringDataBaseDynamicMACTable OBJECT-TYPE
   SYNTAX      SEQUENCE OF GS2326PPLUSFilteringDataBaseDynamicMACEntry
   MAX-ACCESS  not-accessible
   STATUS      current
   DESCRIPTION
       " "
   ::= { gs2326pplusFilteringDataBaseConfig 4 }

gs2326pplusFilteringDataBaseDynamicMACEntry OBJECT-TYPE
   SYNTAX      GS2326PPLUSFilteringDataBaseDynamicMACEntry
   MAX-ACCESS  not-accessible
   STATUS      current
   DESCRIPTION
       ""
   INDEX    { gs2326pplusFilteringDataBaseDynamicMACIndex  }
   ::= { gs2326pplusFilteringDataBaseDynamicMACTable 1 }

GS2326PPLUSFilteringDataBaseDynamicMACEntry ::= SEQUENCE {
   gs2326pplusFilteringDataBaseDynamicMACIndex	    Integer32,
   gs2326pplusFilteringDataBaseDynamicMACType	    INTEGER,
   gs2326pplusFilteringDataBaseDynamicMACVLAN	    Integer32,
   gs2326pplusFilteringDataBaseDynamicMACAddress     MacAddress,
   gs2326pplusFilteringDataBaseDynamicPortMembers    DisplayString
}

gs2326pplusFilteringDataBaseDynamicMACIndex OBJECT-TYPE
   SYNTAX      Integer32(1..4095)
   MAX-ACCESS  not-accessible
   STATUS      current
   DESCRIPTION
       " "
   ::= { gs2326pplusFilteringDataBaseDynamicMACEntry 1 }

gs2326pplusFilteringDataBaseDynamicMACType OBJECT-TYPE
   SYNTAX      INTEGER { dynamic(0), static(1) }
   MAX-ACCESS  read-only
   STATUS      current
   DESCRIPTION
       "Indicates whether the entry is a static or a dynamic entry."
   ::= { gs2326pplusFilteringDataBaseDynamicMACEntry 2 }

gs2326pplusFilteringDataBaseDynamicMACVLAN OBJECT-TYPE
   SYNTAX      Integer32(1..4094)
   MAX-ACCESS  read-only
   STATUS      current
   DESCRIPTION
       "The VLAN ID of the entry."
   ::= { gs2326pplusFilteringDataBaseDynamicMACEntry 3 }

gs2326pplusFilteringDataBaseDynamicMACAddress OBJECT-TYPE
   SYNTAX      MacAddress
   MAX-ACCESS  read-only
   STATUS      current
   DESCRIPTION
       "The MAC address of the entry."
   ::= { gs2326pplusFilteringDataBaseDynamicMACEntry 4 }

gs2326pplusFilteringDataBaseDynamicPortMembers OBJECT-TYPE
   SYNTAX      DisplayString
   MAX-ACCESS  read-only
   STATUS      current
   DESCRIPTION
       "The ports that are members of the entry."
   ::= { gs2326pplusFilteringDataBaseDynamicMACEntry 5 }


gs2326pplusSFlowAgent                                                  OBJECT IDENTIFIER ::= { gs2326pplusConfiguration 22 }

gs2326pplusSFlowAgentCollector                                            OBJECT IDENTIFIER ::= { gs2326pplusSFlowAgent 1 }

gs2326pplusSFlowAgentReceiverMode OBJECT-TYPE
   SYNTAX      INTEGER { disable(0), enable(1) }
   MAX-ACCESS  read-write
   STATUS      current
   DESCRIPTION
       "default: 0
       0: disable
       1: enable "
   ::= { gs2326pplusSFlowAgentCollector 1 }


gs2326pplusLMC                                                   OBJECT IDENTIFIER ::= { gs2326pplusConfiguration 1500 }

gs2326pplusLMCOperating OBJECT-TYPE
   SYNTAX      INTEGER { disabled(0), enabled(1), try(2) }
   MAX-ACCESS  read-write
   STATUS      current
   DESCRIPTION
       "0: disabled
        1: enabled
        2: try"
   ::= { gs2326pplusLMC 1 }

gs2326pplusLMCConfigViaDhcp OBJECT-TYPE
   SYNTAX      INTEGER { disabled(0), enabled(1) }
   MAX-ACCESS  read-write
   STATUS      current
   DESCRIPTION
       "0: disabled
        1: enabled"
   ::= { gs2326pplusLMC 2 }

gs2326pplusLMCDomain OBJECT-TYPE
   SYNTAX      DisplayString(SIZE(0..255))
   MAX-ACCESS  read-write
   STATUS      current
   DESCRIPTION
       "0: disabled
        1: enabled"
   ::= { gs2326pplusLMC 3 }

gs2326pplusLMCDhcpClientAutoRenew OBJECT-TYPE
   SYNTAX      INTEGER { disabled(0), enabled(1) }
   MAX-ACCESS  read-write
   STATUS      current
   DESCRIPTION
       "0: disabled
        1: enabled"
   ::= { gs2326pplusLMC 4 }


gs2326pplusLMCZeroTouchSupport OBJECT-TYPE
   SYNTAX      INTEGER { No(0), Yes(1) }
   MAX-ACCESS  read-only
   STATUS      current
   DESCRIPTION
       "0: No
        1: Yes"
   ::= { gs2326pplusLMC 50 }

gs2326pplusLMCPairingTokenPresent OBJECT-TYPE
   SYNTAX      INTEGER { No(0), Yes(1) }
   MAX-ACCESS  read-only
   STATUS      current
   DESCRIPTION
       "0: No
        1: Yes"
   ::= { gs2326pplusLMC 51 }

gs2326pplusLMCClientStatus OBJECT-TYPE
   SYNTAX      DisplayString
   MAX-ACCESS  read-only
   STATUS      current
   DESCRIPTION
           ""
   ::= { gs2326pplusLMC  52 }


gs2326pplusLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2326pplusLMC  53 }

gs2326pplusLMCControlStatus OBJECT-TYPE
   SYNTAX      INTEGER {Disabled(2), Operating(4)}
   MAX-ACCESS  read-only
   STATUS      current
   DESCRIPTION
           "2: Disabled
            4: Operating"
   ::= { gs2326pplusLMC  54 }

gs2326pplusLMCMonitoringStatus OBJECT-TYPE
   SYNTAX      INTEGER {Disabled(2), Operating(4)}
   MAX-ACCESS  read-only
   STATUS      current
   DESCRIPTION
           "2: Disabled
            4: Operating"
   ::= { gs2326pplusLMC  55 }

gs2326pplusLMCConfigurationSource OBJECT-TYPE
   SYNTAX      DisplayString
   MAX-ACCESS  read-only
   STATUS      current
   DESCRIPTION
           ""
   ::= { gs2326pplusLMC  56 }

gs2326pplusLMCConfigModified OBJECT-TYPE
   SYNTAX      INTEGER { No(0), Yes(1) }
   MAX-ACCESS  read-only
   STATUS      current
   DESCRIPTION
       "0: No
        1: Yes"
   ::= { gs2326pplusLMC 57 }

gs2326pplusLMCDeviceID OBJECT-TYPE
   SYNTAX      DisplayString
   MAX-ACCESS  read-only
   STATUS      current
   DESCRIPTION
           ""
   ::= { gs2326pplusLMC  58 }

gs2326pplusLMCRoundTripTime OBJECT-TYPE
   SYNTAX      INTEGER
   MAX-ACCESS  read-only
   STATUS      current
   DESCRIPTION
           ""
   ::= { gs2326pplusLMC  100 }


----------------------------------------------------------------------------------------------------------------------------
gs2326pplusSecurity                                              OBJECT IDENTIFIER ::= { lancomGS2326Pplus  3 }

gs2326pplusIPSourceGuard                                         OBJECT IDENTIFIER ::= { gs2326pplusSecurity 1 }

gs2326pplusIPSourceGuardConf                                     OBJECT IDENTIFIER ::= { gs2326pplusIPSourceGuard 1 }

gs2326pplusIPSourceGuardMode OBJECT-TYPE
   SYNTAX      INTEGER { disable(0), enable(1) }
   MAX-ACCESS  read-write
   STATUS      current
   DESCRIPTION
       " default:  0
        0: disable
        1: enable"
   ::= { gs2326pplusIPSourceGuardConf 1 }

gs2326pplusIPSourceGuardPortConfigTable OBJECT-TYPE
   SYNTAX      SEQUENCE OF GS2326PPLUSIPSourceGuardPortConfigEntry
   MAX-ACCESS  not-accessible
   STATUS      current
   DESCRIPTION
       " "
   ::= { gs2326pplusIPSourceGuardConf 2 }

gs2326pplusIPSourceGuardPortConfigEntry OBJECT-TYPE
   SYNTAX      GS2326PPLUSIPSourceGuardPortConfigEntry
   MAX-ACCESS  not-accessible
   STATUS      current
   DESCRIPTION
       ""
   INDEX    { gs2326pplusIPSourceGuardPortConfigPort  }
   ::= { gs2326pplusIPSourceGuardPortConfigTable 1 }

GS2326PPLUSIPSourceGuardPortConfigEntry ::= SEQUENCE {
   gs2326pplusIPSourceGuardPortConfigPort               Integer32,
   gs2326pplusIPSourceGuardPortConfigMode               INTEGER,
   gs2326pplusIPSourceGuardPortMaxDynamicClients        Integer32
}

gs2326pplusIPSourceGuardPortConfigPort OBJECT-TYPE
   SYNTAX      Integer32(1..4095)
   MAX-ACCESS  not-accessible
   STATUS      current
   DESCRIPTION
       " "
   ::= { gs2326pplusIPSourceGuardPortConfigEntry 1 }

gs2326pplusIPSourceGuardPortConfigMode OBJECT-TYPE
   SYNTAX      INTEGER { disable(0), enable(1) }
   MAX-ACCESS  read-write
   STATUS      current
   DESCRIPTION
       "default: 0
       0:disable
       1:enable "
   ::= { gs2326pplusIPSourceGuardPortConfigEntry 2 }

gs2326pplusIPSourceGuardPortMaxDynamicClients OBJECT-TYPE
   SYNTAX      Integer32(0..2|99)
   MAX-ACCESS  read-write
   STATUS      current
   DESCRIPTION
       "default: 99
       0~2: Max Dynamic clients
       99:Unlimited "
   ::= { gs2326pplusIPSourceGuardPortConfigEntry 3 }


gs2326pplusIPSourceGuardStatic                                OBJECT IDENTIFIER ::= { gs2326pplusIPSourceGuard 2 }

gs2326pplusIPSourceGuardStaticCreate OBJECT-TYPE
   SYNTAX       INTEGER { none(0), create(1) }
   MAX-ACCESS   read-write
   STATUS       current
   DESCRIPTION
       "default: 0
        0 : None  (read only)
        1 : Create a IP Source Guard"
   ::= { gs2326pplusIPSourceGuardStatic 1 }

gs2326pplusIPSourceGuardStaticTable OBJECT-TYPE
   SYNTAX      SEQUENCE OF GS2326PPLUSIPSourceGuardStaticEntry
   MAX-ACCESS  not-accessible
   STATUS      current
   DESCRIPTION
       " "
   ::= { gs2326pplusIPSourceGuardStatic 2 }

gs2326pplusIPSourceGuardStaticEntry OBJECT-TYPE
   SYNTAX      GS2326PPLUSIPSourceGuardStaticEntry
   MAX-ACCESS  not-accessible
   STATUS      current
   DESCRIPTION
       ""
   INDEX    { gs2326pplusIPSourceGuardStaticIndex  }
   ::= { gs2326pplusIPSourceGuardStaticTable 1 }

GS2326PPLUSIPSourceGuardStaticEntry ::= SEQUENCE {
   gs2326pplusIPSourceGuardStaticIndex         Integer32,
   gs2326pplusIPSourceGuardStaticPort          Integer32,
   gs2326pplusIPSourceGuardStaticVLANId        Integer32,
   gs2326pplusIPSourceGuardStaticIPAddress     IpAddress,
   gs2326pplusIPSourceGuardStaticMACAddress    MacAddress,
   gs2326pplusIPSourceGuardStaticRowStatus     INTEGER
}

gs2326pplusIPSourceGuardStaticIndex OBJECT-TYPE
   SYNTAX      Integer32(1..28)
   MAX-ACCESS  not-accessible
   STATUS      current
   DESCRIPTION
       " "
   ::= { gs2326pplusIPSourceGuardStaticEntry 1 }

gs2326pplusIPSourceGuardStaticPort OBJECT-TYPE
   SYNTAX      Integer32(1..4095)
   MAX-ACCESS  read-write
   STATUS      current
   DESCRIPTION
       " Port, range: 1 - port number. "
   ::= { gs2326pplusIPSourceGuardStaticEntry 2 }

gs2326pplusIPSourceGuardStaticVLANId OBJECT-TYPE
   SYNTAX      Integer32(1..4094)
   MAX-ACCESS  read-write
   STATUS      current
   DESCRIPTION
       " VLAN ID, range: 1 - 4094. "
   ::= { gs2326pplusIPSourceGuardStaticEntry 3 }

gs2326pplusIPSourceGuardStaticIPAddress OBJECT-TYPE
   SYNTAX      IpAddress
   MAX-ACCESS  read-write
   STATUS      current
   DESCRIPTION
       " IP address allowed for doing IP source guard. "
   ::= { gs2326pplusIPSourceGuardStaticEntry 4 }

gs2326pplusIPSourceGuardStaticMACAddress OBJECT-TYPE
   SYNTAX      MacAddress
   MAX-ACCESS  read-write
   STATUS      current
   DESCRIPTION
       " Allowed Source MAC address, format 0a 1b 2c 3d 4e 5f "
   ::= { gs2326pplusIPSourceGuardStaticEntry 5 }

gs2326pplusIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326pplusIPSourceGuardStaticEntry 6 }

gs2326pplusIPSourceGuardDynamicTable OBJECT-TYPE
   SYNTAX      SEQUENCE OF GS2326PPLUSIPSourceGuardDynamicEntry
   MAX-ACCESS  not-accessible
   STATUS      current
   DESCRIPTION
       " "
   ::= { gs2326pplusIPSourceGuard 3 }

gs2326pplusIPSourceGuardDynamicEntry OBJECT-TYPE
   SYNTAX      GS2326PPLUSIPSourceGuardDynamicEntry
   MAX-ACCESS  not-accessible
   STATUS      current
   DESCRIPTION
       ""
   INDEX    { gs2326pplusIPSourceGuardDynamicIndex  }
   ::= { gs2326pplusIPSourceGuardDynamicTable 1 }

GS2326PPLUSIPSourceGuardDynamicEntry ::= SEQUENCE {
   gs2326pplusIPSourceGuardDynamicIndex          Integer32,
   gs2326pplusIPSourceGuardDynamicPort           Integer32,
   gs2326pplusIPSourceGuardDynamicVLANId         Integer32,
   gs2326pplusIPSourceGuardDynamicIPAddress      IpAddress,
   gs2326pplusIPSourceGuardDynamicMACAddress     MacAddress
}

gs2326pplusIPSourceGuardDynamicIndex OBJECT-TYPE
   SYNTAX      Integer32(1..4095)
   MAX-ACCESS  not-accessible
   STATUS      current
   DESCRIPTION
       " "
   ::= { gs2326pplusIPSourceGuardDynamicEntry 1 }

gs2326pplusIPSourceGuardDynamicPort OBJECT-TYPE
   SYNTAX      Integer32(1..10)
   MAX-ACCESS  read-only
   STATUS      current
   DESCRIPTION
       " "
   ::= { gs2326pplusIPSourceGuardDynamicEntry 2 }

gs2326pplusIPSourceGuardDynamicVLANId OBJECT-TYPE
   SYNTAX      Integer32(1..4094)
   MAX-ACCESS  read-only
   STATUS      current
   DESCRIPTION
       " "
   ::= { gs2326pplusIPSourceGuardDynamicEntry 3 }

gs2326pplusIPSourceGuardDynamicIPAddress OBJECT-TYPE
   SYNTAX      IpAddress
   MAX-ACCESS  read-only
   STATUS      current
   DESCRIPTION
       " "
   ::= { gs2326pplusIPSourceGuardDynamicEntry 4 }

gs2326pplusIPSourceGuardDynamicMACAddress OBJECT-TYPE
   SYNTAX      MacAddress
   MAX-ACCESS  read-only
   STATUS      current
   DESCRIPTION
       " "
   ::= { gs2326pplusIPSourceGuardDynamicEntry 5 }

gs2326pplusARPInspection                                         OBJECT IDENTIFIER ::= { gs2326pplusSecurity 2 }

gs2326pplusARPInspectionConf                                     OBJECT IDENTIFIER ::= { gs2326pplusARPInspection 1 }

gs2326pplusARPInspectionConfMode OBJECT-TYPE
   SYNTAX      INTEGER { disable(0), enable(1) }
   MAX-ACCESS  read-write
   STATUS      current
   DESCRIPTION
       "default: 0
        0: disable
        1: enable"
   ::= { gs2326pplusARPInspectionConf 1 }

gs2326pplusARPInspectionConfTable OBJECT-TYPE
   SYNTAX      SEQUENCE OF GS2326PPLUSARPInspectionConfEntry
   MAX-ACCESS  not-accessible
   STATUS      current
   DESCRIPTION
       " "
   ::= { gs2326pplusARPInspectionConf 2 }

gs2326pplusARPInspectionConfEntry OBJECT-TYPE
   SYNTAX      GS2326PPLUSARPInspectionConfEntry
   MAX-ACCESS  not-accessible
   STATUS      current
   DESCRIPTION
       ""
   INDEX    { gs2326pplusARPInspectionConfPortIndex  }
   ::= { gs2326pplusARPInspectionConfTable 1 }

GS2326PPLUSARPInspectionConfEntry ::= SEQUENCE {
   gs2326pplusARPInspectionConfPortIndex	Integer32,
   gs2326pplusARPInspectionConfPortMode	INTEGER
}

gs2326pplusARPInspectionConfPortIndex OBJECT-TYPE
   SYNTAX      Integer32(1..4095)
   MAX-ACCESS  not-accessible
   STATUS      current
   DESCRIPTION
       " "
   ::= { gs2326pplusARPInspectionConfEntry 1 }

gs2326pplusARPInspectionConfPortMode OBJECT-TYPE
   SYNTAX      INTEGER { disable(0), enable(1) }
   MAX-ACCESS  read-write
   STATUS      current
   DESCRIPTION
       "default: 0
        0: disable
        1: enable"
   ::= { gs2326pplusARPInspectionConfEntry 2 }


gs2326pplusARPInspectionStatic                                OBJECT IDENTIFIER ::= { gs2326pplusARPInspection 2 }

gs2326pplusARPInspectionStaticCreate OBJECT-TYPE
   SYNTAX      INTEGER { none(0), create(1) }
   MAX-ACCESS  read-write
   STATUS      current
   DESCRIPTION
       "default: 0
        0: none
        1: create"
   ::= { gs2326pplusARPInspectionStatic 1 }

gs2326pplusARPInspectionStaticTable OBJECT-TYPE
   SYNTAX      SEQUENCE OF GS2326PPLUSARPInspectionStaticEntry
   MAX-ACCESS  not-accessible
   STATUS      current
   DESCRIPTION
       " "
   ::= { gs2326pplusARPInspectionStatic 2 }

gs2326pplusARPInspectionStaticEntry OBJECT-TYPE
   SYNTAX      GS2326PPLUSARPInspectionStaticEntry
   MAX-ACCESS  not-accessible
   STATUS      current
   DESCRIPTION
       ""
   INDEX    { gs2326pplusARPInspectionStaticIndex  }
   ::= { gs2326pplusARPInspectionStaticTable 1 }

GS2326PPLUSARPInspectionStaticEntry ::= SEQUENCE {
   gs2326pplusARPInspectionStaticIndex       Integer32,
   gs2326pplusARPInspectionStaticPort        Integer32,
   gs2326pplusARPInspectionStaticVLANId      Integer32,
   gs2326pplusARPInspectionStaticIPAddress   IpAddress,
   gs2326pplusARPInspectionStaticMACAddress  MacAddress,
   gs2326pplusARPInspectionStaticRowStatus   INTEGER
}

gs2326pplusARPInspectionStaticIndex OBJECT-TYPE
   SYNTAX      Integer32(1..4095)
   MAX-ACCESS  not-accessible
   STATUS      current
   DESCRIPTION
       ""
   ::= { gs2326pplusARPInspectionStaticEntry 1 }

gs2326pplusARPInspectionStaticPort OBJECT-TYPE
   SYNTAX      Integer32(1..4095)
   MAX-ACCESS  read-write
   STATUS      current
   DESCRIPTION
       " Port, range: 1 - port number. "
   ::= { gs2326pplusARPInspectionStaticEntry 2 }

gs2326pplusARPInspectionStaticVLANId OBJECT-TYPE
   SYNTAX      Integer32(1..4094)
   MAX-ACCESS  read-write
   STATUS      current
   DESCRIPTION
       " VLAN ID, range: 1 - 4094. "
   ::= { gs2326pplusARPInspectionStaticEntry 3 }

gs2326pplusARPInspectionStaticIPAddress OBJECT-TYPE
   SYNTAX      IpAddress
   MAX-ACCESS  read-write
   STATUS      current
   DESCRIPTION
       " IP address allowed for doing ARP request. "
   ::= { gs2326pplusARPInspectionStaticEntry 4 }

gs2326pplusARPInspectionStaticMACAddress OBJECT-TYPE
   SYNTAX      MacAddress
   MAX-ACCESS  read-write
   STATUS      current
   DESCRIPTION
       " Allowed Source MAC address in ARP request packets, format 0a 1b 2c 3d 4e 5f "
   ::= { gs2326pplusARPInspectionStaticEntry 5 }

gs2326pplusARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2326pplusARPInspectionStaticEntry 6 }

gs2326pplusARPInspectionDynamicTable OBJECT-TYPE
   SYNTAX      SEQUENCE OF GS2326PPLUSARPInspectionDynamicEntry
   MAX-ACCESS  not-accessible
   STATUS      current
   DESCRIPTION
       " "
   ::= { gs2326pplusARPInspection 3 }

gs2326pplusARPInspectionDynamicEntry OBJECT-TYPE
   SYNTAX      GS2326PPLUSARPInspectionDynamicEntry
   MAX-ACCESS  not-accessible
   STATUS      current
   DESCRIPTION
       ""
   INDEX    { gs2326pplusARPInspectionDynamicIndex  }
   ::= { gs2326pplusARPInspectionDynamicTable 1 }

GS2326PPLUSARPInspectionDynamicEntry ::= SEQUENCE {
   gs2326pplusARPInspectionDynamicIndex          Integer32,
   gs2326pplusARPInspectionDynamicPort           Integer32,
   gs2326pplusARPInspectionDynamicVLANId         Integer32,
   gs2326pplusARPInspectionDynamicIPAddress      IpAddress,
   gs2326pplusARPInspectionDynamicMACAddress     MacAddress
}

gs2326pplusARPInspectionDynamicIndex OBJECT-TYPE
   SYNTAX      Integer32(1..4095)
   MAX-ACCESS  not-accessible
   STATUS      current
   DESCRIPTION
       " "
   ::= { gs2326pplusARPInspectionDynamicEntry 1 }

gs2326pplusARPInspectionDynamicPort OBJECT-TYPE
   SYNTAX      Integer32(1..4095)
   MAX-ACCESS  read-only
   STATUS      current
   DESCRIPTION
       ""
   ::= { gs2326pplusARPInspectionDynamicEntry 2 }

gs2326pplusARPInspectionDynamicVLANId OBJECT-TYPE
   SYNTAX      Integer32(1..4094)
   MAX-ACCESS  read-only
   STATUS      current
   DESCRIPTION
       ""
   ::= { gs2326pplusARPInspectionDynamicEntry 3 }

gs2326pplusARPInspectionDynamicIPAddress OBJECT-TYPE
   SYNTAX      IpAddress
   MAX-ACCESS  read-only
   STATUS      current
   DESCRIPTION
       ""
   ::= { gs2326pplusARPInspectionDynamicEntry 4 }

gs2326pplusARPInspectionDynamicMACAddress OBJECT-TYPE
   SYNTAX      MacAddress
   MAX-ACCESS  read-only
   STATUS      current
   DESCRIPTION
       ""
   ::= { gs2326pplusARPInspectionDynamicEntry 5 }

gs2326pplusARPStaticGatewayCtrl	                                OBJECT IDENTIFIER ::= { gs2326pplusARPInspection 6 }

gs2326pplusARPStaticGatewayCtrlSystemConf                                      OBJECT IDENTIFIER ::= { gs2326pplusARPStaticGatewayCtrl 1 }

gs2326pplusARPStaticGatewayCtrlMode OBJECT-TYPE
   SYNTAX      INTEGER { disable(0), enable(1) }
   MAX-ACCESS  read-write
   STATUS      current
   DESCRIPTION
       "default: 0
       0: disable
       1: enable "
   ::= { gs2326pplusARPStaticGatewayCtrlSystemConf 1 }

gs2326pplusARPStaticGatewayCtrlCreate OBJECT-TYPE
   SYNTAX      INTEGER { none(0), create(1) }
   MAX-ACCESS  read-write
   STATUS      current
   DESCRIPTION
       "default: 0
        0: none
        1: create"
   ::= { gs2326pplusARPStaticGatewayCtrl 2 }

gs2326pplusARPStaticGatewayCtrlTable OBJECT-TYPE
   SYNTAX      SEQUENCE OF GS2326PPLUSARPStaticGatewayCtrlEntry
   MAX-ACCESS  not-accessible
   STATUS      current
   DESCRIPTION
       " "
   ::= { gs2326pplusARPStaticGatewayCtrl 3 }

gs2326pplusARPStaticGatewayCtrlEntry OBJECT-TYPE
   SYNTAX      GS2326PPLUSARPStaticGatewayCtrlEntry
   MAX-ACCESS  not-accessible
   STATUS      current
   DESCRIPTION
       ""
   INDEX    { gs2326pplusARPStaticGatewayCtrlIndex  }
   ::= { gs2326pplusARPStaticGatewayCtrlTable 1 }

GS2326PPLUSARPStaticGatewayCtrlEntry ::= SEQUENCE {
   gs2326pplusARPStaticGatewayCtrlIndex       Integer32,
   gs2326pplusARPStaticGatewayCtrlIPAddress   IpAddress,
   gs2326pplusARPStaticGatewayCtrlMACAddress  MacAddress,
   gs2326pplusARPStaticGatewayCtrlPort        Integer32,
   gs2326pplusARPStaticGatewayCtrlAction      INTEGER,
   gs2326pplusARPStaticGatewayCtrlState       DisplayString,
   gs2326pplusARPStaticGatewayCtrlReOpen      INTEGER,
   gs2326pplusARPStaticGatewayCtrlRowStatus   INTEGER
}

gs2326pplusARPStaticGatewayCtrlIndex OBJECT-TYPE
   SYNTAX      Integer32(1..4)
   MAX-ACCESS  not-accessible
   STATUS      current
   DESCRIPTION
       ""
   ::= { gs2326pplusARPStaticGatewayCtrlEntry 1 }

gs2326pplusARPStaticGatewayCtrlIPAddress OBJECT-TYPE
   SYNTAX      IpAddress
   MAX-ACCESS  read-write
   STATUS      current
   DESCRIPTION
       " Source IP address. "
   ::= { gs2326pplusARPStaticGatewayCtrlEntry 2 }

gs2326pplusARPStaticGatewayCtrlMACAddress OBJECT-TYPE
   SYNTAX      MacAddress
   MAX-ACCESS  read-write
   STATUS      current
   DESCRIPTION
       " Source MAC address , format 0a 1b 2c 3d 4e 5f "
   ::= { gs2326pplusARPStaticGatewayCtrlEntry 3 }

gs2326pplusARPStaticGatewayCtrlPort OBJECT-TYPE
   SYNTAX      Integer32(1..4095)
   MAX-ACCESS  read-write
   STATUS      current
   DESCRIPTION
       " Port, range: 1 - port number. "
   ::= { gs2326pplusARPStaticGatewayCtrlEntry 4 }

gs2326pplusARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2326pplusARPStaticGatewayCtrlEntry 5 }

gs2326pplusARPStaticGatewayCtrlState OBJECT-TYPE
   SYNTAX      DisplayString
   MAX-ACCESS  read-only
   STATUS      current
   DESCRIPTION
       ""
   ::= { gs2326pplusARPStaticGatewayCtrlEntry 6 }

gs2326pplusARPStaticGatewayCtrlReOpen OBJECT-TYPE
   SYNTAX      INTEGER { none(0), reopen(1) }
   MAX-ACCESS  read-write
   STATUS      current
   DESCRIPTION
       "default: 0
       0: none
       1: reopen"
   ::= { gs2326pplusARPStaticGatewayCtrlEntry 7 }

gs2326pplusARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326pplusARPStaticGatewayCtrlEntry 8 }

gs2326pplusARPSpoofingPrevention	                                OBJECT IDENTIFIER ::= { gs2326pplusARPInspection 7 }

gs2326pplusARPSpoofingPreventionSystemConf                                      OBJECT IDENTIFIER ::= { gs2326pplusARPSpoofingPrevention 1 }

gs2326pplusARPSpoofingPreventionMode OBJECT-TYPE
   SYNTAX      INTEGER { disable(0), enable(1) }
   MAX-ACCESS  read-write
   STATUS      current
   DESCRIPTION
       "default: 0
       0: disable
       1: enable "
   ::= { gs2326pplusARPSpoofingPreventionSystemConf 1 }

gs2326pplusARPSpoofingPreventionTable OBJECT-TYPE
   SYNTAX      SEQUENCE OF GS2326PPLUSARPSpoofingPreventionEntry
   MAX-ACCESS  not-accessible
   STATUS      current
   DESCRIPTION
       " "
   ::= { gs2326pplusARPSpoofingPrevention 2 }

gs2326pplusARPSpoofingPreventionEntry OBJECT-TYPE
   SYNTAX      GS2326PPLUSARPSpoofingPreventionEntry
   MAX-ACCESS  not-accessible
   STATUS      current
   DESCRIPTION
       ""
   INDEX    { gs2326pplusARPSpoofingPreventionPort  }
   ::= { gs2326pplusARPSpoofingPreventionTable 1 }

GS2326PPLUSARPSpoofingPreventionEntry ::= SEQUENCE {
   gs2326pplusARPSpoofingPreventionPort           Integer32,
   gs2326pplusARPSpoofingPreventionPortMode       INTEGER,
   gs2326pplusARPSpoofingPreventionPortLimit      Integer32,
   gs2326pplusARPSpoofingPreventionPortAction     INTEGER,
   gs2326pplusARPSpoofingPreventionPortState      DisplayString,
   gs2326pplusARPSpoofingPreventionPortReOpen     INTEGER
}

gs2326pplusARPSpoofingPreventionPort OBJECT-TYPE
   SYNTAX      Integer32(1..4095)
   MAX-ACCESS  not-accessible
   STATUS      current
   DESCRIPTION
       " "
   ::= { gs2326pplusARPSpoofingPreventionEntry 1 }

gs2326pplusARPSpoofingPreventionPortMode OBJECT-TYPE
   SYNTAX      INTEGER { disable(0), enable(1) }
   MAX-ACCESS  read-write
   STATUS      current
   DESCRIPTION
       "default: 0
       0: disable
       1: enable"
   ::= { gs2326pplusARPSpoofingPreventionEntry 2 }

gs2326pplusARPSpoofingPreventionPortLimit OBJECT-TYPE
   SYNTAX      Integer32(1..100)
   MAX-ACCESS  read-write
   STATUS      current
   DESCRIPTION
       "default: 1, range: 1-100"
   ::= { gs2326pplusARPSpoofingPreventionEntry 3 }

gs2326pplusARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2326pplusARPSpoofingPreventionEntry 4 }

gs2326pplusARPSpoofingPreventionPortState OBJECT-TYPE
   SYNTAX      DisplayString
   MAX-ACCESS  read-only
   STATUS      current
   DESCRIPTION
       ""
   ::= { gs2326pplusARPSpoofingPreventionEntry 5 }

gs2326pplusARPSpoofingPreventionPortReOpen OBJECT-TYPE
   SYNTAX      INTEGER { none(0), reopen(1) }
   MAX-ACCESS  read-write
   STATUS      current
   DESCRIPTION
       "default: 0
       0: none
       1: reopen"
   ::= { gs2326pplusARPSpoofingPreventionEntry 6 }

gs2326pplusARPIPDoSPrevention	                                OBJECT IDENTIFIER ::= { gs2326pplusARPInspection 8 }

gs2326pplusARPIPDoSPreventionTCPMode OBJECT-TYPE
   SYNTAX      INTEGER { disable(0), enable(1) }
   MAX-ACCESS  read-write
   STATUS      current
   DESCRIPTION
       "default: 0
       0: disable
       1: enable "
   ::= { gs2326pplusARPIPDoSPrevention 1 }

gs2326pplusARPIPDoSPreventionUDPMode OBJECT-TYPE
   SYNTAX      INTEGER { disable(0), enable(1) }
   MAX-ACCESS  read-write
   STATUS      current
   DESCRIPTION
       "default: 0
       0: disable
       1: enable "
   ::= { gs2326pplusARPIPDoSPrevention 2 }

gs2326pplusARPIPDoSPreventionICMPMode OBJECT-TYPE
   SYNTAX      INTEGER { disable(0), enable(1) }
   MAX-ACCESS  read-write
   STATUS      current
   DESCRIPTION
       "default: 0
       0: disable
       1: enable "
   ::= { gs2326pplusARPIPDoSPrevention 3 }

gs2326pplusARPIPDoSPreventionServerPort1 OBJECT-TYPE
   SYNTAX      Integer32(0..4094)
   MAX-ACCESS  read-write
   STATUS      current
   DESCRIPTION
       " Port, range: 0 - port number. 0: none. "
   ::= { gs2326pplusARPIPDoSPrevention 4 }

gs2326pplusARPIPDoSPreventionServerPort2 OBJECT-TYPE
   SYNTAX      Integer32(0..4094)
   MAX-ACCESS  read-write
   STATUS      current
   DESCRIPTION
       " Port, range: 0 - port number. 0: none. "
   ::= { gs2326pplusARPIPDoSPrevention 5 }

gs2326pplusARPIPDoSPreventionServerPort3 OBJECT-TYPE
   SYNTAX      Integer32(0..4094)
   MAX-ACCESS  read-write
   STATUS      current
   DESCRIPTION
       " Port, range: 0 - port number. 0: none. "
   ::= { gs2326pplusARPIPDoSPrevention 6 }

gs2326pplusARPIPDoSPreventionServerPort4 OBJECT-TYPE
   SYNTAX      Integer32(0..4094)
   MAX-ACCESS  read-write
   STATUS      current
   DESCRIPTION
       " Port, range: 0 - port number. 0: none. "
   ::= { gs2326pplusARPIPDoSPrevention 7 }

gs2326pplusDHCPSnooping                                          OBJECT IDENTIFIER ::= { gs2326pplusSecurity 3 }

gs2326pplusDHCPSnoopingConf                                          OBJECT IDENTIFIER ::= { gs2326pplusDHCPSnooping 1 }

gs2326pplusDHCPSnoopingMode OBJECT-TYPE
   SYNTAX      INTEGER { disable(0), enable(1) }
   MAX-ACCESS  read-write
   STATUS      current
   DESCRIPTION
       "default: 0
       0: disable
       1: enable"
   ::= { gs2326pplusDHCPSnoopingConf 1 }

gs2326pplusDHCPSnoopingPortModeConfigurationTable OBJECT-TYPE
   SYNTAX      SEQUENCE OF GS2326PPLUSDHCPSnoopingPortModeConfigurationEntry
   MAX-ACCESS  not-accessible
   STATUS      current
   DESCRIPTION
       " "
   ::= { gs2326pplusDHCPSnoopingConf 2 }

gs2326pplusDHCPSnoopingPortModeConfigurationEntry OBJECT-TYPE
   SYNTAX      GS2326PPLUSDHCPSnoopingPortModeConfigurationEntry
   MAX-ACCESS  not-accessible
   STATUS      current
   DESCRIPTION
       ""
   INDEX    { gs2326pplusDHCPSnoopingPortModeConfigurationPort  }
   ::= { gs2326pplusDHCPSnoopingPortModeConfigurationTable 1 }

GS2326PPLUSDHCPSnoopingPortModeConfigurationEntry ::= SEQUENCE {
   gs2326pplusDHCPSnoopingPortModeConfigurationPort	Integer32,
   gs2326pplusDHCPSnoopingPortModeConfigurationMode	INTEGER
}

gs2326pplusDHCPSnoopingPortModeConfigurationPort OBJECT-TYPE
   SYNTAX      Integer32(1..4095)
   MAX-ACCESS  not-accessible
   STATUS      current
   DESCRIPTION
       " "
   ::= { gs2326pplusDHCPSnoopingPortModeConfigurationEntry 1 }

gs2326pplusDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2326pplusDHCPSnoopingPortModeConfigurationEntry 2 }

gs2326pplusDHCPSnoopingStatisticsTable OBJECT-TYPE
   SYNTAX      SEQUENCE OF GS2326PPLUSDHCPSnoopingStatisticsEntry
   MAX-ACCESS  not-accessible
   STATUS      current
   DESCRIPTION
       " "
   ::= { gs2326pplusDHCPSnooping 2 }

gs2326pplusDHCPSnoopingStatisticsEntry OBJECT-TYPE
   SYNTAX      GS2326PPLUSDHCPSnoopingStatisticsEntry
   MAX-ACCESS  not-accessible
   STATUS      current
   DESCRIPTION
       ""
   INDEX    { gs2326pplusDHCPSnoopingStatisticsPort  }
   ::= { gs2326pplusDHCPSnoopingStatisticsTable 1 }

GS2326PPLUSDHCPSnoopingStatisticsEntry ::= SEQUENCE {
   gs2326pplusDHCPSnoopingStatisticsPort         Integer32,
   gs2326pplusDHCPSnoopingStatisticsClear        INTEGER,
   gs2326pplusDHCPSnoopingRxDiscover             Counter32,
   gs2326pplusDHCPSnoopingRxOffer                Counter32,
   gs2326pplusDHCPSnoopingRxRequest              Counter32,
   gs2326pplusDHCPSnoopingRxDecline              Counter32,
   gs2326pplusDHCPSnoopingRxACK                  Counter32,
   gs2326pplusDHCPSnoopingRxNAK                  Counter32,
   gs2326pplusDHCPSnoopingRxRelease              Counter32,
   gs2326pplusDHCPSnoopingRxInform               Counter32,
   gs2326pplusDHCPSnoopingRxLeaseQuery           Counter32,
   gs2326pplusDHCPSnoopingRxLeaseUnassigned      Counter32,
   gs2326pplusDHCPSnoopingRxLeaseUnknown         Counter32,
   gs2326pplusDHCPSnoopingRxLeaseActive          Counter32,
   gs2326pplusDHCPSnoopingTxDiscover             Counter32,
   gs2326pplusDHCPSnoopingTxOffer                Counter32,
   gs2326pplusDHCPSnoopingTxRequest              Counter32,
   gs2326pplusDHCPSnoopingTxDecline              Counter32,
   gs2326pplusDHCPSnoopingTxACK                  Counter32,
   gs2326pplusDHCPSnoopingTxNAK                  Counter32,
   gs2326pplusDHCPSnoopingTxRelease              Counter32,
   gs2326pplusDHCPSnoopingTxInform               Counter32,
   gs2326pplusDHCPSnoopingTxLeaseQuery           Counter32,
   gs2326pplusDHCPSnoopingTxLeaseUnassigned      Counter32,
   gs2326pplusDHCPSnoopingTxLeaseUnknown         Counter32,
   gs2326pplusDHCPSnoopingTxLeaseActive          Counter32
}

gs2326pplusDHCPSnoopingStatisticsPort OBJECT-TYPE
   SYNTAX      Integer32(1..4095)
   MAX-ACCESS  not-accessible
   STATUS      current
   DESCRIPTION
       " "
   ::= { gs2326pplusDHCPSnoopingStatisticsEntry 1 }

gs2326pplusDHCPSnoopingStatisticsClear OBJECT-TYPE
   SYNTAX      INTEGER { none(0), clear(1) }
   MAX-ACCESS  read-write
   STATUS      current
   DESCRIPTION
       "default: 0
       0: none
       1: clear"
   ::= { gs2326pplusDHCPSnoopingStatisticsEntry 2 }

gs2326pplusDHCPSnoopingRxDiscover OBJECT-TYPE
   SYNTAX      Counter32
   MAX-ACCESS  read-only
   STATUS      current
   DESCRIPTION
       " "
   ::= { gs2326pplusDHCPSnoopingStatisticsEntry 3 }

gs2326pplusDHCPSnoopingRxOffer OBJECT-TYPE
   SYNTAX      Counter32
   MAX-ACCESS  read-only
   STATUS      current
   DESCRIPTION
       " "
   ::= { gs2326pplusDHCPSnoopingStatisticsEntry 4 }

gs2326pplusDHCPSnoopingRxRequest OBJECT-TYPE
   SYNTAX      Counter32
   MAX-ACCESS  read-only
   STATUS      current
   DESCRIPTION
       " "
   ::= { gs2326pplusDHCPSnoopingStatisticsEntry 5 }

gs2326pplusDHCPSnoopingRxDecline OBJECT-TYPE
   SYNTAX      Counter32
   MAX-ACCESS  read-only
   STATUS      current
   DESCRIPTION
       " "
   ::= { gs2326pplusDHCPSnoopingStatisticsEntry 6 }

gs2326pplusDHCPSnoopingRxACK OBJECT-TYPE
   SYNTAX      Counter32
   MAX-ACCESS  read-only
   STATUS      current
   DESCRIPTION
       " "
   ::= { gs2326pplusDHCPSnoopingStatisticsEntry 7 }

gs2326pplusDHCPSnoopingRxNAK OBJECT-TYPE
   SYNTAX      Counter32
   MAX-ACCESS  read-only
   STATUS      current
   DESCRIPTION
       " "
   ::= { gs2326pplusDHCPSnoopingStatisticsEntry 8 }

gs2326pplusDHCPSnoopingRxRelease OBJECT-TYPE
   SYNTAX      Counter32
   MAX-ACCESS  read-only
   STATUS      current
   DESCRIPTION
       " "
   ::= { gs2326pplusDHCPSnoopingStatisticsEntry 9 }

gs2326pplusDHCPSnoopingRxInform OBJECT-TYPE
   SYNTAX      Counter32
   MAX-ACCESS  read-only
   STATUS      current
   DESCRIPTION
       " "
   ::= { gs2326pplusDHCPSnoopingStatisticsEntry 10 }

gs2326pplusDHCPSnoopingRxLeaseQuery OBJECT-TYPE
   SYNTAX      Counter32
   MAX-ACCESS  read-only
   STATUS      current
   DESCRIPTION
       " "
   ::= { gs2326pplusDHCPSnoopingStatisticsEntry 11 }

gs2326pplusDHCPSnoopingRxLeaseUnassigned OBJECT-TYPE
   SYNTAX      Counter32
   MAX-ACCESS  read-only
   STATUS      current
   DESCRIPTION
       " "
   ::= { gs2326pplusDHCPSnoopingStatisticsEntry 12 }

gs2326pplusDHCPSnoopingRxLeaseUnknown OBJECT-TYPE
   SYNTAX      Counter32
   MAX-ACCESS  read-only
   STATUS      current
   DESCRIPTION
       " "
   ::= { gs2326pplusDHCPSnoopingStatisticsEntry 13 }

gs2326pplusDHCPSnoopingRxLeaseActive OBJECT-TYPE
   SYNTAX      Counter32
   MAX-ACCESS  read-only
   STATUS      current
   DESCRIPTION
       " "
   ::= { gs2326pplusDHCPSnoopingStatisticsEntry 14 }

gs2326pplusDHCPSnoopingTxDiscover OBJECT-TYPE
   SYNTAX      Counter32
   MAX-ACCESS  read-only
   STATUS      current
   DESCRIPTION
       " "
   ::= { gs2326pplusDHCPSnoopingStatisticsEntry 15 }

gs2326pplusDHCPSnoopingTxOffer OBJECT-TYPE
   SYNTAX      Counter32
   MAX-ACCESS  read-only
   STATUS      current
   DESCRIPTION
       " "
   ::= { gs2326pplusDHCPSnoopingStatisticsEntry 16 }

gs2326pplusDHCPSnoopingTxRequest OBJECT-TYPE
   SYNTAX      Counter32
   MAX-ACCESS  read-only
   STATUS      current
   DESCRIPTION
       " "
   ::= { gs2326pplusDHCPSnoopingStatisticsEntry 17 }

gs2326pplusDHCPSnoopingTxDecline OBJECT-TYPE
   SYNTAX      Counter32
   MAX-ACCESS  read-only
   STATUS      current
   DESCRIPTION
       " "
   ::= { gs2326pplusDHCPSnoopingStatisticsEntry 18 }

gs2326pplusDHCPSnoopingTxACK OBJECT-TYPE
   SYNTAX      Counter32
   MAX-ACCESS  read-only
   STATUS      current
   DESCRIPTION
       " "
   ::= { gs2326pplusDHCPSnoopingStatisticsEntry 19 }

gs2326pplusDHCPSnoopingTxNAK OBJECT-TYPE
   SYNTAX      Counter32
   MAX-ACCESS  read-only
   STATUS      current
   DESCRIPTION
       " "
   ::= { gs2326pplusDHCPSnoopingStatisticsEntry 20 }

gs2326pplusDHCPSnoopingTxRelease OBJECT-TYPE
   SYNTAX      Counter32
   MAX-ACCESS  read-only
   STATUS      current
   DESCRIPTION
       " "
   ::= { gs2326pplusDHCPSnoopingStatisticsEntry 21 }

gs2326pplusDHCPSnoopingTxInform OBJECT-TYPE
   SYNTAX      Counter32
   MAX-ACCESS  read-only
   STATUS      current
   DESCRIPTION
       " "
   ::= { gs2326pplusDHCPSnoopingStatisticsEntry 22 }

gs2326pplusDHCPSnoopingTxLeaseQuery OBJECT-TYPE
   SYNTAX      Counter32
   MAX-ACCESS  read-only
   STATUS      current
   DESCRIPTION
       " "
   ::= { gs2326pplusDHCPSnoopingStatisticsEntry 23 }

gs2326pplusDHCPSnoopingTxLeaseUnassigned OBJECT-TYPE
   SYNTAX      Counter32
   MAX-ACCESS  read-only
   STATUS      current
   DESCRIPTION
       " "
   ::= { gs2326pplusDHCPSnoopingStatisticsEntry 24 }

gs2326pplusDHCPSnoopingTxLeaseUnknown OBJECT-TYPE
   SYNTAX      Counter32
   MAX-ACCESS  read-only
   STATUS      current
   DESCRIPTION
       " "
   ::= { gs2326pplusDHCPSnoopingStatisticsEntry 25 }

gs2326pplusDHCPSnoopingTxLeaseActive OBJECT-TYPE
   SYNTAX      Counter32
   MAX-ACCESS  read-only
   STATUS      current
   DESCRIPTION
       " "
   ::= { gs2326pplusDHCPSnoopingStatisticsEntry 26 }


gs2326pplusDHCPRelay                                             OBJECT IDENTIFIER ::= { gs2326pplusSecurity 4 }

gs2326pplusDHCPRelayConfiguration                                         OBJECT IDENTIFIER ::= { gs2326pplusDHCPRelay 1 }

gs2326pplusDHCPRelayMode OBJECT-TYPE
   SYNTAX      INTEGER { disable(0), enable(1) }
   MAX-ACCESS  read-write
   STATUS      current
   DESCRIPTION
       "default: 0
       0: disable
       1: enable
       We need at least one server"
   ::= { gs2326pplusDHCPRelayConfiguration 1 }

gs2326pplusDHCPRelayServer OBJECT-TYPE
   SYNTAX      IpAddress
   MAX-ACCESS  read-write
   STATUS      current
   DESCRIPTION
       " "
   ::= { gs2326pplusDHCPRelayConfiguration 2 }

gs2326pplusDHCPRelayInformationMode OBJECT-TYPE
   SYNTAX      INTEGER { disable(0), enable(1) }
   MAX-ACCESS  read-write
   STATUS      current
   DESCRIPTION
       "default: 0
       0: disable
       1: enable "
   ::= { gs2326pplusDHCPRelayConfiguration 3 }

gs2326pplusDHCPRelayInformationPolicy OBJECT-TYPE
   SYNTAX      INTEGER { replace(0), keep(1), drop(2) }
   MAX-ACCESS  read-write
   STATUS      current
   DESCRIPTION
       "default: 0
       0: replace
       1: keep
       2: drop "
   ::= { gs2326pplusDHCPRelayConfiguration 4 }

gs2326pplusDHCPRelayInformationCustom OBJECT-TYPE
   SYNTAX      DisplayString(SIZE(0..32))
   MAX-ACCESS  read-write
   STATUS      current
   DESCRIPTION
       "DHCP Option 82 Circuit ID custom information"
   ::= { gs2326pplusDHCPRelayConfiguration 1500 }

gs2326pplusDHCPRelayConfigurationGateways                                          OBJECT IDENTIFIER ::= { gs2326pplusDHCPRelayConfiguration 5 }

gs2326pplusDHCPRelayConfigurationGatewaysCreate OBJECT-TYPE
   SYNTAX       INTEGER { none(0), create(1) }
   MAX-ACCESS   read-write
   STATUS       current
   DESCRIPTION
       "default: 0
        0 : None  (read only)
        1 : Create entry"
   ::= { gs2326pplusDHCPRelayConfigurationGateways 1 }

gs2326pplusDHCPRelayConfigurationGatewaysTable OBJECT-TYPE
   SYNTAX      SEQUENCE OF Gs2326pplusDHCPRelayConfigurationGatewaysEntry
   MAX-ACCESS  not-accessible
   STATUS      current
   DESCRIPTION
       " Create DHCP Relay Gateway IP address entry."
   ::= { gs2326pplusDHCPRelayConfigurationGateways 2 }

gs2326pplusDHCPRelayConfigurationGatewaysEntry OBJECT-TYPE
   SYNTAX      Gs2326pplusDHCPRelayConfigurationGatewaysEntry
   MAX-ACCESS  not-accessible
   STATUS      current
   DESCRIPTION
       ""
   INDEX    { gs2326pplusDHCPRelayConfigurationGatewaysIndex  }
   ::= { gs2326pplusDHCPRelayConfigurationGatewaysTable 1 }

Gs2326pplusDHCPRelayConfigurationGatewaysEntry ::= SEQUENCE {
   gs2326pplusDHCPRelayConfigurationGatewaysIndex           Integer32,
   gs2326pplusDHCPRelayConfigurationGatewaysVLANId          Integer32,
   gs2326pplusDHCPRelayConfigurationGatewaysIP              IpAddress,
   gs2326pplusDHCPRelayConfigurationGatewaysRowStatus       INTEGER
}

gs2326pplusDHCPRelayConfigurationGatewaysIndex OBJECT-TYPE
   SYNTAX      Integer32(1..6)
   MAX-ACCESS  not-accessible
   STATUS      current
   DESCRIPTION
       " "
   ::= { gs2326pplusDHCPRelayConfigurationGatewaysEntry 1 }

gs2326pplusDHCPRelayConfigurationGatewaysVLANId OBJECT-TYPE
   SYNTAX      Integer32(1..4094)
   MAX-ACCESS  read-write
   STATUS      current
   DESCRIPTION
       " VLAN ID "
   ::= { gs2326pplusDHCPRelayConfigurationGatewaysEntry 2 }

gs2326pplusDHCPRelayConfigurationGatewaysIP OBJECT-TYPE
   SYNTAX      IpAddress
   MAX-ACCESS  read-write
   STATUS      current
   DESCRIPTION
       "DHCP GIADDR address."
   ::= { gs2326pplusDHCPRelayConfigurationGatewaysEntry 3 }

gs2326pplusDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pplusDHCPRelayConfigurationGatewaysEntry 4 }

gs2326pplusDHCPRelayStatistics                                   OBJECT IDENTIFIER ::= { gs2326pplusDHCPRelay 2 }

gs2326pplusDHCPRelayServerStatistics                                   OBJECT IDENTIFIER ::= { gs2326pplusDHCPRelayStatistics 1 }

gs2326pplusServerStatTransmitToServer OBJECT-TYPE
   SYNTAX      Counter32
   MAX-ACCESS  read-only
   STATUS      current
   DESCRIPTION
       " "
   ::= { gs2326pplusDHCPRelayServerStatistics 1 }

gs2326pplusServerStatTransmitError OBJECT-TYPE
   SYNTAX      Counter32
   MAX-ACCESS  read-only
   STATUS      current
   DESCRIPTION
       " "
   ::= { gs2326pplusDHCPRelayServerStatistics 2 }

gs2326pplusServerStatReceiveFromServer OBJECT-TYPE
   SYNTAX      Counter32
   MAX-ACCESS  read-only
   STATUS      current
   DESCRIPTION
       " "
   ::= { gs2326pplusDHCPRelayServerStatistics 3 }

gs2326pplusServerStatReceiveMissingAgentOption OBJECT-TYPE
   SYNTAX      Counter32
   MAX-ACCESS  read-only
   STATUS      current
   DESCRIPTION
       " "
   ::= { gs2326pplusDHCPRelayServerStatistics 4 }

gs2326pplusServerStatReceiveMissingCircuitID OBJECT-TYPE
   SYNTAX      Counter32
   MAX-ACCESS  read-only
   STATUS      current
   DESCRIPTION
       " "
   ::= { gs2326pplusDHCPRelayServerStatistics 5 }

gs2326pplusServerStatReceiveMissingRemoteID OBJECT-TYPE
   SYNTAX      Counter32
   MAX-ACCESS  read-only
   STATUS      current
   DESCRIPTION
       " "
   ::= { gs2326pplusDHCPRelayServerStatistics 6 }

gs2326pplusServerStatReceiveBadCircuitID OBJECT-TYPE
   SYNTAX      Counter32
   MAX-ACCESS  read-only
   STATUS      current
   DESCRIPTION
       " "
   ::= { gs2326pplusDHCPRelayServerStatistics 7 }

gs2326pplusServerStatReceiveBadRemoteID OBJECT-TYPE
   SYNTAX      Counter32
   MAX-ACCESS  read-only
   STATUS      current
   DESCRIPTION
       " "
   ::= { gs2326pplusDHCPRelayServerStatistics 8 }

gs2326pplusDHCPRelayClientStatistics                                   OBJECT IDENTIFIER ::= { gs2326pplusDHCPRelayStatistics 2 }

gs2326pplusClientStatTransmitToClient OBJECT-TYPE
   SYNTAX      Counter32
   MAX-ACCESS  read-only
   STATUS      current
   DESCRIPTION
       " "
   ::= { gs2326pplusDHCPRelayClientStatistics 1 }

gs2326pplusClientStatTransmitError OBJECT-TYPE
   SYNTAX      Counter32
   MAX-ACCESS  read-only
   STATUS      current
   DESCRIPTION
       " "
   ::= { gs2326pplusDHCPRelayClientStatistics 2 }

gs2326pplusClientStatReceivefromClient OBJECT-TYPE
   SYNTAX      Counter32
   MAX-ACCESS  read-only
   STATUS      current
   DESCRIPTION
       " "
   ::= { gs2326pplusDHCPRelayClientStatistics 3 }

gs2326pplusClientStatReceiveAgentOption OBJECT-TYPE
   SYNTAX      Counter32
   MAX-ACCESS  read-only
   STATUS      current
   DESCRIPTION
       " "
   ::= { gs2326pplusDHCPRelayClientStatistics 4 }

gs2326pplusClientStatReplaceAgentOption OBJECT-TYPE
   SYNTAX      Counter32
   MAX-ACCESS  read-only
   STATUS      current
   DESCRIPTION
       " "
   ::= { gs2326pplusDHCPRelayClientStatistics 5 }

gs2326pplusClientStatKeepAgentOption OBJECT-TYPE
   SYNTAX      Counter32
   MAX-ACCESS  read-only
   STATUS      current
   DESCRIPTION
       " "
   ::= { gs2326pplusDHCPRelayClientStatistics 6 }

gs2326pplusClientStatDropAgentOption OBJECT-TYPE
   SYNTAX      Counter32
   MAX-ACCESS  read-only
   STATUS      current
   DESCRIPTION
       " "
   ::= { gs2326pplusDHCPRelayClientStatistics 7 }

gs2326pplusPortSecurity                                          OBJECT IDENTIFIER ::= { gs2326pplusSecurity 5 }

gs2326pplusPortSecLimitCtrl                                      OBJECT IDENTIFIER ::= { gs2326pplusPortSecurity 1 }

gs2326pplusPortSecLimitCtrlSystemConf                                      OBJECT IDENTIFIER ::= { gs2326pplusPortSecLimitCtrl 1 }

gs2326pplusPortSecurityMode OBJECT-TYPE
   SYNTAX      INTEGER { disable(0), enable(1) }
   MAX-ACCESS  read-write
   STATUS      current
   DESCRIPTION
       "default: 0
       0: disable
       1: enable "
   ::= { gs2326pplusPortSecLimitCtrlSystemConf 1 }

gs2326pplusPortSecurityAging OBJECT-TYPE
   SYNTAX      INTEGER { disable(0), enable(1) }
   MAX-ACCESS  read-write
   STATUS      current
   DESCRIPTION
       "default: 0
       0: disable
       1: enable "
   ::= { gs2326pplusPortSecLimitCtrlSystemConf 2 }

gs2326pplusPortSecurityAgingPeriod OBJECT-TYPE
   SYNTAX      INTEGER(10..10000000)
   MAX-ACCESS  read-write
   STATUS      current
   DESCRIPTION
       "default: 3600, range: 10-10000000 "
   ::= { gs2326pplusPortSecLimitCtrlSystemConf 3 }

gs2326pplusPortSecLimitCtrlTable OBJECT-TYPE
   SYNTAX      SEQUENCE OF GS2326PPLUSPortSecLimitCtrlEntry
   MAX-ACCESS  not-accessible
   STATUS      current
   DESCRIPTION
       " "
   ::= { gs2326pplusPortSecLimitCtrl 2 }

gs2326pplusPortSecLimitCtrlEntry OBJECT-TYPE
   SYNTAX      GS2326PPLUSPortSecLimitCtrlEntry
   MAX-ACCESS  not-accessible
   STATUS      current
   DESCRIPTION
       ""
   INDEX    { gs2326pplusPortSecLimitCtrlPort  }
   ::= { gs2326pplusPortSecLimitCtrlTable 1 }

GS2326PPLUSPortSecLimitCtrlEntry ::= SEQUENCE {
   gs2326pplusPortSecLimitCtrlPort           Integer32,
   gs2326pplusPortSecLimitCtrlPortMode       INTEGER,
   gs2326pplusPortSecLimitCtrlPortLimit      Integer32,
   gs2326pplusPortSecLimitCtrlPortAction     INTEGER,
   gs2326pplusPortSecLimitCtrlPortState      DisplayString,
   gs2326pplusPortSecLimitCtrlPortReOpen     INTEGER
}

gs2326pplusPortSecLimitCtrlPort OBJECT-TYPE
   SYNTAX      Integer32(1..4095)
   MAX-ACCESS  not-accessible
   STATUS      current
   DESCRIPTION
       " "
   ::= { gs2326pplusPortSecLimitCtrlEntry 1 }

gs2326pplusPortSecLimitCtrlPortMode OBJECT-TYPE
   SYNTAX      INTEGER { disable(0), enable(1) }
   MAX-ACCESS  read-write
   STATUS      current
   DESCRIPTION
       "default: 0
       0: disable
       1: enable"
   ::= { gs2326pplusPortSecLimitCtrlEntry 2 }

gs2326pplusPortSecLimitCtrlPortLimit OBJECT-TYPE
   SYNTAX      Integer32(1..1024)
   MAX-ACCESS  read-write
   STATUS      current
   DESCRIPTION
       "default: 4, range: 1-1024"
   ::= { gs2326pplusPortSecLimitCtrlEntry 3 }

gs2326pplusPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2326pplusPortSecLimitCtrlEntry 4 }

gs2326pplusPortSecLimitCtrlPortState OBJECT-TYPE
   SYNTAX      DisplayString
   MAX-ACCESS  read-only
   STATUS      current
   DESCRIPTION
       ""
   ::= { gs2326pplusPortSecLimitCtrlEntry 5 }

gs2326pplusPortSecLimitCtrlPortReOpen OBJECT-TYPE
   SYNTAX      INTEGER { none(0), reopen(1) }
   MAX-ACCESS  read-write
   STATUS      current
   DESCRIPTION
       "default: 0
       0: none
       1: reopen"
   ::= { gs2326pplusPortSecLimitCtrlEntry 6 }

gs2326pplusPortSecSwitchStatusTable OBJECT-TYPE
   SYNTAX      SEQUENCE OF GS2326PPLUSPortSecSwitchStatusEntry
   MAX-ACCESS  not-accessible
   STATUS      current
   DESCRIPTION
       " "
   ::= { gs2326pplusPortSecurity 2 }

gs2326pplusPortSecSwitchStatusEntry OBJECT-TYPE
   SYNTAX      GS2326PPLUSPortSecSwitchStatusEntry
   MAX-ACCESS  not-accessible
   STATUS      current
   DESCRIPTION
       ""
   INDEX    { gs2326pplusPortSecSwitchStatusPort  }
   ::= { gs2326pplusPortSecSwitchStatusTable 1 }

GS2326PPLUSPortSecSwitchStatusEntry ::= SEQUENCE {
   gs2326pplusPortSecSwitchStatusPort                Integer32,
   gs2326pplusPortSecSwitchStatusUsers               DisplayString,
   gs2326pplusPortSecSwitchStatusState               DisplayString,
   gs2326pplusPortSecSwitchStatusMACCountCurrent     Integer32,
   gs2326pplusPortSecSwitchStatusMACCountLimit       Integer32
}

gs2326pplusPortSecSwitchStatusPort OBJECT-TYPE
   SYNTAX      Integer32(1..4095)
   MAX-ACCESS  not-accessible
   STATUS      current
   DESCRIPTION
       " "
   ::= { gs2326pplusPortSecSwitchStatusEntry 1 }

gs2326pplusPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2326pplusPortSecSwitchStatusEntry 2 }

gs2326pplusPortSecSwitchStatusState OBJECT-TYPE
   SYNTAX      DisplayString
   MAX-ACCESS  read-only
   STATUS      current
   DESCRIPTION
       " Shows the current state of the port : Disabled, Ready, Limit Reached, Shutdown. "
   ::= { gs2326pplusPortSecSwitchStatusEntry 3 }

gs2326pplusPortSecSwitchStatusMACCountCurrent OBJECT-TYPE
   SYNTAX      Integer32(1..4095)
   MAX-ACCESS  read-only
   STATUS      current
   DESCRIPTION
       ""
   ::= { gs2326pplusPortSecSwitchStatusEntry 4 }

gs2326pplusPortSecSwitchStatusMACCountLimit OBJECT-TYPE
   SYNTAX      Integer32(1..4095)
   MAX-ACCESS  read-only
   STATUS      current
   DESCRIPTION
       ""
   ::= { gs2326pplusPortSecSwitchStatusEntry 5 }

gs2326pplusPortSecPortStatus                                      OBJECT IDENTIFIER ::= { gs2326pplusPortSecurity 3 }

gs2326pplusPortSecPortStatusPort OBJECT-TYPE
   SYNTAX       Integer32(1..4095)
   MAX-ACCESS   read-write
   STATUS       current
   DESCRIPTION
       "port number
        default: 1
        range: 1 - port number."
   ::= { gs2326pplusPortSecPortStatus 1 }

gs2326pplusPortSecPortStatusTable OBJECT-TYPE
   SYNTAX      SEQUENCE OF GS2326PPLUSPortSecPortStatusEntry
   MAX-ACCESS  not-accessible
   STATUS      current
   DESCRIPTION
      " "
   ::= { gs2326pplusPortSecPortStatus 2 }

gs2326pplusPortSecPortStatusEntry OBJECT-TYPE
   SYNTAX      GS2326PPLUSPortSecPortStatusEntry
   MAX-ACCESS  not-accessible
   STATUS      current
   DESCRIPTION
       ""
   INDEX    { gs2326pplusPortSecPortStatusIndex  }
   ::= { gs2326pplusPortSecPortStatusTable 1 }

GS2326PPLUSPortSecPortStatusEntry ::= SEQUENCE {
   gs2326pplusPortSecPortStatusIndex              Integer32,
   gs2326pplusPortSecPortStatusMACAddress         MacAddress,
   gs2326pplusPortSecPortStatusVLANId             Integer32,
   gs2326pplusPortSecPortStatusState              DisplayString,
   gs2326pplusPortSecPortStatusTimeOfAddition     DisplayString,
   gs2326pplusPortSecPortStatusAgeAndHold         DisplayString
}

gs2326pplusPortSecPortStatusIndex OBJECT-TYPE
   SYNTAX      Integer32(1..4095)
   MAX-ACCESS  not-accessible
   STATUS      current
   DESCRIPTION
       " "
   ::= { gs2326pplusPortSecPortStatusEntry 1 }

gs2326pplusPortSecPortStatusMACAddress OBJECT-TYPE
   SYNTAX      MacAddress
   MAX-ACCESS  read-only
   STATUS      current
   DESCRIPTION
       " "
   ::= { gs2326pplusPortSecPortStatusEntry 2 }

gs2326pplusPortSecPortStatusVLANId OBJECT-TYPE
   SYNTAX      Integer32(1..4094)
   MAX-ACCESS  read-only
   STATUS      current
   DESCRIPTION
       " "
   ::= { gs2326pplusPortSecPortStatusEntry 3 }

gs2326pplusPortSecPortStatusState OBJECT-TYPE
   SYNTAX      DisplayString
   MAX-ACCESS  read-only
   STATUS      current
   DESCRIPTION
       "Blocked / Forwarding "
   ::= { gs2326pplusPortSecPortStatusEntry 4 }

gs2326pplusPortSecPortStatusTimeOfAddition OBJECT-TYPE
   SYNTAX      DisplayString
   MAX-ACCESS  read-only
   STATUS      current
   DESCRIPTION
       " "
   ::= { gs2326pplusPortSecPortStatusEntry 5 }

gs2326pplusPortSecPortStatusAgeAndHold OBJECT-TYPE
   SYNTAX      DisplayString
   MAX-ACCESS  read-only
   STATUS      current
   DESCRIPTION
       " "
   ::= { gs2326pplusPortSecPortStatusEntry 6 }


gs2326pplusAccessManagement                                      OBJECT IDENTIFIER ::= { gs2326pplusSecurity 6 }

gs2326pplusAccessMgtConf                                         OBJECT IDENTIFIER ::= { gs2326pplusAccessManagement 1 }

gs2326pplusAccessMgtConfMode OBJECT-TYPE
   SYNTAX      INTEGER { disable(0), enable(1) }
   MAX-ACCESS  read-write
   STATUS      current
   DESCRIPTION
       "default: 0
       0: disable
       1: enable "
   ::= { gs2326pplusAccessMgtConf 1 }

gs2326pplusAccessMgtConfCreate OBJECT-TYPE
   SYNTAX      INTEGER { none(0), create(1) }
   MAX-ACCESS  read-write
   STATUS      current
   DESCRIPTION
       "default: 0
       0: none
       1: create "
   ::= { gs2326pplusAccessMgtConf 2 }

gs2326pplusAccessMgtConfTable OBJECT-TYPE
   SYNTAX      SEQUENCE OF GS2326PPLUSAccessMgtConfEntry
   MAX-ACCESS  not-accessible
   STATUS      current
   DESCRIPTION
       " "
   ::= { gs2326pplusAccessMgtConf 3 }

gs2326pplusAccessMgtConfEntry OBJECT-TYPE
   SYNTAX      GS2326PPLUSAccessMgtConfEntry
   MAX-ACCESS  not-accessible
   STATUS      current
   DESCRIPTION
       ""
   INDEX    { gs2326pplusAccessMgtIndex  }
   ::= { gs2326pplusAccessMgtConfTable 1 }

GS2326PPLUSAccessMgtConfEntry ::= SEQUENCE {
   gs2326pplusAccessMgtIndex             Integer32,
   gs2326pplusAccessMgtAddresstype       INTEGER,
   gs2326pplusAccessMgtStartIpAddress    DisplayString,
   gs2326pplusAccessMgtEndIpAddress      DisplayString,
   gs2326pplusAccessMgtHttpHttps         INTEGER,
   gs2326pplusAccessMgtSNMP              INTEGER,
   gs2326pplusAccessMgtTelnetSSH         INTEGER,
   gs2326pplusAccessMgtRowStatus         INTEGER
}

gs2326pplusAccessMgtIndex OBJECT-TYPE
   SYNTAX      Integer32(1..16)
   MAX-ACCESS  read-write
   STATUS      current
   DESCRIPTION
       "Set Access Management config index
        range : 1-16."
   ::= { gs2326pplusAccessMgtConfEntry 1 }

gs2326pplusAccessMgtAddresstype OBJECT-TYPE
   SYNTAX      INTEGER { ipv4(0), ipv6(1) }
   MAX-ACCESS  read-write
   STATUS      current
   DESCRIPTION
       "0: ipv4
        1: ipv6 "
   ::= { gs2326pplusAccessMgtConfEntry 2 }

gs2326pplusAccessMgtStartIpAddress OBJECT-TYPE
   SYNTAX      DisplayString
   MAX-ACCESS  read-write
   STATUS      current
   DESCRIPTION
       " Start IP address.
         IP address doesn't allowed all zero or all 'ff'H."
   ::= { gs2326pplusAccessMgtConfEntry 3 }

gs2326pplusAccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2326pplusAccessMgtConfEntry 4 }

gs2326pplusAccessMgtHttpHttps OBJECT-TYPE
   SYNTAX      INTEGER { disable(0), enable(1) }
   MAX-ACCESS  read-write
   STATUS      current
   DESCRIPTION
       "default: 0
       0: disable
       1: enable "
   ::= { gs2326pplusAccessMgtConfEntry 5 }

gs2326pplusAccessMgtSNMP OBJECT-TYPE
   SYNTAX      INTEGER { disable(0), enable(1) }
   MAX-ACCESS  read-write
   STATUS      current
   DESCRIPTION
       "default: 0
       0: disable
       1: enable "
   ::= { gs2326pplusAccessMgtConfEntry 6 }

gs2326pplusAccessMgtTelnetSSH OBJECT-TYPE
   SYNTAX      INTEGER { disable(0), enable(1) }
   MAX-ACCESS  read-write
   STATUS      current
   DESCRIPTION
       "default: 0
       0: disable
       1: enable "
   ::= { gs2326pplusAccessMgtConfEntry 7 }

gs2326pplusAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2326pplusAccessMgtConfEntry 8 }

gs2326pplusAccessMgtStatistics                                   OBJECT IDENTIFIER ::= { gs2326pplusAccessManagement 2 }

gs2326pplusHttpReceivedPkts OBJECT-TYPE
   SYNTAX      Counter32
   MAX-ACCESS  read-only
   STATUS      current
   DESCRIPTION
       " "
   ::= { gs2326pplusAccessMgtStatistics 1 }

gs2326pplusHttpAllowedPkts OBJECT-TYPE
   SYNTAX      Counter32
   MAX-ACCESS  read-only
   STATUS      current
   DESCRIPTION
       " "
   ::= { gs2326pplusAccessMgtStatistics 2 }

gs2326pplusHttpDiscardedPkts OBJECT-TYPE
   SYNTAX      Counter32
   MAX-ACCESS  read-only
   STATUS      current
   DESCRIPTION
       " "
   ::= { gs2326pplusAccessMgtStatistics 3 }

gs2326pplusHttpsReceivedPkts OBJECT-TYPE
   SYNTAX      Counter32
   MAX-ACCESS  read-only
   STATUS      current
   DESCRIPTION
       " "
   ::= { gs2326pplusAccessMgtStatistics 4 }

gs2326pplusHttpsAllowedPkts OBJECT-TYPE
   SYNTAX      Counter32
   MAX-ACCESS  read-only
   STATUS      current
   DESCRIPTION
       " "
   ::= { gs2326pplusAccessMgtStatistics 5 }

gs2326pplusHttpsDiscardedPkts OBJECT-TYPE
   SYNTAX      Counter32
   MAX-ACCESS  read-only
   STATUS      current
   DESCRIPTION
       " "
   ::= { gs2326pplusAccessMgtStatistics 6 }

gs2326pplusSnmpReceivedPkts OBJECT-TYPE
   SYNTAX      Counter32
   MAX-ACCESS  read-only
   STATUS      current
   DESCRIPTION
       " "
   ::= { gs2326pplusAccessMgtStatistics 7 }

gs2326pplusSnmpAllowedPkts OBJECT-TYPE
   SYNTAX      Counter32
   MAX-ACCESS  read-only
   STATUS      current
   DESCRIPTION
       " "
   ::= { gs2326pplusAccessMgtStatistics 8 }

gs2326pplusSnmpDiscardedPkts OBJECT-TYPE
   SYNTAX      Counter32
   MAX-ACCESS  read-only
   STATUS      current
   DESCRIPTION
       " "
   ::= { gs2326pplusAccessMgtStatistics 9 }

gs2326pplusTelnetReceivedPkts OBJECT-TYPE
   SYNTAX      Counter32
   MAX-ACCESS  read-only
   STATUS      current
   DESCRIPTION
       " "
   ::= { gs2326pplusAccessMgtStatistics 10 }

gs2326pplusTelnetAllowedPkts OBJECT-TYPE
   SYNTAX      Counter32
   MAX-ACCESS  read-only
   STATUS      current
   DESCRIPTION
       " "
   ::= { gs2326pplusAccessMgtStatistics 11 }

gs2326pplusTelnetDiscardedPkts OBJECT-TYPE
   SYNTAX      Counter32
   MAX-ACCESS  read-only
   STATUS      current
   DESCRIPTION
       " "
   ::= { gs2326pplusAccessMgtStatistics 12 }

gs2326pplusSSHReceivedPkts OBJECT-TYPE
   SYNTAX      Counter32
   MAX-ACCESS  read-only
   STATUS      current
   DESCRIPTION
       " "
   ::= { gs2326pplusAccessMgtStatistics 13 }

gs2326pplusSSHAllowedPkts OBJECT-TYPE
   SYNTAX      Counter32
   MAX-ACCESS  read-only
   STATUS      current
   DESCRIPTION
       " "
   ::= { gs2326pplusAccessMgtStatistics 14 }

gs2326pplusSSHDiscardedPkts OBJECT-TYPE
   SYNTAX      Counter32
   MAX-ACCESS  read-only
   STATUS      current
   DESCRIPTION
       " "
   ::= { gs2326pplusAccessMgtStatistics 15 }

gs2326pplusAccessMgtStatisticsClearAll OBJECT-TYPE
   SYNTAX      INTEGER { none(0), clear(1) }
   MAX-ACCESS  read-write
   STATUS      current
   DESCRIPTION
       "0: none
        1: clear"
   ::= { gs2326pplusAccessMgtStatistics 16 }

gs2326pplusSSH                                                   OBJECT IDENTIFIER ::= { gs2326pplusSecurity 7 }

gs2326pplusSSHMode OBJECT-TYPE
   SYNTAX      INTEGER { disable(0), enable(1) }
   MAX-ACCESS  read-write
   STATUS      current
   DESCRIPTION
       "default: 1
        0: disable
        1: enable"
   ::= { gs2326pplusSSH 1 }

gs2326pplusHTTPS                                                 OBJECT IDENTIFIER ::= { gs2326pplusSecurity 8 }

gs2326pplusHTTPSMode OBJECT-TYPE
   SYNTAX      INTEGER { disable(0), enable(1) }
   MAX-ACCESS  read-write
   STATUS      current
   DESCRIPTION
       "default: 1
        0: disable
        1: enable"
   ::= { gs2326pplusHTTPS 1 }

gs2326pplusHTTPSAutoRedirect OBJECT-TYPE
   SYNTAX      INTEGER { disable(0), enable(1) }
   MAX-ACCESS  read-write
   STATUS      current
   DESCRIPTION
       "default: 0
        0: disable
        1: enable"
   ::= { gs2326pplusHTTPS 2 }

gs2326pplusHTTPSCertRenew OBJECT-TYPE
   SYNTAX      INTEGER { doNothing(0), renew(1) }
   MAX-ACCESS  read-write
   STATUS      current
   DESCRIPTION
       "default: 0 ,
        0: doNothing
        1: renew"
   ::= { gs2326pplusHTTPS 3 }

gs2326pplusHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2326pplusHTTPS 4 }

gs2326pplusHTTPMode OBJECT-TYPE
   SYNTAX      INTEGER { disable(0), enable(1) }
   MAX-ACCESS  read-write
   STATUS      current
   DESCRIPTION
       "default: 1
        0: disable
        1: enable"
   ::= { gs2326pplusHTTPS 5 }

gs2326pplusAuthMethod                                            OBJECT IDENTIFIER ::= { gs2326pplusSecurity 9 }

gs2326pplusConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pplusAuthMethod 1 }

gs2326pplusConsoleFallback OBJECT-TYPE
   SYNTAX      INTEGER { disable(0), enable(1) }
   MAX-ACCESS  read-write
   STATUS      current
   DESCRIPTION
       "default: 0
        0:disable
        1:enable"
   ::= { gs2326pplusAuthMethod 2 }

gs2326pplusTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pplusAuthMethod 3 }

gs2326pplusTelnetFallback OBJECT-TYPE
   SYNTAX      INTEGER { disable(0), enable(1) }
   MAX-ACCESS  read-write
   STATUS      current
   DESCRIPTION
       "default: 0
        0:disable
        1:enable"
   ::= { gs2326pplusAuthMethod 4 }

gs2326pplusSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pplusAuthMethod 5 }

gs2326pplusSshFallback OBJECT-TYPE
   SYNTAX      INTEGER { disable(0), enable(1) }
   MAX-ACCESS  read-write
   STATUS      current
   DESCRIPTION
       "default: 0
        0:disable
        1:enable"
   ::= { gs2326pplusAuthMethod 6 }

gs2326pplusTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pplusAuthMethod 9 }

gs2326pplusTftpFallback OBJECT-TYPE
   SYNTAX      INTEGER { disable(0), enable(1) }
   MAX-ACCESS  read-write
   STATUS      current
   DESCRIPTION
       "default: 0
        0:disable
        1:enable"
   ::= { gs2326pplusAuthMethod 10 }

gs2326pplusLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2326pplusAuthMethod 11 }

gs2326pplusLockMinutes OBJECT-TYPE
   SYNTAX      Integer32(1..99)
   MAX-ACCESS  read-write
   STATUS      current
   DESCRIPTION
       "Lock time to login failures trigger.
        range: 1-99.
        default: 5."
   ::= { gs2326pplusAuthMethod 12 }

gs2326pplusHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pplusAuthMethod 13 }

gs2326pplusHttpFallback OBJECT-TYPE
   SYNTAX      INTEGER { disable(0), enable(1) }
   MAX-ACCESS  read-write
   STATUS      current
   DESCRIPTION
       "default: 0
        0:disable
        1:enable"
   ::= { gs2326pplusAuthMethod 14 }

gs2326pplusHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pplusAuthMethod 15 }

gs2326pplusHttpsFallback OBJECT-TYPE
   SYNTAX      INTEGER { disable(0), enable(1) }
   MAX-ACCESS  read-write
   STATUS      current
   DESCRIPTION
       "default: 0
        0:disable
        1:enable"
   ::= { gs2326pplusAuthMethod 16 }


gs2326pplusAAA                                              OBJECT IDENTIFIER ::= { gs2326pplusSecurity 10 }

gs2326pplusAAACommonServer                                  OBJECT IDENTIFIER ::= { gs2326pplusAAA 1 }

gs2326pplusAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2326pplusAAACommonServer 1 }

gs2326pplusAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2326pplusAAACommonServer 2 }

gs2326pplusAAATACACSPlusAuthAndAccounting                  OBJECT IDENTIFIER ::= { gs2326pplusAAA 2 }

gs2326pplusAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2326pplusAAATACACSPlusAuthAndAccounting 1 }

gs2326pplusAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2326pplusAAATACACSPlusAuthAndAccounting 2 }

gs2326pplusAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2326pplusAAATACACSPlusAuthAndAccounting 3 }

gs2326pplusRADIUSAuthenticationServerTable OBJECT-TYPE
   SYNTAX      SEQUENCE OF Gs2326pplusRADIUSAuthenticationServerEntry
   MAX-ACCESS  not-accessible
   STATUS      current
   DESCRIPTION
       " "
   ::= { gs2326pplusAAA 3 }

gs2326pplusRADIUSAuthenticationServerEntry OBJECT-TYPE
   SYNTAX      Gs2326pplusRADIUSAuthenticationServerEntry
   MAX-ACCESS  not-accessible
   STATUS      current
   DESCRIPTION
       ""
   INDEX    { gs2326pplusRADIUSAuthenticationServerIndex  }
   ::= { gs2326pplusRADIUSAuthenticationServerTable 1 }

Gs2326pplusRADIUSAuthenticationServerEntry ::= SEQUENCE {
   gs2326pplusRADIUSAuthenticationServerIndex     Integer32,
   gs2326pplusRADIUSAuthenticationServerEnable    INTEGER,
   gs2326pplusRADIUSAuthenticationServerIP        DisplayString,
   gs2326pplusRADIUSAuthenticationServerPort      Integer32,
   gs2326pplusRADIUSAuthenticationServerSecret    DisplayString
}

gs2326pplusRADIUSAuthenticationServerIndex OBJECT-TYPE
   SYNTAX      Integer32(1..5)
   MAX-ACCESS  not-accessible
   STATUS      current
   DESCRIPTION
       "RADIUS Authentication Server index
        range : 1-5."
   ::= { gs2326pplusRADIUSAuthenticationServerEntry 1 }

gs2326pplusRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2326pplusRADIUSAuthenticationServerEntry 2 }

gs2326pplusRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2326pplusRADIUSAuthenticationServerEntry 3 }

gs2326pplusRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2326pplusRADIUSAuthenticationServerEntry 4 }

gs2326pplusRADIUSAuthenticationServerSecret OBJECT-TYPE
   SYNTAX      DisplayString
   MAX-ACCESS  read-write
   STATUS      current
   DESCRIPTION
       "The secret - up to 64 characters long - shared between the RADIUS Authentication Server and the switch. "
   ::= { gs2326pplusRADIUSAuthenticationServerEntry 5 }


gs2326pplusRADIUSAccountingServerTable OBJECT-TYPE
   SYNTAX      SEQUENCE OF Gs2326pplusRADIUSAccountingServerEntry
   MAX-ACCESS  not-accessible
   STATUS      current
   DESCRIPTION
       " "
   ::= { gs2326pplusAAA 4 }

gs2326pplusRADIUSAccountingServerEntry OBJECT-TYPE
   SYNTAX      Gs2326pplusRADIUSAccountingServerEntry
   MAX-ACCESS  not-accessible
   STATUS      current
   DESCRIPTION
       ""
   INDEX    { gs2326pplusRADIUSAccountingServerIndex  }
   ::= { gs2326pplusRADIUSAccountingServerTable 1 }

Gs2326pplusRADIUSAccountingServerEntry ::= SEQUENCE {
   gs2326pplusRADIUSAccountingServerIndex     Integer32,
   gs2326pplusRADIUSAccountingServerEnable    INTEGER,
   gs2326pplusRADIUSAccountingServerIP        DisplayString,
   gs2326pplusRADIUSAccountingServerPort      Integer32,
   gs2326pplusRADIUSAccountingServerSecret    DisplayString
}

gs2326pplusRADIUSAccountingServerIndex OBJECT-TYPE
   SYNTAX      Integer32(1..5)
   MAX-ACCESS  not-accessible
   STATUS      current
   DESCRIPTION
       "RADIUS Accounting Server index
        range : 1-5."
   ::= { gs2326pplusRADIUSAccountingServerEntry 1 }

gs2326pplusRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2326pplusRADIUSAccountingServerEntry 2 }

gs2326pplusRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2326pplusRADIUSAccountingServerEntry 3 }

gs2326pplusRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2326pplusRADIUSAccountingServerEntry 4 }

gs2326pplusRADIUSAccountingServerSecret OBJECT-TYPE
   SYNTAX      DisplayString
   MAX-ACCESS  read-write
   STATUS      current
   DESCRIPTION
       "The secret - up to 64 characters long - shared between the RADIUS Accounting Server and the switch. "
   ::= { gs2326pplusRADIUSAccountingServerEntry 5 }

gs2326pplusTACACSPlusAuthenticationServerTable OBJECT-TYPE
   SYNTAX      SEQUENCE OF Gs2326pplusTACACSPlusAuthenticationServerEntry
   MAX-ACCESS  not-accessible
   STATUS      current
   DESCRIPTION
       " "
   ::= { gs2326pplusAAA 5 }

gs2326pplusTACACSPlusAuthenticationServerEntry OBJECT-TYPE
   SYNTAX      Gs2326pplusTACACSPlusAuthenticationServerEntry
   MAX-ACCESS  not-accessible
   STATUS      current
   DESCRIPTION
       ""
   INDEX    { gs2326pplusTACACSPlusAuthenticationServerIndex  }
   ::= { gs2326pplusTACACSPlusAuthenticationServerTable 1 }

Gs2326pplusTACACSPlusAuthenticationServerEntry ::= SEQUENCE {
   gs2326pplusTACACSPlusAuthenticationServerIndex     Integer32,
   gs2326pplusTACACSPlusAuthenticationServerEnable    INTEGER,
   gs2326pplusTACACSPlusAuthenticationServerIP        DisplayString,
   gs2326pplusTACACSPlusAuthenticationServerPort      Integer32,
   gs2326pplusTACACSPlusAuthenticationServerSecret    DisplayString
}

gs2326pplusTACACSPlusAuthenticationServerIndex OBJECT-TYPE
   SYNTAX      Integer32(1..5)
   MAX-ACCESS  not-accessible
   STATUS      current
   DESCRIPTION
       "TACACSPlus Authentication Server index
        range : 1-5."
   ::= { gs2326pplusTACACSPlusAuthenticationServerEntry 1 }

gs2326pplusTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2326pplusTACACSPlusAuthenticationServerEntry 2 }

gs2326pplusTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2326pplusTACACSPlusAuthenticationServerEntry 3 }

gs2326pplusTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2326pplusTACACSPlusAuthenticationServerEntry 4 }

gs2326pplusTACACSPlusAuthenticationServerSecret OBJECT-TYPE
   SYNTAX      DisplayString
   MAX-ACCESS  read-write
   STATUS      current
   DESCRIPTION
       "The secret - up to 64 characters long - shared between the TACACSPlus Authentication Server and the switch. "
   ::= { gs2326pplusTACACSPlusAuthenticationServerEntry 5 }


gs2326pplusRADIUSStatisticsTable OBJECT-TYPE
   SYNTAX      SEQUENCE OF Gs2326pplusRADIUSStatisticsEntry
   MAX-ACCESS  not-accessible
   STATUS      current
   DESCRIPTION
       " "
   ::= { gs2326pplusAAA 6 }

gs2326pplusRADIUSStatisticsEntry OBJECT-TYPE
   SYNTAX      Gs2326pplusRADIUSStatisticsEntry
   MAX-ACCESS  not-accessible
   STATUS      current
   DESCRIPTION
       ""
   INDEX    { gs2326pplusRADIUSAuthStatisticsServerIndex  }
   ::= { gs2326pplusRADIUSStatisticsTable 1 }

Gs2326pplusRADIUSStatisticsEntry ::= SEQUENCE {
   gs2326pplusRADIUSAuthStatisticsServerIndex                           Integer32,
   gs2326pplusRADIUSAuthStatisticsRecPktAccessAccepts                   Counter32,
   gs2326pplusRADIUSAuthStatisticsRecPktAccessRejects                   Counter32,
   gs2326pplusRADIUSAuthStatisticsRecPktAccessChallenges                Counter32,
   gs2326pplusRADIUSAuthStatisticsRecPktMalformedAccResponses           Counter32,
   gs2326pplusRADIUSAuthStatisticsRecPktBadAuthenticators               Counter32,
   gs2326pplusRADIUSAuthStatisticsRecPktUnknownTypes                    Counter32,
   gs2326pplusRADIUSAuthStatisticsRecPktDropped                         Counter32,
   gs2326pplusRADIUSAuthStatisticsTransmitPktAccessRequests             Counter32,
   gs2326pplusRADIUSAuthStatisticsTransmitPktAccessRetransmissions      Counter32,
   gs2326pplusRADIUSAuthStatisticsTransmitPktPendingRequests            Counter32,
   gs2326pplusRADIUSAuthStatisticsTransmitPktTimeouts                   Counter32,
   gs2326pplusRADIUSAuthIP                                              DisplayString,
   gs2326pplusRADIUSAuthState                                           DisplayString,
   gs2326pplusRADIUSAuthRoundTripTime                                   DisplayString,

   gs2326pplusRADIUSAccountingStatisticsRecPktResponses                 Counter32,
   gs2326pplusRADIUSAccountingStatisticsRecPktMalformedResponses        Counter32,
   gs2326pplusRADIUSAccountingStatisticsRecPktBadAuthenticators         Counter32,
   gs2326pplusRADIUSAccountingStatisticsRecPktUnknownTypes              Counter32,
   gs2326pplusRADIUSAccountingStatisticsRecPktDropped                   Counter32,
   gs2326pplusRADIUSAccountingStatisticsTransmitPktRequests             Counter32,
   gs2326pplusRADIUSAccountingStatisticsTransmitPktRetransmissions      Counter32,
   gs2326pplusRADIUSAccountingStatisticsTransmitPktPendingRequests      Counter32,
   gs2326pplusRADIUSAccountingStatisticsTransmitPktTimeouts             Counter32,
   gs2326pplusRADIUSAccountingIP                                        DisplayString,
   gs2326pplusRADIUSAccountingState                                     DisplayString,
   gs2326pplusRADIUSAccountingRoundTripTime                             DisplayString,
   gs2326pplusRADIUSStatisticsClear                                     INTEGER
}

gs2326pplusRADIUSAuthStatisticsServerIndex OBJECT-TYPE
   SYNTAX      Integer32(1..5)
   MAX-ACCESS  not-accessible
   STATUS      current
   DESCRIPTION
       "RADIUS Authentication Server index
        range : 1-5."
   ::= { gs2326pplusRADIUSStatisticsEntry 1 }

gs2326pplusRADIUSAuthStatisticsRecPktAccessAccepts OBJECT-TYPE
   SYNTAX      Counter32
   MAX-ACCESS  read-only
   STATUS      current
   DESCRIPTION
       "The number of RADIUS Access-Accept packets (valid or invalid) received from the server."
   ::= { gs2326pplusRADIUSStatisticsEntry 2 }

gs2326pplusRADIUSAuthStatisticsRecPktAccessRejects OBJECT-TYPE
   SYNTAX      Counter32
   MAX-ACCESS  read-only
   STATUS      current
   DESCRIPTION
       "The number of RADIUS Access-Reject packets (valid or invalid) received from the server."
   ::= { gs2326pplusRADIUSStatisticsEntry 3 }

gs2326pplusRADIUSAuthStatisticsRecPktAccessChallenges OBJECT-TYPE
   SYNTAX      Counter32
   MAX-ACCESS  read-only
   STATUS      current
   DESCRIPTION
       "The number of RADIUS Access-Challenge packets (valid or invalid) received from the server. "
   ::= { gs2326pplusRADIUSStatisticsEntry 4 }

gs2326pplusRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2326pplusRADIUSStatisticsEntry 5 }

gs2326pplusRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2326pplusRADIUSStatisticsEntry 6 }

gs2326pplusRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2326pplusRADIUSStatisticsEntry 7 }

gs2326pplusRADIUSAuthStatisticsRecPktDropped OBJECT-TYPE
   SYNTAX      Counter32
   MAX-ACCESS  read-only
   STATUS      current
   DESCRIPTION
       "The number of RADIUS packets that were received from the server on the
       authentication port and dropped for some other reason."
   ::= { gs2326pplusRADIUSStatisticsEntry 8 }

gs2326pplusRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2326pplusRADIUSStatisticsEntry 9 }

gs2326pplusRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2326pplusRADIUSStatisticsEntry 10 }

gs2326pplusRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2326pplusRADIUSStatisticsEntry 11 }

gs2326pplusRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2326pplusRADIUSStatisticsEntry 12 }

gs2326pplusRADIUSAuthIP OBJECT-TYPE
   SYNTAX      DisplayString
   MAX-ACCESS  read-only
   STATUS      current
   DESCRIPTION
       "IP address and UDP port for the authentication server in question."
   ::= { gs2326pplusRADIUSStatisticsEntry 13 }

gs2326pplusRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2326pplusRADIUSStatisticsEntry 14 }

gs2326pplusRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2326pplusRADIUSStatisticsEntry 15 }

gs2326pplusRADIUSAccountingStatisticsRecPktResponses OBJECT-TYPE
   SYNTAX      Counter32
   MAX-ACCESS  read-only
   STATUS      current
   DESCRIPTION
       "The number of RADIUS packets (valid or invalid) received from the server."
   ::= { gs2326pplusRADIUSStatisticsEntry 16 }

gs2326pplusRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2326pplusRADIUSStatisticsEntry 17 }

gs2326pplusRADIUSAccountingStatisticsRecPktBadAuthenticators OBJECT-TYPE
   SYNTAX      Counter32
   MAX-ACCESS  read-only
   STATUS      current
   DESCRIPTION
       "The number of RADIUS packets containing invalid authenticators received
       from the server."
   ::= { gs2326pplusRADIUSStatisticsEntry 18 }

gs2326pplusRADIUSAccountingStatisticsRecPktUnknownTypes OBJECT-TYPE
   SYNTAX      Counter32
   MAX-ACCESS  read-only
   STATUS      current
   DESCRIPTION
       "The number of RADIUS packets of unknown types that were received from
       the server on the accounting port."
   ::= { gs2326pplusRADIUSStatisticsEntry 19 }

gs2326pplusRADIUSAccountingStatisticsRecPktDropped OBJECT-TYPE
   SYNTAX      Counter32
   MAX-ACCESS  read-only
   STATUS      current
   DESCRIPTION
       "The number of RADIUS packets that were received from the server on the
       accounting port and dropped for some other reason."
   ::= { gs2326pplusRADIUSStatisticsEntry 20 }

gs2326pplusRADIUSAccountingStatisticsTransmitPktRequests OBJECT-TYPE
   SYNTAX      Counter32
   MAX-ACCESS  read-only
   STATUS      current
   DESCRIPTION
       "The number of RADIUS packets sent to the server. This does not include
       retransmissions."
   ::= { gs2326pplusRADIUSStatisticsEntry 21 }

gs2326pplusRADIUSAccountingStatisticsTransmitPktRetransmissions OBJECT-TYPE
   SYNTAX      Counter32
   MAX-ACCESS  read-only
   STATUS      current
   DESCRIPTION
       "The number of RADIUS packets retransmitted to the RADIUS accounting server."
   ::= { gs2326pplusRADIUSStatisticsEntry 22 }

gs2326pplusRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2326pplusRADIUSStatisticsEntry 23 }

gs2326pplusRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2326pplusRADIUSStatisticsEntry 24 }

gs2326pplusRADIUSAccountingIP OBJECT-TYPE
   SYNTAX      DisplayString
   MAX-ACCESS  read-only
   STATUS      current
   DESCRIPTION
       "IP address and UDP port for the accounting server in question."
   ::= { gs2326pplusRADIUSStatisticsEntry 25 }

gs2326pplusRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2326pplusRADIUSStatisticsEntry 26 }

gs2326pplusRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2326pplusRADIUSStatisticsEntry 27 }

gs2326pplusRADIUSStatisticsClear OBJECT-TYPE
   SYNTAX      INTEGER(0|1)
   MAX-ACCESS  read-write
   STATUS      current
   DESCRIPTION
       "Clears the counters for the server.
       read: always 0
       clear: set 1"
   ::= { gs2326pplusRADIUSStatisticsEntry 28 }


gs2326pplusNAS                                              OBJECT IDENTIFIER ::= { gs2326pplusSecurity 11 }

gs2326pplusNASConfiguration                                 OBJECT IDENTIFIER ::= { gs2326pplusNAS 1 }

gs2326pplusNASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2326pplusNASConfiguration 1 }

gs2326pplusNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2326pplusNASConfiguration 2 }

gs2326pplusNASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2326pplusNASConfiguration 3 }

gs2326pplusNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2326pplusNASConfiguration 4 }

gs2326pplusNASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2326pplusNASConfiguration 5 }

gs2326pplusNASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2326pplusNASConfiguration 6 }

gs2326pplusNASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2326pplusNASConfiguration 7 }

gs2326pplusNASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2326pplusNASConfiguration 8 }

gs2326pplusNASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2326pplusNASConfiguration 9 }

gs2326pplusNASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2326pplusNASConfiguration 10 }

gs2326pplusNASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2326pplusNASConfiguration 11 }

gs2326pplusNASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2326pplusNASConfiguration 12 }

gs2326pplusNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2326pplusNASConfiguration 101 }

gs2326pplusNASPortConfigTable OBJECT-TYPE
   SYNTAX      SEQUENCE OF Gs2326pplusNASPortConfigEntry
   MAX-ACCESS  not-accessible
   STATUS      current
   DESCRIPTION
       ""
   ::= { gs2326pplusNASConfiguration 13 }

gs2326pplusNASPortConfigEntry OBJECT-TYPE
   SYNTAX      Gs2326pplusNASPortConfigEntry
   MAX-ACCESS  not-accessible
   STATUS      current
   DESCRIPTION
       ""
   INDEX    { gs2326pplusNASPortConfigPort }
   ::= { gs2326pplusNASPortConfigTable 1 }

Gs2326pplusNASPortConfigEntry ::= SEQUENCE {
   gs2326pplusNASPortConfigPort                       Integer32,
   gs2326pplusNASPortConfigAdminState                 INTEGER,
   gs2326pplusNASPortConfigRADIUSAssignedQoSEnabled	  INTEGER,
   gs2326pplusNASPortConfigRADIUSAssignedVLANEnabled  INTEGER,
   gs2326pplusNASPortConfigGuestVLANEnabled           INTEGER,
   gs2326pplusNASPortConfigFallbackEnabled            INTEGER,
   gs2326pplusNASPortConfigPortState                  DisplayString,
   gs2326pplusNASPortConfigReauthenticate             INTEGER,
   gs2326pplusNASPortConfigReinitialize               INTEGER
}

gs2326pplusNASPortConfigPort OBJECT-TYPE
   SYNTAX      Integer32(1..255)
   MAX-ACCESS  not-accessible
   STATUS      current
   DESCRIPTION
       " port, range : 1 - port number. "
   ::= { gs2326pplusNASPortConfigEntry 1 }

gs2326pplusNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2326pplusNASPortConfigEntry 2 }

gs2326pplusNASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2326pplusNASPortConfigEntry 3 }

gs2326pplusNASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2326pplusNASPortConfigEntry 4 }

gs2326pplusNASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2326pplusNASPortConfigEntry 5 }

gs2326pplusNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2326pplusNASPortConfigEntry 6 }

gs2326pplusNASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2326pplusNASPortConfigEntry 7 }

gs2326pplusNASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2326pplusNASPortConfigEntry 8 }

gs2326pplusNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2326pplusNASPortConfigEntry 101 }

gs2326pplusNASSwitchStatusTable OBJECT-TYPE
   SYNTAX      SEQUENCE OF Gs2326pplusNASSwitchStatusEntry
   MAX-ACCESS  not-accessible
   STATUS      current
   DESCRIPTION
       ""
   ::= { gs2326pplusNAS 2 }

gs2326pplusNASSwitchStatusEntry OBJECT-TYPE
   SYNTAX      Gs2326pplusNASSwitchStatusEntry
   MAX-ACCESS  not-accessible
   STATUS      current
   DESCRIPTION
       ""
   INDEX    { gs2326pplusNASPortConfigPort }
   ::= { gs2326pplusNASSwitchStatusTable 1 }

Gs2326pplusNASSwitchStatusEntry ::= SEQUENCE {
   gs2326pplusNASSwitchStatusAdminState 	DisplayString,
   gs2326pplusNASSwitchStatusPortState		DisplayString,
   gs2326pplusNASSwitchStatusLastSource		DisplayString,
   gs2326pplusNASSwitchStatusLastID			DisplayString,
   gs2326pplusNASSwitchStatusQoSClass		DisplayString,
   gs2326pplusNASSwitchStatusPortVlanID		DisplayString
}

gs2326pplusNASSwitchStatusAdminState OBJECT-TYPE
   SYNTAX      DisplayString
   MAX-ACCESS  read-only
   STATUS      current
   DESCRIPTION
       "The port's current administrative state. Refer to NAS Admin State for a description of possible values."
   ::= { gs2326pplusNASSwitchStatusEntry 2 }

gs2326pplusNASSwitchStatusPortState OBJECT-TYPE
   SYNTAX      DisplayString
   MAX-ACCESS  read-only
   STATUS      current
   DESCRIPTION
       "The current state of the port. Refer to NAS Port State for a description of the individual states."
   ::= { gs2326pplusNASSwitchStatusEntry 3 }

gs2326pplusNASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2326pplusNASSwitchStatusEntry 4 }

gs2326pplusNASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2326pplusNASSwitchStatusEntry 5 }

gs2326pplusNASSwitchStatusQoSClass OBJECT-TYPE
   SYNTAX      DisplayString
   MAX-ACCESS  read-only
   STATUS      current
   DESCRIPTION
       "QoS Class assigned to the port by the RADIUS server if enabled."
   ::= { gs2326pplusNASSwitchStatusEntry 6 }

gs2326pplusNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2326pplusNASSwitchStatusEntry 7 }

gs2326pplusNASPortStatus                                 OBJECT IDENTIFIER ::= { gs2326pplusNAS 3 }

gs2326pplusNASPortStatusCountersTable OBJECT-TYPE
   SYNTAX      SEQUENCE OF Gs2326pplusNASPortStatusCountersEntry
   MAX-ACCESS  not-accessible
   STATUS      current
   DESCRIPTION
       ""
   ::= { gs2326pplusNASPortStatus 1 }

gs2326pplusNASPortStatusCountersEntry OBJECT-TYPE
   SYNTAX      Gs2326pplusNASPortStatusCountersEntry
   MAX-ACCESS  not-accessible
   STATUS      current
   DESCRIPTION
       ""
   INDEX    { gs2326pplusNASPortConfigPort }
   ::= { gs2326pplusNASPortStatusCountersTable 1 }

Gs2326pplusNASPortStatusCountersEntry ::= SEQUENCE {
   gs2326pplusNASRxCountersEAPOLTotal  	                  Counter32,
   gs2326pplusNASRxCountersEAPOLResponseID	              Counter32,
   gs2326pplusNASRxCountersEAPOLResponses	              Counter32,
   gs2326pplusNASRxCountersEAPOLStart	                  Counter32,
   gs2326pplusNASRxCountersEAPOLLogoff                    Counter32,
   gs2326pplusNASRxCountersEAPOLInvalidType               Counter32,
   gs2326pplusNASRxCountersEAPOLInvalidLength             Counter32,
   gs2326pplusNASTxCountersEAPOLTotal                     Counter32,
   gs2326pplusNASTxCountersEAPOLRequestID                 Counter32,
   gs2326pplusNASTxCountersEAPOLRequests                  Counter32,
   gs2326pplusNASRxBackendServerCountersAccessChallenges  Counter32,
   gs2326pplusNASRxBackendServerCountersOtherRequests     Counter32,
   gs2326pplusNASRxBackendServerCountersAuthSuccesses     Counter32,
   gs2326pplusNASRxBackendServerCountersAuthFailures      Counter32,
   gs2326pplusNASTxBackendServerCountersResponses         Counter32,
   gs2326pplusNASLastSupplicantInfoMACAddress             DisplayString,
   gs2326pplusNASLastSupplicantInfoVlanID                 Integer32,
   gs2326pplusNASLastSupplicantInfoVersion                Integer32,
   gs2326pplusNASLastSupplicantInfoIdentity               DisplayString,
   gs2326pplusNASCountersDoClear                          INTEGER
}

gs2326pplusNASRxCountersEAPOLTotal OBJECT-TYPE
   SYNTAX      Counter32
   MAX-ACCESS  read-only
   STATUS      current
   DESCRIPTION
       "The number of valid EAPOL frames of any type that have been received by the switch."
   ::= { gs2326pplusNASPortStatusCountersEntry 2 }

gs2326pplusNASRxCountersEAPOLResponseID OBJECT-TYPE
   SYNTAX      Counter32
   MAX-ACCESS  read-only
   STATUS      current
   DESCRIPTION
       "The number of valid EAPOL Response Identity frames that have been received by the switch."
   ::= { gs2326pplusNASPortStatusCountersEntry 3 }

gs2326pplusNASRxCountersEAPOLResponses OBJECT-TYPE
   SYNTAX      Counter32
   MAX-ACCESS  read-only
   STATUS      current
   DESCRIPTION
       "The number of valid EAPOL response frames (other than Response Identity frames)
	   that have been received by the switch."
   ::= { gs2326pplusNASPortStatusCountersEntry 4 }

gs2326pplusNASRxCountersEAPOLStart OBJECT-TYPE
   SYNTAX      Counter32
   MAX-ACCESS  read-only
   STATUS      current
   DESCRIPTION
       "The number of EAPOL Start frames that have been received by the switch."
   ::= { gs2326pplusNASPortStatusCountersEntry 5 }

gs2326pplusNASRxCountersEAPOLLogoff OBJECT-TYPE
   SYNTAX      Counter32
   MAX-ACCESS  read-only
   STATUS      current
   DESCRIPTION
       "The number of valid EAPOL Logoff frames that have been received by the switch."
   ::= { gs2326pplusNASPortStatusCountersEntry 6 }

gs2326pplusNASRxCountersEAPOLInvalidType OBJECT-TYPE
   SYNTAX      Counter32
   MAX-ACCESS  read-only
   STATUS      current
   DESCRIPTION
       "The number of EAPOL frames that have been received by the switch in which
	   the frame type is not recognized."
   ::= { gs2326pplusNASPortStatusCountersEntry 7 }

gs2326pplusNASRxCountersEAPOLInvalidLength OBJECT-TYPE
   SYNTAX      Counter32
   MAX-ACCESS  read-only
   STATUS      current
   DESCRIPTION
       "The number of EAPOL frames that have been received by the switch in which the
	   Packet Body Length field is invalid."
   ::= { gs2326pplusNASPortStatusCountersEntry 8 }

gs2326pplusNASTxCountersEAPOLTotal OBJECT-TYPE
   SYNTAX      Counter32
   MAX-ACCESS  read-only
   STATUS      current
   DESCRIPTION
       "The number of EAPOL frames of any type that have been transmitted by the switch."
   ::= { gs2326pplusNASPortStatusCountersEntry 9 }

gs2326pplusNASTxCountersEAPOLRequestID OBJECT-TYPE
   SYNTAX      Counter32
   MAX-ACCESS  read-only
   STATUS      current
   DESCRIPTION
       "The number of EAPOL Request Identity frames that have been transmitted by the switch."
   ::= { gs2326pplusNASPortStatusCountersEntry 10 }

gs2326pplusNASTxCountersEAPOLRequests OBJECT-TYPE
   SYNTAX      Counter32
   MAX-ACCESS  read-only
   STATUS      current
   DESCRIPTION
       "The number of valid EAPOL Request frames (other than Request Identity frames)
	   that have been transmitted by the switch."
   ::= { gs2326pplusNASPortStatusCountersEntry 11 }

gs2326pplusNASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2326pplusNASPortStatusCountersEntry 12 }

gs2326pplusNASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2326pplusNASPortStatusCountersEntry 13 }

gs2326pplusNASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2326pplusNASPortStatusCountersEntry 14 }

gs2326pplusNASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2326pplusNASPortStatusCountersEntry 15 }

gs2326pplusNASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2326pplusNASPortStatusCountersEntry 16 }

gs2326pplusNASLastSupplicantInfoMACAddress OBJECT-TYPE
   SYNTAX      DisplayString
   MAX-ACCESS  read-only
   STATUS      current
   DESCRIPTION
       "The MAC address of the last supplicant/client."
   ::= { gs2326pplusNASPortStatusCountersEntry 17 }

gs2326pplusNASLastSupplicantInfoVlanID OBJECT-TYPE
   SYNTAX      Integer32
   MAX-ACCESS  read-only
   STATUS      current
   DESCRIPTION
       "The VLAN ID on which the last frame from the last supplicant/client was received."
   ::= { gs2326pplusNASPortStatusCountersEntry 18 }

gs2326pplusNASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2326pplusNASPortStatusCountersEntry 19 }

gs2326pplusNASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2326pplusNASPortStatusCountersEntry 20 }

gs2326pplusNASCountersDoClear OBJECT-TYPE
   SYNTAX      INTEGER { doNothing(0), do(1) }
   MAX-ACCESS  read-write
   STATUS      current
   DESCRIPTION
       "Clear the counters for the selected port."
   ::= { gs2326pplusNASPortStatusCountersEntry 21 }

gs2326pplusNASPortStatusClientsTable OBJECT-TYPE
   SYNTAX      SEQUENCE OF Gs2326pplusNASPortStatusClientsEntry
   MAX-ACCESS  not-accessible
   STATUS      current
   DESCRIPTION
       ""
   ::= { gs2326pplusNASPortStatus 2 }

gs2326pplusNASPortStatusClientsEntry OBJECT-TYPE
   SYNTAX      Gs2326pplusNASPortStatusClientsEntry
   MAX-ACCESS  not-accessible
   STATUS      current
   DESCRIPTION
       ""
   INDEX    { gs2326pplusNASPortConfigPort,
		gs2326pplusNASClientsIndex}
   ::= { gs2326pplusNASPortStatusClientsTable 1 }

Gs2326pplusNASPortStatusClientsEntry ::= SEQUENCE {
   gs2326pplusNASClientsIndex  	                  		    Integer32,
   gs2326pplusNASClientsIdentity							DisplayString,
   gs2326pplusNASClientsMACAddress  	                  	DisplayString,
   gs2326pplusNASClientsVlanID		              			Integer32,
   gs2326pplusNASClientsState	              				DisplayString,
   gs2326pplusNASClientsLastAuth	                  		DisplayString,
   gs2326pplusNASRxClientsEAPOLTotal  	                  	Counter32,
   gs2326pplusNASRxClientsEAPOLResponseID	              	Counter32,
   gs2326pplusNASRxClientsEAPOLResponses	              	Counter32,
   gs2326pplusNASRxClientsEAPOLStart	                  	Counter32,
   gs2326pplusNASRxClientsEAPOLLogoff                    	Counter32,
   gs2326pplusNASRxClientsEAPOLInvalidType               	Counter32,
   gs2326pplusNASRxClientsEAPOLInvalidLength             	Counter32,
   gs2326pplusNASTxClientsEAPOLTotal                     	Counter32,
   gs2326pplusNASTxClientsEAPOLRequestID                 	Counter32,
   gs2326pplusNASTxClientsEAPOLRequests                  	Counter32,
   gs2326pplusNASRxBackendServerClientsAccessChallenges  	Counter32,
   gs2326pplusNASRxBackendServerClientsOtherRequests     	Counter32,
   gs2326pplusNASRxBackendServerClientsAuthSuccesses     	Counter32,
   gs2326pplusNASRxBackendServerClientsAuthFailures      	Counter32,
   gs2326pplusNASTxBackendServerClientsResponses         	Counter32
}

gs2326pplusNASClientsIndex OBJECT-TYPE
   SYNTAX      Integer32(1..255)
   MAX-ACCESS  not-accessible
   STATUS      current
   DESCRIPTION
       "Entry of client table in the port."
   ::= { gs2326pplusNASPortStatusClientsEntry 1 }

gs2326pplusNASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2326pplusNASPortStatusClientsEntry 2 }

gs2326pplusNASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2326pplusNASPortStatusClientsEntry 3 }

gs2326pplusNASClientsVlanID OBJECT-TYPE
   SYNTAX      Integer32(1..4095)
   MAX-ACCESS  read-only
   STATUS      current
   DESCRIPTION
       "This column holds the VLAN ID that the corresponding client is currently
	   secured through the Port Security module."
   ::= { gs2326pplusNASPortStatusClientsEntry 4 }

gs2326pplusNASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2326pplusNASPortStatusClientsEntry 5 }

gs2326pplusNASClientsLastAuth OBJECT-TYPE
   SYNTAX      DisplayString
   MAX-ACCESS  read-only
   STATUS      current
   DESCRIPTION
       "Shows the date and time of the last authentication of the client."
   ::= { gs2326pplusNASPortStatusClientsEntry 6 }

gs2326pplusNASRxClientsEAPOLTotal OBJECT-TYPE
   SYNTAX      Counter32
   MAX-ACCESS  read-only
   STATUS      current
   DESCRIPTION
       "The number of valid EAPOL frames of any type that have been received by the switch."
   ::= { gs2326pplusNASPortStatusClientsEntry 7 }

gs2326pplusNASRxClientsEAPOLResponseID OBJECT-TYPE
   SYNTAX      Counter32
   MAX-ACCESS  read-only
   STATUS      current
   DESCRIPTION
       "The number of valid EAPOL Response Identity frames that have been received by the switch."
   ::= { gs2326pplusNASPortStatusClientsEntry 8 }

gs2326pplusNASRxClientsEAPOLResponses OBJECT-TYPE
   SYNTAX      Counter32
   MAX-ACCESS  read-only
   STATUS      current
   DESCRIPTION
       "The number of valid EAPOL response frames (other than Response Identity frames)
	   that have been received by the switch."
   ::= { gs2326pplusNASPortStatusClientsEntry 9 }

gs2326pplusNASRxClientsEAPOLStart OBJECT-TYPE
   SYNTAX      Counter32
   MAX-ACCESS  read-only
   STATUS      current
   DESCRIPTION
       "The number of EAPOL Start frames that have been received by the switch."
   ::= { gs2326pplusNASPortStatusClientsEntry 10 }

gs2326pplusNASRxClientsEAPOLLogoff OBJECT-TYPE
   SYNTAX      Counter32
   MAX-ACCESS  read-only
   STATUS      current
   DESCRIPTION
       "The number of valid EAPOL Logoff frames that have been received by the switch."
   ::= { gs2326pplusNASPortStatusClientsEntry 11 }

gs2326pplusNASRxClientsEAPOLInvalidType OBJECT-TYPE
   SYNTAX      Counter32
   MAX-ACCESS  read-only
   STATUS      current
   DESCRIPTION
       "The number of EAPOL frames that have been received by the switch in which
	   the frame type is not recognized."
   ::= { gs2326pplusNASPortStatusClientsEntry 12 }

gs2326pplusNASRxClientsEAPOLInvalidLength OBJECT-TYPE
   SYNTAX      Counter32
   MAX-ACCESS  read-only
   STATUS      current
   DESCRIPTION
       "The number of EAPOL frames that have been received by the switch in which the
	   Packet Body Length field is invalid."
   ::= { gs2326pplusNASPortStatusClientsEntry 13 }

gs2326pplusNASTxClientsEAPOLTotal OBJECT-TYPE
   SYNTAX      Counter32
   MAX-ACCESS  read-only
   STATUS      current
   DESCRIPTION
       "The number of EAPOL frames of any type that have been transmitted by the switch."
   ::= { gs2326pplusNASPortStatusClientsEntry 14 }

gs2326pplusNASTxClientsEAPOLRequestID OBJECT-TYPE
   SYNTAX      Counter32
   MAX-ACCESS  read-only
   STATUS      current
   DESCRIPTION
       "The number of EAPOL Request Identity frames that have been transmitted by the switch."
   ::= { gs2326pplusNASPortStatusClientsEntry 15 }

gs2326pplusNASTxClientsEAPOLRequests OBJECT-TYPE
   SYNTAX      Counter32
   MAX-ACCESS  read-only
   STATUS      current
   DESCRIPTION
       "The number of valid EAPOL Request frames (other than Request Identity frames)
	   that have been transmitted by the switch."
   ::= { gs2326pplusNASPortStatusClientsEntry 16 }

gs2326pplusNASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2326pplusNASPortStatusClientsEntry 17 }

gs2326pplusNASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2326pplusNASPortStatusClientsEntry 18 }

gs2326pplusNASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2326pplusNASPortStatusClientsEntry 19 }

gs2326pplusNASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2326pplusNASPortStatusClientsEntry 20 }

gs2326pplusNASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2326pplusNASPortStatusClientsEntry 21 }


gs2326pplusMaintenance                                           OBJECT IDENTIFIER ::= { lancomGS2326Pplus  4 }

gs2326pplusRestartDevice OBJECT-TYPE
   SYNTAX      INTEGER { disable(0), enable(1) }
   MAX-ACCESS  read-write
   STATUS      current
   DESCRIPTION
       "default: 0
        0:none
        1:yes"
   ::= { gs2326pplusMaintenance 1 }

gs2326pplusColdRestartDevice OBJECT-TYPE
   SYNTAX      INTEGER { disable(0), enable(1) }
   MAX-ACCESS  read-write
   STATUS      current
   DESCRIPTION
       "default: 0
        0:none
        1:yes"
   ::= { gs2326pplusMaintenance 1500 }

gs2326pplusFirmware                                         OBJECT IDENTIFIER ::= { gs2326pplusMaintenance 2 }

gs2326pplusFirmwareIpAddress OBJECT-TYPE
   SYNTAX       IpAddress
   MAX-ACCESS   read-write
   STATUS       current
   DESCRIPTION
        "Get/Set the firmware tftp server."
   ::= { gs2326pplusFirmware 1 }

gs2326pplusFirmwareFileName OBJECT-TYPE
   SYNTAX       DisplayString
   MAX-ACCESS   read-write
   STATUS       current
   DESCRIPTION
        "Get/Set the path and filename for firmware upgrading."
   ::= { gs2326pplusFirmware 2 }

gs2326pplusDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2326pplusFirmware 3 }

gs2326pplusSaveOrRestore                                         OBJECT IDENTIFIER ::= { gs2326pplusMaintenance 3 }

gs2326pplusFactoryDefaults OBJECT-TYPE
   SYNTAX      INTEGER { none(0), yes(1) }
   MAX-ACCESS  read-write
   STATUS      current
   DESCRIPTION
       "default: 0
        0:none
        1:yes"
   ::= { gs2326pplusSaveOrRestore 1 }

gs2326pplusSaveStart OBJECT-TYPE
   SYNTAX      INTEGER { none(0), yes(1) }
   MAX-ACCESS  read-write
   STATUS      current
   DESCRIPTION
       "default: 0
        0:none
        1:yes"
   ::= { gs2326pplusSaveOrRestore 2 }

gs2326pplusSaveUser OBJECT-TYPE
   SYNTAX      INTEGER { none(0), yes(1) }
   MAX-ACCESS  read-write
   STATUS      current
   DESCRIPTION
       "default: 0
        0:none
        1:yes"
   ::= { gs2326pplusSaveOrRestore 3 }

gs2326pplusRestoreUser OBJECT-TYPE
   SYNTAX      INTEGER { none(0), yes(1) }
   MAX-ACCESS  read-write
   STATUS      current
   DESCRIPTION
       "default: 0
        0:none
        1:yes"
   ::= { gs2326pplusSaveOrRestore 4 }


gs2326pplusExportOrImport                                        OBJECT IDENTIFIER ::= { gs2326pplusMaintenance 4 }

gs2326pplusExportIpAddress OBJECT-TYPE
   SYNTAX       IpAddress
   MAX-ACCESS   read-write
   STATUS       current
   DESCRIPTION
        "Get/Set the export tftp server."
   ::= { gs2326pplusExportOrImport 1 }

gs2326pplusExportConfigName OBJECT-TYPE
   SYNTAX       DisplayString
   MAX-ACCESS   read-write
   STATUS       current
   DESCRIPTION
       "Get/Set the export file path and name."
   ::= { gs2326pplusExportOrImport 2 }

gs2326pplusDoExportConfig OBJECT-TYPE
   SYNTAX       INTEGER{ doNothing(0), do(1) }
   MAX-ACCESS   read-write
   STATUS       current
   DESCRIPTION
        "Do export-config.
         Get this OID always return zero.
         1 - export."
   ::= { gs2326pplusExportOrImport 3 }

gs2326pplusImportIpAddress OBJECT-TYPE
   SYNTAX       IpAddress
   MAX-ACCESS   read-write
   STATUS       current
   DESCRIPTION
        "Get/Set the import tftp server."
   ::= { gs2326pplusExportOrImport 4 }

gs2326pplusImportConfigName OBJECT-TYPE
   SYNTAX      DisplayString
   MAX-ACCESS  read-write
   STATUS      current
   DESCRIPTION
       "Get/Set the import file path and name."
   ::= { gs2326pplusExportOrImport 5 }

gs2326pplusDoImportConfig OBJECT-TYPE
   SYNTAX       INTEGER{ doNothing(0), do(1) }
   MAX-ACCESS   read-write
   STATUS       current
   DESCRIPTION
        "Do export-config.
         Get this OID always return zero.
         1 - import."
   ::= { gs2326pplusExportOrImport 6 }

gs2326pplusDiagnostics                                           OBJECT IDENTIFIER ::= { gs2326pplusMaintenance 5 }

gs2326pplusPingIpAddress OBJECT-TYPE
   SYNTAX      IpAddress
   MAX-ACCESS  read-write
   STATUS      current
   DESCRIPTION
       " The destination IP Address. "
   ::= { gs2326pplusDiagnostics 1 }

gs2326pplusPingSize OBJECT-TYPE
   SYNTAX      Integer32(60..1400)
   MAX-ACCESS  read-write
   STATUS      current
   DESCRIPTION
       " Size of ICMP echo packet.
         range : 60-1400, default : 64. "
   ::= { gs2326pplusDiagnostics 2 }

gs2326pplusDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326pplusDiagnostics 3 }

gs2326pplusPingResult OBJECT-TYPE
   SYNTAX      DisplayString
   MAX-ACCESS  read-only
   STATUS      current
   DESCRIPTION
       " Show ping result. "
   ::= { gs2326pplusDiagnostics 4 }

gs2326pplusPing6IpAddress OBJECT-TYPE
   SYNTAX      DisplayString
   MAX-ACCESS  read-write
   STATUS      current
   DESCRIPTION
       " The destination IPv6 Address. "
   ::= { gs2326pplusDiagnostics 5 }

gs2326pplusPing6Size OBJECT-TYPE
   SYNTAX      Integer32(60..1400)
   MAX-ACCESS  read-write
   STATUS      current
   DESCRIPTION
       " Size of ICMP echo packet.
         range : 60-1400. "
   ::= { gs2326pplusDiagnostics 6 }

gs2326pplusDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326pplusDiagnostics 7 }

gs2326pplusPing6Result OBJECT-TYPE
   SYNTAX      DisplayString
   MAX-ACCESS  read-only
   STATUS      current
   DESCRIPTION
       " Show ping result. "
   ::= { gs2326pplusDiagnostics 8 }


gs2326pplusVeriPHY                                           OBJECT IDENTIFIER ::= { gs2326pplusDiagnostics 9 }

gs2326pplusVeriPHYTest OBJECT-TYPE
   SYNTAX      Integer32(1..4095)
   MAX-ACCESS  read-write
   STATUS      current
   DESCRIPTION
       "Run VeriPHY Cable Diagnostics.
        port, range : 0 - port number.
        0 : ALL "
   ::= { gs2326pplusVeriPHY 1 }

gs2326pplusVeriPHYTable OBJECT-TYPE
   SYNTAX      SEQUENCE OF GS2326PPLUSVeriPHYEntry
   MAX-ACCESS  not-accessible
   STATUS      current
   DESCRIPTION
       " "
   ::= { gs2326pplusVeriPHY 2 }

gs2326pplusVeriPHYEntry OBJECT-TYPE
   SYNTAX      GS2326PPLUSVeriPHYEntry
   MAX-ACCESS  not-accessible
   STATUS      current
   DESCRIPTION
       ""
   INDEX    { gs2326pplusVeriPHYPort  }
   ::= { gs2326pplusVeriPHYTable 1 }

GS2326PPLUSVeriPHYEntry ::= SEQUENCE {
   gs2326pplusVeriPHYPort        Integer32,
   gs2326pplusVeriPHYPairA       DisplayString,
   gs2326pplusVeriPHYLengthA     DisplayString,
   gs2326pplusVeriPHYPairB       DisplayString,
   gs2326pplusVeriPHYLengthB     DisplayString,
   gs2326pplusVeriPHYPairC       DisplayString,
   gs2326pplusVeriPHYLengthC     DisplayString,
   gs2326pplusVeriPHYPairD       DisplayString,
   gs2326pplusVeriPHYLengthD     DisplayString
}

gs2326pplusVeriPHYPort OBJECT-TYPE
   SYNTAX      Integer32(1..4095)
   MAX-ACCESS  not-accessible
   STATUS      current
   DESCRIPTION
       " The length (in meters) of the cable pair. "
   ::= { gs2326pplusVeriPHYEntry 1 }

gs2326pplusVeriPHYPairA OBJECT-TYPE
   SYNTAX      DisplayString
   MAX-ACCESS  read-only
   STATUS      current
   DESCRIPTION
       " The status of the cable pair. "
   ::= { gs2326pplusVeriPHYEntry 2 }

gs2326pplusVeriPHYLengthA OBJECT-TYPE
   SYNTAX      DisplayString
   MAX-ACCESS  read-only
   STATUS      current
   DESCRIPTION
       " The length (in meters) of the cable pair. "
   ::= { gs2326pplusVeriPHYEntry 3 }

gs2326pplusVeriPHYPairB OBJECT-TYPE
   SYNTAX      DisplayString
   MAX-ACCESS  read-only
   STATUS      current
   DESCRIPTION
       " The status of the cable pair. "
   ::= { gs2326pplusVeriPHYEntry 4 }

gs2326pplusVeriPHYLengthB OBJECT-TYPE
   SYNTAX      DisplayString
   MAX-ACCESS  read-only
   STATUS      current
   DESCRIPTION
       " The length (in meters) of the cable pair. "
   ::= { gs2326pplusVeriPHYEntry 5 }

gs2326pplusVeriPHYPairC OBJECT-TYPE
   SYNTAX      DisplayString
   MAX-ACCESS  read-only
   STATUS      current
   DESCRIPTION
       " The status of the cable pair. "
   ::= { gs2326pplusVeriPHYEntry 6 }

gs2326pplusVeriPHYLengthC OBJECT-TYPE
   SYNTAX      DisplayString
   MAX-ACCESS  read-only
   STATUS      current
   DESCRIPTION
       " The length (in meters) of the cable pair. "
   ::= { gs2326pplusVeriPHYEntry 7 }

gs2326pplusVeriPHYPairD OBJECT-TYPE
   SYNTAX      DisplayString
   MAX-ACCESS  read-only
   STATUS      current
   DESCRIPTION
       " The status of the cable pair. "
   ::= { gs2326pplusVeriPHYEntry 8 }

gs2326pplusVeriPHYLengthD OBJECT-TYPE
   SYNTAX      DisplayString
   MAX-ACCESS  read-only
   STATUS      current
   DESCRIPTION
       " The length (in meters) of the cable pair. "
   ::= { gs2326pplusVeriPHYEntry 9 }


------------------------------------------------------------------------------------------------------------------
gs2326pplusTrap                                                  OBJECT IDENTIFIER ::= { lancomGS2326Pplus  5 }

gs2326pplusTrapEvent                                             OBJECT IDENTIFIER ::= { gs2326pplusTrap 1 }

gs2326pplusEmergency NOTIFICATION-TYPE
  OBJECTS   { gs2326pplusInformation }
  STATUS        current
    DESCRIPTION
        "The severity level is Emergency. The system is unusable."
    ::= { gs2326pplusTrapEvent 1 }

gs2326pplusAlert NOTIFICATION-TYPE
  OBJECTS   { gs2326pplusInformation }
  STATUS        current
    DESCRIPTION
        "The severity level is Alert. The action must be taken immediately."
    ::= { gs2326pplusTrapEvent 2 }

gs2326pplusCritical NOTIFICATION-TYPE
  OBJECTS   { gs2326pplusInformation }
  STATUS        current
    DESCRIPTION
        "The severity level is Critical. Critical conditions."
    ::= { gs2326pplusTrapEvent 3 }

gs2326pplusError NOTIFICATION-TYPE
  OBJECTS   { gs2326pplusInformation }
  STATUS        current
    DESCRIPTION
        "The severity level is Error. Error conditions."
    ::= { gs2326pplusTrapEvent 4 }

gs2326pplusWarning NOTIFICATION-TYPE
  OBJECTS   { gs2326pplusInformation }
  STATUS        current
    DESCRIPTION
        "The severity level is Warning. Warning conditions."
    ::= { gs2326pplusTrapEvent 5 }

gs2326pplusNotice NOTIFICATION-TYPE
  OBJECTS   { gs2326pplusInformation }
  STATUS        current
    DESCRIPTION
        "The severity level is Notice. Normal but significant condition."
    ::= { gs2326pplusTrapEvent 6 }

gs2326pplusInformational NOTIFICATION-TYPE
  OBJECTS   { gs2326pplusInformation }
  STATUS        current
    DESCRIPTION
        "The severity level is Informational. Informational messages."
    ::= { gs2326pplusTrapEvent 7 }

gs2326pplusDebug NOTIFICATION-TYPE
  OBJECTS   { gs2326pplusInformation }
  STATUS        current
    DESCRIPTION
        "The severity level is Debug. debug-level messages."
    ::= { gs2326pplusTrapEvent 8 }

gs2326pplusTrapVariable                                          OBJECT IDENTIFIER ::= { gs2326pplusTrap 2 }

gs2326pplusInformation OBJECT-TYPE
    SYNTAX      DisplayString
    MAX-ACCESS  read-only
    STATUS      current
    DESCRIPTION
        "Trap information."
    ::= { gs2326pplusTrapVariable 1 }


END
