LANCOM-GS-2326P-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

lancom-systems MODULE-IDENTITY
        LAST-UPDATED "202002190000Z"
        ORGANIZATION "LANCOM Systems GmbH."
        CONTACT-INFO
            "Adenauerstrasse 20 / B2, 52146 Wuerselen, Germany
            Email: info@lancom.de
            TEL: +49 (0)2405 49936 0
            FAX: +49 (0)2405 49936 99"
        DESCRIPTION
            "The MIB module is for LANCOM Systems"
        ::= { enterprises 2356 }

switchingSystems                                                          OBJECT IDENTIFIER ::= { lancom-systems 800 }

gigabitEthernetSwitches                                             OBJECT IDENTIFIER ::= { switchingSystems 3 }

lancomGS2326P                                               OBJECT IDENTIFIER ::= { gigabitEthernetSwitches 2327 }

gs2326pSystem                                                OBJECT IDENTIFIER ::= { lancomGS2326P  1 }

gs2326pSystemInformation                                     OBJECT IDENTIFIER ::= { gs2326pSystem 1 }

gs2326pModelName OBJECT-TYPE
   SYNTAX       DisplayString
   MAX-ACCESS   read-only
   STATUS       current
   DESCRIPTION
       ""
 ::= { gs2326pSystemInformation 1 }

gs2326pBIOSVersion OBJECT-TYPE
   SYNTAX       DisplayString
   MAX-ACCESS   read-only
   STATUS       current
   DESCRIPTION
       ""
   ::= { gs2326pSystemInformation 2 }

gs2326pFirmwareVersion OBJECT-TYPE
   SYNTAX       DisplayString
   MAX-ACCESS   read-only
   STATUS       current
   DESCRIPTION
       ""
   ::= { gs2326pSystemInformation 3 }

gs2326pHardwareMechanicalVersion OBJECT-TYPE
   SYNTAX       DisplayString
   MAX-ACCESS   read-only
   STATUS       current
   DESCRIPTION
       ""
   ::= { gs2326pSystemInformation 4 }

gs2326pSerialNumber OBJECT-TYPE
   SYNTAX       DisplayString
   MAX-ACCESS   read-only
   STATUS       current
   DESCRIPTION
       ""
   ::= { gs2326pSystemInformation 5 }

gs2326pHostMACAddress OBJECT-TYPE
   SYNTAX       MacAddress
   MAX-ACCESS   read-only
   STATUS       current
   DESCRIPTION
       ""
   ::= { gs2326pSystemInformation 6 }

gs2326pConsoleBaudrate OBJECT-TYPE
   SYNTAX       DisplayString
   MAX-ACCESS   read-only
   STATUS       current
   DESCRIPTION
       ""
   ::= { gs2326pSystemInformation 7 }

gs2326pRAMSize OBJECT-TYPE
   SYNTAX       DisplayString
   MAX-ACCESS   read-only
   STATUS       current
   DESCRIPTION
       ""
   ::= { gs2326pSystemInformation 8 }

gs2326pFlashSize OBJECT-TYPE
   SYNTAX       DisplayString
   MAX-ACCESS   read-only
   STATUS       current
   DESCRIPTION
       ""
   ::= { gs2326pSystemInformation 9 }

gs2326pBridgeFDBSize OBJECT-TYPE
   SYNTAX       DisplayString
   MAX-ACCESS   read-only
   STATUS       current
   DESCRIPTION
       ""
   ::= { gs2326pSystemInformation 10 }

gs2326pTransmitQueue OBJECT-TYPE
   SYNTAX       DisplayString
   MAX-ACCESS   read-only
   STATUS       current
   DESCRIPTION
       ""
   ::= { gs2326pSystemInformation 11 }

gs2326pMaximumFrameSize OBJECT-TYPE
   SYNTAX       DisplayString
   MAX-ACCESS   read-only
   STATUS       current
   DESCRIPTION
       ""
   ::= { gs2326pSystemInformation 12 }

gs2326pCPULoad OBJECT-TYPE
   SYNTAX       DisplayString
   MAX-ACCESS   read-only
   STATUS       current
   DESCRIPTION
       ""
   ::= { gs2326pSystemInformation 13 }

gs2326pSystemDescription OBJECT-TYPE
   SYNTAX       DisplayString
   MAX-ACCESS   read-only
   STATUS       current
   DESCRIPTION
       ""
   ::= { gs2326pSystemInformation 21 }

gs2326pLocation OBJECT-TYPE
   SYNTAX       DisplayString
   MAX-ACCESS   read-only
   STATUS       current
   DESCRIPTION
       ""
   ::= { gs2326pSystemInformation 22 }

gs2326pContact OBJECT-TYPE
   SYNTAX       DisplayString
   MAX-ACCESS   read-only
   STATUS       current
   DESCRIPTION
       ""
   ::= { gs2326pSystemInformation 23 }

gs2326pDeviceName OBJECT-TYPE
   SYNTAX       DisplayString
   MAX-ACCESS   read-only
   STATUS       current
   DESCRIPTION
       ""
   ::= { gs2326pSystemInformation 24 }

gs2326pSystemDate OBJECT-TYPE
   SYNTAX       DisplayString
   MAX-ACCESS   read-only
   STATUS       current
   DESCRIPTION
       ""
   ::= { gs2326pSystemInformation 25 }

gs2326pSystemUptime OBJECT-TYPE
   SYNTAX       DisplayString
   MAX-ACCESS   read-only
   STATUS       current
   DESCRIPTION
       ""
   ::= { gs2326pSystemInformation 26 }

gs2326pSystemIPv4Address OBJECT-TYPE
   SYNTAX       DisplayString
   MAX-ACCESS   read-only
   STATUS       current
   DESCRIPTION
       ""
   ::= { gs2326pSystemInformation 27 }

gs2326pSystemIPv4SubnetMask OBJECT-TYPE
   SYNTAX       DisplayString
   MAX-ACCESS   read-only
   STATUS       current
   DESCRIPTION
       ""
   ::= { gs2326pSystemInformation 28 }

gs2326pSystemIPv4Gateway OBJECT-TYPE
   SYNTAX       DisplayString
   MAX-ACCESS   read-only
   STATUS       current
   DESCRIPTION
       ""
   ::= { gs2326pSystemInformation 29 }

gs2326pIPv6LinkLocalAddress OBJECT-TYPE
   SYNTAX       DisplayString
   MAX-ACCESS   read-only
   STATUS       current
   DESCRIPTION
       ""
   ::= { gs2326pSystemInformation 30 }

gs2326pIPv6Address OBJECT-TYPE
   SYNTAX       DisplayString
   MAX-ACCESS   read-only
   STATUS       current
   DESCRIPTION
       ""
   ::= { gs2326pSystemInformation 31 }

gs2326pIPv6Prefix OBJECT-TYPE
   SYNTAX       DisplayString
   MAX-ACCESS   read-only
   STATUS       current
   DESCRIPTION
       ""
   ::= { gs2326pSystemInformation 32 }

gs2326pIPv6Gateway OBJECT-TYPE
   SYNTAX       DisplayString
   MAX-ACCESS   read-only
   STATUS       current
   DESCRIPTION
       ""
   ::= { gs2326pSystemInformation 33 }

gs2326pLargestFreeMemBlock OBJECT-TYPE
   SYNTAX       Integer32
   MAX-ACCESS   read-only
   STATUS       current
   DESCRIPTION
       "Largest free memory block in Kb"
   ::= { gs2326pSystemInformation 1500 }

gs2326pMemFree  OBJECT-TYPE
   SYNTAX       Integer32
   MAX-ACCESS   read-only
   STATUS       current
   DESCRIPTION
       "Free memory in Kb"
   ::= { gs2326pSystemInformation 1501 }

gs2326pSystemTime                                            OBJECT IDENTIFIER ::= { gs2326pSystem 2 }

gs2326pSystemTimeManual                                      OBJECT IDENTIFIER ::= { gs2326pSystemTime 1 }

gs2326pSystemTimeManualClockSource OBJECT-TYPE
   SYNTAX	INTEGER {useLocal(0),useNTP(1)}
   MAX-ACCESS   read-write
   STATUS       current
   DESCRIPTION
       "default: 0,
        0 : Use Local Settings,
        1 : Use NTP Server."
   ::= { gs2326pSystemTimeManual 1 }

gs2326pSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { gs2326pSystemTimeManual 2 }

gs2326pSystemTimeManualTimeZoneOffset OBJECT-TYPE
   SYNTAX       INTEGER(-720..780)
   MAX-ACCESS   read-write
   STATUS       current
   DESCRIPTION
       "Get/Set the NTP Time Zone.
        The value range is between -720 and 780 (minutes)."
   ::= { gs2326pSystemTimeManual 3 }

gs2326pSystemTimeManualDaylightSavings OBJECT-TYPE
   SYNTAX       INTEGER { disable(0), enable(1) }
   MAX-ACCESS   read-write
   STATUS       current
   DESCRIPTION
       "default: 0,
        0 : Disable,
        1 : Enable."
   ::= { gs2326pSystemTimeManual 4 }

gs2326pSystemTimeManualTimeSetOffset OBJECT-TYPE
   SYNTAX       Integer32(1..1440)
   MAX-ACCESS   read-write
   STATUS       current
   DESCRIPTION
       "Get/Set the Daylight Saving Time.
        The value range is between 1 and 1440 (minutes),
        Default : 60 (minutes)."
   ::= { gs2326pSystemTimeManual 5 }

gs2326pSystemTimeManualDaylightSavingsType OBJECT-TYPE
   SYNTAX       INTEGER { byDates(0), recurring(1) }
   MAX-ACCESS   read-write
   STATUS       current
   DESCRIPTION
       "default: 0,
        0 : By dates,
        1 : Recurring."
   ::= { gs2326pSystemTimeManual 6 }

gs2326pSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326pSystemTimeManual 7 }

gs2326pSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { gs2326pSystemTimeManual 8 }

gs2326pSystemTimeManualDaylightSavingsRecurringDayFrom OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day From.
        0 : Sun, 1 : Mon, 2 : Tue, 3 : Wed, 4 : Thu, 5 : Fri, 6 : Sat."
   ::= { gs2326pSystemTimeManual 9 }

gs2326pSystemTimeManualDaylightSavingsRecurringWeekFrom OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week From.
        1 : first week, 2, 3, 4, 5 : last week"
   ::= { gs2326pSystemTimeManual 10 }

gs2326pSystemTimeManualDaylightSavingsRecurringMonthFrom OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { gs2326pSystemTimeManual 11 }

gs2326pSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326pSystemTimeManual 12 }

gs2326pSystemTimeManualDaylightSavingsRecurringDayTo OBJECT-TYPE
   SYNTAX      INTEGER {
                        sunday(0),
                        monday(1),
                        tuseday(2),
                        wednesday(3),
                        thursday(4),
                        friday(5),
                        saturday(6)
                        }
   MAX-ACCESS   read-write
   STATUS       current
   DESCRIPTION
       "Get/Set the Daylight Saving Time Day To.
        0 : Sun, 1 : Mon, 2 : Tue, 3 : Wed, 4 : Thu, 5 : Fri, 6 : Sat."
   ::= { gs2326pSystemTimeManual 13 }

gs2326pSystemTimeManualDaylightSavingsRecurringWeekTo OBJECT-TYPE
   SYNTAX       INTEGER{
                        firstWeek(1),
                        secondWeek(2),
                        thirdWeek(3),
                        fourthWeek(4),
                        listWeek(5)
                        }
   MAX-ACCESS   read-write
   STATUS       current
   DESCRIPTION
       "Get/Set the Daylight Saving Time Week To.
        1 : first week, 2, 3, 4, 5 : last week"
   ::= { gs2326pSystemTimeManual 14 }

gs2326pSystemTimeManualDaylightSavingsRecurringMonthTo OBJECT-TYPE
   SYNTAX      INTEGER {
                        jan(1),
                        feb(2),
                        mar(3),
                        apr(4),
                        may(5),
                        jun(6),
                        jul(7),
                        aug(8),
                        sep(9),
                        oct(10),
                        nov(11),
                        dec(12)
                        }
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { gs2326pSystemTimeManual 15 }

gs2326pSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { gs2326pSystemTimeManual 16 }

gs2326pSystemTimeNTP                                     OBJECT IDENTIFIER ::= { gs2326pSystemTime 2 }

gs2326pSystemTimeNTPTable OBJECT-TYPE
   SYNTAX      SEQUENCE OF GS2326PSystemTimeNTPEntry
   MAX-ACCESS  not-accessible
   STATUS      current
   DESCRIPTION
       " "
   ::= { gs2326pSystemTimeNTP 1 }

gs2326pSystemTimeNTPEntry OBJECT-TYPE
   SYNTAX      GS2326PSystemTimeNTPEntry
   MAX-ACCESS  not-accessible
   STATUS      current
   DESCRIPTION
       ""
   INDEX    { gs2326pSystemTimeNTPIndex  }
   ::= { gs2326pSystemTimeNTPTable 1 }

GS2326PSystemTimeNTPEntry ::= SEQUENCE {
   gs2326pSystemTimeNTPIndex             Integer32,
   gs2326pSystemTimeNTPServerIPType      INTEGER,
   gs2326pSystemTimeNTPServer            DisplayString,
   gs2326pSystemTimeNTPCurrentMode       INTEGER
}

gs2326pSystemTimeNTPIndex OBJECT-TYPE
   SYNTAX      Integer32(1..5)
   MAX-ACCESS  not-accessible
   STATUS      current
   DESCRIPTION
       " The index of the ntp entry. "
   ::= { gs2326pSystemTimeNTPEntry 1 }

gs2326pSystemTimeNTPServerIPType OBJECT-TYPE
   SYNTAX       INTEGER { ipv4(0), ipv6(1) }
   MAX-ACCESS   read-write
   STATUS       current
   DESCRIPTION
       "Default: 0,
        0 : IPv4,
        1 : IPv6."
   ::= { gs2326pSystemTimeNTPEntry 2 }

gs2326pSystemTimeNTPServer OBJECT-TYPE
   SYNTAX       DisplayString
   MAX-ACCESS   read-write
   STATUS       current
   DESCRIPTION
       "Get/Set the NTP Time Server1. You can use the IP address or domain name."
   ::= { gs2326pSystemTimeNTPEntry 3 }

gs2326pSystemTimeNTPCurrentMode OBJECT-TYPE
   SYNTAX      INTEGER { empty(0), active(1), edit(2), delete(3) }
   MAX-ACCESS  read-write
   STATUS      current
   DESCRIPTION
       " 0: Empty
        1: Active
        2: Edit
        3: Delete"
   ::= { gs2326pSystemTimeNTPEntry 4 }

gs2326pSystemTimeNTPRequestInterval OBJECT-TYPE
   SYNTAX       INTEGER(60..999999999)
   MAX-ACCESS   read-write
   STATUS       current
   DESCRIPTION
       "Get/Set the NTP Request Interval.
        Default : 86400.
        The value range is between 60 and 999999999 (seconds)."
   ::= { gs2326pSystemTimeNTP 2 }

gs2326pSystemTimeNTPTriesNumber OBJECT-TYPE
   SYNTAX       INTEGER(0..999999999)
   MAX-ACCESS   read-write
   STATUS       current
   DESCRIPTION
       "Get/Set the NTP Number of tries.
        Default : 4.
        The value range is between 0 and 999999999."
   ::= { gs2326pSystemTimeNTP 3 }


gs2326pSystemAccount                                         OBJECT IDENTIFIER ::= { gs2326pSystem 3 }

gs2326pSystemAccountUsers                                    OBJECT IDENTIFIER ::= { gs2326pSystemAccount 1 }

gs2326pSystemAccountUserCreate OBJECT-TYPE
   SYNTAX       INTEGER { none(0), create(1) }
   MAX-ACCESS   read-write
   STATUS       current
   DESCRIPTION
       "default: 0
        0 : None  (read only)
        1 : Create a user account"
   ::= { gs2326pSystemAccountUsers 1 }

gs2326pSystemAccountUsersTable OBJECT-TYPE
   SYNTAX      SEQUENCE OF GS2326PSystemAccountUsersEntry
   MAX-ACCESS  not-accessible
   STATUS      current
   DESCRIPTION
       " "
   ::= { gs2326pSystemAccountUsers 2 }

gs2326pSystemAccountUsersEntry OBJECT-TYPE
   SYNTAX      GS2326PSystemAccountUsersEntry
   MAX-ACCESS  not-accessible
   STATUS      current
   DESCRIPTION
       ""
   INDEX    { gs2326pUserIndex  }
   ::= { gs2326pSystemAccountUsersTable 1 }


GS2326PSystemAccountUsersEntry ::= SEQUENCE {
   gs2326pUserIndex              Integer32 ,
   gs2326pUserName               DisplayString,
   gs2326pPassword               DisplayString,
   gs2326pUserPrivilegeLevel     Integer32 ,
   gs2326pAccountUserRowStatus   INTEGER
}


gs2326pUserIndex OBJECT-TYPE
   SYNTAX      Integer32 (1..20)
   MAX-ACCESS  not-accessible
   STATUS      current
   DESCRIPTION
       " "
   ::= { gs2326pSystemAccountUsersEntry 1 }

gs2326pUserName OBJECT-TYPE
   SYNTAX      DisplayString (SIZE (1..32))
   MAX-ACCESS  read-write
   STATUS      current
   DESCRIPTION
       "Please use a combination of letters, numbers and underscores"
   ::= { gs2326pSystemAccountUsersEntry 2 }

gs2326pPassword OBJECT-TYPE
   SYNTAX      DisplayString (SIZE (1..32))
   MAX-ACCESS  read-write
   STATUS      current
   DESCRIPTION
       "Please use ASCII printable code except Quotation mark, Colon (punctuation), Less-than sign, Greater-than sign, At sign, Question mark and Space (punctuation)"
   ::= { gs2326pSystemAccountUsersEntry 3 }

gs2326pUserPrivilegeLevel OBJECT-TYPE
   SYNTAX      Integer32 (1..15)
   MAX-ACCESS  read-write
   STATUS      current
   DESCRIPTION
       "default:1
        User privilege level range : 1 - 15"
   ::= { gs2326pSystemAccountUsersEntry 4 }

gs2326pAccountUserRowStatus OBJECT-TYPE
   SYNTAX      INTEGER { active(1), notInservice(2), edit(3), destroy(4), undo(5) }
   MAX-ACCESS  read-write
   STATUS      current
   DESCRIPTION
       " 1: active
        2: notInservice
        3: edit
        4: destroy
        5: undo"
   ::= { gs2326pSystemAccountUsersEntry 5 }

gs2326pSystemAccountUsersSuperUserPassword OBJECT-TYPE
   SYNTAX      OCTET STRING (SIZE (0..32))
   MAX-ACCESS read-write
   STATUS      current
   DESCRIPTION
        "Super-User Password"
   ::= { gs2326pSystemAccountUsers 1500 }

gs2326pSystemAccountEnforcePasswordRules OBJECT-TYPE
   SYNTAX       INTEGER { yes(0), no(1) }
   MAX-ACCESS   read-write
   STATUS       current
   DESCRIPTION
       "default: 0
        0 : Do not enforce rules
        1 : enforce rules"
   ::= { gs2326pSystemAccountUsers 1501 }

gs2326pSystemAccountPrivilegeLevel                           OBJECT IDENTIFIER ::= { gs2326pSystemAccount 2 }

gs2326pAccountPrivilegeLevel OBJECT-TYPE
   SYNTAX      Integer32 (1..15)
   MAX-ACCESS  read-write
   STATUS      current
   DESCRIPTION
       "Default:15, Range : 1-15. "
   ::= { gs2326pSystemAccountPrivilegeLevel 1 }

gs2326pAggregationPrivilegeLevel OBJECT-TYPE
   SYNTAX      Integer32 (1..15)
   MAX-ACCESS  read-write
   STATUS      current
   DESCRIPTION
       "Default:15, Range : 1-15. "
   ::= { gs2326pSystemAccountPrivilegeLevel 2 }

gs2326pDiagnosticsPrivilegeLevel OBJECT-TYPE
   SYNTAX      Integer32 (1..15)
   MAX-ACCESS  read-write
   STATUS      current
   DESCRIPTION
       "Default:15, Range : 1-15. "
   ::= { gs2326pSystemAccountPrivilegeLevel 3 }

gs2326pEEEPrivilegeLevel OBJECT-TYPE
   SYNTAX      Integer32 (1..15)
   MAX-ACCESS  read-write
   STATUS      current
   DESCRIPTION
       "Default:15, Range : 1-15. "
   ::= { gs2326pSystemAccountPrivilegeLevel 4 }

gs2326pEasyportPrivilegeLevel OBJECT-TYPE
   SYNTAX      Integer32 (1..15)
   MAX-ACCESS  read-write
   STATUS      current
   DESCRIPTION
       "Default:15, Range : 1-15. "
   ::= { gs2326pSystemAccountPrivilegeLevel 9 }

gs2326pGARPPrivilegeLevel OBJECT-TYPE
   SYNTAX      Integer32 (1..15)
   MAX-ACCESS  read-write
   STATUS      current
   DESCRIPTION
       "Default:15, Range : 1-15. "
   ::= { gs2326pSystemAccountPrivilegeLevel 10 }

gs2326pGVRPPrivilegeLevel OBJECT-TYPE
   SYNTAX      Integer32 (1..15)
   MAX-ACCESS  read-write
   STATUS      current
   DESCRIPTION
       "Default:15, Range : 1-15. "
   ::= { gs2326pSystemAccountPrivilegeLevel 11 }

gs2326pIPPrivilegeLevel OBJECT-TYPE
   SYNTAX      Integer32 (1..15)
   MAX-ACCESS  read-write
   STATUS      current
   DESCRIPTION
       "Default:15, Range : 1-15. "
   ::= { gs2326pSystemAccountPrivilegeLevel 12 }

gs2326pIPMCSnoopingPrivilegeLevel OBJECT-TYPE
   SYNTAX      Integer32 (1..15)
   MAX-ACCESS  read-write
   STATUS      current
   DESCRIPTION
       "Default:15, Range : 1-15. "
   ::= { gs2326pSystemAccountPrivilegeLevel 13 }

gs2326pLACPPrivilegeLevel OBJECT-TYPE
   SYNTAX      Integer32 (1..15)
   MAX-ACCESS  read-write
   STATUS      current
   DESCRIPTION
       "Default:15, Range : 1-15. "
   ::= { gs2326pSystemAccountPrivilegeLevel 14 }

gs2326pLLDPPrivilegeLevel OBJECT-TYPE
   SYNTAX      Integer32 (1..15)
   MAX-ACCESS  read-write
   STATUS      current
   DESCRIPTION
       "Default:15, Range : 1-15. "
   ::= { gs2326pSystemAccountPrivilegeLevel 15 }

gs2326pLLDPMEDPrivilegeLevel OBJECT-TYPE
   SYNTAX      Integer32 (1..15)
   MAX-ACCESS  read-write
   STATUS      current
   DESCRIPTION
       "Default:15, Range : 1-15. "
   ::= { gs2326pSystemAccountPrivilegeLevel 16 }

gs2326pLoopProtectPrivilegeLevel OBJECT-TYPE
   SYNTAX      Integer32 (1..15)
   MAX-ACCESS  read-write
   STATUS      current
   DESCRIPTION
       "Default:15, Range : 1-15. "
   ::= { gs2326pSystemAccountPrivilegeLevel 17 }

gs2326pMACTablePrivilegeLevel OBJECT-TYPE
   SYNTAX      Integer32 (1..15)
   MAX-ACCESS  read-write
   STATUS      current
   DESCRIPTION
       "Default:15, Range : 1-15. "
   ::= { gs2326pSystemAccountPrivilegeLevel 18 }

gs2326pMVRPrivilegeLevel OBJECT-TYPE
   SYNTAX      Integer32 (1..15)
   MAX-ACCESS  read-write
   STATUS      current
   DESCRIPTION
       "Default:15, Range : 1-15. "
   ::= { gs2326pSystemAccountPrivilegeLevel 22 }

gs2326pMaintenancePrivilegeLevel OBJECT-TYPE
   SYNTAX      Integer32 (1..15)
   MAX-ACCESS  read-write
   STATUS      current
   DESCRIPTION
       "Default:15, Range : 1-15. "
   ::= { gs2326pSystemAccountPrivilegeLevel 24 }

gs2326pMirroringPrivilegeLevel OBJECT-TYPE
   SYNTAX      Integer32 (1..15)
   MAX-ACCESS  read-write
   STATUS      current
   DESCRIPTION
       "Default:15, Range : 1-15. "
   ::= { gs2326pSystemAccountPrivilegeLevel 25 }

gs2326pPortsPrivilegeLevel OBJECT-TYPE
   SYNTAX      Integer32 (1..15)
   MAX-ACCESS  read-write
   STATUS      current
   DESCRIPTION
       "Default:15, Range : 1-15. "
   ::= { gs2326pSystemAccountPrivilegeLevel 27 }

gs2326pPrivateVLANsPrivilegeLevel OBJECT-TYPE
   SYNTAX      Integer32 (1..15)
   MAX-ACCESS  read-write
   STATUS      current
   DESCRIPTION
       "Default:15, Range : 1-15. "
   ::= { gs2326pSystemAccountPrivilegeLevel 28 }

gs2326pQoSPrivilegeLevel OBJECT-TYPE
   SYNTAX      Integer32 (1..15)
   MAX-ACCESS  read-write
   STATUS      current
   DESCRIPTION
       "Default:15, Range : 1-15. "
   ::= { gs2326pSystemAccountPrivilegeLevel 29 }

gs2326pSFlowPrivilegeLevel OBJECT-TYPE
   SYNTAX      Integer32 (1..15)
   MAX-ACCESS  read-write
   STATUS      current
   DESCRIPTION
       "Default:15, Range : 1-15. "
   ::= { gs2326pSystemAccountPrivilegeLevel 30 }

gs2326pSMTPPrivilegeLevel OBJECT-TYPE
   SYNTAX      Integer32 (1..15)
   MAX-ACCESS  read-write
   STATUS      current
   DESCRIPTION
       "Default:15, Range : 1-15. "
   ::= { gs2326pSystemAccountPrivilegeLevel 31 }

gs2326pSNMPPrivilegeLevel OBJECT-TYPE
   SYNTAX      Integer32 (1..15)
   MAX-ACCESS  read-write
   STATUS      current
   DESCRIPTION
       "Default:15, Range : 1-15. "
   ::= { gs2326pSystemAccountPrivilegeLevel 32 }

gs2326pSecurityPrivilegeLevel OBJECT-TYPE
   SYNTAX      Integer32 (1..15)
   MAX-ACCESS  read-write
   STATUS      current
   DESCRIPTION
       "Default:15, Range : 1-15. "
   ::= { gs2326pSystemAccountPrivilegeLevel 33 }

gs2326pSingleIPPrivilegeLevel OBJECT-TYPE
   SYNTAX      Integer32 (1..15)
   MAX-ACCESS  read-write
   STATUS      current
   DESCRIPTION
       "Default:15, Range : 1-15. "
   ::= { gs2326pSystemAccountPrivilegeLevel 34 }

gs2326pSpanningTreePrivilegeLevel OBJECT-TYPE
   SYNTAX      Integer32 (1..15)
   MAX-ACCESS  read-write
   STATUS      current
   DESCRIPTION
       "Default:15, Range : 1-15. "
   ::= { gs2326pSystemAccountPrivilegeLevel 35 }

gs2326pSystemPrivilegeLevel OBJECT-TYPE
   SYNTAX      Integer32 (1..15)
   MAX-ACCESS  read-write
   STATUS      current
   DESCRIPTION
       "Default:15, Range : 1-15. "
   ::= { gs2326pSystemAccountPrivilegeLevel 36 }

gs2326pTrapEventPrivilegeLevel OBJECT-TYPE
   SYNTAX      Integer32 (1..15)
   MAX-ACCESS  read-write
   STATUS      current
   DESCRIPTION
       "Default:15, Range : 1-15. "
   ::= { gs2326pSystemAccountPrivilegeLevel 37 }

gs2326pUPnPPrivilegeLevel OBJECT-TYPE
   SYNTAX      Integer32 (1..15)
   MAX-ACCESS  read-write
   STATUS      current
   DESCRIPTION
       "Default:15, Range : 1-15. "
   ::= { gs2326pSystemAccountPrivilegeLevel 38 }

gs2326pVCLPrivilegeLevel OBJECT-TYPE
   SYNTAX      Integer32 (1..15)
   MAX-ACCESS  read-write
   STATUS      current
   DESCRIPTION
       "Default:15, Range : 1-15. "
   ::= { gs2326pSystemAccountPrivilegeLevel 39 }

gs2326pVLANsPrivilegeLevel OBJECT-TYPE
   SYNTAX      Integer32 (1..15)
   MAX-ACCESS  read-write
   STATUS      current
   DESCRIPTION
       "Default:15, Range : 1-15. "
   ::= { gs2326pSystemAccountPrivilegeLevel 41 }

gs2326pVoiceVLANPrivilegeLevel OBJECT-TYPE
   SYNTAX      Integer32 (1..15)
   MAX-ACCESS  read-write
   STATUS      current
   DESCRIPTION
       "Default:15, Range : 1-15. "
   ::= { gs2326pSystemAccountPrivilegeLevel 42 }

gs2326pPOEPrivilegeLevel OBJECT-TYPE
   SYNTAX      Integer32 (1..15)
   MAX-ACCESS  read-write
   STATUS      current
   DESCRIPTION
       "Default:15, Range : 1-15. "
   ::= { gs2326pSystemAccountPrivilegeLevel 43 }


gs2326pIP                                                    OBJECT IDENTIFIER ::= { gs2326pSystem 4 }

gs2326pIPv4                                                  OBJECT IDENTIFIER ::= { gs2326pIP 1 }

gs2326pIPv4Configured                                                  OBJECT IDENTIFIER ::= { gs2326pIPv4 1 }

gs2326pIpv4DHCPClient OBJECT-TYPE
   SYNTAX      INTEGER { disable(0), enable(1) }
   MAX-ACCESS  read-write
   STATUS      current
   DESCRIPTION
       "default:0
       0: disable
       1: enable"
   ::= { gs2326pIPv4Configured 1 }

gs2326pIPv4Address OBJECT-TYPE
   SYNTAX      IpAddress
   MAX-ACCESS  read-write
   STATUS      current
   DESCRIPTION
       ""
   ::= { gs2326pIPv4Configured 2 }

gs2326pIPv4Mask OBJECT-TYPE
   SYNTAX      IpAddress
   MAX-ACCESS  read-write
   STATUS      current
   DESCRIPTION
       ""
   ::= { gs2326pIPv4Configured 3 }

gs2326pIPv4Gateway OBJECT-TYPE
   SYNTAX      IpAddress
   MAX-ACCESS  read-write
   STATUS      current
   DESCRIPTION
       ""
   ::= { gs2326pIPv4Configured 4 }

gs2326pIPv4VLANId OBJECT-TYPE
   SYNTAX      Integer32(1..4094)
   MAX-ACCESS  read-write
   STATUS      current
   DESCRIPTION
       "default:1"
   ::= { gs2326pIPv4Configured 5 }

gs2326pIPv4DNSServer OBJECT-TYPE
   SYNTAX      IpAddress
   MAX-ACCESS  read-write
   STATUS      current
   DESCRIPTION
       ""
   ::= { gs2326pIPv4Configured 6 }

gs2326pIPv4DNSProxy OBJECT-TYPE
   SYNTAX      INTEGER { disable(0), enable(1) }
   MAX-ACCESS  read-write
   STATUS      current
   DESCRIPTION
       "0:disable, 1:enable "
   ::= { gs2326pIPv4Configured 7 }

gs2326pIPv4Current                                                  OBJECT IDENTIFIER ::= { gs2326pIPv4 2 }

gs2326pIpv4CurrentDHCPClient OBJECT-TYPE
   SYNTAX      INTEGER { none(0), renew(1) }
   MAX-ACCESS  read-write
   STATUS      current
   DESCRIPTION
       "default:0
       0: none (for read)
       1: renew"
   ::= { gs2326pIPv4Current 1 }

gs2326pIPv4CurrentAddress OBJECT-TYPE
   SYNTAX      IpAddress
   MAX-ACCESS  read-only
   STATUS      current
   DESCRIPTION
       ""
   ::= { gs2326pIPv4Current 2 }

gs2326pIPv4CurrentMask OBJECT-TYPE
   SYNTAX      IpAddress
   MAX-ACCESS  read-only
   STATUS      current
   DESCRIPTION
       ""
   ::= { gs2326pIPv4Current 3 }

gs2326pIPv4CurrentGateway OBJECT-TYPE
   SYNTAX      IpAddress
   MAX-ACCESS  read-only
   STATUS      current
   DESCRIPTION
       ""
   ::= { gs2326pIPv4Current 4 }

gs2326pIPv4CurrentVLANId OBJECT-TYPE
   SYNTAX      Integer32(1..4094)
   MAX-ACCESS  read-only
   STATUS      current
   DESCRIPTION
       "default:1"
   ::= { gs2326pIPv4Current 5 }

gs2326pIPv4CurrentDNSServer OBJECT-TYPE
   SYNTAX      IpAddress
   MAX-ACCESS  read-only
   STATUS      current
   DESCRIPTION
       ""
   ::= { gs2326pIPv4Current 6 }


gs2326pIPv6                                                  OBJECT IDENTIFIER ::= { gs2326pIP 2 }

gs2326pIPv6Configured                                                  OBJECT IDENTIFIER ::= { gs2326pIPv6 1 }

gs2326pIpv6AutoConfiguration OBJECT-TYPE
   SYNTAX      INTEGER { disable(0), enable(1) }
   MAX-ACCESS  read-write
   STATUS      current
   DESCRIPTION
       "default:0
       0: disable
       1: enable"
   ::= { gs2326pIPv6Configured 1 }

gs2326pIpv6Address OBJECT-TYPE
   SYNTAX      DisplayString (SIZE (0..30))
   MAX-ACCESS  read-write
   STATUS      current
   DESCRIPTION
       ""
   ::= { gs2326pIPv6Configured 2 }

gs2326pIpv6Prefix OBJECT-TYPE
   SYNTAX      Integer32 (1..128)
   MAX-ACCESS  read-write
   STATUS      current
   DESCRIPTION
       "default: 96"
   ::= { gs2326pIPv6Configured 3 }

gs2326pIpv6Gateway OBJECT-TYPE
   SYNTAX      DisplayString (SIZE (0..30))
   MAX-ACCESS  read-write
   STATUS      current
   DESCRIPTION
       " "
   ::= { gs2326pIPv6Configured 4 }

gs2326pIPv6Current                                                  OBJECT IDENTIFIER ::= { gs2326pIPv6 2 }

gs2326pIpv6CurrentAutoConfiguration OBJECT-TYPE
   SYNTAX      INTEGER { disable(0), enable(1) }
   MAX-ACCESS  read-only
   STATUS      current
   DESCRIPTION
       "default:0
       0: disable
       1: enable"
   ::= { gs2326pIPv6Current 1 }

gs2326pIpv6CurrentAddress OBJECT-TYPE
   SYNTAX      DisplayString (SIZE (0..30))
   MAX-ACCESS  read-only
   STATUS      current
   DESCRIPTION
       ""
   ::= { gs2326pIPv6Current 2 }


gs2326pIpv6CurrentLinkLocalAddress OBJECT-TYPE
   SYNTAX      DisplayString(SIZE (0..30))
   MAX-ACCESS  read-only
   STATUS      current
   DESCRIPTION
       ""
   ::= { gs2326pIPv6Current 3 }


gs2326pIpv6CurrentPrefix OBJECT-TYPE
   SYNTAX      DisplayString(SIZE (0..64))
   MAX-ACCESS  read-only
   STATUS      current
   DESCRIPTION
       ""
   ::= { gs2326pIPv6Current 4 }

gs2326pIpv6CurrentGateway OBJECT-TYPE
   SYNTAX      DisplayString (SIZE (0..30))
   MAX-ACCESS  read-only
   STATUS      current
   DESCRIPTION
       " "
   ::= { gs2326pIPv6Current 5 }

gs2326pSyslog                                                OBJECT IDENTIFIER ::= { gs2326pSystem 5 }

gs2326pSyslogConf                                            OBJECT IDENTIFIER ::= { gs2326pSyslog 1 }

gs2326pServerMode OBJECT-TYPE
   SYNTAX      INTEGER { disable(0), enable(1) }
   MAX-ACCESS  read-write
   STATUS      current
   DESCRIPTION
       "default: 0
       0: disable
       1: enable "
   ::= { gs2326pSyslogConf 1 }

gs2326pServerAddress1 OBJECT-TYPE
   SYNTAX      IpAddress
   MAX-ACCESS  read-write
   STATUS      current
   DESCRIPTION
       " "
   ::= { gs2326pSyslogConf 2 }

gs2326pServerAddress2 OBJECT-TYPE
   SYNTAX      IpAddress
   MAX-ACCESS  read-write
   STATUS      current
   DESCRIPTION
       " "
   ::= { gs2326pSyslogConf 3 }

gs2326pSyslogLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6 (Info)
       0: Emergency
       1: Alert
       2: Critical
       3: Error
       4: Warning
       5: Notice
       6: Info
       7: Debug"
   ::= { gs2326pSyslogConf 4 }

gs2326pSyslogDetailedInfo                                    OBJECT IDENTIFIER ::= { gs2326pSyslog 2 }

gs2326pSyslogDetailedInfoClear OBJECT-TYPE
   SYNTAX      INTEGER { none(0), clear(1) }
   MAX-ACCESS  read-write
   STATUS      current
   DESCRIPTION
      "default: 0
       0 : None  (read only)
       1 : Clear Syslog"
   ::= { gs2326pSyslogDetailedInfo 1 }

gs2326pSyslogDetailedInfoTable OBJECT-TYPE
  SYNTAX      SEQUENCE OF GS2326PSyslogDetailedInfoEntry
  MAX-ACCESS  not-accessible
  STATUS      current
  DESCRIPTION
           " "
       ::= { gs2326pSyslogDetailedInfo 2 }

gs2326pSyslogDetailedInfoEntry OBJECT-TYPE
   SYNTAX      GS2326PSyslogDetailedInfoEntry
   MAX-ACCESS  not-accessible
   STATUS      current
   DESCRIPTION
           ""
   INDEX    { gs2326pSyslogDetailedInfoIndex  }
   ::= { gs2326pSyslogDetailedInfoTable 1 }

GS2326PSyslogDetailedInfoEntry ::= SEQUENCE {
   gs2326pSyslogDetailedInfoIndex       Integer32,
   gs2326pSyslogDetailedInfoLevel       DisplayString,
   gs2326pSyslogDetailedInfoTime        DisplayString,
   gs2326pSyslogDetailedInfoMessage     DisplayString
}

gs2326pSyslogDetailedInfoIndex OBJECT-TYPE
   SYNTAX      Integer32(1..1024)
   MAX-ACCESS  not-accessible
   STATUS      current
   DESCRIPTION
       " "
   ::= { gs2326pSyslogDetailedInfoEntry 1 }

gs2326pSyslogDetailedInfoLevel OBJECT-TYPE
   SYNTAX      DisplayString
   MAX-ACCESS  read-only
   STATUS      current
   DESCRIPTION
       " "
   ::= { gs2326pSyslogDetailedInfoEntry 2 }

gs2326pSyslogDetailedInfoTime OBJECT-TYPE
   SYNTAX      DisplayString(SIZE (0..20))
   MAX-ACCESS  read-only
   STATUS      current
   DESCRIPTION
       " "
   ::= { gs2326pSyslogDetailedInfoEntry 3 }

gs2326pSyslogDetailedInfoMessage OBJECT-TYPE
   SYNTAX      DisplayString
   MAX-ACCESS  read-only
   STATUS      current
   DESCRIPTION
       " "
   ::= { gs2326pSyslogDetailedInfoEntry 4 }


gs2326pSnmp                                                OBJECT IDENTIFIER ::= { gs2326pSystem 6 }

gs2326pSnmpConf                                            OBJECT IDENTIFIER ::= { gs2326pSnmp 1 }

gs2326pGetCommunityMode OBJECT-TYPE
   SYNTAX       INTEGER { disable(0), enable(1) }
   MAX-ACCESS   read-write
   STATUS       current
   DESCRIPTION
       "Get/Set the get-community mode of the SNMP.
        default : 1, 0: disable, 1: enable. "
   ::= { gs2326pSnmpConf 1 }

gs2326pGetCommunity OBJECT-TYPE
   SYNTAX       DisplayString
   MAX-ACCESS   read-write
   STATUS       current
   DESCRIPTION
       "Get/Set the get-community of the SNMP."
   ::= { gs2326pSnmpConf 2 }

gs2326pSetCommunityMode OBJECT-TYPE
   SYNTAX       INTEGER { disable(0), enable(1) }
   MAX-ACCESS   read-write
   STATUS       current
   DESCRIPTION
       "Get/Set the set-community mode of the SNMP.
        default : 1, 0: disable, 1: enable. "
   ::= { gs2326pSnmpConf 3 }

gs2326pSetCommunity OBJECT-TYPE
   SYNTAX       DisplayString
   MAX-ACCESS   read-write
   STATUS       current
   DESCRIPTION
       "Get/Set the set-community of the SNMP."
   ::= { gs2326pSnmpConf 4 }

gs2326pGetCommunityConfTable OBJECT-TYPE
   SYNTAX      SEQUENCE OF GS2326PGetCommunityConfEntry
   MAX-ACCESS  not-accessible
   STATUS      current
   DESCRIPTION
       " Show get-community of the SNMP. "
   ::= { gs2326pSnmpConf 5 }

gs2326pGetCommunityConfEntry OBJECT-TYPE
   SYNTAX      GS2326PGetCommunityConfEntry
   MAX-ACCESS  not-accessible
   STATUS      current
   DESCRIPTION
       ""
   INDEX    { gs2326pCommunityConfIndex  }
   ::= { gs2326pGetCommunityConfTable 1 }

GS2326PGetCommunityConfEntry ::= SEQUENCE {
   gs2326pCommunityConfIndex				Integer32,
   gs2326pCommunityConfGetCommunity			DisplayString
}

gs2326pCommunityConfIndex OBJECT-TYPE
   SYNTAX      Integer32(1..4095)
   MAX-ACCESS  not-accessible
   STATUS      current
   DESCRIPTION
       " index, range : 1 - 5. "
   ::= { gs2326pGetCommunityConfEntry 1 }

gs2326pCommunityConfGetCommunity OBJECT-TYPE
   SYNTAX      DisplayString
   MAX-ACCESS  read-write
   STATUS      current
   DESCRIPTION
       " Get/Set the get-community of the SNMP."
   ::= { gs2326pGetCommunityConfEntry 2 }

gs2326pTrapHostConfTable OBJECT-TYPE
   SYNTAX      SEQUENCE OF GS2326PTrapHostConfEntry
   MAX-ACCESS  not-accessible
   STATUS      current
   DESCRIPTION
       "A list of trap host entry. The numbers of entries are given by the value of gs2326pTrapHostConfNumber."
   ::= { gs2326pSnmpConf 6 }

gs2326pTrapHostConfEntry OBJECT-TYPE
   SYNTAX      GS2326PTrapHostConfEntry
   MAX-ACCESS  not-accessible
   STATUS      current
   DESCRIPTION
       "This is the entry information for trap host."
   INDEX    { gs2326pTrapHostConfIndex  }
   ::= { gs2326pTrapHostConfTable 1 }

GS2326PTrapHostConfEntry ::= SEQUENCE {
    gs2326pTrapHostConfIndex             Integer32,
    gs2326pTrapHostConfVersion           INTEGER,
    gs2326pTrapHostConfIPType            INTEGER,
    gs2326pTrapHostConfIP                DisplayString,
    gs2326pTrapHostConfPort              Integer32,
    gs2326pTrapHostConfCommunity         DisplayString,
    gs2326pTrapHostConfSeverityLevel     INTEGER,
    gs2326pTrapHostConfSecurityLevel     INTEGER,
    gs2326pTrapHostConfAuthPtc           INTEGER,
    gs2326pTrapHostConfAuthPassword      DisplayString,
    gs2326pTrapHostConfPrivPtc           INTEGER,
    gs2326pTrapHostConfPrivPassword      DisplayString,
    gs2326pTrapHostConfCurrentMode       INTEGER
}

gs2326pTrapHostConfIndex OBJECT-TYPE
   SYNTAX      Integer32(1..6)
   MAX-ACCESS  not-accessible
   STATUS      current
   DESCRIPTION
       " The index of the trap host entry. "
   ::= { gs2326pTrapHostConfEntry 1 }

gs2326pTrapHostConfVersion OBJECT-TYPE
   SYNTAX       INTEGER { snmpv2c(2), snmpv3(3) }
   MAX-ACCESS   read-write
   STATUS       current
   DESCRIPTION
       "The version of the Trap PDU. Version : 2(SNMPv2c), 3(SNMPv3)"
   ::= { gs2326pTrapHostConfEntry 2 }

gs2326pTrapHostConfIPType OBJECT-TYPE
   SYNTAX       INTEGER { ipv4(4), ipv6(6) }
   MAX-ACCESS   read-write
   STATUS       current
   DESCRIPTION
       "Server IP Type. Default: 4,
        4 : IPv4,
        6 : IPv6."
   ::= { gs2326pTrapHostConfEntry 3 }

gs2326pTrapHostConfIP OBJECT-TYPE
   SYNTAX       DisplayString
   MAX-ACCESS   read-write
   STATUS       current
   DESCRIPTION
       "This is the IP of the trap host."
   ::= { gs2326pTrapHostConfEntry 4 }

gs2326pTrapHostConfPort OBJECT-TYPE
   SYNTAX       Integer32(1..65535)
   MAX-ACCESS   read-write
   STATUS       current
   DESCRIPTION
       "This is the receiving-port number of the trap host.
        range : 1 - 65535."
   ::= { gs2326pTrapHostConfEntry 5 }

gs2326pTrapHostConfCommunity OBJECT-TYPE
   SYNTAX       DisplayString (SIZE (1..32))
   MAX-ACCESS   read-write
   STATUS       current
   DESCRIPTION
       "The community/security name for the trap PDU."
   ::= { gs2326pTrapHostConfEntry 6 }

gs2326pTrapHostConfSeverityLevel	OBJECT-TYPE
   SYNTAX      INTEGER {
                    emergency(0),
                    alert(1),
                    critical(2),
                    error(3),
                    warning(4),
                    notice(5),
                    info(6),
                    debug(7)
                }
   MAX-ACCESS   read-write
   STATUS       current
   DESCRIPTION
       "The Severity Level.
        0 : Emerg, 1 : Alert, 2 : Critical, 3 : Error, 4 : Warning, 5 : Notice, 6 : Info, 7 : Debug."
	::= { gs2326pTrapHostConfEntry 7 }

gs2326pTrapHostConfSecurityLevel	OBJECT-TYPE
   SYNTAX       INTEGER { noAuthNoPriv(1), authNoPriv(2), authPriv(3) }
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { gs2326pTrapHostConfEntry 8 }

gs2326pTrapHostConfAuthPtc	OBJECT-TYPE
   SYNTAX       INTEGER { md5(1), sha(2) }
   MAX-ACCESS   read-write
   STATUS       current
   DESCRIPTION
       "Authentication Protocol, there are SHA and MD5 supported presently.
        1 : MD5, 2 : SHA."
	::= { gs2326pTrapHostConfEntry 9 }

gs2326pTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { gs2326pTrapHostConfEntry 10 }

gs2326pTrapHostConfPrivPtc	OBJECT-TYPE
   SYNTAX       INTEGER { des(1) }
   MAX-ACCESS   read-write
   STATUS       current
   DESCRIPTION
       "This is the Privacy Protocol, which is used in AuthPriv. Only supports DES.
        An empty string will be returned if the security level is not 3(AuthPriv).
        1 : DES."
	::= { gs2326pTrapHostConfEntry 11 }

gs2326pTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { gs2326pTrapHostConfEntry 12 }

gs2326pTrapHostConfCurrentMode OBJECT-TYPE
   SYNTAX       INTEGER { empty(0), active(1), edit(2), delete(3) }
   MAX-ACCESS   read-write
   STATUS       current
   DESCRIPTION
       "0:Empty, 1:Active mode, 2:Edit mode, 3:Delete."
   ::= { gs2326pTrapHostConfEntry 13 }


gs2326pSnmpSystem                                          OBJECT IDENTIFIER ::= { gs2326pSnmp 2 }

gs2326pSnmpState OBJECT-TYPE
   SYNTAX       INTEGER { disable(0), enable(1) }
   MAX-ACCESS   read-write
   STATUS       current
   DESCRIPTION
       "Get/Set the state of the SNMP.
        default : 1, 0: disable, 1: enable. "
   ::= { gs2326pSnmpSystem 1 }

gs2326pSnmpEngineID OBJECT-TYPE
   SYNTAX       OCTET STRING (SIZE(5..32))
   MAX-ACCESS   read-write
   STATUS       current
   DESCRIPTION
       "Get/Set the Engine ID of the SNMP.
        An SNMP engine's administratively-unique identifier."
   ::= { gs2326pSnmpSystem 2 }

gs2326pSnmpCommunities                                          OBJECT IDENTIFIER ::= { gs2326pSnmp 3 }

gs2326pSnmpCommunitiesCreate OBJECT-TYPE
   SYNTAX       INTEGER { none(0), create(1) }
   MAX-ACCESS   read-write
   STATUS       current
   DESCRIPTION
       "default: 0
        0 : None  (read only)
        1 : Create entry"
   ::= { gs2326pSnmpCommunities 1 }

gs2326pSnmpCommunitiesTable OBJECT-TYPE
   SYNTAX      SEQUENCE OF GS2326PSnmpCommunitiesEntry
   MAX-ACCESS  not-accessible
   STATUS      current
   DESCRIPTION
       " Create SNMPv1/v2 Communities entry."
   ::= { gs2326pSnmpCommunities 2 }

gs2326pSnmpCommunitiesEntry OBJECT-TYPE
   SYNTAX      GS2326PSnmpCommunitiesEntry
   MAX-ACCESS  not-accessible
   STATUS      current
   DESCRIPTION
       ""
   INDEX    { gs2326pSnmpCommunitiesIndex  }
   ::= { gs2326pSnmpCommunitiesTable 1 }

GS2326PSnmpCommunitiesEntry ::= SEQUENCE {
   gs2326pSnmpCommunitiesIndex          Integer32,
   gs2326pSnmpCommunitiesCommunity      DisplayString,
   gs2326pSnmpCommunitiesUserName       DisplayString,
   gs2326pSnmpCommunitiesSourceIP       IpAddress,
   gs2326pSnmpCommunitiesSourceMask     IpAddress,
   gs2326pSnmpCommunitiesRowStatus      INTEGER
}

gs2326pSnmpCommunitiesIndex OBJECT-TYPE
   SYNTAX      Integer32(1..4)
   MAX-ACCESS  not-accessible
   STATUS      current
   DESCRIPTION
       " "
   ::= { gs2326pSnmpCommunitiesEntry 1 }

gs2326pSnmpCommunitiesCommunity OBJECT-TYPE
   SYNTAX      DisplayString (SIZE (1..32))
   MAX-ACCESS  read-write
   STATUS      current
   DESCRIPTION
       "Up to 32 characters describing Community."
   ::= { gs2326pSnmpCommunitiesEntry 2 }

gs2326pSnmpCommunitiesUserName OBJECT-TYPE
   SYNTAX      DisplayString (SIZE (1..32))
   MAX-ACCESS  read-write
   STATUS      current
   DESCRIPTION
       " Up to 32 characters describing User Name. "
   ::= { gs2326pSnmpCommunitiesEntry 3 }

gs2326pSnmpCommunitiesSourceIP OBJECT-TYPE
   SYNTAX      IpAddress
   MAX-ACCESS  read-write
   STATUS      current
   DESCRIPTION
       " SNMP access source ip. "
   ::= { gs2326pSnmpCommunitiesEntry 4 }

gs2326pSnmpCommunitiesSourceMask OBJECT-TYPE
   SYNTAX      IpAddress
   MAX-ACCESS  read-write
   STATUS      current
   DESCRIPTION
       " SNMP access source address mask. "
   ::= { gs2326pSnmpCommunitiesEntry 5 }

gs2326pSnmpCommunitiesRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pSnmpCommunitiesEntry 6 }


gs2326pSnmpUsers                                          OBJECT IDENTIFIER ::= { gs2326pSnmp 4 }

gs2326pSnmpUsersCreate OBJECT-TYPE
   SYNTAX       INTEGER { none(0), create(1) }
   MAX-ACCESS   read-write
   STATUS       current
   DESCRIPTION
       "default: 0
        0 : None  (read only)
        1 : Create entry"
   ::= { gs2326pSnmpUsers 1 }

gs2326pSnmpUsersTable OBJECT-TYPE
   SYNTAX      SEQUENCE OF GS2326PSnmpUsersEntry
   MAX-ACCESS  not-accessible
   STATUS      current
   DESCRIPTION
       " Create SNMPv3 users entry."
   ::= { gs2326pSnmpUsers 2 }

gs2326pSnmpUsersEntry OBJECT-TYPE
   SYNTAX      GS2326PSnmpUsersEntry
   MAX-ACCESS  not-accessible
   STATUS      current
   DESCRIPTION
       ""
   INDEX    { gs2326pSnmpUsersIndex  }
   ::= { gs2326pSnmpUsersTable 1 }

GS2326PSnmpUsersEntry ::= SEQUENCE {
   gs2326pSnmpUsersIndex                    Integer32,
   gs2326pSnmpUsersUserName                 DisplayString,
   gs2326pSnmpUsersSecurityLevel            INTEGER,
   gs2326pSnmpUsersAuthenticationProtocol   INTEGER,
   gs2326pSnmpUsersAuthenticationPassword   DisplayString,
   gs2326pSnmpUsersPrivacyProtocol          INTEGER,
   gs2326pSnmpUsersPrivacyPassword          DisplayString,
   gs2326pSnmpUsersRowStatus                INTEGER
}

gs2326pSnmpUsersIndex OBJECT-TYPE
   SYNTAX      Integer32(1..10)
   MAX-ACCESS  not-accessible
   STATUS      current
   DESCRIPTION
       " "
   ::= { gs2326pSnmpUsersEntry 1 }

gs2326pSnmpUsersUserName OBJECT-TYPE
   SYNTAX      DisplayString (SIZE (1..32))
   MAX-ACCESS  read-write
   STATUS      current
   DESCRIPTION
       "Up to 32 characters describing User Name."
   ::= { gs2326pSnmpUsersEntry 2 }

gs2326pSnmpUsersSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2326pSnmpUsersEntry 3 }

gs2326pSnmpUsersAuthenticationProtocol OBJECT-TYPE
   SYNTAX      INTEGER { none(0), md5(1), sha(2) }
   MAX-ACCESS  read-write
   STATUS      current
   DESCRIPTION
       " 0: None.
         1: MD5.
         2: SHA "
   ::= { gs2326pSnmpUsersEntry 4 }

gs2326pSnmpUsersAuthenticationPassword OBJECT-TYPE
   SYNTAX      DisplayString
   MAX-ACCESS  read-write
   STATUS      current
   DESCRIPTION
       " Authentication Password, is used for authenticating. The return value is always '********'.
         If the authentication protocol is MD5, the length of password should be 8 ~ 32 characters.
         If the authentication protocol is SHA, the length of password should be 8 ~ 40 characters. "
   ::= { gs2326pSnmpUsersEntry 5 }

gs2326pSnmpUsersPrivacyProtocol OBJECT-TYPE
   SYNTAX      INTEGER { none(0), des(1), aes(2) }
   MAX-ACCESS  read-write
   STATUS      current
   DESCRIPTION
       " 0: None.
         1: DES.
         2: AES
         This is the Privacy Protocol, which is used in AuthPriv.
         An empty string will be returned if the security level is not 3(AuthPriv) "
   ::= { gs2326pSnmpUsersEntry 6 }

gs2326pSnmpUsersPrivacyPassword OBJECT-TYPE
   SYNTAX      DisplayString
   MAX-ACCESS  read-write
   STATUS      current
   DESCRIPTION
       " The password is Privacy Key.  The return value is always '********'.  This Key
        must be more than 8 characters, and less than 32 characters. "
   ::= { gs2326pSnmpUsersEntry 7 }

gs2326pSnmpUsersRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pSnmpUsersEntry 8 }


gs2326pSnmpGroups                                          OBJECT IDENTIFIER ::= { gs2326pSnmp 5 }

gs2326pSnmpGroupsCreate OBJECT-TYPE
   SYNTAX       INTEGER { none(0), create(1) }
   MAX-ACCESS   read-write
   STATUS       current
   DESCRIPTION
       "default: 0
        0 : None  (read only)
        1 : Create entry"
   ::= { gs2326pSnmpGroups 1 }

gs2326pSnmpGroupsTable OBJECT-TYPE
   SYNTAX      SEQUENCE OF GS2326PSnmpGroupsEntry
   MAX-ACCESS  not-accessible
   STATUS      current
   DESCRIPTION
       " Create SNMPv3 groups entry."
   ::= { gs2326pSnmpGroups 2 }

gs2326pSnmpGroupsEntry OBJECT-TYPE
   SYNTAX      GS2326PSnmpGroupsEntry
   MAX-ACCESS  not-accessible
   STATUS      current
   DESCRIPTION
       ""
   INDEX    { gs2326pSnmpGroupsIndex  }
   ::= { gs2326pSnmpGroupsTable 1 }

GS2326PSnmpGroupsEntry ::= SEQUENCE {
   gs2326pSnmpGroupsIndex           Integer32,
   gs2326pSnmpGroupsSecurityModel   INTEGER,
   gs2326pSnmpGroupsSecurityName    DisplayString,
   gs2326pSnmpGroupsGroupName       DisplayString,
   gs2326pSnmpGroupsRowStatus       INTEGER
}

gs2326pSnmpGroupsIndex OBJECT-TYPE
   SYNTAX      Integer32(1..14)
   MAX-ACCESS  not-accessible
   STATUS      current
   DESCRIPTION
       " "
   ::= { gs2326pSnmpGroupsEntry 1 }

gs2326pSnmpGroupsSecurityModel OBJECT-TYPE
   SYNTAX      INTEGER { v1(1), v2c(2), usm(3) }
   MAX-ACCESS  read-write
   STATUS      current
   DESCRIPTION
       " 1: v1.
         2: v2c.
         3: usm."
   ::= { gs2326pSnmpGroupsEntry 2 }

gs2326pSnmpGroupsSecurityName OBJECT-TYPE
   SYNTAX      DisplayString (SIZE (1..32))
   MAX-ACCESS  read-write
   STATUS      current
   DESCRIPTION
       "Up to 32 characters describing User Name."
   ::= { gs2326pSnmpGroupsEntry 3 }

gs2326pSnmpGroupsGroupName OBJECT-TYPE
   SYNTAX      DisplayString (SIZE (1..32))
   MAX-ACCESS  read-write
   STATUS      current
   DESCRIPTION
       "Up to 32 characters describing Group Name."
   ::= { gs2326pSnmpGroupsEntry 4 }

gs2326pSnmpGroupsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pSnmpGroupsEntry 5 }

gs2326pSnmpViews                                              OBJECT IDENTIFIER ::= { gs2326pSnmp 6 }

gs2326pSnmpViewsCreate OBJECT-TYPE
   SYNTAX       INTEGER { none(0), create(1) }
   MAX-ACCESS   read-write
   STATUS       current
   DESCRIPTION
       "default: 0
        0 : None  (read only)
        1 : Create entry"
   ::= { gs2326pSnmpViews 1 }

gs2326pSnmpViewsTable OBJECT-TYPE
   SYNTAX      SEQUENCE OF GS2326PSnmpViewsEntry
   MAX-ACCESS  not-accessible
   STATUS      current
   DESCRIPTION
       " Create SNMPv1/v2 Views entry."
   ::= { gs2326pSnmpViews 2 }

gs2326pSnmpViewsEntry OBJECT-TYPE
   SYNTAX      GS2326PSnmpViewsEntry
   MAX-ACCESS  not-accessible
   STATUS      current
   DESCRIPTION
       ""
   INDEX    { gs2326pSnmpViewsIndex  }
   ::= { gs2326pSnmpViewsTable 1 }

GS2326PSnmpViewsEntry ::= SEQUENCE {
   gs2326pSnmpViewsIndex        Integer32,
   gs2326pSnmpViewsName         DisplayString,
   gs2326pSnmpViewsType         INTEGER,
   gs2326pSnmpViewsOIDSubtree   DisplayString,
   gs2326pSnmpViewsRowStatus    INTEGER
}

gs2326pSnmpViewsIndex OBJECT-TYPE
   SYNTAX      Integer32(1..4)
   MAX-ACCESS  not-accessible
   STATUS      current
   DESCRIPTION
       " "
   ::= { gs2326pSnmpViewsEntry 1 }

gs2326pSnmpViewsName OBJECT-TYPE
   SYNTAX      DisplayString (SIZE (1..32))
   MAX-ACCESS  read-write
   STATUS      current
   DESCRIPTION
       "Up to 32 characters describing view Name."
   ::= { gs2326pSnmpViewsEntry 2 }

gs2326pSnmpViewsType OBJECT-TYPE
   SYNTAX      INTEGER { included(1), excluded(2) }
   MAX-ACCESS  read-write
   STATUS      current
   DESCRIPTION
       "1: included, An optional flag to indicate that this view subtree should be included.
	   2: excluded, An optional flag to indicate that this view subtree should be excluded."
   ::= { gs2326pSnmpViewsEntry 3 }

gs2326pSnmpViewsOIDSubtree OBJECT-TYPE
   SYNTAX      DisplayString (SIZE (1..128))
   MAX-ACCESS  read-write
   STATUS      current
   DESCRIPTION
       "The OID defining the root of the subtree to add to the named view."
   ::= { gs2326pSnmpViewsEntry 4 }

gs2326pSnmpViewsRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pSnmpViewsEntry 5 }


gs2326pSnmpAccess                                          OBJECT IDENTIFIER ::= { gs2326pSnmp 7 }

gs2326pSnmpAccessCreate OBJECT-TYPE
   SYNTAX       INTEGER { none(0), create(1) }
   MAX-ACCESS   read-write
   STATUS       current
   DESCRIPTION
       "default: 0
        0 : None  (read only)
        1 : Create entry"
   ::= { gs2326pSnmpAccess 1 }

gs2326pSnmpAccessTable OBJECT-TYPE
   SYNTAX      SEQUENCE OF GS2326PSnmpAccessEntry
   MAX-ACCESS  not-accessible
   STATUS      current
   DESCRIPTION
       " Create SNMPv3 Access entry."
   ::= { gs2326pSnmpAccess 2 }

gs2326pSnmpAccessEntry OBJECT-TYPE
   SYNTAX      GS2326PSnmpAccessEntry
   MAX-ACCESS  not-accessible
   STATUS      current
   DESCRIPTION
       ""
   INDEX    { gs2326pSnmpAccessIndex  }
   ::= { gs2326pSnmpAccessTable 1 }

GS2326PSnmpAccessEntry ::= SEQUENCE {
   gs2326pSnmpAccessIndex             Integer32,
   gs2326pSnmpAccessGroupName         DisplayString,
   gs2326pSnmpAccessSecurityModel     INTEGER,
   gs2326pSnmpAccessSecurityLevel     INTEGER,
   gs2326pSnmpAccessReadViewName      DisplayString,
   gs2326pSnmpAccessWriteViewName     DisplayString,
   gs2326pSnmpAccessRowStatus         INTEGER
}

gs2326pSnmpAccessIndex OBJECT-TYPE
   SYNTAX      Integer32(1..14)
   MAX-ACCESS  not-accessible
   STATUS      current
   DESCRIPTION
       " "
   ::= { gs2326pSnmpAccessEntry 1 }

gs2326pSnmpAccessGroupName OBJECT-TYPE
   SYNTAX      DisplayString (SIZE (1..32))
   MAX-ACCESS  read-write
   STATUS      current
   DESCRIPTION
       "Up to 32 characters describing Group Name."
   ::= { gs2326pSnmpAccessEntry 2 }

gs2326pSnmpAccessSecurityModel OBJECT-TYPE
   SYNTAX      INTEGER { any(0), v1(1), v2c(2), usm(3) }
   MAX-ACCESS  read-write
   STATUS      current
   DESCRIPTION
       " 0: any.
         1: v1.
         2: v2c.
         3: usm."
   ::= { gs2326pSnmpAccessEntry 3 }

gs2326pSnmpAccessSecurityLevel OBJECT-TYPE
   SYNTAX      INTEGER { noauthnopriv(1), authnopriv(2), authpriv(3) }
   MAX-ACCESS  read-write
   STATUS      current
   DESCRIPTION
       " 1: No authentication and no privacy.
         2: Authentication and no privacy.
         3: Authentication and privacy. "
   ::= { gs2326pSnmpAccessEntry 4 }

gs2326pSnmpAccessReadViewName OBJECT-TYPE
   SYNTAX      DisplayString (SIZE (1..32))
   MAX-ACCESS  read-write
   STATUS      current
   DESCRIPTION
       "Up to 32 characters describing Read View Name.
        None is reserved for Empty."
   ::= { gs2326pSnmpAccessEntry 5 }

gs2326pSnmpAccessWriteViewName OBJECT-TYPE
   SYNTAX      DisplayString (SIZE (1..32))
   MAX-ACCESS  read-write
   STATUS      current
   DESCRIPTION
       "Up to 32 characters describing Write View Name.
        None is reserved for Empty."
   ::= { gs2326pSnmpAccessEntry 6 }

gs2326pSnmpAccessRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pSnmpAccessEntry 7 }


----------------------------------------------------------------------------------------------------

gs2326pConfiguration                                         OBJECT IDENTIFIER ::= { lancomGS2326P  2 }

gs2326pPort                                                  OBJECT IDENTIFIER ::= { gs2326pConfiguration 1 }

gs2326pPortConfigurationTable OBJECT-TYPE
   SYNTAX      SEQUENCE OF GS2326PPortConfigurationEntry
   MAX-ACCESS  not-accessible
   STATUS      current
   DESCRIPTION
       " Show port configurations. "
   ::= { gs2326pPort 1 }

gs2326pPortConfigurationEntry OBJECT-TYPE
   SYNTAX      GS2326PPortConfigurationEntry
   MAX-ACCESS  not-accessible
   STATUS      current
   DESCRIPTION
       ""
   INDEX    { gs2326pPortConfPort  }
   ::= { gs2326pPortConfigurationTable 1 }

GS2326PPortConfigurationEntry ::= SEQUENCE {
   gs2326pPortConfPort                     Integer32,
   gs2326pPortConfPortMedia                DisplayString,
   gs2326pPortConfLink                     DisplayString,
   gs2326pPortConfCurrentSpeed             DisplayString,
   gs2326pPortConfSpeed                    INTEGER,
   gs2326pPortConfCurrentFlowControlRx     INTEGER,
   gs2326pPortConfCurrentFlowControlTx     INTEGER,
   gs2326pPortConfFlowControl              INTEGER,
   gs2326pPortConfMaxFrameSize             Integer32,
   gs2326pPortConfExcessiveCollisionMode   INTEGER,
   gs2326pPortConfPowerControl             INTEGER,
   gs2326pPortConfDescription              DisplayString
}

gs2326pPortConfPort OBJECT-TYPE
   SYNTAX      Integer32(1..4095)
   MAX-ACCESS  not-accessible
   STATUS      current
   DESCRIPTION
       " port, range : 1 - port number. "
   ::= { gs2326pPortConfigurationEntry 1 }

gs2326pPortConfPortMedia OBJECT-TYPE
   SYNTAX      DisplayString(SIZE (1..4))
   MAX-ACCESS  read-only
   STATUS      current
   DESCRIPTION
       " Show port media. "
   ::= { gs2326pPortConfigurationEntry 2 }

gs2326pPortConfLink OBJECT-TYPE
   SYNTAX      DisplayString(SIZE (2..4))
   MAX-ACCESS  read-only
   STATUS      current
   DESCRIPTION
       " The current link state. "
   ::= { gs2326pPortConfigurationEntry 3 }

gs2326pPortConfCurrentSpeed OBJECT-TYPE
   SYNTAX      DisplayString(SIZE (6..12))
   MAX-ACCESS  read-only
   STATUS      current
   DESCRIPTION
       " The current link speed of the port. "
   ::= { gs2326pPortConfigurationEntry 4 }

gs2326pPortConfSpeed OBJECT-TYPE
   SYNTAX      INTEGER {
                    disable(0),
                    auto(1),
                    speed10Half(2),
                    speed10Full(3),
                    speed100Half(4),
                    speed100Full(5),
                    speed1Gfull(6),
                    sfpAutoAMS(7),
                    speed100FXAMS(8),
                    speed1000XAMS(9),
                    speed100FX(10),
                    speed1000X(11)
                }
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { gs2326pPortConfigurationEntry 5 }

gs2326pPortConfCurrentFlowControlRx OBJECT-TYPE
   SYNTAX      INTEGER { disable(0), enable(1), noSupport(2) }
   MAX-ACCESS  read-only
   STATUS      current
   DESCRIPTION
       "0: disable
        1: enable
        2: no support.  "
   ::= { gs2326pPortConfigurationEntry 6 }

gs2326pPortConfCurrentFlowControlTx OBJECT-TYPE
   SYNTAX      INTEGER { disable(0), enable(1), noSupport(2) }
   MAX-ACCESS  read-only
   STATUS      current
   DESCRIPTION
       "0: disable
        1: enable
        2: no support.  "
   ::= { gs2326pPortConfigurationEntry 7 }

gs2326pPortConfFlowControl OBJECT-TYPE
   SYNTAX      INTEGER { disable(0), enable(1), noSupport(2) }
   MAX-ACCESS  read-write
   STATUS      current
   DESCRIPTION
       "default: 0,
        0: disable
        1: enable
        2: no support. "
   ::= { gs2326pPortConfigurationEntry 8 }

gs2326pPortConfMaxFrameSize OBJECT-TYPE
   SYNTAX      Integer32 (1518..9600)
   MAX-ACCESS  read-write
   STATUS      current
   DESCRIPTION
       "default: 9600 , range : 1518 - 9600 "
   ::= { gs2326pPortConfigurationEntry 9 }

gs2326pPortConfExcessiveCollisionMode OBJECT-TYPE
   SYNTAX      INTEGER { discard(0), restart(1), noSupport(2) }
   MAX-ACCESS  read-write
   STATUS      current
   DESCRIPTION
       "default: 0,
        Excessive Collision Mode :
        0: Discard,
        1: Restart,
        2: no support.
       "
   ::= { gs2326pPortConfigurationEntry 10 }

gs2326pPortConfPowerControl OBJECT-TYPE
   SYNTAX      INTEGER { disable(0), actiphy(1), dynamic(2), enable(3), noSupport(4) }
   MAX-ACCESS  read-write
   STATUS      current
   DESCRIPTION
       "default: 0,
        PowerControl :
        0: disable,
        1: Actiphy,
        2: Dynamic (perfectReach),
        3: Enable,
        4: no support.
       "
   ::= { gs2326pPortConfigurationEntry 11 }

gs2326pPortConfDescription OBJECT-TYPE
   SYNTAX      DisplayString
   MAX-ACCESS  read-write
   STATUS      current
   DESCRIPTION
       " Interface specific description.
         Up to 47 characters describing this interface. "
   ::= { gs2326pPortConfigurationEntry 12 }


gs2326pPortTrafficStatisticsTable OBJECT-TYPE
   SYNTAX      SEQUENCE OF GS2326PPortTrafficStatisticsEntry
   MAX-ACCESS  not-accessible
   STATUS      current
   DESCRIPTION
       " "
   ::= { gs2326pPort 2 }

gs2326pPortTrafficStatisticsEntry OBJECT-TYPE
   SYNTAX      GS2326PPortTrafficStatisticsEntry
   MAX-ACCESS  not-accessible
   STATUS      current
   DESCRIPTION
       ""
   INDEX    { gs2326pPortTrafficStatisticsPort  }
   ::= { gs2326pPortTrafficStatisticsTable 1 }

GS2326PPortTrafficStatisticsEntry ::= SEQUENCE {
   gs2326pPortTrafficStatisticsPort          Integer32,
   gs2326pPortTrafficStatisticsClear         INTEGER,
   gs2326pPortTrafficRxPackets               Counter64,
   gs2326pPortTrafficRxOctets                Counter64,
   gs2326pPortTrafficRxUnicast               Counter64,
   gs2326pPortTrafficRxMulticast             Counter64,
   gs2326pPortTrafficRxBroadcast             Counter64,
   gs2326pPortTrafficRxPause                 Counter64,
   gs2326pPortTrafficRx64Bytes               Counter64,
   gs2326pPortTrafficRx65to127Bytes          Counter64,
   gs2326pPortTrafficRx128to255Bytes         Counter64,
   gs2326pPortTrafficRx256to511Bytes         Counter64,
   gs2326pPortTrafficRx512to1023Bytes        Counter64,
   gs2326pPortTrafficRx1024to1526Bytes       Counter64,
   gs2326pPortTrafficRxExceecd1527Bytes      Counter64,
   gs2326pPortTrafficRxQ0                    Counter64,
   gs2326pPortTrafficRxQ1                    Counter64,
   gs2326pPortTrafficRxQ2                    Counter64,
   gs2326pPortTrafficRxQ3                    Counter64,
   gs2326pPortTrafficRxQ4                    Counter64,
   gs2326pPortTrafficRxQ5                    Counter64,
   gs2326pPortTrafficRxQ6                    Counter64,
   gs2326pPortTrafficRxQ7                    Counter64,
   gs2326pPortTrafficRxDrops                 Counter64,
   gs2326pPortTrafficRxCRCorAlignment        Counter64,
   gs2326pPortTrafficRxUndersize             Counter64,
   gs2326pPortTrafficRxOversize              Counter64,
   gs2326pPortTrafficRxFragments             Counter64,
   gs2326pPortTrafficRxJabber                Counter64,
   gs2326pPortTrafficRxFiltered              Counter64,
   gs2326pPortTrafficTxPackets               Counter64,
   gs2326pPortTrafficTxOctets                Counter64,
   gs2326pPortTrafficTxUnicast               Counter64,
   gs2326pPortTrafficTxMulticast             Counter64,
   gs2326pPortTrafficTxBroadcast             Counter64,
   gs2326pPortTrafficTxPause                 Counter64,
   gs2326pPortTrafficTx64Bytes               Counter64,
   gs2326pPortTrafficTx65to127Bytes          Counter64,
   gs2326pPortTrafficTx128to255Bytes         Counter64,
   gs2326pPortTrafficTx256to511Bytes         Counter64,
   gs2326pPortTrafficTx512to1023Bytes        Counter64,
   gs2326pPortTrafficTx1024to1526Bytes       Counter64,
   gs2326pPortTrafficTxExceecd1527Bytes      Counter64,
   gs2326pPortTrafficTxQ0                    Counter64,
   gs2326pPortTrafficTxQ1                    Counter64,
   gs2326pPortTrafficTxQ2                    Counter64,
   gs2326pPortTrafficTxQ3                    Counter64,
   gs2326pPortTrafficTxQ4                    Counter64,
   gs2326pPortTrafficTxQ5                    Counter64,
   gs2326pPortTrafficTxQ6                    Counter64,
   gs2326pPortTrafficTxQ7                    Counter64,
   gs2326pPortTrafficTxDrops                 Counter64,
   gs2326pPortTrafficTxLateOrExcColl         Counter64
}

gs2326pPortTrafficStatisticsPort OBJECT-TYPE
   SYNTAX      Integer32 (1..4095)
   MAX-ACCESS  not-accessible
   STATUS      current
   DESCRIPTION
       " "
   ::= { gs2326pPortTrafficStatisticsEntry 1 }

gs2326pPortTrafficStatisticsClear OBJECT-TYPE
   SYNTAX      INTEGER { disable(0), enable(1) }
   MAX-ACCESS  read-write
   STATUS      current
   DESCRIPTION
       " "
   ::= { gs2326pPortTrafficStatisticsEntry 2 }

gs2326pPortTrafficRxPackets OBJECT-TYPE
   SYNTAX      Counter64
   MAX-ACCESS  read-only
   STATUS      current
   DESCRIPTION
       " "
   ::= { gs2326pPortTrafficStatisticsEntry 3 }

gs2326pPortTrafficRxOctets OBJECT-TYPE
   SYNTAX      Counter64
   MAX-ACCESS  read-only
   STATUS      current
   DESCRIPTION
       " "
   ::= { gs2326pPortTrafficStatisticsEntry 4 }

gs2326pPortTrafficRxUnicast OBJECT-TYPE
   SYNTAX      Counter64
   MAX-ACCESS  read-only
   STATUS      current
   DESCRIPTION
       " "
   ::= { gs2326pPortTrafficStatisticsEntry 5 }

gs2326pPortTrafficRxMulticast OBJECT-TYPE
   SYNTAX      Counter64
   MAX-ACCESS  read-only
   STATUS      current
   DESCRIPTION
       " "
   ::= { gs2326pPortTrafficStatisticsEntry 6 }

gs2326pPortTrafficRxBroadcast OBJECT-TYPE
   SYNTAX      Counter64
   MAX-ACCESS  read-only
   STATUS      current
   DESCRIPTION
       " "
   ::= { gs2326pPortTrafficStatisticsEntry 7 }

gs2326pPortTrafficRxPause OBJECT-TYPE
   SYNTAX      Counter64
   MAX-ACCESS  read-only
   STATUS      current
   DESCRIPTION
       " "
   ::= { gs2326pPortTrafficStatisticsEntry 8 }

gs2326pPortTrafficRx64Bytes OBJECT-TYPE
   SYNTAX      Counter64
   MAX-ACCESS  read-only
   STATUS      current
   DESCRIPTION
       " "
   ::= { gs2326pPortTrafficStatisticsEntry 9 }

gs2326pPortTrafficRx65to127Bytes OBJECT-TYPE
   SYNTAX      Counter64
   MAX-ACCESS  read-only
   STATUS      current
   DESCRIPTION
       " "
   ::= { gs2326pPortTrafficStatisticsEntry 10 }

gs2326pPortTrafficRx128to255Bytes OBJECT-TYPE
   SYNTAX      Counter64
   MAX-ACCESS  read-only
   STATUS      current
   DESCRIPTION
       " "
   ::= { gs2326pPortTrafficStatisticsEntry 11 }

gs2326pPortTrafficRx256to511Bytes OBJECT-TYPE
   SYNTAX      Counter64
   MAX-ACCESS  read-only
   STATUS      current
   DESCRIPTION
       " "
   ::= { gs2326pPortTrafficStatisticsEntry 12 }

gs2326pPortTrafficRx512to1023Bytes OBJECT-TYPE
   SYNTAX      Counter64
   MAX-ACCESS  read-only
   STATUS      current
   DESCRIPTION
       " "
   ::= { gs2326pPortTrafficStatisticsEntry 13 }

gs2326pPortTrafficRx1024to1526Bytes OBJECT-TYPE
   SYNTAX      Counter64
   MAX-ACCESS  read-only
   STATUS      current
   DESCRIPTION
       " "
   ::= { gs2326pPortTrafficStatisticsEntry 14 }

gs2326pPortTrafficRxExceecd1527Bytes OBJECT-TYPE
   SYNTAX      Counter64
   MAX-ACCESS  read-only
   STATUS      current
   DESCRIPTION
       " "
   ::= { gs2326pPortTrafficStatisticsEntry 15 }

gs2326pPortTrafficRxQ0 OBJECT-TYPE
   SYNTAX      Counter64
   MAX-ACCESS  read-only
   STATUS      current
   DESCRIPTION
       " "
   ::= { gs2326pPortTrafficStatisticsEntry 16 }

gs2326pPortTrafficRxQ1 OBJECT-TYPE
   SYNTAX      Counter64
   MAX-ACCESS  read-only
   STATUS      current
   DESCRIPTION
       " "
   ::= { gs2326pPortTrafficStatisticsEntry 17 }

gs2326pPortTrafficRxQ2 OBJECT-TYPE
   SYNTAX      Counter64
   MAX-ACCESS  read-only
   STATUS      current
   DESCRIPTION
       " "
   ::= { gs2326pPortTrafficStatisticsEntry 18 }

gs2326pPortTrafficRxQ3 OBJECT-TYPE
   SYNTAX      Counter64
   MAX-ACCESS  read-only
   STATUS      current
   DESCRIPTION
       " "
   ::= { gs2326pPortTrafficStatisticsEntry 19 }

gs2326pPortTrafficRxQ4 OBJECT-TYPE
   SYNTAX      Counter64
   MAX-ACCESS  read-only
   STATUS      current
   DESCRIPTION
       " "
   ::= { gs2326pPortTrafficStatisticsEntry 20 }

gs2326pPortTrafficRxQ5 OBJECT-TYPE
   SYNTAX      Counter64
   MAX-ACCESS  read-only
   STATUS      current
   DESCRIPTION
       " "
   ::= { gs2326pPortTrafficStatisticsEntry 21 }

gs2326pPortTrafficRxQ6 OBJECT-TYPE
   SYNTAX      Counter64
   MAX-ACCESS  read-only
   STATUS      current
   DESCRIPTION
       " "
   ::= { gs2326pPortTrafficStatisticsEntry 22 }

gs2326pPortTrafficRxQ7 OBJECT-TYPE
   SYNTAX      Counter64
   MAX-ACCESS  read-only
   STATUS      current
   DESCRIPTION
       " "
   ::= { gs2326pPortTrafficStatisticsEntry 23 }

gs2326pPortTrafficRxDrops OBJECT-TYPE
   SYNTAX      Counter64
   MAX-ACCESS  read-only
   STATUS      current
   DESCRIPTION
       " "
   ::= { gs2326pPortTrafficStatisticsEntry 24 }

gs2326pPortTrafficRxCRCorAlignment OBJECT-TYPE
   SYNTAX      Counter64
   MAX-ACCESS  read-only
   STATUS      current
   DESCRIPTION
       " "
   ::= { gs2326pPortTrafficStatisticsEntry 25 }

gs2326pPortTrafficRxUndersize OBJECT-TYPE
   SYNTAX      Counter64
   MAX-ACCESS  read-only
   STATUS      current
   DESCRIPTION
       " "
   ::= { gs2326pPortTrafficStatisticsEntry 26 }

gs2326pPortTrafficRxOversize OBJECT-TYPE
   SYNTAX      Counter64
   MAX-ACCESS  read-only
   STATUS      current
   DESCRIPTION
       " "
   ::= { gs2326pPortTrafficStatisticsEntry 27 }

gs2326pPortTrafficRxFragments OBJECT-TYPE
   SYNTAX      Counter64
   MAX-ACCESS  read-only
   STATUS      current
   DESCRIPTION
       " "
   ::= { gs2326pPortTrafficStatisticsEntry 28 }

gs2326pPortTrafficRxJabber OBJECT-TYPE
   SYNTAX      Counter64
   MAX-ACCESS  read-only
   STATUS      current
   DESCRIPTION
       " "
   ::= { gs2326pPortTrafficStatisticsEntry 29 }

gs2326pPortTrafficRxFiltered OBJECT-TYPE
   SYNTAX      Counter64
   MAX-ACCESS  read-only
   STATUS      current
   DESCRIPTION
       " "
   ::= { gs2326pPortTrafficStatisticsEntry 30 }

gs2326pPortTrafficTxPackets OBJECT-TYPE
   SYNTAX      Counter64
   MAX-ACCESS  read-only
   STATUS      current
   DESCRIPTION
       " "
   ::= { gs2326pPortTrafficStatisticsEntry 31 }

gs2326pPortTrafficTxOctets OBJECT-TYPE
   SYNTAX      Counter64
   MAX-ACCESS  read-only
   STATUS      current
   DESCRIPTION
       " "
   ::= { gs2326pPortTrafficStatisticsEntry 32 }

gs2326pPortTrafficTxUnicast OBJECT-TYPE
   SYNTAX      Counter64
   MAX-ACCESS  read-only
   STATUS      current
   DESCRIPTION
       " "
   ::= { gs2326pPortTrafficStatisticsEntry 33 }

gs2326pPortTrafficTxMulticast OBJECT-TYPE
   SYNTAX      Counter64
   MAX-ACCESS  read-only
   STATUS      current
   DESCRIPTION
       " "
   ::= { gs2326pPortTrafficStatisticsEntry 34 }

gs2326pPortTrafficTxBroadcast OBJECT-TYPE
   SYNTAX      Counter64
   MAX-ACCESS  read-only
   STATUS      current
   DESCRIPTION
       " "
   ::= { gs2326pPortTrafficStatisticsEntry 35 }

gs2326pPortTrafficTxPause OBJECT-TYPE
   SYNTAX      Counter64
   MAX-ACCESS  read-only
   STATUS      current
   DESCRIPTION
       " "
   ::= { gs2326pPortTrafficStatisticsEntry 36 }

gs2326pPortTrafficTx64Bytes OBJECT-TYPE
   SYNTAX      Counter64
   MAX-ACCESS  read-only
   STATUS      current
   DESCRIPTION
       " "
   ::= { gs2326pPortTrafficStatisticsEntry 37 }

gs2326pPortTrafficTx65to127Bytes OBJECT-TYPE
   SYNTAX      Counter64
   MAX-ACCESS  read-only
   STATUS      current
   DESCRIPTION
       " "
   ::= { gs2326pPortTrafficStatisticsEntry 38 }

gs2326pPortTrafficTx128to255Bytes OBJECT-TYPE
   SYNTAX      Counter64
   MAX-ACCESS  read-only
   STATUS      current
   DESCRIPTION
       " "
   ::= { gs2326pPortTrafficStatisticsEntry 39 }

gs2326pPortTrafficTx256to511Bytes OBJECT-TYPE
   SYNTAX      Counter64
   MAX-ACCESS  read-only
   STATUS      current
   DESCRIPTION
       " "
   ::= { gs2326pPortTrafficStatisticsEntry 40 }

gs2326pPortTrafficTx512to1023Bytes OBJECT-TYPE
   SYNTAX      Counter64
   MAX-ACCESS  read-only
   STATUS      current
   DESCRIPTION
       " "
   ::= { gs2326pPortTrafficStatisticsEntry 41 }

gs2326pPortTrafficTx1024to1526Bytes OBJECT-TYPE
   SYNTAX      Counter64
   MAX-ACCESS  read-only
   STATUS      current
   DESCRIPTION
       " "
   ::= { gs2326pPortTrafficStatisticsEntry 42 }

gs2326pPortTrafficTxExceecd1527Bytes OBJECT-TYPE
   SYNTAX      Counter64
   MAX-ACCESS  read-only
   STATUS      current
   DESCRIPTION
       " "
   ::= { gs2326pPortTrafficStatisticsEntry 43 }

gs2326pPortTrafficTxQ0 OBJECT-TYPE
   SYNTAX      Counter64
   MAX-ACCESS  read-only
   STATUS      current
   DESCRIPTION
       " "
   ::= { gs2326pPortTrafficStatisticsEntry 44 }

gs2326pPortTrafficTxQ1 OBJECT-TYPE
   SYNTAX      Counter64
   MAX-ACCESS  read-only
   STATUS      current
   DESCRIPTION
       " "
   ::= { gs2326pPortTrafficStatisticsEntry 45 }

gs2326pPortTrafficTxQ2 OBJECT-TYPE
   SYNTAX      Counter64
   MAX-ACCESS  read-only
   STATUS      current
   DESCRIPTION
       " "
   ::= { gs2326pPortTrafficStatisticsEntry 46 }

gs2326pPortTrafficTxQ3 OBJECT-TYPE
   SYNTAX      Counter64
   MAX-ACCESS  read-only
   STATUS      current
   DESCRIPTION
       " "
   ::= { gs2326pPortTrafficStatisticsEntry 47 }

gs2326pPortTrafficTxQ4 OBJECT-TYPE
   SYNTAX      Counter64
   MAX-ACCESS  read-only
   STATUS      current
   DESCRIPTION
       " "
   ::= { gs2326pPortTrafficStatisticsEntry 48 }

gs2326pPortTrafficTxQ5 OBJECT-TYPE
   SYNTAX      Counter64
   MAX-ACCESS  read-only
   STATUS      current
   DESCRIPTION
       " "
   ::= { gs2326pPortTrafficStatisticsEntry 49 }

gs2326pPortTrafficTxQ6 OBJECT-TYPE
   SYNTAX      Counter64
   MAX-ACCESS  read-only
   STATUS      current
   DESCRIPTION
       " "
   ::= { gs2326pPortTrafficStatisticsEntry 50 }


gs2326pPortTrafficTxQ7 OBJECT-TYPE
   SYNTAX      Counter64
   MAX-ACCESS  read-only
   STATUS      current
   DESCRIPTION
       " "
   ::= { gs2326pPortTrafficStatisticsEntry 51 }

gs2326pPortTrafficTxDrops OBJECT-TYPE
   SYNTAX      Counter64
   MAX-ACCESS  read-only
   STATUS      current
   DESCRIPTION
       " "
   ::= { gs2326pPortTrafficStatisticsEntry 52 }

gs2326pPortTrafficTxLateOrExcColl OBJECT-TYPE
   SYNTAX      Counter64
   MAX-ACCESS  read-only
   STATUS      current
   DESCRIPTION
       " "
   ::= { gs2326pPortTrafficStatisticsEntry 53 }


gs2326pPortQoSStatistics                                     OBJECT IDENTIFIER ::= { gs2326pPort 3 }

gs2326pPortQoSStatisticsClear OBJECT-TYPE
   SYNTAX      INTEGER { none(0), clear(1) }
   MAX-ACCESS  read-only
   STATUS      current
   DESCRIPTION
       "default: 0
       0: none
       1: clear "
   ::= { gs2326pPortQoSStatistics 1 }

gs2326pPortQoSStatisticsTable OBJECT-TYPE
   SYNTAX      SEQUENCE OF GS2326PPortQoSStatisticsEntry
   MAX-ACCESS  not-accessible
   STATUS      current
   DESCRIPTION
       " "
   ::= { gs2326pPortQoSStatistics 2 }

gs2326pPortQoSStatisticsEntry OBJECT-TYPE
   SYNTAX      GS2326PPortQoSStatisticsEntry
   MAX-ACCESS  not-accessible
   STATUS      current
   DESCRIPTION
       ""
   INDEX    { gs2326pPortQoSStatisticsPort  }
   ::= { gs2326pPortQoSStatisticsTable 1 }

GS2326PPortQoSStatisticsEntry ::= SEQUENCE {
   gs2326pPortQoSStatisticsPort      Integer32,
   gs2326pPortQoSQ0Rx                Counter64,
   gs2326pPortQoSQ0Tx                Counter64,
   gs2326pPortQoSQ1Rx                Counter64,
   gs2326pPortQoSQ1Tx                Counter64,
   gs2326pPortQoSQ2Rx                Counter64,
   gs2326pPortQoSQ2Tx                Counter64,
   gs2326pPortQoSQ3Rx                Counter64,
   gs2326pPortQoSQ3Tx                Counter64,
   gs2326pPortQoSQ4Rx                Counter64,
   gs2326pPortQoSQ4Tx                Counter64,
   gs2326pPortQoSQ5Rx                Counter64,
   gs2326pPortQoSQ5Tx                Counter64,
   gs2326pPortQoSQ6Rx                Counter64,
   gs2326pPortQoSQ6Tx                Counter64,
   gs2326pPortQoSQ7Rx                Counter64,
   gs2326pPortQoSQ7Tx                Counter64
}

gs2326pPortQoSStatisticsPort OBJECT-TYPE
   SYNTAX      Integer32(1..4095)
   MAX-ACCESS  not-accessible
   STATUS      current
   DESCRIPTION
       " "
   ::= { gs2326pPortQoSStatisticsEntry 1 }

gs2326pPortQoSQ0Rx OBJECT-TYPE
   SYNTAX      Counter64
   MAX-ACCESS  read-only
   STATUS      current
   DESCRIPTION
       " "
   ::= { gs2326pPortQoSStatisticsEntry 2 }

gs2326pPortQoSQ0Tx OBJECT-TYPE
   SYNTAX      Counter64
   MAX-ACCESS  read-only
   STATUS      current
   DESCRIPTION
       " "
   ::= { gs2326pPortQoSStatisticsEntry 3 }

gs2326pPortQoSQ1Rx OBJECT-TYPE
   SYNTAX      Counter64
   MAX-ACCESS  read-only
   STATUS      current
   DESCRIPTION
       " "
   ::= { gs2326pPortQoSStatisticsEntry 4 }

gs2326pPortQoSQ1Tx OBJECT-TYPE
   SYNTAX      Counter64
   MAX-ACCESS  read-only
   STATUS      current
   DESCRIPTION
       " "
   ::= { gs2326pPortQoSStatisticsEntry 5 }

gs2326pPortQoSQ2Rx OBJECT-TYPE
   SYNTAX      Counter64
   MAX-ACCESS  read-only
   STATUS      current
   DESCRIPTION
       " "
   ::= { gs2326pPortQoSStatisticsEntry 6 }

gs2326pPortQoSQ2Tx OBJECT-TYPE
   SYNTAX      Counter64
   MAX-ACCESS  read-only
   STATUS      current
   DESCRIPTION
       " "
   ::= { gs2326pPortQoSStatisticsEntry 7 }

gs2326pPortQoSQ3Rx OBJECT-TYPE
   SYNTAX      Counter64
   MAX-ACCESS  read-only
   STATUS      current
   DESCRIPTION
       " "
   ::= { gs2326pPortQoSStatisticsEntry 8 }

gs2326pPortQoSQ3Tx OBJECT-TYPE
   SYNTAX      Counter64
   MAX-ACCESS  read-only
   STATUS      current
   DESCRIPTION
       " "
   ::= { gs2326pPortQoSStatisticsEntry 9 }

gs2326pPortQoSQ4Rx OBJECT-TYPE
   SYNTAX      Counter64
   MAX-ACCESS  read-only
   STATUS      current
   DESCRIPTION
       " "
   ::= { gs2326pPortQoSStatisticsEntry 10 }

gs2326pPortQoSQ4Tx OBJECT-TYPE
   SYNTAX      Counter64
   MAX-ACCESS  read-only
   STATUS      current
   DESCRIPTION
       " "
   ::= { gs2326pPortQoSStatisticsEntry 11 }

gs2326pPortQoSQ5Rx OBJECT-TYPE
   SYNTAX      Counter64
   MAX-ACCESS  read-only
   STATUS      current
   DESCRIPTION
       " "
   ::= { gs2326pPortQoSStatisticsEntry 12 }

gs2326pPortQoSQ5Tx OBJECT-TYPE
   SYNTAX      Counter64
   MAX-ACCESS  read-only
   STATUS      current
   DESCRIPTION
       " "
   ::= { gs2326pPortQoSStatisticsEntry 13 }

gs2326pPortQoSQ6Rx OBJECT-TYPE
   SYNTAX      Counter64
   MAX-ACCESS  read-only
   STATUS      current
   DESCRIPTION
       " "
   ::= { gs2326pPortQoSStatisticsEntry 14 }

gs2326pPortQoSQ6Tx OBJECT-TYPE
   SYNTAX      Counter64
   MAX-ACCESS  read-only
   STATUS      current
   DESCRIPTION
       " "
   ::= { gs2326pPortQoSStatisticsEntry 15 }

gs2326pPortQoSQ7Rx OBJECT-TYPE
   SYNTAX      Counter64
   MAX-ACCESS  read-only
   STATUS      current
   DESCRIPTION
       " "
   ::= { gs2326pPortQoSStatisticsEntry 16 }

gs2326pPortQoSQ7Tx OBJECT-TYPE
   SYNTAX      Counter64
   MAX-ACCESS  read-only
   STATUS      current
   DESCRIPTION
       " "
   ::= { gs2326pPortQoSStatisticsEntry 17 }

gs2326pSFPInfoTable OBJECT-TYPE
   SYNTAX      SEQUENCE OF GS2326PSFPInfoEntry
   MAX-ACCESS  not-accessible
   STATUS      current
   DESCRIPTION
       " "
   ::= { gs2326pPort 4 }

gs2326pSFPInfoEntry OBJECT-TYPE
   SYNTAX      GS2326PSFPInfoEntry
   MAX-ACCESS  not-accessible
   STATUS      current
   DESCRIPTION
       ""
   INDEX    { gs2326pSFPInfoIndex }
   ::= { gs2326pSFPInfoTable 1 }

GS2326PSFPInfoEntry ::= SEQUENCE {
   gs2326pSFPInfoIndex               Integer32,
   gs2326pSFPInfoPort                DisplayString,
   gs2326pSFPConnectorType           DisplayString,
   gs2326pSFPFiberType               DisplayString,
   gs2326pSFPTxCentralWavelength     DisplayString,
   gs2326pSFPBaudRate                DisplayString,
   gs2326pSFPVendorOUI               DisplayString,
   gs2326pSFPVendorName              DisplayString,
   gs2326pSFPVendorPN                DisplayString,
   gs2326pSFPVendorRev               DisplayString,
   gs2326pSFPVendorSN                DisplayString,
   gs2326pSFPDateCode                DisplayString,
   gs2326pSFPTemperature             DisplayString,
   gs2326pSFPVcc                     DisplayString,
   gs2326pSFPMon1Bias                DisplayString,
   gs2326pSFPMon2TxPWR               DisplayString,
   gs2326pSFPMon3RxPWR               DisplayString
}

gs2326pSFPInfoIndex OBJECT-TYPE
   SYNTAX      Integer32(1..4095)
   MAX-ACCESS  not-accessible
   STATUS      current
   DESCRIPTION
       " "
   ::= { gs2326pSFPInfoEntry 1 }

gs2326pSFPInfoPort OBJECT-TYPE
   SYNTAX      DisplayString
   MAX-ACCESS  read-only
   STATUS      current
   DESCRIPTION
       " "
   ::= { gs2326pSFPInfoEntry 2 }

gs2326pSFPConnectorType OBJECT-TYPE
   SYNTAX      DisplayString
   MAX-ACCESS  read-only
   STATUS      current
   DESCRIPTION
       " "
   ::= { gs2326pSFPInfoEntry 3 }

gs2326pSFPFiberType OBJECT-TYPE
   SYNTAX      DisplayString
   MAX-ACCESS  read-only
   STATUS      current
   DESCRIPTION
       " "
   ::= { gs2326pSFPInfoEntry 4 }

gs2326pSFPTxCentralWavelength OBJECT-TYPE
   SYNTAX      DisplayString
   MAX-ACCESS  read-only
   STATUS      current
   DESCRIPTION
       " "
   ::= { gs2326pSFPInfoEntry 5 }

gs2326pSFPBaudRate OBJECT-TYPE
   SYNTAX      DisplayString
   MAX-ACCESS  read-only
   STATUS      current
   DESCRIPTION
       " "
   ::= { gs2326pSFPInfoEntry 6 }

gs2326pSFPVendorOUI OBJECT-TYPE
   SYNTAX      DisplayString
   MAX-ACCESS  read-only
   STATUS      current
   DESCRIPTION
       " "
   ::= { gs2326pSFPInfoEntry 7 }

gs2326pSFPVendorName OBJECT-TYPE
   SYNTAX      DisplayString
   MAX-ACCESS  read-only
   STATUS      current
   DESCRIPTION
       " "
   ::= { gs2326pSFPInfoEntry 8 }

gs2326pSFPVendorPN OBJECT-TYPE
   SYNTAX      DisplayString
   MAX-ACCESS  read-only
   STATUS      current
   DESCRIPTION
       " "
   ::= { gs2326pSFPInfoEntry 9 }

gs2326pSFPVendorRev OBJECT-TYPE
   SYNTAX      DisplayString
   MAX-ACCESS  read-only
   STATUS      current
   DESCRIPTION
       " "
   ::= { gs2326pSFPInfoEntry 10 }

gs2326pSFPVendorSN OBJECT-TYPE
   SYNTAX      DisplayString
   MAX-ACCESS  read-only
   STATUS      current
   DESCRIPTION
       " "
   ::= { gs2326pSFPInfoEntry 11 }

gs2326pSFPDateCode OBJECT-TYPE
   SYNTAX      DisplayString
   MAX-ACCESS  read-only
   STATUS      current
   DESCRIPTION
       " "
   ::= { gs2326pSFPInfoEntry 12 }

gs2326pSFPTemperature OBJECT-TYPE
   SYNTAX      DisplayString
   MAX-ACCESS  read-only
   STATUS      current
   DESCRIPTION
       " "
   ::= { gs2326pSFPInfoEntry 13 }

gs2326pSFPVcc OBJECT-TYPE
   SYNTAX      DisplayString
   MAX-ACCESS  read-only
   STATUS      current
   DESCRIPTION
       " "
   ::= { gs2326pSFPInfoEntry 14 }

gs2326pSFPMon1Bias OBJECT-TYPE
   SYNTAX      DisplayString
   MAX-ACCESS  read-only
   STATUS      current
   DESCRIPTION
       " "
   ::= { gs2326pSFPInfoEntry 15 }

gs2326pSFPMon2TxPWR OBJECT-TYPE
   SYNTAX      DisplayString
   MAX-ACCESS  read-only
   STATUS      current
   DESCRIPTION
       " "
   ::= { gs2326pSFPInfoEntry 16 }

gs2326pSFPMon3RxPWR OBJECT-TYPE
   SYNTAX      DisplayString
   MAX-ACCESS  read-only
   STATUS      current
   DESCRIPTION
       " "
   ::= { gs2326pSFPInfoEntry 17 }


gs2326pPortEEETable OBJECT-TYPE
   SYNTAX      SEQUENCE OF GS2326PPortEEEEntry
   MAX-ACCESS  not-accessible
   STATUS      current
   DESCRIPTION
      " "
   ::= { gs2326pPort 5 }

gs2326pPortEEEEntry OBJECT-TYPE
   SYNTAX      GS2326PPortEEEEntry
   MAX-ACCESS  not-accessible
   STATUS      current
   DESCRIPTION
       ""
   INDEX    { gs2326pPortEEEPort }
   ::= { gs2326pPortEEETable 1 }

GS2326PPortEEEEntry ::= SEQUENCE {
   gs2326pPortEEEPort		        Integer32,
   gs2326pPortEEEMode		        INTEGER,
   gs2326pPortEEEUrgentQueue1		INTEGER,
   gs2326pPortEEEUrgentQueue2		INTEGER,
   gs2326pPortEEEUrgentQueue3		INTEGER,
   gs2326pPortEEEUrgentQueue4		INTEGER,
   gs2326pPortEEEUrgentQueue5		INTEGER,
   gs2326pPortEEEUrgentQueue6		INTEGER,
   gs2326pPortEEEUrgentQueue7		INTEGER,
   gs2326pPortEEEUrgentQueue8		INTEGER
}

gs2326pPortEEEPort OBJECT-TYPE
   SYNTAX      Integer32(1..4095)
   MAX-ACCESS  not-accessible
   STATUS      current
   DESCRIPTION
       " "
   ::= { gs2326pPortEEEEntry 1 }

gs2326pPortEEEMode OBJECT-TYPE
   SYNTAX      INTEGER { disable(0), enable(1) }
   MAX-ACCESS  read-write
   STATUS      current
   DESCRIPTION
       "default: 0
       0:disable
       1:enable "
   ::= { gs2326pPortEEEEntry 2 }

gs2326pPortEEEUrgentQueue1 OBJECT-TYPE
   SYNTAX      INTEGER { disable(0), enable(1) }
   MAX-ACCESS  read-write
   STATUS      current
   DESCRIPTION
       "default: 0
       0:disable
       1:enable "
   ::= { gs2326pPortEEEEntry 3 }

gs2326pPortEEEUrgentQueue2 OBJECT-TYPE
   SYNTAX      INTEGER { disable(0), enable(1) }
   MAX-ACCESS  read-write
   STATUS      current
   DESCRIPTION
       "default: 0
       0:disable
       1:enable "
   ::= { gs2326pPortEEEEntry 4 }

gs2326pPortEEEUrgentQueue3 OBJECT-TYPE
   SYNTAX      INTEGER { disable(0), enable(1) }
   MAX-ACCESS  read-write
   STATUS      current
   DESCRIPTION
       "default: 0
       0:disable
       1:enable "
   ::= { gs2326pPortEEEEntry 5 }

gs2326pPortEEEUrgentQueue4 OBJECT-TYPE
   SYNTAX      INTEGER { disable(0), enable(1) }
   MAX-ACCESS  read-write
   STATUS      current
   DESCRIPTION
       "default: 0
       0:disable
       1:enable "
   ::= { gs2326pPortEEEEntry 6 }

gs2326pPortEEEUrgentQueue5 OBJECT-TYPE
   SYNTAX      INTEGER { disable(0), enable(1) }
   MAX-ACCESS  read-write
   STATUS      current
   DESCRIPTION
       "default: 0
       0:disable
       1:enable "
   ::= { gs2326pPortEEEEntry 7 }

gs2326pPortEEEUrgentQueue6 OBJECT-TYPE
   SYNTAX      INTEGER { disable(0), enable(1) }
   MAX-ACCESS  read-write
   STATUS      current
   DESCRIPTION
       "default: 0
       0:disable
       1:enable "
   ::= { gs2326pPortEEEEntry 8 }

gs2326pPortEEEUrgentQueue7 OBJECT-TYPE
   SYNTAX      INTEGER { disable(0), enable(1) }
   MAX-ACCESS  read-write
   STATUS      current
   DESCRIPTION
       "default: 0
       0:disable
       1:enable "
   ::= { gs2326pPortEEEEntry 9 }

gs2326pPortEEEUrgentQueue8 OBJECT-TYPE
   SYNTAX      INTEGER { disable(0), enable(1) }
   MAX-ACCESS  read-write
   STATUS      current
   DESCRIPTION
       "default: 0
       0:disable
       1:enable "
   ::= { gs2326pPortEEEEntry 10 }


gs2326pVoiceVLAN                                             OBJECT IDENTIFIER ::= { gs2326pConfiguration 2 }

gs2326pVoiceVLANConf                                         OBJECT IDENTIFIER ::= { gs2326pVoiceVLAN 1 }

gs2326pVoiceVLANMode OBJECT-TYPE
   SYNTAX      INTEGER { disable(0), enable(1) }
   MAX-ACCESS  read-write
   STATUS      current
   DESCRIPTION
       " Voice VLAN mode operation.
       default: 0,
       0: disable
       1: enable"
   ::= { gs2326pVoiceVLANConf 1 }

gs2326pVoiceVLANVLANId OBJECT-TYPE
   SYNTAX      Integer32(1..4094)
   MAX-ACCESS  read-write
   STATUS      current
   DESCRIPTION
       "Voice VLAN ID.
        default: 1000,
        range : 1-4094. "
   ::= { gs2326pVoiceVLANConf 2 }

gs2326pVoiceVLANAgingTime OBJECT-TYPE
   SYNTAX      Integer32(10..1000000)
   MAX-ACCESS  read-write
   STATUS      current
   DESCRIPTION
       " Voice VLAN secure learning aging time.
         default: 86400,
         range : 10 - 10000000. "
   ::= { gs2326pVoiceVLANConf 3 }

gs2326pVoiceVLANTrafficClass OBJECT-TYPE
   SYNTAX      Integer32(0..7)
   MAX-ACCESS  read-write
   STATUS      current
   DESCRIPTION
       " Voice VLAN traffic class, all traffic on the Voice VLAN
         will apply this class, available value is from 0(Low)
         to 7(High).
         default: 7. "
   ::= { gs2326pVoiceVLANConf 4 }


gs2326pVoiceVLANPortTable OBJECT-TYPE
   SYNTAX      SEQUENCE OF GS2326PVoiceVLANPortEntry
   MAX-ACCESS  not-accessible
   STATUS      current
   DESCRIPTION
       " Show Voice Vlan configuration. "
   ::= { gs2326pVoiceVLANConf 5 }

gs2326pVoiceVLANPortEntry OBJECT-TYPE
   SYNTAX      GS2326PVoiceVLANPortEntry
   MAX-ACCESS  not-accessible
   STATUS      current
   DESCRIPTION
       ""
   INDEX    { gs2326pVoiceVLANPort  }
   ::= { gs2326pVoiceVLANPortTable 1 }

GS2326PVoiceVLANPortEntry ::= SEQUENCE {
   gs2326pVoiceVLANPort                    Integer32,
   gs2326pVoiceVLANPortMode                INTEGER,
   gs2326pVoiceVLANPortSecurity            INTEGER,
   gs2326pVoiceVLANPortDiscoveryProtocol   INTEGER
}

gs2326pVoiceVLANPort OBJECT-TYPE
   SYNTAX      Integer32(1..4095)
   MAX-ACCESS  not-accessible
   STATUS      current
   DESCRIPTION
       " port, range : 1 - port number. "
   ::= { gs2326pVoiceVLANPortEntry 1 }

gs2326pVoiceVLANPortMode OBJECT-TYPE
   SYNTAX      INTEGER { disable(0), auto(1), forced(2) }
   MAX-ACCESS  read-write
   STATUS      current
   DESCRIPTION
       " Voice VLAN port mode.
         default: 0,
         0: Disable (Disjoin from Voice VLAN.)
         1: Auto (Enable auto detect mode. It detects whether there is VoIP phone attached to the specific port and configures the Voice VLAN members automatically.)
         2: Forced (Force join to Voice VLAN.)"
   ::= { gs2326pVoiceVLANPortEntry 2 }

gs2326pVoiceVLANPortSecurity OBJECT-TYPE
   SYNTAX      INTEGER { disable(0), enable(1) }
   MAX-ACCESS  read-write
   STATUS      current
   DESCRIPTION
       " Voice VLAN port security mode.
         default: 0,
         0: Disable (Disjoin from Voice VLAN.)
         1: enable ( Enable Voice VLAN security mode. When the function is
                     enabled, all non-telephone MAC address in Voice VLAN
                     will be blocked 10 seconds.)"
   ::= { gs2326pVoiceVLANPortEntry 3 }

gs2326pVoiceVLANPortDiscoveryProtocol OBJECT-TYPE
   SYNTAX      INTEGER { oui(0), lldp(1), both(2) }
   MAX-ACCESS  read-write
   STATUS      current
   DESCRIPTION
       " Voice VLAN port discovery protocol.
         default: 0
         0: OUI (Detect telephony device by OUI address.)
         1: LLDP (Detect telephony device by LLDP.)
         2: Both (Both OUI and LLDP.) "
   ::= { gs2326pVoiceVLANPortEntry 4 }

gs2326pVoiceVLANSkipNAS OBJECT-TYPE
   SYNTAX      INTEGER { disable(0), enable(1) }
   MAX-ACCESS  read-write
   STATUS      current
   DESCRIPTION
       " Voice VLAN skip NAS mode.
         default: 0,
         0: Disable (Do not skip NAS on Voice VLAN.)
         1: enable (Enable skipping of NAS on Voice VLAN. When the function is
                    enabled, authentication through the NAS module is not
                    applied to the Voice VLAN, but clients are allowed without
                    authentication.)"
   ::= { gs2326pVoiceVLANPortEntry 5 }


gs2326pVoiceVLANOUI                                          OBJECT IDENTIFIER ::= { gs2326pVoiceVLAN 2 }

gs2326pVoiceVLANOUICreate OBJECT-TYPE
   SYNTAX       INTEGER { none(0), create(1) }
   MAX-ACCESS   read-write
   STATUS       current
   DESCRIPTION
       "default: 0
        0 : None  (read only)
        1 : Create an OUI entry"
   ::= { gs2326pVoiceVLANOUI 1 }

gs2326pVoiceVLANOUITable OBJECT-TYPE
   SYNTAX      SEQUENCE OF GS2326PVoiceVLANOUIEntry
   MAX-ACCESS  not-accessible
   STATUS      current
   DESCRIPTION
       " Create Voice VLAN OUI entry. Modify OUI table will
         restart auto detect OUI process. "
   ::= { gs2326pVoiceVLANOUI 2 }

gs2326pVoiceVLANOUIEntry OBJECT-TYPE
   SYNTAX      GS2326PVoiceVLANOUIEntry
   MAX-ACCESS  not-accessible
   STATUS      current
   DESCRIPTION
       ""
   INDEX    { gs2326pVoiceVLANOUIIndex  }
   ::= { gs2326pVoiceVLANOUITable 1 }

GS2326PVoiceVLANOUIEntry ::= SEQUENCE {
   gs2326pVoiceVLANOUIIndex         Integer32,
   gs2326pVoiceVLANTelephonyOUI     OCTET STRING,
   gs2326pVoiceVLANDescription      DisplayString,
   gs2326pVoiceVLANOUIRowStatus     INTEGER
}

gs2326pVoiceVLANOUIIndex OBJECT-TYPE
   SYNTAX      Integer32(1..16)
   MAX-ACCESS  not-accessible
   STATUS      current
   DESCRIPTION
       " "
   ::= { gs2326pVoiceVLANOUIEntry 1 }

gs2326pVoiceVLANTelephonyOUI OBJECT-TYPE
   SYNTAX      OCTET STRING (SIZE (1..32))
   MAX-ACCESS  read-write
   STATUS      current
   DESCRIPTION
       "OUI address, format : 0a 1b 2c "
   ::= { gs2326pVoiceVLANOUIEntry 2 }

gs2326pVoiceVLANDescription OBJECT-TYPE
   SYNTAX      DisplayString (SIZE (1..32))
   MAX-ACCESS  read-write
   STATUS      current
   DESCRIPTION
       " Up to 32 characters describing OUI address. "
   ::= { gs2326pVoiceVLANOUIEntry 3 }

gs2326pVoiceVLANOUIRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pVoiceVLANOUIEntry 4 }

gs2326pGARP                                                   OBJECT IDENTIFIER ::= { gs2326pConfiguration 3 }

gs2326pGARPConfTable OBJECT-TYPE
   SYNTAX      SEQUENCE OF GS2326PGARPConfEntry
   MAX-ACCESS  not-accessible
   STATUS      current
   DESCRIPTION
       " "
   ::= { gs2326pGARP 1 }

gs2326pGARPConfEntry OBJECT-TYPE
   SYNTAX      GS2326PGARPConfEntry
   MAX-ACCESS  not-accessible
   STATUS      current
   DESCRIPTION
       ""
   INDEX    { gs2326pGARPConfPort  }
   ::= { gs2326pGARPConfTable 1 }

GS2326PGARPConfEntry ::= SEQUENCE {
   gs2326pGARPConfPort           Integer32,
   gs2326pGARPJoinTimer          Integer32,
   gs2326pGARPLeaveTimer         Integer32,
   gs2326pGARPLeaveAllTimer      Integer32,
   gs2326pGARPApplicantion       INTEGER,
   gs2326pGARPAttributeType      INTEGER,
   gs2326pGARPApplicant          INTEGER
}

gs2326pGARPConfPort OBJECT-TYPE
   SYNTAX      Integer32(1..4095)
   MAX-ACCESS  not-accessible
   STATUS      current
   DESCRIPTION
       " "
   ::= { gs2326pGARPConfEntry 1 }

gs2326pGARPJoinTimer OBJECT-TYPE
   SYNTAX      Integer32(200..1000)
   MAX-ACCESS  read-write
   STATUS      current
   DESCRIPTION
       "default: 200, range : 200 - 1000 "
   ::= { gs2326pGARPConfEntry 2 }

gs2326pGARPLeaveTimer OBJECT-TYPE
   SYNTAX      Integer32(600..3000)
   MAX-ACCESS  read-write
   STATUS      current
   DESCRIPTION
       "default: 600 , range : 600 - 3000"
   ::= { gs2326pGARPConfEntry 3 }

gs2326pGARPLeaveAllTimer OBJECT-TYPE
   SYNTAX      Integer32(10000..50000)
   MAX-ACCESS  read-write
   STATUS      current
   DESCRIPTION
       "default: 10000, range : 10000 - 50000 "
   ::= { gs2326pGARPConfEntry 4 }

gs2326pGARPApplicantion OBJECT-TYPE
   SYNTAX      INTEGER { gvrp(1)}
   MAX-ACCESS  read-write
   STATUS      current
   DESCRIPTION
       "default: 1
       1: GVRP"
   ::= { gs2326pGARPConfEntry 5 }

gs2326pGARPAttributeType OBJECT-TYPE
   SYNTAX      INTEGER { vlan(1)}
   MAX-ACCESS  read-write
   STATUS      current
   DESCRIPTION
       "default: 1
       1: VLAN"
   ::= { gs2326pGARPConfEntry 6 }

gs2326pGARPApplicant OBJECT-TYPE
   SYNTAX      INTEGER { participant(0), nonParticipant(1) }
   MAX-ACCESS  read-write
   STATUS      current
   DESCRIPTION
       "default: 0
       0: normal-participant
       1: non-participant"
   ::= { gs2326pGARPConfEntry 7 }

gs2326pGARPStatisticsTable OBJECT-TYPE
   SYNTAX      SEQUENCE OF GS2326PGARPStatisticsEntry
   MAX-ACCESS  not-accessible
   STATUS      current
   DESCRIPTION
       " Show the basic GARP port statistics. "
   ::= { gs2326pGARP 2 }

gs2326pGARPStatisticsEntry OBJECT-TYPE
   SYNTAX      GS2326PGARPStatisticsEntry
   MAX-ACCESS  not-accessible
   STATUS      current
   DESCRIPTION
       ""
   INDEX    { gs2326pGARPStatisticsPort  }
   ::= { gs2326pGARPStatisticsTable 1 }

GS2326PGARPStatisticsEntry ::= SEQUENCE {
   gs2326pGARPStatisticsPort             Integer32,
   gs2326pGARPStatisticsPeerMAC          DisplayString,
   gs2326pGARPStatisticsFailedCount      Counter32
}

gs2326pGARPStatisticsPort OBJECT-TYPE
   SYNTAX      Integer32(1..4095)
   MAX-ACCESS  not-accessible
   STATUS      current
   DESCRIPTION
       " port, range : 1 - port number. "
   ::= { gs2326pGARPStatisticsEntry 1 }

gs2326pGARPStatisticsPeerMAC OBJECT-TYPE
   SYNTAX      DisplayString
   MAX-ACCESS  read-only
   STATUS      current
   DESCRIPTION
       " Peer MAC is MAC address of the neighbour Switch from with GARP frame is received.  "
   ::= { gs2326pGARPStatisticsEntry 2 }

gs2326pGARPStatisticsFailedCount OBJECT-TYPE
   SYNTAX      Counter32
   MAX-ACCESS  read-only
   STATUS      current
   DESCRIPTION
       " explain Failed count here. "
   ::= { gs2326pGARPStatisticsEntry 3 }

gs2326pGVRP                                                   OBJECT IDENTIFIER ::= { gs2326pConfiguration 4 }

gs2326pGVRPConf                                                   OBJECT IDENTIFIER ::= { gs2326pGVRP 1 }

gs2326pGVRPMode OBJECT-TYPE
   SYNTAX      INTEGER { disable(0), enable(1) }
   MAX-ACCESS  read-write
   STATUS      current
   DESCRIPTION
       "default: 0,
        0: disable,
        1: enable. "
   ::= { gs2326pGVRPConf 1 }

gs2326pGVRPConfTable OBJECT-TYPE
   SYNTAX      SEQUENCE OF GS2326PGVRPConfEntry
   MAX-ACCESS  not-accessible
   STATUS      current
   DESCRIPTION
       " "
   ::= { gs2326pGVRPConf 2 }

gs2326pGVRPConfEntry OBJECT-TYPE
   SYNTAX      GS2326PGVRPConfEntry
   MAX-ACCESS  not-accessible
   STATUS      current
   DESCRIPTION
       ""
   INDEX    { gs2326pGVRPConfPort  }
   ::= { gs2326pGVRPConfTable 1 }

GS2326PGVRPConfEntry ::= SEQUENCE {
   gs2326pGVRPConfPort           Integer32,
   gs2326pGVRPConfPortMode       INTEGER,
   gs2326pGVRPConfPortRRole      INTEGER
}

gs2326pGVRPConfPort OBJECT-TYPE
   SYNTAX      Integer32(1..4095)
   MAX-ACCESS  not-accessible
   STATUS      current
   DESCRIPTION
       " "
   ::= { gs2326pGVRPConfEntry 1 }

gs2326pGVRPConfPortMode OBJECT-TYPE
   SYNTAX      INTEGER { disable(0), enable(1) }
   MAX-ACCESS  read-write
   STATUS      current
   DESCRIPTION
       "default: 0
       1: enable
       0: disable"
   ::= { gs2326pGVRPConfEntry 2 }

gs2326pGVRPConfPortRRole OBJECT-TYPE
   SYNTAX      INTEGER { disable(0), enable(1) }
   MAX-ACCESS  read-write
   STATUS      current
   DESCRIPTION
       "default: 0
       1: enable
       0: disable"
   ::= { gs2326pGVRPConfEntry 3 }

gs2326pGVRPStatisticsTable OBJECT-TYPE
   SYNTAX      SEQUENCE OF GS2326PGVRPStatisticsEntry
   MAX-ACCESS  not-accessible
   STATUS      current
   DESCRIPTION
       " "
   ::= { gs2326pGVRP 2 }

gs2326pGVRPStatisticsEntry OBJECT-TYPE
   SYNTAX      GS2326PGVRPStatisticsEntry
   MAX-ACCESS  not-accessible
   STATUS      current
   DESCRIPTION
       ""
   INDEX    { gs2326pGVRPStatisticsPort  }
   ::= { gs2326pGVRPStatisticsTable 1 }

GS2326PGVRPStatisticsEntry ::= SEQUENCE {
   gs2326pGVRPStatisticsPort         Integer32,
   gs2326pGVRPStatisticsJoinTxCnt    Counter32,
   gs2326pGVRPStatisticsLeaveTxCnt   Counter32
}

gs2326pGVRPStatisticsPort OBJECT-TYPE
   SYNTAX      Integer32(1..4095)
   MAX-ACCESS  not-accessible
   STATUS      current
   DESCRIPTION
       " "
   ::= { gs2326pGVRPStatisticsEntry 1 }

gs2326pGVRPStatisticsJoinTxCnt OBJECT-TYPE
   SYNTAX      Counter32
   MAX-ACCESS  read-only
   STATUS      current
   DESCRIPTION
       ""
   ::= { gs2326pGVRPStatisticsEntry 2 }

gs2326pGVRPStatisticsLeaveTxCnt OBJECT-TYPE
   SYNTAX      Counter32
   MAX-ACCESS  read-only
   STATUS      current
   DESCRIPTION
       ""
   ::= { gs2326pGVRPStatisticsEntry 3 }


gs2326pMirroring                                             OBJECT IDENTIFIER ::= { gs2326pConfiguration 6 }

gs2326pPortToMirrorOn OBJECT-TYPE
   SYNTAX      Integer32(0..10)
   MAX-ACCESS  read-write
   STATUS      current
   DESCRIPTION
       "default: 0
        0: disable,
        range : 1 - port number. "
   ::= { gs2326pMirroring 1 }

gs2326pMirrorTable OBJECT-TYPE
   SYNTAX      SEQUENCE OF GS2326PMirrorEntry
   MAX-ACCESS  not-accessible
   STATUS      current
   DESCRIPTION
       " "
   ::= { gs2326pMirroring 2 }

gs2326pMirrorEntry OBJECT-TYPE
   SYNTAX      GS2326PMirrorEntry
   MAX-ACCESS  not-accessible
   STATUS      current
   DESCRIPTION
       ""
   INDEX    { gs2326pMirrorPort  }
   ::= { gs2326pMirrorTable 1 }

GS2326PMirrorEntry ::= SEQUENCE {
   gs2326pMirrorPort		Integer32,
   gs2326pMirrorMode		INTEGER
}

gs2326pMirrorPort OBJECT-TYPE
   SYNTAX      Integer32(1..4095)
   MAX-ACCESS  not-accessible
   STATUS      current
   DESCRIPTION
       " "
   ::= { gs2326pMirrorEntry 1 }

gs2326pMirrorMode OBJECT-TYPE
   SYNTAX      INTEGER { disable(0), enable(1), rxOnly(2), txOnly(3) }
   MAX-ACCESS  read-write
   STATUS      current
   DESCRIPTION
       "default: 0
       0: disable
       1: enable
       2: rx only
       3: tx only
       Setting Tx mirroring for analyzer port has no effect. Tx mirroring ignored"
   ::= { gs2326pMirrorEntry 2 }

gs2326pTrapEventSeverity                                             OBJECT IDENTIFIER ::= { gs2326pConfiguration 7 }

gs2326pTrapEventSeverityACL OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 1 }

gs2326pTrapEventSeverityACLLog OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  7(Debug)
        0: Emergency
        1: Alert
        2: Critical
        3: Error
        4: Warning
        5: Notice
        6: Info
        7: Debug"
   ::= { gs2326pTrapEventSeverity 2 }

gs2326pTrapEventSeverityAccessMgmt OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 3 }

gs2326pTrapEventSeverityAuthFailed OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 4 }

gs2326pTrapEventSeverityColdStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 5 }

gs2326pTrapEventSeverityConfigInfo OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 6 }

gs2326pTrapEventSeverityFirmwareUpgrade OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 7 }

gs2326pTrapEventSeverityImportExport OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 8 }

gs2326pTrapEventSeverityLACP OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 9 }

gs2326pTrapEventSeverityLinkStatus OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 10 }

gs2326pTrapEventSeverityLogin OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 11 }

gs2326pTrapEventSeverityLogout OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 12 }

gs2326pTrapEventSeverityLoopProtect OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 13 }

gs2326pTrapEventSeverityMgmtIPChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 14 }

gs2326pTrapEventSeverityModuleChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  5(Notice)
        0: Emergency
        1: Alert
        2: Critical
        3: Error
        4: Warning
        5: Notice
        6: Info
        7: Debug"
   ::= { gs2326pTrapEventSeverity 15 }

gs2326pTrapEventSeverityNAS OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 16 }

gs2326pTrapEventSeverityPasswordChange OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 17 }

gs2326pTrapEventSeverityPortSecurity OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 18 }

gs2326pTrapEventSeverityVLAN OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  6(Info)
        0: Emergency
        1: Alert
        2: Critical
        3: Error
        4: Warning
        5: Notice
        6: Info
        7: Debug"
   ::= { gs2326pTrapEventSeverity 20 }

gs2326pTrapEventSeverityWarmStart OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 21 }

gs2326pTrapEventSeverityPoEAutoCheck OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 22 }

gs2326pTrapEventSeverityARPConflict OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 25 }

gs2326pTrapEventSeveritySpoofingLimit OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 27 }

gs2326pTrapEventSeverityStaticARPConflict	 OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       " default:  4(Warning)
        0: Emergency
        1: Alert
        2: Critical
        3: Error
        4: Warning
        5: Notice
        6: Info
        7: Debug"
   ::= { gs2326pTrapEventSeverity 28 }

gs2326pSMTP                                             OBJECT IDENTIFIER ::= { gs2326pConfiguration 8 }

gs2326pSMTPMailServer OBJECT-TYPE
   SYNTAX      DisplayString
   MAX-ACCESS  read-write
   STATUS      current
   DESCRIPTION
       " Up to 47 characters describing email server. "
   ::= { gs2326pSMTP 1 }

gs2326pSMTPUserName OBJECT-TYPE
   SYNTAX      DisplayString
   MAX-ACCESS  read-write
   STATUS      current
   DESCRIPTION
       " Up to 47 characters describing user name. "
   ::= { gs2326pSMTP 2 }

gs2326pSMTPPassword OBJECT-TYPE
   SYNTAX      DisplayString
   MAX-ACCESS  read-write
   STATUS      current
   DESCRIPTION
       " Up to 47 characters describing password. "
   ::= { gs2326pSMTP 3 }

gs2326pSMTPServeriryLevel OBJECT-TYPE
   SYNTAX      INTEGER {
                    emergency(0),
                    alert(1),
                    critical(2),
                    error(3),
                    warning(4),
                    notice(5),
                    info(6),
                    debug(7)
                }
   MAX-ACCESS  read-write
   STATUS      current
   DESCRIPTION
       "default: 6
       0: Emergency
       1: Alert
       2: Critical
       3: Error
       4: Warning
       5: Notice
       6: Info
       7: Debug"
   ::= { gs2326pSMTP 4 }

gs2326pSMTPSender OBJECT-TYPE
   SYNTAX      DisplayString
   MAX-ACCESS  read-write
   STATUS      current
   DESCRIPTION
       " Up to 47 characters describing sender. "
   ::= { gs2326pSMTP 5 }

gs2326pSMTPReturnPath OBJECT-TYPE
   SYNTAX      DisplayString
   MAX-ACCESS  read-write
   STATUS      current
   DESCRIPTION
       " Up to 47 characters describing return path. "
   ::= { gs2326pSMTP 6 }

gs2326pSMTPEmailAddress1 OBJECT-TYPE
   SYNTAX      DisplayString
   MAX-ACCESS  read-write
   STATUS      current
   DESCRIPTION
       " Up to 47 characters describing mail address. "
   ::= { gs2326pSMTP 7 }

gs2326pSMTPEmailAddress2 OBJECT-TYPE
   SYNTAX      DisplayString
   MAX-ACCESS  read-write
   STATUS      current
   DESCRIPTION
       " Up to 47 characters describing mail address. "
   ::= { gs2326pSMTP 8 }

gs2326pSMTPEmailAddress3 OBJECT-TYPE
   SYNTAX      DisplayString
   MAX-ACCESS  read-write
   STATUS      current
   DESCRIPTION
       " Up to 47 characters describing mail address. "
   ::= { gs2326pSMTP 9 }

gs2326pSMTPEmailAddress4 OBJECT-TYPE
   SYNTAX      DisplayString
   MAX-ACCESS  read-write
   STATUS      current
   DESCRIPTION
       " Up to 47 characters describing mail address. "
   ::= { gs2326pSMTP 10 }

gs2326pSMTPEmailAddress5 OBJECT-TYPE
   SYNTAX      DisplayString
   MAX-ACCESS  read-write
   STATUS      current
   DESCRIPTION
       " Up to 47 characters describing mail address. "
   ::= { gs2326pSMTP 11 }

gs2326pSMTPEmailAddress6 OBJECT-TYPE
   SYNTAX      DisplayString
   MAX-ACCESS  read-write
   STATUS      current
   DESCRIPTION
       " Up to 47 characters describing mail address. "
   ::= { gs2326pSMTP 12 }


gs2326pACL                                                   OBJECT IDENTIFIER ::= { gs2326pConfiguration 9 }

gs2326pACLPortsConfTable OBJECT-TYPE
   SYNTAX      SEQUENCE OF GS2326PACLPortsConfEntry
   MAX-ACCESS  not-accessible
   STATUS      current
   DESCRIPTION
       " "
   ::= { gs2326pACL 1 }

gs2326pACLPortsConfEntry OBJECT-TYPE
   SYNTAX      GS2326PACLPortsConfEntry
   MAX-ACCESS  not-accessible
   STATUS      current
   DESCRIPTION
       ""
   INDEX    { gs2326pACLPortsConfPort  }
   ::= { gs2326pACLPortsConfTable 1 }

GS2326PACLPortsConfEntry ::= SEQUENCE {
   gs2326pACLPortsConfPort               Integer32,
   gs2326pACLPortsConfPolicyID           Integer32,
   gs2326pACLPortsConfAction             INTEGER,
   gs2326pACLPortsConfRateLimiterID      Integer32,
   gs2326pACLPortsConfPortRedirect       Integer32,
   gs2326pACLPortsConfMirror             INTEGER,
   gs2326pACLPortsConfLogging            INTEGER,
   gs2326pACLPortsConfShutdown           INTEGER,
   gs2326pACLPortsConfState              INTEGER,
   gs2326pACLPortsConfCounter            Counter32
}

gs2326pACLPortsConfPort OBJECT-TYPE
   SYNTAX      Integer32 (1..4095)
   MAX-ACCESS  not-accessible
   STATUS      current
   DESCRIPTION
       " "
   ::= { gs2326pACLPortsConfEntry 1 }

gs2326pACLPortsConfPolicyID OBJECT-TYPE
   SYNTAX      Integer32 (0..255)
   MAX-ACCESS  read-write
   STATUS      current
   DESCRIPTION
       "default: 0, range : 0 - 255 "
   ::= { gs2326pACLPortsConfEntry 2 }

gs2326pACLPortsConfAction OBJECT-TYPE
   SYNTAX      INTEGER { deny(0), permit(1) }
   MAX-ACCESS  read-write
   STATUS      current
   DESCRIPTION
       "default: 1,
        0: Deny
        1: Permit"
   ::= { gs2326pACLPortsConfEntry 3 }

gs2326pACLPortsConfRateLimiterID OBJECT-TYPE
   SYNTAX      Integer32 (0..12)
   MAX-ACCESS  read-write
   STATUS      current
   DESCRIPTION
       "default: 0,
        0: Disable
        range : 0 - 12 "
   ::= { gs2326pACLPortsConfEntry 4 }

gs2326pACLPortsConfPortRedirect OBJECT-TYPE
   SYNTAX      Integer32 (0..4095)
   MAX-ACCESS  read-write
   STATUS      current
   DESCRIPTION
       "default: 0
        0: Disable
        range : 0 - end port number "
   ::= { gs2326pACLPortsConfEntry 5 }

gs2326pACLPortsConfMirror OBJECT-TYPE
   SYNTAX      INTEGER { disable(0), enable(1) }
   MAX-ACCESS  read-write
   STATUS      current
   DESCRIPTION
       "default: 0
        0: Disable
        1: Enable "
   ::= { gs2326pACLPortsConfEntry 6 }

gs2326pACLPortsConfLogging OBJECT-TYPE
   SYNTAX      INTEGER { disable(0), enable(1) }
   MAX-ACCESS  read-write
   STATUS      current
   DESCRIPTION
       "default: 0
        0: Disable
        1: Enable "
   ::= { gs2326pACLPortsConfEntry 7 }

gs2326pACLPortsConfShutdown OBJECT-TYPE
   SYNTAX      INTEGER { disable(0), enable(1) }
   MAX-ACCESS  read-write
   STATUS      current
   DESCRIPTION
       "default: 0
        0: Disable
        1: Enable "
   ::= { gs2326pACLPortsConfEntry 8 }

gs2326pACLPortsConfState OBJECT-TYPE
   SYNTAX      INTEGER { disable(0), enable(1) }
   MAX-ACCESS  read-write
   STATUS      current
   DESCRIPTION
       "default: 1
        0: Disable
        1: Enable "
   ::= { gs2326pACLPortsConfEntry 9 }

gs2326pACLPortsConfCounter OBJECT-TYPE
   SYNTAX      Counter32
   MAX-ACCESS  read-only
   STATUS      current
   DESCRIPTION
       "Counts the number of frames that match this ACE. "
   ::= { gs2326pACLPortsConfEntry 10 }


gs2326pACLRateLimiterTable OBJECT-TYPE
   SYNTAX      SEQUENCE OF GS2326PACLRateLimiterEntry
   MAX-ACCESS  not-accessible
   STATUS      current
   DESCRIPTION
       " "
   ::= { gs2326pACL 2 }

gs2326pACLRateLimiterEntry OBJECT-TYPE
   SYNTAX      GS2326PACLRateLimiterEntry
   MAX-ACCESS  not-accessible
   STATUS      current
   DESCRIPTION
       ""
   INDEX    { gs2326pACLRateLimiterID  }
   ::= { gs2326pACLRateLimiterTable 1 }

GS2326PACLRateLimiterEntry ::= SEQUENCE {
   gs2326pACLRateLimiterID       Integer32,
   gs2326pACLRateLimiterUnit     INTEGER,
   gs2326pACLRateLimiterRate     Integer32
}

gs2326pACLRateLimiterID OBJECT-TYPE
   SYNTAX      Integer32 (1..12)
   MAX-ACCESS  not-accessible
   STATUS      current
   DESCRIPTION
       " Rate Limiter ID.
         range : 1-12 "
   ::= { gs2326pACLRateLimiterEntry 1 }

gs2326pACLRateLimiterUnit OBJECT-TYPE
   SYNTAX      INTEGER { pps(0), kbps(1) }
   MAX-ACCESS  read-write
   STATUS      current
   DESCRIPTION
       "default: 0,
        0: pps
        1: kbps"
   ::= { gs2326pACLRateLimiterEntry 2 }

gs2326pACLRateLimiterRate OBJECT-TYPE
   SYNTAX      Integer32(0..3276700)
   MAX-ACCESS  read-write
   STATUS      current
   DESCRIPTION
       "default: 1,
        range : <0-3276700> pps
                <0-10000> kbps"
   ::= { gs2326pACLRateLimiterEntry 3 }


gs2326pACLACE                                          OBJECT IDENTIFIER ::= { gs2326pACL 3 }

gs2326pACLACECreate OBJECT-TYPE
   SYNTAX       INTEGER { none(0), create(1) }
   MAX-ACCESS   read-write
   STATUS       current
   DESCRIPTION
       "default: 0
        0 : None  (read only)
        1 : Create an ACE entry"
   ::= { gs2326pACLACE 1 }

gs2326pACLACETable OBJECT-TYPE
   SYNTAX      SEQUENCE OF GS2326PACLACEEntry
   MAX-ACCESS  not-accessible
   STATUS      current
   DESCRIPTION
       " Create ACL ACE entry. "
   ::= { gs2326pACLACE 2 }

gs2326pACLACEEntry OBJECT-TYPE
   SYNTAX      GS2326PACLACEEntry
   MAX-ACCESS  not-accessible
   STATUS      current
   DESCRIPTION
       ""
   INDEX    { gs2326pACLACEIndex  }
   ::= { gs2326pACLACETable 1 }

GS2326PACLACEEntry ::= SEQUENCE {
   gs2326pACLACEIndex                Integer32,
   gs2326pACLACEID                   Integer32,
   gs2326pACLACENextID               Integer32,
   gs2326pACLACEIngressPort          DisplayString,
   gs2326pACLACEPortPolicyNumber     Integer32,

   gs2326pACLACEPortPolicyBitmask    Integer32,
   gs2326pACLACEFrameType            INTEGER,
   gs2326pACLACEAction               INTEGER,
   gs2326pACLACEDenyPortRedirect     DisplayString,
   gs2326pACLACELogging              INTEGER,

   gs2326pACLACEMirror               INTEGER,
   gs2326pACLACERateLimiter          Integer32,
   gs2326pACLACEShutdown             INTEGER,
   gs2326pACLACEVLAN8021QTagged      INTEGER,
   gs2326pACLACEVLANTagPriority      Integer32,

   gs2326pACLACEVLANVID              Integer32,
   gs2326pACLACEEtherType            Integer32,
   gs2326pACLACESMAC                 DisplayString,
   gs2326pACLACEDMACType             INTEGER,
   gs2326pACLACEDMAC                 DisplayString,

   gs2326pACLACEArpOpcode            INTEGER,
   gs2326pACLACEArpFlagsRequestReply INTEGER,
   gs2326pACLACEArpFlagsArpSmac      INTEGER,
   gs2326pACLACEArpFlagsRarpDmac     INTEGER,
   gs2326pACLACEArpFlagsLength       INTEGER,

   gs2326pACLACEArpFlagsIp           INTEGER,
   gs2326pACLACEArpFlagsEthernet     INTEGER,
   gs2326pACLACESIPType              INTEGER,
   gs2326pACLACESIPIPAddress         IpAddress,
   gs2326pACLACESIPNetworkPrefix     Integer32,

   gs2326pACLACEDIPType              INTEGER,
   gs2326pACLACEDIPIPAddress         IpAddress,
   gs2326pACLACEDIPNetworkPrefix     Integer32,

   gs2326pACLACEIPProtocol           Integer32,
   gs2326pACLACEIPFlagsTTL           INTEGER,
   gs2326pACLACEIPFlagsOptions       INTEGER,
   gs2326pACLACEIPFlagsFragment      INTEGER,
   gs2326pACLACEICMPType             Integer32,

   gs2326pACLACEICMPCode             Integer32,
   gs2326pACLACESourcePortMin        Integer32,
   gs2326pACLACESourcePortMax        Integer32,
   gs2326pACLACEDestPortMin          Integer32,
   gs2326pACLACEDestPortMax          Integer32,

   gs2326pACLACETCPFlagsFin          INTEGER,
   gs2326pACLACETCPFlagsSyn          INTEGER,
   gs2326pACLACETCPFlagsRst          INTEGER,
   gs2326pACLACETCPFlagsPsh          INTEGER,
   gs2326pACLACETCPFlagsAck          INTEGER,

   gs2326pACLACETCPFlagsUrg          INTEGER,

   gs2326pACLACERowStatus            INTEGER
}

gs2326pACLACEIndex OBJECT-TYPE
   SYNTAX      Integer32(1..256)
   MAX-ACCESS  not-accessible
   STATUS      current
   DESCRIPTION
       " "
   ::= { gs2326pACLACEEntry 1 }

gs2326pACLACEID OBJECT-TYPE
   SYNTAX      Integer32(1..256)
   MAX-ACCESS  read-write
   STATUS      current
   DESCRIPTION
       " If the ACE ID is specified and an entry with this ACE ID
         already exists, the ACE will be modified. Otherwise, a
         new ACE will be added.
         range : 1 - 256. "
   ::= { gs2326pACLACEEntry 2 }

gs2326pACLACENextID OBJECT-TYPE
   SYNTAX      Integer32 (0..256)
   MAX-ACCESS  read-write
   STATUS      current
   DESCRIPTION
       " If the next ACE ID is non zero, the ACE will be placed
         before this ACE in the list. If the next ACE ID is zero,
         the ACE will be placed last in the list.
         range : 0 - 256. "
   ::= { gs2326pACLACEEntry 3 }

gs2326pACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { gs2326pACLACEEntry 4 }

gs2326pACLACEPortPolicyNumber OBJECT-TYPE
   SYNTAX      Integer32(0..255)
   MAX-ACCESS  read-write
   STATUS      current
   DESCRIPTION
       " policy value.
         range : 0 - 255. "
   ::= { gs2326pACLACEEntry 5 }

gs2326pACLACEPortPolicyBitmask OBJECT-TYPE
   SYNTAX      Integer32(0..255)
   MAX-ACCESS  read-write
   STATUS      current
   DESCRIPTION
       " policy bitmask.
         range : 0 - 255(0xff). "
   ::= { gs2326pACLACEEntry 6 }

gs2326pACLACEFrameType OBJECT-TYPE
   SYNTAX      INTEGER {
                        any(0),
                        arp(1),
                        etype(2),
                        icmp(3),
                        ipv4(4),
                        tcp(5),
                        udp(6)
                        }
   MAX-ACCESS  read-write
   STATUS      current
   DESCRIPTION
       " 0: any,
         1: arp,
         2: etype,
         3: icmp,
         4: ipv4,
         5: tcp,
         6: udp."
   ::= { gs2326pACLACEEntry 7 }

gs2326pACLACEAction OBJECT-TYPE
   SYNTAX      INTEGER { deny(0), permit(1) }
   MAX-ACCESS  read-write
   STATUS      current
   DESCRIPTION
       "default: 1,
        0: Deny
        1: Permit"
   ::= { gs2326pACLACEEntry 8 }

gs2326pACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { gs2326pACLACEEntry 9 }

gs2326pACLACELogging OBJECT-TYPE
   SYNTAX      INTEGER { disable(0), enable(1) }
   MAX-ACCESS  read-write
   STATUS      current
   DESCRIPTION
       "default: 0,
        0: disable - Frames matching the ACE are not logged.
        1: enable - Frames matching the ACE are stored in the system log."
   ::= { gs2326pACLACEEntry 10 }

gs2326pACLACEMirror OBJECT-TYPE
   SYNTAX      INTEGER { disable(0), enable(1) }
   MAX-ACCESS  read-write
   STATUS      current
   DESCRIPTION
       "default: 0,
        0: disable - Frames matching the ACE are not mirrored.
        1: enable - Frames matching the ACE are mirrored."
   ::= { gs2326pACLACEEntry 11 }

gs2326pACLACERateLimiter OBJECT-TYPE
   SYNTAX      Integer32(0..12)
   MAX-ACCESS  read-write
   STATUS      current
   DESCRIPTION
       "default: 0,
        0: Disable
        range : 0 - 12 "
   ::= { gs2326pACLACEEntry 12 }

gs2326pACLACEShutdown OBJECT-TYPE
   SYNTAX      INTEGER { disable(0), enable(1) }
   MAX-ACCESS  read-write
   STATUS      current
   DESCRIPTION
       "default: 0,
        0: disable - Port shut down is disabled for the AC.
        1: enable - If a frame matches the ACE, the ingress port will be disabled."
   ::= { gs2326pACLACEEntry 13 }

gs2326pACLACEVLAN8021QTagged OBJECT-TYPE
   SYNTAX      INTEGER { disable(0), enable(1), any(2) }
   MAX-ACCESS  read-write
   STATUS      current
   DESCRIPTION
       "Specify whether frames can hit the action according to the 802.1Q tagged.
        default: 2,
        0: disable - Untagged frame only.
        1: enable - Tagged frame only.
        2: Any - Any value is allowed. "
   ::= { gs2326pACLACEEntry 14 }

gs2326pACLACEVLANTagPriority OBJECT-TYPE
   SYNTAX      Integer32(0..8)
   MAX-ACCESS  read-write
   STATUS      current
   DESCRIPTION
       "Specify the tag priority for this ACE.
        The tag priority can't be set when 802.1Q Tagged is disabled
        default: 8,
        8: Any,
        range : 0 - 8 "
   ::= { gs2326pACLACEEntry 15 }

gs2326pACLACEVLANVID OBJECT-TYPE
   SYNTAX      Integer32(0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { gs2326pACLACEEntry 16 }

gs2326pACLACEEtherType OBJECT-TYPE
   SYNTAX      Integer32(0..65535)
   MAX-ACCESS  read-write
   STATUS      current
   DESCRIPTION
       " 0: Any - Any but excluding 0x0800(IPv4) 0x0806(ARP) and 0x86DD(IPv6).
         range : 0 or 1536(0x0600)- 65535(0xffff). "
   ::= { gs2326pACLACEEntry 17 }

gs2326pACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { gs2326pACLACEEntry 18 }

gs2326pACLACEDMACType OBJECT-TYPE
   SYNTAX      INTEGER { any(0), broadcast(1), unicast(2), multicast(3) , macAddress(4) }
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address.
        range : 0 - 4 "
   ::= { gs2326pACLACEEntry 19 }

gs2326pACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { gs2326pACLACEEntry 20 }

gs2326pACLACEArpOpcode OBJECT-TYPE
   SYNTAX      INTEGER { any(0), arp(1), rarp(2), other(3), noData(4) }
   MAX-ACCESS  read-write
   STATUS      current
   DESCRIPTION
       "Configure ARP opcode for this ACE.
        default: 0,
        0: Any - Don't care.
        1: arp.
        2: rarp.
        3: other.
        4: No data.
        range : 0 - 4 "
   ::= { gs2326pACLACEEntry 21 }

gs2326pACLACEArpFlagsRequestReply OBJECT-TYPE
   SYNTAX      INTEGER { reply(0), request(1), any(2), noData(3)}
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 3 "
   ::= { gs2326pACLACEEntry 22 }

gs2326pACLACEArpFlagsArpSmac OBJECT-TYPE
   SYNTAX      INTEGER { notEqualSMAC(0), equalSMAC(1), any(2), noData(3)}
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 3 "
   ::= { gs2326pACLACEEntry 23 }

gs2326pACLACEArpFlagsRarpDmac OBJECT-TYPE
   SYNTAX      INTEGER { notEqualDMAC(0), equalDMAC(1), any(2), noData(3)}
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 3 "
   ::= { gs2326pACLACEEntry 24 }

gs2326pACLACEArpFlagsLength OBJECT-TYPE
   SYNTAX      INTEGER(0..3)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 3 "
   ::= { gs2326pACLACEEntry 25 }

gs2326pACLACEArpFlagsIp OBJECT-TYPE
   SYNTAX      INTEGER(0..3)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 3 "
   ::= { gs2326pACLACEEntry 26 }

gs2326pACLACEArpFlagsEthernet OBJECT-TYPE
   SYNTAX      INTEGER(0..3)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 3 "
   ::= { gs2326pACLACEEntry 27 }

gs2326pACLACESIPType OBJECT-TYPE
   SYNTAX      INTEGER { any(0), ip(1), noData(2) }
   MAX-ACCESS  read-write
   STATUS      current
   DESCRIPTION
       "Configure source IP address for this ACE.
        default: 0,
        0: Any - Don't care.
        1: IP Address.
        2: No data.
        range : 0 - 1"
   ::= { gs2326pACLACEEntry 28 }

gs2326pACLACESIPIPAddress OBJECT-TYPE
   SYNTAX      IpAddress
   MAX-ACCESS  read-write
   STATUS      current
   DESCRIPTION
       "A frame that hits this ACE matches this source IP address value."
   ::= { gs2326pACLACEEntry 29 }

gs2326pACLACESIPNetworkPrefix OBJECT-TYPE
   SYNTAX      Integer32(0..32)
   MAX-ACCESS  read-write
   STATUS      current
   DESCRIPTION
       "Network prefix.
        default: 32,
        0: No data.
        range : 1 - 32"
   ::= { gs2326pACLACEEntry 30 }


gs2326pACLACEDIPType OBJECT-TYPE
   SYNTAX      INTEGER { any(0), ip(1),noData(2) }
   MAX-ACCESS  read-write
   STATUS      current
   DESCRIPTION
       "Configure destination IP address for this ACE.
        default: 0,
        0: Any - Don't care.
        1: IP Address.
        2: No data.
        range : 0 - 1"
   ::= { gs2326pACLACEEntry 32 }

gs2326pACLACEDIPIPAddress OBJECT-TYPE
   SYNTAX      IpAddress
   MAX-ACCESS  read-write
   STATUS      current
   DESCRIPTION
       "A frame that hits this ACE matches this destination IP address value."
   ::= { gs2326pACLACEEntry 33 }

gs2326pACLACEDIPNetworkPrefix OBJECT-TYPE
   SYNTAX      Integer32(0..32)
   MAX-ACCESS  read-write
   STATUS      current
   DESCRIPTION
       "Network prefix.
        default: 32,
        0: No data.
        range : 1 - 32"
   ::= { gs2326pACLACEEntry 34 }


gs2326pACLACEIPProtocol OBJECT-TYPE
   SYNTAX      Integer32(0..257)
   MAX-ACCESS  read-write
   STATUS      current
   DESCRIPTION
       "Configure IP protocol for this ACE.
        default: 256,
        256: Any - Don't care.
        257: No data.
        range : 0 - 256"
   ::= { gs2326pACLACEEntry 36 }

gs2326pACLACEIPFlagsTTL OBJECT-TYPE
   SYNTAX      INTEGER (0..3)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 3 "
   ::= { gs2326pACLACEEntry 37 }

gs2326pACLACEIPFlagsOptions OBJECT-TYPE
   SYNTAX      INTEGER { unset(0), set(1), any(2), noData(3) }
   MAX-ACCESS  read-write
   STATUS      current
   DESCRIPTION
       "Configure IP options flag for this ACE.
        default: 2,
        0: IPv4 frames where the options flag is unset.
        1: IPv4 frames where the options flag is set.
        2: Any - Don't care.
        3: No data.
        range : 0 - 3 "
   ::= { gs2326pACLACEEntry 38 }

gs2326pACLACEIPFlagsFragment OBJECT-TYPE
   SYNTAX      INTEGER(0..3)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 3 "
   ::= { gs2326pACLACEEntry 39 }

gs2326pACLACEICMPType OBJECT-TYPE
   SYNTAX      Integer32(0..257)
   MAX-ACCESS  read-write
   STATUS      current
   DESCRIPTION
       "Configure ICMP type for this ACE.
        default: 256,
        256: Any - Don't care.
        257: No data.
        range : 0 - 256"
   ::= { gs2326pACLACEEntry 40 }

gs2326pACLACEICMPCode OBJECT-TYPE
   SYNTAX      Integer32(0..257)
   MAX-ACCESS  read-write
   STATUS      current
   DESCRIPTION
       "Configure ICMP code for this ACE.
        default: 256,
        256: Any - Don't care.
        257: No data.
        range : 0 - 257"
   ::= { gs2326pACLACEEntry 41 }

gs2326pACLACESourcePortMin OBJECT-TYPE
   SYNTAX      Integer32(0..65536)
   MAX-ACCESS  read-write
   STATUS      current
   DESCRIPTION
       "Configure Source UDP/TCP port range for this ACE.
        default: 0,
        65536: No data.
        range : 0 - 65536"
   ::= { gs2326pACLACEEntry 42 }

gs2326pACLACESourcePortMax OBJECT-TYPE
   SYNTAX      Integer32(0..65536)
   MAX-ACCESS  read-write
   STATUS      current
   DESCRIPTION
       "Configure Source UDP/TCP port range for this ACE.
        default: 0,
        65536: No data.
        range : 0 - 65536"
   ::= { gs2326pACLACEEntry 43 }

gs2326pACLACEDestPortMin OBJECT-TYPE
   SYNTAX      Integer32(0..65536)
   MAX-ACCESS  read-write
   STATUS      current
   DESCRIPTION
       "Configure Destination UDP/TCP port range for this ACE.
        default: 0,
        65536: No data.
        range : 0 - 65535"
   ::= { gs2326pACLACEEntry 44 }

gs2326pACLACEDestPortMax OBJECT-TYPE
   SYNTAX      Integer32(0..65536)
   MAX-ACCESS  read-write
   STATUS      current
   DESCRIPTION
       "Configure Destination UDP/TCP port range for this ACE.
        default: 0,
        65536: No data.
        range : 0 - 65535"
   ::= { gs2326pACLACEEntry 45 }

gs2326pACLACETCPFlagsFin OBJECT-TYPE
   SYNTAX      INTEGER { unset(0), set(1), any(2), noData(3) }
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 3 "
   ::= { gs2326pACLACEEntry 46 }

gs2326pACLACETCPFlagsSyn OBJECT-TYPE
   SYNTAX      INTEGER { unset(0), set(1), any(2), noData(3) }
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 3 "
   ::= { gs2326pACLACEEntry 47 }

gs2326pACLACETCPFlagsRst OBJECT-TYPE
   SYNTAX      INTEGER { unset(0), set(1), any(2), noData(3) }
   MAX-ACCESS  read-write
   STATUS      current
   DESCRIPTION
       "Configure TCP (RST) flags for this ACE.
        default: 2,
        0: TCP frames where the RST field is unset.
        1: TCP frames where the RST field is set.
        2: Any - Don't care.
        3: No data.
        range : 0 - 3 "
   ::= { gs2326pACLACEEntry 48 }

gs2326pACLACETCPFlagsPsh OBJECT-TYPE
   SYNTAX      INTEGER { unset(0), set(1), any(2), noData(3) }
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 3 "
   ::= { gs2326pACLACEEntry 49 }

gs2326pACLACETCPFlagsAck OBJECT-TYPE
   SYNTAX      INTEGER { unset(0), set(1), any(2), noData(3) }
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 3 "
   ::= { gs2326pACLACEEntry 50 }

gs2326pACLACETCPFlagsUrg OBJECT-TYPE
   SYNTAX      INTEGER { unset(0), set(1), any(2), noData(3) }
   MAX-ACCESS  read-write
   STATUS      current
   DESCRIPTION
       "Configure TCP (URG) flags for this ACE.
        default: 2,
        0: TCP frames where the URG field is unset.
        1: TCP frames where the URG field is set.
        2: Any - Don't care.
        3: No data.
        range : 0 - 3 "
   ::= { gs2326pACLACEEntry 51 }

gs2326pACLACERowStatus OBJECT-TYPE
   SYNTAX      INTEGER { active(1), notInservice(2), destroy(4), undo(5) }
   MAX-ACCESS  read-write
   STATUS      current
   DESCRIPTION
       " 1: active
         2: notInservice
         4: destroy
         5: undo"
   ::= { gs2326pACLACEEntry 66 }


gs2326pACLACEClear OBJECT-TYPE
   SYNTAX       INTEGER { noAction(0), clear(1) }
   MAX-ACCESS   read-write
   STATUS       current
   DESCRIPTION
       "default: 0
        0 : No action
        1 : Clear all ACL counters."
   ::= { gs2326pACLACE 3 }

gs2326pACLACEMoveACEID OBJECT-TYPE
   SYNTAX       Integer32(0..256)
   MAX-ACCESS   read-write
   STATUS       current
   DESCRIPTION
       "Move ACE,
        default: 0
        ACE ID must be exist.
        range : 1 - 256."
   ::= { gs2326pACLACE 4 }

gs2326pACLACEMoveNextACEID OBJECT-TYPE
   SYNTAX       Integer32(0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { gs2326pACLACE 5 }

gs2326pACLACEStatusTable OBJECT-TYPE
   SYNTAX      SEQUENCE OF GS2326PACLACEStatusEntry
   MAX-ACCESS  not-accessible
   STATUS      current
   DESCRIPTION
       " ACL ACE Status entry. "
   ::= { gs2326pACLACE 6 }

gs2326pACLACEStatusEntry OBJECT-TYPE
   SYNTAX      GS2326PACLACEStatusEntry
   MAX-ACCESS  not-accessible
   STATUS      current
   DESCRIPTION
       ""
   INDEX    { gs2326pACLACEStatusIndex  }
   ::= { gs2326pACLACEStatusTable 1 }

GS2326PACLACEStatusEntry ::= SEQUENCE {
   gs2326pACLACEStatusIndex          Integer32,
   gs2326pACLACEStatusUser           DisplayString,
   gs2326pACLACEStatusID             Integer32,
   gs2326pACLACEStatusIngressPort    DisplayString,
   gs2326pACLACEStatusFrameType      DisplayString,
   gs2326pACLACEStatusAction         DisplayString,
   gs2326pACLACEStatusRateLimiter    DisplayString,
   gs2326pACLACEStatusPortCopy       DisplayString,
   gs2326pACLACEStatusMirror         DisplayString,
   gs2326pACLACEStatusCPU            DisplayString,
   gs2326pACLACEStatusCounter        Counter32,
   gs2326pACLACEStatusConflict       DisplayString
}

gs2326pACLACEStatusIndex OBJECT-TYPE
   SYNTAX      Integer32(1..256)
   MAX-ACCESS  not-accessible
   STATUS      current
   DESCRIPTION
       " "
   ::= { gs2326pACLACEStatusEntry 1 }

gs2326pACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { gs2326pACLACEStatusEntry 2 }

gs2326pACLACEStatusID OBJECT-TYPE
   SYNTAX      Integer32(1..256)
   MAX-ACCESS  read-only
   STATUS      current
   DESCRIPTION
       " ACE ID.
         range : 1 - 256. "
   ::= { gs2326pACLACEStatusEntry 3 }

gs2326pACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { gs2326pACLACEStatusEntry 4 }

gs2326pACLACEStatusFrameType OBJECT-TYPE
   SYNTAX      DisplayString
   MAX-ACCESS  read-only
   STATUS      current
   DESCRIPTION
       " Indicates the frame type of the ACE. "
   ::= { gs2326pACLACEStatusEntry 5 }

gs2326pACLACEStatusAction OBJECT-TYPE
   SYNTAX      DisplayString
   MAX-ACCESS  read-only
   STATUS      current
   DESCRIPTION
       " Indicates the forwarding action of the ACE. "
   ::= { gs2326pACLACEStatusEntry 6 }

gs2326pACLACEStatusRateLimiter OBJECT-TYPE
   SYNTAX      DisplayString
   MAX-ACCESS  read-only
   STATUS      current
   DESCRIPTION
       " Indicates the rate limiter number of the ACE. "
   ::= { gs2326pACLACEStatusEntry 7 }

gs2326pACLACEStatusPortCopy OBJECT-TYPE
   SYNTAX      DisplayString
   MAX-ACCESS  read-only
   STATUS      current
   DESCRIPTION
       " Indicates the port redirect operation of the ACE. Frames matching the ACE are redirected to the port number. "
   ::= { gs2326pACLACEStatusEntry 8 }

gs2326pACLACEStatusMirror OBJECT-TYPE
   SYNTAX      DisplayString
   MAX-ACCESS  read-only
   STATUS      current
   DESCRIPTION
       " Specify the mirror operation of this port. "
   ::= { gs2326pACLACEStatusEntry 9 }

gs2326pACLACEStatusCPU OBJECT-TYPE
   SYNTAX      DisplayString
   MAX-ACCESS  read-only
   STATUS      current
   DESCRIPTION
       " Forward packet that matched the specific ACE to CPU. "
   ::= { gs2326pACLACEStatusEntry 10 }

gs2326pACLACEStatusCounter OBJECT-TYPE
   SYNTAX      Counter32
   MAX-ACCESS  read-only
   STATUS      current
   DESCRIPTION
       " The counter indicates the number of times the ACE was hit by a frame. "
   ::= { gs2326pACLACEStatusEntry 11 }

gs2326pACLACEStatusConflict OBJECT-TYPE
   SYNTAX      DisplayString
   MAX-ACCESS  read-only
   STATUS      current
   DESCRIPTION
       " Indicates the hardware status of the specific ACE. The specific ACE is not applied to the hardware due to hardware limitations. "
   ::= { gs2326pACLACEStatusEntry 12 }

gs2326pLoopProtection                                                  OBJECT IDENTIFIER ::= { gs2326pConfiguration 12 }

gs2326pLoopProtectionConfig                                            OBJECT IDENTIFIER ::= { gs2326pLoopProtection 1 }

gs2326pLoopProtectionGlobalEnable OBJECT-TYPE
   SYNTAX      INTEGER { disable(0), enable(1) }
   MAX-ACCESS  read-write
   STATUS      current
   DESCRIPTION
       "Configure loop protection mode.
        0: disable,
        1: enable,
        default: disable. "
   ::= { gs2326pLoopProtectionConfig 1 }

gs2326pLoopProtectionTranmisstionTime OBJECT-TYPE
   SYNTAX      Integer32(1..10)
   MAX-ACCESS  read-write
   STATUS      current
   DESCRIPTION
       "Configure loop protection transmit interval.
        default: 5,
        range: 1-10. "
   ::= { gs2326pLoopProtectionConfig 2 }

gs2326pLoopProtectionShutdownTime OBJECT-TYPE
   SYNTAX      Integer32(0..604800)
   MAX-ACCESS  read-write
   STATUS      current
   DESCRIPTION
       "Configure loop protection shutdown time.
        default: 180,
        range: 0-604800. "
   ::= { gs2326pLoopProtectionConfig 3 }

gs2326pLoopProtectionConfigurationTable OBJECT-TYPE
   SYNTAX      SEQUENCE OF GS2326PLoopProtectionConfigurationEntry
   MAX-ACCESS  not-accessible
   STATUS      current
   DESCRIPTION
       " Show Loop Protection configurations. "
   ::= { gs2326pLoopProtectionConfig 4 }

gs2326pLoopProtectionConfigurationEntry OBJECT-TYPE
   SYNTAX      GS2326PLoopProtectionConfigurationEntry
   MAX-ACCESS  not-accessible
   STATUS      current
   DESCRIPTION
       ""
   INDEX    { gs2326pLoopProtectionConfPort  }
   ::= { gs2326pLoopProtectionConfigurationTable 1 }

GS2326PLoopProtectionConfigurationEntry ::= SEQUENCE {
   gs2326pLoopProtectionConfPort	    Integer32,
   gs2326pLoopProtectionConfEnable	INTEGER,
   gs2326pLoopProtectionConfAction	INTEGER,
   gs2326pLoopProtectionConfTxmode	INTEGER
}

gs2326pLoopProtectionConfPort OBJECT-TYPE
   SYNTAX      Integer32(1..4095)
   MAX-ACCESS  not-accessible
   STATUS      current
   DESCRIPTION
       " port, range : 1 - port number. "
   ::= { gs2326pLoopProtectionConfigurationEntry 1 }

gs2326pLoopProtectionConfEnable OBJECT-TYPE
   SYNTAX      INTEGER { disable(0), enable(1) }
   MAX-ACCESS  read-write
   STATUS      current
   DESCRIPTION
       "Configure loop protection port mode.
        0: disable,
        1: enable,
        default: enable. "
   ::= { gs2326pLoopProtectionConfigurationEntry 2 }

gs2326pLoopProtectionConfAction OBJECT-TYPE
   SYNTAX      INTEGER { shutdown(0), shutdownLog(1), log(2) }
   MAX-ACCESS  read-write
   STATUS      current
   DESCRIPTION
       " Configure loop protection port action.
         0: Shutdown port,
         1: Shutdown port and Log,
         2: Log Only,
         default: Shutdown port. "
   ::= { gs2326pLoopProtectionConfigurationEntry 3 }

gs2326pLoopProtectionConfTxmode OBJECT-TYPE
   SYNTAX      INTEGER { disable(0), enable(1) }
   MAX-ACCESS  read-write
   STATUS      current
   DESCRIPTION
       "Configure loop protection port transmit mode.
        0: disable,
        1: enable,
        default: enable. "
   ::= { gs2326pLoopProtectionConfigurationEntry 4 }

gs2326pLoopProtectionStatusTable OBJECT-TYPE
   SYNTAX      SEQUENCE OF GS2326PLoopProtectionStatusEntry
   MAX-ACCESS  not-accessible
   STATUS      current
   DESCRIPTION
       " Show Loop Protection Status. "
   ::= { gs2326pLoopProtection 2 }

gs2326pLoopProtectionStatusEntry OBJECT-TYPE
   SYNTAX      GS2326PLoopProtectionStatusEntry
   MAX-ACCESS  not-accessible
   STATUS      current
   DESCRIPTION
       ""
   INDEX    { gs2326pLoopProtectionStatusPort  }
   ::= { gs2326pLoopProtectionStatusTable 1 }

GS2326PLoopProtectionStatusEntry ::= SEQUENCE {
   gs2326pLoopProtectionStatusPort	       Integer32,
   gs2326pLoopProtectionStatusAction	       DisplayString,
   gs2326pLoopProtectionStatusTransmit	   DisplayString,
   gs2326pLoopProtectionStatusLoops	       Integer32,
   gs2326pLoopProtectionStatusStatus	       DisplayString,
   gs2326pLoopProtectionStatusLoop	       DisplayString,
   gs2326pLoopProtectionStatusTimeLastLoop  DisplayString
}

gs2326pLoopProtectionStatusPort OBJECT-TYPE
   SYNTAX      Integer32(1..4095)
   MAX-ACCESS  not-accessible
   STATUS      current
   DESCRIPTION
       " port, range : 1 - port number. "
   ::= { gs2326pLoopProtectionStatusEntry 1 }

gs2326pLoopProtectionStatusAction OBJECT-TYPE
   SYNTAX      DisplayString
   MAX-ACCESS  read-only
   STATUS      current
   DESCRIPTION
       " The currently configured port action. "
   ::= { gs2326pLoopProtectionStatusEntry 2 }

gs2326pLoopProtectionStatusTransmit OBJECT-TYPE
   SYNTAX      DisplayString
   MAX-ACCESS  read-only
   STATUS      current
   DESCRIPTION
       " The currently configured port transmit mode. "
   ::= { gs2326pLoopProtectionStatusEntry 3 }

gs2326pLoopProtectionStatusLoops OBJECT-TYPE
   SYNTAX      Integer32(0..1000000)
   MAX-ACCESS  read-only
   STATUS      current
   DESCRIPTION
       " The number of loops detected on this port. "
   ::= { gs2326pLoopProtectionStatusEntry 4 }

gs2326pLoopProtectionStatusStatus OBJECT-TYPE
   SYNTAX      DisplayString
   MAX-ACCESS  read-only
   STATUS      current
   DESCRIPTION
       " The current loop protection status of the port. "
   ::= { gs2326pLoopProtectionStatusEntry 5 }

gs2326pLoopProtectionStatusLoop OBJECT-TYPE
   SYNTAX      DisplayString
   MAX-ACCESS  read-only
   STATUS      current
   DESCRIPTION
       " Whether a loop is currently detected on the port. "
   ::= { gs2326pLoopProtectionStatusEntry 6 }

gs2326pLoopProtectionStatusTimeLastLoop OBJECT-TYPE
   SYNTAX      DisplayString
   MAX-ACCESS  read-only
   STATUS      current
   DESCRIPTION
       " The time of the last loop event detected. "
   ::= { gs2326pLoopProtectionStatusEntry 7 }

gs2326pPoe                                                           OBJECT IDENTIFIER ::= { gs2326pConfiguration 13 }

gs2326pPoeStatus                                            OBJECT IDENTIFIER ::= { gs2326pPoe 1 }

gs2326pPoeStatusTable OBJECT-TYPE
   SYNTAX      SEQUENCE OF GS2326PPoeStatusEntry
   MAX-ACCESS  not-accessible
   STATUS      current
   DESCRIPTION
       " Configure PoE Scheduling Table. "
   ::= { gs2326pPoeStatus 1 }

gs2326pPoeStatusEntry OBJECT-TYPE
   SYNTAX      GS2326PPoeStatusEntry
   MAX-ACCESS  not-accessible
   STATUS      current
   DESCRIPTION
       ""
   INDEX    { gs2326pPoeStatusLocalPort }
   ::= { gs2326pPoeStatusTable 1 }

GS2326PPoeStatusEntry ::= SEQUENCE {
   gs2326pPoeStatusLocalPort	        Integer32,
   gs2326pPoeStatusPDclass	        INTEGER,
   gs2326pPoeStatusPowerRequested	    DisplayString,
   gs2326pPoeStatusPowerAllocated     DisplayString,
   gs2326pPoeStatusPowerUsed          DisplayString,
   gs2326pPoeStatusCurrentUsed        DisplayString,
   gs2326pPoeStatusPriority           DisplayString,
   gs2326pPoeStatusPortStatus         DisplayString
}

gs2326pPoeStatusLocalPort OBJECT-TYPE
   SYNTAX      Integer32(1..4094)
   MAX-ACCESS  not-accessible
   STATUS      current
   DESCRIPTION
       " port, range : 1 - port number. "
   ::= { gs2326pPoeStatusEntry 1}

gs2326pPoeStatusPDclass OBJECT-TYPE
   SYNTAX      INTEGER (0..4)
   MAX-ACCESS  read-only
   STATUS      current
   DESCRIPTION
       " Indicates the QCL user.
         0: Max. power 15.4 W,
         1: Max. power 4.0 W,
         2: Max. power 7.0 W,
         3: Max. power 15.4 W,
         4: Max. power 30.0 W. "
   ::= { gs2326pPoeStatusEntry 2 }

gs2326pPoeStatusPowerRequested OBJECT-TYPE
   SYNTAX      DisplayString
   MAX-ACCESS  read-only
   STATUS      current
   DESCRIPTION
      " The Power Requested shows the requested amount of power the PD wants to be reserved. "
   ::= { gs2326pPoeStatusEntry 3}

gs2326pPoeStatusPowerAllocated OBJECT-TYPE
   SYNTAX      DisplayString
   MAX-ACCESS  read-only
   STATUS      current
   DESCRIPTION
      " The Power Allocated shows the amount of power the switch has allocated for the PD. "
   ::= { gs2326pPoeStatusEntry 4}

gs2326pPoeStatusPowerUsed OBJECT-TYPE
   SYNTAX      DisplayString
   MAX-ACCESS  read-only
   STATUS      current
   DESCRIPTION
      " The Power Used shows how much power the PD currently is using. "
   ::= { gs2326pPoeStatusEntry 5}

gs2326pPoeStatusCurrentUsed OBJECT-TYPE
   SYNTAX      DisplayString
   MAX-ACCESS  read-only
   STATUS      current
   DESCRIPTION
      " The Power Used shows how much current the PD currently is using. "
   ::= { gs2326pPoeStatusEntry 6}

gs2326pPoeStatusPriority OBJECT-TYPE
   SYNTAX      DisplayString
   MAX-ACCESS  read-only
   STATUS      current
   DESCRIPTION
      " The Priority shows the port's priority configured by the user.  "
   ::= { gs2326pPoeStatusEntry 7}

gs2326pPoeStatusPortStatus OBJECT-TYPE
   SYNTAX      DisplayString
   MAX-ACCESS  read-only
   STATUS      current
   DESCRIPTION
      " The Port Status shows the port's status.  "
   ::= { gs2326pPoeStatusEntry 8}


gs2326pPoeStatusTotalPowerRequested OBJECT-TYPE
   SYNTAX      DisplayString
   MAX-ACCESS  read-only
   STATUS      current
   DESCRIPTION
      " Total Power Requested."
   ::= { gs2326pPoeStatus 2}

gs2326pPoeStatusTotalPowerAllocated OBJECT-TYPE
   SYNTAX      DisplayString
   MAX-ACCESS  read-only
   STATUS      current
   DESCRIPTION
      " Total Power allocated."
   ::= { gs2326pPoeStatus 3}

gs2326pPoeStatusTotalPowerUsed OBJECT-TYPE
   SYNTAX      DisplayString
   MAX-ACCESS  read-only
   STATUS      current
   DESCRIPTION
      " Total Power Used."
   ::= { gs2326pPoeStatus 4}

gs2326pPoeStatusTotalCurrentUsed OBJECT-TYPE
   SYNTAX      DisplayString
   MAX-ACCESS  read-only
   STATUS      current
   DESCRIPTION
      " Total Current Used."
   ::= { gs2326pPoeStatus 5}

gs2326pPoeMcuVersion OBJECT-TYPE
   SYNTAX      DisplayString
   MAX-ACCESS  read-only
   STATUS      current
   DESCRIPTION
      " PoE MCU version."
   ::= { gs2326pPoeStatus 6 }

gs2326pPoePowerDelay                                                 OBJECT IDENTIFIER ::= { gs2326pPoe 2 }

gs2326pPoePowerDelayTable OBJECT-TYPE
   SYNTAX      SEQUENCE OF GS2326PPoePowerDelayEntry
   MAX-ACCESS  not-accessible
   STATUS      current
   DESCRIPTION
       " Configure PoE Power Delay mode. "
   ::= { gs2326pPoePowerDelay 1 }

gs2326pPoePowerDelayEntry OBJECT-TYPE
   SYNTAX      GS2326PPoePowerDelayEntry
   MAX-ACCESS  not-accessible
   STATUS      current
   DESCRIPTION
       ""
   INDEX    { gs2326pPoePowerDelayPort  }
   ::= { gs2326pPoePowerDelayTable 1 }

GS2326PPoePowerDelayEntry ::= SEQUENCE {
   gs2326pPoePowerDelayPort	        Integer32,
   gs2326pPoePowerDelayMode	        INTEGER,
   gs2326pPoePowerDelayTime         Integer32
}

gs2326pPoePowerDelayPort OBJECT-TYPE
   SYNTAX      Integer32(1..4094)
   MAX-ACCESS  not-accessible
   STATUS      current
   DESCRIPTION
       " port, range : 1 - port number. "
   ::= { gs2326pPoePowerDelayEntry 1 }

gs2326pPoePowerDelayMode OBJECT-TYPE
   SYNTAX      INTEGER { disable(0), enable(1) }
   MAX-ACCESS  read-write
   STATUS      current
   DESCRIPTION
       "Turn on / off the power delay function,
        0: disable,
        1: enable,
        default: disable. "
   ::= { gs2326pPoePowerDelayEntry 2 }

gs2326pPoePowerDelayTime OBJECT-TYPE
   SYNTAX      Integer32(0..300)
   MAX-ACCESS  read-write
   STATUS      current
   DESCRIPTION
       "set Delay Time,
        default: 0,
        range: 0-300 sec. "
   ::= { gs2326pPoePowerDelayEntry 3 }

gs2326pPoeAutoCheck                                                 OBJECT IDENTIFIER ::= { gs2326pPoe 3 }

gs2326pPoeAutoCheckPingCheck OBJECT-TYPE
   SYNTAX      INTEGER { disable(0), enable(1) }
   MAX-ACCESS  read-write
   STATUS      current
   DESCRIPTION
       "connection between PoE port and power device.
        0: disable,
        1: enable,
        default: disable. "
   ::= { gs2326pPoeAutoCheck 1 }

gs2326pPoeAutoCheckTable OBJECT-TYPE
   SYNTAX      SEQUENCE OF GS2326PPoeAutoCheckEntry
   MAX-ACCESS  not-accessible
   STATUS      current
   DESCRIPTION
       " Configure PoE Power Delay mode. "
   ::= { gs2326pPoeAutoCheck 2 }

gs2326pPoeAutoCheckEntry OBJECT-TYPE
   SYNTAX      GS2326PPoeAutoCheckEntry
   MAX-ACCESS  not-accessible
   STATUS      current
   DESCRIPTION
       ""
   INDEX    { gs2326pPoeAutoCheckPort  }
   ::= { gs2326pPoeAutoCheckTable 1 }

GS2326PPoeAutoCheckEntry ::= SEQUENCE {
   gs2326pPoeAutoCheckPort	       Integer32,
   gs2326pPoeAutoCheckPingIPAddress  DisplayString,
   gs2326pPoeAutoCheckIntervalTime   Integer32,
   gs2326pPoeAutoCheckRetryTime      Integer32,
   gs2326pPoeAutoCheckFailureLog     DisplayString,
   gs2326pPoeAutoCheckFailureAction  INTEGER,
   gs2326pPoeAutoCheckRebootTime     Integer32
}

gs2326pPoeAutoCheckPort OBJECT-TYPE
   SYNTAX      Integer32(1..4094)
   MAX-ACCESS  not-accessible
   STATUS      current
   DESCRIPTION
       " port, range : 1 - port number. "
   ::= { gs2326pPoeAutoCheckEntry 1 }

gs2326pPoeAutoCheckPingIPAddress OBJECT-TYPE
   SYNTAX      DisplayString
   MAX-ACCESS  read-write
   STATUS      current
   DESCRIPTION
       "IP Address the system should ping.
        default: 0.0.0.0 . "
   ::= { gs2326pPoeAutoCheckEntry 2 }

gs2326pPoeAutoCheckIntervalTime OBJECT-TYPE
   SYNTAX      Integer32(10..120)
   MAX-ACCESS  read-write
   STATUS      current
   DESCRIPTION
       "Device will send checking message to PD each interval time.
        default: 30,
        range: 10-120 sec.  "
   ::= { gs2326pPoeAutoCheckEntry 3 }

gs2326pPoeAutoCheckRetryTime OBJECT-TYPE
   SYNTAX      Integer32(1..5)
   MAX-ACCESS  read-write
   STATUS      current
   DESCRIPTION
       "It will retry to send detection again.
        default: 3,
        range: 1-5.  "
   ::= { gs2326pPoeAutoCheckEntry 4 }

gs2326pPoeAutoCheckFailureLog OBJECT-TYPE
   SYNTAX      DisplayString
   MAX-ACCESS  read-only
   STATUS      current
   DESCRIPTION
       "Failure loggings counter. "
   ::= { gs2326pPoeAutoCheckEntry 5 }

gs2326pPoeAutoCheckFailureAction OBJECT-TYPE
   SYNTAX      INTEGER { nothing(0), reboot(1) }
   MAX-ACCESS  read-write
   STATUS      current
   DESCRIPTION
       "It will retry to send detection again,
        0: Nothing,
        1: Reboot Remote PD,
        default: Nothing. "
   ::= { gs2326pPoeAutoCheckEntry 6 }

gs2326pPoeAutoCheckRebootTime OBJECT-TYPE
   SYNTAX      Integer32(3..120)
   MAX-ACCESS  read-write
   STATUS      current
   DESCRIPTION
       "When PD has been rebooted, the PoE port restored power after the specified time.
        default: 15,
        range: 3-120 sec. "
   ::= { gs2326pPoeAutoCheckEntry 7 }

gs2326pPoeScheduling                                                 OBJECT IDENTIFIER ::= { gs2326pPoe 4 }

gs2326pPoeSchedulingTable OBJECT-TYPE
   SYNTAX      SEQUENCE OF GS2326PPoeSchedulingEntry
   MAX-ACCESS  not-accessible
   STATUS      current
   DESCRIPTION
       " Configure PoE Scheduling Table. "
   ::= { gs2326pPoeScheduling 1 }

gs2326pPoeSchedulingEntry OBJECT-TYPE
   SYNTAX      GS2326PPoeSchedulingEntry
   MAX-ACCESS  not-accessible
   STATUS      current
   DESCRIPTION
       ""
   INDEX    { gs2326pPoeSchedulingPort }
   ::= { gs2326pPoeSchedulingTable 1 }

GS2326PPoeSchedulingEntry ::= SEQUENCE {
   gs2326pPoeSchedulingPort	        Integer32,
   gs2326pPoeSchedulingStatus	        INTEGER
}

gs2326pPoeSchedulingPort OBJECT-TYPE
   SYNTAX      Integer32(1..4094)
   MAX-ACCESS  not-accessible
   STATUS      current
   DESCRIPTION
       " port, range : 1 - port number. "
   ::= { gs2326pPoeSchedulingEntry 1 }

gs2326pPoeSchedulingStatus OBJECT-TYPE
   SYNTAX      INTEGER { disable(0), enable(1) }
   MAX-ACCESS  read-write
   STATUS      current
   DESCRIPTION
       "PoE Scheduling Status.
        0: Disable,
        1: Enable,
        default: Disable. "
   ::= { gs2326pPoeSchedulingEntry 2 }

gs2326pPoeSchedulingTimeTable OBJECT-TYPE
   SYNTAX      SEQUENCE OF GS2326PPoeSchedulingTimeEntry
   MAX-ACCESS  not-accessible
   STATUS      current
   DESCRIPTION
       " Show Poe Scheduling Time Config. "
   ::= { gs2326pPoeScheduling 2 }

gs2326pPoeSchedulingTimeEntry OBJECT-TYPE
   SYNTAX      GS2326PPoeSchedulingTimeEntry
   MAX-ACCESS  not-accessible
   STATUS      current
   DESCRIPTION
       ""
   INDEX    { gs2326pPoeSchedulingTimePort, gs2326pPoeSchedulingTimeWeek, gs2326pPoeSchedulingTimeHour  }
   ::= { gs2326pPoeSchedulingTimeTable 1 }

GS2326PPoeSchedulingTimeEntry ::= SEQUENCE {
   gs2326pPoeSchedulingTimePort		Integer32,
   gs2326pPoeSchedulingTimeWeek		INTEGER,
   gs2326pPoeSchedulingTimeHour		Integer32,
   gs2326pPoeSchedulingProvidePower	INTEGER
}

gs2326pPoeSchedulingTimePort OBJECT-TYPE
   SYNTAX      Integer32(1..4095)
   MAX-ACCESS  not-accessible
   STATUS      current
   DESCRIPTION
       " port, range : 1 - port number. "
   ::= { gs2326pPoeSchedulingTimeEntry 1 }

gs2326pPoeSchedulingTimeWeek OBJECT-TYPE
   SYNTAX      INTEGER {
                        monday(1),
                        tuseday(2),
                        wednesday(3),
                        thursday(4),
                        friday(5),
                        saturday(6),
                        sunday(7)
                        }
   MAX-ACCESS  not-accessible
   STATUS      current
   DESCRIPTION
       " range: 1-7,
         Sunday:7, Monday:1, Tuseday:2, Wednesday:3, Thursday:4, Friday:5, Saturday:6.  "
   ::= { gs2326pPoeSchedulingTimeEntry 2 }

gs2326pPoeSchedulingTimeHour OBJECT-TYPE
   SYNTAX      Integer32(1..24)
   MAX-ACCESS  not-accessible
   STATUS      current
   DESCRIPTION
       " range: 1-24,
         24: hour 0, 1: hour 1, 2: hour2..."
   ::= { gs2326pPoeSchedulingTimeEntry 3 }

gs2326pPoeSchedulingProvidePower OBJECT-TYPE
   SYNTAX      INTEGER { disable(0), enable(1) }
   MAX-ACCESS  read-write
   STATUS      current
   DESCRIPTION
       " 0: disable,
         1: enable,
         default: disable.  "
   ::= { gs2326pPoeSchedulingTimeEntry 4 }

gs2326pPoeConfiguration                                                 OBJECT IDENTIFIER ::= { gs2326pPoe 5 }

gs2326pPoeConfigurationPrimaryPowerSupply  OBJECT-TYPE
   SYNTAX      Integer32(0..1000)
   MAX-ACCESS  read-only
   STATUS      current
   DESCRIPTION
       "It must be defined what amount of power the primary and backup power sources
        can deliver. "
   ::= { gs2326pPoeConfiguration 1 }

gs2326pPoeConfigurationRetryTime OBJECT-TYPE
   SYNTAX      Integer32(0|5|10|20|30|40|50|60)
   MAX-ACCESS  read-write
   STATUS      current
   DESCRIPTION
       "The period (in seconds) for trying to turn on an overloaded PoE port.
        0: disable,
        5 sec,10 sec,20 sec,30 sec,40 sec,50 sec,60 sec,
        default: 60 sec. "
   ::= { gs2326pPoeConfiguration 2 }

gs2326pPoeConfigurationTable OBJECT-TYPE
   SYNTAX      SEQUENCE OF GS2326PPoeConfigurationEntry
   MAX-ACCESS  not-accessible
   STATUS      current
   DESCRIPTION
       " Configure PoE Configuration mode. "
   ::= { gs2326pPoeConfiguration 3 }

gs2326pPoeConfigurationEntry OBJECT-TYPE
   SYNTAX      GS2326PPoeConfigurationEntry
   MAX-ACCESS  not-accessible
   STATUS      current
   DESCRIPTION
       ""
   INDEX    { gs2326pPoeConfigurationPort  }
   ::= { gs2326pPoeConfigurationTable 1 }

GS2326PPoeConfigurationEntry ::= SEQUENCE {
   gs2326pPoeConfigurationPort	       Integer32,
   gs2326pPoeConfigurationPoEMode       INTEGER,
   gs2326pPoeConfigurationPriority      INTEGER,
   gs2326pPoeConfigurationMaximumPower  DisplayString,
   gs2326pPoeConfigurationDetection     INTEGER,
   gs2326pPoeConfigurationReset         INTEGER
}

gs2326pPoeConfigurationPort OBJECT-TYPE
   SYNTAX      Integer32(1..4094)
   MAX-ACCESS  not-accessible
   STATUS      current
   DESCRIPTION
       " port, range : 1 - port number. "
   ::= { gs2326pPoeConfigurationEntry 1 }

gs2326pPoeConfigurationPoEMode OBJECT-TYPE
   SYNTAX      INTEGER { disable(0), enable(1) }
   MAX-ACCESS  read-write
   STATUS      current
   DESCRIPTION
       "The PoE Mode represents the PoE operating mode for the port.
        0: Disable,
        1: Enable,
        default: Enable. "
   ::= { gs2326pPoeConfigurationEntry 2 }

gs2326pPoeConfigurationPriority OBJECT-TYPE
   SYNTAX      INTEGER { low(0), high(1), critical(2) }
   MAX-ACCESS  read-write
   STATUS      current
   DESCRIPTION
       "The Priority represents the ports priority. There are three levels of power priority named Low, High and Critical.
        0: Low,
        1: High,
        2: Critical,
        default: Low.  "
   ::= { gs2326pPoeConfigurationEntry 3 }

gs2326pPoeConfigurationMaximumPower OBJECT-TYPE
   SYNTAX      DisplayString
   MAX-ACCESS  read-write
   STATUS      current
   DESCRIPTION
       "The Maximum Power value contains a numerical value that indicates the maximum
        power in watts that can be delivered to a remote device.
        default: 15.4[W],
        max: 30[W]. "
   ::= { gs2326pPoeConfigurationEntry 4 }

gs2326pPoeConfigurationDetection OBJECT-TYPE
   SYNTAX      INTEGER(0..5)
   MAX-ACCESS  read-write
   STATUS      current
   DESCRIPTION
       "Configure PoE port capacitor detection.
        0: No Detection(read only),
        1: legacy,
        2: 4-point,
        3: 4-point-legacy,
        4: 2-point,
        5: 2-point-legacy,
        default: 4-point. "
   ::= { gs2326pPoeConfigurationEntry 5 }

gs2326pPoeConfigurationReset OBJECT-TYPE
   SYNTAX      INTEGER { disable(0), enable(1) }
   MAX-ACCESS  read-write
   STATUS      current
   DESCRIPTION
       "Reset the specific PoE port.
        0: Disable,
        1: Enable,
        default: Disable. "
   ::= { gs2326pPoeConfigurationEntry 6 }

gs2326pPoeConfigurationLegacyMode  OBJECT-TYPE
   SYNTAX      INTEGER { disable(0), enable(1) }
   MAX-ACCESS  read-write
   STATUS      current
   DESCRIPTION
       "Legacy Detection.
        0: Disable,
        1: Enable,
        default: Disable. "
   ::= { gs2326pPoeConfiguration 4 }


gs2326pQos                                                             OBJECT IDENTIFIER ::= { gs2326pConfiguration 14 }

gs2326pQosPortClassification                                           OBJECT IDENTIFIER ::= { gs2326pQos 1 }

gs2326pQosPortClassificationTable OBJECT-TYPE
   SYNTAX      SEQUENCE OF GS2326PQosPortClassificationEntry
   MAX-ACCESS  not-accessible
   STATUS      current
   DESCRIPTION
       " QoS Ingress Port Classification . "
   ::= { gs2326pQosPortClassification  1 }

gs2326pQosPortClassificationEntry OBJECT-TYPE
   SYNTAX      GS2326PQosPortClassificationEntry
   MAX-ACCESS  not-accessible
   STATUS      current
   DESCRIPTION
       ""
   INDEX    { gs2326pQosPortClassificationPort  }
   ::= { gs2326pQosPortClassificationTable 1 }

GS2326PQosPortClassificationEntry ::= SEQUENCE {
   gs2326pQosPortClassificationPort	        Integer32,
   gs2326pQosPortClassificationQoSclass       Integer32,
   gs2326pQosPortClassificationDPlevel	    Integer32,
   gs2326pQosPortClassificationPCP	        Integer32,
   gs2326pQosPortClassificationDEI	        INTEGER,
   gs2326pQosPortClassificationTagClass	    INTEGER,
   gs2326pQosPortClassificationDSCPBased    INTEGER,
   gs2326pQosPortClassificationAddressMode  INTEGER
}

gs2326pQosPortClassificationPort OBJECT-TYPE
   SYNTAX      Integer32(1..4095)
   MAX-ACCESS  not-accessible
   STATUS      current
   DESCRIPTION
       " port, range : 1 - port number. "
   ::= { gs2326pQosPortClassificationEntry 1 }

gs2326pQosPortClassificationQoSclass OBJECT-TYPE
   SYNTAX      Integer32(0..7)
   MAX-ACCESS  read-write
   STATUS      current
   DESCRIPTION
      "Controls the default QoS class, i.e., the QoS class
      for frames not classified in any other way. There is
      a one to one mapping between QoS class, queue and priority.
      A QoS class of 0 (zero) has the lowest priority.
      Note: If the QoS class has been dynamically changed, then
      the actual QoS class is shown in parentheses after the
      configured QoS class.

      Configure the default QoS class.
        range: 0-7,
        default: 0. "
   ::= { gs2326pQosPortClassificationEntry 2 }

gs2326pQosPortClassificationDPlevel OBJECT-TYPE
   SYNTAX      Integer32(0|1)
   MAX-ACCESS  read-write
   STATUS      current
   DESCRIPTION
       " DP level for frames not classified in any other way.
         range: 0-1,
         default: 0. "
   ::= { gs2326pQosPortClassificationEntry 3 }

gs2326pQosPortClassificationPCP OBJECT-TYPE
   SYNTAX      Integer32(0..7)
   MAX-ACCESS  read-write
   STATUS      current
   DESCRIPTION
      " Priority Code Point. It is a 3-bit field storing the priority level for the 802.1Q frame.
        range: 0-7,
        default: 0. "
   ::= { gs2326pQosPortClassificationEntry 4 }

gs2326pQosPortClassificationDEI OBJECT-TYPE
   SYNTAX      INTEGER { disable(0), enable(1) }
   MAX-ACCESS  read-write
   STATUS      current
   DESCRIPTION
      " Drop Eligible Indicator. It is a 1-bit field in the VLAN.
        range 0-1,
        default: 0. "
   ::= { gs2326pQosPortClassificationEntry 5 }

gs2326pQosPortClassificationTagClass OBJECT-TYPE
   SYNTAX      INTEGER { disable(0), enable(1) }
   MAX-ACCESS  read-write
   STATUS      current
   DESCRIPTION
      " Configure the classification mode for tagged frames.
        0: Disable,
        1: Enable,
        default: Disable. "
   ::= { gs2326pQosPortClassificationEntry 6 }

gs2326pQosPortClassificationDSCPBased OBJECT-TYPE
   SYNTAX      INTEGER { disable(0), enable(1) }
   MAX-ACCESS  read-write
   STATUS      current
   DESCRIPTION
      " Click to Enable DSCP Based QoS Ingress Port Classification.
        0: disable,
        1: enable,
        default: disable. "
   ::= { gs2326pQosPortClassificationEntry 7 }

gs2326pQosPortClassificationAddressMode OBJECT-TYPE
   SYNTAX      INTEGER { source(0), destination(1) }
   MAX-ACCESS  read-write
   STATUS      current
   DESCRIPTION
      "The IP/MAC address mode specifying whether the QCL classification
       must be based on source (SMAC/SIP) or destination (DMAC/DIP)
       addresses on this port.
        0: source,
        1: destination,
        default: source. "
   ::= { gs2326pQosPortClassificationEntry 8 }

gs2326pQoSIngressPortTagClassificationTable OBJECT-TYPE
   SYNTAX      SEQUENCE OF GS2326PQoSIngressPortTagClassificationEntry
   MAX-ACCESS  not-accessible
   STATUS      current
   DESCRIPTION
       " Show QoS Ingress Port Tag Classification. "
   ::= { gs2326pQosPortClassification 2 }

gs2326pQoSIngressPortTagClassificationEntry OBJECT-TYPE
   SYNTAX      GS2326PQoSIngressPortTagClassificationEntry
   MAX-ACCESS  not-accessible
   STATUS      current
   DESCRIPTION
       ""
   INDEX    { gs2326pQoSIngressPortTagClassificationPort, gs2326pQoSIngressPortTagPCP, gs2326pQoSIngressPortTagDEI  }
   ::= { gs2326pQoSIngressPortTagClassificationTable 1 }

GS2326PQoSIngressPortTagClassificationEntry ::= SEQUENCE {
   gs2326pQoSIngressPortTagClassificationPort	Integer32,
   gs2326pQoSIngressPortTagPCP					INTEGER,
   gs2326pQoSIngressPortTagDEI					INTEGER,
   gs2326pQoSIngressPortTagQosClass				Integer32,
   gs2326pQoSIngressPortTagDPLevel				Integer32
}

gs2326pQoSIngressPortTagClassificationPort OBJECT-TYPE
   SYNTAX      Integer32(1..4095)
   MAX-ACCESS  not-accessible
   STATUS      current
   DESCRIPTION
       " port, range : 1 - port number. "
   ::= { gs2326pQoSIngressPortTagClassificationEntry 1 }

gs2326pQoSIngressPortTagPCP OBJECT-TYPE
   SYNTAX      INTEGER { pcp0(1), pcp1(2), pcp2(3), pcp3(4), pcp4(5), pcp5(6), pcp6(7), pcp7(8) }
   MAX-ACCESS  not-accessible
   STATUS      current
   DESCRIPTION
       " range: 1-8,
         PCP0:1, PCP1:2...  "
   ::= { gs2326pQoSIngressPortTagClassificationEntry 2 }

gs2326pQoSIngressPortTagDEI OBJECT-TYPE
   SYNTAX      INTEGER { dei0(1), dei1(2) }
   MAX-ACCESS  not-accessible
   STATUS      current
   DESCRIPTION
       " range: 1-2,
         DEI0:1, DEI1:2. "
   ::= { gs2326pQoSIngressPortTagClassificationEntry 3 }

gs2326pQoSIngressPortTagQosClass OBJECT-TYPE
   SYNTAX      Integer32 (0..7)
   MAX-ACCESS  read-write
   STATUS      current
   DESCRIPTION
       " range: 0-7.  "
   ::= { gs2326pQoSIngressPortTagClassificationEntry 4 }

gs2326pQoSIngressPortTagDPLevel OBJECT-TYPE
   SYNTAX      Integer32 (0|1)
   MAX-ACCESS  read-write
   STATUS      current
   DESCRIPTION
       " range: 0-1.  "
   ::= { gs2326pQoSIngressPortTagClassificationEntry 5 }


gs2326pQosPortPolicingTable OBJECT-TYPE
   SYNTAX      SEQUENCE OF GS2326PQosPortPolicingEntry
   MAX-ACCESS  not-accessible
   STATUS      current
   DESCRIPTION
       "  configure the Policer settings for all switch ports. "
   ::= { gs2326pQos  2 }

gs2326pQosPortPolicingEntry OBJECT-TYPE
   SYNTAX      GS2326PQosPortPolicingEntry
   MAX-ACCESS  not-accessible
   STATUS      current
   DESCRIPTION
       ""
   INDEX    { gs2326pQosPortPolicingPort  }
   ::= { gs2326pQosPortPolicingTable 1 }

GS2326PQosPortPolicingEntry ::= SEQUENCE {
   gs2326pQosPortPolicingPort	        Integer32,
   gs2326pQosPortPolicingMode           INTEGER,
   gs2326pQosPortPolicingRate	        Integer32,
   gs2326pQosPortPolicingUnit	        INTEGER,
   gs2326pQosPortPolicingFlowControl	INTEGER
}

gs2326pQosPortPolicingPort OBJECT-TYPE
   SYNTAX      Integer32 (1..4095)
   MAX-ACCESS  not-accessible
   STATUS      current
   DESCRIPTION
       " port, range : 1 - port number. "
   ::= { gs2326pQosPortPolicingEntry 1 }

gs2326pQosPortPolicingMode OBJECT-TYPE
   SYNTAX      INTEGER { disable(0), enable(1) }
   MAX-ACCESS  read-write
   STATUS      current
   DESCRIPTION
      " Controls whether the policer is enabled on this switch port.
        0: disable,
        1: enable,
        default: disable. "
   ::= { gs2326pQosPortPolicingEntry 2 }

gs2326pQosPortPolicingRate OBJECT-TYPE
   SYNTAX      Integer32(100..10000000)
   MAX-ACCESS  read-write
   STATUS      current
   DESCRIPTION
       " Controls the rate for the policer.
         range: 100-10000000(kbps/fps),
         default: 500(kbps). "
   ::= { gs2326pQosPortPolicingEntry 3 }

gs2326pQosPortPolicingUnit OBJECT-TYPE
   SYNTAX      INTEGER { kbps(0), fps(1) }
   MAX-ACCESS  read-write
   STATUS      current
   DESCRIPTION
       " Controls the unit of measure for the policer rate.
         0: kbps,
         1: fps,
         default: kbps. "
   ::= { gs2326pQosPortPolicingEntry 4 }

gs2326pQosPortPolicingFlowControl OBJECT-TYPE
   SYNTAX      INTEGER { disable(0), enable(1) }
   MAX-ACCESS  read-write
   STATUS      current
   DESCRIPTION
       " If flow control is enabled and the port is in flow control mode,
        then pause frames are sent instead of discarding frames.
         0: disable,
         1: enable,
         default: disable. "
   ::= { gs2326pQosPortPolicingEntry 5 }

gs2326pQosPortScheduler                                           OBJECT IDENTIFIER ::= { gs2326pQos 3 }

gs2326pQosPortSchedulerModeTable OBJECT-TYPE
   SYNTAX      SEQUENCE OF GS2326PQosPortSchedulerModeEntry
   MAX-ACCESS  not-accessible
   STATUS      current
   DESCRIPTION
       " configure the basic QoS Port Scheduler Mode settings for all switch ports. "
   ::= { gs2326pQosPortScheduler  1 }

gs2326pQosPortSchedulerModeEntry OBJECT-TYPE
   SYNTAX      GS2326PQosPortSchedulerModeEntry
   MAX-ACCESS  not-accessible
   STATUS      current
   DESCRIPTION
       ""
   INDEX    { gs2326pQosSchedulerModePort  }
   ::= { gs2326pQosPortSchedulerModeTable 1 }

GS2326PQosPortSchedulerModeEntry ::= SEQUENCE {
   gs2326pQosSchedulerModePort	                Integer32,
   gs2326pQosSchedulerMode                        INTEGER,
   gs2326pQosSchedulerShaper	                    INTEGER,
   gs2326pQosSchedulerShaperRate	                Integer32
}

gs2326pQosSchedulerModePort OBJECT-TYPE
   SYNTAX      Integer32 (1..4095)
   MAX-ACCESS  not-accessible
   STATUS      current
   DESCRIPTION
       " port, range : 1 - port number. "
   ::= { gs2326pQosPortSchedulerModeEntry 1 }

gs2326pQosSchedulerMode OBJECT-TYPE
   SYNTAX      INTEGER { strictPriority(0), weighted(1) }
   MAX-ACCESS  read-write
   STATUS      current
   DESCRIPTION
       " Controls whether the scheduler mode is Strict Priority or Weighted
       on this switch port.
       0:Strict Priority
       1:Weighted
         default: Strict Priority. "
   ::= { gs2326pQosPortSchedulerModeEntry 2 }

gs2326pQosSchedulerShaper OBJECT-TYPE
   SYNTAX      INTEGER { disable(0), enable(1) }
   MAX-ACCESS  read-write
   STATUS      current
   DESCRIPTION
       " Controls whether the port shaper is enabled
         0: Disable
         1: Enable.
         default: disable. "
   ::= { gs2326pQosPortSchedulerModeEntry 3 }

gs2326pQosSchedulerShaperRate OBJECT-TYPE
   SYNTAX      Integer32(100..1000000)
   MAX-ACCESS  read-write
   STATUS      current
   DESCRIPTION
       " Controls the rate for the port shaper.
         range: 100-1000000
         default: 500 kbps. "
   ::= { gs2326pQosPortSchedulerModeEntry 4 }

gs2326pQosPortSchedulerTable OBJECT-TYPE
   SYNTAX      SEQUENCE OF GS2326PQosPortSchedulerEntry
   MAX-ACCESS  not-accessible
   STATUS      current
   DESCRIPTION
       " Show Qos Port Scheduler. "
   ::= { gs2326pQosPortScheduler 2 }

gs2326pQosPortSchedulerEntry OBJECT-TYPE
   SYNTAX      GS2326PQosPortSchedulerEntry
   MAX-ACCESS  not-accessible
   STATUS      current
   DESCRIPTION
       ""
   INDEX    { gs2326pQosSchedulerPort, gs2326pQosSchedulerPortQueue}
   ::= { gs2326pQosPortSchedulerTable 1 }

GS2326PQosPortSchedulerEntry ::= SEQUENCE {
   gs2326pQosSchedulerPort						Integer32,
   gs2326pQosSchedulerPortQueue					INTEGER,
   gs2326pQosSchedulerPortQueueShaper				INTEGER,
   gs2326pQosSchedulerPortQueueShaperRate			Integer32,
   gs2326pQosSchedulerPortQueueShaperExcess		INTEGER,
   gs2326pQosSchedulerPortQueueSchedulerWeight	Integer32,
   gs2326pQosSchedulerPortQueueSchedulerPercent	DisplayString
}

gs2326pQosSchedulerPort OBJECT-TYPE
   SYNTAX      Integer32 (1..4095)
   MAX-ACCESS  not-accessible
   STATUS      current
   DESCRIPTION
       " port, range : 1 - port number. "
   ::= { gs2326pQosPortSchedulerEntry 1 }

gs2326pQosSchedulerPortQueue OBJECT-TYPE
   SYNTAX      INTEGER { q0(1), q1(2), q2(3), q3(4), q4(5), q5(6), q6(7), q7(8) }
   MAX-ACCESS  not-accessible
   STATUS      current
   DESCRIPTION
       " range: 1-8.
         Q0: 1, Q1: 2, ... "
   ::= { gs2326pQosPortSchedulerEntry 2 }

gs2326pQosSchedulerPortQueueShaper OBJECT-TYPE
   SYNTAX      INTEGER { disable(0), enable(1) }
   MAX-ACCESS  read-write
   STATUS      current
   DESCRIPTION
       " 0: disable  1:enable,
         default: 0.  "
   ::= { gs2326pQosPortSchedulerEntry 3 }

gs2326pQosSchedulerPortQueueShaperRate OBJECT-TYPE
   SYNTAX      Integer32(100..1000000)
   MAX-ACCESS  read-write
   STATUS      current
   DESCRIPTION
       " range: 100..1000000 kbps.  "
   ::= { gs2326pQosPortSchedulerEntry 4 }

gs2326pQosSchedulerPortQueueShaperExcess OBJECT-TYPE
   SYNTAX      INTEGER { disable(0), enable(1) }
   MAX-ACCESS  read-write
   STATUS      current
   DESCRIPTION
       " 0: disable  1:enable,
         default: 0.  "
   ::= { gs2326pQosPortSchedulerEntry 5 }

gs2326pQosSchedulerPortQueueSchedulerWeight OBJECT-TYPE
   SYNTAX      Integer32(0..100)
   MAX-ACCESS  read-write
   STATUS      current
   DESCRIPTION
       " range: 1-100,
         default: 17.
         Only use in Q0 - Q5.  Q6 & Q7 show 0 "
   ::= { gs2326pQosPortSchedulerEntry 6 }

gs2326pQosSchedulerPortQueueSchedulerPercent OBJECT-TYPE
   SYNTAX      DisplayString
   MAX-ACCESS  read-only
   STATUS      current
   DESCRIPTION
       " Only use in Q0 - Q5. Q6 & Q7 show empty "
   ::= { gs2326pQosPortSchedulerEntry 7 }

gs2326pQosPortEgressTagRemarking                                           OBJECT IDENTIFIER ::= { gs2326pQos 4 }

gs2326pQosPortEgressTagRemarkingTable OBJECT-TYPE
   SYNTAX      SEQUENCE OF GS2326PQosPortEgressTagRemarkingEntry
   MAX-ACCESS  not-accessible
   STATUS      current
   DESCRIPTION
       " configure the basic QoS Port Egress Tag Remark Configuration settings for all switch ports. "
   ::= { gs2326pQosPortEgressTagRemarking  1 }

gs2326pQosPortEgressTagRemarkingEntry OBJECT-TYPE
   SYNTAX      GS2326PQosPortEgressTagRemarkingEntry
   MAX-ACCESS  not-accessible
   STATUS      current
   DESCRIPTION
       ""
   INDEX    { gs2326pQosEgressTagRemarkingPort  }
   ::= { gs2326pQosPortEgressTagRemarkingTable 1 }

GS2326PQosPortEgressTagRemarkingEntry ::= SEQUENCE {
   gs2326pQosEgressTagRemarkingPort	                Integer32,
   gs2326pQosEgressTagRemarkingMode	                INTEGER
}

gs2326pQosEgressTagRemarkingPort OBJECT-TYPE
   SYNTAX      Integer32 (1..4095)
   MAX-ACCESS  not-accessible
   STATUS      current
   DESCRIPTION
       " port, range : 1 - port number. "
   ::= { gs2326pQosPortEgressTagRemarkingEntry 1 }

gs2326pQosEgressTagRemarkingMode OBJECT-TYPE
   SYNTAX      INTEGER { classified(0), default(1), mapped(2) }
   MAX-ACCESS  read-write
   STATUS      current
   DESCRIPTION
       " the tag remarking mode for this port.
       0:Classified, Use classified PCP/DEI values.
       1:Default, Use default PCP/DEI values.
       2:Mapped, Use mapped versions of QoS class and DP level."
   ::= { gs2326pQosPortEgressTagRemarkingEntry 2 }


gs2326pQosPortEgressTagRemarkingDefTable OBJECT-TYPE
   SYNTAX      SEQUENCE OF GS2326PQosPortEgressTagRemarkingDefEntry
   MAX-ACCESS  not-accessible
   STATUS      current
   DESCRIPTION
       " configure the basic QoS Port Egress Tag Remark Configuration settings for all switch ports. "
   ::= { gs2326pQosPortEgressTagRemarking  2 }

gs2326pQosPortEgressTagRemarkingDefEntry OBJECT-TYPE
   SYNTAX      GS2326PQosPortEgressTagRemarkingDefEntry
   MAX-ACCESS  not-accessible
   STATUS      current
   DESCRIPTION
       ""
   INDEX    { gs2326pQosEgressTagRemarkingDefPort  }
   ::= { gs2326pQosPortEgressTagRemarkingDefTable 1 }

GS2326PQosPortEgressTagRemarkingDefEntry ::= SEQUENCE {
   gs2326pQosEgressTagRemarkingDefPort	            Integer32,
   gs2326pQosEgressTagRemarkingDefPCP	                Integer32,
   gs2326pQosEgressTagRemarkingDefDEI	                INTEGER
}

gs2326pQosEgressTagRemarkingDefPort OBJECT-TYPE
   SYNTAX      Integer32(1..4095)
   MAX-ACCESS  not-accessible
   STATUS      current
   DESCRIPTION
       " port, range : 1 - port number. "
   ::= { gs2326pQosPortEgressTagRemarkingDefEntry 1 }

gs2326pQosEgressTagRemarkingDefPCP OBJECT-TYPE
   SYNTAX      Integer32(0..7)
   MAX-ACCESS  read-write
   STATUS      current
   DESCRIPTION
       " Controls the default PCP
       Range : 0-7"
   ::= { gs2326pQosPortEgressTagRemarkingDefEntry 2 }

gs2326pQosEgressTagRemarkingDefDEI OBJECT-TYPE
   SYNTAX      INTEGER { disable(0), enable(1) }
   MAX-ACCESS  read-write
   STATUS      current
   DESCRIPTION
       " controls the DEI
       Range 0-1"
   ::= { gs2326pQosPortEgressTagRemarkingDefEntry 3 }

gs2326pQosPortEgressTagRemarkingMapTable OBJECT-TYPE
   SYNTAX      SEQUENCE OF GS2326PQosPortEgressTagRemarkingMapEntry
   MAX-ACCESS  not-accessible
   STATUS      current
   DESCRIPTION
       " Show Qos Port Egress Tag Remarking Map. "
   ::= { gs2326pQosPortEgressTagRemarking 4 }

gs2326pQosPortEgressTagRemarkingMapEntry OBJECT-TYPE
   SYNTAX      GS2326PQosPortEgressTagRemarkingMapEntry
   MAX-ACCESS  not-accessible
   STATUS      current
   DESCRIPTION
       ""
   INDEX    { gs2326pQosPortEgressTagRemarkingMapPort, gs2326pQosTagRemarkingQoSClass, gs2326pQosTagRemarkingDPLevel  }
   ::= { gs2326pQosPortEgressTagRemarkingMapTable 1 }

GS2326PQosPortEgressTagRemarkingMapEntry ::= SEQUENCE {
   gs2326pQosPortEgressTagRemarkingMapPort	Integer32,
   gs2326pQosTagRemarkingQoSClass			INTEGER,
   gs2326pQosTagRemarkingDPLevel				INTEGER,
   gs2326pQosTagRemarkingPCP					Integer32,
   gs2326pQosTagRemarkingDEI					INTEGER
}

gs2326pQosPortEgressTagRemarkingMapPort OBJECT-TYPE
   SYNTAX      Integer32 (1..4095)
   MAX-ACCESS  not-accessible
   STATUS      current
   DESCRIPTION
       " port, range : 1 - port number. "
   ::= { gs2326pQosPortEgressTagRemarkingMapEntry 1 }

gs2326pQosTagRemarkingQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
       " range: 1-8,
         QoS Class0: 1, QoS Class1: 2...  "
   ::= { gs2326pQosPortEgressTagRemarkingMapEntry 2 }

gs2326pQosTagRemarkingDPLevel OBJECT-TYPE
   SYNTAX      INTEGER { level0(1), level1(2) }
   MAX-ACCESS  not-accessible
   STATUS      current
   DESCRIPTION
       " range: 1-2,
         DP Level0: 1, DP Level1: 2. "
   ::= { gs2326pQosPortEgressTagRemarkingMapEntry 3 }

gs2326pQosTagRemarkingPCP OBJECT-TYPE
   SYNTAX      Integer32 (0..7)
   MAX-ACCESS  read-write
   STATUS      current
   DESCRIPTION
       " range: 0-7.  "
   ::= { gs2326pQosPortEgressTagRemarkingMapEntry 4 }

gs2326pQosTagRemarkingDEI OBJECT-TYPE
   SYNTAX      INTEGER (0|1)
   MAX-ACCESS  read-write
   STATUS      current
   DESCRIPTION
       " range: 0-1.  "
   ::= { gs2326pQosPortEgressTagRemarkingMapEntry 5 }


gs2326pQosPortDSCPTable OBJECT-TYPE
   SYNTAX      SEQUENCE OF GS2326PQosPortDSCPEntry
   MAX-ACCESS  not-accessible
   STATUS      current
   DESCRIPTION
       " configure the basic QoS Port DSCP Configuration settings for all switch ports. "
   ::= { gs2326pQos  5 }

gs2326pQosPortDSCPEntry OBJECT-TYPE
   SYNTAX      GS2326PQosPortDSCPEntry
   MAX-ACCESS  not-accessible
   STATUS      current
   DESCRIPTION
       ""
   INDEX    { gs2326pQosPortDSCPPort  }
   ::= { gs2326pQosPortDSCPTable 1 }

GS2326PQosPortDSCPEntry ::= SEQUENCE {
   gs2326pQosPortDSCPPort	                Integer32,
   gs2326pQosPortDSCPIngressTranslate       INTEGER,
   gs2326pQosPortDSCPIngressClassify	    INTEGER,
   gs2326pQosPortDSCPEgressRewrite	        INTEGER
}

gs2326pQosPortDSCPPort OBJECT-TYPE
   SYNTAX      Integer32 (1..4095)
   MAX-ACCESS  not-accessible
   STATUS      current
   DESCRIPTION
       " port, range : 1 - port number. "
   ::= { gs2326pQosPortDSCPEntry 1 }

gs2326pQosPortDSCPIngressTranslate OBJECT-TYPE
   SYNTAX      INTEGER { disable(0), enable(1) }
   MAX-ACCESS  read-write
   STATUS      current
   DESCRIPTION
      " Configure DSCP ingress translation mode.
        0: disable,
        1: enable,
        default: disable. "
   ::= { gs2326pQosPortDSCPEntry 2 }

gs2326pQosPortDSCPIngressClassify OBJECT-TYPE
   SYNTAX      INTEGER(0..3)
   MAX-ACCESS  read-write
   STATUS      current
   DESCRIPTION
       " Classification for a port have 4 different values.
         range: 0-3,
         0: disable,No Ingress DSCP Classification.
         1: DSCP=0,Classify if incoming (or translated if enabled) DSCP is 0.
         2: Selected,Classify only selected DSCP for which classification is
         enabled as specified in DSCP Translation window for the specific DSCP.
         3: All,Classify all DSCP.
         default: disable. "
   ::= { gs2326pQosPortDSCPEntry 3 }

gs2326pQosPortDSCPEgressRewrite OBJECT-TYPE
   SYNTAX      INTEGER(0..3)
   MAX-ACCESS  read-write
   STATUS      current
   DESCRIPTION
       " Configure the port egress rewriting mode.
         range: 0-2
         0: Disable,No Egress rewrite.
         1: Enable, Rewrite enabled without remapping.
         2: Remap DP Unaware , DSCP from analyzer is remapped and frame is
         remarked with remapped DSCP value. The remapped DSCP value is always
         taken from the DSCP Translation->Egress Remap DP0 table.
         3: Remap DP Aware: DSCP from analyzer is remapped and frame is remarked
          with remapped DSCP value. Depending on the DP level of the frame, the
          remapped DSCP value is either taken from the DSCP Translation->Egress
          Remap DP0 table or from the DSCP Translation->Egress Remap DP1 table.
         default: disable. "
   ::= { gs2326pQosPortDSCPEntry 4 }


gs2326pQosDSCPTable OBJECT-TYPE
   SYNTAX      SEQUENCE OF GS2326PQosDSCPEntry
   MAX-ACCESS  not-accessible
   STATUS      current
   DESCRIPTION
       " configure the basic QoS DSCP based QoS Ingress Classification settings for all switches. "
   ::= { gs2326pQos  6 }

gs2326pQosDSCPEntry OBJECT-TYPE
   SYNTAX      GS2326PQosDSCPEntry
   MAX-ACCESS  not-accessible
   STATUS      current
   DESCRIPTION
       ""
   INDEX    { gs2326pQosDSCPList  }
   ::= { gs2326pQosDSCPTable 1 }

GS2326PQosDSCPEntry ::= SEQUENCE {
   gs2326pQosDSCPList       Integer32,
   gs2326pQosDSCP           DisplayString,
   gs2326pQosDSCPTrust      INTEGER,
   gs2326pQosDSCPQosClass	  Integer32,
   gs2326pQosDSCPDPL	      INTEGER
}

gs2326pQosDSCPList OBJECT-TYPE
   SYNTAX      Integer32(1..64)
   MAX-ACCESS  not-accessible
   STATUS      current
   DESCRIPTION
      " DSCP mapping table index(1-64). "
   ::= { gs2326pQosDSCPEntry 1 }

gs2326pQosDSCP OBJECT-TYPE
   SYNTAX      DisplayString
   MAX-ACCESS  read-only
   STATUS      current
   DESCRIPTION
      "Maximum number of supported DSCP values are 64."
   ::= { gs2326pQosDSCPEntry 2 }

gs2326pQosDSCPTrust OBJECT-TYPE
   SYNTAX      INTEGER { disable(0), enable(1) }
   MAX-ACCESS  read-write
   STATUS      current
   DESCRIPTION
      " Controls whether a specific DSCP value is trusted. Only frames with
      trusted DSCP values are mapped to a specific QoS class and Drop Precedence
       Level. Frames with untrusted DSCP values are treated as a non-IP frame.
        0: disable,
        1: enable,
        default: disable. "
   ::= { gs2326pQosDSCPEntry 3 }

gs2326pQosDSCPQosClass OBJECT-TYPE
   SYNTAX      Integer32(0..7)
   MAX-ACCESS  read-write
   STATUS      current
   DESCRIPTION
      " QoS class.
        range: 0-7,
        default: 0. "
   ::= { gs2326pQosDSCPEntry 4 }

gs2326pQosDSCPDPL OBJECT-TYPE
   SYNTAX      INTEGER(0|1)
   MAX-ACCESS  read-write
   STATUS      current
   DESCRIPTION
      " Drop Precedence Level.
        range: 0-1,
        default: disable. "
   ::= { gs2326pQosDSCPEntry 5 }

gs2326pQosDSCPTranslationTable OBJECT-TYPE
   SYNTAX      SEQUENCE OF GS2326PQosDSCPTranslationEntry
   MAX-ACCESS  not-accessible
   STATUS      current
   DESCRIPTION
       "  configure the basic QoS DSCP Translation settings for all switches. "
   ::= { gs2326pQos  7 }

gs2326pQosDSCPTranslationEntry OBJECT-TYPE
   SYNTAX      GS2326PQosDSCPTranslationEntry
   MAX-ACCESS  not-accessible
   STATUS      current
   DESCRIPTION
       ""
   INDEX    { gs2326pQosDSCPTranslationList  }
   ::= { gs2326pQosDSCPTranslationTable 1 }

GS2326PQosDSCPTranslationEntry ::= SEQUENCE {
   gs2326pQosDSCPTranslationList                 Integer32,
   gs2326pQosDSCPTranslationDSCPBasedId          DisplayString,
   gs2326pQosDSCPTranslationIngressTranslate     Integer32,
   gs2326pQosDSCPTranslationIngressClassify      INTEGER,
   gs2326pQosDSCPTranslationEgressRemapDP0       Integer32,
   gs2326pQosDSCPTranslationEgressRemapDP1       Integer32
}

gs2326pQosDSCPTranslationList OBJECT-TYPE
   SYNTAX      Integer32(1..64)
   MAX-ACCESS  not-accessible
   STATUS      current
   DESCRIPTION
      " DSCP translation table index(1-64). "
   ::= { gs2326pQosDSCPTranslationEntry 1 }

gs2326pQosDSCPTranslationDSCPBasedId OBJECT-TYPE
   SYNTAX      DisplayString
   MAX-ACCESS  read-write
   STATUS      current
   DESCRIPTION
      " Configure global ingress DSCP translation table. "
   ::= { gs2326pQosDSCPTranslationEntry 2 }

gs2326pQosDSCPTranslationIngressTranslate OBJECT-TYPE
   SYNTAX      Integer32(0..63)
   MAX-ACCESS  read-write
   STATUS      current
   DESCRIPTION
      " DSCP at Ingress side can be translated to any of DSCP values.
        range: 0-63,
        default: 0. "
   ::= { gs2326pQosDSCPTranslationEntry 3 }

gs2326pQosDSCPTranslationIngressClassify OBJECT-TYPE
   SYNTAX      INTEGER { disable(0), enable(1) }
   MAX-ACCESS  read-write
   STATUS      current
   DESCRIPTION
      " Configure DSCP ingress classification.
        0: disable,
        1: enable,
        default: disable. "
   ::= { gs2326pQosDSCPTranslationEntry 4 }

gs2326pQosDSCPTranslationEgressRemapDP0 OBJECT-TYPE
   SYNTAX      Integer32(0..63)
   MAX-ACCESS  read-write
   STATUS      current
   DESCRIPTION
      "Controls the remapping for frames with DP level 0.
      Select the DSCP value from select menu to which you want to remap.
        range: 0-63,
        default: 0. "
   ::= { gs2326pQosDSCPTranslationEntry 5 }

gs2326pQosDSCPTranslationEgressRemapDP1 OBJECT-TYPE
   SYNTAX      Integer32(0..63)
   MAX-ACCESS  read-write
   STATUS      current
   DESCRIPTION
      "Controls the remapping for frames with DP level 1.
      Select the DSCP value from select menu to which you want to remap.
        range: 0-63,
        default: 0. "
   ::= { gs2326pQosDSCPTranslationEntry 6 }


gs2326pQosDSCPClassificationTable OBJECT-TYPE
   SYNTAX      SEQUENCE OF GS2326PQosDSCPClassificationEntry
   MAX-ACCESS  not-accessible
   STATUS      current
   DESCRIPTION
       "   configure the mapping of QoS class  to DSCP value. "
   ::= { gs2326pQos  8 }

gs2326pQosDSCPClassificationEntry OBJECT-TYPE
   SYNTAX      GS2326PQosDSCPClassificationEntry
   MAX-ACCESS  not-accessible
   STATUS      current
   DESCRIPTION
       ""
   INDEX    { gs2326pQosDSCPClassificationQoSClass, gs2326pQosDSCPClassificationDPL }
   ::= { gs2326pQosDSCPClassificationTable 1 }

GS2326PQosDSCPClassificationEntry ::= SEQUENCE {
   gs2326pQosDSCPClassificationQoSClass		INTEGER,
   gs2326pQosDSCPClassificationDPL			INTEGER,
   gs2326pQosDSCPClassificationDSCP			Integer32
}

gs2326pQosDSCPClassificationQoSClass OBJECT-TYPE
   SYNTAX      INTEGER {
                        class0(1),
                        class1(2),
                        class2(3),
                        class3(4),
                        class4(5),
                        class5(6),
                        class6(7),
                        class7(8)
                        }
   MAX-ACCESS  not-accessible
   STATUS      current
   DESCRIPTION
      " Actual QoS class. Index 1~8 mean Qos Class 0~7."
   ::= { gs2326pQosDSCPClassificationEntry 1 }

gs2326pQosDSCPClassificationDPL OBJECT-TYPE
   SYNTAX      INTEGER(1|2)
   MAX-ACCESS  not-accessible
   STATUS      current
   DESCRIPTION
      " DPL. Index 1~2 mean DPL 0~1."
   ::= { gs2326pQosDSCPClassificationEntry 2 }

gs2326pQosDSCPClassificationDSCP OBJECT-TYPE
   SYNTAX      Integer32(0..63)
   MAX-ACCESS  read-write
   STATUS      current
   DESCRIPTION
      " Select the classified DSCP value.
        range: 0-63,
        default: 0. "
   ::= { gs2326pQosDSCPClassificationEntry 3 }

gs2326pQosControlList                                         OBJECT IDENTIFIER ::= { gs2326pQos 9 }

gs2326pQosQceCreate OBJECT-TYPE
   SYNTAX       INTEGER { none(0), create(1) }
   MAX-ACCESS   read-write
   STATUS       current
   DESCRIPTION
       "default: 0
        0 : None  (read only)
        1 : Create an Qos entry"
   ::= { gs2326pQosControlList 1 }

gs2326pQosQceTable OBJECT-TYPE
   SYNTAX      SEQUENCE OF GS2326PQosQceEntry
   MAX-ACCESS  not-accessible
   STATUS      current
   DESCRIPTION
       " Create Qos QCE entry. "
   ::= { gs2326pQosControlList 2 }

gs2326pQosQceEntry OBJECT-TYPE
   SYNTAX      GS2326PQosQceEntry
   MAX-ACCESS  not-accessible
   STATUS      current
   DESCRIPTION
       ""
   INDEX    { gs2326pQosQceIndex  }
   ::= { gs2326pQosQceTable 1 }

GS2326PQosQceEntry ::= SEQUENCE {
   gs2326pQosQceIndex                Integer32,
   gs2326pQosQceID                   Integer32,
   gs2326pQosQceNextID               Integer32,
   gs2326pQosQcePortMembers          DisplayString,

   gs2326pQosQceTag                  DisplayString,
   gs2326pQosQceVID                  DisplayString,
   gs2326pQosPCP                     DisplayString,
   gs2326pQosDEI                     DisplayString,
   gs2326pQosSMAC                    DisplayString,
   gs2326pQosDMACType                DisplayString,
   gs2326pQosFrameType               INTEGER,

   gs2326pQosMacEtherType            DisplayString,

   gs2326pQosLLCSSAPAddr             DisplayString,
   gs2326pQosLLCDSAPAddr             DisplayString,
   gs2326pQosLLCControl              DisplayString,

   gs2326pQosSNAPPID                 DisplayString,

   gs2326pQosIpv4Protocol            DisplayString,
   gs2326pQosIpv4ProtocolValue       Integer32,
   gs2326pQosIpv4ProtocolUDPSport    DisplayString,
   gs2326pQosIpv4ProtocolUDPDport    DisplayString,
   gs2326pQosIpv4ProtocolTCPSport    DisplayString,
   gs2326pQosIpv4ProtocolTCPDport    DisplayString,
   gs2326pQosIpv4Ip                  DisplayString,
   gs2326pQosIpv4Mask                DisplayString,
   gs2326pQosIpv4IPFragment          INTEGER,
   gs2326pQosIpv4DSCP                DisplayString,


   gs2326pQosIpv6Protocol            DisplayString,
   gs2326pQosIpv6ProtocolValue       Integer32,
   gs2326pQosIpv6ProtocolUDPSport    DisplayString,
   gs2326pQosIpv6ProtocolUDPDport    DisplayString,
   gs2326pQosIpv6ProtocolTCPSport    DisplayString,
   gs2326pQosIpv6ProtocolTCPDport    DisplayString,
   gs2326pQosIpv6Ip                  DisplayString,
   gs2326pQosIpv6Mask                DisplayString,
   gs2326pQosIpv6DSCP                DisplayString,

   gs2326pQosActionClass             Integer32,
   gs2326pQosActionDPL               INTEGER,
   gs2326pQosActionDSCP              Integer32,
   gs2326pQosQceRowStatus            INTEGER
}

gs2326pQosQceIndex OBJECT-TYPE
   SYNTAX      Integer32(1..256)
   MAX-ACCESS  not-accessible
   STATUS      current
   DESCRIPTION
       " "
   ::= { gs2326pQosQceEntry 1 }

gs2326pQosQceID OBJECT-TYPE
   SYNTAX      Integer32(1..256)
   MAX-ACCESS  read-write
   STATUS      current
   DESCRIPTION
       " If the QCE ID is specified and an entry with this QCE ID
         already exists, the QCE will be modified. Otherwise, a
         new QCE will be added.
         range : 1 - 256. "
   ::= { gs2326pQosQceEntry 2 }

gs2326pQosQceNextID OBJECT-TYPE
   SYNTAX      Integer32(1..256)
   MAX-ACCESS  read-write
   STATUS      current
   DESCRIPTION
       " If the next QCE ID is non zero, the QCE will be placed
         before this QCE in the list. If the next QCE ID is zero,
         the QCE will be placed last in the list.
         range : 1 - 256. "
   ::= { gs2326pQosQceEntry 3 }

gs2326pQosQcePortMembers OBJECT-TYPE
   SYNTAX      DisplayString
   MAX-ACCESS  read-write
   STATUS      current
   DESCRIPTION
       " Indicates the ingress port of the QCE. Possible values are:
         All: The QCE will match all ingress port.
         Port: The QCE will match a specific ingress port.Format: 1,3-6."
   ::= { gs2326pQosQceEntry 4 }

gs2326pQosQceTag OBJECT-TYPE
   SYNTAX      DisplayString
   MAX-ACCESS  read-write
   STATUS      current
   DESCRIPTION
       " Value of Tag field can be 'Any', 'Untag' or 'Tag'. "
   ::= { gs2326pQosQceEntry 5 }

gs2326pQosQceVID OBJECT-TYPE
   SYNTAX      DisplayString
   MAX-ACCESS  read-write
   STATUS      current
   DESCRIPTION
       " Valid value of VLAN ID can be any value in 'Specific 1~4094' or 'range 1-4094' or 'Any'. "
   ::= { gs2326pQosQceEntry 6 }

gs2326pQosPCP OBJECT-TYPE
   SYNTAX      DisplayString
   MAX-ACCESS  read-write
   STATUS      current
   DESCRIPTION
       " Priority Code Point: Valid value PCP are specific(0, 1, 2, 3, 4, 5, 6, 7)
         or range(0-1, 2-3, 4-5, 6-7, 0-3, 4-7) or 'Any'. "
   ::= { gs2326pQosQceEntry 7 }

gs2326pQosDEI OBJECT-TYPE
   SYNTAX      DisplayString
   MAX-ACCESS  read-write
   STATUS      current
   DESCRIPTION
       " Drop Eligible Indicator: Valid value of DEI can be any of values between 0, 1 or 'Any'. "
   ::= { gs2326pQosQceEntry 8 }

gs2326pQosSMAC  OBJECT-TYPE
   SYNTAX      DisplayString
   MAX-ACCESS  read-write
   STATUS      current
   DESCRIPTION
       "  Source MAC address: 24 MS bits OUI(00-00-00 ~ FF-FF-FF) or 'Any'. "
   ::= { gs2326pQosQceEntry 9 }

gs2326pQosDMACType OBJECT-TYPE
   SYNTAX      DisplayString
   MAX-ACCESS  read-write
   STATUS      current
   DESCRIPTION
       " Destination MAC type: possible values are 'UC'(unicast), 'MC'(multicast), 'BC'(broadcast) or 'Any'. "
   ::= { gs2326pQosQceEntry 10 }

gs2326pQosFrameType OBJECT-TYPE
   SYNTAX      INTEGER {
                        any(1),
                        ethernet(2),
                        llc(3),
                        snap(4),
                        ipv4(5),
                        ipv6(6)
                        }
   MAX-ACCESS  read-write
   STATUS      current
   DESCRIPTION
       " Frame Type can have any of the following values:
         1: Any,
         2: Ethernet,
         3: LLC,
         4: SNAP,
         5: IPv4,
         6: IPv6. "
   ::= { gs2326pQosQceEntry 11 }

gs2326pQosMacEtherType OBJECT-TYPE
   SYNTAX      DisplayString
   MAX-ACCESS  read-write
   STATUS      current
   DESCRIPTION
       " Valid ethernet type can have a value within 0x600-0xFFFF or 'Any' ,
         but excluding 0x800(IPv4) and 0x86DD(IPv6),
         range: 0000-FFFF,
         default: Any."
   ::= { gs2326pQosQceEntry 12 }

gs2326pQosLLCSSAPAddr OBJECT-TYPE
   SYNTAX      DisplayString
   MAX-ACCESS  read-write
   STATUS      current
   DESCRIPTION
       " Valid SSAP(Source Service Access Point) can vary from 0x00 to 0xFF or 'Any',
         range: 00-FF,
         default: Any. "
   ::= { gs2326pQosQceEntry 13 }

gs2326pQosLLCDSAPAddr OBJECT-TYPE
   SYNTAX      DisplayString
   MAX-ACCESS  read-write
   STATUS      current
   DESCRIPTION
       " Valid DSAP(Destination Service Access Point) can vary from 0x00 to 0xFF or 'Any',
         range: 00-FF,
         default: Any. "
   ::= { gs2326pQosQceEntry 14 }

gs2326pQosLLCControl OBJECT-TYPE
   SYNTAX      DisplayString
   MAX-ACCESS  read-write
   STATUS      current
   DESCRIPTION
       " Valid Control field can vary from 0x00 to 0xFF or 'Any',
         range: 00-FF,
         default: Any. "
   ::= { gs2326pQosQceEntry 15 }

gs2326pQosSNAPPID OBJECT-TYPE
   SYNTAX      DisplayString
   MAX-ACCESS  read-write
   STATUS      current
   DESCRIPTION
       " Valid PID(a.k.a ethernet type) can have value within 0x00-0xFFFF or 'Any',
         range: 0000-FFFF,
         default: Any. "
   ::= { gs2326pQosQceEntry 16 }

gs2326pQosIpv4Protocol OBJECT-TYPE
   SYNTAX      DisplayString
   MAX-ACCESS  read-write
   STATUS      current
   DESCRIPTION
       " IP protocol number: (Other, TCP or UDP) or 'Any'. "
   ::= { gs2326pQosQceEntry 17 }

gs2326pQosIpv4ProtocolValue  OBJECT-TYPE
   SYNTAX      Integer32(0..255)
   MAX-ACCESS  read-write
   STATUS      current
   DESCRIPTION
       " Ipv4 Protocol is Other.
         range: 0-255
         default: 0. "
   ::= { gs2326pQosQceEntry 18 }

gs2326pQosIpv4ProtocolUDPSport OBJECT-TYPE
   SYNTAX      DisplayString
   MAX-ACCESS  read-write
   STATUS      current
   DESCRIPTION
       " Source  TCP/UDP port:(0-65535) or 'Any',
         specific or port range applicable for IP protocol UDP/TCP. "
   ::= { gs2326pQosQceEntry 19 }

gs2326pQosIpv4ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326pQosQceEntry 20 }

gs2326pQosIpv4ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326pQosQceEntry 21 }

gs2326pQosIpv4ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326pQosQceEntry 22 }

gs2326pQosIpv4Ip OBJECT-TYPE
   SYNTAX      DisplayString
   MAX-ACCESS  read-write
   STATUS      current
   DESCRIPTION
       "  Specific Source IP address in value format or value 0.0.0.0 is 'Any'.
          if Ipv4 Mask value 0.0.0.0 is 'Any' ,IP address value also is 'Any'.
          (x.y.z.w),x=0 unless y.z.w also 0,x not is 127 or greater than 223.
          If a port is configured to match on DMAC/DIP, this field is the
          Destination IP address."
   ::= { gs2326pQosQceEntry 23 }

gs2326pQosIpv4Mask OBJECT-TYPE
   SYNTAX      DisplayString
   MAX-ACCESS  read-write
   STATUS      current
   DESCRIPTION
       " Specific IP address in mask format or value 0.0.0.0 is 'Any'. "
   ::= { gs2326pQosQceEntry 24 }

gs2326pQosIpv4IPFragment OBJECT-TYPE
   SYNTAX      INTEGER { any(0), no(1), yes(2) }
   MAX-ACCESS  read-write
   STATUS      current
   DESCRIPTION
       " IPv4 frame fragmented option:
         2: yes,
         1: no,
         0: any. "
   ::= { gs2326pQosQceEntry 25 }

gs2326pQosIpv4DSCP OBJECT-TYPE
   SYNTAX      DisplayString
   MAX-ACCESS  read-write
   STATUS      current
   DESCRIPTION
       " Diffserv Code Point value (DSCP): It can be a specific value,
         range of values or 'Any'. DSCP values are in the range 0-63. "
   ::= { gs2326pQosQceEntry 26 }

gs2326pQosIpv6Protocol OBJECT-TYPE
   SYNTAX      DisplayString
   MAX-ACCESS  read-write
   STATUS      current
   DESCRIPTION
       " IP protocol number: (Other, TCP or UDP) or 'Any'. "
   ::= { gs2326pQosQceEntry 27 }

gs2326pQosIpv6ProtocolValue OBJECT-TYPE
   SYNTAX      Integer32(0..255)
   MAX-ACCESS  read-write
   STATUS      current
   DESCRIPTION
       " when IPv6 protocol is Other ,
         range: 0-255. "
   ::= { gs2326pQosQceEntry 28 }

gs2326pQosIpv6ProtocolUDPSport OBJECT-TYPE
   SYNTAX      DisplayString
   MAX-ACCESS  read-write
   STATUS      current
   DESCRIPTION
       " Source TCP/UDP port:(0-65535) or 'Any',
         specific or port range applicable for IP protocol UDP/TCP. "
   ::= { gs2326pQosQceEntry 29 }

gs2326pQosIpv6ProtocolUDPDport OBJECT-TYPE
   SYNTAX      DisplayString
   MAX-ACCESS  read-write
   STATUS      current
   DESCRIPTION
       " Destination TCP/UDP port:(0-65535) or 'Any',
         specific or port range applicable for IP protocol UDP/TCP. "
   ::= { gs2326pQosQceEntry 30 }

gs2326pQosIpv6ProtocolTCPSport OBJECT-TYPE
   SYNTAX      DisplayString
   MAX-ACCESS  read-write
   STATUS      current
   DESCRIPTION
       " Source TCP/UDP port:(0-65535) or 'Any',
         specific or port range applicable for IP protocol UDP/TCP. "
   ::= { gs2326pQosQceEntry 31 }


gs2326pQosIpv6ProtocolTCPDport OBJECT-TYPE
   SYNTAX      DisplayString
   MAX-ACCESS  read-write
   STATUS      current
   DESCRIPTION
       " Destination TCP/UDP port:(0-65535) or 'Any',
         specific or port range applicable for IP protocol UDP/TCP. "
   ::= { gs2326pQosQceEntry 32 }

gs2326pQosIpv6Ip OBJECT-TYPE
   SYNTAX      DisplayString
   MAX-ACCESS  read-write
   STATUS      current
   DESCRIPTION
       " IPv6 source address: (a.b.c.d) or value 0.0.0.0 is 'Any', 32 LS bits.
         If a port is configured to match on DMAC/DIP, this field is the
         Destination IP address."
   ::= { gs2326pQosQceEntry 33 }

gs2326pQosIpv6Mask OBJECT-TYPE
   SYNTAX      DisplayString
   MAX-ACCESS  read-write
   STATUS      current
   DESCRIPTION
       " IPv6 mask address: (a.b.c.d) or value 0.0.0.0 is 'Any', 32 LS bits. "
   ::= { gs2326pQosQceEntry 34 }

gs2326pQosIpv6DSCP OBJECT-TYPE
   SYNTAX      DisplayString
   MAX-ACCESS  read-write
   STATUS      current
   DESCRIPTION
       " Diffserv Code Point value (DSCP): It can be a specific value,
         range of values or 'Any'. DSCP values are in the range 0-63 including BE,
         CS1-CS7, EF or AF11-AF43. "
   ::= { gs2326pQosQceEntry 35 }

gs2326pQosActionClass  OBJECT-TYPE
   SYNTAX      Integer32(0..8)
   MAX-ACCESS  read-write
   STATUS      current
   DESCRIPTION
       " QoS class: (0-7) or 8: Default."
   ::= { gs2326pQosQceEntry 36 }

gs2326pQosActionDPL OBJECT-TYPE
   SYNTAX      INTEGER (0..4)
   MAX-ACCESS  read-write
   STATUS      current
   DESCRIPTION
       " DP Valid Drop Precedence Level can be (0-3) or 4: Default. "
   ::= { gs2326pQosQceEntry 37 }

gs2326pQosActionDSCP OBJECT-TYPE
   SYNTAX      Integer32(0..64)
   MAX-ACCESS  read-write
   STATUS      current
   DESCRIPTION
       " Valid DSCP value can be (0-63, BE, CS1-CS7, EF or AF11-AF43) or 64: Default. "
   ::= { gs2326pQosQceEntry 38 }

gs2326pQosQceRowStatus OBJECT-TYPE
   SYNTAX      INTEGER { active(1), notInservice(2), destroy(4) }
   MAX-ACCESS  read-write
   STATUS      current
   DESCRIPTION
       "  1: active2: notInservice 4: destroy"
   ::= { gs2326pQosQceEntry 39 }

gs2326pQosQceMoveID OBJECT-TYPE
   SYNTAX       Integer32(0..256)
   MAX-ACCESS   read-write
   STATUS       current
   DESCRIPTION
       " Move Qos,
         default: 0
         Qos ID must be exist.
         range : 0 - 256."
   ::= { gs2326pQosControlList 3 }

gs2326pQosQceMoveNextID OBJECT-TYPE
   SYNTAX       Integer32(0..256)
   MAX-ACCESS   read-write
   STATUS       current
   DESCRIPTION
       " Move Qos,
         default: 0
         If the next Qos ID is non zero, the Qos will be placed before this Qos in the list.
         If the next Qos ID is zero,the Qos will be placed last in the list.
         range : 0 - 256. "
   ::= { gs2326pQosControlList 4 }


gs2326pQosQCLStatusTable OBJECT-TYPE
   SYNTAX      SEQUENCE OF GS2326PQosQCLStatusEntry
   MAX-ACCESS  not-accessible
   STATUS      current
   DESCRIPTION
       "  configure the basic QoS DSCP Translation settings for all switches. "
   ::= { gs2326pQos  10 }

gs2326pQosQCLStatusEntry OBJECT-TYPE
   SYNTAX      GS2326PQosQCLStatusEntry
   MAX-ACCESS  not-accessible
   STATUS      current
   DESCRIPTION
       ""
   INDEX    { gs2326pQosQCLStatusList  }
   ::= { gs2326pQosQCLStatusTable 1 }

GS2326PQosQCLStatusEntry ::= SEQUENCE {
   gs2326pQosQCLStatusList               Integer32,
   gs2326pQosQCLStatusUser               DisplayString,
   gs2326pQosQCLStatusQCEId              DisplayString,
   gs2326pQosQCLStatusFrameType          DisplayString,
   gs2326pQosQCLStatusPortlist           DisplayString,
   gs2326pQosQCLStatusActionClass	       DisplayString,
   gs2326pQosQCLStatusActionDPL	       DisplayString,
   gs2326pQosQCLStatusActionDSCP	       DisplayString,
   gs2326pQosQCLStatusActionConflict     DisplayString
}

gs2326pQosQCLStatusList OBJECT-TYPE
   SYNTAX      Integer32(1..4095)
   MAX-ACCESS  not-accessible
   STATUS      current
   DESCRIPTION
       " QCL table index. "
   ::= { gs2326pQosQCLStatusEntry 1}

gs2326pQosQCLStatusUser OBJECT-TYPE
   SYNTAX      DisplayString
   MAX-ACCESS  read-only
   STATUS      current
   DESCRIPTION
       " Indicates the QCL user. "
   ::= { gs2326pQosQCLStatusEntry 2 }

gs2326pQosQCLStatusQCEId OBJECT-TYPE
   SYNTAX      DisplayString
   MAX-ACCESS  read-only
   STATUS      current
   DESCRIPTION
      " Indicates the index of QCE. "
   ::= { gs2326pQosQCLStatusEntry 3}

gs2326pQosQCLStatusFrameType OBJECT-TYPE
   SYNTAX      DisplayString
   MAX-ACCESS  read-only
   STATUS      current
   DESCRIPTION
       " Indicates the type of frame to look for incomming frames.
       Any: The QCE will match all frame type.
       Ethernet: Only Ethernet frames (with Ether Type 0x600-0xFFFF) are allowed.
       LLC: Only (LLC) frames are allowed.
       SNAP: Only (SNAP) frames are allowed.
       IPv4: The QCE will match only IPV4 frames.
       IPv6: The QCE will match only IPV6 frames."
   ::= { gs2326pQosQCLStatusEntry 4}

gs2326pQosQCLStatusPortlist OBJECT-TYPE
   SYNTAX      DisplayString
   MAX-ACCESS  read-only
   STATUS      current
   DESCRIPTION
       " Indicates the list of ports configured with the QCE. "
   ::= { gs2326pQosQCLStatusEntry 5}

gs2326pQosQCLStatusActionClass OBJECT-TYPE
   SYNTAX      DisplayString
   MAX-ACCESS  read-only
   STATUS      current
   DESCRIPTION
       " Classified QoS class; if a frame matches the QCE it will be put in the
       queue. "
   ::= { gs2326pQosQCLStatusEntry 6}

gs2326pQosQCLStatusActionDPL OBJECT-TYPE
   SYNTAX      DisplayString
   MAX-ACCESS  read-only
   STATUS      current
   DESCRIPTION
       " Drop Precedence Level; if a frame matches the QCE then DP level will
       set to value displayed under DPL column."
   ::= { gs2326pQosQCLStatusEntry 7}

gs2326pQosQCLStatusActionDSCP OBJECT-TYPE
   SYNTAX      DisplayString
   MAX-ACCESS  read-only
   STATUS      current
   DESCRIPTION
       " If a frame matches the QCE then DSCP will be classified with the value
       displayed under DSCP column."
   ::= { gs2326pQosQCLStatusEntry 8}

gs2326pQosQCLStatusActionConflict OBJECT-TYPE
   SYNTAX      DisplayString
   MAX-ACCESS  read-only
   STATUS      current
   DESCRIPTION
       " If a frame matches the QCE then DSCP will be classified with the value
        displayed under DSCP column. "
   ::= { gs2326pQosQCLStatusEntry 9}


gs2326pQosStormControl                                           OBJECT IDENTIFIER ::= { gs2326pQos 11 }

gs2326pQoSStormControlUC OBJECT-TYPE
   SYNTAX      INTEGER { disable(0), enable(1) }
   MAX-ACCESS  read-write
   STATUS      current
   DESCRIPTION
       "Enable or disable the storm control status for the Unicast frame type.
       default:  0
        0: disable
        1: enable"
   ::= { gs2326pQosStormControl 2 }

gs2326pQoSStormControlUCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326pQosStormControl 3 }

gs2326pQoSStormControlMC OBJECT-TYPE
   SYNTAX      INTEGER { disable(0), enable(1) }
   MAX-ACCESS  read-write
   STATUS      current
   DESCRIPTION
       "Enable or disable the storm control status for the Multicast frame type.
       default:  0
        0: disable
        1: enable"
   ::= { gs2326pQosStormControl 4 }

gs2326pQoSStormControlMCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326pQosStormControl 5 }

gs2326pQoSStormControlBC OBJECT-TYPE
   SYNTAX      INTEGER { disable(0), enable(1) }
   MAX-ACCESS  read-write
   STATUS      current
   DESCRIPTION
       "Enable or disable the storm control status for the Broadcast frame type.
       default:  0
        0: disable
        1: enable"
   ::= { gs2326pQosStormControl 6 }

gs2326pQoSStormControlBCRate OBJECT-TYPE
   SYNTAX      DisplayString
   MAX-ACCESS  read-write
   STATUS      current
   DESCRIPTION
       "The rate unit is packets per second (pps). Valid values are: 1, 2, 4, 8,
        16, 32, 64, 128, 256, 512, 1K, 2K, 4K, 8K, 16K, 32K, 64K, 128K, 256K,
        512K or 1024K."
   ::= { gs2326pQosStormControl 7 }


gs2326pVlan                                                           OBJECT IDENTIFIER ::= { gs2326pConfiguration 15 }

gs2326pVlanPorts                                                      OBJECT IDENTIFIER ::= { gs2326pVlan 1 }

gs2326pVlanPortsTPIDforCustomSport  OBJECT-TYPE
   SYNTAX      OCTET STRING(SIZE(2))
   MAX-ACCESS  read-write
   STATUS      current
   DESCRIPTION
       "Configure the TPID used for Custom S-ports. This is a global setting for
       all the Custom S-ports.
       range: 0x0600-0xffff,
       default: 0x88a8. "
   ::= { gs2326pVlanPorts 1 }

gs2326pVlanPortsTable OBJECT-TYPE
   SYNTAX      SEQUENCE OF GS2326PVlanPortsEntry
   MAX-ACCESS  not-accessible
   STATUS      current
   DESCRIPTION
       " Configure Vlan ports Configuration mode. "
   ::= { gs2326pVlanPorts 2 }

gs2326pVlanPortsEntry OBJECT-TYPE
   SYNTAX      GS2326PVlanPortsEntry
   MAX-ACCESS  not-accessible
   STATUS      current
   DESCRIPTION
       ""
   INDEX    { gs2326pVlanPortsPort  }
   ::= { gs2326pVlanPortsTable 1 }

GS2326PVlanPortsEntry ::= SEQUENCE {
   gs2326pVlanPortsPort	         Integer32,
   gs2326pVlanPortsPVID     Integer32,
   gs2326pVlanPortsFrameType      INTEGER,
   gs2326pVlanPortsIngressFilter  INTEGER,
   gs2326pVlanPortsEgressRule     INTEGER,
   gs2326pVlanPortsPortType       INTEGER
}

gs2326pVlanPortsPort OBJECT-TYPE
   SYNTAX      Integer32(1..4094)
   MAX-ACCESS  not-accessible
   STATUS      current
   DESCRIPTION
       " port, range : 1 - port number. "
   ::= { gs2326pVlanPortsEntry 1 }

gs2326pVlanPortsPVID OBJECT-TYPE
   SYNTAX      Integer32(1..4094)
   MAX-ACCESS  read-write
   STATUS      current
   DESCRIPTION
       "Configure PVID.
        range: 1-4094,
        default: 1. "
   ::= { gs2326pVlanPortsEntry 2 }

gs2326pVlanPortsFrameType OBJECT-TYPE
   SYNTAX      INTEGER { all(0), tagged(1), untagged(2) }
   MAX-ACCESS  read-write
   STATUS      current
   DESCRIPTION
       "Configure frame type of switch ports.
        0: all,
        1: tagged,
        2: untagged,
        default: all.  "
   ::= { gs2326pVlanPortsEntry 3 }

gs2326pVlanPortsIngressFilter OBJECT-TYPE
   SYNTAX      INTEGER { disable(0), enable(1) }
   MAX-ACCESS  read-write
   STATUS      current
   DESCRIPTION
       "Configure ingress filtering of switch ports.
        0: disable,
        1: enable,
        default:disable . "
   ::= { gs2326pVlanPortsEntry 4 }

gs2326pVlanPortsEgressRule OBJECT-TYPE
   SYNTAX      INTEGER { access(0), hybrid(1), trunk(2) }
   MAX-ACCESS  read-write
   STATUS      current
   DESCRIPTION
       "Configure egress-rule of switch ports.
        0: access,
        1: hybrid,
        2: trunk"
   ::= { gs2326pVlanPortsEntry 5 }

gs2326pVlanPortsPortType OBJECT-TYPE
   SYNTAX      INTEGER { cPort(0), sCustomPort(1), sPort(2), unaware(3) }
   MAX-ACCESS  read-write
   STATUS      current
   DESCRIPTION
       "Configure port type of switch ports.
        0: c-port,
        1: s-custom-port,
        2: s-port,
        3: unaware.
        default: c-port. "
   ::= { gs2326pVlanPortsEntry 6 }

gs2326pVlanPrivateVLAN                                                              OBJECT IDENTIFIER ::= { gs2326pVlan 2 }

gs2326pVlanPrivateVLANMembership                                                    OBJECT IDENTIFIER ::= { gs2326pVlanPrivateVLAN 1 }

gs2326pVlanPrivateVLANMembershipCreate OBJECT-TYPE
   SYNTAX       Integer32(1..4094)
   MAX-ACCESS   read-write
   STATUS       current
   DESCRIPTION
       "default: 0
        0 : None  (read only)
        1 : Create a pvlan"
   ::= { gs2326pVlanPrivateVLANMembership 1 }

gs2326pVlanPrivateVLANMembershipTable OBJECT-TYPE
   SYNTAX      SEQUENCE OF Gs2326pVlanPrivateVLANMembershipEntry
   MAX-ACCESS  not-accessible
   STATUS      current
   DESCRIPTION
       " Configure Private Vlan Configuration. "
   ::= { gs2326pVlanPrivateVLANMembership 2 }

gs2326pVlanPrivateVLANMembershipEntry OBJECT-TYPE
   SYNTAX      Gs2326pVlanPrivateVLANMembershipEntry
   MAX-ACCESS  not-accessible
   STATUS      current
   DESCRIPTION
       ""
   INDEX    { gs2326pVlanPrivateVLANIndex  }
   ::= { gs2326pVlanPrivateVLANMembershipTable 1 }

Gs2326pVlanPrivateVLANMembershipEntry ::= SEQUENCE {
   gs2326pVlanPrivateVLANIndex          Integer32,
   gs2326pVlanPrivateVLANID             Integer32,
   gs2326pVlanPrivateVLANMemberships    DisplayString,
   gs2326pVlanPrivateVLANRowStatus      INTEGER
}

gs2326pVlanPrivateVLANIndex OBJECT-TYPE
   SYNTAX      Integer32(1..52)
   MAX-ACCESS  not-accessible
   STATUS      current
   DESCRIPTION
       "private VLAN Index. "
   ::= { gs2326pVlanPrivateVLANMembershipEntry 1 }

gs2326pVlanPrivateVLANID OBJECT-TYPE
   SYNTAX      Integer32(1..52)
   MAX-ACCESS  read-write
   STATUS      current
   DESCRIPTION
       "Indicates the ID of this particular private VLAN.
       The CreateEntry can be modify, the other entry can't be modify."
   ::= { gs2326pVlanPrivateVLANMembershipEntry 2 }

gs2326pVlanPrivateVLANMemberships OBJECT-TYPE
   SYNTAX      DisplayString
   MAX-ACCESS  read-write
   STATUS      current
   DESCRIPTION
       "To include the ports in a Private VLAN"
   ::= { gs2326pVlanPrivateVLANMembershipEntry 3 }

gs2326pVlanPrivateVLANRowStatus OBJECT-TYPE
   SYNTAX      INTEGER { active(1), notInservice(2), destroy(4) }
   MAX-ACCESS  read-write
   STATUS      current
   DESCRIPTION
       "1: active
        2: notInservice
        4: destroy"
   ::= { gs2326pVlanPrivateVLANMembershipEntry 4 }

gs2326pVlanPortIsolationTable OBJECT-TYPE
   SYNTAX      SEQUENCE OF Gs2326pVlanPortIsolationEntry
   MAX-ACCESS  not-accessible
   STATUS      current
   DESCRIPTION
       " Configure Vlan Port Isolation Configuration. "
   ::= { gs2326pVlanPrivateVLAN 2 }

gs2326pVlanPortIsolationEntry OBJECT-TYPE
   SYNTAX      Gs2326pVlanPortIsolationEntry
   MAX-ACCESS  not-accessible
   STATUS      current
   DESCRIPTION
       ""
   INDEX    { gs2326pVlanPortIsolationPort  }
   ::= { gs2326pVlanPortIsolationTable 1 }

Gs2326pVlanPortIsolationEntry ::= SEQUENCE {
   gs2326pVlanPortIsolationPort Integer32,
   gs2326pVlanPortIsolation     INTEGER
}

gs2326pVlanPortIsolationPort OBJECT-TYPE
   SYNTAX      Integer32(1..4094)
   MAX-ACCESS  not-accessible
   STATUS      current
   DESCRIPTION
       " port, range : 1 - port number. "
   ::= { gs2326pVlanPortIsolationEntry 1 }

gs2326pVlanPortIsolation OBJECT-TYPE
   SYNTAX      INTEGER{ disable(0), enable(1) }
   MAX-ACCESS  read-write
   STATUS      current
   DESCRIPTION
       "default: 0
        0:disable
        1:enable"
   ::= { gs2326pVlanPortIsolationEntry 2 }


gs2326pMACbasedVLAN                                                      OBJECT IDENTIFIER ::= { gs2326pVlan 3 }

gs2326pMACbasedVLANConf                                                      OBJECT IDENTIFIER ::= { gs2326pMACbasedVLAN 1 }

gs2326pMACbasedVLANConfCreate OBJECT-TYPE
   SYNTAX       Integer32
   MAX-ACCESS   read-write
   STATUS       current
   DESCRIPTION
       "default: 0
       0 : None  (read only) 1 : Create MAC base vlan"
   ::= { gs2326pMACbasedVLANConf 1 }

gs2326pMACbasedVLANConfTable OBJECT-TYPE
   SYNTAX      SEQUENCE OF Gs2326pMACbasedVLANConfEntry
   MAX-ACCESS  not-accessible
   STATUS      current
   DESCRIPTION
       " Configure Vlan Port Isolation Configuration. "
   ::= { gs2326pMACbasedVLANConf 2 }

gs2326pMACbasedVLANConfEntry OBJECT-TYPE
   SYNTAX      Gs2326pMACbasedVLANConfEntry
   MAX-ACCESS  not-accessible
   STATUS      current
   DESCRIPTION
       ""
   INDEX    { gs2326pMACbasedVLANIndex  }
   ::= { gs2326pMACbasedVLANConfTable 1 }

Gs2326pMACbasedVLANConfEntry ::= SEQUENCE {
   gs2326pMACbasedVLANIndex         Integer32,
   gs2326pMACbasedVLANMACAddress    MacAddress,
   gs2326pMACbasedVLANID            Integer32,
   gs2326pMACbasedMemberships       DisplayString,
   gs2326pMACbaseRowStatus          INTEGER
}

gs2326pMACbasedVLANIndex OBJECT-TYPE
   SYNTAX      Integer32(1..256)
   MAX-ACCESS  read-write
   STATUS      current
   DESCRIPTION
       "Indicates the VLAN ID. "
   ::= { gs2326pMACbasedVLANConfEntry 1 }

gs2326pMACbasedVLANMACAddress OBJECT-TYPE
   SYNTAX      MacAddress
   MAX-ACCESS  read-write
   STATUS      current
   DESCRIPTION
       "Indicates the MAC address.
       The CreateEntry can be modify, the other entry can't be modify."
   ::= { gs2326pMACbasedVLANConfEntry 2 }

gs2326pMACbasedVLANID OBJECT-TYPE
   SYNTAX      Integer32(1..4094)
   MAX-ACCESS  read-write
   STATUS      current
   DESCRIPTION
       "Indicates the VLAN ID. "
   ::= { gs2326pMACbasedVLANConfEntry 3 }

gs2326pMACbasedMemberships OBJECT-TYPE
   SYNTAX      DisplayString
   MAX-ACCESS  read-write
   STATUS      current
   DESCRIPTION
       "The ports are displayed for each MAC-based VLAN entry.
        To include the port in a MAC-based VLAN"
   ::= { gs2326pMACbasedVLANConfEntry 4 }


gs2326pMACbaseRowStatus OBJECT-TYPE
   SYNTAX      INTEGER { active(1), notInservice(2), destroy(4)}
   MAX-ACCESS  read-write
   STATUS      current
   DESCRIPTION
       "1: active
        2: notInservice
        4: destroy"
   ::= { gs2326pMACbasedVLANConfEntry 5 }

gs2326pIGMPSnooping                                                           OBJECT IDENTIFIER ::= { gs2326pConfiguration 16 }

gs2326pIGMPSnoopingBasic                                                      OBJECT IDENTIFIER ::= { gs2326pIGMPSnooping 1 }

gs2326pIGMPSnoopingEnable  OBJECT-TYPE
   SYNTAX      INTEGER { disable(0), enable(1) }
   MAX-ACCESS  read-write
   STATUS      current
   DESCRIPTION
       "Enable/Disable the Global IGMP Snooping"
   ::= { gs2326pIGMPSnoopingBasic 1 }

gs2326pIGMPSnoopingUnregisteredIPMCv4Flooding  OBJECT-TYPE
   SYNTAX      INTEGER { disable(0), enable(1) }
   MAX-ACCESS  read-write
   STATUS      current
   DESCRIPTION
       "Enable/Disable unregistered IPMCv4 traffic flooding. "
   ::= { gs2326pIGMPSnoopingBasic 2 }

gs2326pIGMPSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326pIGMPSnoopingBasic 3 }

gs2326pIGMPSnoopingSSMIPRangeValue  OBJECT-TYPE
   SYNTAX      Integer32(4..32)
   MAX-ACCESS  read-write
   STATUS      current
   DESCRIPTION
       "SSM (Source-Specific Multicast) Range allows the SSM-aware hosts and
       routers run the SSM service model for the groups in the address range value. "
   ::= { gs2326pIGMPSnoopingBasic 4 }

gs2326pIGMPSnoopingProxyEnabled  OBJECT-TYPE
   SYNTAX      INTEGER { disable(0), enable(1) }
   MAX-ACCESS  read-write
   STATUS      current
   DESCRIPTION
       "Enable/Disable IGMP Proxy. This feature can be used to avoid forwarding
       unnecessary join and leave messages to the router side. "
   ::= { gs2326pIGMPSnoopingBasic 5 }

gs2326pIGMPSnoopingPortRelatedTable OBJECT-TYPE
   SYNTAX      SEQUENCE OF Gs2326pIGMPSnoopingPortRelatedEntry
   MAX-ACCESS  not-accessible
   STATUS      current
   DESCRIPTION
       " Configure IGMP Snooping Port Related Configuration. "
   ::= { gs2326pIGMPSnoopingBasic 6 }

gs2326pIGMPSnoopingPortRelatedEntry OBJECT-TYPE
   SYNTAX      Gs2326pIGMPSnoopingPortRelatedEntry
   MAX-ACCESS  not-accessible
   STATUS      current
   DESCRIPTION
       ""
   INDEX    { ifIndex  }
   ::= { gs2326pIGMPSnoopingPortRelatedTable 1 }

Gs2326pIGMPSnoopingPortRelatedEntry ::= SEQUENCE {
   gs2326pIGMPSnoopingRouterPort	INTEGER,
   gs2326pIGMPSnoopingFastLeave  	INTEGER,
   gs2326pIGMPSnoopingThrottling    Integer32
}

gs2326pIGMPSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326pIGMPSnoopingPortRelatedEntry 1 }

gs2326pIGMPSnoopingFastLeave OBJECT-TYPE
   SYNTAX      INTEGER { disable(0), enable(1) }
   MAX-ACCESS  read-write
   STATUS      current
   DESCRIPTION
       "Enable/Disable the fast leave on the port. "
   ::= { gs2326pIGMPSnoopingPortRelatedEntry 2 }

gs2326pIGMPSnoopingThrottling OBJECT-TYPE
   SYNTAX      Integer32(0..10)
   MAX-ACCESS  read-write
   STATUS      current
   DESCRIPTION
       "Enable to limit the number of multicast groups to which a switch port can belong.
       0: unlimited"
   ::= { gs2326pIGMPSnoopingPortRelatedEntry 3 }

gs2326pIGMPSnoopingVLANTable OBJECT-TYPE
   SYNTAX      SEQUENCE OF Gs2326pIGMPSnoopingVLANEntry
   MAX-ACCESS  not-accessible
   STATUS      current
   DESCRIPTION
       " Configure IGMP Snooping Vlan Configuration. "
   ::= { gs2326pIGMPSnooping 2 }

gs2326pIGMPSnoopingVLANEntry OBJECT-TYPE
   SYNTAX      Gs2326pIGMPSnoopingVLANEntry
   MAX-ACCESS  not-accessible
   STATUS      current
   DESCRIPTION
       ""
   INDEX    { gs2326pIGMPSnoopingVLANID  }
   ::= { gs2326pIGMPSnoopingVLANTable 1 }

Gs2326pIGMPSnoopingVLANEntry ::= SEQUENCE {
   gs2326pIGMPSnoopingVLANID        	Integer32,
   gs2326pIGMPSnoopingVLANEnable    	INTEGER,
   gs2326pIGMPSnoopingVLANIGMPQuerier   INTEGER,
   gs2326pIGMPSnoopingVLANCompatibility INTEGER,
   gs2326pIGMPSnoopingVLANRV        	Integer32,
   gs2326pIGMPSnoopingVLANQI      	    Integer32,
   gs2326pIGMPSnoopingVLANQRI   	    Integer32,
   gs2326pIGMPSnoopingVLANLLQI   	    Integer32,
   gs2326pIGMPSnoopingVLANURI    	    Integer32
}

gs2326pIGMPSnoopingVLANID OBJECT-TYPE
   SYNTAX      Integer32(1..4095)
   MAX-ACCESS  read-write
   STATUS      current
   DESCRIPTION
       "The VLAN ID of the entry"
   ::= { gs2326pIGMPSnoopingVLANEntry 1 }

gs2326pIGMPSnoopingVLANEnable OBJECT-TYPE
   SYNTAX      INTEGER { disable(0), enable(1) }
   MAX-ACCESS  read-write
   STATUS      current
   DESCRIPTION
       "Enable/Disable the per-VLAN IGMP Snooping. Up to 32 VLANs can be
       selected for IGMP Snooping. "
   ::= { gs2326pIGMPSnoopingVLANEntry 2 }

gs2326pIGMPSnoopingVLANIGMPQuerier OBJECT-TYPE
   SYNTAX      INTEGER { disable(0), enable(1) }
   MAX-ACCESS  read-write
   STATUS      current
   DESCRIPTION
       "Enable/Disable the IGMP Querier in the VLAN. "
   ::= { gs2326pIGMPSnoopingVLANEntry 3 }

gs2326pIGMPSnoopingVLANCompatibility OBJECT-TYPE
   SYNTAX      INTEGER { igmpAuto(0), forcedIGMPv1(1), forcedIGMPv2(2), forcedIGMPv3(3), none(4) }
   MAX-ACCESS  read-write
   STATUS      current
   DESCRIPTION
       "Compatibility is maintained by hosts and routers taking appropriate
       actions depending on the versions of IGMP operating on hosts and routers
       within a network. The allowed selection is IGMP-Auto, Forced IGMPv1,
       Forced IGMPv2, Forced IGMPv3, default compatibility value is IGMP-Auto. "
   ::= { gs2326pIGMPSnoopingVLANEntry 4 }

gs2326pIGMPSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326pIGMPSnoopingVLANEntry 5 }

gs2326pIGMPSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326pIGMPSnoopingVLANEntry 6 }

gs2326pIGMPSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326pIGMPSnoopingVLANEntry 7 }

gs2326pIGMPSnoopingVLANLLQI OBJECT-TYPE
   SYNTAX      Integer32(-1|0..31744)
   MAX-ACCESS  read-write
   STATUS      current
   DESCRIPTION
       "LLQI (LMQI for IGMP).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326pIGMPSnoopingVLANEntry 8 }

gs2326pIGMPSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326pIGMPSnoopingVLANEntry 9 }

gs2326pIGMPSnoopingPortGroupFiltering                                                      OBJECT IDENTIFIER ::= { gs2326pIGMPSnooping 3 }

gs2326pIGMPSnoopingPortGroupFilteringCreate OBJECT-TYPE
   SYNTAX       Integer32
   MAX-ACCESS   read-write
   STATUS       current
   DESCRIPTION
       "default: 0
       0 : None  (read only) 1 : Create IGMP Snooping Port Group Filtering "
   ::= { gs2326pIGMPSnoopingPortGroupFiltering 1 }

gs2326pIGMPSnoopingPortGroupFilteringTable OBJECT-TYPE
   SYNTAX      SEQUENCE OF Gs2326pIGMPSnoopingPortGroupFilteringEntry
   MAX-ACCESS  not-accessible
   STATUS      current
   DESCRIPTION
       " Configure IGMP Snooping port group filtering. "
   ::= { gs2326pIGMPSnoopingPortGroupFiltering 2 }

gs2326pIGMPSnoopingPortGroupFilteringEntry OBJECT-TYPE
   SYNTAX      Gs2326pIGMPSnoopingPortGroupFilteringEntry
   MAX-ACCESS  not-accessible
   STATUS      current
   DESCRIPTION
       ""
   INDEX    { gs2326pIGMPSnoopingPortGroupFilteringIndex  }
   ::= { gs2326pIGMPSnoopingPortGroupFilteringTable 1 }

Gs2326pIGMPSnoopingPortGroupFilteringEntry ::= SEQUENCE {
   gs2326pIGMPSnoopingPortGroupFilteringIndex         Integer32,
   gs2326pIGMPSnoopingPortGroupFilteringPort          Integer32,
   gs2326pIGMPSnoopingPortGroupFilteringGroups        DisplayString,
   gs2326pIGMPSnoopingPortGroupFilteringRowStatus     INTEGER
}

gs2326pIGMPSnoopingPortGroupFilteringIndex OBJECT-TYPE
   SYNTAX      Integer32(1..65535)
   MAX-ACCESS  not-accessible
   STATUS      current
   DESCRIPTION
       "IGMP Snooping Port Group Filtering Configuration Index. "
   ::= { gs2326pIGMPSnoopingPortGroupFilteringEntry 1 }

gs2326pIGMPSnoopingPortGroupFilteringPort OBJECT-TYPE
   SYNTAX      Integer32(1..65535)
   MAX-ACCESS  read-write
   STATUS      current
   DESCRIPTION
       "The logical port for the settings. "
   ::= { gs2326pIGMPSnoopingPortGroupFilteringEntry 2 }

gs2326pIGMPSnoopingPortGroupFilteringGroups OBJECT-TYPE
   SYNTAX      DisplayString
   MAX-ACCESS  read-write
   STATUS      current
   DESCRIPTION
       "The IP Multicast Group that will be filtered. "
   ::= { gs2326pIGMPSnoopingPortGroupFilteringEntry 3 }

gs2326pIGMPSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326pIGMPSnoopingPortGroupFilteringEntry 4 }

gs2326pIGMPSnoopingStatus                                                      OBJECT IDENTIFIER ::= { gs2326pIGMPSnooping 4 }

gs2326pIGMPSnoopingstatisticClear OBJECT-TYPE
   SYNTAX      INTEGER { none(0), clear(1)}
   MAX-ACCESS  read-write
   STATUS      current
   DESCRIPTION
       "Clears all Statistics counters."
   ::= { gs2326pIGMPSnoopingStatus 1 }


gs2326pIGMPSnoopingstatisticTable OBJECT-TYPE
   SYNTAX      SEQUENCE OF Gs2326pIGMPSnoopingstatisticEntry
   MAX-ACCESS  not-accessible
   STATUS      current
   DESCRIPTION
       " Configure Vlan Port Isolation Configuration. "
   ::= { gs2326pIGMPSnoopingStatus 2 }

gs2326pIGMPSnoopingstatisticEntry OBJECT-TYPE
   SYNTAX      Gs2326pIGMPSnoopingstatisticEntry
   MAX-ACCESS  not-accessible
   STATUS      current
   DESCRIPTION
       ""
   INDEX    { gs2326pIGMPSnoopingstatisticVLANID  }
   ::= { gs2326pIGMPSnoopingstatisticTable 1 }

Gs2326pIGMPSnoopingstatisticEntry ::= SEQUENCE {
   gs2326pIGMPSnoopingstatisticVLANID              Integer32,
   gs2326pIGMPSnoopingstatisticQuerierVersion      DisplayString,
   gs2326pIGMPSnoopingstatisticHostVersion         DisplayString,
   gs2326pIGMPSnoopingstatisticQuerierStatus       DisplayString,
   gs2326pIGMPSnoopingstatisticQueriesTransmitted  Counter32,
   gs2326pIGMPSnoopingstatisticQueriesReceived     Counter32,
   gs2326pIGMPSnoopingstatisticV1ReportsReceived   Counter32,
   gs2326pIGMPSnoopingstatisticV2ReportsReceived   Counter32,
   gs2326pIGMPSnoopingstatisticV3ReportsReceived   Counter32,
   gs2326pIGMPSnoopingstatisticV2LeavesReceived    Counter32
}


gs2326pIGMPSnoopingstatisticVLANID OBJECT-TYPE
   SYNTAX      Integer32(1..4095)
   MAX-ACCESS  read-only
   STATUS      current
   DESCRIPTION
       "The VLAN ID of the entry. "
   ::= { gs2326pIGMPSnoopingstatisticEntry 1 }

gs2326pIGMPSnoopingstatisticQuerierVersion OBJECT-TYPE
   SYNTAX      DisplayString
   MAX-ACCESS  read-only
   STATUS      current
   DESCRIPTION
       "Working Querier Version currently. "
   ::= { gs2326pIGMPSnoopingstatisticEntry 2 }

gs2326pIGMPSnoopingstatisticHostVersion OBJECT-TYPE
   SYNTAX      DisplayString
   MAX-ACCESS  read-only
   STATUS      current
   DESCRIPTION
       "Working Host Version currently. "
   ::= { gs2326pIGMPSnoopingstatisticEntry 3 }

gs2326pIGMPSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326pIGMPSnoopingstatisticEntry 4 }

gs2326pIGMPSnoopingstatisticQueriesTransmitted OBJECT-TYPE
   SYNTAX      Counter32
   MAX-ACCESS  read-only
   STATUS      current
   DESCRIPTION
       "The number of Transmitted Queries. "
   ::= { gs2326pIGMPSnoopingstatisticEntry 5 }

gs2326pIGMPSnoopingstatisticQueriesReceived OBJECT-TYPE
   SYNTAX      Counter32
   MAX-ACCESS  read-only
   STATUS      current
   DESCRIPTION
       "The number of Received Queries. "
   ::= { gs2326pIGMPSnoopingstatisticEntry 6 }

gs2326pIGMPSnoopingstatisticV1ReportsReceived OBJECT-TYPE
   SYNTAX      Counter32
   MAX-ACCESS  read-only
   STATUS      current
   DESCRIPTION
       "The number of Received V1 Reports. "
   ::= { gs2326pIGMPSnoopingstatisticEntry 7 }

gs2326pIGMPSnoopingstatisticV2ReportsReceived OBJECT-TYPE
   SYNTAX      Counter32
   MAX-ACCESS  read-only
   STATUS      current
   DESCRIPTION
       "The number of Received V2 Reports. "
   ::= { gs2326pIGMPSnoopingstatisticEntry 8 }

gs2326pIGMPSnoopingstatisticV3ReportsReceived OBJECT-TYPE
   SYNTAX      Counter32
   MAX-ACCESS  read-only
   STATUS      current
   DESCRIPTION
       "The number of Received V3 Reports. "
   ::= { gs2326pIGMPSnoopingstatisticEntry 9 }

gs2326pIGMPSnoopingstatisticV2LeavesReceived OBJECT-TYPE
   SYNTAX      Counter32
   MAX-ACCESS  read-only
   STATUS      current
   DESCRIPTION
       "The number of Received V2 Leaves. "
   ::= { gs2326pIGMPSnoopingstatisticEntry 10 }

gs2326pIGMPSnoopingRouterPortTable OBJECT-TYPE
   SYNTAX      SEQUENCE OF Gs2326pIGMPSnoopingRouterPortEntry
   MAX-ACCESS  not-accessible
   STATUS      current
   DESCRIPTION
       " Configure Vlan Port Isolation Configuration. "
   ::= { gs2326pIGMPSnoopingStatus 3 }

gs2326pIGMPSnoopingRouterPortEntry OBJECT-TYPE
   SYNTAX      Gs2326pIGMPSnoopingRouterPortEntry
   MAX-ACCESS  not-accessible
   STATUS      current
   DESCRIPTION
       ""
   INDEX    { ifIndex  }
   ::= { gs2326pIGMPSnoopingRouterPortTable 1 }

Gs2326pIGMPSnoopingRouterPortEntry ::= SEQUENCE {
   gs2326pIGMPSnoopingRouterPortStatus            DisplayString
}

gs2326pIGMPSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326pIGMPSnoopingRouterPortEntry 1 }

gs2326pIGMPSnoopingGroupsTable OBJECT-TYPE
   SYNTAX      SEQUENCE OF Gs2326pIGMPSnoopingGroupsEntry
   MAX-ACCESS  not-accessible
   STATUS      current
   DESCRIPTION
       "IGMP Snooping Groups Information . "
   ::= { gs2326pIGMPSnooping 5 }

gs2326pIGMPSnoopingGroupsEntry OBJECT-TYPE
   SYNTAX      Gs2326pIGMPSnoopingGroupsEntry
   MAX-ACCESS  not-accessible
   STATUS      current
   DESCRIPTION
       ""
   INDEX    { gs2326pIGMPSnoopingGroupsIndex  }
   ::= { gs2326pIGMPSnoopingGroupsTable 1 }

Gs2326pIGMPSnoopingGroupsEntry ::= SEQUENCE {
   gs2326pIGMPSnoopingGroupsIndex          Integer32,
   gs2326pIGMPSnoopingGroupsVLANID         Integer32,
   gs2326pIGMPSnoopingGroups               InetAddress,
   gs2326pIGMPSnoopingGroupsMemberships    DisplayString
}

gs2326pIGMPSnoopingGroupsIndex OBJECT-TYPE
   SYNTAX      Integer32(1..65535)
   MAX-ACCESS  not-accessible
   STATUS      current
   DESCRIPTION
       "IGMP Snooping Groups Index"
   ::= { gs2326pIGMPSnoopingGroupsEntry 1 }

gs2326pIGMPSnoopingGroupsVLANID OBJECT-TYPE
   SYNTAX      Integer32(1..4095)
   MAX-ACCESS  read-only
   STATUS      current
   DESCRIPTION
       "VLAN ID of the group. "
   ::= { gs2326pIGMPSnoopingGroupsEntry 2 }

gs2326pIGMPSnoopingGroups OBJECT-TYPE
   SYNTAX      DisplayString
   MAX-ACCESS  read-only
   STATUS      current
   DESCRIPTION
       "Group address of the group displayed."
   ::= { gs2326pIGMPSnoopingGroupsEntry 3 }

gs2326pIGMPSnoopingGroupsMemberships OBJECT-TYPE
   SYNTAX      DisplayString
   MAX-ACCESS  read-only
   STATUS      current
   DESCRIPTION
       "Ports under this group."
   ::= { gs2326pIGMPSnoopingGroupsEntry 4 }

gs2326pIGMPSnoopingSSMTable OBJECT-TYPE
   SYNTAX      SEQUENCE OF Gs2326pIGMPSnoopingSSMEntry
   MAX-ACCESS  not-accessible
   STATUS      current
   DESCRIPTION
       "The IGMP SFM (Source-Filtered Multicast) Information Table also contains
        the SSM (Source-Specific Multicast) information. This table is sorted
         first by VLAN ID, then by group, and then by Port. Different source
         addresses belong to the same group are treated as single entry."
   ::= { gs2326pIGMPSnooping 6 }

gs2326pIGMPSnoopingSSMEntry OBJECT-TYPE
   SYNTAX      Gs2326pIGMPSnoopingSSMEntry
   MAX-ACCESS  not-accessible
   STATUS      current
   DESCRIPTION
       ""
   INDEX    { gs2326pIGMPSnoopingSSMIndex  }
   ::= { gs2326pIGMPSnoopingSSMTable 1 }

Gs2326pIGMPSnoopingSSMEntry ::= SEQUENCE {
   gs2326pIGMPSnoopingSSMIndex          Integer32,
   gs2326pIGMPSnoopingSSMVLANID         Integer32,
   gs2326pIGMPSnoopingSSMGroup          DisplayString,
   gs2326pIGMPSnoopingSSMPort           Integer32,
   gs2326pIGMPSnoopingSSMMode           DisplayString,
   gs2326pIGMPSnoopingSSMSourceAddress  DisplayString,
   gs2326pIGMPSnoopingSSMType           DisplayString
}

gs2326pIGMPSnoopingSSMIndex OBJECT-TYPE
   SYNTAX      Integer32(1..65535)
   MAX-ACCESS  not-accessible
   STATUS      current
   DESCRIPTION
       "IGMP Snooping SSM Index"
   ::= { gs2326pIGMPSnoopingSSMEntry 1 }

gs2326pIGMPSnoopingSSMVLANID OBJECT-TYPE
   SYNTAX      Integer32(1..4095)
   MAX-ACCESS  read-only
   STATUS      current
   DESCRIPTION
       "VLAN ID of the group. "
   ::= { gs2326pIGMPSnoopingSSMEntry 2 }

gs2326pIGMPSnoopingSSMGroup OBJECT-TYPE
   SYNTAX      DisplayString
   MAX-ACCESS  read-only
   STATUS      current
   DESCRIPTION
       "Group address of the group displayed."
   ::= { gs2326pIGMPSnoopingSSMEntry 3 }

gs2326pIGMPSnoopingSSMPort OBJECT-TYPE
   SYNTAX      Integer32(1..65535)
   MAX-ACCESS  read-only
   STATUS      current
   DESCRIPTION
       "Ports under this group."
   ::= { gs2326pIGMPSnoopingSSMEntry 4 }

gs2326pIGMPSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326pIGMPSnoopingSSMEntry 5 }

gs2326pIGMPSnoopingSSMSourceAddress OBJECT-TYPE
   SYNTAX      DisplayString
   MAX-ACCESS  read-only
   STATUS      current
   DESCRIPTION
       "IP Address of the source. Currently, system limits the total number of
       IP source addresses for filtering to be 128."
   ::= { gs2326pIGMPSnoopingSSMEntry 6 }

gs2326pIGMPSnoopingSSMType OBJECT-TYPE
   SYNTAX      DisplayString
   MAX-ACCESS  read-only
   STATUS      current
   DESCRIPTION
       "Indicates the Type. It can be either Allow or Deny."
   ::= { gs2326pIGMPSnoopingSSMEntry 7 }

gs2326pMLDSnooping                                                           OBJECT IDENTIFIER ::= { gs2326pConfiguration 17 }

gs2326pMLDSnoopingBasic                                                      OBJECT IDENTIFIER ::= { gs2326pMLDSnooping 1 }

gs2326pMLDSnoopingEnable  OBJECT-TYPE
   SYNTAX      INTEGER { disable(0), enable(1) }
   MAX-ACCESS  read-write
   STATUS      current
   DESCRIPTION
       "Enable/Disable the Global MLD Snooping"
   ::= { gs2326pMLDSnoopingBasic 1 }

gs2326pMLDSnoopingUnregisteredIPMCv6Flooding  OBJECT-TYPE
   SYNTAX      INTEGER { disable(0), enable(1) }
   MAX-ACCESS  read-write
   STATUS      current
   DESCRIPTION
       "Enable/Disable unregistered IPMCv6 traffic flooding. "
   ::= { gs2326pMLDSnoopingBasic 2 }

gs2326pMLDSnoopingSSMIPRangeAddr  OBJECT-TYPE
   SYNTAX      DisplayString
   MAX-ACCESS  read-write
   STATUS      current
   DESCRIPTION
       "SSM (Source-Specific Multicast) Range allows the SSM-aware hosts and
       routers run the SSM service model for the groups in the address range. "
   ::= { gs2326pMLDSnoopingBasic 3 }

gs2326pMLDSnoopingSSMIPRangeValue  OBJECT-TYPE
   SYNTAX      Integer32(8..128)
   MAX-ACCESS  read-write
   STATUS      current
   DESCRIPTION
       "SSM (Source-Specific Multicast) Range allows the SSM-aware hosts and
       routers run the SSM service model for the groups in the address range value. "
   ::= { gs2326pMLDSnoopingBasic 4 }

gs2326pMLDSnoopingProxyEnabled  OBJECT-TYPE
   SYNTAX      INTEGER { disable(0), enable(1) }
   MAX-ACCESS  read-write
   STATUS      current
   DESCRIPTION
       "Enable/Disable MLD Proxy. This feature can be used to avoid forwarding
       unnecessary join and leave messages to the router side. "
   ::= { gs2326pMLDSnoopingBasic 5 }

gs2326pMLDSnoopingPortRelatedTable OBJECT-TYPE
   SYNTAX      SEQUENCE OF Gs2326pMLDSnoopingPortRelatedEntry
   MAX-ACCESS  not-accessible
   STATUS      current
   DESCRIPTION
       " Configure MLD Snooping Port Related Configuration. "
   ::= { gs2326pMLDSnoopingBasic 6 }

gs2326pMLDSnoopingPortRelatedEntry OBJECT-TYPE
   SYNTAX      Gs2326pMLDSnoopingPortRelatedEntry
   MAX-ACCESS  not-accessible
   STATUS      current
   DESCRIPTION
       ""
   INDEX    { ifIndex  }
   ::= { gs2326pMLDSnoopingPortRelatedTable 1 }

Gs2326pMLDSnoopingPortRelatedEntry ::= SEQUENCE {
   gs2326pMLDSnoopingRouterPort	INTEGER,
   gs2326pMLDSnoopingFastLeave  	INTEGER,
   gs2326pMLDSnoopingThrottling    Integer32
}

gs2326pMLDSnoopingRouterPort OBJECT-TYPE
   SYNTAX      INTEGER { disable(0), enable(1) }
   MAX-ACCESS  read-write
   STATUS      current
   DESCRIPTION
       "Specify which ports act as router ports. A router port is a port on the
       Ethernet switch that leads towards the Layer 3 multicast device or IGMP
       querier. If an aggregation member port is selected as a router port, the
       whole aggregation will act as a router port. "
   ::= { gs2326pMLDSnoopingPortRelatedEntry 1 }

gs2326pMLDSnoopingFastLeave OBJECT-TYPE
   SYNTAX      INTEGER { disable(0), enable(1) }
   MAX-ACCESS  read-write
   STATUS      current
   DESCRIPTION
       "Enable/Disable the fast leave on the port. "
   ::= { gs2326pMLDSnoopingPortRelatedEntry 2 }

gs2326pMLDSnoopingThrottling OBJECT-TYPE
   SYNTAX      Integer32(0..10)
   MAX-ACCESS  read-write
   STATUS      current
   DESCRIPTION
       "Enable to limit the number of multicast groups to which a switch port can belong.
       0: unlimited"
   ::= { gs2326pMLDSnoopingPortRelatedEntry 3 }

gs2326pMLDSnoopingVLANTable OBJECT-TYPE
   SYNTAX      SEQUENCE OF Gs2326pMLDSnoopingVLANEntry
   MAX-ACCESS  not-accessible
   STATUS      current
   DESCRIPTION
       " Configure MLD Snooping Vlan Configuration. "
   ::= { gs2326pMLDSnooping 2 }

gs2326pMLDSnoopingVLANEntry OBJECT-TYPE
   SYNTAX      Gs2326pMLDSnoopingVLANEntry
   MAX-ACCESS  not-accessible
   STATUS      current
   DESCRIPTION
       ""
   INDEX    { gs2326pMLDSnoopingVLANID  }
   ::= { gs2326pMLDSnoopingVLANTable 1 }

Gs2326pMLDSnoopingVLANEntry ::= SEQUENCE {
   gs2326pMLDSnoopingVLANID        	Integer32,
   gs2326pMLDSnoopingVLANEnable    	INTEGER,
   gs2326pMLDSnoopingVLANIGMPQuerier   INTEGER,
   gs2326pMLDSnoopingVLANCompatibility INTEGER,
   gs2326pMLDSnoopingVLANRV        	Integer32,
   gs2326pMLDSnoopingVLANQI      	    Integer32,
   gs2326pMLDSnoopingVLANQRI   	    Integer32,
   gs2326pMLDSnoopingVLANLLQI   	    Integer32,
   gs2326pMLDSnoopingVLANURI    	    Integer32
}

gs2326pMLDSnoopingVLANID OBJECT-TYPE
   SYNTAX      Integer32(1..4095)
   MAX-ACCESS  read-write
   STATUS      current
   DESCRIPTION
       "The VLAN ID of the entry"
   ::= { gs2326pMLDSnoopingVLANEntry 1 }

gs2326pMLDSnoopingVLANEnable OBJECT-TYPE
   SYNTAX      INTEGER { disable(0), enable(1) }
   MAX-ACCESS  read-write
   STATUS      current
   DESCRIPTION
       "Enable/Disable the per-VLAN MLD Snooping. Up to 32 VLANs can be
       selected for MLD Snooping. "
   ::= { gs2326pMLDSnoopingVLANEntry 2 }

gs2326pMLDSnoopingVLANIGMPQuerier OBJECT-TYPE
   SYNTAX      INTEGER { disable(0), enable(1) }
   MAX-ACCESS  read-write
   STATUS      current
   DESCRIPTION
       "Enable/Disable the MLD Querier in the VLAN. "
   ::= { gs2326pMLDSnoopingVLANEntry 3 }

gs2326pMLDSnoopingVLANCompatibility OBJECT-TYPE
   SYNTAX      INTEGER { mldAuto(0), forcedMLDv1(1), forcedMLDv2(2), none(3) }
   MAX-ACCESS  read-write
   STATUS      current
   DESCRIPTION
       "Compatibility is maintained by hosts and routers taking appropriate
       actions depending on the versions of IGMP operating on hosts and routers
       within a network. The allowed selection is MLD-Auto, Forced MLDv1,
       Forced MLDv2, default compatibility value is IGMP-Auto. "
   ::= { gs2326pMLDSnoopingVLANEntry 4 }

gs2326pMLDSnoopingVLANRV OBJECT-TYPE
   SYNTAX      Integer32(-1|1..255)
   MAX-ACCESS  read-write
   STATUS      current
   DESCRIPTION
       "Robustness Variable. The Robustness Variable allows tuning for the
       expected packet loss on a network. The allowed range is 1 to 255, default
        robustness variable value is 2. (-1: none)"
   ::= { gs2326pMLDSnoopingVLANEntry 5 }

gs2326pMLDSnoopingVLANQI OBJECT-TYPE
   SYNTAX      Integer32(-1|1..31744)
   MAX-ACCESS  read-write
   STATUS      current
   DESCRIPTION
       "Query Interval. The Query Interval is the interval between General
       Queries sent by the Querier. The allowed range is 1 to 31744 seconds,
       default query interval is 125 seconds.  (-1: none)"
   ::= { gs2326pMLDSnoopingVLANEntry 6 }

gs2326pMLDSnoopingVLANQRI OBJECT-TYPE
   SYNTAX      Integer32(-1|0..31744)
   MAX-ACCESS  read-write
   STATUS      current
   DESCRIPTION
       "Query Response Interval. The Maximum Response Delay used to calculate
       the Maximum Response Code inserted into the periodic General Queries. The
        allowed range is 0 to 31744 in tenths of seconds, default query response
         interval is 100 in tenths of seconds (10 seconds).   (-1: none)"
   ::= { gs2326pMLDSnoopingVLANEntry 7 }

gs2326pMLDSnoopingVLANLLQI OBJECT-TYPE
   SYNTAX      Integer32(-1|0..31744)
   MAX-ACCESS  read-write
   STATUS      current
   DESCRIPTION
       "LLQI (LMQI for MLD).  Last Member Query Interval. The Last Member Query
       Time is the time value represented by the Last Member Query Interval,
       multiplied by the Last Member Query Count. The allowed range is 0 to
       31744 in tenths of seconds, default last member query interval is 10 in
       tenths of seconds (1 second).    (-1: none)"
   ::= { gs2326pMLDSnoopingVLANEntry 8 }

gs2326pMLDSnoopingVLANURI OBJECT-TYPE
   SYNTAX      Integer32(-1|0..31744)
   MAX-ACCESS  read-write
   STATUS      current
   DESCRIPTION
       "Unsolicited Report Interval. The Unsolicited Report Interval is the time
        between repetitions of a host's initial report of membership in a group.
         The allowed range is 0 to 31744 seconds, default unsolicited report
         interval is 1 second.    (-1: none)"
   ::= { gs2326pMLDSnoopingVLANEntry 9 }

gs2326pMLDSnoopingPortGroupFiltering                                                      OBJECT IDENTIFIER ::= { gs2326pMLDSnooping 3 }

gs2326pMLDSnoopingPortGroupFilteringCreate OBJECT-TYPE
   SYNTAX       Integer32
   MAX-ACCESS   read-write
   STATUS       current
   DESCRIPTION
       "default: 0
       0 : None  (read only) 1 : Create MLD Snooping Port Group Filtering "
   ::= { gs2326pMLDSnoopingPortGroupFiltering 1 }

gs2326pMLDSnoopingPortGroupFilteringTable OBJECT-TYPE
   SYNTAX      SEQUENCE OF Gs2326pMLDSnoopingPortGroupFilteringEntry
   MAX-ACCESS  not-accessible
   STATUS      current
   DESCRIPTION
       " Configure MLD Snooping port group filtering. "
   ::= { gs2326pMLDSnoopingPortGroupFiltering 2 }

gs2326pMLDSnoopingPortGroupFilteringEntry OBJECT-TYPE
   SYNTAX      Gs2326pMLDSnoopingPortGroupFilteringEntry
   MAX-ACCESS  not-accessible
   STATUS      current
   DESCRIPTION
       ""
   INDEX    { gs2326pMLDSnoopingPortGroupFilteringIndex  }
   ::= { gs2326pMLDSnoopingPortGroupFilteringTable 1 }

Gs2326pMLDSnoopingPortGroupFilteringEntry ::= SEQUENCE {
   gs2326pMLDSnoopingPortGroupFilteringIndex         Integer32,
   gs2326pMLDSnoopingPortGroupFilteringPort          Integer32,
   gs2326pMLDSnoopingPortGroupFilteringGroups        DisplayString,
   gs2326pMLDSnoopingPortGroupFilteringRowStatus     INTEGER
}

gs2326pMLDSnoopingPortGroupFilteringIndex OBJECT-TYPE
   SYNTAX      Integer32(1..65535)
   MAX-ACCESS  not-accessible
   STATUS      current
   DESCRIPTION
       "MLD Snooping Port Group Filtering Configuration Index. "
   ::= { gs2326pMLDSnoopingPortGroupFilteringEntry 1 }

gs2326pMLDSnoopingPortGroupFilteringPort OBJECT-TYPE
   SYNTAX      Integer32(1..65535)
   MAX-ACCESS  read-write
   STATUS      current
   DESCRIPTION
       "The logical port for the settings. "
   ::= { gs2326pMLDSnoopingPortGroupFilteringEntry 2 }

gs2326pMLDSnoopingPortGroupFilteringGroups OBJECT-TYPE
   SYNTAX      DisplayString
   MAX-ACCESS  read-write
   STATUS      current
   DESCRIPTION
       "The IP Multicast Group that will be filtered. "
   ::= { gs2326pMLDSnoopingPortGroupFilteringEntry 3 }

gs2326pMLDSnoopingPortGroupFilteringRowStatus OBJECT-TYPE
   SYNTAX      INTEGER { active(1), notInservice(2), destroy(4)}
   MAX-ACCESS  read-write
   STATUS      current
   DESCRIPTION
       "1: active
        2: notInservice
        4: destroy"
   ::= { gs2326pMLDSnoopingPortGroupFilteringEntry 4 }

gs2326pMLDSnoopingStatus                                                      OBJECT IDENTIFIER ::= { gs2326pMLDSnooping 4 }

gs2326pMLDSnoopingstatisticClear OBJECT-TYPE
   SYNTAX      INTEGER { none(0), clear(1)}
   MAX-ACCESS  read-write
   STATUS      current
   DESCRIPTION
       "Clears all Statistics counters."
   ::= { gs2326pMLDSnoopingStatus 1 }


gs2326pMLDSnoopingstatisticTable OBJECT-TYPE
   SYNTAX      SEQUENCE OF Gs2326pMLDSnoopingstatisticEntry
   MAX-ACCESS  not-accessible
   STATUS      current
   DESCRIPTION
       " Configure Vlan Port Isolation Configuration. "
   ::= { gs2326pMLDSnoopingStatus 2 }

gs2326pMLDSnoopingstatisticEntry OBJECT-TYPE
   SYNTAX      Gs2326pMLDSnoopingstatisticEntry
   MAX-ACCESS  not-accessible
   STATUS      current
   DESCRIPTION
       ""
   INDEX    { gs2326pMLDSnoopingstatisticVLANID  }
   ::= { gs2326pMLDSnoopingstatisticTable 1 }

Gs2326pMLDSnoopingstatisticEntry ::= SEQUENCE {
   gs2326pMLDSnoopingstatisticVLANID              Integer32,
   gs2326pMLDSnoopingstatisticQuerierVersion      DisplayString,
   gs2326pMLDSnoopingstatisticHostVersion         DisplayString,
   gs2326pMLDSnoopingstatisticQuerierStatus       DisplayString,
   gs2326pMLDSnoopingstatisticQueriesTransmitted  Counter32,
   gs2326pMLDSnoopingstatisticQueriesReceived     Counter32,
   gs2326pMLDSnoopingstatisticV1ReportsReceived   Counter32,
   gs2326pMLDSnoopingstatisticV2ReportsReceived   Counter32,
   gs2326pMLDSnoopingstatisticV1LeavesReceived    Counter32
}


gs2326pMLDSnoopingstatisticVLANID OBJECT-TYPE
   SYNTAX      Integer32(1..4095)
   MAX-ACCESS  read-only
   STATUS      current
   DESCRIPTION
       "The VLAN ID of the entry. "
   ::= { gs2326pMLDSnoopingstatisticEntry 1 }

gs2326pMLDSnoopingstatisticQuerierVersion OBJECT-TYPE
   SYNTAX      DisplayString
   MAX-ACCESS  read-only
   STATUS      current
   DESCRIPTION
       "Working Querier Version currently. "
   ::= { gs2326pMLDSnoopingstatisticEntry 2 }

gs2326pMLDSnoopingstatisticHostVersion OBJECT-TYPE
   SYNTAX      DisplayString
   MAX-ACCESS  read-only
   STATUS      current
   DESCRIPTION
       "Working Host Version currently. "
   ::= { gs2326pMLDSnoopingstatisticEntry 3 }

gs2326pMLDSnoopingstatisticQuerierStatus OBJECT-TYPE
   SYNTAX      DisplayString
   MAX-ACCESS  read-only
   STATUS      current
   DESCRIPTION
       "Shows the Querier status is ACTIVE or IDLE. DISABLE denotes the specific
        interface is administratively disabled. "
   ::= { gs2326pMLDSnoopingstatisticEntry 4 }

gs2326pMLDSnoopingstatisticQueriesTransmitted OBJECT-TYPE
   SYNTAX      Counter32
   MAX-ACCESS  read-only
   STATUS      current
   DESCRIPTION
       "The number of Transmitted Queries. "
   ::= { gs2326pMLDSnoopingstatisticEntry 5 }

gs2326pMLDSnoopingstatisticQueriesReceived OBJECT-TYPE
   SYNTAX      Counter32
   MAX-ACCESS  read-only
   STATUS      current
   DESCRIPTION
       "The number of Received Queries. "
   ::= { gs2326pMLDSnoopingstatisticEntry 6 }

gs2326pMLDSnoopingstatisticV1ReportsReceived OBJECT-TYPE
   SYNTAX      Counter32
   MAX-ACCESS  read-only
   STATUS      current
   DESCRIPTION
       "The number of Received V1 Reports. "
   ::= { gs2326pMLDSnoopingstatisticEntry 7 }

gs2326pMLDSnoopingstatisticV2ReportsReceived OBJECT-TYPE
   SYNTAX      Counter32
   MAX-ACCESS  read-only
   STATUS      current
   DESCRIPTION
       "The number of Received V2 Reports. "
   ::= { gs2326pMLDSnoopingstatisticEntry 8 }

gs2326pMLDSnoopingstatisticV1LeavesReceived OBJECT-TYPE
   SYNTAX      Counter32
   MAX-ACCESS  read-only
   STATUS      current
   DESCRIPTION
       "The number of Received V1 Leaves. "
   ::= { gs2326pMLDSnoopingstatisticEntry 9 }

gs2326pMLDSnoopingRouterPortTable OBJECT-TYPE
   SYNTAX      SEQUENCE OF Gs2326pMLDSnoopingRouterPortEntry
   MAX-ACCESS  not-accessible
   STATUS      current
   DESCRIPTION
       " Configure Vlan Port Isolation Configuration. "
   ::= { gs2326pMLDSnoopingStatus 3 }

gs2326pMLDSnoopingRouterPortEntry OBJECT-TYPE
   SYNTAX      Gs2326pMLDSnoopingRouterPortEntry
   MAX-ACCESS  not-accessible
   STATUS      current
   DESCRIPTION
       ""
   INDEX    { ifIndex  }
   ::= { gs2326pMLDSnoopingRouterPortTable 1 }

Gs2326pMLDSnoopingRouterPortEntry ::= SEQUENCE {
   gs2326pMLDSnoopingRouterPortStatus            DisplayString
}

gs2326pMLDSnoopingRouterPortStatus OBJECT-TYPE
   SYNTAX      DisplayString
   MAX-ACCESS  read-only
   STATUS      current
   DESCRIPTION
       "Display which ports act as router ports. A router port is a port on the
       Ethernet switch that leads towards the Layer 3 multicast device or IGMP
       querier.
       Static denotes the specific port is configured to be a router port.
       Dynamic denotes the specific port is learnt to be a router port.
       Both denote the specific port is configured or learnt to be a router port. "
   ::= { gs2326pMLDSnoopingRouterPortEntry 1 }

gs2326pMLDSnoopingGroupsTable OBJECT-TYPE
   SYNTAX      SEQUENCE OF Gs2326pMLDSnoopingGroupsEntry
   MAX-ACCESS  not-accessible
   STATUS      current
   DESCRIPTION
       "MLD Snooping Groups Information . "
   ::= { gs2326pMLDSnooping 5 }

gs2326pMLDSnoopingGroupsEntry OBJECT-TYPE
   SYNTAX      Gs2326pMLDSnoopingGroupsEntry
   MAX-ACCESS  not-accessible
   STATUS      current
   DESCRIPTION
       ""
   INDEX    { gs2326pMLDSnoopingGroupsIndex  }
   ::= { gs2326pMLDSnoopingGroupsTable 1 }

Gs2326pMLDSnoopingGroupsEntry ::= SEQUENCE {
   gs2326pMLDSnoopingGroupsIndex          Integer32,
   gs2326pMLDSnoopingGroupsVLANID         Integer32,
   gs2326pMLDSnoopingGroups               InetAddress,
   gs2326pMLDSnoopingGroupsMemberships    DisplayString
}

gs2326pMLDSnoopingGroupsIndex OBJECT-TYPE
   SYNTAX      Integer32(1..65535)
   MAX-ACCESS  not-accessible
   STATUS      current
   DESCRIPTION
       "MLD Snooping Groups Index"
   ::= { gs2326pMLDSnoopingGroupsEntry 1 }

gs2326pMLDSnoopingGroupsVLANID OBJECT-TYPE
   SYNTAX      Integer32(1..4095)
   MAX-ACCESS  read-only
   STATUS      current
   DESCRIPTION
       "VLAN ID of the group. "
   ::= { gs2326pMLDSnoopingGroupsEntry 2 }

gs2326pMLDSnoopingGroups OBJECT-TYPE
   SYNTAX      DisplayString
   MAX-ACCESS  read-only
   STATUS      current
   DESCRIPTION
       "Group address of the group displayed."
   ::= { gs2326pMLDSnoopingGroupsEntry 3 }

gs2326pMLDSnoopingGroupsMemberships OBJECT-TYPE
   SYNTAX      DisplayString
   MAX-ACCESS  read-only
   STATUS      current
   DESCRIPTION
       "Ports under this group."
   ::= { gs2326pMLDSnoopingGroupsEntry 4 }

gs2326pMLDSnoopingSSMTable OBJECT-TYPE
   SYNTAX      SEQUENCE OF Gs2326pMLDSnoopingSSMEntry
   MAX-ACCESS  not-accessible
   STATUS      current
   DESCRIPTION
       "The MLD SFM (Source-Filtered Multicast) Information Table also contains
        the SSM (Source-Specific Multicast) information. This table is sorted
         first by VLAN ID, then by group, and then by Port. Different source
         addresses belong to the same group are treated as single entry."
   ::= { gs2326pMLDSnooping 6 }

gs2326pMLDSnoopingSSMEntry OBJECT-TYPE
   SYNTAX      Gs2326pMLDSnoopingSSMEntry
   MAX-ACCESS  not-accessible
   STATUS      current
   DESCRIPTION
       ""
   INDEX    { gs2326pMLDSnoopingSSMIndex  }
   ::= { gs2326pMLDSnoopingSSMTable 1 }

Gs2326pMLDSnoopingSSMEntry ::= SEQUENCE {
   gs2326pMLDSnoopingSSMIndex          Integer32,
   gs2326pMLDSnoopingSSMVLANID         Integer32,
   gs2326pMLDSnoopingSSMGroup          DisplayString,
   gs2326pMLDSnoopingSSMPort           Integer32,
   gs2326pMLDSnoopingSSMMode           DisplayString,
   gs2326pMLDSnoopingSSMSourceAddress  DisplayString,
   gs2326pMLDSnoopingSSMType           DisplayString
}

gs2326pMLDSnoopingSSMIndex OBJECT-TYPE
   SYNTAX      Integer32(1..65535)
   MAX-ACCESS  not-accessible
   STATUS      current
   DESCRIPTION
       "MLD Snooping SSM Index"
   ::= { gs2326pMLDSnoopingSSMEntry 1 }

gs2326pMLDSnoopingSSMVLANID OBJECT-TYPE
   SYNTAX      Integer32(1..4095)
   MAX-ACCESS  read-only
   STATUS      current
   DESCRIPTION
       "VLAN ID of the group. "
   ::= { gs2326pMLDSnoopingSSMEntry 2 }

gs2326pMLDSnoopingSSMGroup OBJECT-TYPE
   SYNTAX      DisplayString
   MAX-ACCESS  read-only
   STATUS      current
   DESCRIPTION
       "Group address of the group displayed."
   ::= { gs2326pMLDSnoopingSSMEntry 3 }

gs2326pMLDSnoopingSSMPort OBJECT-TYPE
   SYNTAX      Integer32(1..65535)
   MAX-ACCESS  read-only
   STATUS      current
   DESCRIPTION
       "Ports under this group."
   ::= { gs2326pMLDSnoopingSSMEntry 4 }

gs2326pMLDSnoopingSSMMode OBJECT-TYPE
   SYNTAX      DisplayString
   MAX-ACCESS  read-only
   STATUS      current
   DESCRIPTION
       "Indicates the filtering mode maintained per (VLAN ID, port number,
       Group Address) basis. It can be either Include or Exclude."
   ::= { gs2326pMLDSnoopingSSMEntry 5 }

gs2326pMLDSnoopingSSMSourceAddress OBJECT-TYPE
   SYNTAX      DisplayString
   MAX-ACCESS  read-only
   STATUS      current
   DESCRIPTION
       "IP Address of the source. Currently, system limits the total number of
       IP source addresses for filtering to be 128."
   ::= { gs2326pMLDSnoopingSSMEntry 6 }

gs2326pMLDSnoopingSSMType OBJECT-TYPE
   SYNTAX      DisplayString
   MAX-ACCESS  read-only
   STATUS      current
   DESCRIPTION
       "Indicates the Type. It can be either Allow or Deny."
   ::= { gs2326pMLDSnoopingSSMEntry 7 }


gs2326pMVR                                                                   OBJECT IDENTIFIER ::= { gs2326pConfiguration 18 }

gs2326pMVRConfiguration                                                      OBJECT IDENTIFIER ::= { gs2326pMVR 1 }

gs2326pMVRMode  OBJECT-TYPE
   SYNTAX      INTEGER { disable(0), enable(1) }
   MAX-ACCESS  read-write
   STATUS      current
   DESCRIPTION
       "Enable/Disable the Global MVR. "
   ::= { gs2326pMVRConfiguration 1 }

gs2326pMVRVLANId  OBJECT-TYPE
   SYNTAX      Integer32(1..4094)
   MAX-ACCESS  read-write
   STATUS      current
   DESCRIPTION
       "Specify the Multicast VLAN ID. "
   ::= { gs2326pMVRConfiguration 2 }

gs2326pMVRPortConfigurationTable OBJECT-TYPE
   SYNTAX      SEQUENCE OF Gs2326pMVRPortConfigurationEntry
   MAX-ACCESS  not-accessible
   STATUS      current
   DESCRIPTION
       " Configure MVR Port Configuration. "
   ::= { gs2326pMVRConfiguration 3 }

gs2326pMVRPortConfigurationEntry OBJECT-TYPE
   SYNTAX      Gs2326pMVRPortConfigurationEntry
   MAX-ACCESS  not-accessible
   STATUS      current
   DESCRIPTION
       ""
   INDEX    { ifIndex  }
   ::= { gs2326pMVRPortConfigurationTable 1 }

Gs2326pMVRPortConfigurationEntry ::= SEQUENCE {
   gs2326pMVRPortConfigurationMode	INTEGER,
   gs2326pMVRPortConfigurationType  	INTEGER,
   gs2326pMVRPortConfigurationImmediateLeave    INTEGER
}

gs2326pMVRPortConfigurationMode OBJECT-TYPE
   SYNTAX      INTEGER { disable(0), enable(1) }
   MAX-ACCESS  read-write
   STATUS      current
   DESCRIPTION
       "Enable MVR on the port. "
   ::= { gs2326pMVRPortConfigurationEntry 1 }

gs2326pMVRPortConfigurationType OBJECT-TYPE
   SYNTAX      INTEGER { receiver(0), source(1) }
   MAX-ACCESS  read-write
   STATUS      current
   DESCRIPTION
       "Specify the MVR port type on the port. "
   ::= { gs2326pMVRPortConfigurationEntry 2 }

gs2326pMVRPortConfigurationImmediateLeave OBJECT-TYPE
   SYNTAX      INTEGER { disable(0), enable(1) }
   MAX-ACCESS  read-write
   STATUS      current
   DESCRIPTION
       "Enable the fast leave on the port. "
   ::= { gs2326pMVRPortConfigurationEntry 3 }


gs2326pMVRPortGroupFiltering                                                      OBJECT IDENTIFIER ::= { gs2326pMVR 2 }

gs2326pMVRPortGroupFilteringCreate OBJECT-TYPE
   SYNTAX       Integer32
   MAX-ACCESS   read-write
   STATUS       current
   DESCRIPTION
       "default: 0
       0 : None  (read only) 1 : Create MLD Snooping Port Group Filtering "
   ::= { gs2326pMVRPortGroupFiltering 1 }

gs2326pMVRPortGroupFilteringTable OBJECT-TYPE
   SYNTAX      SEQUENCE OF Gs2326pMVRPortGroupFilteringEntry
   MAX-ACCESS  not-accessible
   STATUS      current
   DESCRIPTION
       " Configure MVR port group filtering. "
   ::= { gs2326pMVRPortGroupFiltering 2 }

gs2326pMVRPortGroupFilteringEntry OBJECT-TYPE
   SYNTAX      Gs2326pMVRPortGroupFilteringEntry
   MAX-ACCESS  not-accessible
   STATUS      current
   DESCRIPTION
       ""
   INDEX    { gs2326pMVRPortGroupFilteringIndex  }
   ::= { gs2326pMVRPortGroupFilteringTable 1 }

Gs2326pMVRPortGroupFilteringEntry ::= SEQUENCE {
   gs2326pMVRPortGroupFilteringIndex         Integer32,
   gs2326pMVRPortGroupFilteringPort          Integer32,
   gs2326pMVRPortGroupFilteringStartGroups   DisplayString,
   gs2326pMVRPortGroupFilteringEndGroups     DisplayString,
   gs2326pMVRPortGroupFilteringRowStatus     INTEGER
}

gs2326pMVRPortGroupFilteringIndex OBJECT-TYPE
   SYNTAX      Integer32(1..65535)
   MAX-ACCESS  not-accessible
   STATUS      current
   DESCRIPTION
       "MVR Port Group Filtering Configuration Index. "
   ::= { gs2326pMVRPortGroupFilteringEntry 1 }

gs2326pMVRPortGroupFilteringPort OBJECT-TYPE
   SYNTAX      Integer32(1..65535)
   MAX-ACCESS  read-write
   STATUS      current
   DESCRIPTION
       "The logical port for the settings. "
   ::= { gs2326pMVRPortGroupFilteringEntry 2 }

gs2326pMVRPortGroupFilteringStartGroups OBJECT-TYPE
   SYNTAX      DisplayString
   MAX-ACCESS  read-write
   STATUS      current
   DESCRIPTION
       "The IP Multicast Group that will be allowed. "
   ::= { gs2326pMVRPortGroupFilteringEntry 3 }

gs2326pMVRPortGroupFilteringEndGroups OBJECT-TYPE
   SYNTAX      DisplayString
   MAX-ACCESS  read-write
   STATUS      current
   DESCRIPTION
       "The IP Multicast Group that will be allowed. "
   ::= { gs2326pMVRPortGroupFilteringEntry 4 }

gs2326pMVRPortGroupFilteringRowStatus OBJECT-TYPE
   SYNTAX      INTEGER { active(1), notInservice(2), destroy(4)}
   MAX-ACCESS  read-write
   STATUS      current
   DESCRIPTION
       "1: active
        2: notInservice
        4: destroy"
   ::= { gs2326pMVRPortGroupFilteringEntry 5 }

gs2326pMVRGroupsTable OBJECT-TYPE
   SYNTAX      SEQUENCE OF Gs2326pMVRGroupsEntry
   MAX-ACCESS  not-accessible
   STATUS      current
   DESCRIPTION
       "MVR Groups Information . "
   ::= { gs2326pMVR 3 }

gs2326pMVRGroupsEntry OBJECT-TYPE
   SYNTAX      Gs2326pMVRGroupsEntry
   MAX-ACCESS  not-accessible
   STATUS      current
   DESCRIPTION
       ""
   INDEX    { gs2326pMVRGroupsIndex  }
   ::= { gs2326pMVRGroupsTable 1 }

Gs2326pMVRGroupsEntry ::= SEQUENCE {
   gs2326pMVRGroupsIndex          Integer32,
   gs2326pMVRGroupsVLANID         Integer32,
   gs2326pMVRGroups               InetAddress,
   gs2326pMVRGroupsMemberships    DisplayString
}

gs2326pMVRGroupsIndex OBJECT-TYPE
   SYNTAX      Integer32(1..65535)
   MAX-ACCESS  not-accessible
   STATUS      current
   DESCRIPTION
       "MVR Groups Index"
   ::= { gs2326pMVRGroupsEntry 1 }

gs2326pMVRGroupsVLANID OBJECT-TYPE
   SYNTAX      Integer32(1..4095)
   MAX-ACCESS  read-only
   STATUS      current
   DESCRIPTION
       "VLAN ID of the group. "
   ::= { gs2326pMVRGroupsEntry 2 }

gs2326pMVRGroups OBJECT-TYPE
   SYNTAX      DisplayString
   MAX-ACCESS  read-only
   STATUS      current
   DESCRIPTION
       "Group address of the group displayed."
   ::= { gs2326pMVRGroupsEntry 3 }

gs2326pMVRGroupsMemberships OBJECT-TYPE
   SYNTAX      DisplayString
   MAX-ACCESS  read-only
   STATUS      current
   DESCRIPTION
       "Ports under this group."
   ::= { gs2326pMVRGroupsEntry 4 }


gs2326pMVRStatus                                                      OBJECT IDENTIFIER ::= { gs2326pMVR 4 }

gs2326pMVRstatisticClear OBJECT-TYPE
   SYNTAX      INTEGER { none(0), clear(1)}
   MAX-ACCESS  read-write
   STATUS      current
   DESCRIPTION
       "Clears all Statistics counters."
   ::= { gs2326pMVRStatus 1 }

gs2326pMVRstatisticVLANID OBJECT-TYPE
   SYNTAX      Integer32(1..4095)
   MAX-ACCESS  read-only
   STATUS      current
   DESCRIPTION
       "The VLAN ID of the entry. "
   ::= { gs2326pMVRStatus 2 }

gs2326pMVRstatisticV1ReportsReceived OBJECT-TYPE
   SYNTAX      Counter32
   MAX-ACCESS  read-only
   STATUS      current
   DESCRIPTION
       "The number of Received V1 Reports. "
   ::= { gs2326pMVRStatus 3 }

gs2326pMVRstatisticV2ReportsReceived OBJECT-TYPE
   SYNTAX      Counter32
   MAX-ACCESS  read-only
   STATUS      current
   DESCRIPTION
       "The number of Received V2 Reports. "
   ::= { gs2326pMVRStatus 4 }

gs2326pMVRstatisticV3ReportsReceived OBJECT-TYPE
   SYNTAX      Counter32
   MAX-ACCESS  read-only
   STATUS      current
   DESCRIPTION
       "The number of Received V3 Reports. "
   ::= { gs2326pMVRStatus 5 }

gs2326pMVRstatisticV2LeavesReceived OBJECT-TYPE
   SYNTAX      Counter32
   MAX-ACCESS  read-only
   STATUS      current
   DESCRIPTION
       "The number of Received V2 Leaves. "
   ::= { gs2326pMVRStatus 6 }

gs2326pLACP                                                     OBJECT IDENTIFIER ::= { gs2326pConfiguration 19 }

gs2326pLACPConf                                                 OBJECT IDENTIFIER ::= { gs2326pLACP 1 }

gs2326pLACPPortConfigurationTable OBJECT-TYPE
   SYNTAX      SEQUENCE OF Gs2326pLACPPortConfigurationEntry
   MAX-ACCESS  not-accessible
   STATUS      current
   DESCRIPTION
       " "
   ::= { gs2326pLACPConf 1 }

gs2326pLACPPortConfigurationEntry OBJECT-TYPE
   SYNTAX      Gs2326pLACPPortConfigurationEntry
   MAX-ACCESS  not-accessible
   STATUS      current
   DESCRIPTION
       ""
   INDEX    { gs2326pLACPPortConfigurationPort  }
   ::= { gs2326pLACPPortConfigurationTable 1 }

Gs2326pLACPPortConfigurationEntry ::= SEQUENCE {
    gs2326pLACPPortConfigurationPort         Integer32,
    gs2326pLACPPortConfigurationMode         INTEGER,
    gs2326pLACPPortConfigurationKey          Integer32,
    gs2326pLACPPortConfigurationRole         INTEGER
}

gs2326pLACPPortConfigurationPort OBJECT-TYPE
   SYNTAX      Integer32(1..4095)
   MAX-ACCESS  not-accessible
   STATUS      current
   DESCRIPTION
       " "
   ::= { gs2326pLACPPortConfigurationEntry 1 }

gs2326pLACPPortConfigurationMode OBJECT-TYPE
   SYNTAX      INTEGER { disable(0), enable(1) }
   MAX-ACCESS  read-write
   STATUS      current
   DESCRIPTION
       "Enable/Disable LACP Mode."
   ::= { gs2326pLACPPortConfigurationEntry 2 }

gs2326pLACPPortConfigurationKey OBJECT-TYPE
   SYNTAX      Integer32(0..65535)
   MAX-ACCESS  read-write
   STATUS      current
   DESCRIPTION
       "LACP key : 1-65535. 0 : Auto"
   ::= { gs2326pLACPPortConfigurationEntry 3 }

gs2326pLACPPortConfigurationRole OBJECT-TYPE
   SYNTAX      INTEGER { passive(0), active(1) }
   MAX-ACCESS  read-write
   STATUS      current
   DESCRIPTION
       "0 : passive, Listen for LACP packets.
        1 : active, Initiate LACP negotiation, and transmit LACP packets each second"
   ::= { gs2326pLACPPortConfigurationEntry 4 }

gs2326pLACPSystemStatusTable OBJECT-TYPE
   SYNTAX      SEQUENCE OF Gs2326pLACPSystemStatusEntry
   MAX-ACCESS  not-accessible
   STATUS      current
   DESCRIPTION
       " "
   ::= { gs2326pLACP 2 }

gs2326pLACPSystemStatusEntry OBJECT-TYPE
   SYNTAX      Gs2326pLACPSystemStatusEntry
   MAX-ACCESS  not-accessible
   STATUS      current
   DESCRIPTION
       ""
   INDEX    { gs2326pLACPSystemStatusIndex  }
   ::= { gs2326pLACPSystemStatusTable 1 }

Gs2326pLACPSystemStatusEntry ::= SEQUENCE {
   gs2326pLACPSystemStatusIndex             Integer32,
   gs2326pLACPSystemStatusAggrID            DisplayString,
   gs2326pLACPSystemStatusPartnerSystemID   MacAddress,
   gs2326pLACPSystemStatusPartnerKey        DisplayString,
   gs2326pLACPSystemStatusLastchanged       DisplayString,
   gs2326pLACPSystemStatusLocalPorts        DisplayString
}

gs2326pLACPSystemStatusIndex OBJECT-TYPE
   SYNTAX      Integer32(1..12)
   MAX-ACCESS  not-accessible
   STATUS      current
   DESCRIPTION
       " "
   ::= { gs2326pLACPSystemStatusEntry 1 }

gs2326pLACPSystemStatusAggrID OBJECT-TYPE
   SYNTAX      DisplayString
   MAX-ACCESS  read-only
   STATUS      current
   DESCRIPTION
       "The Aggregation ID associated with this aggregation instance."
   ::= { gs2326pLACPSystemStatusEntry 2 }

gs2326pLACPSystemStatusPartnerSystemID OBJECT-TYPE
   SYNTAX      MacAddress
   MAX-ACCESS  read-only
   STATUS      current
   DESCRIPTION
       "The system ID (MAC address) of the aggregation partner."
   ::= { gs2326pLACPSystemStatusEntry 3 }

gs2326pLACPSystemStatusPartnerKey OBJECT-TYPE
   SYNTAX      DisplayString
   MAX-ACCESS  read-only
   STATUS      current
   DESCRIPTION
       " The Key that the partner has assigned to this aggregation ID. "
   ::= { gs2326pLACPSystemStatusEntry 4 }

gs2326pLACPSystemStatusLastchanged OBJECT-TYPE
   SYNTAX      DisplayString
   MAX-ACCESS  read-only
   STATUS      current
   DESCRIPTION
       " The time since this aggregation changed. "
   ::= { gs2326pLACPSystemStatusEntry 5 }

gs2326pLACPSystemStatusLocalPorts OBJECT-TYPE
   SYNTAX      DisplayString
   MAX-ACCESS  read-only
   STATUS      current
   DESCRIPTION
       " Shows which ports are a part of this aggregation for this switch. "
   ::= { gs2326pLACPSystemStatusEntry 6 }

gs2326pLACPStatusTable OBJECT-TYPE
   SYNTAX      SEQUENCE OF Gs2326pLACPStatusEntry
   MAX-ACCESS  not-accessible
   STATUS      current
   DESCRIPTION
       " "
   ::= { gs2326pLACP 3 }

gs2326pLACPStatusEntry OBJECT-TYPE
   SYNTAX      Gs2326pLACPStatusEntry
   MAX-ACCESS  not-accessible
   STATUS      current
   DESCRIPTION
       ""
   INDEX    { gs2326pLACPStatusPort  }
   ::= { gs2326pLACPStatusTable 1 }

Gs2326pLACPStatusEntry ::= SEQUENCE {
   gs2326pLACPStatusPort                Integer32,
   gs2326pLACPStatusLACP                DisplayString,
   gs2326pLACPStatusKey                 DisplayString,
   gs2326pLACPStatusAggrID              DisplayString,
   gs2326pLACPStatusPartnerSystemID     DisplayString,
   gs2326pLACPStatusPartnerPort         DisplayString
}

gs2326pLACPStatusPort OBJECT-TYPE
   SYNTAX      Integer32(1..4095)
   MAX-ACCESS  not-accessible
   STATUS      current
   DESCRIPTION
       " "
   ::= { gs2326pLACPStatusEntry 1 }

gs2326pLACPStatusLACP OBJECT-TYPE
   SYNTAX      DisplayString
   MAX-ACCESS  read-only
   STATUS      current
   DESCRIPTION
       "Enabled means that LACP is enabled and the port link is up.
        Disabled means that LACP is not enabled or that the port link is down.
        Backup means that the port could not join the aggregation group but will join if other port leaves.
        Meanwhile it's LACP status is disabled."
   ::= { gs2326pLACPStatusEntry 2 }

gs2326pLACPStatusKey OBJECT-TYPE
   SYNTAX      DisplayString
   MAX-ACCESS  read-only
   STATUS      current
   DESCRIPTION
       "The key assigned to this port. Only ports with the same key can aggregate together."
   ::= { gs2326pLACPStatusEntry 3 }

gs2326pLACPStatusAggrID	 OBJECT-TYPE
   SYNTAX      DisplayString
   MAX-ACCESS  read-only
   STATUS      current
   DESCRIPTION
       " The Aggregation ID assigned to this aggregation group. "
   ::= { gs2326pLACPStatusEntry 4 }

gs2326pLACPStatusPartnerSystemID OBJECT-TYPE
   SYNTAX      DisplayString
   MAX-ACCESS  read-only
   STATUS      current
   DESCRIPTION
       " The partner's System ID. "
   ::= { gs2326pLACPStatusEntry 5 }

gs2326pLACPStatusPartnerPort OBJECT-TYPE
   SYNTAX      DisplayString
   MAX-ACCESS  read-only
   STATUS      current
   DESCRIPTION
       " The partner's port number connected to this port. "
   ::= { gs2326pLACPStatusEntry 6 }


gs2326pLACPStatisticsTable OBJECT-TYPE
   SYNTAX      SEQUENCE OF Gs2326pLACPStatisticsEntry
   MAX-ACCESS  not-accessible
   STATUS      current
   DESCRIPTION
       " "
   ::= { gs2326pLACP 4 }

gs2326pLACPStatisticsEntry OBJECT-TYPE
   SYNTAX      Gs2326pLACPStatisticsEntry
   MAX-ACCESS  not-accessible
   STATUS      current
   DESCRIPTION
       ""
   INDEX    { gs2326pLACPStatisticsPort  }
   ::= { gs2326pLACPStatisticsTable 1 }

Gs2326pLACPStatisticsEntry ::= SEQUENCE {
   gs2326pLACPStatisticsPort        Integer32,
   gs2326pLACPReceived              Counter32,
   gs2326pLACPTransmitted           Counter32,
   gs2326pLACPDiscardedUnknown      Counter32,
   gs2326pLACPDiscardedIllegal      Counter32
}

gs2326pLACPStatisticsPort OBJECT-TYPE
   SYNTAX      Integer32(1..4095)
   MAX-ACCESS  not-accessible
   STATUS      current
   DESCRIPTION
       " "
   ::= { gs2326pLACPStatisticsEntry 1 }

gs2326pLACPReceived OBJECT-TYPE
   SYNTAX      Counter32
   MAX-ACCESS  read-only
   STATUS      current
   DESCRIPTION
       "Shows how many LACP frames have been received at each port. "
   ::= { gs2326pLACPStatisticsEntry 2 }

gs2326pLACPTransmitted OBJECT-TYPE
   SYNTAX      Counter32
   MAX-ACCESS  read-only
   STATUS      current
   DESCRIPTION
       " Shows how many LACP frames have been sent from each port. "
   ::= { gs2326pLACPStatisticsEntry 3 }

gs2326pLACPDiscardedUnknown OBJECT-TYPE
   SYNTAX      Counter32
   MAX-ACCESS  read-only
   STATUS      current
   DESCRIPTION
       " Shows how many unknown LACP frames have been discarded at each port. "
   ::= { gs2326pLACPStatisticsEntry 4 }

gs2326pLACPDiscardedIllegal OBJECT-TYPE
   SYNTAX      Counter32
   MAX-ACCESS  read-only
   STATUS      current
   DESCRIPTION
       " Shows how many illegal LACP frames have been discarded at each port. "
   ::= { gs2326pLACPStatisticsEntry 5 }

gs2326pLACPStatisticsClear OBJECT-TYPE
   SYNTAX      INTEGER { none(0), clear(1) }
   MAX-ACCESS  read-write
   STATUS      current
   DESCRIPTION
       "default: 0
       0: none
       1: clear"
   ::= { gs2326pLACP 5 }

gs2326pSTP                                                     OBJECT IDENTIFIER ::= { gs2326pConfiguration 20 }

gs2326pSTPBridgeBasicConf                                                 OBJECT IDENTIFIER ::= { gs2326pSTP 1 }

gs2326pSTPBridgeProtocolVersion OBJECT-TYPE
   SYNTAX      INTEGER { stp(0), rstp(2), mstp(3) }
   MAX-ACCESS  read-write
   STATUS      current
   DESCRIPTION
       "default: 3,
       0: stp
       2: rstp
       3: mstp"
   ::= { gs2326pSTPBridgeBasicConf 1 }

gs2326pSTPBridgePriority OBJECT-TYPE
   SYNTAX      Integer32(0..61440)
   MAX-ACCESS  read-write
   STATUS      current
   DESCRIPTION
       " default: 32768,
       STP bridge priority (0/4096/8192/12288/16384/20480/24576/28672/32768/36864/40960/45056/49152/53248/57344/61440)"
   ::= { gs2326pSTPBridgeBasicConf 2 }

gs2326pSTPBridgeForwardDelay OBJECT-TYPE
   SYNTAX      Integer32(4..30)
   MAX-ACCESS  read-write
   STATUS      current
   DESCRIPTION
       " Forward Delay default: 15, range: 4 - 30.
         MaxAge must be <= (FwdDelay-1)*2."
   ::= { gs2326pSTPBridgeBasicConf 3 }

gs2326pSTPBridgeMaxAge OBJECT-TYPE
   SYNTAX      Integer32(6..40)
   MAX-ACCESS  read-write
   STATUS      current
   DESCRIPTION
       " Max Age default: 20, range: 6 - 40.
         MaxAge must be <= (FwdDelay-1)*2"
   ::= { gs2326pSTPBridgeBasicConf 4 }

gs2326pSTPBridgeMaximumHopCount OBJECT-TYPE
   SYNTAX      Integer32(6..40)
   MAX-ACCESS  read-write
   STATUS      current
   DESCRIPTION
       " Maximum Hop Count default: 20, range: 6 - 40."
   ::= { gs2326pSTPBridgeBasicConf 5 }

gs2326pSTPBridgeTransmitHoldCount OBJECT-TYPE
   SYNTAX      Integer32(1..10)
   MAX-ACCESS  read-write
   STATUS      current
   DESCRIPTION
       " Transmit Hold Count default: 6, range: 1 - 10."
   ::= { gs2326pSTPBridgeBasicConf 6 }

gs2326pSTPBridgeAdvancedConf                                                 OBJECT IDENTIFIER ::= { gs2326pSTP 2 }

gs2326pSTPBridgeEdgePortBPDUFiltering OBJECT-TYPE
   SYNTAX      INTEGER { disable(0), enable(1) }
   MAX-ACCESS  read-write
   STATUS      current
   DESCRIPTION
       " default: 0,
        0: disable
        1: enable"
   ::= { gs2326pSTPBridgeAdvancedConf 1 }

gs2326pSTPBridgeEdgePortBPDUGuard OBJECT-TYPE
   SYNTAX      INTEGER { disable(0), enable(1) }
   MAX-ACCESS  read-write
   STATUS      current
   DESCRIPTION
       " default: 0,
        0: disable
        1: enable"
   ::= { gs2326pSTPBridgeAdvancedConf 2 }

gs2326pSTPBridgePortErrorRecoveryTimeout OBJECT-TYPE
   SYNTAX      Integer32(0..86400)
   MAX-ACCESS  read-write
   STATUS      current
   DESCRIPTION
       " Port Error Recovery Timeout disable: 0, range: 30 - 86400."
   ::= { gs2326pSTPBridgeAdvancedConf 3 }

gs2326pSTPMSTIConf                                                 OBJECT IDENTIFIER ::= { gs2326pSTP 3 }

gs2326pSTPMSTIConfigurationName OBJECT-TYPE
   SYNTAX      DisplayString (SIZE (1..32))
   MAX-ACCESS  read-write
   STATUS      current
   DESCRIPTION
       "A text string up to 32 characters long."
   ::= { gs2326pSTPMSTIConf 1 }

gs2326pSTPMSTIConfigurationRevision   OBJECT-TYPE
   SYNTAX      Integer32(0..65535)
   MAX-ACCESS  read-write
   STATUS      current
   DESCRIPTION
       " Configuration Revision default: 0, range: 0 - 65535."
   ::= { gs2326pSTPMSTIConf 2 }

gs2326pSTPMSTIMappingConf                                                 OBJECT IDENTIFIER ::= { gs2326pSTP 4 }

gs2326pSTPMSTI1VLANsMapped OBJECT-TYPE
   SYNTAX      DisplayString (SIZE (1..4096))
   MAX-ACCESS  read-write
   STATUS      current
   DESCRIPTION
       "The list of VLANs mapped to the MSTI1.
       The VLANs must be separated with comma or space.
       An unused MSTI should just be left empty. "
   ::= { gs2326pSTPMSTIMappingConf 1 }

gs2326pSTPMSTI2VLANsMapped OBJECT-TYPE
   SYNTAX      DisplayString (SIZE (1..4096))
   MAX-ACCESS  read-write
   STATUS      current
   DESCRIPTION
       "The list of VLANs mapped to the MSTI2.
       The VLANs must be separated with comma or space.
       An unused MSTI should just be left empty. "
   ::= { gs2326pSTPMSTIMappingConf 2 }

gs2326pSTPMSTI3VLANsMapped OBJECT-TYPE
   SYNTAX      DisplayString (SIZE (1..4096))
   MAX-ACCESS  read-write
   STATUS      current
   DESCRIPTION
       "The list of VLANs mapped to the MSTI3.
       The VLANs must be separated with comma or space.
       An unused MSTI should just be left empty. "
   ::= { gs2326pSTPMSTIMappingConf 3 }

gs2326pSTPMSTI4VLANsMapped OBJECT-TYPE
   SYNTAX      DisplayString (SIZE (1..4096))
   MAX-ACCESS  read-write
   STATUS      current
   DESCRIPTION
       "The list of VLANs mapped to the MSTI4.
       The VLANs must be separated with comma or space.
       An unused MSTI should just be left empty. "
   ::= { gs2326pSTPMSTIMappingConf 4 }

gs2326pSTPMSTI5VLANsMapped OBJECT-TYPE
   SYNTAX      DisplayString (SIZE (1..4096))
   MAX-ACCESS  read-write
   STATUS      current
   DESCRIPTION
       "The list of VLANs mapped to the MSTI5.
       The VLANs must be separated with comma or space.
       An unused MSTI should just be left empty. "
   ::= { gs2326pSTPMSTIMappingConf 5 }

gs2326pSTPMSTI6VLANsMapped OBJECT-TYPE
   SYNTAX      DisplayString (SIZE (1..4096))
   MAX-ACCESS  read-write
   STATUS      current
   DESCRIPTION
       "The list of VLANs mapped to the MSTI6.
       The VLANs must be separated with comma or space.
       An unused MSTI should just be left empty. "
   ::= { gs2326pSTPMSTIMappingConf 6 }

gs2326pSTPMSTI7VLANsMapped OBJECT-TYPE
   SYNTAX      DisplayString (SIZE (1..4096))
   MAX-ACCESS  read-write
   STATUS      current
   DESCRIPTION
       "The list of VLANs mapped to the MSTI7.
       The VLANs must be separated with comma or space.
       An unused MSTI should just be left empty. "
   ::= { gs2326pSTPMSTIMappingConf 7 }

gs2326pSTPMSTIPriority                                                 OBJECT IDENTIFIER ::= { gs2326pSTP 5 }

gs2326pSTPCISTPriority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 1 }

gs2326pSTPMSTI1Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 2 }

gs2326pSTPMSTI2Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 3 }

gs2326pSTPMSTI3Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 4 }

gs2326pSTPMSTI4Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 5 }

gs2326pSTPMSTI5Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 6 }

gs2326pSTPMSTI6Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 7 }

gs2326pSTPMSTI7Priority OBJECT-TYPE
   SYNTAX      Integer32(0..61440)
   MAX-ACCESS  read-write
   STATUS      current
   DESCRIPTION
       " default: 32768,
       STP CIST priority (0/4096/8192/12288/16384/20480/24576/28672/32768/36864/40960/45056/49152/53248/57344/61440)"
   ::= { gs2326pSTPMSTIPriority 8 }

gs2326pSTPCISTPort                                                          OBJECT IDENTIFIER ::= { gs2326pSTP 6 }

gs2326pSTPCISTAggregatedPort                                                OBJECT IDENTIFIER ::= { gs2326pSTPCISTPort 1 }

gs2326pSTPCISTAggregatedPortSTPEnabled OBJECT-TYPE
   SYNTAX      INTEGER { disable(0), enable(1) }
   MAX-ACCESS  read-write
   STATUS      current
   DESCRIPTION
       " default: 0,
        0: disable
        1: enable"
   ::= { gs2326pSTPCISTAggregatedPort 1 }

gs2326pSTPCISTAggregatedPortPathCost OBJECT-TYPE
   SYNTAX      Integer32(0..200000000)
   MAX-ACCESS  read-write
   STATUS      current
   DESCRIPTION
       " Auto: 0,
        Specific Path Cost range: 1 - 200000000."
   ::= { gs2326pSTPCISTAggregatedPort 2 }

gs2326pSTPCISTAggregatedPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326pSTPCISTAggregatedPort 3 }

gs2326pSTPCISTAggregatedPortAdminEdge OBJECT-TYPE
   SYNTAX      INTEGER { non-edge(0), edge(1) }
   MAX-ACCESS  read-write
   STATUS      current
   DESCRIPTION
       " default: 0,
        0: non-edge
        1: edge"
   ::= { gs2326pSTPCISTAggregatedPort 4 }

gs2326pSTPCISTAggregatedPortAutoEdge OBJECT-TYPE
   SYNTAX      INTEGER { disable(0), enable(1) }
   MAX-ACCESS  read-write
   STATUS      current
   DESCRIPTION
       " default: 1,
        0: disable
        1: enable"
   ::= { gs2326pSTPCISTAggregatedPort 5 }

gs2326pSTPCISTAggregatedPortRestrictedRole OBJECT-TYPE
   SYNTAX      INTEGER { disable(0), enable(1) }
   MAX-ACCESS  read-write
   STATUS      current
   DESCRIPTION
       " default: 0,
        0: disable
        1: enable"
   ::= { gs2326pSTPCISTAggregatedPort 6 }

gs2326pSTPCISTAggregatedPortRestrictedTCN OBJECT-TYPE
   SYNTAX      INTEGER { disable(0), enable(1) }
   MAX-ACCESS  read-write
   STATUS      current
   DESCRIPTION
       " default: 0,
        0: disable
        1: enable"
   ::= { gs2326pSTPCISTAggregatedPort 7 }

gs2326pSTPCISTAggregatedPortBPDUGuard OBJECT-TYPE
   SYNTAX      INTEGER { disable(0), enable(1) }
   MAX-ACCESS  read-write
   STATUS      current
   DESCRIPTION
       " default: 0,
        0: disable
        1: enable"
   ::= { gs2326pSTPCISTAggregatedPort 8 }

gs2326pSTPCISTAggregatedPortPointtoPoint OBJECT-TYPE
   SYNTAX      INTEGER { forcetrue(0), forcefalse(1), auto(2) }
   MAX-ACCESS  read-write
   STATUS      current
   DESCRIPTION
       " default: 0,
        0: Forced True
        1: Forced False
        2: Auto"
   ::= { gs2326pSTPCISTAggregatedPort 9 }

gs2326pSTPCISTNormalPortTable OBJECT-TYPE
   SYNTAX      SEQUENCE OF Gs2326pSTPCISTNormalPortEntry
   MAX-ACCESS  not-accessible
   STATUS      current
   DESCRIPTION
       " Show CIST Normal Port Configurations. "
   ::= { gs2326pSTPCISTPort 2 }

gs2326pSTPCISTNormalPortEntry OBJECT-TYPE
   SYNTAX      Gs2326pSTPCISTNormalPortEntry
   MAX-ACCESS  not-accessible
   STATUS      current
   DESCRIPTION
       ""
   INDEX    { gs2326pSTPCISTNormalPortConfPort  }
   ::= { gs2326pSTPCISTNormalPortTable 1 }

Gs2326pSTPCISTNormalPortEntry ::= SEQUENCE {
   gs2326pSTPCISTNormalPortConfPort         Integer32,
   gs2326pSTPCISTNormalPortSTPEnabled       INTEGER,
   gs2326pSTPCISTNormalPortPathCost         Integer32,
   gs2326pSTPCISTNormalPortPriority         Integer32,
   gs2326pSTPCISTNormalPortAdminEdge        INTEGER,
   gs2326pSTPCISTNormalPortAutoEdge         INTEGER,
   gs2326pSTPCISTNormalPortRestrictedRole   INTEGER,
   gs2326pSTPCISTNormalPortRestrictedTCN    INTEGER,
   gs2326pSTPCISTNormalPortBPDUGuard        INTEGER,
   gs2326pSTPCISTNormalPortPointtoPoint     INTEGER
}

gs2326pSTPCISTNormalPortConfPort OBJECT-TYPE
   SYNTAX      Integer32(1..4095)
   MAX-ACCESS  not-accessible
   STATUS      current
   DESCRIPTION
       " port, range : 1 - port number. "
   ::= { gs2326pSTPCISTNormalPortEntry 1 }

gs2326pSTPCISTNormalPortSTPEnabled OBJECT-TYPE
   SYNTAX      INTEGER { disable(0), enable(1) }
   MAX-ACCESS  read-write
   STATUS      current
   DESCRIPTION
       " default: 0,
        0: disable
        1: enable"
   ::= { gs2326pSTPCISTNormalPortEntry 2 }

gs2326pSTPCISTNormalPortPathCost OBJECT-TYPE
   SYNTAX      Integer32(0..200000000)
   MAX-ACCESS  read-write
   STATUS      current
   DESCRIPTION
       " Auto: 0,
        Specific Path Cost range: 1 - 200000000."
   ::= { gs2326pSTPCISTNormalPortEntry 3 }

gs2326pSTPCISTNormalPortPriority OBJECT-TYPE
   SYNTAX      Integer32(0..240)
   MAX-ACCESS  read-write
   STATUS      current
   DESCRIPTION
       " default: 128,
       CIST Aggregated Port Priority (0/16/32/48/64/80/96/112/128/144/160/176/192/208/224/240)"
   ::= { gs2326pSTPCISTNormalPortEntry 4 }

gs2326pSTPCISTNormalPortAdminEdge OBJECT-TYPE
   SYNTAX      INTEGER { non-edge(0), edge(1) }
   MAX-ACCESS  read-write
   STATUS      current
   DESCRIPTION
       " default: 0,
        0: non-edge
        1: edge"
   ::= { gs2326pSTPCISTNormalPortEntry 5 }

gs2326pSTPCISTNormalPortAutoEdge OBJECT-TYPE
   SYNTAX      INTEGER { disable(0), enable(1) }
   MAX-ACCESS  read-write
   STATUS      current
   DESCRIPTION
       " default: 1,
        0: disable
        1: enable"
   ::= { gs2326pSTPCISTNormalPortEntry 6 }

gs2326pSTPCISTNormalPortRestrictedRole OBJECT-TYPE
   SYNTAX      INTEGER { disable(0), enable(1) }
   MAX-ACCESS  read-write
   STATUS      current
   DESCRIPTION
       " default: 0,
        0: disable
        1: enable"
   ::= { gs2326pSTPCISTNormalPortEntry 7 }

gs2326pSTPCISTNormalPortRestrictedTCN OBJECT-TYPE
   SYNTAX      INTEGER { disable(0), enable(1) }
   MAX-ACCESS  read-write
   STATUS      current
   DESCRIPTION
       " default: 0,
        0: disable
        1: enable"
   ::= { gs2326pSTPCISTNormalPortEntry 8 }

gs2326pSTPCISTNormalPortBPDUGuard OBJECT-TYPE
   SYNTAX      INTEGER { disable(0), enable(1) }
   MAX-ACCESS  read-write
   STATUS      current
   DESCRIPTION
       " default: 0,
        0: disable
        1: enable"
   ::= { gs2326pSTPCISTNormalPortEntry 9 }

gs2326pSTPCISTNormalPortPointtoPoint OBJECT-TYPE
   SYNTAX      INTEGER { forcetrue(0), forcefalse(1), auto(2) }
   MAX-ACCESS  read-write
   STATUS      current
   DESCRIPTION
       " default: 2,
        0: Forced True
        1: Forced False
        2: Auto"
   ::= { gs2326pSTPCISTNormalPortEntry 10 }


gs2326pSTPMSTIPort                                                          OBJECT IDENTIFIER ::= { gs2326pSTP 7 }

gs2326pSTPMSTI1Port                                                         OBJECT IDENTIFIER ::= { gs2326pSTPMSTIPort 1 }

gs2326pSTPMSTI1AggregatedPort                                                OBJECT IDENTIFIER ::= { gs2326pSTPMSTI1Port 1 }

gs2326pSTPMSTI1AggregatedPortPathCost OBJECT-TYPE
   SYNTAX      Integer32(0..200000000)
   MAX-ACCESS  read-write
   STATUS      current
   DESCRIPTION
       " Auto: 0,
        Specific Path Cost range: 1 - 200000000."
   ::= { gs2326pSTPMSTI1AggregatedPort 1 }

gs2326pSTPMSTI1AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI1AggregatedPort 2 }

gs2326pSTPMSTI1NormalPortTable OBJECT-TYPE
   SYNTAX      SEQUENCE OF Gs2326pSTPMSTI1NormalPortEntry
   MAX-ACCESS  not-accessible
   STATUS      current
   DESCRIPTION
       " Show MSTI1 Normal Port Configurations. "
   ::= { gs2326pSTPMSTI1Port 2 }

gs2326pSTPMSTI1NormalPortEntry OBJECT-TYPE
   SYNTAX      Gs2326pSTPMSTI1NormalPortEntry
   MAX-ACCESS  not-accessible
   STATUS      current
   DESCRIPTION
       ""
   INDEX    { gs2326pSTPMSTI1NormalPortConfPort  }
   ::= { gs2326pSTPMSTI1NormalPortTable 1 }

Gs2326pSTPMSTI1NormalPortEntry ::= SEQUENCE {
   gs2326pSTPMSTI1NormalPortConfPort         Integer32,
   gs2326pSTPMSTI1NormalPortPathCost         Integer32,
   gs2326pSTPMSTI1NormalPortPriority         Integer32
}

gs2326pSTPMSTI1NormalPortConfPort OBJECT-TYPE
   SYNTAX      Integer32(1..4095)
   MAX-ACCESS  not-accessible
   STATUS      current
   DESCRIPTION
       " port, range : 1 - port number. "
   ::= { gs2326pSTPMSTI1NormalPortEntry 1 }

gs2326pSTPMSTI1NormalPortPathCost OBJECT-TYPE
   SYNTAX      Integer32(0..200000000)
   MAX-ACCESS  read-write
   STATUS      current
   DESCRIPTION
       " Auto: 0,
        Specific Path Cost range: 1 - 200000000."
   ::= { gs2326pSTPMSTI1NormalPortEntry 2 }

gs2326pSTPMSTI1NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI1NormalPortEntry 3 }

gs2326pSTPMSTI2Port                                                          OBJECT IDENTIFIER ::= { gs2326pSTPMSTIPort 2 }

gs2326pSTPMSTI2AggregatedPort                                                OBJECT IDENTIFIER ::= { gs2326pSTPMSTI2Port 1 }

gs2326pSTPMSTI2AggregatedPortPathCost OBJECT-TYPE
   SYNTAX      Integer32(0..200000000)
   MAX-ACCESS  read-write
   STATUS      current
   DESCRIPTION
       " Auto: 0,
        Specific Path Cost range: 1 - 200000000."
   ::= { gs2326pSTPMSTI2AggregatedPort 1 }

gs2326pSTPMSTI2AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI2AggregatedPort 2 }

gs2326pSTPMSTI2NormalPortTable OBJECT-TYPE
   SYNTAX      SEQUENCE OF Gs2326pSTPMSTI2NormalPortEntry
   MAX-ACCESS  not-accessible
   STATUS      current
   DESCRIPTION
       " Show MSTI2 Normal Port Configurations. "
   ::= { gs2326pSTPMSTI2Port 2 }

gs2326pSTPMSTI2NormalPortEntry OBJECT-TYPE
   SYNTAX      Gs2326pSTPMSTI2NormalPortEntry
   MAX-ACCESS  not-accessible
   STATUS      current
   DESCRIPTION
       ""
   INDEX    { gs2326pSTPMSTI2NormalPortConfPort  }
   ::= { gs2326pSTPMSTI2NormalPortTable 1 }

Gs2326pSTPMSTI2NormalPortEntry ::= SEQUENCE {
   gs2326pSTPMSTI2NormalPortConfPort         Integer32,
   gs2326pSTPMSTI2NormalPortPathCost         Integer32,
   gs2326pSTPMSTI2NormalPortPriority         Integer32
}

gs2326pSTPMSTI2NormalPortConfPort OBJECT-TYPE
   SYNTAX      Integer32(1..4095)
   MAX-ACCESS  not-accessible
   STATUS      current
   DESCRIPTION
       " port, range : 1 - port number. "
   ::= { gs2326pSTPMSTI2NormalPortEntry 1 }

gs2326pSTPMSTI2NormalPortPathCost OBJECT-TYPE
   SYNTAX      Integer32(0..200000000)
   MAX-ACCESS  read-write
   STATUS      current
   DESCRIPTION
       " Auto: 0,
        Specific Path Cost range: 1 - 200000000."
   ::= { gs2326pSTPMSTI2NormalPortEntry 2 }

gs2326pSTPMSTI2NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI2NormalPortEntry 3 }

gs2326pSTPMSTI3Port                                                          OBJECT IDENTIFIER ::= { gs2326pSTPMSTIPort 3 }

gs2326pSTPMSTI3AggregatedPort                                                OBJECT IDENTIFIER ::= { gs2326pSTPMSTI3Port 1 }

gs2326pSTPMSTI3AggregatedPortPathCost OBJECT-TYPE
   SYNTAX      Integer32(0..200000000)
   MAX-ACCESS  read-write
   STATUS      current
   DESCRIPTION
       " Auto: 0,
        Specific Path Cost range: 1 - 200000000."
   ::= { gs2326pSTPMSTI3AggregatedPort 1 }

gs2326pSTPMSTI3AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI3AggregatedPort 2 }

gs2326pSTPMSTI3NormalPortTable OBJECT-TYPE
   SYNTAX      SEQUENCE OF Gs2326pSTPMSTI3NormalPortEntry
   MAX-ACCESS  not-accessible
   STATUS      current
   DESCRIPTION
       " Show MSTI3 Normal Port Configurations. "
   ::= { gs2326pSTPMSTI3Port 2 }

gs2326pSTPMSTI3NormalPortEntry OBJECT-TYPE
   SYNTAX      Gs2326pSTPMSTI3NormalPortEntry
   MAX-ACCESS  not-accessible
   STATUS      current
   DESCRIPTION
       ""
   INDEX    { gs2326pSTPMSTI3NormalPortConfPort  }
   ::= { gs2326pSTPMSTI3NormalPortTable 1 }

Gs2326pSTPMSTI3NormalPortEntry ::= SEQUENCE {
   gs2326pSTPMSTI3NormalPortConfPort         Integer32,
   gs2326pSTPMSTI3NormalPortPathCost         Integer32,
   gs2326pSTPMSTI3NormalPortPriority         Integer32
}

gs2326pSTPMSTI3NormalPortConfPort OBJECT-TYPE
   SYNTAX      Integer32(1..4095)
   MAX-ACCESS  not-accessible
   STATUS      current
   DESCRIPTION
       " port, range : 1 - port number. "
   ::= { gs2326pSTPMSTI3NormalPortEntry 1 }

gs2326pSTPMSTI3NormalPortPathCost OBJECT-TYPE
   SYNTAX      Integer32(0..200000000)
   MAX-ACCESS  read-write
   STATUS      current
   DESCRIPTION
       " Auto: 0,
        Specific Path Cost range: 1 - 200000000."
   ::= { gs2326pSTPMSTI3NormalPortEntry 2 }

gs2326pSTPMSTI3NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI3NormalPortEntry 3 }

gs2326pSTPMSTI4Port                                                          OBJECT IDENTIFIER ::= { gs2326pSTPMSTIPort 4 }

gs2326pSTPMSTI4AggregatedPort                                                OBJECT IDENTIFIER ::= { gs2326pSTPMSTI4Port 1 }

gs2326pSTPMSTI4AggregatedPortPathCost OBJECT-TYPE
   SYNTAX      Integer32(0..200000000)
   MAX-ACCESS  read-write
   STATUS      current
   DESCRIPTION
       " Auto: 0,
        Specific Path Cost range: 1 - 200000000."
   ::= { gs2326pSTPMSTI4AggregatedPort 1 }

gs2326pSTPMSTI4AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI4AggregatedPort 2 }

gs2326pSTPMSTI4NormalPortTable OBJECT-TYPE
   SYNTAX      SEQUENCE OF Gs2326pSTPMSTI4NormalPortEntry
   MAX-ACCESS  not-accessible
   STATUS      current
   DESCRIPTION
       " Show MSTI4 Normal Port Configurations. "
   ::= { gs2326pSTPMSTI4Port 2 }

gs2326pSTPMSTI4NormalPortEntry OBJECT-TYPE
   SYNTAX      Gs2326pSTPMSTI4NormalPortEntry
   MAX-ACCESS  not-accessible
   STATUS      current
   DESCRIPTION
       ""
   INDEX    { gs2326pSTPMSTI4NormalPortConfPort  }
   ::= { gs2326pSTPMSTI4NormalPortTable 1 }

Gs2326pSTPMSTI4NormalPortEntry ::= SEQUENCE {
   gs2326pSTPMSTI4NormalPortConfPort         Integer32,
   gs2326pSTPMSTI4NormalPortPathCost         Integer32,
   gs2326pSTPMSTI4NormalPortPriority         Integer32
}

gs2326pSTPMSTI4NormalPortConfPort OBJECT-TYPE
   SYNTAX      Integer32(1..4095)
   MAX-ACCESS  not-accessible
   STATUS      current
   DESCRIPTION
       " port, range : 1 - port number. "
   ::= { gs2326pSTPMSTI4NormalPortEntry 1 }

gs2326pSTPMSTI4NormalPortPathCost OBJECT-TYPE
   SYNTAX      Integer32(0..200000000)
   MAX-ACCESS  read-write
   STATUS      current
   DESCRIPTION
       " Auto: 0,
        Specific Path Cost range: 1 - 200000000."
   ::= { gs2326pSTPMSTI4NormalPortEntry 2 }

gs2326pSTPMSTI4NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI4NormalPortEntry 3 }

gs2326pSTPMSTI5Port                                                          OBJECT IDENTIFIER ::= { gs2326pSTPMSTIPort 5 }

gs2326pSTPMSTI5AggregatedPort                                                OBJECT IDENTIFIER ::= { gs2326pSTPMSTI5Port 1 }

gs2326pSTPMSTI5AggregatedPortPathCost OBJECT-TYPE
   SYNTAX      Integer32(0..200000000)
   MAX-ACCESS  read-write
   STATUS      current
   DESCRIPTION
       " Auto: 0,
        Specific Path Cost range: 1 - 200000000."
   ::= { gs2326pSTPMSTI5AggregatedPort 1 }

gs2326pSTPMSTI5AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI5AggregatedPort 2 }

gs2326pSTPMSTI5NormalPortTable OBJECT-TYPE
   SYNTAX      SEQUENCE OF Gs2326pSTPMSTI5NormalPortEntry
   MAX-ACCESS  not-accessible
   STATUS      current
   DESCRIPTION
       " Show MSTI5 Normal Port Configurations. "
   ::= { gs2326pSTPMSTI5Port 2 }

gs2326pSTPMSTI5NormalPortEntry OBJECT-TYPE
   SYNTAX      Gs2326pSTPMSTI5NormalPortEntry
   MAX-ACCESS  not-accessible
   STATUS      current
   DESCRIPTION
       ""
   INDEX    { gs2326pSTPMSTI5NormalPortConfPort  }
   ::= { gs2326pSTPMSTI5NormalPortTable 1 }

Gs2326pSTPMSTI5NormalPortEntry ::= SEQUENCE {
   gs2326pSTPMSTI5NormalPortConfPort         Integer32,
   gs2326pSTPMSTI5NormalPortPathCost         Integer32,
   gs2326pSTPMSTI5NormalPortPriority         Integer32
}

gs2326pSTPMSTI5NormalPortConfPort OBJECT-TYPE
   SYNTAX      Integer32(1..4095)
   MAX-ACCESS  not-accessible
   STATUS      current
   DESCRIPTION
       " port, range : 1 - port number. "
   ::= { gs2326pSTPMSTI5NormalPortEntry 1 }

gs2326pSTPMSTI5NormalPortPathCost OBJECT-TYPE
   SYNTAX      Integer32(0..200000000)
   MAX-ACCESS  read-write
   STATUS      current
   DESCRIPTION
       " Auto: 0,
        Specific Path Cost range: 1 - 200000000."
   ::= { gs2326pSTPMSTI5NormalPortEntry 2 }

gs2326pSTPMSTI5NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI5NormalPortEntry 3 }

gs2326pSTPMSTI6Port                                                          OBJECT IDENTIFIER ::= { gs2326pSTPMSTIPort 6 }

gs2326pSTPMSTI6AggregatedPort                                                OBJECT IDENTIFIER ::= { gs2326pSTPMSTI6Port 1 }

gs2326pSTPMSTI6AggregatedPortPathCost OBJECT-TYPE
   SYNTAX      Integer32(0..200000000)
   MAX-ACCESS  read-write
   STATUS      current
   DESCRIPTION
       " Auto: 0,
        Specific Path Cost range: 1 - 200000000."
   ::= { gs2326pSTPMSTI6AggregatedPort 1 }

gs2326pSTPMSTI6AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI6AggregatedPort 2 }

gs2326pSTPMSTI6NormalPortTable OBJECT-TYPE
   SYNTAX      SEQUENCE OF Gs2326pSTPMSTI6NormalPortEntry
   MAX-ACCESS  not-accessible
   STATUS      current
   DESCRIPTION
       " Show MSTI6 Normal Port Configurations. "
   ::= { gs2326pSTPMSTI6Port 2 }

gs2326pSTPMSTI6NormalPortEntry OBJECT-TYPE
   SYNTAX      Gs2326pSTPMSTI6NormalPortEntry
   MAX-ACCESS  not-accessible
   STATUS      current
   DESCRIPTION
       ""
   INDEX    { gs2326pSTPMSTI6NormalPortConfPort  }
   ::= { gs2326pSTPMSTI6NormalPortTable 1 }

Gs2326pSTPMSTI6NormalPortEntry ::= SEQUENCE {
   gs2326pSTPMSTI6NormalPortConfPort         Integer32,
   gs2326pSTPMSTI6NormalPortPathCost         Integer32,
   gs2326pSTPMSTI6NormalPortPriority         Integer32
}

gs2326pSTPMSTI6NormalPortConfPort OBJECT-TYPE
   SYNTAX      Integer32(1..4095)
   MAX-ACCESS  not-accessible
   STATUS      current
   DESCRIPTION
       " port, range : 1 - port number. "
   ::= { gs2326pSTPMSTI6NormalPortEntry 1 }

gs2326pSTPMSTI6NormalPortPathCost OBJECT-TYPE
   SYNTAX      Integer32(0..200000000)
   MAX-ACCESS  read-write
   STATUS      current
   DESCRIPTION
       " Auto: 0,
        Specific Path Cost range: 1 - 200000000."
   ::= { gs2326pSTPMSTI6NormalPortEntry 2 }

gs2326pSTPMSTI6NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI6NormalPortEntry 3 }

gs2326pSTPMSTI7Port                                                          OBJECT IDENTIFIER ::= { gs2326pSTPMSTIPort 7 }

gs2326pSTPMSTI7AggregatedPort                                                OBJECT IDENTIFIER ::= { gs2326pSTPMSTI7Port 1 }

gs2326pSTPMSTI7AggregatedPortPathCost OBJECT-TYPE
   SYNTAX      Integer32(0..200000000)
   MAX-ACCESS  read-write
   STATUS      current
   DESCRIPTION
       " Auto: 0,
        Specific Path Cost range: 1 - 200000000."
   ::= { gs2326pSTPMSTI7AggregatedPort 1 }

gs2326pSTPMSTI7AggregatedPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI7AggregatedPort 2 }

gs2326pSTPMSTI7NormalPortTable OBJECT-TYPE
   SYNTAX      SEQUENCE OF Gs2326pSTPMSTI7NormalPortEntry
   MAX-ACCESS  not-accessible
   STATUS      current
   DESCRIPTION
       " Show MSTI7 Normal Port Configurations. "
   ::= { gs2326pSTPMSTI7Port 2 }

gs2326pSTPMSTI7NormalPortEntry OBJECT-TYPE
   SYNTAX      Gs2326pSTPMSTI7NormalPortEntry
   MAX-ACCESS  not-accessible
   STATUS      current
   DESCRIPTION
       ""
   INDEX    { gs2326pSTPMSTI7NormalPortConfPort  }
   ::= { gs2326pSTPMSTI7NormalPortTable 1 }

Gs2326pSTPMSTI7NormalPortEntry ::= SEQUENCE {
   gs2326pSTPMSTI7NormalPortConfPort         Integer32,
   gs2326pSTPMSTI7NormalPortPathCost         Integer32,
   gs2326pSTPMSTI7NormalPortPriority         Integer32
}

gs2326pSTPMSTI7NormalPortConfPort OBJECT-TYPE
   SYNTAX      Integer32(1..4095)
   MAX-ACCESS  not-accessible
   STATUS      current
   DESCRIPTION
       " port, range : 1 - port number. "
   ::= { gs2326pSTPMSTI7NormalPortEntry 1 }

gs2326pSTPMSTI7NormalPortPathCost OBJECT-TYPE
   SYNTAX      Integer32(0..200000000)
   MAX-ACCESS  read-write
   STATUS      current
   DESCRIPTION
       " Auto: 0,
        Specific Path Cost range: 1 - 200000000."
   ::= { gs2326pSTPMSTI7NormalPortEntry 2 }

gs2326pSTPMSTI7NormalPortPriority OBJECT-TYPE
   SYNTAX      Integer32(0..240)
   MAX-ACCESS  read-write
   STATUS      current
   DESCRIPTION
       " default: 128,
       Aggregated Port Priority (0/16/32/48/64/80/96/112/128/144/160/176/192/208/224/240)"
   ::= { gs2326pSTPMSTI7NormalPortEntry 3 }


gs2326pSTPBridgeStatus                                                      OBJECT IDENTIFIER ::= { gs2326pSTP 8 }

gs2326pCISTBridgeSTP                                                        OBJECT IDENTIFIER ::= { gs2326pSTPBridgeStatus 1 }

gs2326pCISTBridgeSTPStatus                                                  OBJECT IDENTIFIER ::= { gs2326pCISTBridgeSTP 1 }

gs2326pCISTBridgeInstance OBJECT-TYPE
   SYNTAX       DisplayString
   MAX-ACCESS   read-only
   STATUS       current
   DESCRIPTION
       "The Bridge instance - CIST, MST1, ..."
   ::= { gs2326pCISTBridgeSTPStatus 1 }

gs2326pCISTBridgeID OBJECT-TYPE
   SYNTAX       DisplayString
   MAX-ACCESS   read-only
   STATUS       current
   DESCRIPTION
       "The Bridge ID of this Bridge instance."
   ::= { gs2326pCISTBridgeSTPStatus 2 }

gs2326pCISTRootID OBJECT-TYPE
   SYNTAX       DisplayString
   MAX-ACCESS   read-only
   STATUS       current
   DESCRIPTION
       "The Bridge ID of the currently elected root bridge."
   ::= { gs2326pCISTBridgeSTPStatus 3 }

gs2326pCISTRootPort OBJECT-TYPE
   SYNTAX       DisplayString
   MAX-ACCESS   read-only
   STATUS       current
   DESCRIPTION
       "The switch port currently assigned the root port role."
   ::= { gs2326pCISTBridgeSTPStatus 4 }

gs2326pCISTRootCost OBJECT-TYPE
   SYNTAX       Integer32(0..200000000)
   MAX-ACCESS   read-only
   STATUS       current
   DESCRIPTION
       "Root Path Cost."
   ::= { gs2326pCISTBridgeSTPStatus 5 }

gs2326pCISTRegionalRoot OBJECT-TYPE
   SYNTAX       DisplayString
   MAX-ACCESS   read-only
   STATUS       current
   DESCRIPTION
       "The Bridge ID of the currently elected regional root bridge, inside the MSTP region of this bridge."
   ::= { gs2326pCISTBridgeSTPStatus 6 }

gs2326pCISTInternalRootCost OBJECT-TYPE
   SYNTAX       Integer32(0..200000000)
   MAX-ACCESS   read-only
   STATUS       current
   DESCRIPTION
       "The Regional Root Path Cost."
   ::= { gs2326pCISTBridgeSTPStatus 7 }

gs2326pCISTTopologyFlag OBJECT-TYPE
   SYNTAX       DisplayString
   MAX-ACCESS   read-only
   STATUS       current
   DESCRIPTION
       "The current state of the Topology Change Flag of this Bridge instance."
   ::= { gs2326pCISTBridgeSTPStatus 8 }

gs2326pCISTTopologyChangeCount OBJECT-TYPE
   SYNTAX       Counter32
   MAX-ACCESS   read-only
   STATUS       current
   DESCRIPTION
       "The number of times where the topology change flag has been set."
   ::= { gs2326pCISTBridgeSTPStatus 9 }

gs2326pCISTTopologyChangeLast OBJECT-TYPE
   SYNTAX       DisplayString
   MAX-ACCESS   read-only
   STATUS       current
   DESCRIPTION
       "The time passed since the Topology Flag was last set."
   ::= { gs2326pCISTBridgeSTPStatus 10 }

gs2326pCISTPortStateTable OBJECT-TYPE
   SYNTAX      SEQUENCE OF Gs2326pCISTPortStateEntry
   MAX-ACCESS  not-accessible
   STATUS      current
   DESCRIPTION
       " Show CIST Ports and Aggregations State Configurations. "
   ::= { gs2326pCISTBridgeSTP 2 }

gs2326pCISTPortStateEntry OBJECT-TYPE
   SYNTAX      Gs2326pCISTPortStateEntry
   MAX-ACCESS  not-accessible
   STATUS      current
   DESCRIPTION
       ""
   INDEX    { gs2326pCISTPortStateIndex  }
   ::= { gs2326pCISTPortStateTable 1 }

Gs2326pCISTPortStateEntry ::= SEQUENCE {
   gs2326pCISTPortStateIndex        Integer32,
   gs2326pCISTPortStatePort         DisplayString,
   gs2326pCISTPortStatePortID       DisplayString,
   gs2326pCISTPortStateRole         DisplayString,
   gs2326pCISTPortStateState        DisplayString,
   gs2326pCISTPortStatePathCost     Integer32,
   gs2326pCISTPortStateEdge         DisplayString,
   gs2326pCISTPortStatePoint2Point  DisplayString,
   gs2326pCISTPortStateUptime       DisplayString
}

gs2326pCISTPortStateIndex OBJECT-TYPE
   SYNTAX      Integer32(1..4095)
   MAX-ACCESS  not-accessible
   STATUS      current
   DESCRIPTION
       "table index."
   ::= { gs2326pCISTPortStateEntry 1 }

gs2326pCISTPortStatePort OBJECT-TYPE
   SYNTAX      DisplayString
   MAX-ACCESS  read-only
   STATUS      current
   DESCRIPTION
       "The switch port number of the logical STP port."
   ::= { gs2326pCISTPortStateEntry 2 }

gs2326pCISTPortStatePortID OBJECT-TYPE
   SYNTAX      DisplayString
   MAX-ACCESS  read-only
   STATUS      current
   DESCRIPTION
       "The port id as used by the STP protocol.
        This is the priority part and the logical port index of the bridge port."
   ::= { gs2326pCISTPortStateEntry 3 }

gs2326pCISTPortStateRole OBJECT-TYPE
   SYNTAX      DisplayString
   MAX-ACCESS  read-only
   STATUS      current
   DESCRIPTION
       "The current STP port role."
   ::= { gs2326pCISTPortStateEntry 4 }

gs2326pCISTPortStateState OBJECT-TYPE
   SYNTAX      DisplayString
   MAX-ACCESS  read-only
   STATUS      current
   DESCRIPTION
       "The current STP port state."
   ::= { gs2326pCISTPortStateEntry 5 }

gs2326pCISTPortStatePathCost OBJECT-TYPE
   SYNTAX      Integer32(0..200000000)
   MAX-ACCESS  read-only
   STATUS      current
   DESCRIPTION
       "The current STP port path cost."
   ::= { gs2326pCISTPortStateEntry 6 }

gs2326pCISTPortStateEdge OBJECT-TYPE
   SYNTAX      DisplayString
   MAX-ACCESS  read-only
   STATUS      current
   DESCRIPTION
       "The current STP port Edge Flag."
   ::= { gs2326pCISTPortStateEntry 7 }

gs2326pCISTPortStatePoint2Point OBJECT-TYPE
   SYNTAX      DisplayString
   MAX-ACCESS  read-only
   STATUS      current
   DESCRIPTION
       "The current STP port point-to-point flag."
   ::= { gs2326pCISTPortStateEntry 8 }

gs2326pCISTPortStateUptime OBJECT-TYPE
   SYNTAX      DisplayString
   MAX-ACCESS  read-only
   STATUS      current
   DESCRIPTION
       "The time since the bridge port was last initialized."
   ::= { gs2326pCISTPortStateEntry 9 }

gs2326pMSTI1BridgeSTP                                                        OBJECT IDENTIFIER ::= { gs2326pSTPBridgeStatus 2 }

gs2326pMSTI1BridgeSTPStatus                                                  OBJECT IDENTIFIER ::= { gs2326pMSTI1BridgeSTP 1 }

gs2326pMSTI1BridgeInstance OBJECT-TYPE
   SYNTAX       DisplayString
   MAX-ACCESS   read-only
   STATUS       current
   DESCRIPTION
       "The Bridge instance - CIST, MST1, ..."
   ::= { gs2326pMSTI1BridgeSTPStatus 1 }

gs2326pMSTI1BridgeID OBJECT-TYPE
   SYNTAX       DisplayString
   MAX-ACCESS   read-only
   STATUS       current
   DESCRIPTION
       "The Bridge ID of this Bridge instance."
   ::= { gs2326pMSTI1BridgeSTPStatus 2 }

gs2326pMSTI1RootID OBJECT-TYPE
   SYNTAX       DisplayString
   MAX-ACCESS   read-only
   STATUS       current
   DESCRIPTION
       "The Bridge ID of the currently elected root bridge."
   ::= { gs2326pMSTI1BridgeSTPStatus 3 }

gs2326pMSTI1RootPort OBJECT-TYPE
   SYNTAX       DisplayString
   MAX-ACCESS   read-only
   STATUS       current
   DESCRIPTION
       "The switch port currently assigned the root port role."
   ::= { gs2326pMSTI1BridgeSTPStatus 4 }

gs2326pMSTI1RootCost OBJECT-TYPE
   SYNTAX       Integer32(0..200000000)
   MAX-ACCESS   read-only
   STATUS       current
   DESCRIPTION
       "Root Path Cost."
   ::= { gs2326pMSTI1BridgeSTPStatus 5 }

gs2326pMSTI1TopologyFlag OBJECT-TYPE
   SYNTAX       DisplayString
   MAX-ACCESS   read-only
   STATUS       current
   DESCRIPTION
       "The current state of the Topology Change Flag of this Bridge instance."
   ::= { gs2326pMSTI1BridgeSTPStatus 8 }

gs2326pMSTI1TopologyChangeCount OBJECT-TYPE
   SYNTAX       Counter32
   MAX-ACCESS   read-only
   STATUS       current
   DESCRIPTION
       "The number of times where the topology change flag has been set."
   ::= { gs2326pMSTI1BridgeSTPStatus 9 }

gs2326pMSTI1TopologyChangeLast OBJECT-TYPE
   SYNTAX       DisplayString
   MAX-ACCESS   read-only
   STATUS       current
   DESCRIPTION
       "The time passed since the Topology Flag was last set."
   ::= { gs2326pMSTI1BridgeSTPStatus 10 }

gs2326pMSTI1PortStateTable OBJECT-TYPE
   SYNTAX      SEQUENCE OF Gs2326pMSTI1PortStateEntry
   MAX-ACCESS  not-accessible
   STATUS      current
   DESCRIPTION
       " Show MSTI1 Ports and Aggregations State Configurations. "
   ::= { gs2326pMSTI1BridgeSTP 2 }

gs2326pMSTI1PortStateEntry OBJECT-TYPE
   SYNTAX      Gs2326pMSTI1PortStateEntry
   MAX-ACCESS  not-accessible
   STATUS      current
   DESCRIPTION
       ""
   INDEX    { gs2326pMSTI1PortStateIndex  }
   ::= { gs2326pMSTI1PortStateTable 1 }

Gs2326pMSTI1PortStateEntry ::= SEQUENCE {
   gs2326pMSTI1PortStateIndex        Integer32,
   gs2326pMSTI1PortStatePort         DisplayString,
   gs2326pMSTI1PortStatePortID       DisplayString,
   gs2326pMSTI1PortStateRole         DisplayString,
   gs2326pMSTI1PortStateState        DisplayString,
   gs2326pMSTI1PortStatePathCost     Integer32,
   gs2326pMSTI1PortStateEdge         DisplayString,
   gs2326pMSTI1PortStatePoint2Point  DisplayString,
   gs2326pMSTI1PortStateUptime       DisplayString
}

gs2326pMSTI1PortStateIndex OBJECT-TYPE
   SYNTAX      Integer32(1..4095)
   MAX-ACCESS  not-accessible
   STATUS      current
   DESCRIPTION
       "table index."
   ::= { gs2326pMSTI1PortStateEntry 1 }

gs2326pMSTI1PortStatePort OBJECT-TYPE
   SYNTAX      DisplayString
   MAX-ACCESS  read-only
   STATUS      current
   DESCRIPTION
       "The switch port number of the logical STP port."
   ::= { gs2326pMSTI1PortStateEntry 2 }

gs2326pMSTI1PortStatePortID OBJECT-TYPE
   SYNTAX      DisplayString
   MAX-ACCESS  read-only
   STATUS      current
   DESCRIPTION
       "The port id as used by the STP protocol.
        This is the priority part and the logical port index of the bridge port."
   ::= { gs2326pMSTI1PortStateEntry 3 }

gs2326pMSTI1PortStateRole OBJECT-TYPE
   SYNTAX      DisplayString
   MAX-ACCESS  read-only
   STATUS      current
   DESCRIPTION
       "The current STP port role."
   ::= { gs2326pMSTI1PortStateEntry 4 }

gs2326pMSTI1PortStateState OBJECT-TYPE
   SYNTAX      DisplayString
   MAX-ACCESS  read-only
   STATUS      current
   DESCRIPTION
       "The current STP port state."
   ::= { gs2326pMSTI1PortStateEntry 5 }

gs2326pMSTI1PortStatePathCost OBJECT-TYPE
   SYNTAX      Integer32(0..200000000)
   MAX-ACCESS  read-only
   STATUS      current
   DESCRIPTION
       "The current STP port path cost."
   ::= { gs2326pMSTI1PortStateEntry 6 }

gs2326pMSTI1PortStateEdge OBJECT-TYPE
   SYNTAX      DisplayString
   MAX-ACCESS  read-only
   STATUS      current
   DESCRIPTION
       "The current STP port Edge Flag."
   ::= { gs2326pMSTI1PortStateEntry 7 }

gs2326pMSTI1PortStatePoint2Point OBJECT-TYPE
   SYNTAX      DisplayString
   MAX-ACCESS  read-only
   STATUS      current
   DESCRIPTION
       "The current STP port point-to-point flag."
   ::= { gs2326pMSTI1PortStateEntry 8 }

gs2326pMSTI1PortStateUptime OBJECT-TYPE
   SYNTAX      DisplayString
   MAX-ACCESS  read-only
   STATUS      current
   DESCRIPTION
       "The time since the bridge port was last initialized."
   ::= { gs2326pMSTI1PortStateEntry 9 }

gs2326pMSTI2BridgeSTP                                                        OBJECT IDENTIFIER ::= { gs2326pSTPBridgeStatus 3 }

gs2326pMSTI2BridgeSTPStatus                                                  OBJECT IDENTIFIER ::= { gs2326pMSTI2BridgeSTP 1 }

gs2326pMSTI2BridgeInstance OBJECT-TYPE
   SYNTAX       DisplayString
   MAX-ACCESS   read-only
   STATUS       current
   DESCRIPTION
       "The Bridge instance - CIST, MST1, ..."
   ::= { gs2326pMSTI2BridgeSTPStatus 1 }

gs2326pMSTI2BridgeID OBJECT-TYPE
   SYNTAX       DisplayString
   MAX-ACCESS   read-only
   STATUS       current
   DESCRIPTION
       "The Bridge ID of this Bridge instance."
   ::= { gs2326pMSTI2BridgeSTPStatus 2 }

gs2326pMSTI2RootID OBJECT-TYPE
   SYNTAX       DisplayString
   MAX-ACCESS   read-only
   STATUS       current
   DESCRIPTION
       "The Bridge ID of the currently elected root bridge."
   ::= { gs2326pMSTI2BridgeSTPStatus 3 }

gs2326pMSTI2RootPort OBJECT-TYPE
   SYNTAX       DisplayString
   MAX-ACCESS   read-only
   STATUS       current
   DESCRIPTION
       "The switch port currently assigned the root port role."
   ::= { gs2326pMSTI2BridgeSTPStatus 4 }

gs2326pMSTI2RootCost OBJECT-TYPE
   SYNTAX       Integer32(0..200000000)
   MAX-ACCESS   read-only
   STATUS       current
   DESCRIPTION
       "Root Path Cost."
   ::= { gs2326pMSTI2BridgeSTPStatus 5 }

gs2326pMSTI2TopologyFlag OBJECT-TYPE
   SYNTAX       DisplayString
   MAX-ACCESS   read-only
   STATUS       current
   DESCRIPTION
       "The current state of the Topology Change Flag of this Bridge instance."
   ::= { gs2326pMSTI2BridgeSTPStatus 8 }

gs2326pMSTI2TopologyChangeCount OBJECT-TYPE
   SYNTAX       Counter32
   MAX-ACCESS   read-only
   STATUS       current
   DESCRIPTION
       "The number of times where the topology change flag has been set."
   ::= { gs2326pMSTI2BridgeSTPStatus 9 }

gs2326pMSTI2TopologyChangeLast OBJECT-TYPE
   SYNTAX       DisplayString
   MAX-ACCESS   read-only
   STATUS       current
   DESCRIPTION
       "The time passed since the Topology Flag was last set."
   ::= { gs2326pMSTI2BridgeSTPStatus 10 }

gs2326pMSTI2PortStateTable OBJECT-TYPE
   SYNTAX      SEQUENCE OF Gs2326pMSTI2PortStateEntry
   MAX-ACCESS  not-accessible
   STATUS      current
   DESCRIPTION
       " Show MSTI2 Ports and Aggregations State Configurations. "
   ::= { gs2326pMSTI2BridgeSTP 2 }

gs2326pMSTI2PortStateEntry OBJECT-TYPE
   SYNTAX      Gs2326pMSTI2PortStateEntry
   MAX-ACCESS  not-accessible
   STATUS      current
   DESCRIPTION
       ""
   INDEX    { gs2326pMSTI2PortStateIndex  }
   ::= { gs2326pMSTI2PortStateTable 1 }

Gs2326pMSTI2PortStateEntry ::= SEQUENCE {
   gs2326pMSTI2PortStateIndex        Integer32,
   gs2326pMSTI2PortStatePort         DisplayString,
   gs2326pMSTI2PortStatePortID       DisplayString,
   gs2326pMSTI2PortStateRole         DisplayString,
   gs2326pMSTI2PortStateState        DisplayString,
   gs2326pMSTI2PortStatePathCost     Integer32,
   gs2326pMSTI2PortStateEdge         DisplayString,
   gs2326pMSTI2PortStatePoint2Point  DisplayString,
   gs2326pMSTI2PortStateUptime       DisplayString
}

gs2326pMSTI2PortStateIndex OBJECT-TYPE
   SYNTAX      Integer32(1..4095)
   MAX-ACCESS  not-accessible
   STATUS      current
   DESCRIPTION
       "table index."
   ::= { gs2326pMSTI2PortStateEntry 1 }

gs2326pMSTI2PortStatePort OBJECT-TYPE
   SYNTAX      DisplayString
   MAX-ACCESS  read-only
   STATUS      current
   DESCRIPTION
       "The switch port number of the logical STP port."
   ::= { gs2326pMSTI2PortStateEntry 2 }

gs2326pMSTI2PortStatePortID OBJECT-TYPE
   SYNTAX      DisplayString
   MAX-ACCESS  read-only
   STATUS      current
   DESCRIPTION
       "The port id as used by the STP protocol.
        This is the priority part and the logical port index of the bridge port."
   ::= { gs2326pMSTI2PortStateEntry 3 }

gs2326pMSTI2PortStateRole OBJECT-TYPE
   SYNTAX      DisplayString
   MAX-ACCESS  read-only
   STATUS      current
   DESCRIPTION
       "The current STP port role."
   ::= { gs2326pMSTI2PortStateEntry 4 }

gs2326pMSTI2PortStateState OBJECT-TYPE
   SYNTAX      DisplayString
   MAX-ACCESS  read-only
   STATUS      current
   DESCRIPTION
       "The current STP port state."
   ::= { gs2326pMSTI2PortStateEntry 5 }

gs2326pMSTI2PortStatePathCost OBJECT-TYPE
   SYNTAX      Integer32(0..200000000)
   MAX-ACCESS  read-only
   STATUS      current
   DESCRIPTION
       "The current STP port path cost."
   ::= { gs2326pMSTI2PortStateEntry 6 }

gs2326pMSTI2PortStateEdge OBJECT-TYPE
   SYNTAX      DisplayString
   MAX-ACCESS  read-only
   STATUS      current
   DESCRIPTION
       "The current STP port Edge Flag."
   ::= { gs2326pMSTI2PortStateEntry 7 }

gs2326pMSTI2PortStatePoint2Point OBJECT-TYPE
   SYNTAX      DisplayString
   MAX-ACCESS  read-only
   STATUS      current
   DESCRIPTION
       "The current STP port point-to-point flag."
   ::= { gs2326pMSTI2PortStateEntry 8 }

gs2326pMSTI2PortStateUptime OBJECT-TYPE
   SYNTAX      DisplayString
   MAX-ACCESS  read-only
   STATUS      current
   DESCRIPTION
       "The time since the bridge port was last initialized."
   ::= { gs2326pMSTI2PortStateEntry 9 }

gs2326pMSTI3BridgeSTP                                                        OBJECT IDENTIFIER ::= { gs2326pSTPBridgeStatus 4 }

gs2326pMSTI3BridgeSTPStatus                                                  OBJECT IDENTIFIER ::= { gs2326pMSTI3BridgeSTP 1 }

gs2326pMSTI3BridgeInstance OBJECT-TYPE
   SYNTAX       DisplayString
   MAX-ACCESS   read-only
   STATUS       current
   DESCRIPTION
       "The Bridge instance - CIST, MST1, ..."
   ::= { gs2326pMSTI3BridgeSTPStatus 1 }

gs2326pMSTI3BridgeID OBJECT-TYPE
   SYNTAX       DisplayString
   MAX-ACCESS   read-only
   STATUS       current
   DESCRIPTION
       "The Bridge ID of this Bridge instance."
   ::= { gs2326pMSTI3BridgeSTPStatus 2 }

gs2326pMSTI3RootID OBJECT-TYPE
   SYNTAX       DisplayString
   MAX-ACCESS   read-only
   STATUS       current
   DESCRIPTION
       "The Bridge ID of the currently elected root bridge."
   ::= { gs2326pMSTI3BridgeSTPStatus 3 }

gs2326pMSTI3RootPort OBJECT-TYPE
   SYNTAX       DisplayString
   MAX-ACCESS   read-only
   STATUS       current
   DESCRIPTION
       "The switch port currently assigned the root port role."
   ::= { gs2326pMSTI3BridgeSTPStatus 4 }

gs2326pMSTI3RootCost OBJECT-TYPE
   SYNTAX       Integer32(0..200000000)
   MAX-ACCESS   read-only
   STATUS       current
   DESCRIPTION
       "Root Path Cost."
   ::= { gs2326pMSTI3BridgeSTPStatus 5 }

gs2326pMSTI3TopologyFlag OBJECT-TYPE
   SYNTAX       DisplayString
   MAX-ACCESS   read-only
   STATUS       current
   DESCRIPTION
       "The current state of the Topology Change Flag of this Bridge instance."
   ::= { gs2326pMSTI3BridgeSTPStatus 8 }

gs2326pMSTI3TopologyChangeCount OBJECT-TYPE
   SYNTAX       Counter32
   MAX-ACCESS   read-only
   STATUS       current
   DESCRIPTION
       "The number of times where the topology change flag has been set."
   ::= { gs2326pMSTI3BridgeSTPStatus 9 }

gs2326pMSTI3TopologyChangeLast OBJECT-TYPE
   SYNTAX       DisplayString
   MAX-ACCESS   read-only
   STATUS       current
   DESCRIPTION
       "The time passed since the Topology Flag was last set."
   ::= { gs2326pMSTI3BridgeSTPStatus 10 }

gs2326pMSTI3PortStateTable OBJECT-TYPE
   SYNTAX      SEQUENCE OF Gs2326pMSTI3PortStateEntry
   MAX-ACCESS  not-accessible
   STATUS      current
   DESCRIPTION
       " Show MSTI3 Ports and Aggregations State Configurations. "
   ::= { gs2326pMSTI3BridgeSTP 2 }

gs2326pMSTI3PortStateEntry OBJECT-TYPE
   SYNTAX      Gs2326pMSTI3PortStateEntry
   MAX-ACCESS  not-accessible
   STATUS      current
   DESCRIPTION
       ""
   INDEX    { gs2326pMSTI3PortStateIndex  }
   ::= { gs2326pMSTI3PortStateTable 1 }

Gs2326pMSTI3PortStateEntry ::= SEQUENCE {
   gs2326pMSTI3PortStateIndex        Integer32,
   gs2326pMSTI3PortStatePort         DisplayString,
   gs2326pMSTI3PortStatePortID       DisplayString,
   gs2326pMSTI3PortStateRole         DisplayString,
   gs2326pMSTI3PortStateState        DisplayString,
   gs2326pMSTI3PortStatePathCost     Integer32,
   gs2326pMSTI3PortStateEdge         DisplayString,
   gs2326pMSTI3PortStatePoint2Point  DisplayString,
   gs2326pMSTI3PortStateUptime       DisplayString
}

gs2326pMSTI3PortStateIndex OBJECT-TYPE
   SYNTAX      Integer32(1..4095)
   MAX-ACCESS  not-accessible
   STATUS      current
   DESCRIPTION
       "table index."
   ::= { gs2326pMSTI3PortStateEntry 1 }

gs2326pMSTI3PortStatePort OBJECT-TYPE
   SYNTAX      DisplayString
   MAX-ACCESS  read-only
   STATUS      current
   DESCRIPTION
       "The switch port number of the logical STP port."
   ::= { gs2326pMSTI3PortStateEntry 2 }

gs2326pMSTI3PortStatePortID OBJECT-TYPE
   SYNTAX      DisplayString
   MAX-ACCESS  read-only
   STATUS      current
   DESCRIPTION
       "The port id as used by the STP protocol.
        This is the priority part and the logical port index of the bridge port."
   ::= { gs2326pMSTI3PortStateEntry 3 }

gs2326pMSTI3PortStateRole OBJECT-TYPE
   SYNTAX      DisplayString
   MAX-ACCESS  read-only
   STATUS      current
   DESCRIPTION
       "The current STP port role."
   ::= { gs2326pMSTI3PortStateEntry 4 }

gs2326pMSTI3PortStateState OBJECT-TYPE
   SYNTAX      DisplayString
   MAX-ACCESS  read-only
   STATUS      current
   DESCRIPTION
       "The current STP port state."
   ::= { gs2326pMSTI3PortStateEntry 5 }

gs2326pMSTI3PortStatePathCost OBJECT-TYPE
   SYNTAX      Integer32(0..200000000)
   MAX-ACCESS  read-only
   STATUS      current
   DESCRIPTION
       "The current STP port path cost."
   ::= { gs2326pMSTI3PortStateEntry 6 }

gs2326pMSTI3PortStateEdge OBJECT-TYPE
   SYNTAX      DisplayString
   MAX-ACCESS  read-only
   STATUS      current
   DESCRIPTION
       "The current STP port Edge Flag."
   ::= { gs2326pMSTI3PortStateEntry 7 }

gs2326pMSTI3PortStatePoint2Point OBJECT-TYPE
   SYNTAX      DisplayString
   MAX-ACCESS  read-only
   STATUS      current
   DESCRIPTION
       "The current STP port point-to-point flag."
   ::= { gs2326pMSTI3PortStateEntry 8 }

gs2326pMSTI3PortStateUptime OBJECT-TYPE
   SYNTAX      DisplayString
   MAX-ACCESS  read-only
   STATUS      current
   DESCRIPTION
       "The time since the bridge port was last initialized."
   ::= { gs2326pMSTI3PortStateEntry 9 }

gs2326pMSTI4BridgeSTP                                                        OBJECT IDENTIFIER ::= { gs2326pSTPBridgeStatus 5 }

gs2326pMSTI4BridgeSTPStatus                                                  OBJECT IDENTIFIER ::= { gs2326pMSTI4BridgeSTP 1 }

gs2326pMSTI4BridgeInstance OBJECT-TYPE
   SYNTAX       DisplayString
   MAX-ACCESS   read-only
   STATUS       current
   DESCRIPTION
       "The Bridge instance - CIST, MST1, ..."
   ::= { gs2326pMSTI4BridgeSTPStatus 1 }

gs2326pMSTI4BridgeID OBJECT-TYPE
   SYNTAX       DisplayString
   MAX-ACCESS   read-only
   STATUS       current
   DESCRIPTION
       "The Bridge ID of this Bridge instance."
   ::= { gs2326pMSTI4BridgeSTPStatus 2 }

gs2326pMSTI4RootID OBJECT-TYPE
   SYNTAX       DisplayString
   MAX-ACCESS   read-only
   STATUS       current
   DESCRIPTION
       "The Bridge ID of the currently elected root bridge."
   ::= { gs2326pMSTI4BridgeSTPStatus 3 }

gs2326pMSTI4RootPort OBJECT-TYPE
   SYNTAX       DisplayString
   MAX-ACCESS   read-only
   STATUS       current
   DESCRIPTION
       "The switch port currently assigned the root port role."
   ::= { gs2326pMSTI4BridgeSTPStatus 4 }

gs2326pMSTI4RootCost OBJECT-TYPE
   SYNTAX       Integer32(0..200000000)
   MAX-ACCESS   read-only
   STATUS       current
   DESCRIPTION
       "Root Path Cost."
   ::= { gs2326pMSTI4BridgeSTPStatus 5 }

gs2326pMSTI4TopologyFlag OBJECT-TYPE
   SYNTAX       DisplayString
   MAX-ACCESS   read-only
   STATUS       current
   DESCRIPTION
       "The current state of the Topology Change Flag of this Bridge instance."
   ::= { gs2326pMSTI4BridgeSTPStatus 8 }

gs2326pMSTI4TopologyChangeCount OBJECT-TYPE
   SYNTAX       Counter32
   MAX-ACCESS   read-only
   STATUS       current
   DESCRIPTION
       "The number of times where the topology change flag has been set."
   ::= { gs2326pMSTI4BridgeSTPStatus 9 }

gs2326pMSTI4TopologyChangeLast OBJECT-TYPE
   SYNTAX       DisplayString
   MAX-ACCESS   read-only
   STATUS       current
   DESCRIPTION
       "The time passed since the Topology Flag was last set."
   ::= { gs2326pMSTI4BridgeSTPStatus 10 }

gs2326pMSTI4PortStateTable OBJECT-TYPE
   SYNTAX      SEQUENCE OF Gs2326pMSTI4PortStateEntry
   MAX-ACCESS  not-accessible
   STATUS      current
   DESCRIPTION
       " Show MSTI4 Ports and Aggregations State Configurations. "
   ::= { gs2326pMSTI4BridgeSTP 2 }

gs2326pMSTI4PortStateEntry OBJECT-TYPE
   SYNTAX      Gs2326pMSTI4PortStateEntry
   MAX-ACCESS  not-accessible
   STATUS      current
   DESCRIPTION
       ""
   INDEX    { gs2326pMSTI4PortStateIndex  }
   ::= { gs2326pMSTI4PortStateTable 1 }

Gs2326pMSTI4PortStateEntry ::= SEQUENCE {
   gs2326pMSTI4PortStateIndex        Integer32,
   gs2326pMSTI4PortStatePort         DisplayString,
   gs2326pMSTI4PortStatePortID       DisplayString,
   gs2326pMSTI4PortStateRole         DisplayString,
   gs2326pMSTI4PortStateState        DisplayString,
   gs2326pMSTI4PortStatePathCost     Integer32,
   gs2326pMSTI4PortStateEdge         DisplayString,
   gs2326pMSTI4PortStatePoint2Point  DisplayString,
   gs2326pMSTI4PortStateUptime       DisplayString
}

gs2326pMSTI4PortStateIndex OBJECT-TYPE
   SYNTAX      Integer32(1..4095)
   MAX-ACCESS  not-accessible
   STATUS      current
   DESCRIPTION
       "table index."
   ::= { gs2326pMSTI4PortStateEntry 1 }

gs2326pMSTI4PortStatePort OBJECT-TYPE
   SYNTAX      DisplayString
   MAX-ACCESS  read-only
   STATUS      current
   DESCRIPTION
       "The switch port number of the logical STP port."
   ::= { gs2326pMSTI4PortStateEntry 2 }

gs2326pMSTI4PortStatePortID OBJECT-TYPE
   SYNTAX      DisplayString
   MAX-ACCESS  read-only
   STATUS      current
   DESCRIPTION
       "The port id as used by the STP protocol.
        This is the priority part and the logical port index of the bridge port."
   ::= { gs2326pMSTI4PortStateEntry 3 }

gs2326pMSTI4PortStateRole OBJECT-TYPE
   SYNTAX      DisplayString
   MAX-ACCESS  read-only
   STATUS      current
   DESCRIPTION
       "The current STP port role."
   ::= { gs2326pMSTI4PortStateEntry 4 }

gs2326pMSTI4PortStateState OBJECT-TYPE
   SYNTAX      DisplayString
   MAX-ACCESS  read-only
   STATUS      current
   DESCRIPTION
       "The current STP port state."
   ::= { gs2326pMSTI4PortStateEntry 5 }

gs2326pMSTI4PortStatePathCost OBJECT-TYPE
   SYNTAX      Integer32(0..200000000)
   MAX-ACCESS  read-only
   STATUS      current
   DESCRIPTION
       "The current STP port path cost."
   ::= { gs2326pMSTI4PortStateEntry 6 }

gs2326pMSTI4PortStateEdge OBJECT-TYPE
   SYNTAX      DisplayString
   MAX-ACCESS  read-only
   STATUS      current
   DESCRIPTION
       "The current STP port Edge Flag."
   ::= { gs2326pMSTI4PortStateEntry 7 }

gs2326pMSTI4PortStatePoint2Point OBJECT-TYPE
   SYNTAX      DisplayString
   MAX-ACCESS  read-only
   STATUS      current
   DESCRIPTION
       "The current STP port point-to-point flag."
   ::= { gs2326pMSTI4PortStateEntry 8 }

gs2326pMSTI4PortStateUptime OBJECT-TYPE
   SYNTAX      DisplayString
   MAX-ACCESS  read-only
   STATUS      current
   DESCRIPTION
       "The time since the bridge port was last initialized."
   ::= { gs2326pMSTI4PortStateEntry 9 }

gs2326pMSTI5BridgeSTP                                                        OBJECT IDENTIFIER ::= { gs2326pSTPBridgeStatus 6 }

gs2326pMSTI5BridgeSTPStatus                                                  OBJECT IDENTIFIER ::= { gs2326pMSTI5BridgeSTP 1 }

gs2326pMSTI5BridgeInstance OBJECT-TYPE
   SYNTAX       DisplayString
   MAX-ACCESS   read-only
   STATUS       current
   DESCRIPTION
       "The Bridge instance - CIST, MST1, ..."
   ::= { gs2326pMSTI5BridgeSTPStatus 1 }

gs2326pMSTI5BridgeID OBJECT-TYPE
   SYNTAX       DisplayString
   MAX-ACCESS   read-only
   STATUS       current
   DESCRIPTION
       "The Bridge ID of this Bridge instance."
   ::= { gs2326pMSTI5BridgeSTPStatus 2 }

gs2326pMSTI5RootID OBJECT-TYPE
   SYNTAX       DisplayString
   MAX-ACCESS   read-only
   STATUS       current
   DESCRIPTION
       "The Bridge ID of the currently elected root bridge."
   ::= { gs2326pMSTI5BridgeSTPStatus 3 }

gs2326pMSTI5RootPort OBJECT-TYPE
   SYNTAX       DisplayString
   MAX-ACCESS   read-only
   STATUS       current
   DESCRIPTION
       "The switch port currently assigned the root port role."
   ::= { gs2326pMSTI5BridgeSTPStatus 4 }

gs2326pMSTI5RootCost OBJECT-TYPE
   SYNTAX       Integer32(0..200000000)
   MAX-ACCESS   read-only
   STATUS       current
   DESCRIPTION
       "Root Path Cost."
   ::= { gs2326pMSTI5BridgeSTPStatus 5 }

gs2326pMSTI5TopologyFlag OBJECT-TYPE
   SYNTAX       DisplayString
   MAX-ACCESS   read-only
   STATUS       current
   DESCRIPTION
       "The current state of the Topology Change Flag of this Bridge instance."
   ::= { gs2326pMSTI5BridgeSTPStatus 8 }

gs2326pMSTI5TopologyChangeCount OBJECT-TYPE
   SYNTAX       Counter32
   MAX-ACCESS   read-only
   STATUS       current
   DESCRIPTION
       "The number of times where the topology change flag has been set."
   ::= { gs2326pMSTI5BridgeSTPStatus 9 }

gs2326pMSTI5TopologyChangeLast OBJECT-TYPE
   SYNTAX       DisplayString
   MAX-ACCESS   read-only
   STATUS       current
   DESCRIPTION
       "The time passed since the Topology Flag was last set."
   ::= { gs2326pMSTI5BridgeSTPStatus 10 }

gs2326pMSTI5PortStateTable OBJECT-TYPE
   SYNTAX      SEQUENCE OF Gs2326pMSTI5PortStateEntry
   MAX-ACCESS  not-accessible
   STATUS      current
   DESCRIPTION
       " Show MSTI5 Ports and Aggregations State Configurations. "
   ::= { gs2326pMSTI5BridgeSTP 2 }

gs2326pMSTI5PortStateEntry OBJECT-TYPE
   SYNTAX      Gs2326pMSTI5PortStateEntry
   MAX-ACCESS  not-accessible
   STATUS      current
   DESCRIPTION
       ""
   INDEX    { gs2326pMSTI5PortStateIndex  }
   ::= { gs2326pMSTI5PortStateTable 1 }

Gs2326pMSTI5PortStateEntry ::= SEQUENCE {
   gs2326pMSTI5PortStateIndex        Integer32,
   gs2326pMSTI5PortStatePort         DisplayString,
   gs2326pMSTI5PortStatePortID       DisplayString,
   gs2326pMSTI5PortStateRole         DisplayString,
   gs2326pMSTI5PortStateState        DisplayString,
   gs2326pMSTI5PortStatePathCost     Integer32,
   gs2326pMSTI5PortStateEdge         DisplayString,
   gs2326pMSTI5PortStatePoint2Point  DisplayString,
   gs2326pMSTI5PortStateUptime       DisplayString
}

gs2326pMSTI5PortStateIndex OBJECT-TYPE
   SYNTAX      Integer32(1..4095)
   MAX-ACCESS  not-accessible
   STATUS      current
   DESCRIPTION
       "table index."
   ::= { gs2326pMSTI5PortStateEntry 1 }

gs2326pMSTI5PortStatePort OBJECT-TYPE
   SYNTAX      DisplayString
   MAX-ACCESS  read-only
   STATUS      current
   DESCRIPTION
       "The switch port number of the logical STP port."
   ::= { gs2326pMSTI5PortStateEntry 2 }

gs2326pMSTI5PortStatePortID OBJECT-TYPE
   SYNTAX      DisplayString
   MAX-ACCESS  read-only
   STATUS      current
   DESCRIPTION
       "The port id as used by the STP protocol.
        This is the priority part and the logical port index of the bridge port."
   ::= { gs2326pMSTI5PortStateEntry 3 }

gs2326pMSTI5PortStateRole OBJECT-TYPE
   SYNTAX      DisplayString
   MAX-ACCESS  read-only
   STATUS      current
   DESCRIPTION
       "The current STP port role."
   ::= { gs2326pMSTI5PortStateEntry 4 }

gs2326pMSTI5PortStateState OBJECT-TYPE
   SYNTAX      DisplayString
   MAX-ACCESS  read-only
   STATUS      current
   DESCRIPTION
       "The current STP port state."
   ::= { gs2326pMSTI5PortStateEntry 5 }

gs2326pMSTI5PortStatePathCost OBJECT-TYPE
   SYNTAX      Integer32(0..200000000)
   MAX-ACCESS  read-only
   STATUS      current
   DESCRIPTION
       "The current STP port path cost."
   ::= { gs2326pMSTI5PortStateEntry 6 }

gs2326pMSTI5PortStateEdge OBJECT-TYPE
   SYNTAX      DisplayString
   MAX-ACCESS  read-only
   STATUS      current
   DESCRIPTION
       "The current STP port Edge Flag."
   ::= { gs2326pMSTI5PortStateEntry 7 }

gs2326pMSTI5PortStatePoint2Point OBJECT-TYPE
   SYNTAX      DisplayString
   MAX-ACCESS  read-only
   STATUS      current
   DESCRIPTION
       "The current STP port point-to-point flag."
   ::= { gs2326pMSTI5PortStateEntry 8 }

gs2326pMSTI5PortStateUptime OBJECT-TYPE
   SYNTAX      DisplayString
   MAX-ACCESS  read-only
   STATUS      current
   DESCRIPTION
       "The time since the bridge port was last initialized."
   ::= { gs2326pMSTI5PortStateEntry 9 }

gs2326pMSTI6BridgeSTP                                                        OBJECT IDENTIFIER ::= { gs2326pSTPBridgeStatus 7 }

gs2326pMSTI6BridgeSTPStatus                                                  OBJECT IDENTIFIER ::= { gs2326pMSTI6BridgeSTP 1 }

gs2326pMSTI6BridgeInstance OBJECT-TYPE
   SYNTAX       DisplayString
   MAX-ACCESS   read-only
   STATUS       current
   DESCRIPTION
       "The Bridge instance - CIST, MST1, ..."
   ::= { gs2326pMSTI6BridgeSTPStatus 1 }

gs2326pMSTI6BridgeID OBJECT-TYPE
   SYNTAX       DisplayString
   MAX-ACCESS   read-only
   STATUS       current
   DESCRIPTION
       "The Bridge ID of this Bridge instance."
   ::= { gs2326pMSTI6BridgeSTPStatus 2 }

gs2326pMSTI6RootID OBJECT-TYPE
   SYNTAX       DisplayString
   MAX-ACCESS   read-only
   STATUS       current
   DESCRIPTION
       "The Bridge ID of the currently elected root bridge."
   ::= { gs2326pMSTI6BridgeSTPStatus 3 }

gs2326pMSTI6RootPort OBJECT-TYPE
   SYNTAX       DisplayString
   MAX-ACCESS   read-only
   STATUS       current
   DESCRIPTION
       "The switch port currently assigned the root port role."
   ::= { gs2326pMSTI6BridgeSTPStatus 4 }

gs2326pMSTI6RootCost OBJECT-TYPE
   SYNTAX       Integer32(0..200000000)
   MAX-ACCESS   read-only
   STATUS       current
   DESCRIPTION
       "Root Path Cost."
   ::= { gs2326pMSTI6BridgeSTPStatus 5 }

gs2326pMSTI6TopologyFlag OBJECT-TYPE
   SYNTAX       DisplayString
   MAX-ACCESS   read-only
   STATUS       current
   DESCRIPTION
       "The current state of the Topology Change Flag of this Bridge instance."
   ::= { gs2326pMSTI6BridgeSTPStatus 8 }

gs2326pMSTI6TopologyChangeCount OBJECT-TYPE
   SYNTAX       Counter32
   MAX-ACCESS   read-only
   STATUS       current
   DESCRIPTION
       "The number of times where the topology change flag has been set."
   ::= { gs2326pMSTI6BridgeSTPStatus 9 }

gs2326pMSTI6TopologyChangeLast OBJECT-TYPE
   SYNTAX       DisplayString
   MAX-ACCESS   read-only
   STATUS       current
   DESCRIPTION
       "The time passed since the Topology Flag was last set."
   ::= { gs2326pMSTI6BridgeSTPStatus 10 }

gs2326pMSTI6PortStateTable OBJECT-TYPE
   SYNTAX      SEQUENCE OF Gs2326pMSTI6PortStateEntry
   MAX-ACCESS  not-accessible
   STATUS      current
   DESCRIPTION
       " Show MSTI6 Ports and Aggregations State Configurations. "
   ::= { gs2326pMSTI6BridgeSTP 2 }

gs2326pMSTI6PortStateEntry OBJECT-TYPE
   SYNTAX      Gs2326pMSTI6PortStateEntry
   MAX-ACCESS  not-accessible
   STATUS      current
   DESCRIPTION
       ""
   INDEX    { gs2326pMSTI6PortStateIndex  }
   ::= { gs2326pMSTI6PortStateTable 1 }

Gs2326pMSTI6PortStateEntry ::= SEQUENCE {
   gs2326pMSTI6PortStateIndex        Integer32,
   gs2326pMSTI6PortStatePort         DisplayString,
   gs2326pMSTI6PortStatePortID       DisplayString,
   gs2326pMSTI6PortStateRole         DisplayString,
   gs2326pMSTI6PortStateState        DisplayString,
   gs2326pMSTI6PortStatePathCost     Integer32,
   gs2326pMSTI6PortStateEdge         DisplayString,
   gs2326pMSTI6PortStatePoint2Point  DisplayString,
   gs2326pMSTI6PortStateUptime       DisplayString
}

gs2326pMSTI6PortStateIndex OBJECT-TYPE
   SYNTAX      Integer32(1..4095)
   MAX-ACCESS  not-accessible
   STATUS      current
   DESCRIPTION
       "table index."
   ::= { gs2326pMSTI6PortStateEntry 1 }

gs2326pMSTI6PortStatePort OBJECT-TYPE
   SYNTAX      DisplayString
   MAX-ACCESS  read-only
   STATUS      current
   DESCRIPTION
       "The switch port number of the logical STP port."
   ::= { gs2326pMSTI6PortStateEntry 2 }

gs2326pMSTI6PortStatePortID OBJECT-TYPE
   SYNTAX      DisplayString
   MAX-ACCESS  read-only
   STATUS      current
   DESCRIPTION
       "The port id as used by the STP protocol.
        This is the priority part and the logical port index of the bridge port."
   ::= { gs2326pMSTI6PortStateEntry 3 }

gs2326pMSTI6PortStateRole OBJECT-TYPE
   SYNTAX      DisplayString
   MAX-ACCESS  read-only
   STATUS      current
   DESCRIPTION
       "The current STP port role."
   ::= { gs2326pMSTI6PortStateEntry 4 }

gs2326pMSTI6PortStateState OBJECT-TYPE
   SYNTAX      DisplayString
   MAX-ACCESS  read-only
   STATUS      current
   DESCRIPTION
       "The current STP port state."
   ::= { gs2326pMSTI6PortStateEntry 5 }

gs2326pMSTI6PortStatePathCost OBJECT-TYPE
   SYNTAX      Integer32(0..200000000)
   MAX-ACCESS  read-only
   STATUS      current
   DESCRIPTION
       "The current STP port path cost."
   ::= { gs2326pMSTI6PortStateEntry 6 }

gs2326pMSTI6PortStateEdge OBJECT-TYPE
   SYNTAX      DisplayString
   MAX-ACCESS  read-only
   STATUS      current
   DESCRIPTION
       "The current STP port Edge Flag."
   ::= { gs2326pMSTI6PortStateEntry 7 }

gs2326pMSTI6PortStatePoint2Point OBJECT-TYPE
   SYNTAX      DisplayString
   MAX-ACCESS  read-only
   STATUS      current
   DESCRIPTION
       "The current STP port point-to-point flag."
   ::= { gs2326pMSTI6PortStateEntry 8 }

gs2326pMSTI6PortStateUptime OBJECT-TYPE
   SYNTAX      DisplayString
   MAX-ACCESS  read-only
   STATUS      current
   DESCRIPTION
       "The time since the bridge port was last initialized."
   ::= { gs2326pMSTI6PortStateEntry 9 }

gs2326pMSTI7BridgeSTP                                                        OBJECT IDENTIFIER ::= { gs2326pSTPBridgeStatus 8 }

gs2326pMSTI7BridgeSTPStatus                                                  OBJECT IDENTIFIER ::= { gs2326pMSTI7BridgeSTP 1 }

gs2326pMSTI7BridgeInstance OBJECT-TYPE
   SYNTAX       DisplayString
   MAX-ACCESS   read-only
   STATUS       current
   DESCRIPTION
       "The Bridge instance - CIST, MST1, ..."
   ::= { gs2326pMSTI7BridgeSTPStatus 1 }

gs2326pMSTI7BridgeID OBJECT-TYPE
   SYNTAX       DisplayString
   MAX-ACCESS   read-only
   STATUS       current
   DESCRIPTION
       "The Bridge ID of this Bridge instance."
   ::= { gs2326pMSTI7BridgeSTPStatus 2 }

gs2326pMSTI7RootID OBJECT-TYPE
   SYNTAX       DisplayString
   MAX-ACCESS   read-only
   STATUS       current
   DESCRIPTION
       "The Bridge ID of the currently elected root bridge."
   ::= { gs2326pMSTI7BridgeSTPStatus 3 }

gs2326pMSTI7RootPort OBJECT-TYPE
   SYNTAX       DisplayString
   MAX-ACCESS   read-only
   STATUS       current
   DESCRIPTION
       "The switch port currently assigned the root port role."
   ::= { gs2326pMSTI7BridgeSTPStatus 4 }

gs2326pMSTI7RootCost OBJECT-TYPE
   SYNTAX       Integer32(0..200000000)
   MAX-ACCESS   read-only
   STATUS       current
   DESCRIPTION
       "Root Path Cost."
   ::= { gs2326pMSTI7BridgeSTPStatus 5 }

gs2326pMSTI7TopologyFlag OBJECT-TYPE
   SYNTAX       DisplayString
   MAX-ACCESS   read-only
   STATUS       current
   DESCRIPTION
       "The current state of the Topology Change Flag of this Bridge instance."
   ::= { gs2326pMSTI7BridgeSTPStatus 8 }

gs2326pMSTI7TopologyChangeCount OBJECT-TYPE
   SYNTAX       Counter32
   MAX-ACCESS   read-only
   STATUS       current
   DESCRIPTION
       "The number of times where the topology change flag has been set."
   ::= { gs2326pMSTI7BridgeSTPStatus 9 }

gs2326pMSTI7TopologyChangeLast OBJECT-TYPE
   SYNTAX       DisplayString
   MAX-ACCESS   read-only
   STATUS       current
   DESCRIPTION
       "The time passed since the Topology Flag was last set."
   ::= { gs2326pMSTI7BridgeSTPStatus 10 }

gs2326pMSTI7PortStateTable OBJECT-TYPE
   SYNTAX      SEQUENCE OF Gs2326pMSTI7PortStateEntry
   MAX-ACCESS  not-accessible
   STATUS      current
   DESCRIPTION
       " Show MSTI7 Ports and Aggregations State Configurations. "
   ::= { gs2326pMSTI7BridgeSTP 2 }

gs2326pMSTI7PortStateEntry OBJECT-TYPE
   SYNTAX      Gs2326pMSTI7PortStateEntry
   MAX-ACCESS  not-accessible
   STATUS      current
   DESCRIPTION
       ""
   INDEX    { gs2326pMSTI7PortStateIndex  }
   ::= { gs2326pMSTI7PortStateTable 1 }

Gs2326pMSTI7PortStateEntry ::= SEQUENCE {
   gs2326pMSTI7PortStateIndex        Integer32,
   gs2326pMSTI7PortStatePort         DisplayString,
   gs2326pMSTI7PortStatePortID       DisplayString,
   gs2326pMSTI7PortStateRole         DisplayString,
   gs2326pMSTI7PortStateState        DisplayString,
   gs2326pMSTI7PortStatePathCost     Integer32,
   gs2326pMSTI7PortStateEdge         DisplayString,
   gs2326pMSTI7PortStatePoint2Point  DisplayString,
   gs2326pMSTI7PortStateUptime       DisplayString
}

gs2326pMSTI7PortStateIndex OBJECT-TYPE
   SYNTAX      Integer32(1..4095)
   MAX-ACCESS  not-accessible
   STATUS      current
   DESCRIPTION
       "table index."
   ::= { gs2326pMSTI7PortStateEntry 1 }

gs2326pMSTI7PortStatePort OBJECT-TYPE
   SYNTAX      DisplayString
   MAX-ACCESS  read-only
   STATUS      current
   DESCRIPTION
       "The switch port number of the logical STP port."
   ::= { gs2326pMSTI7PortStateEntry 2 }

gs2326pMSTI7PortStatePortID OBJECT-TYPE
   SYNTAX      DisplayString
   MAX-ACCESS  read-only
   STATUS      current
   DESCRIPTION
       "The port id as used by the STP protocol.
        This is the priority part and the logical port index of the bridge port."
   ::= { gs2326pMSTI7PortStateEntry 3 }

gs2326pMSTI7PortStateRole OBJECT-TYPE
   SYNTAX      DisplayString
   MAX-ACCESS  read-only
   STATUS      current
   DESCRIPTION
       "The current STP port role."
   ::= { gs2326pMSTI7PortStateEntry 4 }

gs2326pMSTI7PortStateState OBJECT-TYPE
   SYNTAX      DisplayString
   MAX-ACCESS  read-only
   STATUS      current
   DESCRIPTION
       "The current STP port state."
   ::= { gs2326pMSTI7PortStateEntry 5 }

gs2326pMSTI7PortStatePathCost OBJECT-TYPE
   SYNTAX      Integer32(0..200000000)
   MAX-ACCESS  read-only
   STATUS      current
   DESCRIPTION
       "The current STP port path cost."
   ::= { gs2326pMSTI7PortStateEntry 6 }

gs2326pMSTI7PortStateEdge OBJECT-TYPE
   SYNTAX      DisplayString
   MAX-ACCESS  read-only
   STATUS      current
   DESCRIPTION
       "The current STP port Edge Flag."
   ::= { gs2326pMSTI7PortStateEntry 7 }

gs2326pMSTI7PortStatePoint2Point OBJECT-TYPE
   SYNTAX      DisplayString
   MAX-ACCESS  read-only
   STATUS      current
   DESCRIPTION
       "The current STP port point-to-point flag."
   ::= { gs2326pMSTI7PortStateEntry 8 }

gs2326pMSTI7PortStateUptime OBJECT-TYPE
   SYNTAX      DisplayString
   MAX-ACCESS  read-only
   STATUS      current
   DESCRIPTION
       "The time since the bridge port was last initialized."
   ::= { gs2326pMSTI7PortStateEntry 9 }

gs2326pSTPPortStatusTable OBJECT-TYPE
   SYNTAX      SEQUENCE OF Gs2326pSTPPortStatusEntry
   MAX-ACCESS  not-accessible
   STATUS      current
   DESCRIPTION
       " Show STP Port Status."
   ::= { gs2326pSTP 9 }

gs2326pSTPPortStatusEntry OBJECT-TYPE
   SYNTAX      Gs2326pSTPPortStatusEntry
   MAX-ACCESS  not-accessible
   STATUS      current
   DESCRIPTION
       ""
   INDEX    { gs2326pSTPPortStatusPort  }
   ::= { gs2326pSTPPortStatusTable 1 }

Gs2326pSTPPortStatusEntry ::= SEQUENCE {
   gs2326pSTPPortStatusPort         Integer32,
   gs2326pSTPPortStatusCISTRole     DisplayString,
   gs2326pSTPPortStatusCISTState    DisplayString,
   gs2326pSTPPortStatusUptime       DisplayString
}

gs2326pSTPPortStatusPort OBJECT-TYPE
   SYNTAX      Integer32(1..4095)
   MAX-ACCESS  not-accessible
   STATUS      current
   DESCRIPTION
       " port, range : 1 - port number. "
   ::= { gs2326pSTPPortStatusEntry 1 }

gs2326pSTPPortStatusCISTRole OBJECT-TYPE
   SYNTAX      DisplayString
   MAX-ACCESS  read-only
   STATUS      current
   DESCRIPTION
       " The current STP port role of the CIST port. "
   ::= { gs2326pSTPPortStatusEntry 2 }

gs2326pSTPPortStatusCISTState OBJECT-TYPE
   SYNTAX      DisplayString
   MAX-ACCESS  read-only
   STATUS      current
   DESCRIPTION
       " The current STP port state of the CIST port. "
   ::= { gs2326pSTPPortStatusEntry 3 }

gs2326pSTPPortStatusUptime OBJECT-TYPE
   SYNTAX      DisplayString
   MAX-ACCESS  read-only
   STATUS      current
   DESCRIPTION
       " The time since the bridge port was last initialized. "
   ::= { gs2326pSTPPortStatusEntry 4 }

gs2326pSTPPortStatisticsTable OBJECT-TYPE
   SYNTAX      SEQUENCE OF Gs2326pSTPPortStatisticsEntry
   MAX-ACCESS  not-accessible
   STATUS      current
   DESCRIPTION
       " Show STP Port Statistics."
   ::= { gs2326pSTP 10 }

gs2326pSTPPortStatisticsEntry OBJECT-TYPE
   SYNTAX      Gs2326pSTPPortStatisticsEntry
   MAX-ACCESS  not-accessible
   STATUS      current
   DESCRIPTION
       ""
   INDEX    { gs2326pSTPStatisticsIndex  }
   ::= { gs2326pSTPPortStatisticsTable 1 }

Gs2326pSTPPortStatisticsEntry ::= SEQUENCE {
   gs2326pSTPStatisticsIndex            Integer32,
   gs2326pSTPStatisticsPort             DisplayString,
   gs2326pSTPStatisticsTxMSTP           Counter32,
   gs2326pSTPStatisticsTxRSTP           Counter32,
   gs2326pSTPStatisticsTxSTP            Counter32,
   gs2326pSTPStatisticsTxTCN            Counter32,
   gs2326pSTPStatisticsRxMSTP           Counter32,
   gs2326pSTPStatisticsRxRSTP           Counter32,
   gs2326pSTPStatisticsRxSTP            Counter32,
   gs2326pSTPStatisticsRxTCN            Counter32,
   gs2326pSTPStatisticsDiscardedUnknown Counter32,
   gs2326pSTPStatisticsDiscardedIllegal Counter32
}

gs2326pSTPStatisticsIndex OBJECT-TYPE
   SYNTAX      Integer32(1..4095)
   MAX-ACCESS  not-accessible
   STATUS      current
   DESCRIPTION
       "table index."
   ::= { gs2326pSTPPortStatisticsEntry 1 }

gs2326pSTPStatisticsPort OBJECT-TYPE
   SYNTAX      DisplayString
   MAX-ACCESS  not-accessible
   STATUS      current
   DESCRIPTION
       " port, range : 1 - port number. "
   ::= { gs2326pSTPPortStatisticsEntry 2 }

gs2326pSTPStatisticsTxMSTP OBJECT-TYPE
   SYNTAX      Counter32
   MAX-ACCESS  read-only
   STATUS      current
   DESCRIPTION
       " The number of MSTP Configuration BPDU's received/transmitted on the port."
   ::= { gs2326pSTPPortStatisticsEntry 3 }

gs2326pSTPStatisticsTxRSTP OBJECT-TYPE
   SYNTAX      Counter32
   MAX-ACCESS  read-only
   STATUS      current
   DESCRIPTION
       " The number of RSTP Configuration BPDU's received/transmitted on the port. "
   ::= { gs2326pSTPPortStatisticsEntry 4 }

gs2326pSTPStatisticsTxSTP OBJECT-TYPE
   SYNTAX      Counter32
   MAX-ACCESS  read-only
   STATUS      current
   DESCRIPTION
       " The number of legacy STP Configuration BPDU's received/transmitted on the port. "
   ::= { gs2326pSTPPortStatisticsEntry 5 }

gs2326pSTPStatisticsTxTCN OBJECT-TYPE
   SYNTAX      Counter32
   MAX-ACCESS  read-only
   STATUS      current
   DESCRIPTION
       " The number of Topology Change Notification BPDU's received/transmitted on the port. "
   ::= { gs2326pSTPPortStatisticsEntry 6 }

gs2326pSTPStatisticsRxMSTP OBJECT-TYPE
   SYNTAX      Counter32
   MAX-ACCESS  read-only
   STATUS      current
   DESCRIPTION
       " The number of MSTP Configuration BPDU's received/transmitted on the port."
   ::= { gs2326pSTPPortStatisticsEntry 7 }

gs2326pSTPStatisticsRxRSTP OBJECT-TYPE
   SYNTAX      Counter32
   MAX-ACCESS  read-only
   STATUS      current
   DESCRIPTION
       " The number of RSTP Configuration BPDU's received/transmitted on the port. "
   ::= { gs2326pSTPPortStatisticsEntry 8 }

gs2326pSTPStatisticsRxSTP OBJECT-TYPE
   SYNTAX      Counter32
   MAX-ACCESS  read-only
   STATUS      current
   DESCRIPTION
       " The number of legacy STP Configuration BPDU's received/transmitted on the port. "
   ::= { gs2326pSTPPortStatisticsEntry 9 }

gs2326pSTPStatisticsRxTCN OBJECT-TYPE
   SYNTAX      Counter32
   MAX-ACCESS  read-only
   STATUS      current
   DESCRIPTION
       " The number of Topology Change Notification BPDU's received/transmitted on the port. "
   ::= { gs2326pSTPPortStatisticsEntry 10 }

gs2326pSTPStatisticsDiscardedUnknown OBJECT-TYPE
   SYNTAX      Counter32
   MAX-ACCESS  read-only
   STATUS      current
   DESCRIPTION
       " The number of unknown Spanning Tree BPDU's received and discarded on the port. "
   ::= { gs2326pSTPPortStatisticsEntry 11 }

gs2326pSTPStatisticsDiscardedIllegal OBJECT-TYPE
   SYNTAX      Counter32
   MAX-ACCESS  read-only
   STATUS      current
   DESCRIPTION
       " The number of illegal Spanning Tree BPDU's received and discarded on the port. "
   ::= { gs2326pSTPPortStatisticsEntry 12 }


gs2326pFilteringDataBase                                                  OBJECT IDENTIFIER ::= { gs2326pConfiguration 21 }

gs2326pFilteringDataBaseConfig                                            OBJECT IDENTIFIER ::= { gs2326pFilteringDataBase 1 }

gs2326pFilteringDataBaseAgingTime OBJECT-TYPE
   SYNTAX      Integer32(0..1000000)
   MAX-ACCESS  read-write
   STATUS      current
   DESCRIPTION
       "Configure aging time by entering a value here in seconds.
        default: 300,
        range: 10-1000000.
        Disable automatic aging : 0."
   ::= { gs2326pFilteringDataBaseConfig 1 }

gs2326pFilteringDataBaseConfigTable OBJECT-TYPE
   SYNTAX      SEQUENCE OF GS2326PFilteringDataBaseConfigEntry
   MAX-ACCESS  not-accessible
   STATUS      current
   DESCRIPTION
       " "
   ::= { gs2326pFilteringDataBaseConfig 2 }

gs2326pFilteringDataBaseConfigEntry OBJECT-TYPE
   SYNTAX      GS2326PFilteringDataBaseConfigEntry
   MAX-ACCESS  not-accessible
   STATUS      current
   DESCRIPTION
       ""
   INDEX    { gs2326pFilteringDataBaseConfigPort  }
   ::= { gs2326pFilteringDataBaseConfigTable 1 }

GS2326PFilteringDataBaseConfigEntry ::= SEQUENCE {
   gs2326pFilteringDataBaseConfigPort        Integer32,
   gs2326pFilteringDataBaseConfigLearning    INTEGER
}

gs2326pFilteringDataBaseConfigPort OBJECT-TYPE
   SYNTAX      Integer32(1..4095)
   MAX-ACCESS  not-accessible
   STATUS      current
   DESCRIPTION
       " "
   ::= { gs2326pFilteringDataBaseConfigEntry 1 }

gs2326pFilteringDataBaseConfigLearning OBJECT-TYPE
   SYNTAX      INTEGER { auto(0), disable(1), secure(2) }
   MAX-ACCESS  read-write
   STATUS      current
   DESCRIPTION
       "Configure learning mode of switch ports.
        default: 0,
        0: auto,
        1: disable,
        2: secure. "
   ::= { gs2326pFilteringDataBaseConfigEntry 2 }


gs2326pFilteringDataBaseStaticMAC                                OBJECT IDENTIFIER ::= { gs2326pFilteringDataBaseConfig 3 }

gs2326pFilteringDataBaseStaticMACCreate OBJECT-TYPE
   SYNTAX       INTEGER { none(0), create(1) }
   MAX-ACCESS   read-write
   STATUS       current
   DESCRIPTION
       "default: 0
        0 : None  (read only)
        1 : Create Static MAC Table"
   ::= { gs2326pFilteringDataBaseStaticMAC 1 }

gs2326pFilteringDataBaseStaticMACTable OBJECT-TYPE
   SYNTAX      SEQUENCE OF GS2326PFilteringDataBaseStaticMACEntry
   MAX-ACCESS  not-accessible
   STATUS      current
   DESCRIPTION
       " "
   ::= { gs2326pFilteringDataBaseStaticMAC 2 }

gs2326pFilteringDataBaseStaticMACEntry OBJECT-TYPE
   SYNTAX      GS2326PFilteringDataBaseStaticMACEntry
   MAX-ACCESS  not-accessible
   STATUS      current
   DESCRIPTION
       ""
   INDEX    { gs2326pFilteringDataBaseStaticMACIndex  }
   ::= { gs2326pFilteringDataBaseStaticMACTable 1 }

GS2326PFilteringDataBaseStaticMACEntry ::= SEQUENCE {
   gs2326pFilteringDataBaseStaticMACIndex	    Integer32,
   gs2326pFilteringDataBaseStaticMACVLANId	    Integer32,
   gs2326pFilteringDataBaseStaticMACAddress      MacAddress,
   gs2326pFilteringDataBaseStaticMACPortMembers  DisplayString,
   gs2326pFilteringDataBaseStaticMACRowStatus	INTEGER
}

gs2326pFilteringDataBaseStaticMACIndex OBJECT-TYPE
   SYNTAX      Integer32(1..4095)
   MAX-ACCESS  not-accessible
   STATUS      current
   DESCRIPTION
       " "
   ::= { gs2326pFilteringDataBaseStaticMACEntry 1 }

gs2326pFilteringDataBaseStaticMACVLANId OBJECT-TYPE
   SYNTAX      Integer32(1..4094)
   MAX-ACCESS  read-write
   STATUS      current
   DESCRIPTION
       " VLAN ID, range: 1 - 4094. "
   ::= { gs2326pFilteringDataBaseStaticMACEntry 2 }

gs2326pFilteringDataBaseStaticMACAddress OBJECT-TYPE
   SYNTAX      MacAddress
   MAX-ACCESS  read-write
   STATUS      current
   DESCRIPTION
       " MAC address, format 0a 1b 2c 3d 4e 5f "
   ::= { gs2326pFilteringDataBaseStaticMACEntry 3 }

gs2326pFilteringDataBaseStaticMACPortMembers OBJECT-TYPE
   SYNTAX      DisplayString
   MAX-ACCESS  read-write
   STATUS      current
   DESCRIPTION
       "To include the ports in a Static MAC Table"
   ::= { gs2326pFilteringDataBaseStaticMACEntry 4 }

gs2326pFilteringDataBaseStaticMACRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pFilteringDataBaseStaticMACEntry 5 }


gs2326pFilteringDataBaseDynamicMACTable OBJECT-TYPE
   SYNTAX      SEQUENCE OF GS2326PFilteringDataBaseDynamicMACEntry
   MAX-ACCESS  not-accessible
   STATUS      current
   DESCRIPTION
       " "
   ::= { gs2326pFilteringDataBaseConfig 4 }

gs2326pFilteringDataBaseDynamicMACEntry OBJECT-TYPE
   SYNTAX      GS2326PFilteringDataBaseDynamicMACEntry
   MAX-ACCESS  not-accessible
   STATUS      current
   DESCRIPTION
       ""
   INDEX    { gs2326pFilteringDataBaseDynamicMACIndex  }
   ::= { gs2326pFilteringDataBaseDynamicMACTable 1 }

GS2326PFilteringDataBaseDynamicMACEntry ::= SEQUENCE {
   gs2326pFilteringDataBaseDynamicMACIndex	    Integer32,
   gs2326pFilteringDataBaseDynamicMACType	    INTEGER,
   gs2326pFilteringDataBaseDynamicMACVLAN	    Integer32,
   gs2326pFilteringDataBaseDynamicMACAddress     MacAddress,
   gs2326pFilteringDataBaseDynamicPortMembers    DisplayString
}

gs2326pFilteringDataBaseDynamicMACIndex OBJECT-TYPE
   SYNTAX      Integer32(1..4095)
   MAX-ACCESS  not-accessible
   STATUS      current
   DESCRIPTION
       " "
   ::= { gs2326pFilteringDataBaseDynamicMACEntry 1 }

gs2326pFilteringDataBaseDynamicMACType OBJECT-TYPE
   SYNTAX      INTEGER { dynamic(0), static(1) }
   MAX-ACCESS  read-only
   STATUS      current
   DESCRIPTION
       "Indicates whether the entry is a static or a dynamic entry."
   ::= { gs2326pFilteringDataBaseDynamicMACEntry 2 }

gs2326pFilteringDataBaseDynamicMACVLAN OBJECT-TYPE
   SYNTAX      Integer32(1..4094)
   MAX-ACCESS  read-only
   STATUS      current
   DESCRIPTION
       "The VLAN ID of the entry."
   ::= { gs2326pFilteringDataBaseDynamicMACEntry 3 }

gs2326pFilteringDataBaseDynamicMACAddress OBJECT-TYPE
   SYNTAX      MacAddress
   MAX-ACCESS  read-only
   STATUS      current
   DESCRIPTION
       "The MAC address of the entry."
   ::= { gs2326pFilteringDataBaseDynamicMACEntry 4 }

gs2326pFilteringDataBaseDynamicPortMembers OBJECT-TYPE
   SYNTAX      DisplayString
   MAX-ACCESS  read-only
   STATUS      current
   DESCRIPTION
       "The ports that are members of the entry."
   ::= { gs2326pFilteringDataBaseDynamicMACEntry 5 }


gs2326pSFlowAgent                                                  OBJECT IDENTIFIER ::= { gs2326pConfiguration 22 }

gs2326pSFlowAgentCollector                                            OBJECT IDENTIFIER ::= { gs2326pSFlowAgent 1 }

gs2326pSFlowAgentReceiverMode OBJECT-TYPE
   SYNTAX      INTEGER { disable(0), enable(1) }
   MAX-ACCESS  read-write
   STATUS      current
   DESCRIPTION
       "default: 0
       0: disable
       1: enable "
   ::= { gs2326pSFlowAgentCollector 1 }


gs2326pLMC                                                   OBJECT IDENTIFIER ::= { gs2326pConfiguration 1500 }

gs2326pLMCOperating OBJECT-TYPE
   SYNTAX      INTEGER { disabled(0), enabled(1), try(2) }
   MAX-ACCESS  read-write
   STATUS      current
   DESCRIPTION
       "0: disabled
        1: enabled
        2: try"
   ::= { gs2326pLMC 1 }

gs2326pLMCConfigViaDhcp OBJECT-TYPE
   SYNTAX      INTEGER { disabled(0), enabled(1) }
   MAX-ACCESS  read-write
   STATUS      current
   DESCRIPTION
       "0: disabled
        1: enabled"
   ::= { gs2326pLMC 2 }

gs2326pLMCDomain OBJECT-TYPE
   SYNTAX      DisplayString(SIZE(0..255))
   MAX-ACCESS  read-write
   STATUS      current
   DESCRIPTION
       "0: disabled
        1: enabled"
   ::= { gs2326pLMC 3 }

gs2326pLMCDhcpClientAutoRenew OBJECT-TYPE
   SYNTAX      INTEGER { disabled(0), enabled(1) }
   MAX-ACCESS  read-write
   STATUS      current
   DESCRIPTION
       "0: disabled
        1: enabled"
   ::= { gs2326pLMC 4 }

gs2326pLMCZeroTouchSupport OBJECT-TYPE
   SYNTAX      INTEGER { No(0), Yes(1) }
   MAX-ACCESS  read-only
   STATUS      current
   DESCRIPTION
       "0: No
        1: Yes"
   ::= { gs2326pLMC 50 }

gs2326pLMCPairingTokenPresent OBJECT-TYPE
   SYNTAX      INTEGER { No(0), Yes(1) }
   MAX-ACCESS  read-only
   STATUS      current
   DESCRIPTION
       "0: No
        1: Yes"
   ::= { gs2326pLMC 51 }

gs2326pLMCClientStatus OBJECT-TYPE
   SYNTAX      DisplayString
   MAX-ACCESS  read-only
   STATUS      current
   DESCRIPTION
           ""
   ::= { gs2326pLMC  52 }


gs2326pLMCManagementStatus OBJECT-TYPE
   SYNTAX      INTEGER {Unpaired(0), Paired(1), PairedAndClaimed(14)}
   MAX-ACCESS  read-only
   STATUS      current
   DESCRIPTION
           "0: Unpaired
            1: Paired
            14: PairedAndClaimed"
   ::= { gs2326pLMC  53 }

gs2326pLMCControlStatus OBJECT-TYPE
   SYNTAX      INTEGER {Disabled(2), Operating(4)}
   MAX-ACCESS  read-only
   STATUS      current
   DESCRIPTION
           "2: Disabled
            4: Operating"
   ::= { gs2326pLMC  54 }

gs2326pLMCMonitoringStatus OBJECT-TYPE
   SYNTAX      INTEGER {Disabled(2), Operating(4)}
   MAX-ACCESS  read-only
   STATUS      current
   DESCRIPTION
           "2: Disabled
            4: Operating"
   ::= { gs2326pLMC  55 }

gs2326pLMCConfigurationSource OBJECT-TYPE
   SYNTAX      DisplayString
   MAX-ACCESS  read-only
   STATUS      current
   DESCRIPTION
           ""
   ::= { gs2326pLMC  56 }

gs2326pLMCConfigModified OBJECT-TYPE
   SYNTAX      INTEGER { No(0), Yes(1) }
   MAX-ACCESS  read-only
   STATUS      current
   DESCRIPTION
       "0: No
        1: Yes"
   ::= { gs2326pLMC 57 }

gs2326pLMCDeviceID OBJECT-TYPE
   SYNTAX      DisplayString
   MAX-ACCESS  read-only
   STATUS      current
   DESCRIPTION
           ""
   ::= { gs2326pLMC  58 }

gs2326pLMCRoundTripTime OBJECT-TYPE
   SYNTAX      INTEGER
   MAX-ACCESS  read-only
   STATUS      current
   DESCRIPTION
           ""
   ::= { gs2326pLMC  100 }
----------------------------------------------------------------------------------------------------------------------------
gs2326pSecurity                                              OBJECT IDENTIFIER ::= { lancomGS2326P  3 }

gs2326pIPSourceGuard                                         OBJECT IDENTIFIER ::= { gs2326pSecurity 1 }

gs2326pIPSourceGuardConf                                     OBJECT IDENTIFIER ::= { gs2326pIPSourceGuard 1 }

gs2326pIPSourceGuardMode OBJECT-TYPE
   SYNTAX      INTEGER { disable(0), enable(1) }
   MAX-ACCESS  read-write
   STATUS      current
   DESCRIPTION
       " default:  0
        0: disable
        1: enable"
   ::= { gs2326pIPSourceGuardConf 1 }

gs2326pIPSourceGuardPortConfigTable OBJECT-TYPE
   SYNTAX      SEQUENCE OF GS2326PIPSourceGuardPortConfigEntry
   MAX-ACCESS  not-accessible
   STATUS      current
   DESCRIPTION
       " "
   ::= { gs2326pIPSourceGuardConf 2 }

gs2326pIPSourceGuardPortConfigEntry OBJECT-TYPE
   SYNTAX      GS2326PIPSourceGuardPortConfigEntry
   MAX-ACCESS  not-accessible
   STATUS      current
   DESCRIPTION
       ""
   INDEX    { gs2326pIPSourceGuardPortConfigPort  }
   ::= { gs2326pIPSourceGuardPortConfigTable 1 }

GS2326PIPSourceGuardPortConfigEntry ::= SEQUENCE {
   gs2326pIPSourceGuardPortConfigPort               Integer32,
   gs2326pIPSourceGuardPortConfigMode               INTEGER,
   gs2326pIPSourceGuardPortMaxDynamicClients        Integer32
}

gs2326pIPSourceGuardPortConfigPort OBJECT-TYPE
   SYNTAX      Integer32(1..4095)
   MAX-ACCESS  not-accessible
   STATUS      current
   DESCRIPTION
       " "
   ::= { gs2326pIPSourceGuardPortConfigEntry 1 }

gs2326pIPSourceGuardPortConfigMode OBJECT-TYPE
   SYNTAX      INTEGER { disable(0), enable(1) }
   MAX-ACCESS  read-write
   STATUS      current
   DESCRIPTION
       "default: 0
       0:disable
       1:enable "
   ::= { gs2326pIPSourceGuardPortConfigEntry 2 }

gs2326pIPSourceGuardPortMaxDynamicClients OBJECT-TYPE
   SYNTAX      Integer32(0..2|99)
   MAX-ACCESS  read-write
   STATUS      current
   DESCRIPTION
       "default: 99
       0~2: Max Dynamic clients
       99:Unlimited "
   ::= { gs2326pIPSourceGuardPortConfigEntry 3 }


gs2326pIPSourceGuardStatic                                OBJECT IDENTIFIER ::= { gs2326pIPSourceGuard 2 }

gs2326pIPSourceGuardStaticCreate OBJECT-TYPE
   SYNTAX       INTEGER { none(0), create(1) }
   MAX-ACCESS   read-write
   STATUS       current
   DESCRIPTION
       "default: 0
        0 : None  (read only)
        1 : Create a IP Source Guard"
   ::= { gs2326pIPSourceGuardStatic 1 }

gs2326pIPSourceGuardStaticTable OBJECT-TYPE
   SYNTAX      SEQUENCE OF GS2326PIPSourceGuardStaticEntry
   MAX-ACCESS  not-accessible
   STATUS      current
   DESCRIPTION
       " "
   ::= { gs2326pIPSourceGuardStatic 2 }

gs2326pIPSourceGuardStaticEntry OBJECT-TYPE
   SYNTAX      GS2326PIPSourceGuardStaticEntry
   MAX-ACCESS  not-accessible
   STATUS      current
   DESCRIPTION
       ""
   INDEX    { gs2326pIPSourceGuardStaticIndex  }
   ::= { gs2326pIPSourceGuardStaticTable 1 }

GS2326PIPSourceGuardStaticEntry ::= SEQUENCE {
   gs2326pIPSourceGuardStaticIndex         Integer32,
   gs2326pIPSourceGuardStaticPort          Integer32,
   gs2326pIPSourceGuardStaticVLANId        Integer32,
   gs2326pIPSourceGuardStaticIPAddress     IpAddress,
   gs2326pIPSourceGuardStaticMACAddress    MacAddress,
   gs2326pIPSourceGuardStaticRowStatus     INTEGER
}

gs2326pIPSourceGuardStaticIndex OBJECT-TYPE
   SYNTAX      Integer32(1..28)
   MAX-ACCESS  not-accessible
   STATUS      current
   DESCRIPTION
       " "
   ::= { gs2326pIPSourceGuardStaticEntry 1 }

gs2326pIPSourceGuardStaticPort OBJECT-TYPE
   SYNTAX      Integer32(1..4095)
   MAX-ACCESS  read-write
   STATUS      current
   DESCRIPTION
       " Port, range: 1 - port number. "
   ::= { gs2326pIPSourceGuardStaticEntry 2 }

gs2326pIPSourceGuardStaticVLANId OBJECT-TYPE
   SYNTAX      Integer32(1..4094)
   MAX-ACCESS  read-write
   STATUS      current
   DESCRIPTION
       " VLAN ID, range: 1 - 4094. "
   ::= { gs2326pIPSourceGuardStaticEntry 3 }

gs2326pIPSourceGuardStaticIPAddress OBJECT-TYPE
   SYNTAX      IpAddress
   MAX-ACCESS  read-write
   STATUS      current
   DESCRIPTION
       " IP address allowed for doing IP source guard. "
   ::= { gs2326pIPSourceGuardStaticEntry 4 }

gs2326pIPSourceGuardStaticMACAddress OBJECT-TYPE
   SYNTAX      MacAddress
   MAX-ACCESS  read-write
   STATUS      current
   DESCRIPTION
       " Allowed Source MAC address, format 0a 1b 2c 3d 4e 5f "
   ::= { gs2326pIPSourceGuardStaticEntry 5 }

gs2326pIPSourceGuardStaticRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326pIPSourceGuardStaticEntry 6 }

gs2326pIPSourceGuardDynamicTable OBJECT-TYPE
   SYNTAX      SEQUENCE OF GS2326PIPSourceGuardDynamicEntry
   MAX-ACCESS  not-accessible
   STATUS      current
   DESCRIPTION
       " "
   ::= { gs2326pIPSourceGuard 3 }

gs2326pIPSourceGuardDynamicEntry OBJECT-TYPE
   SYNTAX      GS2326PIPSourceGuardDynamicEntry
   MAX-ACCESS  not-accessible
   STATUS      current
   DESCRIPTION
       ""
   INDEX    { gs2326pIPSourceGuardDynamicIndex  }
   ::= { gs2326pIPSourceGuardDynamicTable 1 }

GS2326PIPSourceGuardDynamicEntry ::= SEQUENCE {
   gs2326pIPSourceGuardDynamicIndex          Integer32,
   gs2326pIPSourceGuardDynamicPort           Integer32,
   gs2326pIPSourceGuardDynamicVLANId         Integer32,
   gs2326pIPSourceGuardDynamicIPAddress      IpAddress,
   gs2326pIPSourceGuardDynamicMACAddress     MacAddress
}

gs2326pIPSourceGuardDynamicIndex OBJECT-TYPE
   SYNTAX      Integer32(1..4095)
   MAX-ACCESS  not-accessible
   STATUS      current
   DESCRIPTION
       " "
   ::= { gs2326pIPSourceGuardDynamicEntry 1 }

gs2326pIPSourceGuardDynamicPort OBJECT-TYPE
   SYNTAX      Integer32(1..10)
   MAX-ACCESS  read-only
   STATUS      current
   DESCRIPTION
       " "
   ::= { gs2326pIPSourceGuardDynamicEntry 2 }

gs2326pIPSourceGuardDynamicVLANId OBJECT-TYPE
   SYNTAX      Integer32(1..4094)
   MAX-ACCESS  read-only
   STATUS      current
   DESCRIPTION
       " "
   ::= { gs2326pIPSourceGuardDynamicEntry 3 }

gs2326pIPSourceGuardDynamicIPAddress OBJECT-TYPE
   SYNTAX      IpAddress
   MAX-ACCESS  read-only
   STATUS      current
   DESCRIPTION
       " "
   ::= { gs2326pIPSourceGuardDynamicEntry 4 }

gs2326pIPSourceGuardDynamicMACAddress OBJECT-TYPE
   SYNTAX      MacAddress
   MAX-ACCESS  read-only
   STATUS      current
   DESCRIPTION
       " "
   ::= { gs2326pIPSourceGuardDynamicEntry 5 }

gs2326pARPInspection                                         OBJECT IDENTIFIER ::= { gs2326pSecurity 2 }

gs2326pARPInspectionConf                                     OBJECT IDENTIFIER ::= { gs2326pARPInspection 1 }

gs2326pARPInspectionConfMode OBJECT-TYPE
   SYNTAX      INTEGER { disable(0), enable(1) }
   MAX-ACCESS  read-write
   STATUS      current
   DESCRIPTION
       "default: 0
        0: disable
        1: enable"
   ::= { gs2326pARPInspectionConf 1 }

gs2326pARPInspectionConfTable OBJECT-TYPE
   SYNTAX      SEQUENCE OF GS2326PARPInspectionConfEntry
   MAX-ACCESS  not-accessible
   STATUS      current
   DESCRIPTION
       " "
   ::= { gs2326pARPInspectionConf 2 }

gs2326pARPInspectionConfEntry OBJECT-TYPE
   SYNTAX      GS2326PARPInspectionConfEntry
   MAX-ACCESS  not-accessible
   STATUS      current
   DESCRIPTION
       ""
   INDEX    { gs2326pARPInspectionConfPortIndex  }
   ::= { gs2326pARPInspectionConfTable 1 }

GS2326PARPInspectionConfEntry ::= SEQUENCE {
   gs2326pARPInspectionConfPortIndex	Integer32,
   gs2326pARPInspectionConfPortMode	INTEGER
}

gs2326pARPInspectionConfPortIndex OBJECT-TYPE
   SYNTAX      Integer32(1..4095)
   MAX-ACCESS  not-accessible
   STATUS      current
   DESCRIPTION
       " "
   ::= { gs2326pARPInspectionConfEntry 1 }

gs2326pARPInspectionConfPortMode OBJECT-TYPE
   SYNTAX      INTEGER { disable(0), enable(1) }
   MAX-ACCESS  read-write
   STATUS      current
   DESCRIPTION
       "default: 0
        0: disable
        1: enable"
   ::= { gs2326pARPInspectionConfEntry 2 }


gs2326pARPInspectionStatic                                OBJECT IDENTIFIER ::= { gs2326pARPInspection 2 }

gs2326pARPInspectionStaticCreate OBJECT-TYPE
   SYNTAX      INTEGER { none(0), create(1) }
   MAX-ACCESS  read-write
   STATUS      current
   DESCRIPTION
       "default: 0
        0: none
        1: create"
   ::= { gs2326pARPInspectionStatic 1 }

gs2326pARPInspectionStaticTable OBJECT-TYPE
   SYNTAX      SEQUENCE OF GS2326PARPInspectionStaticEntry
   MAX-ACCESS  not-accessible
   STATUS      current
   DESCRIPTION
       " "
   ::= { gs2326pARPInspectionStatic 2 }

gs2326pARPInspectionStaticEntry OBJECT-TYPE
   SYNTAX      GS2326PARPInspectionStaticEntry
   MAX-ACCESS  not-accessible
   STATUS      current
   DESCRIPTION
       ""
   INDEX    { gs2326pARPInspectionStaticIndex  }
   ::= { gs2326pARPInspectionStaticTable 1 }

GS2326PARPInspectionStaticEntry ::= SEQUENCE {
   gs2326pARPInspectionStaticIndex       Integer32,
   gs2326pARPInspectionStaticPort        Integer32,
   gs2326pARPInspectionStaticVLANId      Integer32,
   gs2326pARPInspectionStaticIPAddress   IpAddress,
   gs2326pARPInspectionStaticMACAddress  MacAddress,
   gs2326pARPInspectionStaticRowStatus   INTEGER
}

gs2326pARPInspectionStaticIndex OBJECT-TYPE
   SYNTAX      Integer32(1..4095)
   MAX-ACCESS  not-accessible
   STATUS      current
   DESCRIPTION
       ""
   ::= { gs2326pARPInspectionStaticEntry 1 }

gs2326pARPInspectionStaticPort OBJECT-TYPE
   SYNTAX      Integer32(1..4095)
   MAX-ACCESS  read-write
   STATUS      current
   DESCRIPTION
       " Port, range: 1 - port number. "
   ::= { gs2326pARPInspectionStaticEntry 2 }

gs2326pARPInspectionStaticVLANId OBJECT-TYPE
   SYNTAX      Integer32(1..4094)
   MAX-ACCESS  read-write
   STATUS      current
   DESCRIPTION
       " VLAN ID, range: 1 - 4094. "
   ::= { gs2326pARPInspectionStaticEntry 3 }

gs2326pARPInspectionStaticIPAddress OBJECT-TYPE
   SYNTAX      IpAddress
   MAX-ACCESS  read-write
   STATUS      current
   DESCRIPTION
       " IP address allowed for doing ARP request. "
   ::= { gs2326pARPInspectionStaticEntry 4 }

gs2326pARPInspectionStaticMACAddress OBJECT-TYPE
   SYNTAX      MacAddress
   MAX-ACCESS  read-write
   STATUS      current
   DESCRIPTION
       " Allowed Source MAC address in ARP request packets, format 0a 1b 2c 3d 4e 5f "
   ::= { gs2326pARPInspectionStaticEntry 5 }

gs2326pARPInspectionStaticRowStatus OBJECT-TYPE
   SYNTAX     INTEGER { active(1), notInservice(2), edit(3), destroy(4), undo(5) }
   MAX-ACCESS  read-write
   STATUS      current
   DESCRIPTION
       "1: active
        2: notInservice
        3: edit
        4: destroy
        5: undo"
   ::= { gs2326pARPInspectionStaticEntry 6 }

gs2326pARPInspectionDynamicTable OBJECT-TYPE
   SYNTAX      SEQUENCE OF GS2326PARPInspectionDynamicEntry
   MAX-ACCESS  not-accessible
   STATUS      current
   DESCRIPTION
       " "
   ::= { gs2326pARPInspection 3 }

gs2326pARPInspectionDynamicEntry OBJECT-TYPE
   SYNTAX      GS2326PARPInspectionDynamicEntry
   MAX-ACCESS  not-accessible
   STATUS      current
   DESCRIPTION
       ""
   INDEX    { gs2326pARPInspectionDynamicIndex  }
   ::= { gs2326pARPInspectionDynamicTable 1 }

GS2326PARPInspectionDynamicEntry ::= SEQUENCE {
   gs2326pARPInspectionDynamicIndex          Integer32,
   gs2326pARPInspectionDynamicPort           Integer32,
   gs2326pARPInspectionDynamicVLANId         Integer32,
   gs2326pARPInspectionDynamicIPAddress      IpAddress,
   gs2326pARPInspectionDynamicMACAddress     MacAddress
}

gs2326pARPInspectionDynamicIndex OBJECT-TYPE
   SYNTAX      Integer32(1..4095)
   MAX-ACCESS  not-accessible
   STATUS      current
   DESCRIPTION
       " "
   ::= { gs2326pARPInspectionDynamicEntry 1 }

gs2326pARPInspectionDynamicPort OBJECT-TYPE
   SYNTAX      Integer32(1..4095)
   MAX-ACCESS  read-only
   STATUS      current
   DESCRIPTION
       ""
   ::= { gs2326pARPInspectionDynamicEntry 2 }

gs2326pARPInspectionDynamicVLANId OBJECT-TYPE
   SYNTAX      Integer32(1..4094)
   MAX-ACCESS  read-only
   STATUS      current
   DESCRIPTION
       ""
   ::= { gs2326pARPInspectionDynamicEntry 3 }

gs2326pARPInspectionDynamicIPAddress OBJECT-TYPE
   SYNTAX      IpAddress
   MAX-ACCESS  read-only
   STATUS      current
   DESCRIPTION
       ""
   ::= { gs2326pARPInspectionDynamicEntry 4 }

gs2326pARPInspectionDynamicMACAddress OBJECT-TYPE
   SYNTAX      MacAddress
   MAX-ACCESS  read-only
   STATUS      current
   DESCRIPTION
       ""
   ::= { gs2326pARPInspectionDynamicEntry 5 }

gs2326pARPStaticGatewayCtrl	                                OBJECT IDENTIFIER ::= { gs2326pARPInspection 6 }

gs2326pARPStaticGatewayCtrlSystemConf                                      OBJECT IDENTIFIER ::= { gs2326pARPStaticGatewayCtrl 1 }

gs2326pARPStaticGatewayCtrlMode OBJECT-TYPE
   SYNTAX      INTEGER { disable(0), enable(1) }
   MAX-ACCESS  read-write
   STATUS      current
   DESCRIPTION
       "default: 0
       0: disable
       1: enable "
   ::= { gs2326pARPStaticGatewayCtrlSystemConf 1 }

gs2326pARPStaticGatewayCtrlCreate OBJECT-TYPE
   SYNTAX      INTEGER { none(0), create(1) }
   MAX-ACCESS  read-write
   STATUS      current
   DESCRIPTION
       "default: 0
        0: none
        1: create"
   ::= { gs2326pARPStaticGatewayCtrl 2 }

gs2326pARPStaticGatewayCtrlTable OBJECT-TYPE
   SYNTAX      SEQUENCE OF GS2326PARPStaticGatewayCtrlEntry
   MAX-ACCESS  not-accessible
   STATUS      current
   DESCRIPTION
       " "
   ::= { gs2326pARPStaticGatewayCtrl 3 }

gs2326pARPStaticGatewayCtrlEntry OBJECT-TYPE
   SYNTAX      GS2326PARPStaticGatewayCtrlEntry
   MAX-ACCESS  not-accessible
   STATUS      current
   DESCRIPTION
       ""
   INDEX    { gs2326pARPStaticGatewayCtrlIndex  }
   ::= { gs2326pARPStaticGatewayCtrlTable 1 }

GS2326PARPStaticGatewayCtrlEntry ::= SEQUENCE {
   gs2326pARPStaticGatewayCtrlIndex       Integer32,
   gs2326pARPStaticGatewayCtrlIPAddress   IpAddress,
   gs2326pARPStaticGatewayCtrlMACAddress  MacAddress,
   gs2326pARPStaticGatewayCtrlPort        Integer32,
   gs2326pARPStaticGatewayCtrlAction      INTEGER,
   gs2326pARPStaticGatewayCtrlState       DisplayString,
   gs2326pARPStaticGatewayCtrlReOpen      INTEGER,
   gs2326pARPStaticGatewayCtrlRowStatus   INTEGER
}

gs2326pARPStaticGatewayCtrlIndex OBJECT-TYPE
   SYNTAX      Integer32(1..4)
   MAX-ACCESS  not-accessible
   STATUS      current
   DESCRIPTION
       ""
   ::= { gs2326pARPStaticGatewayCtrlEntry 1 }

gs2326pARPStaticGatewayCtrlIPAddress OBJECT-TYPE
   SYNTAX      IpAddress
   MAX-ACCESS  read-write
   STATUS      current
   DESCRIPTION
       " Source IP address. "
   ::= { gs2326pARPStaticGatewayCtrlEntry 2 }

gs2326pARPStaticGatewayCtrlMACAddress OBJECT-TYPE
   SYNTAX      MacAddress
   MAX-ACCESS  read-write
   STATUS      current
   DESCRIPTION
       " Source MAC address , format 0a 1b 2c 3d 4e 5f "
   ::= { gs2326pARPStaticGatewayCtrlEntry 3 }

gs2326pARPStaticGatewayCtrlPort OBJECT-TYPE
   SYNTAX      Integer32(1..4095)
   MAX-ACCESS  read-write
   STATUS      current
   DESCRIPTION
       " Port, range: 1 - port number. "
   ::= { gs2326pARPStaticGatewayCtrlEntry 4 }

gs2326pARPStaticGatewayCtrlAction OBJECT-TYPE
   SYNTAX      INTEGER {none(0),trap(1),dropAndTrap(2), shutdown(3), trapAndShutdown(4) }
   MAX-ACCESS  read-write
   STATUS      current
   DESCRIPTION
       "default: 0
       0: none
       1: trap
       2: drop&trap
       3: shutdown
       4: trap&shutdown"
   ::= { gs2326pARPStaticGatewayCtrlEntry 5 }

gs2326pARPStaticGatewayCtrlState OBJECT-TYPE
   SYNTAX      DisplayString
   MAX-ACCESS  read-only
   STATUS      current
   DESCRIPTION
       ""
   ::= { gs2326pARPStaticGatewayCtrlEntry 6 }

gs2326pARPStaticGatewayCtrlReOpen OBJECT-TYPE
   SYNTAX      INTEGER { none(0), reopen(1) }
   MAX-ACCESS  read-write
   STATUS      current
   DESCRIPTION
       "default: 0
       0: none
       1: reopen"
   ::= { gs2326pARPStaticGatewayCtrlEntry 7 }

gs2326pARPStaticGatewayCtrlRowStatus OBJECT-TYPE
   SYNTAX      INTEGER { active(1), notInservice(2), edit(3), destroy(4), undo(5) }
   MAX-ACCESS  read-write
   STATUS      current
   DESCRIPTION
       "1: active
        2: notInservice
        3: edit
        4: destroy
        5: undo"
   ::= { gs2326pARPStaticGatewayCtrlEntry 8 }

gs2326pARPSpoofingPrevention	                                OBJECT IDENTIFIER ::= { gs2326pARPInspection 7 }

gs2326pARPSpoofingPreventionSystemConf                                      OBJECT IDENTIFIER ::= { gs2326pARPSpoofingPrevention 1 }

gs2326pARPSpoofingPreventionMode OBJECT-TYPE
   SYNTAX      INTEGER { disable(0), enable(1) }
   MAX-ACCESS  read-write
   STATUS      current
   DESCRIPTION
       "default: 0
       0: disable
       1: enable "
   ::= { gs2326pARPSpoofingPreventionSystemConf 1 }

gs2326pARPSpoofingPreventionTable OBJECT-TYPE
   SYNTAX      SEQUENCE OF GS2326PARPSpoofingPreventionEntry
   MAX-ACCESS  not-accessible
   STATUS      current
   DESCRIPTION
       " "
   ::= { gs2326pARPSpoofingPrevention 2 }

gs2326pARPSpoofingPreventionEntry OBJECT-TYPE
   SYNTAX      GS2326PARPSpoofingPreventionEntry
   MAX-ACCESS  not-accessible
   STATUS      current
   DESCRIPTION
       ""
   INDEX    { gs2326pARPSpoofingPreventionPort  }
   ::= { gs2326pARPSpoofingPreventionTable 1 }

GS2326PARPSpoofingPreventionEntry ::= SEQUENCE {
   gs2326pARPSpoofingPreventionPort           Integer32,
   gs2326pARPSpoofingPreventionPortMode       INTEGER,
   gs2326pARPSpoofingPreventionPortLimit      Integer32,
   gs2326pARPSpoofingPreventionPortAction     INTEGER,
   gs2326pARPSpoofingPreventionPortState      DisplayString,
   gs2326pARPSpoofingPreventionPortReOpen     INTEGER
}

gs2326pARPSpoofingPreventionPort OBJECT-TYPE
   SYNTAX      Integer32(1..4095)
   MAX-ACCESS  not-accessible
   STATUS      current
   DESCRIPTION
       " "
   ::= { gs2326pARPSpoofingPreventionEntry 1 }

gs2326pARPSpoofingPreventionPortMode OBJECT-TYPE
   SYNTAX      INTEGER { disable(0), enable(1) }
   MAX-ACCESS  read-write
   STATUS      current
   DESCRIPTION
       "default: 0
       0: disable
       1: enable"
   ::= { gs2326pARPSpoofingPreventionEntry 2 }

gs2326pARPSpoofingPreventionPortLimit OBJECT-TYPE
   SYNTAX      Integer32(1..100)
   MAX-ACCESS  read-write
   STATUS      current
   DESCRIPTION
       "default: 1, range: 1-100"
   ::= { gs2326pARPSpoofingPreventionEntry 3 }

gs2326pARPSpoofingPreventionPortAction OBJECT-TYPE
   SYNTAX      INTEGER { none(0), trap(1), dropAndTrap(2), shutdown(3), trapAndShutdown(4) }
   MAX-ACCESS  read-write
   STATUS      current
   DESCRIPTION
       "default: 0
       0: none
       1: trap
       2: drop&trap
       3: shutdown
       4: trap&shutdown"
   ::= { gs2326pARPSpoofingPreventionEntry 4 }

gs2326pARPSpoofingPreventionPortState OBJECT-TYPE
   SYNTAX      DisplayString
   MAX-ACCESS  read-only
   STATUS      current
   DESCRIPTION
       ""
   ::= { gs2326pARPSpoofingPreventionEntry 5 }

gs2326pARPSpoofingPreventionPortReOpen OBJECT-TYPE
   SYNTAX      INTEGER { none(0), reopen(1) }
   MAX-ACCESS  read-write
   STATUS      current
   DESCRIPTION
       "default: 0
       0: none
       1: reopen"
   ::= { gs2326pARPSpoofingPreventionEntry 6 }

gs2326pARPIPDoSPrevention	                                OBJECT IDENTIFIER ::= { gs2326pARPInspection 8 }

gs2326pARPIPDoSPreventionTCPMode OBJECT-TYPE
   SYNTAX      INTEGER { disable(0), enable(1) }
   MAX-ACCESS  read-write
   STATUS      current
   DESCRIPTION
       "default: 0
       0: disable
       1: enable "
   ::= { gs2326pARPIPDoSPrevention 1 }

gs2326pARPIPDoSPreventionUDPMode OBJECT-TYPE
   SYNTAX      INTEGER { disable(0), enable(1) }
   MAX-ACCESS  read-write
   STATUS      current
   DESCRIPTION
       "default: 0
       0: disable
       1: enable "
   ::= { gs2326pARPIPDoSPrevention 2 }

gs2326pARPIPDoSPreventionICMPMode OBJECT-TYPE
   SYNTAX      INTEGER { disable(0), enable(1) }
   MAX-ACCESS  read-write
   STATUS      current
   DESCRIPTION
       "default: 0
       0: disable
       1: enable "
   ::= { gs2326pARPIPDoSPrevention 3 }

gs2326pARPIPDoSPreventionServerPort1 OBJECT-TYPE
   SYNTAX      Integer32(0..4094)
   MAX-ACCESS  read-write
   STATUS      current
   DESCRIPTION
       " Port, range: 0 - port number. 0: none. "
   ::= { gs2326pARPIPDoSPrevention 4 }

gs2326pARPIPDoSPreventionServerPort2 OBJECT-TYPE
   SYNTAX      Integer32(0..4094)
   MAX-ACCESS  read-write
   STATUS      current
   DESCRIPTION
       " Port, range: 0 - port number. 0: none. "
   ::= { gs2326pARPIPDoSPrevention 5 }

gs2326pARPIPDoSPreventionServerPort3 OBJECT-TYPE
   SYNTAX      Integer32(0..4094)
   MAX-ACCESS  read-write
   STATUS      current
   DESCRIPTION
       " Port, range: 0 - port number. 0: none. "
   ::= { gs2326pARPIPDoSPrevention 6 }

gs2326pARPIPDoSPreventionServerPort4 OBJECT-TYPE
   SYNTAX      Integer32(0..4094)
   MAX-ACCESS  read-write
   STATUS      current
   DESCRIPTION
       " Port, range: 0 - port number. 0: none. "
   ::= { gs2326pARPIPDoSPrevention 7 }

gs2326pDHCPSnooping                                          OBJECT IDENTIFIER ::= { gs2326pSecurity 3 }

gs2326pDHCPSnoopingConf                                          OBJECT IDENTIFIER ::= { gs2326pDHCPSnooping 1 }

gs2326pDHCPSnoopingMode OBJECT-TYPE
   SYNTAX      INTEGER { disable(0), enable(1) }
   MAX-ACCESS  read-write
   STATUS      current
   DESCRIPTION
       "default: 0
       0: disable
       1: enable"
   ::= { gs2326pDHCPSnoopingConf 1 }

gs2326pDHCPSnoopingPortModeConfigurationTable OBJECT-TYPE
   SYNTAX      SEQUENCE OF GS2326PDHCPSnoopingPortModeConfigurationEntry
   MAX-ACCESS  not-accessible
   STATUS      current
   DESCRIPTION
       " "
   ::= { gs2326pDHCPSnoopingConf 2 }

gs2326pDHCPSnoopingPortModeConfigurationEntry OBJECT-TYPE
   SYNTAX      GS2326PDHCPSnoopingPortModeConfigurationEntry
   MAX-ACCESS  not-accessible
   STATUS      current
   DESCRIPTION
       ""
   INDEX    { gs2326pDHCPSnoopingPortModeConfigurationPort  }
   ::= { gs2326pDHCPSnoopingPortModeConfigurationTable 1 }

GS2326PDHCPSnoopingPortModeConfigurationEntry ::= SEQUENCE {
   gs2326pDHCPSnoopingPortModeConfigurationPort	Integer32,
   gs2326pDHCPSnoopingPortModeConfigurationMode	INTEGER
}

gs2326pDHCPSnoopingPortModeConfigurationPort OBJECT-TYPE
   SYNTAX      Integer32(1..4095)
   MAX-ACCESS  not-accessible
   STATUS      current
   DESCRIPTION
       " "
   ::= { gs2326pDHCPSnoopingPortModeConfigurationEntry 1 }

gs2326pDHCPSnoopingPortModeConfigurationMode OBJECT-TYPE
   SYNTAX      INTEGER { trust(0), untrust(1) }
   MAX-ACCESS  read-write
   STATUS      current
   DESCRIPTION
       "default: 1
       0: trust port mode
       1: untrust port mode"
   ::= { gs2326pDHCPSnoopingPortModeConfigurationEntry 2 }

gs2326pDHCPSnoopingStatisticsTable OBJECT-TYPE
   SYNTAX      SEQUENCE OF GS2326PDHCPSnoopingStatisticsEntry
   MAX-ACCESS  not-accessible
   STATUS      current
   DESCRIPTION
       " "
   ::= { gs2326pDHCPSnooping 2 }

gs2326pDHCPSnoopingStatisticsEntry OBJECT-TYPE
   SYNTAX      GS2326PDHCPSnoopingStatisticsEntry
   MAX-ACCESS  not-accessible
   STATUS      current
   DESCRIPTION
       ""
   INDEX    { gs2326pDHCPSnoopingStatisticsPort  }
   ::= { gs2326pDHCPSnoopingStatisticsTable 1 }

GS2326PDHCPSnoopingStatisticsEntry ::= SEQUENCE {
   gs2326pDHCPSnoopingStatisticsPort         Integer32,
   gs2326pDHCPSnoopingStatisticsClear        INTEGER,
   gs2326pDHCPSnoopingRxDiscover             Counter32,
   gs2326pDHCPSnoopingRxOffer                Counter32,
   gs2326pDHCPSnoopingRxRequest              Counter32,
   gs2326pDHCPSnoopingRxDecline              Counter32,
   gs2326pDHCPSnoopingRxACK                  Counter32,
   gs2326pDHCPSnoopingRxNAK                  Counter32,
   gs2326pDHCPSnoopingRxRelease              Counter32,
   gs2326pDHCPSnoopingRxInform               Counter32,
   gs2326pDHCPSnoopingRxLeaseQuery           Counter32,
   gs2326pDHCPSnoopingRxLeaseUnassigned      Counter32,
   gs2326pDHCPSnoopingRxLeaseUnknown         Counter32,
   gs2326pDHCPSnoopingRxLeaseActive          Counter32,
   gs2326pDHCPSnoopingTxDiscover             Counter32,
   gs2326pDHCPSnoopingTxOffer                Counter32,
   gs2326pDHCPSnoopingTxRequest              Counter32,
   gs2326pDHCPSnoopingTxDecline              Counter32,
   gs2326pDHCPSnoopingTxACK                  Counter32,
   gs2326pDHCPSnoopingTxNAK                  Counter32,
   gs2326pDHCPSnoopingTxRelease              Counter32,
   gs2326pDHCPSnoopingTxInform               Counter32,
   gs2326pDHCPSnoopingTxLeaseQuery           Counter32,
   gs2326pDHCPSnoopingTxLeaseUnassigned      Counter32,
   gs2326pDHCPSnoopingTxLeaseUnknown         Counter32,
   gs2326pDHCPSnoopingTxLeaseActive          Counter32
}

gs2326pDHCPSnoopingStatisticsPort OBJECT-TYPE
   SYNTAX      Integer32(1..4095)
   MAX-ACCESS  not-accessible
   STATUS      current
   DESCRIPTION
       " "
   ::= { gs2326pDHCPSnoopingStatisticsEntry 1 }

gs2326pDHCPSnoopingStatisticsClear OBJECT-TYPE
   SYNTAX      INTEGER { none(0), clear(1) }
   MAX-ACCESS  read-write
   STATUS      current
   DESCRIPTION
       "default: 0
       0: none
       1: clear"
   ::= { gs2326pDHCPSnoopingStatisticsEntry 2 }

gs2326pDHCPSnoopingRxDiscover OBJECT-TYPE
   SYNTAX      Counter32
   MAX-ACCESS  read-only
   STATUS      current
   DESCRIPTION
       " "
   ::= { gs2326pDHCPSnoopingStatisticsEntry 3 }

gs2326pDHCPSnoopingRxOffer OBJECT-TYPE
   SYNTAX      Counter32
   MAX-ACCESS  read-only
   STATUS      current
   DESCRIPTION
       " "
   ::= { gs2326pDHCPSnoopingStatisticsEntry 4 }

gs2326pDHCPSnoopingRxRequest OBJECT-TYPE
   SYNTAX      Counter32
   MAX-ACCESS  read-only
   STATUS      current
   DESCRIPTION
       " "
   ::= { gs2326pDHCPSnoopingStatisticsEntry 5 }

gs2326pDHCPSnoopingRxDecline OBJECT-TYPE
   SYNTAX      Counter32
   MAX-ACCESS  read-only
   STATUS      current
   DESCRIPTION
       " "
   ::= { gs2326pDHCPSnoopingStatisticsEntry 6 }

gs2326pDHCPSnoopingRxACK OBJECT-TYPE
   SYNTAX      Counter32
   MAX-ACCESS  read-only
   STATUS      current
   DESCRIPTION
       " "
   ::= { gs2326pDHCPSnoopingStatisticsEntry 7 }

gs2326pDHCPSnoopingRxNAK OBJECT-TYPE
   SYNTAX      Counter32
   MAX-ACCESS  read-only
   STATUS      current
   DESCRIPTION
       " "
   ::= { gs2326pDHCPSnoopingStatisticsEntry 8 }

gs2326pDHCPSnoopingRxRelease OBJECT-TYPE
   SYNTAX      Counter32
   MAX-ACCESS  read-only
   STATUS      current
   DESCRIPTION
       " "
   ::= { gs2326pDHCPSnoopingStatisticsEntry 9 }

gs2326pDHCPSnoopingRxInform OBJECT-TYPE
   SYNTAX      Counter32
   MAX-ACCESS  read-only
   STATUS      current
   DESCRIPTION
       " "
   ::= { gs2326pDHCPSnoopingStatisticsEntry 10 }

gs2326pDHCPSnoopingRxLeaseQuery OBJECT-TYPE
   SYNTAX      Counter32
   MAX-ACCESS  read-only
   STATUS      current
   DESCRIPTION
       " "
   ::= { gs2326pDHCPSnoopingStatisticsEntry 11 }

gs2326pDHCPSnoopingRxLeaseUnassigned OBJECT-TYPE
   SYNTAX      Counter32
   MAX-ACCESS  read-only
   STATUS      current
   DESCRIPTION
       " "
   ::= { gs2326pDHCPSnoopingStatisticsEntry 12 }

gs2326pDHCPSnoopingRxLeaseUnknown OBJECT-TYPE
   SYNTAX      Counter32
   MAX-ACCESS  read-only
   STATUS      current
   DESCRIPTION
       " "
   ::= { gs2326pDHCPSnoopingStatisticsEntry 13 }

gs2326pDHCPSnoopingRxLeaseActive OBJECT-TYPE
   SYNTAX      Counter32
   MAX-ACCESS  read-only
   STATUS      current
   DESCRIPTION
       " "
   ::= { gs2326pDHCPSnoopingStatisticsEntry 14 }

gs2326pDHCPSnoopingTxDiscover OBJECT-TYPE
   SYNTAX      Counter32
   MAX-ACCESS  read-only
   STATUS      current
   DESCRIPTION
       " "
   ::= { gs2326pDHCPSnoopingStatisticsEntry 15 }

gs2326pDHCPSnoopingTxOffer OBJECT-TYPE
   SYNTAX      Counter32
   MAX-ACCESS  read-only
   STATUS      current
   DESCRIPTION
       " "
   ::= { gs2326pDHCPSnoopingStatisticsEntry 16 }

gs2326pDHCPSnoopingTxRequest OBJECT-TYPE
   SYNTAX      Counter32
   MAX-ACCESS  read-only
   STATUS      current
   DESCRIPTION
       " "
   ::= { gs2326pDHCPSnoopingStatisticsEntry 17 }

gs2326pDHCPSnoopingTxDecline OBJECT-TYPE
   SYNTAX      Counter32
   MAX-ACCESS  read-only
   STATUS      current
   DESCRIPTION
       " "
   ::= { gs2326pDHCPSnoopingStatisticsEntry 18 }

gs2326pDHCPSnoopingTxACK OBJECT-TYPE
   SYNTAX      Counter32
   MAX-ACCESS  read-only
   STATUS      current
   DESCRIPTION
       " "
   ::= { gs2326pDHCPSnoopingStatisticsEntry 19 }

gs2326pDHCPSnoopingTxNAK OBJECT-TYPE
   SYNTAX      Counter32
   MAX-ACCESS  read-only
   STATUS      current
   DESCRIPTION
       " "
   ::= { gs2326pDHCPSnoopingStatisticsEntry 20 }

gs2326pDHCPSnoopingTxRelease OBJECT-TYPE
   SYNTAX      Counter32
   MAX-ACCESS  read-only
   STATUS      current
   DESCRIPTION
       " "
   ::= { gs2326pDHCPSnoopingStatisticsEntry 21 }

gs2326pDHCPSnoopingTxInform OBJECT-TYPE
   SYNTAX      Counter32
   MAX-ACCESS  read-only
   STATUS      current
   DESCRIPTION
       " "
   ::= { gs2326pDHCPSnoopingStatisticsEntry 22 }

gs2326pDHCPSnoopingTxLeaseQuery OBJECT-TYPE
   SYNTAX      Counter32
   MAX-ACCESS  read-only
   STATUS      current
   DESCRIPTION
       " "
   ::= { gs2326pDHCPSnoopingStatisticsEntry 23 }

gs2326pDHCPSnoopingTxLeaseUnassigned OBJECT-TYPE
   SYNTAX      Counter32
   MAX-ACCESS  read-only
   STATUS      current
   DESCRIPTION
       " "
   ::= { gs2326pDHCPSnoopingStatisticsEntry 24 }

gs2326pDHCPSnoopingTxLeaseUnknown OBJECT-TYPE
   SYNTAX      Counter32
   MAX-ACCESS  read-only
   STATUS      current
   DESCRIPTION
       " "
   ::= { gs2326pDHCPSnoopingStatisticsEntry 25 }

gs2326pDHCPSnoopingTxLeaseActive OBJECT-TYPE
   SYNTAX      Counter32
   MAX-ACCESS  read-only
   STATUS      current
   DESCRIPTION
       " "
   ::= { gs2326pDHCPSnoopingStatisticsEntry 26 }


gs2326pDHCPRelay                                             OBJECT IDENTIFIER ::= { gs2326pSecurity 4 }

gs2326pDHCPRelayConfiguration                                         OBJECT IDENTIFIER ::= { gs2326pDHCPRelay 1 }

gs2326pDHCPRelayMode OBJECT-TYPE
   SYNTAX      INTEGER { disable(0), enable(1) }
   MAX-ACCESS  read-write
   STATUS      current
   DESCRIPTION
       "default: 0
       0: disable
       1: enable
       We need at least one server"
   ::= { gs2326pDHCPRelayConfiguration 1 }

gs2326pDHCPRelayServer OBJECT-TYPE
   SYNTAX      IpAddress
   MAX-ACCESS  read-write
   STATUS      current
   DESCRIPTION
       " "
   ::= { gs2326pDHCPRelayConfiguration 2 }

gs2326pDHCPRelayInformationMode OBJECT-TYPE
   SYNTAX      INTEGER { disable(0), enable(1) }
   MAX-ACCESS  read-write
   STATUS      current
   DESCRIPTION
       "default: 0
       0: disable
       1: enable "
   ::= { gs2326pDHCPRelayConfiguration 3 }

gs2326pDHCPRelayInformationPolicy OBJECT-TYPE
   SYNTAX      INTEGER { replace(0), keep(1), drop(2) }
   MAX-ACCESS  read-write
   STATUS      current
   DESCRIPTION
       "default: 0
       0: replace
       1: keep
       2: drop "
   ::= { gs2326pDHCPRelayConfiguration 4 }

gs2326pDHCPRelayInformationCustom OBJECT-TYPE
   SYNTAX      DisplayString(SIZE(0..32))
   MAX-ACCESS  read-write
   STATUS      current
   DESCRIPTION
       "DHCP Option 82 Circuit ID custom information"
   ::= { gs2326pDHCPRelayConfiguration 1500 }

gs2326pDHCPRelayConfigurationGateways                                          OBJECT IDENTIFIER ::= { gs2326pDHCPRelayConfiguration 5 }

gs2326pDHCPRelayConfigurationGatewaysCreate OBJECT-TYPE
   SYNTAX       INTEGER { none(0), create(1) }
   MAX-ACCESS   read-write
   STATUS       current
   DESCRIPTION
       "default: 0
        0 : None  (read only)
        1 : Create entry"
   ::= { gs2326pDHCPRelayConfigurationGateways 1 }

gs2326pDHCPRelayConfigurationGatewaysTable OBJECT-TYPE
   SYNTAX      SEQUENCE OF Gs2326pDHCPRelayConfigurationGatewaysEntry
   MAX-ACCESS  not-accessible
   STATUS      current
   DESCRIPTION
       " Create DHCP Relay Gateway IP address entry."
   ::= { gs2326pDHCPRelayConfigurationGateways 2 }

gs2326pDHCPRelayConfigurationGatewaysEntry OBJECT-TYPE
   SYNTAX      Gs2326pDHCPRelayConfigurationGatewaysEntry
   MAX-ACCESS  not-accessible
   STATUS      current
   DESCRIPTION
       ""
   INDEX    { gs2326pDHCPRelayConfigurationGatewaysIndex  }
   ::= { gs2326pDHCPRelayConfigurationGatewaysTable 1 }

Gs2326pDHCPRelayConfigurationGatewaysEntry ::= SEQUENCE {
   gs2326pDHCPRelayConfigurationGatewaysIndex           Integer32,
   gs2326pDHCPRelayConfigurationGatewaysVLANId          Integer32,
   gs2326pDHCPRelayConfigurationGatewaysIP              IpAddress,
   gs2326pDHCPRelayConfigurationGatewaysRowStatus       INTEGER
}

gs2326pDHCPRelayConfigurationGatewaysIndex OBJECT-TYPE
   SYNTAX      Integer32(1..6)
   MAX-ACCESS  not-accessible
   STATUS      current
   DESCRIPTION
       " "
   ::= { gs2326pDHCPRelayConfigurationGatewaysEntry 1 }

gs2326pDHCPRelayConfigurationGatewaysVLANId OBJECT-TYPE
   SYNTAX      Integer32(1..4094)
   MAX-ACCESS  read-write
   STATUS      current
   DESCRIPTION
       " VLAN ID "
   ::= { gs2326pDHCPRelayConfigurationGatewaysEntry 2 }

gs2326pDHCPRelayConfigurationGatewaysIP OBJECT-TYPE
   SYNTAX      IpAddress
   MAX-ACCESS  read-write
   STATUS      current
   DESCRIPTION
       "DHCP GIADDR address."
   ::= { gs2326pDHCPRelayConfigurationGatewaysEntry 3 }

gs2326pDHCPRelayConfigurationGatewaysRowStatus OBJECT-TYPE
   SYNTAX      INTEGER { active(1), notInservice(2), destroy(4), undo(5) }
   MAX-ACCESS  read-write
   STATUS      current
   DESCRIPTION
       "1: active
        2: notInservice
        4: destroy
        5: undo"
   ::= { gs2326pDHCPRelayConfigurationGatewaysEntry 4 }

gs2326pDHCPRelayStatistics                                   OBJECT IDENTIFIER ::= { gs2326pDHCPRelay 2 }

gs2326pDHCPRelayServerStatistics                                   OBJECT IDENTIFIER ::= { gs2326pDHCPRelayStatistics 1 }

gs2326pServerStatTransmitToServer OBJECT-TYPE
   SYNTAX      Counter32
   MAX-ACCESS  read-only
   STATUS      current
   DESCRIPTION
       " "
   ::= { gs2326pDHCPRelayServerStatistics 1 }

gs2326pServerStatTransmitError OBJECT-TYPE
   SYNTAX      Counter32
   MAX-ACCESS  read-only
   STATUS      current
   DESCRIPTION
       " "
   ::= { gs2326pDHCPRelayServerStatistics 2 }

gs2326pServerStatReceiveFromServer OBJECT-TYPE
   SYNTAX      Counter32
   MAX-ACCESS  read-only
   STATUS      current
   DESCRIPTION
       " "
   ::= { gs2326pDHCPRelayServerStatistics 3 }

gs2326pServerStatReceiveMissingAgentOption OBJECT-TYPE
   SYNTAX      Counter32
   MAX-ACCESS  read-only
   STATUS      current
   DESCRIPTION
       " "
   ::= { gs2326pDHCPRelayServerStatistics 4 }

gs2326pServerStatReceiveMissingCircuitID OBJECT-TYPE
   SYNTAX      Counter32
   MAX-ACCESS  read-only
   STATUS      current
   DESCRIPTION
       " "
   ::= { gs2326pDHCPRelayServerStatistics 5 }

gs2326pServerStatReceiveMissingRemoteID OBJECT-TYPE
   SYNTAX      Counter32
   MAX-ACCESS  read-only
   STATUS      current
   DESCRIPTION
       " "
   ::= { gs2326pDHCPRelayServerStatistics 6 }

gs2326pServerStatReceiveBadCircuitID OBJECT-TYPE
   SYNTAX      Counter32
   MAX-ACCESS  read-only
   STATUS      current
   DESCRIPTION
       " "
   ::= { gs2326pDHCPRelayServerStatistics 7 }

gs2326pServerStatReceiveBadRemoteID OBJECT-TYPE
   SYNTAX      Counter32
   MAX-ACCESS  read-only
   STATUS      current
   DESCRIPTION
       " "
   ::= { gs2326pDHCPRelayServerStatistics 8 }

gs2326pDHCPRelayClientStatistics                                   OBJECT IDENTIFIER ::= { gs2326pDHCPRelayStatistics 2 }

gs2326pClientStatTransmitToClient OBJECT-TYPE
   SYNTAX      Counter32
   MAX-ACCESS  read-only
   STATUS      current
   DESCRIPTION
       " "
   ::= { gs2326pDHCPRelayClientStatistics 1 }

gs2326pClientStatTransmitError OBJECT-TYPE
   SYNTAX      Counter32
   MAX-ACCESS  read-only
   STATUS      current
   DESCRIPTION
       " "
   ::= { gs2326pDHCPRelayClientStatistics 2 }

gs2326pClientStatReceivefromClient OBJECT-TYPE
   SYNTAX      Counter32
   MAX-ACCESS  read-only
   STATUS      current
   DESCRIPTION
       " "
   ::= { gs2326pDHCPRelayClientStatistics 3 }

gs2326pClientStatReceiveAgentOption OBJECT-TYPE
   SYNTAX      Counter32
   MAX-ACCESS  read-only
   STATUS      current
   DESCRIPTION
       " "
   ::= { gs2326pDHCPRelayClientStatistics 4 }

gs2326pClientStatReplaceAgentOption OBJECT-TYPE
   SYNTAX      Counter32
   MAX-ACCESS  read-only
   STATUS      current
   DESCRIPTION
       " "
   ::= { gs2326pDHCPRelayClientStatistics 5 }

gs2326pClientStatKeepAgentOption OBJECT-TYPE
   SYNTAX      Counter32
   MAX-ACCESS  read-only
   STATUS      current
   DESCRIPTION
       " "
   ::= { gs2326pDHCPRelayClientStatistics 6 }

gs2326pClientStatDropAgentOption OBJECT-TYPE
   SYNTAX      Counter32
   MAX-ACCESS  read-only
   STATUS      current
   DESCRIPTION
       " "
   ::= { gs2326pDHCPRelayClientStatistics 7 }

gs2326pPortSecurity                                          OBJECT IDENTIFIER ::= { gs2326pSecurity 5 }

gs2326pPortSecLimitCtrl                                      OBJECT IDENTIFIER ::= { gs2326pPortSecurity 1 }

gs2326pPortSecLimitCtrlSystemConf                                      OBJECT IDENTIFIER ::= { gs2326pPortSecLimitCtrl 1 }

gs2326pPortSecurityMode OBJECT-TYPE
   SYNTAX      INTEGER { disable(0), enable(1) }
   MAX-ACCESS  read-write
   STATUS      current
   DESCRIPTION
       "default: 0
       0: disable
       1: enable "
   ::= { gs2326pPortSecLimitCtrlSystemConf 1 }

gs2326pPortSecurityAging OBJECT-TYPE
   SYNTAX      INTEGER { disable(0), enable(1) }
   MAX-ACCESS  read-write
   STATUS      current
   DESCRIPTION
       "default: 0
       0: disable
       1: enable "
   ::= { gs2326pPortSecLimitCtrlSystemConf 2 }

gs2326pPortSecurityAgingPeriod OBJECT-TYPE
   SYNTAX      INTEGER(10..10000000)
   MAX-ACCESS  read-write
   STATUS      current
   DESCRIPTION
       "default: 3600, range: 10-10000000 "
   ::= { gs2326pPortSecLimitCtrlSystemConf 3 }

gs2326pPortSecLimitCtrlTable OBJECT-TYPE
   SYNTAX      SEQUENCE OF GS2326PPortSecLimitCtrlEntry
   MAX-ACCESS  not-accessible
   STATUS      current
   DESCRIPTION
       " "
   ::= { gs2326pPortSecLimitCtrl 2 }

gs2326pPortSecLimitCtrlEntry OBJECT-TYPE
   SYNTAX      GS2326PPortSecLimitCtrlEntry
   MAX-ACCESS  not-accessible
   STATUS      current
   DESCRIPTION
       ""
   INDEX    { gs2326pPortSecLimitCtrlPort  }
   ::= { gs2326pPortSecLimitCtrlTable 1 }

GS2326PPortSecLimitCtrlEntry ::= SEQUENCE {
   gs2326pPortSecLimitCtrlPort           Integer32,
   gs2326pPortSecLimitCtrlPortMode       INTEGER,
   gs2326pPortSecLimitCtrlPortLimit      Integer32,
   gs2326pPortSecLimitCtrlPortAction     INTEGER,
   gs2326pPortSecLimitCtrlPortState      DisplayString,
   gs2326pPortSecLimitCtrlPortReOpen     INTEGER
}

gs2326pPortSecLimitCtrlPort OBJECT-TYPE
   SYNTAX      Integer32(1..4095)
   MAX-ACCESS  not-accessible
   STATUS      current
   DESCRIPTION
       " "
   ::= { gs2326pPortSecLimitCtrlEntry 1 }

gs2326pPortSecLimitCtrlPortMode OBJECT-TYPE
   SYNTAX      INTEGER { disable(0), enable(1) }
   MAX-ACCESS  read-write
   STATUS      current
   DESCRIPTION
       "default: 0
       0: disable
       1: enable"
   ::= { gs2326pPortSecLimitCtrlEntry 2 }

gs2326pPortSecLimitCtrlPortLimit OBJECT-TYPE
   SYNTAX      Integer32(1..1024)
   MAX-ACCESS  read-write
   STATUS      current
   DESCRIPTION
       "default: 4, range: 1-1024"
   ::= { gs2326pPortSecLimitCtrlEntry 3 }

gs2326pPortSecLimitCtrlPortAction OBJECT-TYPE
   SYNTAX      INTEGER { none(0), trap(1), shutdown(2), trapShutdown(3) }
   MAX-ACCESS  read-write
   STATUS      current
   DESCRIPTION
       "default: 0
       0: none
       1: trap
       2: shutdown
       3: trap&shutdown"
   ::= { gs2326pPortSecLimitCtrlEntry 4 }

gs2326pPortSecLimitCtrlPortState OBJECT-TYPE
   SYNTAX      DisplayString
   MAX-ACCESS  read-only
   STATUS      current
   DESCRIPTION
       ""
   ::= { gs2326pPortSecLimitCtrlEntry 5 }

gs2326pPortSecLimitCtrlPortReOpen OBJECT-TYPE
   SYNTAX      INTEGER { none(0), reopen(1) }
   MAX-ACCESS  read-write
   STATUS      current
   DESCRIPTION
       "default: 0
       0: none
       1: reopen"
   ::= { gs2326pPortSecLimitCtrlEntry 6 }

gs2326pPortSecSwitchStatusTable OBJECT-TYPE
   SYNTAX      SEQUENCE OF GS2326PPortSecSwitchStatusEntry
   MAX-ACCESS  not-accessible
   STATUS      current
   DESCRIPTION
       " "
   ::= { gs2326pPortSecurity 2 }

gs2326pPortSecSwitchStatusEntry OBJECT-TYPE
   SYNTAX      GS2326PPortSecSwitchStatusEntry
   MAX-ACCESS  not-accessible
   STATUS      current
   DESCRIPTION
       ""
   INDEX    { gs2326pPortSecSwitchStatusPort  }
   ::= { gs2326pPortSecSwitchStatusTable 1 }

GS2326PPortSecSwitchStatusEntry ::= SEQUENCE {
   gs2326pPortSecSwitchStatusPort                Integer32,
   gs2326pPortSecSwitchStatusUsers               DisplayString,
   gs2326pPortSecSwitchStatusState               DisplayString,
   gs2326pPortSecSwitchStatusMACCountCurrent     Integer32,
   gs2326pPortSecSwitchStatusMACCountLimit       Integer32
}

gs2326pPortSecSwitchStatusPort OBJECT-TYPE
   SYNTAX      Integer32(1..4095)
   MAX-ACCESS  not-accessible
   STATUS      current
   DESCRIPTION
       " "
   ::= { gs2326pPortSecSwitchStatusEntry 1 }

gs2326pPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { gs2326pPortSecSwitchStatusEntry 2 }

gs2326pPortSecSwitchStatusState OBJECT-TYPE
   SYNTAX      DisplayString
   MAX-ACCESS  read-only
   STATUS      current
   DESCRIPTION
       " Shows the current state of the port : Disabled, Ready, Limit Reached, Shutdown. "
   ::= { gs2326pPortSecSwitchStatusEntry 3 }

gs2326pPortSecSwitchStatusMACCountCurrent OBJECT-TYPE
   SYNTAX      Integer32(1..4095)
   MAX-ACCESS  read-only
   STATUS      current
   DESCRIPTION
       ""
   ::= { gs2326pPortSecSwitchStatusEntry 4 }

gs2326pPortSecSwitchStatusMACCountLimit OBJECT-TYPE
   SYNTAX      Integer32(1..4095)
   MAX-ACCESS  read-only
   STATUS      current
   DESCRIPTION
       ""
   ::= { gs2326pPortSecSwitchStatusEntry 5 }

gs2326pPortSecPortStatus                                      OBJECT IDENTIFIER ::= { gs2326pPortSecurity 3 }

gs2326pPortSecPortStatusPort OBJECT-TYPE
   SYNTAX       Integer32(1..4095)
   MAX-ACCESS   read-write
   STATUS       current
   DESCRIPTION
       "port number
        default: 1
        range: 1 - port number."
   ::= { gs2326pPortSecPortStatus 1 }

gs2326pPortSecPortStatusTable OBJECT-TYPE
   SYNTAX      SEQUENCE OF GS2326PPortSecPortStatusEntry
   MAX-ACCESS  not-accessible
   STATUS      current
   DESCRIPTION
      " "
   ::= { gs2326pPortSecPortStatus 2 }

gs2326pPortSecPortStatusEntry OBJECT-TYPE
   SYNTAX      GS2326PPortSecPortStatusEntry
   MAX-ACCESS  not-accessible
   STATUS      current
   DESCRIPTION
       ""
   INDEX    { gs2326pPortSecPortStatusIndex  }
   ::= { gs2326pPortSecPortStatusTable 1 }

GS2326PPortSecPortStatusEntry ::= SEQUENCE {
   gs2326pPortSecPortStatusIndex              Integer32,
   gs2326pPortSecPortStatusMACAddress         MacAddress,
   gs2326pPortSecPortStatusVLANId             Integer32,
   gs2326pPortSecPortStatusState              DisplayString,
   gs2326pPortSecPortStatusTimeOfAddition     DisplayString,
   gs2326pPortSecPortStatusAgeAndHold         DisplayString
}

gs2326pPortSecPortStatusIndex OBJECT-TYPE
   SYNTAX      Integer32(1..4095)
   MAX-ACCESS  not-accessible
   STATUS      current
   DESCRIPTION
       " "
   ::= { gs2326pPortSecPortStatusEntry 1 }

gs2326pPortSecPortStatusMACAddress OBJECT-TYPE
   SYNTAX      MacAddress
   MAX-ACCESS  read-only
   STATUS      current
   DESCRIPTION
       " "
   ::= { gs2326pPortSecPortStatusEntry 2 }

gs2326pPortSecPortStatusVLANId OBJECT-TYPE
   SYNTAX      Integer32(1..4094)
   MAX-ACCESS  read-only
   STATUS      current
   DESCRIPTION
       " "
   ::= { gs2326pPortSecPortStatusEntry 3 }

gs2326pPortSecPortStatusState OBJECT-TYPE
   SYNTAX      DisplayString
   MAX-ACCESS  read-only
   STATUS      current
   DESCRIPTION
       "Blocked / Forwarding "
   ::= { gs2326pPortSecPortStatusEntry 4 }

gs2326pPortSecPortStatusTimeOfAddition OBJECT-TYPE
   SYNTAX      DisplayString
   MAX-ACCESS  read-only
   STATUS      current
   DESCRIPTION
       " "
   ::= { gs2326pPortSecPortStatusEntry 5 }

gs2326pPortSecPortStatusAgeAndHold OBJECT-TYPE
   SYNTAX      DisplayString
   MAX-ACCESS  read-only
   STATUS      current
   DESCRIPTION
       " "
   ::= { gs2326pPortSecPortStatusEntry 6 }


gs2326pAccessManagement                                      OBJECT IDENTIFIER ::= { gs2326pSecurity 6 }

gs2326pAccessMgtConf                                         OBJECT IDENTIFIER ::= { gs2326pAccessManagement 1 }

gs2326pAccessMgtConfMode OBJECT-TYPE
   SYNTAX      INTEGER { disable(0), enable(1) }
   MAX-ACCESS  read-write
   STATUS      current
   DESCRIPTION
       "default: 0
       0: disable
       1: enable "
   ::= { gs2326pAccessMgtConf 1 }

gs2326pAccessMgtConfCreate OBJECT-TYPE
   SYNTAX      INTEGER { none(0), create(1) }
   MAX-ACCESS  read-write
   STATUS      current
   DESCRIPTION
       "default: 0
       0: none
       1: create "
   ::= { gs2326pAccessMgtConf 2 }

gs2326pAccessMgtConfTable OBJECT-TYPE
   SYNTAX      SEQUENCE OF GS2326PAccessMgtConfEntry
   MAX-ACCESS  not-accessible
   STATUS      current
   DESCRIPTION
       " "
   ::= { gs2326pAccessMgtConf 3 }

gs2326pAccessMgtConfEntry OBJECT-TYPE
   SYNTAX      GS2326PAccessMgtConfEntry
   MAX-ACCESS  not-accessible
   STATUS      current
   DESCRIPTION
       ""
   INDEX    { gs2326pAccessMgtIndex  }
   ::= { gs2326pAccessMgtConfTable 1 }

GS2326PAccessMgtConfEntry ::= SEQUENCE {
   gs2326pAccessMgtIndex             Integer32,
   gs2326pAccessMgtAddresstype       INTEGER,
   gs2326pAccessMgtStartIpAddress    DisplayString,
   gs2326pAccessMgtEndIpAddress      DisplayString,
   gs2326pAccessMgtHttpHttps         INTEGER,
   gs2326pAccessMgtSNMP              INTEGER,
   gs2326pAccessMgtTelnetSSH         INTEGER,
   gs2326pAccessMgtRowStatus         INTEGER
}

gs2326pAccessMgtIndex OBJECT-TYPE
   SYNTAX      Integer32(1..16)
   MAX-ACCESS  read-write
   STATUS      current
   DESCRIPTION
       "Set Access Management config index
        range : 1-16."
   ::= { gs2326pAccessMgtConfEntry 1 }

gs2326pAccessMgtAddresstype OBJECT-TYPE
   SYNTAX      INTEGER { ipv4(0), ipv6(1) }
   MAX-ACCESS  read-write
   STATUS      current
   DESCRIPTION
       "0: ipv4
        1: ipv6 "
   ::= { gs2326pAccessMgtConfEntry 2 }

gs2326pAccessMgtStartIpAddress OBJECT-TYPE
   SYNTAX      DisplayString
   MAX-ACCESS  read-write
   STATUS      current
   DESCRIPTION
       " Start IP address.
         IP address doesn't allowed all zero or all 'ff'H."
   ::= { gs2326pAccessMgtConfEntry 3 }

gs2326pAccessMgtEndIpAddress OBJECT-TYPE
   SYNTAX      DisplayString
   MAX-ACCESS  read-write
   STATUS      current
   DESCRIPTION
       " End IP address.
         IP address doesn't allowed all zero or all 'ff'H.
         End ip address is not less than start ip address."
   ::= { gs2326pAccessMgtConfEntry 4 }

gs2326pAccessMgtHttpHttps OBJECT-TYPE
   SYNTAX      INTEGER { disable(0), enable(1) }
   MAX-ACCESS  read-write
   STATUS      current
   DESCRIPTION
       "default: 0
       0: disable
       1: enable "
   ::= { gs2326pAccessMgtConfEntry 5 }

gs2326pAccessMgtSNMP OBJECT-TYPE
   SYNTAX      INTEGER { disable(0), enable(1) }
   MAX-ACCESS  read-write
   STATUS      current
   DESCRIPTION
       "default: 0
       0: disable
       1: enable "
   ::= { gs2326pAccessMgtConfEntry 6 }

gs2326pAccessMgtTelnetSSH OBJECT-TYPE
   SYNTAX      INTEGER { disable(0), enable(1) }
   MAX-ACCESS  read-write
   STATUS      current
   DESCRIPTION
       "default: 0
       0: disable
       1: enable "
   ::= { gs2326pAccessMgtConfEntry 7 }

gs2326pAccessMgtRowStatus OBJECT-TYPE
   SYNTAX      INTEGER { active(1), notInservice(2), edit(3),destroy(4), undo(5) }
   MAX-ACCESS  read-write
   STATUS      current
   DESCRIPTION
       "1: active
        2: notInservice
        3: edit
        4: destroy
        5: undo"
   ::= { gs2326pAccessMgtConfEntry 8 }

gs2326pAccessMgtStatistics                                   OBJECT IDENTIFIER ::= { gs2326pAccessManagement 2 }

gs2326pHttpReceivedPkts OBJECT-TYPE
   SYNTAX      Counter32
   MAX-ACCESS  read-only
   STATUS      current
   DESCRIPTION
       " "
   ::= { gs2326pAccessMgtStatistics 1 }

gs2326pHttpAllowedPkts OBJECT-TYPE
   SYNTAX      Counter32
   MAX-ACCESS  read-only
   STATUS      current
   DESCRIPTION
       " "
   ::= { gs2326pAccessMgtStatistics 2 }

gs2326pHttpDiscardedPkts OBJECT-TYPE
   SYNTAX      Counter32
   MAX-ACCESS  read-only
   STATUS      current
   DESCRIPTION
       " "
   ::= { gs2326pAccessMgtStatistics 3 }

gs2326pHttpsReceivedPkts OBJECT-TYPE
   SYNTAX      Counter32
   MAX-ACCESS  read-only
   STATUS      current
   DESCRIPTION
       " "
   ::= { gs2326pAccessMgtStatistics 4 }

gs2326pHttpsAllowedPkts OBJECT-TYPE
   SYNTAX      Counter32
   MAX-ACCESS  read-only
   STATUS      current
   DESCRIPTION
       " "
   ::= { gs2326pAccessMgtStatistics 5 }

gs2326pHttpsDiscardedPkts OBJECT-TYPE
   SYNTAX      Counter32
   MAX-ACCESS  read-only
   STATUS      current
   DESCRIPTION
       " "
   ::= { gs2326pAccessMgtStatistics 6 }

gs2326pSnmpReceivedPkts OBJECT-TYPE
   SYNTAX      Counter32
   MAX-ACCESS  read-only
   STATUS      current
   DESCRIPTION
       " "
   ::= { gs2326pAccessMgtStatistics 7 }

gs2326pSnmpAllowedPkts OBJECT-TYPE
   SYNTAX      Counter32
   MAX-ACCESS  read-only
   STATUS      current
   DESCRIPTION
       " "
   ::= { gs2326pAccessMgtStatistics 8 }

gs2326pSnmpDiscardedPkts OBJECT-TYPE
   SYNTAX      Counter32
   MAX-ACCESS  read-only
   STATUS      current
   DESCRIPTION
       " "
   ::= { gs2326pAccessMgtStatistics 9 }

gs2326pTelnetReceivedPkts OBJECT-TYPE
   SYNTAX      Counter32
   MAX-ACCESS  read-only
   STATUS      current
   DESCRIPTION
       " "
   ::= { gs2326pAccessMgtStatistics 10 }

gs2326pTelnetAllowedPkts OBJECT-TYPE
   SYNTAX      Counter32
   MAX-ACCESS  read-only
   STATUS      current
   DESCRIPTION
       " "
   ::= { gs2326pAccessMgtStatistics 11 }

gs2326pTelnetDiscardedPkts OBJECT-TYPE
   SYNTAX      Counter32
   MAX-ACCESS  read-only
   STATUS      current
   DESCRIPTION
       " "
   ::= { gs2326pAccessMgtStatistics 12 }

gs2326pSSHReceivedPkts OBJECT-TYPE
   SYNTAX      Counter32
   MAX-ACCESS  read-only
   STATUS      current
   DESCRIPTION
       " "
   ::= { gs2326pAccessMgtStatistics 13 }

gs2326pSSHAllowedPkts OBJECT-TYPE
   SYNTAX      Counter32
   MAX-ACCESS  read-only
   STATUS      current
   DESCRIPTION
       " "
   ::= { gs2326pAccessMgtStatistics 14 }

gs2326pSSHDiscardedPkts OBJECT-TYPE
   SYNTAX      Counter32
   MAX-ACCESS  read-only
   STATUS      current
   DESCRIPTION
       " "
   ::= { gs2326pAccessMgtStatistics 15 }

gs2326pAccessMgtStatisticsClearAll OBJECT-TYPE
   SYNTAX      INTEGER { none(0), clear(1) }
   MAX-ACCESS  read-write
   STATUS      current
   DESCRIPTION
       "0: none
        1: clear"
   ::= { gs2326pAccessMgtStatistics 16 }

gs2326pSSH                                                   OBJECT IDENTIFIER ::= { gs2326pSecurity 7 }

gs2326pSSHMode OBJECT-TYPE
   SYNTAX      INTEGER { disable(0), enable(1) }
   MAX-ACCESS  read-write
   STATUS      current
   DESCRIPTION
       "default: 1
        0: disable
        1: enable"
   ::= { gs2326pSSH 1 }

gs2326pHTTPS                                                 OBJECT IDENTIFIER ::= { gs2326pSecurity 8 }

gs2326pHTTPSMode OBJECT-TYPE
   SYNTAX      INTEGER { disable(0), enable(1) }
   MAX-ACCESS  read-write
   STATUS      current
   DESCRIPTION
       "default: 1
        0: disable
        1: enable"
   ::= { gs2326pHTTPS 1 }

gs2326pHTTPSAutoRedirect OBJECT-TYPE
   SYNTAX      INTEGER { disable(0), enable(1) }
   MAX-ACCESS  read-write
   STATUS      current
   DESCRIPTION
       "default: 0
        0: disable
        1: enable"
   ::= { gs2326pHTTPS 2 }

gs2326pHTTPSCertRenew OBJECT-TYPE
   SYNTAX      INTEGER { doNothing(0), renew(1) }
   MAX-ACCESS  read-write
   STATUS      current
   DESCRIPTION
       "default: 0 ,
        0: doNothing
        1: renew"
   ::= { gs2326pHTTPS 3 }

gs2326pHTTPSMinProtoVersion OBJECT-TYPE
   SYNTAX      INTEGER { SSLv3(0), TLSv1(1), TLSv11(2), TLSv12(3)}
   MAX-ACCESS  read-write
   STATUS      current
   DESCRIPTION
       "default: 1
        0: SSLv3
        1: TLSv1
        2: TLSv1.1
        3: TLSv1.2"
   ::= { gs2326pHTTPS 4 }

gs2326pHTTPMode OBJECT-TYPE
   SYNTAX      INTEGER { disable(0), enable(1) }
   MAX-ACCESS  read-write
   STATUS      current
   DESCRIPTION
       "default: 1
        0: disable
        1: enable"
   ::= { gs2326pHTTPS 5 }

gs2326pAuthMethod                                            OBJECT IDENTIFIER ::= { gs2326pSecurity 9 }

gs2326pConsoleAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pAuthMethod 1 }

gs2326pConsoleFallback OBJECT-TYPE
   SYNTAX      INTEGER { disable(0), enable(1) }
   MAX-ACCESS  read-write
   STATUS      current
   DESCRIPTION
       "default: 0
        0:disable
        1:enable"
   ::= { gs2326pAuthMethod 2 }

gs2326pTelnetAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pAuthMethod 3 }

gs2326pTelnetFallback OBJECT-TYPE
   SYNTAX      INTEGER { disable(0), enable(1) }
   MAX-ACCESS  read-write
   STATUS      current
   DESCRIPTION
       "default: 0
        0:disable
        1:enable"
   ::= { gs2326pAuthMethod 4 }

gs2326pSshAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pAuthMethod 5 }

gs2326pSshFallback OBJECT-TYPE
   SYNTAX      INTEGER { disable(0), enable(1) }
   MAX-ACCESS  read-write
   STATUS      current
   DESCRIPTION
       "default: 0
        0:disable
        1:enable"
   ::= { gs2326pAuthMethod 6 }

gs2326pTftpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pAuthMethod 9 }

gs2326pTftpFallback OBJECT-TYPE
   SYNTAX      INTEGER { disable(0), enable(1) }
   MAX-ACCESS  read-write
   STATUS      current
   DESCRIPTION
       "default: 0
        0:disable
        1:enable"
   ::= { gs2326pAuthMethod 10 }

gs2326pLoginFailures OBJECT-TYPE
   SYNTAX      Integer32(0..99)
   MAX-ACCESS  read-write
   STATUS      current
   DESCRIPTION
       "When login failures mechanism is triggered,the lock minutes will prevent to login in this periods.
        The value '0' should deactivate this feature.
        range: 0-99.
        default: 5."
   ::= { gs2326pAuthMethod 11 }

gs2326pLockMinutes OBJECT-TYPE
   SYNTAX      Integer32(1..99)
   MAX-ACCESS  read-write
   STATUS      current
   DESCRIPTION
       "Lock time to login failures trigger.
        range: 1-99.
        default: 5."
   ::= { gs2326pAuthMethod 12 }

gs2326pHttpAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pAuthMethod 13 }

gs2326pHttpFallback OBJECT-TYPE
   SYNTAX      INTEGER { disable(0), enable(1) }
   MAX-ACCESS  read-write
   STATUS      current
   DESCRIPTION
       "default: 0
        0:disable
        1:enable"
   ::= { gs2326pAuthMethod 14 }

gs2326pHttpsAuthMethod OBJECT-TYPE
   SYNTAX      INTEGER { none(0), local(1), radius(2), tacacsplus(3) }
   MAX-ACCESS  read-write
   STATUS      current
   DESCRIPTION
       "default: 1
        0: none
        1: local
        2: RADIUS
        3: TACACS+"
   ::= { gs2326pAuthMethod 15 }

gs2326pHttpsFallback OBJECT-TYPE
   SYNTAX      INTEGER { disable(0), enable(1) }
   MAX-ACCESS  read-write
   STATUS      current
   DESCRIPTION
       "default: 0
        0:disable
        1:enable"
   ::= { gs2326pAuthMethod 16 }


gs2326pAAA                                              OBJECT IDENTIFIER ::= { gs2326pSecurity 10 }

gs2326pAAACommonServer                                  OBJECT IDENTIFIER ::= { gs2326pAAA 1 }

gs2326pAAACommonServerTimeout OBJECT-TYPE
   SYNTAX      Integer32(3..3600)
   MAX-ACCESS  read-write
   STATUS      current
   DESCRIPTION
       "The Timeout, which can be set to a number between 3 and 3600 seconds, is
       the maximum time to wait for a reply from a server. If the server does not
       reply within this timeframe, we will consider it to be dead and continue
       with the next enabled server (if any). RADIUS servers are using the UDP
       protocol, which is unreliable by design. In order to cope with lost frames,
       the timeout interval is divided into 3 subintervals of equal length. If a
       reply is not received within the subinterval, the request is transmitted
       again. This algorithm causes the RADIUS server to be queried up to 3 times
       before it is considered to be dead.
        default: 15."
   ::= { gs2326pAAACommonServer 1 }

gs2326pAAACommonServerDeadTime OBJECT-TYPE
   SYNTAX      Integer32(0..3600)
   MAX-ACCESS  read-write
   STATUS      current
   DESCRIPTION
       "The Dead Time, which can be set to a number between 0 and 3600 seconds,
       is the period during which the switch will not send new requests to a
       server that has failed to respond to a previous request. This will stop
       the switch from continually trying to contact a server that it has already
       determined as dead.
       Setting the Dead Time to a value greater than 0 (zero) will enable this feature,
       but only if more than one server has been configured.
       default: 300."
   ::= { gs2326pAAACommonServer 2 }

gs2326pAAATACACSPlusAuthAndAccounting                  OBJECT IDENTIFIER ::= { gs2326pAAA 2 }

gs2326pAAAAuthorization OBJECT-TYPE
   SYNTAX      INTEGER { disable(0), enable(1) }
   MAX-ACCESS  read-write
   STATUS      current
   DESCRIPTION
       "Authorization is the action of determining what a user is allowed to do.
       An authorization request may indicate that the user is not authenticated.
       In this case it is up to the authorization agent to determine if an
       unauthenticated user is allowed the services in question. "
   ::= { gs2326pAAATACACSPlusAuthAndAccounting 1 }

gs2326pAAAFallbackToLocalAuthorization OBJECT-TYPE
   SYNTAX      INTEGER { disable(0), enable(1) }
   MAX-ACCESS  read-write
   STATUS      current
   DESCRIPTION
       "This function is an auxiliary function of Authorization. When the DUT
       cannot communicate with TACACS+ Server normally, it will check the right/
        permission level of the Local Account to execute the Authorization. "
   ::= { gs2326pAAATACACSPlusAuthAndAccounting 2 }

gs2326pAAAAccounting OBJECT-TYPE
   SYNTAX      INTEGER { disable(0), enable(1) }
   MAX-ACCESS  read-write
   STATUS      current
   DESCRIPTION
       "Accounting is typically the third action after authentication and
       authorization. Accounting is the action of recording what a user is doing,
       and/or has done. TACACS+ accounting records contain all the information
       used in the authorization records and resource usage information. "
   ::= { gs2326pAAATACACSPlusAuthAndAccounting 3 }

gs2326pRADIUSAuthenticationServerTable OBJECT-TYPE
   SYNTAX      SEQUENCE OF Gs2326pRADIUSAuthenticationServerEntry
   MAX-ACCESS  not-accessible
   STATUS      current
   DESCRIPTION
       " "
   ::= { gs2326pAAA 3 }

gs2326pRADIUSAuthenticationServerEntry OBJECT-TYPE
   SYNTAX      Gs2326pRADIUSAuthenticationServerEntry
   MAX-ACCESS  not-accessible
   STATUS      current
   DESCRIPTION
       ""
   INDEX    { gs2326pRADIUSAuthenticationServerIndex  }
   ::= { gs2326pRADIUSAuthenticationServerTable 1 }

Gs2326pRADIUSAuthenticationServerEntry ::= SEQUENCE {
   gs2326pRADIUSAuthenticationServerIndex     Integer32,
   gs2326pRADIUSAuthenticationServerEnable    INTEGER,
   gs2326pRADIUSAuthenticationServerIP        DisplayString,
   gs2326pRADIUSAuthenticationServerPort      Integer32,
   gs2326pRADIUSAuthenticationServerSecret    DisplayString
}

gs2326pRADIUSAuthenticationServerIndex OBJECT-TYPE
   SYNTAX      Integer32(1..5)
   MAX-ACCESS  not-accessible
   STATUS      current
   DESCRIPTION
       "RADIUS Authentication Server index
        range : 1-5."
   ::= { gs2326pRADIUSAuthenticationServerEntry 1 }

gs2326pRADIUSAuthenticationServerEnable OBJECT-TYPE
   SYNTAX      INTEGER { disable(0), enable(1) }
   MAX-ACCESS  read-write
   STATUS      current
   DESCRIPTION
       "Enable/Disable the RADIUS Authentication Server. the RADIUSAuthenticationServerEnable
       can be set, when IP and Secret have value "
   ::= { gs2326pRADIUSAuthenticationServerEntry 2 }

gs2326pRADIUSAuthenticationServerIP OBJECT-TYPE
   SYNTAX      DisplayString
   MAX-ACCESS  read-write
   STATUS      current
   DESCRIPTION
       "The IP address or hostname of the RADIUS Authentication Server.
       IP address is expressed in  dotted decimal notation. "
   ::= { gs2326pRADIUSAuthenticationServerEntry 3 }

gs2326pRADIUSAuthenticationServerPort OBJECT-TYPE
   SYNTAX      Integer32(0..65535)
   MAX-ACCESS  read-write
   STATUS      current
   DESCRIPTION
       "The UDP port to use on the RADIUS Authentication Server. If the port is
       set to 0 (zero), the default port (1812) is used on the RADIUS Authentication Server. "
   ::= { gs2326pRADIUSAuthenticationServerEntry 4 }

gs2326pRADIUSAuthenticationServerSecret OBJECT-TYPE
   SYNTAX      DisplayString
   MAX-ACCESS  read-write
   STATUS      current
   DESCRIPTION
       "The secret - up to 64 characters long - shared between the RADIUS Authentication Server and the switch. "
   ::= { gs2326pRADIUSAuthenticationServerEntry 5 }


gs2326pRADIUSAccountingServerTable OBJECT-TYPE
   SYNTAX      SEQUENCE OF Gs2326pRADIUSAccountingServerEntry
   MAX-ACCESS  not-accessible
   STATUS      current
   DESCRIPTION
       " "
   ::= { gs2326pAAA 4 }

gs2326pRADIUSAccountingServerEntry OBJECT-TYPE
   SYNTAX      Gs2326pRADIUSAccountingServerEntry
   MAX-ACCESS  not-accessible
   STATUS      current
   DESCRIPTION
       ""
   INDEX    { gs2326pRADIUSAccountingServerIndex  }
   ::= { gs2326pRADIUSAccountingServerTable 1 }

Gs2326pRADIUSAccountingServerEntry ::= SEQUENCE {
   gs2326pRADIUSAccountingServerIndex     Integer32,
   gs2326pRADIUSAccountingServerEnable    INTEGER,
   gs2326pRADIUSAccountingServerIP        DisplayString,
   gs2326pRADIUSAccountingServerPort      Integer32,
   gs2326pRADIUSAccountingServerSecret    DisplayString
}

gs2326pRADIUSAccountingServerIndex OBJECT-TYPE
   SYNTAX      Integer32(1..5)
   MAX-ACCESS  not-accessible
   STATUS      current
   DESCRIPTION
       "RADIUS Accounting Server index
        range : 1-5."
   ::= { gs2326pRADIUSAccountingServerEntry 1 }

gs2326pRADIUSAccountingServerEnable OBJECT-TYPE
   SYNTAX      INTEGER { disable(0), enable(1) }
   MAX-ACCESS  read-write
   STATUS      current
   DESCRIPTION
       "Enable/Disable the RADIUS Accounting Server. The RADIUSAccountingServerEnable
       can be set, when IP and Secret have value. "
   ::= { gs2326pRADIUSAccountingServerEntry 2 }

gs2326pRADIUSAccountingServerIP OBJECT-TYPE
   SYNTAX      DisplayString
   MAX-ACCESS  read-write
   STATUS      current
   DESCRIPTION
       "The IP address or hostname of the RADIUS Accounting Server.
       IP address is expressed in  dotted decimal notation. "
   ::= { gs2326pRADIUSAccountingServerEntry 3 }

gs2326pRADIUSAccountingServerPort OBJECT-TYPE
   SYNTAX      Integer32(0..65535)
   MAX-ACCESS  read-write
   STATUS      current
   DESCRIPTION
       "The UDP port to use on the RADIUS Accounting Server. If the port is
       set to 0 (zero), the default port (1812) is used on the RADIUS Accounting Server. "
   ::= { gs2326pRADIUSAccountingServerEntry 4 }

gs2326pRADIUSAccountingServerSecret OBJECT-TYPE
   SYNTAX      DisplayString
   MAX-ACCESS  read-write
   STATUS      current
   DESCRIPTION
       "The secret - up to 64 characters long - shared between the RADIUS Accounting Server and the switch. "
   ::= { gs2326pRADIUSAccountingServerEntry 5 }

gs2326pTACACSPlusAuthenticationServerTable OBJECT-TYPE
   SYNTAX      SEQUENCE OF Gs2326pTACACSPlusAuthenticationServerEntry
   MAX-ACCESS  not-accessible
   STATUS      current
   DESCRIPTION
       " "
   ::= { gs2326pAAA 5 }

gs2326pTACACSPlusAuthenticationServerEntry OBJECT-TYPE
   SYNTAX      Gs2326pTACACSPlusAuthenticationServerEntry
   MAX-ACCESS  not-accessible
   STATUS      current
   DESCRIPTION
       ""
   INDEX    { gs2326pTACACSPlusAuthenticationServerIndex  }
   ::= { gs2326pTACACSPlusAuthenticationServerTable 1 }

Gs2326pTACACSPlusAuthenticationServerEntry ::= SEQUENCE {
   gs2326pTACACSPlusAuthenticationServerIndex     Integer32,
   gs2326pTACACSPlusAuthenticationServerEnable    INTEGER,
   gs2326pTACACSPlusAuthenticationServerIP        DisplayString,
   gs2326pTACACSPlusAuthenticationServerPort      Integer32,
   gs2326pTACACSPlusAuthenticationServerSecret    DisplayString
}

gs2326pTACACSPlusAuthenticationServerIndex OBJECT-TYPE
   SYNTAX      Integer32(1..5)
   MAX-ACCESS  not-accessible
   STATUS      current
   DESCRIPTION
       "TACACSPlus Authentication Server index
        range : 1-5."
   ::= { gs2326pTACACSPlusAuthenticationServerEntry 1 }

gs2326pTACACSPlusAuthenticationServerEnable OBJECT-TYPE
   SYNTAX      INTEGER { disable(0), enable(1) }
   MAX-ACCESS  read-write
   STATUS      current
   DESCRIPTION
       "Enable/Disable the TACACSPlus Authentication Server. The
       TACACSPlusAuthenticationServerEnable can be set, when IP and Secret have
       value."
   ::= { gs2326pTACACSPlusAuthenticationServerEntry 2 }

gs2326pTACACSPlusAuthenticationServerIP OBJECT-TYPE
   SYNTAX      DisplayString
   MAX-ACCESS  read-write
   STATUS      current
   DESCRIPTION
       "The IP address or hostname of the TACACSPlus Authentication Server.
       IP address is expressed in  dotted decimal notation. "
   ::= { gs2326pTACACSPlusAuthenticationServerEntry 3 }

gs2326pTACACSPlusAuthenticationServerPort OBJECT-TYPE
   SYNTAX      Integer32(0..65535)
   MAX-ACCESS  read-write
   STATUS      current
   DESCRIPTION
       "The UDP port to use on the TACACSPlus Authentication Server. If the
       port is set to 0 (zero), the default port (1812) is used on the
       TACACSPlus Authentication Server. "
   ::= { gs2326pTACACSPlusAuthenticationServerEntry 4 }

gs2326pTACACSPlusAuthenticationServerSecret OBJECT-TYPE
   SYNTAX      DisplayString
   MAX-ACCESS  read-write
   STATUS      current
   DESCRIPTION
       "The secret - up to 64 characters long - shared between the TACACSPlus Authentication Server and the switch. "
   ::= { gs2326pTACACSPlusAuthenticationServerEntry 5 }


gs2326pRADIUSStatisticsTable OBJECT-TYPE
   SYNTAX      SEQUENCE OF Gs2326pRADIUSStatisticsEntry
   MAX-ACCESS  not-accessible
   STATUS      current
   DESCRIPTION
       " "
   ::= { gs2326pAAA 6 }

gs2326pRADIUSStatisticsEntry OBJECT-TYPE
   SYNTAX      Gs2326pRADIUSStatisticsEntry
   MAX-ACCESS  not-accessible
   STATUS      current
   DESCRIPTION
       ""
   INDEX    { gs2326pRADIUSAuthStatisticsServerIndex  }
   ::= { gs2326pRADIUSStatisticsTable 1 }

Gs2326pRADIUSStatisticsEntry ::= SEQUENCE {
   gs2326pRADIUSAuthStatisticsServerIndex                           Integer32,
   gs2326pRADIUSAuthStatisticsRecPktAccessAccepts                   Counter32,
   gs2326pRADIUSAuthStatisticsRecPktAccessRejects                   Counter32,
   gs2326pRADIUSAuthStatisticsRecPktAccessChallenges                Counter32,
   gs2326pRADIUSAuthStatisticsRecPktMalformedAccResponses           Counter32,
   gs2326pRADIUSAuthStatisticsRecPktBadAuthenticators               Counter32,
   gs2326pRADIUSAuthStatisticsRecPktUnknownTypes                    Counter32,
   gs2326pRADIUSAuthStatisticsRecPktDropped                         Counter32,
   gs2326pRADIUSAuthStatisticsTransmitPktAccessRequests             Counter32,
   gs2326pRADIUSAuthStatisticsTransmitPktAccessRetransmissions      Counter32,
   gs2326pRADIUSAuthStatisticsTransmitPktPendingRequests            Counter32,
   gs2326pRADIUSAuthStatisticsTransmitPktTimeouts                   Counter32,
   gs2326pRADIUSAuthIP                                              DisplayString,
   gs2326pRADIUSAuthState                                           DisplayString,
   gs2326pRADIUSAuthRoundTripTime                                   DisplayString,

   gs2326pRADIUSAccountingStatisticsRecPktResponses                 Counter32,
   gs2326pRADIUSAccountingStatisticsRecPktMalformedResponses        Counter32,
   gs2326pRADIUSAccountingStatisticsRecPktBadAuthenticators         Counter32,
   gs2326pRADIUSAccountingStatisticsRecPktUnknownTypes              Counter32,
   gs2326pRADIUSAccountingStatisticsRecPktDropped                   Counter32,
   gs2326pRADIUSAccountingStatisticsTransmitPktRequests             Counter32,
   gs2326pRADIUSAccountingStatisticsTransmitPktRetransmissions      Counter32,
   gs2326pRADIUSAccountingStatisticsTransmitPktPendingRequests      Counter32,
   gs2326pRADIUSAccountingStatisticsTransmitPktTimeouts             Counter32,
   gs2326pRADIUSAccountingIP                                        DisplayString,
   gs2326pRADIUSAccountingState                                     DisplayString,
   gs2326pRADIUSAccountingRoundTripTime                             DisplayString,
   gs2326pRADIUSStatisticsClear                                     INTEGER
}

gs2326pRADIUSAuthStatisticsServerIndex OBJECT-TYPE
   SYNTAX      Integer32(1..5)
   MAX-ACCESS  not-accessible
   STATUS      current
   DESCRIPTION
       "RADIUS Authentication Server index
        range : 1-5."
   ::= { gs2326pRADIUSStatisticsEntry 1 }

gs2326pRADIUSAuthStatisticsRecPktAccessAccepts OBJECT-TYPE
   SYNTAX      Counter32
   MAX-ACCESS  read-only
   STATUS      current
   DESCRIPTION
       "The number of RADIUS Access-Accept packets (valid or invalid) received from the server."
   ::= { gs2326pRADIUSStatisticsEntry 2 }

gs2326pRADIUSAuthStatisticsRecPktAccessRejects OBJECT-TYPE
   SYNTAX      Counter32
   MAX-ACCESS  read-only
   STATUS      current
   DESCRIPTION
       "The number of RADIUS Access-Reject packets (valid or invalid) received from the server."
   ::= { gs2326pRADIUSStatisticsEntry 3 }

gs2326pRADIUSAuthStatisticsRecPktAccessChallenges OBJECT-TYPE
   SYNTAX      Counter32
   MAX-ACCESS  read-only
   STATUS      current
   DESCRIPTION
       "The number of RADIUS Access-Challenge packets (valid or invalid) received from the server. "
   ::= { gs2326pRADIUSStatisticsEntry 4 }

gs2326pRADIUSAuthStatisticsRecPktMalformedAccResponses OBJECT-TYPE
   SYNTAX      Counter32
   MAX-ACCESS  read-only
   STATUS      current
   DESCRIPTION
       "The number of malformed RADIUS Access-Response packets received from the
        server. Malformed packets include packets with an invalid length. Bad
        authenticators or Message Authenticator attributes or unknown types are
        not included as malformed access responses. "
   ::= { gs2326pRADIUSStatisticsEntry 5 }

gs2326pRADIUSAuthStatisticsRecPktBadAuthenticators OBJECT-TYPE
   SYNTAX      Counter32
   MAX-ACCESS  read-only
   STATUS      current
   DESCRIPTION
       "The number of RADIUS Access-Response packets containing invalid
       authenticators or Message Authenticator attributes received from the server."
   ::= { gs2326pRADIUSStatisticsEntry 6 }

gs2326pRADIUSAuthStatisticsRecPktUnknownTypes OBJECT-TYPE
   SYNTAX      Counter32
   MAX-ACCESS  read-only
   STATUS      current
   DESCRIPTION
       "The number of RADIUS packets that were received with unknown types from
       the server on the authentication port and dropped."
   ::= { gs2326pRADIUSStatisticsEntry 7 }

gs2326pRADIUSAuthStatisticsRecPktDropped OBJECT-TYPE
   SYNTAX      Counter32
   MAX-ACCESS  read-only
   STATUS      current
   DESCRIPTION
       "The number of RADIUS packets that were received from the server on the
       authentication port and dropped for some other reason."
   ::= { gs2326pRADIUSStatisticsEntry 8 }

gs2326pRADIUSAuthStatisticsTransmitPktAccessRequests OBJECT-TYPE
   SYNTAX      Counter32
   MAX-ACCESS  read-only
   STATUS      current
   DESCRIPTION
       "The number of RADIUS Access-Request packets sent to the server. This
       does not include retransmissions."
   ::= { gs2326pRADIUSStatisticsEntry 9 }

gs2326pRADIUSAuthStatisticsTransmitPktAccessRetransmissions OBJECT-TYPE
   SYNTAX      Counter32
   MAX-ACCESS  read-only
   STATUS      current
   DESCRIPTION
       "The number of RADIUS Access-Request packets retransmitted to the RADIUS
       authentication server."
   ::= { gs2326pRADIUSStatisticsEntry 10 }

gs2326pRADIUSAuthStatisticsTransmitPktPendingRequests OBJECT-TYPE
   SYNTAX      Counter32
   MAX-ACCESS  read-only
   STATUS      current
   DESCRIPTION
       "The number of RADIUS Access-Request packets destined for the server that
        have not yet timed out or received a response. This variable is
        incremented when an Access-Request is sent and decremented due to
        receipt of an Access-Accept, Access-Reject, Access-Challenge, timeout,
        or retransmission. "
   ::= { gs2326pRADIUSStatisticsEntry 11 }

gs2326pRADIUSAuthStatisticsTransmitPktTimeouts OBJECT-TYPE
   SYNTAX      Counter32
   MAX-ACCESS  read-only
   STATUS      current
   DESCRIPTION
       "The number of authentication timeouts to the server. After a timeout,
       the client may retry to the same server, send to a different server, or
       give up. A retry to the same server is counted as a retransmit as well as
        a timeout. A send to a different server is counted as a Request as well
        as a timeout. "
   ::= { gs2326pRADIUSStatisticsEntry 12 }

gs2326pRADIUSAuthIP OBJECT-TYPE
   SYNTAX      DisplayString
   MAX-ACCESS  read-only
   STATUS      current
   DESCRIPTION
       "IP address and UDP port for the authentication server in question."
   ::= { gs2326pRADIUSStatisticsEntry 13 }

gs2326pRADIUSAuthState OBJECT-TYPE
   SYNTAX      DisplayString
   MAX-ACCESS  read-only
   STATUS      current
   DESCRIPTION
       "Shows the state of the server. It takes one of the following values:
        Disabled: The selected server is disabled.
        Not Ready: The server is enabled, but IP communication is not yet up and running.
        Ready: The server is enabled, IP communication is up and running, and the RADIUS
         module is ready to accept access attempts.
        Dead (X seconds left): Access attempts were made to this server, but it did not
        reply within the configured timeout. The server has temporarily been disabled,
        but will get re-enabled when the dead-time expires. The number of seconds left
        before this occurs is displayed in parentheses. This state is only reachable
        when more than one server is enabled. "
   ::= { gs2326pRADIUSStatisticsEntry 14 }

gs2326pRADIUSAuthRoundTripTime OBJECT-TYPE
   SYNTAX      DisplayString
   MAX-ACCESS  read-only
   STATUS      current
   DESCRIPTION
       "The time interval (measured in milliseconds) between the most recent
       Access-Reply/Access-Challenge and the Access-Request that matched it from
        the RADIUS authentication server. The granularity of this measurement is
         100 ms. A value of 0 ms indicates that there hasn't been round-trip
         communication with the server yet. "
   ::= { gs2326pRADIUSStatisticsEntry 15 }

gs2326pRADIUSAccountingStatisticsRecPktResponses OBJECT-TYPE
   SYNTAX      Counter32
   MAX-ACCESS  read-only
   STATUS      current
   DESCRIPTION
       "The number of RADIUS packets (valid or invalid) received from the server."
   ::= { gs2326pRADIUSStatisticsEntry 16 }

gs2326pRADIUSAccountingStatisticsRecPktMalformedResponses OBJECT-TYPE
   SYNTAX      Counter32
   MAX-ACCESS  read-only
   STATUS      current
   DESCRIPTION
       "The number of malformed RADIUS packets received from the server.
       Malformed packets include packets with an invalid length. Bad
       authenticators or unknown types are not included as malformed access
       responses. "
   ::= { gs2326pRADIUSStatisticsEntry 17 }

gs2326pRADIUSAccountingStatisticsRecPktBadAuthenticators OBJECT-TYPE
   SYNTAX      Counter32
   MAX-ACCESS  read-only
   STATUS      current
   DESCRIPTION
       "The number of RADIUS packets containing invalid authenticators received
       from the server."
   ::= { gs2326pRADIUSStatisticsEntry 18 }

gs2326pRADIUSAccountingStatisticsRecPktUnknownTypes OBJECT-TYPE
   SYNTAX      Counter32
   MAX-ACCESS  read-only
   STATUS      current
   DESCRIPTION
       "The number of RADIUS packets of unknown types that were received from
       the server on the accounting port."
   ::= { gs2326pRADIUSStatisticsEntry 19 }

gs2326pRADIUSAccountingStatisticsRecPktDropped OBJECT-TYPE
   SYNTAX      Counter32
   MAX-ACCESS  read-only
   STATUS      current
   DESCRIPTION
       "The number of RADIUS packets that were received from the server on the
       accounting port and dropped for some other reason."
   ::= { gs2326pRADIUSStatisticsEntry 20 }

gs2326pRADIUSAccountingStatisticsTransmitPktRequests OBJECT-TYPE
   SYNTAX      Counter32
   MAX-ACCESS  read-only
   STATUS      current
   DESCRIPTION
       "The number of RADIUS packets sent to the server. This does not include
       retransmissions."
   ::= { gs2326pRADIUSStatisticsEntry 21 }

gs2326pRADIUSAccountingStatisticsTransmitPktRetransmissions OBJECT-TYPE
   SYNTAX      Counter32
   MAX-ACCESS  read-only
   STATUS      current
   DESCRIPTION
       "The number of RADIUS packets retransmitted to the RADIUS accounting server."
   ::= { gs2326pRADIUSStatisticsEntry 22 }

gs2326pRADIUSAccountingStatisticsTransmitPktPendingRequests OBJECT-TYPE
   SYNTAX      Counter32
   MAX-ACCESS  read-only
   STATUS      current
   DESCRIPTION
       "The number of RADIUS packets destined for the server that have not yet
       timed out or received a response. This variable is incremented when a
       Request is sent and decremented due to receipt of a Response, timeout,
       or retransmission. "
   ::= { gs2326pRADIUSStatisticsEntry 23 }

gs2326pRADIUSAccountingStatisticsTransmitPktTimeouts OBJECT-TYPE
   SYNTAX      Counter32
   MAX-ACCESS  read-only
   STATUS      current
   DESCRIPTION
       "The number of accounting timeouts to the server. After a timeout, the
       client may retry to the same server, send to a different server, or give
       up. A retry to the same server is counted as a retransmit as well as a
       timeout. A send to a different server is counted as a Request as well as
       a timeout. "
   ::= { gs2326pRADIUSStatisticsEntry 24 }

gs2326pRADIUSAccountingIP OBJECT-TYPE
   SYNTAX      DisplayString
   MAX-ACCESS  read-only
   STATUS      current
   DESCRIPTION
       "IP address and UDP port for the accounting server in question."
   ::= { gs2326pRADIUSStatisticsEntry 25 }

gs2326pRADIUSAccountingState OBJECT-TYPE
   SYNTAX      DisplayString
   MAX-ACCESS  read-only
   STATUS      current
   DESCRIPTION
       " Shows the state of the server. It takes one of the following values:
        Disabled: The selected server is disabled.
        Not Ready: The server is enabled, but IP communication is not yet up and running.
        Ready: The server is enabled, IP communication is up and running, and the RADIUS
        module is ready to accept accounting attempts.
        Dead (X seconds left): Accounting attempts were made to this server, but it did
        not reply within the configured timeout. The server has temporarily been
        disabled, but will get re-enabled when the dead-time expires. The number of
        seconds left before this occurs is displayed in parentheses. This state is only
        reachable when more than one server is enabled.  "
   ::= { gs2326pRADIUSStatisticsEntry 26 }

gs2326pRADIUSAccountingRoundTripTime OBJECT-TYPE
   SYNTAX      DisplayString
   MAX-ACCESS  read-only
   STATUS      current
   DESCRIPTION
       "The time interval (measured in milliseconds) between the most recent
       Response and the Request that matched it from the RADIUS accounting
       server. The granularity of this measurement is 100 ms. A value of 0 ms
       indicates that there hasn't been round-trip communication with the server
       yet. "
   ::= { gs2326pRADIUSStatisticsEntry 27 }

gs2326pRADIUSStatisticsClear OBJECT-TYPE
   SYNTAX      INTEGER(0|1)
   MAX-ACCESS  read-write
   STATUS      current
   DESCRIPTION
       "Clears the counters for the server.
       read: always 0
       clear: set 1"
   ::= { gs2326pRADIUSStatisticsEntry 28 }


gs2326pNAS                                              OBJECT IDENTIFIER ::= { gs2326pSecurity 11 }

gs2326pNASConfiguration                                 OBJECT IDENTIFIER ::= { gs2326pNAS 1 }

gs2326pNASConfigMode OBJECT-TYPE
   SYNTAX      INTEGER { disable(0), enable(1) }
   MAX-ACCESS  read-write
   STATUS      current
   DESCRIPTION
       "Indicates if NAS is globally enabled or disabled on the switch.
	    If globally disabled, all ports are allowed forwarding of frames."
   ::= { gs2326pNASConfiguration 1 }

gs2326pNASConfigReauthEnabled OBJECT-TYPE
   SYNTAX      INTEGER { disable(0), enable(1) }
   MAX-ACCESS  read-write
   STATUS      current
   DESCRIPTION
       "If checked, successfully authenticated supplicants/clients are
	    reauthenticated after the interval specified by the Reauthentication
		Period. Reauthentication for 802.1X-enabled ports can be used to
		detect if a new device is plugged into a switch port or if a
		supplicant is no longer attached.
		For MAC-based ports, reauthentication is only useful if the RADIUS
		server configuration has changed. It does not involve communication
		between the switch and the client, and therefore doesn't imply that
		a client is still present on a port."
   ::= { gs2326pNASConfiguration 2 }

gs2326pNASConfigReauthPeriod OBJECT-TYPE
   SYNTAX      Integer32(1..3600)
   MAX-ACCESS  read-write
   STATUS      current
   DESCRIPTION
       "Determines the period, in seconds, after which a connected client must
	    be reauthenticated. This is only active if the Reauthentication Enabled
		checkbox is checked.
		range: 1 - 3600 seconds."
   ::= { gs2326pNASConfiguration 3 }

gs2326pNASConfigEAPOLTimeout OBJECT-TYPE
   SYNTAX      Integer32(1..65535)
   MAX-ACCESS  read-write
   STATUS      current
   DESCRIPTION
       "Determines the time for retransmission of Request Identity EAPOL frames.
	    This has no effect for MAC-based ports.
		range: 1 - 65535 seconds."
   ::= { gs2326pNASConfiguration 4 }

gs2326pNASConfigAgingPeriod OBJECT-TYPE
   SYNTAX      Integer32(10..1000000)
   MAX-ACCESS  read-write
   STATUS      current
   DESCRIPTION
       "When the NAS module uses the Port Security module to secure MAC addresses,
	    the Port Security module needs to check for activity on the MAC address
		in question at regular intervals and free resources if no activity
		is seen within a given period of time.
		Admin State supported : Single, Multi and MAC-Based Auth. 802.1X.
		range: 10 - 1000000 seconds."
   ::= { gs2326pNASConfiguration 5 }

gs2326pNASConfigHoldTime OBJECT-TYPE
   SYNTAX      Integer32(10..1000000)
   MAX-ACCESS  read-write
   STATUS      current
   DESCRIPTION
       "If a client is denied access - either because the RADIUS server denies
	    the client access or because the RADIUS server request times out
		- the client is put on hold in the Unauthorized state. The hold timer
		does not count during an on-going authentication. In MAC-based Auth.
		mode, the switch will ignore new frames coming from the client during
		the hold time.
		Admin State supported : Single, Multi and MAC-Based Auth. 802.1X.
		range: 10 - 1000000 seconds."
   ::= { gs2326pNASConfiguration 6 }

gs2326pNASConfigRADIUSAssignedQoSEnabled OBJECT-TYPE
   SYNTAX      INTEGER { disable(0), enable(1) }
   MAX-ACCESS  read-write
   STATUS      current
   DESCRIPTION
       "RADIUS-assigned QoS provides a means to centrally control the
	    traffic class to which traffic coming from a successfully authenticated
		supplicant is assigned on the switch. The RADIUS server must be configured
		to transmit special RADIUS attributes to take advantage of this feature."
   ::= { gs2326pNASConfiguration 7 }

gs2326pNASConfigRADIUSAssignedVLANEnabled OBJECT-TYPE
   SYNTAX      INTEGER { disable(0), enable(1) }
   MAX-ACCESS  read-write
   STATUS      current
   DESCRIPTION
       "RADIUS-assigned VLAN provides a means to centrally control the VLAN on
	    which a successfully authenticated supplicant is placed on the switch.
	    Incoming traffic will be classified to and switched on the RADIUS-assigned
		VLAN. The RADIUS server must be configured to transmit special RADIUS
		attributes to take advantage of this feature.When enable, the individual
		ports' ditto setting determine whether RADIUS-assigned VLAN is enabled
		on that port. When disable, RADIUS-server assigned VLAN is disabled on
		all ports. "
   ::= { gs2326pNASConfiguration 8 }

gs2326pNASConfigGuestVLANEnabled OBJECT-TYPE
   SYNTAX      INTEGER { disable(0), enable(1) }
   MAX-ACCESS  read-write
   STATUS      current
   DESCRIPTION
       "A Guest VLAN is a special VLAN - typically with limited network access -
	   on which 802.1X-unaware clients are placed after a network administrator-defined
	   timeout. The switch follows a set of rules for entering and leaving the Guest
	   VLAN as listed below.When enable, the individual ports' ditto setting determines
	   whether the port can be moved into Guest VLAN. When disable, the ability to
	   move to the Guest VLAN is disabled on all ports. "
   ::= { gs2326pNASConfiguration 9 }

gs2326pNASConfigGuestVLANID OBJECT-TYPE
   SYNTAX      Integer32(1..4094)
   MAX-ACCESS  read-write
   STATUS      current
   DESCRIPTION
       "This is the value that a port's Port VLAN ID is set to if a port is moved into
	   the Guest VLAN. It is only changeable if the Guest VLAN option is globally enabled.
	   range: 1 - 4094."
   ::= { gs2326pNASConfiguration 10 }

gs2326pNASConfigMaxReauthCount OBJECT-TYPE
   SYNTAX      Integer32(1..255)
   MAX-ACCESS  read-write
   STATUS      current
   DESCRIPTION
       "The number of times the switch transmits an EAPOL Request Identity frame without
	   response before considering entering the Guest VLAN is adjusted with this setting.
	   The value can only be changed if the Guest VLAN option is globally enabled.
	   range: 1 - 255."
   ::= { gs2326pNASConfiguration 11 }

gs2326pNASConfigAllowGuestVLANEAPOLSeen OBJECT-TYPE
   SYNTAX      INTEGER { disable(0), enable(1) }
   MAX-ACCESS  read-write
   STATUS      current
   DESCRIPTION
       "The switch remembers if an EAPOL frame has been received on the port for the
	   life-time of the port. Once the switch considers whether to enter the Guest VLAN,
	   it will first check if this option is enabled or disabled. If disabled, the switch
	   will only enter the Guest VLAN if an EAPOL frame has not been received on the port
	   for the life-time of the port. If enabled (checked), the switch will consider
	   entering the Guest VLAN even if an EAPOL frame has been received on the port for
	   the life-time of the port.The value can only be changed if the Guest VLAN option
	   is globally enabled."
   ::= { gs2326pNASConfiguration 12 }

gs2326pNASConfigMacBasedUseEAP OBJECT-TYPE
   SYNTAX      INTEGER { disable(0), enable(1) }
   MAX-ACCESS  read-write
   STATUS      current
   DESCRIPTION
       "The switch can do the RADIUS authentication on behalf of the client in the
       MAC-based Auth. port authentication mode. It can either present itself as a
       normal 802.1X client to the RADIUS Server and use EAP, supporting only the
       MD5-Challenge, or alternativly can use plain RADIUS with username / passwort
       authentification without EAP if this setting is disabled."
   ::= { gs2326pNASConfiguration 101 }

gs2326pNASPortConfigTable OBJECT-TYPE
   SYNTAX      SEQUENCE OF Gs2326pNASPortConfigEntry
   MAX-ACCESS  not-accessible
   STATUS      current
   DESCRIPTION
       ""
   ::= { gs2326pNASConfiguration 13 }

gs2326pNASPortConfigEntry OBJECT-TYPE
   SYNTAX      Gs2326pNASPortConfigEntry
   MAX-ACCESS  not-accessible
   STATUS      current
   DESCRIPTION
       ""
   INDEX    { gs2326pNASPortConfigPort }
   ::= { gs2326pNASPortConfigTable 1 }

Gs2326pNASPortConfigEntry ::= SEQUENCE {
   gs2326pNASPortConfigPort                       Integer32,
   gs2326pNASPortConfigAdminState                 INTEGER,
   gs2326pNASPortConfigRADIUSAssignedQoSEnabled	  INTEGER,
   gs2326pNASPortConfigRADIUSAssignedVLANEnabled  INTEGER,
   gs2326pNASPortConfigGuestVLANEnabled           INTEGER,
   gs2326pNASPortConfigFallbackEnabled            INTEGER,
   gs2326pNASPortConfigPortState                  DisplayString,
   gs2326pNASPortConfigReauthenticate             INTEGER,
   gs2326pNASPortConfigReinitialize               INTEGER
}

gs2326pNASPortConfigPort OBJECT-TYPE
   SYNTAX      Integer32(1..255)
   MAX-ACCESS  not-accessible
   STATUS      current
   DESCRIPTION
       " port, range : 1 - port number. "
   ::= { gs2326pNASPortConfigEntry 1 }

gs2326pNASPortConfigAdminState OBJECT-TYPE
   SYNTAX      INTEGER{ forceAuthorized(1),
						forceUnauthorized(2),
						portBased(3),
						single(4),
						multi(5),
						macBased(6),
						macBasedSingle(7)
					  }
   MAX-ACCESS  read-write
   STATUS      current
   DESCRIPTION
       "This selection controls the port's authentication mode.
		1: Force Authorized,
		2: Force Unauthorized,
		3: Port-based 802.1X,
		4: Single 802.1X,
		5: Multi 802.1X,
		6: MAC-based Auth,
		7: MAC-based Single Auth."
   ::= { gs2326pNASPortConfigEntry 2 }

gs2326pNASPortConfigRADIUSAssignedQoSEnabled OBJECT-TYPE
   SYNTAX      INTEGER { disable(0), enable(1) }
   MAX-ACCESS  read-write
   STATUS      current
   DESCRIPTION
       "When RADIUS-Assigned QoS is both globally enabled and enabled (checked)
	    on a given port, the switch reacts to QoS Class information carried in
		the RADIUS Access-Accept packet transmitted by the RADIUS server when a
		supplicant is successfully authenticated. If present and valid, traffic
		received on the supplicant's port will be classified to the given QoS Class.
		Admin State supported : Port-based and Single 802.1X and MAC-based Single Auth."
   ::= { gs2326pNASPortConfigEntry 3 }

gs2326pNASPortConfigRADIUSAssignedVLANEnabled OBJECT-TYPE
   SYNTAX      INTEGER { disable(0), enable(1) }
   MAX-ACCESS  read-write
   STATUS      current
   DESCRIPTION
       "When RADIUS-Assigned VLAN is both globally enabled and enabled (checked)
	   for a given port, the switch reacts to VLAN ID information carried in the
	   RADIUS Access-Accept packet transmitted by the RADIUS server when a supplicant
	   is successfully authenticated. If present and valid, the port's Port VLAN ID
	   will be changed to this VLAN ID, the port will be set to be a member of that
	   VLAN ID, and the port will be forced into VLAN unaware mode. Once assigned,
	   all traffic arriving on the port will be classified and switched on the
	   RADIUS-assigned VLAN ID.
	   Admin State supported : Port-based and Single 802.1X and MAC-based Single Auth."
   ::= { gs2326pNASPortConfigEntry 4 }

gs2326pNASPortConfigGuestVLANEnabled OBJECT-TYPE
   SYNTAX      INTEGER { disable(0), enable(1) }
   MAX-ACCESS  read-write
   STATUS      current
   DESCRIPTION
       "When Guest VLAN is both globally enabled and enabled (checked) for a given port,
	   the switch considers moving the port into the Guest VLAN according to the rules
	   outlined below.
	   Admin State supported : Port-based , Single and Multi 802.1X."
   ::= { gs2326pNASPortConfigEntry 5 }

gs2326pNASPortConfigPortState OBJECT-TYPE
   SYNTAX      DisplayString
   MAX-ACCESS  read-only
   STATUS      current
   DESCRIPTION
       "Globally Disabled: NAS is globally disabled.
		Link Down: NAS is globally enabled, but there is no link on the port.
		Authorized: The port is in Force Authorized or a single-supplicant mode
		and the supplicant is authorized.
		Unauthorized: The port is in Force Unauthorized or a single-supplicant
		mode and the supplicant is not successfully authorized by the RADIUS server.
		X Auth/Y Unauth: The port is in a multi-supplicant mode. Currently X clients
		are authorized and Y are unauthorized."
   ::= { gs2326pNASPortConfigEntry 6 }

gs2326pNASPortConfigReauthenticate OBJECT-TYPE
   SYNTAX      INTEGER { doNothing(0), do(1) }
   MAX-ACCESS  read-write
   STATUS      current
   DESCRIPTION
       "Schedules a reauthentication whenever the quiet-period of the port runs out
	   (EAPOL-based authentication). For MAC-based authentication, reauthentication
	   will be attempted immediately.The button only has effect for successfully
	   authenticated clients on the port and will not cause the clients to get
	   temporarily unauthorized."
   ::= { gs2326pNASPortConfigEntry 7 }

gs2326pNASPortConfigReinitialize OBJECT-TYPE
   SYNTAX      INTEGER { doNothing(0), do(1) }
   MAX-ACCESS  read-write
   STATUS      current
   DESCRIPTION
       "Forces a reinitialization of the clients on the port and thereby a reauthentication
	   immediately. The clients will transfer to the unauthorized state while the
	   reauthentication is in progress."
   ::= { gs2326pNASPortConfigEntry 8 }

gs2326pNASPortConfigFallbackEnabled OBJECT-TYPE
   SYNTAX      INTEGER { disable(0), enable(1) }
   MAX-ACCESS  read-write
   STATUS      current
   DESCRIPTION
       "When Fallback is enabled, the switch will take over the supplicants role
       after max reauthentication count is reached and tries to authenticate the
       client on its behalf as described for MAC-based Auth.
       Admin State supported : Single and Multi 802.1X."
   ::= { gs2326pNASPortConfigEntry 101 }

gs2326pNASSwitchStatusTable OBJECT-TYPE
   SYNTAX      SEQUENCE OF Gs2326pNASSwitchStatusEntry
   MAX-ACCESS  not-accessible
   STATUS      current
   DESCRIPTION
       ""
   ::= { gs2326pNAS 2 }

gs2326pNASSwitchStatusEntry OBJECT-TYPE
   SYNTAX      Gs2326pNASSwitchStatusEntry
   MAX-ACCESS  not-accessible
   STATUS      current
   DESCRIPTION
       ""
   INDEX    { gs2326pNASPortConfigPort }
   ::= { gs2326pNASSwitchStatusTable 1 }

Gs2326pNASSwitchStatusEntry ::= SEQUENCE {
   gs2326pNASSwitchStatusAdminState 	DisplayString,
   gs2326pNASSwitchStatusPortState		DisplayString,
   gs2326pNASSwitchStatusLastSource		DisplayString,
   gs2326pNASSwitchStatusLastID			DisplayString,
   gs2326pNASSwitchStatusQoSClass		DisplayString,
   gs2326pNASSwitchStatusPortVlanID		DisplayString
}

gs2326pNASSwitchStatusAdminState OBJECT-TYPE
   SYNTAX      DisplayString
   MAX-ACCESS  read-only
   STATUS      current
   DESCRIPTION
       "The port's current administrative state. Refer to NAS Admin State for a description of possible values."
   ::= { gs2326pNASSwitchStatusEntry 2 }

gs2326pNASSwitchStatusPortState OBJECT-TYPE
   SYNTAX      DisplayString
   MAX-ACCESS  read-only
   STATUS      current
   DESCRIPTION
       "The current state of the port. Refer to NAS Port State for a description of the individual states."
   ::= { gs2326pNASSwitchStatusEntry 3 }

gs2326pNASSwitchStatusLastSource OBJECT-TYPE
   SYNTAX      DisplayString
   MAX-ACCESS  read-only
   STATUS      current
   DESCRIPTION
       "The source MAC address carried in the most recently received EAPOL frame for EAPOL-based authentication,
	   and the most recently received frame from a new client for MAC-based authentication."
   ::= { gs2326pNASSwitchStatusEntry 4 }

gs2326pNASSwitchStatusLastID OBJECT-TYPE
   SYNTAX      DisplayString
   MAX-ACCESS  read-only
   STATUS      current
   DESCRIPTION
       "The user name (supplicant identity) carried in the most recently received Response Identity EAPOL frame
	   for EAPOL-based authentication, and the source MAC address from the most recently received frame from a
	   new client for MAC-based authentication."
   ::= { gs2326pNASSwitchStatusEntry 5 }

gs2326pNASSwitchStatusQoSClass OBJECT-TYPE
   SYNTAX      DisplayString
   MAX-ACCESS  read-only
   STATUS      current
   DESCRIPTION
       "QoS Class assigned to the port by the RADIUS server if enabled."
   ::= { gs2326pNASSwitchStatusEntry 6 }

gs2326pNASSwitchStatusPortVlanID OBJECT-TYPE
   SYNTAX      DisplayString
   MAX-ACCESS  read-only
   STATUS      current
   DESCRIPTION
       "The VLAN ID that NAS has put the port in. The field is blank, if the Port VLAN ID is not overridden by NAS."
   ::= { gs2326pNASSwitchStatusEntry 7 }

gs2326pNASPortStatus                                 OBJECT IDENTIFIER ::= { gs2326pNAS 3 }

gs2326pNASPortStatusCountersTable OBJECT-TYPE
   SYNTAX      SEQUENCE OF Gs2326pNASPortStatusCountersEntry
   MAX-ACCESS  not-accessible
   STATUS      current
   DESCRIPTION
       ""
   ::= { gs2326pNASPortStatus 1 }

gs2326pNASPortStatusCountersEntry OBJECT-TYPE
   SYNTAX      Gs2326pNASPortStatusCountersEntry
   MAX-ACCESS  not-accessible
   STATUS      current
   DESCRIPTION
       ""
   INDEX    { gs2326pNASPortConfigPort }
   ::= { gs2326pNASPortStatusCountersTable 1 }

Gs2326pNASPortStatusCountersEntry ::= SEQUENCE {
   gs2326pNASRxCountersEAPOLTotal  	                  Counter32,
   gs2326pNASRxCountersEAPOLResponseID	              Counter32,
   gs2326pNASRxCountersEAPOLResponses	              Counter32,
   gs2326pNASRxCountersEAPOLStart	                  Counter32,
   gs2326pNASRxCountersEAPOLLogoff                    Counter32,
   gs2326pNASRxCountersEAPOLInvalidType               Counter32,
   gs2326pNASRxCountersEAPOLInvalidLength             Counter32,
   gs2326pNASTxCountersEAPOLTotal                     Counter32,
   gs2326pNASTxCountersEAPOLRequestID                 Counter32,
   gs2326pNASTxCountersEAPOLRequests                  Counter32,
   gs2326pNASRxBackendServerCountersAccessChallenges  Counter32,
   gs2326pNASRxBackendServerCountersOtherRequests     Counter32,
   gs2326pNASRxBackendServerCountersAuthSuccesses     Counter32,
   gs2326pNASRxBackendServerCountersAuthFailures      Counter32,
   gs2326pNASTxBackendServerCountersResponses         Counter32,
   gs2326pNASLastSupplicantInfoMACAddress             DisplayString,
   gs2326pNASLastSupplicantInfoVlanID                 Integer32,
   gs2326pNASLastSupplicantInfoVersion                Integer32,
   gs2326pNASLastSupplicantInfoIdentity               DisplayString,
   gs2326pNASCountersDoClear                          INTEGER
}

gs2326pNASRxCountersEAPOLTotal OBJECT-TYPE
   SYNTAX      Counter32
   MAX-ACCESS  read-only
   STATUS      current
   DESCRIPTION
       "The number of valid EAPOL frames of any type that have been received by the switch."
   ::= { gs2326pNASPortStatusCountersEntry 2 }

gs2326pNASRxCountersEAPOLResponseID OBJECT-TYPE
   SYNTAX      Counter32
   MAX-ACCESS  read-only
   STATUS      current
   DESCRIPTION
       "The number of valid EAPOL Response Identity frames that have been received by the switch."
   ::= { gs2326pNASPortStatusCountersEntry 3 }

gs2326pNASRxCountersEAPOLResponses OBJECT-TYPE
   SYNTAX      Counter32
   MAX-ACCESS  read-only
   STATUS      current
   DESCRIPTION
       "The number of valid EAPOL response frames (other than Response Identity frames)
	   that have been received by the switch."
   ::= { gs2326pNASPortStatusCountersEntry 4 }

gs2326pNASRxCountersEAPOLStart OBJECT-TYPE
   SYNTAX      Counter32
   MAX-ACCESS  read-only
   STATUS      current
   DESCRIPTION
       "The number of EAPOL Start frames that have been received by the switch."
   ::= { gs2326pNASPortStatusCountersEntry 5 }

gs2326pNASRxCountersEAPOLLogoff OBJECT-TYPE
   SYNTAX      Counter32
   MAX-ACCESS  read-only
   STATUS      current
   DESCRIPTION
       "The number of valid EAPOL Logoff frames that have been received by the switch."
   ::= { gs2326pNASPortStatusCountersEntry 6 }

gs2326pNASRxCountersEAPOLInvalidType OBJECT-TYPE
   SYNTAX      Counter32
   MAX-ACCESS  read-only
   STATUS      current
   DESCRIPTION
       "The number of EAPOL frames that have been received by the switch in which
	   the frame type is not recognized."
   ::= { gs2326pNASPortStatusCountersEntry 7 }

gs2326pNASRxCountersEAPOLInvalidLength OBJECT-TYPE
   SYNTAX      Counter32
   MAX-ACCESS  read-only
   STATUS      current
   DESCRIPTION
       "The number of EAPOL frames that have been received by the switch in which the
	   Packet Body Length field is invalid."
   ::= { gs2326pNASPortStatusCountersEntry 8 }

gs2326pNASTxCountersEAPOLTotal OBJECT-TYPE
   SYNTAX      Counter32
   MAX-ACCESS  read-only
   STATUS      current
   DESCRIPTION
       "The number of EAPOL frames of any type that have been transmitted by the switch."
   ::= { gs2326pNASPortStatusCountersEntry 9 }

gs2326pNASTxCountersEAPOLRequestID OBJECT-TYPE
   SYNTAX      Counter32
   MAX-ACCESS  read-only
   STATUS      current
   DESCRIPTION
       "The number of EAPOL Request Identity frames that have been transmitted by the switch."
   ::= { gs2326pNASPortStatusCountersEntry 10 }

gs2326pNASTxCountersEAPOLRequests OBJECT-TYPE
   SYNTAX      Counter32
   MAX-ACCESS  read-only
   STATUS      current
   DESCRIPTION
       "The number of valid EAPOL Request frames (other than Request Identity frames)
	   that have been transmitted by the switch."
   ::= { gs2326pNASPortStatusCountersEntry 11 }

gs2326pNASRxBackendServerCountersAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2326pNASPortStatusCountersEntry 12 }

gs2326pNASRxBackendServerCountersOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2326pNASPortStatusCountersEntry 13 }

gs2326pNASRxBackendServerCountersAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2326pNASPortStatusCountersEntry 14 }

gs2326pNASRxBackendServerCountersAuthFailures OBJECT-TYPE
   SYNTAX      Counter32
   MAX-ACCESS  read-only
   STATUS      current
   DESCRIPTION
       "Counts the number of times that the switch receives a failure message.
	   This indicates that the supplicant/client has not authenticated to the
	   backend server. "
   ::= { gs2326pNASPortStatusCountersEntry 15 }

gs2326pNASTxBackendServerCountersResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2326pNASPortStatusCountersEntry 16 }

gs2326pNASLastSupplicantInfoMACAddress OBJECT-TYPE
   SYNTAX      DisplayString
   MAX-ACCESS  read-only
   STATUS      current
   DESCRIPTION
       "The MAC address of the last supplicant/client."
   ::= { gs2326pNASPortStatusCountersEntry 17 }

gs2326pNASLastSupplicantInfoVlanID OBJECT-TYPE
   SYNTAX      Integer32
   MAX-ACCESS  read-only
   STATUS      current
   DESCRIPTION
       "The VLAN ID on which the last frame from the last supplicant/client was received."
   ::= { gs2326pNASPortStatusCountersEntry 18 }

gs2326pNASLastSupplicantInfoVersion OBJECT-TYPE
   SYNTAX      Integer32
   MAX-ACCESS  read-only
   STATUS      current
   DESCRIPTION
       "802.1X-based: The protocol version number carried in the most recently
	   received EAPOL frame.
	   MAC-based: Not applicable."
   ::= { gs2326pNASPortStatusCountersEntry 19 }

gs2326pNASLastSupplicantInfoIdentity OBJECT-TYPE
   SYNTAX      DisplayString
   MAX-ACCESS  read-only
   STATUS      current
   DESCRIPTION
       "802.1X-based: The user name (supplicant identity) carried in the most recently received
	   Response Identity EAPOL frame.
	   MAC-based: Not applicable."
   ::= { gs2326pNASPortStatusCountersEntry 20 }

gs2326pNASCountersDoClear OBJECT-TYPE
   SYNTAX      INTEGER { doNothing(0), do(1) }
   MAX-ACCESS  read-write
   STATUS      current
   DESCRIPTION
       "Clear the counters for the selected port."
   ::= { gs2326pNASPortStatusCountersEntry 21 }

gs2326pNASPortStatusClientsTable OBJECT-TYPE
   SYNTAX      SEQUENCE OF Gs2326pNASPortStatusClientsEntry
   MAX-ACCESS  not-accessible
   STATUS      current
   DESCRIPTION
       ""
   ::= { gs2326pNASPortStatus 2 }

gs2326pNASPortStatusClientsEntry OBJECT-TYPE
   SYNTAX      Gs2326pNASPortStatusClientsEntry
   MAX-ACCESS  not-accessible
   STATUS      current
   DESCRIPTION
       ""
   INDEX    { gs2326pNASPortConfigPort,
		gs2326pNASClientsIndex}
   ::= { gs2326pNASPortStatusClientsTable 1 }

Gs2326pNASPortStatusClientsEntry ::= SEQUENCE {
   gs2326pNASClientsIndex  	                  		    Integer32,
   gs2326pNASClientsIdentity							DisplayString,
   gs2326pNASClientsMACAddress  	                  	DisplayString,
   gs2326pNASClientsVlanID		              			Integer32,
   gs2326pNASClientsState	              				DisplayString,
   gs2326pNASClientsLastAuth	                  		DisplayString,
   gs2326pNASRxClientsEAPOLTotal  	                  	Counter32,
   gs2326pNASRxClientsEAPOLResponseID	              	Counter32,
   gs2326pNASRxClientsEAPOLResponses	              	Counter32,
   gs2326pNASRxClientsEAPOLStart	                  	Counter32,
   gs2326pNASRxClientsEAPOLLogoff                    	Counter32,
   gs2326pNASRxClientsEAPOLInvalidType               	Counter32,
   gs2326pNASRxClientsEAPOLInvalidLength             	Counter32,
   gs2326pNASTxClientsEAPOLTotal                     	Counter32,
   gs2326pNASTxClientsEAPOLRequestID                 	Counter32,
   gs2326pNASTxClientsEAPOLRequests                  	Counter32,
   gs2326pNASRxBackendServerClientsAccessChallenges  	Counter32,
   gs2326pNASRxBackendServerClientsOtherRequests     	Counter32,
   gs2326pNASRxBackendServerClientsAuthSuccesses     	Counter32,
   gs2326pNASRxBackendServerClientsAuthFailures      	Counter32,
   gs2326pNASTxBackendServerClientsResponses         	Counter32
}

gs2326pNASClientsIndex OBJECT-TYPE
   SYNTAX      Integer32(1..255)
   MAX-ACCESS  not-accessible
   STATUS      current
   DESCRIPTION
       "Entry of client table in the port."
   ::= { gs2326pNASPortStatusClientsEntry 1 }

gs2326pNASClientsIdentity OBJECT-TYPE
   SYNTAX      DisplayString
   MAX-ACCESS  read-only
   STATUS      current
   DESCRIPTION
       "Shows the identity of the supplicant, as received in the Response Identity
	   EAPOL frame.This isn't available for MAC-based Auth."
   ::= { gs2326pNASPortStatusClientsEntry 2 }

gs2326pNASClientsMACAddress OBJECT-TYPE
   SYNTAX      DisplayString
   MAX-ACCESS  read-only
   STATUS      current
   DESCRIPTION
       "Multi 802.1X, this column holds the MAC address of the attached supplicant.
	   MAC-based Auth., this column holds the MAC address of the attached client."
   ::= { gs2326pNASPortStatusClientsEntry 3 }

gs2326pNASClientsVlanID OBJECT-TYPE
   SYNTAX      Integer32(1..4095)
   MAX-ACCESS  read-only
   STATUS      current
   DESCRIPTION
       "This column holds the VLAN ID that the corresponding client is currently
	   secured through the Port Security module."
   ::= { gs2326pNASPortStatusClientsEntry 4 }

gs2326pNASClientsState OBJECT-TYPE
   SYNTAX      DisplayString
   MAX-ACCESS  read-only
   STATUS      current
   DESCRIPTION
       "The client can either be authenticated or unauthenticated. In the authenticated
	   state, it is allowed to forward frames on the port, and in the unauthenticated
	   state, it is blocked."
   ::= { gs2326pNASPortStatusClientsEntry 5 }

gs2326pNASClientsLastAuth OBJECT-TYPE
   SYNTAX      DisplayString
   MAX-ACCESS  read-only
   STATUS      current
   DESCRIPTION
       "Shows the date and time of the last authentication of the client."
   ::= { gs2326pNASPortStatusClientsEntry 6 }

gs2326pNASRxClientsEAPOLTotal OBJECT-TYPE
   SYNTAX      Counter32
   MAX-ACCESS  read-only
   STATUS      current
   DESCRIPTION
       "The number of valid EAPOL frames of any type that have been received by the switch."
   ::= { gs2326pNASPortStatusClientsEntry 7 }

gs2326pNASRxClientsEAPOLResponseID OBJECT-TYPE
   SYNTAX      Counter32
   MAX-ACCESS  read-only
   STATUS      current
   DESCRIPTION
       "The number of valid EAPOL Response Identity frames that have been received by the switch."
   ::= { gs2326pNASPortStatusClientsEntry 8 }

gs2326pNASRxClientsEAPOLResponses OBJECT-TYPE
   SYNTAX      Counter32
   MAX-ACCESS  read-only
   STATUS      current
   DESCRIPTION
       "The number of valid EAPOL response frames (other than Response Identity frames)
	   that have been received by the switch."
   ::= { gs2326pNASPortStatusClientsEntry 9 }

gs2326pNASRxClientsEAPOLStart OBJECT-TYPE
   SYNTAX      Counter32
   MAX-ACCESS  read-only
   STATUS      current
   DESCRIPTION
       "The number of EAPOL Start frames that have been received by the switch."
   ::= { gs2326pNASPortStatusClientsEntry 10 }

gs2326pNASRxClientsEAPOLLogoff OBJECT-TYPE
   SYNTAX      Counter32
   MAX-ACCESS  read-only
   STATUS      current
   DESCRIPTION
       "The number of valid EAPOL Logoff frames that have been received by the switch."
   ::= { gs2326pNASPortStatusClientsEntry 11 }

gs2326pNASRxClientsEAPOLInvalidType OBJECT-TYPE
   SYNTAX      Counter32
   MAX-ACCESS  read-only
   STATUS      current
   DESCRIPTION
       "The number of EAPOL frames that have been received by the switch in which
	   the frame type is not recognized."
   ::= { gs2326pNASPortStatusClientsEntry 12 }

gs2326pNASRxClientsEAPOLInvalidLength OBJECT-TYPE
   SYNTAX      Counter32
   MAX-ACCESS  read-only
   STATUS      current
   DESCRIPTION
       "The number of EAPOL frames that have been received by the switch in which the
	   Packet Body Length field is invalid."
   ::= { gs2326pNASPortStatusClientsEntry 13 }

gs2326pNASTxClientsEAPOLTotal OBJECT-TYPE
   SYNTAX      Counter32
   MAX-ACCESS  read-only
   STATUS      current
   DESCRIPTION
       "The number of EAPOL frames of any type that have been transmitted by the switch."
   ::= { gs2326pNASPortStatusClientsEntry 14 }

gs2326pNASTxClientsEAPOLRequestID OBJECT-TYPE
   SYNTAX      Counter32
   MAX-ACCESS  read-only
   STATUS      current
   DESCRIPTION
       "The number of EAPOL Request Identity frames that have been transmitted by the switch."
   ::= { gs2326pNASPortStatusClientsEntry 15 }

gs2326pNASTxClientsEAPOLRequests OBJECT-TYPE
   SYNTAX      Counter32
   MAX-ACCESS  read-only
   STATUS      current
   DESCRIPTION
       "The number of valid EAPOL Request frames (other than Request Identity frames)
	   that have been transmitted by the switch."
   ::= { gs2326pNASPortStatusClientsEntry 16 }

gs2326pNASRxBackendServerClientsAccessChallenges OBJECT-TYPE
   SYNTAX      Counter32
   MAX-ACCESS  read-only
   STATUS      current
   DESCRIPTION
       "802.1X-based: Counts the number of times that the switch receives the first request
	   from the backend server following the first response from the supplicant.
	   MAC-based: Counts all Access Challenges received from the backend server for this
	   port or client."
   ::= { gs2326pNASPortStatusClientsEntry 17 }

gs2326pNASRxBackendServerClientsOtherRequests OBJECT-TYPE
   SYNTAX      Counter32
   MAX-ACCESS  read-only
   STATUS      current
   DESCRIPTION
       "802.1X-based: Counts the number of times that the switch sends an EAP Request
	   packet following the first to the supplicant.
	   MAC-based: Not applicable."
   ::= { gs2326pNASPortStatusClientsEntry 18 }

gs2326pNASRxBackendServerClientsAuthSuccesses OBJECT-TYPE
   SYNTAX      Counter32
   MAX-ACCESS  read-only
   STATUS      current
   DESCRIPTION
       "Counts the number of times that the switch receives a success indication.
	   Indicates that the supplicant/client has successfully authenticated to the
	   backend server."
   ::= { gs2326pNASPortStatusClientsEntry 19 }

gs2326pNASRxBackendServerClientsAuthFailures OBJECT-TYPE
   SYNTAX      Counter32
   MAX-ACCESS  read-only
   STATUS      current
   DESCRIPTION
       "Counts the number of times that the switch receives a failure message.
	   This indicates that the supplicant/client has not authenticated to the
	   backend server. "
   ::= { gs2326pNASPortStatusClientsEntry 20 }

gs2326pNASTxBackendServerClientsResponses OBJECT-TYPE
   SYNTAX      Counter32
   MAX-ACCESS  read-only
   STATUS      current
   DESCRIPTION
       "802.1X-based: Counts the number of times that the switch attempts to
	   send a supplicant's first response packet to the backend server. Indicates
	   the switch attempted communication with the backend server. Possible
	   retransmissions are not counted.
	   MAC-based: Counts all the backend server packets sent from the switch
	   towards the backend server for a given port or client. Possible
	   retransmissions are not counted."
   ::= { gs2326pNASPortStatusClientsEntry 21 }


gs2326pMaintenance                                           OBJECT IDENTIFIER ::= { lancomGS2326P  4 }

gs2326pRestartDevice OBJECT-TYPE
   SYNTAX      INTEGER { disable(0), enable(1) }
   MAX-ACCESS  read-write
   STATUS      current
   DESCRIPTION
       "default: 0
        0:none
        1:yes"
   ::= { gs2326pMaintenance 1 }

gs2326pColdRestartDevice OBJECT-TYPE
   SYNTAX      INTEGER { disable(0), enable(1) }
   MAX-ACCESS  read-write
   STATUS      current
   DESCRIPTION
       "default: 0
        0:none
        1:yes"
   ::= { gs2326pMaintenance 1500 }

gs2326pFirmware                                         OBJECT IDENTIFIER ::= { gs2326pMaintenance 2 }

gs2326pFirmwareIpAddress OBJECT-TYPE
   SYNTAX       IpAddress
   MAX-ACCESS   read-write
   STATUS       current
   DESCRIPTION
        "Get/Set the firmware tftp server."
   ::= { gs2326pFirmware 1 }

gs2326pFirmwareFileName OBJECT-TYPE
   SYNTAX       DisplayString
   MAX-ACCESS   read-write
   STATUS       current
   DESCRIPTION
        "Get/Set the path and filename for firmware upgrading."
   ::= { gs2326pFirmware 2 }

gs2326pDoFirmwareUpgrade OBJECT-TYPE
   SYNTAX       INTEGER { doNothing(0), do(1) }
   MAX-ACCESS   read-write
   STATUS       current
   DESCRIPTION
        "Do firmware upgrade. Get this OID always return zero.
              1 - do firmware upgrade.
              0 - do nothing."
   ::= { gs2326pFirmware 3 }

gs2326pSaveOrRestore                                         OBJECT IDENTIFIER ::= { gs2326pMaintenance 3 }

gs2326pFactoryDefaults OBJECT-TYPE
   SYNTAX      INTEGER { none(0), yes(1) }
   MAX-ACCESS  read-write
   STATUS      current
   DESCRIPTION
       "default: 0
        0:none
        1:yes"
   ::= { gs2326pSaveOrRestore 1 }

gs2326pSaveStart OBJECT-TYPE
   SYNTAX      INTEGER { none(0), yes(1) }
   MAX-ACCESS  read-write
   STATUS      current
   DESCRIPTION
       "default: 0
        0:none
        1:yes"
   ::= { gs2326pSaveOrRestore 2 }

gs2326pSaveUser OBJECT-TYPE
   SYNTAX      INTEGER { none(0), yes(1) }
   MAX-ACCESS  read-write
   STATUS      current
   DESCRIPTION
       "default: 0
        0:none
        1:yes"
   ::= { gs2326pSaveOrRestore 3 }

gs2326pRestoreUser OBJECT-TYPE
   SYNTAX      INTEGER { none(0), yes(1) }
   MAX-ACCESS  read-write
   STATUS      current
   DESCRIPTION
       "default: 0
        0:none
        1:yes"
   ::= { gs2326pSaveOrRestore 4 }


gs2326pExportOrImport                                        OBJECT IDENTIFIER ::= { gs2326pMaintenance 4 }

gs2326pExportIpAddress OBJECT-TYPE
   SYNTAX       IpAddress
   MAX-ACCESS   read-write
   STATUS       current
   DESCRIPTION
        "Get/Set the export tftp server."
   ::= { gs2326pExportOrImport 1 }

gs2326pExportConfigName OBJECT-TYPE
   SYNTAX       DisplayString
   MAX-ACCESS   read-write
   STATUS       current
   DESCRIPTION
       "Get/Set the export file path and name."
   ::= { gs2326pExportOrImport 2 }

gs2326pDoExportConfig OBJECT-TYPE
   SYNTAX       INTEGER{ doNothing(0), do(1) }
   MAX-ACCESS   read-write
   STATUS       current
   DESCRIPTION
        "Do export-config.
         Get this OID always return zero.
         1 - export."
   ::= { gs2326pExportOrImport 3 }

gs2326pImportIpAddress OBJECT-TYPE
   SYNTAX       IpAddress
   MAX-ACCESS   read-write
   STATUS       current
   DESCRIPTION
        "Get/Set the import tftp server."
   ::= { gs2326pExportOrImport 4 }

gs2326pImportConfigName OBJECT-TYPE
   SYNTAX      DisplayString
   MAX-ACCESS  read-write
   STATUS      current
   DESCRIPTION
       "Get/Set the import file path and name."
   ::= { gs2326pExportOrImport 5 }

gs2326pDoImportConfig OBJECT-TYPE
   SYNTAX       INTEGER{ doNothing(0), do(1) }
   MAX-ACCESS   read-write
   STATUS       current
   DESCRIPTION
        "Do export-config.
         Get this OID always return zero.
         1 - import."
   ::= { gs2326pExportOrImport 6 }

gs2326pDiagnostics                                           OBJECT IDENTIFIER ::= { gs2326pMaintenance 5 }

gs2326pPingIpAddress OBJECT-TYPE
   SYNTAX      IpAddress
   MAX-ACCESS  read-write
   STATUS      current
   DESCRIPTION
       " The destination IP Address. "
   ::= { gs2326pDiagnostics 1 }

gs2326pPingSize OBJECT-TYPE
   SYNTAX      Integer32(60..1400)
   MAX-ACCESS  read-write
   STATUS      current
   DESCRIPTION
       " Size of ICMP echo packet.
         range : 60-1400, default : 64. "
   ::= { gs2326pDiagnostics 2 }

gs2326pDoPingConfig OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326pDiagnostics 3 }

gs2326pPingResult OBJECT-TYPE
   SYNTAX      DisplayString
   MAX-ACCESS  read-only
   STATUS      current
   DESCRIPTION
       " Show ping result. "
   ::= { gs2326pDiagnostics 4 }

gs2326pPing6IpAddress OBJECT-TYPE
   SYNTAX      DisplayString
   MAX-ACCESS  read-write
   STATUS      current
   DESCRIPTION
       " The destination IPv6 Address. "
   ::= { gs2326pDiagnostics 5 }

gs2326pPing6Size OBJECT-TYPE
   SYNTAX      Integer32(60..1400)
   MAX-ACCESS  read-write
   STATUS      current
   DESCRIPTION
       " Size of ICMP echo packet.
         range : 60-1400. "
   ::= { gs2326pDiagnostics 6 }

gs2326pDoPing6Config OBJECT-TYPE
   SYNTAX       INTEGER{ doNothing(0), do(1) }
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { gs2326pDiagnostics 7 }

gs2326pPing6Result OBJECT-TYPE
   SYNTAX      DisplayString
   MAX-ACCESS  read-only
   STATUS      current
   DESCRIPTION
       " Show ping result. "
   ::= { gs2326pDiagnostics 8 }


gs2326pVeriPHY                                           OBJECT IDENTIFIER ::= { gs2326pDiagnostics 9 }

gs2326pVeriPHYTest OBJECT-TYPE
   SYNTAX      Integer32(1..4095)
   MAX-ACCESS  read-write
   STATUS      current
   DESCRIPTION
       "Run VeriPHY Cable Diagnostics.
        port, range : 0 - port number.
        0 : ALL "
   ::= { gs2326pVeriPHY 1 }

gs2326pVeriPHYTable OBJECT-TYPE
   SYNTAX      SEQUENCE OF GS2326PVeriPHYEntry
   MAX-ACCESS  not-accessible
   STATUS      current
   DESCRIPTION
       " "
   ::= { gs2326pVeriPHY 2 }

gs2326pVeriPHYEntry OBJECT-TYPE
   SYNTAX      GS2326PVeriPHYEntry
   MAX-ACCESS  not-accessible
   STATUS      current
   DESCRIPTION
       ""
   INDEX    { gs2326pVeriPHYPort  }
   ::= { gs2326pVeriPHYTable 1 }

GS2326PVeriPHYEntry ::= SEQUENCE {
   gs2326pVeriPHYPort        Integer32,
   gs2326pVeriPHYPairA       DisplayString,
   gs2326pVeriPHYLengthA     DisplayString,
   gs2326pVeriPHYPairB       DisplayString,
   gs2326pVeriPHYLengthB     DisplayString,
   gs2326pVeriPHYPairC       DisplayString,
   gs2326pVeriPHYLengthC     DisplayString,
   gs2326pVeriPHYPairD       DisplayString,
   gs2326pVeriPHYLengthD     DisplayString
}

gs2326pVeriPHYPort OBJECT-TYPE
   SYNTAX      Integer32(1..4095)
   MAX-ACCESS  not-accessible
   STATUS      current
   DESCRIPTION
       " The length (in meters) of the cable pair. "
   ::= { gs2326pVeriPHYEntry 1 }

gs2326pVeriPHYPairA OBJECT-TYPE
   SYNTAX      DisplayString
   MAX-ACCESS  read-only
   STATUS      current
   DESCRIPTION
       " The status of the cable pair. "
   ::= { gs2326pVeriPHYEntry 2 }

gs2326pVeriPHYLengthA OBJECT-TYPE
   SYNTAX      DisplayString
   MAX-ACCESS  read-only
   STATUS      current
   DESCRIPTION
       " The length (in meters) of the cable pair. "
   ::= { gs2326pVeriPHYEntry 3 }

gs2326pVeriPHYPairB OBJECT-TYPE
   SYNTAX      DisplayString
   MAX-ACCESS  read-only
   STATUS      current
   DESCRIPTION
       " The status of the cable pair. "
   ::= { gs2326pVeriPHYEntry 4 }

gs2326pVeriPHYLengthB OBJECT-TYPE
   SYNTAX      DisplayString
   MAX-ACCESS  read-only
   STATUS      current
   DESCRIPTION
       " The length (in meters) of the cable pair. "
   ::= { gs2326pVeriPHYEntry 5 }

gs2326pVeriPHYPairC OBJECT-TYPE
   SYNTAX      DisplayString
   MAX-ACCESS  read-only
   STATUS      current
   DESCRIPTION
       " The status of the cable pair. "
   ::= { gs2326pVeriPHYEntry 6 }

gs2326pVeriPHYLengthC OBJECT-TYPE
   SYNTAX      DisplayString
   MAX-ACCESS  read-only
   STATUS      current
   DESCRIPTION
       " The length (in meters) of the cable pair. "
   ::= { gs2326pVeriPHYEntry 7 }

gs2326pVeriPHYPairD OBJECT-TYPE
   SYNTAX      DisplayString
   MAX-ACCESS  read-only
   STATUS      current
   DESCRIPTION
       " The status of the cable pair. "
   ::= { gs2326pVeriPHYEntry 8 }

gs2326pVeriPHYLengthD OBJECT-TYPE
   SYNTAX      DisplayString
   MAX-ACCESS  read-only
   STATUS      current
   DESCRIPTION
       " The length (in meters) of the cable pair. "
   ::= { gs2326pVeriPHYEntry 9 }


------------------------------------------------------------------------------------------------------------------
gs2326pTrap                                                  OBJECT IDENTIFIER ::= { lancomGS2326P  5 }

gs2326pTrapEvent                                             OBJECT IDENTIFIER ::= { gs2326pTrap 1 }

gs2326pEmergency NOTIFICATION-TYPE
  OBJECTS   { gs2326pInformation }
  STATUS        current
    DESCRIPTION
        "The severity level is Emergency. The system is unusable."
    ::= { gs2326pTrapEvent 1 }

gs2326pAlert NOTIFICATION-TYPE
  OBJECTS   { gs2326pInformation }
  STATUS        current
    DESCRIPTION
        "The severity level is Alert. The action must be taken immediately."
    ::= { gs2326pTrapEvent 2 }

gs2326pCritical NOTIFICATION-TYPE
  OBJECTS   { gs2326pInformation }
  STATUS        current
    DESCRIPTION
        "The severity level is Critical. Critical conditions."
    ::= { gs2326pTrapEvent 3 }

gs2326pError NOTIFICATION-TYPE
  OBJECTS   { gs2326pInformation }
  STATUS        current
    DESCRIPTION
        "The severity level is Error. Error conditions."
    ::= { gs2326pTrapEvent 4 }

gs2326pWarning NOTIFICATION-TYPE
  OBJECTS   { gs2326pInformation }
  STATUS        current
    DESCRIPTION
        "The severity level is Warning. Warning conditions."
    ::= { gs2326pTrapEvent 5 }

gs2326pNotice NOTIFICATION-TYPE
  OBJECTS   { gs2326pInformation }
  STATUS        current
    DESCRIPTION
        "The severity level is Notice. Normal but significant condition."
    ::= { gs2326pTrapEvent 6 }

gs2326pInformational NOTIFICATION-TYPE
  OBJECTS   { gs2326pInformation }
  STATUS        current
    DESCRIPTION
        "The severity level is Informational. Informational messages."
    ::= { gs2326pTrapEvent 7 }

gs2326pDebug NOTIFICATION-TYPE
  OBJECTS   { gs2326pInformation }
  STATUS        current
    DESCRIPTION
        "The severity level is Debug. debug-level messages."
    ::= { gs2326pTrapEvent 8 }

gs2326pTrapVariable                                          OBJECT IDENTIFIER ::= { gs2326pTrap 2 }

gs2326pInformation OBJECT-TYPE
    SYNTAX      DisplayString
    MAX-ACCESS  read-only
    STATUS      current
    DESCRIPTION
        "Trap information."
    ::= { gs2326pTrapVariable 1 }


END
