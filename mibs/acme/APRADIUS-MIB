--------------------------------------------------------------------------------
--ACMEPACKET-RADIUS-MIB:  Acme Packet RADIUS MIB file
--
--March 2012
--
--Copyright (c) by Acme Packet, Inc.
--All rights reserved.
--------------------------------------------------------------------------------
--This MIB provides a means to gather information about the
--Acme Management Interface running at the Net-Net SBC
--

APRADIUS-MIB DEFINITIONS ::= BEGIN

    IMPORTS
    MODULE-IDENTITY, OBJECT-TYPE, NOTIFICATION-TYPE,
    Integer32, IpAddress, Unsigned32, Counter32
        FROM SNMPv2-SMI
    OBJECT-GROUP, NOTIFICATION-GROUP
        FROM SNMPv2-CONF
    DisplayString, TruthValue
  	FROM SNMPv2-TC
    acmepacketMgmt
        FROM ACMEPACKET-SMI
    InetAddress, InetAddressType, InetPortNumber
        FROM INET-ADDRESS-MIB;

    apRadiusServerModule MODULE-IDENTITY
        LAST-UPDATED	    "201203150000Z"
        ORGANIZATION	    "Acme Packet, Inc"
        CONTACT-INFO        "   Customer Service
			Postal:	Acme Packet, Inc
				100 Crosby Drive
				Bedford, MA 01730
				US
			Tel:	1-781-328-4400
			E-mail:	support@acmepacket.com"
        DESCRIPTION     "The Net-Net RADIUS MIB for Acme Packet"

        ::= { acmepacketMgmt 18 }

    apRadiusServerMIBObjects OBJECT IDENTIFIER ::= { apRadiusServerModule 1 }

    apRadiusServerStatsTable OBJECT-TYPE
        SYNTAX  	SEQUENCE OF ApRadiusServerStatsEntry
        MAX-ACCESS      not-accessible
        STATUS  	current
        DESCRIPTION
                "The table of RADIUS statistics per RADIUS server."
        ::= { apRadiusServerMIBObjects 1 }

    apRadiusServerStatsEntry OBJECT-TYPE
        SYNTAX  	ApRadiusServerStatsEntry
        MAX-ACCESS      not-accessible
        STATUS  	current
        DESCRIPTION
                "RADIUS negotiation statistics for an RADIUS server."
        INDEX   { apRadiusServerAddressType, apRadiusServerAddress }
        ::= { apRadiusServerStatsTable 1 }

    ApRadiusServerStatsEntry ::=
        SEQUENCE {
	        apRadiusServerAddressType		InetAddressType,
		apRadiusServerAddress			InetAddress,
                apRadiusServerRoundTripTime		Unsigned32,
                apRadiusServerMalformedAccessResponse	Unsigned32,
                apRadiusServerAccessRequests		Unsigned32,
                apRadiusServerDisconnectRequests	Unsigned32,
                apRadiusServerDisconnectACKs		Unsigned32,
                apRadiusServerDisconnectNACks		Unsigned32,
                apRadiusServerBadAuthenticators		Unsigned32,
                apRadiusServerAccessRetransmissions	Unsigned32,
                apRadiusServerAccessAccepts		Unsigned32,
                apRadiusServerTimeouts			Unsigned32,
                apRadiusServerAccessRejects		Unsigned32,
                apRadiusServerUnknownPDUTypes		Unsigned32,
                apRadiusServerAccessChallenges		Unsigned32
		}

    apRadiusServerAddressType OBJECT-TYPE
        SYNTAX		InetAddressType
        MAX-ACCESS	read-only
        STATUS		current
        DESCRIPTION
                "IPAddress type of the RADIUS server"
        ::= { apRadiusServerStatsEntry 1 }

    apRadiusServerAddress OBJECT-TYPE
        SYNTAX		InetAddress
        MAX-ACCESS	read-only
        STATUS		current
        DESCRIPTION
                "IPAddress of  the RADIUS server"
        ::= { apRadiusServerStatsEntry 2 }

    apRadiusServerRoundTripTime OBJECT-TYPE
        SYNTAX		Unsigned32
        MAX-ACCESS	read-only
        STATUS		current
        DESCRIPTION
                "Average Round Trip Time for response on this RADIUS Server"
        ::= { apRadiusServerStatsEntry 3 }

    apRadiusServerMalformedAccessResponse OBJECT-TYPE
        SYNTAX		Unsigned32
        MAX-ACCESS	read-only
        STATUS		current
        DESCRIPTION
                "The count of Malformed Access Response on this RADIUS Server"
        ::= { apRadiusServerStatsEntry 4 }

    apRadiusServerAccessRequests OBJECT-TYPE
        SYNTAX		Unsigned32
        MAX-ACCESS	read-only
        STATUS		current
        DESCRIPTION
                "The count of Access Requests on this RADIUS Server"
        ::= { apRadiusServerStatsEntry 5 }

    apRadiusServerDisconnectRequests OBJECT-TYPE
        SYNTAX		Unsigned32
        MAX-ACCESS	read-only
        STATUS		current
        DESCRIPTION
                "The count of Disconnect Requests on this RADIUS Server"
        ::= { apRadiusServerStatsEntry 6 }

    apRadiusServerDisconnectACKs OBJECT-TYPE
        SYNTAX		Unsigned32
        MAX-ACCESS	read-only
        STATUS		current
        DESCRIPTION
                "The count of Disconnect ACKs on this RADIUS Server"
        ::= { apRadiusServerStatsEntry 7 }

    apRadiusServerDisconnectNACks OBJECT-TYPE
        SYNTAX		Unsigned32
        MAX-ACCESS	read-only
        STATUS		current
        DESCRIPTION
                "The count of Disconnect NACKs on this RADIUS Server"
        ::= { apRadiusServerStatsEntry 8 }

    apRadiusServerBadAuthenticators OBJECT-TYPE
        SYNTAX		Unsigned32
        MAX-ACCESS	read-only
        STATUS		current
        DESCRIPTION
                "The count of Bad Authenticators on this RADIUS Server"
        ::= { apRadiusServerStatsEntry 9 }

    apRadiusServerAccessRetransmissions OBJECT-TYPE
        SYNTAX		Unsigned32
        MAX-ACCESS	read-only
        STATUS		current
        DESCRIPTION
                "The count of Access Retransmissions on this RADIUS Server"
        ::= { apRadiusServerStatsEntry 10 }

    apRadiusServerAccessAccepts OBJECT-TYPE
        SYNTAX		Unsigned32
        MAX-ACCESS	read-only
        STATUS		current
        DESCRIPTION
                "The count of Access Accepts on this RADIUS Server"
        ::= { apRadiusServerStatsEntry 11 }

    apRadiusServerTimeouts OBJECT-TYPE
        SYNTAX		Unsigned32
        MAX-ACCESS	read-only
        STATUS		current
        DESCRIPTION
                "The count of Timeouts for response on this RADIUS Server"
        ::= { apRadiusServerStatsEntry 12 }

    apRadiusServerAccessRejects OBJECT-TYPE
        SYNTAX		Unsigned32
        MAX-ACCESS	read-only
        STATUS		current
        DESCRIPTION
                "The count of Access Rejects on this RADIUS Server"
        ::= { apRadiusServerStatsEntry 13 }

    apRadiusServerUnknownPDUTypes OBJECT-TYPE
        SYNTAX		Unsigned32
        MAX-ACCESS	read-only
        STATUS		current
        DESCRIPTION
                "The count of Unknown PDU Types received on this RADIUS Server"
        ::= { apRadiusServerStatsEntry 14 }

    apRadiusServerAccessChallenges OBJECT-TYPE
        SYNTAX		Unsigned32
        MAX-ACCESS	read-only
        STATUS		current
        DESCRIPTION
                "The count of Access Challenges  on this RADIUS Server"
        ::= { apRadiusServerStatsEntry 15 }


----------------------------------------------------
--
-- apRadiusObjectGroups
--
----------------------------------------------------

apRadiusServerConformance OBJECT IDENTIFIER ::= { apRadiusServerModule 2 }
apRadiusObjectGroups   OBJECT IDENTIFIER ::= { apRadiusServerConformance 1 }

apRadiusInterfaceStatsGroup OBJECT-GROUP
    OBJECTS {
	apRadiusServerRoundTripTime,
	apRadiusServerMalformedAccessResponse,
	apRadiusServerAccessRequests,
	apRadiusServerDisconnectRequests,
	apRadiusServerDisconnectACKs,
	apRadiusServerDisconnectNACks,
	apRadiusServerBadAuthenticators,
	apRadiusServerAccessRetransmissions,
	apRadiusServerAccessAccepts,
	apRadiusServerTimeouts,
	apRadiusServerAccessRejects,
	apRadiusServerUnknownPDUTypes,
	apRadiusServerAccessChallenges
	     }
      STATUS		current
      DESCRIPTION
	  "A collection of statistics for RADIUS server."
      ::= {  apRadiusObjectGroups 1 }


END
