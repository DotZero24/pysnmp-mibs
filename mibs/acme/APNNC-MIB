--------------------------------------------------------------------------------
--ACMEPACKET-EMS-MIB:  Acme Packet NNC MIB file
--
--February 2012
--
--Copyright (c) by Acme Packet, Inc.
--All rights reserved.
--------------------------------------------------------------------------------
--This MIB provides a means to gather information about the
--Acme Management Interface running at the Net-Net EMS and/or Device
--

APNNC-MIB DEFINITIONS ::= BEGIN

    IMPORTS
    MODULE-IDENTITY, OBJECT-TYPE, NOTIFICATION-TYPE, Integer32
        FROM SNMPv2-SMI
    OBJECT-GROUP, NOTIFICATION-GROUP
        FROM SNMPv2-CONF
    DisplayString, TruthValue
  	FROM SNMPv2-TC
    acmepacketMgmt
        FROM ACMEPACKET-SMI
    apEMSModule
        FROM APEMS-MIB;

    apNNCModule MODULE-IDENTITY
        LAST-UPDATED	    "201207160000Z"
        ORGANIZATION	    "Acme Packet, Inc"
        CONTACT-INFO
			  "       Customer Service
                        Postal: Acme Packet, Inc
                                100 Crosby Drive
                                Bedford, MA 01730
                                US
                        Tel:    1-781-328-4400
                        E-mail: support@acmepacket.com"
        DESCRIPTION     "The Net-Net NNC MIB for Acme Packet"
        REVISION        "201207160000Z"
        DESCRIPTION     "Updated contact info"
        ::= { apEMSModule 5 }


    apNNCMIBObjects OBJECT IDENTIFIER ::= { apNNCModule 1 }

    apNNCNotificationObjects OBJECT IDENTIFIER ::= { apNNCModule 2 }

    apNNCServerAddressRemote OBJECT-TYPE
	SYNTAX DisplayString
	MAX-ACCESS accessible-for-notify
	STATUS current
	DESCRIPTION     "The address of a Net-Net Central server, whose reachability status has changed."
	::= { apNNCNotificationObjects 1 }


    apNNCServerNameRemote OBJECT-TYPE
	SYNTAX DisplayString
	MAX-ACCESS accessible-for-notify
	STATUS current
	DESCRIPTION     "The name of a Net-Net Central server (if available), whose
	reachability status has changed and detected by a peer local NNC server."
	::= { apNNCNotificationObjects 2 }


    apNNCServerAddressLocal OBJECT-TYPE
	SYNTAX DisplayString
	MAX-ACCESS accessible-for-notify
	STATUS current
	DESCRIPTION     "The address of the local Net-Net Central server in the cluster, which
	      detected the reachability status change of a peer server in the cluster."
	::= { apNNCNotificationObjects 3 }


    apNNCServerNameLocal OBJECT-TYPE
	SYNTAX DisplayString
	MAX-ACCESS accessible-for-notify
	STATUS current
	DESCRIPTION     "The name (if available) of the local Net-Net Central server, which detected the
            reachability status change of a peer server in the cluster."
	::= { apNNCNotificationObjects 4 }


    apNNCNotifications OBJECT IDENTIFIER ::= { apNNCModule 3 }
    apNNCConfigNotificationsPrefix
		OBJECT IDENTIFIER ::= { apNNCNotifications 1 }
    apNNCConfigNotifications
		OBJECT IDENTIFIER ::= { apNNCConfigNotificationsPrefix 0 }

    apNNCServerHealthNotificationsPrefix
        OBJECT IDENTIFIER ::= { apNNCNotifications 1 }
    apNNCServerHealthNotifications
        OBJECT IDENTIFIER ::= { apNNCServerHealthNotificationsPrefix 0 }


    apNNCServerUnreachable NOTIFICATION-TYPE
        OBJECTS {
	    apNNCServerAddressLocal,
            apNNCServerNameLocal,
            apNNCServerAddressRemote,
            apNNCServerNameRemote
            }
	STATUS current
        DESCRIPTION
            "The notification will be generated whenever a Net-Net Central Server is
            determined to be unreachable by another the Net-Net Central server configured in the same cluster. "
    ::= { apNNCServerHealthNotifications 1 }


    apNNCServerUnreachableClear NOTIFICATION-TYPE
        OBJECTS {
            apNNCServerAddressLocal,
            apNNCServerNameLocal,
	    apNNCServerAddressRemote,
	    apNNCServerNameRemote
	    }
	STATUS current
	DESCRIPTION
            "The notification will be generated whenever a previously
            unreachable Net-Net Central Server is determined to be reachable
            by another Net-Net Central server configured in the same cluster. "
    ::= { apNNCServerHealthNotifications 2 }

    apNNCModuleConformance OBJECT IDENTIFIER ::= { apNNCModule 4 }

    apNNCGroups OBJECT IDENTIFIER ::= { apNNCModuleConformance 1 }
    apNNCNotificationsGroups OBJECT IDENTIFIER ::= { apNNCModuleConformance 2 }
    apNNCNotificationObjectsGroups OBJECT IDENTIFIER ::= { apNNCModuleConformance 3 }

    apNNCServerHealthNotificationsGroup NOTIFICATION-GROUP
        NOTIFICATIONS {
          apNNCServerUnreachable,
          apNNCServerUnreachableClear
        }
    STATUS current
    DESCRIPTION "NNC Server reachability notifications generated by a peer NNC Server"
    ::= { apNNCNotificationsGroups 1 }

    apNNCServerHealthObjectsGroup OBJECT-GROUP
        OBJECTS {
            apNNCServerAddressLocal,
            apNNCServerNameLocal,
            apNNCServerAddressRemote,
            apNNCServerNameRemote
       }
    STATUS current
    DESCRIPTION "Objects for NNC Server reachability notifications."
    ::= { apNNCNotificationObjectsGroups 1 }



END
