--------------------------------------------------------------------------------
--ACMEPACKET-AMI-MIB:  Acme Packet AMI MIB file
--
--March 2007
--
--Copyright (c) by Acme Packet, Inc.
--All rights reserved.
--------------------------------------------------------------------------------
--This MIB provides a means to gather information about the
--Acme Management Interface running at the SD
--

APAMI-MIB DEFINITIONS ::= BEGIN
    IMPORTS
    MODULE-IDENTITY, OBJECT-TYPE, Integer32
        FROM SNMPv2-SMI
    OBJECT-GROUP
        FROM SNMPv2-CONF
    acmepacketMgmt
        FROM ACMEPACKET-SMI;

    apAMIModule MODULE-IDENTITY
        LAST-UPDATED	    "201207160000Z"
        ORGANIZATION	    "Acme Packet, Inc"
        CONTACT-INFO
			"           	Customer Service
		 	Postal:		Acme Packet, Inc
					100 Crosby Drive
					Bedford, MA 01730
					US
		    	Tel:		1-781-328-4400
		 	E-mail:		support@acmepacket.com"
        DESCRIPTION         "The Acme Management Interface MIB for Acme Packet"
        REVISION 	        "201207160000Z"
        DESCRIPTION		"Updated contact information."


        ::= { acmepacketMgmt 6 }


    apAMIMIBObjects OBJECT IDENTIFIER ::= { apAMIModule 1 }

    apAMISoapObjects OBJECT IDENTIFIER ::= { apAMIMIBObjects 1 }

    --Soap Scalars
    apAMISoapHttp OBJECT-TYPE
        SYNTAX              INTEGER {
                                enabled( 1 ),
                                disabled( 2 )
                            }
        MAX-ACCESS          read-only
        STATUS              current
        DESCRIPTION         "Indicates the status of the soap http interface."
        ::= { apAMISoapObjects 1 }

    apAMISoapHttpPort OBJECT-TYPE
        SYNTAX              Integer32
        MAX-ACCESS          read-only
        STATUS              current
        DESCRIPTION         "the tcp port soap over HTTP is running on."
        ::= { apAMISoapObjects 2 }

    apAMISoapHttps OBJECT-TYPE
        SYNTAX              INTEGER {
                                enabled( 1 ),
                                disabled( 2 )
                            }
        MAX-ACCESS          read-only
        STATUS              current
        DESCRIPTION         "Indicates the status of the soap https interface."
        ::= { apAMISoapObjects 3 }

    apAMISoapHttpsPort OBJECT-TYPE
        SYNTAX              Integer32
        MAX-ACCESS          read-only
        STATUS              current
        DESCRIPTION         "the tcp port soap over HTTPS is running on."
        ::= { apAMISoapObjects 4 }

    apAMIModuleConformance OBJECT IDENTIFIER ::= { apAMIModule 2 }

    apAMIModuleGroups OBJECT IDENTIFIER ::= { apAMIModuleConformance 1 }

    apAMIMibObjectsGroup OBJECT-GROUP
        OBJECTS	{
        		apAMISoapHttp,
        		apAMISoapHttpPort,
        		apAMISoapHttps,
        		apAMISoapHttpsPort
        	}
        STATUS		    current
        DESCRIPTION         "This automatically created object group contains
                            all those objects that do not belong to any other
                            OBJECT-GROUP"
        ::= { apAMIModuleGroups 1 }


END
