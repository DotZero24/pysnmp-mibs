--------------------------------------------------------------------------------
--ACMEPACKET-EMS-MIB:  Acme Packet EMS MIB file
--
--March 2007
--
--Copyright (c) by Acme Packet, Inc.
--All rights reserved.
--------------------------------------------------------------------------------
--This MIB provides a means to gather information about the
--Acme Management Interface running at the Net-Net EMS and/or Device
--

APEMS-MIB DEFINITIONS ::= BEGIN

    IMPORTS
    MODULE-IDENTITY, OBJECT-TYPE, NOTIFICATION-TYPE, Integer32
        FROM SNMPv2-SMI
    OBJECT-GROUP, NOTIFICATION-GROUP
        FROM SNMPv2-CONF
    DisplayString, TruthValue
  	FROM SNMPv2-TC
    acmepacketMgmt
        FROM ACMEPACKET-SMI;

    apEMSModule MODULE-IDENTITY
        LAST-UPDATED	    "201207160000Z"
        ORGANIZATION	    "Acme Packet, Inc"
        CONTACT-INFO         "       Customer Service
                        Postal: Acme Packet, Inc
                                100 Crosby Drive
                                Bedford, MA 01730
                                US
                        Tel:    1-781-328-4400
                        E-mail: support@acmepacket.com"
        DESCRIPTION     "The Net-Net EMS MIB for Acme Packet"
        REVISION        "201207160000Z"
        DESCRIPTION     "Updated contact information"
        ::= { acmepacketMgmt 8 }


    apEMSMIBObjects OBJECT IDENTIFIER ::= { apEMSModule 1 }

    apEMSNotificationObjects OBJECT IDENTIFIER ::= { apEMSModule 2 }

    apEMSDiscoveryMode  OBJECT-TYPE
	SYNTAX        INTEGER {
			unknown(0),
			discovery(1),
			reDiscovery(2)
			}
	MAX-ACCESS    accessible-for-notify
	STATUS	      current
	DESCRIPTION   "The discovery mode"
	::= { apEMSNotificationObjects 1 }


    apEMSNodeID	      OBJECT-TYPE
	SYNTAX        DisplayString
	MAX-ACCESS    accessible-for-notify
	STATUS	      current
	DESCRIPTION   "The identifier for a Net-Net EMS node.  This is the
			identifier that appears on the navigation tree in
			the Active Configuration area and on the discovery
			table in the Host Name/IP Address column"
	::= { apEMSNotificationObjects 2 }

    apEMSStartTime     OBJECT-TYPE
	SYNTAX        DisplayString
	MAX-ACCESS    accessible-for-notify
	STATUS	      current
	DESCRIPTION   "Time as configured at the Net-Net EMS server when
			an event occurs."
	::= { apEMSNotificationObjects 3 }

    apEMSDateTime      OBJECT-TYPE
	SYNTAX        DisplayString
	MAX-ACCESS    accessible-for-notify
	STATUS	      current
	DESCRIPTION   "Time as configured at the Net-Net EMS server when an
			event completes."
	::= { apEMSNotificationObjects 4 }

    apEMSUser	      OBJECT-TYPE
	SYNTAX        DisplayString
	MAX-ACCESS    accessible-for-notify
	STATUS	      current
	DESCRIPTION   "The user initiating the function.
		       If the function was initiated by the Net-Net EMS
		       application automatically, the
		       user will be system."
	::= { apEMSNotificationObjects 5 }


    apEMSDeviceAddress  OBJECT-TYPE
	SYNTAX        DisplayString
	MAX-ACCESS    accessible-for-notify
	STATUS	      current
	DESCRIPTION   "The address for a device being managed."
	::= { apEMSNotificationObjects 6 }


    apEMSFunction     OBJECT-TYPE
	SYNTAX        INTEGER {
			unknown(0),
			discovery(1),
			reDiscovery(2),
			save(3)
			}
	MAX-ACCESS    accessible-for-notify
	STATUS	      current
	DESCRIPTION   "The function being performed when the event occurred."
	::= { apEMSNotificationObjects 7 }

    apEMSNotifications OBJECT IDENTIFIER ::= { apEMSModule 3 }
    apEMSConfigNotificationsPrefix
		OBJECT IDENTIFIER ::= { apEMSNotifications 1 }
    apEMSConfigNotifications
		OBJECT IDENTIFIER ::= { apEMSConfigNotificationsPrefix 0 }

    apEMSDiscoveryFailure	NOTIFICATION-TYPE
	OBJECTS		{
			apEMSDiscoveryMode,
			apEMSNodeID,
			apEMSStartTime,
			apEMSDateTime,
			apEMSUser
			}
	STATUS	   	current
	DESCRIPTION
	      "The notification will be generated whenever an error
		is detected during node discovery. "
	::= { apEMSConfigNotifications 1 }


    apEMSSaveFailure	NOTIFICATION-TYPE
	OBJECTS		{
			apEMSNodeID,
			apEMSStartTime,
			apEMSDateTime,
			apEMSUser
			}
	STATUS	   	current
	DESCRIPTION
	      "The notification will be generated whenever an save
		configuration request initiated by Net-Net EMS fails. "
	::= { apEMSConfigNotifications 2 }

    apEMSActivateFailure	NOTIFICATION-TYPE
	OBJECTS		{
			apEMSNodeID,
			apEMSStartTime,
			apEMSDateTime,
			apEMSUser
			}
	STATUS	   	current
	DESCRIPTION
	      "The notification will be generated whenever an activate
		configuration request initiated by Net-Net EMS fails`. "
	::= { apEMSConfigNotifications 3 }

    apEMSInvalidConfigDiscovered	NOTIFICATION-TYPE
	OBJECTS		{
			apEMSNodeID,
			apEMSDateTime
			}
	STATUS	   	current
	DESCRIPTION
	      "The notification will be generated whenever an invalid
		configuration is retrieved from a node.  Additional information
		about the validity failure is available in the discovery log."
	::= { apEMSConfigNotifications 4 }


    apEMSInvalidConfigInventory	NOTIFICATION-TYPE
	OBJECTS		{
			apEMSFunction,
			apEMSNodeID,
			apEMSStartTime,
			apEMSDateTime,
			apEMSUser
			}
	STATUS	   	current
	DESCRIPTION
	      "The notification will be generated whenever an inventory check
		was performed and failed."
	::= { apEMSConfigNotifications 5 }

    apEMSDeviceHealthNotificationsPrefix
		OBJECT IDENTIFIER ::= { apEMSNotifications 2 }
    apEMSDeviceHealthNotifications
		OBJECT IDENTIFIER ::= { apEMSDeviceHealthNotificationsPrefix 0 }

    apEMSNodeUnreachable	NOTIFICATION-TYPE
	OBJECTS		{
			apEMSDeviceAddress,
			apEMSDateTime
			}
	STATUS	   	current
	DESCRIPTION
	      "The notification will be generated whenever a managed device is
		determined to be unreachable from the Net-Net EMS server. "
	::= { apEMSDeviceHealthNotifications 1 }


    apEMSNodeUnreachableClear	NOTIFICATION-TYPE
	OBJECTS		{
			apEMSDeviceAddress,
			apEMSDateTime
			}
	STATUS	   	current
	DESCRIPTION
	      "The notification will be generated whenever a previously
		unreachable managed device is determined to be reachable
		by the Net-Net EMS server. "
	::= { apEMSDeviceHealthNotifications 2 }

    apEMSModuleConformance OBJECT IDENTIFIER ::= { apEMSModule 4 }

    apEMSGroups OBJECT IDENTIFIER ::= { apEMSModuleConformance 1 }
    apEMSNotificationsGroups OBJECT IDENTIFIER ::= { apEMSModuleConformance 2 }
    apEMSNotificationObjectsGroups OBJECT IDENTIFIER ::= { apEMSModuleConformance 3 }

    apEMSConfigNotificationsGroup NOTIFICATION-GROUP
        NOTIFICATIONS {
	            	apEMSDiscoveryFailure,
			apEMSSaveFailure,
			apEMSActivateFailure,
			apEMSInvalidConfigDiscovered
       	              }
        STATUS		    current
        DESCRIPTION  "Provisioning notifications generated by the Net-Net EMS"
        ::= { apEMSNotificationsGroups 1 }

    apEMSDeviceHealthNotificationsGroup NOTIFICATION-GROUP
        NOTIFICATIONS {
			apEMSNodeUnreachable,
			apEMSNodeUnreachableClear
       	              }
        STATUS		    current
        DESCRIPTION  "Device reachability notifications generated by
			the Net-Net EMS"
        ::= { apEMSNotificationsGroups 2 }

    apEMSNotificationObjectsGroup OBJECT-GROUP
        OBJECTS {
			apEMSDiscoveryMode,
			apEMSNodeID,
			apEMSStartTime,
			apEMSDateTime,
			apEMSUser,
			apEMSDeviceAddress,
			apEMSFunction
       }
    STATUS current
    DESCRIPTION "Objects for EMS Server reachability notifications."
    ::= { apEMSNotificationObjectsGroups 1 }

END
