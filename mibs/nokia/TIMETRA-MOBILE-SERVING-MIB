--       TIMETRA MOBILE SERVING
--       Management Information Base

TIMETRA-MOBILE-SERVING-MIB DEFINITIONS ::= BEGIN

IMPORTS
   MODULE-IDENTITY, OBJECT-TYPE, Unsigned32, Gauge32,
   Counter32, Counter64
       FROM SNMPv2-SMI

   MODULE-COMPLIANCE, OBJECT-GROUP
       FROM SNMPv2-CONF

   RowStatus, TimeStamp, TruthValue, DisplayString
       FROM SNMPv2-TC

   InetAddress, InetAddressType, InetAddressPrefixLength, InetPortNumber
       FROM INET-ADDRESS-MIB

   InterfaceIndexOrZero
       FROM IF-MIB

   timetraSRMIBModules, tmnxSRObjs, tmnxSRConfs
       FROM TIMETRA-GLOBAL-MIB

   TmnxEnabledDisabled, TmnxVRtrID, TmnxAdminState, TmnxOperState,
   TTcpUdpPort, TTcpUdpPortOperator, TNamedItemOrEmpty, TItemDescription,
   TmnxEnabledDisabledOrInherit, TmnxCdrDiagnosticAction
       FROM TIMETRA-TC-MIB

   TmnxMobProfName, TmnxMobProfNameOrEmpty, TmnxMobDiaRetryCount,
   TmnxMobDiaTransTimer, TmnxMobDiaPeerHost, TmnxMobNode,
   TmnxMobRtrAdvtInterval, TmnxMobRtrAdvtLifeTime, TmnxMobAddrScheme,
   TmnxMobApn, TmnxMobImsi, TmnxMobMsisdn, TmnxMobImei, TmnxMobNai,
   TmnxMobMcc, TmnxMobMnc, TmnxMobUeState, TmnxMobUeRat, TmnxMobPdnType,
   TmnxMobPgwSigProtocol, TmnxMobPdnSessionState, TmnxMobPdnSessionEvent,
   TmnxMobBearerId, TmnxMobBearerType, TmnxMobQci, TmnxMobArp, TmnxMobSdf,
   TmnxMobSdfRuleName, TmnxMobSdfFilterDirection, TmnxMobSdfFilterProtocol,
   TmnxMobPathMgmtState, TmnxMobGwId, TmnxMobChargingProfile,
   TmnxMobRfAcctLevel, TmnxMobChargingBearerType, TmnxMobServerState,
   TmnxMobChargingLevel, TmnxMobSdfFilter, TmnxMobSdfFilterNum,
   TmnxMobDualStackPref, TmnxMobDiaPathMgmtState, TmnxMobDiaDetailPathMgmtState,
   TmnxMobChargingProfileOrInherit, TmnxMobUeId,
   TmnxMobUeIdType, TmnxMobImsiStr, TmnxMobServRefPointType
       FROM TIMETRA-TC-MG-MIB

   tmnxChassisIndex, tmnxCardSlotNum, TmnxChassisIndex, TmnxSlotNum,
   TmnxSlotNumOrZero
       FROM TIMETRA-CHASSIS-MIB

   vRtrID
       FROM TIMETRA-VRTR-MIB

   tmnxMobGwId
       FROM TIMETRA-MOBILE-GATEWAY-MIB

   tmnxMobGtpPriGrpName, tmnxMobGtpPriServerIndex
       FROM TIMETRA-MOBILE-PROFILE-MIB

   ;

timetraMobServingMIBModule    MODULE-IDENTITY
    LAST-UPDATED    "0912230000Z"
    ORGANIZATION    "Nokia"
    CONTACT-INFO
    "Nokia 7xxx Support
    Web: http://www.nokia.com"
    DESCRIPTION
    "This document is the SNMP MIB module to manage and provision
    the Serving Gateway (SGW).

    Copyright 2008-2016 Nokia. All rights reserved.
    Reproduction of this document is authorized on the condition that
    the foregoing copyright notice is included.

    This SNMP MIB module (Specification) embodies Nokia's
    proprietary intellectual property. Nokia retains all title and
    ownership in the Specification, including any revisions.

    Nokia grants all interested parties a non-exclusive
    license to use and distribute an unmodified copy of this
    Specification in connection with management of Nokia products,
    and without fee, provided this copyright notice and license appear
    on all copies.

    This Specification is supplied 'as is', and Nokia
    makes no warranty, either express or implied, as to the use,
    operation, condition, or performance of the Specification."

--
--  Revision History
--

    REVISION        "200912230000Z"
    DESCRIPTION     "Rev MG-1.0             23 Dec 2009 00:00
                     MG-1.0 release of the TIMETRA-MOBILE-SERVING-MIB."

    ::= { timetraSRMIBModules 66 }

-- ----------------------------------------------------------------------------
--  Nokia 7xxx series MOBILE-SERVING MIB structure
-- ----------------------------------------------------------------------------
tmnxMobServing                OBJECT IDENTIFIER ::= { tmnxSRObjs 66 }
    tmnxMobServingConfObjs          OBJECT IDENTIFIER ::= { tmnxMobServing 1 }
    tmnxMobServingStatObjs          OBJECT IDENTIFIER ::= { tmnxMobServing 2 }
    tmnxMobServingGlobalObjs        OBJECT IDENTIFIER ::= { tmnxMobServing 3 }

tmnxMobServingConformance     OBJECT IDENTIFIER ::= { tmnxSRConfs 66 }
    tmnxMobServingCompliances       OBJECT IDENTIFIER ::=
                                            { tmnxMobServingConformance 1 }
    tmnxMobServingGroups            OBJECT IDENTIFIER ::=
                                            { tmnxMobServingConformance 2 }

-- --------------------------
--  Mib objects
-- --------------------------

--
--  Serving gateway table
--

tmnxMobServTableLastChanged     OBJECT-TYPE
    SYNTAX      TimeStamp
    MAX-ACCESS  read-only
    STATUS      current
    DESCRIPTION
        "The value of tmnxMobServTableLastChanged indicates the sysUpTime at
         the time of the last modification to tmnxMobServTable by adding,
         deleting an entry or change to a writable object in the table.

         If no changes were made to the table since the last re-initialization
         of the local network management subsystem, then this object contains
         a zero value."
    ::= { tmnxMobServingGlobalObjs 1 }

tmnxMobServTable  OBJECT-TYPE
    SYNTAX      SEQUENCE OF TmnxMobServEntry
    MAX-ACCESS  not-accessible
    STATUS      current
    DESCRIPTION
        "The tmnxMobServTable has an entry for each Serving Gateway (SGW)."
    ::= { tmnxMobServingConfObjs 1 }

tmnxMobServEntry  OBJECT-TYPE
    SYNTAX      TmnxMobServEntry
    MAX-ACCESS  not-accessible
    STATUS      current
    DESCRIPTION
        "Each row entry represents a Serving Gateway (SGW). An entry in this
         table is created by the agent itself when an entry is created in the
         tmnxMobGwTable with the value of tmnxMobGwType set to 'sgw'."
    INDEX { tmnxMobGwId }
    ::= { tmnxMobServTable 1 }

TmnxMobServEntry ::= SEQUENCE {
        tmnxMobServLastChanged               TimeStamp,
        tmnxMobServAdminState                TmnxAdminState,
        tmnxMobServOperState                 TmnxOperState,
        tmnxMobServGracefulShutTimeout       Unsigned32,
        tmnxMobServMobNode                   TmnxMobNode,
        tmnxMobServPccDynamicState           TmnxEnabledDisabled,
        tmnxMobServBearerGtpuUdpChecksum     TmnxEnabledDisabled,
        tmnxMobServBearerGtpuSeqNumber       TmnxEnabledDisabled,
        tmnxMobServUplinkQciPolName          TmnxMobProfName,
        tmnxMobServDownlinkQciPolName        TmnxMobProfName,
        tmnxMobServHomePlmnList              TmnxMobProfNameOrEmpty,
        tmnxMobServVisitingPlmnList          TmnxMobProfNameOrEmpty,
        tmnxMobServPolBaseName               TmnxMobProfNameOrEmpty,
        tmnxMobServChargingProfHome          TmnxMobChargingProfile,
        tmnxMobServChargingProfVisiting      TmnxMobChargingProfile,
        tmnxMobServChargingProfRoaming       TmnxMobChargingProfile,
        tmnxMobServChrgCcIgnoreAny           TmnxEnabledDisabled,
        tmnxMobServChrgCcIgnoreHome          TmnxEnabledDisabled,
        tmnxMobServChrgCcIgnoreVisiting      TmnxEnabledDisabled,
        tmnxMobServChrgCcIgnoreRoaming       TmnxEnabledDisabled,
        tmnxMobServChrgCcReject              TruthValue,
        tmnxMobServChrgNodeId                DisplayString,
        tmnxMobServChargingAvpDiag           TmnxCdrDiagnosticAction
    }

tmnxMobServLastChanged  OBJECT-TYPE
    SYNTAX      TimeStamp
    MAX-ACCESS  read-only
    STATUS      current
    DESCRIPTION
        "The value of tmnxMobServLastChanged indicates the timestamp of the last
         change to this row in tmnxMobServTable."
    ::= { tmnxMobServEntry 1 }

tmnxMobServAdminState  OBJECT-TYPE
    SYNTAX      TmnxAdminState
    MAX-ACCESS  read-write
    STATUS      current
    DESCRIPTION
        "The value of tmnxMobServAdminState specifies the desired administrative
         state of this Serving Gateway."
    DEFVAL { outOfService }
    ::= { tmnxMobServEntry 2 }

tmnxMobServOperState  OBJECT-TYPE
    SYNTAX      TmnxOperState
    MAX-ACCESS  read-only
    STATUS      current
    DESCRIPTION
        "The value of tmnxMobServOperState indicates the current operational
         status of this Serving Gateway (SGW)."
    ::= { tmnxMobServEntry 3 }

tmnxMobServGracefulShutTimeout  OBJECT-TYPE
    SYNTAX      Unsigned32 (15..60)
    UNITS       "minutes"
    MAX-ACCESS  read-write
    STATUS      current
    DESCRIPTION
        "The value of tmnxMobServGracefulShutTimeout specifies the graceful
         shutdown time. For graceful system shutdown, the existing
         request or connections are allowed to complete while no new
         requests or connections are accepted.

         This procedure is used to take the system to maintenance mode."
    DEFVAL { 30 }
    ::= { tmnxMobServEntry 4 }

tmnxMobServMobNode  OBJECT-TYPE
    SYNTAX      TmnxMobNode
    MAX-ACCESS  read-write
    STATUS      current
    DESCRIPTION
        "The value of tmnxMobServMobNode specifies the Serving Gateway (SGW)
         name."
    DEFVAL { ''H }
    ::= { tmnxMobServEntry 5 }

tmnxMobServPccDynamicState  OBJECT-TYPE
    SYNTAX      TmnxEnabledDisabled
    MAX-ACCESS  read-write
    STATUS      current
    DESCRIPTION
        "The value of tmnxMobServPccDynamicState specifies if interaction with
         Policy and Charging Rules Function (PCRF) is enabled for bearer
         creation or not. Policy and Charging Control (PCC) rules are pushed
         from PCRF for dedicated bearer creation."
    DEFVAL { disabled }
    ::= { tmnxMobServEntry 6 }

tmnxMobServBearerGtpuUdpChecksum  OBJECT-TYPE
    SYNTAX      TmnxEnabledDisabled
    MAX-ACCESS  read-write
    STATUS      current
    DESCRIPTION
        "The value of tmnxMobServBearerGtpuUdpChecksum specifies whether
         or not to validate the UDP checksum of GPRS Tunneling
         Protocol-User plane (GTP-U) packets.

         If the value of this object is set to 'enabled', the UDP
         checksum of the received GTP-U packets is verified and the
         packets which fail checksum verification are rejected.
         If the value of this object is set to 'disabled',
         the UDP checksum of the received GTP-U packets is not
         verified."
    DEFVAL { disabled }
    ::= { tmnxMobServEntry 7 }

tmnxMobServBearerGtpuSeqNumber  OBJECT-TYPE
    SYNTAX      TmnxEnabledDisabled
    MAX-ACCESS  read-write
    STATUS      current
    DESCRIPTION
        "The value of tmnxMobServBearerGtpuSeqNumber specifies whether
         or not to ignore the sequence number in the GPRS Tunneling
         Protocol-User plane (GTP-U) header.

         If the value of this object is set to 'enabled',
         GTP-U packets are reassembled based on the sequence number and
         complete packet is forwarded onto S5 or S8 interface. If the value
         of this object is set to 'disabled', the sequence number is
         ignored and complete packet is forwarded onto S5 or S8 interface."
    DEFVAL { disabled }
    ::= { tmnxMobServEntry 8 }

tmnxMobServUplinkQciPolName  OBJECT-TYPE
    SYNTAX      TmnxMobProfName
    MAX-ACCESS  read-write
    STATUS      current
    DESCRIPTION
        "The value of tmnxMobServUplinkQciPolName specifies the QoS Class
         Identifier (QCI) policy profile name for uplink direction.

         If a corresponding QCI policy profile does not exist in
         TIMETRA-MOBILE-PROFILE-MIB::tmnxMobProfQciPolTable,
         an 'inconsistentValue' error will be returned."
    DEFVAL { "default" }
    ::= { tmnxMobServEntry 9 }

tmnxMobServDownlinkQciPolName  OBJECT-TYPE
    SYNTAX      TmnxMobProfName
    MAX-ACCESS  read-write
    STATUS      current
    DESCRIPTION
        "The value of tmnxMobServDownlinkQciPolName specifies the QoS Class
         Identifier (QCI) policy profile name for downlink direction.

         If a corresponding QCI policy profile does not exist in
         TIMETRA-MOBILE-PROFILE-MIB::tmnxMobProfQciPolTable,
         an 'inconsistentValue' error will be returned."
    DEFVAL { "default" }
    ::= { tmnxMobServEntry 10 }

tmnxMobServHomePlmnList  OBJECT-TYPE
    SYNTAX      TmnxMobProfNameOrEmpty
    MAX-ACCESS  read-write
    STATUS      current
    DESCRIPTION
        "The value of tmnxMobServHomePlmnList specifies the Home Public Land
         Mobile Network (H-PLMN). H-PLMN is the PLMN the customer belongs to.
         A PLMN list consists of a list of Mobile Country Code (MCC) and Mobile
         Network Code (MNC) ids.

         If a corresponding PLMN does not exist in
         TIMETRA-MOBILE-PROFILE-MIB::tmnxMobProfPlmnListTable,
         an 'inconsistentValue' error will be returned."
    DEFVAL { ''H }
    ::= { tmnxMobServEntry 11 }

tmnxMobServVisitingPlmnList  OBJECT-TYPE
    SYNTAX      TmnxMobProfNameOrEmpty
    MAX-ACCESS  read-write
    STATUS      current
    DESCRIPTION
        "The value of tmnxMobServVisitingPlmnList specifies the Visiting Public
         Land Mobile Network (V-PLMN). A PLMN list consists of a list of
         Mobile Country Code (MCC) and Mobile Network Code (MNC) ids.

         If a corresponding PLMN does not exist in
         TIMETRA-MOBILE-PROFILE-MIB::tmnxMobProfPlmnListTable,
         an 'inconsistentValue' error will be returned."
    DEFVAL { ''H }
    ::= { tmnxMobServEntry 12 }

tmnxMobServPolBaseName  OBJECT-TYPE
    SYNTAX      TmnxMobProfNameOrEmpty
    MAX-ACCESS  read-write
    STATUS      current
    DESCRIPTION
        "The value of tmnxMobServPolBaseName specifies the policy base profile
         name.

         If a corresponding policy base profile does not exist in
         TIMETRA-MOBILE-PROFILE-MIB::tmnxMobProfPolBaseTable,
         an 'inconsistentValue' error will be returned."
    DEFVAL { ''H }
    ::= { tmnxMobServEntry 13 }

tmnxMobServChargingProfHome  OBJECT-TYPE
    SYNTAX      TmnxMobChargingProfile
    MAX-ACCESS  read-write
    STATUS      current
    DESCRIPTION
        "The value of tmnxMobServChargingProfHome specifies the charging
         trigger rules applied for home subscribers.

         If a corresponding charging profile does not exist in
         TIMETRA-MOBILE-PROFILE-MIB::tmnxMobProfSgwChargingTable,
         an 'inconsistentValue' error will be returned."
    DEFVAL { 0 }
    ::= { tmnxMobServEntry 14 }

tmnxMobServChargingProfVisiting  OBJECT-TYPE
    SYNTAX      TmnxMobChargingProfile
    MAX-ACCESS  read-write
    STATUS      current
    DESCRIPTION
        "The value of tmnxMobServChargingProfVisiting specifies the charging
         trigger rules applied for visiting subscribers.

         If a corresponding charging profile does not exist in
         TIMETRA-MOBILE-PROFILE-MIB::tmnxMobProfSgwChargingTable,
         an 'inconsistentValue' error will be returned."
    DEFVAL { 0 }
    ::= { tmnxMobServEntry 15 }

tmnxMobServChargingProfRoaming  OBJECT-TYPE
    SYNTAX      TmnxMobChargingProfile
    MAX-ACCESS  read-write
    STATUS      current
    DESCRIPTION
        "The value of tmnxMobServChargingProfRoaming specifies the charging
         trigger rules applied for roaming subscribers.

         If a corresponding charging profile does not exist in
         TIMETRA-MOBILE-PROFILE-MIB::tmnxMobProfSgwChargingTable,
         an 'inconsistentValue' error will be returned."
    DEFVAL { 0 }
    ::= { tmnxMobServEntry 16 }

tmnxMobServChrgCcIgnoreAny  OBJECT-TYPE
    SYNTAX      TmnxEnabledDisabled
    MAX-ACCESS  read-write
    STATUS      current
    DESCRIPTION
        "The value of tmnxMobServChrgCcIgnoreAny specifies to ignore
         HSS or MME supplied charging characteristics for any subscriber.
         Corresponding default profile is selected when the received charging
         characteristics is ignored."
    DEFVAL { disabled }
    ::= { tmnxMobServEntry 17 }

tmnxMobServChrgCcIgnoreHome  OBJECT-TYPE
    SYNTAX      TmnxEnabledDisabled
    MAX-ACCESS  read-write
    STATUS      current
    DESCRIPTION
        "The value of tmnxMobServChrgCcIgnoreHome specifies to ignore HSS or MME
         supplied charging characteristics for home scenarios. Corresponding
         default profile is selected when the received charging characteristics
         is ignored."
    DEFVAL { disabled }
    ::= { tmnxMobServEntry 18 }

tmnxMobServChrgCcIgnoreVisiting  OBJECT-TYPE
    SYNTAX      TmnxEnabledDisabled
    MAX-ACCESS  read-write
    STATUS      current
    DESCRIPTION
        "The value of tmnxMobServChrgCcIgnoreVisiting specifies to ignore
         HSS or MME supplied charging characteristics for visiting scenarios.
         Corresponding default profile is selected when the received charging
         characteristics is ignored."
    DEFVAL { disabled }
    ::= { tmnxMobServEntry 19 }

tmnxMobServChrgCcIgnoreRoaming  OBJECT-TYPE
    SYNTAX      TmnxEnabledDisabled
    MAX-ACCESS  read-write
    STATUS      current
    DESCRIPTION
        "The value of tmnxMobServChrgCcIgnoreRoaming specifies to ignore
         HSS or MME supplied charging characteristics for roaming scenarios.
         Corresponding default profile is selected when the received charging
         characteristics is ignored."
    DEFVAL { disabled }
    ::= { tmnxMobServEntry 20 }

tmnxMobServChrgCcReject  OBJECT-TYPE
    SYNTAX      TruthValue
    MAX-ACCESS  read-write
    STATUS      current
    DESCRIPTION
        "The value of tmnxMobServChrgCcReject specifies to reject HSS or MME
         supplied charging characteristics for a subscriber.
         Corresponding default charging profile is selected when the value of
         this object is set to 'false'.

         The value of tmnxMobServChrgCcReject is applicable only when the HSS
         or MME supplied charging characteristics are not ignored."
    DEFVAL { false }
    ::= { tmnxMobServEntry 21 }

tmnxMobServChrgNodeId  OBJECT-TYPE
    SYNTAX      DisplayString (SIZE (0..20))
    MAX-ACCESS  read-write
    STATUS      current
    DESCRIPTION
        "The value of tmnxMobServChrgNodeId specifies an operator
         configurable identifier for the charging gateway."
    DEFVAL { ''H }
    ::= { tmnxMobServEntry 22 }

tmnxMobServChargingAvpDiag    OBJECT-TYPE
    SYNTAX      TmnxCdrDiagnosticAction
    MAX-ACCESS  read-write
    STATUS      current
    DESCRIPTION
        "The value of tmnxMobServChargingAvpDiag specifies whether the
         Diagnostics should be included or excluded in the Charging Data
         Record (CDR)."
    DEFVAL { included }
    ::= { tmnxMobServEntry 23 }

--
--  Signaling table
--

tmnxMobServSigTableLastChanged  OBJECT-TYPE
    SYNTAX      TimeStamp
    MAX-ACCESS  read-only
    STATUS      current
    DESCRIPTION
        "The value of tmnxMobServSigTableLastChanged indicates the sysUpTime at
         the time of the last modification to tmnxMobServSigTable by adding,
         deleting an entry or change to a writable object in the table.

         If no changes were made to the table since the last re-initialization
         of the local network management subsystem, then this object contains
         a zero value."
    ::= { tmnxMobServingGlobalObjs 2 }

tmnxMobServSigTable  OBJECT-TYPE
    SYNTAX      SEQUENCE OF TmnxMobServSigEntry
    MAX-ACCESS  not-accessible
    STATUS      current
    DESCRIPTION
        "The tmnxMobServSigTable provides an extension of the tmnxMobServTable
         for signaling configuration."
    ::= { tmnxMobServingConfObjs 2 }

tmnxMobServSigEntry  OBJECT-TYPE
    SYNTAX      TmnxMobServSigEntry
    MAX-ACCESS  not-accessible
    STATUS      current
    DESCRIPTION
        "Each row entry represents additional columns for signaling
         configuration for a Serving Gateway (SGW)."
    AUGMENTS { tmnxMobServEntry }
    ::= { tmnxMobServSigTable 1 }

TmnxMobServSigEntry ::= SEQUENCE {
        tmnxMobServSigLastChanged         TimeStamp,
        tmnxMobServSigGtpcProfile         TmnxMobProfName,
        tmnxMobServSigGtpuProfile         TmnxMobProfName,
        tmnxMobServSigPmipv6Profile       TmnxMobProfName,
        tmnxMobServSigPmipv6RtrAdIntvl    TmnxMobRtrAdvtInterval,
        tmnxMobServSigPmipv6RtrAdLife     TmnxMobRtrAdvtLifeTime,
        tmnxMobServSigPmipv6AddrScheme    TmnxMobAddrScheme,
        tmnxMobServSigDiaProfile          TmnxMobProfNameOrEmpty,
        tmnxMobServSigDiaOriginRealm      TmnxMobDiaPeerHost,
        tmnxMobServSigDiaOriginHost       TmnxMobDiaPeerHost,
        tmnxMobServSigDefaultIfVRtrId     TmnxVRtrID,
        tmnxMobServSigDefaultIfIndex      InterfaceIndexOrZero
    }

tmnxMobServSigLastChanged  OBJECT-TYPE
    SYNTAX      TimeStamp
    MAX-ACCESS  read-only
    STATUS      current
    DESCRIPTION
        "The value of tmnxMobServSigLastChanged indicates the timestamp of
         the last change to this row in tmnxMobServSigTable."
    ::= { tmnxMobServSigEntry 1 }

tmnxMobServSigGtpcProfile  OBJECT-TYPE
    SYNTAX      TmnxMobProfName
    MAX-ACCESS  read-write
    STATUS      current
    DESCRIPTION
        "The value of tmnxMobServSigGtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { "default" }
    ::= { tmnxMobServSigEntry 2 }

tmnxMobServSigGtpuProfile  OBJECT-TYPE
    SYNTAX      TmnxMobProfName
    MAX-ACCESS  read-write
    STATUS      current
    DESCRIPTION
        "The value of tmnxMobServSigGtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { "default" }
    ::= { tmnxMobServSigEntry 3 }

tmnxMobServSigPmipv6Profile  OBJECT-TYPE
    SYNTAX      TmnxMobProfName
    MAX-ACCESS  read-write
    STATUS      current
    DESCRIPTION
        "The value of tmnxMobServSigPmipv6Profile specifies the Proxy Mobile
         IPv6 (PMIPv6) profile name. The PMIPv6 profile provides protocol
         related information applicable to PMIPv6 peers.

         If a corresponding PMIPv6 profile does not exist in
         TIMETRA-MOBILE-PROFILE-MIB::tmnxMobProfPmipv6Table,
         an 'inconsistentValue' error will be returned."
    DEFVAL { "default" }
    ::= { tmnxMobServSigEntry 4 }

tmnxMobServSigPmipv6RtrAdIntvl  OBJECT-TYPE
    SYNTAX      TmnxMobRtrAdvtInterval
    UNITS       "minutes"
    MAX-ACCESS  read-write
    STATUS      current
    DESCRIPTION
        "The value of tmnxMobServSigPmipv6RtrAdIntvl specifies the router
         advertisement interval. The Serving Gateway (SGW) advertises IPv6
         prefixes to the User Equipments (UEs) at router advertisement
         interval."
    DEFVAL { 30 }
    ::= { tmnxMobServSigEntry 5 }

tmnxMobServSigPmipv6RtrAdLife  OBJECT-TYPE
    SYNTAX      TmnxMobRtrAdvtLifeTime
    UNITS       "hours"
    MAX-ACCESS  read-write
    STATUS      current
    DESCRIPTION
        "The value of tmnxMobServSigPmipv6RtrAdLife specifies the router
         advertisement life time. It specifies the validity of the IPv6 prefix
         advertised from the Serving Gateway (SGW) to the User
         Equipments (UEs)."
    DEFVAL { 12 }
    ::= { tmnxMobServSigEntry 6 }

tmnxMobServSigPmipv6AddrScheme  OBJECT-TYPE
    SYNTAX      TmnxMobAddrScheme
    MAX-ACCESS  read-write
    STATUS      current
    DESCRIPTION
        "The value of tmnxMobServSigPmipv6AddrScheme specifies the addressing
         scheme. If the value is set to 'stateful', the User Equipment (UE) uses
         DHCPv6 to get IPv6 address. If the value is set to 'stateless', the UE
         uses ICMPv6 to get IPv6 address."
    DEFVAL { stateless }
    ::= { tmnxMobServSigEntry 7 }

tmnxMobServSigDiaProfile  OBJECT-TYPE
    SYNTAX      TmnxMobProfNameOrEmpty
    MAX-ACCESS  read-write
    STATUS      current
    DESCRIPTION
        "The value of tmnxMobServSigDiaProfile specifies the diameter profile
         name. Diameter profile provides diameter connection related
         information.

         If a corresponding diameter profile does not exist in
         TIMETRA-MOBILE-PROFILE-MIB::tmnxMobProfDiaTable,
         an 'inconsistentValue' error will be returned."
    DEFVAL { "default" }
    ::= { tmnxMobServSigEntry 8 }

tmnxMobServSigDiaOriginRealm  OBJECT-TYPE
    SYNTAX      TmnxMobDiaPeerHost
    MAX-ACCESS  read-write
    STATUS      current
    DESCRIPTION
        "The value of tmnxMobServSigDiaOriginRealm specifies the originating
         realm or domain name of a Diameter node. The Originating Realm is
         included in messages exchanged with a Diameter peer."
    DEFVAL { ''H }
    ::= { tmnxMobServSigEntry 9 }

tmnxMobServSigDiaOriginHost  OBJECT-TYPE
    SYNTAX      TmnxMobDiaPeerHost
    MAX-ACCESS  read-write
    STATUS      current
    DESCRIPTION
        "The value of tmnxMobServSigDiaOriginHost specifies the originating
         host name of a Diameter node. The Originating Host information is sent
         in requests to a Diameter peer."
    DEFVAL { ''H }
    ::= { tmnxMobServSigEntry 10 }

tmnxMobServSigDefaultIfVRtrId  OBJECT-TYPE
    SYNTAX      TmnxVRtrID
    MAX-ACCESS  read-write
    STATUS      current
    DESCRIPTION
        "The value of tmnxMobServSigDefaultIfVRtrId specifies the virtual
         router to which the default signaling interface specified by
         tmnxMobServSigDefaultIfIndex belongs."
    DEFVAL { 1 }
    ::= { tmnxMobServSigEntry 11 }

tmnxMobServSigDefaultIfIndex  OBJECT-TYPE
    SYNTAX      InterfaceIndexOrZero
    MAX-ACCESS  read-write
    STATUS      current
    DESCRIPTION
        "The value of tmnxMobServSigDefaultIfIndex specifies the interface
         index of the default interface used by the signaling protocols.
         When the value of this object is set to 0, no default interface has
         been assigned."
    DEFVAL { 0 }
    ::= { tmnxMobServSigEntry 12 }

--
--  Gxc table
--

tmnxMobServGxcTableLastChanged  OBJECT-TYPE
    SYNTAX      TimeStamp
    MAX-ACCESS  read-only
    STATUS      current
    DESCRIPTION
        "The value of tmnxMobServGxcTableLastChanged indicates the sysUpTime at
         the time of the last modification to tmnxMobServGxcTable by adding,
         deleting an entry or change to a writable object in the table.

         If no changes were made to the table since the last re-initialization
         of the local network management subsystem, then this object contains
         a zero value."
    ::= { tmnxMobServingGlobalObjs 3 }

tmnxMobServGxcTable  OBJECT-TYPE
    SYNTAX      SEQUENCE OF TmnxMobServGxcEntry
    MAX-ACCESS  not-accessible
    STATUS      current
    DESCRIPTION
        "The tmnxMobServGxcTable provides an extension of the tmnxMobServTable
         for Gxc reference point configuration."
    ::= { tmnxMobServingConfObjs 3 }

tmnxMobServGxcEntry  OBJECT-TYPE
    SYNTAX      TmnxMobServGxcEntry
    MAX-ACCESS  not-accessible
    STATUS      current
    DESCRIPTION
        "Each row entry represents additional columns for Gxc reference point
         configuration for a Serving Gateway (SGW)."
    AUGMENTS { tmnxMobServEntry }
    ::= { tmnxMobServGxcTable 1 }

TmnxMobServGxcEntry ::= SEQUENCE {
        tmnxMobServGxcLastChanged            TimeStamp,
        tmnxMobServGxcDiaIfVRtrId            TmnxVRtrID,
        tmnxMobServGxcDiaIfIndex             InterfaceIndexOrZero,
        tmnxMobServGxcDiaTransTimer          TmnxMobDiaTransTimer,
        tmnxMobServGxcDiaRetryCount          TmnxMobDiaRetryCount,
        tmnxMobServGxcDiameterApp            Unsigned32,
        tmnxMobServGxcDefPriDiaPeer          TmnxMobProfNameOrEmpty,
        tmnxMobServGxcDefSecDiaPeer          TmnxMobProfNameOrEmpty
    }

tmnxMobServGxcLastChanged  OBJECT-TYPE
    SYNTAX      TimeStamp
    MAX-ACCESS  read-only
    STATUS      current
    DESCRIPTION
        "The value of tmnxMobServGxcLastChanged indicates the timestamp of
         the last change to this row in tmnxMobServGxcTable."
    ::= { tmnxMobServGxcEntry 1 }

tmnxMobServGxcDiaIfVRtrId  OBJECT-TYPE
    SYNTAX      TmnxVRtrID
    MAX-ACCESS  read-write
    STATUS      current
    DESCRIPTION
        "The value of tmnxMobServGxcDiaIfVRtrId specifies the virtual
         router to which the interface specified by tmnxMobServGxcDiaIfIndex
         belongs."
    DEFVAL { 1 }
    ::= { tmnxMobServGxcEntry 2 }

tmnxMobServGxcDiaIfIndex  OBJECT-TYPE
    SYNTAX      InterfaceIndexOrZero
    MAX-ACCESS  read-write
    STATUS      current
    DESCRIPTION
        "The value of tmnxMobServGxcDiaIfIndex specifies the interface
         index of the local interface used for the diameter connection.
         When the value of this object is set to 0, no interface has
         been assigned."
    DEFVAL { 0 }
    ::= { tmnxMobServGxcEntry 3 }

tmnxMobServGxcDiaTransTimer  OBJECT-TYPE
    SYNTAX      TmnxMobDiaTransTimer
    MAX-ACCESS  read-write
    STATUS      current
    DESCRIPTION
        "The value of tmnxMobServGxcDiaTransTimer specifies the maximum
         amount of time the node waits for a diameter peer to respond before
         trying another peer."
    DEFVAL { 5 }
    ::= { tmnxMobServGxcEntry 4 }

tmnxMobServGxcDiaRetryCount  OBJECT-TYPE
    SYNTAX      TmnxMobDiaRetryCount
    MAX-ACCESS  read-write
    STATUS      current
    DESCRIPTION
        "The value of tmnxMobServGxcDiaRetryCount specifies the number of times
         the same message is re-tried before declaring a failed attempt."
    DEFVAL { 3 }
    ::= { tmnxMobServGxcEntry 5 }

tmnxMobServGxcDiameterApp  OBJECT-TYPE
    SYNTAX      Unsigned32
    MAX-ACCESS  read-write
    STATUS      current
    DESCRIPTION
        "The value of tmnxMobServGxcDiameterApp specifies the diameter
         application number."
    DEFVAL { 0 }
    ::= { tmnxMobServGxcEntry 6 }

tmnxMobServGxcDefPriDiaPeer  OBJECT-TYPE
    SYNTAX      TmnxMobProfNameOrEmpty
    MAX-ACCESS  read-write
    STATUS      current
    DESCRIPTION
        "The value of tmnxMobServGxcDefPriDiaPeer specifies the default primary
         diameter peer profile name.

         If a corresponding diameter peer profile does not exist in
         TIMETRA-MOBILE-PROFILE-MIB::tmnxMobProfDiaPeerTable,
         an 'inconsistentValue' error will be returned."
    DEFVAL { ''H }
    ::= { tmnxMobServGxcEntry 7 }

tmnxMobServGxcDefSecDiaPeer  OBJECT-TYPE
    SYNTAX      TmnxMobProfNameOrEmpty
    MAX-ACCESS  read-write
    STATUS      current
    DESCRIPTION
        "The value of tmnxMobServGxcDefSecDiaPeer specifies the default
         secondary diameter peer profile name.

         If a corresponding diameter peer profile does not exist in
         TIMETRA-MOBILE-PROFILE-MIB::tmnxMobProfDiaPeerTable,
         an 'inconsistentValue' error will be returned."
    DEFVAL { ''H }
    ::= { tmnxMobServGxcEntry 8 }

--
--  S5 table
--

tmnxMobServS5TableLastChanged  OBJECT-TYPE
    SYNTAX      TimeStamp
    MAX-ACCESS  read-only
    STATUS      current
    DESCRIPTION
        "The value of tmnxMobServS5TableLastChanged indicates the sysUpTime at
         the time of the last modification to tmnxMobServS5Table by adding,
         deleting an entry or change to a writable object in the table.

         If no changes were made to the table since the last re-initialization
         of the local network management subsystem, then this object contains
         a zero value."
    ::= { tmnxMobServingGlobalObjs 4 }

tmnxMobServS5Table  OBJECT-TYPE
    SYNTAX      SEQUENCE OF TmnxMobServS5Entry
    MAX-ACCESS  not-accessible
    STATUS      current
    DESCRIPTION
        "The tmnxMobServS5Table provides an extension of the tmnxMobServTable
         for S5 reference point configuration."
    ::= { tmnxMobServingConfObjs 4 }

tmnxMobServS5Entry  OBJECT-TYPE
    SYNTAX      TmnxMobServS5Entry
    MAX-ACCESS  not-accessible
    STATUS      current
    DESCRIPTION
        "Each row entry represents additional columns for S5 reference point
         configuration for a Serving Gateway (SGW)."
    AUGMENTS { tmnxMobServEntry }
    ::= { tmnxMobServS5Table 1 }

TmnxMobServS5Entry ::= SEQUENCE {
        tmnxMobServS5LastChanged             TimeStamp,
        tmnxMobServS5PeerList                TmnxMobProfNameOrEmpty,
        tmnxMobServS5GtpcIfVRtrId            TmnxVRtrID,
        tmnxMobServS5GtpcIfIndex             InterfaceIndexOrZero,
        tmnxMobServS5GtpuIfVRtrId            TmnxVRtrID,
        tmnxMobServS5GtpuIfIndex             InterfaceIndexOrZero,
        tmnxMobServS5Pmipv6IfVRtrId          TmnxVRtrID,
        tmnxMobServS5Pmipv6IfIndex           InterfaceIndexOrZero,
        tmnxMobServS5Pmipv6LnkLclAdrType     InetAddressType,
        tmnxMobServS5Pmipv6LnkLclAddress     InetAddress,
        tmnxMobServS5GtpcProfile             TmnxMobProfNameOrEmpty,
        tmnxMobServS5GtpuProfile             TmnxMobProfNameOrEmpty,
        tmnxMobServS5Pmipv6Profile           TmnxMobProfNameOrEmpty,
        tmnxMobServS5Pmipv6RtrAdIntvl        TmnxMobRtrAdvtInterval,
        tmnxMobServS5Pmipv6RtrAdLife         TmnxMobRtrAdvtLifeTime,
        tmnxMobServS5Pmipv6RtrAddrScheme     TmnxMobAddrScheme,
        tmnxMobServS5DualStackPref           TmnxMobDualStackPref,
        tmnxMobServS5DualStackPrefCplane     INTEGER
    }

tmnxMobServS5LastChanged  OBJECT-TYPE
    SYNTAX      TimeStamp
    MAX-ACCESS  read-only
    STATUS      current
    DESCRIPTION
        "The value of tmnxMobServS5LastChanged indicates the timestamp of
         the last change to this row in tmnxMobServS5Table."
    ::= { tmnxMobServS5Entry 1 }

tmnxMobServS5PeerList  OBJECT-TYPE
    SYNTAX      TmnxMobProfNameOrEmpty
    MAX-ACCESS  read-write
    STATUS      current
    DESCRIPTION
        "The value of tmnxMobServS5PeerList specifies the peer list name.

         If a corresponding peer does not exist in
         TIMETRA-MOBILE-PROFILE-MIB::tmnxMobProfPeerListTable,
         an 'inconsistentValue' error will be returned."
    DEFVAL { ''H }
    ::= { tmnxMobServS5Entry 2 }

tmnxMobServS5GtpcIfVRtrId  OBJECT-TYPE
    SYNTAX      TmnxVRtrID
    MAX-ACCESS  read-write
    STATUS      current
    DESCRIPTION
        "The value of tmnxMobServS5GtpcIfVRtrId specifies the virtual
         router to which the interface specified by tmnxMobServS5GtpcIfIndex
         belongs."
    DEFVAL { 1 }
    ::= { tmnxMobServS5Entry 3 }

tmnxMobServS5GtpcIfIndex  OBJECT-TYPE
    SYNTAX      InterfaceIndexOrZero
    MAX-ACCESS  read-write
    STATUS      current
    DESCRIPTION
        "The value of tmnxMobServS5GtpcIfIndex specifies the interface
         index of the local interface used for the General Packet Radio
         Services Tunneling Protocol for Control Plane (GTP-C) signaling.
         When the value of this object is set to 0, no interface has
         been assigned.

         If value of this object is not set then the value of
         tmnxMobServSigDefaultIfIndex is used."
    DEFVAL { 0 }
    ::= { tmnxMobServS5Entry 4 }

tmnxMobServS5GtpuIfVRtrId  OBJECT-TYPE
    SYNTAX      TmnxVRtrID
    MAX-ACCESS  read-write
    STATUS      current
    DESCRIPTION
        "The value of tmnxMobServS5GtpuIfVRtrId specifies the virtual
         router to which the interface specified by tmnxMobServS5GtpuIfIndex
         belongs."
    DEFVAL { 1 }
    ::= { tmnxMobServS5Entry 5 }

tmnxMobServS5GtpuIfIndex  OBJECT-TYPE
    SYNTAX      InterfaceIndexOrZero
    MAX-ACCESS  read-write
    STATUS      current
    DESCRIPTION
        "The value of tmnxMobServS5GtpuIfIndex specifies the interface
         index of the local interface used for the General Packet Radio
         Services Tunneling Protocol for User Plane (GTP-U) signaling.
         When the value of this object is set to 0, no interface has
         been assigned.

         If value of this object is not set then the value of
         tmnxMobServSigDefaultIfIndex is used."
    DEFVAL { 0 }
    ::= { tmnxMobServS5Entry 6 }

tmnxMobServS5Pmipv6IfVRtrId  OBJECT-TYPE
    SYNTAX      TmnxVRtrID
    MAX-ACCESS  read-write
    STATUS      current
    DESCRIPTION
        "The value of tmnxMobServS5Pmipv6IfVRtrId specifies the virtual
         router to which the interface specified by tmnxMobServS5Pmipv6IfIndex
         belongs."
    DEFVAL { 1 }
    ::= { tmnxMobServS5Entry 7 }

tmnxMobServS5Pmipv6IfIndex  OBJECT-TYPE
    SYNTAX      InterfaceIndexOrZero
    MAX-ACCESS  read-write
    STATUS      current
    DESCRIPTION
        "The value of tmnxMobServS5Pmipv6IfIndex specifies the interface
         index of the local interface used for the Proxy Mobile IPv6 (PMIPv6)
         signaling. When the value of this object is set to 0, no interface has
         been assigned.

         If value of this object is not set then the value of
         tmnxMobServSigDefaultIfIndex is used."
    DEFVAL { 0 }
    ::= { tmnxMobServS5Entry 8 }

tmnxMobServS5Pmipv6LnkLclAdrType  OBJECT-TYPE
    SYNTAX      InetAddressType
    MAX-ACCESS  read-write
    STATUS      current
    DESCRIPTION
        "The value of tmnxMobServS5Pmipv6LnkLclAdrType specifies the IP address
         type of the link local address of the Proxy Mobile IPv6 (PMIPv6)
         interface."
    DEFVAL { unknown }
    ::= { tmnxMobServS5Entry 9 }

tmnxMobServS5Pmipv6LnkLclAddress  OBJECT-TYPE
    SYNTAX      InetAddress (SIZE (0|16))
    MAX-ACCESS  read-write
    STATUS      current
    DESCRIPTION
        "The value of tmnxMobServS5Pmipv6LnkLclAddress specifies the link local
         IP address of the Proxy Mobile IPv6 (PMIPv6) interface.
         The object tmnxMobServS5Pmipv6IfIndex must be set before setting
         tmnxMobServS5Pmipv6LnkLclAddress."
    DEFVAL { ''H }
    ::= { tmnxMobServS5Entry 10 }

tmnxMobServS5GtpcProfile  OBJECT-TYPE
    SYNTAX      TmnxMobProfNameOrEmpty
    MAX-ACCESS  read-write
    STATUS      current
    DESCRIPTION
        "The value of tmnxMobServS5GtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobServS5Entry 11 }

tmnxMobServS5GtpuProfile  OBJECT-TYPE
    SYNTAX      TmnxMobProfNameOrEmpty
    MAX-ACCESS  read-write
    STATUS      current
    DESCRIPTION
        "The value of tmnxMobServS5GtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobServS5Entry 12 }

tmnxMobServS5Pmipv6Profile  OBJECT-TYPE
    SYNTAX      TmnxMobProfNameOrEmpty
    MAX-ACCESS  read-write
    STATUS      current
    DESCRIPTION
        "The value of tmnxMobServS5Pmipv6Profile specifies the Proxy Mobile
         IPv6 (PMIPv6) profile name. The PMIPv6 profile provides protocol
         related information applicable to PMIPv6 peers.

         If a corresponding PMIPv6 profile does not exist in
         TIMETRA-MOBILE-PROFILE-MIB::tmnxMobProfPmipv6Table,
         an 'inconsistentValue' error will be returned."
    DEFVAL { ''H }
    ::= { tmnxMobServS5Entry 13 }

tmnxMobServS5Pmipv6RtrAdIntvl  OBJECT-TYPE
    SYNTAX      TmnxMobRtrAdvtInterval
    UNITS       "minutes"
    MAX-ACCESS  read-write
    STATUS      current
    DESCRIPTION
        "The value of tmnxMobServS5Pmipv6RtrAdIntvl specifies the router
         advertisement interval. The Serving Gateway (SGW) advertises IPv6
         prefixes to the User Equipments (UEs) at router advertisement
         interval."
    DEFVAL {30 }
    ::= { tmnxMobServS5Entry 14 }

tmnxMobServS5Pmipv6RtrAdLife  OBJECT-TYPE
    SYNTAX      TmnxMobRtrAdvtLifeTime
    UNITS       "hours"
    MAX-ACCESS  read-write
    STATUS      current
    DESCRIPTION
        "The value of tmnxMobServS5Pmipv6RtrAdLife specifies the router
         advertisement life time. It specifies the validity of the IPv6 prefix
         advertised from the Serving Gateway (SGW) to the User
         Equipments (UEs)."
    DEFVAL { 12 }
    ::= { tmnxMobServS5Entry 15 }

tmnxMobServS5Pmipv6RtrAddrScheme  OBJECT-TYPE
    SYNTAX      TmnxMobAddrScheme
    MAX-ACCESS  read-write
    STATUS      current
    DESCRIPTION
        "The value of tmnxMobServS5Pmipv6RtrAddrScheme specifies the addressing
         scheme. If the value is set to 'stateful', the User Equipment (UE) uses
         DHCPv6 to get IPv6 address. If the value is set to 'stateless', the UE
         uses ICMPv6 to get IPv6 address."
    DEFVAL { stateless }
    ::= { tmnxMobServS5Entry 16 }

tmnxMobServS5DualStackPref  OBJECT-TYPE
    SYNTAX      TmnxMobDualStackPref
    MAX-ACCESS  read-write
    STATUS      current
    DESCRIPTION
        "The value of tmnxMobServS5DualStackPref specifies the user plane
         preference in a dual stack when both IPv4 and IPv6 addresses are
         configured for the S5 interface.

         If the value 'useCplane' is specified then the value is inherited from
         the value of tmnxMobServS5DualStackPrefCplane."
    DEFVAL { useCplane }
    ::= { tmnxMobServS5Entry 17 }

tmnxMobServS5DualStackPrefCplane  OBJECT-TYPE
    SYNTAX       INTEGER {
                          ipv4      (1),
                          ipv6      (2)
                         }
    MAX-ACCESS  read-write
    STATUS      current
    DESCRIPTION
        "The value of tmnxMobServS5DualStackPrefCplane specifies the control
         plane preference in a dual stack when both IPv4 and IPv6 addresses
         are configured for the S5 interface."
    DEFVAL { ipv6 }
    ::= { tmnxMobServS5Entry 18 }

--
--  S8 table
--

tmnxMobServS8TableLastChanged  OBJECT-TYPE
    SYNTAX      TimeStamp
    MAX-ACCESS  read-only
    STATUS      current
    DESCRIPTION
        "The value of tmnxMobServS8TableLastChanged indicates the sysUpTime at
         the time of the last modification to tmnxMobServS8Table by adding,
         deleting an entry or change to a writable object in the table.

         If no changes were made to the table since the last re-initialization
         of the local network management subsystem, then this object contains
         a zero value."
    ::= { tmnxMobServingGlobalObjs 5 }

tmnxMobServS8Table  OBJECT-TYPE
    SYNTAX      SEQUENCE OF TmnxMobServS8Entry
    MAX-ACCESS  not-accessible
    STATUS      current
    DESCRIPTION
        "The tmnxMobServS8Table provides an extension of the tmnxMobServTable
         for S8 reference point configuration."
    ::= { tmnxMobServingConfObjs 5 }

tmnxMobServS8Entry  OBJECT-TYPE
    SYNTAX      TmnxMobServS8Entry
    MAX-ACCESS  not-accessible
    STATUS      current
    DESCRIPTION
        "Each row entry represents additional columns for S8 reference point
         configuration for a Serving Gateway (SGW)."
    AUGMENTS { tmnxMobServEntry }
    ::= { tmnxMobServS8Table 1 }

TmnxMobServS8Entry ::= SEQUENCE {
        tmnxMobServS8LastChanged             TimeStamp,
        tmnxMobServS8PeerList                TmnxMobProfNameOrEmpty,
        tmnxMobServS8GtpcIfVRtrId            TmnxVRtrID,
        tmnxMobServS8GtpcIfIndex             InterfaceIndexOrZero,
        tmnxMobServS8GtpuIfVRtrId            TmnxVRtrID,
        tmnxMobServS8GtpuIfIndex             InterfaceIndexOrZero,
        tmnxMobServS8Pmipv6IfVRtrId          TmnxVRtrID,
        tmnxMobServS8Pmipv6IfIndex           InterfaceIndexOrZero,
        tmnxMobServS8Pmipv6LnkLclAdrType     InetAddressType,
        tmnxMobServS8Pmipv6LnkLclAddress     InetAddress,
        tmnxMobServS8GtpcProfile             TmnxMobProfNameOrEmpty,
        tmnxMobServS8GtpuProfile             TmnxMobProfNameOrEmpty,
        tmnxMobServS8Pmipv6Profile           TmnxMobProfNameOrEmpty,
        tmnxMobServS8Pmipv6RtrAdIntvl        TmnxMobRtrAdvtInterval,
        tmnxMobServS8Pmipv6RtrAdLife         TmnxMobRtrAdvtLifeTime,
        tmnxMobServS8Pmipv6RtrAddrScheme     TmnxMobAddrScheme,
        tmnxMobServS8DualStackPref           TmnxMobDualStackPref,
        tmnxMobServS8DualStackPrefCplane     INTEGER
    }

tmnxMobServS8LastChanged  OBJECT-TYPE
    SYNTAX      TimeStamp
    MAX-ACCESS  read-only
    STATUS      current
    DESCRIPTION
        "The value of tmnxMobServS8LastChanged indicates the timestamp of
         the last change to this row in tmnxMobServS8Table."
    ::= { tmnxMobServS8Entry 1 }

tmnxMobServS8PeerList  OBJECT-TYPE
    SYNTAX      TmnxMobProfNameOrEmpty
    MAX-ACCESS  read-write
    STATUS      current
    DESCRIPTION
        "The value of tmnxMobServS8PeerList specifies the peer list name.

         If a corresponding peer does not exist in
         TIMETRA-MOBILE-PROFILE-MIB::tmnxMobProfPeerListTable,
         an 'inconsistentValue' error will be returned."
    DEFVAL { ''H }
    ::= { tmnxMobServS8Entry 2 }

tmnxMobServS8GtpcIfVRtrId  OBJECT-TYPE
    SYNTAX      TmnxVRtrID
    MAX-ACCESS  read-write
    STATUS      current
    DESCRIPTION
        "The value of tmnxMobServS8GtpcIfVRtrId specifies the virtual
         router to which the interface specified by tmnxMobServS8GtpcIfIndex
         belongs."
    DEFVAL { 1 }
    ::= { tmnxMobServS8Entry 3 }

tmnxMobServS8GtpcIfIndex  OBJECT-TYPE
    SYNTAX      InterfaceIndexOrZero
    MAX-ACCESS  read-write
    STATUS      current
    DESCRIPTION
        "The value of tmnxMobServS8GtpcIfIndex specifies the interface
         index of the local interface used for the General Packet Radio
         Services Tunneling Protocol for Control Plane (GTP-C) signaling.
         When the value of this object is set to 0, no interface has
         been assigned."
    DEFVAL { 0 }
    ::= { tmnxMobServS8Entry 4 }

tmnxMobServS8GtpuIfVRtrId  OBJECT-TYPE
    SYNTAX      TmnxVRtrID
    MAX-ACCESS  read-write
    STATUS      current
    DESCRIPTION
        "The value of tmnxMobServS8GtpuIfVRtrId specifies the virtual
         router to which the interface specified by tmnxMobServS8GtpuIfIndex
         belongs."
    DEFVAL { 1 }
    ::= { tmnxMobServS8Entry 5 }

tmnxMobServS8GtpuIfIndex  OBJECT-TYPE
    SYNTAX      InterfaceIndexOrZero
    MAX-ACCESS  read-write
    STATUS      current
    DESCRIPTION
        "The value of tmnxMobServS8GtpuIfIndex specifies the interface
         index of the local interface used for the General Packet Radio
         Services Tunneling Protocol for User Plane (GTP-U) signaling.
         When the value of this object is set to 0, no interface has
         been assigned."
    DEFVAL { 0 }
    ::= { tmnxMobServS8Entry 6 }

tmnxMobServS8Pmipv6IfVRtrId  OBJECT-TYPE
    SYNTAX      TmnxVRtrID
    MAX-ACCESS  read-write
    STATUS      current
    DESCRIPTION
        "The value of tmnxMobServS8Pmipv6IfVRtrId specifies the virtual
         router to which the interface specified by tmnxMobServS8Pmipv6IfIndex
         belongs."
    DEFVAL { 1 }
    ::= { tmnxMobServS8Entry 7 }

tmnxMobServS8Pmipv6IfIndex  OBJECT-TYPE
    SYNTAX      InterfaceIndexOrZero
    MAX-ACCESS  read-write
    STATUS      current
    DESCRIPTION
        "The value of tmnxMobServS8Pmipv6IfIndex specifies the interface
         index of the local interface used for the Proxy Mobile IPv6 (PMIPv6)
         signaling. When the value of this object is set to 0, no interface has
         been assigned."
    DEFVAL { 0 }
    ::= { tmnxMobServS8Entry 8 }

tmnxMobServS8Pmipv6LnkLclAdrType  OBJECT-TYPE
    SYNTAX      InetAddressType
    MAX-ACCESS  read-write
    STATUS      current
    DESCRIPTION
        "The value of tmnxMobServS8Pmipv6LnkLclAdrType specifies the IP address
         type of the link local address of the Proxy Mobile IPv6(PMIPv6)
         interface."
    DEFVAL { unknown }
    ::= { tmnxMobServS8Entry 9 }

tmnxMobServS8Pmipv6LnkLclAddress  OBJECT-TYPE
    SYNTAX      InetAddress (SIZE (0|16))
    MAX-ACCESS  read-write
    STATUS      current
    DESCRIPTION
        "The value of tmnxMobServS8Pmipv6LnkLclAddress specifies the link local
         IP address of the Proxy Mobile IPv6 (PMIPv6) interface."
    DEFVAL { ''H }
    ::= { tmnxMobServS8Entry 10 }

tmnxMobServS8GtpcProfile  OBJECT-TYPE
    SYNTAX      TmnxMobProfNameOrEmpty
    MAX-ACCESS  read-write
    STATUS      current
    DESCRIPTION
        "The value of tmnxMobServS8GtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobServS8Entry 11 }

tmnxMobServS8GtpuProfile  OBJECT-TYPE
    SYNTAX      TmnxMobProfNameOrEmpty
    MAX-ACCESS  read-write
    STATUS      current
    DESCRIPTION
        "The value of tmnxMobServS8GtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobServS8Entry 12 }

tmnxMobServS8Pmipv6Profile  OBJECT-TYPE
    SYNTAX      TmnxMobProfNameOrEmpty
    MAX-ACCESS  read-write
    STATUS      current
    DESCRIPTION
        "The value of tmnxMobServS8Pmipv6Profile specifies the Proxy Mobile
         IPv6 (PMIPv6) profile name. The PMIPv6 profile provides protocol
         related information applicable to PMIPv6 peers.

         If a corresponding PMIPv6 profile does not exist in
         TIMETRA-MOBILE-PROFILE-MIB::tmnxMobProfPmipv6Table,
         an 'inconsistentValue' error will be returned."
    DEFVAL { ''H }
    ::= { tmnxMobServS8Entry 13 }

tmnxMobServS8Pmipv6RtrAdIntvl  OBJECT-TYPE
    SYNTAX      TmnxMobRtrAdvtInterval
    UNITS       "minutes"
    MAX-ACCESS  read-write
    STATUS      current
    DESCRIPTION
        "The value of tmnxMobServS8Pmipv6RtrAdIntvl specifies the router
         advertisement interval. The Serving Gateway (SGW) advertises IPv6
         prefixes to the User Equipments (UEs) at router advertisement
         interval."
    DEFVAL { 30 }
    ::= { tmnxMobServS8Entry 14 }

tmnxMobServS8Pmipv6RtrAdLife  OBJECT-TYPE
    SYNTAX      TmnxMobRtrAdvtLifeTime
    UNITS       "hours"
    MAX-ACCESS  read-write
    STATUS      current
    DESCRIPTION
        "The value of tmnxMobServS8Pmipv6RtrAdLife specifies the router
         advertisement life time. It specifies the validity of the IPv6 prefix
         advertised from the Serving Gateway (SGW) to the User
         Equipments (UEs)."
    DEFVAL { 12 }
    ::= { tmnxMobServS8Entry 15 }

tmnxMobServS8Pmipv6RtrAddrScheme  OBJECT-TYPE
    SYNTAX      TmnxMobAddrScheme
    MAX-ACCESS  read-write
    STATUS      current
    DESCRIPTION
        "The value of tmnxMobServS8Pmipv6RtrAddrScheme specifies the addressing
         scheme. If the value is set to 'stateful', the User Equipment (UE) uses
         DHCPv6 to get IPv6 address. If the value is set to 'stateless', the UE
         uses ICMPv6 to get IPv6 address."
    DEFVAL { stateless }
    ::= { tmnxMobServS8Entry 16 }

tmnxMobServS8DualStackPref  OBJECT-TYPE
    SYNTAX      TmnxMobDualStackPref
    MAX-ACCESS  read-write
    STATUS      current
    DESCRIPTION
        "The value of tmnxMobServS8DualStackPref specifies the user plane
         preference in a dual stack when both IPv4 and IPv6 addresses are
         configured for the S8 interface.

         If the value 'useCplane' is specified then the value is inherited from
         the value of tmnxMobServS8DualStackPrefCplane."
    DEFVAL { useCplane }
    ::= { tmnxMobServS8Entry 17 }

tmnxMobServS8DualStackPrefCplane  OBJECT-TYPE
    SYNTAX       INTEGER {
                          ipv4      (1),
                          ipv6      (2)
                         }
    MAX-ACCESS  read-write
    STATUS      current
    DESCRIPTION
        "The value of tmnxMobServS8DualStackPrefCplane specifies the control
         plane preference in a dual stack when both IPv4 and IPv6 addresses
         are configured for the S8 interface."
    DEFVAL { ipv6 }
    ::= { tmnxMobServS8Entry 18 }

--
--  S11 table
--

tmnxMobServS11TableLastChanged  OBJECT-TYPE
    SYNTAX      TimeStamp
    MAX-ACCESS  read-only
    STATUS      current
    DESCRIPTION
        "The value of tmnxMobServS11TableLastChanged indicates the sysUpTime at
         the time of the last modification to tmnxMobServS11Table by
         adding, deleting an entry or change to a writable object in the table.

         If no changes were made to the table since the last re-initialization
         of the local network management subsystem, then this object contains
         a zero value."
    ::= { tmnxMobServingGlobalObjs 6 }

tmnxMobServS11Table  OBJECT-TYPE
    SYNTAX      SEQUENCE OF TmnxMobServS11Entry
    MAX-ACCESS  not-accessible
    STATUS      current
    DESCRIPTION
        "The tmnxMobServS11Table provides an extension of the tmnxMobServTable
         for S11 reference point configuration."
    ::= { tmnxMobServingConfObjs 6 }

tmnxMobServS11Entry  OBJECT-TYPE
    SYNTAX      TmnxMobServS11Entry
    MAX-ACCESS  not-accessible
    STATUS      current
    DESCRIPTION
        "Each row entry represents additional columns for S11 reference point
         configuration for a Serving Gateway (SGW)."
    AUGMENTS { tmnxMobServEntry }
    ::= { tmnxMobServS11Table 1 }

TmnxMobServS11Entry ::= SEQUENCE {
        tmnxMobServS11LastChanged            TimeStamp,
        tmnxMobServS11PeerList               TmnxMobProfNameOrEmpty,
        tmnxMobServS11GtpcIfVRtrId           TmnxVRtrID,
        tmnxMobServS11GtpcIfIndex            InterfaceIndexOrZero,
        tmnxMobServS11GtpcProfile            TmnxMobProfNameOrEmpty,
        tmnxMobServS11GtpcDdnDumpTimer       Unsigned32
    }

tmnxMobServS11LastChanged  OBJECT-TYPE
    SYNTAX      TimeStamp
    MAX-ACCESS  read-only
    STATUS      current
    DESCRIPTION
        "The value of tmnxMobServS11LastChanged indicates the timestamp of
         the last change to this row in tmnxMobServS11Table."
    ::= { tmnxMobServS11Entry 1 }

tmnxMobServS11PeerList  OBJECT-TYPE
    SYNTAX      TmnxMobProfNameOrEmpty
    MAX-ACCESS  read-write
    STATUS      current
    DESCRIPTION
        "The value of tmnxMobServS11PeerList specifies the peer list name.

         If a corresponding peer does not exist in
         TIMETRA-MOBILE-PROFILE-MIB::tmnxMobProfPeerListTable,
         an 'inconsistentValue' error will be returned."
    DEFVAL { ''H }
    ::= { tmnxMobServS11Entry 2 }

tmnxMobServS11GtpcIfVRtrId  OBJECT-TYPE
    SYNTAX      TmnxVRtrID
    MAX-ACCESS  read-write
    STATUS      current
    DESCRIPTION
        "The value of tmnxMobServS11GtpcIfVRtrId specifies the virtual
         router to which the interface specified by tmnxMobServS11GtpcIfIndex
         belongs."
    DEFVAL { 1 }
    ::= { tmnxMobServS11Entry 3 }

tmnxMobServS11GtpcIfIndex  OBJECT-TYPE
    SYNTAX      InterfaceIndexOrZero
    MAX-ACCESS  read-write
    STATUS      current
    DESCRIPTION
        "The value of tmnxMobServS11GtpcIfIndex specifies the interface
         index of the local interface used for the General Packet Radio
         Services Tunneling Protocol for Control Plane (GTP-C) signaling.
         When the value of this object is set to 0, no interface has
         been assigned."
    DEFVAL { 0 }
    ::= { tmnxMobServS11Entry 4 }

tmnxMobServS11GtpcProfile  OBJECT-TYPE
    SYNTAX      TmnxMobProfNameOrEmpty
    MAX-ACCESS  read-write
    STATUS      current
    DESCRIPTION
        "The value of tmnxMobServS11GtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobServS11Entry 5 }

tmnxMobServS11GtpcDdnDumpTimer  OBJECT-TYPE
    SYNTAX      Unsigned32 (0 | 10..3600)
    UNITS       "seconds"
    MAX-ACCESS  read-write
    STATUS      current
    DESCRIPTION
        "The value of tmnxMobServS11GtpcDdnDumpTimer specifies the Downlink Data
         Notification (DDN) dumping timer. If the SGW receives an 'Unable to
         page UE' code in a DDN Ack, the SGW will stop sending DDNs for that
         particular UE until the dampening timer expires. The SGW will also
         discard DL packets during this interval.

         If the timer is set to 0 seconds, the SGW will not perform dampening."
    DEFVAL {0}
    ::= { tmnxMobServS11Entry 6 }

--
--  S1u table
--

tmnxMobServS1uTableLastChanged  OBJECT-TYPE
    SYNTAX      TimeStamp
    MAX-ACCESS  read-only
    STATUS      current
    DESCRIPTION
        "The value of tmnxMobServS1uTableLastChanged indicates the sysUpTime at
         the time of the last modification to tmnxMobServS1uTable by
         adding, deleting an entry or change to a writable object in the table.

         If no changes were made to the table since the last re-initialization
         of the local network management subsystem, then this object contains
         a zero value."
    ::= { tmnxMobServingGlobalObjs 7 }

tmnxMobServS1uTable  OBJECT-TYPE
    SYNTAX      SEQUENCE OF TmnxMobServS1uEntry
    MAX-ACCESS  not-accessible
    STATUS      current
    DESCRIPTION
        "The tmnxMobServS1uTable provides an extension of the tmnxMobServTable
         for S1-u reference point configuration."
    ::= { tmnxMobServingConfObjs 7 }

tmnxMobServS1uEntry  OBJECT-TYPE
    SYNTAX      TmnxMobServS1uEntry
    MAX-ACCESS  not-accessible
    STATUS      current
    DESCRIPTION
        "Each row entry represents additional columns for S1-u reference point
         configuration for a Serving Gateway (SGW)."
    AUGMENTS { tmnxMobServEntry }
    ::= { tmnxMobServS1uTable 1 }

TmnxMobServS1uEntry ::= SEQUENCE {
        tmnxMobServS1uLastChanged            TimeStamp,
        tmnxMobServS1uPeerList               TmnxMobProfNameOrEmpty,
        tmnxMobServS1uGtpuIfVRtrId           TmnxVRtrID,
        tmnxMobServS1uGtpuIfIndex            InterfaceIndexOrZero,
        tmnxMobServS1uGtpuProfile            TmnxMobProfNameOrEmpty,
        tmnxMobServS1uGtpuUdpCheckSum        TmnxEnabledDisabled,
        tmnxMobServS1uGtpuSeqNumber          TmnxEnabledDisabled,
        tmnxMobServS1uDualStackPref          INTEGER
    }

tmnxMobServS1uLastChanged  OBJECT-TYPE
    SYNTAX      TimeStamp
    MAX-ACCESS  read-only
    STATUS      current
    DESCRIPTION
        "The value of tmnxMobServS1uLastChanged indicates the timestamp of
         the last change to this row in tmnxMobServS1uTable."
    ::= { tmnxMobServS1uEntry 1 }

tmnxMobServS1uPeerList  OBJECT-TYPE
    SYNTAX      TmnxMobProfNameOrEmpty
    MAX-ACCESS  read-write
    STATUS      current
    DESCRIPTION
        "The value of tmnxMobServS1uPeerList specifies the peer list name.

         If a corresponding peer does not exist in
         TIMETRA-MOBILE-PROFILE-MIB::tmnxMobProfPeerListTable,
         an 'inconsistentValue' error will be returned."
    DEFVAL { ''H }
    ::= { tmnxMobServS1uEntry 2 }

tmnxMobServS1uGtpuIfVRtrId  OBJECT-TYPE
    SYNTAX      TmnxVRtrID
    MAX-ACCESS  read-write
    STATUS      current
    DESCRIPTION
        "The value of tmnxMobServS1uGtpuIfVRtrId specifies the virtual
         router to which the interface specified by tmnxMobServS1uGtpuIfIndex
         belongs."
    DEFVAL { 1 }
    ::= { tmnxMobServS1uEntry 3 }

tmnxMobServS1uGtpuIfIndex  OBJECT-TYPE
    SYNTAX      InterfaceIndexOrZero
    MAX-ACCESS  read-write
    STATUS      current
    DESCRIPTION
        "The value of tmnxMobServS1uGtpuIfIndex specifies the interface
         index of the local interface used for the General Packet Radio
         Services Tunneling Protocol for User Plane (GTP-U) signaling.
         When the value of this object is set to 0, no interface has
         been assigned."
    DEFVAL { 0 }
    ::= { tmnxMobServS1uEntry 4 }

tmnxMobServS1uGtpuProfile  OBJECT-TYPE
    SYNTAX      TmnxMobProfNameOrEmpty
    MAX-ACCESS  read-write
    STATUS      current
    DESCRIPTION
        "The value of tmnxMobServS1uGtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobServS1uEntry 5 }

tmnxMobServS1uGtpuUdpCheckSum  OBJECT-TYPE
    SYNTAX      TmnxEnabledDisabled
    MAX-ACCESS  read-write
    STATUS      current
    DESCRIPTION
        "The value of tmnxMobServS1uGtpuUdpCheckSum specifies whether
         or not to validate the UDP checksum of GPRS Tunneling
         Protocol-User plane (GTP-U) packets.

         If the value of this object is set to 'enabled', the UDP
         checksum of the received GTP-U packets is verified and the
         packets which fail checksum verification are rejected.
         If the value of this object is set to 'disabled',
         the UDP checksum of the received GTP-U packets is not
         verified."
    DEFVAL { disabled }
    ::= { tmnxMobServS1uEntry 6 }

tmnxMobServS1uGtpuSeqNumber  OBJECT-TYPE
    SYNTAX      TmnxEnabledDisabled
    MAX-ACCESS  read-write
    STATUS      current
    DESCRIPTION
        "The value of tmnxMobServS1uGtpuSeqNumber specifies whether
         or not to ignore the sequence number in the GPRS Tunneling
         Protocol-User plane (GTP-U) header.

         If the value of this object is set to 'enabled',
         GTP-U packets are reassembled based on the sequence number and
         complete packet is forwarded onto S5 or S8 interface. If the value
         of this object is set to 'disabled', the sequence number is
         ignored and complete packet is forwarded onto S5 or S8 interface."
    DEFVAL { disabled }
    ::= { tmnxMobServS1uEntry 7 }

tmnxMobServS1uDualStackPref  OBJECT-TYPE
    SYNTAX       INTEGER {
                          ipv4      (1),
                          ipv6      (2)
                         }
    MAX-ACCESS  read-write
    STATUS      current
    DESCRIPTION
        "The value of tmnxMobServS1uDualStackPref specifies the preference in a
         dual stack when both IPv4 and IPv6 addresses are configured for the
         S1u interface."
    DEFVAL { ipv6 }
    ::= { tmnxMobServS1uEntry 8 }

--
--  S12 table
--

tmnxMobServS12TableLastChanged  OBJECT-TYPE
    SYNTAX      TimeStamp
    MAX-ACCESS  read-only
    STATUS      current
    DESCRIPTION
        "The value of tmnxMobServS12TableLastChanged indicates the sysUpTime at
         the time of the last modification to tmnxMobServS12Table by
         adding, deleting an entry or change to a writable object in the table.

         If no changes were made to the table since the last re-initialization
         of the local network management subsystem, then this object contains
         a zero value."
    ::= { tmnxMobServingGlobalObjs 8 }

tmnxMobServS12Table  OBJECT-TYPE
    SYNTAX      SEQUENCE OF TmnxMobServS12Entry
    MAX-ACCESS  not-accessible
    STATUS      current
    DESCRIPTION
        "The tmnxMobServS12Table provides an extension of the tmnxMobServTable
         for S12 reference point configuration."
    ::= { tmnxMobServingConfObjs 8 }

tmnxMobServS12Entry  OBJECT-TYPE
    SYNTAX      TmnxMobServS12Entry
    MAX-ACCESS  not-accessible
    STATUS      current
    DESCRIPTION
        "Each row entry represents additional columns for S12 reference point
         configuration for a Serving Gateway (SGW)."
    AUGMENTS { tmnxMobServEntry }
    ::= { tmnxMobServS12Table 1 }

TmnxMobServS12Entry ::= SEQUENCE {
        tmnxMobServS12LastChanged            TimeStamp,
        tmnxMobServS12PeerList               TmnxMobProfNameOrEmpty,
        tmnxMobServS12GtpuIfVRtrId           TmnxVRtrID,
        tmnxMobServS12GtpuIfIndex            InterfaceIndexOrZero,
        tmnxMobServS12GtpuProfile            TmnxMobProfNameOrEmpty,
        tmnxMobServS12GtpuUdpCheckSum        TmnxEnabledDisabled,
        tmnxMobServS12GtpuSeqNumber          TmnxEnabledDisabled
    }

tmnxMobServS12LastChanged  OBJECT-TYPE
    SYNTAX      TimeStamp
    MAX-ACCESS  read-only
    STATUS      current
    DESCRIPTION
        "The value of tmnxMobServS12LastChanged indicates the timestamp of
         the last change to this row in tmnxMobServS12Table."
    ::= { tmnxMobServS12Entry 1 }

tmnxMobServS12PeerList  OBJECT-TYPE
    SYNTAX      TmnxMobProfNameOrEmpty
    MAX-ACCESS  read-write
    STATUS      current
    DESCRIPTION
        "The value of tmnxMobServS12PeerList specifies the peer list name.

         If a corresponding peer does not exist in
         TIMETRA-MOBILE-PROFILE-MIB::tmnxMobProfPeerListTable,
         an 'inconsistentValue' error will be returned."
    DEFVAL { ''H }
    ::= { tmnxMobServS12Entry 2 }

tmnxMobServS12GtpuIfVRtrId  OBJECT-TYPE
    SYNTAX      TmnxVRtrID
    MAX-ACCESS  read-write
    STATUS      current
    DESCRIPTION
        "The value of tmnxMobServS12GtpuIfVRtrId specifies the virtual
         router to which the interface specified by tmnxMobServS12GtpuIfIndex
         belongs."
    DEFVAL { 1 }
    ::= { tmnxMobServS12Entry 3 }

tmnxMobServS12GtpuIfIndex  OBJECT-TYPE
    SYNTAX      InterfaceIndexOrZero
    MAX-ACCESS  read-write
    STATUS      current
    DESCRIPTION
        "The value of tmnxMobServS12GtpuIfIndex specifies the interface
         index of the local interface used for the General Packet Radio
         Services Tunneling Protocol for User Plane (GTP-U) signaling.
         When the value of this object is set to 0, no interface has
         been assigned."
    DEFVAL { 0 }
    ::= { tmnxMobServS12Entry 4 }

tmnxMobServS12GtpuProfile  OBJECT-TYPE
    SYNTAX      TmnxMobProfNameOrEmpty
    MAX-ACCESS  read-write
    STATUS      current
    DESCRIPTION
        "The value of tmnxMobServS12GtpuProfile specifies the GPRS Tunneling
         Protocol-User plane (GTP-U) profile name. The GTP-U profile provides
         GTP-U signaling related configuration.

         If a corresponding GTP profile does not exist in
         TIMETRA-MOBILE-PROFILE-MIB::tmnxMobProfGtpTable,
         an 'inconsistentValue' error will be returned."
    DEFVAL { ''H }
    ::= { tmnxMobServS12Entry 5 }

tmnxMobServS12GtpuUdpCheckSum  OBJECT-TYPE
    SYNTAX      TmnxEnabledDisabled
    MAX-ACCESS  read-write
    STATUS      current
    DESCRIPTION
        "The value of tmnxMobServS12GtpuUdpCheckSum specifies whether
         or not to validate the UDP checksum of GPRS Tunneling
         Protocol-User plane (GTP-U) packets.

         If the value of this object is set to 'enabled', the UDP
         checksum of the received GTP-U packets is verified and the
         packets which fail checksum verification are rejected.
         If the value of this object is set to 'disabled',
         the UDP checksum of the received GTP-U packets is not
         verified."
    DEFVAL { disabled }
    ::= { tmnxMobServS12Entry 6 }

tmnxMobServS12GtpuSeqNumber  OBJECT-TYPE
    SYNTAX      TmnxEnabledDisabled
    MAX-ACCESS  read-write
    STATUS      current
    DESCRIPTION
        "The value of tmnxMobServS12GtpuSeqNumber specifies whether
         or not to ignore the sequence number in the GPRS Tunneling
         Protocol-User plane (GTP-U) header.

         If the value of this object is set to 'enabled',
         GTP-U packets are reassembled based on the sequence number and
         complete packet is forwarded onto S5 or S8 interface. If the value
         of this object is set to 'disabled', the sequence number is
         ignored and complete packet is forwarded onto S5 or S8 interface."
    DEFVAL { disabled }
    ::= { tmnxMobServS12Entry 7 }

--
--  Rf table
--

tmnxMobServRfTableLastChanged  OBJECT-TYPE
    SYNTAX      TimeStamp
    MAX-ACCESS  read-only
    STATUS      current
    DESCRIPTION
        "The value of tmnxMobServRfTableLastChanged indicates the sysUpTime at
         the time of the last modification to tmnxMobServRfTable by
         adding, deleting an entry or change to a writable object in the table.

         If no changes were made to the table since the last re-initialization
         of the local network management subsystem, then this object contains
         a zero value."
    ::= { tmnxMobServingGlobalObjs 9 }

tmnxMobServRfTable  OBJECT-TYPE
    SYNTAX      SEQUENCE OF TmnxMobServRfEntry
    MAX-ACCESS  not-accessible
    STATUS      current
    DESCRIPTION
        "The tmnxMobServRfTable provides an extension of the tmnxMobServTable
         for Rating Function (RF) configuration."
    ::= { tmnxMobServingConfObjs 9 }

tmnxMobServRfEntry  OBJECT-TYPE
    SYNTAX      TmnxMobServRfEntry
    MAX-ACCESS  not-accessible
    STATUS      current
    DESCRIPTION
        "Each row entry represents additional columns for Rating Function (RF)
         configuration for a Serving Gateway (SGW)."
    AUGMENTS { tmnxMobServEntry }
    ::= { tmnxMobServRfTable 1 }

TmnxMobServRfEntry ::= SEQUENCE {
        tmnxMobServRfLastChanged             TimeStamp,
        tmnxMobServRfVRtrId                  TmnxVRtrID,
        tmnxMobServRfIfIndex                 InterfaceIndexOrZero,
        tmnxMobServRfPriDiaPeer              TmnxMobProfNameOrEmpty,
        tmnxMobServRfSecDiaPeer              TmnxMobProfNameOrEmpty,
        tmnxMobServRfAcctIntmInterval        Unsigned32,
        tmnxMobServRfApplTxTimer             Unsigned32,
        tmnxMobServRfRetryCount              TmnxMobDiaRetryCount,
        tmnxMobServRfChargingGroupID         TmnxEnabledDisabled,
        tmnxMobServRfOperatorString          TNamedItemOrEmpty,
        tmnxMobServRfAcctLevel               TmnxMobRfAcctLevel,
        tmnxMobServRfNodeId                  DisplayString,
        tmnxMobServRfOcFilePrivateInfo       TNamedItemOrEmpty,
        tmnxMobServRfOcFileExtension         DisplayString,
        tmnxMobServRfOcFileClosureSize       Unsigned32,
        tmnxMobServRfOcFileClsLifeTime       Unsigned32,
        tmnxMobServRfOcFileClsMaxAcrs        Unsigned32,
        tmnxMobServRfOcFileObsoleteTime      Unsigned32,
        tmnxMobServRfOcPrimaryCf             INTEGER,
        tmnxMobServRfOcCf1State              TruthValue,
        tmnxMobServRfOcCf1Limit              Unsigned32,
        tmnxMobServRfOcCf2State              TruthValue,
        tmnxMobServRfOcCf2Limit              Unsigned32,
        tmnxMobServRfSuppVendorAvps          TmnxEnabledDisabled
    }

tmnxMobServRfLastChanged  OBJECT-TYPE
    SYNTAX      TimeStamp
    MAX-ACCESS  read-only
    STATUS      current
    DESCRIPTION
        "The value of tmnxMobServRfLastChanged indicates the timestamp of
         the last change to this row in tmnxMobServS11Table."
    ::= { tmnxMobServRfEntry 1 }

tmnxMobServRfVRtrId  OBJECT-TYPE
    SYNTAX      TmnxVRtrID
    MAX-ACCESS  read-write
    STATUS      current
    DESCRIPTION
        "The value of tmnxMobServRfVRtrId specifies the virtual
         router to which the interface specified by tmnxMobServRfVRtrId
         belongs."
    DEFVAL { 1 }
    ::= { tmnxMobServRfEntry 2 }

tmnxMobServRfIfIndex  OBJECT-TYPE
    SYNTAX      InterfaceIndexOrZero
    MAX-ACCESS  read-write
    STATUS      current
    DESCRIPTION
        "The value of tmnxMobServRfIfIndex specifies the interface index of
         the local interface used by diameter applications."
    DEFVAL { 0 }
    ::= { tmnxMobServRfEntry 3 }

tmnxMobServRfPriDiaPeer  OBJECT-TYPE
    SYNTAX      TmnxMobProfNameOrEmpty
    MAX-ACCESS  read-write
    STATUS      current
    DESCRIPTION
        "The value of tmnxMobServRfPriDiaPeer specifies the diameter peer
         profile to be used for the primary Charging Data Function (CDF) at the
         Gateway level.

         If a corresponding diameter peer profile does not exist in
         TIMETRA-MOBILE-PROFILE-MIB::tmnxMobProfDiaPeerTable,
         an 'inconsistentValue' error will be returned."
    DEFVAL { ''H }
    ::= { tmnxMobServRfEntry 4 }

tmnxMobServRfSecDiaPeer  OBJECT-TYPE
    SYNTAX      TmnxMobProfNameOrEmpty
    MAX-ACCESS  read-write
    STATUS      current
    DESCRIPTION
        "The value of tmnxMobServRfSecDiaPeer specifies the diameter peer
         profile to be used for the secondary Charging Data Function (CDF) at
         the Gateway level.

         If a corresponding diameter peer profile does not exist in
         TIMETRA-MOBILE-PROFILE-MIB::tmnxMobProfDiaPeerTable,
         an 'inconsistentValue' error will be returned."
    DEFVAL { ''H }
    ::= { tmnxMobServRfEntry 5 }

tmnxMobServRfAcctIntmInterval  OBJECT-TYPE
    SYNTAX      Unsigned32 (1..86400)
    UNITS       "seconds"
    MAX-ACCESS  read-write
    STATUS      current
    DESCRIPTION
        "The value of tmnxMobServRfAcctIntmInterval specifies the accounting
         interim interval to send interim accounting information to the
         Charging Data Function (CDF) at the Gateway level."
    DEFVAL { 1800 }
    ::= { tmnxMobServRfEntry 6 }

tmnxMobServRfApplTxTimer  OBJECT-TYPE
    SYNTAX      Unsigned32 (1..30)
    UNITS       "seconds"
    MAX-ACCESS  read-write
    STATUS      current
    DESCRIPTION
        "The value of tmnxMobServRfApplTxTimer specifies the application
         transaction timer for Accounting Requests (ACR) and
         Accounting Answers (ACA)."
    DEFVAL { 5 }
    ::= { tmnxMobServRfEntry 7 }

tmnxMobServRfRetryCount  OBJECT-TYPE
    SYNTAX      TmnxMobDiaRetryCount
    UNITS       "seconds"
    MAX-ACCESS  read-write
    STATUS      current
    DESCRIPTION
        "The value of tmnxMobServRfRetryCount specifies the retry count for
         Accounting Requests (ACR) messages. An Accounting Requests (ACR)
         message will be retransmitted for the number of times specified,
         when an Accounting Answers (ACA) is not received from the Charging Data
         Function (CDF) server."
    DEFVAL { 3 }
    ::= { tmnxMobServRfEntry 8 }

tmnxMobServRfChargingGroupID  OBJECT-TYPE
    SYNTAX      TmnxEnabledDisabled
    MAX-ACCESS  read-write
    STATUS      current
    DESCRIPTION
        "The value of tmnxMobServRfChargingGroupID specifies whether the
         inclusion of Charging-Group-ID AVP in Accounting Requests (ACR)
         message is enabled or not."
    DEFVAL { disabled }
    ::= { tmnxMobServRfEntry 9 }

tmnxMobServRfOperatorString  OBJECT-TYPE
    SYNTAX      TNamedItemOrEmpty
    MAX-ACCESS  read-write
    STATUS      current
    DESCRIPTION
        "The value of tmnxMobServRfOperatorString specifies string to be
         included in operator-string AVP (non-standard) of an Accounting
         Requests (ACR) message."
    DEFVAL { ''H }
    ::= { tmnxMobServRfEntry 10 }

tmnxMobServRfAcctLevel  OBJECT-TYPE
    SYNTAX      TmnxMobRfAcctLevel
    MAX-ACCESS  read-write
    STATUS      current
    DESCRIPTION
        "The value of tmnxMobServRfAcctLevel specifies whether PDN-level
         accounting or QCI-level accounting is applicable. When PDN-level
         accounting is specified, diameter charging sessions to the Charging
         Data Function (CDF) are setup on a per Packet Data Network (PDN)
         connection basis. When QCI-level accounting is specified, diameter
         charging sessions to the Charging Data Function (CDF) are setup on a
         per bearer basis."
    DEFVAL { qciLevel }
    ::= { tmnxMobServRfEntry 11 }

tmnxMobServRfNodeId  OBJECT-TYPE
    SYNTAX      DisplayString (SIZE (0..20))
    MAX-ACCESS  read-write
    STATUS      current
    DESCRIPTION
        "The value of tmnxMobServRfNodeId specifies an operator
         configurable identifier for the node which is used over the Rating
         Function (RF) interface."
    DEFVAL { ''H }
    ::= { tmnxMobServRfEntry 12 }

tmnxMobServRfOcFilePrivateInfo  OBJECT-TYPE
    SYNTAX      TNamedItemOrEmpty
    MAX-ACCESS  read-write
    STATUS      current
    DESCRIPTION
        "The value of tmnxMobServRfOcFilePrivateInfo specifies an operator
         configurable file private information field that is used in the file
         name."
    DEFVAL { ''H }
    ::= { tmnxMobServRfEntry 13 }

tmnxMobServRfOcFileExtension  OBJECT-TYPE
    SYNTAX      DisplayString (SIZE (0..8))
    MAX-ACCESS  read-write
    STATUS      current
    DESCRIPTION
        "The value of tmnxMobServRfOcFileExtension specifies an operator
         configurable file extension field that is used in the file name."
    DEFVAL { ''H }
    ::= { tmnxMobServRfEntry 14 }

tmnxMobServRfOcFileClosureSize  OBJECT-TYPE
    SYNTAX      Unsigned32 (1..100)
    UNITS       "megabytes"
    MAX-ACCESS  read-write
    STATUS      current
    DESCRIPTION
        "The value of tmnxMobServRfOcFileClosureSize specifies an operator
         configurable file closure size limit."
    DEFVAL { 50 }
    ::= { tmnxMobServRfEntry 15 }

tmnxMobServRfOcFileClsLifeTime  OBJECT-TYPE
    SYNTAX      Unsigned32 (1..24)
    UNITS       "hours"
    MAX-ACCESS  read-write
    STATUS      current
    DESCRIPTION
        "The value of tmnxMobServRfOcFileClsLifeTime specifies an operator
         configurable file closure lifetime. The file is closed after the
         specified duration."
    DEFVAL { 1 }
    ::= { tmnxMobServRfEntry 16 }

tmnxMobServRfOcFileClsMaxAcrs  OBJECT-TYPE
    SYNTAX      Unsigned32 (100..75000)
    MAX-ACCESS  read-write
    STATUS      current
    DESCRIPTION
        "The value of tmnxMobServRfOcFileClsMaxAcrs specifies an operator
         configurable limit for the number of Accounting Requests (ACR) that
         are stored in a file. The file is closed after the specified limit is
         reached."
    DEFVAL { 50000 }
    ::= { tmnxMobServRfEntry 17 }

tmnxMobServRfOcFileObsoleteTime  OBJECT-TYPE
    SYNTAX      Unsigned32 (1..31)
    UNITS       "days"
    MAX-ACCESS  read-write
    STATUS      current
    DESCRIPTION
        "The value of tmnxMobServRfOcFileObsoleteTime specifies an operator
         configurable file duration, after which the file is deleted."
    DEFVAL { 7 }
    ::= { tmnxMobServRfEntry 18 }

tmnxMobServRfOcPrimaryCf  OBJECT-TYPE
    SYNTAX      INTEGER {
                         cf1    (1),
                         cf2    (2)
                        }
    MAX-ACCESS  read-write
    STATUS      current
    DESCRIPTION
        "The value of tmnxMobServRfOcPrimaryCf specifies which compact flash
         will be used as a primary storage for the Accounting Requests (ACR)
         storage.

         If the user tries to set the 'cf1' and if the 'cf1' is not available
         then 'cf2' will be set as primary storage. If the user tries to set
         the 'cf2' and if 'cf2' is not available then cf1 will be set as
         primary storage."
    DEFVAL { cf1 }
    ::= { tmnxMobServRfEntry 19 }

tmnxMobServRfOcCf1State  OBJECT-TYPE
    SYNTAX      TruthValue
    MAX-ACCESS  read-write
    STATUS      current
    DESCRIPTION
        "The value of tmnxMobServRfOcCf1State specifies whether the first
         compact flash is enabled to be used for the Accounting Requests (ACR)
         storage.

         If the compact flash is not available then it will be disabled."
    DEFVAL { true }
    ::= { tmnxMobServRfEntry 20 }

tmnxMobServRfOcCf1Limit  OBJECT-TYPE
    SYNTAX      Unsigned32
    UNITS       "megabytes"
    MAX-ACCESS  read-write
    STATUS      current
    DESCRIPTION
        "The value of tmnxMobServRfOcCf1Limit specifies the limit
         (in megabytes) for an amount of memory on the first compact flash that
         can be used for the Accounting Requests (ACR) storage. Once the
         threshold has been reached, the system can no longer support accurate
         charging.

         If the compact flash is not available then tmnxMobServRfOcCf1Limit
         will be set to 0.

         If tmnxMobServRfOcCf1State is enabled and the value of
         tmnxMobServRfOcCf1Limit is 0, then maximum available memory on the
         second compact flash can be used for the ACR storage."
    DEFVAL { 0 }
    ::= { tmnxMobServRfEntry 21 }

tmnxMobServRfOcCf2State  OBJECT-TYPE
    SYNTAX      TruthValue
    MAX-ACCESS  read-write
    STATUS      current
    DESCRIPTION
        "The value of tmnxMobServRfOcCf2State specifies whether
         the second compact flash is enabled to be used for the Accounting
         Requests (ACR) storage.

         If the compact flash is not available then it will be disabled."
    DEFVAL { true }
    ::= { tmnxMobServRfEntry 22 }

tmnxMobServRfOcCf2Limit  OBJECT-TYPE
    SYNTAX      Unsigned32
    UNITS       "megabytes"
    MAX-ACCESS  read-write
    STATUS      current
    DESCRIPTION
        "The value of tmnxMobServRfOcCf2Limit specifies the limit
         (in megabytes) for an amount of memory on the second compact flash that
         can be used for the Accounting Requests (ACR) storage. Once the
         threshold has been reached, the system can no longer support accurate
         charging.

         If the compact flash is not available then tmnxMobServRfOcCf2Limit
         will be set to 0.

         If tmnxMobServRfOcCf2State is enabled and the value of
         tmnxMobServRfOcCf2Limit is 0, then maximum available memory on the
         second compact flash can be used for the ACR storage."
    DEFVAL { 0 }
    ::= { tmnxMobServRfEntry 23 }

tmnxMobServRfSuppVendorAvps  OBJECT-TYPE
    SYNTAX      TmnxEnabledDisabled
    MAX-ACCESS  read-write
    STATUS      current
    DESCRIPTION
        "The value of tmnxMobServRfSuppVendorAvps specifies whether the
         supported vendor IDs to be advertised for Capabilities Exchange
         negotiation. When it is disabled 3GPP standard defined Attribute Value
         Pair (AVPs) are supported."
    DEFVAL { disabled }
    ::= { tmnxMobServRfEntry 24 }

--
--  APN table
--

tmnxMobServApnTableLastChanged  OBJECT-TYPE
    SYNTAX      TimeStamp
    MAX-ACCESS  read-only
    STATUS      current
    DESCRIPTION
        "The value of tmnxMobServApnTableLastChanged indicates the sysUpTime at
         the time of the last modification to tmnxMobServApnTable by
         adding, deleting an entry or change to a writable object in the table.

         If no changes were made to the table since the last re-initialization
         of the local network management subsystem, then this object contains
         a zero value."
    ::= { tmnxMobServingGlobalObjs 10 }

tmnxMobServApnTable  OBJECT-TYPE
    SYNTAX      SEQUENCE OF TmnxMobServApnEntry
    MAX-ACCESS  not-accessible
    STATUS      current
    DESCRIPTION
        "The tmnxMobServApnTable has an entry for each Access Point Name (APN).
         An APN identifies an external network that is accessible from a
         terminal."
    ::= { tmnxMobServingConfObjs 10 }

tmnxMobServApnEntry  OBJECT-TYPE
    SYNTAX      TmnxMobServApnEntry
    MAX-ACCESS  not-accessible
    STATUS      current
    DESCRIPTION
        "Each row entry represents an Access Point Name (APN). Entries can be
         created and deleted by the user."
    INDEX { tmnxMobGwId,
            tmnxMobServApnName
          }
    ::= { tmnxMobServApnTable 1 }

TmnxMobServApnEntry ::= SEQUENCE {
        tmnxMobServApnName                   TmnxMobApn,
        tmnxMobServApnRowStatus              RowStatus,
        tmnxMobServApnLastChanged            TimeStamp,
        tmnxMobServApnDescription            TItemDescription,
        tmnxMobServApnDynamicPcc             TmnxEnabledDisabled,
        tmnxMobServApnUplinkQciPolName       TmnxMobProfNameOrEmpty,
        tmnxMobServApnDownlinkQciPolName     TmnxMobProfNameOrEmpty,
        tmnxMobServApnPolBaseName            TmnxMobProfNameOrEmpty,
        tmnxMobServApnChrgProfileHome        TmnxMobChargingProfileOrInherit,
        tmnxMobServApnChrgProfVisiting      TmnxMobChargingProfileOrInherit,
        tmnxMobServApnChrgProfileRoaming     TmnxMobChargingProfileOrInherit,
        tmnxMobServApnChrgCcIgnoreAny        TmnxEnabledDisabledOrInherit,
        tmnxMobServApnChrgCcIgnoreHome       TmnxEnabledDisabledOrInherit,
        tmnxMobServApnChrgCcIgnoreVisit      TmnxEnabledDisabledOrInherit,
        tmnxMobServApnChrgCcIgnorRoaming     TmnxEnabledDisabledOrInherit,
        tmnxMobServApnChrgCcReject           TmnxEnabledDisabledOrInherit
    }

tmnxMobServApnName  OBJECT-TYPE
    SYNTAX      TmnxMobApn
    MAX-ACCESS  not-accessible
    STATUS      current
    DESCRIPTION
        "The value of tmnxMobServApnName specifies the Access Point Name (APN)."
    ::= { tmnxMobServApnEntry 1 }

tmnxMobServApnRowStatus  OBJECT-TYPE
    SYNTAX      RowStatus
    MAX-ACCESS  read-create
    STATUS      current
    DESCRIPTION
        "The value of tmnxMobServApnRowStatus specifies the row status of
         this entry. It is used for creation and deletion of this Access Point
         Name (APN)."
    ::= { tmnxMobServApnEntry 2 }

tmnxMobServApnLastChanged  OBJECT-TYPE
    SYNTAX      TimeStamp
    MAX-ACCESS  read-only
    STATUS      current
    DESCRIPTION
        "The value of tmnxMobServApnLastChanged indicates the timestamp of
         the last change to this row in tmnxMobServApnTable."
    ::= { tmnxMobServApnEntry 3 }

tmnxMobServApnDescription  OBJECT-TYPE
    SYNTAX      TItemDescription
    MAX-ACCESS  read-create
    STATUS      current
    DESCRIPTION
        "The value of tmnxMobServApnDescription specifies the description
         string for this Access Point Name (APN). It can consist of any
         printable, seven-bit ASCII characters up to 80 characters in length."
    DEFVAL { ''H }
    ::= { tmnxMobServApnEntry 4 }

tmnxMobServApnDynamicPcc  OBJECT-TYPE
    SYNTAX      TmnxEnabledDisabled
    MAX-ACCESS  read-create
    STATUS      current
    DESCRIPTION
        "The value of tmnxMobServApnDynamicPcc specifies whether to enable
         the interaction with Policy and Charging Rules Function (PCRF)
         for bearer creation. When dynamic-pcc is enabled,
         Policy and Charging Control (PCC) rules are sent from
         PCRF for dedicated bearer creation."
    DEFVAL { enabled }
    ::= { tmnxMobServApnEntry 5 }

tmnxMobServApnUplinkQciPolName  OBJECT-TYPE
    SYNTAX      TmnxMobProfNameOrEmpty
    MAX-ACCESS  read-create
    STATUS      current
    DESCRIPTION
        "The value of tmnxMobServApnUplinkQciPolName specifies the QoS Class
         Identifier (QCI) policy profile name for uplink direction.

         If a corresponding QCI policy profile does not exist in
         TIMETRA-MOBILE-PROFILE-MIB::tmnxMobProfQciPolTable,
         an 'inconsistentValue' error will be returned."
    DEFVAL { ''H }
    ::= { tmnxMobServApnEntry 6 }

tmnxMobServApnDownlinkQciPolName  OBJECT-TYPE
    SYNTAX      TmnxMobProfNameOrEmpty
    MAX-ACCESS  read-create
    STATUS      current
    DESCRIPTION
        "The value of tmnxMobServApnDownlinkQciPolName specifies the QoS Class
         Identifier (QCI) policy profile name for downlink direction.

         If a corresponding QCI policy profile does not exist in
         TIMETRA-MOBILE-PROFILE-MIB::tmnxMobProfQciPolTable,
         an 'inconsistentValue' error will be returned."
    DEFVAL { ''H }
    ::= { tmnxMobServApnEntry 7 }

tmnxMobServApnPolBaseName  OBJECT-TYPE
    SYNTAX      TmnxMobProfNameOrEmpty
    MAX-ACCESS  read-create
    STATUS      current
    DESCRIPTION
        "The value of tmnxMobServApnPolBaseName specifies the policy base
         profile name.

         If a corresponding policy base profile does not exist in
         TIMETRA-MOBILE-PROFILE-MIB::tmnxMobProfPolBaseTable,
         an 'inconsistentValue' error will be returned."
    DEFVAL { ''H }
    ::= { tmnxMobServApnEntry 8 }

tmnxMobServApnChrgProfileHome  OBJECT-TYPE
    SYNTAX      TmnxMobChargingProfileOrInherit
    MAX-ACCESS  read-create
    STATUS      current
    DESCRIPTION
        "The value of tmnxMobServApnChrgProfileHome specifies the charging
         trigger rules applied for generating Charging Data Records (CDR) for
         home subscribers.

         If a corresponding charging profile does not exist in
         TIMETRA-MOBILE-PROFILE-MIB::tmnxMobProfSgwChargingTable,
         an 'inconsistentValue' error will be returned.

         A value of '-1' specifies that charging profile information is
         inherited from the value of tmnxMobServChargingProfHome which specifies
         the charging trigger rules applied for home subscribers at the gateway
         level."
    DEFVAL { -1 }
    ::= { tmnxMobServApnEntry 9 }

tmnxMobServApnChrgProfVisiting  OBJECT-TYPE
    SYNTAX      TmnxMobChargingProfileOrInherit
    MAX-ACCESS  read-create
    STATUS      current
    DESCRIPTION
        "The value of tmnxMobServApnChrgProfVisiting specifies the visiting
         charging trigger rules applied for generating Charging Data Records
         (CDR) for visiting subscribers.

         If a corresponding charging profile does not exist in
         TIMETRA-MOBILE-PROFILE-MIB::tmnxMobProfSgwChargingTable,
         an 'inconsistentValue' error will be returned.

         A value of '-1' specifies that charging profile information is
         inherited from the value of tmnxMobServChargingProfVisiting which
         specifies the charging trigger rules applied for visiting subscribers
         at the gateway level."
    DEFVAL { -1 }
    ::= { tmnxMobServApnEntry 10 }

tmnxMobServApnChrgProfileRoaming  OBJECT-TYPE
    SYNTAX      TmnxMobChargingProfileOrInherit
    MAX-ACCESS  read-create
    STATUS      current
    DESCRIPTION
        "The value of tmnxMobServApnChrgProfileRoaming specifies the charging
         trigger rules applied for generating Charging Data Records (CDR) for
         roaming subscribers.

         If a corresponding charging profile does not exist in
         TIMETRA-MOBILE-PROFILE-MIB::tmnxMobProfSgwChargingTable,
         an 'inconsistentValue' error will be returned.

         A value of '-1' specifies that charging profile information is
         inherited from the value of tmnxMobServChargingProfRoaming which
         specifies the charging trigger rules applied for roaming subscribers
         at the gateway level."
    DEFVAL { -1 }
    ::= { tmnxMobServApnEntry 11 }

tmnxMobServApnChrgCcIgnoreAny  OBJECT-TYPE
    SYNTAX      TmnxEnabledDisabledOrInherit
    MAX-ACCESS  read-create
    STATUS      current
    DESCRIPTION
        "The value of tmnxMobServApnChrgCcIgnoreAny specifies to ignore
         HSS or MME supplied charging characteristics for any subscriber.
         Corresponding default profile is selected when the received charging
         characteristics is ignored.

         When the value of tmnxMobServApnChrgCcIgnoreAny is 'inherit', the value
         is inherited from the value of tmnxMobServChrgCcIgnoreAny which
         specifies to ignore HSS or MME supplied charging characteristics for
         any subscriber at the gateway level."
    DEFVAL { inherit }
    ::= { tmnxMobServApnEntry 12 }

tmnxMobServApnChrgCcIgnoreHome  OBJECT-TYPE
    SYNTAX      TmnxEnabledDisabledOrInherit
    MAX-ACCESS  read-create
    STATUS      current
    DESCRIPTION
        "The value of tmnxMobServApnChrgCcIgnoreHome specifies to ignore
         HSS or MME supplied charging characteristics for home scenarios.
         Corresponding default profile is selected when the received charging
         characteristics is ignored.

         When the value of tmnxMobServApnChrgCcIgnoreHome is 'inherit', the value
         is inherited from the value of tmnxMobServChrgCcIgnoreHome which
         specifies to ignore HSS or MME supplied charging characteristics for
         home scenarios at the gateway level."
    DEFVAL { inherit }
    ::= { tmnxMobServApnEntry 13 }

tmnxMobServApnChrgCcIgnoreVisit  OBJECT-TYPE
    SYNTAX      TmnxEnabledDisabledOrInherit
    MAX-ACCESS  read-create
    STATUS      current
    DESCRIPTION
        "The value of tmnxMobServApnChrgCcIgnoreVisit specifies to ignore
         HSS or MME supplied charging characteristics for visiting scenarios.
         Corresponding default profile is selected when the received charging
         characteristics is ignored.

         When the value of tmnxMobServApnChrgCcIgnoreVisit is 'inherit', the
         value is inherited from the value of tmnxMobServChrgCcIgnoreVisiting
         which specifies to ignore HSS or MME supplied charging characteristics
         for visiting scenarios at the gateway level."
    DEFVAL { inherit }
    ::= { tmnxMobServApnEntry 14 }

tmnxMobServApnChrgCcIgnorRoaming  OBJECT-TYPE
    SYNTAX      TmnxEnabledDisabledOrInherit
    MAX-ACCESS  read-create
    STATUS      current
    DESCRIPTION
        "The value of tmnxMobServApnChrgCcIgnorRoaming specifies to ignore
         HSS or MME supplied charging characteristics for roaming scenarios.
         Corresponding default profile is selected when the received charging
         characteristics is ignored.

         When the value of tmnxMobServApnChrgCcIgnorRoaming is 'inherit', the
         value is inherited from the value of tmnxMobServChrgCcIgnoreRoaming
         which specifies to ignore HSS or MME supplied charging characteristics
         for roaming scenarios at the gateway level."
    DEFVAL { inherit }
    ::= { tmnxMobServApnEntry 15 }

tmnxMobServApnChrgCcReject  OBJECT-TYPE
    SYNTAX      TmnxEnabledDisabledOrInherit
    MAX-ACCESS  read-create
    STATUS      current
    DESCRIPTION
        "The value of tmnxMobServApnChrgCcReject specifies to reject HSS or MME
         supplied charging characteristics for a subscriber.
         Corresponding default charging profile is selected when the value of
         this object is set to 'disable'.

         The value of tmnxMobServApnChrgCcReject is applicable only when the HSS
         or MME supplied charging characteristics are not ignored.

         When the value of tmnxMobServApnChrgCcReject is 'inherit', the
         value is inherited from the value of tmnxMobServChrgCcReject which
         specifies to reject HSS or MME supplied charging characteristics for
         a subscriber at the gateway level."
    DEFVAL { inherit }
    ::= { tmnxMobServApnEntry 16 }

--
--  Serving KCI/KPI Accounting Policy Table
--

tmnxMobServApTableLastChanged     OBJECT-TYPE
    SYNTAX      TimeStamp
    MAX-ACCESS  read-only
    STATUS      current
    DESCRIPTION
        "The value of tmnxMobServApTableLastChanged indicates the sysUpTime at
         the time of the last modification to tmnxMobServApTable by adding,
         deleting an entry or change to a writable object in the table.

         If no changes were made to the table since the last re-initialization
         of the local network management subsystem, then this object contains
         a zero value."
    ::= { tmnxMobServingGlobalObjs 13 }

tmnxMobServApTable  OBJECT-TYPE
    SYNTAX      SEQUENCE OF TmnxMobServApEntry
    MAX-ACCESS  not-accessible
    STATUS      current
    DESCRIPTION
        "The tmnxMobServApTable has an entry for each Accounting Policy
         associated with the Serving Gateway (SGW). The policy can be either
         Key Capacity Indicator (KCI) or Key Performance Indicator (KPI)."
    ::= { tmnxMobServingConfObjs 11 }

tmnxMobServApEntry  OBJECT-TYPE
    SYNTAX      TmnxMobServApEntry
    MAX-ACCESS  not-accessible
    STATUS      current
    DESCRIPTION
        "Each row entry represents a Accounting Policy associated with the
         Serving Gateway (SGW). Entries can be created and deleted by the
         user."
    INDEX { tmnxMobGwId, tmnxMobServApPolicyId }
    ::= { tmnxMobServApTable 1 }

TmnxMobServApEntry ::= SEQUENCE {
        tmnxMobServApPolicyId           Unsigned32,
        tmnxMobServApRowStatus          RowStatus,
        tmnxMobServApLastChanged        TimeStamp,
        tmnxMobServApCollectAcctStats   TruthValue
    }

tmnxMobServApPolicyId  OBJECT-TYPE
   SYNTAX      Unsigned32 (1..99)
   MAX-ACCESS  not-accessible
   STATUS      current
   DESCRIPTION
       "The value of tmnxMobServApPolicyId uniquely identifies an Accounting
        Policy to be used for creating accounting records on this Serving
        Gateway (SGW).

        If a corresponding Accounting Policy does not exist in
        TIMETRA-LOG-MIB::tmnxLogApTable,
        an 'inconsistentValue' error will be returned."
   ::= { tmnxMobServApEntry 1 }

tmnxMobServApRowStatus  OBJECT-TYPE
    SYNTAX      RowStatus
    MAX-ACCESS  read-create
    STATUS      current
    DESCRIPTION
        "The value of tmnxMobServApRowStatus specifies the row status of
         this entry. It is used for creation and deletion of this Accounting
         Policy for the Serving Gateway (SGW)."
    ::= { tmnxMobServApEntry 2 }

tmnxMobServApLastChanged  OBJECT-TYPE
    SYNTAX      TimeStamp
    MAX-ACCESS  read-only
    STATUS      current
    DESCRIPTION
        "The value of tmnxMobServApLastChanged indicates
         the timestamp of the last change to this row in tmnxMobServApTable."
    ::= { tmnxMobServApEntry 3 }

tmnxMobServApCollectAcctStats OBJECT-TYPE
    SYNTAX          TruthValue
    MAX-ACCESS      read-create
    STATUS          current
    DESCRIPTION
        "The value of tmnxMobServApCollectAcctStats specifies whether the agent
         collects accounting statistics for this Accounting Policy."
    DEFVAL { false }
    ::= { tmnxMobServApEntry 4 }

--
--  Ga table
--

tmnxMobServGaTableLastChanged  OBJECT-TYPE
    SYNTAX      TimeStamp
    MAX-ACCESS  read-only
    STATUS      current
    DESCRIPTION
        "The value of tmnxMobServGaTableLastChanged indicates the sysUpTime at
         the time of the last modification to tmnxMobServGaTable by adding,
         deleting an entry or change to a writable object in the table.

         If no changes were made to the table since the last re-initialization
         of the local network management subsystem, then this object contains
         a zero value."
    ::= { tmnxMobServingGlobalObjs 15 }

tmnxMobServGaTable  OBJECT-TYPE
    SYNTAX      SEQUENCE OF TmnxMobServGaEntry
    MAX-ACCESS  not-accessible
    STATUS      current
    DESCRIPTION
        "The tmnxMobServGaTable provides an extension of the tmnxMobServTable
         for Ga reference point configuration."
    ::= { tmnxMobServingConfObjs 14 }

tmnxMobServGaEntry  OBJECT-TYPE
    SYNTAX      TmnxMobServGaEntry
    MAX-ACCESS  not-accessible
    STATUS      current
    DESCRIPTION
        "Each row entry represents additional columns for Ga reference point
         configuration for the Serving Gateway (SGW)."
    AUGMENTS { tmnxMobServEntry }
    ::= { tmnxMobServGaTable 1 }

TmnxMobServGaEntry ::= SEQUENCE {
        tmnxMobServGaLastChanged             TimeStamp,
        tmnxMobServGaIfVRtrId                TmnxVRtrID,
        tmnxMobServGaIfIndex                 InterfaceIndexOrZero,
        tmnxMobServGaGtpcProfile             TmnxMobProfNameOrEmpty,
        tmnxMobServGaGtpPrimeGrpName         TmnxMobProfNameOrEmpty
    }

tmnxMobServGaLastChanged  OBJECT-TYPE
    SYNTAX      TimeStamp
    MAX-ACCESS  read-only
    STATUS      current
    DESCRIPTION
        "The value of tmnxMobServGaLastChanged indicates the timestamp of
         the last change to this row in tmnxMobServGaTable."
    ::= { tmnxMobServGaEntry 1 }

tmnxMobServGaIfVRtrId  OBJECT-TYPE
    SYNTAX      TmnxVRtrID
    MAX-ACCESS  read-write
    STATUS      current
    DESCRIPTION
        "The value of tmnxMobServGaIfVRtrId specifies the virtual
         router to which the interface specified by tmnxMobServGaIfIndex
         belongs."
    DEFVAL { 1 }
    ::= { tmnxMobServGaEntry 2 }

tmnxMobServGaIfIndex  OBJECT-TYPE
    SYNTAX      InterfaceIndexOrZero
    MAX-ACCESS  read-write
    STATUS      current
    DESCRIPTION
        "The value of tmnxMobServGaIfIndex specifies the interface
         index of the local interface used for the Ga reference point.
         When the value of this object is set to 0, no interface has
         been assigned.

         If tmnxMobServGaGtpPrimeGrpName is specified, then the value of
         TIMETRA-MOBILE-PROFILE-MIB::tmnxMobGtpPriGrpIfIndex is used as the
         interface index of the local interface used for the Ga reference
         point."
    DEFVAL { 0 }
    ::= { tmnxMobServGaEntry 3 }

tmnxMobServGaGtpcProfile  OBJECT-TYPE
    SYNTAX      TmnxMobProfNameOrEmpty
    MAX-ACCESS  read-write
    STATUS      current
    DESCRIPTION
        "The value of tmnxMobServGaGtpcProfile specifies the GPRS Tunneling
         Protocol-Control plane (GTP-C) profile name. The GTP-C profile provides
         GTP-C signaling related configuration.

         If a corresponding GTP profile does not exist in
         TIMETRA-MOBILE-PROFILE-MIB::tmnxMobProfGtpTable,
         an 'inconsistentValue' error will be returned."
    DEFVAL { ''H }
    ::= { tmnxMobServGaEntry 4 }

tmnxMobServGaGtpPrimeGrpName  OBJECT-TYPE
    SYNTAX      TmnxMobProfNameOrEmpty
    MAX-ACCESS  read-write
    STATUS      current
    DESCRIPTION
        "The value of tmnxMobServGaGtpPrimeGrpName specifies GPRS Tunneling
         Protocol (GTP) prime group name.

         If a corresponding GPRS Tunneling Protocol (GTP) prime group does not
         exist in TIMETRA-MOBILE-PROFILE-MIB::tmnxMobGtpPriGrpTable,
         an 'inconsistentValue' error will be returned."
    DEFVAL { ''H }
    ::= { tmnxMobServGaEntry 5 }

--
--  Statistics Table
--

tmnxMobServStatTable  OBJECT-TYPE
    SYNTAX      SEQUENCE OF TmnxMobServStatEntry
    MAX-ACCESS  not-accessible
    STATUS      current
    DESCRIPTION
        "The tmnxMobServStatTable has an entry for each each Mobility Service
         Module (MSM) configured in the mobility system group defined
         for a Serving Gateway (SGW)."
    ::= { tmnxMobServingStatObjs 1 }

tmnxMobServStatEntry  OBJECT-TYPE
    SYNTAX      TmnxMobServStatEntry
    MAX-ACCESS  not-accessible
    STATUS      current
    DESCRIPTION
        "Each row entry represents a Mobility Service Module (MSM) and contains
         statistics for this card.

         When the value of tmnxCardSlotNum is equal to '0', then each row entry
         contains aggregated statistics for a given gateway."
    INDEX { tmnxMobGwId,
            tmnxChassisIndex,
            tmnxMobServCardSlotNum
          }
    ::= { tmnxMobServStatTable 1 }

TmnxMobServStatEntry ::= SEQUENCE {
        tmnxMobServCardSlotNum              TmnxSlotNumOrZero,
        tmnxMobServStatApn                  Gauge32,
        tmnxMobServStatBearers              Gauge32,
        tmnxMobServStatDefaultBearers       Gauge32,
        tmnxMobServStatDedicatedBearers     Gauge32,
        tmnxMobServStatIpv4Bearers          Gauge32,
        tmnxMobServStatIpv6Bearers          Gauge32,
        tmnxMobServStatIpv4v6Bearers        Gauge32,
        tmnxMobServStatActiveBearers        Gauge32,
        tmnxMobServStatIdleBearers          Gauge32,
        tmnxMobServStatRoamers              Gauge32,
        tmnxMobServStatPagingInProgress     Gauge32,
        tmnxMobServStatIpv4Sdf              Gauge32,
        tmnxMobServStatIpv6Sdf              Gauge32,
        tmnxMobServStatBuffersAllocated     Gauge32,
        tmnxMobServStatBuffersAvailable     Gauge32,
        tmnxMobServStatBuffersAllocErr      Gauge32,
        tmnxMobServStatHomers               Gauge32,
        tmnxMobServStatVisitors             Gauge32,
        tmnxMobServStatENBs                 Gauge32,
        tmnxMobServStatMmes                 Gauge32,
        tmnxMobServStatPgws                 Gauge32,
        tmnxMobServStatUes                  Gauge32,
        tmnxMobServStatRfPeer               Gauge32,
        tmnxMobServStatRfAcctStartBuf       Gauge32,
        tmnxMobServStatRfAcctIntBuf         Gauge32,
        tmnxMobServStatRfAcctStopBuf        Gauge32,
        tmnxMobServStatIdleUes              Gauge32,
        tmnxMobServStatNumSuspendedUE       Gauge32,
        tmnxMobServStatEmergencyPdnSess     Gauge32,
        tmnxMobServStatPagingDrops          Gauge32
    }

tmnxMobServCardSlotNum    OBJECT-TYPE
    SYNTAX      TmnxSlotNumOrZero
    MAX-ACCESS  not-accessible
    STATUS      current
    DESCRIPTION
        "The value of tmnxMobServCardSlotNum indicates the slot number of this
         card."
    ::= { tmnxMobServStatEntry 1 }

tmnxMobServStatApn  OBJECT-TYPE
    SYNTAX      Gauge32
    MAX-ACCESS  read-only
    STATUS      current
    DESCRIPTION
        "The value of tmnxMobServStatApn indicates the number of Access Point
         Names (APNs) being served by this card."
    ::= { tmnxMobServStatEntry 2 }

tmnxMobServStatBearers  OBJECT-TYPE
    SYNTAX      Gauge32
    MAX-ACCESS  read-only
    STATUS      current
    DESCRIPTION
        "The value of tmnxMobServStatBearers indicates the number of bearers
         being served by this card."
    ::= { tmnxMobServStatEntry 3 }

tmnxMobServStatDefaultBearers  OBJECT-TYPE
    SYNTAX      Gauge32
    MAX-ACCESS  read-only
    STATUS      current
    DESCRIPTION
        "The value of tmnxMobServStatDefaultBearers indicates the number of
         default bearers being served by this card."
    ::= { tmnxMobServStatEntry 4 }

tmnxMobServStatDedicatedBearers  OBJECT-TYPE
    SYNTAX      Gauge32
    MAX-ACCESS  read-only
    STATUS      current
    DESCRIPTION
        "The value of tmnxMobServStatDedicatedBearers indicates the number of
         dedicated bearers being served by this card."
    ::= { tmnxMobServStatEntry 5 }

tmnxMobServStatIpv4Bearers  OBJECT-TYPE
    SYNTAX      Gauge32
    MAX-ACCESS  read-only
    STATUS      current
    DESCRIPTION
        "The value of tmnxMobServStatIpv4Bearers indicates the number of
         IPv4 bearers being served by this card."
    ::= { tmnxMobServStatEntry 6 }

tmnxMobServStatIpv6Bearers  OBJECT-TYPE
    SYNTAX      Gauge32
    MAX-ACCESS  read-only
    STATUS      current
    DESCRIPTION
        "The value of tmnxMobServStatIpv6Bearers indicates the number of
         IPv6 bearers being served by this card."
    ::= { tmnxMobServStatEntry 7 }

tmnxMobServStatIpv4v6Bearers  OBJECT-TYPE
    SYNTAX      Gauge32
    MAX-ACCESS  read-only
    STATUS      current
    DESCRIPTION
        "The value of tmnxMobServStatIpv4v6Bearers indicates the number of
         IPv4v6 bearers being served by this card."
    ::= { tmnxMobServStatEntry 8 }

tmnxMobServStatActiveBearers  OBJECT-TYPE
    SYNTAX      Gauge32
    MAX-ACCESS  read-only
    STATUS      current
    DESCRIPTION
        "The value of tmnxMobServStatActiveBearers indicates the number of
         active bearers being served by this card."
    ::= { tmnxMobServStatEntry 9 }

tmnxMobServStatIdleBearers  OBJECT-TYPE
    SYNTAX      Gauge32
    MAX-ACCESS  read-only
    STATUS      current
    DESCRIPTION
        "The value of tmnxMobServStatIdleBearers indicates the number of
         idle bearers being served by this card."
    ::= { tmnxMobServStatEntry 10 }

tmnxMobServStatRoamers  OBJECT-TYPE
    SYNTAX      Gauge32
    MAX-ACCESS  read-only
    STATUS      current
    DESCRIPTION
        "The value of tmnxMobServStatRoamers indicates the number of roamers
         being served by this card."
    ::= { tmnxMobServStatEntry 11 }

tmnxMobServStatPagingInProgress  OBJECT-TYPE
    SYNTAX      Gauge32
    MAX-ACCESS  read-only
    STATUS      current
    DESCRIPTION
        "The value of tmnxMobServStatPagingInProgress indicates the number of
         paging processes in progress on this card."
    ::= { tmnxMobServStatEntry 12 }

tmnxMobServStatIpv4Sdf  OBJECT-TYPE
    SYNTAX      Gauge32
    MAX-ACCESS  read-only
    STATUS      current
    DESCRIPTION
        "The value of tmnxMobServStatIpv4Sdf indicates the number of IPv4
         Service Data Flows (SDFs) on this card."
    ::= { tmnxMobServStatEntry 13 }

tmnxMobServStatIpv6Sdf  OBJECT-TYPE
    SYNTAX      Gauge32
    MAX-ACCESS  read-only
    STATUS      current
    DESCRIPTION
        "The value of tmnxMobServStatIpv6Sdf indicates the number of IPv6
         Service Data Flows (SDFs) on this card."
    ::= { tmnxMobServStatEntry 14 }

tmnxMobServStatBuffersAllocated  OBJECT-TYPE
    SYNTAX      Gauge32
    MAX-ACCESS  read-only
    STATUS      current
    DESCRIPTION
        "The value of tmnxMobServStatBuffersAllocated indicates the number of
         allocated paging buffers on this card."
    ::= { tmnxMobServStatEntry 15 }

tmnxMobServStatBuffersAvailable  OBJECT-TYPE
    SYNTAX      Gauge32
    MAX-ACCESS  read-only
    STATUS      current
    DESCRIPTION
        "The value of tmnxMobServStatBuffersAvailable indicates the number of
         available paging buffers on this card."
    ::= { tmnxMobServStatEntry 16 }

tmnxMobServStatBuffersAllocErr  OBJECT-TYPE
    SYNTAX      Gauge32
    MAX-ACCESS  read-only
    STATUS      current
    DESCRIPTION
        "The value of tmnxMobServStatBuffersAllocErr indicates the number of
         paging buffers not available errors on this card."
    ::= { tmnxMobServStatEntry 17 }

tmnxMobServStatHomers  OBJECT-TYPE
    SYNTAX      Gauge32
    MAX-ACCESS  read-only
    STATUS      current
    DESCRIPTION
        "The value of tmnxMobServStatHomers indicates the number of
         homers being served by this card."
    ::= { tmnxMobServStatEntry 18 }

tmnxMobServStatVisitors  OBJECT-TYPE
    SYNTAX      Gauge32
    MAX-ACCESS  read-only
    STATUS      current
    DESCRIPTION
        "The value of tmnxMobServStatVisitors indicates the number of
         visitors being served by this card."
    ::= { tmnxMobServStatEntry 19 }

tmnxMobServStatENBs  OBJECT-TYPE
    SYNTAX      Gauge32
    MAX-ACCESS  read-only
    STATUS      current
    DESCRIPTION
        "The value of tmnxMobServStatENBs indicates the number of
         Evolved NodeBs (eNodeBs) being served by this card."
    ::= { tmnxMobServStatEntry 20 }

tmnxMobServStatMmes  OBJECT-TYPE
    SYNTAX      Gauge32
    MAX-ACCESS  read-only
    STATUS      current
    DESCRIPTION
        "The value of tmnxMobServStatMmes indicates the number of
         Mobility Management Entities (MMEs) being served by this card."
    ::= { tmnxMobServStatEntry 21 }

tmnxMobServStatPgws  OBJECT-TYPE
    SYNTAX      Gauge32
    MAX-ACCESS  read-only
    STATUS      current
    DESCRIPTION
        "The value of tmnxMobServStatPgws indicates the number of
         Packet Data Network (PDN) gateways being served by this card."
    ::= { tmnxMobServStatEntry 22 }

tmnxMobServStatUes  OBJECT-TYPE
    SYNTAX      Gauge32
    MAX-ACCESS  read-only
    STATUS      current
    DESCRIPTION
        "The value of tmnxMobServStatUes indicates the number of
         User Equipments (UE) being served by this card."
    ::= { tmnxMobServStatEntry 23 }

tmnxMobServStatRfPeer  OBJECT-TYPE
    SYNTAX      Gauge32
    MAX-ACCESS  read-only
    STATUS      current
    DESCRIPTION
        "The value of tmnxMobServStatRfPeer indicates the number of
         peers on the Rf reference point being served by this card."
    ::= { tmnxMobServStatEntry 24 }

tmnxMobServStatRfAcctStartBuf  OBJECT-TYPE
    SYNTAX      Gauge32
    MAX-ACCESS  read-only
    STATUS      current
    DESCRIPTION
        "The value of tmnxMobServStatRfAcctStartBuf indicates the number of
         Accounting Request (ACR) Start messages buffered by this card."
    ::= { tmnxMobServStatEntry 25 }

tmnxMobServStatRfAcctIntBuf  OBJECT-TYPE
    SYNTAX      Gauge32
    MAX-ACCESS  read-only
    STATUS      current
    DESCRIPTION
        "The value of tmnxMobServStatRfAcctIntBuf indicates the number of
         Accounting Request (ACR) Interim messages buffered by this card."
    ::= { tmnxMobServStatEntry 26 }

tmnxMobServStatRfAcctStopBuf  OBJECT-TYPE
    SYNTAX      Gauge32
    MAX-ACCESS  read-only
    STATUS      current
    DESCRIPTION
        "The value of tmnxMobServStatRfAcctStopBuf indicates the number of
         Accounting Request (ACR) Stop messages buffered by this card."
    ::= { tmnxMobServStatEntry 27 }

tmnxMobServStatIdleUes  OBJECT-TYPE
    SYNTAX      Gauge32
    MAX-ACCESS  read-only
    STATUS      current
    DESCRIPTION
        "The value of tmnxMobServStatIdleUes indicates the number of
         idle User Equipments (UE) being served by this card."
    ::= { tmnxMobServStatEntry 28 }

tmnxMobServStatNumSuspendedUE  OBJECT-TYPE
    SYNTAX      Gauge32
    MAX-ACCESS  read-only
    STATUS      current
    DESCRIPTION
        "The value of tmnxMobServStatNumSuspendedUE indicates the number of
         User Equipments (UE) in the suspended state."
    ::= { tmnxMobServStatEntry 29 }

tmnxMobServStatEmergencyPdnSess  OBJECT-TYPE
    SYNTAX      Gauge32
    MAX-ACCESS  read-only
    STATUS      current
    DESCRIPTION
        "The value of tmnxMobServStatEmergencyPdnSess indicates the number of
         Emergency PDN sessions on this card."
    ::= { tmnxMobServStatEntry 30 }

tmnxMobServStatPagingDrops  OBJECT-TYPE
    SYNTAX      Gauge32
    MAX-ACCESS  read-only
    STATUS      current
    DESCRIPTION
        "The value of tmnxMobServStatPagingDrops indicates the number of
         packets that are dropped while the User Equipment (UE) is in paging
         mode."
    ::= { tmnxMobServStatEntry 31 }

--
--  Call flows Table
--

tmnxMobServProcsTable  OBJECT-TYPE
    SYNTAX      SEQUENCE OF TmnxMobServProcsEntry
    MAX-ACCESS  not-accessible
    STATUS      current
    DESCRIPTION
        "The tmnxMobServProcsTable has an entry for each each Mobility Service
         Module (MSM) configured in the mobility system group defined
         for a Serving Gateway (SGW)."
    ::= { tmnxMobServingStatObjs 2 }

tmnxMobServProcsEntry  OBJECT-TYPE
    SYNTAX      TmnxMobServProcsEntry
    MAX-ACCESS  not-accessible
    STATUS      current
    DESCRIPTION
        "Each row entry represents a Mobility Service Module (MSM) and contains
         statistics for call flow procedures on this card."
    AUGMENTS { tmnxMobServStatEntry }
    ::= { tmnxMobServProcsTable 1 }

TmnxMobServProcsEntry ::= SEQUENCE {
        tmnxMobServProcAttach               Counter32,
        tmnxMobServProcDetach               Counter32,
        tmnxMobServProcNwServiceReq         Counter32,
        tmnxMobServProcUeServiceReq         Counter32,
        tmnxMobServProcS1Release            Counter32,
        tmnxMobServProcInterENBX2Hndovr     Counter32,
        tmnxMobServProcInterENBS1Hndovr     Counter32,
        tmnxMobServProcUeDedBrActivation    Counter32,
        tmnxMobServProcNwDedBrActivtn       Counter32,
        tmnxMobServProcNwDedBrDeActiv       Counter32,
        tmnxMobServProcMmeDedBrDeActiv      Counter32,
        tmnxMobServProcHssQosModificatn     Counter32,
        tmnxMobServProcAttachFailures       Counter32,
        tmnxMobServProcDetachFailures       Counter32,
        tmnxMobServProcNwServiceReqFails    Counter32,
        tmnxMobServProcUeServiceReqFails    Counter32,
        tmnxMobServProcS1ReleaseFailures    Counter32,
        tmnxMobServProcEnbX2HndovrFails     Counter32,
        tmnxMobServProcEnbS1HndovrFails     Counter32,
        tmnxMobServProcUeDedBrActvFails     Counter32,
        tmnxMobServProcNwDedBrActvFails     Counter32,
        tmnxMobServProcNwDedBrDeActFails    Counter32,
        tmnxMobServProcMmeDedBrDeAcFails    Counter32,
        tmnxMobServProcHssQosModifyFails    Counter32,
        tmnxMobServProcPagingTimeoutExp     Counter32,
        tmnxMobServProcIntraIdleModeTau     Counter32,
        tmnxMobServProcInterMmeRel          Counter32,
        tmnxMobServProcInterMmeRelFails     Counter32,
        tmnxMobServProcInterIdleTau         Counter32,
        tmnxMobServProcInterIdleTauFails    Counter32,
        tmnxMobServProcS1WithIndTnl         Counter32,
        tmnxMobServProcS1WithIndTnlFails    Counter32,
        tmnxMobServProcS1WoIndTnl           Counter32,
        tmnxMobServProcS1WoIndTnlFails      Counter32,
        tmnxMobServProcInterX2Hndor         Counter32,
        tmnxMobServProcInterX2HndorFails    Counter32,
        tmnxMobServProcInterSgwHoOut        Counter32,
        tmnxMobServProcMltPdnConcvtReqs     Counter32,
        tmnxMobServProcMltPdnConcvtFails    Counter32,
        tmnxMobServProcModBearers           Counter32,
        tmnxMobServProcModBearersFails      Counter32,
        tmnxMobServProcDelBearers           Counter32,
        tmnxMobServProcDelBearersFails      Counter32,
        tmnxMobServProcBearerRes            Counter32,
        tmnxMobServProcBearerResFails       Counter32,
        tmnxMobServProcEhrpdLteHo           Counter32,
        tmnxMobServProcEhrpdLteHoFails      Counter32,
        tmnxMobServProcIntraIdleTauFails    Counter32,
        tmnxMobServProcNwPdnSessDeActiv     Counter32,
        tmnxMobServProcNwPdnSesDeActFail    Counter32,
        tmnxMobServProcPagingAttempts       Counter32,
        tmnxMobServProcPagingFails          Counter32,
        tmnxMobServProcIntraSgwHndvr        Counter32,
        tmnxMobServProcIntraSgwHndvrFail    Counter32,
        tmnxMobServProcIntraSgwS1IndTnl     Counter32,
        tmnxMobServProcIntraS1IndTnlFail    Counter32,
        tmnxMobServProcInterMmeIdleTau      Counter32,
        tmnxMobServProcInterMmeIdlTauFls    Counter32,
        tmnxMobServProcInterMmeS1X2RlSuc    Counter32,
        tmnxMobServProcInterMmeS1X2RlFls    Counter32,
        tmnxMobServProcInterMmeS1RlTnSuc    Counter32,
        tmnxMobServProcInterMmeS1RlTnFls    Counter32,
        tmnxMobServProcInterMmeRelocs       Counter32,
        tmnxMobServProcAttachPiggyBack      Counter32,
        tmnxMobServProcAttachPiggyFail      Counter32,
        tmnxMobServProcUeDedBrDeActv        Counter32,
        tmnxMobServProcUeDedBrDeActvFail    Counter32,
        tmnxMobServProcUeDedBrModify        Counter32,
        tmnxMobServProcUeDedBrModifyFail    Counter32,
        tmnxMobServProcNwBrModify           Counter32,
        tmnxMobServProcNwBrModifyFail       Counter32,
        tmnxMobServProcPDNSuspNotice        Counter32,
        tmnxMobServProcPDNResumeNotice      Counter32,
        tmnxMobServProcIRSR                 Counter32,
        tmnxMobServProcEmergncyAttachSuc    Counter32
    }

tmnxMobServProcAttach  OBJECT-TYPE
    SYNTAX      Counter32
    MAX-ACCESS  read-only
    STATUS      current
    DESCRIPTION
        "The value of tmnxMobServProcAttach indicates the number of attach
         procedures sent by the User Equipments (UEs) and executed successfully
         on this card."
    ::= { tmnxMobServProcsEntry 1 }

tmnxMobServProcDetach  OBJECT-TYPE
    SYNTAX      Counter32
    MAX-ACCESS  read-only
    STATUS      current
    DESCRIPTION
        "The value of tmnxMobServProcDetach indicates the number of detach
         procedures executed successfully on this card."
    ::= { tmnxMobServProcsEntry 2 }

tmnxMobServProcNwServiceReq  OBJECT-TYPE
    SYNTAX      Counter32
    MAX-ACCESS  read-only
    STATUS      obsolete
    DESCRIPTION
        "The value of tmnxMobServProcNwServiceReq indicates the number of
         successful network initiated service request procedures served by
         this card.

         This object was made obsolete in the 3.0 release."
    ::= { tmnxMobServProcsEntry 3 }

tmnxMobServProcUeServiceReq  OBJECT-TYPE
    SYNTAX      Counter32
    MAX-ACCESS  read-only
    STATUS      current
    DESCRIPTION
        "The value of tmnxMobServProcUeServiceReq indicates the number of
         successful User Equipment (UE) initiated service request procedures
         served by this card."
    ::= { tmnxMobServProcsEntry 4 }

tmnxMobServProcS1Release  OBJECT-TYPE
    SYNTAX      Counter32
    MAX-ACCESS  read-only
    STATUS      current
    DESCRIPTION
        "The value of tmnxMobServProcS1Release indicates the number of
         successful Evolved NodeB (eNodeB) and Mobility Management Entity (MME)
         initiated S1 release procedures served by this card."
    ::= { tmnxMobServProcsEntry 5 }

tmnxMobServProcInterENBX2Hndovr  OBJECT-TYPE
    SYNTAX      Counter32
    MAX-ACCESS  read-only
    STATUS      obsolete
    DESCRIPTION
        "The value of tmnxMobServProcInterENBX2Hndovr indicates the number of
         successful intra Serving Gateway (SGW) X2-based handovers served by
         this card.

         This object was made obsolete in the 3.0 release."
    ::= { tmnxMobServProcsEntry 6 }

tmnxMobServProcInterENBS1Hndovr  OBJECT-TYPE
    SYNTAX      Counter32
    MAX-ACCESS  read-only
    STATUS      obsolete
    DESCRIPTION
        "The value of tmnxMobServProcInterENBS1Hndovr indicates the number of
         successful  intra Serving Gateway (SGW) S1-based handovers served by
         this card. The S1-based handover procedure is used when the X2-based
         handover cannot be used.

         This object was made obsolete in the 3.0 release."
    ::= { tmnxMobServProcsEntry 7 }

tmnxMobServProcUeDedBrActivation  OBJECT-TYPE
    SYNTAX      Counter32
    MAX-ACCESS  read-only
    STATUS      current
    DESCRIPTION
        "The value of tmnxMobServProcUeDedBrActivation indicates the number of
         successful User Equipment (UE) initiated dedicated bearer activation
         procedures served by this card."
    ::= { tmnxMobServProcsEntry 8 }

tmnxMobServProcNwDedBrActivtn  OBJECT-TYPE
    SYNTAX      Counter32
    MAX-ACCESS  read-only
    STATUS      current
    DESCRIPTION
        "The value of tmnxMobServProcNwDedBrActivtn indicates the number of
         successful network initiated dedicated bearer activation procedures
         served by this card."
    ::= { tmnxMobServProcsEntry 9 }

tmnxMobServProcNwDedBrDeActiv  OBJECT-TYPE
    SYNTAX      Counter32
    MAX-ACCESS  read-only
    STATUS      current
    DESCRIPTION
        "The value of tmnxMobServProcNwDedBrDeActiv indicates the number of
         successful network initiated dedicated bearer de-activation procedures
         served by this card."
    ::= { tmnxMobServProcsEntry 10 }

tmnxMobServProcMmeDedBrDeActiv  OBJECT-TYPE
    SYNTAX      Counter32
    MAX-ACCESS  read-only
    STATUS      current
    DESCRIPTION
        "The value of tmnxMobServProcMmeDedBrDeActiv indicates the number of
         successful Mobility Management Entity (MME) initiated dedicated bearer
         de-activation procedures served by this card."
    ::= { tmnxMobServProcsEntry 11 }

tmnxMobServProcHssQosModificatn  OBJECT-TYPE
    SYNTAX      Counter32
    MAX-ACCESS  read-only
    STATUS      current
    DESCRIPTION
        "The value of tmnxMobServProcHssQosModificatn indicates the number of
         successful HSS initiated QoS modification procedures served by this
         card."
    ::= { tmnxMobServProcsEntry 12 }

tmnxMobServProcAttachFailures  OBJECT-TYPE
    SYNTAX      Counter32
    MAX-ACCESS  read-only
    STATUS      current
    DESCRIPTION
        "The value of tmnxMobServProcAttachFailures indicates the number of
         attach procedure failures."
    ::= { tmnxMobServProcsEntry 13 }

tmnxMobServProcDetachFailures  OBJECT-TYPE
    SYNTAX      Counter32
    MAX-ACCESS  read-only
    STATUS      current
    DESCRIPTION
        "The value of tmnxMobServProcDetachFailures indicates the number of
         detach procedure failures."
    ::= { tmnxMobServProcsEntry 14 }

tmnxMobServProcNwServiceReqFails  OBJECT-TYPE
    SYNTAX      Counter32
    MAX-ACCESS  read-only
    STATUS      obsolete
    DESCRIPTION
        "The value of tmnxMobServProcNwServiceReqFails indicates the number of
         network initiated service request procedure failures.

         This object was made obsolete in the 3.0 release."
    ::= { tmnxMobServProcsEntry 15 }

tmnxMobServProcUeServiceReqFails  OBJECT-TYPE
    SYNTAX      Counter32
    MAX-ACCESS  read-only
    STATUS      current
    DESCRIPTION
        "The value of tmnxMobServProcUeServiceReqFails indicates the number of
          User Equipment (UE) initiated service request procedure failures."
    ::= { tmnxMobServProcsEntry 16 }

tmnxMobServProcS1ReleaseFailures  OBJECT-TYPE
    SYNTAX      Counter32
    MAX-ACCESS  read-only
    STATUS      current
    DESCRIPTION
        "The value of tmnxMobServProcS1ReleaseFailures indicates the number of
         Evolved NodeB (eNodeB) and Mobility Management Entity (MME) initiated
         S1 release procedure failures."
    ::= { tmnxMobServProcsEntry 17 }

tmnxMobServProcEnbX2HndovrFails  OBJECT-TYPE
    SYNTAX      Counter32
    MAX-ACCESS  read-only
    STATUS      obsolete
    DESCRIPTION
        "The value of tmnxMobServProcEnbX2HndovrFails indicates the number of
         intra Serving Gateway (SGW) inter eNodeB X2-based handover failures.

         This object was made obsolete in the 3.0 release."
    ::= { tmnxMobServProcsEntry 18 }

tmnxMobServProcEnbS1HndovrFails  OBJECT-TYPE
    SYNTAX      Counter32
    MAX-ACCESS  read-only
    STATUS      obsolete
    DESCRIPTION
        "The value of tmnxMobServProcEnbS1HndovrFails indicates the number of
         intra Serving Gateway (SGW) inter eNodeB S1-based handover failures.

         This object was made obsolete in the 3.0 release."
    ::= { tmnxMobServProcsEntry 19 }

tmnxMobServProcUeDedBrActvFails  OBJECT-TYPE
    SYNTAX      Counter32
    MAX-ACCESS  read-only
    STATUS      current
    DESCRIPTION
        "The value of tmnxMobServProcUeDedBrActvFails indicates the number of
         User Equipment (UE) initiated dedicated bearer activation procedure
         failures."
    ::= { tmnxMobServProcsEntry 20 }

tmnxMobServProcNwDedBrActvFails  OBJECT-TYPE
    SYNTAX      Counter32
    MAX-ACCESS  read-only
    STATUS      current
    DESCRIPTION
        "The value of tmnxMobServProcNwDedBrActvFails indicates the number of
         Policy and Charging Rules Function (PCRF) initiated dedicated bearer
         activation procedure failures."
    ::= { tmnxMobServProcsEntry 21 }

tmnxMobServProcNwDedBrDeActFails  OBJECT-TYPE
    SYNTAX      Counter32
    MAX-ACCESS  read-only
    STATUS      current
    DESCRIPTION
        "The value of tmnxMobServProcNwDedBrDeActFails indicates the number of
         Policy and Charging Rules Function (PCRF) initiated dedicated bearer
         de-activation procedure failures."
    ::= { tmnxMobServProcsEntry 22 }

tmnxMobServProcMmeDedBrDeAcFails  OBJECT-TYPE
    SYNTAX      Counter32
    MAX-ACCESS  read-only
    STATUS      current
    DESCRIPTION
        "The value of tmnxMobServProcMmeDedBrDeAcFails indicates the number of
         Mobility Management Entity (MME) initiated dedicated bearer
         de-activation procedure failures."
    ::= { tmnxMobServProcsEntry 23 }

tmnxMobServProcHssQosModifyFails  OBJECT-TYPE
    SYNTAX      Counter32
    MAX-ACCESS  read-only
    STATUS      current
    DESCRIPTION
        "The value of tmnxMobServProcHssQosModifyFails indicates the number of
         QoS modification procedure failures."
    ::= { tmnxMobServProcsEntry 24 }

tmnxMobServProcPagingTimeoutExp  OBJECT-TYPE
    SYNTAX      Counter32
    MAX-ACCESS  read-only
    STATUS      current
    DESCRIPTION
        "The value of tmnxMobServProcPagingTimeoutExp indicates the number of
         paging timeout expiration."
    ::= { tmnxMobServProcsEntry 25 }

tmnxMobServProcIntraIdleModeTau  OBJECT-TYPE
    SYNTAX      Counter32
    MAX-ACCESS  read-only
    STATUS      current
    DESCRIPTION
        "The value of tmnxMobServProcIntraIdleModeTau indicates the number of
         intra Serving Gateway (SGW) idle mode Tracking Area Updates (TAU)
         served successfully by this card."
    ::= { tmnxMobServProcsEntry 26 }

tmnxMobServProcInterMmeRel  OBJECT-TYPE
    SYNTAX      Counter32
    MAX-ACCESS  read-only
    STATUS      obsolete
    DESCRIPTION
        "The value of tmnxMobServProcInterMmeRelFails indicates the number of
         intra Serving Gateway (SGW) inter Mobility Management Entity (MME)
         relocation.

         This object was made obsolete in the 3.0 release."
    ::= { tmnxMobServProcsEntry 27 }

tmnxMobServProcInterMmeRelFails  OBJECT-TYPE
    SYNTAX      Counter32
    MAX-ACCESS  read-only
    STATUS      obsolete
    DESCRIPTION
        "The value of tmnxMobServProcInterMmeRelFails indicates the number of
         intra Serving Gateway (SGW) inter Mobility Management Entity (MME)
         relocation failures.

         This object was made obsolete in the 3.0 release."
    ::= { tmnxMobServProcsEntry 28 }

tmnxMobServProcInterIdleTau  OBJECT-TYPE
    SYNTAX      Counter32
    MAX-ACCESS  read-only
    STATUS      current
    DESCRIPTION
        "The value of tmnxMobServProcInterIdleTau indicates the number of
         incoming inter Serving Gateway (SGW) idle mode Tracking Area
         Updates (TAU) served successfully by this card."
    ::= { tmnxMobServProcsEntry 29 }

tmnxMobServProcInterIdleTauFails  OBJECT-TYPE
    SYNTAX      Counter32
    MAX-ACCESS  read-only
    STATUS      current
    DESCRIPTION
        "The value of tmnxMobServProcInterIdleTauFails indicates the number of
         incoming inter Serving Gateway (SGW) idle mode Tracking Area
         Update (TAU) failures."
    ::= { tmnxMobServProcsEntry 30 }

tmnxMobServProcS1WithIndTnl  OBJECT-TYPE
    SYNTAX      Counter32
    MAX-ACCESS  read-only
    STATUS      current
    DESCRIPTION
        "The value of tmnxMobServProcS1WithIndTnl indicates the number of
         incoming inter Serving Gateway (SGW) handovers with indirect tunnels
         served successfully by this card."
    ::= { tmnxMobServProcsEntry 31 }

tmnxMobServProcS1WithIndTnlFails  OBJECT-TYPE
    SYNTAX      Counter32
    MAX-ACCESS  read-only
    STATUS      current
    DESCRIPTION
        "The value of tmnxMobServProcS1WithIndTnlFails indicates the number of
         incoming inter Serving Gateway (SGW) handover failures with indirect
         tunnels."
    ::= { tmnxMobServProcsEntry 32 }

tmnxMobServProcS1WoIndTnl  OBJECT-TYPE
    SYNTAX      Counter32
    MAX-ACCESS  read-only
    STATUS      current
    DESCRIPTION
        "The value of tmnxMobServProcS1WoIndTnl indicates the number of
         incoming inter Serving Gateway (SGW) handovers without indirect
         tunnels served successfully by this card."
    ::= { tmnxMobServProcsEntry 33 }

tmnxMobServProcS1WoIndTnlFails  OBJECT-TYPE
    SYNTAX      Counter32
    MAX-ACCESS  read-only
    STATUS      current
    DESCRIPTION
        "The value of tmnxMobServProcS1WoIndTnlFails indicates the number of
         incoming inter Serving Gateway (SGW) handover failures without indirect
         tunnels."
    ::= { tmnxMobServProcsEntry 34 }

tmnxMobServProcInterX2Hndor  OBJECT-TYPE
    SYNTAX      Counter32
    MAX-ACCESS  read-only
    STATUS      current
    DESCRIPTION
        "The value of tmnxMobServProcInterX2Hndor indicates the number of
         incoming inter Serving Gateway (SGW) X2-based handovers served
         successfully by this card."
    ::= { tmnxMobServProcsEntry 35 }

tmnxMobServProcInterX2HndorFails  OBJECT-TYPE
    SYNTAX      Counter32
    MAX-ACCESS  read-only
    STATUS      current
    DESCRIPTION
        "The value of tmnxMobServProcInterX2HndorFails indicates the number of
         incoming inter Serving Gateway (SGW) X2-based handover failures."
    ::= { tmnxMobServProcsEntry 36 }

tmnxMobServProcInterSgwHoOut  OBJECT-TYPE
    SYNTAX      Counter32
    MAX-ACCESS  read-only
    STATUS      current
    DESCRIPTION
        "The value of tmnxMobServProcInterSgwHoOut indicates the number of
         outgoing inter Serving Gateway (SGW) handovers served successfully by
         this card."
    ::= { tmnxMobServProcsEntry 37 }

tmnxMobServProcMltPdnConcvtReqs  OBJECT-TYPE
    SYNTAX      Counter32
    MAX-ACCESS  read-only
    STATUS      obsolete
    DESCRIPTION
        "The value of tmnxMobServProcMltPdnConcvtReqs indicates the number of
         multiple Packet Data Network (PDN) connectivity requests served
         successfully by this card.

         This object was made obsolete in the 3.0 release."
    ::= { tmnxMobServProcsEntry 38 }

tmnxMobServProcMltPdnConcvtFails  OBJECT-TYPE
    SYNTAX      Counter32
    MAX-ACCESS  read-only
    STATUS      obsolete
    DESCRIPTION
        "The value of tmnxMobServProcMltPdnConcvtFails indicates the number of
         multiple Packet Data Network (PDN) connectivity failures.

         This object was made obsolete in the 3.0 release."
    ::= { tmnxMobServProcsEntry 39 }

tmnxMobServProcModBearers  OBJECT-TYPE
    SYNTAX      Counter32
    MAX-ACCESS  read-only
    STATUS      obsolete
    DESCRIPTION
        "The value of tmnxMobServProcModBearers indicates the number of
         modify bearer commands served by this card.

         This object was made obsolete in the 3.0 release."
    ::= { tmnxMobServProcsEntry 40 }

tmnxMobServProcModBearersFails  OBJECT-TYPE
    SYNTAX      Counter32
    MAX-ACCESS  read-only
    STATUS      obsolete
    DESCRIPTION
        "The value of tmnxMobServProcModBearersFails indicates the number of
         modify bearer command failures served by this card.

         This object was made obsolete in the 3.0 release."
    ::= { tmnxMobServProcsEntry 41 }

tmnxMobServProcDelBearers  OBJECT-TYPE
    SYNTAX      Counter32
    MAX-ACCESS  read-only
    STATUS      obsolete
    DESCRIPTION
        "The value of tmnxMobServProcDelBearers indicates the number of
         delete bearer commands served by this card.

         This object was made obsolete in the 3.0 release."
    ::= { tmnxMobServProcsEntry 42 }

tmnxMobServProcDelBearersFails  OBJECT-TYPE
    SYNTAX      Counter32
    MAX-ACCESS  read-only
    STATUS      obsolete
    DESCRIPTION
        "The value of tmnxMobServProcDelBearersFails indicates the number of
         delete bearer command failures served by this card.

         This object was made obsolete in the 3.0 release."
    ::= { tmnxMobServProcsEntry 43 }

tmnxMobServProcBearerRes  OBJECT-TYPE
    SYNTAX      Counter32
    MAX-ACCESS  read-only
    STATUS      obsolete
    DESCRIPTION
        "The value of tmnxMobServProcBearerRes indicates the number of
         bearer resource commands served by this card.

         This object was made obsolete in the 3.0 release."
    ::= { tmnxMobServProcsEntry 44 }

tmnxMobServProcBearerResFails  OBJECT-TYPE
    SYNTAX      Counter32
    MAX-ACCESS  read-only
    STATUS      obsolete
    DESCRIPTION
        "The value of tmnxMobServProcBearerResFails indicates the number of
         bearer resource command failures served by this card.

         This object was made obsolete in the 3.0 release."
    ::= { tmnxMobServProcsEntry 45 }

tmnxMobServProcEhrpdLteHo  OBJECT-TYPE
    SYNTAX      Counter32
    MAX-ACCESS  read-only
    STATUS      current
    DESCRIPTION
        "The value of tmnxMobServProcEhrpdLteHo indicates the number of
         evolved High Rate Packet Data (eHRPD) to Long Term Evolution (LTE)
         handovers served successfully by this card."
    ::= { tmnxMobServProcsEntry 46 }

tmnxMobServProcEhrpdLteHoFails  OBJECT-TYPE
    SYNTAX      Counter32
    MAX-ACCESS  read-only
    STATUS      current
    DESCRIPTION
        "The value of tmnxMobServProcEhrpdLteHoFails indicates the number of
         evolved High Rate Packet Data (eHRPD) to Long Term Evolution (LTE)
         handover failures served by this card."
    ::= { tmnxMobServProcsEntry 47 }

tmnxMobServProcIntraIdleTauFails  OBJECT-TYPE
    SYNTAX      Counter32
    MAX-ACCESS  read-only
    STATUS      current
    DESCRIPTION
        "The value of tmnxMobServProcIntraIdleTauFails indicates the number of
         intra Serving Gateway (SGW) idle mode Tracking Area Updates (TAU)
         failures served by this card."
    ::= { tmnxMobServProcsEntry 48 }

tmnxMobServProcNwPdnSessDeActiv  OBJECT-TYPE
    SYNTAX      Counter32
    MAX-ACCESS  read-only
    STATUS      current
    DESCRIPTION
        "The value of tmnxMobServProcNwPdnSessDeActiv indicates the number of
         network initiated Packet Data Network (PDN) session de-activation
         procedures served by this card."
    ::= { tmnxMobServProcsEntry 49 }

tmnxMobServProcNwPdnSesDeActFail  OBJECT-TYPE
    SYNTAX      Counter32
    MAX-ACCESS  read-only
    STATUS      current
    DESCRIPTION
        "The value of tmnxMobServProcNwPdnSesDeActFail indicates the number of
         network initiated Packet Data Network (PDN) session de-activation
         procedure failures served by this card."
    ::= { tmnxMobServProcsEntry 50 }

tmnxMobServProcPagingAttempts  OBJECT-TYPE
    SYNTAX      Counter32
    MAX-ACCESS  read-only
    STATUS      current
    DESCRIPTION
     "The value of tmnxMobServProcPagingAttempts indicates the number of paging
      attempts served by this card."
    ::= { tmnxMobServProcsEntry 51 }

tmnxMobServProcPagingFails  OBJECT-TYPE
    SYNTAX      Counter32
    MAX-ACCESS  read-only
    STATUS      current
    DESCRIPTION
     "The value of tmnxMobServProcPagingFails indicates the number of paging
      failures served by this card."
    ::= { tmnxMobServProcsEntry 52 }

tmnxMobServProcIntraSgwHndvr  OBJECT-TYPE
    SYNTAX      Counter32
    MAX-ACCESS  read-only
    STATUS      current
    DESCRIPTION
     "The value of tmnxMobServProcIntraSgwHndvr indicates the number of
      incoming intra Serving Gateway (SGW) X2-based and S1-based handovers
      with and without indirect tunnels served successfully by this card."
    ::= { tmnxMobServProcsEntry 53 }

tmnxMobServProcIntraSgwHndvrFail  OBJECT-TYPE
    SYNTAX      Counter32
    MAX-ACCESS  read-only
    STATUS      current
    DESCRIPTION
     "The value of tmnxMobServProcIntraSgwHndvrFail indicates the number of
      incoming intra Serving Gateway (SGW) X2-based and S1-based handover
      failures with and without indirect tunnels served by this card."
    ::= { tmnxMobServProcsEntry 54 }

tmnxMobServProcIntraSgwS1IndTnl  OBJECT-TYPE
    SYNTAX      Counter32
    MAX-ACCESS  read-only
    STATUS      current
    DESCRIPTION
     "The value of tmnxMobServProcIntraSgwS1IndTnl indicates the number of
      incoming intra Serving Gateway (SGW) S1-based handovers with indirect
      tunnels served successfully by this card."
    ::= { tmnxMobServProcsEntry 55 }

tmnxMobServProcIntraS1IndTnlFail  OBJECT-TYPE
    SYNTAX      Counter32
    MAX-ACCESS  read-only
    STATUS      current
    DESCRIPTION
     "The value of tmnxMobServProcIntraS1IndTnlFail indicates the number of
      incoming intra Serving Gateway (SGW) S1-based handover failures with
      indirect tunnels served by this card."
    ::= { tmnxMobServProcsEntry 56 }

tmnxMobServProcInterMmeIdleTau  OBJECT-TYPE
    SYNTAX      Counter32
    MAX-ACCESS  read-only
    STATUS      current
    DESCRIPTION
        "The value of tmnxMobServProcInterMmeIdleTau indicates the number of
         incoming intra Serving Gateway (SGW) inter Mobility Management
         Entity (MME) Idle mode Tracking Area Updates (TAU) served
         successfully by this card."
    ::= { tmnxMobServProcsEntry 57 }

tmnxMobServProcInterMmeIdlTauFls  OBJECT-TYPE
    SYNTAX      Counter32
    MAX-ACCESS  read-only
    STATUS      current
    DESCRIPTION
        "The value of tmnxMobServProcInterMmeIdlTauFls indicates the number of
         incoming intra Serving Gateway (SGW) inter Mobility Management
         Entity (MME) Idle mode Tracking Area Updates (TAU) served
         unsuccessfully by this card."
    ::= { tmnxMobServProcsEntry 58 }

tmnxMobServProcInterMmeS1X2RlSuc  OBJECT-TYPE
    SYNTAX      Counter32
    MAX-ACCESS  read-only
    STATUS      current
    DESCRIPTION
        "The value of tmnxMobServProcInterMmeS1X2RlSuc indicates the number of
         intra Serving Gateway (SGW) inter Mobility Management Entity (MME)
         X2-based and S1-based relocation served successfully by this card."
    ::= { tmnxMobServProcsEntry 59 }

tmnxMobServProcInterMmeS1X2RlFls  OBJECT-TYPE
    SYNTAX      Counter32
    MAX-ACCESS  read-only
    STATUS      current
    DESCRIPTION
        "The value of tmnxMobServProcInterMmeS1X2RlFls indicates the number of
         intra Serving Gateway (SGW) inter Mobility Management Entity (MME)
         X2-based and S1-based relocation failures served by this card."
    ::= { tmnxMobServProcsEntry 60 }

tmnxMobServProcInterMmeS1RlTnSuc  OBJECT-TYPE
    SYNTAX      Counter32
    MAX-ACCESS  read-only
    STATUS      current
    DESCRIPTION
        "The value of tmnxMobServProcInterMmeS1RlTnSuc indicates the number of
         intra Serving Gateway (SGW) inter Mobility Management Entity (MME)
         S1-based relocation with indirect tunnels served successfully by this
         card."
    ::= { tmnxMobServProcsEntry 61 }

tmnxMobServProcInterMmeS1RlTnFls  OBJECT-TYPE
    SYNTAX      Counter32
    MAX-ACCESS  read-only
    STATUS      current
    DESCRIPTION
        "The value of tmnxMobServProcInterMmeS1RlTnFls indicates the number of
         intra Serving Gateway (SGW) inter Mobility Management Entity (MME)
         S1-based relocation failures with indirect tunnels served by this
         card."
    ::= { tmnxMobServProcsEntry 62 }

tmnxMobServProcInterMmeRelocs  OBJECT-TYPE
    SYNTAX      Counter32
    MAX-ACCESS  read-only
    STATUS      current
    DESCRIPTION
        "The value of tmnxMobServProcInterMmeRelocs indicates the number of
         incoming intra Serving Gateway (SGW) inter Mobility Management
         Entity (MME) detected by this card."
    ::= { tmnxMobServProcsEntry 63 }

tmnxMobServProcAttachPiggyBack  OBJECT-TYPE
    SYNTAX      Counter32
    MAX-ACCESS  read-only
    STATUS      current
    DESCRIPTION
        "The value of tmnxMobServProcAttachPiggyBack indicates the number of
         attach procedures sent by the User Equipments (UEs) and executed
         successfully on this card with piggybacking."
    ::= { tmnxMobServProcsEntry 64 }

tmnxMobServProcAttachPiggyFail  OBJECT-TYPE
    SYNTAX      Counter32
    MAX-ACCESS  read-only
    STATUS      current
    DESCRIPTION
        "The value of tmnxMobServProcAttachPiggyFail indicates the number of
         attach procedure failures with piggybacking."
    ::= { tmnxMobServProcsEntry 65 }

tmnxMobServProcUeDedBrDeActv  OBJECT-TYPE
    SYNTAX      Counter32
    MAX-ACCESS  read-only
    STATUS      current
    DESCRIPTION
        "The value of tmnxMobServProcUeDedBrDeActv indicates the number of
         User-Equipment (UE) initiated dedicated bearer deactivation procedures
         served by this card."
    ::= { tmnxMobServProcsEntry 66 }

tmnxMobServProcUeDedBrDeActvFail  OBJECT-TYPE
    SYNTAX      Counter32
    MAX-ACCESS  read-only
    STATUS      current
    DESCRIPTION
        "The value of tmnxMobServProcUeDedBrDeActvFail indicates the number
         of User-Equipment (UE) initiated dedicated bearer deactivation procedure
         failures in this card."
    ::= { tmnxMobServProcsEntry 67 }

tmnxMobServProcUeDedBrModify  OBJECT-TYPE
    SYNTAX      Counter32
    MAX-ACCESS  read-only
    STATUS      current
    DESCRIPTION
        "The value of tmnxMobServProcUeDedBrModify indicates the number of
         User-Equipment (UE) initiated dedicated bearer modification procedures
         served by this card."
    ::= { tmnxMobServProcsEntry 68 }

tmnxMobServProcUeDedBrModifyFail  OBJECT-TYPE
    SYNTAX      Counter32
    MAX-ACCESS  read-only
    STATUS      current
    DESCRIPTION
        "The value of tmnxMobServProcUeDedBrModifyFail indicates the number of
         User-Equipment (UE) initiated dedicated bearer modification procedure
         failures in this card."
    ::= { tmnxMobServProcsEntry 69 }

tmnxMobServProcNwBrModify  OBJECT-TYPE
    SYNTAX      Counter32
    MAX-ACCESS  read-only
    STATUS      current
    DESCRIPTION
        "The value of tmnxMobServProcNwBrModify indicates the number of
         network initiated bearer modification procedures served by this card."
    ::= { tmnxMobServProcsEntry 70 }

tmnxMobServProcNwBrModifyFail  OBJECT-TYPE
    SYNTAX      Counter32
    MAX-ACCESS  read-only
    STATUS      current
    DESCRIPTION
        "The value of tmnxMobServProcNwBrModifyFail indicates the number of
         network initiated bearer modification procedure failures in this card."
    ::= { tmnxMobServProcsEntry 71 }

tmnxMobServProcPDNSuspNotice  OBJECT-TYPE
    SYNTAX      Counter32
    MAX-ACCESS  read-only
    STATUS      current
    DESCRIPTION
        "The value of tmnxMobServProcPDNSuspNotice indicates the number of
         Packet Data Network (PDN) suspend notifications sent by the
         Mobility Management Entity (MME)."
    ::= { tmnxMobServProcsEntry 72 }

tmnxMobServProcPDNResumeNotice  OBJECT-TYPE
    SYNTAX      Counter32
    MAX-ACCESS  read-only
    STATUS      current
    DESCRIPTION
        "The value of tmnxMobServProcPDNResumeNotice indicates the number of
         Packet Data Network (PDN) resume notifications sent by the
         Mobility Management Entity (MME)."
    ::= { tmnxMobServProcsEntry 73 }

tmnxMobServProcIRSR  OBJECT-TYPE
    SYNTAX      Counter32
    MAX-ACCESS  read-only
    STATUS      current
    DESCRIPTION
        "The value of tmnxMobServProcIRSR indicates the number of
         Implicit Resume Service Requests (IRSR) sent  by the
         Mobility Management Entity (MME)."
    ::= { tmnxMobServProcsEntry 74 }

tmnxMobServProcEmergncyAttachSuc  OBJECT-TYPE
    SYNTAX      Counter32
    MAX-ACCESS  read-only
    STATUS      current
    DESCRIPTION
        "The value of tmnxMobServProcEmergncyAttachSuc indicates the number of
         successful Emergency Attach messages served at the Serving
         Gateway (SGW)."
    ::= { tmnxMobServProcsEntry 75 }

--
--  UE Table
--

tmnxMobServUeTable  OBJECT-TYPE
    SYNTAX      SEQUENCE OF TmnxMobServUeEntry
    MAX-ACCESS  not-accessible
    STATUS      current
    DESCRIPTION
        "The tmnxMobServUeTable has an entry for an User Equipment (UE)
         being served by this gateway.

         There will not be more than one row in this table. Whenever a new row
         is created, existing row will be deleted and then new row will be
         created.

         This table will only have an entry for a UE served by the gateways,
         identified by TIMETRA-MOBILE-GATEWAY-MIB::tmnxMobGwId, where the value
         of TIMETRA-MOBILE-GATEWAY-MIB::tmnxMobGwType is equal to 'sgw'."
    ::= { tmnxMobServingStatObjs 3 }

tmnxMobServUeEntry  OBJECT-TYPE
    SYNTAX      TmnxMobServUeEntry
    MAX-ACCESS  not-accessible
    STATUS      current
    DESCRIPTION
        "Each row entry represents an User Equipment (UE) and contains
         identification, connection information."
    INDEX { tmnxMobGwId,
            tmnxMobServUeImsi
          }
    ::= { tmnxMobServUeTable 1 }

TmnxMobServUeEntry ::= SEQUENCE {
        tmnxMobServUeImsi                   TmnxMobUeId,
        tmnxMobServUeRowStatus              RowStatus,
        tmnxMobServUeMsIsdn                 TmnxMobMsisdn,
        tmnxMobServUeImei                   TmnxMobImei,
        tmnxMobServUeNai                    TmnxMobNai,
        tmnxMobServUeNwkMcc                 TmnxMobMcc,
        tmnxMobServUeNwkMnc                 TmnxMobMnc,
        tmnxMobServUeTrackingAreaId         Unsigned32,
        tmnxMobServUeCellId                 Unsigned32,
        tmnxMobServUeState                  TmnxMobUeState,
        tmnxMobServUeRat                    TmnxMobUeRat,
        tmnxMobServUePdnContexts            Unsigned32,
        tmnxMobServUeBearerContexts         Unsigned32,
        tmnxMobServUeChassisIndex           TmnxChassisIndex,
        tmnxMobServUeCardSlotNum            TmnxSlotNum,
        tmnxMobServUeS11MmeCtrlTeid         Unsigned32,
        tmnxMobServUeS11MmeCtrlAddrType     InetAddressType,
        tmnxMobServUeS11MmeCtrlAddr         InetAddress,
        tmnxMobServUeS11SgwCtrlTeid         Unsigned32,
        tmnxMobServUeS11SgwCtrlAddrType     InetAddressType,
        tmnxMobServUeS11SgwCtrlAddr         InetAddress,
        tmnxMobServUeS11InterEnbX2HandOv    Counter32,
        tmnxMobServUeS11InterEnbS1HandOv    Counter32,
        tmnxMobServUeS1ReleaseProcedures    Counter32,
        tmnxMobServUePagingReq              Counter32,
        tmnxMobServUeRfSgwAddrType          InetAddressType,
        tmnxMobServUeRfSgwAddr              InetAddress,
        tmnxMobServUeIntraSgwIdleTau        Counter32,
        tmnxMobServUeInitServReqProcs       Counter32,
        tmnxMobServUePagedCount             Counter32,
        tmnxMobServKeyType                  TmnxMobUeIdType,
        tmnxMobServUeImsiStr                TmnxMobImsiStr
    }

tmnxMobServUeImsi  OBJECT-TYPE
    SYNTAX      TmnxMobUeId
    MAX-ACCESS  not-accessible
    STATUS      current
    DESCRIPTION
        "The value of tmnxMobServUeImsi indicates the International Mobile
         Subscriber Identity (IMSI) of this User Equipment (UE). IMSI is used
         to uniquely identify an UE."
    ::= { tmnxMobServUeEntry 1 }

tmnxMobServUeRowStatus  OBJECT-TYPE
    SYNTAX      RowStatus
    MAX-ACCESS  read-create
    STATUS      current
    DESCRIPTION
        "The value of tmnxMobServUeRowStatus specifies the row status of this
         entry. It is used for the creation and deletion of this User
         Equipment (UE) entry. Creation of a new row will result in the
         existing row, if any, to be deleted.

         If a UE is not served by the gateway identified by tmnxMobGwId, then
         the row creation will fail with an 'inconsistentName' error.

         The creation or deletion of an entry in this table causes creation or
         deletion of corresponding entries in tmnxMobServPdnContextTable,
         tmnxMobServBearerContextTable, tmnxMobServBcSdfTable,
         tmnxMobServBcSdfFilterTable and tmnxMobServBcTftFilterTable."
    ::= { tmnxMobServUeEntry 2 }

tmnxMobServUeMsIsdn  OBJECT-TYPE
    SYNTAX      TmnxMobMsisdn
    MAX-ACCESS  read-only
    STATUS      current
    DESCRIPTION
        "The value of tmnxMobServUeMsIsdn indicates the Mobile Subscriber
         Integrated Services Digital Network (MSISDN) number of this User
         Equipment (UE)."
    ::= { tmnxMobServUeEntry 3 }

tmnxMobServUeImei  OBJECT-TYPE
    SYNTAX      TmnxMobImei
    MAX-ACCESS  read-only
    STATUS      current
    DESCRIPTION
        "The value of tmnxMobServUeImei indicates the International Mobile
         Equipment Identity (IMEI) of this User Equipment (UE)."
    ::= { tmnxMobServUeEntry 4 }

tmnxMobServUeNai  OBJECT-TYPE
    SYNTAX      TmnxMobNai
    MAX-ACCESS  read-only
    STATUS      current
    DESCRIPTION
        "The value of tmnxMobServUeNai indicates the Network Address
         Identifier (NAI) of this User Equipment (UE)."
    ::= { tmnxMobServUeEntry 5 }

tmnxMobServUeNwkMcc  OBJECT-TYPE
    SYNTAX      TmnxMobMcc
    MAX-ACCESS  read-only
    STATUS      current
    DESCRIPTION
        "The value of tmnxMobServUeNwkMcc indicates the Mobile Country Code
         (MCC) of this User Equipment (UE)."
    ::= { tmnxMobServUeEntry 6 }

tmnxMobServUeNwkMnc  OBJECT-TYPE
    SYNTAX      TmnxMobMnc
    MAX-ACCESS  read-only
    STATUS      current
    DESCRIPTION
        "The value of tmnxMobServUeNwkMnc indicates the Mobile Network Code
         (MNC) of this User Equipment (UE)."
    ::= { tmnxMobServUeEntry 7 }

tmnxMobServUeTrackingAreaId  OBJECT-TYPE
    SYNTAX      Unsigned32
    MAX-ACCESS  read-only
    STATUS      current
    DESCRIPTION
        "The value of tmnxMobServUeTrackingAreaId indicates the tracking area
         identifier of this User Equipment (UE)."
    ::= { tmnxMobServUeEntry 8 }

tmnxMobServUeCellId  OBJECT-TYPE
    SYNTAX      Unsigned32
    MAX-ACCESS  read-only
    STATUS      current
    DESCRIPTION
        "The value of tmnxMobServUeCellId indicates the cell identification of
         this User Equipment (UE)."
    ::= { tmnxMobServUeEntry 9 }

tmnxMobServUeState  OBJECT-TYPE
    SYNTAX      TmnxMobUeState
    MAX-ACCESS  read-only
    STATUS      current
    DESCRIPTION
        "The value of tmnxMobServUeState indicates the current state of this
         User Equipment (UE)."
    ::= { tmnxMobServUeEntry 10 }

tmnxMobServUeRat  OBJECT-TYPE
    SYNTAX      TmnxMobUeRat
    MAX-ACCESS  read-only
    STATUS      current
    DESCRIPTION
        "The value of tmnxMobServUeRat indicates the Radio Access Type (RAT)
         of this User Equipment (UE)."
    ::= { tmnxMobServUeEntry 11 }

tmnxMobServUePdnContexts  OBJECT-TYPE
    SYNTAX      Unsigned32
    MAX-ACCESS  read-only
    STATUS      current
    DESCRIPTION
        "The value of tmnxMobServUePdnContexts indicates the number of Packet
         Data Network (PDN) contexts on this User Equipment (UE)."
    ::= { tmnxMobServUeEntry 12 }

tmnxMobServUeBearerContexts  OBJECT-TYPE
    SYNTAX      Unsigned32
    MAX-ACCESS  read-only
    STATUS      current
    DESCRIPTION
        "The value of tmnxMobServUeBearerContexts indicates the number of
         bearer contexts on this User Equipment (UE)."
    ::= { tmnxMobServUeEntry 13 }

tmnxMobServUeChassisIndex  OBJECT-TYPE
    SYNTAX      TmnxChassisIndex
    MAX-ACCESS  read-only
    STATUS      current
    DESCRIPTION
        "The value of tmnxMobServUeChassisIndex indicates the chassis index
         which identifies the chassis registered for this User Equipment (UE)."
    ::= { tmnxMobServUeEntry 14 }

tmnxMobServUeCardSlotNum  OBJECT-TYPE
    SYNTAX      TmnxSlotNum
    MAX-ACCESS  read-only
    STATUS      current
    DESCRIPTION
        "The value of tmnxMobServUeCardSlotNum indicates the slot number in a
         chassis which identifies the card registered for this User
         Equipment (UE)."
    ::= { tmnxMobServUeEntry 15 }

tmnxMobServUeS11MmeCtrlTeid  OBJECT-TYPE
    SYNTAX      Unsigned32
    MAX-ACCESS  read-only
    STATUS      current
    DESCRIPTION
        "The value of tmnxMobServUeS11MmeCtrlTeid indicates the Mobility
         Management Entity (MME) control plane Tunnel Endpoint Identifier
         (TEID) of this User Equipment (UE) in S11 reference point."
    ::= { tmnxMobServUeEntry 16 }

tmnxMobServUeS11MmeCtrlAddrType  OBJECT-TYPE
    SYNTAX      InetAddressType
    MAX-ACCESS  read-only
    STATUS      current
    DESCRIPTION
        "The value of tmnxMobServUeS11MmeCtrlAddrType indicates the type of
         address represented by tmnxMobServUeS11MmeCtrlAddr."
    ::= { tmnxMobServUeEntry 17 }

tmnxMobServUeS11MmeCtrlAddr  OBJECT-TYPE
    SYNTAX      InetAddress (SIZE (0|4|16))
    MAX-ACCESS  read-only
    STATUS      current
    DESCRIPTION
        "The value of tmnxMobServUeS11MmeCtrlAddr indicates the Mobility
         Management Entity (MME) control plane IP address of this User
         Equipment (UE) in S11 reference point."
    ::= { tmnxMobServUeEntry 18 }

tmnxMobServUeS11SgwCtrlTeid  OBJECT-TYPE
    SYNTAX      Unsigned32
    MAX-ACCESS  read-only
    STATUS      current
    DESCRIPTION
        "The value of tmnxMobServUeS11SgwCtrlTeid indicates the Serving Gateway
         (SGW) control plane Tunnel Endpoint Identifier (TEID) of this User
         Equipment (UE) in S11 reference point."
    ::= { tmnxMobServUeEntry 19 }

tmnxMobServUeS11SgwCtrlAddrType  OBJECT-TYPE
    SYNTAX      InetAddressType
    MAX-ACCESS  read-only
    STATUS      current
    DESCRIPTION
        "The value of tmnxMobServUeS11SgwCtrlAddrType indicates the type of
         address represented by tmnxMobServUeS11SgwCtrlAddr."
    ::= { tmnxMobServUeEntry 20 }

tmnxMobServUeS11SgwCtrlAddr  OBJECT-TYPE
    SYNTAX      InetAddress (SIZE (0|4|16))
    MAX-ACCESS  read-only
    STATUS      current
    DESCRIPTION
        "The value of tmnxMobServUeS11SgwCtrlAddr indicates the Serving
         Gateway (SGW) control plane IP address of this User Equipment (UE)
         in S11 reference point."
    ::= { tmnxMobServUeEntry 21 }

tmnxMobServUeS11InterEnbX2HandOv  OBJECT-TYPE
    SYNTAX      Counter32
    MAX-ACCESS  read-only
    STATUS      current
    DESCRIPTION
        "The value of tmnxMobServUeS11InterEnbX2HandOv indicates the number of
         X2-based handovers from one Evolved NodeB (eNodeB) to another Evolved
         NodeB (eNodeB)."
    ::= { tmnxMobServUeEntry 22 }

tmnxMobServUeS11InterEnbS1HandOv  OBJECT-TYPE
    SYNTAX      Counter32
    MAX-ACCESS  read-only
    STATUS      current
    DESCRIPTION
        "The value of tmnxMobServUeS11InterEnbS1HandOv indicates the number of
         S1-based handovers from one Evolved NodeB (eNodeB) to another Evolved
         NodeB (eNodeB)."
    ::= { tmnxMobServUeEntry 23 }

tmnxMobServUeS1ReleaseProcedures  OBJECT-TYPE
    SYNTAX      Counter32
    MAX-ACCESS  read-only
    STATUS      current
    DESCRIPTION
        "The value of tmnxMobServUeS1ReleaseProcedures indicates the number of
         S1 release procedures."
    ::= { tmnxMobServUeEntry 24 }

tmnxMobServUePagingReq  OBJECT-TYPE
    SYNTAX      Counter32
    MAX-ACCESS  read-only
    STATUS      current
    DESCRIPTION
        "The value of tmnxMobServUePagingReq indicates the number of paging
         requests sent by the gateway to this User Equipment (UE)."
    ::= { tmnxMobServUeEntry 25 }

tmnxMobServUeRfSgwAddrType  OBJECT-TYPE
    SYNTAX      InetAddressType
    MAX-ACCESS  read-only
    STATUS      current
    DESCRIPTION
        "The value of tmnxMobServUeRfSgwAddrType indicates the type of
         address represented by tmnxMobServUeRfSgwAddr."
    ::= { tmnxMobServUeEntry 26 }

tmnxMobServUeRfSgwAddr  OBJECT-TYPE
    SYNTAX      InetAddress (SIZE (0|4|16))
    MAX-ACCESS  read-only
    STATUS      current
    DESCRIPTION
        "The value of tmnxMobServUeRfSgwAddr indicates the IP address of
         the Serving Gateway (SGW) in Rf reference point."
    ::= { tmnxMobServUeEntry 27 }

tmnxMobServUeIntraSgwIdleTau  OBJECT-TYPE
    SYNTAX      Counter32
    MAX-ACCESS  read-only
    STATUS      current
    DESCRIPTION
        "The value of tmnxMobServUeIntraSgwIdleTau indicates the number of
         intra Serving Gateway (SGW) idle mode Tracking Area Updates (TAU)
         initiated by this User Equipment (UE)."
    ::= { tmnxMobServUeEntry 28 }

tmnxMobServUeInitServReqProcs  OBJECT-TYPE
    SYNTAX      Counter32
    MAX-ACCESS  read-only
    STATUS      current
    DESCRIPTION
        "The value of tmnxMobServUeInitServReqProcs indicates the number of
         User Equipment (UE) initiated service request procedures."
    ::= { tmnxMobServUeEntry 29 }

tmnxMobServUePagedCount  OBJECT-TYPE
    SYNTAX      Counter32
    MAX-ACCESS  read-only
    STATUS      obsolete
    DESCRIPTION
        "The value of tmnxMobServUePagedCount indicates the number of
         time User Equipments (UEs) paged.

         This object was made obsolete in the 3.0 release."
    ::= { tmnxMobServUeEntry 30 }

tmnxMobServKeyType  OBJECT-TYPE
    SYNTAX      TmnxMobUeIdType
    MAX-ACCESS  read-create
    STATUS      current
    DESCRIPTION
        "The value of tmnxMobServKeyType indicates the subscriber
         identification type of this User Equipment (UE)."
    ::= { tmnxMobServUeEntry 31 }

tmnxMobServUeImsiStr  OBJECT-TYPE
    SYNTAX      TmnxMobImsiStr
    MAX-ACCESS  read-only
    STATUS      current
    DESCRIPTION
        "The value of tmnxMobServUeImsiStr indicates the International Mobile
         Subscriber Identity (IMSI) of this User Equipment (UE)."
    ::= { tmnxMobServUeEntry 32 }

--
--  PDN Context Table
--

tmnxMobServPdnContextTable  OBJECT-TYPE
    SYNTAX      SEQUENCE OF TmnxMobServPdnContextEntry
    MAX-ACCESS  not-accessible
    STATUS      current
    DESCRIPTION
        "The tmnxMobServPdnContextTable has an entry for each Packet Data
         Network (PDN) context of an User Equipment (UE)."
    ::= { tmnxMobServingStatObjs 4 }

tmnxMobServPdnContextEntry  OBJECT-TYPE
    SYNTAX      TmnxMobServPdnContextEntry
    MAX-ACCESS  not-accessible
    STATUS      current
    DESCRIPTION
        "Each row entry represents a Packet Data Network (PDN) context of an
         User Equipment (UE) and contains identification, connection
         information."
    INDEX { tmnxMobGwId,
            tmnxMobServUeImsi,
            tmnxMobServPcApn,
            tmnxMobServPcPdnType
          }
    ::= { tmnxMobServPdnContextTable 1 }

TmnxMobServPdnContextEntry ::= SEQUENCE {
        tmnxMobServPcApn                    TmnxMobApn,
        tmnxMobServPcPdnType                TmnxMobPdnType,
        tmnxMobServPcLinkedBearerId         TmnxMobBearerId,
        tmnxMobServPcApnRestriction         Unsigned32,
        tmnxMobServPcUlApnAmbr              Unsigned32,
        tmnxMobServPcDlApnAmbr              Unsigned32,
        tmnxMobServPcIpv4AddressType        InetAddressType,
        tmnxMobServPcIpv4Address            InetAddress,
        tmnxMobServPcIpv6AddressType        InetAddressType,
        tmnxMobServPcIpv6Address            InetAddress,
        tmnxMobServPcBearerContexts         Unsigned32,
        tmnxMobServPcSessionState           TmnxMobPdnSessionState,
        tmnxMobServPcLastEvent              TmnxMobPdnSessionEvent,
        tmnxMobServPcS5S8SigProtocol        TmnxMobPgwSigProtocol,
        tmnxMobServPcS5S8SgwCtrlTeid        Unsigned32,
        tmnxMobServPcS5S8SgwCtrlAddrType    InetAddressType,
        tmnxMobServPcS5S8SgwCtrlAddr        InetAddress,
        tmnxMobServPcS5S8PgwCtrlTeid        Unsigned32,
        tmnxMobServPcS5S8PgwCtrlAddrType    InetAddressType,
        tmnxMobServPcS5S8PgwCtrlAddr        InetAddress,
        tmnxMobServPcRfServerAddrType       InetAddressType,
        tmnxMobServPcRfServerAddr           InetAddress,
        tmnxMobServPcRfServerState          TmnxMobServerState,
        tmnxMobServPcRfBearerType           TmnxMobChargingBearerType,
        tmnxMobServPcRfChargingLevel        TmnxMobChargingLevel,
        tmnxMobServPcRfChargingProfile      TmnxMobChargingProfile,
        tmnxMobServPcRfTriggeredRecords     Counter32,
        tmnxMobServPcRfInterimRecords       Counter32,
        tmnxMobServPcPcrfEventTriggers      Unsigned32,
        tmnxMobServPcGxcPcrfAddressType     InetAddressType,
        tmnxMobServPcGxcPcrfAddress         InetAddress,
        tmnxMobServPcGxcSgwAddressType      InetAddressType,
        tmnxMobServPcGxcSgwAddress          InetAddress,
        tmnxMobServPcS5S8SgwGreKey          Unsigned32,
        tmnxMobServPcS5S8PgwGreKey          Unsigned32,
        tmnxMobServPcS5S8PgwTrprtAdrType    InetAddressType,
        tmnxMobServPcS5S8PgwTransprtAddr    InetAddress,
        tmnxMobServPcS5S8SgwV6CtrlAdrTyp    InetAddressType,
        tmnxMobServPcS5S8SgwV6CtrlAddr      InetAddress,
        tmnxMobServPcS5S8PgwV6CtrlAdrTyp    InetAddressType,
        tmnxMobServPcS5S8PgwV6CtrlAddr      InetAddress,
        tmnxMobServPcAntiSpoofFailureCnt    Counter32,
        tmnxMobServPcImsiAuthStatus         INTEGER,
        tmnxMobServPcImeiStr                TmnxMobImei,
        tmnxMobServPcImsiStr                TmnxMobImsiStr,
        tmnxMobServPcRefPointType           TmnxMobServRefPointType
    }

tmnxMobServPcApn  OBJECT-TYPE
    SYNTAX      TmnxMobApn
    MAX-ACCESS  not-accessible
    STATUS      current
    DESCRIPTION
        "The value of tmnxMobServPcApn indicates the Access Point Name (APN)
         which uniquely identifies a Packet Data Network (PDN) context of
         an User Equipment (UE)."
    ::= { tmnxMobServPdnContextEntry 1 }

tmnxMobServPcPdnType  OBJECT-TYPE
    SYNTAX      TmnxMobPdnType
    MAX-ACCESS  not-accessible
    STATUS      current
    DESCRIPTION
        "The value of tmnxMobServPcPdnType indicates the Packet Data Network
         (PDN) type of this context."
    ::= { tmnxMobServPdnContextEntry 2 }

tmnxMobServPcLinkedBearerId  OBJECT-TYPE
    SYNTAX      TmnxMobBearerId
    MAX-ACCESS  read-only
    STATUS      current
    DESCRIPTION
        "The value of tmnxMobServPcLinkedBearerId indicates the Linked Evolved
         Packet System (EPS) Bearer Identity (LBI) which is the EPS Bearer
         Identity of the default bearer in this Packet Data Network (PDN)
         context."
    ::= { tmnxMobServPdnContextEntry 3 }

tmnxMobServPcApnRestriction  OBJECT-TYPE
    SYNTAX      Unsigned32
    MAX-ACCESS  read-only
    STATUS      current
    DESCRIPTION
        "The value of tmnxMobServPcApnRestriction indicates the restriction
         required by any active bearer context in this Packet Data Network
         (PDN) context."
    ::= { tmnxMobServPdnContextEntry 4 }

tmnxMobServPcUlApnAmbr  OBJECT-TYPE
    SYNTAX      Unsigned32
    UNITS       "kbps"
    MAX-ACCESS  read-only
    STATUS      current
    DESCRIPTION
        "The value of tmnxMobServPcUlApnAmbr indicates the uplink Aggregate
         Maximum Bit Rate (AMBR) of this Packet Data Network (PDN) context."
    ::= { tmnxMobServPdnContextEntry 5 }

tmnxMobServPcDlApnAmbr  OBJECT-TYPE
    SYNTAX      Unsigned32
    UNITS       "kbps"
    MAX-ACCESS  read-only
    STATUS      current
    DESCRIPTION
        "The value of tmnxMobServPcDlApnAmbr indicates the downlink Aggregate
         Maximum Bit Rate (AMBR) of this Packet Data Network (PDN) context."
    ::= { tmnxMobServPdnContextEntry 6 }

tmnxMobServPcIpv4AddressType  OBJECT-TYPE
    SYNTAX      InetAddressType
    MAX-ACCESS  read-only
    STATUS      current
    DESCRIPTION
        "The value of tmnxMobServPcIpv4AddressType indicates the type of
         address represented by tmnxMobServPcIpv4Address."
    ::= { tmnxMobServPdnContextEntry 7 }

tmnxMobServPcIpv4Address  OBJECT-TYPE
    SYNTAX      InetAddress (SIZE (0|4))
    MAX-ACCESS  read-only
    STATUS      current
    DESCRIPTION
        "The value of tmnxMobServPcIpv4Address indicates the IPv4 address of
         the User Equipment (UE) in this Packet Data Network (PDN) context."
    ::= { tmnxMobServPdnContextEntry 8 }

tmnxMobServPcIpv6AddressType  OBJECT-TYPE
    SYNTAX      InetAddressType
    MAX-ACCESS  read-only
    STATUS      current
    DESCRIPTION
        "The value of tmnxMobServPcIpv6AddressType indicates the type of
         address represented by tmnxMobServPcIpv6Address."
    ::= { tmnxMobServPdnContextEntry 9 }

tmnxMobServPcIpv6Address  OBJECT-TYPE
    SYNTAX      InetAddress (SIZE (0|16))
    MAX-ACCESS  read-only
    STATUS      current
    DESCRIPTION
        "The value of tmnxMobServPcIpv6Address indicates the IPv6 address of
         the User Equipment (UE) in this Packet Data Network (PDN) context."
    ::= { tmnxMobServPdnContextEntry 10 }

tmnxMobServPcBearerContexts  OBJECT-TYPE
    SYNTAX      Unsigned32
    MAX-ACCESS  read-only
    STATUS      current
    DESCRIPTION
        "The value of tmnxMobServPcBearerContexts indicates the number of
         bearer contexts in this Packet Data Network (PDN) context."
    ::= { tmnxMobServPdnContextEntry 11 }

tmnxMobServPcSessionState  OBJECT-TYPE
    SYNTAX      TmnxMobPdnSessionState
    MAX-ACCESS  read-only
    STATUS      current
    DESCRIPTION
        "The value of tmnxMobServPcSessionState indicates the current
         feedback signaling message (FSM) state of this context."
    ::= { tmnxMobServPdnContextEntry 12 }

tmnxMobServPcLastEvent  OBJECT-TYPE
    SYNTAX      TmnxMobPdnSessionEvent
    MAX-ACCESS  read-only
    STATUS      current
    DESCRIPTION
        "The value of tmnxMobServPcLastEvent indicates the last
         feedback signaling message (FSM) event of this context."
    ::= { tmnxMobServPdnContextEntry 13 }

tmnxMobServPcS5S8SigProtocol  OBJECT-TYPE
    SYNTAX      TmnxMobPgwSigProtocol
    MAX-ACCESS  read-only
    STATUS      current
    DESCRIPTION
        "The value of tmnxMobServPcS5S8SigProtocol indicates the signaling
         protocol used on S5 or S8 reference point."
    ::= { tmnxMobServPdnContextEntry 14 }

tmnxMobServPcS5S8SgwCtrlTeid  OBJECT-TYPE
    SYNTAX      Unsigned32
    MAX-ACCESS  read-only
    STATUS      current
    DESCRIPTION
        "The value of tmnxMobServPcS5S8SgwCtrlTeid indicates the Serving Gateway
         (SGW) control plane Tunnel Endpoint Identifier (TEID) on S5 or S8
         reference point."
    ::= { tmnxMobServPdnContextEntry 15 }

tmnxMobServPcS5S8SgwCtrlAddrType  OBJECT-TYPE
    SYNTAX      InetAddressType
    MAX-ACCESS  read-only
    STATUS      current
    DESCRIPTION
        "The value of tmnxMobServPcS5S8SgwCtrlAddrType indicates the type of
         address represented by tmnxMobServPcS5S8SgwCtrlAddr."
    ::= { tmnxMobServPdnContextEntry 16 }

tmnxMobServPcS5S8SgwCtrlAddr  OBJECT-TYPE
    SYNTAX      InetAddress (SIZE (0|4))
    MAX-ACCESS  read-only
    STATUS      current
    DESCRIPTION
        "The value of tmnxMobServPcS5S8SgwCtrlAddr indicates the IPv4 address of
         the Serving Gateway (SGW) currently used for sending the control plane
         signaling on S5 or S8 reference point."
    ::= { tmnxMobServPdnContextEntry 17 }

tmnxMobServPcS5S8PgwCtrlTeid  OBJECT-TYPE
    SYNTAX      Unsigned32
    MAX-ACCESS  read-only
    STATUS      current
    DESCRIPTION
        "The value of tmnxMobServPcS5S8PgwCtrlTeid indicates the Packet Data
         Network Gateway (PGW) control plane Tunnel Endpoint Identifier (TEID)
         on S5 or S8 reference point."
    ::= { tmnxMobServPdnContextEntry 18 }

tmnxMobServPcS5S8PgwCtrlAddrType  OBJECT-TYPE
    SYNTAX      InetAddressType
    MAX-ACCESS  read-only
    STATUS      current
    DESCRIPTION
        "The value of tmnxMobServPcS5S8PgwCtrlAddrType indicates the type of
         address represented by tmnxMobServPcS5S8PgwCtrlAddr."
    ::= { tmnxMobServPdnContextEntry 19 }

tmnxMobServPcS5S8PgwCtrlAddr  OBJECT-TYPE
    SYNTAX      InetAddress (SIZE (0|4))
    MAX-ACCESS  read-only
    STATUS      current
    DESCRIPTION
        "The value of tmnxMobServPcS5S8PgwCtrlAddr indicates the IPv4 address of
         the Packet Data Network Gateway (PGW) currently used for sending the
         control plane signaling on S5 or S8 reference point."
    ::= { tmnxMobServPdnContextEntry 20 }

tmnxMobServPcRfServerAddrType  OBJECT-TYPE
    SYNTAX      InetAddressType
    MAX-ACCESS  read-only
    STATUS      current
    DESCRIPTION
        "The value of tmnxMobServPcRfServerAddrType indicates the type of
         address represented by tmnxMobServPcRfServerAddr.

         The value of this object is valid only if the value of
         tmnxMobServPcRfChargingLevel is equal to 'pdn'."
    ::= { tmnxMobServPdnContextEntry 21 }

tmnxMobServPcRfServerAddr  OBJECT-TYPE
    SYNTAX      InetAddress (SIZE (0|4|16))
    MAX-ACCESS  read-only
    STATUS      current
    DESCRIPTION
        "The value of tmnxMobServPcRfServerAddr indicates the charging server
         address on the Rf reference point.

         The value of this object is valid only if the value of
         tmnxMobServPcRfChargingLevel is equal to 'pdn'."
    ::= { tmnxMobServPdnContextEntry 22 }

tmnxMobServPcRfServerState  OBJECT-TYPE
    SYNTAX      TmnxMobServerState
    MAX-ACCESS  read-only
    STATUS      current
    DESCRIPTION
        "The value of tmnxMobServPcRfServerState indicates the charging server
         state on the Rf reference point.

         The value of this object is valid only if the value of
         tmnxMobServPcRfChargingLevel is equal to 'pdn'."
    ::= { tmnxMobServPdnContextEntry 23 }

tmnxMobServPcRfBearerType  OBJECT-TYPE
    SYNTAX      TmnxMobChargingBearerType
    MAX-ACCESS  read-only
    STATUS      current
    DESCRIPTION
        "The value of tmnxMobServPcRfBearerType indicates the bearer type used
         in charging on the Rf reference point."
    ::= { tmnxMobServPdnContextEntry 24 }

tmnxMobServPcRfChargingLevel  OBJECT-TYPE
    SYNTAX      TmnxMobChargingLevel
    MAX-ACCESS  read-only
    STATUS      current
    DESCRIPTION
        "The value of tmnxMobServPcRfChargingLevel indicates the charging level
         on the Rf reference point."
    ::= { tmnxMobServPdnContextEntry 25 }

tmnxMobServPcRfChargingProfile  OBJECT-TYPE
    SYNTAX      TmnxMobChargingProfile
    MAX-ACCESS  read-only
    STATUS      current
    DESCRIPTION
        "The value of tmnxMobServPcRfChargingProfile indicates the charging
         profile used on the Rf reference point.

         The value of this object is valid only if the value of
         tmnxMobServPcRfChargingLevel is equal to 'pdn'."
    ::= { tmnxMobServPdnContextEntry 26 }

tmnxMobServPcRfTriggeredRecords  OBJECT-TYPE
    SYNTAX      Counter32
    MAX-ACCESS  read-only
    STATUS      current
    DESCRIPTION
        "The value of tmnxMobServPcRfTriggeredRecords indicates the number of
         records generated by triggers on the Rf reference point.

         The value of this object is valid only if the value of
         tmnxMobServPcRfChargingLevel is equal to 'pdn'."
    ::= { tmnxMobServPdnContextEntry 27 }

tmnxMobServPcRfInterimRecords  OBJECT-TYPE
    SYNTAX      Counter32
    MAX-ACCESS  read-only
    STATUS      current
    DESCRIPTION
        "The value of tmnxMobServPcRfInterimRecords indicates the number of
         interim records sent on the Rf reference point.

         The value of this object is valid only if the value of
         tmnxMobServPcRfChargingLevel is equal to 'pdn'."
    ::= { tmnxMobServPdnContextEntry 28 }

tmnxMobServPcPcrfEventTriggers  OBJECT-TYPE
    SYNTAX      Unsigned32
    MAX-ACCESS  read-only
    STATUS      current
    DESCRIPTION
        "The value of tmnxMobServPcPcrfEventTriggers indicates the diameter
         policy control triggers."
    ::= { tmnxMobServPdnContextEntry 29 }

tmnxMobServPcGxcPcrfAddressType  OBJECT-TYPE
    SYNTAX      InetAddressType
    MAX-ACCESS  read-only
    STATUS      current
    DESCRIPTION
        "The value of tmnxMobServPcGxcPcrfAddressType indicates the type of
         address represented by tmnxMobServPcGxcPcrfAddress."
    ::= { tmnxMobServPdnContextEntry 30 }

tmnxMobServPcGxcPcrfAddress  OBJECT-TYPE
    SYNTAX      InetAddress (SIZE (0|4|16))
    MAX-ACCESS  read-only
    STATUS      current
    DESCRIPTION
        "The value of tmnxMobServPcGxcPcrfAddress indicates the Policy and
         Charging Rules Function (PCRF) IP address of the Gxc control plane."
    ::= { tmnxMobServPdnContextEntry 31 }

tmnxMobServPcGxcSgwAddressType  OBJECT-TYPE
    SYNTAX      InetAddressType
    MAX-ACCESS  read-only
    STATUS      current
    DESCRIPTION
        "The value of tmnxMobServPcGxcSgwAddressType indicates the type of
         address represented by tmnxMobServPcGxcSgwAddress."
    ::= { tmnxMobServPdnContextEntry 32 }

tmnxMobServPcGxcSgwAddress  OBJECT-TYPE
    SYNTAX      InetAddress (SIZE (0|4|16))
    MAX-ACCESS  read-only
    STATUS      current
    DESCRIPTION
        "The value of tmnxMobServPcGxcSgwAddress indicates the Serving Gateway
         (SGW) IP address of the Gxc control plane."
    ::= { tmnxMobServPdnContextEntry 33 }

tmnxMobServPcS5S8SgwGreKey  OBJECT-TYPE
    SYNTAX      Unsigned32
    MAX-ACCESS  read-only
    STATUS      current
    DESCRIPTION
        "The value of tmnxMobServPcS5S8SgwGreKey indicates the Generic Routing
         Encapsulation (GRE) key of the Serving Gateway (SGW) on S5 or S8
         reference point."
    ::= { tmnxMobServPdnContextEntry 34 }

tmnxMobServPcS5S8PgwGreKey  OBJECT-TYPE
    SYNTAX      Unsigned32
    MAX-ACCESS  read-only
    STATUS      current
    DESCRIPTION
        "The value of tmnxMobServPcS5S8PgwGreKey indicates the Generic Routing
         Encapsulation (GRE) key of the Packet Data Network Gateway (PGW) on
         S5 or S8 reference point."
    ::= { tmnxMobServPdnContextEntry 35 }

tmnxMobServPcS5S8PgwTrprtAdrType  OBJECT-TYPE
    SYNTAX      InetAddressType
    MAX-ACCESS  read-only
    STATUS      current
    DESCRIPTION
        "The value of tmnxMobServPcS5S8PgwTrprtAdrType indicates the type of
         address represented by tmnxMobServPcS5S8PgwTransprtAddr."
    ::= { tmnxMobServPdnContextEntry 36 }

tmnxMobServPcS5S8PgwTransprtAddr  OBJECT-TYPE
    SYNTAX      InetAddress (SIZE (0|4))
    MAX-ACCESS  read-only
    STATUS      current
    DESCRIPTION
        "The value of tmnxMobServPcS5S8PgwTransprtAddr indicates the Packet Data
         Network Gateway (PGW) transport address on S5 or S8 reference point."
    ::= { tmnxMobServPdnContextEntry 37 }

tmnxMobServPcS5S8SgwV6CtrlAdrTyp  OBJECT-TYPE
    SYNTAX      InetAddressType
    MAX-ACCESS  read-only
    STATUS      current
    DESCRIPTION
        "The value of tmnxMobServPcS5S8SgwV6CtrlAdrTyp indicates the type of
         address represented by tmnxMobServPcS5S8SgwV6CtrlAddr."
    ::= { tmnxMobServPdnContextEntry 38 }

tmnxMobServPcS5S8SgwV6CtrlAddr  OBJECT-TYPE
    SYNTAX      InetAddress (SIZE (0|16))
    MAX-ACCESS  read-only
    STATUS      current
    DESCRIPTION
        "The value of tmnxMobServPcS5S8SgwV6CtrlAddr indicates the IPv6 address
         of the Serving Gateway (SGW) currently used for sending the control
         plane signaling on S5 or S8 reference point."
    ::= { tmnxMobServPdnContextEntry 39 }

tmnxMobServPcS5S8PgwV6CtrlAdrTyp  OBJECT-TYPE
    SYNTAX      InetAddressType
    MAX-ACCESS  read-only
    STATUS      current
    DESCRIPTION
        "The value of tmnxMobServPcS5S8PgwV6CtrlAdrTyp indicates the type of
         address represented by tmnxMobServPcS5S8PgwV6CtrlAddr."
    ::= { tmnxMobServPdnContextEntry 40 }

tmnxMobServPcS5S8PgwV6CtrlAddr  OBJECT-TYPE
    SYNTAX      InetAddress (SIZE (0|16))
    MAX-ACCESS  read-only
    STATUS      current
    DESCRIPTION
        "The value of tmnxMobServPcS5S8PgwV6CtrlAddr indicates the IPv6 address
         of the Packet Data Network Gateway (PGW) currently used for sending the
         control plane signaling on S5 or S8 reference point."
    ::= { tmnxMobServPdnContextEntry 41 }

tmnxMobServPcAntiSpoofFailureCnt  OBJECT-TYPE
    SYNTAX      Counter32
    MAX-ACCESS  read-only
    STATUS      current
    DESCRIPTION
        "The value of tmnxMobServPcAntiSpoofFailureCnt indicates the number of
         anti-spoof validation failures."
    ::= { tmnxMobServPdnContextEntry 42 }

tmnxMobServPcImsiAuthStatus  OBJECT-TYPE
    SYNTAX      INTEGER {
                         notApplicable    (0),
                         authenticated    (1),
                         unauthenticated  (2)
                        }
    MAX-ACCESS  read-only
    STATUS      current
    DESCRIPTION
        "The value of tmnxMobServPcImsiAuthStatus indicates the
         authentication status for the International Mobile Subscriber
         Identity (IMSI) of this User Equipment (UE)."
    ::= { tmnxMobServPdnContextEntry 43 }

tmnxMobServPcImeiStr  OBJECT-TYPE
    SYNTAX      TmnxMobImei
    MAX-ACCESS  read-only
    STATUS      current
    DESCRIPTION
        "The value of tmnxMobServPcImeiStr indicates the International Mobile
         Equipment Identity (IMEI) of this User Equipment (UE)."
    ::= { tmnxMobServPdnContextEntry 44 }

tmnxMobServPcImsiStr  OBJECT-TYPE
    SYNTAX      TmnxMobImsiStr
    MAX-ACCESS  read-only
    STATUS      current
    DESCRIPTION
        "The value of tmnxMobServPcImsiStr indicates the International Mobile
         Subscriber Identity (IMSI) of this User Equipment (UE)."
    ::= { tmnxMobServPdnContextEntry 60 }

tmnxMobServPcRefPointType  OBJECT-TYPE
    SYNTAX      TmnxMobServRefPointType
    MAX-ACCESS  read-only
    STATUS      current
    DESCRIPTION
        "The value of tmnxMobServPcRefPointType indicates the reference point
         type for the session."
    ::= { tmnxMobServPdnContextEntry 61 }

--
--  Bearer Context Table
--

tmnxMobServBearerContextTable  OBJECT-TYPE
    SYNTAX      SEQUENCE OF TmnxMobServBearerContextEntry
    MAX-ACCESS  not-accessible
    STATUS      current
    DESCRIPTION
        "The tmnxMobServBearerContextTable has an entry for each bearer context
         of an User Equipment (UE)."
    ::= { tmnxMobServingStatObjs 5 }

tmnxMobServBearerContextEntry  OBJECT-TYPE
    SYNTAX      TmnxMobServBearerContextEntry
    MAX-ACCESS  not-accessible
    STATUS      current
    DESCRIPTION
        "Each row entry represents a bearer context of an User Equipment (UE)
         and contains identification, connection, statistics information."
    INDEX { tmnxMobGwId,
            tmnxMobServUeImsi,
            tmnxMobServPcApn,
            tmnxMobServPcPdnType,
            tmnxMobServBcBearerId
          }
    ::= { tmnxMobServBearerContextTable 1 }

TmnxMobServBearerContextEntry ::= SEQUENCE {
        tmnxMobServBcBearerId               TmnxMobBearerId,
        tmnxMobServBcBearerType             TmnxMobBearerType,
        tmnxMobServBcUpTime                 Unsigned32,
        tmnxMobServBcQci                    TmnxMobQci,
        tmnxMobServBcArp                    TmnxMobArp,
        tmnxMobServBcSdfs                   TmnxMobSdf,
        tmnxMobServBcFilters                TmnxMobSdfFilterNum,
        tmnxMobServBcQosUlMbr               Unsigned32,
        tmnxMobServBcQosDlMbr               Unsigned32,
        tmnxMobServBcQosUlGbr               Unsigned32,
        tmnxMobServBcQosDlGbr               Unsigned32,
        tmnxMobServBcS1uEnodebTeid          Unsigned32,
        tmnxMobServBcS1uEnodebAddrType      InetAddressType,
        tmnxMobServBcS1uEnodebAddr          InetAddress,
        tmnxMobServBcS1uSgwTeid             Unsigned32,
        tmnxMobServBcS1uSgwAddrType         InetAddressType,
        tmnxMobServBcS1uSgwAddr             InetAddress,
        tmnxMobServBcS5S8SgwTeid            Unsigned32,
        tmnxMobServBcS5S8SgwDataAddrType    InetAddressType,
        tmnxMobServBcS5S8SgwDataAddr        InetAddress,
        tmnxMobServBcS5S8PgwTeid            Unsigned32,
        tmnxMobServBcS5S8PgwDataAddrType    InetAddressType,
        tmnxMobServBcS5S8PgwDataAddr        InetAddress,
        tmnxMobServBcS11QosModifications    Counter32,
        tmnxMobServBcS5ULPackets            Counter64,
        tmnxMobServBcS5ULBytes              Counter64,
        tmnxMobServBcS1uDLPackets           Counter64,
        tmnxMobServBcS1uDLBytes             Counter64,
        tmnxMobServBcS5ULPacketsLow         Counter32,
        tmnxMobServBcS5ULPacketsHigh        Counter32,
        tmnxMobServBcS5ULBytesLow           Counter32,
        tmnxMobServBcS5ULBytesHigh          Counter32,
        tmnxMobServBcS1uDLPacketsLow        Counter32,
        tmnxMobServBcS1uDLPacketsHigh       Counter32,
        tmnxMobServBcS1uDLBytesLow          Counter32,
        tmnxMobServBcS1uDLBytesHigh         Counter32,
        tmnxMobServBcSetupLatencyTime       Unsigned32,
        tmnxMobServBcIndTnlRemTeid          Unsigned32,
        tmnxMobServBcIndTnlRemAddrType      InetAddressType,
        tmnxMobServBcIndTnlRemAddr          InetAddress,
        tmnxMobServBcIndTnlLocalTeid        Unsigned32,
        tmnxMobServBcIndTnlLocalAddrType    InetAddressType,
        tmnxMobServBcIndTnlLocalAddr        InetAddress,
        tmnxMobServBcRfServerAddrType       InetAddressType,
        tmnxMobServBcRfServerAddr           InetAddress,
        tmnxMobServBcRfServerState          TmnxMobServerState,
        tmnxMobServBcRfChargingProfile      TmnxMobChargingProfile,
        tmnxMobServBcRfTriggeredRecords     Counter32,
        tmnxMobServBcRfInterimRecords       Counter32,
        tmnxMobServBcRefPointType           TmnxMobServRefPointType
    }

tmnxMobServBcBearerId  OBJECT-TYPE
    SYNTAX      TmnxMobBearerId
    MAX-ACCESS  not-accessible
    STATUS      current
    DESCRIPTION
        "The value of tmnxMobServBcBearerId indicates the bearer id which
         uniquely identifies a bearer context in a Packet Data Network (PDN)
         context."
    ::= { tmnxMobServBearerContextEntry 1 }

tmnxMobServBcBearerType  OBJECT-TYPE
    SYNTAX      TmnxMobBearerType
    MAX-ACCESS  read-only
    STATUS      current
    DESCRIPTION
        "The value of tmnxMobServBcBearerType indicates the type of this
         bearer."
    ::= { tmnxMobServBearerContextEntry 2 }

tmnxMobServBcUpTime  OBJECT-TYPE
    SYNTAX      Unsigned32
    UNITS       "seconds"
    MAX-ACCESS  read-only
    STATUS      current
    DESCRIPTION
        "The value of tmnxMobServBcUpTime indicates the time, in seconds,
         since this bearer context was created."
    ::= { tmnxMobServBearerContextEntry 3 }

tmnxMobServBcQci  OBJECT-TYPE
    SYNTAX      TmnxMobQci
    MAX-ACCESS  read-only
    STATUS      current
    DESCRIPTION
        "The value of tmnxMobServBcQci indicates the Qos Class Identifier of
         this bearer context. The value of this object is used as a reference
         to access node-specific parameters that control bearer level packet
         forwarding treatment."
    ::= { tmnxMobServBearerContextEntry 4 }

tmnxMobServBcArp  OBJECT-TYPE
    SYNTAX      TmnxMobArp
    MAX-ACCESS  read-only
    STATUS      current
    DESCRIPTION
        "The value of tmnxMobServBcArp indicates the Allocation and Retention
         Priority (ARP) of this bearer context. The value of this object gives
         information about the priority level, the pre-emption capability and
         the pre-emption vulnerability."
    ::= { tmnxMobServBearerContextEntry 5 }

tmnxMobServBcSdfs  OBJECT-TYPE
    SYNTAX      TmnxMobSdf
    MAX-ACCESS  read-only
    STATUS      current
    DESCRIPTION
        "The value of tmnxMobServBcSdfs indicates the number of Service Data
         Flows (SDFs) in this bearer context."
    ::= { tmnxMobServBearerContextEntry 6 }

tmnxMobServBcFilters  OBJECT-TYPE
    SYNTAX      TmnxMobSdfFilterNum
    MAX-ACCESS  read-only
    STATUS      current
    DESCRIPTION
        "The value of tmnxMobServBcFilters indicates the number of IP filters
         in this bearer context."
    ::= { tmnxMobServBearerContextEntry 7 }

tmnxMobServBcQosUlMbr  OBJECT-TYPE
    SYNTAX      Unsigned32
    UNITS       "Kbps"
    MAX-ACCESS  read-only
    STATUS      current
    DESCRIPTION
        "The value of tmnxMobServBcQosUlMbr indicates the uplink Maximum
         Bit Rate (MBR) for this bearer."
    ::= { tmnxMobServBearerContextEntry 8 }

tmnxMobServBcQosDlMbr  OBJECT-TYPE
    SYNTAX      Unsigned32
    UNITS       "Kbps"
    MAX-ACCESS  read-only
    STATUS      current
    DESCRIPTION
        "The value of tmnxMobServBcQosDlMbr indicates the downlink Maximum
         Bit Rate (MBR) for this bearer."
    ::= { tmnxMobServBearerContextEntry 9 }

tmnxMobServBcQosUlGbr  OBJECT-TYPE
    SYNTAX      Unsigned32
    UNITS       "Kbps"
    MAX-ACCESS  read-only
    STATUS      current
    DESCRIPTION
        "The value of tmnxMobServBcQosUlGbr indicates the uplink Guaranteed
         Bit Rate (GBR) for this bearer."
    ::= { tmnxMobServBearerContextEntry 10 }

tmnxMobServBcQosDlGbr  OBJECT-TYPE
    SYNTAX      Unsigned32
    UNITS       "Kbps"
    MAX-ACCESS  read-only
    STATUS      current
    DESCRIPTION
        "The value of tmnxMobServBcQosDlGbr indicates the downlink
         Guaranteed Bit Rate (GBR) for this bearer."
    ::= { tmnxMobServBearerContextEntry 11 }

tmnxMobServBcS1uEnodebTeid  OBJECT-TYPE
    SYNTAX      Unsigned32
    MAX-ACCESS  read-only
    STATUS      current
    DESCRIPTION
        "The value of tmnxMobServBcS1uEnodebTeid indicates the Tunnel Endpoint
         Identifier (TEID) of the Evolved NodeB (eNodeB) on the S1-U
         reference point."
    ::= { tmnxMobServBearerContextEntry 12 }

tmnxMobServBcS1uEnodebAddrType  OBJECT-TYPE
    SYNTAX      InetAddressType
    MAX-ACCESS  read-only
    STATUS      current
    DESCRIPTION
        "The value of tmnxMobServBcS1uEnodebAddrType indicates the type of
         address represented by tmnxMobServBcS1uEnodebAddr."
    ::= { tmnxMobServBearerContextEntry 13 }

tmnxMobServBcS1uEnodebAddr  OBJECT-TYPE
    SYNTAX      InetAddress (SIZE (0|4|16))
    MAX-ACCESS  read-only
    STATUS      current
    DESCRIPTION
        "The value of tmnxMobServBcS1uEnodebAddr indicates the IP address of
         the Evolved NodeB (eNodeB) on the S1-U reference point."
    ::= { tmnxMobServBearerContextEntry 14 }

tmnxMobServBcS1uSgwTeid  OBJECT-TYPE
    SYNTAX      Unsigned32
    MAX-ACCESS  read-only
    STATUS      current
    DESCRIPTION
        "The value of tmnxMobServBcS1uSgwTeid indicates the Tunnel Endpoint
         Identifier (TEID) of the Serving Gateway (SGW) on S1-U reference
         point."
    ::= { tmnxMobServBearerContextEntry 15 }

tmnxMobServBcS1uSgwAddrType  OBJECT-TYPE
    SYNTAX      InetAddressType
    MAX-ACCESS  read-only
    STATUS      current
    DESCRIPTION
        "The value of tmnxMobServBcS1uSgwAddrType indicates the type of
         address represented by tmnxMobServBcS1uSgwAddr."
    ::= { tmnxMobServBearerContextEntry 16 }

tmnxMobServBcS1uSgwAddr  OBJECT-TYPE
    SYNTAX      InetAddress (SIZE (0|4|16))
    MAX-ACCESS  read-only
    STATUS      current
    DESCRIPTION
        "The value of tmnxMobServBcS1uSgwAddr indicates the IP address of
         the Serving Gateway (SGW) on S1-U reference point."
    ::= { tmnxMobServBearerContextEntry 17 }

tmnxMobServBcS5S8SgwTeid  OBJECT-TYPE
    SYNTAX      Unsigned32
    MAX-ACCESS  read-only
    STATUS      current
    DESCRIPTION
        "The value of tmnxMobServBcS5S8SgwTeid indicates the Tunnel Endpoint
         Identifier (TEID) of the Serving Gateway (SGW) on the S5 or S8
         reference point."
    ::= { tmnxMobServBearerContextEntry 18 }

tmnxMobServBcS5S8SgwDataAddrType  OBJECT-TYPE
    SYNTAX      InetAddressType
    MAX-ACCESS  read-only
    STATUS      current
    DESCRIPTION
        "The value of tmnxMobServBcS5S8SgwDataAddrType indicates the type of
         address represented by tmnxMobServBcS5S8SgwDataAddr."
    ::= { tmnxMobServBearerContextEntry 19 }

tmnxMobServBcS5S8SgwDataAddr  OBJECT-TYPE
    SYNTAX      InetAddress (SIZE (0|4|16))
    MAX-ACCESS  read-only
    STATUS      current
    DESCRIPTION
        "The value of tmnxMobServBcS5S8SgwDataAddr indicates the IP address of
         the Serving Gateway (SGW) on the S5 or S8 reference point."
    ::= { tmnxMobServBearerContextEntry 20 }

tmnxMobServBcS5S8PgwTeid  OBJECT-TYPE
    SYNTAX      Unsigned32
    MAX-ACCESS  read-only
    STATUS      current
    DESCRIPTION
        "The value of tmnxMobServBcS5S8PgwTeid indicates the Tunnel Endpoint
         Identifier (TEID) of the Packet Data Network Gateway (PGW) on the S5
         or S8 reference point."
    ::= { tmnxMobServBearerContextEntry 21 }

tmnxMobServBcS5S8PgwDataAddrType  OBJECT-TYPE
    SYNTAX      InetAddressType
    MAX-ACCESS  read-only
    STATUS      current
    DESCRIPTION
        "The value of tmnxMobServBcS5S8PgwDataAddrType indicates the type of
         address represented by tmnxMobServBcS5S8PgwDataAddr."
    ::= { tmnxMobServBearerContextEntry 22 }

tmnxMobServBcS5S8PgwDataAddr  OBJECT-TYPE
    SYNTAX      InetAddress (SIZE (0|4|16))
    MAX-ACCESS  read-only
    STATUS      current
    DESCRIPTION
        "The value of tmnxMobServBcS5S8PgwDataAddr indicates the IP address of
         the Packet Data Network Gateway (PGW) on the S5 or S8 reference point."
    ::= { tmnxMobServBearerContextEntry 23 }

tmnxMobServBcS11QosModifications  OBJECT-TYPE
    SYNTAX      Counter32
    MAX-ACCESS  read-only
    STATUS      current
    DESCRIPTION
        "The value of tmnxMobServBcS11QosModifications indicates the number of
         S11 QoS modifications."
    ::= { tmnxMobServBearerContextEntry 24 }

tmnxMobServBcS5ULPackets  OBJECT-TYPE
    SYNTAX      Counter64
    MAX-ACCESS  read-only
    STATUS      current
    DESCRIPTION
        "The value of tmnxMobServBcS5ULPackets indicates the number of
         S5 uplink packets."
    ::= { tmnxMobServBearerContextEntry 25 }

tmnxMobServBcS5ULBytes  OBJECT-TYPE
    SYNTAX      Counter64
    MAX-ACCESS  read-only
    STATUS      current
    DESCRIPTION
        "The value of tmnxMobServBcS5ULBytes indicates the number of
         S5 uplink bytes."
    ::= { tmnxMobServBearerContextEntry 26 }

tmnxMobServBcS1uDLPackets  OBJECT-TYPE
    SYNTAX      Counter64
    MAX-ACCESS  read-only
    STATUS      current
    DESCRIPTION
        "The value of tmnxMobServBcS1uDLPackets indicates the number of
         S1-U downlink packets."
    ::= { tmnxMobServBearerContextEntry 27 }

tmnxMobServBcS1uDLBytes  OBJECT-TYPE
    SYNTAX      Counter64
    MAX-ACCESS  read-only
    STATUS      current
    DESCRIPTION
        "The value of tmnxMobServBcS1uDLBytes indicates the number of
         S1-U downlink bytes."
    ::= { tmnxMobServBearerContextEntry 28 }

tmnxMobServBcS5ULPacketsLow  OBJECT-TYPE
    SYNTAX      Counter32
    MAX-ACCESS  read-only
    STATUS      current
    DESCRIPTION
        "The value of tmnxMobServBcS5ULPacketsLow indicates the lower 32 bits
         of the value of tmnxMobServBcS5ULPackets."
    ::= { tmnxMobServBearerContextEntry 29 }

tmnxMobServBcS5ULPacketsHigh  OBJECT-TYPE
    SYNTAX      Counter32
    MAX-ACCESS  read-only
    STATUS      current
    DESCRIPTION
        "The value of tmnxMobServBcS5ULPacketsHigh indicates the higher 32
         bits of the value of tmnxMobServBcS5ULPackets."
    ::= { tmnxMobServBearerContextEntry 30 }

tmnxMobServBcS5ULBytesLow  OBJECT-TYPE
    SYNTAX      Counter32
    MAX-ACCESS  read-only
    STATUS      current
    DESCRIPTION
        "The value of tmnxMobServBcS5ULBytesLow indicates the lower 32 bits
         of the value of tmnxMobServBcS5ULBytes."
    ::= { tmnxMobServBearerContextEntry 31 }

tmnxMobServBcS5ULBytesHigh  OBJECT-TYPE
    SYNTAX      Counter32
    MAX-ACCESS  read-only
    STATUS      current
    DESCRIPTION
        "The value of tmnxMobServBcS5ULBytesHigh indicates the higher 32
         bits of the value of tmnxMobServBcS5ULBytes."
    ::= { tmnxMobServBearerContextEntry 32 }

tmnxMobServBcS1uDLPacketsLow  OBJECT-TYPE
    SYNTAX      Counter32
    MAX-ACCESS  read-only
    STATUS      current
    DESCRIPTION
        "The value of tmnxMobServBcS1uDLPacketsLow indicates the lower 32 bits
         of the value of tmnxMobServBcS1uDLPackets."
    ::= { tmnxMobServBearerContextEntry 33 }

tmnxMobServBcS1uDLPacketsHigh  OBJECT-TYPE
    SYNTAX      Counter32
    MAX-ACCESS  read-only
    STATUS      current
    DESCRIPTION
        "The value of tmnxMobServBcS1uDLPacketsHigh indicates the higher 32
         bits of the value of tmnxMobServBcS1uDLPackets."
    ::= { tmnxMobServBearerContextEntry 34 }

tmnxMobServBcS1uDLBytesLow  OBJECT-TYPE
    SYNTAX      Counter32
    MAX-ACCESS  read-only
    STATUS      current
    DESCRIPTION
        "The value of tmnxMobServBcS1uDLBytesLow indicates the lower 32 bits
         of the value of tmnxMobServBcS1uDLBytes."
    ::= { tmnxMobServBearerContextEntry 35 }

tmnxMobServBcS1uDLBytesHigh  OBJECT-TYPE
    SYNTAX      Counter32
    MAX-ACCESS  read-only
    STATUS      current
    DESCRIPTION
        "The value of tmnxMobServBcS1uDLBytesHigh indicates the higher 32
         bits of the value of tmnxMobServBcS1uDLBytes."
    ::= { tmnxMobServBearerContextEntry 36 }

tmnxMobServBcSetupLatencyTime  OBJECT-TYPE
    SYNTAX      Unsigned32
    UNITS       "milliseconds"
    MAX-ACCESS  read-only
    STATUS      current
    DESCRIPTION
        "The value of tmnxMobServBcSetupLatencyTime indicates the setup
         latency time in this bearer context."
    ::= { tmnxMobServBearerContextEntry 37 }

tmnxMobServBcIndTnlRemTeid  OBJECT-TYPE
    SYNTAX      Unsigned32
    MAX-ACCESS  read-only
    STATUS      current
    DESCRIPTION
        "The value of tmnxMobServBcIndTnlRemTeid indicates the Tunnel Endpoint
         Identifier (TEID) of the far end in the indirect tunnel created during
         S1 handover."
    ::= { tmnxMobServBearerContextEntry 38 }

tmnxMobServBcIndTnlRemAddrType  OBJECT-TYPE
    SYNTAX      InetAddressType
    MAX-ACCESS  read-only
    STATUS      current
    DESCRIPTION
        "The value of tmnxMobServBcIndTnlRemAddrType indicates the type of
         address represented by tmnxMobServBcIndTnlRemAddr."
    ::= { tmnxMobServBearerContextEntry 39 }

tmnxMobServBcIndTnlRemAddr  OBJECT-TYPE
    SYNTAX      InetAddress (SIZE (0|4|16))
    MAX-ACCESS  read-only
    STATUS      current
    DESCRIPTION
        "The value of tmnxMobServBcIndTnlRemAddr indicates the IP address of
         the far end in the indirect tunnel created during S1 handover."
    ::= { tmnxMobServBearerContextEntry 40 }

tmnxMobServBcIndTnlLocalTeid  OBJECT-TYPE
    SYNTAX      Unsigned32
    MAX-ACCESS  read-only
    STATUS      current
    DESCRIPTION
        "The value of tmnxMobServBcIndTnlLocalTeid indicates the Tunnel Endpoint
         Identifier (TEID) of the local endpoint in the indirect
         tunnel created during S1 handover."
    ::= { tmnxMobServBearerContextEntry 41 }

tmnxMobServBcIndTnlLocalAddrType  OBJECT-TYPE
    SYNTAX      InetAddressType
    MAX-ACCESS  read-only
    STATUS      current
    DESCRIPTION
        "The value of tmnxMobServBcIndTnlLocalAddrType indicates the type of
         address represented by tmnxMobServBcIndTnlLocalAddr."
    ::= { tmnxMobServBearerContextEntry 42 }

tmnxMobServBcIndTnlLocalAddr  OBJECT-TYPE
    SYNTAX      InetAddress (SIZE (0|4|16))
    MAX-ACCESS  read-only
    STATUS      current
    DESCRIPTION
        "The value of tmnxMobServBcIndTnlLocalAddr indicates the IP address of
         the local endpoint in the indirect tunnel created during S1 handover."
    ::= { tmnxMobServBearerContextEntry 43 }

tmnxMobServBcRfServerAddrType  OBJECT-TYPE
    SYNTAX      InetAddressType
    MAX-ACCESS  read-only
    STATUS      current
    DESCRIPTION
        "The value of tmnxMobServBcRfServerAddrType indicates the type of
         address represented by tmnxMobServBcRfServerAddr.

         The value of this object is valid only if the value of
         tmnxMobServPcRfChargingLevel is equal to 'bearer'."
    ::= { tmnxMobServBearerContextEntry 44 }

tmnxMobServBcRfServerAddr  OBJECT-TYPE
    SYNTAX      InetAddress (SIZE (0|4|16))
    MAX-ACCESS  read-only
    STATUS      current
    DESCRIPTION
        "The value of tmnxMobServBcRfServerAddr indicates the charging server
         address on the Rf reference point.

         The value of this object is valid only if the value of
         tmnxMobServPcRfChargingLevel is equal to 'bearer'."
    ::= { tmnxMobServBearerContextEntry 45 }

tmnxMobServBcRfServerState  OBJECT-TYPE
    SYNTAX      TmnxMobServerState
    MAX-ACCESS  read-only
    STATUS      current
    DESCRIPTION
        "The value of tmnxMobServBcRfServerState indicates the charging server
         state on the Rf reference point.

         The value of this object is valid only if the value of
         tmnxMobServPcRfChargingLevel is equal to 'bearer'."
    ::= { tmnxMobServBearerContextEntry 46 }

tmnxMobServBcRfChargingProfile  OBJECT-TYPE
    SYNTAX      TmnxMobChargingProfile
    MAX-ACCESS  read-only
    STATUS      current
    DESCRIPTION
        "The value of tmnxMobServBcRfChargingProfile indicates the charging
         profile used on the Rf reference point.

         The value of this object is valid only if the value of
         tmnxMobServPcRfChargingLevel is equal to 'bearer'."
    ::= { tmnxMobServBearerContextEntry 47 }

tmnxMobServBcRfTriggeredRecords  OBJECT-TYPE
    SYNTAX      Counter32
    MAX-ACCESS  read-only
    STATUS      current
    DESCRIPTION
        "The value of tmnxMobServBcRfTriggeredRecords indicates the number of
         records generated by triggers on the Rf reference point.

         The value of this object is valid only if the value of
         tmnxMobServPcRfChargingLevel is equal to 'bearer'."
    ::= { tmnxMobServBearerContextEntry 48 }

tmnxMobServBcRfInterimRecords  OBJECT-TYPE
    SYNTAX      Counter32
    MAX-ACCESS  read-only
    STATUS      current
    DESCRIPTION
        "The value of tmnxMobServBcRfInterimRecords indicates the number of
         interim records sent on the Rf reference point.

         The value of this object is valid only if the value of
         tmnxMobServPcRfChargingLevel is equal to 'bearer'."
    ::= { tmnxMobServBearerContextEntry 49 }

tmnxMobServBcRefPointType  OBJECT-TYPE
    SYNTAX      TmnxMobServRefPointType
    MAX-ACCESS  read-only
    STATUS      current
    DESCRIPTION
        "The value of tmnxMobServBcRefPointType indicates the reference point
         type for the bearer context of an User Equipment (UE)."
    ::= { tmnxMobServBearerContextEntry 50 }

--
--  Bearer Context SDF Table
--

tmnxMobServBcSdfTable  OBJECT-TYPE
    SYNTAX      SEQUENCE OF TmnxMobServBcSdfEntry
    MAX-ACCESS  not-accessible
    STATUS      current
    DESCRIPTION
        "The tmnxMobServBcSdfTable has an entry for each Service Data
         Flow mapped to a bearer of a User Equipment (UE).

        Entries will be created in this table only when the value of
        tmnxMobServPcS5S8SigProtocol is equal to 'pmip'."
    ::= { tmnxMobServingStatObjs 6 }

tmnxMobServBcSdfEntry  OBJECT-TYPE
    SYNTAX      TmnxMobServBcSdfEntry
    MAX-ACCESS  not-accessible
    STATUS      current
    DESCRIPTION
        "Each row entry represents an Service Data Flow (SDF). Service Data
         Flows are defined by the Policy and Charging Rules Function (PCRF)."
    INDEX { tmnxMobGwId,
            tmnxMobServUeImsi,
            tmnxMobServPcApn,
            tmnxMobServPcPdnType,
            tmnxMobServBcBearerId,
            tmnxMobServBcSdfPrecedence
          }
    ::= { tmnxMobServBcSdfTable 1 }

TmnxMobServBcSdfEntry ::= SEQUENCE {
        tmnxMobServBcSdfPrecedence          Unsigned32,
        tmnxMobServBcSdfPcrfPrecedence      Unsigned32,
        tmnxMobServBcSdfRuleName            TmnxMobSdfRuleName,
        tmnxMobServBcSdfPacketFilters       Unsigned32,
        tmnxMobServBcSdfQosUlMbr            Unsigned32,
        tmnxMobServBcSdfQosDlMbr            Unsigned32,
        tmnxMobServBcSdfQosUlGbr            Unsigned32,
        tmnxMobServBcSdfQosDlGbr            Unsigned32
    }

tmnxMobServBcSdfPrecedence  OBJECT-TYPE
    SYNTAX      Unsigned32 (0..65535)
    MAX-ACCESS  not-accessible
    STATUS      current
    DESCRIPTION
        "The value of tmnxMobServBcSdfPrecedence indicates the internally
         mapped value of rule precedence of this Service Data Flow (SDF)."
    ::= { tmnxMobServBcSdfEntry 1 }

tmnxMobServBcSdfPcrfPrecedence  OBJECT-TYPE
    SYNTAX      Unsigned32
    MAX-ACCESS  read-only
    STATUS      current
    DESCRIPTION
        "The value of tmnxMobServBcSdfPcrfPrecedence indicates the rule
         precedence of this Service Data Flow (SDF) received from the Policy
         and Charging Rules Function (PCRF)."
    ::= { tmnxMobServBcSdfEntry 2 }

tmnxMobServBcSdfRuleName  OBJECT-TYPE
    SYNTAX      TmnxMobSdfRuleName
    MAX-ACCESS  read-only
    STATUS      current
    DESCRIPTION
        "The value of tmnxMobServBcSdfRuleName indicates the policy rule name
         of this Service Data Flow (SDF). Rule name is unique within an IP-CAN
         session."
    ::= { tmnxMobServBcSdfEntry 3 }

tmnxMobServBcSdfPacketFilters  OBJECT-TYPE
    SYNTAX      Unsigned32
    MAX-ACCESS  read-only
    STATUS      current
    DESCRIPTION
        "The value of tmnxMobServBcSdfPacketFilters indicates the number of
         packet filters in this Service Data Flow (SDF)."
    ::= { tmnxMobServBcSdfEntry 4 }

tmnxMobServBcSdfQosUlMbr  OBJECT-TYPE
    SYNTAX      Unsigned32
    UNITS       "Kbps"
    MAX-ACCESS  read-only
    STATUS      current
    DESCRIPTION
        "The value of tmnxMobServBcSdfQosUlMbr indicates the uplink Maximum
         Bit Rate (MBR) included within the rule."
    ::= { tmnxMobServBcSdfEntry 5 }

tmnxMobServBcSdfQosDlMbr  OBJECT-TYPE
    SYNTAX      Unsigned32
    UNITS       "Kbps"
    MAX-ACCESS  read-only
    STATUS      current
    DESCRIPTION
        "The value of tmnxMobServBcSdfQosDlMbr indicates the downlink Maximum
         Bit Rate (MBR) included within the rule."
    ::= { tmnxMobServBcSdfEntry 6 }

tmnxMobServBcSdfQosUlGbr  OBJECT-TYPE
    SYNTAX      Unsigned32
    UNITS       "Kbps"
    MAX-ACCESS  read-only
    STATUS      current
    DESCRIPTION
        "The value of tmnxMobServBcSdfQosUlGbr indicates the uplink Guaranteed
         Bit Rate (GBR) included within the rule."
    ::= { tmnxMobServBcSdfEntry 7 }

tmnxMobServBcSdfQosDlGbr  OBJECT-TYPE
    SYNTAX      Unsigned32
    UNITS       "Kbps"
    MAX-ACCESS  read-only
    STATUS      current
    DESCRIPTION
        "The value of tmnxMobServBcSdfQosDlGbr indicates the downlink
         Guaranteed Bit Rate (GBR) included within the rule."
    ::= { tmnxMobServBcSdfEntry 8 }

--
--  Bearer Context SDF IP Packet Filter Table
--

tmnxMobServBcSdfFilterTable  OBJECT-TYPE
    SYNTAX      SEQUENCE OF TmnxMobServBcSdfFilterEntry
    MAX-ACCESS  not-accessible
    STATUS      current
    DESCRIPTION
        "The tmnxMobServBcSdfFilterTable has an entry for each IP filter rule
         defined in a Service Data Flow (SDF).

         Entries will be created in this table only when the value of
         tmnxMobServPcS5S8SigProtocol is equal to 'pmip'."
    ::= { tmnxMobServingStatObjs 7 }

tmnxMobServBcSdfFilterEntry  OBJECT-TYPE
    SYNTAX      TmnxMobServBcSdfFilterEntry
    MAX-ACCESS  not-accessible
    STATUS      current
    DESCRIPTION
        "Each row entry represents an IP filter rule defined in a Service Data
         Flow (SDF)."
    INDEX { tmnxMobGwId,
            tmnxMobServUeImsi,
            tmnxMobServPcApn,
            tmnxMobServPcPdnType,
            tmnxMobServBcBearerId,
            tmnxMobServBcSdfPrecedence,
            tmnxMobServBcSdfFilterDirection,
            tmnxMobServBcSdfFilterId
          }
    ::= { tmnxMobServBcSdfFilterTable 1 }

TmnxMobServBcSdfFilterEntry ::= SEQUENCE {
        tmnxMobServBcSdfFilterDirection     TmnxMobSdfFilterDirection,
        tmnxMobServBcSdfFilterId            TmnxMobSdfFilter,
        tmnxMobServBcSdfFilterProtocol      TmnxMobSdfFilterProtocol,
        tmnxMobServBcSdfFilterSrcAdrType    InetAddressType,
        tmnxMobServBcSdfFilterSrcAddr       InetAddress,
        tmnxMobServBcSdfFilterSrcPfxLen     InetAddressPrefixLength,
        tmnxMobServBcSdfFilterDstAdrType    InetAddressType,
        tmnxMobServBcSdfFilterDestAddr      InetAddress,
        tmnxMobServBcSdfFilterDestPfxLen    InetAddressPrefixLength,
        tmnxMobServBcSdfFilterSrcPorts      Unsigned32,
        tmnxMobServBcSdfFilterDestPorts     Unsigned32,
        tmnxMobServBcSdfFirstSrcPortOper    TTcpUdpPortOperator,
        tmnxMobServBcSdfFirstSrcPortVal1    TTcpUdpPort,
        tmnxMobServBcSdfFirstSrcPortVal2    TTcpUdpPort,
        tmnxMobServBcSdfSecndSrcPortOper    TTcpUdpPortOperator,
        tmnxMobServBcSdfSecndSrcPortVal1    TTcpUdpPort,
        tmnxMobServBcSdfSecndSrcPortVal2    TTcpUdpPort,
        tmnxMobServBcSdfFirstDstPortOper    TTcpUdpPortOperator,
        tmnxMobServBcSdfFirstDstPortVal1    TTcpUdpPort,
        tmnxMobServBcSdfFirstDstPortVal2    TTcpUdpPort,
        tmnxMobServBcSdfSecndDstPortOper    TTcpUdpPortOperator,
        tmnxMobServBcSdfSecndDstPortVal1    TTcpUdpPort,
        tmnxMobServBcSdfSecndDstPortVal2    TTcpUdpPort
    }

tmnxMobServBcSdfFilterDirection  OBJECT-TYPE
    SYNTAX      TmnxMobSdfFilterDirection
    MAX-ACCESS  not-accessible
    STATUS      current
    DESCRIPTION
        "The value of tmnxMobServBcSdfFilterDirection indicates the direction
         on which this filter rule is valid."
    ::= { tmnxMobServBcSdfFilterEntry 1 }

tmnxMobServBcSdfFilterId  OBJECT-TYPE
    SYNTAX      TmnxMobSdfFilter
    MAX-ACCESS  not-accessible
    STATUS      current
    DESCRIPTION
        "The value of tmnxMobServBcSdfFilterId indicates the unique value which
         identifies a filter rule in the Service Data Flow (SDF)."
    ::= { tmnxMobServBcSdfFilterEntry 2 }

tmnxMobServBcSdfFilterProtocol  OBJECT-TYPE
    SYNTAX      TmnxMobSdfFilterProtocol
    MAX-ACCESS  read-only
    STATUS      current
    DESCRIPTION
        "The value of tmnxMobServBcSdfFilterProtocol indicates the IPv4 protocol
         or IPv6 next header on which this filter matches.

         If the value of this object is set to 'any', then this filter matches
         any protocol field."
    ::= { tmnxMobServBcSdfFilterEntry 3 }

tmnxMobServBcSdfFilterSrcAdrType  OBJECT-TYPE
    SYNTAX      InetAddressType
    MAX-ACCESS  read-only
    STATUS      current
    DESCRIPTION
        "The value of tmnxMobServBcSdfFilterSrcAdrType indicates the type of
         address represented by tmnxMobServBcSdfFilterSrcAddr."
    ::= { tmnxMobServBcSdfFilterEntry 4 }

tmnxMobServBcSdfFilterSrcAddr  OBJECT-TYPE
    SYNTAX      InetAddress (SIZE (0|4|16))
    MAX-ACCESS  read-only
    STATUS      current
    DESCRIPTION
        "The value of tmnxMobServBcSdfFilterSrcAddr indicates the IP address
         of the source on which this filter rule is valid."
    ::= { tmnxMobServBcSdfFilterEntry 5 }

tmnxMobServBcSdfFilterSrcPfxLen  OBJECT-TYPE
    SYNTAX      InetAddressPrefixLength
    MAX-ACCESS  read-only
    STATUS      current
    DESCRIPTION
        "The value of tmnxMobServBcSdfFilterSrcPfxLen indicates the prefix
         mask length of tmnxMobServBcSdfFilterSrcAddr."
    ::= { tmnxMobServBcSdfFilterEntry 6 }

tmnxMobServBcSdfFilterDstAdrType  OBJECT-TYPE
    SYNTAX      InetAddressType
    MAX-ACCESS  read-only
    STATUS      current
    DESCRIPTION
        "The value of tmnxMobServBcSdfFilterDstAdrType indicates the type of
         address represented by tmnxMobServBcSdfFilterDestAddr."
    ::= { tmnxMobServBcSdfFilterEntry 7 }

tmnxMobServBcSdfFilterDestAddr  OBJECT-TYPE
    SYNTAX      InetAddress (SIZE (0|4|16))
    MAX-ACCESS  read-only
    STATUS      current
    DESCRIPTION
        "The value of tmnxMobServBcSdfFilterDestAddr indicates the IP address
         of the destination on which this filter rule is valid."
    ::= { tmnxMobServBcSdfFilterEntry 8 }

tmnxMobServBcSdfFilterDestPfxLen  OBJECT-TYPE
    SYNTAX      InetAddressPrefixLength
    MAX-ACCESS  read-only
    STATUS      current
    DESCRIPTION
        "The value of tmnxMobServBcSdfFilterDestPfxLen indicates the prefix
         mask length of tmnxMobServBcSdfFilterDestPfxLen."
    ::= { tmnxMobServBcSdfFilterEntry 9 }

tmnxMobServBcSdfFilterSrcPorts  OBJECT-TYPE
    SYNTAX      Unsigned32
    MAX-ACCESS  read-only
    STATUS      current
    DESCRIPTION
        "The value of tmnxMobServBcSdfFilterSrcPorts indicates the number of
         source ports."
    ::= { tmnxMobServBcSdfFilterEntry 10 }

tmnxMobServBcSdfFilterDestPorts  OBJECT-TYPE
    SYNTAX      Unsigned32
    MAX-ACCESS  read-only
    STATUS      current
    DESCRIPTION
        "The value of tmnxMobServBcSdfFilterDestPorts indicates the number of
         destination ports."
    ::= { tmnxMobServBcSdfFilterEntry 11 }

tmnxMobServBcSdfFirstSrcPortOper  OBJECT-TYPE
    SYNTAX      TTcpUdpPortOperator
    MAX-ACCESS  read-only
    STATUS      current
    DESCRIPTION
        "The value of tmnxMobServBcSdfFirstSrcPortOper indicates the manner in
         which tmnxMobServBcSdfFirstSrcPortVal1 and
         tmnxMobServBcSdfFirstSrcPortVal2 are to be used. The values of these
         three objects are used as described in TTcpUdpPortOperator."
    ::= { tmnxMobServBcSdfFilterEntry 12 }

tmnxMobServBcSdfFirstSrcPortVal1  OBJECT-TYPE
    SYNTAX      TTcpUdpPort
    MAX-ACCESS  read-only
    STATUS      current
    DESCRIPTION
        "The value of tmnxMobServBcSdfFirstSrcPortVal1 indicates the TCP or UDP
         starting destination port. The value of this object is used as per the
         description for tmnxMobServBcSdfFirstSrcPortOper."
    ::= { tmnxMobServBcSdfFilterEntry 13 }

tmnxMobServBcSdfFirstSrcPortVal2  OBJECT-TYPE
    SYNTAX      TTcpUdpPort
    MAX-ACCESS  read-only
    STATUS      current
    DESCRIPTION
        "The value of tmnxMobServBcSdfFirstSrcPortVal2 indicates the TCP or UDP
         starting destination port. The value of this object is used as per the
         description for tmnxMobServBcSdfFirstSrcPortOper."
    ::= { tmnxMobServBcSdfFilterEntry 14 }

tmnxMobServBcSdfSecndSrcPortOper  OBJECT-TYPE
    SYNTAX      TTcpUdpPortOperator
    MAX-ACCESS  read-only
    STATUS      current
    DESCRIPTION
        "The value of tmnxMobServBcSdfSecndSrcPortOper indicates the manner in
         which tmnxMobServBcSdfSecndSrcPortVal2 and
         tmnxMobServBcSdfFirstSrcPortVal2 are to be used. The values of these
         three objects are used as described in TTcpUdpPortOperator."
    ::= { tmnxMobServBcSdfFilterEntry 15 }

tmnxMobServBcSdfSecndSrcPortVal1  OBJECT-TYPE
    SYNTAX      TTcpUdpPort
    MAX-ACCESS  read-only
    STATUS      current
    DESCRIPTION
        "The value of tmnxMobServBcSdfSecndSrcPortVal1 indicates the TCP or UDP
         starting destination port. The value of this object is used as per the
         description for tmnxMobServBcSdfSecndSrcPortOper."
    ::= { tmnxMobServBcSdfFilterEntry 16 }

tmnxMobServBcSdfSecndSrcPortVal2  OBJECT-TYPE
    SYNTAX      TTcpUdpPort
    MAX-ACCESS  read-only
    STATUS      current
    DESCRIPTION
        "The value of tmnxMobServBcSdfSecndSrcPortVal2 indicates the TCP or UDP
         starting destination port. The value of this object is used as per the
         description for tmnxMobServBcSdfSecndSrcPortOper."
    ::= { tmnxMobServBcSdfFilterEntry 17 }

tmnxMobServBcSdfFirstDstPortOper  OBJECT-TYPE
    SYNTAX      TTcpUdpPortOperator
    MAX-ACCESS  read-only
    STATUS      current
    DESCRIPTION
        "The value of tmnxMobServBcSdfFirstDstPortOper indicates the manner in
         which tmnxMobServBcSdfFirstDstPortVal1 and
         tmnxMobServBcSdfFirstDstPortVal2 are to be used. The values of these
         three objects are used as described in TTcpUdpPortOperator."
    ::= { tmnxMobServBcSdfFilterEntry 18 }

tmnxMobServBcSdfFirstDstPortVal1  OBJECT-TYPE
    SYNTAX      TTcpUdpPort
    MAX-ACCESS  read-only
    STATUS      current
    DESCRIPTION
        "The value of tmnxMobServBcSdfFirstDstPortVal1 indicates the TCP or UDP
         starting destination port. The value of this object is used as per the
         description for tmnxMobServBcSdfFirstDstPortOper."
    ::= { tmnxMobServBcSdfFilterEntry 19 }

tmnxMobServBcSdfFirstDstPortVal2  OBJECT-TYPE
    SYNTAX      TTcpUdpPort
    MAX-ACCESS  read-only
    STATUS      current
    DESCRIPTION
        "The value of tmnxMobServBcSdfFirstDstPortVal2 indicates the TCP or UDP
         starting destination port. The value of this object is used as per the
         description for tmnxMobServBcSdfFirstDstPortOper."
    ::= { tmnxMobServBcSdfFilterEntry 20 }

tmnxMobServBcSdfSecndDstPortOper  OBJECT-TYPE
    SYNTAX      TTcpUdpPortOperator
    MAX-ACCESS  read-only
    STATUS      current
    DESCRIPTION
        "The value of tmnxMobServBcSdfSecndDstPortOper indicates the manner in
         which tmnxMobServBcSdfSecndDstPortVal1 and
         tmnxMobServBcSdfSecndDstPortVal2 are to be used. The values of these
         three objects are used as described in TTcpUdpPortOperator."
    ::= { tmnxMobServBcSdfFilterEntry 21 }

tmnxMobServBcSdfSecndDstPortVal1  OBJECT-TYPE
    SYNTAX      TTcpUdpPort
    MAX-ACCESS  read-only
    STATUS      current
    DESCRIPTION
        "The value of tmnxMobServBcSdfSecndDstPortVal1 indicates the TCP or UDP
         starting destination port. The value of this object is used as per the
         description for tmnxMobServBcSdfSecndDstPortOper."
    ::= { tmnxMobServBcSdfFilterEntry 22 }

tmnxMobServBcSdfSecndDstPortVal2  OBJECT-TYPE
    SYNTAX      TTcpUdpPort
    MAX-ACCESS  read-only
    STATUS      current
    DESCRIPTION
        "The value of tmnxMobServBcSdfSecndDstPortVal2 indicates the TCP or UDP
         starting destination port. The value of this object is used as per the
         description for tmnxMobServBcSdfSecndDstPortOper."
    ::= { tmnxMobServBcSdfFilterEntry 23 }

--
--  Bearer Context TFT IP Packet Filter Table
--

tmnxMobServBcTftFilterTable  OBJECT-TYPE
    SYNTAX      SEQUENCE OF TmnxMobServBcTftFilterEntry
    MAX-ACCESS  not-accessible
    STATUS      current
    DESCRIPTION
        "The tmnxMobServBcTftFilterTable has an entry for each IP filter rule
         defined in a Traffic Flow Template (TFT).

         Entries will be created in this table only when the value of
         tmnxMobServPcS5S8SigProtocol is equal to 'gtp'."
    ::= { tmnxMobServingStatObjs 8 }

tmnxMobServBcTftFilterEntry  OBJECT-TYPE
    SYNTAX      TmnxMobServBcTftFilterEntry
    MAX-ACCESS  not-accessible
    STATUS      current
    DESCRIPTION
        "Each row entry represents an IP filter rule defined in a Traffic Flow
         Template (TFT)."
    INDEX { tmnxMobGwId,
            tmnxMobServUeImsi,
            tmnxMobServPcApn,
            tmnxMobServPcPdnType,
            tmnxMobServBcBearerId,
            tmnxMobServBcTftFilterDirection,
            tmnxMobServBcTftFilterId
          }
    ::= { tmnxMobServBcTftFilterTable 1 }

TmnxMobServBcTftFilterEntry ::= SEQUENCE {
        tmnxMobServBcTftFilterDirection     TmnxMobSdfFilterDirection,
        tmnxMobServBcTftFilterId            TmnxMobSdfFilter,
        tmnxMobServBcTftFilterProtocol      TmnxMobSdfFilterProtocol,
        tmnxMobServBcTftFilterSrcAdrType    InetAddressType,
        tmnxMobServBcTftFilterSrcAddr       InetAddress,
        tmnxMobServBcTftFilterSrcPfxLen     InetAddressPrefixLength,
        tmnxMobServBcTftFilterDstAdrType    InetAddressType,
        tmnxMobServBcTftFilterDestAddr      InetAddress,
        tmnxMobServBcTftFilterDestPfxLen    InetAddressPrefixLength,
        tmnxMobServBcTftFilterSrcPorts      Unsigned32,
        tmnxMobServBcTftFilterDestPorts     Unsigned32,
        tmnxMobServBcTftFirstSrcPortOper    TTcpUdpPortOperator,
        tmnxMobServBcTftFirstSrcPortVal1    TTcpUdpPort,
        tmnxMobServBcTftFirstSrcPortVal2    TTcpUdpPort,
        tmnxMobServBcTftSecndSrcPortOper    TTcpUdpPortOperator,
        tmnxMobServBcTftSecndSrcPortVal1    TTcpUdpPort,
        tmnxMobServBcTftSecndSrcPortVal2    TTcpUdpPort,
        tmnxMobServBcTftFirstDstPortOper    TTcpUdpPortOperator,
        tmnxMobServBcTftFirstDstPortVal1    TTcpUdpPort,
        tmnxMobServBcTftFirstDstPortVal2    TTcpUdpPort,
        tmnxMobServBcTftSecndDstPortOper    TTcpUdpPortOperator,
        tmnxMobServBcTftSecndDstPortVal1    TTcpUdpPort,
        tmnxMobServBcTftSecndDstPortVal2    TTcpUdpPort
    }

tmnxMobServBcTftFilterDirection  OBJECT-TYPE
    SYNTAX      TmnxMobSdfFilterDirection
    MAX-ACCESS  not-accessible
    STATUS      current
    DESCRIPTION
        "The value of tmnxMobServBcTftFilterDirection indicates the direction
         on which this filter rule is valid."
    ::= { tmnxMobServBcTftFilterEntry 1 }

tmnxMobServBcTftFilterId  OBJECT-TYPE
    SYNTAX      TmnxMobSdfFilter
    MAX-ACCESS  not-accessible
    STATUS      current
    DESCRIPTION
        "The value of tmnxMobServBcTftFilterId indicates the unique value which
         identifies a filter rule in the Traffic Flow Template (TFT)."
    ::= { tmnxMobServBcTftFilterEntry 2 }

tmnxMobServBcTftFilterProtocol  OBJECT-TYPE
    SYNTAX      TmnxMobSdfFilterProtocol
    MAX-ACCESS  read-only
    STATUS      current
    DESCRIPTION
        "The value of tmnxMobServBcTftFilterProtocol indicates the IPv4 protocol
         or IPv6 next header on which this filter matches.

         If the value of this object is set to 'any', then this filter matches
         any protocol field."
    ::= { tmnxMobServBcTftFilterEntry 3 }

tmnxMobServBcTftFilterSrcAdrType  OBJECT-TYPE
    SYNTAX      InetAddressType
    MAX-ACCESS  read-only
    STATUS      current
    DESCRIPTION
        "The value of tmnxMobServBcTftFilterSrcAdrType indicates the type of
         address represented by tmnxMobServBcTftFilterSrcAddr."
    ::= { tmnxMobServBcTftFilterEntry 4 }

tmnxMobServBcTftFilterSrcAddr  OBJECT-TYPE
    SYNTAX      InetAddress (SIZE (0|4|16))
    MAX-ACCESS  read-only
    STATUS      current
    DESCRIPTION
        "The value of tmnxMobServBcTftFilterSrcAddr indicates the IP address
         of the source on which this filter rule is valid."
    ::= { tmnxMobServBcTftFilterEntry 5 }

tmnxMobServBcTftFilterSrcPfxLen  OBJECT-TYPE
    SYNTAX      InetAddressPrefixLength
    MAX-ACCESS  read-only
    STATUS      current
    DESCRIPTION
        "The value of tmnxMobServBcTftFilterSrcPfxLen indicates the prefix
         mask length of tmnxMobServBcTftFilterSrcAddr."
    ::= { tmnxMobServBcTftFilterEntry 6 }

tmnxMobServBcTftFilterDstAdrType  OBJECT-TYPE
    SYNTAX      InetAddressType
    MAX-ACCESS  read-only
    STATUS      current
    DESCRIPTION
        "The value of tmnxMobServBcTftFilterDstAdrType indicates the type of
         address represented by tmnxMobServBcTftFilterDestAddr."
    ::= { tmnxMobServBcTftFilterEntry 7 }

tmnxMobServBcTftFilterDestAddr  OBJECT-TYPE
    SYNTAX      InetAddress (SIZE (0|4|16))
    MAX-ACCESS  read-only
    STATUS      current
    DESCRIPTION
        "The value of tmnxMobServBcTftFilterDestAddr indicates the IP address
         of the destination on which this filter rule is valid."
    ::= { tmnxMobServBcTftFilterEntry 8 }

tmnxMobServBcTftFilterDestPfxLen  OBJECT-TYPE
    SYNTAX      InetAddressPrefixLength
    MAX-ACCESS  read-only
    STATUS      current
    DESCRIPTION
        "The value of tmnxMobServBcTftFilterDestPfxLen indicates the prefix
         mask length of tmnxMobServBcTftFilterDestPfxLen."
    ::= { tmnxMobServBcTftFilterEntry 9 }

tmnxMobServBcTftFilterSrcPorts  OBJECT-TYPE
    SYNTAX      Unsigned32
    MAX-ACCESS  read-only
    STATUS      current
    DESCRIPTION
        "The value of tmnxMobServBcTftFilterSrcPorts indicates the number of
         source ports."
    ::= { tmnxMobServBcTftFilterEntry 10 }

tmnxMobServBcTftFilterDestPorts  OBJECT-TYPE
    SYNTAX      Unsigned32
    MAX-ACCESS  read-only
    STATUS      current
    DESCRIPTION
        "The value of tmnxMobServBcTftFilterDestPorts indicates the number of
         destination ports."
    ::= { tmnxMobServBcTftFilterEntry 11 }

tmnxMobServBcTftFirstSrcPortOper  OBJECT-TYPE
    SYNTAX      TTcpUdpPortOperator
    MAX-ACCESS  read-only
    STATUS      current
    DESCRIPTION
        "The value of tmnxMobServBcTftFirstSrcPortOper indicates the manner in
         which tmnxMobServBcTftFirstSrcPortVal1 and
         tmnxMobServBcTftFirstSrcPortVal2 are to be used. The values of these
         three objects are used as described in TTcpUdpPortOperator."
    ::= { tmnxMobServBcTftFilterEntry 12 }

tmnxMobServBcTftFirstSrcPortVal1  OBJECT-TYPE
    SYNTAX      TTcpUdpPort
    MAX-ACCESS  read-only
    STATUS      current
    DESCRIPTION
        "The value of tmnxMobServBcTftFirstSrcPortVal1 indicates the TCP or UDP
         starting destination port. The value of this object is used as per the
         description for tmnxMobServBcTftFirstSrcPortOper."
    ::= { tmnxMobServBcTftFilterEntry 13 }

tmnxMobServBcTftFirstSrcPortVal2  OBJECT-TYPE
    SYNTAX      TTcpUdpPort
    MAX-ACCESS  read-only
    STATUS      current
    DESCRIPTION
        "The value of tmnxMobServBcTftFirstSrcPortVal2 indicates the TCP or UDP
         starting destination port. The value of this object is used as per the
         description for tmnxMobServBcTftFirstSrcPortOper."
    ::= { tmnxMobServBcTftFilterEntry 14 }

tmnxMobServBcTftSecndSrcPortOper  OBJECT-TYPE
    SYNTAX      TTcpUdpPortOperator
    MAX-ACCESS  read-only
    STATUS      current
    DESCRIPTION
        "The value of tmnxMobServBcTftSecndSrcPortOper indicates the manner in
         which tmnxMobServBcTftSecndSrcPortVal2 and
         tmnxMobServBcTftFirstSrcPortVal2 are to be used. The values of these
         three objects are used as described in TTcpUdpPortOperator."
    ::= { tmnxMobServBcTftFilterEntry 15 }

tmnxMobServBcTftSecndSrcPortVal1  OBJECT-TYPE
    SYNTAX      TTcpUdpPort
    MAX-ACCESS  read-only
    STATUS      current
    DESCRIPTION
        "The value of tmnxMobServBcTftSecndSrcPortVal1 indicates the TCP or UDP
         starting destination port. The value of this object is used as per the
         description for tmnxMobServBcTftSecndSrcPortOper."
    ::= { tmnxMobServBcTftFilterEntry 16 }

tmnxMobServBcTftSecndSrcPortVal2  OBJECT-TYPE
    SYNTAX      TTcpUdpPort
    MAX-ACCESS  read-only
    STATUS      current
    DESCRIPTION
        "The value of tmnxMobServBcTftSecndSrcPortVal2 indicates the TCP or UDP
         starting destination port. The value of this object is used as per the
         description for tmnxMobServBcTftSecndSrcPortOper."
    ::= { tmnxMobServBcTftFilterEntry 17 }

tmnxMobServBcTftFirstDstPortOper  OBJECT-TYPE
    SYNTAX      TTcpUdpPortOperator
    MAX-ACCESS  read-only
    STATUS      current
    DESCRIPTION
        "The value of tmnxMobServBcTftFirstDstPortOper indicates the manner in
         which tmnxMobServBcTftFirstDstPortVal1 and
         tmnxMobServBcTftFirstDstPortVal2 are to be used. The values of these
         three objects are used as described in TTcpUdpPortOperator."
    ::= { tmnxMobServBcTftFilterEntry 18 }

tmnxMobServBcTftFirstDstPortVal1  OBJECT-TYPE
    SYNTAX      TTcpUdpPort
    MAX-ACCESS  read-only
    STATUS      current
    DESCRIPTION
        "The value of tmnxMobServBcTftFirstDstPortVal1 indicates the TCP or UDP
         starting destination port. The value of this object is used as per the
         description for tmnxMobServBcTftFirstDstPortOper."
    ::= { tmnxMobServBcTftFilterEntry 19 }

tmnxMobServBcTftFirstDstPortVal2  OBJECT-TYPE
    SYNTAX      TTcpUdpPort
    MAX-ACCESS  read-only
    STATUS      current
    DESCRIPTION
        "The value of tmnxMobServBcTftFirstDstPortVal2 indicates the TCP or UDP
         starting destination port. The value of this object is used as per the
         description for tmnxMobServBcTftFirstDstPortOper."
    ::= { tmnxMobServBcTftFilterEntry 20 }

tmnxMobServBcTftSecndDstPortOper  OBJECT-TYPE
    SYNTAX      TTcpUdpPortOperator
    MAX-ACCESS  read-only
    STATUS      current
    DESCRIPTION
        "The value of tmnxMobServBcTftSecndDstPortOper indicates the manner in
         which tmnxMobServBcTftSecndDstPortVal1 and
         tmnxMobServBcTftSecndDstPortVal2 are to be used. The values of these
         three objects are used as described in TTcpUdpPortOperator."
    ::= { tmnxMobServBcTftFilterEntry 21 }

tmnxMobServBcTftSecndDstPortVal1  OBJECT-TYPE
    SYNTAX      TTcpUdpPort
    MAX-ACCESS  read-only
    STATUS      current
    DESCRIPTION
        "The value of tmnxMobServBcTftSecndDstPortVal1 indicates the TCP or UDP
         starting destination port. The value of this object is used as per the
         description for tmnxMobServBcTftSecndDstPortOper."
    ::= { tmnxMobServBcTftFilterEntry 22 }

tmnxMobServBcTftSecndDstPortVal2  OBJECT-TYPE
    SYNTAX      TTcpUdpPort
    MAX-ACCESS  read-only
    STATUS      current
    DESCRIPTION
        "The value of tmnxMobServBcTftSecndDstPortVal2 indicates the TCP or UDP
         starting destination port. The value of this object is used as per the
         description for tmnxMobServBcTftSecndDstPortOper."
    ::= { tmnxMobServBcTftFilterEntry 23 }

--
--  Gxc Stats Table
--

tmnxMobServGxcStatTable  OBJECT-TYPE
    SYNTAX      SEQUENCE OF TmnxMobServGxcStatEntry
    MAX-ACCESS  not-accessible
    STATUS      current
    DESCRIPTION
        "The tmnxMobServGxcStatTable has an entry for each peer on the Gxc
         reference point."
    ::= { tmnxMobServingStatObjs 9 }

tmnxMobServGxcStatEntry  OBJECT-TYPE
    SYNTAX      TmnxMobServGxcStatEntry
    MAX-ACCESS  not-accessible
    STATUS      current
    DESCRIPTION
        "Each row entry represents a peer on the Gxc reference point and
         contains statistics for this peer."
    INDEX { vRtrID,
            tmnxMobServGxcPeerAddressType,
            tmnxMobServGxcPeerAddress,
            tmnxMobServGxcPeerPort,
            tmnxChassisIndex,
            tmnxCardSlotNum
          }
    ::= { tmnxMobServGxcStatTable 1 }

TmnxMobServGxcStatEntry ::= SEQUENCE {
        tmnxMobServGxcPeerAddressType        InetAddressType,
        tmnxMobServGxcPeerAddress            InetAddress,
        tmnxMobServGxcPeerPort               InetPortNumber,
        tmnxMobServGxcStatCcr                Counter32,
        tmnxMobServGxcStatCca                Counter32,
        tmnxMobServGxcStatCcrFailures        Counter32,
        tmnxMobServGxcStatRar                Counter32,
        tmnxMobServGxcStatRaa                Counter32,
        tmnxMobServGxcStatBberf              Counter32,
        tmnxMobServGxcStatRxMalformedPkt     Counter32,
        tmnxMobServGxcStatRxUnknownPkts      Counter32,
        tmnxMobServGxcStatRxMissingIePkt     Counter32,
        tmnxMobServGxcStatStr                Counter32,
        tmnxMobServGxcStatSta                Counter32,
        tmnxMobServGxcStatAsr                Counter32,
        tmnxMobServGxcStatAsa                Counter32,
        tmnxMobServGxcStatCer                Counter32,
        tmnxMobServGxcStatCea                Counter32,
        tmnxMobServGxcStatDpr                Counter32,
        tmnxMobServGxcStatDpa                Counter32,
        tmnxMobServGxcStatDwr                Counter32,
        tmnxMobServGxcStatDwa                Counter32,
        tmnxMobServGxcStatPrProfStatus       INTEGER,
        tmnxMobServGxcStatPrDetailStatus     INTEGER
    }

tmnxMobServGxcPeerAddressType  OBJECT-TYPE
    SYNTAX      InetAddressType
    MAX-ACCESS  not-accessible
    STATUS      current
    DESCRIPTION
        "The value of tmnxMobServGxcPeerAddressType indicates the type of
         address represented by tmnxMobServGxcPeerAddress."
    ::= { tmnxMobServGxcStatEntry 1 }

tmnxMobServGxcPeerAddress  OBJECT-TYPE
    SYNTAX      InetAddress (SIZE (4|16))
    MAX-ACCESS  not-accessible
    STATUS      current
    DESCRIPTION
        "The value of tmnxMobServGxcPeerAddress indicates the IP address of the
         peer on Gxc reference point."
    ::= { tmnxMobServGxcStatEntry 2 }

tmnxMobServGxcPeerPort  OBJECT-TYPE
    SYNTAX      InetPortNumber
    MAX-ACCESS  not-accessible
    STATUS      current
    DESCRIPTION
        "The value of tmnxMobServGxcPeerPort indicates the port number of this
         peer."
    ::= { tmnxMobServGxcStatEntry 3 }

tmnxMobServGxcStatCcr  OBJECT-TYPE
    SYNTAX      Counter32
    MAX-ACCESS  read-only
    STATUS      current
    DESCRIPTION
        "The value of tmnxMobServGxcStatCcr indicates the number of Credit
         Control Request (CCR) messages transmitted to this peer."
    ::= { tmnxMobServGxcStatEntry 4 }

tmnxMobServGxcStatCca  OBJECT-TYPE
    SYNTAX      Counter32
    MAX-ACCESS  read-only
    STATUS      current
    DESCRIPTION
        "The value of tmnxMobServGxcStatCca indicates the number of Credit
         Control Answer (CCA) messages received from this peer."
    ::= { tmnxMobServGxcStatEntry 5 }

tmnxMobServGxcStatCcrFailures  OBJECT-TYPE
    SYNTAX      Counter32
    MAX-ACCESS  read-only
    STATUS      current
    DESCRIPTION
        "The value of tmnxMobServGxcStatCcrFailures indicates the number of
         failed Credit Control Requests (CCRs) due to timeout on this peer."
    ::= { tmnxMobServGxcStatEntry 6 }

tmnxMobServGxcStatRar  OBJECT-TYPE
    SYNTAX      Counter32
    MAX-ACCESS  read-only
    STATUS      current
    DESCRIPTION
        "The value of tmnxMobServGxcStatRar indicates the number of Re-Auth
         Request (RAR) messages received from this peer."
    ::= { tmnxMobServGxcStatEntry 7 }

tmnxMobServGxcStatRaa  OBJECT-TYPE
    SYNTAX      Counter32
    MAX-ACCESS  read-only
    STATUS      current
    DESCRIPTION
        "The value of tmnxMobServGxcStatRaa indicates the number of Re-Auth
         Answer (RAA) messages transmitted to this peer."
    ::= { tmnxMobServGxcStatEntry 8 }

tmnxMobServGxcStatBberf  OBJECT-TYPE
    SYNTAX      Counter32
    MAX-ACCESS  read-only
    STATUS      current
    DESCRIPTION
        "The value of tmnxMobServGxcStatBberf indicates the number of Bearer
         Binding and Event Reporting Function (BBERF) procedures transmitted
         by this peer."
    ::= { tmnxMobServGxcStatEntry 9 }

tmnxMobServGxcStatRxMalformedPkt  OBJECT-TYPE
    SYNTAX      Counter32
    MAX-ACCESS  read-only
    STATUS      current
    DESCRIPTION
        "The value of tmnxMobServGxcStatRxMalformedPkt indicates the number of
         malformed packets received from this peer."
    ::= { tmnxMobServGxcStatEntry 10 }

tmnxMobServGxcStatRxUnknownPkts  OBJECT-TYPE
    SYNTAX      Counter32
    MAX-ACCESS  read-only
    STATUS      current
    DESCRIPTION
        "The value of tmnxMobServGxcStatRxUnknownPkts indicates the number of
         unknown message type packets received from this peer."
    ::= { tmnxMobServGxcStatEntry 11 }

tmnxMobServGxcStatRxMissingIePkt  OBJECT-TYPE
    SYNTAX      Counter32
    MAX-ACCESS  read-only
    STATUS      current
    DESCRIPTION
        "The value of tmnxMobServGxcStatRxMissingIePkt indicates the number of
         missing mandatory Information Element (IE) packets received from this
         peer."
    ::= { tmnxMobServGxcStatEntry 12 }

tmnxMobServGxcStatStr  OBJECT-TYPE
    SYNTAX      Counter32
    MAX-ACCESS  read-only
    STATUS      current
    DESCRIPTION
        "The value of tmnxMobServGxcStatStr indicates the number of Session
         Termination Request (STR) messages received from this peer."
    ::= { tmnxMobServGxcStatEntry 13 }

tmnxMobServGxcStatSta  OBJECT-TYPE
    SYNTAX      Counter32
    MAX-ACCESS  read-only
    STATUS      current
    DESCRIPTION
        "The value of tmnxMobServGxcStatSta indicates the number of Session
         Termination Answer (STA) messages transmitted to this peer."
    ::= { tmnxMobServGxcStatEntry 14 }

tmnxMobServGxcStatAsr  OBJECT-TYPE
    SYNTAX      Counter32
    MAX-ACCESS  read-only
    STATUS      current
    DESCRIPTION
        "The value of tmnxMobServGxcStatAsr indicates the number of Abort
         Session Request (ASR) messages received from this peer."
    ::= { tmnxMobServGxcStatEntry 15 }

tmnxMobServGxcStatAsa  OBJECT-TYPE
    SYNTAX      Counter32
    MAX-ACCESS  read-only
    STATUS      current
    DESCRIPTION
        "The value of tmnxMobServGxcStatAsa indicates the number of Abort
         Session Answer (ASA) messages transmitted to this peer."
    ::= { tmnxMobServGxcStatEntry 16 }

tmnxMobServGxcStatCer  OBJECT-TYPE
    SYNTAX      Counter32
    MAX-ACCESS  read-only
    STATUS      current
    DESCRIPTION
        "The value of tmnxMobServGxcStatCer indicates the number of Capabilities
         Exchange Request (CER) messages transmitted to this peer."
    ::= { tmnxMobServGxcStatEntry 17 }

tmnxMobServGxcStatCea  OBJECT-TYPE
    SYNTAX      Counter32
    MAX-ACCESS  read-only
    STATUS      current
    DESCRIPTION
        "The value of tmnxMobServGxcStatCea indicates the number of Capabilities
         Exchange Answer (CEA) messages received from this peer."
    ::= { tmnxMobServGxcStatEntry 18 }

tmnxMobServGxcStatDpr  OBJECT-TYPE
    SYNTAX      Counter32
    MAX-ACCESS  read-only
    STATUS      current
    DESCRIPTION
        "The value of tmnxMobServGxcStatDpr indicates the number of Disconnect
         Peer Request (DPR) messages received from this peer."
    ::= { tmnxMobServGxcStatEntry 19 }

tmnxMobServGxcStatDpa  OBJECT-TYPE
    SYNTAX      Counter32
    MAX-ACCESS  read-only
    STATUS      current
    DESCRIPTION
        "The value of tmnxMobServGxcStatDpa indicates the number of Disconnect
         Peer Answer (DPA) messages transmitted to this peer."
    ::= { tmnxMobServGxcStatEntry 20 }

tmnxMobServGxcStatDwr  OBJECT-TYPE
    SYNTAX      Counter32
    MAX-ACCESS  read-only
    STATUS      current
    DESCRIPTION
        "The value of tmnxMobServGxcStatDwr indicates the number of Device
         Watchdog Request (DWR) messages transmitted to this peer."
    ::= { tmnxMobServGxcStatEntry 21 }

tmnxMobServGxcStatDwa  OBJECT-TYPE
    SYNTAX      Counter32
    MAX-ACCESS  read-only
    STATUS      current
    DESCRIPTION
        "The value of tmnxMobServGxcStatDwa indicates the number of Device
         Watchdog Answer (DWA) messages received from this peer."
    ::= { tmnxMobServGxcStatEntry 22 }

tmnxMobServGxcStatPrProfStatus  OBJECT-TYPE
    SYNTAX      INTEGER {
                         active         (1),
                         inactive       (2),
                         shutdown       (3),
                         shutingDown    (4)
                        }
    MAX-ACCESS  read-only
    STATUS      current
    DESCRIPTION
        "The value of tmnxMobServGxcStatPrProfStatus indicates the status of the
         connection to the peer and whether the connection is usable or not."
    ::= { tmnxMobServGxcStatEntry 23 }

tmnxMobServGxcStatPrDetailStatus  OBJECT-TYPE
    SYNTAX      INTEGER {
                         error              (1),
                         idle               (2),
                         closed             (3),
                         localShutdown      (4),
                         remoteClosing      (5),
                         waitConnack        (6),
                         waitCea            (7),
                         open               (8),
                         openCoolingDown    (9),
                         waitDns            (10)
                        }
    MAX-ACCESS  read-only
    STATUS      current
    DESCRIPTION
        "The value of tmnxMobServGxcStatPrDetailStatus indicates the detailed
         status of the connection to the peer and may inform why a connection
         is not usable."
    ::= { tmnxMobServGxcStatEntry 24 }

--
--  S11 peer list Table
--

tmnxMobServS11PeerTableLastChngd     OBJECT-TYPE
    SYNTAX      TimeStamp
    MAX-ACCESS  read-only
    STATUS      current
    DESCRIPTION
        "The value of tmnxMobServS11PeerTableLastChngd indicates the sysUpTime
         at the time of the last modification to tmnxMobServS11PeerTable by
         adding, deleting an entry or change to a writable object in the table.

         If no changes were made to the table since the last re-initialization
         of the local network management subsystem, then this object contains
         a zero value."
    ::= { tmnxMobServingGlobalObjs 11 }

tmnxMobServS11PeerTable  OBJECT-TYPE
    SYNTAX      SEQUENCE OF TmnxMobServS11PeerEntry
    MAX-ACCESS  not-accessible
    STATUS      current
    DESCRIPTION
        "The tmnxMobServS11PeerTable has an entry for each peer on the S11
         reference point served by a Serving Gateway (SGW)."
    ::= { tmnxMobServingStatObjs 10 }

tmnxMobServS11PeerEntry  OBJECT-TYPE
    SYNTAX      TmnxMobServS11PeerEntry
    MAX-ACCESS  not-accessible
    STATUS      current
    DESCRIPTION
        "Each row entry represents a peer on the S11 reference point."
    INDEX { vRtrID,
            tmnxMobServS11PeerAddressType,
            tmnxMobServS11PeerAddress,
            tmnxMobServS11PeerPort
          }
    ::= { tmnxMobServS11PeerTable 1 }

TmnxMobServS11PeerEntry ::= SEQUENCE {
        tmnxMobServS11PeerAddressType       InetAddressType,
        tmnxMobServS11PeerAddress           InetAddress,
        tmnxMobServS11PeerPort              InetPortNumber,
        tmnxMobServS11PeerLastChanged       TimeStamp,
        tmnxMobServS11PeerCreateTime        TimeStamp,
        tmnxMobServS11PeerPathMgmtState     TmnxMobPathMgmtState,
        tmnxMobServS11PeerGatewayId         TmnxMobGwId
    }

tmnxMobServS11PeerAddressType  OBJECT-TYPE
    SYNTAX      InetAddressType
    MAX-ACCESS  not-accessible
    STATUS      current
    DESCRIPTION
        "The value of tmnxMobServS11PeerAddressType indicates the type of
         address represented by tmnxMobServS11PeerAddress."
    ::= { tmnxMobServS11PeerEntry 1 }

tmnxMobServS11PeerAddress  OBJECT-TYPE
    SYNTAX      InetAddress (SIZE (4|16))
    MAX-ACCESS  not-accessible
    STATUS      current
    DESCRIPTION
        "The value of tmnxMobServS11PeerAddress indicates the IP address of
         this peer on S11 reference point."
    ::= { tmnxMobServS11PeerEntry 2 }

tmnxMobServS11PeerPort  OBJECT-TYPE
    SYNTAX      InetPortNumber
    MAX-ACCESS  not-accessible
    STATUS      current
    DESCRIPTION
        "The value of tmnxMobServS11PeerPort indicates the port number of this
         peer."
    ::= { tmnxMobServS11PeerEntry 3 }

tmnxMobServS11PeerLastChanged  OBJECT-TYPE
    SYNTAX      TimeStamp
    MAX-ACCESS  read-only
    STATUS      current
    DESCRIPTION
        "The value of tmnxMobServS11PeerLastChanged indicates the timestamp of
         the last change to this row in tmnxMobServS11PeerTable."
    ::= { tmnxMobServS11PeerEntry 4 }

tmnxMobServS11PeerCreateTime  OBJECT-TYPE
    SYNTAX      TimeStamp
    MAX-ACCESS  read-only
    STATUS      current
    DESCRIPTION
        "The value of tmnxMobServS11PeerCreateTime indicates the sysUpTime when
         this entry was created."
    ::= { tmnxMobServS11PeerEntry 5 }

tmnxMobServS11PeerPathMgmtState  OBJECT-TYPE
    SYNTAX      TmnxMobPathMgmtState
    MAX-ACCESS  read-only
    STATUS      current
    DESCRIPTION
        "The value of tmnxMobServS11PeerPathMgmtState indicates the state of
         the path."
    ::= { tmnxMobServS11PeerEntry 6 }

tmnxMobServS11PeerGatewayId  OBJECT-TYPE
    SYNTAX      TmnxMobGwId
    MAX-ACCESS  read-only
    STATUS      current
    DESCRIPTION
        "The value of tmnxMobServS11PeerGatewayId indicates the gateway
         to which this peer belongs."
    ::= { tmnxMobServS11PeerEntry 7 }

--
--  S11 Stats Table
--

tmnxMobServS11StatTable  OBJECT-TYPE
    SYNTAX      SEQUENCE OF TmnxMobServS11StatEntry
    MAX-ACCESS  not-accessible
    STATUS      current
    DESCRIPTION
        "The tmnxMobServS11StatTable has an entry for each peer on the S11
         reference point served by a Serving Gateway (SGW)."
    ::= { tmnxMobServingStatObjs 11 }

tmnxMobServS11StatEntry  OBJECT-TYPE
    SYNTAX      TmnxMobServS11StatEntry
    MAX-ACCESS  not-accessible
    STATUS      current
    DESCRIPTION
        "Each row entry represents a peer on the S11 reference point and
         contains statistics for this peer on a card."
    INDEX { vRtrID,
            tmnxMobServS11PeerAddressType,
            tmnxMobServS11PeerAddress,
            tmnxMobServS11PeerPort,
            tmnxChassisIndex,
            tmnxCardSlotNum
          }
    ::= { tmnxMobServS11StatTable 1 }

TmnxMobServS11StatEntry ::= SEQUENCE {
        tmnxMobServS11StatCreateSessnReq    Counter32,
        tmnxMobServS11StatCreateSessnRsp    Counter32,
        tmnxMobServS11StatDeleteSessnReq    Counter32,
        tmnxMobServS11StatDeleteSessnRsp    Counter32,
        tmnxMobServS11StatCreateBearrReq    Counter32,
        tmnxMobServS11StatCreateBearrRsp    Counter32,
        tmnxMobServS11StatDeleteBearrReq    Counter32,
        tmnxMobServS11StatDeleteBearrRsp    Counter32,
        tmnxMobServS11StatModifyBearrReq    Counter32,
        tmnxMobServS11StatModifyBearrRsp    Counter32,
        tmnxMobServS11StatRxEchoRequests    Counter32,
        tmnxMobServS11StatTxEchoResp        Counter32,
        tmnxMobServS11StatTxEchoRequests    Counter32,
        tmnxMobServS11StatRxEchoResp        Counter32,
        tmnxMobServS11StatTxDlNotify        Counter32,
        tmnxMobServS11StatRxDlAcks          Counter32,
        tmnxMobServS11StatRxDlFailNotify    Counter32,
        tmnxMobServS11StatPagingSvcReq      Counter32,
        tmnxMobServS11StatRxMalfrmedPkts    Counter32,
        tmnxMobServS11StatRxUnknownPkts     Counter32,
        tmnxMobServS11StatRxMissngIePkts    Counter32,
        tmnxMobServS11StatPeerRestarts      Counter32,
        tmnxMobServS11StatPeerRestartCnt    Counter32,
        tmnxMobServS11StatPathMgmtFails     Counter32,
        tmnxMobServS11StatRelBearersReq     Counter32,
        tmnxMobServS11StatRelBearersResp    Counter32,
        tmnxMobServS11StatCrtIndrTnlReq     Counter32,
        tmnxMobServS11StatCrtIndrTnlResp    Counter32,
        tmnxMobServS11StatDelIndrTnlReq     Counter32,
        tmnxMobServS11StatDelIndrTnlResp    Counter32,
        tmnxMobServS11StatBearersIpv4       Gauge32,
        tmnxMobServS11StatBearersIpv6       Gauge32,
        tmnxMobServS11StatBearerIpv4v6      Gauge32,
        tmnxMobServS11StatDedctdBearers     Gauge32,
        tmnxMobServS11StatBearers           Gauge32,
        tmnxMobServS11StatDefBearers        Gauge32,
        tmnxMobServS11StatRoamers           Gauge32,
        tmnxMobServS11StatActiveBearers     Gauge32,
        tmnxMobServS11StatIdleBearers       Gauge32,
        tmnxMobServS11StatUpdateBearrReq    Counter32,
        tmnxMobServS11StatUpdateBearrRsp    Counter32,
        tmnxMobServS11StatModifyBearrCmd    Counter32,
        tmnxMobServS11StatModifyBearrFlr    Counter32,
        tmnxMobServS11StatDeleteBearrCmd    Counter32,
        tmnxMobServS11StatDeleteBearrFlr    Counter32,
        tmnxMobServS11StatBearrResCmd       Counter32,
        tmnxMobServS11StatBrrResFailInd     Counter32,
        tmnxMobServS11StatSuspNoticeReq     Counter32,
        tmnxMobServS11StatSuspNoticeAck     Counter32,
        tmnxMobServS11StatResNoticeReq      Counter32,
        tmnxMobServS11StatResNoticeAck      Counter32,
        tmnxMobServS11StatDelSesnRspFl      Counter32,
        tmnxMobServS11StatUpdtBearrRspFl    Counter32,
        tmnxMobServS11StatModBearrRspFl     Counter32,
        tmnxMobServS11StatDelBearrRspFl     Counter32,
        tmnxMobServS11StatCreatBearRspFl    Counter32,
        tmnxMobServS11StatCreatSesnRspFl    Counter32,
        tmnxMobServS11StatRelBearrRespFl    Counter32,
        tmnxMobServS11StatCrtIndTnlRspFl    Counter32,
        tmnxMobServS11StatDelIndTnlRspFl    Counter32,
        tmnxMobServS11StatRxDlAcksFail      Counter32
    }

tmnxMobServS11StatCreateSessnReq  OBJECT-TYPE
    SYNTAX      Counter32
    MAX-ACCESS  read-only
    STATUS      current
    DESCRIPTION
        "The value of tmnxMobServS11StatCreateSessnReq indicates the number of
         create session request messages received from this peer."
    ::= { tmnxMobServS11StatEntry 1 }

tmnxMobServS11StatCreateSessnRsp  OBJECT-TYPE
    SYNTAX      Counter32
    MAX-ACCESS  read-only
    STATUS      current
    DESCRIPTION
        "The value of tmnxMobServS11StatCreateSessnRsp indicates the number of
         create session response messages transmitted to this peer with cause
         code set to request accepted."
    ::= { tmnxMobServS11StatEntry 2 }

tmnxMobServS11StatDeleteSessnReq  OBJECT-TYPE
    SYNTAX      Counter32
    MAX-ACCESS  read-only
    STATUS      current
    DESCRIPTION
        "The value of tmnxMobServS11StatDeleteSessnReq indicates the number of
         delete session request messages received from this peer."
    ::= { tmnxMobServS11StatEntry 3 }

tmnxMobServS11StatDeleteSessnRsp  OBJECT-TYPE
    SYNTAX      Counter32
    MAX-ACCESS  read-only
    STATUS      current
    DESCRIPTION
        "The value of tmnxMobServS11StatDeleteSessnRsp indicates the number of
         delete session response messages transmitted to this peer with cause
         code set to request accepted."
    ::= { tmnxMobServS11StatEntry 4 }

tmnxMobServS11StatCreateBearrReq  OBJECT-TYPE
    SYNTAX      Counter32
    MAX-ACCESS  read-only
    STATUS      current
    DESCRIPTION
        "The value of tmnxMobServS11StatCreateBearrReq indicates the number of
         create bearer request messages transmitted to this peer."
    ::= { tmnxMobServS11StatEntry 5 }

tmnxMobServS11StatCreateBearrRsp  OBJECT-TYPE
    SYNTAX      Counter32
    MAX-ACCESS  read-only
    STATUS      current
    DESCRIPTION
        "The value of tmnxMobServS11StatCreateBearrRsp indicates the number of
         create bearer response messages received from this peer with cause
         code set to request accepted."
    ::= { tmnxMobServS11StatEntry 6 }

tmnxMobServS11StatDeleteBearrReq  OBJECT-TYPE
    SYNTAX      Counter32
    MAX-ACCESS  read-only
    STATUS      current
    DESCRIPTION
        "The value of tmnxMobServS11StatDeleteBearrReq indicates the number of
         delete bearer request messages transmitted to this peer."
    ::= { tmnxMobServS11StatEntry 7 }

tmnxMobServS11StatDeleteBearrRsp  OBJECT-TYPE
    SYNTAX      Counter32
    MAX-ACCESS  read-only
    STATUS      current
    DESCRIPTION
        "The value of tmnxMobServS11StatDeleteBearrRsp indicates the number of
         delete bearer response messages received from this peer with cause
         code set to request accepted."
    ::= { tmnxMobServS11StatEntry 8 }

tmnxMobServS11StatModifyBearrReq  OBJECT-TYPE
    SYNTAX      Counter32
    MAX-ACCESS  read-only
    STATUS      current
    DESCRIPTION
        "The value of tmnxMobServS11StatModifyBearrReq indicates the number of
         modify bearer request messages received from this peer."
    ::= { tmnxMobServS11StatEntry 9 }

tmnxMobServS11StatModifyBearrRsp  OBJECT-TYPE
    SYNTAX      Counter32
    MAX-ACCESS  read-only
    STATUS      current
    DESCRIPTION
        "The value of tmnxMobServS11StatModifyBearrRsp indicates the number of
         modify bearer response messages transmitted to this peer with cause
         code set to request accepted."
    ::= { tmnxMobServS11StatEntry 10 }

tmnxMobServS11StatRxEchoRequests  OBJECT-TYPE
    SYNTAX      Counter32
    MAX-ACCESS  read-only
    STATUS      current
    DESCRIPTION
        "The value of tmnxMobServS11StatRxEchoRequests indicates the number of
         echo request messages received from this peer."
    ::= { tmnxMobServS11StatEntry 11 }

tmnxMobServS11StatTxEchoResp  OBJECT-TYPE
    SYNTAX      Counter32
    MAX-ACCESS  read-only
    STATUS      current
    DESCRIPTION
        "The value of tmnxMobServS11StatTxEchoResp indicates the number of
         echo response messages transmitted to this peer."
    ::= { tmnxMobServS11StatEntry 12 }

tmnxMobServS11StatTxEchoRequests  OBJECT-TYPE
    SYNTAX      Counter32
    MAX-ACCESS  read-only
    STATUS      current
    DESCRIPTION
        "The value of tmnxMobServS11StatTxEchoRequests indicates the number of
         echo request messages transmitted to this peer."
    ::= { tmnxMobServS11StatEntry 13 }

tmnxMobServS11StatRxEchoResp  OBJECT-TYPE
    SYNTAX      Counter32
    MAX-ACCESS  read-only
    STATUS      current
    DESCRIPTION
        "The value of tmnxMobServS11StatRxEchoResp indicates the number of
         echo response messages received from this peer."
    ::= { tmnxMobServS11StatEntry 14 }

tmnxMobServS11StatTxDlNotify  OBJECT-TYPE
    SYNTAX      Counter32
    MAX-ACCESS  read-only
    STATUS      current
    DESCRIPTION
        "The value of tmnxMobServS11StatTxDlNotify indicates the number of
         downlink data notification messages transmitted to this peer."
    ::= { tmnxMobServS11StatEntry 15 }

tmnxMobServS11StatRxDlAcks  OBJECT-TYPE
    SYNTAX      Counter32
    MAX-ACCESS  read-only
    STATUS      current
    DESCRIPTION
        "The value of tmnxMobServS11StatRxDlAcks indicates the number of
         downlink data notification acknowledgements received from this peer
         with cause code set to request accepted."
    ::= { tmnxMobServS11StatEntry 16 }

tmnxMobServS11StatRxDlFailNotify  OBJECT-TYPE
    SYNTAX      Counter32
    MAX-ACCESS  read-only
    STATUS      current
    DESCRIPTION
        "The value of tmnxMobServS11StatRxDlFailNotify indicates the number of
         downlink data notification failure indication messages received from
         this peer."
    ::= { tmnxMobServS11StatEntry 17 }

tmnxMobServS11StatPagingSvcReq  OBJECT-TYPE
    SYNTAX      Counter32
    MAX-ACCESS  read-only
    STATUS      obsolete
    DESCRIPTION
        "The value of tmnxMobServS11StatPagingSvcReq indicates the number of
         paging initiated service requests received from this peer.

         This object was made obsolete in the 3.0 release."
    ::= { tmnxMobServS11StatEntry 18 }

tmnxMobServS11StatRxMalfrmedPkts  OBJECT-TYPE
    SYNTAX      Counter32
    MAX-ACCESS  read-only
    STATUS      current
    DESCRIPTION
        "The value of tmnxMobServS11StatRxMalfrmedPkts indicates the number of
         malformed packets received from this peer."
    ::= { tmnxMobServS11StatEntry 19 }

tmnxMobServS11StatRxUnknownPkts  OBJECT-TYPE
    SYNTAX      Counter32
    MAX-ACCESS  read-only
    STATUS      current
    DESCRIPTION
        "The value of tmnxMobServS11StatRxUnknownPkts indicates the number of
         unknown message type packets received from this peer."
    ::= { tmnxMobServS11StatEntry 20 }

tmnxMobServS11StatRxMissngIePkts  OBJECT-TYPE
    SYNTAX      Counter32
    MAX-ACCESS  read-only
    STATUS      current
    DESCRIPTION
        "The value of tmnxMobServS11StatRxMissngIePkts indicates the number of
         missing mandatory Information Element (IE) packets received from this
         peer."
    ::= { tmnxMobServS11StatEntry 21 }

tmnxMobServS11StatPeerRestarts  OBJECT-TYPE
    SYNTAX      Counter32
    MAX-ACCESS  read-only
    STATUS      current
    DESCRIPTION
        "The value of tmnxMobServS11StatPeerRestarts indicates the number of
         times this peer restarted."
    ::= { tmnxMobServS11StatEntry 22 }

tmnxMobServS11StatPeerRestartCnt  OBJECT-TYPE
    SYNTAX      Counter32
    MAX-ACCESS  read-only
    STATUS      current
    DESCRIPTION
        "The value of tmnxMobServS11StatPeerRestartCnt indicates the counter
         value of the number of times this peer restarted."
    ::= { tmnxMobServS11StatEntry 23 }

tmnxMobServS11StatPathMgmtFails  OBJECT-TYPE
    SYNTAX      Counter32
    MAX-ACCESS  read-only
    STATUS      current
    DESCRIPTION
        "The value of tmnxMobServS11StatPathMgmtFails indicates the number of
         path management failures for this peer."
    ::= { tmnxMobServS11StatEntry 24 }

tmnxMobServS11StatRelBearersReq  OBJECT-TYPE
    SYNTAX      Counter32
    MAX-ACCESS  read-only
    STATUS      current
    DESCRIPTION
        "The value of tmnxMobServS11StatRelBearersReq indicates the number of
         Release Access Bearers Request messages transmitted by this peer."
    ::= { tmnxMobServS11StatEntry 25 }

tmnxMobServS11StatRelBearersResp  OBJECT-TYPE
    SYNTAX      Counter32
    MAX-ACCESS  read-only
    STATUS      current
    DESCRIPTION
        "The value of tmnxMobServS11StatRelBearersResp indicates the number of
         Release Access Bearers Response messages transmitted to this peer with
         cause code set to request accepted."
    ::= { tmnxMobServS11StatEntry 26 }

tmnxMobServS11StatCrtIndrTnlReq  OBJECT-TYPE
    SYNTAX      Counter32
    MAX-ACCESS  read-only
    STATUS      current
    DESCRIPTION
        "The value of tmnxMobServS11StatCrtIndrTnlReq indicates the number of
         Create Indirect Data Forwarding Tunnel Request messages transmitted by
         this peer."
    ::= { tmnxMobServS11StatEntry 27 }

tmnxMobServS11StatCrtIndrTnlResp  OBJECT-TYPE
    SYNTAX      Counter32
    MAX-ACCESS  read-only
    STATUS      current
    DESCRIPTION
        "The value of tmnxMobServS11StatCrtIndrTnlResp indicates the number of
         Create Indirect Data Forwarding Tunnel Response messages transmitted to
         this peer with cause code set to request accepted."
    ::= { tmnxMobServS11StatEntry 28 }

tmnxMobServS11StatDelIndrTnlReq  OBJECT-TYPE
    SYNTAX      Counter32
    MAX-ACCESS  read-only
    STATUS      current
    DESCRIPTION
        "The value of tmnxMobServS11StatDelIndrTnlReq indicates the number of
         Delete Indirect Data Forwarding Tunnel Request messages transmitted
         by this peer."
    ::= { tmnxMobServS11StatEntry 29 }

tmnxMobServS11StatDelIndrTnlResp  OBJECT-TYPE
    SYNTAX      Counter32
    MAX-ACCESS  read-only
    STATUS      current
    DESCRIPTION
        "The value of tmnxMobServS11StatDelIndrTnlResp indicates the number of
         Delete Indirect Data Forwarding Tunnel Response messages transmitted
         to this peer with cause code set to request accepted."
    ::= { tmnxMobServS11StatEntry 30 }

tmnxMobServS11StatBearersIpv4  OBJECT-TYPE
    SYNTAX      Gauge32
    MAX-ACCESS  read-only
    STATUS      obsolete
    DESCRIPTION
        "The value of tmnxMobServS11StatBearersIpv4 indicates the number of
         IPv4 bearers being served by this peer.

         This object was made obsolete in the 3.1R2 release."
    ::= { tmnxMobServS11StatEntry 31 }

tmnxMobServS11StatBearersIpv6  OBJECT-TYPE
    SYNTAX      Gauge32
    MAX-ACCESS  read-only
    STATUS      obsolete
    DESCRIPTION
        "The value of tmnxMobServS11StatBearersIpv6 indicates the number of
         IPv6 bearers being served by this peer.

         This object was made obsolete in the 3.1R2 release."
    ::= { tmnxMobServS11StatEntry 32 }

tmnxMobServS11StatBearerIpv4v6  OBJECT-TYPE
    SYNTAX      Gauge32
    MAX-ACCESS  read-only
    STATUS      obsolete
    DESCRIPTION
        "The value of tmnxMobServS11StatBearerIpv4v6 indicates the number of
         IPv4v6 bearers being served by this peer.

         This object was made obsolete in the 3.1R2 release."
    ::= { tmnxMobServS11StatEntry 33 }

tmnxMobServS11StatDedctdBearers  OBJECT-TYPE
    SYNTAX      Gauge32
    MAX-ACCESS  read-only
    STATUS      obsolete
    DESCRIPTION
        "The value of tmnxMobServS11StatDedctdBearers indicates the number of
         dedicated bearers being served by this peer.

         This object was made obsolete in the 3.1R2 release."
    ::= { tmnxMobServS11StatEntry 34 }

tmnxMobServS11StatBearers  OBJECT-TYPE
    SYNTAX      Gauge32
    MAX-ACCESS  read-only
    STATUS      current
    DESCRIPTION
        "The value of tmnxMobServS11StatBearers indicates the total number of
         bearers being served by this peer."
    ::= { tmnxMobServS11StatEntry 35 }

tmnxMobServS11StatDefBearers  OBJECT-TYPE
    SYNTAX      Gauge32
    MAX-ACCESS  read-only
    STATUS      obsolete
    DESCRIPTION
        "The value of tmnxMobServS11StatDefBearers indicates the number of
         default bearers being served by this peer.

         This object was made obsolete in the 3.1R2 release."
    ::= { tmnxMobServS11StatEntry 36 }

tmnxMobServS11StatRoamers  OBJECT-TYPE
    SYNTAX      Gauge32
    MAX-ACCESS  read-only
    STATUS      obsolete
    DESCRIPTION
        "The value of tmnxMobServS11StatRoamers indicates the number of
         roamers being served by this peer.

         This object was made obsolete in the 3.1R2 release."
    ::= { tmnxMobServS11StatEntry 37 }

tmnxMobServS11StatActiveBearers  OBJECT-TYPE
    SYNTAX      Gauge32
    MAX-ACCESS  read-only
    STATUS      obsolete
    DESCRIPTION
        "The value of tmnxMobServS11StatActiveBearers indicates the number of
         active bearers being served by this peer.

         This object was made obsolete in the 3.1R2 release."
    ::= { tmnxMobServS11StatEntry 38 }

tmnxMobServS11StatIdleBearers  OBJECT-TYPE
    SYNTAX      Gauge32
    MAX-ACCESS  read-only
    STATUS      obsolete
    DESCRIPTION
        "The value of tmnxMobServS11StatIdleBearers indicates the number of
         idle bearers being served by this peer.

         This object was made obsolete in the 3.1R2 release."
    ::= { tmnxMobServS11StatEntry 39 }

tmnxMobServS11StatUpdateBearrReq  OBJECT-TYPE
    SYNTAX      Counter32
    MAX-ACCESS  read-only
    STATUS      current
    DESCRIPTION
        "The value of tmnxMobServS11StatUpdateBearrReq indicates the number of
         update bearer request messages transmitted to this peer."
    ::= { tmnxMobServS11StatEntry 40 }

tmnxMobServS11StatUpdateBearrRsp  OBJECT-TYPE
    SYNTAX      Counter32
    MAX-ACCESS  read-only
    STATUS      current
    DESCRIPTION
        "The value of tmnxMobServS11StatUpdateBearrRsp indicates the number of
         update bearer response messages received from this peer with cause
         code set to request accepted."
    ::= { tmnxMobServS11StatEntry 41 }

tmnxMobServS11StatModifyBearrCmd  OBJECT-TYPE
    SYNTAX      Counter32
    MAX-ACCESS  read-only
    STATUS      current
    DESCRIPTION
        "The value of tmnxMobServS11StatModifyBearrCmd indicates the number of
         modify bearer command messages received from this peer."
    ::= { tmnxMobServS11StatEntry 42 }

tmnxMobServS11StatModifyBearrFlr  OBJECT-TYPE
    SYNTAX      Counter32
    MAX-ACCESS  read-only
    STATUS      current
    DESCRIPTION
        "The value of tmnxMobServS11StatModifyBearrFlr indicates the number of
         modify bearer failure messages received from this peer."
    ::= { tmnxMobServS11StatEntry 43 }

tmnxMobServS11StatDeleteBearrCmd  OBJECT-TYPE
    SYNTAX      Counter32
    MAX-ACCESS  read-only
    STATUS      current
    DESCRIPTION
        "The value of tmnxMobServS11StatDeleteBearrCmd indicates the number of
         delete bearer command messages received from this peer."
    ::= { tmnxMobServS11StatEntry 44 }

tmnxMobServS11StatDeleteBearrFlr  OBJECT-TYPE
    SYNTAX      Counter32
    MAX-ACCESS  read-only
    STATUS      current
    DESCRIPTION
        "The value of tmnxMobServS11StatDeleteBearrFlr indicates the number of
         delete bearer failure messages received from this peer."
    ::= { tmnxMobServS11StatEntry 45 }

tmnxMobServS11StatBearrResCmd  OBJECT-TYPE
    SYNTAX      Counter32
    MAX-ACCESS  read-only
    STATUS      current
    DESCRIPTION
        "The value of tmnxMobServS11StatBearrResCmd indicates the number of
         bearer resource command packets on the gateway."
    ::= { tmnxMobServS11StatEntry 46 }

tmnxMobServS11StatBrrResFailInd  OBJECT-TYPE
    SYNTAX      Counter32
    MAX-ACCESS  read-only
    STATUS      current
    DESCRIPTION
        "The value of tmnxMobServS11StatBrrResFailInd indicates the number of
        bearer resource failure indication packets on the gateway."
    ::= { tmnxMobServS11StatEntry 47 }

tmnxMobServS11StatSuspNoticeReq  OBJECT-TYPE
    SYNTAX      Counter32
    MAX-ACCESS  read-only
    STATUS      current
    DESCRIPTION
        "The value of tmnxMobServS11StatSuspNoticeReq indicates the number of
        suspend notification requests received at the Serving Gateway(SGW) from
        the Mobility Management Entity (MME)."
    ::= { tmnxMobServS11StatEntry 48 }

tmnxMobServS11StatSuspNoticeAck  OBJECT-TYPE
    SYNTAX      Counter32
    MAX-ACCESS  read-only
    STATUS      current
    DESCRIPTION
        "The value of tmnxMobServS11StatSuspNoticeAck indicates the number of
        suspend notification acknowledgements sent from the Serving Gateway (SGW)
        to the Mobility Management Entity (MME)."
    ::= { tmnxMobServS11StatEntry 49 }

tmnxMobServS11StatResNoticeReq  OBJECT-TYPE
    SYNTAX      Counter32
    MAX-ACCESS  read-only
    STATUS      current
    DESCRIPTION
        "The value of tmnxMobServS11StatResNoticeReq indicates the number of
        resume notification requests received at the Serving Gateway (SGW) from the
        Mobility Management Entity (MME)."
    ::= { tmnxMobServS11StatEntry 50 }

tmnxMobServS11StatResNoticeAck  OBJECT-TYPE
    SYNTAX      Counter32
    MAX-ACCESS  read-only
    STATUS      current
    DESCRIPTION
        "The value of tmnxMobServS11StatResNoticeAck indicates the number of
        resume notification acknowledgements sent from the Serving Gateway (SGW)
        to the Mobility Management Entity (MME)."
    ::= { tmnxMobServS11StatEntry 51 }

tmnxMobServS11StatDelSesnRspFl      OBJECT-TYPE
    SYNTAX      Counter32
    MAX-ACCESS  read-only
    STATUS      current
    DESCRIPTION
        "The value of tmnxMobServS11StatDelSesnRspFl indicates the number of
         delete session response messages transmitted to this peer with
         cause code not set to request accepted."
    ::= { tmnxMobServS11StatEntry 52 }

tmnxMobServS11StatUpdtBearrRspFl    OBJECT-TYPE
    SYNTAX      Counter32
    MAX-ACCESS  read-only
    STATUS      current
    DESCRIPTION
        "The value of tmnxMobServS11StatUpdtBearrRspFl indicates the number of
         update bearer response messages received from this peer with cause
         code not set to request accepted."
    ::= { tmnxMobServS11StatEntry 53 }

tmnxMobServS11StatModBearrRspFl     OBJECT-TYPE
    SYNTAX      Counter32
    MAX-ACCESS  read-only
    STATUS      current
    DESCRIPTION
        "The value of tmnxMobServS11StatModBearrRspFl indicates the number of
         modify bearer response messages transmitted to this peer with cause
         code not set to request accepted."
    ::= { tmnxMobServS11StatEntry 54 }

tmnxMobServS11StatDelBearrRspFl     OBJECT-TYPE
    SYNTAX      Counter32
    MAX-ACCESS  read-only
    STATUS      current
    DESCRIPTION
        "The value of tmnxMobServS11StatDelBearrRspFl indicates the number of
         delete bearer response messages received from this peer with cause
         code not set to request accepted."
    ::= { tmnxMobServS11StatEntry 55 }

tmnxMobServS11StatCreatBearRspFl    OBJECT-TYPE
    SYNTAX      Counter32
    MAX-ACCESS  read-only
    STATUS      current
    DESCRIPTION
        "The value of tmnxMobServS11StatCreatBearRspFl indicates the number of
         create bearer response messages received from this peer with cause
         code not set to request accepted."
    ::= { tmnxMobServS11StatEntry 56 }

tmnxMobServS11StatCreatSesnRspFl    OBJECT-TYPE
    SYNTAX      Counter32
    MAX-ACCESS  read-only
    STATUS      current
    DESCRIPTION
        "The value of tmnxMobServS11StatCreatSesnRspFl indicates the number of
         create session response messages transmitted to this peer with cause
         code not set to request accepted."
    ::= { tmnxMobServS11StatEntry 57 }

tmnxMobServS11StatRelBearrRespFl    OBJECT-TYPE
    SYNTAX      Counter32
    MAX-ACCESS  read-only
    STATUS      current
    DESCRIPTION
        "The value of tmnxMobServS11StatRelBearrRespFl indicates the number of
         Release Access Bearers Response messages transmitted to this peer with
         cause code not set to request accepted."
    ::= { tmnxMobServS11StatEntry 58 }

tmnxMobServS11StatCrtIndTnlRspFl    OBJECT-TYPE
    SYNTAX      Counter32
    MAX-ACCESS  read-only
    STATUS      current
    DESCRIPTION
        "The value of tmnxMobServS11StatCrtIndTnlRspFl indicates the number of
         Create Indirect Data Forwarding Tunnel Response messages transmitted to
         this peer with cause code not set to request accepted."
    ::= { tmnxMobServS11StatEntry 59 }

tmnxMobServS11StatDelIndTnlRspFl    OBJECT-TYPE
    SYNTAX      Counter32
    MAX-ACCESS  read-only
    STATUS      current
    DESCRIPTION
        "The value of tmnxMobServS11StatDelIndTnlRspFl indicates the number of
         Delete Indirect Data Forwarding Tunnel Response messages transmitted to
         this peer with cause code not set to request accepted."
    ::= { tmnxMobServS11StatEntry 60 }

tmnxMobServS11StatRxDlAcksFail      OBJECT-TYPE
    SYNTAX      Counter32
    MAX-ACCESS  read-only
    STATUS      current
    DESCRIPTION
        "The value of tmnxMobServS11StatRxDlAcksFail indicates the number of
         downlink data notification acknowledgements received from this peer
         with cause code not set to request accepted."
    ::= { tmnxMobServS11StatEntry 61 }

--
--  S1u peer list Table
--

tmnxMobServS1uPeerTableLastChngd     OBJECT-TYPE
    SYNTAX      TimeStamp
    MAX-ACCESS  read-only
    STATUS      current
    DESCRIPTION
        "The value of tmnxMobServS1uPeerTableLastChngd indicates the sysUpTime
         at the time of the last modification to tmnxMobServS1uPeerTable by
         adding, deleting an entry or change to a writable object in the table.

         If no changes were made to the table since the last re-initialization
         of the local network management subsystem, then this object contains
         a zero value."
    ::= { tmnxMobServingGlobalObjs 12 }

tmnxMobServS1uPeerTable  OBJECT-TYPE
    SYNTAX      SEQUENCE OF TmnxMobServS1uPeerEntry
    MAX-ACCESS  not-accessible
    STATUS      current
    DESCRIPTION
        "The tmnxMobServS1uPeerTable has an entry for each peer on the S1-U
         reference point served by a Serving Gateway (SGW)."
    ::= { tmnxMobServingStatObjs 12 }

tmnxMobServS1uPeerEntry  OBJECT-TYPE
    SYNTAX      TmnxMobServS1uPeerEntry
    MAX-ACCESS  not-accessible
    STATUS      current
    DESCRIPTION
        "Each row entry represents a peer on the S1-U reference point."
    INDEX { vRtrID,
            tmnxMobServS1uPeerAddressType,
            tmnxMobServS1uPeerAddress,
            tmnxMobServS1uPeerPort
          }
    ::= { tmnxMobServS1uPeerTable 1 }

TmnxMobServS1uPeerEntry ::= SEQUENCE {
        tmnxMobServS1uPeerAddressType       InetAddressType,
        tmnxMobServS1uPeerAddress           InetAddress,
        tmnxMobServS1uPeerPort              InetPortNumber,
        tmnxMobServS1uPeerLastChanged       TimeStamp,
        tmnxMobServS1uPeerCreateTime        TimeStamp,
        tmnxMobServS1uPeerPathMgmtState     TmnxMobPathMgmtState,
        tmnxMobServS1uPeerGatewayId         TmnxMobGwId
    }

tmnxMobServS1uPeerAddressType  OBJECT-TYPE
    SYNTAX      InetAddressType
    MAX-ACCESS  not-accessible
    STATUS      current
    DESCRIPTION
        "The value of tmnxMobServS1uPeerAddressType indicates the type of
         address represented by tmnxMobServS1uPeerAddress."
    ::= { tmnxMobServS1uPeerEntry 1 }

tmnxMobServS1uPeerAddress  OBJECT-TYPE
    SYNTAX      InetAddress (SIZE (4|16))
    MAX-ACCESS  not-accessible
    STATUS      current
    DESCRIPTION
        "The value of tmnxMobServS1uPeerAddress indicates the IP address of the
         peer on S1-U reference point."
    ::= { tmnxMobServS1uPeerEntry 2 }

tmnxMobServS1uPeerPort  OBJECT-TYPE
    SYNTAX      InetPortNumber
    MAX-ACCESS  not-accessible
    STATUS      current
    DESCRIPTION
        "The value of tmnxMobServS1uPeerPort indicates the port number of this
         peer."
    ::= { tmnxMobServS1uPeerEntry 3 }

tmnxMobServS1uPeerLastChanged  OBJECT-TYPE
    SYNTAX      TimeStamp
    MAX-ACCESS  read-only
    STATUS      current
    DESCRIPTION
        "The value of tmnxMobServS1uPeerLastChanged indicates the timestamp of
         the last change to this row in tmnxMobServS1uPeerTable."
    ::= { tmnxMobServS1uPeerEntry 4 }

tmnxMobServS1uPeerCreateTime  OBJECT-TYPE
    SYNTAX      TimeStamp
    MAX-ACCESS  read-only
    STATUS      current
    DESCRIPTION
        "The value of tmnxMobServS1uPeerCreateTime indicates the sysUpTime when
         this entry was created."
    ::= { tmnxMobServS1uPeerEntry 5 }

tmnxMobServS1uPeerPathMgmtState  OBJECT-TYPE
    SYNTAX      TmnxMobPathMgmtState
    MAX-ACCESS  read-only
    STATUS      current
    DESCRIPTION
        "The value of tmnxMobServS1uPeerPathMgmtState indicates the state of
         the path."
    ::= { tmnxMobServS1uPeerEntry 6 }

tmnxMobServS1uPeerGatewayId  OBJECT-TYPE
    SYNTAX      TmnxMobGwId
    MAX-ACCESS  read-only
    STATUS      current
    DESCRIPTION
        "The value of tmnxMobServS1uPeerGatewayId indicates the gateway
         to which this peer belongs."
    ::= { tmnxMobServS1uPeerEntry 7 }

--
--  S1u Stats Table
--

tmnxMobServS1uStatTable  OBJECT-TYPE
    SYNTAX      SEQUENCE OF TmnxMobServS1uStatEntry
    MAX-ACCESS  not-accessible
    STATUS      current
    DESCRIPTION
        "The tmnxMobServS1uStatTable has an entry for each peer on the S1-U
         reference point served by a Serving Gateway (SGW)."
    ::= { tmnxMobServingStatObjs 13 }

tmnxMobServS1uStatEntry  OBJECT-TYPE
    SYNTAX      TmnxMobServS1uStatEntry
    MAX-ACCESS  not-accessible
    STATUS      current
    DESCRIPTION
        "Each row entry represents a peer on the S1-U reference point and
         contain statistics for this peer on a card."
    INDEX { vRtrID,
            tmnxMobServS1uPeerAddressType,
            tmnxMobServS1uPeerAddress,
            tmnxMobServS1uPeerPort,
            tmnxChassisIndex,
            tmnxCardSlotNum
          }
    ::= { tmnxMobServS1uStatTable 1 }

TmnxMobServS1uStatEntry ::= SEQUENCE {
        tmnxMobServS1uStatBcNotFound        Counter32,
        tmnxMobServS1uStatRxEchoRequests    Counter32,
        tmnxMobServS1uStatTxEchoResponse    Counter32,
        tmnxMobServS1uStatTxEchoRequests    Counter32,
        tmnxMobServS1uStatRxEchoResponse    Counter32,
        tmnxMobServS1uStatPeerRestarts      Counter32,
        tmnxMobServS1uStatPeerRestartCnt    Counter32,
        tmnxMobServS1uStatPathMgmtFails     Counter32,
        tmnxMobServS1uStatBearersIpv4       Gauge32,
        tmnxMobServS1uStatBearersIpv6       Gauge32,
        tmnxMobServS1uStatBearerIpv4v6      Gauge32,
        tmnxMobServS1uStatDedctdBearers     Gauge32,
        tmnxMobServS1uStatUlBytes           Counter32,
        tmnxMobServS1uStatDlBytes           Counter32,
        tmnxMobServS1uStatUlPackets         Counter32,
        tmnxMobServS1uStatDlPackets         Counter32,
        tmnxMobServS1uStatBearers           Gauge32,
        tmnxMobServS1uStatDefBearers        Gauge32,
        tmnxMobServS1uStatRoamers           Gauge32,
        tmnxMobServS1uStatActiveBearers     Gauge32,
        tmnxMobServS1uStatIdleBearers       Gauge32
    }

tmnxMobServS1uStatBcNotFound  OBJECT-TYPE
    SYNTAX      Counter32
    MAX-ACCESS  read-only
    STATUS      current
    DESCRIPTION
        "The value of tmnxMobServS1uStatBcNotFound indicates the number of
         bearer context not found errors on this peer."
    ::= { tmnxMobServS1uStatEntry 1 }

tmnxMobServS1uStatRxEchoRequests  OBJECT-TYPE
    SYNTAX      Counter32
    MAX-ACCESS  read-only
    STATUS      current
    DESCRIPTION
        "The value of tmnxMobServS1uStatRxEchoRequests indicates the number of
         echo request messages received from this peer."
    ::= { tmnxMobServS1uStatEntry 2 }

tmnxMobServS1uStatTxEchoResponse  OBJECT-TYPE
    SYNTAX      Counter32
    MAX-ACCESS  read-only
    STATUS      current
    DESCRIPTION
        "The value of tmnxMobServS1uStatTxEchoResponse indicates the number of
         echo response messages transmitted to this peer."
    ::= { tmnxMobServS1uStatEntry 3 }

tmnxMobServS1uStatTxEchoRequests  OBJECT-TYPE
    SYNTAX      Counter32
    MAX-ACCESS  read-only
    STATUS      current
    DESCRIPTION
        "The value of tmnxMobServS1uStatTxEchoRequests indicates the number of
         echo request messages transmitted to this peer."
    ::= { tmnxMobServS1uStatEntry 4 }

tmnxMobServS1uStatRxEchoResponse  OBJECT-TYPE
    SYNTAX      Counter32
    MAX-ACCESS  read-only
    STATUS      current
    DESCRIPTION
        "The value of tmnxMobServS1uStatRxEchoResponse indicates the number of
         echo response messages received from this peer."
    ::= { tmnxMobServS1uStatEntry 5 }

tmnxMobServS1uStatPeerRestarts  OBJECT-TYPE
    SYNTAX      Counter32
    MAX-ACCESS  read-only
    STATUS      current
    DESCRIPTION
        "The value of tmnxMobServS1uStatPeerRestarts indicates the number of
         times this peer restarted."
    ::= { tmnxMobServS1uStatEntry 6 }

tmnxMobServS1uStatPeerRestartCnt  OBJECT-TYPE
    SYNTAX      Counter32
    MAX-ACCESS  read-only
    STATUS      current
    DESCRIPTION
        "The value of tmnxMobServS1uStatPeerRestartCnt indicates the counter
         value of the number of times this peer restarted."
    ::= { tmnxMobServS1uStatEntry 7 }

tmnxMobServS1uStatPathMgmtFails  OBJECT-TYPE
    SYNTAX      Counter32
    MAX-ACCESS  read-only
    STATUS      current
    DESCRIPTION
        "The value of tmnxMobServS1uStatPathMgmtFails indicates the number of
         path management failures for this peer."
    ::= { tmnxMobServS1uStatEntry 8 }

tmnxMobServS1uStatBearersIpv4  OBJECT-TYPE
    SYNTAX      Gauge32
    MAX-ACCESS  read-only
    STATUS      obsolete
    DESCRIPTION
        "The value of tmnxMobServS1uStatBearersIpv4 indicates the number of
         IPv4 bearers being served by this peer.

         This object was made obsolete in the 3.1R2 release."
    ::= { tmnxMobServS1uStatEntry 9 }

tmnxMobServS1uStatBearersIpv6  OBJECT-TYPE
    SYNTAX      Gauge32
    MAX-ACCESS  read-only
    STATUS      obsolete
    DESCRIPTION
        "The value of tmnxMobServS1uStatBearersIpv6 indicates the number of
         IPv6 bearers being served by this peer.

         This object was made obsolete in the 3.1R2 release."
    ::= { tmnxMobServS1uStatEntry 10 }

tmnxMobServS1uStatBearerIpv4v6  OBJECT-TYPE
    SYNTAX      Gauge32
    MAX-ACCESS  read-only
    STATUS      obsolete
    DESCRIPTION
        "The value of tmnxMobServS1uStatBearerIpv4v6 indicates the number of
         IPv4v6 bearers being served by this peer.

         This object was made obsolete in the 3.1R2 release."
    ::= { tmnxMobServS1uStatEntry 11 }

tmnxMobServS1uStatDedctdBearers  OBJECT-TYPE
    SYNTAX      Gauge32
    MAX-ACCESS  read-only
    STATUS      obsolete
    DESCRIPTION
        "The value of tmnxMobServS1uStatDedctdBearers indicates the number of
         dedicated bearers being served by this peer.

         This object was made obsolete in the 3.1R2 release."
    ::= { tmnxMobServS1uStatEntry 12 }

tmnxMobServS1uStatUlBytes  OBJECT-TYPE
    SYNTAX      Counter32
    MAX-ACCESS  read-only
    STATUS      current
    DESCRIPTION
        "The value of tmnxMobServS1uStatUlBytes indicates the number of
         uplink bytes received from this peer."
    ::= { tmnxMobServS1uStatEntry 13 }

tmnxMobServS1uStatDlBytes  OBJECT-TYPE
    SYNTAX      Counter32
    MAX-ACCESS  read-only
    STATUS      current
    DESCRIPTION
        "The value of tmnxMobServS1uStatDlBytes indicates the number of
         downlink bytes transmitted to this peer."
    ::= { tmnxMobServS1uStatEntry 14 }

tmnxMobServS1uStatUlPackets  OBJECT-TYPE
    SYNTAX      Counter32
    MAX-ACCESS  read-only
    STATUS      current
    DESCRIPTION
        "The value of tmnxMobServS1uStatUlPackets indicates the number of
         uplink packets received from this peer."
    ::= { tmnxMobServS1uStatEntry 15 }

tmnxMobServS1uStatDlPackets  OBJECT-TYPE
    SYNTAX      Counter32
    MAX-ACCESS  read-only
    STATUS      current
    DESCRIPTION
        "The value of tmnxMobServS1uStatDlPackets indicates the number of
         downlink packets transmitted to this peer."
    ::= { tmnxMobServS1uStatEntry 16 }

tmnxMobServS1uStatBearers  OBJECT-TYPE
    SYNTAX      Gauge32
    MAX-ACCESS  read-only
    STATUS      current
    DESCRIPTION
        "The value of tmnxMobServS1uStatBearers indicates the total number of
         bearers being served by this peer."
    ::= { tmnxMobServS1uStatEntry 17 }

tmnxMobServS1uStatDefBearers  OBJECT-TYPE
    SYNTAX      Gauge32
    MAX-ACCESS  read-only
    STATUS      obsolete
    DESCRIPTION
        "The value of tmnxMobServS1uStatDefBearers indicates the number of
         default bearers being served by this peer.

         This object was made obsolete in the 3.1R2 release."
    ::= { tmnxMobServS1uStatEntry 18 }

tmnxMobServS1uStatRoamers  OBJECT-TYPE
    SYNTAX      Gauge32
    MAX-ACCESS  read-only
    STATUS      obsolete
    DESCRIPTION
        "The value of tmnxMobServS1uStatRoamers indicates the number of
         roamers being served by this peer.

         This object was made obsolete in the 3.1R2 release."
    ::= { tmnxMobServS1uStatEntry 19 }

tmnxMobServS1uStatActiveBearers  OBJECT-TYPE
    SYNTAX      Gauge32
    MAX-ACCESS  read-only
    STATUS      obsolete
    DESCRIPTION
        "The value of tmnxMobServS1uStatActiveBearers indicates the number of
         active bearers being served by this peer.

         This object was made obsolete in the 3.1R2 release."
    ::= { tmnxMobServS1uStatEntry 20 }

tmnxMobServS1uStatIdleBearers  OBJECT-TYPE
    SYNTAX      Gauge32
    MAX-ACCESS  read-only
    STATUS      obsolete
    DESCRIPTION
        "The value of tmnxMobServS1uStatIdleBearers indicates the number of
         Idle bearers being served by this peer.

         This object was made obsolete in the 3.1R2 release."
    ::= { tmnxMobServS1uStatEntry 21 }

--
--  Ga peer list Table
--

tmnxMobSgwGaPeerTableLastChngd     OBJECT-TYPE
    SYNTAX      TimeStamp
    MAX-ACCESS  read-only
    STATUS      current
    DESCRIPTION
        "The value of tmnxMobSgwGaPeerTableLastChngd indicates the sysUpTime
         at the time of the last modification to tmnxMobSgwGaPeerTable by
         adding, deleting an entry or change to a writable object in the table.

         If no changes were made to the table since the last re-initialization
         of the local network management subsystem, then this object contains
         a zero value."
    ::= { tmnxMobServingGlobalObjs 24 }

tmnxMobSgwGaPeerTable  OBJECT-TYPE
    SYNTAX      SEQUENCE OF TmnxMobSgwGaPeerEntry
    MAX-ACCESS  not-accessible
    STATUS      current
    DESCRIPTION
        "The tmnxMobSgwGaPeerTable has an entry for each peer on the Ga
         reference point served by a Serving Gateway (SGW)."
    ::= { tmnxMobServingStatObjs 14 }

tmnxMobSgwGaPeerEntry  OBJECT-TYPE
    SYNTAX      TmnxMobSgwGaPeerEntry
    MAX-ACCESS  not-accessible
    STATUS      current
    DESCRIPTION
        "Each row entry represents a peer on the Ga reference point."
    INDEX { tmnxMobGwId,
            vRtrID,
            tmnxMobGtpPriGrpName,
            tmnxMobGtpPriServerIndex,
            tmnxMobSgwGaStatAddressType,
            tmnxMobSgwGaStatAddress,
            tmnxMobSgwGaStatPort
          }
    ::= { tmnxMobSgwGaPeerTable 1 }

TmnxMobSgwGaPeerEntry ::= SEQUENCE {
        tmnxMobSgwGaPeerLastChanged       TimeStamp,
        tmnxMobSgwGaPeerCreateTime        TimeStamp,
        tmnxMobSgwGaPeerPathMgmtState     TmnxMobDiaPathMgmtState,
        tmnxMobSgwGaPeerDetailState       TmnxMobDiaDetailPathMgmtState
    }

tmnxMobSgwGaPeerLastChanged  OBJECT-TYPE
    SYNTAX      TimeStamp
    MAX-ACCESS  read-only
    STATUS      current
    DESCRIPTION
        "The value of tmnxMobSgwGaPeerLastChanged indicates the timestamp of
         the last change to this row in tmnxMobSgwGaPeerTable."
    ::= { tmnxMobSgwGaPeerEntry 1 }

tmnxMobSgwGaPeerCreateTime  OBJECT-TYPE
    SYNTAX      TimeStamp
    MAX-ACCESS  read-only
    STATUS      current
    DESCRIPTION
        "The value of tmnxMobSgwGaPeerCreateTime indicates the sysUpTime when
         this entry was created."
    ::= { tmnxMobSgwGaPeerEntry 2 }

tmnxMobSgwGaPeerPathMgmtState  OBJECT-TYPE
    SYNTAX      TmnxMobDiaPathMgmtState
    MAX-ACCESS  read-only
    STATUS      current
    DESCRIPTION
        "The value of tmnxMobSgwGaPeerPathMgmtState indicates the state of
         the path."
    ::= { tmnxMobSgwGaPeerEntry 3 }

tmnxMobSgwGaPeerDetailState  OBJECT-TYPE
    SYNTAX      TmnxMobDiaDetailPathMgmtState
    MAX-ACCESS  read-only
    STATUS      current
    DESCRIPTION
        "The value of tmnxMobSgwGaPeerDetailState indicates the detail state
         of the path."
    ::= { tmnxMobSgwGaPeerEntry 4 }

--
--  Ga Stats Table
--

tmnxMobSgwGaStatTable  OBJECT-TYPE
    SYNTAX      SEQUENCE OF TmnxMobSgwGaStatEntry
    MAX-ACCESS  not-accessible
    STATUS      current
    DESCRIPTION
        "The tmnxMobSgwGaStatTable has an entry for each peer on the Ga
         reference point served by a Serving Gateway (SGW)."
    ::= { tmnxMobServingStatObjs 15 }

tmnxMobSgwGaStatEntry  OBJECT-TYPE
    SYNTAX      TmnxMobSgwGaStatEntry
    MAX-ACCESS  not-accessible
    STATUS      current
    DESCRIPTION
        "Each row entry represents a peer on the Ga reference point and
         contain statistics for this peer on a card."
    INDEX { tmnxMobGwId,
            vRtrID,
            tmnxMobGtpPriGrpName,
            tmnxMobGtpPriServerIndex,
            tmnxMobSgwGaStatAddressType,
            tmnxMobSgwGaStatAddress,
            tmnxMobSgwGaStatPort,
            tmnxChassisIndex,
            tmnxCardSlotNum
          }
    ::= { tmnxMobSgwGaStatTable 1 }

TmnxMobSgwGaStatEntry ::= SEQUENCE {
        tmnxMobSgwGaStatAddressType         InetAddressType,
        tmnxMobSgwGaStatAddress             InetAddress,
        tmnxMobSgwGaStatPort                InetPortNumber,
        tmnxMobSgwGaStatLastChanged         TimeStamp,
        tmnxMobSgwGaStatCreateTime          TimeStamp,
        tmnxMobSgwGaStatRxEchoRequests      Counter32,
        tmnxMobSgwGaStatTxEchoResponses     Counter32,
        tmnxMobSgwGaStatTxEchoRequests      Counter32,
        tmnxMobSgwGaStatRxEchoResponses     Counter32,
        tmnxMobSgwGaStatRxNodeAlRequests    Counter32,
        tmnxMobSgwGaStatTxNodeAlResps       Counter32,
        tmnxMobSgwGaStatTxDataRecReqs       Counter32,
        tmnxMobSgwGaStatTxDataRecTferReq    Counter32,
        tmnxMobSgwGaStatRetrDataRecReqs     Counter32,
        tmnxMobSgwGaStatRxDataRecReqs       Counter32,
        tmnxMobSgwGaStatUnackDataRexReqs    Counter32,
        tmnxMobSgwGaStatRxRedirectionReq    Counter32,
        tmnxMobSgwGaStatTxRedrnResp         Counter32,
        tmnxMobSgwGaStatRxInvalidMsgs       Counter32,
        tmnxMobSgwGaStatRxVerNotSupp        Counter32,
        tmnxMobSgwGaStatTxCdrTermination    Counter32,
        tmnxMobSgwGaStatTxCdrMaxChngCond    Counter32,
        tmnxMobSgwGaStatTxCdrMsTmzChng      Counter32,
        tmnxMobSgwGaStatTxCdrRatChng        Counter32,
        tmnxMobSgwGaStatTxCdrTimeLimit      Counter32,
        tmnxMobSgwGaStatTxCdrVolLimit       Counter32,
        tmnxMobSgwGaStatRxCdrReqAcc         Counter32,
        tmnxMobSgwGaStatRxCdrNoResAva       Counter32,
        tmnxMobSgwGaStatRxCdrReqNotFf       Counter32,
        tmnxMobSgwGaStatRxCdrReqFfilled     Counter32,
        tmnxMobSgwGaStatRxCdrDupReqFf       Counter32,
        tmnxMobSgwGaStatRxCdrInvMsgFmat     Counter32,
        tmnxMobSgwGaStatRxCdrVerNotSupp     Counter32,
        tmnxMobSgwGaStatRxCdrSrvcNotSupp    Counter32,
        tmnxMobSgwGaStatRxCdrMandIeInc      Counter32,
        tmnxMobSgwGaStatRxCdrMandIeMiss     Counter32,
        tmnxMobSgwGaStatRxCdrOptIeInc       Counter32,
        tmnxMobSgwGaStatRxCdrSystemFail     Counter32,
        tmnxMobSgwGaStatRtrEchoRequests     Counter32,
        tmnxMobSgwGaStatGtpPrimeFail        Counter32,
        tmnxMobSgwGaStatOperState           INTEGER,
        tmnxMobSgwGaStatUpTime              TimeStamp,
        tmnxMobSgwGaStatTxNodeAlRequests    Counter32,
        tmnxMobSgwGaStatRxNodeAlResps       Counter32,
        tmnxMobSgwGaStatNodeAlReqRetried    Counter32,
        tmnxMobSgwGaStatCdrsTx              Counter32,
        tmnxMobSgwGaStatCdrsRx              Counter32,
        tmnxMobSgwGaStatTxCdrSerNdChLmt     Counter32,
        tmnxMobSgwGaStatTxVerNotSupp        Counter32,
        tmnxMobSgwGaStatTxCdrMgmtInterv     Counter32
    }

tmnxMobSgwGaStatAddressType  OBJECT-TYPE
    SYNTAX      InetAddressType
    MAX-ACCESS  not-accessible
    STATUS      current
    DESCRIPTION
        "The value of tmnxMobSgwGaStatAddressType indicates the type of
         address represented by tmnxMobSgwGaStatAddress.

         When the value of tmnxMobSgwGaStatAddressType is unknown then the peer
         is a Fully Qualified Domain Name (FQDN) address and this entry
         represents an aggregate of all the peer IP addresses that this FQDN
         resolves to."
    ::= { tmnxMobSgwGaStatEntry 1 }

tmnxMobSgwGaStatAddress  OBJECT-TYPE
    SYNTAX      InetAddress (SIZE (0|4|16))
    MAX-ACCESS  not-accessible
    STATUS      current
    DESCRIPTION
        "The value of tmnxMobSgwGaStatAddress indicates the IP address of the
         peer on Ga reference point.

         When the length of tmnxMobSgwGaStatAddress is equal to 0 then the peer
         is a Fully Qualified Domain Name (FQDN) address and this entry
         represents an aggregate of all the peer IP addresses that this FQDN
         resolves to. In this case the value of tmnxMobSgwGaStatAddressType is
         unknown and the value of tmnxMobSgwGaStatPort is equal to 0."
    ::= { tmnxMobSgwGaStatEntry 2 }

tmnxMobSgwGaStatPort  OBJECT-TYPE
    SYNTAX      InetPortNumber
    MAX-ACCESS  not-accessible
    STATUS      current
    DESCRIPTION
        "The value of tmnxMobSgwGaStatPort indicates the port number of this
         peer.

         When the value of tmnxMobSgwGaStatPort is equal to 0 then the peer is
         a Fully Qualified Domain Name (FQDN) address and this entry represents
         an aggregate of all the peer IP addresses that this FQDN resolves to."
    ::= { tmnxMobSgwGaStatEntry 3 }

tmnxMobSgwGaStatLastChanged  OBJECT-TYPE
    SYNTAX      TimeStamp
    MAX-ACCESS  read-only
    STATUS      current
    DESCRIPTION
        "The value of tmnxMobSgwGaStatLastChanged indicates the timestamp of
         the last change to this row in tmnxMobSgwGaStatTable."
    ::= { tmnxMobSgwGaStatEntry 4 }

tmnxMobSgwGaStatCreateTime  OBJECT-TYPE
    SYNTAX      TimeStamp
    MAX-ACCESS  read-only
    STATUS      current
    DESCRIPTION
        "The value of tmnxMobSgwGaStatCreateTime indicates the sysUpTime when
         this entry was created."
    ::= { tmnxMobSgwGaStatEntry 5 }

tmnxMobSgwGaStatRxEchoRequests  OBJECT-TYPE
    SYNTAX      Counter32
    MAX-ACCESS  read-only
    STATUS      current
    DESCRIPTION
        "The value of tmnxMobSgwGaStatRxEchoRequests indicates the number of
         echo request messages received from this peer."
    ::= { tmnxMobSgwGaStatEntry 6 }

tmnxMobSgwGaStatTxEchoResponses  OBJECT-TYPE
    SYNTAX      Counter32
    MAX-ACCESS  read-only
    STATUS      current
    DESCRIPTION
        "The value of tmnxMobSgwGaStatTxEchoResponses indicates the number of
         echo response messages transmitted to this peer."
    ::= { tmnxMobSgwGaStatEntry 7 }

tmnxMobSgwGaStatTxEchoRequests  OBJECT-TYPE
    SYNTAX      Counter32
    MAX-ACCESS  read-only
    STATUS      current
    DESCRIPTION
        "The value of tmnxMobSgwGaStatTxEchoRequests indicates the number of
         echo request messages transmitted to this peer."
    ::= { tmnxMobSgwGaStatEntry 8 }

tmnxMobSgwGaStatRxEchoResponses  OBJECT-TYPE
    SYNTAX      Counter32
    MAX-ACCESS  read-only
    STATUS      current
    DESCRIPTION
        "The value of tmnxMobSgwGaStatRxEchoResponses indicates the number of
         echo response messages received from this peer."
    ::= { tmnxMobSgwGaStatEntry 9 }

tmnxMobSgwGaStatRxNodeAlRequests  OBJECT-TYPE
    SYNTAX      Counter32
    MAX-ACCESS  read-only
    STATUS      current
    DESCRIPTION
        "The value of tmnxMobSgwGaStatRxNodeAlRequests indicates the number of
         node alive request messages received from this peer."
    ::= { tmnxMobSgwGaStatEntry 10 }

tmnxMobSgwGaStatTxNodeAlResps  OBJECT-TYPE
    SYNTAX      Counter32
    MAX-ACCESS  read-only
    STATUS      current
    DESCRIPTION
        "The value of tmnxMobSgwGaStatTxNodeAlResps indicates the number of
         node alive response messages transmitted to this peer."
    ::= { tmnxMobSgwGaStatEntry 11 }

tmnxMobSgwGaStatTxDataRecReqs  OBJECT-TYPE
    SYNTAX      Counter32
    MAX-ACCESS  read-only
    STATUS      current
    DESCRIPTION
        "The value of tmnxMobSgwGaStatTxDataRecReqs indicates the number of
         Data record requests transmitted to this peer."
    ::= { tmnxMobSgwGaStatEntry 12 }

tmnxMobSgwGaStatTxDataRecTferReq  OBJECT-TYPE
    SYNTAX      Counter32
    MAX-ACCESS  read-only
    STATUS      current
    DESCRIPTION
        "The value of tmnxMobSgwGaStatTxDataRecTferReq indicates the number of
         duplicate Data record transfer requests transmitted to this peer."
    ::= { tmnxMobSgwGaStatEntry 13 }

tmnxMobSgwGaStatRetrDataRecReqs  OBJECT-TYPE
    SYNTAX      Counter32
    MAX-ACCESS  read-only
    STATUS      current
    DESCRIPTION
        "The value of tmnxMobSgwGaStatRetrDataRecReqs indicates the number
        of Data record transfer requests retried to this peer."
    ::= { tmnxMobSgwGaStatEntry 14 }

tmnxMobSgwGaStatRxDataRecReqs  OBJECT-TYPE
    SYNTAX      Counter32
    MAX-ACCESS  read-only
    STATUS      current
    DESCRIPTION
        "The value of tmnxMobSgwGaStatRxDataRecReqs indicates the number of
         Data record transfer requests received by this peer."
    ::= { tmnxMobSgwGaStatEntry 15 }

tmnxMobSgwGaStatUnackDataRexReqs  OBJECT-TYPE
    SYNTAX      Counter32
    MAX-ACCESS  read-only
    STATUS      current
    DESCRIPTION
        "The value of tmnxMobSgwGaStatUnackDataRexReqs indicates the number of
         Data record transfer requests unacknowledged by this peer."
    ::= { tmnxMobSgwGaStatEntry 16 }

tmnxMobSgwGaStatRxRedirectionReq  OBJECT-TYPE
    SYNTAX      Counter32
    MAX-ACCESS  read-only
    STATUS      current
    DESCRIPTION
        "The value of tmnxMobSgwGaStatRxRedirectionReq indicates the number of
         redirection request messages received from this peer."
    ::= { tmnxMobSgwGaStatEntry 17 }

tmnxMobSgwGaStatTxRedrnResp  OBJECT-TYPE
    SYNTAX      Counter32
    MAX-ACCESS  read-only
    STATUS      current
    DESCRIPTION
        "The value of tmnxMobSgwGaStatTxRedrnResp indicates the number of
         redirection request messages transmitted to this peer."
    ::= { tmnxMobSgwGaStatEntry 18 }

tmnxMobSgwGaStatRxInvalidMsgs  OBJECT-TYPE
    SYNTAX      Counter32
    MAX-ACCESS  read-only
    STATUS      current
    DESCRIPTION
        "The value of tmnxMobSgwGaStatRxInvalidMsgs indicates the number of
         invalid messages received from this peer."
    ::= { tmnxMobSgwGaStatEntry 19 }

tmnxMobSgwGaStatRxVerNotSupp  OBJECT-TYPE
    SYNTAX      Counter32
    MAX-ACCESS  read-only
    STATUS      current
    DESCRIPTION
        "The value of tmnxMobSgwGaStatRxVerNotSupp indicates the number of
         version not supported messages received from this peer."
    ::= { tmnxMobSgwGaStatEntry 20 }

tmnxMobSgwGaStatTxCdrTermination  OBJECT-TYPE
    SYNTAX      Counter32
    MAX-ACCESS  read-only
    STATUS      current
    DESCRIPTION
        "The value of tmnxMobSgwGaStatTxCdrTermination indicates the number of
         Charging Data Records (CDR) termination requests transmitted to this
         peer."
    ::= { tmnxMobSgwGaStatEntry 21 }

tmnxMobSgwGaStatTxCdrMaxChngCond  OBJECT-TYPE
    SYNTAX      Counter32
    MAX-ACCESS  read-only
    STATUS      current
    DESCRIPTION
        "The value of tmnxMobSgwGaStatTxCdrMaxChngCond indicates the number of
         Charging Data Records (CDR) maximum change condition requests
         transmitted to this peer."
    ::= { tmnxMobSgwGaStatEntry 22 }

tmnxMobSgwGaStatTxCdrMsTmzChng  OBJECT-TYPE
    SYNTAX      Counter32
    MAX-ACCESS  read-only
    STATUS      current
    DESCRIPTION
        "The value of tmnxMobSgwGaStatTxCdrMsTmzChng indicates the number
        of Charging Data Records (CDR) MS Time Zone Change requests transmitted
        to this peer."
    ::= { tmnxMobSgwGaStatEntry 23 }

tmnxMobSgwGaStatTxCdrRatChng  OBJECT-TYPE
    SYNTAX      Counter32
    MAX-ACCESS  read-only
    STATUS      current
    DESCRIPTION
        "The value of tmnxMobSgwGaStatTxCdrRatChng indicates the number of
         Charging Data Records (CDR) Radio Access Type (RAT) change requests
         transmitted to this peer."
    ::= { tmnxMobSgwGaStatEntry 24 }

tmnxMobSgwGaStatTxCdrTimeLimit  OBJECT-TYPE
    SYNTAX      Counter32
    MAX-ACCESS  read-only
    STATUS      current
    DESCRIPTION
        "The value of tmnxMobSgwGaStatTxCdrTimeLimit indicates the number of
         Charging Data Records (CDR) time limit requests transmitted to this
         peer."
    ::= { tmnxMobSgwGaStatEntry 25 }

tmnxMobSgwGaStatTxCdrVolLimit  OBJECT-TYPE
    SYNTAX      Counter32
    MAX-ACCESS  read-only
    STATUS      current
    DESCRIPTION
        "The value of tmnxMobSgwGaStatTxCdrVolLimit indicates the number of
         Charging Data Records (CDR) volume limit requests transmitted to this
         peer."
    ::= { tmnxMobSgwGaStatEntry 26 }

tmnxMobSgwGaStatRxCdrReqAcc  OBJECT-TYPE
    SYNTAX      Counter32
    MAX-ACCESS  read-only
    STATUS      current
    DESCRIPTION
        "The value of tmnxMobSgwGaStatRxCdrReqAcc indicates the number of
         Charging Data Records (CDR) responses with cause value 'requests
         accepted' received from this peer."
    ::= { tmnxMobSgwGaStatEntry 27 }

tmnxMobSgwGaStatRxCdrNoResAva  OBJECT-TYPE
    SYNTAX      Counter32
    MAX-ACCESS  read-only
    STATUS      current
    DESCRIPTION
        "The value of tmnxMobSgwGaStatRxCdrNoResAva indicates the number of
         Charging Data Records (CDR) responses with cause value 'no resources
         available' received from this peer."
    ::= { tmnxMobSgwGaStatEntry 28 }

tmnxMobSgwGaStatRxCdrReqNotFf  OBJECT-TYPE
    SYNTAX      Counter32
    MAX-ACCESS  read-only
    STATUS      current
    DESCRIPTION
        "The value of tmnxMobSgwGaStatRxCdrReqNotFf indicates the number of
         Charging Data Records (CDR) responses with cause value 'requests not
         fulfilled' received from this peer."
    ::= { tmnxMobSgwGaStatEntry 29 }

tmnxMobSgwGaStatRxCdrReqFfilled  OBJECT-TYPE
    SYNTAX      Counter32
    MAX-ACCESS  read-only
    STATUS      current
    DESCRIPTION
        "The value of tmnxMobSgwGaStatRxCdrReqFfilled indicates the number of
         Charging Data Records (CDR) responses with cause value 'requests
         already fulfilled' received from this peer."
    ::= { tmnxMobSgwGaStatEntry 30 }

tmnxMobSgwGaStatRxCdrDupReqFf  OBJECT-TYPE
    SYNTAX      Counter32
    MAX-ACCESS  read-only
    STATUS      current
    DESCRIPTION
        "The value of tmnxMobSgwGaStatRxCdrDupReqFf indicates the number of
         Charging Data Records (CDR) responses with cause value 'duplicate
         requests already fulfilled' received from this peer."
    ::= { tmnxMobSgwGaStatEntry 31 }

tmnxMobSgwGaStatRxCdrInvMsgFmat  OBJECT-TYPE
    SYNTAX      Counter32
    MAX-ACCESS  read-only
    STATUS      current
    DESCRIPTION
        "The value of tmnxMobSgwGaStatRxCdrInvMsgFmat indicates the number of
         Charging Data Records (CDR) responses with cause value 'invalid message
         format' received from this peer."
    ::= { tmnxMobSgwGaStatEntry 32 }

tmnxMobSgwGaStatRxCdrVerNotSupp  OBJECT-TYPE
    SYNTAX      Counter32
    MAX-ACCESS  read-only
    STATUS      current
    DESCRIPTION
        "The value of tmnxMobSgwGaStatRxCdrVerNotSupp indicates the number of
         Charging Data Records (CDR) responses with cause value 'version not
         supported' received from this peer."
    ::= { tmnxMobSgwGaStatEntry 33 }

tmnxMobSgwGaStatRxCdrSrvcNotSupp  OBJECT-TYPE
    SYNTAX      Counter32
    MAX-ACCESS  read-only
    STATUS      current
    DESCRIPTION
        "The value of tmnxMobSgwGaStatRxCdrSrvcNotSupp indicates the number of
         Charging Data Records (CDR) responses with cause value 'Service not
         supported' received from this peer."
    ::= { tmnxMobSgwGaStatEntry 34 }

tmnxMobSgwGaStatRxCdrMandIeInc  OBJECT-TYPE
    SYNTAX      Counter32
    MAX-ACCESS  read-only
    STATUS      current
    DESCRIPTION
        "The value of tmnxMobSgwGaStatRxCdrMandIeInc indicates the number of
         Charging Data Records (CDR) responses with cause value 'mandatory
         Information Element (IE) incorrect' received from this peer."
    ::= { tmnxMobSgwGaStatEntry 35 }

tmnxMobSgwGaStatRxCdrMandIeMiss  OBJECT-TYPE
    SYNTAX      Counter32
    MAX-ACCESS  read-only
    STATUS      current
    DESCRIPTION
        "The value of tmnxMobSgwGaStatRxCdrMandIeMiss indicates the number of
         Charging Data Records (CDR) responses with cause value 'mandatory
         Information Element (IE) missing' received from this peer."
    ::= { tmnxMobSgwGaStatEntry 36 }

tmnxMobSgwGaStatRxCdrOptIeInc  OBJECT-TYPE
    SYNTAX      Counter32
    MAX-ACCESS  read-only
    STATUS      current
    DESCRIPTION
        "The value of tmnxMobSgwGaStatRxCdrOptIeInc indicates the number of
         Charging Data Records (CDR) responses with cause value 'optional
         Information Element (IE) incorrect' received from this peer."
    ::= { tmnxMobSgwGaStatEntry 37 }

tmnxMobSgwGaStatRxCdrSystemFail  OBJECT-TYPE
    SYNTAX      Counter32
    MAX-ACCESS  read-only
    STATUS      current
    DESCRIPTION
        "The value of tmnxMobSgwGaStatRxCdrSystemFail indicates the number of
         Charging Data Records (CDR) responses with cause value 'system failure'
         received from this peer."
    ::= { tmnxMobSgwGaStatEntry 38 }

tmnxMobSgwGaStatRtrEchoRequests  OBJECT-TYPE
    SYNTAX      Counter32
    MAX-ACCESS  read-only
    STATUS      current
    DESCRIPTION
        "The value of tmnxMobSgwGaStatRtrEchoRequests indicates the number of
         echo request messages retried to this peer."
    ::= { tmnxMobSgwGaStatEntry 39 }


tmnxMobSgwGaStatGtpPrimeFail  OBJECT-TYPE
    SYNTAX      Counter32
    MAX-ACCESS  read-only
    STATUS      current
    DESCRIPTION
        "The value of tmnxMobSgwGaStatGtpPrimeFail indicates the number of
         GPRS Tunneling Protocol (GTP) prime message failures
         transmitted to this peer."
    ::= { tmnxMobSgwGaStatEntry 40 }

tmnxMobSgwGaStatOperState OBJECT-TYPE
    SYNTAX      INTEGER {
                    up      (1),
                    down    (2),
                    active  (3)
                }
    MAX-ACCESS     read-only
    STATUS         current
    DESCRIPTION
        "The value of tmnxMobSgwGaStatOperState indicates the current
         operational state of this group. The operational state may be one of:
         'up'     - connection goes 'up' and is used by the Ga module to send
                    Charging Data Records (CDRs).
         'down'   - connection goes 'down' and is used by the Ga module to send
                    Charging Data Records (CDRs).
         'active' - connection is 'active' and is used by the Ga module to send
                    Charging Data Records (CDRs)."
    ::= { tmnxMobSgwGaStatEntry 41 }

tmnxMobSgwGaStatUpTime OBJECT-TYPE
    SYNTAX      TimeStamp
    MAX-ACCESS  read-only
    STATUS      current
    DESCRIPTION
        "The value of tmnxMobSgwGaStatUpTime indicates the time when the
         connection comes up."
    ::= { tmnxMobSgwGaStatEntry 42 }

tmnxMobSgwGaStatTxNodeAlRequests  OBJECT-TYPE
    SYNTAX      Counter32
    MAX-ACCESS  read-only
    STATUS      current
    DESCRIPTION
        "The value of tmnxMobSgwGaStatTxNodeAlRequests indicates the number of
         node alive request messages transmitted from this peer."
    ::= { tmnxMobSgwGaStatEntry 43 }

tmnxMobSgwGaStatRxNodeAlResps  OBJECT-TYPE
    SYNTAX      Counter32
    MAX-ACCESS  read-only
    STATUS      current
    DESCRIPTION
        "The value of tmnxMobSgwGaStatRxNodeAlResps indicates the number of
         node alive response messages received on this peer."
    ::= { tmnxMobSgwGaStatEntry 44 }

tmnxMobSgwGaStatNodeAlReqRetried  OBJECT-TYPE
    SYNTAX      Counter32
    MAX-ACCESS  read-only
    STATUS      current
    DESCRIPTION
        "The value of tmnxMobSgwGaStatNodeAlReqRetried indicates the number of
         node alive request retry messages transmitted from this peer."
    ::= { tmnxMobSgwGaStatEntry 45 }

tmnxMobSgwGaStatCdrsTx  OBJECT-TYPE
    SYNTAX      Counter32
    MAX-ACCESS  read-only
    STATUS      current
    DESCRIPTION
        "The value of tmnxMobSgwGaStatCdrsTx indicates the total number of
         Charging Data Records (CDR) sent from this peer."
    ::= { tmnxMobSgwGaStatEntry 46 }

tmnxMobSgwGaStatCdrsRx  OBJECT-TYPE
    SYNTAX      Counter32
    MAX-ACCESS  read-only
    STATUS      current
    DESCRIPTION
        "The value of tmnxMobSgwGaStatCdrsRx indicates the total number of
         Charging Data Records (CDR) received on this peer."
    ::= { tmnxMobSgwGaStatEntry 47 }

tmnxMobSgwGaStatTxCdrSerNdChLmt  OBJECT-TYPE
    SYNTAX      Counter32
    MAX-ACCESS  read-only
    STATUS      current
    DESCRIPTION
        "The value of tmnxMobSgwGaStatTxCdrSerNdChLmt indicates the number of
         Charging Data Records (CDR) Serving Node Change Limit requests
         transmitted to this peer."
    ::= { tmnxMobSgwGaStatEntry 48 }

tmnxMobSgwGaStatTxVerNotSupp  OBJECT-TYPE
    SYNTAX      Counter32
    MAX-ACCESS  read-only
    STATUS      current
    DESCRIPTION
        "The value of tmnxMobSgwGaStatTxVerNotSupp indicates the number of
         version not supported messages transmitted to this peer."
    ::= { tmnxMobSgwGaStatEntry 49 }

tmnxMobSgwGaStatTxCdrMgmtInterv  OBJECT-TYPE
    SYNTAX      Counter32
    MAX-ACCESS  read-only
    STATUS      current
    DESCRIPTION
        "The value of tmnxMobSgwGaStatTxCdrMgmtInterv indicates the number of
         Charging Data Records (CDR) transferred due to management intervention
         on this peer."
    ::= { tmnxMobSgwGaStatEntry 50 }

--
--  Thresholds counters Table
--

tmnxMobServThresTable  OBJECT-TYPE
    SYNTAX      SEQUENCE OF TmnxMobServThresEntry
    MAX-ACCESS  not-accessible
    STATUS      current
    DESCRIPTION
        "The tmnxMobServThresTable has an entry for the set of thresholds
         in each Serving Gateway (SGW)."
    ::= { tmnxMobServingStatObjs 16 }

tmnxMobServThresEntry  OBJECT-TYPE
    SYNTAX      TmnxMobServThresEntry
    MAX-ACCESS  not-accessible
    STATUS      current
    DESCRIPTION
        "Each row entry represents a set of thresholds."
    INDEX { tmnxMobGwId }
    ::= { tmnxMobServThresTable 1 }

TmnxMobServThresEntry ::= SEQUENCE {
        tmnxMobServThresLastChanged        TimeStamp,
        tmnxMobServThresBrMgmtLmtUe        Gauge32,
        tmnxMobServThresBrMgmtLmtBr        Gauge32,
        tmnxMobServThresBrMgmtLmtDefBr     Gauge32,
        tmnxMobServThresBrMgmtLmtDedBr     Gauge32,
        tmnxMobServThresBrMgmtLmtActBr     Gauge32,
        tmnxMobServThresBrMgmtLmtUePgd     Gauge32,
        tmnxMobServThresBrMgmtCfsAttch     Gauge32,
        tmnxMobServThresBrMgmtCfsDedBr     Gauge32,
        tmnxMobServThresBrMgmtCfsSvrReq    Gauge32,
        tmnxMobServThresBrMgmtCfsItaRlc    Gauge32,
        tmnxMobServThresBrMgmtCfsItrRlc    Gauge32,
        tmnxMobServThresBrMgmtCfsIdlRlc    Gauge32,
        tmnxMobServThresBrMgmtCffAttch     Gauge32,
        tmnxMobServThresBrMgmtCffDedBr     Gauge32,
        tmnxMobServThresBrMgmtCffPaging    Gauge32,
        tmnxMobServThresBrMgmtCffHdOver    Gauge32,
        tmnxMobServThresBrMgmtCffSvrReq    Gauge32,
        tmnxMobServThresBrMgmtCffSrUnavl   Gauge32,
        tmnxMobServThresBrTrfcThrptUL      Gauge32,
        tmnxMobServThresBrTrfcThrptDL      Gauge32,
        tmnxMobServThresPthMgmtS5Fail      Gauge32,
        tmnxMobServThresPthMgmtS5Restart   Gauge32,
        tmnxMobServThresPthMgmtS5NoResp    Gauge32,
        tmnxMobServThresPthMgmtS11PrPath   Gauge32,
        tmnxMobServThresPthMgmtS11PrRstt   Gauge32,
        tmnxMobServThresPthMgmtS11NoResp   Gauge32,
        tmnxMobServThresPthMgmtS1UENB      Gauge32,
        tmnxMobServThresPthMgmtS11MME      Gauge32,
        tmnxMobServThresPthMgmtS5Peer      Gauge32,
        tmnxMobServThresPthMgmtS8Peer      Gauge32,
        tmnxMobServThresPthMgmtRfFail      Gauge32
    }

tmnxMobServThresLastChanged  OBJECT-TYPE
    SYNTAX      TimeStamp
    MAX-ACCESS  read-only
    STATUS      current
    DESCRIPTION
        "The value of tmnxMobServThresLastChanged indicates the timestamp of
         the last change to this row in tmnxMobServThresTable."
    ::= { tmnxMobServThresEntry 1 }

tmnxMobServThresBrMgmtLmtUe  OBJECT-TYPE
    SYNTAX      Gauge32
    MAX-ACCESS  read-only
    STATUS      current
    DESCRIPTION
        "The value of tmnxMobServThresBrMgmtLmtUe indicates the number of
         User Equipments(UE)."
    ::= { tmnxMobServThresEntry 2 }

tmnxMobServThresBrMgmtLmtBr  OBJECT-TYPE
    SYNTAX      Gauge32
    MAX-ACCESS  read-only
    STATUS      current
    DESCRIPTION
        "The value of tmnxMobServThresBrMgmtLmtBr indicates the number of
         bearers."
    ::= { tmnxMobServThresEntry 3 }

tmnxMobServThresBrMgmtLmtDefBr  OBJECT-TYPE
    SYNTAX      Gauge32
    MAX-ACCESS  read-only
    STATUS      current
    DESCRIPTION
        "The value of tmnxMobServThresBrMgmtLmtDefBr indicates the number of
         default bearers."
    ::= { tmnxMobServThresEntry 4 }

tmnxMobServThresBrMgmtLmtDedBr  OBJECT-TYPE
    SYNTAX      Gauge32
    MAX-ACCESS  read-only
    STATUS      current
    DESCRIPTION
        "The value of tmnxMobServThresBrMgmtLmtDedBr indicates the number of
         dedicated bearers."
    ::= { tmnxMobServThresEntry 5 }

tmnxMobServThresBrMgmtLmtActBr  OBJECT-TYPE
    SYNTAX      Gauge32
    MAX-ACCESS  read-only
    STATUS      current
    DESCRIPTION
        "The value of tmnxMobServThresBrMgmtLmtActBr indicates the number of
         active bearers."
    ::= { tmnxMobServThresEntry 6 }

tmnxMobServThresBrMgmtLmtUePgd  OBJECT-TYPE
    SYNTAX      Gauge32
    MAX-ACCESS  read-only
    STATUS      current
    DESCRIPTION
        "The value of tmnxMobServThresBrMgmtLmtUePgd indicates the number of
         idle User Equipment (UE) paged."
    ::= { tmnxMobServThresEntry 7 }

tmnxMobServThresBrMgmtCfsAttch  OBJECT-TYPE
    SYNTAX      Gauge32
    MAX-ACCESS  read-only
    STATUS      current
    DESCRIPTION
        "The value of tmnxMobServThresBrMgmtCfsAttch indicates the number of
         attaches (call setups)."
    ::= { tmnxMobServThresEntry 8 }

tmnxMobServThresBrMgmtCfsDedBr  OBJECT-TYPE
    SYNTAX      Gauge32
    MAX-ACCESS  read-only
    STATUS      current
    DESCRIPTION
        "The value of tmnxMobServThresBrMgmtCfsDedBr indicates the number of
         dedicated bearers setups."
    ::= { tmnxMobServThresEntry 9 }

tmnxMobServThresBrMgmtCfsSvrReq OBJECT-TYPE
    SYNTAX      Gauge32
    MAX-ACCESS  read-only
    STATUS      current
    DESCRIPTION
        "The value of tmnxMobServThresBrMgmtCfsSvrReq indicates the number of
         service request setups."
    ::= { tmnxMobServThresEntry 10 }

tmnxMobServThresBrMgmtCfsItaRlc OBJECT-TYPE
       SYNTAX      Gauge32
       MAX-ACCESS  read-only
       STATUS      current
       DESCRIPTION
           "The value of tmnxMobServThresBrMgmtCfsItaRlc indicates the number
            of intra serving gateway relocations."
       ::= { tmnxMobServThresEntry 11 }

tmnxMobServThresBrMgmtCfsItrRlc OBJECT-TYPE
       SYNTAX      Gauge32
       MAX-ACCESS  read-only
       STATUS      current
       DESCRIPTION
           "The value of tmnxMobServThresBrMgmtCfsItrRlc indicates the number
            of inter serving gateway relocations."
       ::= { tmnxMobServThresEntry 12 }

tmnxMobServThresBrMgmtCfsIdlRlc  OBJECT-TYPE
    SYNTAX      Gauge32
    MAX-ACCESS  read-only
    STATUS      current
    DESCRIPTION
        "The value of tmnxMobServThresBrMgmtCfsIdlRlc indicates the number of
         inter Serving Gateway idle relocations."
    ::= { tmnxMobServThresEntry 13 }

tmnxMobServThresBrMgmtCffAttch  OBJECT-TYPE
    SYNTAX      Gauge32 (0..100)
    UNITS       "Percent"
    MAX-ACCESS  read-only
    STATUS      current
    DESCRIPTION
        "The value of tmnxMobServThresBrMgmtCffAttch indicates the percentage
         of default bearer setup failures. It is calculated as
         (default bearer setup failures / all default bearer setups) * 100"
    ::= { tmnxMobServThresEntry 14 }

tmnxMobServThresBrMgmtCffDedBr  OBJECT-TYPE
    SYNTAX      Gauge32 (0..100)
    UNITS       "Percent"
    MAX-ACCESS  read-only
    STATUS      current
    DESCRIPTION
        "The value of tmnxMobServThresBrMgmtCffDedBr indicates the percentage
         of dedicated bearer setup failures. It is calculated as
         (dedicated bearer setup failures / all dedicated bearer setups) * 100"
    ::= { tmnxMobServThresEntry 15 }

tmnxMobServThresBrMgmtCffPaging  OBJECT-TYPE
    SYNTAX      Gauge32 (0..100)
    UNITS       "Percent"
    MAX-ACCESS  read-only
    STATUS      current
    DESCRIPTION
        "The value of tmnxMobServThresBrMgmtCffPaging indicates the percentage
         of idle user paging failures. It is calculated as
         (idle user paging failures / all user paging) * 100"
    ::= { tmnxMobServThresEntry 16 }

tmnxMobServThresBrMgmtCffHdOver  OBJECT-TYPE
    SYNTAX      Gauge32 (0..100)
    UNITS       "Percent"
    MAX-ACCESS  read-only
    STATUS      current
    DESCRIPTION
        "The value of tmnxMobServThresBrMgmtCffHdOver indicates the percentage
         of inter Serving Gateway handover failures. It is calculated as
         (inter serving gateway handover failures / all inter serving gateway
         handovers) * 100"
    ::= { tmnxMobServThresEntry 17 }

tmnxMobServThresBrMgmtCffSvrReq   OBJECT-TYPE
       SYNTAX      Gauge32 (0..100)
       UNITS       "Percent"
       MAX-ACCESS  read-only
       STATUS      current
       DESCRIPTION
           "The value of tmnxMobServThresBrMgmtCffSvrReq indicates the
            percentage of service request failures. It is calculated as
            (service request failures / all service request handovers) * 100"
       ::= { tmnxMobServThresEntry 18 }

tmnxMobServThresBrMgmtCffSrUnavl  OBJECT-TYPE
    SYNTAX      Gauge32 (0..100)
    UNITS       "Percent"
    MAX-ACCESS  read-only
    STATUS      current
    DESCRIPTION
        "The value of tmnxMobServThresBrMgmtCffSrUnavl indicates the percentage
         of failures due to system resources unavailable. It is calculated as
        (failures due to system resources unavailable / total failures) * 100"
    ::= { tmnxMobServThresEntry 19 }

tmnxMobServThresBrTrfcThrptUL  OBJECT-TYPE
    SYNTAX      Gauge32
    MAX-ACCESS  read-only
    STATUS      current
    DESCRIPTION
        "The value of tmnxMobServThresBrTrfcThrptUL indicates the uplink
         traffic throughput in mega-bytes per polling period."
    ::= { tmnxMobServThresEntry 20 }

tmnxMobServThresBrTrfcThrptDL  OBJECT-TYPE
    SYNTAX      Gauge32
    MAX-ACCESS  read-only
    STATUS      current
    DESCRIPTION
        "The value of tmnxMobServThresBrTrfcThrptDL indicates the downlink
         traffic throughput in mega-bytes per polling period."
    ::= { tmnxMobServThresEntry 21 }

tmnxMobServThresPthMgmtS5Fail  OBJECT-TYPE
    SYNTAX      Gauge32
    MAX-ACCESS  read-only
    STATUS      current
    DESCRIPTION
        "The value of tmnxMobServThresPthMgmtS5Fail indicates the number of
         S5 path management failures."
    ::= { tmnxMobServThresEntry 22 }

tmnxMobServThresPthMgmtS5Restart  OBJECT-TYPE
    SYNTAX      Gauge32
    MAX-ACCESS  read-only
    STATUS      current
    DESCRIPTION
        "The value of tmnxMobServThresPthMgmtS5Restart indicates the number of
         S5 restarts."
    ::= { tmnxMobServThresEntry 23 }

tmnxMobServThresPthMgmtS5NoResp  OBJECT-TYPE
    SYNTAX      Gauge32
    MAX-ACCESS  read-only
    STATUS      current
    DESCRIPTION
        "The value of tmnxMobServThresPthMgmtS5NoResp indicates the number of
         S5 peer not responding to requests."
    ::= { tmnxMobServThresEntry 24 }

tmnxMobServThresPthMgmtS11PrPath OBJECT-TYPE
    SYNTAX      Gauge32
    MAX-ACCESS  read-only
    STATUS      current
    DESCRIPTION
        "The value of tmnxMobServThresPthMgmtS11PrPath indicates the number of
         total S11 peer path-management failures."
    ::= { tmnxMobServThresEntry 25 }

tmnxMobServThresPthMgmtS11PrRstt OBJECT-TYPE
       SYNTAX      Gauge32
       MAX-ACCESS  read-only
       STATUS      current
       DESCRIPTION
           "The value of tmnxMobServThresPthMgmtS11PrRstt indicates the number
            of total S11 peer restarts."
       ::= { tmnxMobServThresEntry 26 }

tmnxMobServThresPthMgmtS11NoResp OBJECT-TYPE
       SYNTAX      Gauge32
       MAX-ACCESS  read-only
       STATUS      current
       DESCRIPTION
           "The value of tmnxMobServThresPthMgmtS11NoResp indicates the number
            of total S11 peer not responding to control plane request."
       ::= { tmnxMobServThresEntry 27 }

tmnxMobServThresPthMgmtS1UENB OBJECT-TYPE
       SYNTAX      Gauge32
       MAX-ACCESS  read-only
       STATUS      current
       DESCRIPTION
           "The value of tmnxMobServThresPthMgmtS1UENB indicates the number
            of evolved NodeBs (eNBs)."
       ::= { tmnxMobServThresEntry 28 }

tmnxMobServThresPthMgmtS11MME  OBJECT-TYPE
    SYNTAX      Gauge32
    MAX-ACCESS  read-only
    STATUS      current
    DESCRIPTION
        "The value of tmnxMobServThresPthMgmtS11MME indicates the number of
         Mobility Management Entity (MME)."
    ::= { tmnxMobServThresEntry 29 }

tmnxMobServThresPthMgmtS5Peer  OBJECT-TYPE
    SYNTAX      Gauge32
    MAX-ACCESS  read-only
    STATUS      current
    DESCRIPTION
        "The value of tmnxMobServThresPthMgmtS5Peer indicates the number of
         S5 peers."
    ::= { tmnxMobServThresEntry 30 }

tmnxMobServThresPthMgmtS8Peer  OBJECT-TYPE
    SYNTAX      Gauge32
    MAX-ACCESS  read-only
    STATUS      current
    DESCRIPTION
        "The value of tmnxMobServThresPthMgmtS8Peer indicates the number of
         s8 peers."
    ::= { tmnxMobServThresEntry 31 }

tmnxMobServThresPthMgmtRfFail  OBJECT-TYPE
    SYNTAX      Gauge32
    MAX-ACCESS  read-only
    STATUS      current
    DESCRIPTION
        "The value of tmnxMobServThresPthMgmtRfFail indicates the number of
         RF peer path failures."
    ::= { tmnxMobServThresEntry 32 }

--
--  Bearer Context Accounting Ga Table
--

tmnxMobServBcAcctGaTable  OBJECT-TYPE
    SYNTAX      SEQUENCE OF TmnxMobServBcAcctGaEntry
    MAX-ACCESS  not-accessible
    STATUS      current
    DESCRIPTION
        "The tmnxMobServBcAcctGaTable has an entry for each bearer context
         of an User Equipment (UE).

         The tmnxMobServBcAcctGaTable provides an extension of the
         tmnxMobServBearerContextTable."
    ::= { tmnxMobServingStatObjs 17 }

tmnxMobServBcAcctGaEntry  OBJECT-TYPE
    SYNTAX      TmnxMobServBcAcctGaEntry
    MAX-ACCESS  not-accessible
    STATUS      current
    DESCRIPTION
        "Each row entry represents a bearer context of an User Equipment (UE)
         and contains reference point Ga Accounting statistics information."
    AUGMENTS { tmnxMobServBearerContextEntry }
    ::= { tmnxMobServBcAcctGaTable 1 }

TmnxMobServBcAcctGaEntry ::= SEQUENCE {
        tmnxMobServBcAcctGaChargingId       TmnxMobChargingProfile,
        tmnxMobServBcAcctGaUlSustRate       Counter32,
        tmnxMobServBcAcctGaDlSustRate       Counter32,
        tmnxMobServBcAcctGaAggrUlPkts       Counter64,
        tmnxMobServBcAcctGaAggrUlPktsLow    Counter32,
        tmnxMobServBcAcctGaAggrUlPktsHi     Counter32,
        tmnxMobServBcAcctGaAggrDlPkts       Counter64,
        tmnxMobServBcAcctGaAggrDlPktsLow    Counter32,
        tmnxMobServBcAcctGaAggrDlPktsHi     Counter32,
        tmnxMobServBcAcctGaAggrUlByts       Counter64,
        tmnxMobServBcAcctGaAggrUlBytsLow    Counter32,
        tmnxMobServBcAcctGaAggrUlBytsHi     Counter32,
        tmnxMobServBcAcctGaAggrDlByts       Counter64,
        tmnxMobServBcAcctGaAggrDlBytsLow    Counter32,
        tmnxMobServBcAcctGaAggrDlBytsHi     Counter32,
        tmnxMobServBcAcctGaNumPartCdrs      Counter32,
        tmnxMobServBcAcctGaNumTdvs          Counter32,
        tmnxMobServBcAcctGaNumMaxChanges    Counter32
    }

tmnxMobServBcAcctGaChargingId  OBJECT-TYPE
    SYNTAX      TmnxMobChargingProfile
    MAX-ACCESS  read-only
    STATUS      current
    DESCRIPTION
        "The value of tmnxMobServBcAcctGaChargingId indicates the charging
         profile assigned by the Serving Gateway (PGW) for this bearer."
    ::= { tmnxMobServBcAcctGaEntry 1 }

tmnxMobServBcAcctGaUlSustRate  OBJECT-TYPE
    SYNTAX      Counter32
    MAX-ACCESS  read-only
    STATUS      current
    DESCRIPTION
        "The value of tmnxMobServBcAcctGaUlSustRate indicates the uplink
         sustained rate for this bearer since last 5 minutes."
    ::= { tmnxMobServBcAcctGaEntry 2 }

tmnxMobServBcAcctGaDlSustRate  OBJECT-TYPE
    SYNTAX      Counter32
    MAX-ACCESS  read-only
    STATUS      current
    DESCRIPTION
        "The value of tmnxMobServBcAcctGaDlSustRate indicates the downlink
         sustained rate for this bearer since last 5 minutes."
    ::= { tmnxMobServBcAcctGaEntry 3 }

tmnxMobServBcAcctGaAggrUlPkts  OBJECT-TYPE
    SYNTAX      Counter64
    MAX-ACCESS  read-only
    STATUS      current
    DESCRIPTION
        "The value of tmnxMobServBcAcctGaAggrUlPkts indicates the aggregate
         uplink packets for this bearer."
    ::= { tmnxMobServBcAcctGaEntry 4 }

tmnxMobServBcAcctGaAggrUlPktsLow  OBJECT-TYPE
    SYNTAX      Counter32
    MAX-ACCESS  read-only
    STATUS      current
    DESCRIPTION
        "The value of tmnxMobServBcAcctGaAggrUlPktsLow indicates the lower 32
         bits of the value of tmnxMobServBcAcctGaAggrUlPkts."
    ::= { tmnxMobServBcAcctGaEntry 5 }

tmnxMobServBcAcctGaAggrUlPktsHi  OBJECT-TYPE
    SYNTAX      Counter32
    MAX-ACCESS  read-only
    STATUS      current
    DESCRIPTION
        "The value of tmnxMobServBcAcctGaAggrUlPktsHi indicates the higher 32
         bits of the value of tmnxMobServBcAcctGaAggrUlPkts."
    ::= { tmnxMobServBcAcctGaEntry 6 }

tmnxMobServBcAcctGaAggrDlPkts  OBJECT-TYPE
    SYNTAX      Counter64
    MAX-ACCESS  read-only
    STATUS      current
    DESCRIPTION
        "The value of tmnxMobServBcAcctGaAggrDlPkts indicates the aggregate
         downlink packets for this bearer."
    ::= { tmnxMobServBcAcctGaEntry 7 }

tmnxMobServBcAcctGaAggrDlPktsLow  OBJECT-TYPE
    SYNTAX      Counter32
    MAX-ACCESS  read-only
    STATUS      current
    DESCRIPTION
        "The value of tmnxMobServBcAcctGaAggrDlPktsLow indicates the lower 32
         bits of the value of tmnxMobServBcAcctGaAggrDlPkts."
    ::= { tmnxMobServBcAcctGaEntry 8 }

tmnxMobServBcAcctGaAggrDlPktsHi  OBJECT-TYPE
    SYNTAX      Counter32
    MAX-ACCESS  read-only
    STATUS      current
    DESCRIPTION
        "The value of tmnxMobServBcAcctGaAggrDlPktsHi indicates the higher 32
         bits of the value of tmnxMobServBcAcctGaAggrDlPkts."
    ::= { tmnxMobServBcAcctGaEntry 9 }

tmnxMobServBcAcctGaAggrUlByts  OBJECT-TYPE
    SYNTAX      Counter64
    MAX-ACCESS  read-only
    STATUS      current
    DESCRIPTION
        "The value of tmnxMobServBcAcctGaAggrUlByts indicates the aggregate
         uplink bytes for this bearer."
    ::= { tmnxMobServBcAcctGaEntry 10 }

tmnxMobServBcAcctGaAggrUlBytsLow  OBJECT-TYPE
    SYNTAX      Counter32
    MAX-ACCESS  read-only
    STATUS      current
    DESCRIPTION
        "The value of tmnxMobServBcAcctGaAggrUlBytsLow indicates the lower 32
         bits of the value of tmnxMobServBcAcctGaAggrUlByts."
    ::= { tmnxMobServBcAcctGaEntry 11 }

tmnxMobServBcAcctGaAggrUlBytsHi  OBJECT-TYPE
    SYNTAX      Counter32
    MAX-ACCESS  read-only
    STATUS      current
    DESCRIPTION
        "The value of tmnxMobServBcAcctGaAggrUlBytsHi indicates the higher 32
         bits of the value of tmnxMobServBcAcctGaAggrUlByts."
    ::= { tmnxMobServBcAcctGaEntry 12 }

tmnxMobServBcAcctGaAggrDlByts  OBJECT-TYPE
    SYNTAX      Counter64
    MAX-ACCESS  read-only
    STATUS      current
    DESCRIPTION
        "The value of tmnxMobServBcAcctGaAggrDlByts indicates the aggregate
         downlink bytes for this bearer."
    ::= { tmnxMobServBcAcctGaEntry 13 }

tmnxMobServBcAcctGaAggrDlBytsLow  OBJECT-TYPE
    SYNTAX      Counter32
    MAX-ACCESS  read-only
    STATUS      current
    DESCRIPTION
        "The value of tmnxMobServBcAcctGaAggrDlBytsLow indicates the lower 32
         bits of the value of tmnxMobServBcAcctGaAggrDlByts."
    ::= { tmnxMobServBcAcctGaEntry 14 }

tmnxMobServBcAcctGaAggrDlBytsHi  OBJECT-TYPE
    SYNTAX      Counter32
    MAX-ACCESS  read-only
    STATUS      current
    DESCRIPTION
        "The value of tmnxMobServBcAcctGaAggrDlBytsHi indicates the higher 32
         bits of the value of tmnxMobServBcAcctGaAggrDlByts."
    ::= { tmnxMobServBcAcctGaEntry 15 }

tmnxMobServBcAcctGaNumPartCdrs  OBJECT-TYPE
    SYNTAX      Counter32
    MAX-ACCESS  read-only
    STATUS      current
    DESCRIPTION
        "The value of tmnxMobServBcAcctGaNumPartCdrs indicates the number of
         partial Charging Data Requests(CDR) messages for this bearer."
    ::= { tmnxMobServBcAcctGaEntry 16 }

tmnxMobServBcAcctGaNumTdvs  OBJECT-TYPE
    SYNTAX      Counter32
    MAX-ACCESS  read-only
    STATUS      current
    DESCRIPTION
        "The value of tmnxMobServBcAcctGaNumTdvs indicates the number of cached
         Traffic Data Volume (TDV) containers for this bearer."
    ::= { tmnxMobServBcAcctGaEntry 17 }

tmnxMobServBcAcctGaNumMaxChanges  OBJECT-TYPE
    SYNTAX      Counter32
    MAX-ACCESS  read-only
    STATUS      current
    DESCRIPTION
        "The value of tmnxMobServBcAcctGaNumMaxChanges indicates the number of
         maximum change events generated for this bearer."
    ::= { tmnxMobServBcAcctGaEntry 18 }

--
--  PDN Context Rf Acct Table
--

tmnxMobServPcAcctRfTable  OBJECT-TYPE
    SYNTAX      SEQUENCE OF TmnxMobServPcAcctRfEntry
    MAX-ACCESS  not-accessible
    STATUS      current
    DESCRIPTION
        "The tmnxMobServPcAcctRfTable has an entry for each Packet Data
         Network (PDN) context of an User Equipment (UE).

         The tmnxMobServPcAcctRfTable provides an extension of the
         tmnxMobServPdnContextTable for Accounting Rf related information."
    ::= { tmnxMobServingStatObjs 18 }

tmnxMobServPcAcctRfEntry  OBJECT-TYPE
    SYNTAX      TmnxMobServPcAcctRfEntry
    MAX-ACCESS  not-accessible
    STATUS      current
    DESCRIPTION
        "Each row entry represents a Packet Data Network (PDN) context of an
         User Equipment (UE) and contains Accounting Rf interface related
         information."
    AUGMENTS { tmnxMobServPdnContextEntry }
    ::= { tmnxMobServPcAcctRfTable 1 }

TmnxMobServPcAcctRfEntry ::= SEQUENCE {
        tmnxMobServPcAcctRfAggrUlPkts       Counter64,
        tmnxMobServPcAcctRfAggrUlPktsLow    Counter32,
        tmnxMobServPcAcctRfAggrUlPktsHi     Counter32,
        tmnxMobServPcAcctRfAggrDlPkts       Counter64,
        tmnxMobServPcAcctRfAggrDlPktsLow    Counter32,
        tmnxMobServPcAcctRfAggrDlPktsHi     Counter32,
        tmnxMobServPcAcctRfAggrUlByts       Counter64,
        tmnxMobServPcAcctRfAggrUlBytsLow    Counter32,
        tmnxMobServPcAcctRfAggrUlBytsHi     Counter32,
        tmnxMobServPcAcctRfAggrDlByts       Counter64,
        tmnxMobServPcAcctRfAggrDlBytsLow    Counter32,
        tmnxMobServPcAcctRfAggrDlBytsHi     Counter32,
        tmnxMobServPcAcctRfUlAvgRate        Counter32,
        tmnxMobServPcAcctRfDlAvgRate        Counter32,
        tmnxMobServPcAcctRfNumIntrimSent    Counter32
    }

tmnxMobServPcAcctRfAggrUlPkts  OBJECT-TYPE
    SYNTAX      Counter64
    MAX-ACCESS  read-only
    STATUS      current
    DESCRIPTION
        "The value of tmnxMobServPcAcctRfAggrUlPkts indicates the aggregate
         uplink packets for this Packet Data Network (PDN) context."
    ::= { tmnxMobServPcAcctRfEntry 1 }

tmnxMobServPcAcctRfAggrUlPktsLow  OBJECT-TYPE
    SYNTAX      Counter32
    MAX-ACCESS  read-only
    STATUS      current
    DESCRIPTION
        "The value of tmnxMobServPcAcctRfAggrUlPktsLow indicates the lower 32
         bits of the value of tmnxMobServPcAcctRfAggrUlPkts."
    ::= { tmnxMobServPcAcctRfEntry 2 }

tmnxMobServPcAcctRfAggrUlPktsHi  OBJECT-TYPE
    SYNTAX      Counter32
    MAX-ACCESS  read-only
    STATUS      current
    DESCRIPTION
        "The value of tmnxMobServPcAcctRfAggrUlPktsHi indicates the higher 32
         bits of the value of tmnxMobServPcAcctRfAggrUlPkts."
    ::= { tmnxMobServPcAcctRfEntry 3 }

tmnxMobServPcAcctRfAggrDlPkts  OBJECT-TYPE
    SYNTAX      Counter64
    MAX-ACCESS  read-only
    STATUS      current
    DESCRIPTION
        "The value of tmnxMobServPcAcctRfAggrDlPkts indicates the aggregate
         downlink packets for this Packet Data Network (PDN) context."
    ::= { tmnxMobServPcAcctRfEntry 4 }

tmnxMobServPcAcctRfAggrDlPktsLow  OBJECT-TYPE
    SYNTAX      Counter32
    MAX-ACCESS  read-only
    STATUS      current
    DESCRIPTION
        "The value of tmnxMobServPcAcctRfAggrDlPktsLow indicates the lower 32
         bits of the value of tmnxMobServPcAcctRfAggrDlPkts."
    ::= { tmnxMobServPcAcctRfEntry 5 }

tmnxMobServPcAcctRfAggrDlPktsHi  OBJECT-TYPE
    SYNTAX      Counter32
    MAX-ACCESS  read-only
    STATUS      current
    DESCRIPTION
        "The value of tmnxMobServPcAcctRfAggrDlPktsHi indicates the higher 32
         bits of the value of tmnxMobServPcAcctRfAggrDlPkts."
    ::= { tmnxMobServPcAcctRfEntry 6 }

tmnxMobServPcAcctRfAggrUlByts  OBJECT-TYPE
    SYNTAX      Counter64
    MAX-ACCESS  read-only
    STATUS      current
    DESCRIPTION
        "The value of tmnxMobServPcAcctRfAggrUlByts indicates the aggregate
         uplink bytes for this Packet Data Network (PDN) context."
    ::= { tmnxMobServPcAcctRfEntry 7 }

tmnxMobServPcAcctRfAggrUlBytsLow  OBJECT-TYPE
    SYNTAX      Counter32
    MAX-ACCESS  read-only
    STATUS      current
    DESCRIPTION
        "The value of tmnxMobServPcAcctRfAggrUlBytsLow indicates the lower 32
         bits of the value of tmnxMobServPcAcctRfAggrUlByts."
    ::= { tmnxMobServPcAcctRfEntry 8 }

tmnxMobServPcAcctRfAggrUlBytsHi  OBJECT-TYPE
    SYNTAX      Counter32
    MAX-ACCESS  read-only
    STATUS      current
    DESCRIPTION
        "The value of tmnxMobServPcAcctRfAggrUlBytsHi indicates the higher 32
         bits of the value of tmnxMobServPcAcctRfAggrUlByts."
    ::= { tmnxMobServPcAcctRfEntry 9 }

tmnxMobServPcAcctRfAggrDlByts  OBJECT-TYPE
    SYNTAX      Counter64
    MAX-ACCESS  read-only
    STATUS      current
    DESCRIPTION
        "The value of tmnxMobServPcAcctRfAggrDlByts indicates the aggregate
         downlink bytes for this Packet Data Network (PDN) context."
    ::= { tmnxMobServPcAcctRfEntry 10 }

tmnxMobServPcAcctRfAggrDlBytsLow  OBJECT-TYPE
    SYNTAX      Counter32
    MAX-ACCESS  read-only
    STATUS      current
    DESCRIPTION
        "The value of tmnxMobServPcAcctRfAggrDlBytsLow indicates the lower 32
         bits of the value of tmnxMobServPcAcctRfAggrDlByts."
    ::= { tmnxMobServPcAcctRfEntry 11 }

tmnxMobServPcAcctRfAggrDlBytsHi  OBJECT-TYPE
    SYNTAX      Counter32
    MAX-ACCESS  read-only
    STATUS      current
    DESCRIPTION
        "The value of tmnxMobServPcAcctRfAggrDlBytsHi indicates the higher 32
         bits of the value of tmnxMobServPcAcctRfAggrDlByts."
    ::= { tmnxMobServPcAcctRfEntry 12 }

tmnxMobServPcAcctRfUlAvgRate  OBJECT-TYPE
    SYNTAX      Counter32
    UNITS       "kbps"
    MAX-ACCESS  read-only
    STATUS      current
    DESCRIPTION
        "The value of tmnxMobServPcAcctRfUlAvgRate indicates the average uplink
         traffic on this Packet Data Network (PDN) context."
    ::= { tmnxMobServPcAcctRfEntry 13 }

tmnxMobServPcAcctRfDlAvgRate  OBJECT-TYPE
    SYNTAX      Counter32
    UNITS       "kbps"
    MAX-ACCESS  read-only
    STATUS      current
    DESCRIPTION
        "The value of tmnxMobServPcAcctRfDlAvgRate indicates the average downlink
         traffic on this Packet Data Network (PDN) context."
    ::= { tmnxMobServPcAcctRfEntry 14 }

tmnxMobServPcAcctRfNumIntrimSent  OBJECT-TYPE
    SYNTAX      Counter32
    MAX-ACCESS  read-only
    STATUS      current
    DESCRIPTION
        "The value of tmnxMobServPcAcctRfNumIntrimSent indicates the number of
         interim accounting messages sent for this Packet Data Network (PDN)
         context."
    ::= { tmnxMobServPcAcctRfEntry 15 }

--
--  S11 Cause Codes Stats Table
--

tmnxMobServS11CauseCodeTable  OBJECT-TYPE
    SYNTAX      SEQUENCE OF TmnxMobServS11CauseCodeEntry
    MAX-ACCESS  not-accessible
    STATUS      current
    DESCRIPTION
        "The tmnxMobServS11CauseCodeTable has an entry for each peer on the S11
         reference point."
    ::= { tmnxMobServingStatObjs 19 }

tmnxMobServS11CauseCodeEntry  OBJECT-TYPE
    SYNTAX      TmnxMobServS11CauseCodeEntry
    MAX-ACCESS  not-accessible
    STATUS      current
    DESCRIPTION
        "Each row entry represents a peer on the S11 reference point
         and contains cause code statistics for this peer on a card."
    AUGMENTS { tmnxMobServS11StatEntry }
    ::= { tmnxMobServS11CauseCodeTable 1 }

TmnxMobServS11CauseCodeEntry ::= SEQUENCE {
        tmnxMobServS11CcRxReqAccepted        Counter32,
        tmnxMobServS11CcRxCtxNotFound        Counter32,
        tmnxMobServS11CcRxInvalidLength      Counter32,
        tmnxMobServS11CcRxMndIeIncorrect     Counter32,
        tmnxMobServS11CcRxMandIeMissing      Counter32,
        tmnxMobServS11CcRxReqRejected        Counter32,
        tmnxMobServS11CcRxRemPeerNoResp      Counter32,
        tmnxMobServS11CcRxNoResAvailable     Counter32,
        tmnxMobServS11CcRxUsrAuthFailure     Counter32,
        tmnxMobServS11CcRxOthers             Counter32,
        tmnxMobServS11CcTxReqAccepted        Counter32,
        tmnxMobServS11CcTxCtxNotFound        Counter32,
        tmnxMobServS11CcTxInvalidLength      Counter32,
        tmnxMobServS11CcTxMndIeIncorrect     Counter32,
        tmnxMobServS11CcTxMandIeMissing      Counter32,
        tmnxMobServS11CcTxReqRejected        Counter32,
        tmnxMobServS11CcTxRemPeerNoResp      Counter32,
        tmnxMobServS11CcTxNoResAvailable     Counter32,
        tmnxMobServS11CcTxUsrAuthFailure     Counter32,
        tmnxMobServS11CcTxOthers             Counter32
    }

tmnxMobServS11CcRxReqAccepted  OBJECT-TYPE
    SYNTAX      Counter32
    MAX-ACCESS  read-only
    STATUS      current
    DESCRIPTION
        "The value of tmnxMobServS11CcRxReqAccepted indicates the number of
         messages received on this peer with cause code set to request
         accepted."
    ::= { tmnxMobServS11CauseCodeEntry 1 }

tmnxMobServS11CcRxCtxNotFound  OBJECT-TYPE
    SYNTAX      Counter32
    MAX-ACCESS  read-only
    STATUS      current
    DESCRIPTION
        "The value of tmnxMobServS11CcRxCtxNotFound indicates the number of
         messages received on this peer with cause code set to context not
         found."
    ::= { tmnxMobServS11CauseCodeEntry 2 }

tmnxMobServS11CcRxInvalidLength  OBJECT-TYPE
    SYNTAX      Counter32
    MAX-ACCESS  read-only
    STATUS      current
    DESCRIPTION
        "The value of tmnxMobServS11CcRxInvalidLength indicates the number of
         messages received on this peer with cause code set to invalid length."
    ::= { tmnxMobServS11CauseCodeEntry 3 }

tmnxMobServS11CcRxMndIeIncorrect  OBJECT-TYPE
    SYNTAX      Counter32
    MAX-ACCESS  read-only
    STATUS      current
    DESCRIPTION
        "The value of tmnxMobServS11CcRxMndIeIncorrect indicates the number of
         messages received on this peer with cause code set to mandatory
         Information Elements (IE) incorrect."
    ::= { tmnxMobServS11CauseCodeEntry 4 }

tmnxMobServS11CcRxMandIeMissing  OBJECT-TYPE
    SYNTAX      Counter32
    MAX-ACCESS  read-only
    STATUS      current
    DESCRIPTION
        "The value of tmnxMobServS11CcRxMandIeMissing indicates the number of
         messages received on this peer with cause code set to mandatory
         Information Elements (IE) missing."
    ::= { tmnxMobServS11CauseCodeEntry 5 }

tmnxMobServS11CcRxReqRejected  OBJECT-TYPE
    SYNTAX      Counter32
    MAX-ACCESS  read-only
    STATUS      current
    DESCRIPTION
        "The value of tmnxMobServS11CcRxReqRejected indicates the number of
         messages received on this peer with cause code set to request
         rejected."
    ::= { tmnxMobServS11CauseCodeEntry 6 }

tmnxMobServS11CcRxRemPeerNoResp  OBJECT-TYPE
    SYNTAX      Counter32
    MAX-ACCESS  read-only
    STATUS      current
    DESCRIPTION
        "The value of tmnxMobServS11CcRxRemPeerNoResp indicates the number of
         messages received on this peer with cause code set to remote peer
         not responding."
    ::= { tmnxMobServS11CauseCodeEntry 7 }

tmnxMobServS11CcRxNoResAvailable  OBJECT-TYPE
    SYNTAX      Counter32
    MAX-ACCESS  read-only
    STATUS      current
    DESCRIPTION
        "The value of tmnxMobServS11CcRxNoResAvailable indicates the number of
         messages received on this peer with cause code set to no resources
         available."
    ::= { tmnxMobServS11CauseCodeEntry 8 }

tmnxMobServS11CcRxUsrAuthFailure  OBJECT-TYPE
    SYNTAX      Counter32
    MAX-ACCESS  read-only
    STATUS      current
    DESCRIPTION
        "The value of tmnxMobServS11CcRxUsrAuthFailure indicates the number of
         messages received on this peer with cause code set to user
         authentication failed."
    ::= { tmnxMobServS11CauseCodeEntry 9 }

tmnxMobServS11CcRxOthers  OBJECT-TYPE
    SYNTAX      Counter32
    MAX-ACCESS  read-only
    STATUS      current
    DESCRIPTION
        "The value of tmnxMobServS11CcRxOthers indicates the number of
         messages received on this peer with cause code set to other values."
    ::= { tmnxMobServS11CauseCodeEntry 10 }

tmnxMobServS11CcTxReqAccepted  OBJECT-TYPE
    SYNTAX      Counter32
    MAX-ACCESS  read-only
    STATUS      current
    DESCRIPTION
        "The value of tmnxMobServS11CcTxReqAccepted indicates the number of
         messages transmitted from this peer with cause code set to request
         accepted."
    ::= { tmnxMobServS11CauseCodeEntry 11 }

tmnxMobServS11CcTxCtxNotFound  OBJECT-TYPE
    SYNTAX      Counter32
    MAX-ACCESS  read-only
    STATUS      current
    DESCRIPTION
        "The value of tmnxMobServS11CcTxCtxNotFound indicates the number of
         messages transmitted from this peer with cause code set to context not
         found."
    ::= { tmnxMobServS11CauseCodeEntry 12 }

tmnxMobServS11CcTxInvalidLength  OBJECT-TYPE
    SYNTAX      Counter32
    MAX-ACCESS  read-only
    STATUS      current
    DESCRIPTION
        "The value of tmnxMobServS11CcTxInvalidLength indicates the number of
         messages transmitted from this peer with cause code set to invalid
         length."
    ::= { tmnxMobServS11CauseCodeEntry 13 }

tmnxMobServS11CcTxMndIeIncorrect  OBJECT-TYPE
    SYNTAX      Counter32
    MAX-ACCESS  read-only
    STATUS      current
    DESCRIPTION
        "The value of tmnxMobServS11CcTxMndIeIncorrect indicates the number of
         messages transmitted from this peer with cause code set to mandatory
         Information Elements (IE) incorrect."
    ::= { tmnxMobServS11CauseCodeEntry 14 }

tmnxMobServS11CcTxMandIeMissing  OBJECT-TYPE
    SYNTAX      Counter32
    MAX-ACCESS  read-only
    STATUS      current
    DESCRIPTION
        "The value of tmnxMobServS11CcTxMandIeMissing indicates the number of
         messages transmitted from this peer with cause code set to mandatory
         Information Elements (IE) missing."
    ::= { tmnxMobServS11CauseCodeEntry 15 }

tmnxMobServS11CcTxReqRejected  OBJECT-TYPE
    SYNTAX      Counter32
    MAX-ACCESS  read-only
    STATUS      current
    DESCRIPTION
        "The value of tmnxMobServS11CcTxReqRejected indicates the number of
         messages transmitted from this peer with cause code set to request
         rejected."
    ::= { tmnxMobServS11CauseCodeEntry 16 }

tmnxMobServS11CcTxRemPeerNoResp  OBJECT-TYPE
    SYNTAX      Counter32
    MAX-ACCESS  read-only
    STATUS      current
    DESCRIPTION
        "The value of tmnxMobServS11CcTxRemPeerNoResp indicates the number of
         messages transmitted from this peer with cause code set to remote peer
         not responding."
    ::= { tmnxMobServS11CauseCodeEntry 17 }

tmnxMobServS11CcTxNoResAvailable  OBJECT-TYPE
    SYNTAX      Counter32
    MAX-ACCESS  read-only
    STATUS      current
    DESCRIPTION
        "The value of tmnxMobServS11CcTxNoResAvailable indicates the number of
         messages transmitted from this peer with cause code set to no resources
         available."
    ::= { tmnxMobServS11CauseCodeEntry 18 }

tmnxMobServS11CcTxUsrAuthFailure  OBJECT-TYPE
    SYNTAX      Counter32
    MAX-ACCESS  read-only
    STATUS      current
    DESCRIPTION
        "The value of tmnxMobServS11CcTxUsrAuthFailure indicates the number of
         messages transmitted from this peer with cause code set to user
         authentication failed."
    ::= { tmnxMobServS11CauseCodeEntry 19 }

tmnxMobServS11CcTxOthers  OBJECT-TYPE
    SYNTAX      Counter32
    MAX-ACCESS  read-only
    STATUS      current
    DESCRIPTION
        "The value of tmnxMobServS11CcTxOthers indicates the number of
         messages transmitted from this peer with cause code set to other
         values."
    ::= { tmnxMobServS11CauseCodeEntry 20 }


-- ----------------------------------------------
-- Compliance Statements
-- ----------------------------------------------

tmnxMobServV1v0Compliance  MODULE-COMPLIANCE
    STATUS      obsolete
    DESCRIPTION
        "The compliance statement for management of the Serving Gateway (SGW)
         on the Nokia 7750 Mobile Gateway systems R1.0."
    MODULE
        MANDATORY-GROUPS {
            tmnxMobServingGlobalGroup,
            tmnxMobServingGroup,
            tmnxMobServingStatGroup,
            tmnxMobServingBcGroup,
            tmnxMobServingRefPointGroup,
            tmnxMobServingChargingGroup,
            tmnxMobServingApGroup
            -- tmnxMobServingUnsupportedGroup Not supported
        }
    ::= { tmnxMobServingCompliances 1 }

tmnxMobServV3v0Compliance  MODULE-COMPLIANCE
    STATUS      obsolete
    DESCRIPTION
        "The compliance statement for management of the Serving Gateway (SGW)
         on the Nokia 7750 Mobile Gateway systems R3.0.

         This compliance module was made obsolete in 3.1 R2 release."
    MODULE
        MANDATORY-GROUPS {
            tmnxMobServingGlobalGroup,
            tmnxMobServingGroup,
            tmnxMobServingChargingGroup,
            tmnxMobServingApGroup,
            tmnxMobServingStatV3v0Group,
            tmnxMobServingRefPointV3v0Group,
            tmnxMobServingBcV3v0Group,
            tmnxMobServingGlobalV3v0Group,
            tmnxMobServingV3v0Group,
            tmnxMobServingChargingV3Group,
            tmnxMobServingThresholdV3Group,
            tmnxMobServingAcctStatsV3Group
            -- tmnxMobServingUnsupportedGroup Not supported
        }
    ::= { tmnxMobServingCompliances 2 }

tmnxMobServ7xxxV10v0Compliance  MODULE-COMPLIANCE
    STATUS      current
    DESCRIPTION
        "The compliance statement for management of the Serving Gateway (SGW)
         on the Nokia 7750 SROS R10.0."
    MODULE
        MANDATORY-GROUPS {
            tmnxMobServingAcctStatsV3Group,
            tmnxMobServingApGroup,
            tmnxMobServingBcV3v0Group,
            tmnxMobServingChargingGroup,
            tmnxMobServingChargingV3Group,
            tmnxMobServingGlobalGroup,
            tmnxMobServingGlobalV3v0Group,
            tmnxMobServingGroup,
            tmnxMobServingRefPointGroupV31v2,
            tmnxMobServingStatV3v0Group,
            tmnxMobServingThresholdV3Group,
            tmnxMobServingV3v0Group,
            tmnxMobServingV4v0Group,
            tmnxMobServStatV4v0Group,
            tmnxMobServingUnsupportedGroup,
            tmnxMobServingRefPointV3v5Group
        }
    ::= { tmnxMobServingCompliances 3 }

-- ----------------------------------------------
-- Units of Conformance
-- ----------------------------------------------

tmnxMobServingGlobalGroup  OBJECT-GROUP
    OBJECTS {
                tmnxMobServTableLastChanged,
                tmnxMobServSigTableLastChanged,
                tmnxMobServS5TableLastChanged,
                tmnxMobServS11TableLastChanged,
                tmnxMobServS1uTableLastChanged,
                tmnxMobServApnTableLastChanged,
                tmnxMobServS11PeerTableLastChngd,
                tmnxMobServS1uPeerTableLastChngd,
                tmnxMobServRfTableLastChanged,
                tmnxMobServApTableLastChanged,
                tmnxMobSgwGaPeerTableLastChngd
            }
    STATUS      current
    DESCRIPTION
        "The group of global objects supporting management of the Serving
         Gateway (SGW) on the Nokia 7750 Mobile Gateway systems."
    ::= { tmnxMobServingGroups 1 }

tmnxMobServingGroup  OBJECT-GROUP
    OBJECTS {
                tmnxMobServLastChanged,
                tmnxMobServAdminState,
                tmnxMobServOperState,
                tmnxMobServGracefulShutTimeout,
                tmnxMobServMobNode,
                tmnxMobServUplinkQciPolName,
                tmnxMobServDownlinkQciPolName,
                tmnxMobServSigLastChanged,
                tmnxMobServSigGtpcProfile,
                tmnxMobServSigGtpuProfile,
                tmnxMobServSigDiaOriginHost,
                tmnxMobServSigDiaOriginRealm,
                tmnxMobServSigDiaProfile,
                tmnxMobServSigDefaultIfVRtrId,
                tmnxMobServSigDefaultIfIndex,
                tmnxMobServBearerGtpuUdpChecksum,
                tmnxMobServBearerGtpuSeqNumber,
                tmnxMobServS5LastChanged,
                tmnxMobServS5PeerList,
                tmnxMobServS5GtpcIfVRtrId,
                tmnxMobServS5GtpcIfIndex,
                tmnxMobServS5GtpuIfVRtrId,
                tmnxMobServS5DualStackPref,
                tmnxMobServS5GtpuIfIndex,
                tmnxMobServS5GtpcProfile,
                tmnxMobServS5GtpuProfile,
                tmnxMobServS11LastChanged,
                tmnxMobServS11PeerList,
                tmnxMobServS11GtpcIfVRtrId,
                tmnxMobServS11GtpcIfIndex,
                tmnxMobServS11GtpcProfile,
                tmnxMobServS1uLastChanged,
                tmnxMobServS1uPeerList,
                tmnxMobServS1uGtpuIfVRtrId,
                tmnxMobServS1uGtpuIfIndex,
                tmnxMobServS1uGtpuProfile,
                tmnxMobServS1uGtpuUdpCheckSum,
                tmnxMobServS1uGtpuSeqNumber,
                tmnxMobServS1uDualStackPref,
                tmnxMobServApnRowStatus,
                tmnxMobServApnLastChanged,
                tmnxMobServApnUplinkQciPolName,
                tmnxMobServApnDownlinkQciPolName,
                tmnxMobServS5DualStackPrefCplane
            }
    STATUS      current
    DESCRIPTION
        "The group of objects supporting management of the Serving Gateway (SGW)
         on the Nokia 7750 Mobile Gateway systems."
    ::= { tmnxMobServingGroups 2 }

tmnxMobServingStatGroup  OBJECT-GROUP
    OBJECTS {
                tmnxMobServStatApn,
                tmnxMobServStatBearers,
                tmnxMobServStatDefaultBearers,
                tmnxMobServStatDedicatedBearers,
                tmnxMobServStatIpv4Bearers,
                tmnxMobServStatIpv6Bearers,
                tmnxMobServStatIpv4v6Bearers,
                tmnxMobServStatActiveBearers,
                tmnxMobServStatIdleBearers,
                tmnxMobServStatRoamers,
                tmnxMobServStatPagingInProgress,
                tmnxMobServStatBuffersAllocated,
                tmnxMobServStatBuffersAvailable,
                tmnxMobServStatBuffersAllocErr,
                tmnxMobServProcAttach,
                tmnxMobServProcDetach,
                tmnxMobServProcNwServiceReq,
                tmnxMobServProcUeServiceReq,
                tmnxMobServProcS1Release,
                tmnxMobServProcInterENBX2Hndovr,
                tmnxMobServProcInterENBS1Hndovr,
                tmnxMobServProcUeDedBrActivation,
                tmnxMobServProcNwDedBrActivtn,
                tmnxMobServProcNwDedBrDeActiv,
                tmnxMobServProcMmeDedBrDeActiv,
                tmnxMobServProcHssQosModificatn,
                tmnxMobServProcAttachFailures,
                tmnxMobServProcDetachFailures,
                tmnxMobServProcNwServiceReqFails,
                tmnxMobServProcUeServiceReqFails,
                tmnxMobServProcS1ReleaseFailures,
                tmnxMobServProcEnbX2HndovrFails,
                tmnxMobServProcEnbS1HndovrFails,
                tmnxMobServProcUeDedBrActvFails,
                tmnxMobServProcNwDedBrActvFails,
                tmnxMobServProcNwDedBrDeActFails,
                tmnxMobServProcMmeDedBrDeAcFails,
                tmnxMobServProcHssQosModifyFails,
                tmnxMobServStatHomers,
                tmnxMobServStatVisitors,
                tmnxMobServStatENBs,
                tmnxMobServStatMmes,
                tmnxMobServStatPgws,
                tmnxMobServStatUes,
                tmnxMobServStatRfPeer,
                tmnxMobServStatRfAcctStartBuf,
                tmnxMobServStatRfAcctIntBuf,
                tmnxMobServStatRfAcctStopBuf,
                tmnxMobServProcPagingTimeoutExp,
                tmnxMobServProcIntraIdleModeTau,
                tmnxMobServProcInterMmeRel,
                tmnxMobServProcInterMmeRelFails,
                tmnxMobServProcInterIdleTau,
                tmnxMobServProcInterIdleTauFails,
                tmnxMobServProcS1WithIndTnl,
                tmnxMobServProcS1WithIndTnlFails,
                tmnxMobServProcS1WoIndTnl,
                tmnxMobServProcS1WoIndTnlFails,
                tmnxMobServProcInterX2Hndor,
                tmnxMobServProcInterX2HndorFails,
                tmnxMobServProcInterSgwHoOut,
                tmnxMobServProcMltPdnConcvtReqs,
                tmnxMobServProcMltPdnConcvtFails,
                tmnxMobServProcModBearers,
                tmnxMobServProcModBearersFails,
                tmnxMobServProcDelBearers,
                tmnxMobServProcDelBearersFails,
                tmnxMobServProcBearerRes,
                tmnxMobServProcBearerResFails,
                tmnxMobServProcEhrpdLteHo,
                tmnxMobServProcEhrpdLteHoFails
            }
    STATUS      obsolete
    DESCRIPTION
        "The group of objects supporting management of the Serving Gateway
         (SGW) statistics on the Nokia 7750 Mobile Gateway systems."
    ::= { tmnxMobServingGroups 3 }

tmnxMobServingBcGroup  OBJECT-GROUP
    OBJECTS {
                tmnxMobServUeRowStatus,
                tmnxMobServUeMsIsdn,
                tmnxMobServUeImei,
                tmnxMobServUeNai,
                tmnxMobServUeNwkMcc,
                tmnxMobServUeNwkMnc,
                tmnxMobServUeTrackingAreaId,
                tmnxMobServUeCellId,
                tmnxMobServUeState,
                tmnxMobServUeRat,
                tmnxMobServUePdnContexts,
                tmnxMobServUeBearerContexts,
                tmnxMobServUeChassisIndex,
                tmnxMobServUeCardSlotNum,
                tmnxMobServUeS11MmeCtrlTeid,
                tmnxMobServUeS11MmeCtrlAddrType,
                tmnxMobServUeS11MmeCtrlAddr,
                tmnxMobServUeS11SgwCtrlTeid,
                tmnxMobServUeS11SgwCtrlAddrType,
                tmnxMobServUeS11SgwCtrlAddr,
                tmnxMobServUeS11InterEnbX2HandOv,
                tmnxMobServUeS11InterEnbS1HandOv,
                tmnxMobServUeS1ReleaseProcedures,
                tmnxMobServUePagingReq,
                tmnxMobServUeRfSgwAddrType,
                tmnxMobServUeRfSgwAddr,
                tmnxMobServPcLinkedBearerId,
                tmnxMobServPcApnRestriction,
                tmnxMobServPcUlApnAmbr,
                tmnxMobServPcDlApnAmbr,
                tmnxMobServPcIpv4AddressType,
                tmnxMobServPcIpv4Address,
                tmnxMobServPcIpv6AddressType,
                tmnxMobServPcIpv6Address,
                tmnxMobServPcBearerContexts,
                tmnxMobServPcSessionState,
                tmnxMobServPcLastEvent,
                tmnxMobServPcS5S8SigProtocol,
                tmnxMobServPcS5S8SgwCtrlTeid,
                tmnxMobServPcS5S8SgwCtrlAddrType,
                tmnxMobServPcS5S8SgwCtrlAddr,
                tmnxMobServPcS5S8PgwCtrlTeid,
                tmnxMobServPcS5S8PgwCtrlAddrType,
                tmnxMobServPcS5S8PgwCtrlAddr,
                tmnxMobServPcRfServerAddrType,
                tmnxMobServPcRfServerAddr,
                tmnxMobServPcRfServerState,
                tmnxMobServPcRfBearerType,
                tmnxMobServPcRfChargingLevel,
                tmnxMobServPcRfChargingProfile,
                tmnxMobServPcRfTriggeredRecords,
                tmnxMobServPcRfInterimRecords,
                tmnxMobServPcS5S8SgwV6CtrlAdrTyp,
                tmnxMobServPcS5S8SgwV6CtrlAddr,
                tmnxMobServPcS5S8PgwV6CtrlAdrTyp,
                tmnxMobServPcS5S8PgwV6CtrlAddr,
                tmnxMobServBcBearerType,
                tmnxMobServBcUpTime,
                tmnxMobServBcQci,
                tmnxMobServBcArp,
                tmnxMobServBcQosUlMbr,
                tmnxMobServBcQosDlMbr,
                tmnxMobServBcQosUlGbr,
                tmnxMobServBcQosDlGbr,
                tmnxMobServBcS1uEnodebTeid,
                tmnxMobServBcS1uEnodebAddrType,
                tmnxMobServBcS1uEnodebAddr,
                tmnxMobServBcS1uSgwTeid,
                tmnxMobServBcS1uSgwAddrType,
                tmnxMobServBcS1uSgwAddr,
                tmnxMobServBcS5S8SgwTeid,
                tmnxMobServBcS5S8SgwDataAddrType,
                tmnxMobServBcS5S8SgwDataAddr,
                tmnxMobServBcS5S8PgwTeid,
                tmnxMobServBcS5S8PgwDataAddrType,
                tmnxMobServBcS5S8PgwDataAddr,
                tmnxMobServBcS11QosModifications,
                tmnxMobServBcS5ULPackets,
                tmnxMobServBcS5ULBytes,
                tmnxMobServBcS1uDLPackets,
                tmnxMobServBcS1uDLBytes,
                tmnxMobServBcS5ULPacketsLow,
                tmnxMobServBcS5ULPacketsHigh,
                tmnxMobServBcS5ULBytesLow,
                tmnxMobServBcS5ULBytesHigh,
                tmnxMobServBcS1uDLPacketsLow,
                tmnxMobServBcS1uDLPacketsHigh,
                tmnxMobServBcS1uDLBytesLow,
                tmnxMobServBcS1uDLBytesHigh,
                tmnxMobServUeIntraSgwIdleTau,
                tmnxMobServUeInitServReqProcs,
                tmnxMobServUePagedCount,
                tmnxMobServPcAntiSpoofFailureCnt,
                tmnxMobServBcSetupLatencyTime,
                tmnxMobServBcIndTnlRemTeid,
                tmnxMobServBcIndTnlRemAddrType,
                tmnxMobServBcIndTnlRemAddr,
                tmnxMobServBcIndTnlLocalTeid,
                tmnxMobServBcIndTnlLocalAddrType,
                tmnxMobServBcIndTnlLocalAddr,
                tmnxMobServBcRfServerAddrType,
                tmnxMobServBcRfServerAddr,
                tmnxMobServBcRfServerState,
                tmnxMobServBcRfChargingProfile,
                tmnxMobServBcRfTriggeredRecords,
                tmnxMobServBcRfInterimRecords
            }
    STATUS      obsolete
    DESCRIPTION
        "The group of objects supporting management of the Serving Gateway
         (SGW) bearer contexts on the Nokia 7750 Mobile Gateway
         systems."
    ::= { tmnxMobServingGroups 4 }

tmnxMobServingRefPointGroup  OBJECT-GROUP
    OBJECTS {
                tmnxMobServS11PeerLastChanged,
                tmnxMobServS11PeerCreateTime,
                tmnxMobServS11PeerPathMgmtState,
                tmnxMobServS11PeerGatewayId,
                tmnxMobServS11StatCreateSessnReq,
                tmnxMobServS11StatCreateSessnRsp,
                tmnxMobServS11StatDeleteSessnReq,
                tmnxMobServS11StatDeleteSessnRsp,
                tmnxMobServS11StatCreateBearrReq,
                tmnxMobServS11StatCreateBearrRsp,
                tmnxMobServS11StatDeleteBearrReq,
                tmnxMobServS11StatDeleteBearrRsp,
                tmnxMobServS11StatModifyBearrReq,
                tmnxMobServS11StatModifyBearrRsp,
                tmnxMobServS11StatRxEchoRequests,
                tmnxMobServS11StatTxEchoResp,
                tmnxMobServS11StatTxEchoRequests,
                tmnxMobServS11StatRxEchoResp,
                tmnxMobServS11StatTxDlNotify,
                tmnxMobServS11StatRxDlAcks,
                tmnxMobServS11StatRxDlFailNotify,
                tmnxMobServS11StatPagingSvcReq,
                tmnxMobServS11StatRxMalfrmedPkts,
                tmnxMobServS11StatRxUnknownPkts,
                tmnxMobServS11StatRxMissngIePkts,
                tmnxMobServS11StatPeerRestarts,
                tmnxMobServS11StatPeerRestartCnt,
                tmnxMobServS11StatPathMgmtFails,
                tmnxMobServS11StatRelBearersReq,
                tmnxMobServS11StatRelBearersResp,
                tmnxMobServS11StatCrtIndrTnlReq,
                tmnxMobServS11StatCrtIndrTnlResp,
                tmnxMobServS11StatDelIndrTnlReq,
                tmnxMobServS11StatDelIndrTnlResp,
                tmnxMobServS1uPeerLastChanged,
                tmnxMobServS1uPeerCreateTime,
                tmnxMobServS1uPeerPathMgmtState,
                tmnxMobServS1uPeerGatewayId,
                tmnxMobServS1uStatBcNotFound,
                tmnxMobServS1uStatRxEchoRequests,
                tmnxMobServS1uStatTxEchoResponse,
                tmnxMobServS1uStatTxEchoRequests,
                tmnxMobServS1uStatRxEchoResponse,
                tmnxMobServS1uStatPeerRestarts,
                tmnxMobServS1uStatPeerRestartCnt,
                tmnxMobServS1uStatPathMgmtFails,
                tmnxMobServS11StatBearersIpv4,
                tmnxMobServS11StatBearersIpv6,
                tmnxMobServS11StatBearerIpv4v6,
                tmnxMobServS11StatDedctdBearers,
                tmnxMobServS11StatBearers,
                tmnxMobServS11StatDefBearers,
                tmnxMobServS11StatRoamers,
                tmnxMobServS11StatActiveBearers,
                tmnxMobServS11StatIdleBearers,
                tmnxMobServS11StatUpdateBearrReq,
                tmnxMobServS11StatUpdateBearrRsp,
                tmnxMobServS1uStatBearersIpv4,
                tmnxMobServS1uStatBearersIpv6,
                tmnxMobServS1uStatBearerIpv4v6,
                tmnxMobServS1uStatDedctdBearers,
                tmnxMobServS1uStatUlBytes,
                tmnxMobServS1uStatDlBytes,
                tmnxMobServS1uStatUlPackets,
                tmnxMobServS1uStatDlPackets,
                tmnxMobServS1uStatBearers,
                tmnxMobServS1uStatDefBearers,
                tmnxMobServS1uStatRoamers,
                tmnxMobServS1uStatActiveBearers,
                tmnxMobServS1uStatIdleBearers
            }
    STATUS      obsolete
    DESCRIPTION
        "The group of objects supporting management of the Serving Gateway
         (SGW) reference point statistics on the Nokia 7750 Mobile
         Gateway systems."
    ::= { tmnxMobServingGroups 5 }

tmnxMobServingUnsupportedGroup  OBJECT-GROUP
    OBJECTS {
                tmnxMobServGxcTableLastChanged,
                tmnxMobServS12TableLastChanged,
                tmnxMobServPccDynamicState,
                tmnxMobServVisitingPlmnList,
                tmnxMobServPolBaseName,
                tmnxMobServSigPmipv6Profile,
                tmnxMobServSigPmipv6AddrScheme,
                tmnxMobServSigPmipv6RtrAdIntvl,
                tmnxMobServSigPmipv6RtrAdLife,
                tmnxMobServGxcLastChanged,
                tmnxMobServGxcDiaIfVRtrId,
                tmnxMobServGxcDiaIfIndex,
                tmnxMobServGxcDiaTransTimer,
                tmnxMobServGxcDiaRetryCount,
                tmnxMobServGxcDefPriDiaPeer,
                tmnxMobServGxcDefSecDiaPeer,
                tmnxMobServGxcDiameterApp,
                tmnxMobServS5Pmipv6IfVRtrId,
                tmnxMobServS5Pmipv6IfIndex,
                tmnxMobServS5Pmipv6LnkLclAdrType,
                tmnxMobServS5Pmipv6LnkLclAddress,
                tmnxMobServS5Pmipv6Profile,
                tmnxMobServS5Pmipv6RtrAdIntvl,
                tmnxMobServS5Pmipv6RtrAdLife,
                tmnxMobServS5Pmipv6RtrAddrScheme,
                tmnxMobServS8Pmipv6IfVRtrId,
                tmnxMobServS8Pmipv6IfIndex,
                tmnxMobServS8Pmipv6LnkLclAdrType,
                tmnxMobServS8Pmipv6LnkLclAddress,
                tmnxMobServS8Pmipv6Profile,
                tmnxMobServS8Pmipv6RtrAdIntvl,
                tmnxMobServS8Pmipv6RtrAdLife,
                tmnxMobServS8Pmipv6RtrAddrScheme,
                tmnxMobServS12LastChanged,
                tmnxMobServS12PeerList,
                tmnxMobServS12GtpuIfVRtrId,
                tmnxMobServS12GtpuIfIndex,
                tmnxMobServS12GtpuProfile,
                tmnxMobServS12GtpuUdpCheckSum,
                tmnxMobServS12GtpuSeqNumber,
                tmnxMobServApnDescription,
                tmnxMobServApnDynamicPcc,
                tmnxMobServApnPolBaseName,
                tmnxMobServGxcStatCcr,
                tmnxMobServGxcStatCca,
                tmnxMobServGxcStatCcrFailures,
                tmnxMobServGxcStatRar,
                tmnxMobServGxcStatRaa,
                tmnxMobServGxcStatBberf,
                tmnxMobServGxcStatRxMalformedPkt,
                tmnxMobServGxcStatRxUnknownPkts,
                tmnxMobServGxcStatRxMissingIePkt,
                tmnxMobServGxcStatStr,
                tmnxMobServGxcStatSta,
                tmnxMobServGxcStatAsr,
                tmnxMobServGxcStatAsa,
                tmnxMobServGxcStatCer,
                tmnxMobServGxcStatCea,
                tmnxMobServGxcStatDpr,
                tmnxMobServGxcStatDpa,
                tmnxMobServGxcStatDwr,
                tmnxMobServGxcStatDwa,
                tmnxMobServGxcStatPrProfStatus,
                tmnxMobServGxcStatPrDetailStatus,
                tmnxMobServPcPcrfEventTriggers,
                tmnxMobServPcS5S8SgwGreKey,
                tmnxMobServPcS5S8PgwGreKey,
                tmnxMobServPcS5S8PgwTrprtAdrType,
                tmnxMobServPcS5S8PgwTransprtAddr,
                tmnxMobServPcGxcPcrfAddressType,
                tmnxMobServPcGxcPcrfAddress,
                tmnxMobServPcGxcSgwAddressType,
                tmnxMobServPcGxcSgwAddress,
                tmnxMobServBcSdfs,
                tmnxMobServBcFilters,
                tmnxMobServBcSdfPcrfPrecedence,
                tmnxMobServBcSdfRuleName,
                tmnxMobServBcSdfPacketFilters,
                tmnxMobServBcSdfQosUlMbr,
                tmnxMobServBcSdfQosDlMbr,
                tmnxMobServBcSdfQosUlGbr,
                tmnxMobServBcSdfQosDlGbr,
                tmnxMobServBcSdfFilterProtocol,
                tmnxMobServBcSdfFilterSrcAdrType,
                tmnxMobServBcSdfFilterSrcAddr,
                tmnxMobServBcSdfFilterSrcPfxLen,
                tmnxMobServBcSdfFilterDstAdrType,
                tmnxMobServBcSdfFilterDestAddr,
                tmnxMobServBcSdfFilterDestPfxLen,
                tmnxMobServBcSdfFilterSrcPorts,
                tmnxMobServBcSdfFilterDestPorts,
                tmnxMobServBcSdfFirstSrcPortOper,
                tmnxMobServBcSdfFirstSrcPortVal1,
                tmnxMobServBcSdfFirstSrcPortVal2,
                tmnxMobServBcSdfSecndSrcPortOper,
                tmnxMobServBcSdfSecndSrcPortVal1,
                tmnxMobServBcSdfSecndSrcPortVal2,
                tmnxMobServBcSdfFirstDstPortOper,
                tmnxMobServBcSdfFirstDstPortVal1,
                tmnxMobServBcSdfFirstDstPortVal2,
                tmnxMobServBcSdfSecndDstPortOper,
                tmnxMobServBcSdfSecndDstPortVal1,
                tmnxMobServBcSdfSecndDstPortVal2,
                tmnxMobServBcTftFilterProtocol,
                tmnxMobServBcTftFilterSrcAdrType,
                tmnxMobServBcTftFilterSrcAddr,
                tmnxMobServBcTftFilterSrcPfxLen,
                tmnxMobServBcTftFilterDstAdrType,
                tmnxMobServBcTftFilterDestAddr,
                tmnxMobServBcTftFilterDestPfxLen,
                tmnxMobServBcTftFilterSrcPorts,
                tmnxMobServBcTftFilterDestPorts,
                tmnxMobServBcTftFirstSrcPortOper,
                tmnxMobServBcTftFirstSrcPortVal1,
                tmnxMobServBcTftFirstSrcPortVal2,
                tmnxMobServBcTftSecndSrcPortOper,
                tmnxMobServBcTftSecndSrcPortVal1,
                tmnxMobServBcTftSecndSrcPortVal2,
                tmnxMobServBcTftFirstDstPortOper,
                tmnxMobServBcTftFirstDstPortVal1,
                tmnxMobServBcTftFirstDstPortVal2,
                tmnxMobServBcTftSecndDstPortOper,
                tmnxMobServBcTftSecndDstPortVal1,
                tmnxMobServBcTftSecndDstPortVal2,
                tmnxMobServStatIpv4Sdf,
                tmnxMobServStatIpv6Sdf
            }
    STATUS      current
    DESCRIPTION
        "This group of objects is not supported on the Nokia 7750
         Mobile Gateway systems."
    ::= { tmnxMobServingGroups 6 }

tmnxMobServingChargingGroup  OBJECT-GROUP
    OBJECTS {
                tmnxMobServChargingProfHome,
                tmnxMobServChargingProfVisiting,
                tmnxMobServChargingProfRoaming,
                tmnxMobServChrgCcIgnoreAny,
                tmnxMobServChrgCcIgnoreHome,
                tmnxMobServChrgCcIgnoreVisiting,
                tmnxMobServChrgCcIgnoreRoaming,
                tmnxMobServRfLastChanged,
                tmnxMobServRfVRtrId,
                tmnxMobServRfIfIndex,
                tmnxMobServRfPriDiaPeer,
                tmnxMobServRfSecDiaPeer,
                tmnxMobServRfAcctIntmInterval,
                tmnxMobServRfApplTxTimer,
                tmnxMobServRfRetryCount,
                tmnxMobServRfChargingGroupID,
                tmnxMobServRfOperatorString,
                tmnxMobServRfAcctLevel,
                tmnxMobServRfNodeId,
                tmnxMobServRfOcFilePrivateInfo,
                tmnxMobServRfOcFileExtension,
                tmnxMobServRfOcFileClosureSize,
                tmnxMobServRfOcFileClsLifeTime,
                tmnxMobServRfOcFileClsMaxAcrs,
                tmnxMobServRfOcFileObsoleteTime,
                tmnxMobServRfOcPrimaryCf,
                tmnxMobServRfOcCf1State,
                tmnxMobServRfOcCf1Limit,
                tmnxMobServRfOcCf2State,
                tmnxMobServRfOcCf2Limit,
                tmnxMobServChrgCcReject
            }
    STATUS      current
    DESCRIPTION
        "The group of objects supporting the management of the Serving Gateway
         (SGW) charging applications on the Nokia 7750 Mobile Gateway
         systems."
    ::= { tmnxMobServingGroups 7 }

tmnxMobServingApGroup  OBJECT-GROUP
    OBJECTS {
                tmnxMobServApRowStatus,
                tmnxMobServApLastChanged,
                tmnxMobServApCollectAcctStats
            }
    STATUS      current
    DESCRIPTION
        "The group of objects supporting the management of the Serving Gateway
         (SGW) Accounting Policies on the Nokia 7750 Mobile Gateway
         systems."
    ::= { tmnxMobServingGroups 8 }

tmnxMobServingObsoletedGroup   OBJECT-GROUP
    OBJECTS {
                tmnxMobServProcBearerRes,
                tmnxMobServProcBearerResFails,
                tmnxMobServProcDelBearers,
                tmnxMobServProcDelBearersFails,
                tmnxMobServProcEnbS1HndovrFails,
                tmnxMobServProcEnbX2HndovrFails,
                tmnxMobServProcInterENBS1Hndovr,
                tmnxMobServProcInterENBX2Hndovr,
                tmnxMobServProcInterMmeRel,
                tmnxMobServProcInterMmeRelFails,
                tmnxMobServProcMltPdnConcvtFails,
                tmnxMobServProcMltPdnConcvtReqs,
                tmnxMobServProcModBearers,
                tmnxMobServProcModBearersFails,
                tmnxMobServProcNwServiceReq,
                tmnxMobServProcNwServiceReqFails,
                tmnxMobServS11StatPagingSvcReq,
                tmnxMobServUePagedCount
            }
    STATUS      obsolete
    DESCRIPTION
        "The group of obsolete objects which are no longer supported in the 3.0
         release on the Serving Gateway (SGW) on the Nokia 7750 Mobile
         Gateway systems.

         This group was made obsolete in the 3.1 R2 release"
    ::= { tmnxMobServingGroups 9 }

tmnxMobServingStatV3v0Group  OBJECT-GROUP
    OBJECTS {
                tmnxMobServStatApn,
                tmnxMobServStatBearers,
                tmnxMobServStatDefaultBearers,
                tmnxMobServStatDedicatedBearers,
                tmnxMobServStatIpv4Bearers,
                tmnxMobServStatIpv6Bearers,
                tmnxMobServStatIpv4v6Bearers,
                tmnxMobServStatActiveBearers,
                tmnxMobServStatIdleBearers,
                tmnxMobServStatRoamers,
                tmnxMobServStatPagingInProgress,
                tmnxMobServStatBuffersAllocated,
                tmnxMobServStatBuffersAvailable,
                tmnxMobServStatBuffersAllocErr,
                tmnxMobServProcAttach,
                tmnxMobServProcDetach,
                tmnxMobServProcUeServiceReq,
                tmnxMobServProcS1Release,
                tmnxMobServProcUeDedBrActivation,
                tmnxMobServProcNwDedBrActivtn,
                tmnxMobServProcNwDedBrDeActiv,
                tmnxMobServProcMmeDedBrDeActiv,
                tmnxMobServProcHssQosModificatn,
                tmnxMobServProcAttachFailures,
                tmnxMobServProcDetachFailures,
                tmnxMobServProcUeServiceReqFails,
                tmnxMobServProcS1ReleaseFailures,
                tmnxMobServProcUeDedBrActvFails,
                tmnxMobServProcNwDedBrActvFails,
                tmnxMobServProcNwDedBrDeActFails,
                tmnxMobServProcMmeDedBrDeAcFails,
                tmnxMobServProcHssQosModifyFails,
                tmnxMobServStatHomers,
                tmnxMobServStatVisitors,
                tmnxMobServStatENBs,
                tmnxMobServStatMmes,
                tmnxMobServStatPgws,
                tmnxMobServStatUes,
                tmnxMobServStatRfPeer,
                tmnxMobServStatRfAcctStartBuf,
                tmnxMobServStatRfAcctIntBuf,
                tmnxMobServStatRfAcctStopBuf,
                tmnxMobServProcPagingTimeoutExp,
                tmnxMobServProcIntraIdleModeTau,
                tmnxMobServProcInterIdleTau,
                tmnxMobServProcInterIdleTauFails,
                tmnxMobServProcS1WithIndTnl,
                tmnxMobServProcS1WithIndTnlFails,
                tmnxMobServProcS1WoIndTnl,
                tmnxMobServProcS1WoIndTnlFails,
                tmnxMobServProcInterX2Hndor,
                tmnxMobServProcInterX2HndorFails,
                tmnxMobServProcInterSgwHoOut,
                tmnxMobServProcEhrpdLteHo,
                tmnxMobServProcEhrpdLteHoFails,
                tmnxMobServProcIntraIdleTauFails,
                tmnxMobServProcNwPdnSessDeActiv,
                tmnxMobServProcNwPdnSesDeActFail,
                tmnxMobServProcPagingAttempts,
                tmnxMobServProcPagingFails,
                tmnxMobServProcIntraSgwHndvr,
                tmnxMobServProcIntraSgwHndvrFail,
                tmnxMobServProcIntraSgwS1IndTnl,
                tmnxMobServProcIntraS1IndTnlFail,
                tmnxMobServProcInterMmeIdleTau,
                tmnxMobServProcInterMmeIdlTauFls,
                tmnxMobServProcInterMmeS1X2RlSuc,
                tmnxMobServProcInterMmeS1X2RlFls,
                tmnxMobServProcInterMmeS1RlTnSuc,
                tmnxMobServProcInterMmeS1RlTnFls,
                tmnxMobServStatIdleUes,
                tmnxMobServProcInterMmeRelocs,
                tmnxMobServProcAttachPiggyBack,
                tmnxMobServProcAttachPiggyFail,
                tmnxMobServProcUeDedBrDeActv,
                tmnxMobServProcUeDedBrDeActvFail,
                tmnxMobServProcUeDedBrModify,
                tmnxMobServProcUeDedBrModifyFail,
                tmnxMobServProcNwBrModify,
                tmnxMobServProcNwBrModifyFail,
                tmnxMobServStatNumSuspendedUE,
                tmnxMobServProcPDNSuspNotice,
                tmnxMobServProcPDNResumeNotice,
                tmnxMobServProcIRSR,
                tmnxMobServProcEmergncyAttachSuc,
                tmnxMobServStatEmergencyPdnSess
            }
    STATUS      current
    DESCRIPTION
        "The group of objects supporting management of the Serving Gateway
         (SGW) statistics on the Nokia 7750 Mobile Gateway systems."
    ::= { tmnxMobServingGroups 10 }

tmnxMobServingRefPointV3v0Group  OBJECT-GROUP
    OBJECTS {
                tmnxMobServS11PeerLastChanged,
                tmnxMobServS11PeerCreateTime,
                tmnxMobServS11PeerPathMgmtState,
                tmnxMobServS11PeerGatewayId,
                tmnxMobServS11StatCreateSessnReq,
                tmnxMobServS11StatCreateSessnRsp,
                tmnxMobServS11StatDeleteSessnReq,
                tmnxMobServS11StatDeleteSessnRsp,
                tmnxMobServS11StatCreateBearrReq,
                tmnxMobServS11StatCreateBearrRsp,
                tmnxMobServS11StatDeleteBearrReq,
                tmnxMobServS11StatDeleteBearrRsp,
                tmnxMobServS11StatModifyBearrReq,
                tmnxMobServS11StatModifyBearrRsp,
                tmnxMobServS11StatRxEchoRequests,
                tmnxMobServS11StatTxEchoResp,
                tmnxMobServS11StatTxEchoRequests,
                tmnxMobServS11StatRxEchoResp,
                tmnxMobServS11StatTxDlNotify,
                tmnxMobServS11StatRxDlAcks,
                tmnxMobServS11StatRxDlFailNotify,
                tmnxMobServS11StatRxMalfrmedPkts,
                tmnxMobServS11StatRxUnknownPkts,
                tmnxMobServS11StatRxMissngIePkts,
                tmnxMobServS11StatPeerRestarts,
                tmnxMobServS11StatPeerRestartCnt,
                tmnxMobServS11StatPathMgmtFails,
                tmnxMobServS11StatRelBearersReq,
                tmnxMobServS11StatRelBearersResp,
                tmnxMobServS11StatCrtIndrTnlReq,
                tmnxMobServS11StatCrtIndrTnlResp,
                tmnxMobServS11StatDelIndrTnlReq,
                tmnxMobServS11StatDelIndrTnlResp,
                tmnxMobServS1uPeerLastChanged,
                tmnxMobServS1uPeerCreateTime,
                tmnxMobServS1uPeerPathMgmtState,
                tmnxMobServS1uPeerGatewayId,
                tmnxMobServS1uStatBcNotFound,
                tmnxMobServS1uStatRxEchoRequests,
                tmnxMobServS1uStatTxEchoResponse,
                tmnxMobServS1uStatTxEchoRequests,
                tmnxMobServS1uStatRxEchoResponse,
                tmnxMobServS1uStatPeerRestarts,
                tmnxMobServS1uStatPeerRestartCnt,
                tmnxMobServS1uStatPathMgmtFails,
                tmnxMobServS11StatBearersIpv4,
                tmnxMobServS11StatBearersIpv6,
                tmnxMobServS11StatBearerIpv4v6,
                tmnxMobServS11StatDedctdBearers,
                tmnxMobServS11StatBearers,
                tmnxMobServS11StatDefBearers,
                tmnxMobServS11StatRoamers,
                tmnxMobServS11StatActiveBearers,
                tmnxMobServS11StatIdleBearers,
                tmnxMobServS11StatUpdateBearrReq,
                tmnxMobServS11StatUpdateBearrRsp,
                tmnxMobServS1uStatBearersIpv4,
                tmnxMobServS1uStatBearersIpv6,
                tmnxMobServS1uStatBearerIpv4v6,
                tmnxMobServS1uStatDedctdBearers,
                tmnxMobServS1uStatUlBytes,
                tmnxMobServS1uStatDlBytes,
                tmnxMobServS1uStatUlPackets,
                tmnxMobServS1uStatDlPackets,
                tmnxMobServS1uStatBearers,
                tmnxMobServS1uStatDefBearers,
                tmnxMobServS1uStatRoamers,
                tmnxMobServS1uStatActiveBearers,
                tmnxMobServS1uStatIdleBearers,
                tmnxMobServS11StatModifyBearrCmd,
                tmnxMobServS11StatModifyBearrFlr,
                tmnxMobServS11StatDeleteBearrCmd,
                tmnxMobServS11StatDeleteBearrFlr,
                tmnxMobSgwGaPeerLastChanged,
                tmnxMobSgwGaPeerCreateTime,
                tmnxMobSgwGaPeerPathMgmtState,
                tmnxMobSgwGaPeerDetailState,
                tmnxMobSgwGaStatLastChanged,
                tmnxMobSgwGaStatCreateTime,
                tmnxMobSgwGaStatRxEchoRequests,
                tmnxMobSgwGaStatTxEchoResponses,
                tmnxMobSgwGaStatTxEchoRequests,
                tmnxMobSgwGaStatRxEchoResponses,
                tmnxMobSgwGaStatRxNodeAlRequests,
                tmnxMobSgwGaStatTxNodeAlResps,
                tmnxMobSgwGaStatTxDataRecReqs,
                tmnxMobSgwGaStatTxDataRecTferReq,
                tmnxMobSgwGaStatRetrDataRecReqs,
                tmnxMobSgwGaStatRxDataRecReqs,
                tmnxMobSgwGaStatUnackDataRexReqs,
                tmnxMobSgwGaStatRxRedirectionReq,
                tmnxMobSgwGaStatTxRedrnResp,
                tmnxMobSgwGaStatRxInvalidMsgs,
                tmnxMobSgwGaStatRxVerNotSupp,
                tmnxMobSgwGaStatTxCdrTermination,
                tmnxMobSgwGaStatTxCdrMaxChngCond,
                tmnxMobSgwGaStatTxCdrMsTmzChng,
                tmnxMobSgwGaStatTxCdrRatChng,
                tmnxMobSgwGaStatTxCdrTimeLimit,
                tmnxMobSgwGaStatTxCdrVolLimit,
                tmnxMobSgwGaStatRxCdrReqAcc,
                tmnxMobSgwGaStatRxCdrNoResAva,
                tmnxMobSgwGaStatRxCdrReqNotFf,
                tmnxMobSgwGaStatRxCdrReqFfilled,
                tmnxMobSgwGaStatRxCdrDupReqFf,
                tmnxMobSgwGaStatRxCdrInvMsgFmat,
                tmnxMobSgwGaStatRxCdrVerNotSupp,
                tmnxMobSgwGaStatRxCdrSrvcNotSupp,
                tmnxMobSgwGaStatRxCdrMandIeInc,
                tmnxMobSgwGaStatRxCdrMandIeMiss,
                tmnxMobSgwGaStatRxCdrOptIeInc,
                tmnxMobSgwGaStatRxCdrSystemFail,
                tmnxMobSgwGaStatRtrEchoRequests,
                tmnxMobSgwGaStatGtpPrimeFail,
                tmnxMobSgwGaStatOperState,
                tmnxMobSgwGaStatUpTime,
                tmnxMobSgwGaStatTxNodeAlRequests,
                tmnxMobSgwGaStatRxNodeAlResps,
                tmnxMobSgwGaStatNodeAlReqRetried,
                tmnxMobSgwGaStatCdrsTx,
                tmnxMobSgwGaStatCdrsRx,
                tmnxMobSgwGaStatTxCdrSerNdChLmt,
                tmnxMobServS11StatBearrResCmd,
                tmnxMobServS11StatBrrResFailInd,
                tmnxMobSgwGaStatTxVerNotSupp,
                tmnxMobServS11StatSuspNoticeReq,
                tmnxMobServS11StatSuspNoticeAck,
                tmnxMobServS11StatResNoticeReq,
                tmnxMobServS11StatResNoticeAck,
                tmnxMobSgwGaStatTxCdrMgmtInterv
            }
    STATUS      obsolete
    DESCRIPTION
        "The group of objects supporting management of the Serving Gateway
         (SGW) reference point statistics on the Nokia 7750 Mobile
         Gateway systems.

         This group was made obsolete in the 3.1 R2 release"
    ::= { tmnxMobServingGroups 11 }

tmnxMobServingBcV3v0Group  OBJECT-GROUP
    OBJECTS {
                tmnxMobServUeRowStatus,
                tmnxMobServUeMsIsdn,
                tmnxMobServUeImei,
                tmnxMobServUeNai,
                tmnxMobServUeNwkMcc,
                tmnxMobServUeNwkMnc,
                tmnxMobServUeTrackingAreaId,
                tmnxMobServUeCellId,
                tmnxMobServUeState,
                tmnxMobServUeRat,
                tmnxMobServUePdnContexts,
                tmnxMobServUeBearerContexts,
                tmnxMobServUeChassisIndex,
                tmnxMobServUeCardSlotNum,
                tmnxMobServUeS11MmeCtrlTeid,
                tmnxMobServUeS11MmeCtrlAddrType,
                tmnxMobServUeS11MmeCtrlAddr,
                tmnxMobServUeS11SgwCtrlTeid,
                tmnxMobServUeS11SgwCtrlAddrType,
                tmnxMobServUeS11SgwCtrlAddr,
                tmnxMobServUeS11InterEnbX2HandOv,
                tmnxMobServUeS11InterEnbS1HandOv,
                tmnxMobServUeS1ReleaseProcedures,
                tmnxMobServUePagingReq,
                tmnxMobServUeRfSgwAddrType,
                tmnxMobServUeRfSgwAddr,
                tmnxMobServPcLinkedBearerId,
                tmnxMobServPcApnRestriction,
                tmnxMobServPcUlApnAmbr,
                tmnxMobServPcDlApnAmbr,
                tmnxMobServPcIpv4AddressType,
                tmnxMobServPcIpv4Address,
                tmnxMobServPcIpv6AddressType,
                tmnxMobServPcIpv6Address,
                tmnxMobServPcBearerContexts,
                tmnxMobServPcSessionState,
                tmnxMobServPcLastEvent,
                tmnxMobServPcS5S8SigProtocol,
                tmnxMobServPcS5S8SgwCtrlTeid,
                tmnxMobServPcS5S8SgwCtrlAddrType,
                tmnxMobServPcS5S8SgwCtrlAddr,
                tmnxMobServPcS5S8PgwCtrlTeid,
                tmnxMobServPcS5S8PgwCtrlAddrType,
                tmnxMobServPcS5S8PgwCtrlAddr,
                tmnxMobServPcRfServerAddrType,
                tmnxMobServPcRfServerAddr,
                tmnxMobServPcRfServerState,
                tmnxMobServPcRfBearerType,
                tmnxMobServPcRfChargingLevel,
                tmnxMobServPcRfChargingProfile,
                tmnxMobServPcRfTriggeredRecords,
                tmnxMobServPcRfInterimRecords,
                tmnxMobServPcS5S8SgwV6CtrlAdrTyp,
                tmnxMobServPcS5S8SgwV6CtrlAddr,
                tmnxMobServPcS5S8PgwV6CtrlAdrTyp,
                tmnxMobServPcS5S8PgwV6CtrlAddr,
                tmnxMobServBcBearerType,
                tmnxMobServBcUpTime,
                tmnxMobServBcQci,
                tmnxMobServBcArp,
                tmnxMobServBcQosUlMbr,
                tmnxMobServBcQosDlMbr,
                tmnxMobServBcQosUlGbr,
                tmnxMobServBcQosDlGbr,
                tmnxMobServBcS1uEnodebTeid,
                tmnxMobServBcS1uEnodebAddrType,
                tmnxMobServBcS1uEnodebAddr,
                tmnxMobServBcS1uSgwTeid,
                tmnxMobServBcS1uSgwAddrType,
                tmnxMobServBcS1uSgwAddr,
                tmnxMobServBcS5S8SgwTeid,
                tmnxMobServBcS5S8SgwDataAddrType,
                tmnxMobServBcS5S8SgwDataAddr,
                tmnxMobServBcS5S8PgwTeid,
                tmnxMobServBcS5S8PgwDataAddrType,
                tmnxMobServBcS5S8PgwDataAddr,
                tmnxMobServBcS11QosModifications,
                tmnxMobServBcS5ULPackets,
                tmnxMobServBcS5ULBytes,
                tmnxMobServBcS1uDLPackets,
                tmnxMobServBcS1uDLBytes,
                tmnxMobServBcS5ULPacketsLow,
                tmnxMobServBcS5ULPacketsHigh,
                tmnxMobServBcS5ULBytesLow,
                tmnxMobServBcS5ULBytesHigh,
                tmnxMobServBcS1uDLPacketsLow,
                tmnxMobServBcS1uDLPacketsHigh,
                tmnxMobServBcS1uDLBytesLow,
                tmnxMobServBcS1uDLBytesHigh,
                tmnxMobServUeIntraSgwIdleTau,
                tmnxMobServUeInitServReqProcs,
                tmnxMobServPcAntiSpoofFailureCnt,
                tmnxMobServBcSetupLatencyTime,
                tmnxMobServBcIndTnlRemTeid,
                tmnxMobServBcIndTnlRemAddrType,
                tmnxMobServBcIndTnlRemAddr,
                tmnxMobServBcIndTnlLocalTeid,
                tmnxMobServBcIndTnlLocalAddrType,
                tmnxMobServBcIndTnlLocalAddr,
                tmnxMobServBcRfServerAddrType,
                tmnxMobServBcRfServerAddr,
                tmnxMobServBcRfServerState,
                tmnxMobServBcRfChargingProfile,
                tmnxMobServBcRfTriggeredRecords,
                tmnxMobServBcRfInterimRecords,
                tmnxMobServKeyType,
                tmnxMobServUeImsiStr,
                tmnxMobServPcImsiAuthStatus,
                tmnxMobServPcImeiStr,
                tmnxMobServPcImsiStr,
                tmnxMobServBcRefPointType,
                tmnxMobServPcRefPointType
            }
    STATUS      current
    DESCRIPTION
        "The group of objects supporting management of the Serving Gateway
         (SGW) bearer contexts on the Nokia 7750 Mobile Gateway
         systems."
    ::= { tmnxMobServingGroups 12 }

tmnxMobServingGlobalV3v0Group  OBJECT-GROUP
    OBJECTS {
                tmnxMobServGaTableLastChanged
            }
    STATUS      current
    DESCRIPTION
        "The group of global objects supporting management of the Serving
         Gateway (SGW) on the Nokia 7750 Mobile Gateway systems
         in 3.0 release."
    ::= { tmnxMobServingGroups 13 }

tmnxMobServingV3v0Group  OBJECT-GROUP
    OBJECTS {
                tmnxMobServGaLastChanged,
                tmnxMobServGaIfVRtrId,
                tmnxMobServGaIfIndex,
                tmnxMobServGaGtpcProfile,
                tmnxMobServGaGtpPrimeGrpName,
                tmnxMobServApnChrgProfileHome,
                tmnxMobServApnChrgProfVisiting,
                tmnxMobServApnChrgProfileRoaming,
                tmnxMobServApnChrgCcIgnoreAny,
                tmnxMobServApnChrgCcIgnoreHome,
                tmnxMobServApnChrgCcIgnoreVisit,
                tmnxMobServApnChrgCcIgnorRoaming,
                tmnxMobServApnChrgCcReject,
                tmnxMobServS8TableLastChanged,
                tmnxMobServS8LastChanged,
                tmnxMobServS8PeerList,
                tmnxMobServS8GtpcIfVRtrId,
                tmnxMobServS8GtpcIfIndex,
                tmnxMobServS8GtpuIfVRtrId,
                tmnxMobServS8GtpuIfIndex,
                tmnxMobServS8GtpcProfile,
                tmnxMobServS8GtpuProfile,
                tmnxMobServS8DualStackPref,
                tmnxMobServS8DualStackPrefCplane,
                tmnxMobServHomePlmnList
            }
    STATUS      current
    DESCRIPTION
        "The group of objects supporting management of the Serving Gateway (SGW)
         on the Nokia 7750 Mobile Gateway systems in 3.0 release."
    ::= { tmnxMobServingGroups 14 }

tmnxMobServingChargingV3Group  OBJECT-GROUP
    OBJECTS {
                tmnxMobServChrgNodeId
            }
    STATUS      current
    DESCRIPTION
        "The group of objects supporting the management of the Serving Gateway
         (SGW) charging applications on the Nokia 7750 Mobile Gateway
         systems in 3.0 release."
    ::= { tmnxMobServingGroups 15 }

tmnxMobServingThresholdV3Group OBJECT-GROUP
     OBJECTS {
                tmnxMobServThresLastChanged,
                tmnxMobServThresBrMgmtLmtUe,
                tmnxMobServThresBrMgmtLmtBr,
                tmnxMobServThresBrMgmtLmtDefBr,
                tmnxMobServThresBrMgmtLmtDedBr,
                tmnxMobServThresBrMgmtLmtActBr,
                tmnxMobServThresBrMgmtLmtUePgd,
                tmnxMobServThresBrMgmtCfsAttch,
                tmnxMobServThresBrMgmtCfsDedBr,
                tmnxMobServThresBrMgmtCfsSvrReq,
                tmnxMobServThresBrMgmtCfsItaRlc,
                tmnxMobServThresBrMgmtCfsItrRlc,
                tmnxMobServThresBrMgmtCfsIdlRlc,
                tmnxMobServThresBrMgmtCffAttch,
                tmnxMobServThresBrMgmtCffDedBr,
                tmnxMobServThresBrMgmtCffPaging,
                tmnxMobServThresBrMgmtCffHdOver,
                tmnxMobServThresBrMgmtCffSvrReq,
                tmnxMobServThresBrMgmtCffSrUnavl,
                tmnxMobServThresBrTrfcThrptUL,
                tmnxMobServThresBrTrfcThrptDL,
                tmnxMobServThresPthMgmtS5Fail,
                tmnxMobServThresPthMgmtS5Restart,
                tmnxMobServThresPthMgmtS5NoResp,
                tmnxMobServThresPthMgmtS11PrPath,
                tmnxMobServThresPthMgmtS11PrRstt,
                tmnxMobServThresPthMgmtS11NoResp ,
                tmnxMobServThresPthMgmtS1UENB,
                tmnxMobServThresPthMgmtS11MME,
                tmnxMobServThresPthMgmtS5Peer,
                tmnxMobServThresPthMgmtS8Peer,
                tmnxMobServThresPthMgmtRfFail
             }
     STATUS      current
     DESCRIPTION
         "The group of objects supporting management of the set thresholds
          of the Packet Data Network Gateway (PGW) on the Nokia
          7750 Mobile Gateway systems in 3.0 release."
     ::= { tmnxMobServingGroups 16 }

tmnxMobServingAcctStatsV3Group  OBJECT-GROUP
    OBJECTS {
                tmnxMobServBcAcctGaChargingId,
                tmnxMobServBcAcctGaUlSustRate,
                tmnxMobServBcAcctGaDlSustRate,
                tmnxMobServBcAcctGaAggrUlPkts,
                tmnxMobServBcAcctGaAggrUlPktsLow,
                tmnxMobServBcAcctGaAggrUlPktsHi,
                tmnxMobServBcAcctGaAggrDlPkts,
                tmnxMobServBcAcctGaAggrDlPktsLow,
                tmnxMobServBcAcctGaAggrDlPktsHi,
                tmnxMobServBcAcctGaAggrUlByts,
                tmnxMobServBcAcctGaAggrUlBytsLow,
                tmnxMobServBcAcctGaAggrUlBytsHi,
                tmnxMobServBcAcctGaAggrDlByts,
                tmnxMobServBcAcctGaAggrDlBytsLow,
                tmnxMobServBcAcctGaAggrDlBytsHi,
                tmnxMobServBcAcctGaNumPartCdrs,
                tmnxMobServBcAcctGaNumTdvs,
                tmnxMobServBcAcctGaNumMaxChanges,
                tmnxMobServPcAcctRfAggrUlPkts,
                tmnxMobServPcAcctRfAggrUlPktsLow,
                tmnxMobServPcAcctRfAggrUlPktsHi,
                tmnxMobServPcAcctRfAggrDlPkts,
                tmnxMobServPcAcctRfAggrDlPktsLow,
                tmnxMobServPcAcctRfAggrDlPktsHi,
                tmnxMobServPcAcctRfAggrUlByts,
                tmnxMobServPcAcctRfAggrUlBytsLow,
                tmnxMobServPcAcctRfAggrUlBytsHi,
                tmnxMobServPcAcctRfAggrDlByts,
                tmnxMobServPcAcctRfAggrDlBytsLow,
                tmnxMobServPcAcctRfAggrDlBytsHi,
                tmnxMobServPcAcctRfUlAvgRate,
                tmnxMobServPcAcctRfDlAvgRate,
                tmnxMobServPcAcctRfNumIntrimSent
            }
    STATUS      current
    DESCRIPTION
        "The group of objects supporting management of the Serving Gateway (SGW)
         accounting statistics on the Nokia 7750 Mobile Gateway
         systems."
    ::= { tmnxMobServingGroups 17 }

tmnxMobServingRefPointV3v5Group  OBJECT-GROUP
    OBJECTS {
                tmnxMobServS11StatDelSesnRspFl,
                tmnxMobServS11StatUpdtBearrRspFl,
                tmnxMobServS11StatModBearrRspFl,
                tmnxMobServS11StatDelBearrRspFl,
                tmnxMobServS11StatCreatBearRspFl,
                tmnxMobServS11StatCreatSesnRspFl,
                tmnxMobServS11StatRelBearrRespFl,
                tmnxMobServS11StatCrtIndTnlRspFl,
                tmnxMobServS11StatDelIndTnlRspFl,
                tmnxMobServS11StatRxDlAcksFail,
                tmnxMobServS11CcRxReqAccepted,
                tmnxMobServS11CcRxCtxNotFound,
                tmnxMobServS11CcRxInvalidLength,
                tmnxMobServS11CcRxMndIeIncorrect,
                tmnxMobServS11CcRxMandIeMissing,
                tmnxMobServS11CcRxReqRejected,
                tmnxMobServS11CcRxRemPeerNoResp,
                tmnxMobServS11CcRxNoResAvailable,
                tmnxMobServS11CcRxUsrAuthFailure,
                tmnxMobServS11CcRxOthers,
                tmnxMobServS11CcTxReqAccepted,
                tmnxMobServS11CcTxCtxNotFound,
                tmnxMobServS11CcTxInvalidLength,
                tmnxMobServS11CcTxMndIeIncorrect,
                tmnxMobServS11CcTxMandIeMissing,
                tmnxMobServS11CcTxReqRejected,
                tmnxMobServS11CcTxRemPeerNoResp,
                tmnxMobServS11CcTxNoResAvailable,
                tmnxMobServS11CcTxUsrAuthFailure,
                tmnxMobServS11CcTxOthers
            }
    STATUS      current
    DESCRIPTION
        "The group of objects supporting management of the Serving Gateway
         (SGW) reference point statistics on the Nokia 7750 Mobile
         Gateway systems in the 3.0 R5 release."
    ::= { tmnxMobServingGroups 18 }

tmnxMobServingRefPointGroupV31v2  OBJECT-GROUP
    OBJECTS {
                tmnxMobServS11PeerLastChanged,
                tmnxMobServS11PeerCreateTime,
                tmnxMobServS11PeerPathMgmtState,
                tmnxMobServS11PeerGatewayId,
                tmnxMobServS11StatCreateSessnReq,
                tmnxMobServS11StatCreateSessnRsp,
                tmnxMobServS11StatDeleteSessnReq,
                tmnxMobServS11StatDeleteSessnRsp,
                tmnxMobServS11StatCreateBearrReq,
                tmnxMobServS11StatCreateBearrRsp,
                tmnxMobServS11StatDeleteBearrReq,
                tmnxMobServS11StatDeleteBearrRsp,
                tmnxMobServS11StatModifyBearrReq,
                tmnxMobServS11StatModifyBearrRsp,
                tmnxMobServS11StatRxEchoRequests,
                tmnxMobServS11StatTxEchoResp,
                tmnxMobServS11StatTxEchoRequests,
                tmnxMobServS11StatRxEchoResp,
                tmnxMobServS11StatTxDlNotify,
                tmnxMobServS11StatRxDlAcks,
                tmnxMobServS11StatRxDlFailNotify,
                tmnxMobServS11StatRxMalfrmedPkts,
                tmnxMobServS11StatRxUnknownPkts,
                tmnxMobServS11StatRxMissngIePkts,
                tmnxMobServS11StatPeerRestarts,
                tmnxMobServS11StatPeerRestartCnt,
                tmnxMobServS11StatPathMgmtFails,
                tmnxMobServS11StatRelBearersReq,
                tmnxMobServS11StatRelBearersResp,
                tmnxMobServS11StatCrtIndrTnlReq,
                tmnxMobServS11StatCrtIndrTnlResp,
                tmnxMobServS11StatDelIndrTnlReq,
                tmnxMobServS11StatDelIndrTnlResp,
                tmnxMobServS1uPeerLastChanged,
                tmnxMobServS1uPeerCreateTime,
                tmnxMobServS1uPeerPathMgmtState,
                tmnxMobServS1uPeerGatewayId,
                tmnxMobServS1uStatBcNotFound,
                tmnxMobServS1uStatRxEchoRequests,
                tmnxMobServS1uStatTxEchoResponse,
                tmnxMobServS1uStatTxEchoRequests,
                tmnxMobServS1uStatRxEchoResponse,
                tmnxMobServS1uStatPeerRestarts,
                tmnxMobServS1uStatPeerRestartCnt,
                tmnxMobServS1uStatPathMgmtFails,
                tmnxMobServS11StatBearers,
                tmnxMobServS11StatUpdateBearrReq,
                tmnxMobServS11StatUpdateBearrRsp,
                tmnxMobServS1uStatUlBytes,
                tmnxMobServS1uStatDlBytes,
                tmnxMobServS1uStatUlPackets,
                tmnxMobServS1uStatDlPackets,
                tmnxMobServS1uStatBearers,
                tmnxMobServS11StatModifyBearrCmd,
                tmnxMobServS11StatModifyBearrFlr,
                tmnxMobServS11StatDeleteBearrCmd,
                tmnxMobServS11StatDeleteBearrFlr,
                tmnxMobSgwGaPeerLastChanged,
                tmnxMobSgwGaPeerCreateTime,
                tmnxMobSgwGaPeerPathMgmtState,
                tmnxMobSgwGaPeerDetailState,
                tmnxMobSgwGaStatLastChanged,
                tmnxMobSgwGaStatCreateTime,
                tmnxMobSgwGaStatRxEchoRequests,
                tmnxMobSgwGaStatTxEchoResponses,
                tmnxMobSgwGaStatTxEchoRequests,
                tmnxMobSgwGaStatRxEchoResponses,
                tmnxMobSgwGaStatRxNodeAlRequests,
                tmnxMobSgwGaStatTxNodeAlResps,
                tmnxMobSgwGaStatTxDataRecReqs,
                tmnxMobSgwGaStatTxDataRecTferReq,
                tmnxMobSgwGaStatRetrDataRecReqs,
                tmnxMobSgwGaStatRxDataRecReqs,
                tmnxMobSgwGaStatUnackDataRexReqs,
                tmnxMobSgwGaStatRxRedirectionReq,
                tmnxMobSgwGaStatTxRedrnResp,
                tmnxMobSgwGaStatRxInvalidMsgs,
                tmnxMobSgwGaStatRxVerNotSupp,
                tmnxMobSgwGaStatTxCdrTermination,
                tmnxMobSgwGaStatTxCdrMaxChngCond,
                tmnxMobSgwGaStatTxCdrMsTmzChng,
                tmnxMobSgwGaStatTxCdrRatChng,
                tmnxMobSgwGaStatTxCdrTimeLimit,
                tmnxMobSgwGaStatTxCdrVolLimit,
                tmnxMobSgwGaStatRxCdrReqAcc,
                tmnxMobSgwGaStatRxCdrNoResAva,
                tmnxMobSgwGaStatRxCdrReqNotFf,
                tmnxMobSgwGaStatRxCdrReqFfilled,
                tmnxMobSgwGaStatRxCdrDupReqFf,
                tmnxMobSgwGaStatRxCdrInvMsgFmat,
                tmnxMobSgwGaStatRxCdrVerNotSupp,
                tmnxMobSgwGaStatRxCdrSrvcNotSupp,
                tmnxMobSgwGaStatRxCdrMandIeInc,
                tmnxMobSgwGaStatRxCdrMandIeMiss,
                tmnxMobSgwGaStatRxCdrOptIeInc,
                tmnxMobSgwGaStatRxCdrSystemFail,
                tmnxMobSgwGaStatRtrEchoRequests,
                tmnxMobSgwGaStatGtpPrimeFail,
                tmnxMobSgwGaStatOperState,
                tmnxMobSgwGaStatUpTime,
                tmnxMobSgwGaStatTxNodeAlRequests,
                tmnxMobSgwGaStatRxNodeAlResps,
                tmnxMobSgwGaStatNodeAlReqRetried,
                tmnxMobSgwGaStatCdrsTx,
                tmnxMobSgwGaStatCdrsRx,
                tmnxMobSgwGaStatTxCdrSerNdChLmt,
                tmnxMobServS11StatBearrResCmd,
                tmnxMobServS11StatBrrResFailInd,
                tmnxMobSgwGaStatTxVerNotSupp,
                tmnxMobServS11StatSuspNoticeReq,
                tmnxMobServS11StatSuspNoticeAck,
                tmnxMobServS11StatResNoticeReq,
                tmnxMobServS11StatResNoticeAck,
                tmnxMobSgwGaStatTxCdrMgmtInterv
            }
    STATUS      current
    DESCRIPTION
        "The group of objects supporting management of the Serving Gateway
         (SGW) reference point statistics on the Nokia 7750 Mobile
         Gateway systems in the 3.1 release."
    ::= { tmnxMobServingGroups 19 }

tmnxMobServingObsoletedGrpV31v2   OBJECT-GROUP
    OBJECTS {
                tmnxMobServProcBearerRes,
                tmnxMobServProcBearerResFails,
                tmnxMobServProcDelBearers,
                tmnxMobServProcDelBearersFails,
                tmnxMobServProcEnbS1HndovrFails,
                tmnxMobServProcEnbX2HndovrFails,
                tmnxMobServProcInterENBS1Hndovr,
                tmnxMobServProcInterENBX2Hndovr,
                tmnxMobServProcInterMmeRel,
                tmnxMobServProcInterMmeRelFails,
                tmnxMobServProcMltPdnConcvtFails,
                tmnxMobServProcMltPdnConcvtReqs,
                tmnxMobServProcModBearers,
                tmnxMobServProcModBearersFails,
                tmnxMobServProcNwServiceReq,
                tmnxMobServProcNwServiceReqFails,
                tmnxMobServS11StatPagingSvcReq,
                tmnxMobServUePagedCount,
                tmnxMobServS1uStatBearersIpv4,
                tmnxMobServS1uStatBearersIpv6,
                tmnxMobServS1uStatBearerIpv4v6,
                tmnxMobServS1uStatDedctdBearers,
                tmnxMobServS1uStatDefBearers,
                tmnxMobServS1uStatRoamers,
                tmnxMobServS1uStatActiveBearers,
                tmnxMobServS1uStatIdleBearers,
                tmnxMobServS11StatBearersIpv4,
                tmnxMobServS11StatBearersIpv6,
                tmnxMobServS11StatBearerIpv4v6,
                tmnxMobServS11StatDedctdBearers,
                tmnxMobServS11StatDefBearers,
                tmnxMobServS11StatRoamers,
                tmnxMobServS11StatActiveBearers,
                tmnxMobServS11StatIdleBearers
            }
    STATUS      current
    DESCRIPTION
        "The group of obsolete objects which are no longer supported in the 3.1
         release on the Serving Gateway (SGW) on the Nokia 7750
         Mobile Gateway systems."
    ::= { tmnxMobServingGroups 20 }

tmnxMobServingV4v0Group  OBJECT-GROUP
    OBJECTS {
                tmnxMobServS11GtpcDdnDumpTimer,
                tmnxMobServChargingAvpDiag,
                tmnxMobServRfSuppVendorAvps
            }
    STATUS      current
    DESCRIPTION
        "The group of objects supporting management of the Serving Gateway (SGW)
         on the Nokia 7750 Mobile Gateway systems in 4.0 release."
    ::= { tmnxMobServingGroups 21 }

tmnxMobServStatV4v0Group  OBJECT-GROUP
    OBJECTS {
                tmnxMobServStatPagingDrops
            }
    STATUS      current
    DESCRIPTION
        "The group of objects supporting management of the Serving Gateway
         (SGW) statistics on the Nokia 7750 Mobile Gateway systems
         in 4.0 release."
    ::= { tmnxMobServingGroups 22 }

END
