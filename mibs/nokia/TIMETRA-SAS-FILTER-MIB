TIMETRA-SAS-FILTER-MIB DEFINITIONS ::= BEGIN

IMPORTS
    MODULE-IDENTITY, OBJECT-TYPE, NOTIFICATION-TYPE,
    Unsigned32, Integer32, IpAddress, Counter32, Counter64,
    Gauge32, TimeTicks, Opaque
        FROM SNMPv2-SMI

    MODULE-COMPLIANCE, OBJECT-GROUP, NOTIFICATION-GROUP
        FROM SNMPv2-CONF

    TEXTUAL-CONVENTION, RowStatus, MacAddress,
    TruthValue, DisplayString, TimeStamp,
    RowPointer

        FROM SNMPv2-TC

    timetraSRMIBModules, tmnxSRObjs, tmnxSRNotifyPrefix,
    tmnxSRConfs
        FROM TIMETRA-GLOBAL-MIB

    TmnxAdminState, TmnxOperState, TNamedItem,
    TNamedItemOrEmpty, Dot1PPriority, IpAddressPrefixLength,
    ServiceAccessPoint, TItemDescription, TDSCPNameOrEmpty,
    TDSCPFilterActionValue, TIpProtocol, TIpOption,
    TTcpUdpPort, TTcpUdpPortOperator, TFrameType,
    TmnxServId, TmnxPortID, TmnxEncapVal,
    SdpBindId
        FROM TIMETRA-TC-MIB

    InetAddressIPv6,InetAddressPrefixLength
        FROM INET-ADDRESS-MIB

    tIPFilterEntry, tIPv6FilterEntry            FROM TIMETRA-FILTER-MIB

    timetraSASObjs, timetraSASNotifyPrefix,
    timetraSASConfs, timetraSASModules          FROM TIMETRA-SAS-GLOBAL-MIB

    ;

timetraSASFilterMIBModule   MODULE-IDENTITY
        LAST-UPDATED    "1204010000Z"
        ORGANIZATION    "Alcatel"
        CONTACT-INFO
            "Alcatel 7x50 Support
             Web: http://www.alcatel.com/comps/pages/carrier_support.jhtml"
        DESCRIPTION
        "This document is the SNMP MIB module to manage and provision
         Filter features on Alcatel 7x50 systems.

         Copyright 2003-2012 Alcatel-Lucent. All rights reserved.
         Reproduction of this document is authorized on the condition that
         the foregoing copyright notice is included.

         This SNMP MIB module (Specification) embodies Alcatel's
         proprietary intellectual property.  Alcatel retains
         all title and ownership in the Specification, including any
         revisions.

         Alcatel grants all interested parties a non-exclusive
         license to use and distribute an unmodified copy of this
         Specification in connection with management of Alcatel
         products, and without fee, provided this copyright notice and
         license appear on all copies.

         This Specification is supplied 'as is', and Alcatel
         makes no warranty, either express or implied, as to the use,
         operation, condition, or performance of the Specification."

--
--  Revision History
--
        REVISION        "1204010000Z"
        DESCRIPTION     "Rev 1.0                01 Apr 2012 00:00
                         1.0 release of the TIMETRA-SAS-FILTER-MIB."

        ::= { timetraSASModules 16 }

tmnxSASFilterObjs             OBJECT IDENTIFIER ::= { timetraSASObjs 21 }

-- tmnxSASFilterConformance      OBJECT IDENTIFIER ::= { tmnxSASServConformance 20 }


tSASFilterObjects             OBJECT IDENTIFIER ::= { tmnxSASFilterObjs 1 }


--
-- mib objects
--

--
-- IP Filter Extn Table
--

tIPFilterExtnTable OBJECT-TYPE
    SYNTAX       SEQUENCE OF TIPFilterExtnEntry
    MAX-ACCESS   not-accessible
    STATUS       current
    DESCRIPTION
        "Contains a List of all ip filters configured on this system."
    ::= { tSASFilterObjects 1 }

tIPFilterExtnEntry OBJECT-TYPE
    SYNTAX       TIPFilterExtnEntry
    MAX-ACCESS   not-accessible
    STATUS       current
    DESCRIPTION
        "Information about a particular IP Filter entry. Entries are
         created/deleted  by user. Entries have a presumed StorageType of
         nonVolatile."
    AUGMENTS { tIPFilterEntry }
    ::= { tIPFilterExtnTable 1 }

TIPFilterExtnEntry ::= SEQUENCE
    {
        tFilterUseIpv6Resource TruthValue
    }

tFilterUseIpv6Resource  OBJECT-TYPE
    SYNTAX       TruthValue
    MAX-ACCESS   read-create
    STATUS       current
    DESCRIPTION
        "tFilterUseIpv6Resource specifies if the ipv6 resources should
        be used."
    DEFVAL { false }
    ::= { tIPFilterExtnEntry 1 }

--
-- IPv6 Filter Extn Table
--

tIPv6FilterExtnTable OBJECT-TYPE
    SYNTAX       SEQUENCE OF TIPv6FilterExtnEntry
    MAX-ACCESS   not-accessible
    STATUS       current
    DESCRIPTION
        "Contains a List of all IPv6 filters configured on this system."
    ::= { tSASFilterObjects 2 }

tIPv6FilterExtnEntry OBJECT-TYPE
    SYNTAX       TIPv6FilterExtnEntry
    MAX-ACCESS   not-accessible
    STATUS       current
    DESCRIPTION
        "Information about a particular IPv6 Filter entry. Entries are
         created/deleted  by user. Entries have a presumed StorageType of
         nonVolatile."
    AUGMENTS { tIPv6FilterEntry }
    ::= { tIPv6FilterExtnTable 1 }

TIPv6FilterExtnEntry ::= SEQUENCE
    {
        tFilter64Bitsor128    INTEGER
    }

tFilter64Bitsor128  OBJECT-TYPE
    SYNTAX  INTEGER {
                ipv6128 (1),
                ipv664  (2)
            }
    MAX-ACCESS   read-create
    STATUS       current
    DESCRIPTION
        "tFilter64Bitsor128 is used to create a 64 bit or 128 bit
        ipv6 filter."
    DEFVAL { ipv6128 }
    ::= { tIPv6FilterExtnEntry 1 }

END
