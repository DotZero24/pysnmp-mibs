TIMETRA-SAS-SYSTEM-MIB DEFINITIONS ::= BEGIN

IMPORTS

    MODULE-IDENTITY, OBJECT-TYPE,
    NOTIFICATION-TYPE, Gauge32,
    Integer32, IpAddress, Unsigned32        FROM SNMPv2-SMI

    MODULE-COMPLIANCE, OBJECT-GROUP,
    NOTIFICATION-GROUP                      FROM SNMPv2-CONF

    TEXTUAL-CONVENTION, DateAndTime,
    DisplayString, RowStatus,
    TruthValue, RowPointer, TimeStamp       FROM SNMPv2-TC

    timetraSASObjs, timetraSASNotifyPrefix,
    timetraSASConfs, timetraSASModules      FROM TIMETRA-SAS-GLOBAL-MIB

    timetraSRMIBModules, tmnxSRObjs,
    tmnxSRConfs, tmnxSRNotifyPrefix         FROM TIMETRA-GLOBAL-MIB

    TNamedItem, TNamedItemOrEmpty,
    TmnxAdminState, TmnxOperState,
    TmnxActionType, TTcpUdpPort,
    IpAddressPrefixLength,TmnxVwmCardType,
    TItemDescription,TPolicyID,TCIRRate,
    TPIRRate,TBurstSize, TmnxPortID,
    TSysResource, ServiceOperStatus,
    TmnxOperGrpHoldUpTime,
    TmnxOperGrpHoldDownTime                 FROM TN-TC-MIB

    TmnxLEDState, tmnxChassisIndex          FROM TIMETRA-CHASSIS-MIB

    InterfaceIndexOrZero                    FROM IF-MIB

    InetAddress
                                            FROM INET-ADDRESS-MIB

    tmnxHwName, tmnxCpmCardEntry,
    tmnxChassisNotifyHwIndex, tmnxCpmCardEntry,
    tmnxChassisEntry, tmnxHwID,
    tmnxHwClass, tmnxHwTemperature,
    tmnxHwEntry, tmnxHwOperState,
    tmnxChassisPowerSupplyEntry,
    tmnxChassisFanEntry, tmnxCardEntry,
    tmnxChassisPowerSupplyInputStatus,
    TmnxSlotNumOrZero,
    tmnxChassisPowerSupplyOutputStatus     FROM TIMETRA-CHASSIS-MIB;

timetraSASysMIBModule   MODULE-IDENTITY
        LAST-UPDATED    "0701010000Z"
        ORGANIZATION    "Alcatel"
        CONTACT-INFO
            "Alcatel 7x50 Support
             Web: http://www.alcatel.com/comps/pages/carrier_support.jhtml"
        DESCRIPTION
        "This document is the System SNMP MIB module for the Alcatel
        7x50 device.  The System MIB module defines SNMP objects to
        manage and provision system features.

        Copyright 2003-2014 Alcatel-Lucent. All rights reserved.
        Reproduction of this document is authorized on the condition
        that the foregoing copyright notice is included.

        This SNMP MIB module (Specification) embodies Alcatel's
        proprietary intellectual property.  Alcatel retains
        all title and ownership in the Specification, including any
        revisions.

        Alcatel grants all interested parties a non-exclusive
        license to use and distribute an unmodified copy of this
        Specification in connection with management of Alcatel
        products, and without fee, provided this copyright notice and
        license appear on all copies.

        This Specification is supplied `as is', and Alcatel
        makes no warranty, either express or implied, as to the use,
        operation, condition, or performance of the Specification."

--
--  Revision History
--
        REVISION        "0801010000Z"
        DESCRIPTION     "Rev 0.1                01 Jan 2008 00:00
                         First version of the TIMETRA-SAS-SYSTEM-MIB."
    ::= { timetraSASModules 7 }

--
--  sub-tree for ALcatel 7210 SAS System MIB managed objects
--
    tmnxSASSysObjs         OBJECT IDENTIFIER ::= { timetraSASObjs 5 }
    tmnxSASChassisObjs     OBJECT IDENTIFIER ::= { timetraSASObjs 6 }
    tmnxSASSysConformance  OBJECT IDENTIFIER ::= { timetraSASConfs 3 }

--
--  Sub-tree for Alcatel 7210 SAS System MIB notification (trap) events
--
tmnxSASSysMIBNotifyPrefix  OBJECT IDENTIFIER ::= { timetraSASNotifyPrefix 1 }
tmnxSASSysNotifications    OBJECT IDENTIFIER ::= { tmnxSASSysMIBNotifyPrefix 3 }
tmnxSASChassisNotificationObjs OBJECT IDENTIFIER ::= { tmnxSASChassisObjs 1 }
tmnxSASChassisNotification OBJECT IDENTIFIER ::= { tmnxSASChassisObjs 2 }


sysSASBofInfo           OBJECT IDENTIFIER ::= { tmnxSASSysObjs 11 }
sysEthMgmtBofInfo       OBJECT IDENTIFIER ::= { tmnxSASSysObjs 12 }
sysMpointMgmtInfo       OBJECT IDENTIFIER ::= { tmnxSASSysObjs 15 }
sysLoopBackInfo         OBJECT IDENTIFIER ::= { tmnxSASSysObjs 16 }
sysResourceProfInfo     OBJECT IDENTIFIER ::= { tmnxSASSysObjs 17 }
sysSASObjs              OBJECT IDENTIFIER ::= { tmnxSASSysObjs 18 }
sysSASVwmObjs           OBJECT IDENTIFIER ::= { tmnxSASSysObjs 19 }
sysQosObjs              OBJECT IDENTIFIER ::= { tmnxSASSysObjs 20 }
sysClockInfo            OBJECT IDENTIFIER ::= { tmnxSASSysObjs 21 }
sysResProfPlcyObjs      OBJECT IDENTIFIER ::= { tmnxSASSysObjs 22 }
sysResProfDecommObjs    OBJECT IDENTIFIER ::= { tmnxSASSysObjs 23 }
sysOperGrpObjs          OBJECT IDENTIFIER ::= { tmnxSASSysObjs 24 }

tmnxSASSecurityObjects         OBJECT IDENTIFIER ::= { timetraSASObjs 15 }
tmnxSASSecurityNotifyPrefix    OBJECT IDENTIFIER ::= { timetraSASNotifyPrefix 2 }
    tmnxSASSecurityNotifications   OBJECT IDENTIFIER ::= { tmnxSASSecurityNotifyPrefix 0 }

TmnxFanCfgMode ::= TEXTUAL-CONVENTION
    STATUS   current
    DESCRIPTION
       "User controlled fan oper modes"
    SYNTAX   INTEGER {
                 on (1),
                 off (2),
                 auto (3)
                 }

TmnxPtpTime ::= TEXTUAL-CONVENTION
    STATUS   current
    DESCRIPTION
       "Identify usage of PTP derived time."
    SYNTAX   INTEGER {
                 noPtpTime (0),
                 system (1),
                 oam (2)
                 }

TmnxSysOperGrpCreationOrigin ::= TEXTUAL-CONVENTION
    STATUS          current
    DESCRIPTION
        "A number used to identify creation origin for the system operational
        group."
    SYNTAX         INTEGER {
                     manual    (1),
                     mvrp      (2)
                   }

sbiUplinkAPort  OBJECT-TYPE
    SYNTAX      InterfaceIndexOrZero
    MAX-ACCESS  read-write
    STATUS      current
    DESCRIPTION
        "Primary bof port used for autoconfig. When set to zero
        'uplinAport' would be reset"
    ::= { sysSASBofInfo 1 }

sbiUplinkAIpAddr  OBJECT-TYPE
    SYNTAX      IpAddress
    MAX-ACCESS  read-write
    STATUS      current
    DESCRIPTION
        "Primary bof port ip address"
    ::= { sysSASBofInfo 2 }

sbiUplinkAMask  OBJECT-TYPE
    SYNTAX      IpAddressPrefixLength
    MAX-ACCESS  read-write
    STATUS      current
    DESCRIPTION
        "The value of sbiActiveIpMask specifies the mask length of the
         subnet associated with the IP address of the primary bof port."
    DEFVAL { 0 }
    ::= { sysSASBofInfo 3 }

sbiUplinkAVlan  OBJECT-TYPE
    SYNTAX      Integer32 (-1..4094)
    MAX-ACCESS  read-write
    STATUS      current
    DESCRIPTION
        "Vlan tag to be used on uplinkA, if set to -1 packets are sent out without
         vlan tag"
    DEFVAL { -1 }
    ::= { sysSASBofInfo 5 }

sbiUplinkBPort  OBJECT-TYPE
    SYNTAX      InterfaceIndexOrZero
    MAX-ACCESS  read-write
    STATUS      current
    DESCRIPTION
        "Secondary bof port used for autoconfig. When set to zero
        'uplinBport' would be reset"
    ::= { sysSASBofInfo 6 }

sbiUplinkBIpAddr  OBJECT-TYPE
    SYNTAX      IpAddress
    MAX-ACCESS  read-write
    STATUS      current
    DESCRIPTION
        "Secondary bof port ip address"
    ::= { sysSASBofInfo 7 }


sbiUplinkBMask  OBJECT-TYPE
    SYNTAX      IpAddressPrefixLength
    MAX-ACCESS  read-write
    STATUS      current
    DESCRIPTION
        "The value of sbiActiveIpMask specifies the mask length of the
         subnet associated with the IP address of the bof uplink B port."
    DEFVAL { 0 }
    ::= { sysSASBofInfo 8 }

sbiUplinkBVlan  OBJECT-TYPE
    SYNTAX      Integer32 (-1..4094)
    MAX-ACCESS  read-write
    STATUS      current
    DESCRIPTION
        "Vlan tag to be used on uplinkB, if set to -1 packets are sent out without
         vlan tag"
    DEFVAL { -1 }
    ::= { sysSASBofInfo 10 }

sbiPingAddress OBJECT-TYPE
    SYNTAX      IpAddress
    MAX-ACCESS  read-write
    STATUS      current
    DESCRIPTION
        "IP address to be used for ping-test after booting. This is the
         last step in the auto-init process"
    ::= { sysSASBofInfo 11 }

sbiUplinkRouteTable   OBJECT-TYPE
    SYNTAX      SEQUENCE OF SbiUplinkRouteEntry
    MAX-ACCESS  not-accessible
    STATUS      current
    DESCRIPTION
        "The sbiUplinkRouteTable contains an entry for each static route
         configured for the given uplink A or B. These static routes are
         only used during the system bootup"
    ::= { sysSASBofInfo 12}

sbiUplinkRouteEntry OBJECT-TYPE
    SYNTAX      SbiUplinkRouteEntry
    MAX-ACCESS  not-accessible
    STATUS      current
    DESCRIPTION
        "Each row entry contains information about a static route
         configured for the inband mangement.

         Entries in this table can be created and deleted via SNMP
         SET operations to sbiUplinkRouteRowStatus."
    INDEX { sbiUplinkAorB, sbiUplinkRouteDest,
            sbiUplinkRouteMask }
    ::= { sbiUplinkRouteTable 1 }

SbiUplinkRouteEntry ::=
    SEQUENCE {
        sbiUplinkAorB                   Unsigned32,
        sbiUplinkRouteDest              IpAddress,
        sbiUplinkRouteMask              IpAddressPrefixLength,
        sbiUplinkRouteNextHop           IpAddress,
        sbiUplinkRouteRowStatus         RowStatus
    }

sbiUplinkAorB  OBJECT-TYPE
    SYNTAX      Unsigned32 (1|2)
    MAX-ACCESS  not-accessible
    STATUS      current
    DESCRIPTION
        "If set to 1 this route is for the uplinkA, if it is set to 2 it is for uplinkB"
    ::= { sbiUplinkRouteEntry 1 }

sbiUplinkRouteDest  OBJECT-TYPE
    SYNTAX      IpAddress
    MAX-ACCESS  not-accessible
    STATUS      current
    DESCRIPTION
        "The value of 'sbiUplinkBofRouteDest' specifies the destination IP
         address of this static route."
    ::= { sbiUplinkRouteEntry 2 }

sbiUplinkRouteMask  OBJECT-TYPE
    SYNTAX      IpAddressPrefixLength
    MAX-ACCESS  not-accessible
    STATUS      current
    DESCRIPTION
        "The value of sbiUplinkRouteMask specifies the length of the
         subnet mask associated with the destination IP address of this
         static route."
    ::= { sbiUplinkRouteEntry 3 }

sbiUplinkRouteNextHop  OBJECT-TYPE
    SYNTAX      IpAddress
    MAX-ACCESS  read-create
    STATUS      current
    DESCRIPTION
        "The value of sbiUplinkRouteNextHop specifies the IP address of
         the next hop for this static route. This IP address should be
         in the same subnet as the ethernet port on the active CPM.
         The value of sbiUplinkRouteNextHop must be set to a valid IP
         address for the row creation to succeed."
    ::= { sbiUplinkRouteEntry 4 }

sbiUplinkRouteRowStatus  OBJECT-TYPE
    SYNTAX      RowStatus
    MAX-ACCESS  read-create
    STATUS      current
    DESCRIPTION
        "sbiUplinkRouteRowStatus controls the creation and deletion of
         rows in the table. To create a row in this table, set the row
         status to createAndGo(4)'. The value of sbiUplinkRouteNextHop
         must also be set to a valid IP address for the row creation to
         succeed. To delete a row in this table, set the row status to
         delete(6)."
    ::= { sbiUplinkRouteEntry 5 }


-- Out of Ethernet Mangement Objects

sbiEthMgmtDisabled  OBJECT-TYPE
    SYNTAX      TruthValue
    MAX-ACCESS  read-write
    STATUS      current
    DESCRIPTION
        "The value of sbiEthMgmtDisabled determines whether or not the
         out of band ethernet management port is enabled. When set to
         'true', out of band ethernet management port is disabled."
    DEFVAL { true }
    ::= { sysEthMgmtBofInfo 1 }

sbiEthMgmtActiveIpAddr  OBJECT-TYPE
    SYNTAX      IpAddress
    MAX-ACCESS  read-write
    STATUS      current
    DESCRIPTION
        "The value of sbiEthMgmtActiveIpAddr specifies the IP address of
        the out of band ethernet port."
    DEFVAL { 0 }
    ::= { sysEthMgmtBofInfo 2 }

sbiEthMgmtActiveIpMask  OBJECT-TYPE
    SYNTAX      IpAddressPrefixLength
    MAX-ACCESS  read-write
    STATUS      current
    DESCRIPTION
        "The value of sbiEthMgmtActiveIpMask specifies the mask length of the
         subnet associated with the IP address of the out of band ethernet port."
    DEFVAL { 0 }
    ::= { sysEthMgmtBofInfo 3 }

sbiEthMgmtAutoNegotiate  OBJECT-TYPE
    SYNTAX      TruthValue
    MAX-ACCESS  read-write
    STATUS      current
    DESCRIPTION
        "The value of sbiEthMgmtAutoNegotiate determines whether or not the
         speed and duplex parameters will be automatically negotiated on the
         out of band ethernet port. "
    DEFVAL { true }
    ::= { sysEthMgmtBofInfo 4 }

sbiEthMgmtSpeed  OBJECT-TYPE
    SYNTAX      Unsigned32 (10|100)
    UNITS       "Mbps"
    MAX-ACCESS  read-write
    STATUS      current
    DESCRIPTION
        "The value of sbiEthMgmtSpeed specifies the speed of the out of band
        ethernet port. This value is ignored if auto-negotiation is enabled."
    DEFVAL { 100 }
    ::= { sysEthMgmtBofInfo 5 }

sbiEthMgmtDuplex  OBJECT-TYPE
    SYNTAX      INTEGER {
                    full(1),
                    half (2)
                }
    MAX-ACCESS  read-write
    STATUS      current
    DESCRIPTION
        "The value of sbiEthMgmtDuplex specifies the duplex mode for the
        out of band ethernet port. This value is ignored if auto-negotiation
        is enabled."
    DEFVAL { full }
    ::= { sysEthMgmtBofInfo 6 }

sbiEthMgmtStaticRouteTable   OBJECT-TYPE
    SYNTAX      SEQUENCE OF SbiEthMgmtStaticRouteEntry
    MAX-ACCESS  not-accessible
    STATUS      current
    DESCRIPTION
        "The sbiEthMgmtStaticRouteTable contains an entry for each static
        route configured for the out of band ethernet port. These static
        routes are only used to route traffic generated by the out of band
        ethernet port.The table can have upto a maximum of 10 entries."
    ::= { sysEthMgmtBofInfo 7 }

sbiEthMgmtStaticRouteEntry OBJECT-TYPE
    SYNTAX      SbiEthMgmtStaticRouteEntry
    MAX-ACCESS  not-accessible
    STATUS      current
    DESCRIPTION
        "Each row entry contains information about a static route
         configured for the out of band ethernet port.

         Entries in this table can be created and deleted via SNMP
         SET operations to sbiEthMgmtStaticRouteRowStatus."
    INDEX { sbiEthMgmtStaticRouteDest,
            sbiEthMgmtStaticRouteMask }
    ::= { sbiEthMgmtStaticRouteTable 1 }

SbiEthMgmtStaticRouteEntry ::=
    SEQUENCE {
        sbiEthMgmtStaticRouteDest              IpAddress,
        sbiEthMgmtStaticRouteMask              IpAddressPrefixLength,
        sbiEthMgmtStaticRouteNextHop           IpAddress,
        sbiEthMgmtStaticRouteRowStatus         RowStatus
    }

sbiEthMgmtStaticRouteDest  OBJECT-TYPE
    SYNTAX      IpAddress
    MAX-ACCESS  not-accessible
    STATUS      current
    DESCRIPTION
        "The value of sbiEthMgmtStaticRouteDest specifies the destination IP
         address of this static route."
    ::= { sbiEthMgmtStaticRouteEntry 1 }

sbiEthMgmtStaticRouteMask  OBJECT-TYPE
    SYNTAX      IpAddressPrefixLength
    MAX-ACCESS  not-accessible
    STATUS      current
    DESCRIPTION
        "The value of sbiEthMgmtStaticRouteMask specifies the length of the
         subnet mask associated with the destination IP address of this
         static route."
    ::= { sbiEthMgmtStaticRouteEntry 2 }

sbiEthMgmtStaticRouteNextHop  OBJECT-TYPE
    SYNTAX      IpAddress
    MAX-ACCESS  read-create
    STATUS      current
    DESCRIPTION
        "The value of sbiEthMgmtStaticRouteNextHop specifies the IP address of
         the next hop for this static route. This IP address should be
         in the same subnet as the ethernet port on the active CPM.
         The value of sbiEthMgmtStaticRouteNextHop must be set to a valid IP
         address for the row creation to succeed."
    ::= { sbiEthMgmtStaticRouteEntry 3 }

sbiEthMgmtStaticRouteRowStatus  OBJECT-TYPE
    SYNTAX      RowStatus
    MAX-ACCESS  read-create
    STATUS      current
    DESCRIPTION
        "sbiEthMgmtStaticRouteRowStatus controls the creation and deletion of
         rows in the table. To create a row in this table, set the row
         status to createAndGo(4)'. The value of sbiEthMgmtStaticRouteNextHop
         must also be set to a valid IP address for the row creation to
         succeed. To delete a row in this table, set the row status to
         delete(6)."
    ::= { sbiEthMgmtStaticRouteEntry 4 }

--

sbiNoServicePortOne  OBJECT-TYPE
    SYNTAX      InterfaceIndexOrZero
    MAX-ACCESS  read-write
    STATUS      current
    DESCRIPTION
        "The value of sbiNoServicePortOne indicates service traffic
        on the port identified by this InterfaceIndex is disabled."
    DEFVAL { 0 }
    ::= { sysSASBofInfo 13 }

sbiNoServicePortTwo  OBJECT-TYPE
    SYNTAX      InterfaceIndexOrZero
    MAX-ACCESS  read-write
    STATUS      current
    DESCRIPTION
        "The value of sbiNoServicePortTwo indicates service traffic
        on the port identified by this InterfaceIndex is disabled."
    DEFVAL { 0 }
    ::= { sysSASBofInfo 14 }

--

sbiUplinkAdminMode OBJECT-TYPE
    SYNTAX      INTEGER {
                    network (1),
                    access-uplink (2)
                }
    MAX-ACCESS  read-write
    STATUS      current
    DESCRIPTION
        "sbiUplinkAdminMode when set to access-uplink, bof uplink would be used
        in l2 mode,the default mode is network"
    DEFVAL { network }
    ::= { sysSASBofInfo 15 }

sbiUplinkOperMode OBJECT-TYPE
    SYNTAX      INTEGER {
                    network (1),
                    access-uplink (2)
                }
    MAX-ACCESS  read-only
    STATUS      current
    DESCRIPTION
        "sbiUplinkOperMode is operational mode of the system. This object is
        initialized during system bootup based on sbiUplinkAdminMode setting"
    ::= { sysSASBofInfo 16 }

--

sbiExpansionCardType OBJECT-TYPE
    SYNTAX      INTEGER {
                    m4-ds1-ces (1),
                    m2-xfp (2)
                }
    MAX-ACCESS  read-write
    STATUS      current
    DESCRIPTION
        "sbiExpansionCardType identifies the expansion card type to the system
        before boot up. The system will not allow for provisioning of a different
        MDA than the one currently specified in the BOF. Changes to
        sbiExpansionCardType equires a reboot to take effect"
    DEFVAL { m4-ds1-ces }
    ::= { sysSASBofInfo 17 }

sbiConsoleDisabled  OBJECT-TYPE
    SYNTAX      TruthValue
    MAX-ACCESS  read-write
    STATUS      current
    DESCRIPTION
        "The value of sbiConsoleDisabled determines whether or not the
         system console is disabled. When set to 'true' console is disabled."
    DEFVAL { false }
    ::= { sysSASBofInfo 18}

sbiPassword OBJECT-TYPE
    SYNTAX      OCTET STRING (SIZE(1..20))
    MAX-ACCESS  read-write
    STATUS      current
    DESCRIPTION
        "sbiPassword is used to enable the user to configure the bof
        password."
    ::= { sysSASBofInfo 19 }

sbiUplinkAAutoNegotiate  OBJECT-TYPE
    SYNTAX      TruthValue
    MAX-ACCESS  read-write
    STATUS      current
    DESCRIPTION
        "The value of sbiUplinkAAutoNegotiate determines whether or not the
         speed and duplex parameters will be automatically negotiated
         on the uplinkAport. When set to 'true', auto-negotiation
         is enabled."
    DEFVAL { true }
    ::= { sysSASBofInfo 20 }

sbiUplinkASpeed  OBJECT-TYPE
    SYNTAX      Unsigned32 (10|100|1000)
    UNITS       "Mbps"
    MAX-ACCESS  read-write
    STATUS      current
    DESCRIPTION
        "The value of sbiSpeed specifies the speed of the uplinkA
         port. This value is ignored if auto-negotiation is enabled."
    DEFVAL { 100 }
    ::= { sysSASBofInfo 21 }

sbiUplinkADuplex  OBJECT-TYPE
    SYNTAX      INTEGER {
                    full(1),
                    half (2)
                }
    MAX-ACCESS  read-write
    STATUS      current
    DESCRIPTION
        "The value of sbiDuplex specifies the duplex mode for the
         uplinkA port. This value is ignored if auto-negotiation is
         enabled."
    DEFVAL { full }
    ::= { sysSASBofInfo 22 }

sbiUplinkBAutoNegotiate  OBJECT-TYPE
    SYNTAX      TruthValue
    MAX-ACCESS  read-write
    STATUS      current
    DESCRIPTION
        "The value of sbiUplinkBAutoNegotiate determines whether or not the
         speed and duplex parameters will be automatically negotiated
         on the uplinkBport. When set to 'true', auto-negotiation
         is enabled."
    DEFVAL { true }
    ::= { sysSASBofInfo 23 }

sbiUplinkBSpeed  OBJECT-TYPE
    SYNTAX      Unsigned32 (10|100|1000)
    UNITS       "Mbps"
    MAX-ACCESS  read-write
    STATUS      current
    DESCRIPTION
        "The value of sbiSpeed specifies the speed of the uplinkB
         port. This value is ignored if auto-negotiation is enabled."
    DEFVAL { 100 }
    ::= { sysSASBofInfo 24 }

sbiUplinkBDuplex  OBJECT-TYPE
    SYNTAX      INTEGER {
                    full(1),
                    half (2)
                }
    MAX-ACCESS  read-write
    STATUS      current
    DESCRIPTION
        "The value of sbiDuplex specifies the duplex mode for the
         uplinkB port. This value is ignored if auto-negotiation is
         enabled."
    DEFVAL { full }
    ::= { sysSASBofInfo 25 }

--

tmnxChassisExtnTable OBJECT-TYPE
    SYNTAX  SEQUENCE OF TmnxChassisExtnEntry
    MAX-ACCESS  not-accessible
    STATUS      current
    DESCRIPTION
        "The chassis table has an entry for each chassis in the system. This
         table extends the tmnxChassisTable for the SAS platform"
    ::= { tmnxSASChassisObjs 3 }

tmnxChassisExtnEntry    OBJECT-TYPE
    SYNTAX      TmnxChassisExtnEntry
    MAX-ACCESS  not-accessible
    STATUS      current
    DESCRIPTION
        "An entry in this table would be created for every entry in the
         tmnxChassisEntry"
    AUGMENTS    { tmnxChassisEntry }
    ::= { tmnxChassisExtnTable 1 }

TmnxChassisExtnEntry ::=
    SEQUENCE {
        tmnxChassisUpdateGoldenBootstrapImage     TmnxActionType,
        tmnxChassisGoldenBootstrapImageSrc        DisplayString,
        tmnxChassisValidateGoldenBootstrapImage   TmnxActionType,
        tmnxChassisGoldenBootstrapImageVersion    DisplayString,
        tmnxChassisRebootAutoInit                 TmnxActionType,
        tmnxChassisLowTempState                   INTEGER,
        tmnxChassisSystemLEDState                 TmnxLEDState
    }

tmnxChassisUpdateGoldenBootstrapImage OBJECT-TYPE
     SYNTAX      TmnxActionType
     MAX-ACCESS  read-write
     STATUS      current
     DESCRIPTION
        "Setting this action variable to 'doAction' causes the current
         golden bootstrap image to be updated with the image at the location
         specified by tmnxChassisGoldenBootstrapImageSrc.  If no location is
         specified by tmnxChassisGoldenBootstrapImageSrc, cf1:/boot.tim will
         be saved as the golden bootstrap image."
    DEFVAL { notApplicable }
    ::= { tmnxChassisExtnEntry 1 }

tmnxChassisGoldenBootstrapImageSrc OBJECT-TYPE
     SYNTAX      DisplayString
     MAX-ACCESS  read-write
     STATUS      current
     DESCRIPTION
       "The value of tmnxChassisGoldenBootstrapImageSrc specifies the source
        filepath or file-URL which will be saved as the golden bootstrap image
        when tmnxChassisUpdateGoldenBootstrapImage is set to 'doAction'.  If
        'tmnxChassisGoldenBootstrapImage'  is set to the empty string, ''H,
        cf1:/boot.tim will be saved as the golden bootstrap image."
     ::= { tmnxChassisExtnEntry 2 }

tmnxChassisValidateGoldenBootstrapImage OBJECT-TYPE
     SYNTAX      TmnxActionType
     MAX-ACCESS  read-write
     STATUS      current
     DESCRIPTION
        "Setting this action variable to 'doAction' causes the current
         golden bootstrap image to be validated and upon completion
         tmnxChassisGoldenBootstrapImageVersion will be populated with its
         version. If the validation fails tmnxChassisGoldenBootstrapImageVersion
         will be populated apropriately. "
    DEFVAL { notApplicable }
    ::= { tmnxChassisExtnEntry 3 }

tmnxChassisGoldenBootstrapImageVersion OBJECT-TYPE
     SYNTAX      DisplayString
     MAX-ACCESS  read-only
     STATUS      current
     DESCRIPTION
        "This object is populated with the version of the golden bootstrap image
         when validation is completed. If the validation fails, one of the
         following values is set:
            'Invalid Golden Bootstrap Image' - Indicates the image is invalid."
    DEFVAL { "not-validated" }
     ::= { tmnxChassisExtnEntry 4 }

tmnxChassisRebootAutoInit OBJECT-TYPE
     SYNTAX      TmnxActionType
     MAX-ACCESS  read-write
     STATUS      current
     DESCRIPTION
        "Setting this action variable to 'doAction', will reset the bof and
         reboot the system"
     ::= { tmnxChassisExtnEntry 5 }

tmnxChassisLowTempState    OBJECT-TYPE
    SYNTAX      INTEGER {
                    stateOk       (1),
                    stateLowTemp (2)
                }
    MAX-ACCESS  read-only
    STATUS      current
    DESCRIPTION
        "The current Low Temperature state of this chassis.

         stateOk         Indicates chassis is above the low temperature threshold.
         stateLowTemp    Indicates chassis is below the low temperature threshold."
    ::= { tmnxChassisExtnEntry 6 }

tmnxChassisSystemLEDState    OBJECT-TYPE
    SYNTAX      TmnxLEDState
    MAX-ACCESS  read-only
    STATUS      current
    DESCRIPTION
        "The current state of the System LED in this chassis."
  ::= { tmnxChassisExtnEntry 7 }

tmnxHwExtnTable OBJECT-TYPE
    SYNTAX  SEQUENCE OF TmnxHwExtnEntry
    MAX-ACCESS  not-accessible
    STATUS      current
    DESCRIPTION
        "The tmnxHwTable has an entry for each managed hardware component.
        This table extends the TmnxHwEntry for the SAS platform"
    ::= { tmnxSASChassisObjs 4 }

tmnxHwExtnEntry  OBJECT-TYPE
    SYNTAX      TmnxHwExtnEntry
    MAX-ACCESS  not-accessible
    STATUS      current
    DESCRIPTION
        "An entry in this table would be created for every entry in the
         tmnxChassisEntry"
    AUGMENTS    { tmnxHwEntry }
    ::= { tmnxHwExtnTable 1 }

TmnxHwExtnEntry ::=
    SEQUENCE {
        tmnxHwLowTempThreshold         Integer32
    }

tmnxHwLowTempThreshold   OBJECT-TYPE
    SYNTAX      Integer32
    UNITS       "degrees celsius"
    MAX-ACCESS  read-only
    STATUS      current
    DESCRIPTION
        "The low temperature threshold for this hardware component in degrees
         celsius.  When the value of tmnxHwTemperature lowers below
         tmnxHwLowTempThreshold, a 'temperature too low' event will
         be generated."
    ::= { tmnxHwExtnEntry 1 }

tmnxFabricPolicyTable OBJECT-TYPE
    SYNTAX   SEQUENCE OF TmnxFabricPolicyEntry
    MAX-ACCESS not-accessible
    STATUS   current
    DESCRIPTION
           "This table provides the context to configure the fabric policy in use
           by different applications. Currently, PBB is the only application using it and only
           one default object is supported"
    ::= { tmnxSASChassisObjs 5 }

tmnxFabricPolicyEntry OBJECT-TYPE
    SYNTAX    TmnxFabricPolicyEntry
    MAX-ACCESS   not-accessible
    STATUS    current
    DESCRIPTION   ""
    INDEX  {tmnxFabricPolicyIndex}
    ::= {tmnxFabricPolicyTable 1}

TmnxFabricPolicyEntry ::=
     SEQUENCE {
                        tmnxFabricPolicyIndex     TPolicyID,
                        tmnxFabricPolicyRowStatus    RowStatus,
                        tmnxFabricPolicyCIR   TCIRRate,
                        tmnxFabricPolicyPIR    TPIRRate,
                        tmnxFabricPolicyCBS   TBurstSize,
                        tmnxFabricPolicyMBS   TBurstSize,
                        tmnxFabricPolicyMpointFabricPort   Integer32
                       }

tmnxFabricPolicyIndex OBJECT-TYPE
    SYNTAX       TPolicyID (1..65535)
    MAX-ACCESS   not-accessible
    STATUS       current
    DESCRIPTION
        "the policy ID is the index to this table."
    ::= { tmnxFabricPolicyEntry 1 }

tmnxFabricPolicyRowStatus OBJECT-TYPE
    SYNTAX       RowStatus
    MAX-ACCESS   read-create
    STATUS       current
    DESCRIPTION
        "Row Status for the policy."
    ::= { tmnxFabricPolicyEntry 2 }

tmnxFabricPolicyCIR OBJECT-TYPE
    SYNTAX       TCIRRate
    UNITS        "kbps"
    MAX-ACCESS   read-create
    STATUS       current
    DESCRIPTION
        "The CIR specified by the user."
    DEFVAL { 0 }
    ::= { tmnxFabricPolicyEntry 3 }

tmnxFabricPolicyPIR OBJECT-TYPE
    SYNTAX       TPIRRate
    UNITS        "kbps"
    MAX-ACCESS   read-create
    STATUS       current
    DESCRIPTION
        "The PIR specified by the user."
    DEFVAL { 8000000 }
    ::= { tmnxFabricPolicyEntry 4 }

tmnxFabricPolicyCBS OBJECT-TYPE
    SYNTAX       TBurstSize
    MAX-ACCESS   read-create
    STATUS       current
    DESCRIPTION
        "The amount of reserved buffer space (in kilo bytes)."
    DEFVAL { 4 }
    ::= { tmnxFabricPolicyEntry 5 }

tmnxFabricPolicyMBS OBJECT-TYPE
    SYNTAX       TBurstSize
    MAX-ACCESS   read-create
    STATUS       current
    DESCRIPTION
        "The maximum amount of buffer space (in kilo bytes) allowed"
    DEFVAL { -1 }
    ::= { tmnxFabricPolicyEntry 6 }

tmnxFabricPolicyMpointFabricPort  OBJECT-TYPE
    SYNTAX      Integer32 (0..4)
    MAX-ACCESS  read-create
    STATUS      current
    DESCRIPTION
        ""
    DEFVAL { 2 }
    ::= { tmnxFabricPolicyEntry 7 }


tmnxChassisPowerSupplyExtnTable OBJECT-TYPE
    SYNTAX      SEQUENCE OF TmnxChassisPowerSupplyExtnEntry
    MAX-ACCESS  not-accessible
    STATUS      current
    DESCRIPTION
        "This table extends the Power Supply Information
        defined in tmnxChassisPowerSupplyTable"
    ::= { tmnxSASChassisObjs 6 }

tmnxChassisPowerSupplyExtnEntry OBJECT-TYPE
    SYNTAX      TmnxChassisPowerSupplyExtnEntry
    MAX-ACCESS  not-accessible
    STATUS  current
    DESCRIPTION
        "Contains information regarding a power supply tray."
    AUGMENTS    { tmnxChassisPowerSupplyEntry }
    ::= { tmnxChassisPowerSupplyExtnTable 1 }

TmnxChassisPowerSupplyExtnEntry ::=
    SEQUENCE {
        tmnxChassisPowerSupplyAssignedDCType  INTEGER
    }

tmnxChassisPowerSupplyAssignedDCType OBJECT-TYPE
    SYNTAX         INTEGER {
                       not-applicable (0),
                       m48-dc (1),
                       p24-dc (2),
                       unknown (3)
                   }
    MAX-ACCESS     read-only
    STATUS         current
    DESCRIPTION
        " tmnxChassisPowerSupplyAssignedDCType when set to `m48-dc`, the power supply
        is -48V DC, when set to P24-dc it is +24V DC. tmnxChassisPowerSupplyAssignedDCType
        is set to m48-dc or p24-dc  if tmnxChassisPowerSupplyAssignedType is of type `dc`,
        If tmnxChassisPowerSupplyAssignedType  is not `dc` tmnxChassisPowerSupplyAssignedDCType
        will be set to not-applicable.
       "
    ::= { tmnxChassisPowerSupplyExtnEntry 1 }

tmnxChassisFanExtnTable OBJECT-TYPE
    SYNTAX      SEQUENCE OF TmnxChassisFanExtnEntry
    MAX-ACCESS  not-accessible
    STATUS      current
    DESCRIPTION
        "This table extends the system fan information"
    ::= { tmnxSASChassisObjs 7 }

tmnxChassisFanExtnEntry OBJECT-TYPE
    SYNTAX      TmnxChassisFanExtnEntry
    MAX-ACCESS  not-accessible
    STATUS  current
    DESCRIPTION
        "Contains information regarding Fan tray."
    AUGMENTS    { tmnxChassisFanEntry }
    ::= { tmnxChassisFanExtnTable 1 }

TmnxChassisFanExtnEntry ::=
    SEQUENCE {
        tmnxChassisFanCfgMode  TmnxFanCfgMode,
        tmnxChassisFanOperMode  INTEGER
    }

tmnxChassisFanCfgMode OBJECT-TYPE
    SYNTAX        TmnxFanCfgMode
    MAX-ACCESS     read-create
    STATUS         current
    DESCRIPTION
        " tmnxChassisFanCfgMode is the configuration object used to
          determine how the fan in controlled. It can be either user controlled (on|off)
          or in 'auto' mode where the operation will be based on threshold values."
    DEFVAL { auto }
    ::= { tmnxChassisFanExtnEntry 1 }

tmnxChassisFanOperMode OBJECT-TYPE
    SYNTAX        INTEGER {
                       on (1),
                       off (2)
                   }
    MAX-ACCESS     read-only
    STATUS         current
    DESCRIPTION
        " tmnxChassisFanOperMode is a read only object which will determine the
        current mode of operation."
    ::= { tmnxChassisFanExtnEntry 2 }

--


tmnxSASCardObjs     OBJECT IDENTIFIER ::= { tmnxSASChassisObjs 8 }

tmnxCardExtnTable OBJECT-TYPE
    SYNTAX  SEQUENCE OF TmnxCardExtnEntry
    MAX-ACCESS  not-accessible
    STATUS      current
    DESCRIPTION
        "The tmnxCardExtnTable has an entry for each one
        of the entry in tmnxCardTable"
    ::= { tmnxSASCardObjs 1 }

tmnxCardExtnEntry OBJECT-TYPE
    SYNTAX     TmnxCardExtnEntry
    MAX-ACCESS not-accessible
    STATUS     current
    DESCRIPTION
        "The tmnxCardExtnEntry extends tmnxCardEntry capabilities"
    AUGMENTS      { tmnxCardEntry }
    ::= { tmnxCardExtnTable 1 }

TmnxCardExtnEntry ::=
    SEQUENCE {
        tmnxCardSysResPlcyId           INTEGER
    }

tmnxCardSysResPlcyId OBJECT-TYPE
    SYNTAX      INTEGER (1..16)
    MAX-ACCESS  read-write
    STATUS      current
    DESCRIPTION
        " system resource policy id attached to this
        card"
     DEFVAL { 1 }
    ::= { tmnxCardExtnEntry 1 }

--


tmnxCpmCardExtnTable    OBJECT-TYPE
    SYNTAX  SEQUENCE OF TmnxCpmCardExtnEntry
    MAX-ACCESS  not-accessible
    STATUS      current
    DESCRIPTION
        "The tmnxCpmCardExtnTable has an entry for each CPM card or module in
         each chassis in the TMNX system."
    ::= { tmnxSASCardObjs 2 }

tmnxCpmCardExtnEntry       OBJECT-TYPE
    SYNTAX      TmnxCpmCardExtnEntry
    MAX-ACCESS  not-accessible
    STATUS      current
    DESCRIPTION
        "Each row entry represents a CPM card or module in a chassis in the
         system.  Entries cannot be created and deleted via SNMP SET
         operations.  When a tmnxChassisEntry is created, a tmnxCpmCardExtnEntry
         is created for each CPM card or module in that chassis.  Before a
         tmnxChassisEntry can be deleted, each tmnxCpmCardEntry for that
         chassis must be in the proper state for removal."
    AUGMENTS   { tmnxCpmCardEntry }
    ::= { tmnxCpmCardExtnTable 1 }

TmnxCpmCardExtnEntry ::=
    SEQUENCE {
        tmnxCpmCardBootImageSource            DisplayString
    }


tmnxCpmCardBootImageSource  OBJECT-TYPE
    SYNTAX      DisplayString
    MAX-ACCESS  read-only
    STATUS      current
    DESCRIPTION
        "tmnxCpmCardBootImageSource indicates the compact flash slot where the
         Boot image file was found when the system last rebooted.
         For example, if the BOF file was found on compact flash slot 1, the
         value of this variable will be 'cf1:'"
    ::= { tmnxCpmCardExtnEntry 1 }

--
sysLoopbackNoServPort OBJECT-TYPE
    SYNTAX      TmnxPortID
    MAX-ACCESS  read-write
    STATUS      current
    DESCRIPTION
        " Second loopback port used for internal sap creation"
    ::= { sysLoopBackInfo 1 }

sysMirrorLoopbackNoServPort OBJECT-TYPE
    SYNTAX      TmnxPortID
    MAX-ACCESS  read-write
    STATUS      current
    DESCRIPTION
        " Loopback port for mirroring"
    ::= { sysLoopBackInfo 2 }

sysTestHdNoServPort OBJECT-TYPE
    SYNTAX      TmnxPortID
    MAX-ACCESS  read-write
    STATUS      current
    DESCRIPTION
        " Loopback port for testhead"
    ::= { sysLoopBackInfo 3 }

--

sysG8032FastFloodEnable OBJECT-TYPE
    SYNTAX      TruthValue
    MAX-ACCESS  read-write
    STATUS      current
    DESCRIPTION
        " Enable disable G.8032 fast flood enable"
    DEFVAL { false }
    ::= { sysResourceProfInfo 1 }

sysResIngTcamSapIngAcl OBJECT-TYPE
    SYNTAX      TSysResource
    MAX-ACCESS  read-write
    STATUS      current
    DESCRIPTION
        " sysResIngTcamSapIngAcl sets the resource to be used
        for Sap Ingress Acl application"
    DEFVAL { -1 }
    ::= { sysResourceProfInfo 2 }

sysResIngTcamIngAclMac OBJECT-TYPE
    SYNTAX      TSysResource
    MAX-ACCESS  read-write
    STATUS      current
    DESCRIPTION
        " sysResIngTcamIngAclMac sets the resource to be used
        for mac match from the allocated sysResIngTcamSapIngAcl"
    DEFVAL { -1 }
    ::= { sysResourceProfInfo 3 }

sysResIngTcamIngAclIpv4 OBJECT-TYPE
    SYNTAX      TSysResource
    MAX-ACCESS  read-write
    STATUS      current
    DESCRIPTION
        " sysResIngTcamIngAclIpv4 sets the resource to be used
        for ipv4 match from the allocated sysResIngTcamSapIngAcl"
    DEFVAL { -1 }
    ::= { sysResourceProfInfo 4 }

sysResIngTcamIngAcl64bitIpv4Ipv6 OBJECT-TYPE
    SYNTAX      TSysResource
    MAX-ACCESS  read-write
    STATUS      current
    DESCRIPTION
        " sysResIngTcamIngAcl64bitIpv4 sets the resource to be used
        for ipv6 64 bit match from the allocated sysResIngTcamSapIngAcl"
    DEFVAL { -1 }
    ::= { sysResourceProfInfo 5 }

sysResIngTcamIngAcl128bitIpv4Ipv6 OBJECT-TYPE
    SYNTAX      TSysResource
    MAX-ACCESS  read-write
    STATUS      current
    DESCRIPTION
        " sysResIngTcamIngAcl128bitIpv4Ipv6 sets the resource to be used
        for ipv6 128 bit  match from the allocated sysResIngTcamSapIngAcl"
    DEFVAL { -1 }
    ::= { sysResourceProfInfo 6 }

sysResIngTcamIngAcl64bitIpv6Only OBJECT-TYPE
    SYNTAX      TSysResource
    MAX-ACCESS  read-write
    STATUS      current
    DESCRIPTION
        " sysResIngTcamIngAcl64bitIpv6Only sets the resource to be used
        for Ipv6 64 bit match only from the allocated sysResIngTcamSapIngAcl"
    DEFVAL { -1 }
    ::= { sysResourceProfInfo 7 }

sysResIngSapIngClass OBJECT-TYPE
    SYNTAX      TSysResource
    MAX-ACCESS  read-write
    STATUS      current
    DESCRIPTION
        " sysResIngSapIngClass sets the resource to be used
        for Sap Ingress classification"
    DEFVAL { -1 }
    ::= { sysResourceProfInfo 8 }

sysResIngSapIngClassMac OBJECT-TYPE
    SYNTAX      TSysResource
    MAX-ACCESS  read-write
    STATUS      current
    DESCRIPTION
        " sysResIngSapIngClassMac sets the resource to be used
        for mac match from the allocated sysResIngSapIngClass"
    DEFVAL { -1 }
    ::= { sysResourceProfInfo 9 }

sysResIngSapIngClassIpv4 OBJECT-TYPE
    SYNTAX      TSysResource
    MAX-ACCESS  read-write
    STATUS      current
    DESCRIPTION
        " sysResIngSapIngClassIpv4 sets the resource to be used
        for ipv4 match from the allocated sysResIngSapIngClass"
    DEFVAL { -1 }
    ::= { sysResourceProfInfo 10 }

sysResIngSapIngClassIpv4Ipv6 OBJECT-TYPE
    SYNTAX      TSysResource
    MAX-ACCESS  read-write
    STATUS      current
    DESCRIPTION
        " sysResIngSapIngClassIpv4Ipv4Ipv6 sets the resource to be used
        for ipv4, ipv6 match from the allocated sysResIngSapIngClass"
    DEFVAL { -1 }
    ::= { sysResourceProfInfo 11 }

sysResFabricPathBandwidth OBJECT-TYPE
    SYNTAX      INTEGER{
                       lb1-11-lb2-25 (1),
                       lb1-24-lb2-12 (2),
                       lb1-25-lb2-11 (3),
                       lb1-18-lb2-18 (4)
                   }
    MAX-ACCESS  read-write
    STATUS      obsolete
    DESCRIPTION
        "This object is used to configure the system fabric path bandwidth "
    DEFVAL { lb1-11-lb2-25 }
    ::= { sysResourceProfInfo 12 }

sysResMaxIPv6Routes OBJECT-TYPE
    SYNTAX      Integer32 (-1..16000)
    MAX-ACCESS  read-create
    STATUS      current
    DESCRIPTION
        "Specifies the number of routes to be reserved for use by IPv6.
         If the value is -1, then there is no limit."
    DEFVAL { -1 }
    ::= { sysResourceProfInfo 13 }


sysResIngTcamEthCfm OBJECT-TYPE
    SYNTAX      TSysResource
    MAX-ACCESS  read-write
    STATUS      current
    DESCRIPTION
        " sysResIngTcamEthCfm sets the resource to be used
        for Eth Cfm application"
    ::= { sysResourceProfInfo 14 }

sysResIngTcamEthCfmUpMep OBJECT-TYPE
    SYNTAX      TSysResource
    MAX-ACCESS  read-write
    STATUS      current
    DESCRIPTION
        " sysResIngTcamEthCfmUpMep sets the resource to be used
        for Up MEP from the allocated sysResIngTcamEthCfm"
    DEFVAL { 1 }
    ::= { sysResourceProfInfo 15 }

sysG8032FastFloodEnableOperVal OBJECT-TYPE
    SYNTAX      TruthValue
    MAX-ACCESS  read-only
    STATUS      current
    DESCRIPTION
        " Shows current active value of sysG8032FastFloodEnable "
    DEFVAL { false }
    ::= { sysResourceProfInfo 16 }

sysResEgrTcamSapEgrAcl OBJECT-TYPE
    SYNTAX      TSysResource
    MAX-ACCESS  read-write
    STATUS      current
    DESCRIPTION
        " sysResEgrTcamSapEgrAcl sets the resource to be used
        for Sap Egress Acl application"
    DEFVAL { -1 }
    ::= { sysResourceProfInfo 17 }

sysResEgrTcamEgrAclMac OBJECT-TYPE
    SYNTAX      TSysResource
    MAX-ACCESS  read-write
    STATUS      current
    DESCRIPTION
        " sysResEgrTcamEgrAclMac sets the resource to be used
        for mac match from the allocated sysResEgrTcamSapEgrAcl"
    DEFVAL { -1 }
    ::= { sysResourceProfInfo 18 }

sysResEgrTcamEgrAclIpv4 OBJECT-TYPE
    SYNTAX      TSysResource
    MAX-ACCESS  read-write
    STATUS      current
    DESCRIPTION
        " sysResEgrTcamEgrAclIpv4 sets the resource to be used
        for ipv4 match from the allocated sysResEgrTcamSapEgrAcl"
    DEFVAL { -1 }
    ::= { sysResourceProfInfo 19 }

sysResEgrTcamEgrAcl64bitIpv4Ipv6 OBJECT-TYPE
    SYNTAX      TSysResource
    MAX-ACCESS  read-write
    STATUS      current
    DESCRIPTION
        " sysResEgrTcamEgrAcl64bitIpv4 sets the resource to be used
        for ipv6 64 bit match from the allocated sysResEgrTcamSapEgrAcl"
    DEFVAL { -1 }
    ::= { sysResourceProfInfo 20 }

sysResEgrTcamEgrAcl128bitIpv4Ipv6 OBJECT-TYPE
    SYNTAX      TSysResource
    MAX-ACCESS  read-write
    STATUS      current
    DESCRIPTION
        " sysResEgrTcamEgrAcl128bitIpv4Ipv6 sets the resource to be used
        for ipv6 128 bit  match from the allocated sysResEgrTcamSapEgrAcl"
    DEFVAL { -1 }
    ::= { sysResourceProfInfo 21 }

sysResEgrTcamEgrAcl64bitIpv6Only OBJECT-TYPE
    SYNTAX      TSysResource
    MAX-ACCESS  read-write
    STATUS      current
    DESCRIPTION
        " sysResEgrTcamEgrAcl64bitIpv6Only sets the resource to be used
        for Ipv6 64 bit match only from the allocated sysResEgrTcamSapEgrAcl"
    DEFVAL { -1 }
    ::= { sysResourceProfInfo 22 }

sysResEgrSapEgrClass OBJECT-TYPE
    SYNTAX      TSysResource
    MAX-ACCESS  read-write
    STATUS      current
    DESCRIPTION
        " sysResEgrSapEgrClass sets the resource to be used
        for Sap Egress classification"
    DEFVAL { -1 }
    ::= { sysResourceProfInfo 23}

sysResEgrSapEgrClassMac OBJECT-TYPE
    SYNTAX      TSysResource
    MAX-ACCESS  read-write
    STATUS      current
    DESCRIPTION
        " sysResEgrSapEgrClassMac sets the resource to be used
        for mac match from the allocated sysResEgrSapEgrClass"
    DEFVAL { -1 }
    ::= { sysResourceProfInfo 24 }

sysResEgrSapEgrClassIpv4 OBJECT-TYPE
    SYNTAX      TSysResource
    MAX-ACCESS  read-write
    STATUS      current
    DESCRIPTION
        " sysResEgrSapEgrClassIpv4 sets the resource to be used
        for ipv4 match from the allocated sysResEgrSapEgrClass"
    DEFVAL { -1 }
    ::= { sysResourceProfInfo 25 }

sysResEgrSapEgrClassIpv4Ipv6 OBJECT-TYPE
    SYNTAX      TSysResource
    MAX-ACCESS  read-write
    STATUS      current
    DESCRIPTION
        " sysResEgrSapEgrClassIpv4Ipv4Ipv6 sets the resource to be used
        for ipv4, ipv6 match from the allocated sysResEgrSapEgrClass"
    DEFVAL { -1 }
    ::= { sysResourceProfInfo 26 }

sysResIngTcamSapAggMeter OBJECT-TYPE
    SYNTAX      TSysResource
    MAX-ACCESS  read-write
    STATUS      current
    DESCRIPTION
        " sysResIngTcamSapAggMeter sets the resource to be used
        for sap-aggregate-meters"
    DEFVAL { -1 }
    ::= { sysResourceProfInfo 27 }

sysResIngTcamSapAggMeterOperVal OBJECT-TYPE
    SYNTAX      TSysResource
    MAX-ACCESS  read-only
    STATUS      current
    DESCRIPTION
        " This object shows the operational value of
        sysResIngTcamSapAggMeter"
    DEFVAL { -1 }
    ::= { sysResourceProfInfo 28 }

sysResQosSapIngQMode OBJECT-TYPE
    SYNTAX      TruthValue
    MAX-ACCESS  read-write
    STATUS      current
    DESCRIPTION
        " This object allows the user to switch between
        the current mode and 22Gig mode."
    DEFVAL { false }
    ::= { sysResourceProfInfo 29 }

sysResQosSapIngQOperMode OBJECT-TYPE
    SYNTAX      TruthValue
    MAX-ACCESS  read-only
    STATUS      current
    DESCRIPTION
        " This object returns the current operational value
        of sysResQosSapIngQMode"
    DEFVAL { false }
    ::= { sysResourceProfInfo 30 }

sysResRouterEcmpMaxRoutesDst OBJECT-TYPE
    SYNTAX      Integer32 (1..16)
    MAX-ACCESS  read-create
    STATUS      current
    DESCRIPTION
        "Specifies the number of routes to be reserved for use by ECMP."
    DEFVAL { 1 }
    ::= { sysResourceProfInfo 31 }

sysDhcpSnoopingSdpEnable OBJECT-TYPE
    SYNTAX      TruthValue
    MAX-ACCESS  read-write
    STATUS      current
    DESCRIPTION
        " Enable/disable dhcp snooping on SDPs"
    DEFVAL { false }
    ::= { sysResourceProfInfo 32 }

sysDhcpSnoopingEnable OBJECT-TYPE
    SYNTAX      TruthValue
    MAX-ACCESS  read-write
    STATUS      current
    DESCRIPTION
        " Enable/disable dhcp snooping on the system. Currently for STU only."
    DEFVAL { false }
    ::= { sysResourceProfInfo 33 }

sysResRouterEcmpMaxRoutesDstOperVal OBJECT-TYPE
    SYNTAX      Integer32 (1..16)
    MAX-ACCESS  read-only
    STATUS      obsolete
    DESCRIPTION
        "Specifies the operational value of number of routes to be reserved for use by ECMP."
    DEFVAL { 1 }
    ::= { sysResourceProfInfo 34 }

sysResIpMacMatchEnable OBJECT-TYPE
    SYNTAX          INTEGER (-1 | 0..10)
    MAX-ACCESS      read-create
    STATUS          current
    DESCRIPTION     "Resource allocation for ip mac match enable"
    DEFVAL { -1 }
    ::= { sysResourceProfInfo 35 }

sysG8032FastFlood OBJECT-TYPE
    SYNTAX      INTEGER (0..8)
    MAX-ACCESS  read-write
    STATUS      current
    DESCRIPTION
        "sysG8032FastFlood sets max-slices of 1 to 5"
    DEFVAL { 5 }
    ::= { sysResourceProfInfo 40 }

sysResIngTcamEthCfmDownMep OBJECT-TYPE
    SYNTAX      TSysResource
    MAX-ACCESS  read-write
    STATUS      current
    DESCRIPTION
        " sysResIngTcamEthCfmDownMep sets the resource to be used
        for Down MEP from the allocated sysResIngTcamEthCfm"
    DEFVAL { 1 }
    ::= { sysResourceProfInfo 51 }

sysResQosMbsPool OBJECT-TYPE
    SYNTAX      INTEGER
                {
                    node (1),
                    port (2)
                }
    MAX-ACCESS  read-write
    STATUS      current
    DESCRIPTION
        "This object allows the user to set buffer allocation at node or
        port level.

        'node' means no change in the buffer allocation and
        works without any decommission ports.

        'port' means buffers will be divided and shared across ports. In absence of
        decommission, buffers will be equally divided. If decommission
        entries are present, the division will happen as per decommission logic.
        Refer to tResDecommTable"
    DEFVAL { node }
    ::= { sysResourceProfInfo 53 }

sysResIngTcamEthCfmUpMepPrimaryVlan OBJECT-TYPE
    SYNTAX      INTEGER (0..8)
    MAX-ACCESS  read-write
    STATUS      current
    DESCRIPTION
        "sysResIngTcamEthCfmUpMepPrimaryVlan sets max-slices of 0 to 8"
    DEFVAL { 0 }
    ::= { sysResourceProfInfo 54 }

sysResIngTcamEthCfmDownMepPrimaryVlan OBJECT-TYPE
    SYNTAX      INTEGER (0..8)
    MAX-ACCESS  read-write
    STATUS      current
    DESCRIPTION
        "sysResIngTcamEthCfmDownMepPrimaryVlan sets max-slices of 0 to 8"
    DEFVAL { 0 }
    ::= { sysResourceProfInfo 55 }

sysResRouterMaxIPSubnets OBJECT-TYPE
    SYNTAX      Integer32 (1..32000)
    MAX-ACCESS  read-create
    STATUS      current
    DESCRIPTION
        "Specifies the number of subnets to be reserved for IP."
    DEFVAL { 2000 }
    ::= { sysResourceProfInfo 56 }


sysQosPortSchedModeEnable OBJECT-TYPE
    SYNTAX      TruthValue
    MAX-ACCESS  read-write
    STATUS      current
    DESCRIPTION
        " Enable disable qos port scheduler mode"
    DEFVAL { false }
    ::= { sysResourceProfInfo 57 }

sysResMaxIPv6RoutesOperVal OBJECT-TYPE
    SYNTAX      Integer32 (-1..16000)
    MAX-ACCESS  read-only
    STATUS      current
    DESCRIPTION
        "Specifies the number of routes to be reserved for use by IPv6.
         If the value is -1, then there is no limit."
    DEFVAL { -1 }
    ::= { sysResourceProfInfo 58 }


tResPlcyTable OBJECT-TYPE
    SYNTAX  SEQUENCE OF TResPlcyEntry
    MAX-ACCESS  not-accessible
    STATUS      current
    DESCRIPTION
        "The tResPlcyTable has an entry for each user configured system
        resource policy."
    ::= { sysResProfPlcyObjs 1 }

tResPlcyEntry   OBJECT-TYPE
    SYNTAX      TResPlcyEntry
    MAX-ACCESS  not-accessible
    STATUS      current
    DESCRIPTION
        "An entry in this table would be created for every resource policy
        creation"
    INDEX    { tResPlcyId }
    ::= { tResPlcyTable 1 }

TResPlcyEntry ::=
    SEQUENCE {
        tResPlcyId                           INTEGER,
        tResPlcyRowStatus                    RowStatus,
        tResPlcyIngTcamSapAggMeter           INTEGER,
        tResPlcyIngTcamQosSapIng             INTEGER,
        tResPlcyIngTcamQosSapIngIpv4         INTEGER,
        tResPlcyIngTcamQosSapIngIpv4Ipv6     INTEGER,
        tResPlcyIngTcamQosSapIngMac          INTEGER,
        tResPlcyIngTcamAclSapIng             INTEGER,
        tResPlcyIngTcamAclSapIngIpv4         INTEGER,
        tResPlcyIngTcamAclSapIng64Ipv6       INTEGER,
        tResPlcyIngTcamAclSapIng128Ipv4Ipv6  INTEGER,
        tResPlcyIngTcamAclSapIngMac          INTEGER,
        tResPlcyEgrTcamAclSapEgr             INTEGER,
        tResPlcyEgrTcamAclSapEgrMacIpv4      INTEGER,
        tResPlcyEgrTcamAclSapEgr128Ipv6      INTEGER,
        tResPlcyEgrTcamAclSapEgr64MacIpv6    INTEGER,
        tResPlcyEgrTcamAclSapEgrMac          INTEGER,
        tResPlcyDescription                  TItemDescription,
        tResPlcyLastChanged                  TimeStamp,
        tResPlcyIngTcamEthCfm                INTEGER,
        tResPlcyIngTcamEthCfmUpMep           INTEGER,
        tResPlcyG8032CtrlSapStartVlan        Unsigned32,
        tResPlcyG8032CtrlSapEndVlan          Unsigned32,
        tResPlcyResIpMacMatchEnable          INTEGER,
        tResPlcyIngTcamEthCfmDownMep         INTEGER,
        tResPlcyIngTcamEthCfmUpMepEnable     TruthValue,
        tResPlcyIngTcamEthCfmDownMepEnable   TruthValue

    }


tResPlcyId OBJECT-TYPE
    SYNTAX      INTEGER (1..16)
    MAX-ACCESS  not-accessible
    STATUS      current
    DESCRIPTION
        " system resource policy id"
    ::= { tResPlcyEntry 1 }

tResPlcyRowStatus OBJECT-TYPE
    SYNTAX      RowStatus
    MAX-ACCESS  read-create
    STATUS      current
    DESCRIPTION
        " RowStatus of this policy entry"
    ::= { tResPlcyEntry 2 }

tResPlcyIngTcamSapAggMeter OBJECT-TYPE
    SYNTAX      INTEGER (0..2)
    MAX-ACCESS  read-create
    STATUS      current
    DESCRIPTION
        " Ingress tcam sap aggregate meter resource"
    DEFVAL { 0 }
    ::= { tResPlcyEntry 3 }


tResPlcyIngTcamQosSapIng OBJECT-TYPE
    SYNTAX      INTEGER (0..5)
    MAX-ACCESS  read-create
    STATUS      current
    DESCRIPTION
        " Ingress tcam sap sap ingress resource"
    DEFVAL { 0 }
    ::= { tResPlcyEntry 4 }

tResPlcyIngTcamQosSapIngIpv4 OBJECT-TYPE
    SYNTAX      INTEGER (-1..5)
    MAX-ACCESS  read-create
    STATUS      current
    DESCRIPTION
        " Ingress tcam sap ingress ipv4 resource"
    DEFVAL { 0 }
    ::= { tResPlcyEntry 5 }

tResPlcyIngTcamQosSapIngIpv4Ipv6 OBJECT-TYPE
    SYNTAX      INTEGER (-1..5)
    MAX-ACCESS  read-create
    STATUS      current
    DESCRIPTION
        " Ingress tcam sap ingress ipv4, ipv6 resource"
    DEFVAL { 0 }
    ::= { tResPlcyEntry 6 }

tResPlcyIngTcamQosSapIngMac OBJECT-TYPE
    SYNTAX      INTEGER (-1..5)
    MAX-ACCESS  read-create
    STATUS      current
    DESCRIPTION
        " Ingress tcam sap ingress mac resource"
    DEFVAL { 0 }
    ::= { tResPlcyEntry 7 }

tResPlcyIngTcamAclSapIng OBJECT-TYPE
    SYNTAX      INTEGER (0..5)
    MAX-ACCESS  read-create
    STATUS      current
    DESCRIPTION
        " Ingress tcam acl sap ingress resource"
    DEFVAL { 0 }
    ::= { tResPlcyEntry 8 }

tResPlcyIngTcamAclSapIngIpv4 OBJECT-TYPE
    SYNTAX      INTEGER (-1..5)
    MAX-ACCESS  read-create
    STATUS      current
    DESCRIPTION
        " Ingress tcam acl sap ingress ipv4 resource"
    DEFVAL { 0 }
    ::= { tResPlcyEntry 9 }

tResPlcyIngTcamAclSapIng64Ipv6 OBJECT-TYPE
    SYNTAX      INTEGER (-1..5)
    MAX-ACCESS  read-create
    STATUS      current
    DESCRIPTION
        " Ingress tcam acl sap ingress 64 bit ipv6
        match resource"
    DEFVAL { 0 }
    ::= { tResPlcyEntry 10 }

tResPlcyIngTcamAclSapIng128Ipv4Ipv6 OBJECT-TYPE
    SYNTAX      INTEGER (-1..5)
    MAX-ACCESS  read-create
    STATUS      current
    DESCRIPTION
        " Ingress tcam acl sap ingress 128 bit ipv6
        resource"
    DEFVAL { 0 }
    ::= { tResPlcyEntry 11 }

tResPlcyIngTcamAclSapIngMac OBJECT-TYPE
    SYNTAX      INTEGER (-1..5)
    MAX-ACCESS  read-create
    STATUS      current
    DESCRIPTION
        " Ingress tcam acl sap ingress mac resource"
    DEFVAL { 0 }
    ::= { tResPlcyEntry 12 }

tResPlcyEgrTcamAclSapEgr OBJECT-TYPE
    SYNTAX      INTEGER (0 | 2)
    MAX-ACCESS  read-create
    STATUS      current
    DESCRIPTION
        " Egress tcam acl sap sap egress 1resource"
    DEFVAL { 0 }
    ::= { tResPlcyEntry 13 }

tResPlcyEgrTcamAclSapEgrMacIpv4 OBJECT-TYPE
    SYNTAX      INTEGER (0 | 2)
    MAX-ACCESS  read-create
    STATUS      current
    DESCRIPTION
        " Egress tcam acl sap egress mac ipv4 resource"
    DEFVAL { 0 }
    ::= { tResPlcyEntry 14 }

tResPlcyEgrTcamAclSapEgr128Ipv6 OBJECT-TYPE
    SYNTAX      INTEGER (0 | 2)
    MAX-ACCESS  read-create
    STATUS      current
    DESCRIPTION
        "Egress tcam acl sap egress 128bit ipv6 resource"
    DEFVAL { 0 }
    ::= { tResPlcyEntry 15 }

tResPlcyEgrTcamAclSapEgr64MacIpv6 OBJECT-TYPE
    SYNTAX      INTEGER (0 | 2)
    MAX-ACCESS  read-create
    STATUS      current
    DESCRIPTION
        "Egress tcam acl sap egress mac resource"
    DEFVAL { 0 }
    ::= { tResPlcyEntry 16 }

tResPlcyEgrTcamAclSapEgrMac OBJECT-TYPE
    SYNTAX      INTEGER (0 | 2)
    MAX-ACCESS  read-create
    STATUS      current
    DESCRIPTION
        "Egress tcam acl sap egress mac resource"
    DEFVAL { 0 }
    ::= { tResPlcyEntry 17 }

tResPlcyDescription OBJECT-TYPE
    SYNTAX       TItemDescription
    MAX-ACCESS   read-create
    STATUS       current
    DESCRIPTION
        "user-provided description of the policy."
    DEFVAL { ''H }
    ::= { tResPlcyEntry 18 }

tResPlcyLastChanged OBJECT-TYPE
    SYNTAX       TimeStamp
    MAX-ACCESS   read-only
    STATUS       current
    DESCRIPTION
        "timestamp of last change to this row."
    ::= { tResPlcyEntry 19 }

tResPlcyIngTcamEthCfm OBJECT-TYPE
    SYNTAX      INTEGER (1..3)
    MAX-ACCESS  read-create
    STATUS      current
    DESCRIPTION
        " Ingress tcam eth cfm resource"
    DEFVAL { 1 }
    ::= { tResPlcyEntry 20 }

tResPlcyIngTcamEthCfmUpMep OBJECT-TYPE
    SYNTAX      INTEGER (0..7)
    MAX-ACCESS  read-create
    STATUS      current
    DESCRIPTION
        " Ingress tcam eth cfm up-mep resource"
    DEFVAL { 0 }
    ::= { tResPlcyEntry 21 }

tResPlcyG8032CtrlSapStartVlan OBJECT-TYPE
    SYNTAX          Unsigned32(0 | 3000 .. 3512)
    MAX-ACCESS      read-create
    STATUS          current
    DESCRIPTION     "G8032 control sap tag start vlan"
    DEFVAL { 0 }
    ::= { tResPlcyEntry 22 }


tResPlcyG8032CtrlSapEndVlan OBJECT-TYPE
    SYNTAX          Unsigned32(0 | 3000 .. 3512)
    MAX-ACCESS      read-create
    STATUS          current
    DESCRIPTION     "G8032 control sap tag End vlan"
    DEFVAL { 0 }
    ::= { tResPlcyEntry 23 }

tResPlcyResIpMacMatchEnable OBJECT-TYPE
    SYNTAX          INTEGER (-1 | 0..10)
    MAX-ACCESS      read-create
    STATUS          current
    DESCRIPTION     "Resource allocation for ip mac match enable"
    DEFVAL { -1 }
    ::= { tResPlcyEntry 24 }

tResPlcyIngTcamEthCfmDownMep OBJECT-TYPE
    SYNTAX      INTEGER (1..3)
    MAX-ACCESS  read-create
    STATUS      current
    DESCRIPTION
        " Ingress tcam eth cfm down-mep resource"
    DEFVAL { 1 }
    ::= { tResPlcyEntry 25 }


tResPlcyIngTcamEthCfmUpMepEnable OBJECT-TYPE
    SYNTAX      TruthValue
    MAX-ACCESS  read-write
    STATUS      current
    DESCRIPTION
        "Enable/Disable Up Mep"
    DEFVAL { false }
    ::= { tResPlcyEntry 27 }

tResPlcyIngTcamEthCfmDownMepEnable OBJECT-TYPE
    SYNTAX      TruthValue
    MAX-ACCESS  read-write
    STATUS      current
    DESCRIPTION
        "Enable/Disable Down Mep"
    DEFVAL { false }
    ::= { tResPlcyEntry 28 }

--

tResDecommTable OBJECT-TYPE
    SYNTAX  SEQUENCE OF TResDecommEntry
    MAX-ACCESS  not-accessible
    STATUS      current
    DESCRIPTION
        "The tResDecommTable has an entry for each user configured system
        decommissioned resource port."
    ::= { sysResProfDecommObjs 1 }

tResDecommEntry   OBJECT-TYPE
    SYNTAX      TResDecommEntry
    MAX-ACCESS  not-accessible
    STATUS      current
    DESCRIPTION
        "An entry in this table would be created for every decommissioned
        entry created
        "
    INDEX    { tResDecommId }
    ::= { tResDecommTable 1 }

TResDecommEntry ::=
    SEQUENCE {
        tResDecommId                      INTEGER,
        tResDecommRowStatus               RowStatus,
        tResDecommFromPortMap             Unsigned32,
        tResDecommToPortMap               Unsigned32
     }

tResDecommId OBJECT-TYPE
    SYNTAX      INTEGER (1..30)
    MAX-ACCESS  not-accessible
    STATUS      current
    DESCRIPTION
        " system resource decommision id"
    ::= { tResDecommEntry 1 }

tResDecommRowStatus OBJECT-TYPE
    SYNTAX      RowStatus
    MAX-ACCESS  read-create
    STATUS      current
    DESCRIPTION
        " RowStatus of this policy entry"
    ::= { tResDecommEntry 2 }

tResDecommFromPortMap OBJECT-TYPE
    SYNTAX      Unsigned32
    MAX-ACCESS  read-create
    STATUS      current
    DESCRIPTION
        " tResDecommFromPortMap is the bit map of ports that are
        decommissioned"
    ::= { tResDecommEntry 3 }

tResDecommToPortMap OBJECT-TYPE
    SYNTAX      Unsigned32
    MAX-ACCESS  read-create
    STATUS      current
    DESCRIPTION
        " tResDecommToPortMap is the bit map of ports that are
        are allocated the resources freed up by the ports in
        tResDecommFromPortMap"
    ::= { tResDecommEntry 4 }

--

tResDecommOperTable OBJECT-TYPE
    SYNTAX  SEQUENCE OF TResDecommOperEntry
    MAX-ACCESS  not-accessible
    STATUS      current
    DESCRIPTION
        "The tResDecommOperTable has an entry for each user configured system
        decommissioned resource port. This table is updated only at boot time,
        the entries in this table will match the entries available in
        tResDecommTable until administrative decommission entries are modified
        by the user"
    ::= { sysResProfDecommObjs 2 }

tResDecommOperEntry   OBJECT-TYPE
    SYNTAX      TResDecommOperEntry
    MAX-ACCESS  not-accessible
    STATUS      current
    DESCRIPTION
        "An entry in this table would be created for every decommissioned
        entry created
        "
    INDEX    { tResDecommOperId }
    ::= { tResDecommOperTable 1 }

TResDecommOperEntry ::=
    SEQUENCE {
        tResDecommOperId                      INTEGER,
        tResDecommOperFromPortMap             Unsigned32,
        tResDecommOperToPortMap               Unsigned32
     }

tResDecommOperId OBJECT-TYPE
    SYNTAX      INTEGER (1..30)
    MAX-ACCESS  not-accessible
    STATUS      current
    DESCRIPTION
        " system resource decommision id"
    ::= { tResDecommOperEntry 1 }

tResDecommOperFromPortMap OBJECT-TYPE
    SYNTAX      Unsigned32
    MAX-ACCESS  read-only
    STATUS      current
    DESCRIPTION
        " tResDecommOperFromPortMap is the bit map of ports that are
        decommissioned"
    ::= { tResDecommOperEntry 2 }

tResDecommOperToPortMap OBJECT-TYPE
    SYNTAX      Unsigned32
    MAX-ACCESS  read-only
    STATUS      current
    DESCRIPTION
        " tResDecommOperToPortMap is the bit map of ports that are
        are allocated the resources freed up by the ports in
        tResDecommFromPortMap"
    ::= { tResDecommOperEntry 3 }

--

sysQosWredSlopes OBJECT-TYPE
    SYNTAX      INTEGER {
                       high-low (1),
                       tcp-non-tcp (2)
                   }
    MAX-ACCESS  read-write
    STATUS      current
    DESCRIPTION
        "When tcp-non-tcp is set, 3 WRED slopes are used
         per queue. When high-low is set, 2 slopes are
         used per queue for both tcp and non-tcp traffic "
    DEFVAL { tcp-non-tcp }
    ::= { sysQosObjs 1 }


-- Added by Mohan Pulliah
--
-- Operational-Group
--
sysOperGrpTblLastChanged  OBJECT-TYPE
    SYNTAX          TimeStamp
    MAX-ACCESS      read-only
    STATUS          current
    DESCRIPTION
        "The value of sysOperGrpTblLastChanged indicates the sysUpTime
         at the time of the last modification of sysOperGrpTable.

         If no changes were made to the entry since the last re-initialization
         of the local network management subsystem, then this object contains a
         zero value."
    ::= { sysOperGrpObjs 1 }

sysOperGrpTable OBJECT-TYPE
    SYNTAX          SEQUENCE OF SysOperGrpEntry
    MAX-ACCESS      not-accessible
    STATUS          current
    DESCRIPTION     "A table that contains Operational-Group information."
    ::= { sysOperGrpObjs 2 }

sysOperGrpEntry OBJECT-TYPE
    SYNTAX          SysOperGrpEntry
    MAX-ACCESS      not-accessible
    STATUS          current
    DESCRIPTION     "Each row specifies information about a specific
                     Operational-Group."
    INDEX           { sysOperGrpName }
    ::= { sysOperGrpTable 1 }

SysOperGrpEntry ::=
    SEQUENCE {
        sysOperGrpName               TNamedItem,
        sysOperGrpRowStatus          RowStatus,
        sysOperGrpLastChange         TimeStamp,
        sysOperGrpOperStatus         ServiceOperStatus,
        sysOperGrpHoldDownTime       TmnxOperGrpHoldDownTime,
        sysOperGrpCreationOrigin     TmnxSysOperGrpCreationOrigin,
        sysOperGrpHoldUpTime         TmnxOperGrpHoldUpTime,
        sysOperGrpHoldUpTimeRemain   TmnxOperGrpHoldUpTime,
        sysOperGrpHoldDownTimeRemain TmnxOperGrpHoldDownTime,
        sysOperGrpNumMembers         Gauge32,
        sysOperGrpNumMonitoring      Gauge32
    }

sysOperGrpName OBJECT-TYPE
    SYNTAX          TNamedItem
    MAX-ACCESS      not-accessible
    STATUS          current
    DESCRIPTION
        "The value of the object sysOperGrpName specifies the
         Operational-Group identifier."
    ::= { sysOperGrpEntry 1 }

sysOperGrpRowStatus OBJECT-TYPE
    SYNTAX          RowStatus
    MAX-ACCESS      read-create
    STATUS          current
    DESCRIPTION
        "This value of the object sysOperGrpRowStatus specifies the
         status of this row."
    ::= { sysOperGrpEntry 2 }

sysOperGrpLastChange OBJECT-TYPE
    SYNTAX       TimeStamp
    MAX-ACCESS   read-only
    STATUS       current
    DESCRIPTION
        "The value of sysOperGrpLastChange indicates the timestamp of last
        change to this row in sysOperGrpTable."
    ::= { sysOperGrpEntry 3 }

sysOperGrpOperStatus OBJECT-TYPE
    SYNTAX          ServiceOperStatus
    MAX-ACCESS      read-only
    STATUS          current
    DESCRIPTION
        "The value of sysOperGrpOperStatus indicates the operational
        state of this group."
    ::= { sysOperGrpEntry 4 }

sysOperGrpHoldDownTime OBJECT-TYPE
    SYNTAX          TmnxOperGrpHoldDownTime
    UNITS           "seconds"
    MAX-ACCESS      read-create
    STATUS          current
    DESCRIPTION
        "The value of sysOperGrpHoldDownTime specifies number of seconds to
        wait before notifying clients monitoring this group when its
        operational status transitions from up to down."
    DEFVAL { 0 }
    ::= { sysOperGrpEntry 5 }

sysOperGrpCreationOrigin   OBJECT-TYPE
    SYNTAX          TmnxSysOperGrpCreationOrigin
    MAX-ACCESS      read-only
    STATUS          current
    DESCRIPTION
        "The value of sysOperGrpCreationOrigin indicates the protocol or
         mechanism which created this group."
    ::= { sysOperGrpEntry 6 }

sysOperGrpHoldUpTime OBJECT-TYPE
    SYNTAX          TmnxOperGrpHoldUpTime
    UNITS           "seconds"
    MAX-ACCESS      read-create
    STATUS          current
    DESCRIPTION
        "The value of sysOperGrpHoldUpTime specifies number of seconds to
        wait before notifying clients monitoring this group when its
        operational status transitions from down to up."
    DEFVAL { 4 }
    ::= { sysOperGrpEntry 7 }

sysOperGrpHoldUpTimeRemain OBJECT-TYPE
    SYNTAX         TmnxOperGrpHoldUpTime
    UNITS          "seconds"
    MAX-ACCESS     read-only
    STATUS         current
    DESCRIPTION
        "The value of sysOperGrpHoldUpTimeRemain indicates the number of
        seconds remaining in the sysOperGrpHoldUpTime."
    ::= { sysOperGrpEntry 8 }

sysOperGrpHoldDownTimeRemain OBJECT-TYPE
    SYNTAX         TmnxOperGrpHoldDownTime
    UNITS          "seconds"
    MAX-ACCESS     read-only
    STATUS         current
    DESCRIPTION
        "The value of sysOperGrpHoldDownTimeRemain indicates the number of
        seconds remaining in the sysOperGrpHoldDownTime."
    ::= { sysOperGrpEntry 9 }

sysOperGrpNumMembers OBJECT-TYPE
    SYNTAX         Gauge32
    MAX-ACCESS     read-only
    STATUS         current
    DESCRIPTION
        "The value of sysOperGrpNumMembers indicates the number of
        members as part of this operational-group."
    ::= { sysOperGrpEntry 10 }

sysOperGrpNumMonitoring OBJECT-TYPE
    SYNTAX         Gauge32
    MAX-ACCESS     read-only
    STATUS         current
    DESCRIPTION
        "The value of sysOperGrpNumMonitoring indicates the number of
        objects monitoring this operational-group."
    ::= { sysOperGrpEntry 11 }

--
--  Environmental Alarms
--
 tmnxEnvTempTooLow NOTIFICATION-TYPE
    OBJECTS {
        tmnxChassisNotifyHwIndex,
        tmnxHwID,
        tmnxHwClass,
        tmnxHwTemperature,
        tmnxHwLowTempThreshold
    }
    STATUS  current
    DESCRIPTION
        "Generated when the temperature sensor reading on an equipment
         object is lesser than its configured threshold."
    ::= { tmnxSASChassisNotification 1 }

tmnxEqMDACfgMissing  NOTIFICATION-TYPE
    OBJECTS {
        tmnxChassisNotifyHwIndex,
        tmnxHwID,
        tmnxHwClass,
        tmnxHwOperState,
        tmnxChassisNotifyMDACfgFailReason
    }
    STATUS  current
    DESCRIPTION
        "Generated when a supported MDA is inserted into a slot, but the current
         configuration is not sufficient for the MDA to operate."
    ::= { tmnxSASChassisNotification 5 }

tmnxVwmShelfInserted NOTIFICATION-TYPE
    OBJECTS {
        tmnxVwmShelfId
    }
    STATUS  current
    DESCRIPTION
        "Generated when the vwm-shelf is inserted"
    ::= { tmnxSASChassisNotification 6 }

tmnxVwmShelfIdMismatch NOTIFICATION-TYPE
    OBJECTS {
        tmnxVwmShelfId
    }
    STATUS  current
    DESCRIPTION
        "tmnxVwmShelfIdMismatch is when the vwm-shelf configured by
        the user does not match the rotary switch setting"
    ::= { tmnxSASChassisNotification 7 }

tmnxVwmShelfRemoved NOTIFICATION-TYPE
    OBJECTS {
        tmnxVwmShelfId
    }
    STATUS  current
    DESCRIPTION
        "Generated when the vwm-shelf is removed"
    ::= { tmnxSASChassisNotification 8 }


tmnxUsbUnknownDev NOTIFICATION-TYPE
    STATUS  current
    DESCRIPTION
        "Generated when unsupported USB device is
        inserted into a 7210 device"
    ::= { tmnxSASChassisNotification 9 }

 tmnxVwmShelfCardInserted   NOTIFICATION-TYPE
    OBJECTS {
        tmnxChassisNotifyHwIndex,
        tmnxHwID,
        tmnxHwClass,
        tmnxVwmShelfCardId
    }
    STATUS  current
    DESCRIPTION
        "Generated when a VWM shelf line card is inserted."
    ::= { tmnxSASChassisNotification 11 }

tmnxVwmShelfCardRemoved   NOTIFICATION-TYPE
    OBJECTS {
        tmnxChassisNotifyHwIndex,
        tmnxHwID,
        tmnxHwClass,
        tmnxVwmShelfCardId
    }
    STATUS  current
    DESCRIPTION
        "Generated when a VWM shelf line card is removed."
    ::= { tmnxSASChassisNotification 12 }

tmnxVwmShelfCardIdMismatch   NOTIFICATION-TYPE
    OBJECTS {
        tmnxChassisNotifyHwIndex,
        tmnxHwID,
        tmnxHwClass,
        tmnxVwmShelfCardId
    }
    STATUS  current
    DESCRIPTION
        "Generated when there is a VWM shelf line card mismatch
        with configured id."
    ::= { tmnxSASChassisNotification 13 }

tmnxVwmShelfPSInputFailure   NOTIFICATION-TYPE
    OBJECTS {
        tmnxChassisNotifyHwIndex,
        tmnxHwID,
        tmnxHwClass,
        tmnxVwmShelfCardId
    }
    STATUS  current
    DESCRIPTION
        "Generated when there is a input power supply failure
        on VWM shelf"
    ::= { tmnxSASChassisNotification 14 }

tmnxVwmShelfPSOutputFailure   NOTIFICATION-TYPE
    OBJECTS {
        tmnxChassisNotifyHwIndex,
        tmnxHwID,
        tmnxHwClass,
        tmnxVwmShelfCardId
    }
    STATUS  current
    DESCRIPTION
        "Generated when there is a output power supply failure
        on VWM shelf"
    ::= { tmnxSASChassisNotification 15 }

tmnxVwmShelfInputLoss   NOTIFICATION-TYPE
    OBJECTS {
        tmnxChassisNotifyHwIndex,
        tmnxHwID,
        tmnxHwClass,
        tmnxVwmShelfCardId
    }
    STATUS  current
    DESCRIPTION
        "Generated when there is a loss
        on VWM shelf input"
    ::= { tmnxSASChassisNotification 16 }

tmnxVwmShelfOutputLoss   NOTIFICATION-TYPE
    OBJECTS {
        tmnxChassisNotifyHwIndex,
        tmnxHwID,
        tmnxHwClass,
        tmnxVwmShelfCardId
    }
    STATUS  current
    DESCRIPTION
        "Generated when there is a loss
        on VWM shelf output"
    ::= { tmnxSASChassisNotification 17 }

tmnxVwmShelfCardCfgError   NOTIFICATION-TYPE
    OBJECTS {
        tmnxChassisNotifyHwIndex,
        tmnxHwID,
        tmnxHwClass,
        tmnxVwmShelfCardId
    }
    STATUS  current
    DESCRIPTION
        "Generated when the vwm shelf inserted does not
        match with configured shelf id, card"
    ::= { tmnxSASChassisNotification 18 }

tmnxAlarmInputVoltageFailure NOTIFICATION-TYPE
    OBJECTS {
        tmnxChassisNotifyHwIndex,
        tmnxHwID,
        tmnxHwClass
    }
    STATUS  current
    DESCRIPTION
        "Generated when the internal alam input voltage
          fails"
    ::= { tmnxSASChassisNotification 10 }


tmnxRootDirFull NOTIFICATION-TYPE
    OBJECTS {
        tmnxChassisNotifyHwIndex,
        tmnxHwClass,
        tmnxHwName
    }
    STATUS  current
    DESCRIPTION
        "Generated when the dosfs root directory is full,
         number of files in root directory has reached the
         threshold limit."
    ::= { tmnxSASChassisNotification 2 }
--
--  Multipoint Management
--

tSASMpointBwPlcy  OBJECT-TYPE
    SYNTAX      TNamedItem
    MAX-ACCESS  read-write
    STATUS      current
    DESCRIPTION
        "The value of multipoint bandwidth management policy."
    DEFVAL { ''H }
    ::= { sysMpointMgmtInfo 1 }

--
-- PTP
--

tmnxPtpTimeUsePtp OBJECT-TYPE
   SYNTAX  TmnxPtpTime
    MAX-ACCESS  read-write
    STATUS      current
    DESCRIPTION
       "If this object is configured with 'system', ptp derived time (in UTC timescale)
        is used for all the system applications that need time, including the timestamps
        needed for OAM tools.
        If configured with 'oam', the system will use the PTP derived time (in UTC timescale)
        for only the timestamps needed by OAM. By default NTP derived time is used for all
        system applications. If NTP is not configured, then the system RTC is used for obtaining
        timestmaps in UTC timescale for all system applications"
   DEFVAL {noPtpTime}
   ::= {sysClockInfo 1}

tmnxSysConsoleAlarmInput OBJECT-TYPE
    SYNTAX      TruthValue
    MAX-ACCESS  read-write
    STATUS      current
    DESCRIPTION
        "Enable/Disable Console Alarm Input"
    DEFVAL { false }
    ::= { sysSASObjs 2 }

tmnxDyingGasp NOTIFICATION-TYPE
    STATUS  current
    DESCRIPTION
    " tmnxDyingGasp trap is generated when the system goes
    down due to power failure. System would make best effort
    to send out this trap with the power remaining in Dying
    Gasp capacitor"
    ::= { tmnxSASSysNotifications 1 }

tmnxVwmShelfTable   OBJECT-TYPE
    SYNTAX      SEQUENCE OF TmnxVwmShelfEntry
    MAX-ACCESS  not-accessible
    STATUS      current
    DESCRIPTION
        "The tmnxVwmShelfTable contains an entry for each VWM shelf
        in the device"
    ::= { sysSASVwmObjs 1 }

tmnxVwmShelfEntry OBJECT-TYPE
    SYNTAX      TmnxVwmShelfEntry
    MAX-ACCESS  not-accessible
    STATUS      current
    DESCRIPTION
        "Each row entry contains information about a VWM shelf

         Entries in this table can be created and deleted via SNMP
         SET operations to tmnxVwmShelfRowStatus."
    INDEX { tmnxVwmShelfId }
    ::= { tmnxVwmShelfTable 1 }

TmnxVwmShelfEntry ::=
    SEQUENCE {
        tmnxVwmShelfId                  INTEGER,
        tmnxVwmShelfRowStatus           RowStatus,
        tmnxVwmShelfAdminState          TmnxAdminState,
        tmnxVwmShelfOperState           TmnxAdminState,
        tmnxVwmShelfVwmType             INTEGER,
        tmnxVwmShelfEquippedType        INTEGER,
        tmnxVwmshelfTypeConnected       INTEGER
    }

tmnxVwmShelfId  OBJECT-TYPE
    SYNTAX      INTEGER (0..7)
    MAX-ACCESS  accessible-for-notify
    STATUS      current
    DESCRIPTION
        "Shelf ID of the VWM Shelf"
    ::= { tmnxVwmShelfEntry 1 }

tmnxVwmShelfRowStatus  OBJECT-TYPE
    SYNTAX      RowStatus
    MAX-ACCESS  read-create
    STATUS      current
    DESCRIPTION
        "tmnxVwmShelfRowStatus controls the creation and deletion of
         rows in the table. To create a row in this table, set the row
         status to createAndGo(4)'. "
    ::= { tmnxVwmShelfEntry 2 }

tmnxVwmShelfAdminState   OBJECT-TYPE
    SYNTAX      TmnxAdminState
    MAX-ACCESS  read-create
    STATUS      current
    DESCRIPTION
        "The value of tmnxVwmShelfAdminState specifies the administrative
        state of the VWM shelf."
    DEFVAL { outOfService }
    ::= { tmnxVwmShelfEntry 3 }

tmnxVwmShelfOperState   OBJECT-TYPE
    SYNTAX      TmnxAdminState
    MAX-ACCESS  read-only
    STATUS      current
    DESCRIPTION
        "The value of tmnxVwmShelfOperState specifies the operational
        state of the VWM shelf."
    DEFVAL { outOfService }
    ::= { tmnxVwmShelfEntry 4 }

tmnxVwmShelfVwmType   OBJECT-TYPE
    SYNTAX      INTEGER {
        ec-cw (1),
        ec-dw (2)
    }
    MAX-ACCESS  read-create
    STATUS      current
    DESCRIPTION
        "The value of tmnxVwmShelfVwmType specifies the vwm shelf type.
        "
    ::= { tmnxVwmShelfEntry 5 }

tmnxVwmShelfEquippedType OBJECT-TYPE
    SYNTAX      INTEGER {
        not-equipped (0),
        unknown (1),
        cwdm (2),
        dwdm (4)
    }
    MAX-ACCESS  read-only
    STATUS      current
    DESCRIPTION
        "The value of tmnxVwmshelfTypeConnected specifies the vwm shelf type.equipped
        to the system.
        "
    ::= { tmnxVwmShelfEntry 6 }

tmnxVwmshelfTypeConnected   OBJECT-TYPE
    SYNTAX      INTEGER {
        usb (1),
        i2c (2)
    }
    MAX-ACCESS  read-only
    STATUS      current
    DESCRIPTION
        "The value of tmnxVwmshelfTypeConnected specifies the vwm shelf  optical type.connected
        to the system.
        "
    ::= { tmnxVwmShelfEntry 7 }
--

tmnxVwmShelfCardTable   OBJECT-TYPE
    SYNTAX      SEQUENCE OF TmnxVwmShelfCardEntry
    MAX-ACCESS  not-accessible
    STATUS      current
    DESCRIPTION
        "The tmnxVwmShelfCardTable contains an entry for each VWM shelf
         slot in the device"
    ::= { sysSASVwmObjs 2 }

tmnxVwmShelfCardEntry OBJECT-TYPE
    SYNTAX      TmnxVwmShelfCardEntry
    MAX-ACCESS  not-accessible
    STATUS      current
    DESCRIPTION
        "Each row entry contains information about a VWM shelf slot

         Entries in this table can be created and deleted via SNMP
         SET operations to tmnxVwmShelfRowStatus."
    INDEX { tmnxVwmShelfId, tmnxVwmShelfCardId}
    ::= { tmnxVwmShelfCardTable 1 }

TmnxVwmShelfCardEntry ::=
    SEQUENCE {
        tmnxVwmShelfCardId                  INTEGER,
        tmnxVwmShelfCardType                TmnxVwmCardType,
        tmnxVwmShelfCardEqType              TmnxVwmCardType,
        tmnxVwmShelfCardAdminState          TmnxAdminState,
        tmnxVwmShelfCardOperState           TmnxAdminState
    }

tmnxVwmShelfCardId  OBJECT-TYPE
    SYNTAX      INTEGER (1..7)
    MAX-ACCESS  accessible-for-notify
    STATUS      current
    DESCRIPTION
        "Slot ID of the VWM Shelf slot"
    ::= { tmnxVwmShelfCardEntry 1 }

tmnxVwmShelfCardType OBJECT-TYPE
    SYNTAX      TmnxVwmCardType
    MAX-ACCESS  read-write
    STATUS      current
    DESCRIPTION
        "tmnxVwmShelfCardType is the vwm slot type that is being
        configured by user"
    ::= { tmnxVwmShelfCardEntry 2 }

tmnxVwmShelfCardEqType OBJECT-TYPE
    SYNTAX      TmnxVwmCardType
    MAX-ACCESS  read-only
    STATUS      current
    DESCRIPTION
        "tmnxVwmShelfCardEqType is the vwm slot type that is being
        provisioned"
    ::= { tmnxVwmShelfCardEntry 3 }

tmnxVwmShelfCardAdminState   OBJECT-TYPE
    SYNTAX      TmnxAdminState
    MAX-ACCESS  read-write
    STATUS      current
    DESCRIPTION
        "The value of tmnxVwmShelfCardAdminState specifies the administrative
        state of the VWM shelf slot."
    DEFVAL { outOfService }
    ::= { tmnxVwmShelfCardEntry 4 }

tmnxVwmShelfCardOperState   OBJECT-TYPE
    SYNTAX      TmnxAdminState
    MAX-ACCESS  read-only
    STATUS      current
    DESCRIPTION
        "The value of tmnxVwmShelfCardOperState specifies the operational
        state of the VWM shelf slot."
    DEFVAL { outOfService }
    ::= { tmnxVwmShelfCardEntry 5 }


--
--  Alcatel-Lucent 7210 series Chassis Extensions
--
aluExtTmnxChassisTable OBJECT-TYPE
    SYNTAX  SEQUENCE OF AluExtTmnxChassisEntry
    MAX-ACCESS  not-accessible
    STATUS      current
    DESCRIPTION
        "The chassis table has an entry for each chassis in the system."
    ::= { tmnxSASChassisObjs 9 }

aluExtTmnxChassisEntry       OBJECT-TYPE
    SYNTAX      AluExtTmnxChassisEntry
    MAX-ACCESS  not-accessible
    STATUS      current
    DESCRIPTION
        "Each row entry represents a chassis in the system.  The agent
         creates the row for the first chassis in the system, with
         tmnxChassisIndex = 1, which is auto-discovered by the active CPM
         card.  Additional chassis entries can be created and deleted via
         SNMP SET operations.  Creation requires a SET request containing
         at least tmnxChassisAdminMode and tmnxChassisRowStatus.  Note
         that the first Alcatel 7x50 series product release does not
         support multiple chassis, therefore there will not be more
         than one row entry in this table; attempts to create additional
         rows in this table will be denied."
    INDEX   { tmnxChassisIndex }
    ::= { aluExtTmnxChassisTable 1 }

AluExtTmnxChassisEntry ::=
    SEQUENCE {
        aluExtPoePowerMode                  INTEGER,
        aluExtPoePowerSupplyStatus          INTEGER,
        aluExtPoeExternalPowerSupplyStatus  INTEGER
    }

aluExtPoePowerMode OBJECT-TYPE
    SYNTAX      INTEGER
                {
                    none         (0),
                    internal     (1),
                    external     (2)
                }

    MAX-ACCESS  read-write
    STATUS      current
    DESCRIPTION
        "aluExtPoePowerMode represents set of poe capabilities,
         the mode is general for all MDAs, ports "
    DEFVAL { none }
    ::= { aluExtTmnxChassisEntry 3 }


aluExtPoePowerSupplyStatus OBJECT-TYPE
    SYNTAX      INTEGER
                {
                   none        (0),
                   bad         (1),
                   good        (2)
                }

    MAX-ACCESS  read-only
    STATUS      current
    DESCRIPTION
        "Current status of the PoE Power Supply."
    ::= { aluExtTmnxChassisEntry  4 }

aluExtPoeExternalPowerSupplyStatus OBJECT-TYPE
    SYNTAX      INTEGER
                {
                   absent   (0),
                   present  (1)
                }

    MAX-ACCESS  read-only
    STATUS      current
    DESCRIPTION
        "Current status of the PoE External Power Supply connection"
    ::= { aluExtTmnxChassisEntry  5 }

--
tCardResOperTable    OBJECT-TYPE
    SYNTAX  SEQUENCE OF TCardResOperEntry
    MAX-ACCESS  not-accessible
    STATUS      current
    DESCRIPTION
        "The tCardResOperTable has an entry for each CPM card or module in
         each chassis in the TMNX system, this table provides the
         operations system resource values used on the card"
    ::= { tmnxSASChassisObjs 10 }

tCardResOperEntry       OBJECT-TYPE
    SYNTAX      TCardResOperEntry
    MAX-ACCESS  not-accessible
    STATUS      current
    DESCRIPTION
        "Each row entry represents a CPM card or module in a chassis in the
         system.  Entries cannot be created and deleted via SNMP SET
         operations.  When a tmnxChassisEntry is created, a tCardResOperEntry
         is created for each CPM card or module in that chassis.  Before a
         tmnxChassisEntry can be deleted, each tCardResOperEntry for that
         chassis must be in the proper state for removal."
    AUGMENTS   { tmnxCpmCardEntry }
    ::= { tCardResOperTable 1 }

TCardResOperEntry ::=
    SEQUENCE {
        tCardResOperIngTcamSapAggMeter           INTEGER,
        tCardResOperIngTcamQosSapIng             INTEGER,
        tCardResOperIngTcamQosSapIngIpv4         INTEGER,
        tCardResOperIngTcamQosSapIngIpv4Ipv6     INTEGER,
        tCardResOperIngTcamQosSapIngMac          INTEGER,
        tCardResOperIngTcamAclSapIng             INTEGER,
        tCardResOperIngTcamAclSapIngIpv4         INTEGER,
        tCardResOperIngTcamAclSapIng64Ipv6       INTEGER,
        tCardResOperIngTcamAclSapIng128Ipv4Ipv6  INTEGER,
        tCardResOperIngTcamAclSapIngMac          INTEGER,
        tCardResOperEgrTcamAclSapEgr             INTEGER,
        tCardResOperEgrTcamAclSapEgrMacIpv4      INTEGER,
        tCardResOperEgrTcamAclSapEgr128Ipv6      INTEGER,
        tCardResOperEgrTcamAclSapEgr64MacIpv6    INTEGER,
        tCardResOperEgrTcamAclSapEgrMac          INTEGER,
        tCardResOperIngTcamEthCfm                INTEGER,
        tCardResOperIngTcamEthCfmUpMep           INTEGER,
        tCardResOperG8032CtrlSapStartVlan        Unsigned32,
        tCardResOperG8032CtrlSapEndVlan          Unsigned32,
        tCardResOperResIpMacMatchEnable          INTEGER,
        tCardResOperIngTcamEthCfmDownMep         INTEGER,
        tCardResOperIngTcamIpMulticast           INTEGER
}

tCardResOperIngTcamSapAggMeter OBJECT-TYPE
    SYNTAX      INTEGER (0..2)
    MAX-ACCESS  read-only
    STATUS      current
    DESCRIPTION
        " Ingress tcam sap aggregate meter resource"
    ::= { tCardResOperEntry 1 }


tCardResOperIngTcamQosSapIng OBJECT-TYPE
    SYNTAX      INTEGER (0..5)
    MAX-ACCESS  read-only
    STATUS      current
    DESCRIPTION
        " Ingress tcam sap sap ingress resource"
    ::= { tCardResOperEntry 2 }

tCardResOperIngTcamQosSapIngIpv4 OBJECT-TYPE
    SYNTAX      INTEGER (-1..5)
    MAX-ACCESS  read-only
    STATUS      current
    DESCRIPTION
        " Ingress tcam sap ingress ipv4 resource"
    ::= { tCardResOperEntry 3 }

tCardResOperIngTcamQosSapIngIpv4Ipv6 OBJECT-TYPE
    SYNTAX      INTEGER (0..7)
    MAX-ACCESS  read-only
    STATUS      current
    DESCRIPTION
        " Ingress tcam sap ingress ipv4, ipv6 resource"
    ::= { tCardResOperEntry 4 }

tCardResOperIngTcamQosSapIngMac OBJECT-TYPE
    SYNTAX      INTEGER (-1..5)
    MAX-ACCESS  read-only
    STATUS      current
    DESCRIPTION
        " Ingress tcam sap ingress mac resource"
    ::= { tCardResOperEntry 5 }

tCardResOperIngTcamAclSapIng OBJECT-TYPE
    SYNTAX      INTEGER (0..5)
    MAX-ACCESS  read-only
    STATUS      current
    DESCRIPTION
        " Ingress tcam acl sap ingress resource"
    ::= { tCardResOperEntry 6 }

tCardResOperIngTcamAclSapIngIpv4 OBJECT-TYPE
    SYNTAX      INTEGER (-1..5)
    MAX-ACCESS  read-only
    STATUS      current
    DESCRIPTION
        " Ingress tcam acl sap ingress ipv4 resource"
    ::= { tCardResOperEntry 7 }

tCardResOperIngTcamAclSapIng64Ipv6 OBJECT-TYPE
    SYNTAX      INTEGER (-1..5)
    MAX-ACCESS  read-only
    STATUS      current
    DESCRIPTION
        " Ingress tcam acl sap ingress 64 bit ipv6
        match resource"
    ::= { tCardResOperEntry 8 }

tCardResOperIngTcamAclSapIng128Ipv4Ipv6 OBJECT-TYPE
    SYNTAX      INTEGER (-1..5)
    MAX-ACCESS  read-only
    STATUS      current
    DESCRIPTION
        " Ingress tcam acl sap ingress 128 bit ipv6
        resource"
    ::= { tCardResOperEntry 9 }

tCardResOperIngTcamAclSapIngMac OBJECT-TYPE
    SYNTAX      INTEGER (-1..5)
    MAX-ACCESS  read-only
    STATUS      current
    DESCRIPTION
        " Ingress tcam acl sap ingress mac resource"
    ::= { tCardResOperEntry 10 }

tCardResOperEgrTcamAclSapEgr OBJECT-TYPE
    SYNTAX      INTEGER (0 | 2)
    MAX-ACCESS  read-only
    STATUS      current
    DESCRIPTION
        " Egress tcam acl sap sap egress 1resource"
    ::= { tCardResOperEntry 11 }

tCardResOperEgrTcamAclSapEgrMacIpv4 OBJECT-TYPE
    SYNTAX      INTEGER (0 | 2)
    MAX-ACCESS  read-only
    STATUS      current
    DESCRIPTION
        " Egress tcam acl sap egress mac ipv4 resource"
    ::= { tCardResOperEntry 12 }

tCardResOperEgrTcamAclSapEgr128Ipv6 OBJECT-TYPE
    SYNTAX      INTEGER (0 | 2)
    MAX-ACCESS  read-only
    STATUS      current
    DESCRIPTION
        "Egress tcam acl sap egress 128bit ipv6 resource"
    ::= { tCardResOperEntry 13 }

tCardResOperEgrTcamAclSapEgr64MacIpv6 OBJECT-TYPE
    SYNTAX      INTEGER (0 | 2)
    MAX-ACCESS  read-only
    STATUS      current
    DESCRIPTION
        "Egress tcam acl sap egress mac resource"
    ::= { tCardResOperEntry 14 }

tCardResOperEgrTcamAclSapEgrMac OBJECT-TYPE
    SYNTAX      INTEGER (0 | 2)
    MAX-ACCESS  read-only
    STATUS      current
    DESCRIPTION
        "Egress tcam acl sap egress mac resource"
    ::= { tCardResOperEntry 15 }

tCardResOperIngTcamEthCfm OBJECT-TYPE
    SYNTAX      INTEGER (1..3)
    MAX-ACCESS  read-only
    STATUS      current
    DESCRIPTION
        " Ingress tcam eth cfm resource"
    ::= { tCardResOperEntry 18 }

tCardResOperIngTcamEthCfmUpMep OBJECT-TYPE
    SYNTAX      INTEGER (0..7)
    MAX-ACCESS  read-only
    STATUS      current
    DESCRIPTION
        " Ingress tcam eth cfm up-mep resource"
    ::= { tCardResOperEntry 19 }

tCardResOperG8032CtrlSapStartVlan OBJECT-TYPE
    SYNTAX          Unsigned32(0 .. 4094)
    MAX-ACCESS      read-only
    STATUS          current
    DESCRIPTION     "G8032 control sap tag start vlan"
    ::= { tCardResOperEntry 20 }


tCardResOperG8032CtrlSapEndVlan OBJECT-TYPE
    SYNTAX          Unsigned32(0 .. 4094)
    MAX-ACCESS      read-only
    STATUS          current
    DESCRIPTION     "G8032 control sap tag End vlan"
    ::= { tCardResOperEntry 21 }

tCardResOperResIpMacMatchEnable OBJECT-TYPE
    SYNTAX          INTEGER (-1 | 0..10)
    MAX-ACCESS      read-only
    STATUS          current
    DESCRIPTION     "Resource allocation for ip mac match enable"
    ::= { tCardResOperEntry 22 }

tCardResOperIngTcamEthCfmDownMep OBJECT-TYPE
    SYNTAX      INTEGER (1..3)
    MAX-ACCESS  read-only
    STATUS      current
    DESCRIPTION
        " Ingress tcam eth cfm down-mep resource"
    ::= { tCardResOperEntry 23 }

tCardResOperIngTcamIpMulticast OBJECT-TYPE
    SYNTAX      INTEGER (0..1)
    MAX-ACCESS  read-only
    STATUS      current
    DESCRIPTION
        "tCardResOperIngTcamIpMulticast sets the resource to be used for ip-multicast."
    ::= { tCardResOperEntry 24 }



tmnxSASSecurityNotificationObjs   OBJECT IDENTIFIER ::= { tmnxSASSecurityObjects 5 }

tmnxLoginUserName  OBJECT-TYPE
    SYNTAX      TNamedItem (SIZE(1..20))
    MAX-ACCESS  accessible-for-notify
    STATUS      current
    DESCRIPTION
        "The value of tmnxUserName specifies the name for a system user.
         This name must be unique amongst the table entries. tmnxUserName
         will be sent in the notifications when the user crosses the
         threshold login attempts configured in tmnxPasswordAttemptsCount"
    ::= { tmnxSASSecurityNotificationObjs 1 }

tmnxLoginUserSrcIPAddress      OBJECT-TYPE
    SYNTAX      InetAddress (SIZE(0|4|16))
    MAX-ACCESS  accessible-for-notify
    STATUS      current
    DESCRIPTION
        "The value of tmnxLoginUserSrcIPAddress specifies the source address of the
        client station from where the user has tried to login"
    DEFVAL { ''H }
    ::= { tmnxSASSecurityNotificationObjs 2 }

tmnxLoginMaxAttempts     OBJECT-TYPE
    SYNTAX      INTEGER
    MAX-ACCESS  accessible-for-notify
    STATUS      current
    DESCRIPTION
        "The value of tmnxLoginMaxAttempts specifies the number of times user
        could attempt to login before raising a max attempt trap"
    ::= { tmnxSASSecurityNotificationObjs 3 }

tmnxUserLoginMaxAttempts  NOTIFICATION-TYPE
    OBJECTS {
        tmnxLoginUserName,
        tmnxLoginUserSrcIPAddress,
        tmnxLoginMaxAttempts
    }
    STATUS  current
    DESCRIPTION
        "The tmnxUserLoginMaxAttempts is generated when a user failed to
        authenticate in more than the permitted number of login retries."
    ::= { tmnxSASSecurityNotifications 1 }

tmnxSSHUserLoginMaxAttempts  NOTIFICATION-TYPE
    OBJECTS {
        tmnxLoginUserName,
        tmnxLoginUserSrcIPAddress,
        tmnxLoginMaxAttempts
    }
    STATUS  current
    DESCRIPTION
        "The tmnxSSHUserLoginMaxAttempts is generated when a user failed to
        authenticate in more than the permitted number of login retries through
        SSH."
    ::= { tmnxSASSecurityNotifications 3 }

tmnxEqPowerInputFailure   NOTIFICATION-TYPE
    OBJECTS {
        tmnxChassisNotifyHwIndex,
        tmnxHwID,
        tmnxHwClass,
        tmnxHwName,
        tmnxChassisPowerSupplyInputStatus
    }
    STATUS  current
    DESCRIPTION
        "Generated when one of the chassis's power source supplies fails."
    ::= { tmnxSASChassisNotification 3 }

tmnxEqPowerOutputFailure   NOTIFICATION-TYPE
      OBJECTS {
          tmnxChassisNotifyHwIndex,
          tmnxHwID,
          tmnxHwClass,
          tmnxHwName,
          tmnxChassisPowerSupplyOutputStatus
      }
      STATUS  current
      DESCRIPTION
          "Generated when one of the chassis's power output  fails."
    ::= { tmnxSASChassisNotification 4 }

sysOperGrpOperStatusChanged NOTIFICATION-TYPE
   OBJECTS {
       sysOperGrpOperStatus
   }
   STATUS          current
   DESCRIPTION
        "[CAUSE] The svcOperGrpOperStatusChanged notification is generated when
        there is a change in the value of svcOperGrpOperStatus.

        [EFFECT] Status of the one or more of the members of the operational
        group has changed.

        [RECOVERY] Operational status of the members of the operational-group
        will need to be investigated."
   ::= { tmnxSASChassisNotification 25 }

tmnxChassisNotifyMDACfgFailReason OBJECT-TYPE
    SYNTAX      DisplayString
    MAX-ACCESS  accessible-for-notify
    STATUS      current
    DESCRIPTION
        "Used by tmnxEqMDACfgMissing, the value of
         tmnxChassisNotifyMDACfgFailReason contains the
         reason for MDA config failure."
    ::= { tmnxSASSecurityNotificationObjs 4 }


tmnxSASSysCompliances OBJECT IDENTIFIER ::= { tmnxSASSysConformance 1 }
tmnxSASSysGroups      OBJECT IDENTIFIER ::= { tmnxSASSysConformance 2 }

tmnxSASSysSecConformance  OBJECT IDENTIFIER ::= { tmnxSASSysConformance  4 }
tmnxSASSysSecGroups       OBJECT IDENTIFIER ::= { tmnxSASSysSecConformance 1 }

tmnxSASChassisGroups OBJECT IDENTIFIER ::= { timetraSASConfs 10 }

tmnxSASSysV1v0Group OBJECT-GROUP
    OBJECTS    {
        sbiUplinkAPort,
        sbiUplinkAIpAddr,
        sbiUplinkAMask,
        sbiUplinkAVlan,
        sbiUplinkBPort,
        sbiUplinkBIpAddr,
        sbiUplinkBMask,
        sbiUplinkBVlan,
        sbiPingAddress,
        sbiUplinkRouteNextHop,
        sbiUplinkRouteRowStatus,
        tmnxChassisUpdateGoldenBootstrapImage,
        tmnxChassisGoldenBootstrapImageSrc,
        tmnxChassisValidateGoldenBootstrapImage,
        tmnxChassisGoldenBootstrapImageVersion,
        tmnxChassisRebootAutoInit
}
       STATUS obsolete
       DESCRIPTION
           " sas system group object definition for first release"
       ::= { tmnxSASSysGroups 1 }

tmnxSASSysV2v0Group OBJECT-GROUP
    OBJECTS    {
        tSASMpointBwPlcy,
        sbiUplinkAPort,
        sbiUplinkAIpAddr,
        sbiUplinkAMask,
        sbiUplinkAVlan,
        sbiUplinkBPort,
        sbiUplinkBIpAddr,
        sbiUplinkBMask,
        sbiUplinkBVlan,
        sbiPingAddress,
        sbiUplinkRouteNextHop,
        sbiUplinkRouteRowStatus,
        tmnxChassisUpdateGoldenBootstrapImage,
        tmnxChassisGoldenBootstrapImageSrc,
        tmnxChassisValidateGoldenBootstrapImage,
        tmnxChassisGoldenBootstrapImageVersion,
        tmnxChassisRebootAutoInit,
        sbiEthMgmtDisabled,
        sbiEthMgmtActiveIpAddr,
        sbiEthMgmtActiveIpMask,
        sbiEthMgmtAutoNegotiate,
        sbiEthMgmtSpeed,
        sbiEthMgmtDuplex,
        sbiEthMgmtStaticRouteNextHop,
        sbiEthMgmtStaticRouteRowStatus,
        tmnxChassisLowTempState
}
       STATUS current
       DESCRIPTION
           " sas system group object definition for 2.0 release"
       ::= { tmnxSASSysGroups 2 }

tmnxSASSysV3v0Group OBJECT-GROUP
    OBJECTS    {
        sbiExpansionCardType,
        tmnxFabricPolicyRowStatus,
        tmnxFabricPolicyCIR,
        tmnxFabricPolicyPIR,
        tmnxFabricPolicyCBS,
        tmnxFabricPolicyMBS,
        tmnxFabricPolicyMpointFabricPort,
        tmnxChassisPowerSupplyAssignedDCType
    }
       STATUS current
       DESCRIPTION
           " sas system group object definition for 3.0 release"
       ::= { tmnxSASSysGroups 3 }

tmnxSASSysV4v0Group OBJECT-GROUP
    OBJECTS    {
        sbiConsoleDisabled,
        sysLoopbackNoServPort,
        sysG8032FastFloodEnable,
        sysMirrorLoopbackNoServPort,
        sysResFabricPathBandwidth,
        sysResMaxIPv6Routes,
        sysResIngTcamEthCfm,
        sysResIngTcamEthCfmUpMep,
        sysG8032FastFloodEnableOperVal
    }
       STATUS current
       DESCRIPTION
           " sas system group object definition for 4.0 release"
       ::= { tmnxSASSysGroups 4 }

tmnxSASSysV5v0Group OBJECT-GROUP
    OBJECTS    {
         sysResIngTcamIngAclMac,
         sysResEgrTcamSapEgrAcl,
         sysResEgrTcamEgrAclMac,
         sysResEgrTcamEgrAclIpv4,
         sysResEgrTcamEgrAcl64bitIpv4Ipv6,
         sysResEgrTcamEgrAcl128bitIpv4Ipv6,
         sysResEgrTcamEgrAcl64bitIpv6Only,
         sysResEgrSapEgrClass,
         sysResEgrSapEgrClassMac,
         sysResEgrSapEgrClassIpv4,
         sysResEgrSapEgrClassIpv4Ipv6,
         sysResIngTcamSapAggMeter,
         sysResIngTcamSapAggMeterOperVal,
         tmnxChassisFanCfgMode,
         tmnxChassisFanOperMode,
         sysResIngTcamIngAcl64bitIpv4Ipv6,
         tmnxPtpTimeUsePtp,
         sysResQosSapIngQMode,
         sysResQosSapIngQOperMode,
         sysResRouterEcmpMaxRoutesDst,
         sysResRouterEcmpMaxRoutesDstOperVal,
         sysTestHdNoServPort
    }
       STATUS current
       DESCRIPTION
           " sas system group object definition for 5.0 release"
       ::= { tmnxSASSysGroups 5 }

tmnxSASSysObjsV6v0Group OBJECT-GROUP
    OBJECTS    {
       tmnxSysConsoleAlarmInput
    }
       STATUS current
       DESCRIPTION
           " sas system group object definition for 5.0 release"
       ::= { tmnxSASSysGroups 6 }

tmnxSASSysQosV5v0Group OBJECT-GROUP
    OBJECTS    {
        sysQosWredSlopes
    }
       STATUS current
       DESCRIPTION
           " sas system group object definition for 5.0 release"
       ::= { tmnxSASSysGroups 7 }

tmnxSASSysV6v0Group OBJECT-GROUP
    OBJECTS    {
        sysDhcpSnoopingSdpEnable ,
        sysDhcpSnoopingEnable
    }
       STATUS current
       DESCRIPTION
           " sas system group object definition for 6.0 release"
       ::= { tmnxSASSysGroups 8 }

tmnxSASSysConsoleV6v0Group OBJECT-GROUP
    OBJECTS    {
       tmnxSysConsoleAlarmInput
    }
       STATUS current
       DESCRIPTION
           " sas system group object definition for 6.0 release"
       ::= { tmnxSASSysGroups 9 }

tmnxSASSysResPlcyV6v1Group OBJECT-GROUP
    OBJECTS    {
        tResPlcyRowStatus,
        tResPlcyIngTcamSapAggMeter,
        tResPlcyIngTcamQosSapIng,
        tResPlcyIngTcamQosSapIngIpv4,
        tResPlcyIngTcamQosSapIngIpv4Ipv6,
        tResPlcyIngTcamQosSapIngMac,
        tResPlcyIngTcamAclSapIng,
        tResPlcyIngTcamAclSapIngIpv4,
        tResPlcyIngTcamAclSapIng64Ipv6,
        tResPlcyIngTcamAclSapIng128Ipv4Ipv6,
        tResPlcyIngTcamAclSapIngMac,
        tResPlcyEgrTcamAclSapEgr,
        tResPlcyEgrTcamAclSapEgrMacIpv4,
        tResPlcyEgrTcamAclSapEgr128Ipv6,
        tResPlcyEgrTcamAclSapEgr64MacIpv6,
        tResPlcyEgrTcamAclSapEgrMac,
        tResPlcyDescription,
        tResPlcyLastChanged,
        tResPlcyIngTcamEthCfm,
        tResPlcyIngTcamEthCfmUpMep,
        tResPlcyG8032CtrlSapStartVlan,
        tResPlcyG8032CtrlSapEndVlan,
        tResPlcyResIpMacMatchEnable,
        tResPlcyIngTcamEthCfmDownMep,
        tResPlcyIngTcamEthCfmUpMepEnable,
        tResPlcyIngTcamEthCfmDownMepEnable
    }
       STATUS current
       DESCRIPTION
           " sas system resource policy group object definition
           for 6.1 release"
       ::= { tmnxSASSysGroups 10 }

tmnxSASSysSecV4v0Group OBJECT-GROUP
    OBJECTS    {
        tmnxLoginUserName,
        tmnxLoginUserSrcIPAddress,
        tmnxLoginMaxAttempts
    }
       STATUS current
       DESCRIPTION
           " sas system security group object definition for 4.0
           release"
       ::= { tmnxSASSysSecGroups 1 }

tmnxSASSysSecNotifyV4v0Group NOTIFICATION-GROUP
    NOTIFICATIONS {
        tmnxUserLoginMaxAttempts,
        tmnxSSHUserLoginMaxAttempts
    }
    STATUS    current
    DESCRIPTION
        "The group of notifications supported in 7210 4.0 release"
    ::= { tmnxSASSysSecGroups 2 }

tmnxSASChassisNotificationV3v0Group NOTIFICATION-GROUP
    NOTIFICATIONS {
        tmnxEnvTempTooLow,
        tmnxRootDirFull,
        tmnxEqPowerInputFailure,
        tmnxEqPowerOutputFailure,
        tmnxEqMDACfgMissing
    }
    STATUS    current
    DESCRIPTION
        "The group of notifications supported in 7210 3.0 release"
    ::= { tmnxSASChassisGroups 1 }

tmnxSASChassisGroup OBJECT-GROUP
    OBJECTS  {
        tmnxChassisSystemLEDState
    }
    STATUS    current
    DESCRIPTION
        "The group of notifications supported in 7210 5.0 release"
    ::= { tmnxSASChassisGroups 2 }

tmnxSASChassisV61Group OBJECT-GROUP
    OBJECTS  {
        tmnxCpmCardBootImageSource
    }
    STATUS    current
    DESCRIPTION
        "The group of notifications supported in 7210 6.1 release"
    ::= { tmnxSASChassisGroups 3 }

END
