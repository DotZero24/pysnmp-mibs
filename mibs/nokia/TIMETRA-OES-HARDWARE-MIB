TIMETRA-OES-HARDWARE-MIB DEFINITIONS ::= BEGIN

-- (c) Copyright 2013-2016 Nokia.  All rights reserved.
-- This software is the confidential and proprietary property of
-- Nokia and may only be used in accordance with the
-- terms of the license agreement provided with this software.

 IMPORTS
    SnmpAdminString                         FROM SNMP-FRAMEWORK-MIB

    OBJECT-TYPE, MODULE-IDENTITY,
    NOTIFICATION-TYPE, Unsigned32,
    Integer32, Counter64, Gauge32,
    Counter32                               FROM SNMPv2-SMI

    MODULE-COMPLIANCE, OBJECT-GROUP,
    NOTIFICATION-GROUP                      FROM SNMPv2-CONF

    TEXTUAL-CONVENTION, DateAndTime,
    DisplayString, RowStatus,
    TruthValue, TimeStamp                   FROM SNMPv2-TC

    TmnxHwIndex, tmnxHwIndex,
    TmnxPhysChassisIndex, TmnxLEDState,
    TmnxCardRebootType, TmnxDeviceState,
    tmnxHwClass                             FROM TIMETRA-CHASSIS-MIB

    TmnxActionType, TmnxAdminState,
    TmnxOperState, TNamedItemOrEmpty,
    TItemDescription, TNamedItem            FROM TIMETRA-TC-MIB

    ifIndex                                 FROM IF-MIB

    tmnxSRObjs,tmnxSRConfs,
    tmnxSRNotifyPrefix, timetraSRMIBModules FROM TIMETRA-GLOBAL-MIB

    tmnxPortNotifyPortId,
    TmnxPortOperStatus                      FROM TIMETRA-PORT-MIB
    ;

timetraOesHardwareMIBModule      MODULE-IDENTITY
        LAST-UPDATED    "201308010000Z"
        ORGANIZATION "Nokia"
        CONTACT-INFO
            "Nokia SROS Support
             Web: http://www.nokia.com"
        DESCRIPTION
        "This document is the SNMP MIB module to manage and provision the
        Optical Extension Shelf (OES) hardware components of the Nokia
        SROS device.

        Copyright (c) 2013-2016 Nokia.  All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."

--
-- Revision History
--
        REVISION    "201308010000Z"
        DESCRIPTION "Rev 1.0                            05 Sep 2013 00:00
                     Initial release of the TIMETRA-OES-HARDWARE-MIB."

      ::= { timetraSRMIBModules 99 }

tmnxOesHwObjs            OBJECT IDENTIFIER ::= { tmnxSRObjs 99 }
tmnxOesHwMIBNotifyPrefix OBJECT IDENTIFIER ::= { tmnxSRNotifyPrefix 99 }
tmnxOesHwConformance     OBJECT IDENTIFIER ::= { tmnxSRConfs 99 }

-- Object Groups in the Nokia OES MIB Module
tmnxOesChassisObjs       OBJECT IDENTIFIER ::= { tmnxOesHwObjs 1 }
tmnxOesCardObjs          OBJECT IDENTIFIER ::= { tmnxOesHwObjs 2 }
tmnxOesPortObjs          OBJECT IDENTIFIER ::= { tmnxOesHwObjs 3 }
tmnxOesHwNotifyObjs      OBJECT IDENTIFIER ::= { tmnxOesHwObjs 4 }

-- Notification Groups in the Nokia OES MIB Module
tmnxOesHwNotifications   OBJECT IDENTIFIER ::= { tmnxOesHwMIBNotifyPrefix 1 }

-- Compliance Groups in the Nokia OES MIB Module
tmnxOesHwCompliances     OBJECT IDENTIFIER ::= { tmnxOesHwConformance 1 }
tmnxOesHwGroups          OBJECT IDENTIFIER ::= { tmnxOesHwConformance 2 }

--%%%%%%%%%%%%%%%%%%%%%%%%%%%%%%%%%%%%%%%%%%%%%%%%%%%%%%%%%%%%%%%%%%%%%%%%%%%
--
--  TIMETRA-OES-HARDWARE-MIB Textual Conventions
--
TmnxOesCardHFD                   ::= TEXTUAL-CONVENTION
    STATUS      current
    DESCRIPTION
        "TmnxOesCardHFD specifies ..."
    SYNTAX      SnmpAdminString (SIZE(0..2))

TmnxOesHwMktPartNo               ::= TEXTUAL-CONVENTION
    STATUS      current
    DESCRIPTION
        "TmnxOesHwMktPartNo specifies ..."
    SYNTAX      SnmpAdminString (SIZE(0..20))

TmnxOesHwSWGenLoadName           ::= TEXTUAL-CONVENTION
    STATUS      current
    DESCRIPTION
        "TmnxOesHwSWGenLoadName specifies ..."
    SYNTAX      SnmpAdminString (SIZE(0..20))

TmnxOesHwLEDColorType            ::= TEXTUAL-CONVENTION
    STATUS      current
    DESCRIPTION
        "TmnxOesHwLEDColorType specifies ..."
    SYNTAX      INTEGER {
                    unknown(1),
                    off(2),
                    red(3),
                    green(4),
                    orange(5)
                }

TmnxOesHwLEDStateType            ::= TEXTUAL-CONVENTION
    STATUS      current
    DESCRIPTION
        "TmnxOesHwLEDStateType specifies ..."
    SYNTAX      INTEGER {
                    unknown   (1),
                    solid     (2),
                    fastBlink (3),
                    slowBlink (4)
                }

TmnxOesSlotNumber                ::= TEXTUAL-CONVENTION
    STATUS      current
    DESCRIPTION
        "TmnxOesSlotNumber specifies a unique index that identifies a physical
         slot number within an OES chassis."
    SYNTAX      Unsigned32 (1..40)

TmnxOesChassisType               ::= TEXTUAL-CONVENTION
    STATUS      current
    DESCRIPTION
        "TmnxOesChassisType specifies an Nokia SR OES chassis type."
    SYNTAX      Unsigned32

TmnxOesCardType                  ::= TEXTUAL-CONVENTION
    STATUS      current
    DESCRIPTION
        "TmnxOesCardType specifies an Nokia SR OES card type."
    SYNTAX      Unsigned32

TmnxOesCardSuppType              ::= TEXTUAL-CONVENTION
    STATUS      current
    DESCRIPTION
        "TmnxCardSuppType specifies the valid card types supported for a
         specific card slot. When multiple bits are set, it can be used to
         identify a set or list of card types.

         Some example card types:

             112SCA1 -- 112G Single Port Tunable
             112SNA1 -- 112G Single Port Tunable Coherent
             130SCA1 -- 130G Single Port Tunable
             EC      -- Equipment Controller"
    SYNTAX      BITS {
                    invalid-card-type    (0),
                    unassigned           (1),
                    oes-supp-card-type-2 (2),
                    oes-supp-card-type-3 (3),
                    oes-supp-card-type-4 (4),
                    oes-supp-card-type-5 (5),
                    oes-supp-card-type-6 (6),
                    oes-supp-card-type-7 (7),
                    oes-supp-card-type-8 (8)
                }

TmnxOesCmnEqpPortNumber                ::= TEXTUAL-CONVENTION
    STATUS      current
    DESCRIPTION
        "TmnxOesCmnEqpPortNumber specifies a unique index that identifies a
         physical port number within an OES chassis common equipment slot."
    SYNTAX      Unsigned32

TmnxOesPortErrorStatus                 ::= TEXTUAL-CONVENTION
    STATUS  current
    DESCRIPTION
        "The TmnxOesPortErrorStatus is a bitmask which describes error
         conditions that can be raised/cleared on an OES port.

         The possible values are:
            deviceFailure       (0) - generic port device failure.
            transmissionFailure (1) - port transmission failure."
    SYNTAX  BITS {
                deviceFailure       (0),
                transmissionFailure (1)
            }

--%%%%%%%%%%%%%%%%%%%%%%%%%%%%%%%%%%%%%%%%%%%%%%%%%%%%%%%%%%%%%%%%%%%%%%%%%%%
--
--  TIMETRA-OES-HARDWARE-MIB Global Configuration Objects
--
tmnxOesChassisTypeTable          OBJECT-TYPE
    SYNTAX      SEQUENCE OF TmnxOesChassisTypeEntry
    MAX-ACCESS  not-accessible
    STATUS      current
    DESCRIPTION
        "The chassis type table has an entry for each Nokia SROS EOS
         series chassis model."
    ::= { tmnxOesChassisObjs 1 }

tmnxOesChassisTypeEntry          OBJECT-TYPE
    SYNTAX      TmnxOesChassisTypeEntry
    MAX-ACCESS  not-accessible
    STATUS      current
    DESCRIPTION
        "Each row entry represents an Nokia SROS OES series chassis
         model. Rows in this table are created by the agent at initialization
         and cannot be created or destroyed by SNMP Get or Set requests."
    INDEX       { tmnxOesChassisTypeIndex }
    ::= { tmnxOesChassisTypeTable 1 }

TmnxOesChassisTypeEntry          ::= SEQUENCE {
    tmnxOesChassisTypeIndex        TmnxOesChassisType,
    tmnxOesChassisTypeName         TNamedItemOrEmpty,
    tmnxOesChassisTypeDescription  TItemDescription,
    tmnxOesChassisTypeStatus       TruthValue
}

tmnxOesChassisTypeIndex          OBJECT-TYPE
    SYNTAX      TmnxOesChassisType
    MAX-ACCESS  not-accessible
    STATUS      current
    DESCRIPTION
        "The value of tmnxOesChassisTypeIndex specifies the type of
         Nokia SROS series OES chassis model."
    ::= { tmnxOesChassisTypeEntry 1 }

tmnxOesChassisTypeName           OBJECT-TYPE
    SYNTAX      TNamedItemOrEmpty
    MAX-ACCESS  read-only
    STATUS      current
    DESCRIPTION
        "The value of tmnxOesChassisTypeName indicates the administrative name
         that identifies this type of Nokia SROS series OES chassis
         model.  This name string may be used in CLI commands to specify a
         particular OES chassis model type."
    ::= { tmnxOesChassisTypeEntry 2 }

tmnxOesChassisTypeDescription    OBJECT-TYPE
    SYNTAX      TItemDescription
    MAX-ACCESS  read-only
    STATUS      current
    DESCRIPTION
        "The value of tmnxOesChassisTypeDescription indicates the detailed
         description of this Nokia SROS series OES chassis model."
    ::= { tmnxOesChassisTypeEntry 3 }

tmnxOesChassisTypeStatus         OBJECT-TYPE
    SYNTAX      TruthValue
    MAX-ACCESS  read-only
    STATUS      current
    DESCRIPTION
        "The value of tmnxOesChassisTypeStatus indicates the chassis type
         support. When tmnxOesChassisTypeStatus has a value of 'true' it
         indicates that this chassis model is supported in this revision of the
         management software. When it has a value of 'false' there is no
         support."
    ::= { tmnxOesChassisTypeEntry 4 }

tmnxOesChassisLastChange         OBJECT-TYPE
    SYNTAX      TimeStamp
    MAX-ACCESS  read-only
    STATUS      current
    DESCRIPTION
        "The value of tmnxOesChassisLastChange indicates the time, since
         system startup, when tmnxOesChassisTable last changed configuration."
    ::= { tmnxOesChassisObjs 2 }

tmnxOesChassisTable              OBJECT-TYPE
    SYNTAX      SEQUENCE OF TmnxOesChassisEntry
    MAX-ACCESS  not-accessible
    STATUS      current
    DESCRIPTION
        "The tmnxOesChassisTable contains configuration information for
         OES chassis."
    ::= { tmnxOesChassisObjs 3 }

tmnxOesChassisEntry              OBJECT-TYPE
    SYNTAX      TmnxOesChassisEntry
    MAX-ACCESS  not-accessible
    STATUS      current
    DESCRIPTION
        "The tmnxOesChassisEntry consists of the configurable objects for
         a given OES chassis."
    INDEX       { tmnxOesChassisNumber }
    ::= { tmnxOesChassisTable 1 }

TmnxOesChassisEntry              ::= SEQUENCE {
    tmnxOesChassisNumber             TmnxPhysChassisIndex,
    tmnxOesChassisRowStatus          RowStatus,
    tmnxOesChassisRowLastChanged     TimeStamp,
    tmnxOesChassisAssignedType       TmnxOesChassisType,
    tmnxOesChassisEquippedType       TmnxOesChassisType,
    tmnxOesChassisActivitySwitch     TmnxActionType,
    tmnxOesChassisHwEntryIndex       TmnxHwIndex
}

tmnxOesChassisNumber             OBJECT-TYPE
    SYNTAX      TmnxPhysChassisIndex
    MAX-ACCESS  not-accessible
    STATUS      current
    DESCRIPTION
        "The value of tmnxOesChassisNumber specifies a unique value which
         identifies the OES chassis."
    ::= { tmnxOesChassisEntry 1 }

tmnxOesChassisRowStatus          OBJECT-TYPE
    SYNTAX      RowStatus
    MAX-ACCESS  read-create
    STATUS      current
    DESCRIPTION
        "The value of tmnxOesChassisRowStatus specifies the row status.
         It allows the creation and deletion of rows in tmnxOesChassisTable.

         When creating an OES Chassis entry, tmnxOesChassisRowStatus and
         tmnxOesChassisAssignedType must be set together in the same SNMP SET
         request PDU."
    ::= { tmnxOesChassisEntry 2 }

tmnxOesChassisRowLastChanged     OBJECT-TYPE
    SYNTAX      TimeStamp
    MAX-ACCESS  read-only
    STATUS      current
    DESCRIPTION
        "The value of tmnxOesChassisRowLastChanged indicates the time this row
         was last changed."
    ::= { tmnxOesChassisEntry 3 }

tmnxOesChassisAssignedType       OBJECT-TYPE
    SYNTAX      TmnxOesChassisType
    MAX-ACCESS  read-create
    STATUS      current
    DESCRIPTION
        "The value of tmnxOesChassisAssignedType specifies the administratively
         assigned type of the OES chassis.

         tmnxOesChassisRowStatus and tmnxOesChassisAssignedType must be set
         together in the same SNMP SET request PDU."
    DEFVAL      { 1 }
    ::= { tmnxOesChassisEntry 4 }

tmnxOesChassisEquippedType       OBJECT-TYPE
    SYNTAX      TmnxOesChassisType
    MAX-ACCESS  read-only
    STATUS      current
    DESCRIPTION
        "The value of tmnxOesChassisEquippedType indicates the OES chassis type
         that is equipped."
    ::= { tmnxOesChassisEntry 5 }

tmnxOesChassisActivitySwitch     OBJECT-TYPE
    SYNTAX      TmnxActionType
    MAX-ACCESS  read-create
    STATUS      current
    DESCRIPTION
        "The value of tmnxOesChassisActivitySwitch specifies the activity switch
         action for the OES chassis. When the value is set to 'doAction (1)',
         the OES chassis causes an activity switchover between this chassis's
         controller (i.e. EC) cards."
    DEFVAL      { notApplicable }
    ::= { tmnxOesChassisEntry 6 }

tmnxOesChassisHwEntryIndex       OBJECT-TYPE
    SYNTAX      TmnxHwIndex
    MAX-ACCESS  read-only
    STATUS      current
    DESCRIPTION
        "The value is a unique index that identifies
         common management information for Nokia SROS series
         manufactured hardware components within the specified chassis."
    ::= { tmnxOesChassisEntry 7 }

tmnxOesPFTable                 OBJECT-TYPE
    SYNTAX      SEQUENCE OF TmnxOesPFEntry
    MAX-ACCESS  not-accessible
    STATUS      current
    DESCRIPTION
        "The table tmnxOesPFTable contains information about the OES
         power filter cards."
    ::= { tmnxOesChassisObjs 4 }

tmnxOesPFEntry                 OBJECT-TYPE
    SYNTAX      TmnxOesPFEntry
    MAX-ACCESS  not-accessible
    STATUS      current
    DESCRIPTION
        "A row in tmnxOesPFTable is created/destroyed by the SYSTEM when there
         is a row created/destroyed in the tmnxHwTable for an OES power
         filter card."
    INDEX       { tmnxOesChassisNumber,
                  tmnxOesSlotNumber }
    ::= { tmnxOesPFTable 1 }

TmnxOesPFEntry                 ::= SEQUENCE {
    tmnxOesSlotNumber     TmnxOesSlotNumber,
    tmnxOesPFType           INTEGER,
    tmnxOesPFAmpRating      Unsigned32,
    tmnxOesPFInputCurrent   Unsigned32,
    tmnxOesPFInputVoltage   Unsigned32,
    tmnxOesPFInputPower     Unsigned32,
    tmnxOesPFClkA           Unsigned32,
    tmnxOesPFClkB           Unsigned32,
    tmnxOesPFClkDelta       Integer32,
    tmnxOesPFState          TmnxDeviceState,
    tmnxOesPFHwIndex        TmnxHwIndex
}

tmnxOesSlotNumber                OBJECT-TYPE
    SYNTAX      TmnxOesSlotNumber
    MAX-ACCESS  not-accessible
    STATUS      current
    DESCRIPTION
        "The value of tmnxOesSlotNumber specifies the slot number of an OES
         power filter card."
    ::= { tmnxOesPFEntry 1 }

tmnxOesPFType   OBJECT-TYPE
    SYNTAX      INTEGER {
                    ac (1),
                    dc (2)
                }
    MAX-ACCESS  read-only
    STATUS      current
    DESCRIPTION
        "The value of tmnxOesPFType indicates the type of an OES power filter
         card."
    ::= { tmnxOesPFEntry 2 }

tmnxOesPFAmpRating               OBJECT-TYPE
    SYNTAX      Unsigned32
    UNITS       "deci-amps"
    MAX-ACCESS  read-only
    STATUS      current
    DESCRIPTION
        "The value of tmnxOesPFAmpRating indicates the amperage rating of an OES
         power filter."
    ::= { tmnxOesPFEntry 3 }

tmnxOesPFInputCurrent            OBJECT-TYPE
    SYNTAX      Unsigned32
    UNITS       "milli-amps"
    MAX-ACCESS  read-only
    STATUS      current
    DESCRIPTION
        "The value of tmnxOesPFInputCurrent indicates the input current of an
         OES power filter."
    ::= { tmnxOesPFEntry 4 }

tmnxOesPFInputVoltage            OBJECT-TYPE
    SYNTAX      Unsigned32
    UNITS       "milli-volts"
    MAX-ACCESS  read-only
    STATUS      current
    DESCRIPTION
        "The value of tmnxOesPFInputVoltage indicates the input voltage of an
         OES power filter."
    ::= { tmnxOesPFEntry 5 }

tmnxOesPFInputPower              OBJECT-TYPE
    SYNTAX      Unsigned32
    UNITS       "watts"
    MAX-ACCESS  read-only
    STATUS      current
    DESCRIPTION
        "The value of tmnxOesPFInputPower indicates the input power of an OES
         power filter."
    ::= { tmnxOesPFEntry 6 }

tmnxOesPFClkA                    OBJECT-TYPE
    SYNTAX      Unsigned32
    UNITS       "1/10 parts-per-million"
    MAX-ACCESS  read-only
    STATUS      current
    DESCRIPTION
        "The value of tmnxOesPFClkA indicates the frequency offset
         of clock A of the OES power filter."
    ::= { tmnxOesPFEntry 7 }

tmnxOesPFClkB                    OBJECT-TYPE
    SYNTAX      Unsigned32
    UNITS       "1/10 parts-per-million"
    MAX-ACCESS  read-only
    STATUS      current
    DESCRIPTION
        "The value of tmnxOesPFClkB indicates the frequency offset
         of clock B of the OES power filter."
    ::= { tmnxOesPFEntry 8 }

tmnxOesPFClkDelta                OBJECT-TYPE
    SYNTAX      Integer32
    UNITS       "1/10 parts-per-million"
    MAX-ACCESS  read-only
    STATUS      current
    DESCRIPTION
        "The value of tmnxOesPFClkDelta indicates the difference between
         the frequency offset of clock A and that of clock B"
    ::= { tmnxOesPFEntry 9 }

tmnxOesPFState                   OBJECT-TYPE
    SYNTAX      TmnxDeviceState
    MAX-ACCESS  read-only
    STATUS      current
    DESCRIPTION
        "The value of tmnxOesPFState indicates an OES power filter's operational

         state."
    ::= { tmnxOesPFEntry 10 }

tmnxOesPFHwIndex                 OBJECT-TYPE
    SYNTAX      TmnxHwIndex
    MAX-ACCESS  read-only
    STATUS      current
    DESCRIPTION
        "The value of tmnxOesPFHwIndex indicates a unique index of common
         management information for hardware components within the specified
         chassis."
    ::= { tmnxOesPFEntry 11 }

tmnxOesFanLastChg                OBJECT-TYPE
    SYNTAX      TimeStamp
    MAX-ACCESS  read-only
    STATUS      current
    DESCRIPTION
        "The value of sysUpTime when tmnxOesFanTable was last changed."
    ::= { tmnxOesChassisObjs 5 }

tmnxOesFanTable                  OBJECT-TYPE
    SYNTAX      SEQUENCE OF TmnxOesFanEntry
    MAX-ACCESS  not-accessible
    STATUS      current
    DESCRIPTION
        "The table tmnxOesFanTable contains the information pertaining
         to the fan tray(s) of OES chassis."
    ::= { tmnxOesChassisObjs 6 }

tmnxOesFanEntry                  OBJECT-TYPE
    SYNTAX      TmnxOesFanEntry
    MAX-ACCESS  not-accessible
    STATUS      current
    DESCRIPTION
        "Rows in tmnxOesFanTable are created/destroyed by the SYSTEM when
         tmnxOesChassisEntry rows are created/destroyed. Only certain slots
         can contain a fan in each OES chassis type."
    INDEX       { tmnxOesChassisNumber,
                  tmnxOesFanSlotNumber }
    ::= { tmnxOesFanTable 1 }

TmnxOesFanEntry                ::= SEQUENCE {
    tmnxOesFanSlotNumber      TmnxOesSlotNumber,
    tmnxOesFanState           TmnxDeviceState,
    tmnxOesFanSpeedControl    INTEGER,
    tmnxOesFanHwIndex         TmnxHwIndex
}

tmnxOesFanSlotNumber             OBJECT-TYPE
    SYNTAX      TmnxOesSlotNumber
    MAX-ACCESS  not-accessible
    STATUS      current
    DESCRIPTION
        "The value of tmnxOesFanSlotNumber specifies the slot number of the
         fan in OES chassis."
    ::= { tmnxOesFanEntry 1 }

tmnxOesFanState      OBJECT-TYPE
    SYNTAX      TmnxDeviceState
    MAX-ACCESS  read-only
    STATUS      current
    DESCRIPTION
        "The value of tmnxOesFanState indicates the fan's operational state."
    ::= { tmnxOesFanEntry 2 }

tmnxOesFanSpeedControl           OBJECT-TYPE
    SYNTAX      INTEGER {
                    normal  (1),
                    maximum (2)
                }
    MAX-ACCESS  read-write
    STATUS      current
    DESCRIPTION
        "The value of tmnxOesFanSpeedControl specifies the level of the fan
         speed."
    DEFVAL      { normal }
    ::= { tmnxOesFanEntry 3 }

tmnxOesFanHwIndex                OBJECT-TYPE
    SYNTAX      TmnxHwIndex
    MAX-ACCESS  read-only
    STATUS      current
    DESCRIPTION
        "The value of tmnxOesFanHwIndex indicates a unique index that
         identifies common management information for Nokia SROS
         series manufactured hardware components within the specified chassis."
    ::= { tmnxOesFanEntry 4 }

tmnxOesCardTypeTable             OBJECT-TYPE
    SYNTAX      SEQUENCE OF TmnxOesCardTypeEntry
    MAX-ACCESS  not-accessible
    STATUS      current
    DESCRIPTION
        "The card type table has an entry for each Nokia SROS EOS
         series card model."
    ::= { tmnxOesCardObjs 1 }

tmnxOesCardTypeEntry             OBJECT-TYPE
    SYNTAX      TmnxOesCardTypeEntry
    MAX-ACCESS  not-accessible
    STATUS      current
    DESCRIPTION
        "Each row entry represents an Nokia SROS series Card model.
         Rows in this table are created by the agent at initialization and
         cannot be created or destroyed by SNMP Get or Set requests."
    INDEX       { tmnxOesCardTypeIndex }
    ::= { tmnxOesCardTypeTable 1 }

TmnxOesCardTypeEntry             ::= SEQUENCE {
    tmnxOesCardTypeIndex        TmnxOesCardType,
    tmnxOesCardTypeName         SnmpAdminString,
    tmnxOesCardTypeDescription  SnmpAdminString,
    tmnxOesCardTypeStatus       TruthValue,
    tmnxOesCardTypeHeight       Unsigned32,
    tmnxOesCardTypeWidth        Unsigned32,
    tmnxOesCardTypeNumPorts     Unsigned32
}

tmnxOesCardTypeIndex             OBJECT-TYPE
    SYNTAX      TmnxOesCardType
    MAX-ACCESS  not-accessible
    STATUS      current
    DESCRIPTION
        "The unique index value which identifies this type of Nokia
         SROS series OES card model."
    ::= { tmnxOesCardTypeEntry 1 }

tmnxOesCardTypeName              OBJECT-TYPE
    SYNTAX      SnmpAdminString (SIZE(0..31))
    MAX-ACCESS  read-only
    STATUS      current
    DESCRIPTION
        "The administrative name that identifies this type of Nokia
         SROS series OES card model.  This name string may be used in
         CLI commands to specify a particular card model type."
    ::= { tmnxOesCardTypeEntry 2 }

tmnxOesCardTypeDescription       OBJECT-TYPE
    SYNTAX      SnmpAdminString (SIZE(0..255))
    MAX-ACCESS  read-only
    STATUS      current
    DESCRIPTION
        "A detailed description of this Nokia SROS series OES card
         model."
    ::= { tmnxOesCardTypeEntry 3 }

tmnxOesCardTypeStatus            OBJECT-TYPE
    SYNTAX      TruthValue
    MAX-ACCESS  read-only
    STATUS      current
    DESCRIPTION
        "When tmnxOesCardTypeStatus has a value of 'true' it indicates that
         this card model is supported in this revision of the management
         software.  When it has a value of 'false' there is no support."
    ::= { tmnxOesCardTypeEntry 4 }

tmnxOesCardTypeHeight            OBJECT-TYPE
    SYNTAX      Unsigned32
    MAX-ACCESS  read-only
    STATUS      current
    DESCRIPTION
        "The value indicates the number of vertical slots this card type
         occupies."
    ::= { tmnxOesCardTypeEntry 5 }

tmnxOesCardTypeWidth             OBJECT-TYPE
    SYNTAX      Unsigned32
    MAX-ACCESS  read-only
    STATUS      current
    DESCRIPTION
        "The value indicates the number of horizontal slots this card type
         occupies."
    ::= { tmnxOesCardTypeEntry 6 }

tmnxOesCardTypeNumPorts          OBJECT-TYPE
    SYNTAX      Unsigned32
    MAX-ACCESS  read-only
    STATUS      current
    DESCRIPTION
        "The value indicates the number of ports that this card type contains."
    ::= { tmnxOesCardTypeEntry 7 }

tmnxOesCardLastChange            OBJECT-TYPE
    SYNTAX      TimeStamp
    MAX-ACCESS  read-only
    STATUS      current
    DESCRIPTION
        "The value of tmnxOesCardLastChange indicates the time since system
         startup this table was last changed."
    ::= { tmnxOesCardObjs 2 }

tmnxOesCardTable                 OBJECT-TYPE
    SYNTAX      SEQUENCE OF TmnxOesCardEntry
    MAX-ACCESS  not-accessible
    STATUS      current
    DESCRIPTION
        "The tmnxOesCardTable has an entry for each OES card slot in
         each chassis."
    ::= { tmnxOesCardObjs 3 }

tmnxOesCardEntry                 OBJECT-TYPE
    SYNTAX      TmnxOesCardEntry
    MAX-ACCESS  not-accessible
    STATUS      current
    DESCRIPTION
        "Each row entry represents an OES card slot in an OES chassis in
         the system. Entries cannot be created and deleted via
         SNMP SET operations. When tmnxOesChassisEntry is created,
         a tmnxOesCardEntry is created for each OES card slot in that
         chassis."
    INDEX       { tmnxOesChassisNumber,
                  tmnxOesSlotNumber }
    ::= { tmnxOesCardTable 1 }

TmnxOesCardEntry                 ::= SEQUENCE {
    tmnxOesCardAssignedType    TmnxOesCardType,
    tmnxOesCardEquippedType    TmnxOesCardType,
    tmnxOesCardSupportedTypes  TmnxOesCardSuppType,
    tmnxOesCardReboot          TmnxCardRebootType,
    tmnxOesCardHwEntryIndex    TmnxHwIndex,
    tmnxOesCardRowLastChanged  TimeStamp,
    tmnxOesCardMemorySize      Unsigned32
}

tmnxOesCardAssignedType          OBJECT-TYPE
    SYNTAX      TmnxOesCardType
    MAX-ACCESS  read-write
    STATUS      current
    DESCRIPTION
        "The value of tmnxOesCardAssignedType specifies the administratively
         assigned OES card type that should occupy this fabric slot in this
         chassis."
    DEFVAL      { 2 }
    ::= { tmnxOesCardEntry 1 }

tmnxOesCardEquippedType          OBJECT-TYPE
    SYNTAX      TmnxOesCardType
    MAX-ACCESS  read-only
    STATUS      current
    DESCRIPTION
        "The value of tmnxOesCardEquippedType indicates the OES card type that
         is physically inserted into this slot in this chassis."
    ::= { tmnxOesCardEntry 2 }

tmnxOesCardSupportedTypes        OBJECT-TYPE
    SYNTAX      TmnxOesCardSuppType
    MAX-ACCESS  read-only
    STATUS      current
    DESCRIPTION
        "The value of tmnxOesCardSupportedTypes indicates what OES card types
         can be configured in this slot in this chassis."
    ::= { tmnxOesCardEntry 3 }

tmnxOesCardReboot                OBJECT-TYPE
    SYNTAX      TmnxCardRebootType
    MAX-ACCESS  read-write
    STATUS      current
    DESCRIPTION
        "The value of tmnxOesCardReboot specifies the reboot type and
         executes the reboot. Setting this variable to 'cardReboot' causes
         the OES card to execute a soft-reboot. Setting this variable to
         'cardPowerCycle' causes the OES card to turn off and turn on power
         to the card initiating a hard-reboot."
    DEFVAL      { notApplicable }
    ::= { tmnxOesCardEntry 4 }

tmnxOesCardHwEntryIndex          OBJECT-TYPE
    SYNTAX      TmnxHwIndex
    MAX-ACCESS  read-only
    STATUS      current
    DESCRIPTION
        "The value of tmnxOesCardHwEntryIndex indicates a unique index that
         identifies common management information for Nokia SROS
         series manufactured hardware components within the specified chassis."
    ::= { tmnxOesCardEntry 5 }

tmnxOesCardRowLastChanged        OBJECT-TYPE
    SYNTAX      TimeStamp
    MAX-ACCESS  read-only
    STATUS      current
    DESCRIPTION
        "The value of tmnxOesCardRowLastChanged indicates the time since system
         startup this row was last changed."
    ::= { tmnxOesCardEntry 6 }

tmnxOesCardMemorySize            OBJECT-TYPE
    SYNTAX      Unsigned32
    UNITS       "Giga-bytes"
    MAX-ACCESS  read-only
    STATUS      current
    DESCRIPTION
        "The value of tmnxOesCardMemorySize indicates the amount of memory
         populated on this OES card."
    ::= { tmnxOesCardEntry 7 }

tmnxOesControlCardTable        OBJECT-TYPE
    SYNTAX      SEQUENCE OF TmnxOesControlCardEntry
    MAX-ACCESS  not-accessible
    STATUS      current
    DESCRIPTION
        "The table tmnxOesControlCardTable contains information pertaining to
         the OES equipment controller (EC)."
    ::= { tmnxOesCardObjs 4 }

tmnxOesControlCardEntry        OBJECT-TYPE
    SYNTAX      TmnxOesControlCardEntry
    MAX-ACCESS  not-accessible
    STATUS      current
    DESCRIPTION
        "A row in tmnxOesControlCardTable is created/destroyed by the SYSTEM
         when there is a row created/destroyed in tmnxOesChassisTable for each
         OES chassis."
    INDEX       { tmnxOesChassisNumber,
                  tmnxOesSlotNumber }
    ::= { tmnxOesControlCardTable 1 }

TmnxOesControlCardEntry        ::= SEQUENCE {
    tmnxOesControlCardActState     INTEGER,
    tmnxOesControlCardHwIndex      TmnxHwIndex
}

tmnxOesControlCardActState     OBJECT-TYPE
    SYNTAX      INTEGER {
                    unknown    (1),
                    active     (2),
                    standby    (3),
                    unequipped (4)
                }
    MAX-ACCESS  read-only
    STATUS      current
    DESCRIPTION
        "The value of tmnxOesControlCardActState indicates whether or not
         this control card is active."
    ::= { tmnxOesControlCardEntry 1 }

tmnxOesControlCardHwIndex        OBJECT-TYPE
    SYNTAX      TmnxHwIndex
    MAX-ACCESS  read-only
    STATUS      current
    DESCRIPTION
        "The value of tmnxOesControlCardHwIndex indicates a unique index that
         identifies common management information for Nokia SROS
         series manufactured hardware components within the specified chassis."
    ::= { tmnxOesControlCardEntry 2 }

-- Common equipment port table

tmnxOesCmnEqpPortTable           OBJECT-TYPE
    SYNTAX      SEQUENCE OF TmnxOesCmnEqpPortEntry
    MAX-ACCESS  not-accessible
    STATUS      current
    DESCRIPTION
        "The table tmnxOesCmnEqpPortTable contains the information pertaining
         to the ports of the common equipment cards of the OES chassis. The
         common equipment represents the hardware which includes the shelf,
         shelf controller, user panel (USPNL), equipment controller (EC), first
         level controller (FLC), PSS power distribution units, power filter
         card (PFD), fans, etc."
    ::= { tmnxOesPortObjs 1 }

tmnxOesCmnEqpPortEntry           OBJECT-TYPE
    SYNTAX      TmnxOesCmnEqpPortEntry
    MAX-ACCESS  not-accessible
    STATUS      current
    DESCRIPTION
        "A Row in tmnxOesCmnEqpPortTable is created/destroyed by the SYSTEM
         when there is a row created/destroyed in the tmnxHwTable for each OES
         common equipment, e.g. equipment controller (EC) and user panel."
    INDEX       { tmnxOesChassisNumber,
                  tmnxOesSlotNumber,
                  tmnxOesCmnEqpPortNumber}
    ::= { tmnxOesCmnEqpPortTable  1}

TmnxOesCmnEqpPortEntry           ::= SEQUENCE {
    tmnxOesCmnEqpPortNumber         TmnxOesCmnEqpPortNumber,
    tmnxOesCmnEqpPortCardType       TmnxOesCardType,
    tmnxOesCmnEqpPortOperStatus     TmnxPortOperStatus
}

tmnxOesCmnEqpPortNumber                OBJECT-TYPE
    SYNTAX      TmnxOesCmnEqpPortNumber
    MAX-ACCESS  not-accessible
    STATUS      current
    DESCRIPTION
        "The value of tmnxOesCmnEqpPortNumber specifies the index of the
         tmnxOesCmnEqpPortTable table. It is a number that represents
         a port of the common equipment card uniquely within the card. This
         index along with the other indexes of the table are used to map this
         port uniquely within the equipment cards in an OES chassis."
    ::= { tmnxOesCmnEqpPortEntry  1 }

tmnxOesCmnEqpPortCardType          OBJECT-TYPE
    SYNTAX      TmnxOesCardType
    MAX-ACCESS  read-only
    STATUS      current
    DESCRIPTION
        "The value of tmnxOesCmnEqpPortCardType indicates the type of the
         common equipment card that the port belongs to."
    ::= { tmnxOesCmnEqpPortEntry  2 }

tmnxOesCmnEqpPortOperStatus       OBJECT-TYPE
    SYNTAX      TmnxPortOperStatus
    MAX-ACCESS  read-only
    STATUS      current
    DESCRIPTION
        "The value of tmnxOesCmnEqpPortOperStatus indicates the operational
         status of the port of the OES common equipment card."
    ::= { tmnxOesCmnEqpPortEntry  3 }

-- Common equipment port type table

tmnxOesCmnEqpPortTypeTable             OBJECT-TYPE
    SYNTAX      SEQUENCE OF TmnxOesCmnEqpPortTypeEntry
    MAX-ACCESS  not-accessible
    STATUS      current
    DESCRIPTION
        "The table tmnxOesCmnEqpPortTypeTable contains the information
         pertaining to the type of the ports of the common equipment cards,
         e.g. equipment control (EC) and user panel, of the OES chassis."
    ::= { tmnxOesPortObjs 2 }

tmnxOesCmnEqpPortTypeEntry             OBJECT-TYPE
    SYNTAX      TmnxOesCmnEqpPortTypeEntry
    MAX-ACCESS  not-accessible
    STATUS      current
    DESCRIPTION
        "Rows in table tmnxOesCmnEqpPortTypeEntry are created by the SYSTEM at
         initialization and can not be created or destroyed by SNMP
         set requests. Each row represents an OES port within a common
         equipment OES card of a certain type."
    INDEX       {tmnxOesCardTypeIndex, tmnxOesCmnEqpPortNumber }
    ::= { tmnxOesCmnEqpPortTypeTable 1 }

TmnxOesCmnEqpPortTypeEntry          ::= SEQUENCE {
    tmnxOesCmnEqpPortTypeName   TNamedItem,
    tmnxOesCmnEqpPortTypeDescr  TItemDescription
}

tmnxOesCmnEqpPortTypeName              OBJECT-TYPE
    SYNTAX      TNamedItem
    MAX-ACCESS  read-only
    STATUS      current
    DESCRIPTION
        "The value of tmnxOesCmnEqpPortTypeName indicates the administrative
         name that describes the OES common equipment port type."
    ::= { tmnxOesCmnEqpPortTypeEntry 1 }

tmnxOesCmnEqpPortTypeDescr       OBJECT-TYPE
    SYNTAX      TItemDescription
    MAX-ACCESS  read-only
    STATUS      current
    DESCRIPTION
        "The value of tmnxOesCmnEqpPortTypeDescr indicates the detailed
         description of the OES common equipment port type."
    ::= { tmnxOesCmnEqpPortTypeEntry 2 }

--%%%%%%%%%%%%%%%%%%%%%%%%%%%%%%%%%%%%%%%%%%%%%%%%%%%%%%%%%%%%%%%%%%%%%%%%%%%
--
--  TIMETRA-OES-HARDWARE-MIB Notification Objects
--
tmnxOesNotifyFailureReason       OBJECT-TYPE
    SYNTAX      DisplayString
    MAX-ACCESS  accessible-for-notify
    STATUS      current
    DESCRIPTION
        "The value of tmnxOesNotifyFailureReason is used by OES card or common
         equipment failure notifications to indicate the reason of failure."
    ::= { tmnxOesHwNotifyObjs 1 }

tmnxOesPortNotifyError           OBJECT-TYPE
    SYNTAX      TmnxOesPortErrorStatus
    MAX-ACCESS  accessible-for-notify
    STATUS      current
    DESCRIPTION
        "The value of tmnxOesPortNotifyError indicates the error conditions
         on this OES port."
    ::= { tmnxOesHwNotifyObjs 2 }

--%%%%%%%%%%%%%%%%%%%%%%%%%%%%%%%%%%%%%%%%%%%%%%%%%%%%%%%%%%%%%%%%%%%%%%%%%%%
--
--  TIMETRA-OES-HARDWARE-MIB Notifications
--
tmnxOesCtlCardPortDown           NOTIFICATION-TYPE
    OBJECTS {
        tmnxOesCmnEqpPortOperStatus
    }
    STATUS      current
    DESCRIPTION
        "[CAUSE] The tmnxOesCtlCardPortDown notification is generated when a
         port (e.g. ES 1 or AUX) on an OES Control Card (e.g. EC card) is not
         operational. The reason may be a misconnected, disconnected or faulty
         cable, a faulty port or Control Card.

         [EFFECT] If an ES (Extension Shelf) port is down then one of the
         control plane communication paths between EC (Equipment Controller)
         cards in different OES Chassis is not available. The control
         communications with one or more OES subtending chassis may be
         affected rendering the Chassis unmanageable. Other control paths
         may be available.

         If an AUX port is down then one of the control plane communication
         paths between the router and the OES Master Chassis is not available
         and control communications with the OES may be affected rendering
         the OES unmanageable. Other control paths may be available.

         [RECOVERY] Check that the cable is correctly connected and test the
         cable."
    ::= { tmnxOesHwNotifications 1 }

tmnxOesCtlCardPortUp             NOTIFICATION-TYPE
    OBJECTS {
        tmnxOesCmnEqpPortOperStatus
    }
    STATUS      current
    DESCRIPTION
        "[CAUSE] The tmnxOesCtlCardPortUp notification is generated when the
         port on the OES Control Card (e.g. EC card) is operational.

         [EFFECT] If an ES port is up then a control plane communication path
         between EC cards in different OES Chassis has been established.

         If an AUX port is up then a control plane communication path between
         the router and the OES Master Chassis has been established and the OES
         can be managed by the router.

         [RECOVERY] No recovery required"
    ::= { tmnxOesHwNotifications 2 }


tmnxOesUsrpnlPortDown            NOTIFICATION-TYPE
    OBJECTS {
        tmnxOesCmnEqpPortOperStatus
    }
    STATUS      current
    DESCRIPTION
        "[CAUSE] The tmnxOesUsrpnlPortDown notification is generated when
         a port (E1 or E2) on an OES USRPNL card is not operational. The
         reason may be a misconnected, disconnected or faulty cable, or a
         faulty port or USRPNL.

         [EFFECT] If an E1 or E2 port is down then one of the control plane
         communication paths between the router and the OES Master Chassis is
         not available. The control communications with the OES may be affected
         rendering the OES chassis unmanageable. Other control communications
         paths may be available.

         [RECOVERY] Check that the cable is correctly connected and test the
         cable."
    ::= { tmnxOesHwNotifications 3 }

tmnxOesUsrpnlPortUp              NOTIFICATION-TYPE
    OBJECTS {
        tmnxOesCmnEqpPortOperStatus
    }
    STATUS      current
    DESCRIPTION
        "[CAUSE] The tmnxOesUsrpnlPortUp notification is generated when the
         OES USRPNL port is now operational.

         [EFFECT] If an E1 or E2 port is up then a control plane communication
         path between the router and the OES Master Chassis has been established
         and the OES can be managed by the router.

         [RECOVERY] No recovery required."
    ::= { tmnxOesHwNotifications 4 }

tmnxOesFanRemoved                NOTIFICATION-TYPE
    OBJECTS {
        tmnxHwClass
    }
    STATUS  current
    DESCRIPTION
        "[CAUSE] The tmnxOesFanRemoved notification is generated when the OES
         fan unit is removed from its slot in the OES chassis.

         [EFFECT] The function of OES fan unit is not available.

         [RECOVERY] Insert OES fan unit into its slot."
    ::= { tmnxOesHwNotifications 5 }

tmnxOesFanInserted               NOTIFICATION-TYPE
    OBJECTS {
        tmnxHwClass
    }
    STATUS  current
    DESCRIPTION
        "[CAUSE] The tmnxOesFanInserted notification is generated when the OES
         fan unit is inserted into its slot in the OES chassis.

         [EFFECT] The OES chassis is now equipped with a fan unit.

         [RECOVERY] No recovery required."
    ::= { tmnxOesHwNotifications 6 }

tmnxOesFan32HReqd                NOTIFICATION-TYPE
    OBJECTS {
        tmnxHwClass
    }
    STATUS  current
    DESCRIPTION
        "[CAUSE] The tmnxOesFan32HReqd notification is generated when the
         OES chassis in a PSS32 shelf requires high speed fan (FAN32H), but the
         fan inserted is not the right type.

         [EFFECT] The OES chassis is not operating with required fan type.

         [RECOVERY] Replace the OES fan unit with the correct one for 1830
         PSS32 shelf."
    ::= { tmnxOesHwNotifications 7 }

tmnxOesFan32HReqdClear           NOTIFICATION-TYPE
    OBJECTS {
        tmnxHwClass
    }
    STATUS  current
    DESCRIPTION
        "[CAUSE] The tmnxOesFan32HReqdClear notification is generated when the
         OES chassis is equipped with FAN32H or when the alarmed fan unit with
         tmnxOesFan32HReqd condition is removed from the slot.

         [EFFECT] The OES chassis is operating with required fan type for 1830
         PSS32 shelf (FAN32H), or the incorrect fan unit has been removed.

         [RECOVERY] No recovery required."
    ::= { tmnxOesHwNotifications 8 }

tmnxOesFanFailure               NOTIFICATION-TYPE
    OBJECTS {
        tmnxHwClass,
        tmnxOesFanState,
        tmnxOesNotifyFailureReason
    }
    STATUS  current
    DESCRIPTION
        "[CAUSE] The tmnxOesFanFailure notification is generated when the fan
         unit in an OES chassis has failed. tmnxOesNotifyFailureReason contains
         the reason for fan failure.

         [EFFECT] The fan unit in the OES chassis is out of service.

         [RECOVERY] If the condition causing fan failure can not be removed,
         replace the faulty fan unit."
    ::= { tmnxOesHwNotifications 9 }

tmnxOesFanFailureClear          NOTIFICATION-TYPE
    OBJECTS {
        tmnxHwClass,
        tmnxOesFanState,
        tmnxOesNotifyFailureReason
    }
    STATUS  current
    DESCRIPTION
        "[CAUSE] The tmnxOesFanFailureClear notification is generated when fan
         failure in an OES chassis is cleared. tmnxOesNotifyFailureReason contains
         the reason for fan failure being cleared.

         [EFFECT] The fan unit in the OES chassis is in service.

         [RECOVERY] No recovery required."
    ::= { tmnxOesHwNotifications 10 }

tmnxOesPowerSupplyRemoved       NOTIFICATION-TYPE
    OBJECTS {
        tmnxHwClass
    }
    STATUS  current
    DESCRIPTION
        "[CAUSE] The tmnxOesPowerSupplyRemoved notification is generated when
         an OES power supply unit is removed from its slot in the OES chassis.

         [EFFECT] The power supply unit is not present in the indicated OES
         chassis slot.

         [RECOVERY] Insert OES power supply unit into its slot."
    ::= { tmnxOesHwNotifications 11 }

tmnxOesPowerSupplyInserted      NOTIFICATION-TYPE
    OBJECTS {
        tmnxHwClass
    }
    STATUS  current
    DESCRIPTION
        "[CAUSE] The tmnxOesPowerSupplyInserted notification is generated when
         the OES power supply unit is inserted into its slot in the OES chassis.

         [EFFECT] The indicated slot of the OES chassis is now equipped with
         the power supply unit.

         [RECOVERY] No recovery required."
    ::= { tmnxOesHwNotifications 12 }

tmnxOesPowerSupplyFailure       NOTIFICATION-TYPE
    OBJECTS {
        tmnxHwClass,
        tmnxOesPFState,
        tmnxOesNotifyFailureReason
    }
    STATUS  current
    DESCRIPTION
        "[CAUSE] The tmnxOesPowerSupplyFailure notification is generated when
         the power supply unit in the indicated slot of the OES chassis has
         failed. tmnxOesNotifyFailureReason contains the reason for the failure.

         [EFFECT] The indicated OES power supply unit is out of service.

         [RECOVERY] If the condition causing the power supply failure can not
         be removed, replace the faulty power supply unit."
    ::= { tmnxOesHwNotifications 13 }

tmnxOesPowerSupplyFailureClear  NOTIFICATION-TYPE
    OBJECTS {
        tmnxHwClass,
        tmnxOesPFState,
        tmnxOesNotifyFailureReason
    }
    STATUS  current
    DESCRIPTION
        "[CAUSE] The tmnxOesPowerSupplyFailureClear notification is generated
         when the power supply failure in the indicated slot of the OES chassis
         is cleared. tmnxOesNotifyFailureReason contains the reason for the
         power supply failure being cleared.

         [EFFECT] The indicated power supply unit in the OES chassis is
         in service.

         [RECOVERY] No recovery required."
    ::= { tmnxOesHwNotifications 14 }

tmnxOesPortError                 NOTIFICATION-TYPE
    OBJECTS {
        tmnxPortNotifyPortId,
        tmnxOesPortNotifyError
    }
    STATUS      current
    DESCRIPTION
        "[CAUSE] The tmnxOesPortError notification is generated when an error
         condition listed in tmnxOesPortNotifyError is detected on the OES port.

         [EFFECT] The OES port is experiencing errors that could be service affecting.

         [RECOVERY] tmnxOesPortError is cleared by taking the port out of
         service, eg. shutdown, or try a soft reset, hard reset, then replacement
         of the card if the error condition persists."
    ::= { tmnxOesHwNotifications 15 }

tmnxOesPortErrorClear            NOTIFICATION-TYPE
    OBJECTS {
        tmnxPortNotifyPortId
    }
    STATUS      current
    DESCRIPTION
        "[CAUSE] The tmnxOesPortErrorClear notification is generated when
         all error conditions on the OES port are cleared.

         [EFFECT] The OES port error conditions are cleared.

         [RECOVERY] No recovery required."
    ::= { tmnxOesHwNotifications 16 }

tmnxOesCtlCardActivityChange     NOTIFICATION-TYPE
    OBJECTS {
        tmnxHwClass
    }
    STATUS      current
    DESCRIPTION
        "[CAUSE] The tmnxOesCtlCardActivityChange notification is generated
         when the active Equipment Controller has changed to the card
         specified by the tmnxHwIndex.

         [EFFECT] The active Equipment Controller has moved to the previously
         standby card.

         [RECOVERY] No recovery is required."
    ::= { tmnxOesHwNotifications 17 }

tmnxOesFpgaFail                  NOTIFICATION-TYPE
    OBJECTS {
        tmnxHwClass
    }
    STATUS      current
    DESCRIPTION
        "[CAUSE] The tmnxOesFpgaFail notification is generated during an
         out-of-service upgrade when the FPGA file downloaded to the card was
         corrupt or the FPGA failed to program correctly.

         [EFFECT] The OES card shall automatically cold reboot and the card
         shall attempt to recover. While the condition exists the card remains
         out-of-service.

         [RECOVERY] If the card has rebooted and the condition did not clear,
         then first reseat the card and see if the condition clears. If the
         condition remains, then replace the card and follow the return and
         repair process for the problem card."
    ::= { tmnxOesHwNotifications 18 }

tmnxOesFpgaFailClear             NOTIFICATION-TYPE
    OBJECTS {
        tmnxHwClass
    }
    STATUS      current
    DESCRIPTION
        "[CAUSE] The tmnxOesFpgaFailClear notification is generated when the
         FPGA is successfully programmed.

         [EFFECT] The FPGA is successfully programmed.

         [RECOVERY] No recovery is required."
    ::= { tmnxOesHwNotifications 19 }

tmnxOesFpgaTimeout               NOTIFICATION-TYPE
    OBJECTS {
        tmnxHwClass
    }
    STATUS  current
    DESCRIPTION
        "[CAUSE] The tmnxOesFpgaTimeout notification is generated when the FPGA
         file download and reprogramming took longer than expected (about 45
         minutes).

         [EFFECT] The FPGA on the indicated card was not reprogrammed in the
         time window.

         [RECOVERY] If the OES card is operational, wait for a maintenance window
         and reset the OES card."
    ::= { tmnxOesHwNotifications 20 }

tmnxOesFpgaTimeoutClear          NOTIFICATION-TYPE
    OBJECTS {
        tmnxHwClass
    }
    STATUS      current
    DESCRIPTION
        "[CAUSE] The tmnxOesFpgaTimeoutClear notification is generated
         when the OES FPGA timeout condition is cleared.

         [EFFECT] The FPGA is successfully programmed.

         [RECOVERY] No recovery is required."
    ::= { tmnxOesHwNotifications 21 }


tmnxOesOptTrnspndrMiscFail       NOTIFICATION-TYPE
    OBJECTS {
        tmnxHwClass
    }
    STATUS      current
    DESCRIPTION
        "[CAUSE] The tmnxOesOptTrnspndrMiscFail notification is generated when
         a non-service affecting hardware defect is detected on the card.
         This condition may be declared on the card due to one of the
         following causes:
           1) Detection of line side transmitter laser bias or optical output
              power nearing end-of-life.
           2) Detection of line receiver ITLA (Integrated Tunable Laser
              Assembly) laser bias or output power nearing end-of-life.
           3) Detection of board-level Analog-to-Digital Conversion Digital
              Signal Processor (ADC DSP) device defect.
           4) A device-to-device interface communication problem.

         [EFFECT] The tmnxOesOptTrnspndrMiscFail alarm indicates a lower
         priority fault on the card that does not directly affect the
         traffic currently flowing through the card. However, the card
         should be replaced at the next available maintenance opportunity.

         [RECOVERY] Replace the card."
    ::= { tmnxOesHwNotifications 22 }

tmnxOesCardDegraded              NOTIFICATION-TYPE
    OBJECTS {
        tmnxHwClass
    }
    STATUS      current
    DESCRIPTION
        "[CAUSE] The tmnxOesCardDegraded notification is generated when a fault
         on the card has caused the system to declare a hardware failure.
         This condition may be declared due to a failure in the SEEP or
         another hardware failure, depending on the card type the alarm is
         raised against.

         [EFFECT] The tmnxOesCardDegraded alarm indicates a lower priority
         fault on the card that does not directly affect the traffic
         currently flowing through the device.

         [RECOVERY] First attempt a soft reset of the card. If the card has
         rebooted and the condition does not clear, then try a hard reset of
         the card. If the card has rebooted and the condition does not clear,
         then remove the card and re-insert it to see if the condition clears.
         If the condition remains, then replace the card and follow the return
         and repair process for the problem card."
    ::= { tmnxOesHwNotifications 23 }

tmnxOesFanSpeedHigh              NOTIFICATION-TYPE
    OBJECTS {
        tmnxHwClass
    }
    STATUS      current
    DESCRIPTION
        "[CAUSE] The tmnxOesFanSpeedHigh notification is generated when the fan
         speed is too high, based upon the current shelf cooling requirements.

         [EFFECT] The fans run faster than required.

         [RECOVERY] Remove and re-insert the fan tray into the chassis. If the
         alarm does not clear then replace the fan tray."
    ::= { tmnxOesHwNotifications 24 }

tmnxOesFanSpeedHighClear         NOTIFICATION-TYPE
    OBJECTS {
        tmnxHwClass
    }
    STATUS      current
    DESCRIPTION
        "[CAUSE] The tmnxOesFanSpeedHighClear notification is generated when
         the conditions causing a tmnxOesFanSpeedHigh notification have been
         cleared. Fan speed has returned to acceptable conditions.

         [EFFECT] The fan speed is normal.

         [RECOVERY] No recovery is required."
    ::= { tmnxOesHwNotifications 25 }

    tmnxOesFanSpeedLow           NOTIFICATION-TYPE
    OBJECTS {
        tmnxHwClass
    }
    STATUS      current
    DESCRIPTION
    "[CAUSE] The tmnxOesFanSpeedLow notification is generated when the fan
    speed is too low, based upon the current shelf cooling requirements.

    [EFFECT] The fans run slower than required.

    [RECOVERY] Check for airflow blockage or a dirty filter, and clear.
    If no problems are found, replace the fan tray."
    ::= { tmnxOesHwNotifications 26 }

    tmnxOesFanSpeedLowClear      NOTIFICATION-TYPE
    OBJECTS {
        tmnxHwClass
    }
    STATUS      current
    DESCRIPTION
    "[CAUSE] The tmnxOesFanSpeedLowClear notification is generated when the
    conditions causing a tmnxOesFanSpeedLow notification have been cleared.
    Fan speed has returned to acceptable conditions.

    [EFFECT] The fan speed is normal.

    [RECOVERY]  No recovery is required."

    ::= { tmnxOesHwNotifications 27 }

tmnxOesTempLow                   NOTIFICATION-TYPE
    OBJECTS {
        tmnxHwClass
    }
    STATUS      current
    DESCRIPTION
        "[CAUSE] The tmnxOesTempLow notification is generated when the card
         has detected its temperature is below operational limits.

         [EFFECT] The card performance may degrade or may not work as expected.

         [RECOVERY] Ensure that no environmental issues exist where the network
         element resides. Resolve any existing issues."
    ::= { tmnxOesHwNotifications 28 }

    tmnxOesTempLowClear          NOTIFICATION-TYPE
    OBJECTS {
        tmnxHwClass
    }
    STATUS      current
    DESCRIPTION
        "[CAUSE] The tmnxOesFanSpeedLowClear notification is generated when the
         card has indicated its temperature is within operational limits.

         [EFFECT] The card resumes normal operation state.

         [RECOVERY] No recovery is required."

    ::= { tmnxOesHwNotifications 29 }

tmnxOesRedundancyFail            NOTIFICATION-TYPE
    OBJECTS {
        tmnxHwClass
    }
    STATUS      current
    DESCRIPTION
        "[CAUSE] The tmnxOesRedundancyFail notification is generated when the
         inactive equipment controller card in the OES is not providing
         redundancy protection. In some cases this is a transitory alarm that
         occurs as redundant Equipment Controllers discover one another and
         synchronize. Typical causes for the persistence of this alarm are:
           1) Irreconcilable database schemas.
           2) Inability to support system timing.
           3) System timing is compromised. The inactive controller system
              timing module is not reporting the same status as the active
              controller or is reporting an error that the active controller
              does not have.
           4) Subshelf link missing.
         Reasons that are generally transitory are:
           1) Database not yet fully synchronized.
           2) Software loads are not yet synchronized.
         Some or all of these may apply when the alarm is raised.

         [EFFECT] The OES is not protected against failure of the active
         Equipment Controller.

         [RECOVERY] Check for the Redundancy demerit in the detailed information
         of the chassis indicated."

    ::= { tmnxOesHwNotifications 30 }

tmnxOesRedundancyReady           NOTIFICATION-TYPE
    OBJECTS {
        tmnxHwClass
    }
    STATUS      current
    DESCRIPTION
        "[CAUSE] The tmnxOesRedundancyReady notification is generated when the
         equipment controller cards in the indicated OES chassis are providing
         redundant protection. The equipment controller cards are synchronized.

         [EFFECT] The equipment controller cards are synchronized.

         [RECOVERY] No recovery is required."

    ::= { tmnxOesHwNotifications 31 }

tmnxOesCardFirmwareErr              NOTIFICATION-TYPE
    OBJECTS {
        tmnxHwClass
    }
    STATUS      current
    DESCRIPTION
        "[CAUSE] The tmnxOesCardFirmwareErr is raised when
         the device installed in the shelf has an EEPROM that does not contain
         the correct or recognizable information.

         [EFFECT] The card may demonstrate other alarms due to this condition.

         [RECOVERY] Replace the card."

    ::= { tmnxOesHwNotifications 33 }


--%%%%%%%%%%%%%%%%%%%%%%%%%%%%%%%%%%%%%%%%%%%%%%%%%%%%%%%%%%%%%%%%%%%%%%%%%%%
--
--  TIMETRA-OES-HARDWARE-MIB Compliance Statements
--
tmnxOesHwV14v0Compliance         MODULE-COMPLIANCE
    STATUS      current
    DESCRIPTION
        "The compliance statement for management of OES
         on Nokia SROS series systems for release 14.0."
    MODULE -- this module
        MANDATORY-GROUPS {
            tmnxOesHwGroupV14v0,
            tmnxOesHwNotifyObjsGroupV14v0,
            tmnxOesHwNotificationGroupV14v0
        }
    ::= { tmnxOesHwCompliances 1 }

--%%%%%%%%%%%%%%%%%%%%%%%%%%%%%%%%%%%%%%%%%%%%%%%%%%%%%%%%%%%%%%%%%%%%%%%%%%%
--
--  TIMETRA-OES-HARDWARE-MIB Group Statements
--
tmnxOesHwV14v0Groups OBJECT IDENTIFIER ::= { tmnxOesHwGroups 1 }

tmnxOesHwGroupV14v0              OBJECT-GROUP
    OBJECTS {
        tmnxOesChassisRowLastChanged,
        tmnxOesChassisRowStatus,
        tmnxOesChassisTypeName,
        tmnxOesChassisTypeDescription,
        tmnxOesChassisTypeStatus,
        tmnxOesChassisLastChange,
        tmnxOesChassisAssignedType,
        tmnxOesChassisEquippedType,
        tmnxOesChassisActivitySwitch,
        tmnxOesChassisHwEntryIndex,
        tmnxOesPFType,
        tmnxOesPFAmpRating,
        tmnxOesPFInputCurrent,
        tmnxOesPFInputVoltage,
        tmnxOesPFInputPower,
        tmnxOesPFClkA,
        tmnxOesPFClkB,
        tmnxOesPFClkDelta,
        tmnxOesPFState,
        tmnxOesPFHwIndex,
        tmnxOesFanLastChg,
        tmnxOesFanState,
        tmnxOesFanSpeedControl,
        tmnxOesFanHwIndex,
        tmnxOesCardTypeName,
        tmnxOesCardTypeDescription,
        tmnxOesCardTypeStatus,
        tmnxOesCardTypeHeight,
        tmnxOesCardTypeWidth,
        tmnxOesCardTypeNumPorts,
        tmnxOesCardLastChange,
        tmnxOesCardAssignedType,
        tmnxOesCardEquippedType,
        tmnxOesCardSupportedTypes,
        tmnxOesCardReboot,
        tmnxOesCardHwEntryIndex,
        tmnxOesCardRowLastChanged,
        tmnxOesCardMemorySize,
        tmnxOesControlCardActState,
        tmnxOesControlCardHwIndex,
        tmnxOesCmnEqpPortCardType,
        tmnxOesCmnEqpPortOperStatus,
        tmnxOesCmnEqpPortTypeDescr,
        tmnxOesCmnEqpPortTypeName
    }
    STATUS      current
    DESCRIPTION
        "The group of objects supporting management of OES on Nokia
         SROS series systems in release 14.0."
    ::= { tmnxOesHwV14v0Groups 1 }

tmnxOesHwNotifyObjsGroupV14v0    OBJECT-GROUP
    OBJECTS {
        tmnxOesNotifyFailureReason,
        tmnxOesPortNotifyError
    }
    STATUS      current
    DESCRIPTION
        "The group of objects supporting OES notifications on Nokia
         SROS series systems in release 14.0."
    ::= { tmnxOesHwV14v0Groups 2 }

tmnxOesHwNotificationGroupV14v0  NOTIFICATION-GROUP
    NOTIFICATIONS {
        tmnxOesCtlCardPortDown,
        tmnxOesCtlCardPortUp,
        tmnxOesUsrpnlPortDown,
        tmnxOesUsrpnlPortUp,
        tmnxOesFanRemoved,
        tmnxOesFanInserted,
        tmnxOesFan32HReqd,
        tmnxOesFan32HReqdClear,
        tmnxOesFanFailure,
        tmnxOesFanFailureClear,
        tmnxOesPowerSupplyRemoved,
        tmnxOesPowerSupplyInserted,
        tmnxOesPowerSupplyFailure,
        tmnxOesPowerSupplyFailureClear,
        tmnxOesPortError,
        tmnxOesPortErrorClear,
        tmnxOesCtlCardActivityChange,
        tmnxOesFpgaFail,
        tmnxOesFpgaFailClear,
        tmnxOesFpgaTimeout,
        tmnxOesFpgaTimeoutClear,
        tmnxOesOptTrnspndrMiscFail,
        tmnxOesCardDegraded,
        tmnxOesFanSpeedHigh,
        tmnxOesFanSpeedHighClear,
        tmnxOesFanSpeedLow,
        tmnxOesFanSpeedLowClear,
        tmnxOesRedundancyFail,
        tmnxOesRedundancyReady,
        tmnxOesCardFirmwareErr,
        tmnxOesTempLow,
        tmnxOesTempLowClear
    }
    STATUS      current
    DESCRIPTION
        "The group of notifications supporting the OES hardware
         capabilities on Nokia SROS series systems in release 14.0."
    ::= { tmnxOesHwV14v0Groups 3 }

END -- DEFINITION OF TIMETRA-OES-HARDWARE-MIB
