TIMETRA-SAS-LOG-MIB DEFINITIONS ::= BEGIN

IMPORTS
        MODULE-IDENTITY, OBJECT-TYPE, NOTIFICATION-TYPE,
        Unsigned32, Integer32, IpAddress, Counter32, Counter64
            FROM SNMPv2-SMI

        MODULE-COMPLIANCE, OBJECT-GROUP, NOTIFICATION-GROUP
            FROM SNMPv2-CONF

        TEXTUAL-CONVENTION, RowStatus, StorageType, TruthValue,
        DateAndTime, DisplayString, TimeStamp
            FROM SNMPv2-TC

        sysDescr, sysObjectID
            FROM SNMPv2-MIB

        SnmpMessageProcessingModel, SnmpSecurityLevel, SnmpAdminString
            FROM SNMP-FRAMEWORK-MIB

        snmpNotifyEntry
            FROM SNMP-NOTIFICATION-MIB

        InetAddressType, InetAddress
            FROM INET-ADDRESS-MIB

        TItemDescription, TNamedItemOrEmpty, TNamedItem,
        TmnxAdminState, TmnxOperState, TmnxActionType,
        TQueueId, THsmdaCounterIdOrZero, TmnxAccPlcyQICounters,
        TmnxAccPlcyQECounters, TmnxAccPlcyOICounters, TmnxAccPlcyOECounters,
        TmnxAccPlcyAACounters, THsmdaCounterIdOrZeroOrAll, TQueueIdOrAll
            FROM TIMETRA-TC-MIB

        timetraSRMIBModules, tmnxSRObjs, tmnxSRConfs,
        tmnxSRNotifyPrefix
            FROM TIMETRA-GLOBAL-MIB

        timetraSASObjs, timetraSASNotifyPrefix,
        timetraSASConfs, timetraSASModules
            FROM TIMETRA-SAS-GLOBAL-MIB

        tmnxSnmpTrapDestEntry, TmnxLogIdIndex, tmnxLogApEntry
            FROM TIMETRA-LOG-MIB

        TFilterAction, TFilterActionOrDefault
            FROM TIMETRA-FILTER-MIB
        ;

timetraSASLogMIBModule MODULE-IDENTITY
        LAST-UPDATED    "1108010000Z"
        ORGANIZATION    "Alcatel"
        CONTACT-INFO
            "Alcatel 7210 Support
             Web: http://www.alcatel.com/comps/pages/carrier_support.jhtml"
        DESCRIPTION
        "This document is the SNMP MIB module to manage and provision the
        Alcatel 7210 Logging utility.

        Copyright 2003-2012 Alcatel-Lucent.  All rights reserved.
        Reproduction of this document is authorized on the condition that
        the foregoing copyright notice is included.

        This SNMP MIB module (Specification) embodies Alcatel's
        proprietary intellectual property.  Alcatel retains
        all title and ownership in the Specification, including any
        revisions.

        Alcatel grants all interested parties a non-exclusive
        license to use and distribute an unmodified copy of this
        Specification in connection with management of Alcatel
        products, and without fee, provided this copyright notice and
        license appear on all copies.

        This Specification is supplied 'as is', and Alcatel
        makes no warranty, either express or implied, as to the use,
        operation, condition, or performance of the Specification."
--
--  Revision History
--
        REVISION        "1108010000Z"
        DESCRIPTION     "Rev 1.0                01 Aug 2011 00:00
                         1.0 release of the TIMETRA-SAS-LOG-MIB."

        ::= { timetraSASModules 14 }


--%%%%%%%%%%%%%%%%%%%%%%%%%%%%%%%%%%%%%%%%%%%%%%%%%%%%%%%%%%%%%%%%%%%%%%
--
--
tmnxSASLogObjs             OBJECT IDENTIFIER ::= { timetraSASObjs 14 }
  tmnxSASLogGlobObjs             OBJECT IDENTIFIER ::= { tmnxSASLogObjs 1 }

tmnxSASLogConformance OBJECT IDENTIFIER ::= { timetraSASConfs 9 }
 tmnxSASLogGroups OBJECT IDENTIFIER ::= { tmnxSASLogConformance 1 }

TLogMemSize ::= TEXTUAL-CONVENTION
   STATUS       current
   DESCRIPTION
      "The amount of buffer space (in kbytes) indicating
        the size of the log memory"
   SYNTAX       Integer32 (0..128)

tmnxDygGaspPriLogId OBJECT-TYPE
    SYNTAX       INTEGER (0..100)
    MAX-ACCESS   read-write
    STATUS       current
    DESCRIPTION
        "Primary SNMP trap group number to which dying gasp
        trap needs to be sent. An entry with this id and
        tmnxDygGaspPriTgtName has to exist in
        tmnxSnmpTrapDestEntry before  tmnxDygGaspPriLogId
        can be set"
    DEFVAL  { 0 }
    ::= { tmnxSASLogGlobObjs 1 }

tmnxDygGaspPriTgtName OBJECT-TYPE
    SYNTAX       SnmpAdminString (SIZE(0..28))
    MAX-ACCESS   read-write
    STATUS       current
    DESCRIPTION
        "Primary SNMP trap target to which dying gasp
        trap needs to be sent. An entry with this name and
        tmnxDygGaspPriLogId has to exist in
        tmnxSnmpTrapDestEntry before  tmnxDygGaspPriTgtName
        can be set"
    DEFVAL { "" }
    ::= { tmnxSASLogGlobObjs 2 }

tmnxDygGaspSecLogId OBJECT-TYPE
    SYNTAX       INTEGER (0..100)
    MAX-ACCESS   read-write
    STATUS       current
    DESCRIPTION
        "Secondary SNMP trap group number to which dying gasp
        trap needs to be sent. An entry with this id and
        tmnxDygGaspSecTgtName has to exist in
        tmnxSnmpTrapDestEntry before  tmnxDygGaspSecLogId
        can be set"
    DEFVAL  { 0 }
    ::= { tmnxSASLogGlobObjs 3 }

tmnxDygGaspSecTgtName OBJECT-TYPE
    SYNTAX       SnmpAdminString (SIZE(0..28))
    MAX-ACCESS   read-write
    STATUS       current
    DESCRIPTION
        "Secondary SNMP trap target to which dying gasp
        trap needs to be sent. An entry with this name and
        tmnxDygGaspSecLogId has to exist in
        tmnxSnmpTrapDestEntry before  tmnxDygGaspSecTgtName
        can be set"
    DEFVAL { "" }
    ::= { tmnxSASLogGlobObjs 4 }

tmnxDygGaspTerLogId OBJECT-TYPE
    SYNTAX       INTEGER (0..100)
    MAX-ACCESS   read-write
    STATUS       current
    DESCRIPTION
        "Tertiary SNMP trap group number to which dying gasp
        trap needs to be sent. An entry with this id and
        tmnxDygGaspSecTgtName has to exist in
        tmnxSnmpTrapDestEntry before  tmnxDygGaspTerLogId
        can be set"
    DEFVAL  { 0 }
    ::= { tmnxSASLogGlobObjs 5 }

tmnxDygGaspTerTgtName OBJECT-TYPE
    SYNTAX       SnmpAdminString (SIZE(0..28))
    MAX-ACCESS   read-write
    STATUS       current
    DESCRIPTION
        "Tertiary SNMP trap target to which dying gasp
        trap needs to be sent. An entry with this name and
        tmnxDygGaspTerLogId has to exist in
        tmnxSnmpTrapDestEntry before  tmnxDygGaspTerTgtName
        can be set"
    DEFVAL { "" }
    ::= { tmnxSASLogGlobObjs 6 }

tmnxLogApExtnTable OBJECT-TYPE
    SYNTAX       SEQUENCE OF TmnxLogApExtnEntry
    MAX-ACCESS   not-accessible
    STATUS       current
    DESCRIPTION
        ""
    ::= { tmnxSASLogGlobObjs 7 }

tmnxLogApExtnEntry OBJECT-TYPE
    SYNTAX       TmnxLogApExtnEntry
    MAX-ACCESS   not-accessible
    STATUS       current
    DESCRIPTION
        ""
    AUGMENTS {tmnxLogApEntry}
    ::= { tmnxLogApExtnTable 1 }

TmnxLogApExtnEntry ::=
    SEQUENCE {
      tmnxLogApLogMemory         TruthValue,
      tmnxLogApLogMemSize       TLogMemSize
    }

 tmnxLogApLogMemory       OBJECT-TYPE
    SYNTAX      TruthValue
    MAX-ACCESS  read-create
    STATUS      current
    DESCRIPTION
        "This parameter specifies if Accounting record policy
         records are cached in order to reduce frequent flash write operations "
    DEFVAL { false }
    ::= { tmnxLogApExtnEntry 1 }

 tmnxLogApLogMemSize       OBJECT-TYPE
    SYNTAX      TLogMemSize
    MAX-ACCESS  read-only
    STATUS      current
    DESCRIPTION
        "This parameter is a read only object specifying the log memory size
          that is currently in use"
    ::= { tmnxLogApExtnEntry 2 }

END
