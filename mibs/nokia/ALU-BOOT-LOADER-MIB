ALU-BOOT-LOADER-MIB DEFINITIONS ::= BEGIN

IMPORTS
        MODULE-IDENTITY, OBJECT-TYPE,
        NOTIFICATION-TYPE            FROM SNMPv2-SMI
        MODULE-COMPLIANCE, OBJECT-GROUP,
        NOTIFICATION-GROUP           FROM SNMPv2-CONF
        DisplayString                FROM SNMPv2-TC
        aluSARMIBModules, aluSARConfs
                                     FROM ALU-SAR-GLOBAL-MIB
        aluCardObjs,
        aluChassisNotification       FROM ALU-CHASSIS-MIB

        ;

aluBootLoaderMIBModule MODULE-IDENTITY
        LAST-UPDATED "1406020000Z"
        ORGANIZATION    "Nokia"
        CONTACT-INFO
            "Nokia 7705 Support
             Web: http://www.nokia.com/comps/pages/carrier_support.jhtml"
        DESCRIPTION
        "This document is the SNMP MIB module to manage and provision the
        boot.ldr of the Nokia 7705 device.

        Copyright 2003-2014 Nokia.  All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."

--
--  Revision History
--
        REVISION        "1406020000Z" -- 2 June 2014 00:00
        DESCRIPTION     "Rev 1.0                2 June 2014 00:00
                         1.0 release of the ALU-BOOT-LOADER-MIB."
        ::= { aluSARMIBModules 17 }

aluBootLoaderMIBConformance    OBJECT IDENTIFIER ::= { aluSARConfs 27 }

aluBootLoaderUpdateFile OBJECT-TYPE
        SYNTAX      DisplayString (SIZE (0..180))
        MAX-ACCESS  read-write
        STATUS      current
        DESCRIPTION
            "The value of aluBootLoaderUpdateFile specifies the location and
             name of the new boot loader file to which the system may be updated."
        DEFVAL { ''H }
        ::= { aluCardObjs 1 }

aluBootLoaderForceUpdateFile OBJECT-TYPE
        SYNTAX      DisplayString (SIZE (0..180))
        MAX-ACCESS  read-write
        STATUS      current
        DESCRIPTION
            "The value of aluBootLoaderUpdateFile specifies the location and
             name of the new boot loader file to which the system will be updated.
             This variant provides no safeguard against corruption of the boot loader
             and is not recommended."
        DEFVAL { ''H }
        ::= { aluCardObjs 2 }

aluBootLoaderUpdateResultMessage OBJECT-TYPE
        SYNTAX      DisplayString (SIZE (0..180))
        MAX-ACCESS  read-only
        STATUS      current
        DESCRIPTION
            "The last result of setting aluBootLoaderUpdateFile or aluBootLoaderForceUpdateFile."
        DEFVAL { ''H }
        ::= { aluCardObjs 3}

aluBootLoaderUpdateResult   NOTIFICATION-TYPE
        OBJECTS {
            aluBootLoaderUpdateResultMessage
        }
        STATUS  current
        DESCRIPTION
            "The aluBootLoaderUpdateResult notification is
            generated in response to either an aluBootLoaderUpdateFile or
            aluBootLoaderForceUpdateFile, and the operation has completed
            (successfully or not)."
        ::= { aluChassisNotification 18 }

aluBootLoaderMIBCompliances OBJECT IDENTIFIER ::= { aluBootLoaderMIBConformance 1}
aluBootLoaderMIBGroups      OBJECT IDENTIFIER ::= { aluBootLoaderMIBConformance 2}

aluBootLoader7705V6v2Compliance MODULE-COMPLIANCE
        STATUS current
        DESCRIPTION
            "The compliance statement for management of boot loader update features on
             Nokia 7705 SAR series systems."
        MODULE
            MANDATORY-GROUPS {
                aluBootLoaderGroup,
                aluBootLoaderNotificationGroup
            }
        ::= { aluBootLoaderMIBCompliances 1 }

aluBootLoaderGroup OBJECT-GROUP
        OBJECTS {
            aluBootLoaderForceUpdateFile,
            aluBootLoaderUpdateFile,
            aluBootLoaderUpdateResultMessage
        }
        STATUS    current
        DESCRIPTION
            "The group of objects supporting the boot loader update feature capabilities
             on Nokia 7705 SAR series systems."
        ::= { aluBootLoaderMIBGroups 1 }

aluBootLoaderNotificationGroup NOTIFICATION-GROUP
        NOTIFICATIONS {
            aluBootLoaderUpdateResult
        }
        STATUS    current
        DESCRIPTION
            "The group of notifications use in the boot loader update feature on
             Nokia 705 SAR series systems."
        ::= { aluBootLoaderMIBGroups 2 }
END
