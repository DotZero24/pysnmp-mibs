TIMETRA-SAS-VRTR-MIB DEFINITIONS ::= BEGIN

IMPORTS
        MODULE-IDENTITY, OBJECT-TYPE,
        NOTIFICATION-TYPE,
        Unsigned32, IpAddress, Counter64,
        Integer32,  Gauge32, Counter32          FROM SNMPv2-SMI

        MODULE-COMPLIANCE, OBJECT-GROUP,
        NOTIFICATION-GROUP                      FROM SNMPv2-CONF

        TEXTUAL-CONVENTION, DisplayString,
        RowStatus, TruthValue, MacAddress,
        TimeStamp, TestAndIncr                  FROM SNMPv2-TC

        vRtrIfEntry, vRtrIfIndex, vRtrID,
        vRtrConfEntry, vRtrStatEntry,
        vRtrIfBfdSessExtLclDisc,
        vRtrMaxRoutesType
                                                FROM TIMETRA-VRTR-MIB

        TNetworkIngressMeterId,
        TMplsLspExpProfMapID                    FROM TN-TC-MIB

        timetraSASObjs, timetraSASNotifyPrefix,
        timetraSASConfs, timetraSASModules      FROM TIMETRA-SAS-GLOBAL-MIB
        ;

timetraSASVRtrMIBModule MODULE-IDENTITY
        LAST-UPDATED    "0901010000Z"
        ORGANIZATION    "Alcatel"
        CONTACT-INFO
            "Alcatel 7x50 Support
             Web: http://www.alcatel.com/comps/pages/carrier_support.jhtml"
        DESCRIPTION
            "This document  is the SNMP MIB  module to manage and provision
             the  Alcatel  7x50 device transport and virtual routers, their
             interfaces, and other related features.

             Copyright 2009-2014 Alcatel-Lucent. All rights reserved.
             Reproduction of  this document is authorized  on the condition
             that the foregoing copyright notice is included.

             This   SNMP  MIB  module  (Specification)  embodies  Alcatel's
             proprietary  intellectual  property. Alcatel retains all title
             and ownership in the Specification, including any revisions.

             Alcatel  grants all interested parties a non-exclusive license
             to use and distribute an unmodified copy of this Specification
             in connection with management of Alcatel products, and without
             fee,  provided this copyright notice and license appear on all
             copies.

             This  Specification  is supplied `as is', and Alcatel makes no
             warranty, either express or implied, as to the use, operation,
             condition, or performance of the Specification."

--
--  Revision History
--
        REVISION        "0901010000Z"
        DESCRIPTION     "Rev 1.0                01 Jan 2009 00:00
                         1.0 release of the TIMETRA-SAS-VRTR-MIB."

        ::= { timetraSASModules 8 }

tSASVRtrObjects                  OBJECT IDENTIFIER ::= { timetraSASObjs 7 }

vRtrIfExtnTable  OBJECT-TYPE
    SYNTAX      SEQUENCE OF VRtrIfExtnEntry
    MAX-ACCESS  not-accessible
    STATUS      current
    DESCRIPTION
        "The 'rtrIfTable' has an entry for each router interface configured in
         the system."
    ::= { tSASVRtrObjects 1 }

vRtrIfExtnEntry  OBJECT-TYPE
    SYNTAX      VRtrIfExtnEntry
    MAX-ACCESS  not-accessible
    STATUS      current
    DESCRIPTION
        "Each row entry represents a virtual router interface in the system.
         The objects in this table are addtions to the vRtrIfTable"
        AUGMENTS { vRtrIfEntry }
        ::= { vRtrIfExtnTable 1 }

VRtrIfExtnEntry ::=
    SEQUENCE {
      vRtrIfAcctPolicyId         Unsigned32,
      vRtrIfCollectStats         TruthValue
    }

vRtrIfAcctPolicyId  OBJECT-TYPE
    SYNTAX      Unsigned32 (0..99)
    MAX-ACCESS  read-write
    STATUS      current
    DESCRIPTION
        "The value of the accounting policy must be defined prior to associating
         the policy with this router interface.

         A non-zero value indicates the tmnxLogApPolicyId index identifying the
         policy entry in the tmnxLogApTable from the TIMETRA-LOG-MIB which is
         associated with this interface.  A zero value indicates that there is
         no accounting policy associated with this interface"
    DEFVAL { 0 }
    ::= { vRtrIfExtnEntry 1 }

vRtrIfCollectStats  OBJECT-TYPE
    SYNTAX      TruthValue
    MAX-ACCESS  read-write
    STATUS      current
    DESCRIPTION
        "Enable/disable the collection of accounting and statistical data
         for this router interface. When applying accounting policies the
         data by default will be collected in the appropriate records and
         written to the designated billing file.
         When the value is set to false, the statistics are still accumulated
         by the IOM cards, however, the CPU will not obtain the results and
         write them to the billing file."
    DEFVAL { false }
    ::= { vRtrIfExtnEntry 2 }

vRtrNetIfIngressStatsTable  OBJECT-TYPE
    SYNTAX      SEQUENCE OF VRtrNetIfIngressStatsEntry
    MAX-ACCESS  not-accessible
    STATUS      current
    DESCRIPTION
        "The vRtrNetIfIngressStatsTable has statistics entry for each router interface
        for each meter configured in the system."
    ::= { tSASVRtrObjects 2 }

vRtrNetIfIngressStatsEntry  OBJECT-TYPE
    SYNTAX      VRtrNetIfIngressStatsEntry
    MAX-ACCESS  not-accessible
    STATUS      current
    DESCRIPTION
        "Each row entry has statistics information for each router interface
        for each meter configured in the system."
    INDEX { vRtrID, vRtrIfIndex, vRtrNetIfIngressMeterIndex }
        ::= { vRtrNetIfIngressStatsTable 1 }

VRtrNetIfIngressStatsEntry ::=
    SEQUENCE {
      vRtrNetIfIngressMeterIndex      TNetworkIngressMeterId,
      vRtrNetIfIngressFwdInProfPkts   Counter64,
      vRtrNetIfIngressFwdOutProfPkts  Counter64,
      vRtrNetIfIngressFwdInProfOcts   Counter64,
      vRtrNetIfIngressFwdOutProfOcts  Counter64
    }

vRtrNetIfIngressMeterIndex OBJECT-TYPE
    SYNTAX      TNetworkIngressMeterId
    MAX-ACCESS  not-accessible
    STATUS      current
    DESCRIPTION
        "vRtrNetIfIngressMeterIndex serves as the tertiary index. When used
         in conjunction with vRtrID and vRtrIfIndex, it uniquely identifies
         a network ingress meter for the specified router interface in the
         managed system."
    ::= { vRtrNetIfIngressStatsEntry 1 }

vRtrNetIfIngressFwdInProfPkts   OBJECT-TYPE
    SYNTAX      Counter64
    MAX-ACCESS  read-only
    STATUS      current
    DESCRIPTION
        "vRtrNetIfIngressFwdInProfPkts  indicates the number of conforming
         network interface ingress packets forwarded on this router interface
         using this meter."
    ::= { vRtrNetIfIngressStatsEntry 2 }

vRtrNetIfIngressFwdOutProfPkts OBJECT-TYPE
    SYNTAX      Counter64
    MAX-ACCESS  read-only
    STATUS      current
    DESCRIPTION
        "vRtrNetIfIngressFwdOutProfPkts indicates the number of exceeding
         network interface ingress packets forwarded on this router interface
         using this meter."
    ::= { vRtrNetIfIngressStatsEntry 3 }

vRtrNetIfIngressFwdInProfOcts OBJECT-TYPE
    SYNTAX      Counter64
    MAX-ACCESS  read-only
    STATUS      current
    DESCRIPTION
        "vRtrNetIfIngressFwdInProfOcts indicates the number of conforming
         network interface ingress octets forwarded on this router interface
         using this meter."
    ::= { vRtrNetIfIngressStatsEntry 4 }

vRtrNetIfIngressFwdOutProfOcts OBJECT-TYPE
    SYNTAX      Counter64
    MAX-ACCESS  read-only
    STATUS      current
    DESCRIPTION
        "vRtrNetIfIngressFwdOutProfOcts indicates the number of exceeding
         network interface ingress octets forwarded on this router interface
         using this meter."
    ::= { vRtrNetIfIngressStatsEntry 5 }

vRtrConfExtnTable  OBJECT-TYPE
    SYNTAX      SEQUENCE OF VRtrConfExtnEntry
    MAX-ACCESS  not-accessible
    STATUS      current
    DESCRIPTION
        "The 'rtrIfTable' has an entry for each router interface configured in
         the system."
    ::= { tSASVRtrObjects 4 }

vRtrConfExtnEntry  OBJECT-TYPE
    SYNTAX      VRtrConfExtnEntry
    MAX-ACCESS  not-accessible
    STATUS      current
    DESCRIPTION
        "Each row entry represents a virtual router interface in the system.
         The objects in this table are addtions to the vRtrConfTable"
    AUGMENTS { vRtrConfEntry }
        ::= { vRtrConfExtnTable 1 }

VRtrConfExtnEntry ::=
    SEQUENCE {
      vRtrMaxNumRouteDests         Integer32
    }

vRtrMaxNumRouteDests OBJECT-TYPE
    SYNTAX      Integer32 (-1..'7FFFFFFF'h)
    MAX-ACCESS  read-only
    STATUS      current
    DESCRIPTION
        "The maximum number of route destinations that supported on
         this virtual router. If the value is -1, then there is no limit."
    DEFVAL { -1 }
    ::= { vRtrConfExtnEntry 1 }

vRtrStatExtnTable  OBJECT-TYPE
    SYNTAX      SEQUENCE OF VRtrStatExtnEntry
    MAX-ACCESS  not-accessible
    STATUS      current
    DESCRIPTION
        "The 'rtrIfTable' has an entry for each router interface configured in
         the system."
    ::= { tSASVRtrObjects 5 }

vRtrStatExtnEntry  OBJECT-TYPE
    SYNTAX      VRtrStatExtnEntry
    MAX-ACCESS  not-accessible
    STATUS      current
    DESCRIPTION
        "Each row entry represents a virtual router interface in the system.
         The objects in this table are addition to the vRtrStatTable"
    AUGMENTS { vRtrStatEntry }
        ::= { vRtrStatExtnTable 1 }

VRtrStatExtnEntry ::=
    SEQUENCE {
      vRtrStatCurrNumRouteDests    Gauge32
    }

vRtrStatCurrNumRouteDests  OBJECT-TYPE
    SYNTAX      Gauge32
    MAX-ACCESS  read-only
    STATUS      current
    DESCRIPTION
        "vRtrStatCurrNumRouteDests indicates the current number of route
         destionations in the VRF for this virtual router."
    ::= { vRtrStatExtnEntry 1 }

tmnxSASVRtrNotifications OBJECT IDENTIFIER ::= { tSASVRtrObjects 20 }

tmnxVRtrMaxRouteDests    NOTIFICATION-TYPE
    OBJECTS {
        vRtrStatCurrNumRouteDests,
        vRtrMaxNumRouteDests,
        vRtrMaxRoutesType
    }
    STATUS          current
    DESCRIPTION
        "The tmnxVRtrMaxRouteDests notification is generated when the number of
         routes of type vRtrMaxRoutesType contained in a VPRN reaches the value
         specified by vRtrMaxNumRouteDests."
    ::= { tmnxSASVRtrNotifications 1 }

tmnxVRtrBfdNoBfdHashResources NOTIFICATION-TYPE
    OBJECTS {
        vRtrIfBfdSessExtLclDisc
    }
    STATUS          current
    DESCRIPTION
        "The tmnxVRtrBfdNoBfdHashResources notification is generated when a BFD
         session could not be established because the session requires a Bfd Hash
         session termination resource and no resources are available."
    ::= { tmnxSASVRtrNotifications 2 }

tmnxVRtrBfdNoIomHwResources NOTIFICATION-TYPE
    OBJECTS {
        vRtrIfBfdSessExtLclDisc
    }
    STATUS          current
    DESCRIPTION
        "The tmnxVRtrBfdNoIomHwResources notification is generated when a BFD
         session could not be established because the session requires a IOM
         session termination hardware resource and no resources are available."
    ::= { tmnxSASVRtrNotifications 3 }

tmnxSASVRtrGroups      OBJECT IDENTIFIER ::= { timetraSASConfs 11 }

tmnxSASVRtrV1v0Group       OBJECT-GROUP
    OBJECTS {   vRtrIfAcctPolicyId,
                vRtrIfCollectStats,
                vRtrNetIfIngressFwdInProfPkts,
                vRtrNetIfIngressFwdOutProfPkts,
                vRtrNetIfIngressFwdInProfOcts,
                vRtrNetIfIngressFwdOutProfOcts,
                vRtrMaxNumRouteDests,
                vRtrStatCurrNumRouteDests
            }
    STATUS        current
    DESCRIPTION
        "The group of objects supporting management of transport and
         virtual routers on version 1.0 Alcatel 7210 SAS series systems."
    ::= { tmnxSASVRtrGroups 1 }

tmnxSASVrtrNotificationGroup NOTIFICATION-GROUP
    NOTIFICATIONS {
        tmnxVRtrMaxRouteDests
    }
    STATUS    current
    DESCRIPTION
        "The group of notifications supported in 7210 3.0 release"
    ::= { tmnxSASVRtrGroups 2 }

END
