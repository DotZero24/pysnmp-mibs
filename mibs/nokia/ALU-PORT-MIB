ALU-PORT-MIB DEFINITIONS ::= BEGIN

IMPORTS
        MODULE-IDENTITY, OBJECT-TYPE,
        NOTIFICATION-TYPE, Counter64,
        Unsigned32, Integer32, Counter32
                                                FROM SNMPv2-SMI

        MODULE-COMPLIANCE, OBJECT-GROUP,
        NOTIFICATION-GROUP                      FROM SNMPv2-CONF

        TEXTUAL-CONVENTION, TimeStamp,
        TruthValue, RowStatus, DateAndTime,
        DisplayString                           FROM SNMPv2-TC

        TNamedItemOrEmpty, TmnxActionType,
        TItemLongDescription,   TQueueId,
        TmnxPortID, TmnxEnabledDisabled         FROM TIMETRA-TC-MIB

        tmnxDS1PortEntry, tmnxPortPortID,
        tmnxPortEtherEntry, tmnxDS0ChanGroupEntry,
        tmnxPortNotifyPortId, tmnxDS1Entry,
        TmnxDs0ChannelList,
        TmnxDSXIdleFillType, TmnxDSXIdleCycleFlags,
        TmnxDSXClockSource,
        tmnxPortCemStatsEntry,
        tmnxFrIntfEntry, tmnxPortEntry          FROM TIMETRA-PORT-MIB

        tmnxChassisIndex                        FROM TIMETRA-CHASSIS-MIB

        aluSARMIBModules                        FROM ALU-SAR-GLOBAL-MIB

        aluHwObjs, aluHwConformance,
        aluHwNotification                       FROM ALU-CHASSIS-MIB
        frCircuitEntry                          FROM FRAME-RELAY-DTE-MIB

        pethPsePortEntry,
        pethPsePortPowerClassifications,
        pethPsePortDetectionStatus              FROM POWER-ETHERNET-MIB

        dot1xPaePortNumber                     FROM IEEE8021-PAE-MIB
        ;


aluPortMIBModule MODULE-IDENTITY
        LAST-UPDATED    "0809100000Z"
        ORGANIZATION    "Nokia"
        CONTACT-INFO
            "Nokia 7x50 Support
             Web: http://www.nokia.com/comps/pages/carrier_support.jhtml"
        DESCRIPTION
        "This document is the SNMP MIB module to manage and provision the
        hardware components of the Nokia 7x50 device.

        Copyright 2003-2015 Nokia.  All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."

--
--  Revision History
--
        REVISION        "0801090000Z"
        DESCRIPTION     "Rev 1.0                09 Jan 2008 00:00
                         1.0 release of the ALU-PORT-MIB."

        REVISION
            "0809100000Z"        -- 10 Sept 2008 00:00
        DESCRIPTION
            "Rev 1.1.2 for 2.0 release of the ALU-PORT-MIB.
            1) synchonous ethernet support
            2) tdm port ACR statistics"

        ::= { aluSARMIBModules 2 }


aluPortObjs                    OBJECT IDENTIFIER ::= { aluHwObjs 4 }

aluPortNotifyPrefix      OBJECT IDENTIFIER ::= { aluHwNotification 2}
  aluPortNotification      OBJECT IDENTIFIER ::= { aluPortNotifyPrefix 0 }

aluPortNotificationObjects     OBJECT IDENTIFIER ::= { aluHwObjs 7 }
aluPortStatsObjs               OBJECT IDENTIFIER ::= { aluHwObjs 12 }
aluPortConformance              OBJECT IDENTIFIER ::= { aluHwConformance 4 }


--%%%%%%%%%%%%%%%%%%%%%%%%%%%%%%%%%%%%%%%%%%%%%%%%%%%%%%%%%%%%%%%%%%%%%
--
--      ALU-PORT-MIB textual conventions
--

--
--      AluRS232ReportStatus
--
AluRS232ReportStatus ::= TEXTUAL-CONVENTION
    STATUS  current
    DESCRIPTION
        "The AluRS232ReportStatus is a bitmask that describes alarms that
         can be raised/cleared on a Serial Port:
         hcmOof - local HCM out-of-frame errors
         hcmRai - remote HCM alarm indication
         ctrlLeadMon - control lead monitoring is forcing link down
         monClockDev - monitoring of clock deviation is forcing link down
         monDataInac - monitoring of data inactivity is forcing link down
        "
    SYNTAX  BITS {
                notUsed (0),
                hcmOof (1),
                hcmRai (2),
                ctrlLeadMon (3),
                monClockDev (4),
                monDataInac (5)
            }

--
--      AluRS232ControlLead
--
AluRS232ControlLead  ::= TEXTUAL-CONVENTION
    STATUS  current
    DESCRIPTION
        "The programmed setting of a Serial control lead."
    SYNTAX  INTEGER {
                high       (1),
                low        (2),
                end-to-end (3)
            }

--
--      AluVoicePortTlp
--
AluVoicePortTlp ::= TEXTUAL-CONVENTION
    STATUS       current
    DESCRIPTION
       "AluVoicePortTlp is a signed integer that indicates the Transmission
        Level Points level in tenths of decibels.
       "
    SYNTAX       Integer32 (-160..70)

--
--      AluVoiceSignalingLead
--
AluVoiceSignalingLead  ::= TEXTUAL-CONVENTION
    STATUS  current
    DESCRIPTION
        "The programmed setting of a Voice signaling lead."
    SYNTAX  INTEGER {
                notApplicable (0),
                high       (1),
                low        (2),
                end-to-end (3)
            }

--
--      AluDslTpsTcType
--
AluDslTpsTcType  ::= TEXTUAL-CONVENTION
    STATUS  current
    DESCRIPTION
        "The TPS-TC type of an Alu DSL Port or Alu DSL Line."
    SYNTAX      INTEGER {
                none (0),
                atm (4),
                efm (2)
            }

--
--      AluDslAdminState
--
AluDslAdminState ::= TEXTUAL-CONVENTION
    STATUS      current
    DESCRIPTION
        "The desired administrative status of this DSL Line."
    SYNTAX      INTEGER {
                    outOfService (0),
                    inService (1)
                }

--
--      AluDataReportStatus
--
AluDataReportStatus ::= TEXTUAL-CONVENTION
    STATUS  current
    DESCRIPTION
        "The AluDataReportStatus is a bitmask that indicates the type of alarms
         that can be raised/cleared on a Data Port:
         ais - alarm indication signal errors.
         los - loss of signal errors.
         rai - remote alarm indication events.
        "
    SYNTAX  BITS {
                notUsed  (0),
                ais      (1),
                los      (2),
                rai      (3)
            }

--
--      AluRS232ControlLeadMon
--
AluRS232ControlLeadMon  ::= TEXTUAL-CONVENTION
    STATUS  current
    DESCRIPTION
        "The programmed monitor setting of a Serial control lead.

         on        - detected transitions will trigger
                     aluRS232ControlLeadsSignalChange
         off       - disabled; no monitoring performed
         high      - same as 'on' and, control lead transitions to high will
                     be treated as a port fault condition
         low       - same as 'on' and, control lead transitions to low will
                     be treated as a port fault condition
        "
    SYNTAX  INTEGER {
                on         (1),
                off        (2),
                high       (3),
                low        (4)
            }


--%%%%%%%%%%%%%%%%%%%%%%%%%%%%%%%%%%%%%%%%%%%%%%%%%%%%%%%%%%%%%%%%%%%%%
--
--      ALU-PORT-MIB at a glance
--
--  timetra (enterprises 6527)
--    timetraBasedProducts (6)
--        aluServiceAggrRouters (1)
--        aluSARObjects (2)
--            aluSARMIB (1)
--                aluSARConfs (1)
--                aluSARObjs (2)
--                      aluHwObjs (aluSARObjs 2)
--                aluSARNotifyPrefix (3)
--
--  aluPortObjs (aluHwObjs 4)
--        aluExtTmnxDS1PortTable (1)
--        aluExtTmnxPortEtherTable (2)
--        aluExtTmnxDS1Table (3)
--        aluRS232PortTable (4)
--        aluRS232Table (5)
--        aluRS232ChanGroupTable (6)
--        aluVoicePortTable (7)
--        aluVoiceTable (8)
--        aluVoiceChanGroupTable (9)
--        aluGponPortTable (10)
--        aluDslPortTable (11)
--        aluXdslLineTable (12)
--        aluShdslLineTable (13)
--        aluDataPortTable (14)
--        aluDataTable (15)
--        aluDataChanGroupTable (16)
--        aluScadaBridgeTable (20)
--        aluSerialMddbTable(21)
--        aluScadaBranchTable (22)
--        aluPortCfmLbVlanTable (23)
--        aluGnssPortTable (24)
--
--  aluPortNotificationObjects (aluHwObjs 7)
--        aluPortEtherSfpESyncCompatibility (1)
--        aluPortNotifyRS232AlarmReason (2)
--        aluPortNotifyDataAlarmReason (3)
--
--  aluPortStatsObjs (aluHwObjs 12)
--        aluPortDiscardStatsTable (1)
--        aluPortAcrClkStatsTable (2)
--        aluPortAcrClkStatsShortIntervalTable (3)
--        aluPortNetIngressControlStatsTable (4)
--        aluPortNetEgressControlStatsTable (5)
--        aluGponPortCurrentTable (6)
--        aluGponPortPreviousTable (7)
--        aluXdslLineStatsTable (8)
--        aluShdslLineStatsTable (9)
--        aluPortCtlStatsTable  (10)
--        aluFrIfStatsTable(11)
--        aluExtFrCircuitTable(12)
--        aluEthPtpTimestampStatsTable (13)
--        aluPortNetRingAddDropStatsTable (14)
--
--
-- ALU Extensions of Tmnx DS1 Port table
--
aluExtTmnxDS1PortTable OBJECT-TYPE
    SYNTAX      SEQUENCE OF AluExtTmnxDS1PortEntry
    MAX-ACCESS  not-accessible
    STATUS      current
    DESCRIPTION
        "The aluExtTmnxDS1PortTable has an entry for a DS1 physical port."
    ::= { aluPortObjs 1 }

aluExtTmnxDS1PortEntry       OBJECT-TYPE
    SYNTAX      AluExtTmnxDS1PortEntry
    MAX-ACCESS  not-accessible
    STATUS      current
    DESCRIPTION
        "Each row entry represents extended functionality of a physical
         DS1 port on Nokia 7705 SAR devices.  Entries cannot be
         created or deleted via SNMP SET operations.  Entries in this table
         will be created or deleted automatically when entries in the
         tmnxDS1PortTable are created or deleted."
    AUGMENTS  { tmnxDS1PortEntry }
    ::= { aluExtTmnxDS1PortTable 1 }

AluExtTmnxDS1PortEntry ::=
    SEQUENCE {
        aluExtDS1PortLineImpedance        INTEGER,
        aluExtDS1PortLineEncoding         INTEGER
    }

aluExtDS1PortLineImpedance    OBJECT-TYPE
    SYNTAX      INTEGER {
                    notApplicable     (0),
                    impedance75Ohms   (1),
                    impedance100Ohms  (2),
                    impedance120Ohms  (3)
                }
    MAX-ACCESS  read-write
    STATUS      current
    DESCRIPTION
        "The value of aluExtDS1PortLineImpedance indicates the current line
         impedance set on the physical T1/E1 port.

         T1 Ports may only be configured to have an impedance of 100 Ohms.

         E1 Ports may be configured to have an impledance of either 75 or
         120 Ohms where the default impedance is 120 Ohms."
    DEFVAL      { impedance100Ohms }
    ::= { aluExtTmnxDS1PortEntry 1 }

aluExtDS1PortLineEncoding    OBJECT-TYPE
    SYNTAX      INTEGER {
                    notApplicable     (0),
                    b8zs              (1),
                    ami               (2),
                    hdb3              (3)
                }
    MAX-ACCESS  read-write
    STATUS      current
    DESCRIPTION
        "The value of aluExtDS1PortLineEncoding indicates the Zero Code
         Suppression set on the physical T1/E1 port."
    DEFVAL      { b8zs }
    ::= { aluExtTmnxDS1PortEntry 2 }


aluExtTmnxPortEtherTable OBJECT-TYPE
    SYNTAX      SEQUENCE OF AluExtTmnxPortEtherEntry
    MAX-ACCESS  not-accessible
    STATUS      current
    DESCRIPTION
        "The aluExtTmnxPortEtherTable has an entry for each Ethernet port."
    ::= { aluPortObjs 2 }

aluExtTmnxPortEtherEntry       OBJECT-TYPE
    SYNTAX      AluExtTmnxPortEtherEntry
    MAX-ACCESS  not-accessible
    STATUS      current
    DESCRIPTION
        "Each row entry represents extended functionality of a Ethernet port
         on Nokia 7705 SAR devices.  Entries cannot be
         created or deleted via SNMP SET operations.  Entries in this table
         will be created or deleted automatically when entries in the
         tmnxPortEtherTable are created or deleted."
    AUGMENTS  { tmnxPortEtherEntry }
    ::= { aluExtTmnxPortEtherTable 1 }

AluExtTmnxPortEtherEntry ::=
    SEQUENCE {
        aluExtPortEtherSfpSyncEStatus          INTEGER,
        aluExtPortEtherLoopback                INTEGER,
        aluExtPortEtherLoopbackTimer           Unsigned32,
        aluExtPortEtherLoopbackTimeLeft        Unsigned32,
        aluExtPortEtherNwSchedulerMode         INTEGER,
        aluExtPortEtherLoopbackCfmLbMode       INTEGER,
        aluExtPortEtherCfmLbmRx                Counter64,
        aluExtPortEtherCfmLbmDropped           Counter64,
        aluExtPortEtherCfmLbrTx                Counter64,
        aluExtPortEtherLoopbackSwapMacAddr     TruthValue,
        aluExtPortEtherAdminPhyTxClock         INTEGER,
        aluExtPortEtherOperPhyTxClock          INTEGER,
        aluEthPtpTimestampCapable              TruthValue,
        aluEthPtpTimestampEnable               TruthValue,
        aluEthPtpAsymmetry                     Integer32,
        aluExtPortEtherLoopbackPersist         TruthValue,
        aluPortEtherIngressRateCbs             Unsigned32,
        aluPortEtherIngressRateSrcPause        TruthValue,
        aluPortEtherXorMode                    INTEGER,
        aluPortEtherEgrUnshapedSapCir          Integer32,
        aluExtPortEtherVlanFilter              INTEGER,
        aluExtPortEtherCfmLbVlanList           OCTET STRING,
        aluExtPortEtherAccEgrShaper            TNamedItemOrEmpty,
        aluExtPortEtherNetEgrShaper            TNamedItemOrEmpty,
        aluPortEtherEgrUnshapedNwIfCir         Integer32,
        aluExtPortEtherEgrRateIncludeFCS       TruthValue,
        aluPortEtherOperXorMode                INTEGER,
        aluExtPortEtherBnAllowed               TruthValue,
        aluExtPortEtherBnHoldTime              Unsigned32
    }

--
--  Port ESync Status
--
aluExtPortEtherSfpSyncEStatus       OBJECT-TYPE
    SYNTAX      INTEGER {
                    not-applicable (0),
                    capable        (1),
                    incapable      (2)
                }
    MAX-ACCESS  read-only
    STATUS      current
    DESCRIPTION
        "The value of aluExtPortEtherSfpSyncEStatus indicates whether or not
         the SFP installed in the port is capabable of supporting synchronous
         Ethernet (syncE) communications.

         not-applicable - The port does not support an SFP or the SFP is not
                          installed.
         capable        - The SFP installed in the port is capable of supporting
                          synchronous Ethernet operations.
         incapable      - The SFP installed in the port is incapable of supporting
                          synchronous Ethernet operations.

         On MDAs that only support TIMETRA-CHASSIS::tmnxMDASynchronousEthernet
         with a value of 'not-applicable(0)', aluExtPortEtherSfpSyncEStatus
         will be 'not-applicable (0)'."
    DEFVAL { not-applicable }
    ::= { aluExtTmnxPortEtherEntry 1 }


--
--      aluExtPortEtherLoopback
--

aluExtPortEtherLoopback    OBJECT-TYPE
   SYNTAX  INTEGER {
                none (0),
                line (1),
                internal (2)
            }
    MAX-ACCESS  read-write
    STATUS      current
    DESCRIPTION
       "aluExtPortEtherLoopback is used to put an ethernet port into a loopback mode.
        Setting aluExtPortEtherLoopback must be accompanied by setting aluExtPortEtherLoopbackTimer
        for the same port.

        A 'line' loopback loops frames received on this port back to the remote system.
        An 'internal' loopback loops frames from the local system back at the framer.
        Use 'none' to turn off either one of the above loopback mode.

        The Nokia 7705 SAR devices restrict the following interactions:
        - A 'line' loopback is only allowed on ports with aluExtPortEtherLoopbackCfmLbMode set to 'disabled'.
        - An 'internal' loopback is only allowed on ports with tmnxPortMode set to 'access (1)'.
        - aluExtPortEtherLoopback can only be 'none' if dot3OamAdminState of the port is 'enable (2)'.
        - aluExtPortEtherLoopback can only be 'none' if aluExtPortEtherLoopbackCfmLbMode of the port is not 'disabled (0)'. "
    DEFVAL      { none }
    ::= { aluExtTmnxPortEtherEntry 2}

aluExtPortEtherLoopbackTimer    OBJECT-TYPE
    SYNTAX      Unsigned32 (0|30..86400)
    MAX-ACCESS  read-write
    STATUS      current
    DESCRIPTION
        "aluExtPortEtherLoopbackTimer is used to specify the time duration, in seconds, to set the ethernet port
         into a loopback mode.  Setting aluExtPortEtherLoopbackTimer to a non-zero value must be accompanied by
         setting aluExtPortEtherLoopback to either 'line' or 'internal' for the same port.  When this timer expires,
         it will be reset to the default value 0 by the system.

         Set aluExtPortEtherLoopbackTimer to 0 to keep the loopback mode until modified by the operator.

         While setting aluExtPortEtherLoopback to 'line' on a network port, aluExtPortEtherLoopbackTimer CAN NOT be set to 0.
         While setting aluExtPortEtherLoopback on an access port, aluExtPortEtherLoopbackTimer CAN be set to 0.
         While setting aluExtPortEtherLoopback to 'none', aluExtPortEtherLoopbackTimer MUST be set to 0.
         While setting aluExtPortEtherLoopbackPersist to 'true', aluExtPortEtherLoopbackTimer CAN NOT be set to a non-zero value."

    DEFVAL  { 0 }
    ::= { aluExtTmnxPortEtherEntry 3}

aluExtPortEtherLoopbackTimeLeft   OBJECT-TYPE
    SYNTAX      Unsigned32 (0..86400)
    MAX-ACCESS  read-only
    STATUS      current
    DESCRIPTION
        "aluExtPortEtherLoopbackTimeLeft is used to specify the number of seconds left since the loopback has started.
         0 if aluExtPortEtherLoopbackTimer was assigned 0, or when aluExtPortEtherLoopback is 'none'."
    ::= { aluExtTmnxPortEtherEntry 4}

--
--  Port Egress Scheduler Mode
--
aluExtPortEtherNwSchedulerMode    OBJECT-TYPE
    SYNTAX      INTEGER {
                    profile        (0),
                    four-priority  (1),
                    sixteen-priority (2)
                }
    MAX-ACCESS  read-write
    STATUS      current
    DESCRIPTION
         "The value of aluExtPortEtherNwSchedulerMode indicates the mode that the
         egress scheduler is provisioned to operate in.

         profile        - Basic in/out scheduling
         four-priority  - Expedited/Best-Effort plus in/out scheduling
         sixteen-priority  - Straight Priority CIR/EIR scheduling

         The value of aluExtPortEtherNwSchedulerMode is only configurable on network
         ethernet ports.  The port must be shutdown to modify this value.

         MDAs that can support sixteen-priority do not support profile or four-priority mode.
         Thus, when ports are created for these MDAs, aluExtPortEtherNwSchedulerMode of these ports is
         initialized with 'sixteen-priority'."

    DEFVAL { profile }
    ::= { aluExtTmnxPortEtherEntry 5 }

aluExtPortEtherLoopbackCfmLbMode  OBJECT-TYPE
   SYNTAX  INTEGER {
                disabled (0),
                priority-low  (1),
                priority-high (2),
                priority-dot1p (3)
            }
    MAX-ACCESS  read-write
    STATUS      current
    DESCRIPTION
       "aluExtPortEtherLoopbackCfmLbMode is to enable/disable an ethernet port to reply to an ethernet CFM
       Loopback Message (LBM) frame at the port level.  If enabled then it indicates the desired egress QoS
       priority treatment for the CFM Loopback Reply (LBR) frame.

               - disabled        (0) : disables the handling of LBM.
               - priority-low    (1) : enables the handling of LBM by sending LBR using low priority QoS treatment.
               - priority-high   (2) : enables the handling of LBM by sending LBR using high priority QoS treatment.
               - priority-dot1p (3) : enables the handling of LBM classification based on the Dot1p priority.  LBR will be forwarded
                                         to the corresponding egress queues based on the policy configuration.

       When enabled, all imcoming layer 2 LBM's frames (i.e. not encapsulated within any tunnel/services), with
       MAC destination address matched with the port address, will be processed.  An LBR will be generated, in
       reverse direction, back toward the sender.  The LBR's contain the same content as the received LBM's, with
       the exception of the swapping for source and destination MAC addresses, and the CFM op code being set to
       indicate frame type being LBR.

       The Nokia 7705 SAR devices has the following restrictions:
           - Only one port per MDA can have the cfm-loopback enabled at a time.
           - aluExtPortEtherLoopbackCfmLbMode can only be 'disabled' if aluExtPortEtherLoopback is not set to 'none'.
           - aluExtPortEtherLoopbackCfmLbMode can not be changed from one priority to another, i.e. once it is enabled
             to a priority, it can only be modified to 'disabled'.
           - priority-dot1p is allowed only on physical ring ports. CFM LB frames destined to these physical ring ports
             with aluExtPortEtherLoopbackCfmLbMode being priority-dot1p will be processed and replied only if ithey have
             no Vlan tags, or with Vlan tags of Vlan IDs specified by aluExtPortEtherCfmLbVlanList."

    DEFVAL      { disabled }
    ::= { aluExtTmnxPortEtherEntry 6}

aluExtPortEtherCfmLbmRx OBJECT-TYPE
    SYNTAX      Counter64
    MAX-ACCESS  read-only
    STATUS      current
    DESCRIPTION
        "aluExtPortEtherCfmLbmRx indicates the received number of Ethernet
        CFM Loopback messages (ETH-LBM) with destination MAC address matches
        tmnxPortMacAddress of this port, while aluExtPortEtherLoopbackCfmLbMode
        is enabled.

        aluExtPortEtherCfmLbmRx should be the sum of aluExtPortEtherCfmLbmDropped
        and aluExtPortEtherCfmLbrTx of the port."
    ::= { aluExtTmnxPortEtherEntry 7 }

aluExtPortEtherCfmLbmDropped OBJECT-TYPE
    SYNTAX      Counter64
    MAX-ACCESS  read-only
    STATUS      current
    DESCRIPTION
        "aluExtPortEtherCfmLbmDropped indicates the number of received, but
        discarded Ethernet CFM Loopback messages (ETH-LBM) at this port
        while its aluExtPortEtherLoopbackCfmLbMode is enabled."
    ::= { aluExtTmnxPortEtherEntry 8 }

aluExtPortEtherCfmLbrTx OBJECT-TYPE
    SYNTAX      Counter64
    MAX-ACCESS  read-only
    STATUS      current
    DESCRIPTION
        "aluExtPortEtherCfmLbrTx indicates the number of Ethernet CFM
        Loopback Replies (ETH-LBR) that were sent back to the sender, in reponding to the
        received ETH-LBM at this port while aluExtPortEtherLoopbackCfmLbMode is
        enabled."
    ::= { aluExtTmnxPortEtherEntry 9 }

aluExtPortEtherLoopbackSwapMacAddr OBJECT-TYPE
     SYNTAX     TruthValue
     MAX-ACCESS read-write
     STATUS     current
     DESCRIPTION
         "This variable indicates if Source and Destination MAC addresses in the packets are to be
         interchanged before being loopbacked to the sender.  Setting aluExtPortEtherLoopbackSwapMacAddr
         must be accompanied by setting aluExtPortEtherLoopback for the same port."
     DEFVAL  { false }
     ::= { aluExtTmnxPortEtherEntry 10 }

aluExtPortEtherAdminPhyTxClock OBJECT-TYPE
    SYNTAX      INTEGER {
                    notApplicable    (0),
                    slave            (1),
                    master           (2),
                    auto-pref-slave  (3),
                    auto-pref-master (4)
                }
    MAX-ACCESS  read-write
    STATUS      current
    DESCRIPTION
        "The value of aluExtPortEtherAdminPhyTxClock indicates the mode
        used to establish timing control of a 1000BASE-T port. The
        aluExtPortEtherAdminPhyTxClock is used to control the setting
        of register 9, bits 10-12 that are described in Table 40-3 of
        IEEE 802.3-2008.

        Register 9.12, the MASTER-SLAVE Manual Config Enable bit, is
        cleared when 'auto-pref-slave (3)' or 'auto-pref-master (4)'
        is configured. Otherwise the register 9.12 bit is set.

        Register 9.10 will be cleared when 'auto-pref-slave (3)' is
        configured and 'auto-pref-master (4)' will cause register 9.10
        to be cleared.

        When aluExtPortEtherAdminPhyTxClock is 'slave (1)', register
        9.11, the MASTER-SLAVE Manual Config Value bit, is cleared. When
        aluExtPortEtherAdminPhyTxClock is 'master (2)' MASTER-SLAVE
        Manual Config Value bit is set.

        For ports that cannot support 1000BASE-T, aluExtPortEtherAdminPhyTxClock
        will be defaulted to 'notApplicable (0)' and cannot be changed.

        For ports that support 1000BASE-T, setting aluExtPortEtherAdminPhyTxClock
        to 'notApplicable (0)' will result in aluExtPortEtherAdminPhyTxClock
        being set to the DEFVAL value of 'auto-pref-slave (3)'.

        Setting aluExtPortEtherAdminPhyTxClock on 1000BaseT microwave aware
        ports (ie. ports associated with ALU-MICROWAVE-PORT::aluMwRadioPortID)
        is allowed but it does not establish timing control of the 1000BASE-T
        port. The operational aspects of microwave ports with respect to timing
        control is described under aluExtPortEtherOperPhyTxClock"
    REFERENCE   "IEEE Std 802.3-2008 Section 40.5"
    DEFVAL { auto-pref-slave }
    ::= { aluExtTmnxPortEtherEntry 11 }

aluExtPortEtherOperPhyTxClock OBJECT-TYPE
    SYNTAX      INTEGER {
                    notApplicable  (0),
                    slave          (1),
                    master         (2)
                }
    MAX-ACCESS  read-only
    STATUS      current
    DESCRIPTION
        "The value of aluExtPortEtherOperPhyTxClock indicates the operational
        value of the MASTER-SLAVE Configuration Resolution bit of register 10
        from Table 40-3 of IEEE 802.3-2008. When the bit is cleared the
        aluExtPortEtherOperPhyTxClock is 'slave (1)' and when the bit is set
        the aluExtPortEtherOperPhyTxClock is 'master (2)'.

        If a port is not 1000BASE-T, down or failed,
        aluExtPortEtherOperPhyTxClock is 'notApplicable (0)'.

        On 1000BaseT microwave aware ports (ie. ports associated with
        ALU-MICROWAVE-PORT::aluMwRadioPortID) are always 'master(2)'."
    REFERENCE   "IEEE Std 802.3-2008 Section 40.5"
    ::= { aluExtTmnxPortEtherEntry 12 }

aluEthPtpTimestampCapable  OBJECT-TYPE
    SYNTAX      TruthValue
    MAX-ACCESS  read-only
    STATUS      current
    DESCRIPTION
        "The aluEthPtpTimestampCapable indicates whether
        the hardware is capable of supporting 1588 PTP time stamp
        functions."
    ::= { aluExtTmnxPortEtherEntry 13 }

aluEthPtpTimestampEnable  OBJECT-TYPE
    SYNTAX      TruthValue
    MAX-ACCESS  read-only
    STATUS      current
    DESCRIPTION
        "the aluEthPtpTimestampEnable attribute indicate whether
        the port is enabled to support 1588 PTP edge time stamp
        functions."
    ::= { aluExtTmnxPortEtherEntry 14 }

aluEthPtpAsymmetry  OBJECT-TYPE
    SYNTAX      Integer32 (-8388608..8388607)
    UNITS       "nanoseconds"
    MAX-ACCESS  read-write
    STATUS      obsolete
    DESCRIPTION
        "aluEthPtpAsymmetry is a path asymmetry correction value
         that is used to specify the difference in transmission time
         between master-to-slave and slave-to-master. The value
         can be derived from the following formula.

         (ingress propagation time - egress propagation time)/2.

         This object was made obsolete for revision 9.0 on Nokia 7705 SROS
         series systems; it was replaced by tmnxPortEtherPTPAsymmetry. "
    DEFVAL { 0 }
    ::= { aluExtTmnxPortEtherEntry 15}


aluExtPortEtherLoopbackPersist OBJECT-TYPE
     SYNTAX     TruthValue
     MAX-ACCESS read-write
     STATUS     current
     DESCRIPTION
         "Setting this variable to 'true' indicates the configuration of aluExtPortEtherLoopback,
         aluExtPortEtherLoopbackPersist, aluExtPortEtherLoopbackSwapMacAddr can be saved
         to persist over system reboots.

         Setting aluExtPortEtherLoopbackPersist to 'true' can only be applied to an ethernet
         port in access mode, and it must be accompanied by setting aluExtPortEtherLoopback.

         While setting aluExtPortEtherLoopbackPersist to true, aluExtPortEtherLoopbackTimer
         cannot be set to a non-zero value."
     DEFVAL  { false }
     ::= { aluExtTmnxPortEtherEntry 16 }

aluPortEtherIngressRateCbs  OBJECT-TYPE
    SYNTAX      Unsigned32 (1..130816)
    UNITS       "bytes"
    MAX-ACCESS  read-write
    STATUS      current
    DESCRIPTION
        "aluPortEtherIngressRateCbs specifies the committed burst size that hard policer can accept while complying
        to the ingress rate tmnxPortEtherIngressRate of the port.

        aluPortEtherIngressRateCbs is not applicable when tmnxPortEtherIngressRate is -1.
        Setting tmnxPortEtherIngressRate to -1 causes aluPortEtherIngressRateCbs of the port
        to revert back to its default value.

        aluPortEtherIngressRateCbs must be configured in multiples of 256 bytes."

    DEFVAL { 130816 }
    ::= { aluExtTmnxPortEtherEntry 17}

aluPortEtherIngressRateSrcPause  OBJECT-TYPE
    SYNTAX      TruthValue
    MAX-ACCESS  read-write
    STATUS      current
    DESCRIPTION
        "aluPortEtherIngressRateSrcPause indicates whether to send a pause frame for every dropped packet
        by the hard policer when tmnxPortEtherIngressRate is > 0.

        aluPortEtherIngressRateSrcPause is not applicable when tmnxPortEtherIngressRate is -1.
        Setting tmnxPortEtherIngressRate to -1 causes aluPortEtherIngressRateSrcPause of the port
        to revert back to its default value."

    DEFVAL { false }
    ::= { aluExtTmnxPortEtherEntry 18}

aluPortEtherXorMode    OBJECT-TYPE
    SYNTAX      INTEGER {
                    notApplicable (0),
                    rj45          (1),
                    sfp           (2),
                    rjp5          (3),
                    auto          (4)
                }
    MAX-ACCESS  read-write
    STATUS      current
    DESCRIPTION
         "The aluPortEtherXorMode variable specifies the type of physical connector
         for MDA ports which support configurable connector type. aluPortEther
         must be 'notApplicable' if the MDA port does not support xor mode configuration."

    DEFVAL { rj45 }
    ::= { aluExtTmnxPortEtherEntry 19}

aluPortEtherEgrUnshapedSapCir  OBJECT-TYPE
    SYNTAX      Integer32 (-1 | 0..10000000)
    UNITS        "kbps"
    MAX-ACCESS   read-write
    STATUS       current
    DESCRIPTION
         "The value of aluPortEtherEgrUnshapedSapCir specifies the egress CIR of all unshaped SAPs,
         i.e.  all SAPs using this port that have aluSapEgressSchedulerMode in 4-priority-mode."
    DEFVAL { 0 }
    ::= { aluExtTmnxPortEtherEntry 20 }

aluExtPortEtherVlanFilter    OBJECT-TYPE
    SYNTAX      INTEGER (-1 | 1..65535)
    MAX-ACCESS  read-write
    STATUS      current
    DESCRIPTION
         "aluExtPortEtherVlanFilter specifies the VLAN filter provisioned for bridge ethernet
         ports. The value -1 indicates that no VLAN filter is configured."
    DEFVAL { -1 }
    ::= { aluExtTmnxPortEtherEntry 21}

aluExtPortEtherCfmLbVlanList          OBJECT-TYPE
    SYNTAX        OCTET STRING (SIZE(0..255))
    MAX-ACCESS    read-write
    STATUS        current
    DESCRIPTION
    "The aluExtPortEtherCfmLbVlanList is an OCTET STRING in which a list of Vlan Ids to be enabled for cfm Loopback when
    aluExtPortEtherLoopbackCfmLbMode is priority-dot1p.

    Any incoming CFM LB frame destined for this tmnxPortPortID will be processed if it has no vlan tags or if it has a vlan tag
    matched with those specified in this string aluExtPortEtherCfmLbVlanList.

    Either string 'none' or empty string can be use to disable cfm loopback on all vlans on the port.

    If aluExtPortEtherLoopbackCfmLbMode is priority-dot1p while aluExtPortEtherCfmLbVlanList is 'none' or an empty string,
    Any incoming CFM LB frame destined for this tmnxPortPortID will get processed and replied only if it has no Vlan tags.

    Acceptable characters in the string are:

    -  numbers within the range [1..4094] ,
    -  comma (,),
    -  hyphen (-) to indicate a range of consecutive numbers.
    -  string 'none'

    Those characters can be combined using syntax below:

    -  aluExtPortEtherCfmLbVlanList can have multiple numbers or some ranges with a comma ',' separating them with no spaces.
    -  It's acceptable to have a same number specified more than once in the string, and this number is only counted as one vlan id toward the maximum limit of max vlan ids per port.

    Examples of valid strings:
        1
        1,2,10,4094
        100-109,11,6,4-8,11

    Examples of invalid strings:
        1,           :  should not end the string with any character other than a valid number/digit.
        1.5         :  only a comma is accepted, a period is invalid
        1, 5        :  a space is not acceptable
        200-220  :  there are 21 vlan id's in this range, exceeded the maximum of 16 vlan ids per port."

    DEFVAL      { ''H }   -- the empty string
    ::= { aluExtTmnxPortEtherEntry 22 }

aluExtPortEtherAccEgrShaper       OBJECT-TYPE
    SYNTAX      TNamedItemOrEmpty
    MAX-ACCESS  read-write
    STATUS      current
    DESCRIPTION
        "aluExtPortEtherNetEgrShaper contains the access egress shaper policy if the tmnxPortMode is hybrid.
        Otherwise this object has no significance."
    DEFVAL      { ''H }   -- the empty string
    ::= { aluExtTmnxPortEtherEntry 23 }

aluExtPortEtherNetEgrShaper       OBJECT-TYPE
    SYNTAX      TNamedItemOrEmpty
    MAX-ACCESS  read-write
    STATUS      current
    DESCRIPTION
        "aluExtPortEtherNetEgrShaper contains the network egress shaper policy if the tmnxPortMode is hybrid.
        Otherwise this object has no significance."
    DEFVAL       { ''H }   -- the empty string
    ::= { aluExtTmnxPortEtherEntry 24 }

aluPortEtherEgrUnshapedNwIfCir  OBJECT-TYPE
    SYNTAX      Integer32 (-1 | 0..10000000)
    UNITS        "kbps"
    MAX-ACCESS   read-write
    STATUS       current
    DESCRIPTION
         "The value of aluPortEtherEgrUnshapedNwIfCir specifies the egress CIR of all unshaped network interfaces
          on this port,  i.e. those network interfaces on this port without a network queue policy, their
          aluVrtrIfNetworkEgrQueuePol is empty."
    DEFVAL { 0 }
    ::= { aluExtTmnxPortEtherEntry 25 }

aluExtPortEtherEgrRateIncludeFCS OBJECT-TYPE
     SYNTAX     TruthValue
     MAX-ACCESS read-write
     STATUS     current
     DESCRIPTION
         "This variable indicates if the value of tmnxPortEtherEgressRate of the port includes 4 bytes
         of ethernet frame check sequence (FCS)."
     DEFVAL  { false }
     ::= { aluExtTmnxPortEtherEntry 26 }

aluPortEtherOperXorMode    OBJECT-TYPE
    SYNTAX      INTEGER {
                    notApplicable (0),
                    rj45          (1),
                    sfp           (2),
                    rjp5          (3)
                }
    MAX-ACCESS  read-only
    STATUS      current
    DESCRIPTION
         "The aluPortEtherOperXorMode specifies the type of physical connector used
         when MDA ports are configured as auto xor mode. aluPortEtherOperXorMode
         must be 'notApplicable' if the MDA port does not support xor mode configuration."

    ::= { aluExtTmnxPortEtherEntry 27}

aluExtPortEtherBnAllowed     OBJECT-TYPE
     SYNTAX     TruthValue
     MAX-ACCESS read-write
     STATUS     current
     DESCRIPTION
         "The aluExtPortEtherBnAllowed allows the handling of the received ETH-BN to be processed,
          and possibly to enforce the bandwidth indicated in the ETH-BN by changing the egress-rate
          of the port.

          When modify aluExtPortEtherBnAllowed to 'true', aluExtPortEtherBnHoldTime is set to its
          default value automatically if it is not explicitly provided."
     DEFVAL  { false }
     ::= { aluExtTmnxPortEtherEntry 28 }

aluExtPortEtherBnHoldTime      OBJECT-TYPE
    SYNTAX     Unsigned32 (1..600)
    UNITS      "seconds"
    MAX-ACCESS read-write
    STATUS     current
    DESCRIPTION
        "aluExtPortEtherBnHoldTime is the time interval to hold aluExtPortEtherBnEgressRateInUse
        when changed.  This guards against excessive rate changes.

        aluExtPortEtherBnHoldTime is applicable only when aluExtPortEtherBnAllowed is 'true'."
    DEFVAL  { 5 }
    ::= { aluExtTmnxPortEtherEntry 29 }

--
-- ALU Extensions of Tmnx DS1 table
--
aluExtTmnxDS1Table OBJECT-TYPE
    SYNTAX      SEQUENCE OF AluExtTmnxDS1Entry
    MAX-ACCESS  not-accessible
    STATUS      current
    DESCRIPTION
        "The aluExtTmnxDS1Table has an entry for a DS1 physical port or channel."
    ::= { aluPortObjs 3 }

aluExtTmnxDS1Entry       OBJECT-TYPE
    SYNTAX      AluExtTmnxDS1Entry
    MAX-ACCESS  not-accessible
    STATUS      current
    DESCRIPTION
        "Each row entry represents extended functionality of a DS1 physical
         port or channel on Nokia 7705 SAR devices.  Entries cannot be
         created or deleted via SNMP SET operations.  Entries in this table
         will be created or deleted automatically when entries in the
         tmnxDS1Table are created or deleted."
    AUGMENTS  { tmnxDS1Entry }
    ::= { aluExtTmnxDS1Table 1 }

AluExtTmnxDS1Entry ::=
    SEQUENCE {
        aluExtDS1HoldTimeUp          Unsigned32,
        aluExtDS1HoldTimeDown        Unsigned32,
        aluExtDS1SignalBitsState     OCTET STRING,
        aluExtDS1E1Ssm               TruthValue,
        aluExtDS1E1SsmTxDus          TruthValue,
        aluExtE1SsmSaBit             Unsigned32,
        aluExtDs1E1TxSsmValue        Unsigned32,
        aluExtDs1E1RxSsmValue        Unsigned32
    }

aluExtDS1HoldTimeUp  OBJECT-TYPE
    SYNTAX      Unsigned32 (0..100)
    UNITS       "deci-seconds"
    MAX-ACCESS  read-write
    STATUS      current
    DESCRIPTION
        "The value of aluExtDS1HoldTimeUp is used to configure the
         hold-timer for link up event dampening. This guards against
         reporting excessive interface transitions. This is implemented
         by not advertising subsequent transitions of the interface to
         upper layer protocols until the configured timer has expired.
         A value of zero (0) indicates that an up transition is reported
         immediately.

         Channelized SONET ports have a range of 5..100 where the default
         value is 5."
    DEFVAL { 0 }
    ::= { aluExtTmnxDS1Entry 1 }

aluExtDS1HoldTimeDown    OBJECT-TYPE
    SYNTAX      Unsigned32 (0..100)
    UNITS       "deci-seconds"
    MAX-ACCESS  read-write
    STATUS      current
    DESCRIPTION
        "The value of aluExtDS1HoldTimeDown is used to configure the
         hold-timer for link down event dampening. This guards against
         reporting excessive interface transitions. This is implemented
         by not advertising subsequent transitions of the interface to
         upper layer protocols until the configured timer has expired.
         A value of zero (0) indicates that a down transition is reported
         immediately."
    DEFVAL { 0 }
    ::= { aluExtTmnxDS1Entry 2 }

aluExtDS1SignalBitsState OBJECT-TYPE
    SYNTAX      OCTET STRING (SIZE(64))
    MAX-ACCESS  read-only
    STATUS      current
    DESCRIPTION
        "aluExtDS1SignalBitsState is an array of bytes used to indicate the
         current state of the ABCD signalling bits for all timeslots of a
         DS1/E1.

         The first half of the array or the 32 most significant bytes describe
         the RX ABCD bits. The other half describes the TX ABCD bits.

         In each half of the array, every byte represents a particular timeslot.
         The most significant byte represents timeslot 1. The least significant
         byte represents timeslot 32.

         The byte arrangement is as follows:

         array index: |  0  1 ... 30 31 | 32 33 ... 62 63 |
         timeslot:    |  1  2 ... 31 32 |  1  2 ... 31 32 |
                      | <---- RX -----> | <---- TX -----> |

         Each byte carries ABCD bits in the least significant nibble. The
         byte's most significant bit indicates the validity of the ABCD bits.

         The bit arrangement is as follows:

         bit pos:    | 7 6 5 4 3 2 1 0 |
                     | V x x x A B C D |

         'V' - validity (0 = invalid, 1 = valid)
         'x' - don't care

         ABCD bits are marked invalid for a variety of situations (eg.
         tmnxDS1SignalMode not configured for CAS, timeslot(s) not configured
         as part of a channel-group, DS1/E1 status not up, etc.).

         For CAS DS1 SF, only the AB signalling bits are supported. The remaining
         2 least significant bits in the nibble are undefined.
         "
    ::= { aluExtTmnxDS1Entry 3 }

aluExtDS1E1Ssm OBJECT-TYPE
    SYNTAX      TruthValue
    MAX-ACCESS  read-write
    STATUS      current
    DESCRIPTION
        "aluExtDS1E1Ssm specifies whether or not Synchronous Status
        Messages (SSM) are enabled on the DS1/E1 port."
    DEFVAL { false }
    ::= { aluExtTmnxDS1Entry 4 }

aluExtDS1E1SsmTxDus OBJECT-TYPE
    SYNTAX      TruthValue
    MAX-ACCESS  read-write
    STATUS      current
    DESCRIPTION
        "The value of aluExtDS1E1SsmTxDus specifies whether or not the
         value 0xF (dus/dnu) is forced in the Synchronous Status Message."
    DEFVAL      { false }
    ::= { aluExtTmnxDS1Entry 5 }

aluExtE1SsmSaBit  OBJECT-TYPE
    SYNTAX      Unsigned32 (0|4..8)
    MAX-ACCESS  read-write
    STATUS      current
    DESCRIPTION
        "The value of aluExtE1SsmSaBit specifies the national use bit to
        carry SSM Messages. This applies only to E1 interfaces.

        aluExtE1SsmSaBit is not supported on DS1 interfaces and
        cannot be written. aluExtE1SsmSaBit on DS1 interfaces shall
        default to '0'."
    DEFVAL { 8 }
    ::= { aluExtTmnxDS1Entry 6 }

aluExtDs1E1TxSsmValue  OBJECT-TYPE
    SYNTAX      Unsigned32 (0..255)
    MAX-ACCESS  read-only
    STATUS      current
    DESCRIPTION
        "The value of aluExtDs1E1TxSsmValue indicates the Synchronous Status
        Message (SSM) value that is transmitted on the line.

        On ports that do not support SSM or for ports that do not have
        SSM enabled the aluExtDs1E1TxSsmValue will be '254'."
    REFERENCE
        "Bellcore (Telcordia Technologies) GR-253-CORE, Issue 3, September 2000,
         5.4.2.
         ITU-T Recommendation G.781, June 1999.
         ITU-T Recommendation G.8264, October 2008."
    ::= { aluExtTmnxDS1Entry 7 }

aluExtDs1E1RxSsmValue  OBJECT-TYPE
    SYNTAX      Unsigned32 (0..255)
    MAX-ACCESS  read-only
    STATUS      current
    DESCRIPTION
        "The value of aluExtDs1E1RxSsmValue indicates the last Synchronous Status
        Message (SSM) value that was received by the port.

        On ports that do not support SSM or for ports that do not have
        SSM enabled the aluExtDs1E1RxSsmValue will be '254'.

        If ports are administratively enabled and the port is operationally out of
        service due to LOS, OOF or AIS the aluExtDs1E1RxSsmValue will be '255'. "
    REFERENCE
        "Bellcore (Telcordia Technologies) GR-253-CORE, Issue 3, September 2000,
         5.4.2.
         ITU-T Recommendation G.781, June 1999.
         ITU-T Recommendation G.8264, October 2008."
    ::= { aluExtTmnxDS1Entry 8 }

--
-- ALU RS232 Port table
--
aluRS232PortTable OBJECT-TYPE
    SYNTAX      SEQUENCE OF AluRS232PortEntry
    MAX-ACCESS  not-accessible
    STATUS      current
    DESCRIPTION
        "The aluRS232PortTable has an entry for a physical Serial Data port."
    ::= { aluPortObjs 4 }

aluRS232PortEntry       OBJECT-TYPE
    SYNTAX      AluRS232PortEntry
    MAX-ACCESS  not-accessible
    STATUS      current
    DESCRIPTION
        "Each row entry represents a physical Serial Data port on an
         IOM card in a chassis in the system.  Entries cannot be created
         and deleted via SNMP SET operations.  Entries in this table will
         be created automatically when the tmnxMDAAssignedType object is
         set to a Serial Data Interface (SDI) MDA type. The aluRS232PortEntry
         contains attributes that are unique to the 'rs232/v35/x21/rs530'
         aluRS232PortType. The tmnxPortPortID contains the slot, mda and port
         numbers encoded into it.

         For each aluRS232PortEntry, there will be a corresponding entry
         in the tmnxPortTable and the ifTable."
    INDEX       { tmnxChassisIndex, tmnxPortPortID }
    ::= { aluRS232PortTable 1 }

AluRS232PortEntry ::=
    SEQUENCE {
        aluRS232PortLastChangeTime       TimeStamp,
        aluRS232PortType                 INTEGER
    }

aluRS232PortLastChangeTime OBJECT-TYPE
    SYNTAX      TimeStamp
    MAX-ACCESS  read-only
    STATUS      current
    DESCRIPTION
        "aluRS232PortLastChangeTime contains the sysUpTime
         value of the most recently modified writable variable in the
         aluRS232PortEntry row for this port."
    ::= { aluRS232PortEntry 1 }

aluRS232PortType           OBJECT-TYPE
    SYNTAX      INTEGER {
                    rs232 (1),
                    v35   (2),
                    x21   (3),
                    rs530 (4)
                }
    MAX-ACCESS  read-create
    STATUS      current
    DESCRIPTION
        "aluRS232PortType configures the interface-type of the physical
         port to one of the defined values, above.

         Regarding sdiv1 and sdiv2 (tmnxMDAAssignedType 11 and 56):
         Due to hardware limitations, each port in a port trio must be of the
         same aluRS232PortType. For example, if port 1 is configured as rs232,
         ports 2 and 3 must be configured as rs232.

         Regarding sdiv3 (tmnxMDAAssignedType 71):
         Due to hardware limitations, each port in a port duo must be of the
         same aluRS232PortType. For example, if port 1 is configured as rs232,
         then port 2 must be configured as rs232, too.

         v35, x21 and rs530 are not supported on the SAR-H and SAR-Hc systems.

         rs530 is not supported on sdiv1 and sdiv2."
    DEFVAL      { rs232 }
    ::= { aluRS232PortEntry 2 }

--
-- ALU RS232 table
--
aluRS232Table OBJECT-TYPE
    SYNTAX      SEQUENCE OF AluRS232Entry
    MAX-ACCESS  not-accessible
    STATUS      current
    DESCRIPTION
         "aluRS232Table has an entry for each Serial
         channel on each IOM card in each chassis in the system."
    ::= { aluPortObjs 5 }


aluRS232Entry       OBJECT-TYPE
    SYNTAX  AluRS232Entry
    MAX-ACCESS      not-accessible
    STATUS          current
    DESCRIPTION
         "Each row entry represents a Serial channel on an IOM card
         in a chassis in the system.  Channel entries for
         serial ports can be created and deleted via SNMP SET operations.
         For each aluRS232Entry, there will be a corresponding entry
         in the tmnxPortTable and the ifTable."
    INDEX   { tmnxChassisIndex, tmnxPortPortID }
    ::= { aluRS232Table 1 }

AluRS232Entry ::=
SEQUENCE {
        aluRS232RowStatus                  RowStatus,
        aluRS232LastChangeTime             TimeStamp,
        aluRS232Type                       INTEGER,
        aluRS232DeviceMode                 INTEGER,
        aluRS232DeviceGender               INTEGER,
        aluRS232Duplex                     INTEGER,
        aluRS232Speed                      INTEGER,
        aluRS232ClockSource                INTEGER,
        aluRS232Loopback                   INTEGER,
        aluRS232CharacterLength            INTEGER,
        aluRS232Parity                     INTEGER,
        aluRS232StopBits                   INTEGER,
        aluRS232ReportAlarm                AluRS232ReportStatus,
        aluRS232ReportAlarmStatus          AluRS232ReportStatus,
        aluRS232ControlLeadDtrDsr          AluRS232ControlLead,
        aluRS232ControlLeadRtsDcdC         AluRS232ControlLead,
        aluRS232ControlLeadAlbCts          AluRS232ControlLead,
        aluRS232ControlLeadRdlRi           AluRS232ControlLead,
        aluRS232ControlLeadDsrDtr          AluRS232ControlLead,
        aluRS232ControlLeadDcdRtsI         AluRS232ControlLead,
        aluRS232ControlLeadCtsAlb          AluRS232ControlLead,
        aluRS232ControlLeadRiRdl           AluRS232ControlLead,
        aluRS232ControlLeadsState          OCTET STRING,
        aluRS232MultiDrop                  INTEGER,
        aluRS232SBitSignaling              INTEGER,
        aluRS232DataPosition               INTEGER,
        aluRS232HoldTimeUp                 Unsigned32,
        aluRS232HoldTimeDown               Unsigned32,
        aluRS232ControlLeadsSignal         OCTET STRING,
        aluRS232ControlLeadMonDtrDsr       AluRS232ControlLeadMon,
        aluRS232ControlLeadMonRtsDcdC      AluRS232ControlLeadMon,
        aluRS232ControlLeadMonAlbCts       AluRS232ControlLeadMon,
        aluRS232ControlLeadMonRdlRi        AluRS232ControlLeadMon,
        aluRS232ClockSyncState             INTEGER,
        aluRS232ClockMasterPortId          TmnxPortID,
        aluRS232InvertClock                TmnxEnabledDisabled,
        aluRS232MonClockDeviationRaise     Unsigned32,
        aluRS232MonClockDeviationClear     Unsigned32,
        aluRS232MonDataInactivityRaise     Unsigned32,
        aluRS232MonDataInactivityClear     Unsigned32
}

aluRS232RowStatus    OBJECT-TYPE
    SYNTAX      RowStatus
    MAX-ACCESS  read-create
    STATUS      current
    DESCRIPTION
        "aluRS232RowStatus controls the creation and deletion of
         row entries in the aluRS232Table.
         For row creation, the manager has to first calculate the
         tmnxPortPortID based on the TiMOS encoding scheme."
::= { aluRS232Entry 1 }

aluRS232LastChangeTime OBJECT-TYPE
    SYNTAX      TimeStamp
    MAX-ACCESS  read-only
    STATUS      current
    DESCRIPTION
        "aluRS232LastChangeTime contains the sysUpTime value of the
         most recently modified writable variable in the
         aluRS232Entry row for this Serial channel."
    ::= { aluRS232Entry 2 }

aluRS232Type OBJECT-TYPE
    SYNTAX      INTEGER {
                    rs232 (1),
                    v35   (2),
                    x21   (3),
                    rs530 (4)
                }
    MAX-ACCESS  read-only
    STATUS      current
    DESCRIPTION
        "aluRS232Type configures the interface for RS-232, V.35, X.21 or
         RS-530."
    ::= { aluRS232Entry 3 }

aluRS232DeviceMode OBJECT-TYPE
    SYNTAX      INTEGER {
                    synchronous  (1),
                    asynchronous (2)
                }
    MAX-ACCESS  read-create
    STATUS      current
    DESCRIPTION
        "aluRS232DeviceMode configures the interface for
         synchronous or asynchronous operation.

         Changing to asynchronous results in defaulting of
         aluRS232CharacterLength, aluRS232Parity and aluRS232StopBits.

         Changing to synchronous results in defaulting of aluRS232ClockSource,
         aluRS232InvertClock, aluRS232MonClockDeviationRaise and
         aluRS232MonClockDeviationClear.

         Valid values depend on aluRS232Speed.

         synchronous is not supported on the SAR-H and SAR-Hc systems.

         synchronous is not valid while the sub-channel is
         aluRS232SocketEntry.

         synchronous is not allowed on rs530 while aluRS232MultiDrop is not
         disabled.
        "
    DEFVAL { synchronous }
    ::= { aluRS232Entry 4 }

aluRS232DeviceGender OBJECT-TYPE
    SYNTAX      INTEGER {
                    dte (1),
                    dce (2)
                }
    MAX-ACCESS  read-create
    STATUS      current
    DESCRIPTION
        "aluRS232DeviceGender configures the gender offered by the
         local interface.

         dte is not valid while the sub-channel is aluRS232SocketEntry.

         dte is not supported on the SAR-H and SAR-Hc systems.

         Regarding sdiv3 (tmnxMDAAssignedType 71):
         Due to hardware limitations, each Serial channel in a port duo must
         be of the same aluRS232DeviceGender. For example, if the channel on
         port 1 is configured as dte, then the channel on port 2 must be
         configured as dte, too.
        "
    DEFVAL { dce }
    ::= { aluRS232Entry 5 }

aluRS232Duplex OBJECT-TYPE
    SYNTAX      INTEGER {
                    fullDuplex (1),
                    halfDuplex (2)
                }
    MAX-ACCESS  read-create
    STATUS      current
    DESCRIPTION
        "aluRS232Duplex configures the duplex method of the interface to
         half or full duplex.

         full is not allowed while aluRS232MultiDrop is slave.

         half is not valid while the sub-channel is aluRS232SocketEntry.
        "
    DEFVAL { fullDuplex }
    ::= { aluRS232Entry 6 }

aluRS232Speed  OBJECT-TYPE
    SYNTAX      INTEGER {
                    speed1200   (1),
                    speed2400   (2),
                    speed9600   (3),
                    speed19200  (4),
                    speed38400  (5),
                    speed56000  (6),
                    speed64k    (7),
                    speed128k   (8),
                    speed256k   (9),
                    speed384k   (10),
                    speed512k   (11),
                    speed640k   (12),
                    speed768k   (13),
                    speed896k   (14),
                    speed1024k  (15),
                    speed1152k  (16),
                    speed1280k  (17),
                    speed1408k  (18),
                    speed1536k  (19),
                    speed1664k  (20),
                    speed1792k  (21),
                    speed1920k  (22),
                    speed4800   (23),
                    speed600    (24),
                    speed57600  (25),
                    speed115200 (26),
                    speed16000  (27),
                    speed2048k  (28),
                    speed3072k  (29),
                    speed4096k  (30),
                    speed5120k  (31),
                    speed6144k  (32),
                    speed7168k  (33),
                    speed8192k  (34),
                    speed9216k  (35),
                    speed10240k (36),
                    speed11264k (37),
                    speed12288k (38),
                    speed13312k (39),
                    speed14336k (40),
                    speed15360k (41),
                    speed16384k (42)
                }
    MAX-ACCESS  read-create
    STATUS      current
    DESCRIPTION
        "aluRS232Speed specifies the link speed of the Serial interface.
         A value of 'speed1200' sets the link to 1200bps. A value of 'speed64k'
         sets the link to 64kbps.

         Valid values depend on tmnxMDAAssignedType :
         sdiv1 : 600, 1200, 2400, 4800, 9600, 19200, 38400, 56000,
                 64k, 128k, 256k, 384k, 512k, 640k, 768k, 896k, 1024k, 1152k,
                 1280k, 1408k, 1536k, 1664k, 1792k, 1920k
         sdiv2 : 600, 1200, 2400, 4800, 9600, 19200, 38400, 56000,
                 57600, 115200
                 64k, 128k, 256k, 384k, 512k, 640k, 768k, 896k, 1024k, 1152k,
                 1280k, 1408k, 1536k, 1664k, 1792k, 1920k
         sdiv3 : <all speeds>

         On the SAR-H and SAR-Hc systems, valid values are the same as sdiv2.

         Valid values also depend on aluRS232Type :
         rs232 : 600, 1200, 2400, 4800, 9600, 16000, 19200, 38400, 56000,
                 57600, 115200
                 64k (sdiv3 only)
         v35   : 64k, 128k, 256k, 384k, 512k, 640k, 768k, 896k, 1024k, 1152k,
                 1280k, 1408k, 1536k, 1664k, 1792k, 1920k, 2048k
         x21   : 1200, 2400, 4800, 9600, 19200, 38400, 56000,
                 64k, 128k, 256k, 384k, 512k, 640k, 768k, 896k, 1024k, 1152k,
                 1280k, 1408k, 1536k, 1664k, 1792k, 1920k, 2048k
         rs530 : <all speeds except 57600 and 115200>

         Valid values also depend on aluRS232DeviceMode :
         synchronous  : <all speeds except 57600 and 115200>
         asynchronous : 600, 1200, 2400, 4800, 9600, 19200, 38400, 57600,
                        115200

         Valid values also depend on the sub-channel:
         (none)                 : <no additional restrictions>
         aluRS232ChanGroupEntry : <all speeds except 57600 and 115200>
         aluRS232SocketEntry    : <asynchronous speeds only>

         High Capacity Multiplexing (HCM) is supported on
         aluRS232ChanGroupEntry only, running at subrate speed:
         hcm   : 600, 1200, 2400, 4800, 9600, 16000, 19200, 38400, 56000

         Valid values also depend on aluRS232ControlLeadXxx :
         high       : <no additional restrictions>
         low        : <no additional restrictions>
         end-to-end : <HCM speeds only; rs530 exempt>

         Valid values also depend on aluRS232MultiDrop :
         disabled   : <no additional restrictions>
         slave      : <HCM speeds only>
         master     : <HCM speeds only>

         Default values depend on aluRS232Type :
         rs232 : 9600
         v35   : 64k
         x21   : 64k
         rs530 : 64k
        "
   DEFVAL { speed9600 }
   ::= { aluRS232Entry 7 }

aluRS232ClockSource  OBJECT-TYPE
    SYNTAX      INTEGER {
                    notApplicable (0),
                    slave         (1),
                    external      (2),
                    dcrSerial     (3)
                }
    MAX-ACCESS  read-create
    STATUS      current
    DESCRIPTION
        "aluRS232ClockSource specifies the clock for transmitted data
         on a serial port.

         slave(1)     - clock is derived from the system
         external(2)  - clock is provided by the attached device
         dcrSerial(3) - clock is recovered from the differential timestamp in
                        the RTP header but undirectional only, from attached
                        source DCE device to attached slave DTE device

         aluRS232ClockSource is 'notApplicable' while aluRS232DeviceMode is
         asynchronous. The value 'notApplicable' is set by the system.

         'external' and 'dcrSerial' are not supported on the SAR-H and SAR-Hc
         systems.
         'external' and 'dcrSerial' are not supported on sdiv1 and sdiv2.
         'external' and 'dcrSerial' are supported on rs232 and rs530 only.

         'dcrSerial' is not allowed while aluRS232MultiDrop is not disabled.
        "
    DEFVAL { slave }
    ::= { aluRS232Entry 8 }

aluRS232Loopback    OBJECT-TYPE
    SYNTAX     INTEGER {
                none     (1),
                bidirB   (2),
                bidirE   (3)
            }

    MAX-ACCESS  read-create
    STATUS      current
    DESCRIPTION
        "aluRS232Loopback is used to put the port into a loopback mode.
         The value of tmnxPortAdminStatus should be set to outOfService
         in order for the loopback to be enabled.

         Both loopbacks are bidirectional. They reside in the same device but
         relative to each other, 'bidirB' is closer to the system-side.

         'bidirB' is not supported while sub-channel is aluRS232SocketEntry.
         'bidirB' is not supported on sdiv3.
        "
    DEFVAL  { none }
    ::= { aluRS232Entry 9 }

aluRS232CharacterLength OBJECT-TYPE
    SYNTAX      INTEGER (6..8)
    MAX-ACCESS  read-create
    STATUS      current
    DESCRIPTION
        "The aluRS232CharacterLength specifies the character length.
         Parameter is only valid while the port is configured for asynchronous operation.

         The value of aluRS232CharacterLength plus the value of aluRS232StopBits
         plus the number of bits needed to encode aluRS232Parity must be less
         than or equal to 10. Note that aluRS232Parity 'none' needs ZERO bits.
        "
    DEFVAL { 8 }
    ::= { aluRS232Entry 10 }

aluRS232Parity OBJECT-TYPE
    SYNTAX      INTEGER {
                    none  (1),
                    odd   (2),
                    even  (3),
                    mark  (4),
                    space (5)
                }
    MAX-ACCESS  read-create
    STATUS      current
    DESCRIPTION
         "The aluRS232Parity specifies the parity type.
         Parameter is only valid while the port is configured for asynchronous operation.

         The value of aluRS232CharacterLength plus the value of aluRS232StopBits
         plus the number of bits needed to encode aluRS232Parity must be less
         than or equal to 10. Note that aluRS232Parity 'none' needs ZERO bits.
        "
    DEFVAL { none }
    ::= { aluRS232Entry 11 }

aluRS232StopBits OBJECT-TYPE
    SYNTAX      INTEGER (1..2)
    MAX-ACCESS  read-create
    STATUS      current
    DESCRIPTION
        "The aluRS232StopBits specifies the stop bits.
         Parameter is only valid while the port is configured for asynchronous operation.

         The value of aluRS232CharacterLength plus the value of aluRS232StopBits
         plus the number of bits needed to encode aluRS232Parity must be less
         than or equal to 10. Note that aluRS232Parity 'none' needs ZERO bits.
        "
    DEFVAL { 1 }
    ::= { aluRS232Entry 12 }

aluRS232ReportAlarm OBJECT-TYPE
    SYNTAX      AluRS232ReportStatus
    MAX-ACCESS  read-create
    STATUS      current
    DESCRIPTION
        "The value of aluRS232ReportAlarm determines when and if to
         generate aluEqPortRS232Alarm and aluEqPortRS232AlarmClear
         notifications for this port:
         hcmOof - Reports local HCM out-of-frame errors.
         hcmRai - Reports remote HCM alarm indication.
         ctrlLeadMon - control lead monitoring is forcing link down
         monClockDev - monitoring of clock deviation is forcing link down
         monDataInac - monitoring of data inactivity is forcing link down

         hcmOof and hcmRai are valid for subrate (HCM) speeds only.
         ctrlLeadMon, monClockDev and monDataInac are supported on sdiv3 only.

         monClockDev is not applicable while aluRS232DeviceMode is
         asynchronous.
        "
    DEFVAL      { {hcmOof, hcmRai, ctrlLeadMon, monClockDev, monDataInac} }
   ::= { aluRS232Entry 13 }

aluRS232ReportAlarmStatus OBJECT-TYPE
    SYNTAX      AluRS232ReportStatus
    MAX-ACCESS  read-only
    STATUS      current
    DESCRIPTION
      "The value of aluRS232ReportAlarmStatus indicates the alarms on
         this port."
    ::= { aluRS232Entry 14 }

aluRS232ControlLeadDtrDsr OBJECT-TYPE
    SYNTAX      AluRS232ControlLead
    MAX-ACCESS  read-create
    STATUS      current
    DESCRIPTION
        "aluRS232ControlLeadDtrDsr is used to configure the DTR/DSR input lead
         to an ASSUMED value.
         For RS-232, V.35 and RS-530:
           if local gender is DCE, lead indicates Data Terminal Ready
           if local gender is DTE, lead indicates Data Set Ready
         For X.21:
           lead is undefined
         Valid values are 'high' and 'low'."
    DEFVAL { high }
    ::= { aluRS232Entry 15 }

aluRS232ControlLeadRtsDcdC OBJECT-TYPE
    SYNTAX      AluRS232ControlLead
    MAX-ACCESS  read-create
    STATUS      current
    DESCRIPTION
        "aluRS232ControlLeadRtsDcdC is used to configure the RTS/DCD/C input lead
         to an ASSUMED value.
         For RS-232, V.35 and RS-530:
           if local gender is DCE, lead indicates Request To Send
           if local gender is DTE, lead indicates Data Carrier Detect
         For X.21:
           if local gender is DCE, lead indicates Control
           if local gender is DTE, lead indicates Indication
         Valid values are 'high', 'low' and 'end-to-end'.

         'end-to-end' is valid only for subrate (HCM) speeds and for interface
         configurations compatible with 'satopSerial'."
    DEFVAL { high }
    ::= { aluRS232Entry 16 }

aluRS232ControlLeadAlbCts OBJECT-TYPE
    SYNTAX      AluRS232ControlLead
    MAX-ACCESS  read-create
    STATUS      current
    DESCRIPTION
        "aluRS232ControlLeadAlbCts is used to configure the ALB/CTS input lead
         to an ASSUMED value.
         For RS-232 and V.35:
           if local gender is DCE, lead indicates Analog loopback
           if local gender is DTE, lead indicates Clear To Send
         For X.21:
           lead is undefined
         For RS-530, AlbCts represents RlCts:
           if local gender is DCE, lead indicates Remote Loopback
           if local gender is DTE, lead indicates Clear To Send
         Valid values are 'high', 'low' and 'end-to-end'.

         This object is not supported on the SAR-H and SAR-Hc systems.

         'end-to-end' is valid only for subrate (HCM) speeds and for interface
         configurations compatible with 'satopSerial'."
    DEFVAL { high }
    ::= { aluRS232Entry 17 }

aluRS232ControlLeadRdlRi OBJECT-TYPE
    SYNTAX      AluRS232ControlLead
    MAX-ACCESS  read-create
    STATUS      current
    DESCRIPTION
        "aluRS232ControlLeadRdlRi is used to configure the RDL/RI input lead
         to an ASSUMED value.
         For RS-232:
           if local gender is DCE, lead indicates Remote Digital Loopback
           if local gender is DTE, lead indicates Ring Indicator
         For V.35 and X.21:
           lead is undefined
         For RS-530, RdlRi represents LlTm:
           if local gender is DCE, lead indicates Local Loopback
           if local gender is DTE, lead indicates Test Mode
         Valid values are 'high' and 'low'.

         This object is not supported on the SAR-H and SAR-Hc systems."
    DEFVAL { high }
    ::= { aluRS232Entry 18 }

aluRS232ControlLeadDsrDtr OBJECT-TYPE
    SYNTAX      AluRS232ControlLead
    MAX-ACCESS  read-create
    STATUS      current
    DESCRIPTION
        "aluRS232ControlLeadDsrDtr is used to configure the DSR/DTR output lead
         to a FORCED value.
         For RS-232, V.35 and RS-530:
           if local gender is DCE, lead indicates Data Set Ready
           if local gender is DTE, lead indicates Data Terminal Ready
         For X.21:
           lead is undefined
         Valid values are 'high' and 'low'.

         This object is not supported on the SAR-H and SAR-Hc systems."
    DEFVAL { high }
    ::= { aluRS232Entry 19 }

aluRS232ControlLeadDcdRtsI OBJECT-TYPE
    SYNTAX      AluRS232ControlLead
    MAX-ACCESS  read-create
    STATUS      current
    DESCRIPTION
        "aluRS232ControlLeadDcdRtsI is used to configure the DCD/RTS/I output lead
         to a FORCED value.
         For RS-232, V.35 and RS-530:
           if local gender is DCE, lead indicates Data Carrier Detect
           if local gender is DTE, lead indicates Request To Send
         For X.21:
           if local gender is DCE, lead indicates Indication
           if local gender is DTE, lead indicates Control
         Valid values are 'high', 'low' and 'end-to-end'.

         'end-to-end' is valid only for subrate (HCM) speeds and for interface
         configurations compatible with 'satopSerial'."
    DEFVAL { high }
    ::= { aluRS232Entry 20 }

aluRS232ControlLeadCtsAlb OBJECT-TYPE
    SYNTAX      AluRS232ControlLead
    MAX-ACCESS  read-create
    STATUS      current
    DESCRIPTION
        "aluRS232ControlLeadCtsAlb is used to configure the CTS/ALB output lead
         to a FORCED value.
         For RS-232 and V.35:
           if local gender is DCE, lead indicates Clear To Send
           if local gender is DTE, lead indicates Analog loopback
         For X.21:
           lead is undefined
         For RS-530, CtsAlb represents CtsRl:
           if local gender is DCE, lead indicates Clear To Send
           if local gender is DTE, lead indicates Remote Loopback
         Valid values are 'high', 'low' and 'end-to-end'.

         'end-to-end' is valid only for subrate (HCM) speeds and for interface
         configurations compatible with 'satopSerial'."
    DEFVAL { high }
    ::= { aluRS232Entry 21 }

aluRS232ControlLeadRiRdl OBJECT-TYPE
    SYNTAX      AluRS232ControlLead
    MAX-ACCESS  read-create
    STATUS      current
    DESCRIPTION
        "aluRS232ControlLeadRiRdl is used to configure the RI/RDL output lead
         to a FORCED value.
         For RS-232:
           if local gender is DCE, lead indicates Ring Indicator
           if local gender is DTE, lead indicates Remote Digital Loopback
         For V.35 and X.21:
           lead is undefined
         For RS-530, RiRdl represents TmLl:
           if local gender is DCE, lead indicates Test Mode
           if local gender is DTE, lead indicates Local Loopback
         Valid values are 'high' and 'low'."
    DEFVAL { high }
    ::= { aluRS232Entry 22 }

aluRS232ControlLeadsState OBJECT-TYPE
    SYNTAX      OCTET STRING (SIZE(8))
    MAX-ACCESS  read-only
    STATUS      current
    DESCRIPTION
        "aluRS232ControlLeadsState is an array of byte values used to indicate
         the current states of the input and output control leads. These state
         values are historically known as scan and drive values, respectively.
         These state values are the ones that get transported over the network
         (provided there is a means, such as HCM). As such, they are sometimes
         referred to as NETWORK-side values.
         For line-side values, see aluRS232ControlLeadsSignal.

         Each byte in the array represents the state of an individual control
         lead. The byte order is as follows:

             -- DtrDsr (LSB or byte0)
             -- RtsDcdC
             -- AlbCts
             -- RdlRi
             -- DsrDtr
             -- DcdRtsI
             -- CtsAlb
             -- RiRdl (MSB or byte7)

         A byte value of 1 represents on (or high as per AluRS232ControlLead).
         A byte value of 2 represents off (or low as per AluRS232ControlLead).
         All other byte values are undefined.

         A particular byte is undefined if its config counterpart is undefined.
         For example, given an X.21 interface, aluRS232ControlLeadDsrDtr is
         undefined thus, aluRS232ControlLeadsState byte 'DtrDsr' is also
         undefined.

         Some bytes can represent something else depending on the interface
         type. For example, given an RS-530, RdlRi represents LlTm.
         See the respective object for details (eg. aluRS232ControlLeadRdlRi).
         "
    ::= { aluRS232Entry 23 }

aluRS232MultiDrop OBJECT-TYPE
    SYNTAX      INTEGER {
                    disabled (1),
                    slave    (2),
                    master   (3)
                }
    MAX-ACCESS  read-create
    STATUS      current
    DESCRIPTION
        "aluRS232MultiDrop is used to configure the Multi-drop Data Bridge (MDDB)
         mode of the interface.

         'slave' and 'master' mode is valid for subrate (HCM) speeds only.

         Changing to 'slave' results in forcing aluRS232Duplex to 'half' and
         aluRS232SBitSignaling to 'off'.
         Changing to 'disabled' results in defaulting aluRS232Duplex and
         aluRS232SBitSignaling (as aluRS232DataPosition permits).
         Changing to 'master' results in forcing aluRS232Duplex to 'full',
         aluRS232SBitSignaling to 'on' and aluRS232DataPosition to 'f0b5'.

         aluRS232MultiDrop is not valid while the sub-channel is
         aluRS232SocketEntry.
        "
    DEFVAL { disabled }
    ::= { aluRS232Entry 24 }

aluRS232SBitSignaling OBJECT-TYPE
    SYNTAX      INTEGER {
                    on  (1),
                    off (2)
                }
    MAX-ACCESS  read-create
    STATUS      current
    DESCRIPTION
        "aluRS232SBitSignaling is used to configure the S-Bit signaling
         mode of the interface.

         This object is valid for subrate (HCM) speeds only.

         'on' is not supported while aluRS232MultiDrop is 'slave'.
         'on' is not allowed while aluRS232DataPosition is 'f0b6'.
        "
    DEFVAL { on }
    ::= { aluRS232Entry 25 }

aluRS232DataPosition OBJECT-TYPE
    SYNTAX      INTEGER {
                    f0b5 (1),
                    f0b6 (2)
                }
    MAX-ACCESS  read-create
    STATUS      current
    DESCRIPTION
        "aluRS232DataPosition is used to configure the HCM data position.

         This object is valid for subrate (HCM) speeds only.

         'f0b6' is not allowed while aluRS232SBitSignaling is 'on'.
        "
    DEFVAL { f0b5 }
    ::= { aluRS232Entry 26 }

aluRS232HoldTimeUp  OBJECT-TYPE
    SYNTAX      Unsigned32 (0..100)
    UNITS       "deci-seconds"
    MAX-ACCESS  read-create
    STATUS      current
    DESCRIPTION
        "The value of aluRS232HoldTimeUp is used to configure the
         hold-timer for link up event dampening. This guards against
         reporting excessive interface transitions. This is implemented
         by not advertising subsequent transitions of the interface to
         upper layer protocols until the configured timer has expired.
         A value of zero (0) indicates that an up transition is reported
         immediately."
    DEFVAL { 0 }
    ::= { aluRS232Entry 27 }

aluRS232HoldTimeDown    OBJECT-TYPE
    SYNTAX      Unsigned32 (0..100)
    UNITS       "deci-seconds"
    MAX-ACCESS  read-create
    STATUS      current
    DESCRIPTION
        "The value of aluRS232HoldTimeDown is used to configure the
         hold-timer for link down event dampening. This guards against
         reporting excessive interface transitions. This is implemented
         by not advertising subsequent transitions of the interface to
         upper layer protocols until the configured timer has expired.
         A value of zero (0) indicates that a down transition is reported
         immediately."
    DEFVAL { 0 }
    ::= { aluRS232Entry 28 }

aluRS232ControlLeadsSignal OBJECT-TYPE
    SYNTAX      OCTET STRING (SIZE(8))
    MAX-ACCESS  read-only
    STATUS      current
    DESCRIPTION
        "aluRS232ControlLeadsSignal is an array of byte values used to indicate
         the current signal levels of the input and output control leads
         (connected to the attached CPE). These values are the ones that get
         signalled over the (physical) line. As such, they are sometimes
         referred to as LINE-side values.
         For network-side values, see aluRS232ControlLeadsState.

         Each byte in the array represents the signal level of an individual
         control lead. The byte order is as follows:

             -- DtrDsr (LSB or byte0)
             -- RtsDcdC
             -- AlbCts
             -- RdlRi
             -- DsrDtr
             -- DcdRtsI
             -- CtsAlb
             -- RiRdl (MSB or byte7)

         A byte value of 1 represents on (or high as per AluRS232ControlLead).
         A byte value of 2 represents off (or low as per AluRS232ControlLead).
         All other byte values are undefined.

         A particular byte is undefined if its config counterpart is undefined.
         For example, given an X.21 interface, aluRS232ControlLeadDsrDtr is
         undefined thus, aluRS232ControlLeadsSignal byte 'DtrDsr' is also
         undefined.

         Some bytes can represent something else depending on the interface
         type. For example, given an RS-530, RdlRi represents LlTm.
         See the respective object for details (eg. aluRS232ControlLeadRdlRi).
         "
    ::= { aluRS232Entry 29 }

aluRS232ControlLeadMonDtrDsr OBJECT-TYPE
    SYNTAX      AluRS232ControlLeadMon
    MAX-ACCESS  read-create
    STATUS      current
    DESCRIPTION
        "aluRS232ControlLeadMonDtrDsr is used to configure monitoring of the
         input control lead signal, DtrDsr. While monitored, detected
         transitions will trigger aluRS232ControlLeadsSignalChange.

         'high' and 'low' are supported on sdiv3 only."
    DEFVAL { off }
    ::= { aluRS232Entry 30 }

aluRS232ControlLeadMonRtsDcdC OBJECT-TYPE
    SYNTAX      AluRS232ControlLeadMon
    MAX-ACCESS  read-create
    STATUS      current
    DESCRIPTION
        "aluRS232ControlLeadMonRtsDcdC is used to configure monitoring of the
         input control lead signal, RtsDcdC. While monitored, detected
         transitions will trigger aluRS232ControlLeadsSignalChange.

         'high' and 'low' are supported on sdiv3 only."
    DEFVAL { off }
    ::= { aluRS232Entry 31 }

aluRS232ControlLeadMonAlbCts OBJECT-TYPE
    SYNTAX      AluRS232ControlLeadMon
    MAX-ACCESS  read-create
    STATUS      current
    DESCRIPTION
        "aluRS232ControlLeadMonAlbCts is used to configure monitoring of the
         input control lead signal, AlbCts. While monitored, detected
         transitions will trigger aluRS232ControlLeadsSignalChange.

         For RS-530, AlbCts represents RlCts.

         This object is not supported on the SAR-H and SAR-Hc systems.
         'high' and 'low' are supported on sdiv3 only."
    DEFVAL { off }
    ::= { aluRS232Entry 32 }

aluRS232ControlLeadMonRdlRi OBJECT-TYPE
    SYNTAX      AluRS232ControlLeadMon
    MAX-ACCESS  read-create
    STATUS      current
    DESCRIPTION
        "aluRS232ControlLeadMonRdlRi is used to configure monitoring of the
         input control lead signal, RdlRi. While monitored, detected
         transitions will trigger aluRS232ControlLeadsSignalChange.

         For RS-530, RdlRi represents LlTm.

         This object is not supported on the SAR-H and SAR-Hc systems.
         'high' and 'low' are supported on sdiv3 only."
    DEFVAL { off }
    ::= { aluRS232Entry 33 }

aluRS232ClockSyncState           OBJECT-TYPE
    SYNTAX      INTEGER {
                    unknown  (0),
                    normal   (1),
                    holdOver (2),
                    freeRun  (3)
                }
    MAX-ACCESS  read-only
    STATUS      current
    DESCRIPTION
        "The value of aluRS232ClockSyncState indicates the current clock
         synchronization state if aluRS232ClockSource is 'dcrSerial'.

         unknown(0)       - Unsupported or unknown state
         normal(1)        - Normal (locked) state
         holdOver(2)      - Synchronization with reference has been lost
         freeRun(3)       - Synchronized with internal reference"
    ::= { aluRS232Entry 34 }

aluRS232ClockMasterPortId        OBJECT-TYPE
    SYNTAX      TmnxPortID
    MAX-ACCESS  read-only
    STATUS      current
    DESCRIPTION
        "The value of aluRS232ClockMasterPortId indicates the current clock
         synchronization master port id if aluRS232ClockSource is
         'dcrSerial'."
    ::= { aluRS232Entry 35 }

aluRS232InvertClock              OBJECT-TYPE
    SYNTAX      TmnxEnabledDisabled
    MAX-ACCESS  read-create
    STATUS      current
    DESCRIPTION
        "The value of aluRS232InvertClock specifies whether to invert the
         clock edge that the interface samples for received data (if local
         gender is DCE) or transmitted data (if local gender is DTE).

         Inverting the clock may correct issues such as those related to phase
         shift. For example, data changes state near the interface's sampling
         clock edge. Contributors to phase shift variance include, but are not
         limited to: cable length and interface rate.

         'enabled' not supported on SAR-H and SAR-Hc systems.
         'enabled' not supported on sdiv1 and sdiv2.
         'enabled' not allowed while aluRS232DeviceMode is asynchronous.
        "
    DEFVAL { disabled }
    ::= { aluRS232Entry 36 }

aluRS232MonClockDeviationRaise   OBJECT-TYPE
    SYNTAX      Unsigned32 (0|10..100)
    UNITS       "seconds"
    MAX-ACCESS  read-create
    STATUS      current
    DESCRIPTION
        "The value of the object aluRS232MonClockDeviationRaise specifies the
         amount of time to debounce clock deviation before asserting the port
         fault condition, 'monClockDeviation'. Clock deviation is detected
         when the external clock exceeds a +/- 6% deviation from the
         internal interface rate clock.

         The special value 0 means clock deviation monitoring is disabled (ie.
         detection off and any concurrent assertion will be cleared
         immediately). While this object is 0, aluRS232MonClockDeviationClear
         must also be 0.

         Non-zero values must be specified in increments of 10.

         Non-zero values not supported on SAR-H and SAR-Hc systems.
         Non-zero values not supported on sdiv1 and sdiv2.
         Non-zero values not allowed while aluRS232DeviceMode is asynchronous.
        "
    DEFVAL { 0 }
    ::= { aluRS232Entry 37 }

aluRS232MonClockDeviationClear   OBJECT-TYPE
    SYNTAX      Unsigned32 (0|10..100)
    UNITS       "seconds"
    MAX-ACCESS  read-create
    STATUS      current
    DESCRIPTION
        "The value of the object aluRS232MonClockDeviationClear specifies the
         amount of time to debounce no clock deviation before de-asserting the
         port fault condition, 'monClockDeviation'. No clock deviation is
         detected when the external clock does not exceed a +/- 6% deviation
         from the internal interface rate clock.

         The special value 0 means clock deviation monitoring is disabled (ie.
         detection off and any concurrent assertion will be cleared
         immediately). While this object is 0, aluRS232MonClockDeviationRaise
         must also be 0.

         Non-zero values must be specified in increments of 10.

         Non-zero values not supported on SAR-H and SAR-Hc systems.
         Non-zero values not supported on sdiv1 and sdiv2.
         Non-zero values not allowed while aluRS232DeviceMode is asynchronous.
        "
    DEFVAL { 0 }
    ::= { aluRS232Entry 38 }

aluRS232MonDataInactivityRaise   OBJECT-TYPE
    SYNTAX      Unsigned32 (0|10..100)
    UNITS       "seconds"
    MAX-ACCESS  read-create
    STATUS      current
    DESCRIPTION
        "The value of the object aluRS232MonDataInactivityRaise specifies the
         amount of time to debounce data inactivity before asserting the port
         fault condition, 'monDataInactivity'.

         The special value 0 means data inactivity monitoring is disabled (ie.
         detection off and any concurrent assertion will be cleared
         immediately). While this object is 0, aluRS232MonDataInactivityClear
         must also be 0.

         Non-zero values must be specified in increments of 10.

         Non-zero values not supported on SAR-H and SAR-Hc systems.
         Non-zero values not supported on sdiv1 and sdiv2.
        "
    DEFVAL { 0 }
    ::= { aluRS232Entry 39 }

aluRS232MonDataInactivityClear   OBJECT-TYPE
    SYNTAX      Unsigned32 (0|10..100)
    UNITS       "seconds"
    MAX-ACCESS  read-create
    STATUS      current
    DESCRIPTION
        "The value of the object aluRS232MonDataInactivityClear specifies the
         amount of time to debounce data activity before de-asserting the
         port fault condition, 'monDataInactivity'.

         The special value 0 means data inactivity monitoring is disabled (ie.
         detection off and any concurrent assertion will be cleared
         immediately). While this object is 0, aluRS232MonDataInactivityRaise
         must also be 0.

         Non-zero values must be specified in increments of 10.

         Non-zero values not supported on SAR-H and SAR-Hc systems.
         Non-zero values not supported on sdiv1 and sdiv2.
        "
    DEFVAL { 0 }
    ::= { aluRS232Entry 40 }

--
-- RS232 Channel Group Table
--
aluRS232ChanGroupTable   OBJECT-TYPE
    SYNTAX      SEQUENCE OF AluRS232ChanGroupEntry
    MAX-ACCESS  not-accessible
    STATUS      current
    DESCRIPTION
        "The aluRS232ChanGroupTable has an entry for 64kbps (DS0) channels
         grouped together and belonging to a particular Serial channel."
    ::= { aluPortObjs 6 }

aluRS232ChanGroupEntry       OBJECT-TYPE
    SYNTAX      AluRS232ChanGroupEntry
    MAX-ACCESS  not-accessible
    STATUS      current
    DESCRIPTION
        "Each row entry represents one or more Serial channels on an
         interface.

         Entries can be created and deleted via SNMP SET operations
         using the aluRS232ChanGroupRowStatus object.

         For each aluRS232ChanGroupEntry, there will be a corresponding entry
         in the tmnxPortTable and the ifTable."
    INDEX       { tmnxChassisIndex, tmnxPortPortID }
    ::= { aluRS232ChanGroupTable 1 }

AluRS232ChanGroupEntry ::=
    SEQUENCE {
        aluRS232ChanGroupRowStatus           RowStatus,
        aluRS232ChanGroupTimeSlots           TmnxDs0ChannelList,
        aluRS232ChanGroupMTU                 Unsigned32,
        aluRS232ChanGroupOperMTU             Unsigned32,
        aluRS232ChanGroupCRC                 INTEGER,
        aluRS232ChanGroupIdleCycleFlags      TmnxDSXIdleCycleFlags,
        aluRS232ChanGroupPayloadFillType     TmnxDSXIdleFillType,
        aluRS232ChanGroupPayloadPattern      Unsigned32
    }

aluRS232ChanGroupRowStatus    OBJECT-TYPE
    SYNTAX      RowStatus
    MAX-ACCESS  read-create
    STATUS      current
    DESCRIPTION
        "aluRS232ChanGroupRowStatus controls the creation and deletion of
         row entries in the aluRS232ChanGroupTable. The tmnxPortPortID
         for a channel group includes a group ID in the lower bits.
         The manager has to first calculate the tmnxPortPortID based on the
         TiMOS encoding scheme."
    ::= { aluRS232ChanGroupEntry 1 }

aluRS232ChanGroupTimeSlots    OBJECT-TYPE
    SYNTAX      TmnxDs0ChannelList
    MAX-ACCESS  read-only
    STATUS      current
    DESCRIPTION
        "aluRS232ChanGroupTimeSlots is a bitmap which is used to
         represent the timeslots from a channel group.
         The description for TmnxDs0ChannelList contains details of the
         bitmap organization."
    ::= { aluRS232ChanGroupEntry 2 }

aluRS232ChanGroupMTU  OBJECT-TYPE
    SYNTAX      Unsigned32 (0|578..9208)
    UNITS       "bytes"
    MAX-ACCESS  read-create
    STATUS      current
    DESCRIPTION
        "The size of the largest packet which can be sent/received
         on the channel group, specified in octets.  For groups that
         are used for transmitting network datagrams, this is the
         size of the largest network datagram that can be sent.

         Setting aluRS232ChanGroupMTU to a value of zero (0), causes the agent
         to recalculate the default MTU size which can vary based on the
         current setting of tmnxPortMode and tmnxPortEncapType variables.
         Some typical 7705 default values are:
                1572 with mode access and encap-type ipcp"
    ::= { aluRS232ChanGroupEntry 3 }

aluRS232ChanGroupOperMTU  OBJECT-TYPE
    SYNTAX      Unsigned32
    UNITS       "bytes"
    MAX-ACCESS  read-only
    STATUS      current
    DESCRIPTION
        "The negotiated size of the largest packet which can be sent on
         the channel group, specified in octets.  For channel groups that
         are used for transmitting network datagrams, this is the size of
         the largest network datagram that can be sent."
    ::= { aluRS232ChanGroupEntry 4 }

aluRS232ChanGroupCRC  OBJECT-TYPE
    SYNTAX      INTEGER {
                    crc16 (1),
                    crc32 (2)
                }
    MAX-ACCESS  read-create
    STATUS      current
    DESCRIPTION
        "The value of aluRS232ChanGroupCRC variable indicates the precision of
         the cyclic redundancy check.  A value of 'crc16' is a 16-bit
         CRC calculation.  A value of 'crc32' is a 32-bit CRC
         calculation.  32-bit CRC increases the error detection ability,
         but it also adds some performance overhead."
    DEFVAL { crc32 }
    ::= { aluRS232ChanGroupEntry 5 }

aluRS232ChanGroupIdleCycleFlags    OBJECT-TYPE
    SYNTAX      TmnxDSXIdleCycleFlags
    MAX-ACCESS  read-create
    STATUS      current
    DESCRIPTION
        "aluRS232ChanGroupIdleCycleFlags configures the value that the
         channel group transmits during idle cycle."

    DEFVAL      { flags }
    ::= { aluRS232ChanGroupEntry 6 }

aluRS232ChanGroupPayloadFillType  OBJECT-TYPE
    SYNTAX      TmnxDSXIdleFillType
    MAX-ACCESS  read-create
    STATUS      current
    DESCRIPTION
        "The value of aluRS232ChanGroupPayloadFillType specifies the type of
         idle payload fill to be sent when the CEM channel group experiences
         an underrun.

         If the type is set to 'userDefinedPattern' then the value of
         aluRS232ChanGroupPayloadPattern is used to define the payload pattern.

         The default value depends on the encap type of the channel group:
         For CEM encap           - 'allOnes'
         For all other encaps    - 'notApplicable' "
    DEFVAL { notApplicable }
    ::= { aluRS232ChanGroupEntry 7 }

aluRS232ChanGroupPayloadPattern   OBJECT-TYPE
    SYNTAX      Unsigned32 (0..255)
    MAX-ACCESS  read-create
    STATUS      current
    DESCRIPTION
         "The value of aluRS232ChanGroupPayloadPattern specifies the idle
         payload
         fill pattern when the CEM channel group experiences an underrun and
         aluRS232ChanGroupPayloadFillType is set to 'userDefinedPattern'.

         The default value depends on the encap type of the channel group:
         For CEM encap channel group             - 255 (Valid range 0..255)
         For non-CEM encap channel group         -   0 (Valid range 0..0)."
    DEFVAL { 0 }
    ::= { aluRS232ChanGroupEntry 8 }

--
--  Port Discards Stats Table
--
aluPortDiscardStatsTable OBJECT-TYPE
    SYNTAX      SEQUENCE OF AluPortDiscardsStatsEntry
    MAX-ACCESS  not-accessible
    STATUS      current
    DESCRIPTION
        "Defines the Nokia SAR series port packet discard
         statistics table for providing, via SNMP, the capability of
         retrieving the detailed packet discard statistics."
    ::= { aluPortStatsObjs 1 }

aluPortDiscardsStatsEntry    OBJECT-TYPE
    SYNTAX      AluPortDiscardsStatsEntry
    MAX-ACCESS  not-accessible
    STATUS      current
    DESCRIPTION
        "Defines an entry in aluPortDiscardStatsTable. Entries are
         created and deleted by the system depending port
         configuration."
    INDEX   { tmnxChassisIndex, tmnxPortPortID }
    ::= { aluPortDiscardStatsTable 1 }

AluPortDiscardsStatsEntry ::=
    SEQUENCE {
        aluPortInL2AddrProtoDiscards        Counter64,
        aluPortInMPLSLabelDiscards          Counter64,
        aluPortInIPAddrProtoDiscards        Counter64,
        aluPortInVlanIdDiscards             Counter64,
        aluPortInHdlcCrcDiscards            Counter64,
        aluPortOutPortMtuDiscards           Counter64,
        aluPortInCsmQHiPriDiscards          Counter64,
        aluPortInCsmQLowPriDiscards         Counter64,
        aluPortInCsmQFtpPriDiscards         Counter64,
        aluPortOutCsmQDiscards              Counter64,
        aluPortInOtherDiscards              Counter64,
        aluPortOutOtherDiscards             Counter64,
        aluPortInCsmQMediumPriDiscards      Counter64,
        aluPortInHardPolicerDiscards        Counter64,
        aluPortInL2MacDADiscards            Counter64,
        aluPortInL2ETypeDiscards            Counter64
    }

aluPortInL2AddrProtoDiscards OBJECT-TYPE
    SYNTAX      Counter64
    MAX-ACCESS  read-only
    STATUS      current
    DESCRIPTION
        "aluPortInL2AddrProtoDiscards indicates the number of packets discarded
        that contained an unsupported type/protocol or unknown address at
        layer 2."
    ::= { aluPortDiscardsStatsEntry 1 }

aluPortInMPLSLabelDiscards OBJECT-TYPE
    SYNTAX      Counter64
    MAX-ACCESS  read-only
    STATUS      current
    DESCRIPTION
        "aluPortInMPLSLabelDiscards indicates the number of packets discarded that
        contained unknown mpls outer tunnels, unknown inner label or more than
        two unsupported labels."
    ::= { aluPortDiscardsStatsEntry 2 }

aluPortInIPAddrProtoDiscards OBJECT-TYPE
    SYNTAX      Counter64
    MAX-ACCESS  read-only
    STATUS      current
    DESCRIPTION
        "aluPortInIPAddrProtoDiscards indicates the number of packets discarded
        that contained an invalid IP address or unsupported IP protocol."
    ::= { aluPortDiscardsStatsEntry 3 }

aluPortInVlanIdDiscards OBJECT-TYPE
    SYNTAX      Counter64
    MAX-ACCESS  read-only
    STATUS      current
    DESCRIPTION
        "aluPortInVlanIdDiscards indicates the number of packets discarded
        that contained an unknown VLAN Id."
    ::= { aluPortDiscardsStatsEntry 4 }

aluPortInHdlcCrcDiscards OBJECT-TYPE
    SYNTAX      Counter64
    MAX-ACCESS  read-only
    STATUS      current
    DESCRIPTION
        "aluPortInHdlcCrcDiscards indicates the number of packets discarded
        due to the HDLC frame containing a CRC error.

        This statistic is only applicable to interfaces that have an
        encapsulation type of PPP-AUTO."
    ::= { aluPortDiscardsStatsEntry 5 }

aluPortOutPortMtuDiscards OBJECT-TYPE
    SYNTAX      Counter64
    MAX-ACCESS  read-only
    STATUS      current
    DESCRIPTION
        "aluPortOutPortMtuDiscards indicates the number of packets discarded
        at egress due to the packet exceeding the configured port mtu."
    ::= { aluPortDiscardsStatsEntry 6 }

aluPortInCsmQHiPriDiscards OBJECT-TYPE
    SYNTAX      Counter64
    MAX-ACCESS  read-only
    STATUS      current
    DESCRIPTION
        "aluPortInCsmQHiPriDiscards indicates the number of packets discarded
        in the Ingress CSM High Priority Queue."
    ::= { aluPortDiscardsStatsEntry 7 }

aluPortInCsmQLowPriDiscards OBJECT-TYPE
    SYNTAX      Counter64
    MAX-ACCESS  read-only
    STATUS      current
    DESCRIPTION
        "aluPortInCsmQLowPriDiscards indicates the number of packets discarded
        in the Ingress CSM Low Priority Queue."
    ::= { aluPortDiscardsStatsEntry 8 }

aluPortInCsmQFtpPriDiscards OBJECT-TYPE
    SYNTAX      Counter64
    MAX-ACCESS  read-only
    STATUS      obsolete
    DESCRIPTION
        "aluPortInCsmQFtpPriDiscards indicates the number of packets discarded
        in the Ingress CSM Ftp Priority Queue."
    ::= { aluPortDiscardsStatsEntry 9 }

aluPortOutCsmQDiscards OBJECT-TYPE
    SYNTAX      Counter64
    MAX-ACCESS  read-only
    STATUS      current
    DESCRIPTION
        "aluPortOutCsmQDiscards indicates the number of packets discarded
        in the Egress CSM Queue."
    ::= { aluPortDiscardsStatsEntry 10 }

aluPortInOtherDiscards OBJECT-TYPE
    SYNTAX      Counter64
    MAX-ACCESS  read-only
    STATUS      current
    DESCRIPTION
        "aluPortInOtherDiscards indicates the number of packets discarded
        at ingress for other reasons during processing."
    ::= { aluPortDiscardsStatsEntry 11 }

aluPortOutOtherDiscards OBJECT-TYPE
    SYNTAX      Counter64
    MAX-ACCESS  read-only
    STATUS      current
    DESCRIPTION
        "aluPortOutOtherDiscards indicates the number of packets discarded
        at egress for other reasons during processing."
    ::= { aluPortDiscardsStatsEntry 12 }

aluPortInCsmQMediumPriDiscards OBJECT-TYPE
    SYNTAX      Counter64
    MAX-ACCESS  read-only
    STATUS      current
    DESCRIPTION
        "aluPortInCsmQMediumPriDiscards indicates the number of packets discarded
        in the Ingress CSM Medium Priority Queue."
    ::= { aluPortDiscardsStatsEntry 13 }

aluPortInHardPolicerDiscards OBJECT-TYPE
    SYNTAX      Counter64
    MAX-ACCESS  read-only
    STATUS      current
    DESCRIPTION
        "aluPortInHardPolicerDiscards indicates the number of packets discarded
        by the ingress hard policer."
    ::= { aluPortDiscardsStatsEntry 14 }

aluPortInL2MacDADiscards OBJECT-TYPE
    SYNTAX      Counter64
    MAX-ACCESS  read-only
    STATUS      current
    DESCRIPTION
        "aluPortInL2MacDADiscards indicates the number of packets discarded
        that contained an unknown Mac DA."
    ::= { aluPortDiscardsStatsEntry 15 }

aluPortInL2ETypeDiscards OBJECT-TYPE
    SYNTAX      Counter64
    MAX-ACCESS  read-only
    STATUS      current
    DESCRIPTION
        "aluPortInL2MacDADiscards indicates the number of packets discarded
        that contained an unknown Ethertype."
    ::= { aluPortDiscardsStatsEntry 16 }

--
--  Port ACR Clock Stats Table
--
aluPortAcrClkStatsTable OBJECT-TYPE
    SYNTAX      SEQUENCE OF AluPortAcrClkStatsEntry
    MAX-ACCESS  not-accessible
    STATUS      current
    DESCRIPTION
        "Defines the Nokia SAR series port adaptive clock
         recovery (ACR) statistics table for providing, via SNMP, the
         capability of retrieving statistical information relating
         to clock that is derived from the ACR CPIPE PW."
    ::= { aluPortStatsObjs 2 }

aluPortAcrClkStatsEntry    OBJECT-TYPE
    SYNTAX      AluPortAcrClkStatsEntry
    MAX-ACCESS  not-accessible
    STATUS      current
    DESCRIPTION
        "Defines an entry in aluPortAcrClkStatsTable. Entries are
         created and deleted by the system depending port
         configuration."
    INDEX   { tmnxChassisIndex, tmnxPortPortID }
    ::= { aluPortAcrClkStatsTable 1 }

AluPortAcrClkStatsEntry ::=
    SEQUENCE {
        aluLastUpdateTime                   TimeStamp,
        aluTotalMinutesIn24Hour             Unsigned32,
        aluCurrent24HourFreqOffsetMeanPpb   Integer32,
        aluCurrent24HourFreqOffsetStdDevPpb Unsigned32,
        aluMaxShortIntervalMinutes          Unsigned32,
        aluTotalShortIntervalMinutes        Unsigned32,
        aluCurrent1MinValidData              TruthValue,
        aluCurrent1MinPhaseErrorMeanPpb      Integer32,
        aluCurrent1MinPhaseErrorStdDevNs     Unsigned32,
        aluCurrent1MinPhaseErrorMeanNs       Integer32,
        aluCurrent1MinFreqOffsetMeanPpb      Integer32,
        aluCurrent1MinFreqOffsetStdDevPpb    Unsigned32
    }

aluLastUpdateTime OBJECT-TYPE
    SYNTAX      TimeStamp
    MAX-ACCESS  read-only
    STATUS      current
    DESCRIPTION
        "The last time the ACR statistics were updated"
    ::= { aluPortAcrClkStatsEntry 1 }

aluTotalMinutesIn24Hour OBJECT-TYPE
    SYNTAX      Unsigned32
    MAX-ACCESS  read-only
    STATUS      current
    DESCRIPTION
        "The number of minutes in alu24HourFreqOffsetMeanPpb
        and alu24HourFreqOffsetStdDevPpb"
    ::= { aluPortAcrClkStatsEntry 2 }

aluCurrent24HourFreqOffsetMeanPpb OBJECT-TYPE
    SYNTAX      Integer32
    MAX-ACCESS  read-only
    STATUS      current
    DESCRIPTION
        "aluCurrent24HourFreqOffsetMeanPpb indicates the mean frequency offset
         from the local oscillator clock in parts per billion for up to the
         last 24 hour."
    ::= { aluPortAcrClkStatsEntry 3 }

aluCurrent24HourFreqOffsetStdDevPpb OBJECT-TYPE
    SYNTAX      Unsigned32
    MAX-ACCESS  read-only
    STATUS      current
    DESCRIPTION
        "aluCurrent24HourFreqOffsetStdDevPpb indicates the standard deviation of the
         frequency offset from the local oscillator clock in parts per billion
         for up to the last 24 hour."
    ::= { aluPortAcrClkStatsEntry 4 }

aluMaxShortIntervalMinutes OBJECT-TYPE
    SYNTAX      Unsigned32
    MAX-ACCESS  read-only
    STATUS      current
    DESCRIPTION
        "aluMaxShortIntervalMinutes the maximum number of aluIntervalNumber."
    ::= { aluPortAcrClkStatsEntry 5 }

aluTotalShortIntervalMinutes OBJECT-TYPE
    SYNTAX      Unsigned32
    MAX-ACCESS  read-only
    STATUS      current
    DESCRIPTION
        "aluTotalShortIntervalMinutes is the number of aluIntervalNumber
        that have valid statistics"
    ::= { aluPortAcrClkStatsEntry 6 }

aluCurrent1MinValidData OBJECT-TYPE
     SYNTAX TruthValue
     MAX-ACCESS read-only
     STATUS current
     DESCRIPTION
            "This variable indicates if the data for the first
            interval is valid."
     ::= { aluPortAcrClkStatsEntry 7 }

aluCurrent1MinPhaseErrorMeanPpb OBJECT-TYPE
     SYNTAX  Integer32
     MAX-ACCESS  read-only
     STATUS  current
     DESCRIPTION
            "The mean phase error from the local oscillator clock
            in parts per billion during the first interval."
     ::= { aluPortAcrClkStatsEntry 8 }

aluCurrent1MinPhaseErrorStdDevNs OBJECT-TYPE
     SYNTAX  Unsigned32
     MAX-ACCESS  read-only
     STATUS  current
     DESCRIPTION
            "The standard deviation of the phase error from the local
            oscillator clock in nano seconds during the first interval."
     ::= { aluPortAcrClkStatsEntry 9 }

aluCurrent1MinPhaseErrorMeanNs OBJECT-TYPE
     SYNTAX  Integer32
     MAX-ACCESS  read-only
     STATUS  current
     DESCRIPTION
            "The mean of the phase error from the local
            oscillator clock in nano seconds during the first interval."
     ::= { aluPortAcrClkStatsEntry 10 }

aluCurrent1MinFreqOffsetMeanPpb OBJECT-TYPE
     SYNTAX  Integer32
     MAX-ACCESS  read-only
     STATUS  current
     DESCRIPTION
            "The mean frequency offset from the local oscillator clock
            in parts per billion during the first interval."
     ::= { aluPortAcrClkStatsEntry 11 }

aluCurrent1MinFreqOffsetStdDevPpb OBJECT-TYPE
     SYNTAX  Unsigned32
     MAX-ACCESS  read-only
     STATUS  current
     DESCRIPTION
            "The standard deviation of the frequency offset from the
            local oscillator clock in nano seconds during the first interval."
     ::= { aluPortAcrClkStatsEntry 12 }

--
--  Port ACR Clock Stats Short Interval Table
--
aluPortAcrClkStatsShortIntervalTable OBJECT-TYPE
     SYNTAX  SEQUENCE OF AluPortAcrClkStatsShortIntervalEntry
     MAX-ACCESS  not-accessible
     STATUS  current
     DESCRIPTION
            "The Port ACR Clock Interval Table contains various
            statistics collected by each adaptively timed port
            over the previous 15 minutes. The past 15 minutes are
            broken into 15 1 minute intervals.  Each
            row in this table represents one such interval
            (identified by aluAcrClkIntervalNumber)."
     ::= { aluPortStatsObjs 3 }

aluPortAcrClkStatsShortIntervalEntry OBJECT-TYPE
     SYNTAX  AluPortAcrClkStatsShortIntervalEntry
     MAX-ACCESS  not-accessible
     STATUS  current
     DESCRIPTION
            "An entry in the Port ACR Clock Interval table."
    INDEX   { tmnxChassisIndex, tmnxPortPortID, aluIntervalNumber}
     ::= { aluPortAcrClkStatsShortIntervalTable 1 }

AluPortAcrClkStatsShortIntervalEntry ::=
     SEQUENCE {
         aluIntervalNumber              INTEGER,
         aluIntervalValidData           TruthValue,
         aluIntervalUpdateTime          TimeStamp,
         aluIntervalPhaseErrorMeanPpb   Integer32,
         aluIntervalPhaseErrorStdDevNs  Unsigned32,
         aluIntervalPhaseErrorMeanNs    Integer32,
         aluIntervalFreqOffsetMeanPpb   Integer32,
         aluIntervalFreqOffsetStdDevPpb Unsigned32
}

aluIntervalNumber OBJECT-TYPE
     SYNTAX  INTEGER (1..15)
     MAX-ACCESS  read-only
     STATUS  current
     DESCRIPTION
            "A number between 1 and 15, where 1 is the most
            recently completed 1 minute interval and 15 is
            the 1 minutes interval completed 14 minutes prior
            to interval 1."
     ::= { aluPortAcrClkStatsShortIntervalEntry 1 }

aluIntervalValidData OBJECT-TYPE
     SYNTAX TruthValue
     MAX-ACCESS read-only
     STATUS current
     DESCRIPTION
            "This variable indicates if the data for this
            interval is valid."
     ::= { aluPortAcrClkStatsShortIntervalEntry 2 }

aluIntervalUpdateTime OBJECT-TYPE
    SYNTAX      TimeStamp
    MAX-ACCESS  read-only
    STATUS      current
    DESCRIPTION
        "The update time of the ACR interval statistics"
    ::= { aluPortAcrClkStatsShortIntervalEntry 3 }

aluIntervalPhaseErrorMeanPpb OBJECT-TYPE
     SYNTAX  Integer32
     MAX-ACCESS  read-only
     STATUS  current
     DESCRIPTION
            "The mean phase error from the local oscillator clock
            in parts per billion during the interval."
     ::= { aluPortAcrClkStatsShortIntervalEntry 4 }

aluIntervalPhaseErrorStdDevNs OBJECT-TYPE
     SYNTAX  Unsigned32
     MAX-ACCESS  read-only
     STATUS  current
     DESCRIPTION
            "The standard deviation of the phase error from the local
            oscillator clock in nano seconds during the interval."
     ::= { aluPortAcrClkStatsShortIntervalEntry 5 }

aluIntervalPhaseErrorMeanNs OBJECT-TYPE
     SYNTAX  Integer32
     MAX-ACCESS  read-only
     STATUS  current
     DESCRIPTION
            "The mean of the phase error from the local
            oscillator clock in nano seconds during the interval."
     ::= { aluPortAcrClkStatsShortIntervalEntry 6 }

aluIntervalFreqOffsetMeanPpb OBJECT-TYPE
     SYNTAX  Integer32
     MAX-ACCESS  read-only
     STATUS  current
     DESCRIPTION
            "The mean frequency offset from the local oscillator clock
            in parts per billion during the interval."
     ::= { aluPortAcrClkStatsShortIntervalEntry 7 }

aluIntervalFreqOffsetStdDevPpb OBJECT-TYPE
     SYNTAX  Unsigned32
     MAX-ACCESS  read-only
     STATUS  current
     DESCRIPTION
            "The standard deviation of the frequency offset from the
            local oscillator clock in nano seconds during the interval."
     ::= { aluPortAcrClkStatsShortIntervalEntry 8 }

--
--  Network Port Ingress Control Stats Table
--
aluPortNetIngressControlStatsTable OBJECT-TYPE
    SYNTAX      SEQUENCE OF AluPortNetIngressControlStatsEntry
    MAX-ACCESS  not-accessible
    STATUS      current
    DESCRIPTION
        "Defines the Nokia SAR series port ingress control statistics
        table for providing, via SNMP, the capability of retrieving the ingress
        control traffic statistics for ports in network or hybrid modes.
        This table is not applicable to ports in access mode."
    ::= { aluPortStatsObjs 4 }

aluPortNetIngressControlStatsEntry  OBJECT-TYPE
    SYNTAX      AluPortNetIngressControlStatsEntry
    MAX-ACCESS  not-accessible
    STATUS      current
    DESCRIPTION
        "Defines an entry in aluPortNetIngressControlStatsTable. Entries are
         created and deleted by the system depending port configuration."
    INDEX   { tmnxChassisIndex, tmnxPortPortID }
    ::= { aluPortNetIngressControlStatsTable 1 }

AluPortNetIngressControlStatsEntry ::=
    SEQUENCE {
        aluPortNetIngressControlFwdPkts        Counter64,
        aluPortNetIngressControlFwdOcts        Counter64,
        aluPortNetIngressControlDroPkts        Counter64,
        aluPortNetIngressControlDroOcts        Counter64
    }

aluPortNetIngressControlFwdPkts OBJECT-TYPE
    SYNTAX      Counter64
    MAX-ACCESS  read-only
    STATUS      current
    DESCRIPTION
        "aluPortNetIngressControlFwdPkts indicates the number of
         ingress control packets forwarded on this port."
    ::= { aluPortNetIngressControlStatsEntry 1 }

aluPortNetIngressControlFwdOcts OBJECT-TYPE
    SYNTAX      Counter64
    MAX-ACCESS  read-only
    STATUS      current
    DESCRIPTION
        "aluPortNetIngressControlFwdOcts indicates the number of
         ingress control octets forwarded on this port."
    ::= { aluPortNetIngressControlStatsEntry 2 }

aluPortNetIngressControlDroPkts OBJECT-TYPE
    SYNTAX      Counter64
    MAX-ACCESS  read-only
    STATUS      current
    DESCRIPTION
        "aluPortNetIngressControlDroPkts indicates the number of
         ingress control packets dropped on this port."
    ::= { aluPortNetIngressControlStatsEntry 3 }

aluPortNetIngressControlDroOcts OBJECT-TYPE
    SYNTAX      Counter64
    MAX-ACCESS  read-only
    STATUS      current
    DESCRIPTION
        "aluPortNetIngressControlDroOcts indicates the number of
         ingress control octets dropped on this port."
    ::= { aluPortNetIngressControlStatsEntry 4 }

--
--  Network Port Egress Control Stats Table
--
aluPortNetEgressControlStatsTable OBJECT-TYPE
    SYNTAX      SEQUENCE OF AluPortNetEgressControlStatsEntry
    MAX-ACCESS  not-accessible
    STATUS      current
    DESCRIPTION
        "Defines the Nokia SAR series port egress control statistics
         table for providing, via SNMP, the capability of retrieving the egress
         control traffic statistics for ports in network or hybrid modes."
    ::= { aluPortStatsObjs 5 }

aluPortNetEgressControlStatsEntry  OBJECT-TYPE
    SYNTAX      AluPortNetEgressControlStatsEntry
    MAX-ACCESS  not-accessible
    STATUS      current
    DESCRIPTION
        "Defines an entry in aluPortNetEgressControlStatsTable. Entries are
         created and deleted by the system depending port configuration."
    INDEX   { tmnxChassisIndex, tmnxPortPortID }
    ::= { aluPortNetEgressControlStatsTable 1 }

AluPortNetEgressControlStatsEntry ::=
    SEQUENCE {
        aluPortNetEgressControlFwdPkts        Counter64,
        aluPortNetEgressControlFwdOcts        Counter64,
        aluPortNetEgressControlDroPkts        Counter64,
        aluPortNetEgressControlDroOcts        Counter64
    }

aluPortNetEgressControlFwdPkts OBJECT-TYPE
    SYNTAX      Counter64
    MAX-ACCESS  read-only
    STATUS      current
    DESCRIPTION
        "aluPortNetEgressControlFwdPkts indicates the number of
         egress control packets forwarded on this port."
    ::= { aluPortNetEgressControlStatsEntry 1 }

aluPortNetEgressControlFwdOcts OBJECT-TYPE
    SYNTAX      Counter64
    MAX-ACCESS  read-only
    STATUS      current
    DESCRIPTION
        "aluPortNetEgressControlFwdOcts indicates the number of
         egress control octets forwarded on this port."
    ::= { aluPortNetEgressControlStatsEntry 2 }

aluPortNetEgressControlDroPkts OBJECT-TYPE
    SYNTAX      Counter64
    MAX-ACCESS  read-only
    STATUS      current
    DESCRIPTION
        "aluPortNetEgressControlDroPkts indicates the number of
         egress control packets dropped on this port."
    ::= { aluPortNetEgressControlStatsEntry 3 }

aluPortNetEgressControlDroOcts OBJECT-TYPE
    SYNTAX      Counter64
    MAX-ACCESS  read-only
    STATUS      current
    DESCRIPTION
        "aluPortNetEgressControlDroOcts indicates the number of
         egress control octets dropped on this port."
    ::= { aluPortNetEgressControlStatsEntry 4 }

--
-- ALU GPON Port Current Interval Stats Table
--
aluGponPortCurrentTable  OBJECT-TYPE
    SYNTAX      SEQUENCE OF AluGponPortCurrentEntry
    MAX-ACCESS  not-accessible
    STATUS      current
    DESCRIPTION
        "The aluGponPortCurrentTable contains various
         statistics being collected from the ONT for the current 15
         minute interval."
     ::= { aluPortStatsObjs 6 }

aluGponPortCurrentEntry OBJECT-TYPE
    SYNTAX      AluGponPortCurrentEntry
    MAX-ACCESS  not-accessible
    STATUS      current
    DESCRIPTION
        "Defines an entry in aluGponPortCurrentTable. Entries
         are created and deleted by the system depending on port
         configuration."
     INDEX      { tmnxChassisIndex, tmnxPortPortID }
     ::= { aluGponPortCurrentTable 1 }

AluGponPortCurrentEntry ::=
    SEQUENCE {
        aluGponPortCurrentLastUpdTime       TimeStamp,
        aluGponPortCurrentPMEnabled            TruthValue,
        aluGponPortCurrentTxFrames             Counter32,
        aluGponPortCurrentRxFrames             Counter32,
        aluGponPortCurrentTxBytes              Counter32,
        aluGponPortCurrentRxBytes              Counter32,
        aluGponPortCurrentDropFrsUp            Counter32,
        aluGponPortCurrentDropFrsDn            Counter32,
        aluGponPortCurrentTxFrsMcast           Counter32,
        aluGponPortCurrentRxFrsMcast           Counter32,
        aluGponPortCurrentFCSEs                Counter32,
        aluGponPortCurrentECs                  Counter32,
        aluGponPortCurrentLCs                  Counter32,
        aluGponPortCurrentFTLs                 Counter32,
        aluGponPortCurrentRBOs                 Counter32,
        aluGponPortCurrentTBOs                 Counter32,
        aluGponPortCurrentSCFs                 Counter32,
        aluGponPortCurrentMCFs                 Counter32,
        aluGponPortCurrentSQEs                 Counter32,
        aluGponPortCurrentDTs                  Counter32,
        aluGponPortCurrentIMTEs                Counter32,
        aluGponPortCurrentCSEs                 Counter32,
        aluGponPortCurrentAEs                  Counter32,
        aluGponPortCurrentIMREs                Counter32,
        aluGponPortCurrentLostFragsDn          Counter32,
        aluGponPortCurrentLostFragsUp          Counter32,
        aluGponPortCurrentRxFrags              Counter32,
        aluGponPortCurrentRxBlocks             Counter32,
        aluGponPortCurrentTxBlocks             Counter32,
        aluGponPortCurrentTxFrags              Counter32,
        aluGponPortCurrentBadHeaders           Counter32
    }

aluGponPortCurrentLastUpdTime OBJECT-TYPE
        SYNTAX        TimeStamp
        MAX-ACCESS    read-only
        STATUS        current
        DESCRIPTION
                "The last time at which this data was collected."
        ::= { aluGponPortCurrentEntry 1 }

aluGponPortCurrentPMEnabled  OBJECT-TYPE
        SYNTAX        TruthValue
        MAX-ACCESS    read-only
        STATUS        current
        DESCRIPTION
                "Indicates whether or not PM Collection has been enabled on the ONT."
        ::= { aluGponPortCurrentEntry 2 }

aluGponPortCurrentTxFrames  OBJECT-TYPE
        SYNTAX        Counter32
        MAX-ACCESS    read-only
        STATUS        current
        DESCRIPTION
                "A count of Transmitted Ethernet Frames. "
        ::= { aluGponPortCurrentEntry 3 }

aluGponPortCurrentRxFrames  OBJECT-TYPE
        SYNTAX        Counter32
        MAX-ACCESS    read-only
        STATUS        current
        DESCRIPTION
                "A count of Received Ethernet Frames. "
        ::= { aluGponPortCurrentEntry 4 }

aluGponPortCurrentTxBytes  OBJECT-TYPE
        SYNTAX        Counter32
        MAX-ACCESS    read-only
        STATUS        current
        DESCRIPTION
                "A count of Transmitted Ethernet Bytes. "
        ::= { aluGponPortCurrentEntry 5 }

aluGponPortCurrentRxBytes  OBJECT-TYPE
        SYNTAX        Counter32
        MAX-ACCESS    read-only
        STATUS        current
        DESCRIPTION
                "A count of Received Ethernet Bytes. "
        ::= { aluGponPortCurrentEntry 6 }

aluGponPortCurrentDropFrsUp  OBJECT-TYPE
        SYNTAX        Counter32
        MAX-ACCESS    read-only
        STATUS        current
        DESCRIPTION
                "A count of Dropped Frames Upstream. "
        ::= { aluGponPortCurrentEntry 7 }

aluGponPortCurrentDropFrsDn  OBJECT-TYPE
        SYNTAX        Counter32
        MAX-ACCESS    read-only
        STATUS        current
        DESCRIPTION
                "A count of Dropped Frames Downstream. "
        ::= { aluGponPortCurrentEntry 8 }

aluGponPortCurrentTxFrsMcast  OBJECT-TYPE
        SYNTAX        Counter32
        MAX-ACCESS    read-only
        STATUS        current
        DESCRIPTION
                "A count of Transmitted Multicast Ethernet Frames. "
        ::= { aluGponPortCurrentEntry 9 }

aluGponPortCurrentRxFrsMcast  OBJECT-TYPE
        SYNTAX        Counter32
        MAX-ACCESS    read-only
        STATUS        current
        DESCRIPTION
                "A count of Received Multicast Ethernet Frames. "
        ::= { aluGponPortCurrentEntry 10 }

aluGponPortCurrentFCSEs  OBJECT-TYPE
        SYNTAX        Counter32
        MAX-ACCESS    read-only
        STATUS        current
        DESCRIPTION
                "A count of Frame Check Sequence(FCS)Errors."
        ::= { aluGponPortCurrentEntry 11 }

aluGponPortCurrentECs  OBJECT-TYPE
        SYNTAX        Counter32
        MAX-ACCESS    read-only
        STATUS        current
        DESCRIPTION
                "A count of Excessive Collisions."
        ::= { aluGponPortCurrentEntry 12 }

aluGponPortCurrentLCs  OBJECT-TYPE
        SYNTAX        Counter32
        MAX-ACCESS    read-only
        STATUS        current
        DESCRIPTION
                "A count of Late Collisions."
        ::= { aluGponPortCurrentEntry 13 }

aluGponPortCurrentFTLs  OBJECT-TYPE
        SYNTAX        Counter32
        MAX-ACCESS    read-only
        STATUS        current
        DESCRIPTION
                "A count of Frames that are Too Long."
        ::= { aluGponPortCurrentEntry 14 }

aluGponPortCurrentRBOs  OBJECT-TYPE
        SYNTAX        Counter32
        MAX-ACCESS    read-only
        STATUS        current
        DESCRIPTION
                "A count of Receive Buffer Overflows."
        ::= { aluGponPortCurrentEntry 15 }

aluGponPortCurrentTBOs  OBJECT-TYPE
        SYNTAX        Counter32
        MAX-ACCESS    read-only
        STATUS        current
        DESCRIPTION
                "A count of Transmit Buffer Overflows."
        ::= { aluGponPortCurrentEntry 16 }

aluGponPortCurrentSCFs  OBJECT-TYPE
        SYNTAX        Counter32
        MAX-ACCESS    read-only
        STATUS        current
        DESCRIPTION
                "A count of successfully transmitted
                 Single Collision Frames."
        ::= { aluGponPortCurrentEntry 17 }

aluGponPortCurrentMCFs  OBJECT-TYPE
        SYNTAX        Counter32
        MAX-ACCESS    read-only
        STATUS        current
        DESCRIPTION
                "A count of successfully transmitted
                 Multiple Collision Frames."
        ::= { aluGponPortCurrentEntry 18 }

aluGponPortCurrentSQEs  OBJECT-TYPE
        SYNTAX        Counter32
        MAX-ACCESS    read-only
        STATUS        current
        DESCRIPTION
                "A count of SQE Test Error messages generated."
        ::= { aluGponPortCurrentEntry 19 }

aluGponPortCurrentDTs  OBJECT-TYPE
        SYNTAX        Counter32
        MAX-ACCESS    read-only
        STATUS        current
        DESCRIPTION
                "A count of frames delayed due to Deferred
                 Transmission."
        ::= { aluGponPortCurrentEntry 20 }

aluGponPortCurrentIMTEs  OBJECT-TYPE
        SYNTAX        Counter32
        MAX-ACCESS    read-only
        STATUS        current
        DESCRIPTION
                "A count of unsuccessfully transmitted frames
                 due to Internal MAC Transmit Error."
        ::= { aluGponPortCurrentEntry 21 }

aluGponPortCurrentCSEs  OBJECT-TYPE
        SYNTAX        Counter32
        MAX-ACCESS    read-only
        STATUS        current
        DESCRIPTION
                "A count of Carrier Sense Errors."
        ::= { aluGponPortCurrentEntry 22 }

aluGponPortCurrentAEs  OBJECT-TYPE
        SYNTAX        Counter32
        MAX-ACCESS    read-only
        STATUS        current
        DESCRIPTION
                "A count of frames having Alignment Errors."
        ::= { aluGponPortCurrentEntry 23 }

aluGponPortCurrentIMREs  OBJECT-TYPE
        SYNTAX        Counter32
        MAX-ACCESS    read-only
        STATUS        current
        DESCRIPTION
                "A count of unsuccessfully received frames
                 due to Internal MAC Receive Error."
        ::= { aluGponPortCurrentEntry 24 }

aluGponPortCurrentLostFragsDn  OBJECT-TYPE
        SYNTAX        Counter32
        MAX-ACCESS    read-only
        STATUS        current
        DESCRIPTION
                "A count of Lost GEM Fragments (downstream). "
        ::= { aluGponPortCurrentEntry 25 }

aluGponPortCurrentLostFragsUp  OBJECT-TYPE
        SYNTAX        Counter32
        MAX-ACCESS    read-only
        STATUS        current
        DESCRIPTION
                "A count of Lost GEM Fragments (upstream). "
        ::= { aluGponPortCurrentEntry 26 }

aluGponPortCurrentRxFrags  OBJECT-TYPE
        SYNTAX        Counter32
        MAX-ACCESS    read-only
        STATUS        current
        DESCRIPTION
                "A count of Received GEM Fragments. "
        ::= { aluGponPortCurrentEntry 27 }


aluGponPortCurrentRxBlocks  OBJECT-TYPE
        SYNTAX        Counter32
        MAX-ACCESS    read-only
        STATUS        current
        DESCRIPTION
                "A count of Received GEM Blocks. "
        ::= { aluGponPortCurrentEntry 28 }


aluGponPortCurrentTxBlocks  OBJECT-TYPE
        SYNTAX        Counter32
        MAX-ACCESS    read-only
        STATUS        current
        DESCRIPTION
                "A count of Transmitted GEM Blocks. "
        ::= { aluGponPortCurrentEntry 29 }

aluGponPortCurrentTxFrags  OBJECT-TYPE
        SYNTAX        Counter32
        MAX-ACCESS    read-only
        STATUS        current
        DESCRIPTION
                "A count of Transmitted GEM Fragments. "
        ::= { aluGponPortCurrentEntry 30 }

aluGponPortCurrentBadHeaders  OBJECT-TYPE
        SYNTAX        Counter32
        MAX-ACCESS    read-only
        STATUS        current
        DESCRIPTION
                "A count of Received GEM Headers that are bad. "
        ::= { aluGponPortCurrentEntry 31 }


--
-- ALU GPON Port Previous Interval Stats Table
--
aluGponPortPreviousTable  OBJECT-TYPE
    SYNTAX      SEQUENCE OF AluGponPortPreviousEntry
    MAX-ACCESS  not-accessible
    STATUS      current
    DESCRIPTION
        "The aluGponPortPreviousTable contains various
        statistics that were collected during the previous 15 minute
        interval."
     ::= { aluPortStatsObjs 7 }

aluGponPortPreviousEntry OBJECT-TYPE
    SYNTAX      AluGponPortPreviousEntry
    MAX-ACCESS  not-accessible
    STATUS      current
    DESCRIPTION
        "Defines an entry in aluGponPortPreviousTable. Entries
         are created and deleted by the system depending on port
         configuration."
     INDEX      { tmnxChassisIndex, tmnxPortPortID }
     ::= { aluGponPortPreviousTable 1 }

AluGponPortPreviousEntry ::=
    SEQUENCE {
        aluGponPortPreviousLastUpdTime          TimeStamp,
        aluGponPortPreviousPMEnabled            TruthValue,
        aluGponPortPreviousTxFrames             Counter32,
        aluGponPortPreviousRxFrames             Counter32,
        aluGponPortPreviousTxBytes              Counter32,
        aluGponPortPreviousRxBytes              Counter32,
        aluGponPortPreviousDropFrsUp            Counter32,
        aluGponPortPreviousDropFrsDn            Counter32,
        aluGponPortPreviousTxFrsMcast           Counter32,
        aluGponPortPreviousRxFrsMcast           Counter32,
        aluGponPortPreviousFCSEs                Counter32,
        aluGponPortPreviousECs                  Counter32,
        aluGponPortPreviousLCs                  Counter32,
        aluGponPortPreviousFTLs                 Counter32,
        aluGponPortPreviousRBOs                 Counter32,
        aluGponPortPreviousTBOs                 Counter32,
        aluGponPortPreviousSCFs                 Counter32,
        aluGponPortPreviousMCFs                 Counter32,
        aluGponPortPreviousSQEs                 Counter32,
        aluGponPortPreviousDTs                  Counter32,
        aluGponPortPreviousIMTEs                Counter32,
        aluGponPortPreviousCSEs                 Counter32,
        aluGponPortPreviousAEs                  Counter32,
        aluGponPortPreviousIMREs                Counter32,
        aluGponPortPreviousLostFragsDn          Counter32,
        aluGponPortPreviousLostFragsUp          Counter32,
        aluGponPortPreviousRxFrags              Counter32,
        aluGponPortPreviousRxBlocks             Counter32,
        aluGponPortPreviousTxBlocks             Counter32,
        aluGponPortPreviousTxFrags              Counter32,
        aluGponPortPreviousBadHeaders           Counter32
    }

aluGponPortPreviousLastUpdTime OBJECT-TYPE
        SYNTAX        TimeStamp
        MAX-ACCESS    read-only
        STATUS        current
        DESCRIPTION
                "The last time at which this data was collected."
        ::= { aluGponPortPreviousEntry 1 }

aluGponPortPreviousPMEnabled  OBJECT-TYPE
        SYNTAX        TruthValue
        MAX-ACCESS    read-only
        STATUS        current
        DESCRIPTION
                "Indicates whether or not PM Collection has been enabled on the ONT."
        ::= { aluGponPortPreviousEntry 2 }

aluGponPortPreviousTxFrames  OBJECT-TYPE
        SYNTAX        Counter32
        MAX-ACCESS    read-only
        STATUS        current
        DESCRIPTION
                "A count of Transmitted Ethernet Frames. "
        ::= { aluGponPortPreviousEntry 3 }

aluGponPortPreviousRxFrames  OBJECT-TYPE
        SYNTAX        Counter32
        MAX-ACCESS    read-only
        STATUS        current
        DESCRIPTION
                "A count of Received Ethernet Frames. "
        ::= { aluGponPortPreviousEntry 4 }

aluGponPortPreviousTxBytes  OBJECT-TYPE
        SYNTAX        Counter32
        MAX-ACCESS    read-only
        STATUS        current
        DESCRIPTION
                "A count of Transmitted Ethernet Bytes. "
        ::= { aluGponPortPreviousEntry 5 }

aluGponPortPreviousRxBytes  OBJECT-TYPE
        SYNTAX        Counter32
        MAX-ACCESS    read-only
        STATUS        current
        DESCRIPTION
                "A count of Received Ethernet Bytes. "
        ::= { aluGponPortPreviousEntry 6 }

aluGponPortPreviousDropFrsUp  OBJECT-TYPE
        SYNTAX        Counter32
        MAX-ACCESS    read-only
        STATUS        current
        DESCRIPTION
                "A count of Dropped Frames Upstream. "
        ::= { aluGponPortPreviousEntry 7 }

aluGponPortPreviousDropFrsDn  OBJECT-TYPE
        SYNTAX        Counter32
        MAX-ACCESS    read-only
        STATUS        current
        DESCRIPTION
                "A count of Dropped Frames Downstream. "
        ::= { aluGponPortPreviousEntry 8 }

aluGponPortPreviousTxFrsMcast  OBJECT-TYPE
        SYNTAX        Counter32
        MAX-ACCESS    read-only
        STATUS        current
        DESCRIPTION
                "A count of Transmitted Multicast Ethernet Frames. "
        ::= { aluGponPortPreviousEntry 9 }

aluGponPortPreviousRxFrsMcast  OBJECT-TYPE
        SYNTAX        Counter32
        MAX-ACCESS    read-only
        STATUS        current
        DESCRIPTION
                "A count of Received Multicast Ethernet Frames. "
        ::= { aluGponPortPreviousEntry 10 }

aluGponPortPreviousFCSEs  OBJECT-TYPE
        SYNTAX        Counter32
        MAX-ACCESS    read-only
        STATUS        current
        DESCRIPTION
                "A count of Frame Check Sequence(FCS)Errors."
        ::= { aluGponPortPreviousEntry 11 }

aluGponPortPreviousECs  OBJECT-TYPE
        SYNTAX        Counter32
        MAX-ACCESS    read-only
        STATUS        current
        DESCRIPTION
                "A count of Excessive Collisions."
        ::= { aluGponPortPreviousEntry 12 }

aluGponPortPreviousLCs  OBJECT-TYPE
        SYNTAX        Counter32
        MAX-ACCESS    read-only
        STATUS        current
        DESCRIPTION
                "A count of Late Collisions."
        ::= { aluGponPortPreviousEntry 13 }

aluGponPortPreviousFTLs  OBJECT-TYPE
        SYNTAX        Counter32
        MAX-ACCESS    read-only
        STATUS        current
        DESCRIPTION
                "A count of Frames that are Too Long."
        ::= { aluGponPortPreviousEntry 14 }

aluGponPortPreviousRBOs  OBJECT-TYPE
        SYNTAX        Counter32
        MAX-ACCESS    read-only
        STATUS        current
        DESCRIPTION
                "A count of Receive Buffer Overflows."
        ::= { aluGponPortPreviousEntry 15 }

aluGponPortPreviousTBOs  OBJECT-TYPE
        SYNTAX        Counter32
        MAX-ACCESS    read-only
        STATUS        current
        DESCRIPTION
                "A count of Transmit Buffer Overflows."
        ::= { aluGponPortPreviousEntry 16 }

aluGponPortPreviousSCFs  OBJECT-TYPE
        SYNTAX        Counter32
        MAX-ACCESS    read-only
        STATUS        current
        DESCRIPTION
                "A count of successfully transmitted
                 Single Collision Frames."
        ::= { aluGponPortPreviousEntry 17 }

aluGponPortPreviousMCFs  OBJECT-TYPE
        SYNTAX        Counter32
        MAX-ACCESS    read-only
        STATUS        current
        DESCRIPTION
                "A count of successfully transmitted
                 Multiple Collision Frames."
        ::= { aluGponPortPreviousEntry 18 }

aluGponPortPreviousSQEs  OBJECT-TYPE
        SYNTAX        Counter32
        MAX-ACCESS    read-only
        STATUS        current
        DESCRIPTION
                "A count of SQE Test Error messages generated."
        ::= { aluGponPortPreviousEntry 19 }

aluGponPortPreviousDTs  OBJECT-TYPE
        SYNTAX        Counter32
        MAX-ACCESS    read-only
        STATUS        current
        DESCRIPTION
                "A count of frames delayed due to Deferred
                 Transmission."
        ::= { aluGponPortPreviousEntry 20 }

aluGponPortPreviousIMTEs  OBJECT-TYPE
        SYNTAX        Counter32
        MAX-ACCESS    read-only
        STATUS        current
        DESCRIPTION
                "A count of unsuccessfully transmitted frames
                 due to Internal MAC Transmit Error."
        ::= { aluGponPortPreviousEntry 21 }

aluGponPortPreviousCSEs  OBJECT-TYPE
        SYNTAX        Counter32
        MAX-ACCESS    read-only
        STATUS        current
        DESCRIPTION
                "A count of Carrier Sense Errors."
        ::= { aluGponPortPreviousEntry 22 }

aluGponPortPreviousAEs  OBJECT-TYPE
        SYNTAX        Counter32
        MAX-ACCESS    read-only
        STATUS        current
        DESCRIPTION
                "A count of frames having Alignment Errors."
        ::= { aluGponPortPreviousEntry 23 }

aluGponPortPreviousIMREs  OBJECT-TYPE
        SYNTAX        Counter32
        MAX-ACCESS    read-only
        STATUS        current
        DESCRIPTION
                "A count of unsuccessfully received frames
                 due to Internal MAC Receive Error."
        ::= { aluGponPortPreviousEntry 24 }

aluGponPortPreviousLostFragsDn  OBJECT-TYPE
        SYNTAX        Counter32
        MAX-ACCESS    read-only
        STATUS        current
        DESCRIPTION
                "A count of Lost GEM Fragments (downstream). "
        ::= { aluGponPortPreviousEntry 25 }

aluGponPortPreviousLostFragsUp  OBJECT-TYPE
        SYNTAX        Counter32
        MAX-ACCESS    read-only
        STATUS        current
        DESCRIPTION
                "A count of Lost GEM Fragments (upstream). "
        ::= { aluGponPortPreviousEntry 26 }

aluGponPortPreviousRxFrags  OBJECT-TYPE
        SYNTAX        Counter32
        MAX-ACCESS    read-only
        STATUS        current
        DESCRIPTION
                "A count of Received GEM Fragments. "
        ::= { aluGponPortPreviousEntry 27 }


aluGponPortPreviousRxBlocks  OBJECT-TYPE
        SYNTAX        Counter32
        MAX-ACCESS    read-only
        STATUS        current
        DESCRIPTION
                "A count of Received GEM Blocks. "
        ::= { aluGponPortPreviousEntry 28 }


aluGponPortPreviousTxBlocks  OBJECT-TYPE
        SYNTAX        Counter32
        MAX-ACCESS    read-only
        STATUS        current
        DESCRIPTION
                "A count of Transmitted GEM Blocks. "
        ::= { aluGponPortPreviousEntry 29 }

aluGponPortPreviousTxFrags  OBJECT-TYPE
        SYNTAX        Counter32
        MAX-ACCESS    read-only
        STATUS        current
        DESCRIPTION
                "A count of Transmitted GEM Fragments. "
        ::= { aluGponPortPreviousEntry 30 }

aluGponPortPreviousBadHeaders  OBJECT-TYPE
        SYNTAX        Counter32
        MAX-ACCESS    read-only
        STATUS        current
        DESCRIPTION
                "A count of Received GEM Headers that are bad. "
        ::= { aluGponPortPreviousEntry 31 }

--
-- ALU XDSL Line Stats Table
--
aluXdslLineStatsTable OBJECT-TYPE
    SYNTAX  SEQUENCE OF AluXdslLineStatsEntry
    MAX-ACCESS  not-accessible
    STATUS      current
    DESCRIPTION
        "The aluXdslLineStatsTable contains various statistics being collected
         from the BCM6519 for each physical XDSL line on the 'XDSL'
         tmnxPortType port."
     ::= { aluPortStatsObjs 8 }

aluXdslLineStatsEntry OBJECT-TYPE
    SYNTAX AluXdslLineStatsEntry
    MAX-ACCESS  not-accessible
    STATUS      current
    DESCRIPTION
        "Defines an entry in aluXdslLineStatsTable. Entries
         are created and deleted by the system depending on port
         configuration."
    INDEX       { tmnxChassisIndex, tmnxPortPortID, aluXdslLineID }
    ::= { aluXdslLineStatsTable 1 }

AluXdslLineStatsEntry ::=
    SEQUENCE {
        aluXdslLineStatsNearEndFECS                     Counter64,
        aluXdslLineStatsNearEndLOSS                     Counter64,
        aluXdslLineStatsNearEndES                       Counter64,
        aluXdslLineStatsNearEndSES                      Counter64,
        aluXdslLineStatsNearEndUAS                      Counter64,
        aluXdslLineStatsNearEndAS                       Counter64,
        aluXdslLineStatsNearEndLOFS                     Counter64,
        aluXdslLineStatsNearEndLPRS                     Counter64,
        aluXdslLineStatsNearEndLEFTRS                   Counter64,
        aluXdslLineStatsFarEndFECS                      Counter64,
        aluXdslLineStatsFarEndLOSS                      Counter64,
        aluXdslLineStatsFarEndES                        Counter64,
        aluXdslLineStatsFarEndSES                       Counter64,
        aluXdslLineStatsFarEndUAS                       Counter64,
        aluXdslLineStatsFarEndAS                        Counter64,
        aluXdslLineStatsFarEndLOFS                      Counter64,
        aluXdslLineStatsFarEndLPRS                      Counter64,
        aluXdslLineStatsFarEndLEFTRS                    Counter64,
        aluXdslLineStatsUpTime                          Unsigned32
    }

aluXdslLineStatsNearEndFECS OBJECT-TYPE
    SYNTAX        Counter64
    MAX-ACCESS    read-only
    STATUS        current
    DESCRIPTION
        "A count of Forward Error Correction Seconds - Near-End:
         Count of 1-second intervals with one or more FEC corrections on
         either one of the active latencies at the near-end."
    ::= { aluXdslLineStatsEntry 1 }

aluXdslLineStatsNearEndLOSS OBJECT-TYPE
    SYNTAX        Counter64
    MAX-ACCESS    read-only
    STATUS        current
    DESCRIPTION
        "A count of Loss of Signal Seconds - Near-End:
         Count of 1-second intervals with one or more LOS defects present at
         the near-end."
    ::= { aluXdslLineStatsEntry 2 }

aluXdslLineStatsNearEndES OBJECT-TYPE
    SYNTAX        Counter64
    MAX-ACCESS    read-only
    STATUS        current
    DESCRIPTION
        "A count of Errored Seconds - Near-End:
         Count of 1-second intervals with one or more FEBE anomalies, or 1
         or more LOS defects, or one or more RDI defects."
    ::= { aluXdslLineStatsEntry 3 }

aluXdslLineStatsNearEndSES OBJECT-TYPE
    SYNTAX        Counter64
    MAX-ACCESS    read-only
    STATUS        current
    DESCRIPTION
        "A count of Severely Errored Seconds - Near-End:
         Count of 1-second intervals with 18 or more FEBE anomalies, or 1
         or more LOS defects, or one or more RDI defects."
    ::= { aluXdslLineStatsEntry 4 }

aluXdslLineStatsNearEndUAS OBJECT-TYPE
    SYNTAX        Counter64
    MAX-ACCESS    read-only
    STATUS        current
    DESCRIPTION
        "A count of Unavailable Seconds - Near-End:
         Count of 1-second intervals for which the ADSL line is not
         available (the line becomes unavailable at the onset of 10 continuous
         SES)."
    ::= { aluXdslLineStatsEntry 5 }

aluXdslLineStatsNearEndAS OBJECT-TYPE
    SYNTAX        Counter64
    MAX-ACCESS    read-only
    STATUS        current
    DESCRIPTION
        "A count of Available Seconds - Near-End:
         Count of 1 second intervals for which the ADSL line is available."
    ::= { aluXdslLineStatsEntry 6 }

aluXdslLineStatsNearEndLOFS OBJECT-TYPE
    SYNTAX        Counter64
    MAX-ACCESS    read-only
    STATUS        current
    DESCRIPTION
        "A count of Loss of Framing Seconds - Near-End:
         Count of 1-second intervals containing one or more SEF defects at the
         near-end."
    ::= { aluXdslLineStatsEntry 7 }

aluXdslLineStatsNearEndLPRS OBJECT-TYPE
    SYNTAX        Counter64
    MAX-ACCESS    read-only
    STATUS        current
    DESCRIPTION
        "A count of Loss of power Seconds - Near-End:
         Count of 1-second intervals containing one or more LPR defects at the
         near-end."
    ::= { aluXdslLineStatsEntry 8 }

aluXdslLineStatsNearEndLEFTRS OBJECT-TYPE
    SYNTAX        Counter64
    MAX-ACCESS    read-only
    STATUS        current
    DESCRIPTION
        "A count of Low Error-Free Troughtput Rate Seconds - Near-End."
    ::= { aluXdslLineStatsEntry 9 }

aluXdslLineStatsFarEndFECS OBJECT-TYPE
    SYNTAX        Counter64
    MAX-ACCESS    read-only
    STATUS        current
    DESCRIPTION
        "A count of Forward Error Correction Seconds - Far-End:
         Count of 1-second intervals with one or more FEC corrections on
         either one of the active latencies at the far-end."
    ::= { aluXdslLineStatsEntry 10 }

aluXdslLineStatsFarEndLOSS OBJECT-TYPE
    SYNTAX        Counter64
    MAX-ACCESS    read-only
    STATUS        current
    DESCRIPTION
        "A count of Loss of Signal Seconds - Far-End:
         Count of 1-second intervals with one or more LOS defects present at
         the far-end."
    ::= { aluXdslLineStatsEntry 11 }

aluXdslLineStatsFarEndES OBJECT-TYPE
    SYNTAX        Counter64
    MAX-ACCESS    read-only
    STATUS        current
    DESCRIPTION
        "A count of Errored Seconds - Far-End:
         Count of 1-second intervals with one or more FEBE anomalies, or 1
         or more LOS defects, or one or more RDI defects."
    ::= { aluXdslLineStatsEntry 12 }

aluXdslLineStatsFarEndSES OBJECT-TYPE
    SYNTAX        Counter64
    MAX-ACCESS    read-only
    STATUS        current
    DESCRIPTION
        "A count of Severely Errored Seconds - Far-End:
         Count of 1-second intervals with 18 or more FEBE anomalies, or 1
         or more LOS defects, or one or more RDI defects."
    ::= { aluXdslLineStatsEntry 13 }

aluXdslLineStatsFarEndUAS OBJECT-TYPE
    SYNTAX        Counter64
    MAX-ACCESS    read-only
    STATUS        current
    DESCRIPTION
        "A count of Unavailable Seconds - Far-End:
         Count of 1-second intervals for which the ADSL line is not
         available (the line becomes unavailable at the onset of 10 continuous
         SES)."
    ::= { aluXdslLineStatsEntry 14 }

aluXdslLineStatsFarEndAS OBJECT-TYPE
    SYNTAX        Counter64
    MAX-ACCESS    read-only
    STATUS        current
    DESCRIPTION
        "A count of Available Seconds - Far-End:
         Count of 1 second intervals for which the ADSL line is available."
    ::= { aluXdslLineStatsEntry 15 }

aluXdslLineStatsFarEndLOFS OBJECT-TYPE
    SYNTAX        Counter64
    MAX-ACCESS    read-only
    STATUS        current
    DESCRIPTION
        "A count of Loss of Framing Seconds - Far-End:
         Count of 1-second intervals containing one or more SEF defects at the
         far-end."
    ::= { aluXdslLineStatsEntry 16 }

aluXdslLineStatsFarEndLPRS OBJECT-TYPE
    SYNTAX        Counter64
    MAX-ACCESS    read-only
    STATUS        current
    DESCRIPTION
        "A count of Loss of power Seconds - Far-End:
         Count of 1-second intervals containing one or more LPR defects at the
         far-end."
    ::= { aluXdslLineStatsEntry 17 }

aluXdslLineStatsFarEndLEFTRS OBJECT-TYPE
    SYNTAX        Counter64
    MAX-ACCESS    read-only
    STATUS        current
    DESCRIPTION
        "A count of Low Error-Free Troughtput Rate Seconds - Far-End."
    ::= { aluXdslLineStatsEntry 18 }

aluXdslLineStatsUpTime OBJECT-TYPE
    SYNTAX        Unsigned32
    MAX-ACCESS    read-only
    STATUS        current
    DESCRIPTION
        "A count of the number of seconds already in showtime."
    ::= { aluXdslLineStatsEntry 19 }

--
-- ALU SHDSL Line Stats Table
--
aluShdslLineStatsTable OBJECT-TYPE
    SYNTAX  SEQUENCE OF AluShdslLineStatsEntry
    MAX-ACCESS  not-accessible
    STATUS      current
    DESCRIPTION
        "The aluShdslLineStatsTable contains the SHDSL Performance
         statistics being collected from the Socrate-4e for each
         physical SHDSL line on the 'SHDSL' tmnxPortType port."
     ::= { aluPortStatsObjs 9 }

aluShdslLineStatsEntry OBJECT-TYPE
    SYNTAX AluShdslLineStatsEntry
    MAX-ACCESS  not-accessible
    STATUS      current
    DESCRIPTION
        "Defines an entry in aluShdslLineStatsTable. Entries
         are created and deleted by the system depending on port
         configuration."
    INDEX       { tmnxChassisIndex, tmnxPortPortID, aluShdslLineID}
    ::= { aluShdslLineStatsTable 1 }

AluShdslLineStatsEntry ::=
    SEQUENCE {
        aluShdslLineStatsLinkLoss                 Counter64,
        aluShdslLineStatsCVError                  Counter64,
        aluShdslLineStatsES                       Counter64,
        aluShdslLineStatsSES                      Counter64,
        aluShdslLineStatsLOSWS                    Counter64,
        aluShdslLineStatsUAS                      Counter64,
        aluShdslLineStatsInvalidDataFlag          INTEGER
    }

aluShdslLineStatsLinkLoss OBJECT-TYPE
    SYNTAX        Counter64
    MAX-ACCESS    read-only
    STATUS        current
    DESCRIPTION
        "Link Loss Counter (Network Side). This counter is only valid for the
         local STU-R and is not polled by the STU-C,"
    ::= { aluShdslLineStatsEntry 2 }

aluShdslLineStatsCVError OBJECT-TYPE
    SYNTAX        Counter64
    MAX-ACCESS    read-only
    STATUS        current
    DESCRIPTION
        "Code Violation Error Counter (Network Side). It is updated every
         second when the link is active."
    ::= { aluShdslLineStatsEntry 4 }

aluShdslLineStatsES OBJECT-TYPE
    SYNTAX        Counter64
    MAX-ACCESS    read-only
    STATUS        current
    DESCRIPTION
        "Erroneous Seconds Counter (Network Side). It is updated every
         second when the link is active."
    ::= { aluShdslLineStatsEntry 5 }

aluShdslLineStatsSES OBJECT-TYPE
    SYNTAX        Counter64
    MAX-ACCESS    read-only
    STATUS        current
    DESCRIPTION
        "Severely Erroneous Seconds Counter (Network Side). It is updated every
         second when the link is active."
    ::= { aluShdslLineStatsEntry 6 }

aluShdslLineStatsLOSWS OBJECT-TYPE
    SYNTAX        Counter64
    MAX-ACCESS    read-only
    STATUS        current
    DESCRIPTION
        "LOSWS Counter (Network Side). It is updated every second when the link
         is active."
    ::= { aluShdslLineStatsEntry 7 }

aluShdslLineStatsUAS OBJECT-TYPE
    SYNTAX        Counter64
    MAX-ACCESS    read-only
    STATUS        current
    DESCRIPTION
        "Unavailable Seconds Counter (Network Side). It is updated every
         second when the link is active."
    ::= { aluShdslLineStatsEntry 8 }

aluShdslLineStatsInvalidDataFlag OBJECT-TYPE
    SYNTAX        INTEGER
    MAX-ACCESS    read-only
    STATUS        current
    DESCRIPTION
        "It indicates the validity of the PM data. It is set to 0 when the
         counters are reliable, otherwise it indicates that the
         far-end counters are not reliable."
    ::= { aluShdslLineStatsEntry 10 }

--
--  Port Control Stats Table
--
aluPortCtlStatsTable OBJECT-TYPE
    SYNTAX      SEQUENCE OF AluPortCtlStatsEntry
    MAX-ACCESS  not-accessible
    STATUS      current
    DESCRIPTION
        "Defines the Nokia SAR series port control statistics
         table for providing, via SNMP, the capability of retrieving the
         detailed control packet statistics for ports in access modes.
         This table is not applicable to ports in network or hybrid mode."
    ::= { aluPortStatsObjs 10 }

aluPortCtlStatsEntry    OBJECT-TYPE
    SYNTAX      AluPortCtlStatsEntry
    MAX-ACCESS  not-accessible
    STATUS      current
    DESCRIPTION
        "Defines an entry in aluPortCtlStatsTable. Entries are
         created and deleted by the system depending port
         configuration."
    INDEX   { tmnxChassisIndex, tmnxPortPortID }
    ::= { aluPortCtlStatsTable 1 }

AluPortCtlStatsEntry ::=
    SEQUENCE {
        aluPortAccessCtlInFwdPkts    Counter64,
        aluPortAccessCtlInFwdOcts    Counter64,
        aluPortAccessCtlInDroPkts    Counter64,
        aluPortAccessCtlInDroOcts    Counter64,
        aluPortAccessCtlEgrFwdPkts   Counter64,
        aluPortAccessCtlEgrFwdOcts   Counter64,
        aluPortAccessCtlEgrDroPkts   Counter64,
        aluPortAccessCtlEgrDroOcts   Counter64
    }

aluPortAccessCtlInFwdPkts OBJECT-TYPE
    SYNTAX      Counter64
    MAX-ACCESS  read-only
    STATUS      current
    DESCRIPTION
        "aluPortAccessCtlInFwdPkts indicates the number of CTL packets
        that get forwarded on access port ingress ."
    ::= { aluPortCtlStatsEntry 1 }

aluPortAccessCtlInFwdOcts OBJECT-TYPE
    SYNTAX      Counter64
    MAX-ACCESS  read-only
    STATUS      current
    DESCRIPTION
        "aluPortAccessCtlInFwdOcts indicates the number of CTL octets
        that get forwarded on access port ingress ."
    ::= { aluPortCtlStatsEntry 2 }

aluPortAccessCtlInDroPkts OBJECT-TYPE
    SYNTAX      Counter64
    MAX-ACCESS  read-only
    STATUS      current
    DESCRIPTION
        "aluPortAccessCtlInDroPkts indicates the number of CTL packets
        that get dropped on access port ingress ."
    ::= { aluPortCtlStatsEntry 3 }

aluPortAccessCtlInDroOcts OBJECT-TYPE
    SYNTAX      Counter64
    MAX-ACCESS  read-only
    STATUS      current
    DESCRIPTION
        "aluPortAccessCtlInDroOcts indicates the number of CTL octets
        that get dropped on access port ingress ."
    ::= { aluPortCtlStatsEntry 4 }

aluPortAccessCtlEgrFwdPkts OBJECT-TYPE
    SYNTAX      Counter64
    MAX-ACCESS  read-only
    STATUS      current
    DESCRIPTION
        "aluPortAccessCtlEgrFwdPkts indicates the number of CTL packets
        that get forwarded on access port egress ."
    ::= { aluPortCtlStatsEntry 5 }

aluPortAccessCtlEgrFwdOcts OBJECT-TYPE
    SYNTAX      Counter64
    MAX-ACCESS  read-only
    STATUS      current
    DESCRIPTION
        "aluPortAccessCtlEgrFwdOcts indicates the number of CTL octets
        that get forwarded on access port egress ."
    ::= { aluPortCtlStatsEntry 6 }

aluPortAccessCtlEgrDroPkts OBJECT-TYPE
    SYNTAX      Counter64
    MAX-ACCESS  read-only
    STATUS      current
    DESCRIPTION
        "aluPortAccessCtlEgrDroPkts indicates the number of CTL packets
        that get dropped on access port egress ."
    ::= { aluPortCtlStatsEntry 7 }

aluPortAccessCtlEgrDroOcts OBJECT-TYPE
    SYNTAX      Counter64
    MAX-ACCESS  read-only
    STATUS      current
    DESCRIPTION
        "aluPortAccessCtlEgrDroOcts indicates the number of CTL octets
        that get dropped on access port egress ."
    ::= { aluPortCtlStatsEntry 8 }



--
-- ALU Voice Port table
--
aluVoicePortTable OBJECT-TYPE
    SYNTAX      SEQUENCE OF AluVoicePortEntry
    MAX-ACCESS  not-accessible
    STATUS      current
    DESCRIPTION
        "The aluVoicePortTable has an entry for a physical Voice port."
    ::= { aluPortObjs 7 }

aluVoicePortEntry OBJECT-TYPE
    SYNTAX      AluVoicePortEntry
    MAX-ACCESS  not-accessible
    STATUS      current
    DESCRIPTION
        "Each row entry represents a physical Voice port on an
         IOM card in a chassis in the system.  Entries cannot be created
         and deleted via SNMP SET operations.  Entries in this table will
         be created automatically when the tmnxMDAAssignedType object is
         set to a Voice MDA type. The aluVoicePortEntry contains attributes
         that are unique to the Voice TmnxPortType. The
         tmnxPortPortID contains the slot, mda and port numbers encoded into it.

         For each aluVoicePortEntry, there will be a corresponding entry
         in the tmnxPortTable and the ifTable."
    INDEX       { tmnxChassisIndex, tmnxPortPortID }
    ::= { aluVoicePortTable 1 }

AluVoicePortEntry ::=
    SEQUENCE {
        aluVoicePortLastChangeTime       TimeStamp,
        aluVoicePortType                 INTEGER,
        aluVoicePortAudioWires           INTEGER,
        aluVoicePortTlpRx                AluVoicePortTlp,
        aluVoicePortTlpTx                AluVoicePortTlp,
        aluVoicePortLineBalance          INTEGER,
        aluVoicePortRingGeneration       INTEGER,
        aluVoicePortSignalingType        INTEGER
    }

aluVoicePortLastChangeTime OBJECT-TYPE
    SYNTAX      TimeStamp
    MAX-ACCESS  read-only
    STATUS      current
    DESCRIPTION
        "aluVoicePortLastChangeTime contains the sysUpTime value of the most
         recently modified writable variable in the aluVoicePortEntry row for
         this port."
    ::= { aluVoicePortEntry 1 }

aluVoicePortType           OBJECT-TYPE
    SYNTAX      INTEGER {
                    em  (1),
                    fxo (2),
                    fxs (3)
                }
    MAX-ACCESS  read-create
    STATUS      current
    DESCRIPTION
        "aluVoicePortType configures the interface-type of the physical port."
    DEFVAL      { em }
    ::= { aluVoicePortEntry 2 }

aluVoicePortAudioWires OBJECT-TYPE
    SYNTAX     INTEGER {
                notApplicable (0),
                twoWires  (1),
                fourWires (2)
            }
    MAX-ACCESS  read-create
    STATUS      current
    DESCRIPTION
        "aluVoicePortAudioWires is used to configure the number of audio wires
         for a given E&M interface.

         This object is valid for em ports only.

         twoWires is not allowed when any channel in the port trio is
         transmissionOnly.  For example, if the channel under port 1 is
         transmissionOnly, then ports 1, 2 and port 3 cannot be set to twoWires.

         To change aluVoicePortAudioWires, the port must be shutdown.
         Changes result in defaulting of aluVoicePortTlpRx and aluVoicePortTlpTx.
        "
    DEFVAL  { fourWires }
    ::= { aluVoicePortEntry 3 }

aluVoicePortTlpRx OBJECT-TYPE
    SYNTAX      AluVoicePortTlp
    UNITS       "tenths of decibels"
    MAX-ACCESS  read-create
    STATUS      current
    DESCRIPTION
        "aluVoicePortTlpRx is used to configure the receive Transmission Level
         Point level for a given voice interface. The receive TLP refers to the
         digital-to-analog level.

         The valid aluVoicePortTlpRx range for em 'fourWires' mode is -160 to
         +70.
         The valid aluVoicePortTlpRx range for em 'twoWires' mode is -100 to
         +60.
         For fxo and fxs ports:
         - valid range is -70 to 0 in 1db increments
         - default value is -30

         To change aluVoicePortTlpRx, the port must be shutdown.
        "
    DEFVAL  { 0 }
    ::= { aluVoicePortEntry 4 }

aluVoicePortTlpTx OBJECT-TYPE
    SYNTAX      AluVoicePortTlp
    UNITS       "tenths of decibels"
    MAX-ACCESS  read-create
    STATUS      current
    DESCRIPTION
        "aluVoicePortTlpTx is used to configure the transmit Transmission Level
         Point level for a given voice interface. The transmit TLP refers to the
         analog-to-digital level.

         The valid aluVoicePortTlpTx range for em 'fourWires' mode is -160 to
         +70.
         The valid aluVoicePortTlpTx range for em 'twoWires' mode is -100 to
         +60.
         For fxo and fxs ports:
         - valid range is -40 to +30 in 1db increments
         - default value is 0

         To change aluVoicePortTlpTx, the port must be shutdown.
        "
    DEFVAL  { 0 }
    ::= { aluVoicePortEntry 5 }

aluVoicePortLineBalance OBJECT-TYPE
    SYNTAX     INTEGER {
                notApplicable (0),
                short        (1),  -- less than 200 Ohms
                long         (2),  -- greater than 200 Ohms
                nominal      (3),  -- 600 Ohms
                eightHundred (4)   -- 800 Ohms//(100 Ohms+50nF)
            }
    MAX-ACCESS  read-create
    STATUS      current
    DESCRIPTION
        "The value of the object aluVoicePortLineBalance specifies the line
         balance on a given voice interface.

         This object is valid for fxo and fxs ports only.

         Valid values for fxo and fxs ports:
         nominal (default)
         eightHundred

         To change aluVoicePortLineBalance, the port must be shutdown.
        "
    ::= { aluVoicePortEntry 6 }

aluVoicePortRingGeneration OBJECT-TYPE
    SYNTAX     INTEGER {
                notApplicable (0),
                none   (1),
                freq16 (2),
                freq20 (3),
                freq25 (4)
            }
    MAX-ACCESS  read-create
    STATUS      current
    DESCRIPTION
        "The value of the object aluVoicePortRingGeneration specifies the
         frequency (in Hz) of the generated ring signal.

         This object is valid for fxs ports only.
        "
    DEFVAL  { freq16 }
    ::= { aluVoicePortEntry 7 }

aluVoicePortSignalingType OBJECT-TYPE
    SYNTAX      INTEGER {
                    notApplicable                    (0),
                    privateLineAutomaticRingdown3600 (1),  -- 3600PLAR
                    privateLineAutomaticRingdown1511 (2),  -- 1511PLAR
                    loopStart3600                    (3),  -- 3600LS
                    profileOne1511                   (4),  -- 1511Profile1
                    remoteExtension3600              (5),  -- 3600RE
                    fifteenElevenSigSel137           (6)   -- 1511SN137
                }
    MAX-ACCESS  read-create
    STATUS      current
    DESCRIPTION
        "The value of the object aluVoicePortSignalingType specifies how the
         signaling leads operate to establish a call.

         This object is valid for fxo and fxs ports only.

         privateLineAutomaticRingdown3600 - Does not involve exchange.
            When subscriber 1 goes off-hook, cadenced ringing occurs at
            subscriber 2. Subscriber 2 answers call by going off-hook.
         privateLineAutomaticRingdown1511 - same description as for 3600PLAR but
            ABCD bits differ
         loopStart3600 - Subscriber applies loop current to seize the line.
            Central office signals idle throughout the entire call and does not
            provide answer supervision.
         profileOne1511 - same as 3600LS but ABCD bits differ
         remoteExtension3600 - Subscriber seizes the line by closing loop.
            Exchange signals idle throughout the entire call and does not
            provide answer supervision.  Subscriber can apply a recall signal
            by connecting the B lead to earth.
         fifteenElevenSigSel137 - aka Exchange_transp

         Valid values for fxo ports:
         loopStart3600                    (muLaw only; default)
         profileOne1511                   ( aLaw only)
         remoteExtension3600              ( aLaw only; default)
         fifteenElevenSigSel137           ( aLaw only)

         Valid values for fxs ports:
         privateLineAutomaticRingdown3600
         privateLineAutomaticRingdown1511 ( aLaw only)
         loopStart3600                    (muLaw only; default)
         profileOne1511                   ( aLaw only)
         remoteExtension3600              ( aLaw only; default)
         fifteenElevenSigSel137           ( aLaw only)

         To change aluVoicePortSignalingType, the port must be shutdown.
        "
    ::= { aluVoicePortEntry 8 }

--
-- ALU Voice table
--
aluVoiceTable OBJECT-TYPE
    SYNTAX      SEQUENCE OF AluVoiceEntry
    MAX-ACCESS  not-accessible
    STATUS      current
    DESCRIPTION
        "aluVoiceTable has an entry for each Voice channel on an IOM card
         in each chassis in the system.
        "
    ::= { aluPortObjs 8 }

aluVoiceEntry       OBJECT-TYPE
    SYNTAX  AluVoiceEntry
    MAX-ACCESS      not-accessible
    STATUS          current
    DESCRIPTION
        "Each row entry represents a Voice channel on an IOM card
         in a chassis in the system.  Channel entries for
         voice ports can be created and deleted via SNMP SET operations.
         For each aluVoiceEntry, there will be a corresponding entry
         in the tmnxPortTable and the ifTable.
        "
    INDEX   { tmnxChassisIndex, tmnxPortPortID }
    ::= { aluVoiceTable 1 }

AluVoiceEntry ::=
SEQUENCE {
        aluVoiceRowStatus                  RowStatus,
        aluVoiceLastChangeTime             TimeStamp,
        aluVoiceType                       INTEGER,
        aluVoiceSignalingMode              INTEGER,
        aluVoiceLoopback                   INTEGER,
        aluVoiceFaultSignaling             INTEGER,
        aluVoiceSignalBitsState            OCTET STRING,
        aluVoiceClockSource                TmnxDSXClockSource,
        aluVoiceSignalingLeadE             AluVoiceSignalingLead,
        aluVoiceSignalingLeadM             AluVoiceSignalingLead,
        aluVoiceSignalingLeadsState        OCTET STRING,
        aluVoiceSignalMode                 INTEGER,
        aluVoiceCallState                  INTEGER,
        aluVoiceIncomingCallCount          Counter32,
        aluVoiceIncomingCallCountAns       Counter32,
        aluVoiceIncomingCallTime           Counter32,
        aluVoiceIncomingCallTimeAns        Counter32,
        aluVoiceOutgoingCallCount          Counter32,
        aluVoiceOutgoingCallCountAns       Counter32,
        aluVoiceOutgoingCallTime           Counter32,
        aluVoiceOutgoingCallTimeAns        Counter32,
        aluVoiceOutOfServiceTime           Counter32,
        aluVoiceIdleTime                   Counter32,
        aluVoiceTotalCallCount             Counter32,
        aluVoiceTotalCallTime              Counter32,
        aluVoiceIdleCode                   Unsigned32,
        aluVoiceSeizedCode                 Unsigned32
}

aluVoiceRowStatus    OBJECT-TYPE
    SYNTAX      RowStatus
    MAX-ACCESS  read-create
    STATUS      current
    DESCRIPTION
        "aluVoiceRowStatus controls the creation and deletion of
         row entries in the aluVoiceTable.
         For row creation, the manager has to first calculate the
         tmnxPortPortID based on the TiMOS encoding scheme.
        "
    ::= { aluVoiceEntry 1 }

aluVoiceLastChangeTime OBJECT-TYPE
    SYNTAX      TimeStamp
    MAX-ACCESS  read-only
    STATUS      current
    DESCRIPTION
        "aluVoiceLastChangeTime contains the sysUpTime value of the
         most recently modified writable variable in the
         aluVoiceEntry row for this Voice channel.
        "
    ::= { aluVoiceEntry 2 }

aluVoiceType OBJECT-TYPE
    SYNTAX      INTEGER {
                    em  (1),
                    fxo (2),
                    fxs (3)
                }
    MAX-ACCESS  read-only
    STATUS      current
    DESCRIPTION
        "aluVoiceType indicates the channel type."
    ::= { aluVoiceEntry 3 }

aluVoiceSignalingMode  OBJECT-TYPE
    SYNTAX     INTEGER {
                notApplicable    (0),
                em               (1),
                transmissionOnly (2)
            }
    MAX-ACCESS  read-create
    STATUS      current
    DESCRIPTION
        "aluVoiceSignalingMode configures the channel's signaling mode for
         E&M or transmission only.

         This object is valid for em channels only.

         transmissionOnly is not allowed when any port in the port trio is
         twoWires.  For example, if port 1 is twoWires, then the channels under
         ports 1, 2 and 3 cannot be set to transmissionOnly.

         aluVoiceSignalingMode is not allowed to differ from other channels in
         the port trio. For example, if the channel under port 1 is
         transmissionOnly, then the channels under port 2 and port 3 must also
         be transmissionOnly.

         aluVoiceSignalingMode cannot be changed if a channel-group already
         exists for the port.

         Changing to em results in defaulting of
         aluVoiceFaultSignaling, aluVoiceSignalingLeadE, aluVoiceSignalingLeadM,
         aluVoiceIdleCode and aluVoiceSeizedCode.
        "
    DEFVAL  { em }
    ::= { aluVoiceEntry 4 }

aluVoiceLoopback    OBJECT-TYPE
    SYNTAX     INTEGER {
                none            (1),
                internalAnalog  (2),
                internalDigital (3)
            }
    MAX-ACCESS  read-create
    STATUS      current
    DESCRIPTION
        "aluVoiceLoopback is used to put the port into a loopback mode.
         Only internal loopbacks are supported.

         'internalAnalog' (aka Loopback B) is located on the analag side of the
         CODEC. 'internalDigital' (aka Loopback A) is located on the digital
         side of the CODEC.
         'internalAnalog' is closer to the line-side than 'internalDigital'.

         The value 'internalAnalog' is valid for em channels only.
        "
    DEFVAL  { none }
    ::= { aluVoiceEntry 5 }

aluVoiceFaultSignaling  OBJECT-TYPE
    SYNTAX     INTEGER {
                idle   (1),
                seized (2)
            }
    MAX-ACCESS  read-create
    STATUS      current
    DESCRIPTION
        "aluVoiceFaultSignaling is used to configure fault signaling as idle
         or seized.

         The idle code is defined by aluVoiceIdleCode.
         The seized code is defined by aluVoiceSeizedCode.

         This object is invalid for em channels whose aluVoiceSignalingMode is
         'transmissionOnly'.
        "
    DEFVAL  { idle }
    ::= { aluVoiceEntry 6 }

aluVoiceSignalBitsState OBJECT-TYPE
    SYNTAX      OCTET STRING (SIZE(2))
    MAX-ACCESS  read-only
    STATUS      current
    DESCRIPTION
        "aluVoiceSignalBitsState is an array of two bytes used to indicate the
         current state of the ABCD signalling bits for the voice channel.

         The first byte of the array describes the RX ABCD bits. The second byte
         of the array describes the TX ABCD bits.

         The byte arrangement is as follows:

         array index: |  0  1  |
                      |  RX TX |

         Each byte carries ABCD bits in the least significant nibble. The
         byte's most significant bit indicates the validity of the ABCD bits.

         The bit arrangement is as follows:

         bit pos:    | 7 6 5 4 3 2 1 0 |
                     | V x x x A B C D |

         'V' - validity (0 = invalid, 1 = valid)
         'x' - don't care

         ABCD bits are marked invalid for a variety of situations (eg.
         channel-group not configured, channel status not up, etc.).
         "
    ::= { aluVoiceEntry 7 }

aluVoiceClockSource OBJECT-TYPE
    SYNTAX      TmnxDSXClockSource
    MAX-ACCESS  read-only
    STATUS      current
    DESCRIPTION
        "aluVoiceClockSource indicates the clock for transmitted data from
         either the internal clock ('nodeTimed'), or from a clock recovered
         from the line's receive data stream ('loopTimed'), or recovered
         adaptively from the rate at which the data that is received and not
         from the physical layer ('adaptive'), or recovered from the
         differential timestamp in the RTP header ('differential').

         Only 'nodeTimed' is supported.
        "
    ::= { aluVoiceEntry 8 }

aluVoiceSignalingLeadE OBJECT-TYPE
    SYNTAX      AluVoiceSignalingLead
    MAX-ACCESS  read-create
    STATUS      current
    DESCRIPTION
        "aluVoiceSignalingLeadE is an output (or drive) lead.

         This object is valid for em channels only.

         This object is invalid for em channels whose aluVoiceSignalingMode is
         'transmissionOnly'.
        "
    DEFVAL { end-to-end }
    ::= { aluVoiceEntry 9 }

aluVoiceSignalingLeadM OBJECT-TYPE
    SYNTAX      AluVoiceSignalingLead
    MAX-ACCESS  read-create
    STATUS      current
    DESCRIPTION
        "aluVoiceSignalingLeadM is an input (or scan) lead.

         This object is valid for em channels only.

         This object is invalid for em channels whose aluVoiceSignalingMode is
         'transmissionOnly'.
        "
    DEFVAL { end-to-end }
    ::= { aluVoiceEntry 10 }

aluVoiceSignalingLeadsState OBJECT-TYPE
    SYNTAX      OCTET STRING (SIZE(2))
    MAX-ACCESS  read-only
    STATUS      current
    DESCRIPTION
        "aluVoiceSignalingLeadsState is an array of two bytes used to indicate
         the current state of the output (or drive) and input (or scan)
         signaling leads (AluVoiceSignalingLead).

         This object is valid for em channels only.

         This object is invalid for em channels whose aluVoiceSignalingMode is
         'transmissionOnly'.

         The byte arrangement is as follows:

         byte array index: |  0  1  |
         signaling lead:   |  M  E  |

         Each byte represents the state of the respective signaling lead.

         Valid byte values are:
         1 = ON (or high as per AluVoiceSignalingLead)
         2 = OFF (or low as per AluVoiceSignalingLead)
         All other byte values are undefined.
         "
    ::= { aluVoiceEntry 11 }

aluVoiceSignalMode    OBJECT-TYPE
    SYNTAX      INTEGER {
                    none (1),
                    cas  (2)
                }
    MAX-ACCESS  read-only
    STATUS      current
    DESCRIPTION
        "The value of aluVoiceSignalMode indicates the type of signalling
         associated with the channel:
         none  - Indicates no signalling on this channel.
         cas   - Indicates Channel Associated Signalling (CAS) on this channel.

         aluVoiceSignalMode is just like tmnxDS1SignalMode except that it's read-only.
        "
    ::= { aluVoiceEntry 12 }

aluVoiceCallState OBJECT-TYPE
   SYNTAX  INTEGER {
                unknown       (0),
                outOfService  (1),
                idle          (2),
                incoming      (3),
                outgoing      (4),
                nonForwarding (5)
            }
    MAX-ACCESS  read-only
    STATUS      current
    DESCRIPTION
       "The current state of the voice circuit."
     ::= { aluVoiceEntry 13 }

aluVoiceIncomingCallCount OBJECT-TYPE
     SYNTAX      Counter32
     MAX-ACCESS  read-only
     STATUS      current
     DESCRIPTION
            "The number of incoming calls (received by the circuit).

             This count is accumulated since the last time the statistics were cleared.
            "
     ::= { aluVoiceEntry 14 }

aluVoiceIncomingCallCountAns OBJECT-TYPE
     SYNTAX      Counter32
     MAX-ACCESS  read-only
     STATUS      current
     DESCRIPTION
            "The number of incoming calls (received by the circuit) that were answered.

             This count is accumulated since the last time the statistics were cleared.
            "
     ::= { aluVoiceEntry 15 }

aluVoiceIncomingCallTime OBJECT-TYPE
     SYNTAX      Counter32
     UNITS       "seconds"
     MAX-ACCESS  read-only
     STATUS      current
     DESCRIPTION
            "The total duration (in seconds) of all incoming calls.

             This count is accumulated since the last time the statistics were cleared.
            "
     ::= { aluVoiceEntry 16 }

aluVoiceIncomingCallTimeAns OBJECT-TYPE
     SYNTAX      Counter32
     UNITS       "seconds"
     MAX-ACCESS  read-only
     STATUS      current
     DESCRIPTION
            "The total duration (in seconds) of all incoming calls that were answered.

             This count is accumulated since the last time the statistics were cleared.
            "
     ::= { aluVoiceEntry 17 }

aluVoiceOutgoingCallCount OBJECT-TYPE
     SYNTAX      Counter32
     MAX-ACCESS  read-only
     STATUS      current
     DESCRIPTION
            "The number of outgoing calls (originated by the circuit).

             This count is accumulated since the last time the statistics were cleared.
            "
     ::= { aluVoiceEntry 18 }

aluVoiceOutgoingCallCountAns OBJECT-TYPE
     SYNTAX      Counter32
     MAX-ACCESS  read-only
     STATUS      current
     DESCRIPTION
            "The number of outgoing calls (originated by the circuit) that were answered.

             This count is accumulated since the last time the statistics were cleared.
            "
     ::= { aluVoiceEntry 19 }

aluVoiceOutgoingCallTime OBJECT-TYPE
     SYNTAX      Counter32
     UNITS       "seconds"
     MAX-ACCESS  read-only
     STATUS      current
     DESCRIPTION
            "The total duration (in seconds) of all outgoing calls.

             This count is accumulated since the last time the statistics were cleared.
            "
     ::= { aluVoiceEntry 20 }

aluVoiceOutgoingCallTimeAns OBJECT-TYPE
     SYNTAX      Counter32
     UNITS       "seconds"
     MAX-ACCESS  read-only
     STATUS      current
     DESCRIPTION
            "The total duration (in seconds) of all outgoing calls that were answered.

             This count is accumulated since the last time the statistics were cleared.
            "
     ::= { aluVoiceEntry 21 }

aluVoiceOutOfServiceTime OBJECT-TYPE
     SYNTAX      Counter32
     UNITS       "seconds"
     MAX-ACCESS  read-only
     STATUS      current
     DESCRIPTION
            "The time in seconds for which the circuit was unavailable for connection.

             This count is accumulated since the last time the statistics were cleared.
            "
     ::= { aluVoiceEntry 22 }

aluVoiceIdleTime OBJECT-TYPE
     SYNTAX      Counter32
     UNITS       "seconds"
     MAX-ACCESS  read-only
     STATUS      current
     DESCRIPTION
            "The time in seconds for which the circuit was idle.

             This count is accumulated since the last time the statistics were cleared.
            "
     ::= { aluVoiceEntry 23 }

aluVoiceTotalCallCount OBJECT-TYPE
     SYNTAX      Counter32
     MAX-ACCESS  read-only
     STATUS      current
     DESCRIPTION
            "The sum of aluVoiceIncomingCallCount and aluVoiceOutgoingCallCount.

             This count is accumulated since the last time the statistics were cleared.
            "
     ::= { aluVoiceEntry 24 }

aluVoiceTotalCallTime OBJECT-TYPE
     SYNTAX      Counter32
     UNITS       "seconds"
     MAX-ACCESS  read-only
     STATUS      current
     DESCRIPTION
            "The sum of aluVoiceIncomingCallTime and aluVoiceOutgoingCallTime.

             This count is accumulated since the last time the statistics were cleared.
            "
     ::= { aluVoiceEntry 25 }

aluVoiceIdleCode OBJECT-TYPE
    SYNTAX      Unsigned32 (0..15)
    MAX-ACCESS  read-create
    STATUS      current
    DESCRIPTION
        "This object contains the code transmitted on the signaling path when
         the channel is configured to transmit idle fault signaling. It's also
         used for driving/scanning the E&M signaling leads.

         This object is valid for em channels only.
         For fxo and fxs, the value is assigned internally by the system.

         The object is a bitmap arranged as follows:

         bit pos:    | 7 6 5 4 3 2 1 0 |
                     | x x x x A B C D |

         'x' - don't care

         The default value depends on aluExtTmnxMDAVoiceCompandingLaw:
         For muLaw    -   0 (or 0x0 or 0b0000)
         For aLaw     -  13 (or 0xD or 0b1101)

         This object is invalid for em channels whose aluVoiceSignalingMode is
         'transmissionOnly'.
        "
    ::= { aluVoiceEntry 26 }

aluVoiceSeizedCode OBJECT-TYPE
    SYNTAX      Unsigned32 (0..15)
    MAX-ACCESS  read-create
    STATUS      current
    DESCRIPTION
        "This object contains the code transmitted on the signaling path when
         the channel is configured to transmit seized fault signaling. It's also
         used for driving/scanning the E&M signaling leads.

         This object is valid for em channels only.
         For fxo and fxs, the value is assigned internally by the system.

         The object is a bitmap arranged as follows:

         bit pos:    | 7 6 5 4 3 2 1 0 |
                     | x x x x A B C D |

         'x' - don't care

         The default value depends on aluExtTmnxMDAVoiceCompandingLaw:
         For muLaw    -  15 (or 0xF or 0b1111)
         For aLaw     -   5 (or 0x5 or 0b0101)

         This object is invalid for em channels whose aluVoiceSignalingMode is
         'transmissionOnly'.
        "
    ::= { aluVoiceEntry 27 }

--
-- Voice Channel Group Table
--
aluVoiceChanGroupTable   OBJECT-TYPE
    SYNTAX      SEQUENCE OF AluVoiceChanGroupEntry
    MAX-ACCESS  not-accessible
    STATUS      current
    DESCRIPTION
        "The aluVoiceChanGroupTable has an entry for a single 64kbps (DS0)
         channel belonging to a particular Voice channel.
        "
    ::= { aluPortObjs 9 }

aluVoiceChanGroupEntry       OBJECT-TYPE
    SYNTAX      AluVoiceChanGroupEntry
    MAX-ACCESS  not-accessible
    STATUS      current
    DESCRIPTION
        "Each row entry represents one or more Voice channels on an interface.

         Entries can be created and deleted via SNMP SET operations
         using the aluVoiceChanGroupRowStatus object.

         For each aluVoiceChanGroupEntry, there will be a corresponding entry
         in the tmnxPortTable and the ifTable.
        "
    INDEX   { tmnxChassisIndex, tmnxPortPortID }
    ::= { aluVoiceChanGroupTable 1 }

AluVoiceChanGroupEntry ::=
    SEQUENCE {
        aluVoiceChanGroupRowStatus        RowStatus,
        aluVoiceChanGroupMTU              Unsigned32,
        aluVoiceChanGroupOperMTU          Unsigned32
    }

aluVoiceChanGroupRowStatus    OBJECT-TYPE
    SYNTAX      RowStatus
    MAX-ACCESS  read-create
    STATUS      current
    DESCRIPTION
        "aluVoiceChanGroupRowStatus controls the creation and deletion of
         row entries in the aluVoiceChanGroupTable. The tmnxPortPortID
         for a channel group includes a group ID in the lower bits.
         The manager has to first calculate the tmnxPortPortID based on the
         TiMOS encoding scheme."
    ::= { aluVoiceChanGroupEntry 1 }

aluVoiceChanGroupMTU  OBJECT-TYPE
    SYNTAX      Unsigned32
    UNITS       "bytes"
    MAX-ACCESS  read-only
    STATUS      current
    DESCRIPTION
        "The size of the largest packet which can be sent/received
         on the channel group, specified in octets.  For groups that
         are used for transmitting network datagrams, this is the
         size of the largest network datagram that can be sent.

         aluVoiceChanGroupMTU cannot be modified as only encap-type cem is
         supported. The predetermined default value will always be reflected.
        "
    ::= { aluVoiceChanGroupEntry 2 }

aluVoiceChanGroupOperMTU  OBJECT-TYPE
    SYNTAX      Unsigned32
    UNITS       "bytes"
    MAX-ACCESS  read-only
    STATUS      current
    DESCRIPTION
        "The negotiated size of the largest packet which can be sent on
         the channel group, specified in octets.  For channel groups that
         are used for transmitting network datagrams, this is the size of
         the largest network datagram that can be sent."
    ::= { aluVoiceChanGroupEntry 3 }

--
-- ALU GPON Port Table
--
aluGponPortTable OBJECT-TYPE
    SYNTAX  SEQUENCE OF AluGponPortEntry
    MAX-ACCESS  not-accessible
    STATUS      current
    DESCRIPTION
        "The aluGponPortTable has an entry for every GPON port in the system."
     ::= { aluPortObjs 10 }

aluGponPortEntry OBJECT-TYPE
    SYNTAX AluGponPortEntry
    MAX-ACCESS  not-accessible
    STATUS      current
    DESCRIPTION
        "Each row entry represents a physical GPON port on an
         IOM card in a chassis in the system.  Entries cannot be
         created and deleted via SNMP SET operations.  Entries in this
         table will be created automatically when the
         tmnxMDAAssignedType object is set to a GPON MDA type. The
         aluGponPortEntry contains attributes that are unique to the
         'GPON' tmnxPortType. The tmnxPortPortID contains the slot,
         mda and port numbers encoded into it.

         For each aluGponPortEntry, there will be a corresponding
         entry in the tmnxPortTable and the ifTable."
    INDEX       { tmnxChassisIndex, tmnxPortPortID }
    ::= { aluGponPortTable 1 }

AluGponPortEntry ::=
    SEQUENCE {
        aluGponPortG984SerialNumber           OCTET STRING,
        aluGponPortSubsLocId                  OCTET STRING,
        aluGponPortActiveSwVersion            OCTET STRING,
        aluGponPortPonStatus                  INTEGER,
        aluGponPortOntEnetStatus              INTEGER,
        aluGponPortOntEnetSpeed               INTEGER
    }

aluGponPortG984SerialNumber OBJECT-TYPE
    SYNTAX      OCTET STRING (SIZE(0..8))
    MAX-ACCESS  read-only
    STATUS      current
    DESCRIPTION
        "Represents the ONT's G.984 Serial Number of the ONT.  From a
        display standpoint, it should be interpreted as follows: 1st 4
        bytes are ASCII Vendor ID, and 2nd 4 bytes are a 32 bit number
        (which gets displayed as 8 ASCII characters). "
    ::= { aluGponPortEntry 1 }

aluGponPortSubsLocId OBJECT-TYPE
    SYNTAX      OCTET STRING (SIZE(0..10))
    MAX-ACCESS  read-write
    STATUS      current
    DESCRIPTION
        "The Subscriber Location ID (SLID) that is sent to the OLT via
        the G.984.3 password PLOAM message.  Contains the binary
        representation of the 10-byte SLID that will be sent on the
        next reboot."
    ::= { aluGponPortEntry 2 }

aluGponPortActiveSwVersion OBJECT-TYPE
    SYNTAX      OCTET STRING (SIZE(0..14))
    MAX-ACCESS  read-only
    STATUS      current
    DESCRIPTION
        "The active software version running on the GPON port's ONT."
    ::= { aluGponPortEntry 3 }

aluGponPortPonStatus OBJECT-TYPE
    SYNTAX      INTEGER {
                    shutdown           (0),
                    active             (1),
                    hardwareFailure    (2),
                    softwareFailure    (3),
                    lossOfLink         (4),
                    softwareDownload   (5),
                    omciNotEstablished (6),
                    boot               (7),
                    ranging            (8),
                    busy               (9)
                }
    MAX-ACCESS  read-only
    STATUS      current
    DESCRIPTION
        "The aluGponPortPonStatus indicates the current status of the
         PON."
    ::= { aluGponPortEntry 4 }

aluGponPortOntEnetStatus OBJECT-TYPE
    SYNTAX      INTEGER {
                    noLink (0),
                    active (1)
                }
    MAX-ACCESS  read-only
    STATUS      current
    DESCRIPTION
        "Indicates the operational status of the ONT's Ethernet interface."
    ::= { aluGponPortEntry 5 }

aluGponPortOntEnetSpeed OBJECT-TYPE
    SYNTAX      INTEGER {
                    undefined (0),
                    halfDuplex10Mbps (1),
                    fullDuplex10Mbps (2),
                    halfDuplex100Mbps (3),
                    fullDuplex100Mbps (4),
                    halfDuplex1Gbps (5),
                    fullDuplex1Gbps (6)
                }
    MAX-ACCESS  read-only
    STATUS      current
    DESCRIPTION
        "Indicates the operational speed of the ONT's Ethernet interface."
    ::= { aluGponPortEntry 6 }

--
-- ALU DSL Port Table
--
aluDslPortTable OBJECT-TYPE
    SYNTAX  SEQUENCE OF AluDslPortEntry
    MAX-ACCESS  not-accessible
    STATUS      current
    DESCRIPTION
        "The aluDslPortTable has an entry for every DSL port in the system."
     ::= { aluPortObjs 11 }

aluDslPortEntry OBJECT-TYPE
    SYNTAX AluDslPortEntry
    MAX-ACCESS  not-accessible
    STATUS      current
    DESCRIPTION
        "Each row entry represents a backplane ethernet DSL port on an
         IOM card in a chassis in the system.  Entries cannot be
         created and deleted via SNMP SET operations.  Entries in this
         table will be created automatically when the
         tmnxMDAAssignedType object is set to a p8-xdsl or p6-dsl MDA type. The
         aluDslPortEntry contains attributes that are unique to the
         'XDSL' or 'SHDSL' tmnxPortType. The tmnxPortPortID contains the slot,
         mda and port numbers encoded into it.

         For each aluDslPortEntry, there will be a corresponding
         entry in the tmnxPortTable and the ifTable."
    INDEX       { tmnxChassisIndex, tmnxPortPortID }
    ::= { aluDslPortTable 1 }

AluDslPortEntry ::=
    SEQUENCE {
        aluDslPortBondingType                   AluDslTpsTcType,
        aluDslPortBondingState                  INTEGER,
        aluDslPortBondingBitRateUS              Unsigned32,
        aluDslPortBondingBitRateDS              Unsigned32,
        aluDslPortAtmVpi                        INTEGER,
        aluDslPortAtmVci                        INTEGER,
        aluDslPortAtmF5OamLoopback              INTEGER,
        aluDslPortAtmF5OamLoopbackStatus        INTEGER,
        aluDslPortAtmF5OamLoopbackTime          Unsigned32,
        aluDslPortNtrDslLineID                  INTEGER,
        aluDslPortNtrLockedStatus               INTEGER,
        aluDslPortNtrStdDev                     Unsigned32,
        aluDslPortNtrMaxError                   INTEGER,
        aluDslPortNtrMinError                   INTEGER,
        aluDslPortAdsl2Plus                     INTEGER,
        aluDslPortNtrSampleClockPeriod          INTEGER,
        aluDslPortNtrErrorHistory               OCTET STRING
    }

aluDslPortBondingType OBJECT-TYPE
    SYNTAX      AluDslTpsTcType
    MAX-ACCESS  read-only
    STATUS      current
    DESCRIPTION
        "The aluDslPortBondingType indicates the bonding type of the DSL port."
    ::= { aluDslPortEntry 1 }

aluDslPortBondingState OBJECT-TYPE
    SYNTAX      INTEGER {
                down          (0),
                up            (1)
            }
    MAX-ACCESS  read-only
    STATUS      current
    DESCRIPTION
        "The aluDslPortBondingState indicates the bonding opretional state of
         the DSL port. The 'up' state indicates that the bonding group can
         be used for passing traffic."
    ::= { aluDslPortEntry 2 }

aluDslPortBondingBitRateUS OBJECT-TYPE
    SYNTAX      Unsigned32
    MAX-ACCESS  read-only
    STATUS      current
    DESCRIPTION
        "The aluDslPortBondingBitRateUS indicates the upstream bonding bit
         rate, unit is 1Kpbs."
    ::= { aluDslPortEntry 3 }

aluDslPortBondingBitRateDS OBJECT-TYPE
    SYNTAX      Unsigned32
    MAX-ACCESS  read-only
    STATUS      current
    DESCRIPTION
        "The aluDslPortBondingBitRateDS indicates the downstream bonding bit
         rate, unit is 1Kpbs."
    ::= { aluDslPortEntry 4 }

aluDslPortAtmVpi OBJECT-TYPE
    SYNTAX      INTEGER (0..255)
    MAX-ACCESS  read-write
    STATUS      current
    DESCRIPTION
        "The aluDslPortAtmVpi indicates the Vpi for the bonding group.
         It is only used when the aluDslPortBondingType is 'atm'."
    DEFVAL { 8 }
    ::= { aluDslPortEntry 5 }

aluDslPortAtmVci OBJECT-TYPE
    SYNTAX      INTEGER (32..65535)
    MAX-ACCESS  read-write
    STATUS      current
    DESCRIPTION
        "aluDslPortAtmVci indicates the Vci for the bonding group.
         The minimum value is 32, values 0 to 31 are
         reserved for other uses by the ITU and ATM Forum.
         It is only used when the aluDslPortBondingType is 'atm'."
    DEFVAL { 35 }
    ::= { aluDslPortEntry 6 }

aluDslPortAtmF5OamLoopback OBJECT-TYPE
    SYNTAX      INTEGER {
                none   (0),
                active (1)
            }
    MAX-ACCESS  read-write
    STATUS      current
    DESCRIPTION
        "aluDslPortAtmF5OamLoopback is used to generate an CPE initiated F5
         OAM loopback cell on an ATM bonding type DSL port .

         The aluDslPortAtmF5OamLoopback always starts in the none(0) state
         until an explicit management action causes a transition to the
         active(1) state.   When active(1), an F5 ATM OAM cell is initiated
         and sent to PEER. The state goes back to none when a loopback cell
         is received from PEER or a default 10-seconds times out.

         When active(1), setting aluDslPortAtmF5OamLoopback to none is not
         allowed.

         It is applicable only when the aluDslPortBondingType is 'atm'."
    DEFVAL  { none }
    ::= { aluDslPortEntry 7 }

aluDslPortAtmF5OamLoopbackStatus OBJECT-TYPE
    SYNTAX      INTEGER {
                none (0),
                fail (1),
                pass (2)
            }
    MAX-ACCESS  read-only
    STATUS      current
    DESCRIPTION
        "aluDslPortAtmF5OamLoopbackStatus is used to indicate the F5 loopback
         test result.

         It is applicable only when the value of tmnxPortType is 'XDSL' and the
         aluDslPortBondingType is 'atm'."
    DEFVAL  { none }
    ::= { aluDslPortEntry 8 }

aluDslPortAtmF5OamLoopbackTime OBJECT-TYPE
    SYNTAX      Unsigned32
    MAX-ACCESS  read-only
    STATUS      current
    DESCRIPTION
        "aluDslPortAtmF5OamLoopbackTime is used to indicate the round-trip time
         , in ms, for the ATM F5 Loopback testing.

         It is applicable only when the value of tmnxPortType is 'XDSL' and the
         aluDslPortBondingType is 'atm'."
    DEFVAL  { 0 }
    ::= { aluDslPortEntry 9 }

aluDslPortNtrDslLineID OBJECT-TYPE
    SYNTAX      INTEGER
    MAX-ACCESS  read-only
    STATUS      current
    DESCRIPTION
        "The aluDslPortNtrDslLineID indicates the DSL physical line controlling
         the NTR. The value of '0' indicates that the NTR is not available on
         the port"
    DEFVAL  { 0 }
    ::= { aluDslPortEntry 10 }

aluDslPortNtrLockedStatus OBJECT-TYPE
    SYNTAX      INTEGER {
                acquringLock  (0),
                preLock       (1),
                lock          (2),
                notSelected   (3),
                freeRunning   (4)
            }
    MAX-ACCESS  read-only
    STATUS      current
    DESCRIPTION
        "The aluDslPortNtrLockedStatus indicates that NTR status."
    DEFVAL  { freeRunning }
    ::= { aluDslPortEntry 11 }

aluDslPortNtrStdDev OBJECT-TYPE
    SYNTAX      Unsigned32
    MAX-ACCESS  read-only
    STATUS      current
    DESCRIPTION
        "The aluDslPortNtrStdDev indicates the standard deviation, or one
         sigma, over a 10 second period of the phase error between the
         encoded phase information (as present in the NTR field of
         the overhead frame) and the CPE regenerated NTR clock. This
         therefore indicates the standard deviation of the phase error
         between the CO NTR clock and the CPE regenerated NTR clock.
         It is expressed in nanoseconds.

         It is applicable only when the value of tmnxPortType is 'XDSL'."
    DEFVAL  { 0 }
    ::= { aluDslPortEntry 12 }

aluDslPortNtrMaxError OBJECT-TYPE
    SYNTAX      INTEGER
    MAX-ACCESS  read-only
    STATUS      current
    DESCRIPTION
        "The aluDslPortNtrMaxError indicates the maximum phase error, after
         lock has been declared, between the encoded phase information
         (as present in the NTR field of the overhead frame) and the CPE
         regenerated NTR clock.  This therefore indicates the maximum phase
         error between the CO NTR clock and the CPE regenerated NTR clock.
         It is expressed in nanoseconds.

         It is applicable only when the value of tmnxPortType is 'XDSL'."
    DEFVAL  { 0 }
    ::= { aluDslPortEntry 13 }

aluDslPortNtrMinError OBJECT-TYPE
    SYNTAX      INTEGER
    MAX-ACCESS  read-only
    STATUS      current
    DESCRIPTION
        "The aluDslPortNtrMinError indicates the minimum phase error, after
         lock has been declared, between the encoded phase information
         (as present in the NTR field of the overhead frame) and the CPE
         regenerated NTR clock. This therefore indicates the minimum phase
         error between the CO NTR clock and the CPE regenerated NTR clock.
         It is expressed in nanoseconds.

         It is applicable only when the value of tmnxPortType is 'XDSL'."
    DEFVAL  { 0 }
    ::= { aluDslPortEntry 14 }

aluDslPortAdsl2Plus OBJECT-TYPE
    SYNTAX      INTEGER {
                g992Dot5a (0),
                g992Dot5b (1)
            }
    MAX-ACCESS  read-write
    STATUS      current
    DESCRIPTION
        "The aluDslPortAdsl2Plus indicates the support of G992.5
         Annex A operations which are specific to POTS (g992Dot5a), or
         support of G992.5 ISDN operations over ADSL2+ (g992Dot5b).

         It is applicable only when the value of tmnxPortType is 'XDSL'."
    DEFVAL  { g992Dot5a }
    ::= { aluDslPortEntry 15 }

aluDslPortNtrSampleClockPeriod OBJECT-TYPE
    SYNTAX      INTEGER
    MAX-ACCESS  read-only
    STATUS      current
    DESCRIPTION
        "The aluDslPortNtrSampleClockPeriod indicates the sample
         clock period for NTR in nanoseconds. This number multiplied by
         the aluDslPortNtrErrorHistory value results in the phase error
         in nanoseconds between the encoded phase information (as present
         in the NTR field of the overhead frame) and the CPE regenerated
         NTR clock.

         It is applicable only when the value of tmnxPortType is 'XDSL'."
    DEFVAL  { 0 }
    ::= { aluDslPortEntry 16 }

aluDslPortNtrErrorHistory OBJECT-TYPE
    SYNTAX      OCTET STRING (SIZE(256))
    MAX-ACCESS  read-only
    STATUS      current
    DESCRIPTION
        "The aluDslPortNtrErrorHistory is an array of bytes used to
         indicate phase error history. Each byte represents the phase
         error between the encoded phase information (as present in
         the NTR field of the overhead frame) and the CPE regenerated
         NTR clock. Therefore each byte indicates the phase error between
         the CO NTR clock and the CPE regenerated NTR clock. These values
         are expressed in clock ticks based on the
         aluDslPortNtrSampleClockPeriod. The time interval between bytes
         in this array is 1/16 of a second

         It is applicable only when the value of tmnxPortType is 'XDSL'."
    ::= { aluDslPortEntry 17 }

--
-- ALU XDSL Line Table
--
aluXdslLineTable OBJECT-TYPE
    SYNTAX  SEQUENCE OF AluXdslLineEntry
    MAX-ACCESS  not-accessible
    STATUS      current
    DESCRIPTION
        "The aluXdslLineTable has an entry for every physical XDSL line in the
         system."
     ::= { aluPortObjs 12 }

aluXdslLineEntry OBJECT-TYPE
    SYNTAX AluXdslLineEntry
    MAX-ACCESS  not-accessible
    STATUS      current
    DESCRIPTION
        "Each row entry represents a physical XDSL line on an
         DSL module in a chassis in the system.  Entries cannot be
         created and deleted via SNMP SET operations.  Entries in this
         table will be created automatically when the
         tmnxMDAAssignedType object is set to a p8-xdsl or p6-dsl MDA type. The
         aluXdslLineEntry contains attributes that are unique to the XDSL
         physical lines. "
    INDEX       { tmnxChassisIndex, tmnxPortPortID, aluXdslLineID }
    ::= { aluXdslLineTable 1 }

AluXdslLineEntry ::=
    SEQUENCE {
        aluXdslLineID                          Unsigned32,
        aluXdslLineOperState                   INTEGER,
        aluXdslLineState                       INTEGER,
        aluXdslLineProtocol                    INTEGER,
        aluXdslLineVdslProfile                 INTEGER,
        aluXdslLineTpsTcType                   AluDslTpsTcType,
        aluXdslLineInBondingGroup              TruthValue,
        aluXdslLineBitRateUS                   Unsigned32,
        aluXdslLineSnrMarginUS                 INTEGER,
        aluXdslLineOutputPowerUS               INTEGER,
        aluXdslLineRefPsdUS                    INTEGER,
        aluXdslLineLoopDelayUS                 INTEGER,
        aluXdslLineFailureUS                   Unsigned32,
        aluXdslLineB0DelayUS                   Unsigned32,
        aluXdslLineB0InpUS                     Unsigned32,
        aluXdslLineBitRateDS                   Unsigned32,
        aluXdslLineSnrMarginDS                 INTEGER,
        aluXdslLineOutputPowerDS               INTEGER,
        aluXdslLineRefPsdDS                    INTEGER,
        aluXdslLineLoopDelayDS                 INTEGER,
        aluXdslLineFailureDS                   Unsigned32,
        aluXdslLineB0DelayDS                   Unsigned32,
        aluXdslLineB0InpDS                     Unsigned32,
        aluXdslLineAdminState                  AluDslAdminState
    }

aluXdslLineID OBJECT-TYPE
    SYNTAX      Unsigned32 (1..8)
    MAX-ACCESS  not-accessible
    STATUS      current
    DESCRIPTION
        "When aluXdslLineID is used in conjunction with tmnxChassisIndex
         and tmnxPortPortID, it uniquely identifies a specified
         physical XDSL line in the managed system. "
    ::= { aluXdslLineEntry 1 }

aluXdslLineOperState OBJECT-TYPE
    SYNTAX      INTEGER {
                down (0),
                up   (1)
            }
    MAX-ACCESS  read-only
    STATUS      current
    DESCRIPTION
        "It indicates the operational state of the XDSL line. The 'up' state
         indicates that the DSL line can be used for passing traffic.

         For 'ptm' TPS-TC XDSL line, the aluXdslLineOperState is up when the
         line state goes to 'runShow' and the line is in a bonding group.

         For 'atm' TPS-TC XDSL line, the aluXdslLineOperState is up when the
         line state goes to 'runShow' and the line is also available for
         bonding through G.998.1 protocol."
    ::= { aluXdslLineEntry 2 }

aluXdslLineState OBJECT-TYPE
    SYNTAX      INTEGER {
                idlNcon   (0),
                idlConf   (1),
                runActi   (2),
                runInit   (3),
                runShow   (4),
                tstMode   (5),
                runLdInit (6),
                idlLdDone (7),
                runShowL2 (8)
            }
    MAX-ACCESS  read-only
    STATUS      current
    DESCRIPTION
        "It indicates the state of the XDSL line retrieved from BCM6519."
    ::= { aluXdslLineEntry 3 }

aluXdslLineProtocol OBJECT-TYPE
    SYNTAX      INTEGER {
                none       (-1),
                proc9921a  (0),
                proc9921b  (1),
                proc9921c  (2),
                proc9922a  (3),
                proc9922c  (4),
                proc9921h  (5),
                proc9921i  (6),
                proc9932   (7),
                proc9912a  (8),
                proc9912b  (9),
                proc9923a  (16),
                proc9923b  (17),
                proc9923i  (18),
                proc9923m  (19),
                proc9923j  (20),
                proc9924i  (21),
                proc9923l1 (22),
                proc9923l2 (23),
                proc9925a  (24),
                proc9925b  (25),
                proc9925i  (26),
                proc9925m  (27),
                proc9925j  (28),
                sadsl      (29),
                ansi       (30),
                etsi       (31),
                proc9932v  (32),
                proc9935   (33)
            }
    MAX-ACCESS  read-only
    STATUS      current
    DESCRIPTION
        "It indicates the protocol of the XDSL line retrieved from BCM6519."
    DEFVAL { none }
    ::= { aluXdslLineEntry 4 }

aluXdslLineVdslProfile OBJECT-TYPE
    SYNTAX      INTEGER {
                none       (0),
                profile8a  (1),
                profile8b  (2),
                profile8c  (3),
                profile8d  (4),
                profile12a (5),
                profile12b (6),
                profile17a (7),
                profile30a (8),
                unknown    (9)
            }
    MAX-ACCESS  read-only
    STATUS      current
    DESCRIPTION
        "It indicates the VDSL profile of the XDSL line retrieved from BCM6519."
    DEFVAL { none }
    ::= { aluXdslLineEntry 5 }

aluXdslLineTpsTcType OBJECT-TYPE
    SYNTAX      AluDslTpsTcType
    MAX-ACCESS  read-only
    STATUS      current
    DESCRIPTION
        "It indicates the TPS-TC of the XDSL line retrieved from BCM6519."
    ::= { aluXdslLineEntry 6 }

aluXdslLineInBondingGroup OBJECT-TYPE
    SYNTAX      TruthValue
    MAX-ACCESS  read-only
    STATUS      current
    DESCRIPTION
        "It indicates if the line belongs to bonding group on the DSL Port"
    ::= { aluXdslLineEntry 7 }

aluXdslLineBitRateUS OBJECT-TYPE
    SYNTAX      Unsigned32
    MAX-ACCESS  read-only
    STATUS      current
    DESCRIPTION
        "It indicates the upstream line bit rate, unit is 1Kpbs.
         It is retrieved from BCM6519."
    ::= { aluXdslLineEntry 8 }

aluXdslLineSnrMarginUS OBJECT-TYPE
    SYNTAX      INTEGER (0..65535)
    MAX-ACCESS  read-only
    STATUS      current
    DESCRIPTION
        "It indicates the upstream SNR margin (expressed in tenth of dB's).
         It is retrieved from BCM6519."
    ::= { aluXdslLineEntry 9 }

aluXdslLineOutputPowerUS OBJECT-TYPE
    SYNTAX      INTEGER (0..65535)
    MAX-ACCESS  read-only
    STATUS      current
    DESCRIPTION
        "It indicates the upstream transmit power (expressed in tenth of dBm's).
         It is retrieved from BCM6519."
    ::= { aluXdslLineEntry 10 }

aluXdslLineRefPsdUS OBJECT-TYPE
    SYNTAX      INTEGER (0..65535)
    MAX-ACCESS  read-only
    STATUS      current
    DESCRIPTION
        "It indicates the upstream ref psd = nomial PSD - power cutback
         (expressed in tenths of dB's). It applies to ADSL ptotocols only.
         It is retrieved from BCM6519."
    ::= { aluXdslLineEntry 11 }

aluXdslLineLoopDelayUS OBJECT-TYPE
    SYNTAX      INTEGER (0..65535)
    MAX-ACCESS  read-only
    STATUS      current
    DESCRIPTION
        "It indicates the current loop group delay, only measured in VDSL.
         US: delay as measured on RMSG1 = actual loop delay
         DS: delay as measured on R-P-TRAINING1 = residual after application
             of timing advance expressed in samples at 35.328MHz.
         It is retrieved from BCM6519."
    ::= { aluXdslLineEntry 12 }

aluXdslLineFailureUS OBJECT-TYPE
    SYNTAX      Unsigned32
    MAX-ACCESS  read-only
    STATUS      current
    DESCRIPTION
        "It is bit mask giving the set of current active failure
         on the upstream line. The value is retrieved from BCM6519.

         A failure is declared when the corresponding defect is active for
         more than 2.5 (+ or - 0.5) sec. A failure is cleared when the
         corresponding defect is off for at least 10.5 (+ or - 0.5) sec.
         The bit index and corresponding failures are:
         Bit[1]: Set when unavailable time is counted
         Bit[2]: Set when the modem is not in the RUNNING_SHOWTIME state
         Bit[6]: Loss of ATM cell or PTM packet delineation, bearer B0
         Bit[7]: Loss of ATM cell or PTM packet delineation, bearer B1
         Bit[12]: Loss of signal
         Bit[13]: Loss of frame
         Bit[14]: No ATM cell or PTM packet delineation, bearer B0
         Bit[15]: No ATM cell or PTM packet delineation, bearer B1
         Bit[18]: Loss of power
         Bit[24]: CONFIG_ERROR
         Bit[25]: HIGH_BIT_RATE
         Bit[26]: COMM_PROBLEM
         Bit[27]: NO_PEER_DETECTED
         Bit[28]: Set when the loss of margin failure is set (when the SNR
                  margin drops below the minimum SNR margin for more than 20
                  consective seconds).
         Bit[29]: Set when the line leaves Showtime because the L3 state is
                  requested by the CO or CPE.
         "
    ::= { aluXdslLineEntry 13 }

aluXdslLineB0DelayUS OBJECT-TYPE
    SYNTAX      Unsigned32 (0..255)
    MAX-ACCESS  read-only
    STATUS      current
    DESCRIPTION
        "It indicates the current delay incurred on the upstream B0 latency
         path, expressed in milliseconds. The value is retrieved from BCM6519."
    ::= { aluXdslLineEntry 14 }

aluXdslLineB0InpUS OBJECT-TYPE
    SYNTAX      Unsigned32 (0..255)
    MAX-ACCESS  read-only
    STATUS      current
    DESCRIPTION
        "It indicates the current INP protection achived on the upstream B0
         latency path, Unit is 1/2 symbol.  The value is retrieved from
         BCM6519."
    ::= { aluXdslLineEntry 15 }

aluXdslLineBitRateDS OBJECT-TYPE
    SYNTAX      Unsigned32
    MAX-ACCESS  read-only
    STATUS      current
    DESCRIPTION
        "It indicates the downstream line bit rate, unit is 1Kpbs.
         It is retrieved from BCM6519."
    ::= { aluXdslLineEntry 16 }

aluXdslLineSnrMarginDS OBJECT-TYPE
    SYNTAX      INTEGER (0..65535)
    MAX-ACCESS  read-only
    STATUS      current
    DESCRIPTION
        "It indicates the downstream SNR margin (expressed in tenth of dB's).
         It is retrieved from BCM6519."
    ::= { aluXdslLineEntry 17 }

aluXdslLineOutputPowerDS OBJECT-TYPE
    SYNTAX      INTEGER (0..65535)
    MAX-ACCESS  read-only
    STATUS      current
    DESCRIPTION
        "It indicates the downstream transmit power (expressed in tenth of
         dBm's).  It is retrieved from BCM6519."
    ::= { aluXdslLineEntry 18 }

aluXdslLineRefPsdDS OBJECT-TYPE
    SYNTAX      INTEGER (0..65535)
    MAX-ACCESS  read-only
    STATUS      current
    DESCRIPTION
        "It indicates the downstream ref psd = nomial PSD - power cutback
         (expressed in tenths of dB's). It applies to ADSL ptotocols only.
         It is retrieved from BCM6519."
    ::= { aluXdslLineEntry 19 }

aluXdslLineLoopDelayDS OBJECT-TYPE
    SYNTAX      INTEGER (0..65535)
    MAX-ACCESS  read-only
    STATUS      current
    DESCRIPTION
        "It indicates the current loop group delay, only measured in VDSL.
         US: delay as measured on RMSG1 = actual loop delay
         DS: delay as measured on R-P-TRAINING1 = residual after application
             of timing advance expressed in samples at 35.328MHz.
         It is retrieved from BCM6519."
    ::= { aluXdslLineEntry 20 }

aluXdslLineFailureDS OBJECT-TYPE
    SYNTAX      Unsigned32
    MAX-ACCESS  read-only
    STATUS      current
    DESCRIPTION
        "It is bit mask giving the set of current active failure
         on the downstream line. The value is retrieved from BCM6519.

         A failure is declared when the corresponding defect is active for
         more than 2.5 (+ or - 0.5) sec. A failure is cleared when the
         corresponding defect is off for at least 10.5 (+ or - 0.5) sec. The
         bit index and corresponding failures are:
         Bit[1]: Set when unavailable time is counted
         Bit[2]: Set when the modem is not in the RUNNING_SHOWTIME state
         Bit[6]: Loss of ATM cell or PTM packet delineation, bearer B0
         Bit[7]: Loss of ATM cell or PTM packet delineation, bearer B1
         Bit[12]: Loss of signal
         Bit[13]: Loss of frame
         Bit[14]: No ATM cell or PTM packet delineation, bearer B0
         Bit[15]: No ATM cell or PTM packet delineation, bearer B1
         Bit[18]: Loss of power
         Bit[24]: CONFIG_ERROR
         Bit[25]: HIGH_BIT_RATE
         Bit[26]: COMM_PROBLEM
         Bit[27]: NO_PEER_DETECTED
         Bit[28]: Set when the loss of margin failure is set (when the SNR
                  margin drops below the the minimum SNR margin for more than 20
                  consective seconds).
         Bit[29]: Set when the line leaves Showtime because the L3 state is
                  requested by the CO or CPE.
         "
    ::= { aluXdslLineEntry 21 }

aluXdslLineB0DelayDS OBJECT-TYPE
    SYNTAX      Unsigned32 (0..255)
    MAX-ACCESS  read-only
    STATUS      current
    DESCRIPTION
        "It indicates the current delay incurred on the downstream B0 latency
         path, expressed in milliseconds. The value is retrieved from BCM6519."
    ::= { aluXdslLineEntry 22 }

aluXdslLineB0InpDS OBJECT-TYPE
    SYNTAX      Unsigned32 (0..255)
    MAX-ACCESS  read-only
    STATUS      current
    DESCRIPTION
        "It indicates the current INP protection achived on the downstream B0
         latency path, Unit is 1/2 symbol.  The value is retrieved from
         BCM6519."
    ::= { aluXdslLineEntry 23 }

aluXdslLineAdminState OBJECT-TYPE
    SYNTAX      AluDslAdminState
    MAX-ACCESS  read-write
    STATUS      current
    DESCRIPTION
        "It indicates the desired administrative status of this DSL Line"
    DEFVAL { inService }
    ::= { aluXdslLineEntry 24 }


--
-- ALU SHDSL Line Status Table
--
aluShdslLineTable OBJECT-TYPE
    SYNTAX  SEQUENCE OF AluShdslLineEntry
    MAX-ACCESS  not-accessible
    STATUS      current
    DESCRIPTION
        "The aluShdslLineTable has an entry for every SHDSL line in the system."
     ::= { aluPortObjs 13 }

aluShdslLineEntry OBJECT-TYPE
    SYNTAX AluShdslLineEntry
    MAX-ACCESS  not-accessible
    STATUS      current
    DESCRIPTION
        "Each row entry represents a physical SHDSL line on an
         DSL module in a chassis in the system.  Entries cannot be
         created and deleted via SNMP SET operations.  Entries in this
         table will be created automatically when the
         tmnxMDAAssignedType object is set to a p6-dsl MDA type. The
         aluShdslLineEntry contains attributes that are unique to the SHDSL
         physical lines. "
    INDEX       { tmnxChassisIndex, tmnxPortPortID, aluShdslLineID }
    ::= { aluShdslLineTable 1 }

AluShdslLineEntry ::=
    SEQUENCE {
        aluShdslLineID                           Unsigned32,
        aluShdslLineDataRate                     Unsigned32,
        aluShdslLineState                        INTEGER,
        aluShdslLineNegotiatedConst              INTEGER,
        aluShdslLineUsedCaplist                  INTEGER,
        aluShdslLineRegion                       INTEGER,
        aluShdslLineCaplistMode                  INTEGER,
        aluShdslLineTpsTcType                    AluDslTpsTcType,
        aluShdslLineInBondingGroup               TruthValue,
        aluShdslLineAdminState                   AluDslAdminState,
        aluShdslLineLineAttenuation              Unsigned32,
        aluShdslLineRxSNRMargin                  INTEGER,
        aluShdslLinePowerBackOffValue            Unsigned32
    }

aluShdslLineID OBJECT-TYPE
    SYNTAX      Unsigned32
    MAX-ACCESS  not-accessible
    STATUS      current
    DESCRIPTION
        "When aluShdslLineID is used in conjunction with tmnxChassisIndex and
         tmnxPortPortID, it uniquely identifies a SHDSL line in the managed
         system."
    ::= { aluShdslLineEntry 1 }

aluShdslLineDataRate OBJECT-TYPE
    SYNTAX      Unsigned32
    MAX-ACCESS  read-only
    STATUS      current
    DESCRIPTION
        "Current data rate of the PMD in units of 1kbs
         Note: This parameter is only valid if link is in UP_DATA_MODE."
    ::= { aluShdslLineEntry 2 }

aluShdslLineState OBJECT-TYPE
    SYNTAX      INTEGER {
                downNotReady  (0),
                downReady     (1),
                stopDownReady (2),
                initializing  (3),
                upDateMode    (4)
            }
    MAX-ACCESS  read-only
    STATUS      current
    DESCRIPTION
        "Indicates the current state"
    ::= { aluShdslLineEntry 3 }

aluShdslLineNegotiatedConst OBJECT-TYPE
    SYNTAX      INTEGER {
                pmd16TcPAM (0),
                pmd32TcPAM (1)
            }
    MAX-ACCESS  read-only
    STATUS      current
    DESCRIPTION
        "Indicates the Negotiated Constellation.
         Note: This parameter is only valid if link is in UP_DATA_MODE."
    ::= { aluShdslLineEntry 4 }

aluShdslLineUsedCaplist OBJECT-TYPE
    SYNTAX      INTEGER {
                newStyleCapList (0),
                oldStyleCapList (1)
            }
    MAX-ACCESS  read-only
    STATUS      current
    DESCRIPTION
        "Indicates the Negotiated Constellation.
         Note: This parameter is only valid if link is in UP_DATA_MODE."
    ::= { aluShdslLineEntry 5 }

aluShdslLineRegion OBJECT-TYPE
    SYNTAX      INTEGER {
                annexAF (0),
                annexBG (1)
            }
    MAX-ACCESS  read-only
    STATUS      current
    DESCRIPTION
        "Indicates the Region Information
         Note: This parameter is only valid if link is in UP_DATA_MODE."
    ::= { aluShdslLineEntry 6 }

aluShdslLineCaplistMode OBJECT-TYPE
    SYNTAX      INTEGER {
                newStyleCapList (0),
                oldStyleCapList (1),
                autoCapList     (2),
                autoTcDetect    (3)
            }
    MAX-ACCESS  read-only
    STATUS      current
    DESCRIPTION
        "Indicates the Capability List Mode."
    ::= { aluShdslLineEntry 7 }

aluShdslLineTpsTcType OBJECT-TYPE
    SYNTAX      AluDslTpsTcType
    MAX-ACCESS  read-only
    STATUS      current
    DESCRIPTION
        "This parameter indicates the TPS-TC of the physical SHDSL line."
    ::= { aluShdslLineEntry 8 }

aluShdslLineInBondingGroup OBJECT-TYPE
    SYNTAX      TruthValue
    MAX-ACCESS  read-only
    STATUS      current
    DESCRIPTION
        "It indicates if the line belongs to bonding group on the DSL Port"
    ::= { aluShdslLineEntry 9 }

aluShdslLineAdminState OBJECT-TYPE
    SYNTAX      AluDslAdminState
    MAX-ACCESS  read-write
    STATUS      current
    DESCRIPTION
        "It indicates the desired administrative status of this DSL Line"
    DEFVAL { inService }
    ::= { aluShdslLineEntry 10 }

aluShdslLineLineAttenuation OBJECT-TYPE
    SYNTAX        Unsigned32
    MAX-ACCESS    read-only
    STATUS        current
    DESCRIPTION
        "Line Attenuation in dB (Network Side).
         The local STU-R value is updated every second when the link is active."
    ::= { aluShdslLineEntry 11 }

aluShdslLineRxSNRMargin OBJECT-TYPE
    SYNTAX        INTEGER
    MAX-ACCESS    read-only
    STATUS        current
    DESCRIPTION
        "RX SNR Margin (Network Side). The local STU-R value is updated
         every second when the link is active."
    ::= { aluShdslLineEntry 12 }

aluShdslLinePowerBackOffValue OBJECT-TYPE
    SYNTAX        Unsigned32
    MAX-ACCESS    read-only
    STATUS        current
    DESCRIPTION
        "Power Back-Off Value (Network Side). The local STU-R value in dB
         is updated every second when the link is active."
    ::= { aluShdslLineEntry 13 }

--
-- Nokia 7705 Frame-relay Interface Stats Table
--
--  Augmententation of tmnxFrIntfTable in TIMETRA-PORT-MIB
--
aluFrIfStatsTable OBJECT-TYPE
    SYNTAX   SEQUENCE OF AluFrIfStatsEntry
    MAX-ACCESS   not-accessible
    STATUS   current
    DESCRIPTION
       "A table is used to gather the additional statistics for
        Nokia 7705 SAR series devices on a particular
        frame relay Interface."
    ::= { aluPortStatsObjs 11 }

aluFrIfStatsEntry OBJECT-TYPE
    SYNTAX   AluFrIfStatsEntry
    MAX-ACCESS   not-accessible
    STATUS   current
    DESCRIPTION
       "The statistics collected on a single frame relay
       Interface."
    AUGMENTS { tmnxFrIntfEntry }
    ::= { aluFrIfStatsTable 1 }

AluFrIfStatsEntry ::=
    SEQUENCE {
        aluFrIfRxFrames                    Counter64,
        aluFrIfRxOctets                    Counter64,
        aluFrIfRxDEFrames                  Counter64,
        aluFrIfRxDEOctets                  Counter64,
        aluFrIfRxFECNFrames                Counter64,
        aluFrIfRxBECNFrames                Counter64,
        aluFrIfTxFrames                    Counter64,
        aluFrIfTxOctets                    Counter64,
        aluFrIfTxDEFrames                  Counter64,
        aluFrIfTxDEOctets                  Counter64,
        aluFrIfTxFECNFrames                Counter64,
        aluFrIfTxBECNFrames                Counter64,
        aluFrIfRxDiscardsInvalidDlci       Counter64,
        aluFrIfRxLastInvalidDlci           Counter64,
        aluFrIfRxDiscardsCrcErrors         Counter64,
        aluFrIfRxDiscardsAlignmentErrors   Counter64,
        aluFrIfRxDiscardsLengthViolations  Counter64,
        aluFrIfRxDiscardsIllegalHeader     Counter64,
        aluFrIfRxDiscardsOtherErrors       Counter64,
        aluFrIfTxDiscardsUnderruns         Counter64,
        aluFrIfTxDiscardsOtherErrors       Counter64
    }


aluFrIfRxFrames OBJECT-TYPE
    SYNTAX   Counter64
    MAX-ACCESS   read-only
    STATUS   current
    DESCRIPTION
       "The number of frames received on this interface"
    ::= { aluFrIfStatsEntry 1 }


aluFrIfRxOctets OBJECT-TYPE
    SYNTAX   Counter64
    MAX-ACCESS   read-only
    STATUS   current
    DESCRIPTION
       "The number of octets received on this interface"
    ::= { aluFrIfStatsEntry 2 }

aluFrIfRxDEFrames OBJECT-TYPE
    SYNTAX   Counter64
    MAX-ACCESS   read-only
    STATUS   current
    DESCRIPTION
       "The number of DE=1 frames received on this interface"
    ::= { aluFrIfStatsEntry 3 }

aluFrIfRxDEOctets OBJECT-TYPE
    SYNTAX   Counter64
    MAX-ACCESS   read-only
    STATUS   current
    DESCRIPTION
       "The number of DE=1 octets received on this interface"
    ::= { aluFrIfStatsEntry 4 }

aluFrIfRxFECNFrames OBJECT-TYPE
    SYNTAX   Counter64
    MAX-ACCESS   read-only
    STATUS   current
    DESCRIPTION
       "The number of FECN frames received on this interface"
    ::= { aluFrIfStatsEntry 5 }

aluFrIfRxBECNFrames OBJECT-TYPE
    SYNTAX   Counter64
    MAX-ACCESS   read-only
    STATUS   current
    DESCRIPTION
       "The number of BECN frames received on this interface"
    ::= { aluFrIfStatsEntry 6 }

aluFrIfTxFrames OBJECT-TYPE
    SYNTAX   Counter64
    MAX-ACCESS   read-only
    STATUS   current
    DESCRIPTION
       "The number of frames sent on this interface"
    ::= { aluFrIfStatsEntry 7 }


aluFrIfTxOctets OBJECT-TYPE
    SYNTAX   Counter64
    MAX-ACCESS   read-only
    STATUS   current
    DESCRIPTION
       "The number of octets sent on this interface"
    ::= { aluFrIfStatsEntry 8 }

aluFrIfTxDEFrames OBJECT-TYPE
    SYNTAX   Counter64
    MAX-ACCESS   read-only
    STATUS   current
    DESCRIPTION
       "The number of DE=1 frames sent on this interface"
    ::= { aluFrIfStatsEntry 9 }

aluFrIfTxDEOctets OBJECT-TYPE
    SYNTAX   Counter64
    MAX-ACCESS   read-only
    STATUS   current
    DESCRIPTION
       "The number of DE=1 octets sent on this interface"
    ::= { aluFrIfStatsEntry 10 }

aluFrIfTxFECNFrames OBJECT-TYPE
    SYNTAX   Counter64
    MAX-ACCESS   read-only
    STATUS   current
    DESCRIPTION
       "The number of FECN frames sent on this interface"
    ::= { aluFrIfStatsEntry 11 }

aluFrIfTxBECNFrames OBJECT-TYPE
    SYNTAX   Counter64
    MAX-ACCESS   read-only
    STATUS   current
    DESCRIPTION
       "The number of BECN frames sent on this interface"
    ::= { aluFrIfStatsEntry 12 }

aluFrIfRxDiscardsInvalidDlci OBJECT-TYPE
    SYNTAX   Counter64
    MAX-ACCESS   read-only
    STATUS   current
    DESCRIPTION
       "The number of received frames with invalid or unsupported DLCI."
    ::= { aluFrIfStatsEntry 13 }

aluFrIfRxLastInvalidDlci   OBJECT-TYPE
    SYNTAX   Counter64
    MAX-ACCESS   read-only
    STATUS   current
    DESCRIPTION
       "The DLCI of the last received frames with an invalid DLCI."
    ::= { aluFrIfStatsEntry 14 }

aluFrIfRxDiscardsCrcErrors OBJECT-TYPE
    SYNTAX   Counter64
    MAX-ACCESS   read-only
    STATUS   current
    DESCRIPTION
       "The received crc errors."
    ::= { aluFrIfStatsEntry 15 }

aluFrIfRxDiscardsAlignmentErrors OBJECT-TYPE
    SYNTAX   Counter64
    MAX-ACCESS   read-only
    STATUS   current
    DESCRIPTION
       "The received alignment errors."
    ::= { aluFrIfStatsEntry 16 }

aluFrIfRxDiscardsLengthViolations OBJECT-TYPE
    SYNTAX   Counter64
    MAX-ACCESS   read-only
    STATUS   current
    DESCRIPTION
       "The received length errors."
    ::= { aluFrIfStatsEntry 17 }

aluFrIfRxDiscardsIllegalHeader OBJECT-TYPE
    SYNTAX   Counter64
    MAX-ACCESS   read-only
    STATUS   current
    DESCRIPTION
       "The received frames with illegal header "
    ::= { aluFrIfStatsEntry 18 }

aluFrIfRxDiscardsOtherErrors OBJECT-TYPE
    SYNTAX   Counter64
    MAX-ACCESS   read-only
    STATUS   current
    DESCRIPTION
       "The other received errors"
    ::= { aluFrIfStatsEntry 19 }

aluFrIfTxDiscardsUnderruns OBJECT-TYPE
    SYNTAX   Counter64
    MAX-ACCESS   read-only
    STATUS   current
    DESCRIPTION
       "Transmit Underruns."
    ::= { aluFrIfStatsEntry 20 }

aluFrIfTxDiscardsOtherErrors OBJECT-TYPE
    SYNTAX   Counter64
    MAX-ACCESS   read-only
    STATUS   current
    DESCRIPTION
       "The other transmit errors"
    ::= { aluFrIfStatsEntry 21 }

--
-- Nokia 7705 Frame-relay Circuit Table
--
--  Augmententation of frCircuitTable in FRAME-RELAY-DTE-MIB
--
--
aluExtFrCircuitTable OBJECT-TYPE
    SYNTAX   SEQUENCE OF AluExtFrCircuitEntry
    MAX-ACCESS   not-accessible
    STATUS   current
    DESCRIPTION
       "A table containing stats information about specific Data
       Link Connections (DLC) or virtual circuits."
    ::= { aluPortStatsObjs 12 }

aluExtFrCircuitEntry OBJECT-TYPE
    SYNTAX  AluExtFrCircuitEntry
    MAX-ACCESS   not-accessible
    STATUS   current
    DESCRIPTION
       "The stats information regarding a single Data Link
       Connection."
    AUGMENTS { frCircuitEntry }
    ::= { aluExtFrCircuitTable 1 }

AluExtFrCircuitEntry ::=
    SEQUENCE {
        aluExtFrCircuitReceivedCrcDiscards      Counter32,
        aluExtFrCircuitReceivedAborts           Counter32,
        aluExtFrCircuitReceivedOtherDiscards    Counter32,
        aluExtFrCircuitSentAborts               Counter32,
        aluExtFrCircuitSentFECNs                Counter32,
        aluExtFrCircuitSentBECNs                Counter32,
        aluExtFrCircuitReceivedDEOctets         Counter32,
        aluExtFrCircuitSentDEOctets             Counter32
    }


aluExtFrCircuitReceivedCrcDiscards OBJECT-TYPE
    SYNTAX   Counter32
    MAX-ACCESS   read-only
    STATUS   current
    DESCRIPTION
       "The number of inbound frames dropped because of Crc
       errors."
    ::= { aluExtFrCircuitEntry 1 }

aluExtFrCircuitReceivedAborts OBJECT-TYPE
    SYNTAX   Counter32
    MAX-ACCESS   read-only
    STATUS   current
    DESCRIPTION
       "The number of inbound frames dropped due to insufficient buffer resource."
    ::= { aluExtFrCircuitEntry 2 }

aluExtFrCircuitReceivedOtherDiscards OBJECT-TYPE
    SYNTAX   Counter32
    MAX-ACCESS   read-only
    STATUS   current
    DESCRIPTION
       "The number of inbound frames dropped because of other
       errors."
    ::= { aluExtFrCircuitEntry 3 }

aluExtFrCircuitSentAborts OBJECT-TYPE
    SYNTAX   Counter32
    MAX-ACCESS   read-only
    STATUS   current
    DESCRIPTION
       "The number of outbound frames dropped because of format
       errors, or because the VC is inactive."
    ::= { aluExtFrCircuitEntry 4 }

aluExtFrCircuitSentFECNs OBJECT-TYPE
    SYNTAX   Counter32
    MAX-ACCESS   read-only
    STATUS   current
    DESCRIPTION
       "Number of frames sent to the network indicating
       forward congestion since the virtual circuit was
       created.  This occurs when transmission queue is congested or
       when frames sent with FECN flage set."
    ::= { aluExtFrCircuitEntry 5 }

aluExtFrCircuitSentBECNs OBJECT-TYPE
    SYNTAX   Counter32
    MAX-ACCESS   read-only
    STATUS   current
    DESCRIPTION
       "Number of frames sent to the network indicating
       backward congestion since the virtual circuit was
       created.  This occurs when frames sent with
       FECN flags set."
    ::= { aluExtFrCircuitEntry 6 }


aluExtFrCircuitReceivedDEOctets OBJECT-TYPE
    SYNTAX   Counter32
    MAX-ACCESS   read-only
    STATUS   current
    DESCRIPTION
       "Number of octets received from the network indicating
       that they were eligible for discard since the virtual
       circuit was created.  This occurs when the remote DTE
       sets the DE flag, or when in remote DTE's switch
       detects that the frame was received as Excess Burst
       data."
    ::= { aluExtFrCircuitEntry 7 }

aluExtFrCircuitSentDEOctets OBJECT-TYPE
    SYNTAX   Counter32
    MAX-ACCESS   read-only
    STATUS   current
    DESCRIPTION
       "Number of octets sent to the network indicating that
       they were eligible for discard since the virtual
       circuit was created.   This occurs when the local DTE
       sets the DE flag, indicating that during Network
       congestion situations those frames should be discarded
       in preference of other frames sent without the DE bit
       set."
    ::= { aluExtFrCircuitEntry 8 }

--
--  Port PTP Transparent Clock Packet Statistics Table
--
aluEthPtpTimestampStatsTable OBJECT-TYPE
    SYNTAX      SEQUENCE OF AluEthPtpTimestampStatsEntry
    MAX-ACCESS  not-accessible
    STATUS      current
    DESCRIPTION
        "Defines the Nokia SAR series port IEEE1588 PTP
         Transparent Clock packet statistics table for providing,
         via SNMP, the capability of retrieving statistical information
         relating to packets that are timestamped."
    ::= { aluPortStatsObjs 13 }

aluEthPtpTimestampStatsEntry    OBJECT-TYPE
    SYNTAX      AluEthPtpTimestampStatsEntry
    MAX-ACCESS  not-accessible
    STATUS      current
    DESCRIPTION
        "Defines an entry in aluEthPtpTimestampStatsTable. Entries are
         created and deleted by the system depending port
         configuration."
    INDEX   { tmnxChassisIndex, tmnxPortPortID }
    ::= { aluEthPtpTimestampStatsTable 1 }

AluEthPtpTimestampStatsEntry ::=
    SEQUENCE {
        aluEthPtpInSyncPktTimestamped    Counter64,
        aluEthPtpOutSyncPktTimestamped   Counter64,
        aluEthPtpInDelReqPktTimestamped  Counter64,
        aluEthPtpOutDelReqPktTimestamped Counter64,
        aluEthPtpInFcsErrorCount         Counter64,
        aluEthPtpOutFcsErrorCount        Counter64,
        aluEthPtpOutFollowUpPktTimestamped Counter64
    }

aluEthPtpInSyncPktTimestamped OBJECT-TYPE
    SYNTAX      Counter64
    MAX-ACCESS  read-only
    STATUS      current
    DESCRIPTION
        "Indicate the number of ingress Sync packets that have been
         timestamped."
    ::= { aluEthPtpTimestampStatsEntry 1 }

aluEthPtpOutSyncPktTimestamped OBJECT-TYPE
    SYNTAX      Counter64
    MAX-ACCESS  read-only
    STATUS      current
    DESCRIPTION
        "Indicate the number of egress Sync packets that have been
         timestamped."
    ::= { aluEthPtpTimestampStatsEntry 2 }

aluEthPtpInDelReqPktTimestamped OBJECT-TYPE
    SYNTAX      Counter64
    MAX-ACCESS  read-only
    STATUS      current
    DESCRIPTION
        "Indicate the number of ingress Delay Request packets that have been
         timestamped."
    ::= { aluEthPtpTimestampStatsEntry 3 }

aluEthPtpOutDelReqPktTimestamped OBJECT-TYPE
    SYNTAX      Counter64
    MAX-ACCESS  read-only
    STATUS      current
    DESCRIPTION
        "Indicate the number of egress Delay Request packets that have been
         timestamped."
    ::= { aluEthPtpTimestampStatsEntry 4 }

aluEthPtpInFcsErrorCount OBJECT-TYPE
    SYNTAX      Counter64
    MAX-ACCESS  read-only
    STATUS      obsolete
    DESCRIPTION
        "Indicate the number of ingress packets that contained FCS Error."
    ::= { aluEthPtpTimestampStatsEntry 5 }

aluEthPtpOutFcsErrorCount OBJECT-TYPE
    SYNTAX      Counter64
    MAX-ACCESS  read-only
    STATUS      obsolete
    DESCRIPTION
        "Indicate the number of egress packets that contained FCS Error."
    ::= { aluEthPtpTimestampStatsEntry 6 }

aluEthPtpOutFollowUpPktTimestamped OBJECT-TYPE
    SYNTAX      Counter64
    MAX-ACCESS  read-only
    STATUS      current
    DESCRIPTION
        "Indicate the number of egress Follow-Up packets that have been
         transmitted."
    ::= { aluEthPtpTimestampStatsEntry 7 }

--
--  Add-drop Network Ring Port Stats Table
--
aluPortNetRingAddDropStatsTable OBJECT-TYPE
    SYNTAX      SEQUENCE OF AluPortNetRingAddDropStatsEntry
    MAX-ACCESS  not-accessible
    STATUS      current
    DESCRIPTION
        "Defines the Nokia 7705 series network add-drop ring port
         statistics table for providing, via SNMP, the capability of
         retrieving the traffic statistics for the ring add-drop port queues."
    ::= { aluPortStatsObjs 14 }

aluPortNetRingAddDropStatsEntry    OBJECT-TYPE
    SYNTAX      AluPortNetRingAddDropStatsEntry
    MAX-ACCESS  not-accessible
    STATUS      current
    DESCRIPTION
        "Defines an entry in aluPortNetRingAddDropStatsTable. Entries are
         created and deleted by the system depending on the add-drop port queue policy
         being used at the specific port."
    INDEX   { tmnxChassisIndex, tmnxPortPortID, aluPortNetRingAddDropQueueIndex }
    ::= { aluPortNetRingAddDropStatsTable 1 }

AluPortNetRingAddDropStatsEntry ::=
    SEQUENCE {
        aluPortNetRingAddDropQueueIndex      TQueueId,
        aluPortNetRingAddDropFwdInProfPkts   Counter64,
        aluPortNetRingAddDropFwdOutProfPkts  Counter64,
        aluPortNetRingAddDropFwdInProfOcts   Counter64,
        aluPortNetRingAddDropFwdOutProfOcts  Counter64,
        aluPortNetRingAddDropDroInProfPkts   Counter64,
        aluPortNetRingAddDropDroOutProfPkts  Counter64,
        aluPortNetRingAddDropDroInProfOcts   Counter64,
        aluPortNetRingAddDropDroOutProfOcts  Counter64
    }

aluPortNetRingAddDropQueueIndex OBJECT-TYPE
    SYNTAX      TQueueId (1..16)
    MAX-ACCESS  not-accessible
    STATUS      current
    DESCRIPTION
        "aluPortNetRingAddDropQueueIndex serves as the tertiary index. When used
         in conjunction with tmnxChassisIndex and tmnxPortPortID, it uniquely
         identifies a network ring add-drop queue for the specified port in the
         managed system."
    ::= { aluPortNetRingAddDropStatsEntry 1 }

aluPortNetRingAddDropFwdInProfPkts OBJECT-TYPE
    SYNTAX      Counter64
    MAX-ACCESS  read-only
    STATUS      current
    DESCRIPTION
        "aluPortNetRingAddDropFwdInProfPkts indicates the number of conforming
         network add-drop packets forwarded on this port using this queue."
    ::= { aluPortNetRingAddDropStatsEntry 2 }

aluPortNetRingAddDropFwdOutProfPkts OBJECT-TYPE
    SYNTAX      Counter64
    MAX-ACCESS  read-only
    STATUS      current
    DESCRIPTION
        "aluPortNetRingAddDropFwdOutProfPkts indicates the number of exceeding
         network add-drop packets forwarded on this port using this queue."
    ::= { aluPortNetRingAddDropStatsEntry 3 }

aluPortNetRingAddDropFwdInProfOcts OBJECT-TYPE
    SYNTAX      Counter64
    MAX-ACCESS  read-only
    STATUS      current
    DESCRIPTION
        "aluPortNetRingAddDropFwdInProfOcts indicates the number of conforming
         network add-drop octets forwarded on this port using this queue."
    ::= { aluPortNetRingAddDropStatsEntry 4 }

aluPortNetRingAddDropFwdOutProfOcts OBJECT-TYPE
    SYNTAX      Counter64
    MAX-ACCESS  read-only
    STATUS      current
    DESCRIPTION
        "aluPortNetRingAddDropFwdOutProfOcts indicates the number of exceeding
         network add-drop octets forwarded on this port using this queue."
    ::= { aluPortNetRingAddDropStatsEntry 5 }

aluPortNetRingAddDropDroInProfPkts OBJECT-TYPE
    SYNTAX      Counter64
    MAX-ACCESS  read-only
    STATUS      current
    DESCRIPTION
        "aluPortNetRingAddDropDroInProfPkts indicates the number of conforming
         network add-drop packets dropped on this port using this queue."
    ::= { aluPortNetRingAddDropStatsEntry 6 }

aluPortNetRingAddDropDroOutProfPkts OBJECT-TYPE
    SYNTAX      Counter64
    MAX-ACCESS  read-only
    STATUS      current
    DESCRIPTION
        "aluPortNetRingAddDropDroOutProfPkts indicates the number of exceeding
         network add-drop packets dropped on this port using this queue."
    ::= { aluPortNetRingAddDropStatsEntry 7 }

aluPortNetRingAddDropDroInProfOcts OBJECT-TYPE
    SYNTAX      Counter64
    MAX-ACCESS  read-only
    STATUS      current
    DESCRIPTION
        "aluPortNetRingAddDropDroInProfOcts indicates the number of conforming
         network add-drop octets dropped on this port using this queue."
    ::= { aluPortNetRingAddDropStatsEntry 8 }

aluPortNetRingAddDropDroOutProfOcts OBJECT-TYPE
    SYNTAX      Counter64
    MAX-ACCESS  read-only
    STATUS      current
    DESCRIPTION
        "aluPortNetRingAddDropDroOutProfOcts indicates the number of exceeding
         network add-drop octets dropped on this port using this queue."
    ::= { aluPortNetRingAddDropStatsEntry 9 }

aluPortNgeL2KeygroupStatsTable OBJECT-TYPE
    SYNTAX      SEQUENCE OF AluPortNgeL2KeygroupStatsEntry
    MAX-ACCESS  not-accessible
    STATUS      current
    DESCRIPTION
        "Defines the Nokia 7705 series Network Group Encryption port-level
        statistics."
    ::= { aluPortStatsObjs 15 }

aluPortNgeL2KeygroupStatsEntry  OBJECT-TYPE
    SYNTAX      AluPortNgeL2KeygroupStatsEntry
    MAX-ACCESS  not-accessible
    STATUS      current
    DESCRIPTION
        "Defines an entry in the aluPortNgeL2KeygroupStatsTable. Entries are
         created and deleted by the system depending port
         configuration."
    INDEX   { tmnxChassisIndex, tmnxPortPortID }
    ::= { aluPortNgeL2KeygroupStatsTable 1 }

AluPortNgeL2KeygroupStatsEntry ::=
    SEQUENCE {
        aluPortNgeL2KeygroupTxFrames     Counter64,
        aluPortNgeL2KeygroupTxBytes      Counter64,
        aluPortNgeL2KeygroupRxFrames     Counter64,
        aluPortNgeL2KeygroupRxBytes      Counter64,
        aluPortNgeL2KGRxDropOtherFrames  Counter64,
        aluPortNgeL2KGRxDropOtherBytes   Counter64,
        aluPortNgeL2KeygroupTxDropFrames Counter64,
        aluPortNgeL2KeygroupTxDropBytes  Counter64,
        aluPortNgeL2KGRxDrpInvldSpiFrms  Counter64,
        aluPortNgeL2KGRxDrpInvldSpiBytes Counter64
    }

aluPortNgeL2KeygroupTxFrames OBJECT-TYPE
    SYNTAX      Counter64
    MAX-ACCESS  read-only
    STATUS      current
    DESCRIPTION
        "Indicates the number of egress Ethernet frames that
         have been encrypted."
    ::= { aluPortNgeL2KeygroupStatsEntry 1 }

aluPortNgeL2KeygroupTxBytes OBJECT-TYPE
    SYNTAX      Counter64
    MAX-ACCESS  read-only
    STATUS      current
    DESCRIPTION
        "Indicates the number of egress Ethernet bytes that
         have been encrypted."
    ::= { aluPortNgeL2KeygroupStatsEntry 2 }

aluPortNgeL2KeygroupRxFrames OBJECT-TYPE
    SYNTAX      Counter64
    MAX-ACCESS  read-only
    STATUS      current
    DESCRIPTION
        "Indicates the number of ingress Ethernet frames that
         have been decrypted."
    ::= { aluPortNgeL2KeygroupStatsEntry 3 }

aluPortNgeL2KeygroupRxBytes OBJECT-TYPE
    SYNTAX      Counter64
    MAX-ACCESS  read-only
    STATUS      current
    DESCRIPTION
        "Indicates the number of ingress Ethernet bytes that
         have been decrypted."
    ::= { aluPortNgeL2KeygroupStatsEntry 4 }

aluPortNgeL2KGRxDropOtherFrames OBJECT-TYPE
    SYNTAX      Counter64
    MAX-ACCESS  read-only
    STATUS      current
    DESCRIPTION
        "Indicates the number of ingress Ethernet frames that
         have been dropped."
    ::= { aluPortNgeL2KeygroupStatsEntry 5 }

aluPortNgeL2KGRxDropOtherBytes OBJECT-TYPE
    SYNTAX      Counter64
    MAX-ACCESS  read-only
    STATUS      current
    DESCRIPTION
        "Indicates the number of ingress Ethernet bytes that
         have been dropped."
    ::= { aluPortNgeL2KeygroupStatsEntry 6 }

aluPortNgeL2KeygroupTxDropFrames OBJECT-TYPE
    SYNTAX      Counter64
    MAX-ACCESS  read-only
    STATUS      current
    DESCRIPTION
        "Indicates the number of egress Ethernet frames that
         have been dropped."
    ::= { aluPortNgeL2KeygroupStatsEntry 7 }

aluPortNgeL2KeygroupTxDropBytes OBJECT-TYPE
    SYNTAX      Counter64
    MAX-ACCESS  read-only
    STATUS      current
    DESCRIPTION
        "Indicates the number of egress Ethernet bytes that
         have been dropped."
    ::= { aluPortNgeL2KeygroupStatsEntry 8 }

aluPortNgeL2KGRxDrpInvldSpiFrms OBJECT-TYPE
    SYNTAX      Counter64
    MAX-ACCESS  read-only
    STATUS      current
    DESCRIPTION
        "Indicates the number of ingress Ethernet frames that
         have been dropped due to invalid SPI."
    ::= { aluPortNgeL2KeygroupStatsEntry 9 }

aluPortNgeL2KGRxDrpInvldSpiBytes OBJECT-TYPE
    SYNTAX      Counter64
    MAX-ACCESS  read-only
    STATUS      current
    DESCRIPTION
        "Indicates the number of ingress Ethernet bytes that
         have been dropped due to invalid SPI."
    ::= { aluPortNgeL2KeygroupStatsEntry 10 }

aluRS232SocketStatsTable         OBJECT-TYPE
    SYNTAX      SEQUENCE OF AluRS232SocketStatsEntry
    MAX-ACCESS  not-accessible
    STATUS      current
    DESCRIPTION
        "The aluRS232SocketStatsTable contains an entry for each Serial socket
         channel that exists in the system. Each row contains traffic and event
         counters."
    ::= { aluPortStatsObjs 16 }

aluRS232SocketStatsEntry         OBJECT-TYPE
    SYNTAX      AluRS232SocketStatsEntry
    MAX-ACCESS  not-accessible
    STATUS      current
    DESCRIPTION
        "Defines an entry in the aluRS232SocketStatsTable. Entries are
         created and deleted by the system depending on the port
         configuration."
    INDEX   { tmnxChassisIndex, tmnxPortPortID }
    ::= { aluRS232SocketStatsTable 1 }

AluRS232SocketStatsEntry ::=
    SEQUENCE {
        aluRS232SocketRxChars            Counter64,
        aluRS232SocketTxChars            Counter64,
        aluRS232SocketEopIdleTimeoutCnt  Counter64,
        aluRS232SocketEopLengthCnt       Counter64,
        aluRS232SocketEopSpecialCharCnt  Counter64,
        aluRS232SocketIngrForwardedPkts  Counter64,
        aluRS232SocketEgrForwardedPkts   Counter64,
        aluRS232SocketIngrDroppedPkts    Counter64,
        aluRS232SocketEgrDroppedPkts     Counter64,
        aluRS232SocketSquelchCnt         Counter32
    }

aluRS232SocketRxChars            OBJECT-TYPE
    SYNTAX      Counter64
    MAX-ACCESS  read-only
    STATUS      current
    DESCRIPTION
        "The value of the object aluRS232SocketRxChars indicates the number of
         characters received from the Serial data stream."
    ::= { aluRS232SocketStatsEntry 1 }

aluRS232SocketTxChars            OBJECT-TYPE
    SYNTAX      Counter64
    MAX-ACCESS  read-only
    STATUS      current
    DESCRIPTION
        "The value of the object aluRS232SocketTxChars indicates the number of
         characters transmitted to the Serial data stream."
    ::= { aluRS232SocketStatsEntry 2 }

aluRS232SocketEopIdleTimeoutCnt  OBJECT-TYPE
    SYNTAX      Counter64
    MAX-ACCESS  read-only
    STATUS      current
    DESCRIPTION
        "The value of the object aluRS232SocketEopIdleTimeoutCnt indicates the
         number of times an end of packet event occurred due to idle timeout."
    ::= { aluRS232SocketStatsEntry 3 }

aluRS232SocketEopLengthCnt       OBJECT-TYPE
    SYNTAX      Counter64
    MAX-ACCESS  read-only
    STATUS      current
    DESCRIPTION
        "The value of the object aluRS232SocketEopLengthCnt indicates the
         number of times an end of packet event occurred due to length."
    ::= { aluRS232SocketStatsEntry 4 }

aluRS232SocketEopSpecialCharCnt  OBJECT-TYPE
    SYNTAX      Counter64
    MAX-ACCESS  read-only
    STATUS      current
    DESCRIPTION
        "The value of the object aluRS232SocketEopSpecialCharCnt indicates the
         number of times an end of packet event occurred due to special
         character."
    ::= { aluRS232SocketStatsEntry 5 }

aluRS232SocketIngrForwardedPkts  OBJECT-TYPE
    SYNTAX      Counter64
    MAX-ACCESS  read-only
    STATUS      current
    DESCRIPTION
        "The value of the object aluRS232SocketIngrForwardedPkts indicates the
         number of packets (constructed from the incoming Serial data stream)
         that were successfully forwarded."
    ::= { aluRS232SocketStatsEntry 6 }

aluRS232SocketEgrForwardedPkts   OBJECT-TYPE
    SYNTAX      Counter64
    MAX-ACCESS  read-only
    STATUS      current
    DESCRIPTION
        "The value of the object aluRS232SocketIngrForwardedPkts indicates the
         number of packets (destined for the outgoing Serial data stream)
         that were successfully forwarded."
    ::= { aluRS232SocketStatsEntry 7 }

aluRS232SocketIngrDroppedPkts    OBJECT-TYPE
    SYNTAX      Counter64
    MAX-ACCESS  read-only
    STATUS      current
    DESCRIPTION
        "The value of the object aluRS232SocketIngrDroppedPkts indicates the
         number of packets (constructed from the incoming Serial data stream)
         that were dropped due to errors."
    ::= { aluRS232SocketStatsEntry 8 }

aluRS232SocketEgrDroppedPkts     OBJECT-TYPE
    SYNTAX      Counter64
    MAX-ACCESS  read-only
    STATUS      current
    DESCRIPTION
        "The value of the object aluRS232SocketEgrDroppedPkts indicates the
         number of packets (destined for the outgoing Serial data stream)
         that were dropped due to errors."
    ::= { aluRS232SocketStatsEntry 9 }

aluRS232SocketSquelchCnt         OBJECT-TYPE
    SYNTAX      Counter32
    MAX-ACCESS  read-only
    STATUS      current
    DESCRIPTION
        "The value of the object aluRS232SocketSquelchCnt indicates the
         number of times squelch has been activated."
    ::= { aluRS232SocketStatsEntry 10 }

--
-- ALU Data Port table
--
aluDataPortTable OBJECT-TYPE
    SYNTAX      SEQUENCE OF AluDataPortEntry
    MAX-ACCESS  not-accessible
    STATUS      current
    DESCRIPTION
        "The aluDataPortTable has an entry for a physical Data port."
    ::= { aluPortObjs 14 }

aluDataPortEntry OBJECT-TYPE
    SYNTAX      AluDataPortEntry
    MAX-ACCESS  not-accessible
    STATUS      current
    DESCRIPTION
        "Each row entry represents a physical Data port on an IOM card in a
         chassis in the system.  Entries cannot be created and deleted via SNMP
         SET operations.  Entries in this table will be created automatically
         when the tmnxMDAAssignedType object is set to a Data MDA type. The
         aluDataPortEntry contains attributes that are unique to the Data
         TmnxPortType. The tmnxPortPortID contains the slot, mda and port
         numbers encoded into it.

         For each aluDataPortEntry, there will be a corresponding entry in the
         tmnxPortTable and the ifTable."
    INDEX       { tmnxChassisIndex, tmnxPortPortID }
    ::= { aluDataPortTable 1 }

AluDataPortEntry ::=
    SEQUENCE {
        aluDataPortLastChangeTime       TimeStamp,
        aluDataPortType                 INTEGER
    }

aluDataPortLastChangeTime OBJECT-TYPE
    SYNTAX      TimeStamp
    MAX-ACCESS  read-only
    STATUS      current
    DESCRIPTION
        "The value of the object aluDataPortLastChangeTime indicates the
         sysUpTime of the most recently modified writable variable in the
         aluDataPortEntry row for this port.
        "
    ::= { aluDataPortEntry 1 }

aluDataPortType           OBJECT-TYPE
    SYNTAX      INTEGER {
                    codir (1),
                    tpif  (2)
                }
    MAX-ACCESS  read-create
    STATUS      current
    DESCRIPTION
        "The value of the object aluDataPortType specifies the interface-type of
         the physical port.
        "
    DEFVAL { codir }
    ::= { aluDataPortEntry 2 }

--
-- ALU Data table
--
aluDataTable OBJECT-TYPE
    SYNTAX      SEQUENCE OF AluDataEntry
    MAX-ACCESS  not-accessible
    STATUS      current
    DESCRIPTION
        "aluDataTable has an entry for each Data channel on an IOM card
         in each chassis in the system.
        "
    ::= { aluPortObjs 15 }

aluDataEntry       OBJECT-TYPE
    SYNTAX  AluDataEntry
    MAX-ACCESS      not-accessible
    STATUS          current
    DESCRIPTION
        "Each row entry represents a Data channel on an IOM card
         in a chassis in the system.  Channel entries for
         Data ports can be created and deleted via SNMP SET operations.
         For each aluDataEntry, there will be a corresponding entry
         in the tmnxPortTable and the ifTable.
        "
    INDEX   { tmnxChassisIndex, tmnxPortPortID }
    ::= { aluDataTable 1 }

AluDataEntry ::=
SEQUENCE {
        aluDataRowStatus                  RowStatus,
        aluDataLastChangeTime             TimeStamp,
        aluDataType                       INTEGER,
        aluDataClockSource                TmnxDSXClockSource,
        aluDataTiming8k                   TmnxEnabledDisabled,
        aluDataReportAlarm                AluDataReportStatus,
        aluDataReportAlarmStatus          AluDataReportStatus,
        aluDataLoopback                   INTEGER
}

aluDataRowStatus    OBJECT-TYPE
    SYNTAX      RowStatus
    MAX-ACCESS  read-create
    STATUS      current
    DESCRIPTION
        "aluDataRowStatus controls the creation and deletion of
         row entries in the aluDataTable.
         For row creation, the manager has to first calculate the
         tmnxPortPortID based on the TiMOS encoding scheme.
        "
    ::= { aluDataEntry 1 }

aluDataLastChangeTime OBJECT-TYPE
    SYNTAX      TimeStamp
    MAX-ACCESS  read-only
    STATUS      current
    DESCRIPTION
        "The value of the object aluDataLastChangeTime indicates the sysUpTime
         of the most recently modified writable variable in the aluDataEntry row
         for this Data channel.
        "
    ::= { aluDataEntry 2 }

aluDataType OBJECT-TYPE
    SYNTAX      INTEGER {
                    codir (1),
                    tpif  (2)
                }
    MAX-ACCESS  read-only
    STATUS      current
    DESCRIPTION
        "aluDataType indicates the channel type."
    ::= { aluDataEntry 3 }

aluDataClockSource OBJECT-TYPE
    SYNTAX      TmnxDSXClockSource
    MAX-ACCESS  read-only
    STATUS      current
    DESCRIPTION
        "aluDataClockSource indicates the clock for transmitted data from
         either the internal clock ('nodeTimed'), or from a clock recovered
         from the line's receive data stream ('loopTimed'), or recovered
         adaptively from the rate at which the data that is received and not
         from the physical layer ('adaptive'), or recovered from the
         differential timestamp in the RTP header ('differential').

         Only 'nodeTimed' is supported.
        "
    ::= { aluDataEntry 4 }

aluDataTiming8k OBJECT-TYPE
    SYNTAX      TmnxEnabledDisabled
    MAX-ACCESS  read-create
    STATUS      current
    DESCRIPTION
        "The value of the object aluDataTiming8k specifies whether to generate
         the 8k timing signal while the channel's service is NOT operational.

         This object is valid for codir channels only.
        "
   DEFVAL { disabled }
   ::= { aluDataEntry 5 }

aluDataReportAlarm OBJECT-TYPE
    SYNTAX      AluDataReportStatus
    MAX-ACCESS  read-create
    STATUS      current
    DESCRIPTION
        "The value of the object aluDataReportAlarm determines when and if to
         generate aluEqPortDataAlarm and aluEqPortDataAlarmClear
         notifications for this channel.

         Valid bits for codir ports:
         ais (default)
         los (default)

         Valid bits for tpif ports:
         los (default)
         rai (default)
        "
   ::= { aluDataEntry 6 }

aluDataReportAlarmStatus OBJECT-TYPE
    SYNTAX      AluDataReportStatus
    MAX-ACCESS  read-only
    STATUS      current
    DESCRIPTION
        "The value of the object aluDataReportAlarmStatus indicates the current
         alarms on this channel."
    ::= { aluDataEntry 7 }

aluDataLoopback    OBJECT-TYPE
    SYNTAX     INTEGER {
                none     (1),
                internal (2),
                line     (3)
            }
    MAX-ACCESS  read-create
    STATUS      current
    DESCRIPTION
        "The value of the object aluDataLoopback specifies the loopback mode of
         the Data interface.

         An 'internal' loopback loops frames from the local system back at the
         framer.
         A 'line' loopback loops frames received on this port back to the remote
         system.
        "
    DEFVAL  { none }
    ::= { aluDataEntry 8 }

--
-- Data Channel Group Table
--
aluDataChanGroupTable   OBJECT-TYPE
    SYNTAX      SEQUENCE OF AluDataChanGroupEntry
    MAX-ACCESS  not-accessible
    STATUS      current
    DESCRIPTION
        "The aluDataChanGroupTable has an entry for 64kbps (DS0) channels
         grouped together and belonging to a particular Data channel."
    ::= { aluPortObjs 16 }




aluDataChanGroupEntry       OBJECT-TYPE
    SYNTAX      AluDataChanGroupEntry
    MAX-ACCESS  not-accessible
    STATUS      current
    DESCRIPTION
        "Each row entry represents one or more Data channels on an interface.

         Entries can be created and deleted via SNMP SET operations
         using the aluDataChanGroupRowStatus object.

         For each aluDataChanGroupEntry, there will be a corresponding entry
         in the tmnxPortTable and the ifTable.
        "
    INDEX   { tmnxChassisIndex, tmnxPortPortID }
    ::= { aluDataChanGroupTable 1 }

AluDataChanGroupEntry ::=
    SEQUENCE {
        aluDataChanGroupRowStatus        RowStatus,
        aluDataChanGroupLastChangeTime   TimeStamp,
        aluDataChanGroupMTU              Unsigned32,
        aluDataChanGroupOperMTU          Unsigned32,
        aluDataChanGroupPayloadFillType  TmnxDSXIdleFillType,
        aluDataChanGroupPayloadPattern   Unsigned32,
        aluDataChanGroupTimeSlots        TmnxDs0ChannelList
    }

aluDataChanGroupRowStatus    OBJECT-TYPE
    SYNTAX      RowStatus
    MAX-ACCESS  read-create
    STATUS      current
    DESCRIPTION
        "aluDataChanGroupRowStatus controls the creation and deletion of
         row entries in the aluDataChanGroupTable. The tmnxPortPortID
         for a channel group includes a group ID in the lower bits.
         The manager has to first calculate the tmnxPortPortID based on the
         TiMOS encoding scheme."
    ::= { aluDataChanGroupEntry 1 }

aluDataChanGroupLastChangeTime    OBJECT-TYPE
    SYNTAX      TimeStamp
    MAX-ACCESS  read-only
    STATUS      current
    DESCRIPTION
        "The aluDataChanGroupLastChangeTime variable contains the sysUpTime
         value of the most recently modified writable variable in the
         aluDataChanGroupEntry row for this channel group."
    ::= { aluDataChanGroupEntry 2 }

aluDataChanGroupMTU  OBJECT-TYPE
    SYNTAX      Unsigned32
    UNITS       "bytes"
    MAX-ACCESS  read-only
    STATUS      current
    DESCRIPTION
        "The size of the largest packet which can be sent/received
         on the channel group, specified in octets.  For groups that
         are used for transmitting network datagrams, this is the
         size of the largest network datagram that can be sent.

         aluDataChanGroupMTU cannot be modified as only encap-type cem is
         supported. The predetermined default value will always be reflected.
        "
    ::= { aluDataChanGroupEntry 3 }

aluDataChanGroupOperMTU  OBJECT-TYPE
    SYNTAX      Unsigned32
    UNITS       "bytes"
    MAX-ACCESS  read-only
    STATUS      current
    DESCRIPTION
        "The negotiated size of the largest packet which can be sent on
         the channel group, specified in octets.  For channel groups that
         are used for transmitting network datagrams, this is the size of
         the largest network datagram that can be sent."
    ::= { aluDataChanGroupEntry 4 }

aluDataChanGroupPayloadFillType  OBJECT-TYPE
    SYNTAX      TmnxDSXIdleFillType
    MAX-ACCESS  read-create
    STATUS      current
    DESCRIPTION
        "The value of aluDataChanGroupPayloadFillType specifies the type of
         idle payload fill to be sent when the CEM channel group experiences
         an underrun.

         This object is valid for codir channels only.

         If the type is set to 'userDefinedPattern' then the value of
         aluDataChanGroupPayloadPattern is used to define the payload pattern.

         The default value depends on the encap type of the channel group:
         For CEM encap           - 'allOnes'
         For all other encaps    - 'notApplicable' "
    DEFVAL { notApplicable }
    ::= { aluDataChanGroupEntry 5 }

aluDataChanGroupPayloadPattern   OBJECT-TYPE
    SYNTAX      Unsigned32 (0..255)
    MAX-ACCESS  read-create
    STATUS      current
    DESCRIPTION
         "The value of aluDataChanGroupPayloadPattern specifies the idle
         payload
         fill pattern when the CEM channel group experiences an underrun and
         aluDataChanGroupPayloadFillType is set to 'userDefinedPattern'.

         This object is valid for codir channels only.

         The default value depends on the encap type of the channel group:
         For CEM encap channel group             - 255 (Valid range 0..255)
         For non-CEM encap channel group         -   0 (Valid range 0..0)."
    DEFVAL { 0 }
    ::= { aluDataChanGroupEntry 6 }

aluDataChanGroupTimeSlots    OBJECT-TYPE
    SYNTAX      TmnxDs0ChannelList
    MAX-ACCESS  read-create
    STATUS      current
    DESCRIPTION
        "aluDataChanGroupTimeSlots is a bitmap which is used to
         add/remove DS0 timeslots from a channel group.
         The description for TmnxDs0ChannelList contains details of the
         bitmap organization.

         This object specifies the number of CONSECUTIVE timeslot(s) to be
         associated with the channel group. The value must start from the
         first timeslot. The value represents line bandwidth (N x 64kbps).

         For codir, the value cannot be changed from the first timeslot.
         For tpif, the value can range from 1 to 12 timeslots.

         The default value is the first timeslot, 0x00000001."

    ::= { aluDataChanGroupEntry 7 }

--
-- ALU Extensions of tmnxDS0ChanGroupTable
--
aluExtTmnxDS0ChanGroupTable OBJECT-TYPE
    SYNTAX      SEQUENCE OF AluExtTmnxDS0ChanGroupEntry
    MAX-ACCESS  not-accessible
    STATUS      current
    DESCRIPTION
        "The aluExtTmnxDS0ChanGroupTable has an entry for DS0 channels
         grouped together and belonging to a particular DS0/E1 channel"
    ::= { aluPortObjs 17 }

aluExtTmnxDS0ChanGroupEntry  OBJECT-TYPE
    SYNTAX      AluExtTmnxDS0ChanGroupEntry
    MAX-ACCESS  not-accessible
    STATUS      current
    DESCRIPTION
        "Each row entry represents the extended functionality of a DS0 channel
         group.
         Entries cannot be created and deleted via SNMP SET operations.
         It will be automatically created or deleted when an tmnxDS0ChanGroupEntry
         is created/deleted."
    AUGMENTS  { tmnxDS0ChanGroupEntry }
    ::= { aluExtTmnxDS0ChanGroupTable 1 }

AluExtTmnxDS0ChanGroupEntry ::=
    SEQUENCE {
        aluExtDS0ChanGroupSignalMode     INTEGER,
        aluExtDS0ChanGroupLoopback       INTEGER
    }

aluExtDS0ChanGroupSignalMode OBJECT-TYPE
    SYNTAX      INTEGER {
                    none (1),
                    cas  (2)
                }
    MAX-ACCESS  read-create
    STATUS      current
    DESCRIPTION
        "The value of aluExtDS0ChanGroupSignalMode indicates the type of signalling
         associated with the channel:
         none  - Indicates no signalling on this channel.
         cas   - Indicates Channel Associated Signalling (CAS) on this channel.
         The default signalling is 'none'. "
    DEFVAL      { none }
    ::= { aluExtTmnxDS0ChanGroupEntry 1 }

aluExtDS0ChanGroupLoopback       OBJECT-TYPE
    SYNTAX      INTEGER {
                    none (0),
                    line (1),
                    internal (2)
            }
    MAX-ACCESS  read-create
    STATUS      current
    DESCRIPTION
        "The value of aluExtDS0ChanGroupLoopback specifies the type of loopback
         applied to the DS0 channel group. The value of tmnxPortAdminStatus
         should be set to 'outOfService' prior to applying loopback.

         none     - no loopback applied
         line     - loops ingress traffic back to the remote system
         internal - loops egress traffic back to the local system
        "
    DEFVAL      { none }
    ::= { aluExtTmnxDS0ChanGroupEntry 2 }

--
-- ALU Extensions of pethPsePortTable
--
aluExtPethPsePortTable OBJECT-TYPE
    SYNTAX      SEQUENCE OF AluExtPethPsePortEntry
    MAX-ACCESS  not-accessible
    STATUS      current
    DESCRIPTION
        "The aluExtPethPsePortTable has an entry for a table of objects
        that display and control the power characteristics of power Ethernet
        ports on a Power Source Entity (PSE) device."
    ::= { aluPortObjs 18 }

aluExtPethPsePortEntry  OBJECT-TYPE
    SYNTAX      AluExtPethPsePortEntry
    MAX-ACCESS  not-accessible
    STATUS      current
    DESCRIPTION
        "Each row entry represents the extended functionality of a power Ethernet
        port"
    AUGMENTS  { pethPsePortEntry }
    ::= { aluExtPethPsePortTable 1 }

AluExtPethPsePortEntry ::=
    SEQUENCE {
        aluExtPethPsePortFaultReason INTEGER,
        aluExtPethPsePortPowerLevel INTEGER,
        aluExtPethPsePortPowerConsumption Unsigned32,
        aluExtPethPsePortMaximumPower Unsigned32
    }

aluExtPethPsePortFaultReason OBJECT-TYPE
    SYNTAX INTEGER   {
             none   (1),
             dcp    (2),
             hicap  (3),
             rlow   (4),
             detok  (5),
             rhigh  (6),
             open   (7),
             dcn    (8),
             tstart (9),
             icv    (10),
             tcut   (11),
             dis    (12),
             sup    (13)
          }
    MAX-ACCESS  read-only
    STATUS      current
    DESCRIPTION
        "Reason for a detection status failure:
          none   (1)
          dcp    (2) - Positive DC supply connected at the port
          hicap  (3) - High Capacitance at the port
          rlow   (4) - Low Resistance at the port
          detok  (5) - detection ok
          rhigh  (6) - High resistance at the port
          open   (7) - open circuit
          dcn    (8) - Low impedence to Vee at the port
          tstart (9) - Startup failure at the port
          icv   (10) - Current limit disconnect timeout at the port
          tcut  (11) - Overcurrent and current limit violation at the port
          dis   (12) - DC load disconnect
          sup   (13) - Supply fault at the PSE device"
    DEFVAL      { none }
    ::= { aluExtPethPsePortEntry 1 }

aluExtPethPsePortPowerLevel OBJECT-TYPE
    SYNTAX INTEGER   {
               none     (1),
               standard (2),
               plus     (3)
          }
    MAX-ACCESS  read-write
    STATUS      current
    DESCRIPTION
        "none     (1) The interface does not provide the power ethernet function.
         standard (2) The interface provides the standard power ethernet power level.
         plus     (3) The interface provides the higher power 'Poe Plus' PSE function"
    DEFVAL      { plus }
    ::= { aluExtPethPsePortEntry 2 }

aluExtPethPsePortPowerConsumption OBJECT-TYPE
    SYNTAX      Unsigned32
    UNITS      "Milliwatts"
    MAX-ACCESS  read-only
    STATUS      current
    DESCRIPTION
        "The power consumption of the port expressed in milliwatts."
    ::= { aluExtPethPsePortEntry 3 }

aluExtPethPsePortMaximumPower OBJECT-TYPE
    SYNTAX      Unsigned32
    UNITS      "Milliwatts"
    MAX-ACCESS  read-only
    STATUS      current
    DESCRIPTION
        "The maximum power available to the port expressed in milliwatts."
    ::= { aluExtPethPsePortEntry 4 }

--
-- ALU Extensions of Tmnx Port table
--
aluExtPortTable OBJECT-TYPE
    SYNTAX      SEQUENCE OF AluExtTmnxPortEntry
    MAX-ACCESS  not-accessible
    STATUS      current
    DESCRIPTION
        "The aluExtPortTable has an entry for port in the chassis."
    ::= { aluPortObjs 19 }

aluExtTmnxPortEntry       OBJECT-TYPE
    SYNTAX      AluExtTmnxPortEntry
    MAX-ACCESS  not-accessible
    STATUS      current
    DESCRIPTION
        "Each row entry represents extended functionality of a port on
        Nokia 7705 SAR devices. Entries cannot be created or
        deleted via SNMP SET operations. Entries in this table will be
        created or deleted automatically when entries in the
        tmnxPortTable are created or deleted."
    AUGMENTS  { tmnxPortEntry }
    ::= { aluExtPortTable 1 }

AluExtTmnxPortEntry ::=
    SEQUENCE {
        aluExtPortSsmTxQualityLevel INTEGER
    }

aluExtPortSsmTxQualityLevel   OBJECT-TYPE
    SYNTAX      INTEGER {
                    unknown (0),
                    prs     (1),
                    stu     (2),
                    st2     (3),
                    tnc     (4),
                    st3e    (5),
                    st3     (6),
                    smc     (7),
                    st4     (8),
                    dus     (9),
                    prc     (10),
                    ssua    (11),
                    ssub    (12),
                    sec     (13),
                    dnu     (14),
                    inv     (15),
                    pno     (16),
                    eec1    (17),
                    eec2    (18),
                    failed  (19)
                }
    MAX-ACCESS  read-only
    STATUS      current
    DESCRIPTION
        "aluExtPortSsmTxQualityLevel indicates the SSM quality level
         of transmitted SSM messages. On ports not supporting SSM, or not
         transmitting SSM messages, the quality level will be 'unknown (0)'.

         The values 'prs (1)' through 'dus (9)' and 'pno (16)' correspond to
         quality levels defined in GR-253-CORE.  The values 'prc (10)' through
         'inv (15)' correspond to quality levels defined in G.781.
         The values 'eec1 (17)' and 'eec2 (18)' correspond to quality levels
         defines in G.8264."
    REFERENCE
        "Bellcore (Telcordia Technologies) GR-253-CORE, Issue 3, September 2000,
         5.4.2.
         ITU-T Recommendation G.781, June 1999.
         ITU-T Recommendation G.8264, October 2008."
    DEFVAL { unknown }
    ::= { aluExtTmnxPortEntry 1 }

--
-- ALU Scada Bridge table
--
aluScadaBridgeTable OBJECT-TYPE
    SYNTAX      SEQUENCE OF AluScadaBridgeEntry
    MAX-ACCESS  not-accessible
    STATUS      current
    DESCRIPTION
        "The aluScadaBridgeTable has an entry for a Scada Bridge."
    ::= { aluPortObjs 20 }

aluScadaBridgeEntry       OBJECT-TYPE
    SYNTAX      AluScadaBridgeEntry
    MAX-ACCESS  not-accessible
    STATUS      current
    DESCRIPTION
        "Each row entry represents a Scada bridge
         in the system.  Entries cannot be created
         and deleted via SNMP SET operations.  Entries in this table will
         be created automatically when the tmnxMDAAssignedType object is
         set to the SCADA MDA type. The aluScadaBridgeEntry contains attributes
         that are unique to the Scada bridge. The
         port ID contains the slot, mda and bridge id(1-10) encoded into it."

    INDEX       { tmnxChassisIndex, tmnxPortPortID }
    ::= { aluScadaBridgeTable 1 }

AluScadaBridgeEntry ::=
    SEQUENCE {
        aluScadaBridgeType               INTEGER,
        aluScadaBridgeAdminStatus        INTEGER,
        aluScadaBridgeOperStatus         INTEGER,
        aluScadaBridgeDescription        TItemLongDescription,
        aluScadaBridgeName               TNamedItemOrEmpty
    }

aluScadaBridgeType           OBJECT-TYPE
    SYNTAX      INTEGER {
                    mddb (1),
                    pcm (2),
                    vcb (3)
                }
    MAX-ACCESS  read-only
    STATUS      current
    DESCRIPTION
        "The value of the object aluScadaBridgeType indicates the type of the
         scada bridge.

         Due to FPGA limitations, all scada bridges on a SCADA card must
         be the same type. The type is determined by the mda mode,
         aluExtTmnxMDACapabilityMode."

    ::= { aluScadaBridgeEntry 1 }

aluScadaBridgeAdminStatus    OBJECT-TYPE
    SYNTAX      INTEGER {
                    outOfService (0),
                    inService (1)
                }
    MAX-ACCESS  read-write
    STATUS      current
    DESCRIPTION
        "aluScadaBridgeAdminStatus indicates the admin status of the scada bridge"

    ::= { aluScadaBridgeEntry 2 }

aluScadaBridgeOperStatus    OBJECT-TYPE
    SYNTAX      INTEGER {
                    outOfService (0),
                    inService (1)
                }
    MAX-ACCESS  read-only
    STATUS      current
    DESCRIPTION
        "aluScadaBridgeOperStatus indicates the operational status of the scada bridge"

    ::= { aluScadaBridgeEntry 3 }

aluScadaBridgeDescription   OBJECT-TYPE
    SYNTAX      TItemLongDescription
    MAX-ACCESS  read-write
    STATUS      current
    DESCRIPTION
        "A textual string containing user supplied information about the
         scada bridge."
    DEFVAL { ''H }

    ::= { aluScadaBridgeEntry 4 }

aluScadaBridgeName               OBJECT-TYPE
    SYNTAX      TNamedItemOrEmpty
    MAX-ACCESS  read-only
    STATUS      current
    DESCRIPTION
        "The textual name of the interface.  The value of this
         object should be the name of the interface as assigned by
         the local device and should be suitable for use in commands
         entered at the device's `console'.  This might be a text
         name, such as `1/1/1'."
    ::= { aluScadaBridgeEntry 5 }


--
-- ALU Serial MDDB table
--
aluSerialMddbTable OBJECT-TYPE
   SYNTAX      SEQUENCE OF AluSerialMddbEntry
    MAX-ACCESS  not-accessible
    STATUS      current
    DESCRIPTION
         "aluSerialMddbTable has an entry for each Serial
         MDDB port on each IOM card in each chassis in the system."
    ::= { aluPortObjs 21 }


aluSerialMddbEntry       OBJECT-TYPE
    SYNTAX  AluSerialMddbEntry
    MAX-ACCESS      not-accessible
    STATUS          current
    DESCRIPTION
         "Each row entry represents a Serial MDDB in the system.  Entries for
         serial mddbs can not be created and deleted via SNMP SET operations.
         The Entries are automatically created when the tmnxMDAAssignedType object is
         set to the SCADA MDA type and mode mode supports serail MDDB.
         For each aluSerialMddbEntry, there will be a corresponding entry
         in the aluScadaBridgeTable."
    INDEX   { tmnxChassisIndex, tmnxPortPortID }
    ::= { aluSerialMddbTable 1 }

AluSerialMddbEntry ::=
SEQUENCE {
        aluSerialMddbReportAlarms            AluRS232ReportStatus,
        aluSerialMddbForceActive             INTEGER,
        aluSerialMddbSquelchStatus           Unsigned32,
        aluSerialMddbSquelchEnable           INTEGER,
        aluSerialMddbSquelchTimeout          INTEGER,
        aluSerialMddbSquelchReset            INTEGER,
        aluSerialMddbSpeed                   INTEGER,
        aluSerialMddbSquelchResetMode        INTEGER,
        aluSerialMddbSquelchResetTimeout     INTEGER,
        aluSerialMddbRedMode                 INTEGER
}


aluSerialMddbReportAlarms OBJECT-TYPE
    SYNTAX      AluRS232ReportStatus
    MAX-ACCESS  read-create
    STATUS      current
    DESCRIPTION
        "The value of aluSerialMddbReportAlarms determines if the
         the following alarms for branches belong to the Mddb should be monitored.

         hcmOof - Reports local HCM out-of-frame errors.
         hcmRai - Reports remote HCM alarm indication.
         ctrlLeadMon - (not supported)
         monClockDev - (not supported)
         monDataInac - (not supported)

         If enabled, the alarms will be show in aluScadaBranchAlarmStatus"

    DEFVAL      { {hcmOof, hcmRai} }
   ::= { aluSerialMddbEntry 1 }

aluSerialMddbForceActive OBJECT-TYPE
    SYNTAX      INTEGER (1..2)
    MAX-ACCESS  read-create
    STATUS      current
    DESCRIPTION
        "aluSerialMddbForceActive forces the specified master branch to be
         active. default is the master branch 1.
         Not configurable in when aluSerialMddbRedMode is auto"
    DEFVAL      { 1 }
   ::= { aluSerialMddbEntry 2 }

aluSerialMddbSquelchStatus OBJECT-TYPE
    SYNTAX      Unsigned32
    MAX-ACCESS  read-only
    STATUS      current
    DESCRIPTION
        "aluSerialMddbSquelchStatus shows squelch status of the scada bridge. It is a 32-bit integer and
         each bit represent a branch. Bit with value one indicates that the associated branch is squelched."
   ::= { aluSerialMddbEntry 3 }


aluSerialMddbSquelchEnable OBJECT-TYPE
    SYNTAX      INTEGER {
                    false (1),
                    true  (2)
                }
    MAX-ACCESS  read-create
    STATUS      current
    DESCRIPTION
        "During nomal SCADA system operation, it is common for a single slave to lock-up
         and continue to send data after the allocated response time. To solve the problem,
         the bridge has a squelching function which will over-ride the incoming data on the locked up
         slave with all ones.

         aluSerialMddbSquelchEnable enables and disables squelching function for the specified MDDB.
        "
    DEFVAL { false }
    ::= { aluSerialMddbEntry 4 }


aluSerialMddbSquelchTimeout OBJECT-TYPE
    SYNTAX      INTEGER (1..120)
    MAX-ACCESS  read-create
    STATUS      current
    DESCRIPTION
        "The bridge will start squelching after a user-selectable time period.

         aluSerialMddbSquelchTimeout specifies such a period in seconds. It can only be set to value larger than
         zero. Value zero is an undefined value."
    DEFVAL      { 1 }
    ::= { aluSerialMddbEntry 5 }


aluSerialMddbSquelchReset   OBJECT-TYPE
    SYNTAX      INTEGER {
                    noAction (1),
                    action   (2)
                }
    MAX-ACCESS  read-create
    STATUS      current
    DESCRIPTION
        "aluSerialMddbSquelchReset is a one shot action used to reset the squelching."
    DEFVAL { noAction }
    ::= { aluSerialMddbEntry 6 }

aluSerialMddbSpeed OBJECT-TYPE
    SYNTAX      INTEGER {
                    speed1200  (1),
                    speed2400  (2),
                    speed9600  (3),
                    speed19200 (4),
                    speed38400 (5),
                    speed56000 (6),
                    speed4800  (23),
                    speed600   (24)
                }
    MAX-ACCESS  read-create
    STATUS      current
    DESCRIPTION
        "aluSerialMddbSpeed specifies the speed of the Mddb.
         A value of 'speed1200' sets the bridge to 1200bps.  These
         speed definitions are consistent with those used for RS232 port.

         The speed of the bridge should match to the speed configured on
         the RS232 port of the branches."
   DEFVAL { speed2400 }
    ::= { aluSerialMddbEntry 7 }

aluSerialMddbSquelchResetMode OBJECT-TYPE
    SYNTAX      INTEGER {
                    manual  (1),
                    auto    (2)
                }
    MAX-ACCESS  read-create
    STATUS      current
    DESCRIPTION
        "aluSerialMddbResetMode specifies the method of re-enabling squelched branch.
         In manual mode, squelched branches can be only re-enabled when user sets  aluSerialMddbSquelchReset.
         In auto mode, squelched branches will be re-enabled after a user defined timeout period."
   DEFVAL { manual }
    ::= { aluSerialMddbEntry 8 }

aluSerialMddbSquelchResetTimeout OBJECT-TYPE
    SYNTAX      INTEGER (1..120)
    MAX-ACCESS  read-create
    STATUS      current
    DESCRIPTION
        "aluSerialMddbResetTimeout specifies how long the squelched branches have to be remain squelched,
         after the squelch condition is cleared and before it can be re-enabled.
         It is only meaningful when aluSerialMddbResetMode is auto."
    DEFVAL      { 1 }
    ::= { aluSerialMddbEntry 9 }

aluSerialMddbRedMode OBJECT-TYPE
    SYNTAX      INTEGER {
                    manual  (1),
                    auto    (2)
                }
    MAX-ACCESS  read-create
    STATUS      current
    DESCRIPTION
        "aluSerialMddbRedMode specifies the redundant mode of the bridge.
         In auto mode, both master branches are active; one could be for voice and another one for data.
         In manual mode, only one master branch can be active; User can use aluSerialMddbForceActive to set a particular master as active."
   DEFVAL { manual }
    ::= { aluSerialMddbEntry 10 }

--
-- Scada Bridge Member Table
--
aluScadaBranchTable   OBJECT-TYPE
    SYNTAX      SEQUENCE OF AluScadaBranchEntry
    MAX-ACCESS  not-accessible
    STATUS      current
    DESCRIPTION
        "The aluScadaBranchTable has an entry for each branch
         belonging to a particular scada bridge."
    ::= { aluPortObjs 22 }

aluScadaBranchEntry       OBJECT-TYPE
    SYNTAX      AluScadaBranchEntry
    MAX-ACCESS  not-accessible
    STATUS      current
    DESCRIPTION
        "Each row entry represents one branch on the bridge.

         Entries can be created and deleted via SNMP SET operations
         using the aluScadaBranchRowStatus object."

    INDEX       { tmnxChassisIndex, tmnxPortPortID }
    ::= { aluScadaBranchTable 1 }

AluScadaBranchEntry ::=
    SEQUENCE {
        aluScadaBranchRowStatus          RowStatus,
        aluScadaBranchAdminStatus        INTEGER,
        aluScadaBranchOperStatus         INTEGER,
        aluScadaBranchMultiDrop          INTEGER,
        aluScadaBranchAlarmStatus        AluRS232ReportStatus,
        aluScadaBranchDescription        TItemLongDescription,
        aluScadaBranchEncapType          INTEGER,
        aluScadaBranchMode               INTEGER,
        aluScadaBranchSquelch            INTEGER,
        aluScadaBranchGainInput          Integer32,
        aluScadaBranchGainOutput         Integer32,
        aluScadaBranchGainSidetoneEnable TmnxEnabledDisabled,
        aluScadaBranchName               TNamedItemOrEmpty
    }

aluScadaBranchRowStatus    OBJECT-TYPE
    SYNTAX      RowStatus
    MAX-ACCESS  read-create
    STATUS      current
    DESCRIPTION
        "aluScadaBranchRowStatus controls the creation and deletion of
         row entries in the aluScadaBranchTable. The tmnxPortPortID
         The port ID contains the slot, mda, bridge id and branch id
         encoded into it."
    ::= { aluScadaBranchEntry 1 }

aluScadaBranchAdminStatus    OBJECT-TYPE
    SYNTAX      INTEGER {
                    outOfService (0),
                    inService (1)
                }
    MAX-ACCESS  read-create
    STATUS      current
    DESCRIPTION
        "aluScadaBranchAdminStatus indicates the admin status of the scada branch."
    ::= { aluScadaBranchEntry 2 }

aluScadaBranchOperStatus    OBJECT-TYPE
    SYNTAX      INTEGER {
                    outOfService (0),
                    inService (1)
                }
    MAX-ACCESS  read-only
    STATUS      current
    DESCRIPTION
        "aluScadaBranchOperStatus indicates the operational status of the scada branch"
    ::= { aluScadaBranchEntry 3 }


aluScadaBranchMultiDrop    OBJECT-TYPE
    SYNTAX      INTEGER {
                    slave    (1),
                    master   (2)
                }
    MAX-ACCESS  read-only
    STATUS      current
    DESCRIPTION
        "aluScadaBranchMultiDrop is used to specify the Multi-drop Data Bridge
         (Mddb) mode of the branch. Branch 1-2 are fixed to Master, and 3-32
         are fixed to Slaves.

         This object is not applicable while aluExtTmnxMDACapabilityMode is
         'modeC' (ie. VCB)."
    ::= { aluScadaBranchEntry 4 }

aluScadaBranchAlarmStatus OBJECT-TYPE
    SYNTAX      AluRS232ReportStatus
    MAX-ACCESS  read-only
    STATUS      current
    DESCRIPTION
        "The value of aluScadaBranchAlarmStatus indicates the alarms on this
         scada branch.

         This object is not applicable while aluExtTmnxMDACapabilityMode is
         'modeC' (ie. VCB)."
    ::= { aluScadaBranchEntry 5 }

aluScadaBranchDescription   OBJECT-TYPE
    SYNTAX      TItemLongDescription
    MAX-ACCESS  read-create
    STATUS      current
    DESCRIPTION
        "A textual string containing user supplied information about the
         scada bridge branch."
    DEFVAL { ''H }

    ::= { aluScadaBranchEntry 6 }

aluScadaBranchEncapType     OBJECT-TYPE
    SYNTAX      INTEGER {
                    unknown (0),
                    nullEncap (1),
                    qEncap (2),
                    mplsEncap (3),
                    bcpNullEncap (4),
                    bcpDot1qEncap (5),
                    ipcpEncap (6),
                    frEncap (7),
                    pppAutoEncap (8),
                    atmEncap (9),
                    qinqEncap (10),
                    wanMirrorEncap (11),
                    ciscoHDLCEncap (12),
                    cemEncap (13)
                }
    MAX-ACCESS  read-only
    STATUS      current
    DESCRIPTION
        "The type of encapsulation protocol configured on this branch. It
         scada bridge branch."
    DEFVAL { cemEncap }

    ::= { aluScadaBranchEntry 7 }

aluScadaBranchMode          OBJECT-TYPE
    SYNTAX      INTEGER {
                    undefined (0),
                    access (1),
                    network (2)
                }
    MAX-ACCESS  read-only
    STATUS      current
    DESCRIPTION
        "The aluScadaBranchMode  indicates if the branch is configured as a service access or a network access."
    DEFVAL { access }

    ::= { aluScadaBranchEntry 8 }

aluScadaBranchSquelch       OBJECT-TYPE
    SYNTAX      INTEGER {
                    undefined (0),
                    disabled (1),
                    enabled (2)
                }
    MAX-ACCESS  read-create
    STATUS      current
    DESCRIPTION
        "The aluScadaBranchSquelch indicates if the branch is enabled for
         squelch. If enabled, the bridge-level squelch needs to be enabled as
         well to take effect; default value is enabled for slaves and disabled
         for masters to allow a seemless upgrade for mddb branches.

         This object is invalid while aluExtTmnxMDACapabilityMode is 'modeC'
         (ie. VCB)."
    DEFVAL { disabled }

    ::= { aluScadaBranchEntry 9 }

aluScadaBranchGainInput          OBJECT-TYPE
    SYNTAX      Integer32 (-160..90)
    UNITS       "tenths of decibels"
    MAX-ACCESS  read-create
    STATUS      current
    DESCRIPTION
        "The value of the object aluScadaBranchGainInput specifies the input
         gain for a given branch.

         This object is valid only while aluExtTmnxMDACapabilityMode is
         'modeC' (ie. VCB).

         Although the units are in tenths of decibels, only increments of 1db
         are currently supported (eg. -160, -150, ..., 80, 90)."
    DEFVAL { 0 }
    ::= { aluScadaBranchEntry 10 }

aluScadaBranchGainOutput         OBJECT-TYPE
    SYNTAX      Integer32 (-160..90)
    UNITS       "tenths of decibels"
    MAX-ACCESS  read-create
    STATUS      current
    DESCRIPTION
        "The value of the object aluScadaBranchGainOutput specifies the output
         gain for a given branch.

         This object is valid only while aluExtTmnxMDACapabilityMode is
         'modeC' (ie. VCB).

         Although the units are in tenths of decibels, only increments of 1db
         are currently supported (eg. -160, -150, ..., 80, 90)."
    DEFVAL { 0 }
    ::= { aluScadaBranchEntry 11 }

aluScadaBranchGainSidetoneEnable OBJECT-TYPE
    SYNTAX      TmnxEnabledDisabled
    MAX-ACCESS  read-create
    STATUS      current
    DESCRIPTION
        "The value of the object aluScadaBranchGainSidetoneEnable specifies
         whether sidetone gain is to be applied for a given branch.

         This object is valid only while aluExtTmnxMDAVcbApplication is 'vcb'.
        "
    DEFVAL { disabled }
    ::= { aluScadaBranchEntry 12 }

aluScadaBranchName               OBJECT-TYPE
    SYNTAX      TNamedItemOrEmpty
    MAX-ACCESS  read-only
    STATUS      current
    DESCRIPTION
        "The textual name of the interface.  The value of this
         object should be the name of the interface as assigned by
         the local device and should be suitable for use in commands
         entered at the device's `console'.  This might be a text
         name, such as `1/1/1.1'."
    ::= { aluScadaBranchEntry 13 }


--
-- Ethernet Loopback Vlan Table
--
aluPortCfmLbVlanTable   OBJECT-TYPE
    SYNTAX      SEQUENCE OF AluPortCfmLbVlanEntry
    MAX-ACCESS  not-accessible
    STATUS      obsolete
    DESCRIPTION
        "The aluPortCfmLbVlanTable has an entry for a vlan Id of the port that must have
         aluExtPortEtherLoopbackCfmLbMode set to priority-dot1p."
    ::= { aluPortObjs 23 }

aluPortCfmLbVlanEntry       OBJECT-TYPE
    SYNTAX      AluPortCfmLbVlanEntry
    MAX-ACCESS  not-accessible
    STATUS      obsolete
    DESCRIPTION
        "Each row entry represents an acceptable vlan ID in the tag of incoming CFM LB frames
        destined to the ethernet port with tmnxPortPortID.

         Entries can be created and deleted via SNMP SET operations using the aluPortCfmLbVlanRowStatus object. "
    INDEX       { tmnxChassisIndex, tmnxPortPortID, aluPortCfmLbVlanId }
    ::= { aluPortCfmLbVlanTable 1 }

AluPortCfmLbVlanEntry ::=
    SEQUENCE {
        aluPortCfmLbVlanId                        Unsigned32,
        aluPortCfmLbVlanRowStatus           RowStatus
    }

aluPortCfmLbVlanId    OBJECT-TYPE
    SYNTAX           Unsigned32 (1..4094)
    MAX-ACCESS  read-create
    STATUS           obsolete
    DESCRIPTION
        " aluPortCfmLbVlanId indicates the vlan ID of the ethernet port."
    ::= { aluPortCfmLbVlanEntry 1 }

aluPortCfmLbVlanRowStatus    OBJECT-TYPE
    SYNTAX      RowStatus
    MAX-ACCESS  read-create
    STATUS      obsolete
    DESCRIPTION
        "The value of aluPortCfmLbVlanRowStatus specifies the status of this row.

        The only values supported during a set operation are  'createAndGo' and 'destroy'.

        'createAndGo' can only be applied to ports with aluExtPortEtherLoopbackCfmLbMode set to priority-dot1p.
        When createAndGo is successful, the value of aluPortCfmLbVlanRowStatus becomes 'active'.   Any incoming
        CFM LB frame destined for this tmnxPortPortID will get processed if it has no vlan tags or it has a vlan tag
        matched with aluPortCfmLbVlanId of an active row entry."

    ::= { aluPortCfmLbVlanEntry 2 }

--
-- ALU GNSS Port table
--
aluGnssPortTable OBJECT-TYPE
    SYNTAX      SEQUENCE OF AluGnssPortEntry
    MAX-ACCESS  not-accessible
    STATUS      current
    DESCRIPTION
        "The aluGnssPortTable has an entry for a physical GNSS port."
    ::= { aluPortObjs 24 }

aluGnssPortEntry OBJECT-TYPE
    SYNTAX      AluGnssPortEntry
    MAX-ACCESS  not-accessible
    STATUS      current
    DESCRIPTION
        "Each row entry represents a physical GNSS port on an IOM card in a
         chassis in the system.  Entries cannot be created and deleted via SNMP
         SET operations.  Entries in this table will be created automatically
         when the tmnxMDAAssignedType object is set to a GNSS-capable MDA type.
         The aluGnssPortEntry contains attributes that are unique to the GNSS
         TmnxPortType. The tmnxPortPortID contains the slot, mda and port
         numbers encoded into it.

         For each aluGnssPortEntry, there will be a corresponding entry in the
         tmnxPortTable and the ifTable."
    INDEX       { tmnxChassisIndex, tmnxPortPortID }
    ::= { aluGnssPortTable 1 }

AluGnssPortEntry ::=
    SEQUENCE {
        aluGnssPortLastChangeTime           TimeStamp,
        aluGnssPortType                     BITS,
        aluGnssPortAntennaCableDelay        INTEGER,
        aluGnssPortElevationMaskAngle       Integer32,
        aluGnssPortVisibleSatelliteCount    Unsigned32,
        aluGnssPortUsedSatelliteCount       Unsigned32,
        aluGnssPortAntennaStatus            INTEGER,
        aluGnssPortSyncStatus               INTEGER,
        aluGnssPortPositionLatitude         INTEGER,
        aluGnssPortPositionLongitude        INTEGER,
        aluGnssPortPositionAltitude         INTEGER,
        aluGnssPortDateAndTime              DateAndTime,
        aluGnssPortReceiverStatus           DisplayString,
        aluGnssPortCurUtcOffset             Integer32,
        aluGnssPortCurUtcOffsetValid        TruthValue,
        aluGnssPortReceiverFwVersion        DisplayString
    }

aluGnssPortLastChangeTime OBJECT-TYPE
    SYNTAX      TimeStamp
    MAX-ACCESS  read-only
    STATUS      current
    DESCRIPTION
        "The value of aluGnssPortLastChangeTime indicates the sysUpTime at
         the time of the last modification of this entry."
    ::= { aluGnssPortEntry 1 }

aluGnssPortType           OBJECT-TYPE
    SYNTAX      BITS {
                    gps     (0),
                    glonass (1)
                }
    MAX-ACCESS  read-write
    STATUS      current
    DESCRIPTION
        "The value of the object aluGnssPortType specifies which constellation
         types the installed GNSS receiver module shall process."
    DEFVAL { {gps} }
    ::= { aluGnssPortEntry 2 }

aluGnssPortAntennaCableDelay OBJECT-TYPE
    SYNTAX      INTEGER (0..32767)
    UNITS       "1 ns"
    MAX-ACCESS  read-write
    STATUS      current
    DESCRIPTION
        "The value of the object aluGnssPortAntennaCableDelay specifies the
         antenna cable delay that has to be taken into account given the
         characteristics (eg. length) of the installed antenna cable."
    DEFVAL { 0 }
    ::= { aluGnssPortEntry 3 }

aluGnssPortElevationMaskAngle OBJECT-TYPE
    SYNTAX      Integer32 (0..89)
    UNITS       "1 degree"
    MAX-ACCESS  read-write
    STATUS      current
    DESCRIPTION
        "The value of the object aluGnssPortElevationMaskAngle specifies the
         the elevation mask angle. It provides a method of
         filtering satellites to be used by the system.

         Elevation angle is the angle above the horizon. When satellites are
         close to horizon, there is more atmosphere, troposphere, and
         ionosphere for the signals to go through (ie. more noise).
         Elevation angle mask determines the minimum elevation angle below
         which the GNSS receiver module will not use a satellite in its
         computations.

        Typical values are 10 and 15 degrees."
    DEFVAL { 10 }
    ::= { aluGnssPortEntry 4 }

aluGnssPortVisibleSatelliteCount OBJECT-TYPE
    SYNTAX      Unsigned32
    MAX-ACCESS  read-only
    STATUS      current
    DESCRIPTION
        "The value of the object aluGnssPortVisibleSatelliteCount indicates the
         number of satellites currently 'seen' by the GNSS receiver module."
    ::= { aluGnssPortEntry 5 }

aluGnssPortUsedSatelliteCount OBJECT-TYPE
    SYNTAX      Unsigned32
    MAX-ACCESS  read-only
    STATUS      current
    DESCRIPTION
        "The value of the object aluGnssPortUsedSatelliteCount indicates the
         number of satellites currently 'used' in computations by the GNSS
         receiver module."
    ::= { aluGnssPortEntry 6 }

aluGnssPortAntennaStatus OBJECT-TYPE
    SYNTAX      INTEGER {
                    unknown (1),
                    unsupported (2),
                    ok (3),
                    overCurrent (4),
                    underCurrent (5),
                    noBiasVoltage (6)
                }
    MAX-ACCESS  read-only
    STATUS      current
    DESCRIPTION
        "The value of the object aluGnssPortAntennaStatus indicates the status
         of the antenna."
    ::= { aluGnssPortEntry 7 }

aluGnssPortSyncStatus OBJECT-TYPE
    SYNTAX      INTEGER {
                    unknown (1),
                    locked (2),
                    notLocked (3)
                }
    MAX-ACCESS  read-only
    STATUS      current
    DESCRIPTION
        "The value of the object aluGnssPortSyncStatus indicates the status
         of the GNSS receiver module with respect to generating a sync-worthy
         clock signal."
    ::= { aluGnssPortEntry 8 }

aluGnssPortPositionLatitude OBJECT-TYPE
    SYNTAX INTEGER (-9000000..9000000|134217727)
    UNITS "0.00001 decimal degrees"
    MAX-ACCESS read-only
    STATUS current
    DESCRIPTION
        "The value of the object aluGnssPortPositionLatitude indicates the
         latitude of the antenna.

         Encoding:
            < 0: west of prime meridian
            = 0: at prime meridian
            > 0: east of prime meridian
         The unit corresponds to a resolution of approximately 1.11 metres.

         The default value is 134217727. It's considered invalid. It's used to
         signify that a surveyed (valid) position has yet to be determined."
    ::= { aluGnssPortEntry 9 }

aluGnssPortPositionLongitude OBJECT-TYPE
    SYNTAX INTEGER (-18000000..18000000|134217727)
    UNITS "0.00001 decimal degrees"
    MAX-ACCESS read-only
    STATUS current
    DESCRIPTION
        "The value of the object aluGnssPortPositionLongitude indicates the
         longitude of the antenna.

         Encoding:
            < 0: south of equator
            = 0: at equator
            > 0: north of equator
         The unit corresponds to a resolution of approximately 1.11 metres.

         The default value is 134217727. It's considered invalid. It's used to
         signify that a surveyed (valid) position has yet to be determined."
    ::= { aluGnssPortEntry 10 }

aluGnssPortPositionAltitude OBJECT-TYPE
    SYNTAX INTEGER (-1000..10000|134217727)
    UNITS "1 metre"
    MAX-ACCESS read-only
    STATUS current
    DESCRIPTION
        "The value of the object aluGnssPortPositionAltitude indicates the
         altitude of the antenna.

         Encoding:
            < 0: below sea level
            = 0: at sea level
            > 0: above sea level

         The default value is 134217727. It's considered invalid. It's used to
         signify that a surveyed (valid) position has yet to be determined."
    ::= { aluGnssPortEntry 11 }

aluGnssPortDateAndTime       OBJECT-TYPE
    SYNTAX      DateAndTime
    MAX-ACCESS  read-only
    STATUS      current
    DESCRIPTION
        "The value of the object aluGnssPortDateAndTime indicates the current
         date and time as provided by the receiver module."
    ::= { aluGnssPortEntry 12 }

aluGnssPortReceiverStatus OBJECT-TYPE
    SYNTAX      DisplayString
    MAX-ACCESS  read-only
    STATUS      current
    DESCRIPTION
        "The value of the object aluGnssPortReceiverStatus indicates the
         status of the GNSS receiver module."
    ::= { aluGnssPortEntry 13 }

aluGnssPortCurUtcOffset OBJECT-TYPE
    SYNTAX      Integer32 (-65536..65535)
    MAX-ACCESS  read-only
    STATUS      current
    DESCRIPTION
        "The value of the object aluGnssPortCurUtcOffset indicates the
         current offset between GPS time and UTC in seconds, as provided by the
         GNSS receiver module.

         The value can be valid or invalid. See aluGnssPortCurUtcOffsetValid."
    ::= { aluGnssPortEntry 14 }

aluGnssPortCurUtcOffsetValid OBJECT-TYPE
    SYNTAX 	    TruthValue
    MAX-ACCESS  read-only
    STATUS      current
    DESCRIPTION
        "The value of the object aluGnssPortCurUtcOffsetValid indicates
         'true (1)' if the aluGnssPortCurUtcOffset is known to be correct."
    ::= { aluGnssPortEntry 15 }

aluGnssPortReceiverFwVersion     OBJECT-TYPE
    SYNTAX 	    DisplayString
    MAX-ACCESS  read-only
    STATUS      current
    DESCRIPTION
        "The value of the object aluGnssPortReceiverFwVersion indicates
         the firmware version of the GNSS receiver module.

         The format of the value may differ between receiver modules. For
         example, one may return 2.28, another may return 2.02.0."
    ::= { aluGnssPortEntry 16 }

aluPortScalarObjs OBJECT IDENTIFIER ::= { aluPortObjs 32 }

aluLsrIpLoadBalBtmOfStk         OBJECT-TYPE
    SYNTAX      INTEGER {
                    profile-1 (1),
                    profile-2 (2),
                    profile-3 (3)
                }
    MAX-ACCESS  read-write
    STATUS      current
    DESCRIPTION
        "The value of aluLsrIpLoadBalBtmOfStk specifies whether the is
         used in the LAG and ECMP LSR hashing algorithm. This is the global
         system setting that all ports will inherit."
    DEFVAL { profile-1 }
    ::= { aluPortScalarObjs 1 }

aluLsrIpLoadBalIngressPort OBJECT-TYPE
    SYNTAX      TruthValue
    MAX-ACCESS  read-write
    STATUS      current
    DESCRIPTION
        "The value of aluLsrIpLoadBalIngressPort specifies whether ingress port
         is used in the LAG and ECMP hashing algorithm. This is the global system
         setting that all ports will inherit. When set to 'true', the ingress port
         is used in the hashing algorithm."
    DEFVAL { false }
    ::= { aluPortScalarObjs 2 }

--
-- ALU PCM table
--
aluPcmTable OBJECT-TYPE
   SYNTAX      SEQUENCE OF AluPcmEntry
    MAX-ACCESS  not-accessible
    STATUS      current
    DESCRIPTION
         "aluPcmTable has an entry for each
         PCM bridge on each IOM card in each chassis in the system."
    ::= { aluPortObjs 25 }


aluPcmEntry       OBJECT-TYPE
    SYNTAX  AluPcmEntry
    MAX-ACCESS      not-accessible
    STATUS          current
    DESCRIPTION
         "Each row entry represents a  PCM bridge in the system.  Entries for
         serial pcms can not be created and deleted via SNMP SET operations.
         The Entries are automatically created when the tmnxMDAAssignedType object is
         set to the SCADA MDA type and mode mode supports PCM.
         For each aluPcmEntry, there will be a corresponding entry
         in the aluScadaBridgeTable."
    INDEX   { tmnxChassisIndex, tmnxPortPortID }
    ::= { aluPcmTable 1 }

AluPcmEntry ::=
SEQUENCE {
        aluPcmForceActive             INTEGER,
        aluPcmSquelchStatus           Unsigned32,
        aluPcmSquelchEnable           INTEGER,
        aluPcmSquelchTimeout          INTEGER,
        aluPcmSquelchReset            INTEGER,
        aluPcmSquelchResetMode        INTEGER,
        aluPcmSquelchResetTimeout     INTEGER,
        aluPcmRedMode                 INTEGER
}

aluPcmForceActive OBJECT-TYPE
    SYNTAX      INTEGER (1..2)
    MAX-ACCESS  read-create
    STATUS      current
    DESCRIPTION
        "aluPcmForceActive forces the specified master branch to be
         active. default is the master branch 1."
    DEFVAL      { 1 }
   ::= { aluPcmEntry 1 }

aluPcmSquelchStatus OBJECT-TYPE
    SYNTAX      Unsigned32
    MAX-ACCESS  read-only
    STATUS      current
    DESCRIPTION
        "aluPcmSquelchStatus shows squelch status of the scada bridge. It is a 32-bit integer and
         each bit represent a branch. Bit with value one indicates that the associated branch is squelched."
   ::= { aluPcmEntry 2 }


aluPcmSquelchEnable OBJECT-TYPE
    SYNTAX      INTEGER {
                    false (1),
                    true  (2)
                }
    MAX-ACCESS  read-create
    STATUS      current
    DESCRIPTION
        "During nomal SCADA system operation, it is common for a single slave to lock-up
         and continue to send data after the allocated response time. To solve the problem,
         the bridge has a squelching function which will over-ride the incoming data on the locked up
         slave with all ones.

         aluPcmSquelchEnable enables and disables squelching function for the specified PCM.
        "
    DEFVAL { false }
    ::= { aluPcmEntry 3 }


aluPcmSquelchTimeout OBJECT-TYPE
    SYNTAX      INTEGER (1..120)
    MAX-ACCESS  read-create
    STATUS      current
    DESCRIPTION
        "The bridge will start squelching after a user-selectable time period."
    DEFVAL      { 1 }
    ::= { aluPcmEntry 4 }

aluPcmSquelchReset   OBJECT-TYPE
    SYNTAX      INTEGER {
                    noAction (1),
                    action   (2)
                }
    MAX-ACCESS  read-create
    STATUS      current
    DESCRIPTION
        "aluPcmSquelchReset is a one shot action used to reset the squelching."
    DEFVAL { noAction }
    ::= { aluPcmEntry 5 }

aluPcmSquelchResetMode OBJECT-TYPE
    SYNTAX      INTEGER {
                    manual  (1),
                    auto    (2)
                }
    MAX-ACCESS  read-create
    STATUS      current
    DESCRIPTION
        "aluPcmResetMode specifies the method of re-enabling squelched branch.
         In manual mode, squelched branches will be re-enabled only when user sets aluPcmSquelchReset.
         In auto mode, squelched branches will be re-enabled after a user defined timeout period."
   DEFVAL { manual }
    ::= { aluPcmEntry 6 }

aluPcmSquelchResetTimeout OBJECT-TYPE
    SYNTAX      INTEGER (1..120)
    MAX-ACCESS  read-create
    STATUS      current
    DESCRIPTION
        "aluPcmResetTimeout specifies how long the squelched branches have to be remain squelched,
         after the squelch condition is cleared and before it can be re-enabled.
         It is only meaningful when aluPcmResetMode is auto."
    DEFVAL      { 1 }
    ::= { aluPcmEntry 7 }

aluPcmRedMode OBJECT-TYPE
    SYNTAX      INTEGER {
                    manual  (1),
                    auto    (2)
                }
    MAX-ACCESS  read-create
    STATUS      current
    DESCRIPTION
        "aluPcmRedMode specifies the redundant mode of the bridge.
         In auto mode, both master branches are active; one could be for voice and another one for data.
         In manual mode, only one master branch can be active; User can use aluPcmForceActive to set a particular master as active."
   DEFVAL { manual }
    ::= { aluPcmEntry 8 }


--
-- ALU PCM table
--
aluPortCemStatsTable OBJECT-TYPE
    SYNTAX          SEQUENCE OF AluPortCemStatsEntry
    MAX-ACCESS      not-accessible
    STATUS          current
    DESCRIPTION     "A table that contains SAR specific CEM Port statistics."
    ::= { aluPortObjs 26 }

aluPortCemStatsEntry      OBJECT-TYPE
    SYNTAX      AluPortCemStatsEntry
    MAX-ACCESS  not-accessible
    STATUS      current
    DESCRIPTION
        "Each row entry contains 7705 SAR specific cem stats."
    AUGMENTS  { tmnxPortCemStatsEntry }
    ::= { aluPortCemStatsTable 1 }

AluPortCemStatsEntry ::=
    SEQUENCE {
        aluPortCemStatsEgressSamplingDoneCnt Counter32,
        aluPortCemStatsEgressAdjustDoneCnt   Counter32
    }

aluPortCemStatsEgressSamplingDoneCnt OBJECT-TYPE
    SYNTAX      Counter32
    MAX-ACCESS  read-only
    STATUS      current
    DESCRIPTION
        "The value of aluPortCemStatsEgressSamplingDoneCnt indicates
         the number of times the sampling is done for asymetric delay
         control."
    ::= { aluPortCemStatsEntry 1 }

aluPortCemStatsEgressAdjustDoneCnt OBJECT-TYPE
    SYNTAX      Counter32
    MAX-ACCESS  read-only
    STATUS      current
    DESCRIPTION
        "The value of aluPortCemStatsEgressAdjustDoneCnt indicates
         the number of times the adjustment is done for asymetric delay
         control."
    ::= { aluPortCemStatsEntry 2 }

--
-- RS232 Socket Table
--
aluRS232SocketTable              OBJECT-TYPE
    SYNTAX      SEQUENCE OF AluRS232SocketEntry
    MAX-ACCESS  not-accessible
    STATUS      current
    DESCRIPTION
        "The aluRS232SocketTable has an entry for a Socket entity belonging
         to a particular Serial channel."
    ::= { aluPortObjs 27 }

aluRS232SocketEntry              OBJECT-TYPE
    SYNTAX      AluRS232SocketEntry
    MAX-ACCESS  not-accessible
    STATUS      current
    DESCRIPTION
        "Each row entry represents a Socket on a particular interface.

         Entries can be created and deleted via SNMP SET operations
         using the aluRS232SocketRowStatus object.

         For each aluRS232SocketEntry, there will be a corresponding entry
         in the tmnxPortTable and the ifTable."
    INDEX       { tmnxChassisIndex, tmnxPortPortID }
    ::= { aluRS232SocketTable 1 }

AluRS232SocketEntry ::=
    SEQUENCE {
        aluRS232SocketRowStatus         RowStatus,
        aluRS232SocketLastChangeTime    TimeStamp,
        aluRS232SocketEopLength         Unsigned32,
        aluRS232SocketEopIdleTimeout    Unsigned32,
        aluRS232SocketEopSpecialChar    Unsigned32,
        aluRS232SocketSquelchDelay      Unsigned32,
        aluRS232SocketUnsquelchDelay    Unsigned32,
        aluRS232SocketInterSessionDelay Unsigned32,
        aluRS232SocketSquelchStatus     INTEGER,
        aluRS232SocketSquelchReset      TmnxActionType
    }

aluRS232SocketRowStatus          OBJECT-TYPE
    SYNTAX      RowStatus
    MAX-ACCESS  read-create
    STATUS      current
    DESCRIPTION
        "aluRS232SocketRowStatus controls the creation and deletion of row
         entries in the aluRS232SocketTable.

         The tmnxPortPortID for a Socket includes a socket ID in the lower bits.
         The manager has to first calculate the tmnxPortPortID based on the
         TiMOS encoding scheme."
    ::= { aluRS232SocketEntry 1 }

aluRS232SocketLastChangeTime     OBJECT-TYPE
    SYNTAX      TimeStamp
    MAX-ACCESS  read-only
    STATUS      current
    DESCRIPTION
        "The value of aluRS232SocketLastChangeTime indicates the time, since
         system startup, that the configuration of this Socket was created or
         modified."
    ::= { aluRS232SocketEntry 2 }

aluRS232SocketEopLength          OBJECT-TYPE
    SYNTAX      Unsigned32 (1..1500)
    UNITS       "bytes"
    MAX-ACCESS  read-create
    STATUS      current
    DESCRIPTION
        "The value of the object aluRS232SocketEopLength specifies the
         maximum number of bytes (characters) that may be received from the
         Serial data stream.

         If and when reached, EOP (end of packet) is assumed and handled
         accordingly."
    DEFVAL { 1500 }
    ::= { aluRS232SocketEntry 3 }

aluRS232SocketEopIdleTimeout     OBJECT-TYPE
    SYNTAX      Unsigned32 (10..5000)
    UNITS       "milliseconds"
    MAX-ACCESS  read-create
    STATUS      current
    DESCRIPTION
        "The value of the object aluRS232SocketEopIdleTimeout specifies the
         maximum period of idle time that may elapse since the last received
         character from the Serial data stream.

         If and when reached, EOP (end of packet) is assumed and handled
         accordingly."
    DEFVAL { 50 }
    ::= { aluRS232SocketEntry 4 }

aluRS232SocketEopSpecialChar     OBJECT-TYPE
    SYNTAX      Unsigned32 (0..255|4294967295)
    MAX-ACCESS  read-create
    STATUS      current
    DESCRIPTION
        "The value of the object aluRS232SocketEopSpecialChar specifies the
         numerical value for the character, considered special, that may be
         received from the Serial data stream.

         If and when received, EOP (end of packet) is recognized and handled
         accordingly.

         The value 0xFFFFFFFF means disabled (ie. no character is special)."
    DEFVAL { 4294967295 }
    ::= { aluRS232SocketEntry 5 }

aluRS232SocketSquelchDelay       OBJECT-TYPE
    SYNTAX      Unsigned32 (1..120|4294967295)
    UNITS       "seconds"
    MAX-ACCESS  read-create
    STATUS      current
    DESCRIPTION
        "The value of the object aluRS232SocketSquelchDelay specifies the
         period of time that a continuous data stream is allowed to be received
         before squelch is applied. When squelch is applied, the system
         suppresses the channel from receiving any more data.

         The value 0xFFFFFFFF means disabled (ie. squelch will not get applied
         and any concurrent squelch will get cleared immediately)."
    DEFVAL { 4294967295 }
    ::= { aluRS232SocketEntry 6 }

aluRS232SocketUnsquelchDelay     OBJECT-TYPE
    SYNTAX      Unsigned32 (1..120|4294967295)
    UNITS       "seconds"
    MAX-ACCESS  read-create
    STATUS      current
    DESCRIPTION
        "The value of the object aluRS232SocketUnsquelchDelay specifies the
         period of time that squelch will persist before it gets cleared
         automatically.

         The value 0xFFFFFFFF means disabled (ie. squelch will not get cleared
         automatically)."
    DEFVAL { 4294967295 }
    ::= { aluRS232SocketEntry 7 }

aluRS232SocketInterSessionDelay  OBJECT-TYPE
    SYNTAX      Unsigned32 (0..5000)
    UNITS       "milliseconds"
    MAX-ACCESS  read-create
    STATUS      current
    DESCRIPTION
        "The value of the object aluRS232SocketInterSessionDelay specifies the
         nominal period of time to idle between transmitting the last bit of
         the current session and transmitting the first bit of the next
         session."
    DEFVAL { 10 }
    ::= { aluRS232SocketEntry 8 }

aluRS232SocketSquelchStatus      OBJECT-TYPE
    SYNTAX      INTEGER {
                    on      (1),
                    off     (2)
                }
    MAX-ACCESS  read-only
    STATUS      current
    DESCRIPTION
        "The value of the object aluRS232SocketSquelchStatus indicates the
         squelch status."
    ::= { aluRS232SocketEntry 9 }

aluRS232SocketSquelchReset       OBJECT-TYPE
    SYNTAX      TmnxActionType
    MAX-ACCESS  read-create
    STATUS      current
    DESCRIPTION
        "The value of the object aluRS232SocketSquelchReset specifies that a
         manual reset of squelch is to be triggered.

         Setting this object to the value of 'doAction' triggers the one-shot
         reset operation. Any concurrent squelch will get cleared immediately
         and aluRS232SocketSquelchDelay will restart accordingly.

         Reading this object will return the value of 'notApplicable'."
    DEFVAL { notApplicable }
    ::= { aluRS232SocketEntry 10 }

-- --------------------------------------------------
-- dot1X Mac-Based Authentication Config table
-- --------------------------------------------------

aluDot1xAuthConfigTable OBJECT-TYPE
    SYNTAX          SEQUENCE OF AluDot1xAuthConfigEntry
    MAX-ACCESS      not-accessible
    STATUS          current
    DESCRIPTION     "A table that contains dot1x PAE port information in the
                     system."
    ::= { aluPortObjs 28 }

aluDot1xAuthConfigEntry OBJECT-TYPE
    SYNTAX          AluDot1xAuthConfigEntry
    MAX-ACCESS      not-accessible
    STATUS          current
    DESCRIPTION     "A row-entry that contains port specific dot1x PAE
                     information."
    INDEX           { dot1xPaePortNumber }
    ::= { aluDot1xAuthConfigTable 1 }

AluDot1xAuthConfigEntry ::=
    SEQUENCE {
        aluDot1xAuthMacAuthEnabled   TruthValue,
        aluDot1xAuthMacAuthWait      Unsigned32
    }

aluDot1xAuthMacAuthEnabled OBJECT-TYPE
    SYNTAX          TruthValue
    MAX-ACCESS      read-write
    STATUS          current
    DESCRIPTION     "The value of aluDot1xAuthMacAuthEnabled specifies whether
                     a dot1x enabled ethernet port can aithenticate itself
                     using MAC based authentication methods. MAC based
                     authentication will only occur if no EAP frames are
                     recieved on the port indicating the connected supplicant
                     does not support DOT1x authentication."
    DEFVAL { false }
    ::= { aluDot1xAuthConfigEntry 1 }

aluDot1xAuthMacAuthWait     OBJECT-TYPE
    SYNTAX      Unsigned32 (0..3600)
    UNITS       "seconds"
    MAX-ACCESS  read-write
    STATUS      current
    DESCRIPTION
        "The value of the object aluDot1xAuthMacAuthWait specifies the
         period of time that no EAP packets must be recieved in order start
         MAC Based Authentication on the port.

         aluDot1xAuthMacAuthEnabled must be set to 'true' before this value
         is used."
    DEFVAL { 0 }
    ::= { aluDot1xAuthConfigEntry 2 }

-- --------------------------------------------------
-- dot1X Mac-Based Authentication Stats table
-- --------------------------------------------------

aluDot1xAuthStatsTable OBJECT-TYPE
    SYNTAX          SEQUENCE OF AluDot1xAuthStatsEntry
    MAX-ACCESS      not-accessible
    STATUS          current
    DESCRIPTION     "A table that contains dot1x PAE port information in the
                     system."
    ::= { aluPortObjs 29 }

aluDot1xAuthStatsEntry OBJECT-TYPE
    SYNTAX          AluDot1xAuthStatsEntry
    MAX-ACCESS      not-accessible
    STATUS          current
    DESCRIPTION     "A row-entry that contains port specific dot1x PAE
                     information."
    INDEX           { dot1xPaePortNumber }
    ::= { aluDot1xAuthStatsTable 1 }

AluDot1xAuthStatsEntry ::=
    SEQUENCE {
        aluDot1xAuthLastAuthMethod   INTEGER,
        aluDot1xAuthMacAuthFramesRx  Unsigned32
    }

aluDot1xAuthLastAuthMethod OBJECT-TYPE
    SYNTAX      INTEGER {
                    none (0),
                    eap  (1),
                    mac  (2)
                }
    MAX-ACCESS      read-only
    STATUS          current
    DESCRIPTION     "The value of aluDot1xAuthLastAuthMethod indicates
                     the last authentication method of the port.
                     (0) - Never authenticated
                     (1) - EAP - DOT1x EAPOL Frames
                     (2) - Source MAC Based Authentication"
    ::= { aluDot1xAuthStatsEntry 1 }

aluDot1xAuthMacAuthFramesRx    OBJECT-TYPE
    SYNTAX      Unsigned32
    MAX-ACCESS  read-only
    STATUS      current
    DESCRIPTION
        "The value of the object aluDot1xAuthMacAuthFramesRx specifies the
         the number of ethernet frames recieved to perform MAC Authentication
         on."
    ::= { aluDot1xAuthStatsEntry 2 }

--
-- ALU SCADA VCB table
--
aluScadaVcbTable                 OBJECT-TYPE
    SYNTAX      SEQUENCE OF AluScadaVcbEntry
    MAX-ACCESS  not-accessible
    STATUS      current
    DESCRIPTION
        "The aluScadaVcbTable has an entry for each SCADA bridge,
         aluScadaBridgeEntry."
    ::= { aluPortObjs 30 }

aluScadaVcbEntry                 OBJECT-TYPE
    SYNTAX      AluScadaVcbEntry
    MAX-ACCESS  not-accessible
    STATUS      current
    DESCRIPTION
        "Each row entry represents a Voice Conference Bridge (VCB) in the
         system.

         Entries cannot be created and deleted via SNMP SET operations. They
         are created automatically for SCADA MDAs, such as the ISC, when the
         MDA mode, aluExtTmnxMDACapabilityMode, is set to 'modeC' (ie. VCB).

         For each aluScadaVcbEntry, there will be a corresponding entry in the
         aluScadaBridgeTable."
    INDEX { tmnxChassisIndex, tmnxPortPortID }
    ::= { aluScadaVcbTable 1 }

AluScadaVcbEntry ::=
    SEQUENCE {
        aluScadaVcbIdleCode             Unsigned32,
        aluScadaVcbSeizedCode           Unsigned32,
        aluScadaVcbSignalMode           INTEGER
    }

aluScadaVcbIdleCode              OBJECT-TYPE
    SYNTAX      Unsigned32 (0..15)
    MAX-ACCESS  read-write
    STATUS      current
    DESCRIPTION
        "The value of the object aluScadaVcbIdleCode specifies the signaling
         code transmitted on all branches of the bridge indicating idle.  It
         is also used to interpret received signaling codes from the branches.

         This object is valid only while aluExtTmnxMDAVcbApplication is
         'vcbBranchInitiate'.

         The object is a bitmap arranged as follows:

         bit pos:    | 7 6 5 4 3 2 1 0 |
                     | x x x x A B C D |

         'x' - don't care

         The default value depends on aluExtTmnxMDAVoiceCompandingLaw:
         For muLaw    -   0 (or 0x0 or 0b0000)
         For aLaw     -  13 (or 0xD or 0b1101) "
    ::= { aluScadaVcbEntry 1 }

aluScadaVcbSeizedCode            OBJECT-TYPE
    SYNTAX      Unsigned32 (0..15)
    MAX-ACCESS  read-write
    STATUS      current
    DESCRIPTION
        "The value of the object aluScadaVcbSeizedCode specifies the signaling
         code transmitted on all branches of the bridge indicating seized. It
         is also used to interpret received signaling codes from the branches.

         This object is valid only while aluExtTmnxMDAVcbApplication is
         'vcbBranchInitiate'.

         The object is a bitmap arranged as follows:

         bit pos:    | 7 6 5 4 3 2 1 0 |
                     | x x x x A B C D |

         'x' - don't care

         The default value depends on aluExtTmnxMDAVoiceCompandingLaw:
         For muLaw    -  15 (or 0xF or 0b1111)
         For aLaw     -   5 (or 0x5 or 0b0101) "
    ::= { aluScadaVcbEntry 2 }

aluScadaVcbSignalMode            OBJECT-TYPE
    SYNTAX      INTEGER {
                    none (1),
                    cas  (2)
                }
    MAX-ACCESS  read-only
    STATUS      current
    DESCRIPTION
        "The value of aluScadaVcbSignalMode indicates the type of signalling
         associated with the bridge (aka channel):
         none  - Indicates no signalling on this channel
         cas   - Indicates Channel Associated Signalling (CAS) on this channel

         aluScadaVcbSignalMode is like tmnxDS1SignalMode but it's read-only."
    ::= { aluScadaVcbEntry 3 }

--
-- ALU Extensions Ethernet BN Change table
--
aluExtPortEtherBnChangeTable OBJECT-TYPE
    SYNTAX      SEQUENCE OF AluExtPortEtherBnChangeEntry
    MAX-ACCESS  not-accessible
    STATUS      current
    DESCRIPTION
        "Defines the Nokia SAR series ethernet port Bandwidch Notification change
        table for providing, via SNMP, the capability of retrieving the changes
        resulted from the processing of incoming Eth-BN."
        ::= { aluPortObjs 31}

aluExtPortEtherBnChangeEntry  OBJECT-TYPE
    SYNTAX      AluExtPortEtherBnChangeEntry
    MAX-ACCESS  not-accessible
    STATUS      current
    DESCRIPTION
        "Defines an entry in aluExtPortEtherBnChangeTable. Entries are
         created and deleted by the system depending port configuration."
    INDEX   { tmnxChassisIndex, tmnxPortPortID }
    ::= { aluExtPortEtherBnChangeTable 1 }

AluExtPortEtherBnChangeEntry ::=
    SEQUENCE {
        aluExtPortEtherBnEgressRateInUse       Integer32,
        aluExtPortEtherBnLastRateChangeTime    TimeStamp,
        aluExtPortEtherBnLastMgsRxTime         TimeStamp,
        aluExtPortEtherBnNumRateChanges        Counter64,
        aluExtPortEtherBnNumMsgRx              Counter64,
        aluExtPortEtherBnNumInvalidMsgRx       Counter64,
        aluExtPortEtherBnNumBWOutOfRange       Counter64
    }

aluExtPortEtherBnEgressRateInUse      OBJECT-TYPE
    SYNTAX     Integer32
    UNITS      "kilo-bits per second"
    MAX-ACCESS read-only
    STATUS     current
    DESCRIPTION
        "When aluExtPortEtherBnAllowed is 'true', the value of aluExtPortEtherBnEgressRateInUse indicates the
        egress rate currently being enforced.

        aluExtPortEtherBnEgressRateInUse is set to the default value of '-1' to indicate tmnxPortEtherEgressRate
        is currently enforced.

        When the difference between the sysUpTime of a received Y.1731 ETH-BNM and the value of
        aluExtPortEtherBnLastRateChangeTime is greater than the configured aluExtPortEtherBnHoldTime, then
        aluExtPortEtherBnEgressRateInUse is modified to use the current rate in the Y.1731 ETH-BNM frame."
    DEFVAL  { -1 }
    ::= { aluExtPortEtherBnChangeEntry 1 }

aluExtPortEtherBnLastRateChangeTime OBJECT-TYPE
    SYNTAX      TimeStamp
    MAX-ACCESS  read-only
    STATUS      current
    DESCRIPTION
        "aluExtPortEtherBnLastRateChangeTime contains the sysUpTime value as time stamp
         of the most recently modified aluExtPortEtherBnEgressRateInUse of this port."
    ::= { aluExtPortEtherBnChangeEntry 2 }

aluExtPortEtherBnLastMgsRxTime OBJECT-TYPE
    SYNTAX      TimeStamp
    MAX-ACCESS  read-only
    STATUS      current
    DESCRIPTION
        "aluExtPortEtherBnLastMgsRxTime contains the sysUpTime value as time stamp
         of the most recently received valid Y.1731 ETH-BNM frame at this port.
         This frame may or may not cause the change of aluExtPortEtherBnLastRateChangeTime. "
    ::= { aluExtPortEtherBnChangeEntry 3 }

aluExtPortEtherBnNumRateChanges OBJECT-TYPE
    SYNTAX      Counter64
    MAX-ACCESS  read-only
    STATUS      current
    DESCRIPTION
        "aluExtPortEtherBnNumRateChanges is the number of times the Y.1731 ETH-BNM has changed
        the egress rate aluExtPortEtherBnEgressRateInUse at this port while
        aluExtPortEtherBnAllowed was set to 'true'.

        aluExtPortEtherBnNumRateChanges is reset to 0 when aluExtPortEtherBnAllowed modified to 'false',
        or when clear port stats, or when the port is deleted."
    ::= { aluExtPortEtherBnChangeEntry 4 }

aluExtPortEtherBnNumMsgRx OBJECT-TYPE
    SYNTAX      Counter64
    MAX-ACCESS  read-only
    STATUS      current
    DESCRIPTION
        "aluExtPortEtherBnNumMsgRx has the number of valid Y.1731 ETH-BNM received at this port since
         aluExtPortEtherBnAllowed was set to 'true'.

         aluExtPortEtherBnNumMsgRx is reset to 0 when aluExtPortEtherBnAllowed modified to 'false',
         or when clear port stats, or when the port is deleted."
    ::= { aluExtPortEtherBnChangeEntry 5 }

aluExtPortEtherBnNumInvalidMsgRx OBJECT-TYPE
    SYNTAX      Counter64
    MAX-ACCESS  read-only
    STATUS      current
    DESCRIPTION
        "aluExtPortEtherBnNumInvalidMsgRx has the number of invvalid Y.1731 ETH-BNM received and dropped
        at this port since aluExtPortEtherBnAllowed was set to 'true'.

        aluExtPortEtherBnNumInvalidMsgRx is reset to 0 when aluExtPortEtherBnAllowed modified to 'false',
        or when clear port stats, or when the port is deleted."
    ::= { aluExtPortEtherBnChangeEntry 6 }

aluExtPortEtherBnNumBWOutOfRange OBJECT-TYPE
    SYNTAX      Counter64
    MAX-ACCESS  read-only
    STATUS      current
    DESCRIPTION
        "aluExtPortEtherBnNumBWOutOfRange has the number of Y.1731 ETH-BNM received with bandwidth requested
        being bigger than the maximum bandwidth supported by the port, as well as those frames with bandwidth
        requested being smaller than the minimum bandwidth supported at this port .

        aluExtPortEtherBnNumBWOutOfRange is reset to 0 when aluExtPortEtherBnAllowed modified to 'false',
        or when clear port stats, or when the port is deleted."
    ::= { aluExtPortEtherBnChangeEntry 7 }

--%%%%%%%%%%%%%%%%%%%%%%%%%%%%%%%%%%%%%%%%%%%%%%%%%%%%%%%%%%%%%%%%%%%%%
 --
 --     Notification Definition section
 --

 --
 --  Port Notification Objects
 --
aluPortEtherSfpESyncCompatibility NOTIFICATION-TYPE
    OBJECTS {
        tmnxPortNotifyPortId,
        aluExtPortEtherSfpSyncEStatus
    }
    STATUS  current
    DESCRIPTION
        "Generated when a SFP is installed in a MDA that supports
        synchronous ethernet operation."
    ::= { aluPortNotificationObjects 1 }

aluPortNotifyRS232AlarmReason  OBJECT-TYPE
    SYNTAX      INTEGER {
                    notUsed (0),
                    hcmOof  (1),
                    hcmRai  (2),
                    ctrlLeadMon (3),
                    monClockDev (4),
                    monDataInac (5)
                }
    MAX-ACCESS   accessible-for-notify
    STATUS       current
    DESCRIPTION
        "Used by alu RS232 Port Notifications, the value of
         aluPortNotifyRS232AlarmReason indicates the reason a RS232 interface
         alarm has been raised."
    ::= { aluPortNotificationObjects 2 }

aluPortNotifyDataAlarmReason  OBJECT-TYPE
    SYNTAX      INTEGER {
                    notUsed  (0),
                    ais      (1),
                    los      (2),
                    rai      (3)
                }
    MAX-ACCESS   accessible-for-notify
    STATUS       current
    DESCRIPTION
        "Used by alu Data Port Notifications, the value of
         aluPortNotifyDataAlarmReason indicates the reason a Data interface
         alarm has been raised."
    ::= { aluPortNotificationObjects 3 }

aluPortNotifyRS232ControlLeadsSignalChange OBJECT-TYPE
    SYNTAX       DisplayString
    MAX-ACCESS   accessible-for-notify
    STATUS       current
    DESCRIPTION
        "The object aluPortNotifyRS232ControlLeadsSignalChange is a printable
         character string."
    ::= { aluPortNotificationObjects 4 }

--
--  ALU-PORT-MIB Notifications
--

--
--  Equipment Alarms
--

aluEqPortRS232Alarm         NOTIFICATION-TYPE
    OBJECTS {
        tmnxPortNotifyPortId,
        aluPortNotifyRS232AlarmReason
    }
    STATUS  current
    DESCRIPTION
        "Generated when a RS232 interface alarm condition is detected.
         It is generated only when the type of alarm being raised is enabled
         in aluRS232ReportAlarm."
    ::= { aluPortNotification 1 }

aluEqPortRS232AlarmClear    NOTIFICATION-TYPE
    OBJECTS {
        tmnxPortNotifyPortId,
        aluPortNotifyRS232AlarmReason
    }
    STATUS  current
    DESCRIPTION
        "Generated when a RS232 interface alarm condition is cleared.
         It is generated only when the type of alarm being cleared is enabled
         in aluRS232ReportAlarm."
    ::= { aluPortNotification 2 }

aluRS232LoopbackStarted     NOTIFICATION-TYPE
    OBJECTS {
        tmnxPortNotifyPortId,
        aluRS232Loopback
    }
    STATUS          current
    DESCRIPTION
        "The aluRS232LoopbackStarted notification is generated when a
         loopback is provisioned on a RS-232/V.35/X.21/RS-530 port."
    ::= { aluPortNotification 3 }

aluRS232LoopbackStopped     NOTIFICATION-TYPE
    OBJECTS {
        tmnxPortNotifyPortId,
        aluRS232Loopback
    }
    STATUS          current
    DESCRIPTION
        "The aluRS232LoopbackStopped notification is generated when a
         loopback is removed on a RS-232/V.35/X.21/RS-530 port. The value of
         aluRS232Loopback specifies the type of loopback that was
         configured and has now been removed."
    ::= { aluPortNotification 4 }

aluVoiceLoopbackStarted     NOTIFICATION-TYPE
    OBJECTS {
        tmnxPortNotifyPortId,
        aluVoiceLoopback
    }
    STATUS          current
    DESCRIPTION
        "The aluVoiceLoopbackStarted notification is generated when a
         loopback is provisioned on a voice port."
    ::= { aluPortNotification 5 }

aluVoiceLoopbackStopped     NOTIFICATION-TYPE
    OBJECTS {
        tmnxPortNotifyPortId,
        aluVoiceLoopback
    }
    STATUS          current
    DESCRIPTION
        "The aluVoiceLoopbackStopped notification is generated when a
         loopback is removed on a voice port. The value of
         aluVoiceLoopback specifies the type of loopback that was
         configured and has now been removed."
    ::= { aluPortNotification 6 }

aluGponPortInbandAlarm NOTIFICATION-TYPE
    OBJECTS {
        tmnxPortNotifyPortId,
        aluGponPortG984SerialNumber
    }
    STATUS      current
    DESCRIPTION
        "Generated when an alarm condition is detected on the inband signaling
         mechanism between the ONT and SAR"
    ::= { aluPortNotification 7 }

aluGponPortInbandAlarmClear NOTIFICATION-TYPE
    OBJECTS {
        tmnxPortNotifyPortId,
        aluGponPortG984SerialNumber
    }
    STATUS      current
    DESCRIPTION
        "Generated when an alarm condition is cleared on the inband signaling
         mechanism between the ONT and SAR"
    ::= { aluPortNotification 8 }

aluEqPortDataAlarm         NOTIFICATION-TYPE
    OBJECTS {
        tmnxPortNotifyPortId,
        aluPortNotifyDataAlarmReason
    }
    STATUS  current
    DESCRIPTION
        "Generated when a Data interface alarm condition is detected.
         It is generated only when the type of alarm being raised is enabled
         in aluDataReportAlarm."
    ::= { aluPortNotification 9 }

aluEqPortDataAlarmClear    NOTIFICATION-TYPE
    OBJECTS {
        tmnxPortNotifyPortId,
        aluPortNotifyDataAlarmReason
    }
    STATUS  current
    DESCRIPTION
        "Generated when a Data interface alarm condition is cleared.
         It is generated only when the type of alarm being cleared is enabled
         in aluDataReportAlarm."
    ::= { aluPortNotification 10 }

aluDataLoopbackStarted     NOTIFICATION-TYPE
    OBJECTS {
        tmnxPortNotifyPortId,
        aluDataLoopback
    }
    STATUS          current
    DESCRIPTION
        "The aluDataLoopbackStarted notification is generated when a
         loopback is provisioned on a Data port."
    ::= { aluPortNotification 11 }

aluDataLoopbackStopped     NOTIFICATION-TYPE
    OBJECTS {
        tmnxPortNotifyPortId,
        aluDataLoopback
    }
    STATUS          current
    DESCRIPTION
        "The aluDataLoopbackStopped notification is generated when a
         loopback is removed on a Data port. The value of
         aluDataLoopback specifies the type of loopback that was
         configured and has now been removed."
    ::= { aluPortNotification 12 }

aluExtPethPsePortStatusChange NOTIFICATION-TYPE
        OBJECTS {
            pethPsePortDetectionStatus,
            pethPsePortPowerClassifications,
            aluExtPethPsePortFaultReason
        }
        STATUS  current
        DESCRIPTION
            "Generated when there is a change in Power Classification,
            Detection Status, Fault Reason, or Oper Status on a power ethernet port."
        ::= { aluPortNotification 13 }

aluSerialMddbSquelchStatusChanged  NOTIFICATION-TYPE
    OBJECTS {
        aluSerialMddbSquelchStatus
    }
    STATUS          current
    DESCRIPTION
        "The aluSerialMddbSquelchStatusChanged notification is generated when the
         Squelch Status of a scada bridge is changed. The value of
         aluSerialMddbSquelchStatus indicates the new squelch status detected."
    ::= { aluPortNotification 14 }


aluSerialMddbSquelchResetIssued NOTIFICATION-TYPE
    OBJECTS {
        aluSerialMddbSquelchStatus
    }
    STATUS          current
    DESCRIPTION
        "The aluSerialMddbSquelchResetIssued notification is generated when user
         reset the squelch of the scada bridge. The value of
         aluSerialMddbSquelchStatus indicates the existing squelch status."
    ::= { aluPortNotification 15 }

aluGnssPortStatusChange  NOTIFICATION-TYPE
    OBJECTS {
        aluGnssPortSyncStatus,
        aluGnssPortAntennaStatus,
        aluGnssPortReceiverStatus
    }
    STATUS          current
    DESCRIPTION
        "The aluGnssPortStatusChange notification is generated when
         there is a change in the status of the GNSS receiver. This
notification
         is a point-in-time status change event.

         [CAUSE] This notification may be triggered for a variety of reasons
         including (but not limited to):

         1) The antenna is experiencing fault issues
         2) The number of visible satellites is too low

         [EFFECT] The GNSS receiver is not able to provide a sync-worthy clock
         signal.

         [RECOVERY] If the customer is expecting the GNSS receiver to be
locked,
         the customer will need to determine the root cause (for example,
         insufficient visible satellites) and resolve the issue (for example,
         ensure aluGnssPortElevationMaskAngle is set accordingly)."

    ::= { aluPortNotification 16 }

aluPcmSquelchStatusChanged  NOTIFICATION-TYPE
    OBJECTS {
        aluPcmSquelchStatus
    }
    STATUS          current
    DESCRIPTION
        "The aluPcmSquelchStatusChanged notification is generated when the
         Squelch Status of a scada bridge is changed. The value of
         aluPcmSquelchStatus indicates the new squelch status detected."
    ::= { aluPortNotification 17 }


aluPcmSquelchResetIssued NOTIFICATION-TYPE
    OBJECTS {
        aluPcmSquelchStatus
    }
    STATUS          current
    DESCRIPTION
        "The aluPcmSquelchResetIssued notification is generated when user
         reset the squelch of the scada bridge. The value of
         aluPcmSquelchStatus indicates the existing squelch status."
    ::= { aluPortNotification 18 }

aluRS232ControlLeadsSignalChange NOTIFICATION-TYPE
    OBJECTS {
        aluPortNotifyRS232ControlLeadsSignalChange
    }
    STATUS          current
    DESCRIPTION
        "The aluRS232ControlLeadsSignalChange notification is generated when
         there is a change in the status of a Serial control lead signal. This
         notification is a point-in-time status change event.

         [CAUSE] This notification may be triggered for a variety of reasons.
         One example is that the far-end equipment has been disconnected.

         [EFFECT] Alert user of transitions.

         [RECOVERY] Determine root cause and resolve accordingly."

    ::= { aluPortNotification 19 }

aluRS232SquelchStatusChange      NOTIFICATION-TYPE
    OBJECTS {
        tmnxPortNotifyPortId,
        aluRS232SocketSquelchStatus
    }
    STATUS      current
    DESCRIPTION
        "The aluRS232SquelchStatusChange notification is generated when
         there is a change in the status of squelch on the respective channel.
         This notification is a point-in-time status change event.

         [CAUSE] This notification may be triggered for the following reasons:

         1) A continuous stream of data is being received for a specified
            period of time, aluRS232SocketSquelchDelay.
         2) The continuous stream of data is no longer being received for a
            specified period of time, aluRS232SocketUnsquelchDelay.

         [EFFECT] Incoming data will be suppressed or unsuppressed accordingly.

         [RECOVERY] Determine root cause of far-end sending continuous data
         and resolve accordingly."

    ::= { aluPortNotification 20 }

aluRS232SquelchResetIssued       NOTIFICATION-TYPE
    OBJECTS {
        tmnxPortNotifyPortId,
        aluRS232SocketSquelchStatus
    }
    STATUS      current
    DESCRIPTION
        "The aluRS232SquelchResetIssued notification is generated when the
         user triggers a manual reset of squelch via
         aluRS232SocketSquelchReset. The value of aluRS232SocketSquelchStatus
         indicates the existing squelch status."

    ::= { aluPortNotification 21 }

aluRS232ClockSyncStateChange     NOTIFICATION-TYPE
    OBJECTS {
        tmnxPortNotifyPortId,
        aluRS232ClockSyncState
    }
    STATUS      current
    DESCRIPTION
        "The aluRS232ClockSyncStateChange notification is generated when the
         aluRS232ClockSyncState changes for an RS232 interface."
    ::= { aluPortNotification 22 }

aluExtDS0ChanGrpLoopbackStarted  NOTIFICATION-TYPE
    OBJECTS {
        tmnxPortNotifyPortId,
        aluExtDS0ChanGroupLoopback
    }
    STATUS          current
    DESCRIPTION
        "The aluExtDS0ChanGrpLoopbackStarted notification is generated when a
         loopback is provisioned on a DS0 channel group."
    ::= { aluPortNotification 23 }

aluExtDS0ChanGrpLoopbackStopped  NOTIFICATION-TYPE
    OBJECTS {
        tmnxPortNotifyPortId,
        aluExtDS0ChanGroupLoopback
    }
    STATUS          current
    DESCRIPTION
        "The aluExtDS0ChanGrpLoopbackStopped notification is generated when a
         loopback is removed on a DS0 channel group. The value of
         aluExtDS0ChanGroupLoopback specifies the type of loopback that was
         configured and has now been removed."
    ::= { aluPortNotification 24 }

--%%%%%%%%%%%%%%%%%%%%%%%%%%%%%%%%%%%%%%%%%%%%%%%%%%%%%%%%%%%%%%%%%%%%%
--
--      The compliance specifications.
--

aluPortCompliances     OBJECT IDENTIFIER ::= { aluPortConformance 1 }
aluPortGroups          OBJECT IDENTIFIER ::= { aluPortConformance 2 }

aluPortComp7705        OBJECT IDENTIFIER ::= { aluPortCompliances 1 }
--  aluPortComp7705V1v0  OBJECT IDENTIFIER ::= { aluPortComp7705 1}
--  aluPortComp7705V1v1  OBJECT IDENTIFIER ::= { aluPortComp7705 2}
--  aluPortComp7705V2v0  OBJECT IDENTIFIER ::= { aluPortComp7705 3}
--  aluPortComp7705V2v1  OBJECT IDENTIFIER ::= { aluPortComp7705 4}
--  aluPortComp7705V3v0  OBJECT IDENTIFIER ::= { aluPortComp7705 5}
--  aluPortComp7705V4v0  OBJECT IDENTIFIER ::= { aluPortComp7705 6}
--  aluPortComp7705V5v0  OBJECT IDENTIFIER ::= { aluPortComp7705 7}
--  aluPortComp7705V6v0  OBJECT IDENTIFIER ::= { aluPortComp7705 8}
--  aluPortComp7705V6v1  OBJECT IDENTIFIER ::= { aluPortComp7705 9}
--  aluPortComp7705V7v0  OBJECT IDENTIFIER ::= { aluPortComp7705 10}
--  aluPortComp7705V8v0  OBJECT IDENTIFIER ::= { aluPortComp7705 11}
--  aluPortComp7705V9v0  OBJECT IDENTIFIER ::= { aluPortComp7705 12}

aluPortComp7705V1v0  MODULE-COMPLIANCE
    STATUS  current
    DESCRIPTION
            "The compliance statement for revision 1.0 of ALU-PORT-MIB."
    MODULE  -- this module
        MANDATORY-GROUPS {
            aluExtDS1PortLineImpedanceGroup,
            aluPortDiscardStatsGroup
        }
    ::= { aluPortComp7705 1 }

aluPortComp7705V1v1  MODULE-COMPLIANCE
    STATUS  current
    DESCRIPTION
            "The compliance statement for revision 1.1 of ALU-PORT-MIB."
    MODULE  -- this module
        MANDATORY-GROUPS {
            aluExtPortEtherSfpSyncEGroup,
            aluPortAcrClkStatsGroup
        }
    ::= { aluPortComp7705 2 }

aluPortComp7705V2v0  MODULE-COMPLIANCE
    STATUS  current
    DESCRIPTION
            "The compliance statement for revision 2.0 of ALU-PORT-MIB."
    MODULE  -- this module
        MANDATORY-GROUPS {
            aluExtDS1HoldTimeGroup
        }
    ::= { aluPortComp7705 3 }

aluPortComp7705V2v1  MODULE-COMPLIANCE
    STATUS  current
    DESCRIPTION
            "The compliance statement for revision 2.1 of ALU-PORT-MIB."
    MODULE  -- this module
        MANDATORY-GROUPS {
            aluRS232GroupV2v1,
            aluPortNotificationGroupV2v1,
            aluExtPortCemGroupV2v1,
            aluPortNotifyObjsGroupV2v1,
            aluExtPortEtherLoopbackGroupV2v1
        }
    ::= { aluPortComp7705 4 }

aluPortComp7705V3v0  MODULE-COMPLIANCE
    STATUS  current
    DESCRIPTION
            "The compliance statement for revision 3.0 of ALU-PORT-MIB."
    MODULE  -- this module
        MANDATORY-GROUPS {
            aluVoiceGroup,
            aluVoiceNotifGroup,
            aluRS232MultiDropGroup,
            aluPortDiscardStatsGroupV3v0,
            aluPortNetControlStatsGroupV3v0,
            aluRS232SBitSignalingGroup,
            aluRS232DataPositionGroup
        }
    ::= { aluPortComp7705 5 }

aluPortComp7705V4v0  MODULE-COMPLIANCE
    STATUS  current
    DESCRIPTION
            "The compliance statement for revision 4.0 of ALU-PORT-MIB."
    MODULE  -- this module
        MANDATORY-GROUPS {
            aluExtPortEtherLoopbackGroupV4v0,
            aluPortEtherSfpSyncECompatibilityGroup
        }
    ::= { aluPortComp7705 6 }

aluPortComp7705V5v0  MODULE-COMPLIANCE
    STATUS  current
    DESCRIPTION
            "The compliance statement for revision 5.0 of ALU-PORT-MIB."
    MODULE  -- this module
        MANDATORY-GROUPS {
            aluGponGroupV5v0,
            aluDslGroupV5v0,
            aluGponStatsGroupV5v0,
            aluDslStatsGroupV5v0,
            aluDslGponNotificationGroupV5v0,
            aluVoiceTeleprotectionGroup,
            aluDataGroup,
            aluDataNotifGroup,
            aluExtDS0ChanGroupSignalModeGroup,
            aluPortCtlStatsGroup,
            aluExtPortEtherLoopbackGroupV5v0,
            aluDataPortNotifyObjsGroup
        }
    ::= { aluPortComp7705 7 }

aluPortComp7705V6v0  MODULE-COMPLIANCE
    STATUS  current
    DESCRIPTION
            "The compliance statement for revision 6.0 of ALU-PORT-MIB."
    MODULE  -- this module
        MANDATORY-GROUPS {
            aluPortEthernetGroupV6v0,
            aluPortDiscardStatsGroupV6v0,
            aluPortEtherXorGroupV6v0,
            aluPwrEthPortGroupV6v0,
            aluRS232HoldTimeGroup,
            aluExtPethPsePortNotificationGroupV6v0
        }
    ::= { aluPortComp7705 8 }

aluPortComp7705V6v1  MODULE-COMPLIANCE
    STATUS  current
    DESCRIPTION
            "The compliance statement for revision 6.1 of ALU-PORT-MIB."
    MODULE  -- this module
        MANDATORY-GROUPS {
            aluGnssPortGroup,
            aluPortDiscardStatsGroupV6v1,
            aluScadaBridgeNotificationGroupV6v1,
            aluGnssPortNotifGroup
        }
    ::= { aluPortComp7705 9 }

aluPortComp7705V7v0  MODULE-COMPLIANCE
    STATUS  current
    DESCRIPTION
            "The compliance statement for revision 7.0 of ALU-PORT-MIB."
    MODULE  -- this module
        MANDATORY-GROUPS {
            aluRS232ControlLeadsNotifGroup,
            aluGnssPortReceiverFwVersGroup
        }
    ::= { aluPortComp7705 10 }

aluPortComp7705V8v0  MODULE-COMPLIANCE
    STATUS  current
    DESCRIPTION
            "The compliance statement for revision 8.0 of ALU-PORT-MIB."
    MODULE  -- this module
        MANDATORY-GROUPS {
            aluRS232SocketGroup,
            aluRS232SocketNotifGroup,
            aluRS232SocketStatsGroup,
            aluDot1xAuthGroup,
            aluScadaVcbGroup,
            aluScadaBranchGainGroup
        }
    ::= { aluPortComp7705 11 }

aluPortComp7705V9v0  MODULE-COMPLIANCE
    STATUS  current
    DESCRIPTION
            "The compliance statement for revision 9.0 of ALU-PORT-MIB."
    MODULE  -- this module
        MANDATORY-GROUPS {
            aluRS232ClockSyncGroup,
            aluRS232ClockSyncNotifGroup,
            aluRS232InvertClockGroup,
            aluRS232MonClockDataGroup,
            aluScadaNameGroup,
            aluExtDS0ChanGroupLoopbackGroup,
            aluExtDS0ChanGrpLpbckNotifGroup,
            aluPortPtpTimestampStatsV9v0Group
        }
    ::= { aluPortComp7705 12 }


-- units of conformance

aluExtDS1PortLineImpedanceGroup     OBJECT-GROUP
    OBJECTS {   aluExtDS1PortLineImpedance
            }
    STATUS      current
    DESCRIPTION
        "The group of objects supporting management of the line impedance
         of DS1/E1 physical ports on Nokia SAR series systems."
    ::= { aluPortGroups 1 }

aluPortDiscardStatsGroup     OBJECT-GROUP
    OBJECTS {  aluPortInL2AddrProtoDiscards,
               aluPortInMPLSLabelDiscards,
               aluPortInIPAddrProtoDiscards,
               aluPortInVlanIdDiscards,
               aluPortInHdlcCrcDiscards,
               aluPortOutPortMtuDiscards,
               aluPortInCsmQHiPriDiscards,
               aluPortInCsmQLowPriDiscards,
               aluPortInCsmQFtpPriDiscards,
               aluPortOutCsmQDiscards,
               aluPortInOtherDiscards,
               aluPortOutOtherDiscards
            }
    STATUS      obsolete
    DESCRIPTION
        "The group of objects supporting retrieval of the detailed packet
         discard statistics on Nokia SAR series systems"
    ::= { aluPortGroups 2 }

aluExtPortEtherSfpSyncEGroup     OBJECT-GROUP
    OBJECTS {
               aluExtPortEtherSfpSyncEStatus
            }
    STATUS      current
    DESCRIPTION
        "The group of objects supporting the management of the capabilities
        of synchronous operations with respect to the installed SFP's."
    ::= { aluPortGroups 3 }

aluPortEtherSfpSyncECompatibilityGroup NOTIFICATION-GROUP
    NOTIFICATIONS   {
                      aluPortEtherSfpESyncCompatibility
                    }
    STATUS        current
    DESCRIPTION
        "The group of notifications supporting the management of Synchronous
        Ethernet with respect to installed SFP's on the Nokia 7705 SAR."
    ::= { aluPortGroups 4 }

aluPortAcrClkStatsGroup     OBJECT-GROUP
    OBJECTS {
                aluLastUpdateTime,
                aluTotalMinutesIn24Hour,
                aluCurrent24HourFreqOffsetMeanPpb,
                aluCurrent24HourFreqOffsetStdDevPpb,
                aluMaxShortIntervalMinutes,
                aluTotalShortIntervalMinutes,
                aluCurrent1MinValidData,
                aluCurrent1MinPhaseErrorMeanPpb,
                aluCurrent1MinPhaseErrorStdDevNs,
                aluCurrent1MinPhaseErrorMeanNs,
                aluCurrent1MinFreqOffsetMeanPpb,
                aluCurrent1MinFreqOffsetStdDevPpb,
                aluIntervalNumber,
                aluIntervalValidData,
                aluIntervalUpdateTime,
                aluIntervalPhaseErrorMeanPpb,
                aluIntervalPhaseErrorStdDevNs,
                aluIntervalPhaseErrorMeanNs,
                aluIntervalFreqOffsetMeanPpb,
                aluIntervalFreqOffsetStdDevPpb
            }
    STATUS      current
    DESCRIPTION
        "The group of objects supporting retrieval of the ACR clock statistic
        on Nokia SAR series systems"
    ::= { aluPortGroups 5 }

aluExtDS1HoldTimeGroup OBJECT-GROUP
    OBJECTS   {
                      aluExtDS1HoldTimeUp,
                      aluExtDS1HoldTimeDown
              }
    STATUS        current
    DESCRIPTION
        "The group of objects supporting management of hold-time
         capabilities on Nokia SAR series systems."
    ::= { aluPortGroups 6 }

aluRS232GroupV2v1   OBJECT-GROUP
    OBJECTS {
                aluRS232PortLastChangeTime,
                aluRS232PortType,
                aluRS232RowStatus,
                aluRS232LastChangeTime,
                aluRS232Type,
                aluRS232DeviceMode,
                aluRS232DeviceGender,
                aluRS232Duplex,
                aluRS232Speed,
                aluRS232ClockSource,
                aluRS232Loopback,
                aluRS232CharacterLength,
                aluRS232Parity,
                aluRS232StopBits,
                aluRS232ReportAlarm,
                aluRS232ReportAlarmStatus,
                aluRS232ControlLeadDtrDsr,
                aluRS232ControlLeadRtsDcdC,
                aluRS232ControlLeadAlbCts,
                aluRS232ControlLeadRdlRi,
                aluRS232ControlLeadDsrDtr,
                aluRS232ControlLeadDcdRtsI,
                aluRS232ControlLeadCtsAlb,
                aluRS232ControlLeadRiRdl,
                aluRS232ChanGroupRowStatus,
                aluRS232ChanGroupTimeSlots,
                aluRS232ChanGroupMTU,
                aluRS232ChanGroupOperMTU,
                aluRS232ChanGroupCRC,
                aluRS232ChanGroupIdleCycleFlags,
                aluRS232ChanGroupPayloadFillType,
                aluRS232ChanGroupPayloadPattern,
                aluRS232ControlLeadsState
            }
    STATUS      current
    DESCRIPTION
        "The group of objects supporting management of Serial type ports
        for version 2.1 on Nokia SAR series systems"
    ::= { aluPortGroups 7 }

aluPortNotificationGroupV2v1 NOTIFICATION-GROUP
    NOTIFICATIONS   {   aluEqPortRS232Alarm,
                        aluEqPortRS232AlarmClear,
                        aluRS232LoopbackStarted,
                        aluRS232LoopbackStopped
                    }
    STATUS        current
    DESCRIPTION
        "The group of notifications supporting the management of physical
         ports for revision 2.1 on Nokia SAR series systems."
    ::= { aluPortGroups 8 }

aluExtPortCemGroupV2v1   OBJECT-GROUP
    OBJECTS {
                aluExtDS1SignalBitsState
            }
    STATUS     current
    DESCRIPTION
        "The group of objects supporting management of CEM encapsulation TDM
         type ports for revision 2.1 on Nokia SAR series systems."
    ::= { aluPortGroups 9 }

aluVoiceGroup   OBJECT-GROUP
    OBJECTS {
                aluVoicePortLastChangeTime,
                aluVoicePortType,
                aluVoicePortAudioWires,
                aluVoicePortTlpRx,
                aluVoicePortTlpTx,
                aluVoiceRowStatus,
                aluVoiceLastChangeTime,
                aluVoiceType,
                aluVoiceSignalingMode,
                aluVoiceLoopback,
                aluVoiceFaultSignaling,
                aluVoiceSignalBitsState,
                aluVoiceClockSource,
                aluVoiceChanGroupRowStatus,
                aluVoiceChanGroupMTU,
                aluVoiceChanGroupOperMTU,
                aluVoiceSignalingLeadE,
                aluVoiceSignalingLeadM,
                aluVoiceSignalingLeadsState,
                aluVoiceSignalMode,
                aluVoiceCallState,
                aluVoiceIncomingCallCount,
                aluVoiceIncomingCallCountAns,
                aluVoiceIncomingCallTime,
                aluVoiceIncomingCallTimeAns,
                aluVoiceOutgoingCallCount,
                aluVoiceOutgoingCallCountAns,
                aluVoiceOutgoingCallTime,
                aluVoiceOutgoingCallTimeAns,
                aluVoiceOutOfServiceTime,
                aluVoiceIdleTime,
                aluVoiceTotalCallCount,
                aluVoiceTotalCallTime,
                aluVoiceIdleCode,
                aluVoiceSeizedCode
            }
    STATUS      current
    DESCRIPTION
        "The group of objects supporting management of Voice type ports
        on Nokia SAR series systems."
    ::= { aluPortGroups 10 }

aluVoiceNotifGroup NOTIFICATION-GROUP
    NOTIFICATIONS   {   aluVoiceLoopbackStarted,
                        aluVoiceLoopbackStopped
                    }
    STATUS        current
    DESCRIPTION
        "The group of notifications supporting management of Voice type ports
         on Nokia SAR series systems."
    ::= { aluPortGroups 11 }

aluPortNotifyObjsGroupV2v1   OBJECT-GROUP
    OBJECTS {   aluPortNotifyRS232AlarmReason
            }
    STATUS        current
    DESCRIPTION
        "The group of objects supporting physical port notifications
         for revision 2.1 on Nokia SAR series systems."
    ::= { aluPortGroups 12 }

aluExtPortEtherLoopbackGroupV2v1   OBJECT-GROUP
    OBJECTS {
                aluExtPortEtherLoopback,
                aluExtPortEtherLoopbackTimer,
                aluExtPortEtherLoopbackTimeLeft
            }
    STATUS     obsolete
    DESCRIPTION
        "The group of objects supporting management of loopbacks for ethernet
         ports for revision 2.1 on Nokia SAR series systems."
    ::= { aluPortGroups 13 }

aluExtPortEtherNwSchedulingGroup   OBJECT-GROUP
    OBJECTS {
                aluExtPortEtherNwSchedulerMode
            }
    STATUS     current
    DESCRIPTION
        "The group of objects supporting management of egress scheduling of
         ports on Nokia SAR series systems."
    ::= { aluPortGroups 14 }

aluRS232MultiDropGroup  OBJECT-GROUP
    OBJECTS {
                aluRS232MultiDrop
            }
    STATUS      current
    DESCRIPTION
        "The group of objects supporting management of multi-drop data bridge
         mode on Serial type ports on Nokia SAR series systems."
    ::= { aluPortGroups 15 }

aluPortDiscardStatsGroupV3v0     OBJECT-GROUP
    OBJECTS {  aluPortInL2AddrProtoDiscards,
               aluPortInMPLSLabelDiscards,
               aluPortInIPAddrProtoDiscards,
               aluPortInVlanIdDiscards,
               aluPortInHdlcCrcDiscards,
               aluPortOutPortMtuDiscards,
               aluPortInCsmQHiPriDiscards,
               aluPortInCsmQMediumPriDiscards,
               aluPortInCsmQLowPriDiscards,
               aluPortOutCsmQDiscards,
               aluPortInOtherDiscards,
               aluPortOutOtherDiscards
            }
    STATUS      obsolete
    DESCRIPTION
        "The group of objects supporting retrieval of the detailed packet
         discard statistics on Nokia SAR series systems"
    ::= { aluPortGroups 16 }

aluPortObsoletedGroupV3v0     OBJECT-GROUP
    OBJECTS {  aluPortInCsmQFtpPriDiscards
            }
    STATUS      current
    DESCRIPTION
        "The group of objects obsoleted in the 7705 SAR series 3.0 release"
    ::= { aluPortGroups 17 }

aluPortNetControlStatsGroupV3v0  OBJECT-GROUP
     OBJECTS { aluPortNetIngressControlFwdPkts,
               aluPortNetIngressControlFwdOcts,
               aluPortNetIngressControlDroPkts,
               aluPortNetIngressControlDroOcts,
               aluPortNetEgressControlFwdPkts,
               aluPortNetEgressControlFwdOcts,
               aluPortNetEgressControlDroPkts,
               aluPortNetEgressControlDroOcts
            }
    STATUS      current
    DESCRIPTION
        "The group of objects supporting retrieval of ingress and egress control
        traffic statistics in the Nokia SAR series 3.0 release"
    ::= { aluPortGroups 18 }

aluRS232SBitSignalingGroup  OBJECT-GROUP
    OBJECTS {
                aluRS232SBitSignaling
            }
    STATUS      current
    DESCRIPTION
        "The group of objects supporting management of S-bit signaling
         mode on Serial type ports on Nokia SAR series systems."
    ::= { aluPortGroups 19 }

aluRS232DataPositionGroup  OBJECT-GROUP
    OBJECTS {
                aluRS232DataPosition
            }
    STATUS      current
    DESCRIPTION
        "The group of objects supporting management of S-bit signaling
         mode on Serial type ports on Nokia SAR series systems."
    ::= { aluPortGroups 20 }

aluExtPortEtherLoopbackGroupV4v0   OBJECT-GROUP
    OBJECTS {
                aluExtPortEtherLoopback,
                aluExtPortEtherLoopbackTimer,
                aluExtPortEtherLoopbackTimeLeft,
                aluExtPortEtherLoopbackCfmLbMode,
                aluExtPortEtherCfmLbmRx,
                aluExtPortEtherCfmLbmDropped,
                aluExtPortEtherCfmLbrTx,
                aluExtPortEtherLoopbackSwapMacAddr
            }
    STATUS     obsolete
    DESCRIPTION
        "The group of objects supporting management of loopbacks for ethernet
         ports for revision 4.0 on Nokia SAR series systems."
    ::= { aluPortGroups 21 }

aluGponGroupV5v0   OBJECT-GROUP
    OBJECTS {
                aluGponPortG984SerialNumber,
                aluGponPortSubsLocId,
                aluGponPortActiveSwVersion,
                aluGponPortPonStatus,
                aluGponPortOntEnetStatus,
                aluGponPortOntEnetSpeed
            }
    STATUS     current
    DESCRIPTION
        "The group of objects supporting management of GPON ports
         for revision 5.0 on Nokia SAR series systems."
    ::= { aluPortGroups 22 }

aluDslGroupV5v0   OBJECT-GROUP
    OBJECTS {
                aluDslPortBondingType,
                aluDslPortBondingState,
                aluDslPortBondingBitRateUS,
                aluDslPortBondingBitRateDS,
                aluDslPortAtmVpi,
                aluDslPortAtmVci,
                aluDslPortAtmF5OamLoopback,
                aluDslPortAtmF5OamLoopbackStatus,
                aluDslPortAtmF5OamLoopbackTime,
                aluDslPortNtrDslLineID,
                aluDslPortNtrLockedStatus,
                aluDslPortNtrStdDev,
                aluDslPortNtrMaxError,
                aluDslPortNtrMinError,
                aluDslPortAdsl2Plus,
                aluDslPortNtrSampleClockPeriod,
                aluDslPortNtrErrorHistory,
                aluXdslLineOperState,
                aluXdslLineState,
                aluXdslLineProtocol,
                aluXdslLineVdslProfile,
                aluXdslLineTpsTcType,
                aluXdslLineInBondingGroup,
                aluXdslLineBitRateUS,
                aluXdslLineSnrMarginUS,
                aluXdslLineOutputPowerUS,
                aluXdslLineRefPsdUS,
                aluXdslLineLoopDelayUS,
                aluXdslLineFailureUS,
                aluXdslLineB0DelayUS,
                aluXdslLineB0InpUS,
                aluXdslLineBitRateDS,
                aluXdslLineSnrMarginDS,
                aluXdslLineOutputPowerDS,
                aluXdslLineRefPsdDS,
                aluXdslLineLoopDelayDS,
                aluXdslLineFailureDS,
                aluXdslLineB0DelayDS,
                aluXdslLineB0InpDS,
                aluXdslLineAdminState,
                aluShdslLineDataRate,
                aluShdslLineState,
                aluShdslLineNegotiatedConst,
                aluShdslLineUsedCaplist,
                aluShdslLineRegion,
                aluShdslLineCaplistMode,
                aluShdslLineTpsTcType,
                aluShdslLineInBondingGroup,
                aluShdslLineAdminState,
                aluShdslLineLineAttenuation,
                aluShdslLineRxSNRMargin,
                aluShdslLinePowerBackOffValue
            }
    STATUS     current
    DESCRIPTION
        "The group of objects supporting management of DSL ports
         for revision 5.0 on Nokia SAR series systems."
    ::= { aluPortGroups 23 }

aluGponStatsGroupV5v0   OBJECT-GROUP
    OBJECTS {
                aluGponPortCurrentLastUpdTime,
                aluGponPortCurrentPMEnabled,
                aluGponPortCurrentTxFrames,
                aluGponPortCurrentRxFrames,
                aluGponPortCurrentTxBytes,
                aluGponPortCurrentRxBytes,
                aluGponPortCurrentDropFrsUp,
                aluGponPortCurrentDropFrsDn,
                aluGponPortCurrentTxFrsMcast,
                aluGponPortCurrentRxFrsMcast,
                aluGponPortCurrentFCSEs,
                aluGponPortCurrentECs,
                aluGponPortCurrentLCs,
                aluGponPortCurrentFTLs,
                aluGponPortCurrentRBOs,
                aluGponPortCurrentTBOs,
                aluGponPortCurrentSCFs,
                aluGponPortCurrentMCFs,
                aluGponPortCurrentSQEs,
                aluGponPortCurrentDTs,
                aluGponPortCurrentIMTEs,
                aluGponPortCurrentCSEs,
                aluGponPortCurrentAEs,
                aluGponPortCurrentIMREs,
                aluGponPortCurrentLostFragsDn,
                aluGponPortCurrentLostFragsUp,
                aluGponPortCurrentRxFrags,
                aluGponPortCurrentRxBlocks,
                aluGponPortCurrentTxBlocks,
                aluGponPortCurrentTxFrags,
                aluGponPortCurrentBadHeaders,
                aluGponPortPreviousLastUpdTime,
                aluGponPortPreviousPMEnabled,
                aluGponPortPreviousTxFrames,
                aluGponPortPreviousRxFrames,
                aluGponPortPreviousTxBytes,
                aluGponPortPreviousRxBytes,
                aluGponPortPreviousDropFrsUp,
                aluGponPortPreviousDropFrsDn,
                aluGponPortPreviousTxFrsMcast,
                aluGponPortPreviousRxFrsMcast,
                aluGponPortPreviousFCSEs,
                aluGponPortPreviousECs,
                aluGponPortPreviousLCs,
                aluGponPortPreviousFTLs,
                aluGponPortPreviousRBOs,
                aluGponPortPreviousTBOs,
                aluGponPortPreviousSCFs,
                aluGponPortPreviousMCFs,
                aluGponPortPreviousSQEs,
                aluGponPortPreviousDTs,
                aluGponPortPreviousIMTEs,
                aluGponPortPreviousCSEs,
                aluGponPortPreviousAEs,
                aluGponPortPreviousIMREs,
                aluGponPortPreviousLostFragsDn,
                aluGponPortPreviousLostFragsUp,
                aluGponPortPreviousRxFrags,
                aluGponPortPreviousRxBlocks,
                aluGponPortPreviousTxBlocks,
                aluGponPortPreviousTxFrags,
                aluGponPortPreviousBadHeaders
            }
    STATUS     current
    DESCRIPTION
        "The group of objects supporting retrieval of the GPON
         statistics for revision 5.0 on Nokia SAR series
         systems."
    ::= { aluPortGroups 24 }

aluDslStatsGroupV5v0   OBJECT-GROUP
    OBJECTS {
                aluXdslLineStatsNearEndFECS,
                aluXdslLineStatsNearEndLOSS,
                aluXdslLineStatsNearEndES,
                aluXdslLineStatsNearEndSES,
                aluXdslLineStatsNearEndUAS,
                aluXdslLineStatsNearEndAS,
                aluXdslLineStatsNearEndLOFS,
                aluXdslLineStatsNearEndLPRS,
                aluXdslLineStatsNearEndLEFTRS,
                aluXdslLineStatsFarEndFECS,
                aluXdslLineStatsFarEndLOSS,
                aluXdslLineStatsFarEndES,
                aluXdslLineStatsFarEndSES,
                aluXdslLineStatsFarEndUAS,
                aluXdslLineStatsFarEndAS,
                aluXdslLineStatsFarEndLOFS,
                aluXdslLineStatsFarEndLPRS,
                aluXdslLineStatsFarEndLEFTRS,
                aluXdslLineStatsFarEndLEFTRS,
                aluXdslLineStatsUpTime,
                aluShdslLineStatsLinkLoss,
                aluShdslLineStatsCVError,
                aluShdslLineStatsES,
                aluShdslLineStatsSES,
                aluShdslLineStatsLOSWS,
                aluShdslLineStatsUAS,
                aluShdslLineStatsInvalidDataFlag
            }
    STATUS     current
    DESCRIPTION
        "The group of objects supporting retrieval of the DSL Line
         statistics for revision 5.0 on Nokia SAR series
         systems."
    ::= { aluPortGroups 25 }

aluDslGponNotificationGroupV5v0   NOTIFICATION-GROUP
    NOTIFICATIONS {
                aluGponPortInbandAlarm,
                aluGponPortInbandAlarmClear
            }
    STATUS     current
    DESCRIPTION
        "The group of notifications supporting the management of
         GPON ports for revision 5.0 on Nokia SAR series
         systems."
    ::= { aluPortGroups 26 }



aluVoiceTeleprotectionGroup OBJECT-GROUP
    OBJECTS {
                aluVoicePortLineBalance,
                aluVoicePortRingGeneration,
                aluVoicePortSignalingType
            }
    STATUS      current
    DESCRIPTION
        "The group of additional voice objects supporting the new Voice and
         Teleprotection MDA introduced in Release 5.0 of the Nokia SAR
         series systems."
    ::= { aluPortGroups 27 }

aluDataGroup   OBJECT-GROUP
    OBJECTS {
                aluDataPortLastChangeTime,
                aluDataPortType,
                aluDataRowStatus,
                aluDataLastChangeTime,
                aluDataType,
                aluDataClockSource,
                aluDataTiming8k,
                aluDataReportAlarm,
                aluDataReportAlarmStatus,
                aluDataLoopback,
                aluDataChanGroupRowStatus,
                aluDataChanGroupLastChangeTime,
                aluDataChanGroupMTU,
                aluDataChanGroupOperMTU,
                aluDataChanGroupPayloadFillType,
                aluDataChanGroupPayloadPattern,
                aluDataChanGroupTimeSlots
            }
    STATUS      current
    DESCRIPTION
        "The group of objects supporting management of TDM Data type ports
         introduced in Release 5.0 of the Nokia SAR series systems."
    ::= { aluPortGroups 28 }

aluDataNotifGroup NOTIFICATION-GROUP
    NOTIFICATIONS {
                    aluEqPortDataAlarm,
                    aluEqPortDataAlarmClear,
                    aluDataLoopbackStarted,
                    aluDataLoopbackStopped
                  }
    STATUS        current
    DESCRIPTION
        "The group of notifications supporting management of TDM Data type ports
         introduced in Release 5.0 of the Nokia SAR series systems."
    ::= { aluPortGroups 29 }


aluPortCtlStatsGroup  OBJECT-GROUP
    OBJECTS {
               aluPortAccessCtlInFwdPkts,
               aluPortAccessCtlInFwdOcts,
               aluPortAccessCtlInDroPkts,
               aluPortAccessCtlInDroOcts,
               aluPortAccessCtlEgrFwdPkts,
               aluPortAccessCtlEgrFwdOcts,
               aluPortAccessCtlEgrDroPkts,
               aluPortAccessCtlEgrDroOcts
            }
    STATUS        current
    DESCRIPTION
        "The group of objects supporting management of access port Control
         packet statistics introduced in Release 5.0 of the Nokia
         SAR series systems."

    ::= { aluPortGroups 30 }

  aluFrStatsGroupV5v0   OBJECT-GROUP
      OBJECTS {
          aluFrIfRxFrames,
          aluFrIfRxOctets,
          aluFrIfRxDEFrames,
          aluFrIfRxDEOctets,
          aluFrIfRxFECNFrames,
          aluFrIfRxBECNFrames,
          aluFrIfTxFrames,
          aluFrIfTxOctets,
          aluFrIfTxDEFrames,
          aluFrIfTxDEOctets,
          aluFrIfTxFECNFrames,
          aluFrIfTxBECNFrames,
          aluFrIfRxDiscardsInvalidDlci,
          aluFrIfRxLastInvalidDlci,
          aluFrIfRxDiscardsCrcErrors,
          aluFrIfRxDiscardsAlignmentErrors,
          aluFrIfRxDiscardsLengthViolations,
          aluFrIfRxDiscardsIllegalHeader,
          aluFrIfRxDiscardsOtherErrors,
          aluFrIfTxDiscardsUnderruns,
          aluFrIfTxDiscardsOtherErrors,
          aluExtFrCircuitReceivedCrcDiscards,
          aluExtFrCircuitReceivedAborts,
          aluExtFrCircuitReceivedOtherDiscards,
          aluExtFrCircuitSentAborts,
          aluExtFrCircuitSentFECNs,
          aluExtFrCircuitSentBECNs,
          aluExtFrCircuitReceivedDEOctets,
          aluExtFrCircuitSentDEOctets
      }
      STATUS     current
      DESCRIPTION
          "The group of objects supporting retrieval of the frame relay
           statistics for revision 5.0 on Nokia SAR series
           systems."
      ::= { aluPortGroups 31 }


aluExtPortEtherSyncGroup     OBJECT-GROUP
    OBJECTS {
               aluExtPortEtherAdminPhyTxClock,
               aluExtPortEtherOperPhyTxClock
            }
    STATUS      current
    DESCRIPTION
        "The group of objects supporting the management of the synchronous
        Ethernet on copper interfaces."
    ::= { aluPortGroups 32 }

aluEthPtpTimestampStatsGroup     OBJECT-GROUP
    OBJECTS {
                aluEthPtpInSyncPktTimestamped,
                aluEthPtpOutSyncPktTimestamped,
                aluEthPtpInDelReqPktTimestamped,
                aluEthPtpOutDelReqPktTimestamped,
                aluEthPtpInFcsErrorCount,
                aluEthPtpOutFcsErrorCount
            }
    STATUS      obsolete
    DESCRIPTION
        "The group of objects supporting retrieval of the IEEE1588
         PTP transparent clock statistic on Nokia SAR series systems"
    ::= { aluPortGroups 33 }

aluEthPtpTimestampGroup   OBJECT-GROUP
    OBJECTS {
                aluEthPtpTimestampCapable,
                aluEthPtpTimestampEnable,
                aluEthPtpAsymmetry
            }
    STATUS     current
    DESCRIPTION
        "The group of objects supporting management of IEEE1588 PTP
         Transparent Clock function for ethernet ports on
         Nokia SAR series systems."
    ::= { aluPortGroups 34 }

aluExtDS0ChanGroupSignalModeGroup OBJECT-GROUP
    OBJECTS {
                aluExtDS0ChanGroupSignalMode
            }
    STATUS      current
    DESCRIPTION
        "The group of objects supporting signal mode for ds0 chan groups
         Nokia SAR series systems."
    ::= { aluPortGroups 35 }

aluExtPortEtherLoopbackGroupV5v0   OBJECT-GROUP
    OBJECTS {
                aluExtPortEtherLoopback,
                aluExtPortEtherLoopbackTimer,
                aluExtPortEtherLoopbackTimeLeft,
                aluExtPortEtherLoopbackCfmLbMode,
                aluExtPortEtherCfmLbmRx,
                aluExtPortEtherCfmLbmDropped,
                aluExtPortEtherCfmLbrTx,
                aluExtPortEtherLoopbackSwapMacAddr,
                aluExtPortEtherLoopbackPersist
            }
    STATUS     obsolete
    DESCRIPTION
        "The group of objects supporting management of loopbacks for ethernet
         ports for revision 5.0 on 7705 Nokia systems."
    ::= { aluPortGroups 36 }

aluPortEthernetGroupV6v0     OBJECT-GROUP
    OBJECTS {   aluPortEtherIngressRateCbs,
                aluPortEtherIngressRateSrcPause,
                aluPortEtherEgrUnshapedSapCir,
                aluPortCfmLbVlanRowStatus,
                aluExtPortEtherCfmLbVlanList
            }
    STATUS      obsolete
    DESCRIPTION
        "The group of objects supporting management of ethernet ports
        on Nokia SAR series systems."
    ::= { aluPortGroups 37 }

aluPortDiscardStatsGroupV6v0     OBJECT-GROUP
    OBJECTS {  aluPortInL2AddrProtoDiscards,
               aluPortInMPLSLabelDiscards,
               aluPortInIPAddrProtoDiscards,
               aluPortInVlanIdDiscards,
               aluPortInHdlcCrcDiscards,
               aluPortOutPortMtuDiscards,
               aluPortInCsmQHiPriDiscards,
               aluPortInCsmQMediumPriDiscards,
               aluPortInCsmQLowPriDiscards,
               aluPortOutCsmQDiscards,
               aluPortInOtherDiscards,
               aluPortOutOtherDiscards,
               aluPortInHardPolicerDiscards
            }
    STATUS      current
    DESCRIPTION
        "The group of objects supporting retrieval of the detailed packet
         discard statistics on Nokia SAR series systems"
    ::= { aluPortGroups 38 }

aluPortEtherXorGroupV6v0   OBJECT-GROUP
    OBJECTS {
                aluPortEtherXorMode,
                aluPortEtherOperXorMode
            }
    STATUS     current
    DESCRIPTION
        "The group of objects supporting management of XOR mode for ethernet
         ports for revision 6.0 on 7705 Nokia systems."
    ::= { aluPortGroups 39 }

aluExtDS1E1SsmGroup   OBJECT-GROUP
    OBJECTS {
                aluExtDS1E1Ssm,
                aluExtDS1E1SsmTxDus,
                aluExtE1SsmSaBit,
                aluExtDs1E1TxSsmValue,
                aluExtDs1E1RxSsmValue,
                aluExtPortSsmTxQualityLevel
            }
    STATUS     current
    DESCRIPTION
        "The group of objects supporting management of port that support
        Synchronous Status Messages (SSM) on 7705 Nokia systems."
    ::= { aluPortGroups 40 }

aluPwrEthPortGroupV6v0   OBJECT-GROUP
    OBJECTS {
                aluExtPethPsePortFaultReason,
                aluExtPethPsePortPowerLevel,
                aluExtPethPsePortPowerConsumption,
                aluExtPethPsePortMaximumPower
            }
    STATUS     current
    DESCRIPTION
        "The group of objects supporting management of power ethernet
         ports for revision 6.0 on 7705 Nokia systems."
    ::= { aluPortGroups 41 }

aluRS232HoldTimeGroup OBJECT-GROUP
    OBJECTS   {
                      aluRS232HoldTimeUp,
                      aluRS232HoldTimeDown
              }
    STATUS        current
    DESCRIPTION
        "The group of objects supporting management of hold-time
         capabilities on Serial type ports on Nokia SAR series systems."
    ::= { aluPortGroups 42 }

aluEthPtpTimestampStatsGroupV6v0     OBJECT-GROUP
    OBJECTS {
                aluEthPtpInSyncPktTimestamped,
                aluEthPtpOutSyncPktTimestamped,
                aluEthPtpInDelReqPktTimestamped,
                aluEthPtpOutDelReqPktTimestamped
            }
    STATUS      current
    DESCRIPTION
        "The group of objects supporting retrieval of the IEEE1588
         PTP transparent clock statistic on Nokia SAR series systems"
    ::= { aluPortGroups 43 }

aluVlanFilterPortGroup OBJECT-GROUP
    OBJECTS   {
                      aluExtPortEtherVlanFilter
              }
    STATUS        current
    DESCRIPTION
        "The group of objects supporting management of VLAN filter
         capabilities on Bridged Ethernet ports on Nokia SAR series systems."
    ::= { aluPortGroups 44 }

aluScadaBridgeGroupV6v1   OBJECT-GROUP
    OBJECTS {
                aluScadaBridgeType,
                aluScadaBridgeAdminStatus,
                aluScadaBridgeOperStatus,
                aluScadaBridgeDescription,
                aluSerialMddbReportAlarms,
                aluSerialMddbForceActive,
                aluSerialMddbSquelchStatus,
                aluSerialMddbSquelchEnable,
                aluSerialMddbSquelchTimeout,
                aluSerialMddbSquelchReset,
                aluSerialMddbSpeed,
                aluScadaBranchRowStatus,
                aluScadaBranchAdminStatus,
                aluScadaBranchOperStatus,
                aluScadaBranchMultiDrop,
                aluScadaBranchAlarmStatus,
                aluScadaBranchDescription,
                aluScadaBranchEncapType,
                aluScadaBranchMode
            }
    STATUS      obsolete
    DESCRIPTION
        "The group of objects supporting management of scada bridges
        for version 6.1 on Nokia SAR series systems"
    ::= { aluPortGroups 45 }


aluExtPethPsePortNotificationGroupV6v0   NOTIFICATION-GROUP
    NOTIFICATIONS {
                aluExtPethPsePortStatusChange
            }
    STATUS     current
    DESCRIPTION
        "The group of notifications supporting the management of
         power ethernet Pse ports for revision 6.0 on Nokia SAR series
         systems."
    ::= { aluPortGroups 46 }

   aluPortNetRingGroupV6v0   OBJECT-GROUP
       OBJECTS {
                    aluPortNetRingAddDropFwdInProfPkts,
                    aluPortNetRingAddDropFwdOutProfPkts,
                    aluPortNetRingAddDropFwdInProfOcts,
                    aluPortNetRingAddDropFwdOutProfOcts,
                    aluPortNetRingAddDropDroInProfPkts,
                    aluPortNetRingAddDropDroOutProfPkts,
                    aluPortNetRingAddDropDroInProfOcts,
                    aluPortNetRingAddDropDroOutProfOcts
                 }
        STATUS     current
        DESCRIPTION
            "The group of objects supporting port statistics specific to ring
             Network Ports for revision 6.0 on 7705 Nokia systems."
    ::= { aluPortGroups 47 }

aluPortEtherQosGroupV6v0     OBJECT-GROUP
    OBJECTS {
                aluPortEtherIngressRateCbs,
                aluPortEtherIngressRateSrcPause,
                aluPortEtherEgrUnshapedSapCir
            }
    STATUS      current
    DESCRIPTION
        "The group of objects supporting management of ethernet ports
        on Nokia SAR series systems."
    ::= { aluPortGroups 48 }

 aluPortEtherLoopbackGroupV6v0   OBJECT-GROUP
    OBJECTS {
                aluExtPortEtherLoopback,
                aluExtPortEtherLoopbackTimer,
                aluExtPortEtherLoopbackTimeLeft,
                aluExtPortEtherLoopbackCfmLbMode,
                aluExtPortEtherCfmLbmRx,
                aluExtPortEtherCfmLbmDropped,
                aluExtPortEtherCfmLbrTx,
                aluExtPortEtherLoopbackSwapMacAddr,
                aluExtPortEtherLoopbackPersist,
                aluExtPortEtherCfmLbVlanList
            }
    STATUS     current
    DESCRIPTION
        "The group of objects supporting management of loopbacks for ethernet
         ports for revision 6.0 on 7705 Nokia systems."
    ::= { aluPortGroups 49 }

aluScadaBridgeNotificationGroupV6v1 NOTIFICATION-GROUP
    NOTIFICATIONS {
               aluSerialMddbSquelchStatusChanged,
               aluSerialMddbSquelchResetIssued
            }
    STATUS    obsolete
    DESCRIPTION
        "The group of notifications supporting the management of
         scada bridges for revision 6.1 on Nokia SAR series
         systems."
    ::= { aluPortGroups 50 }

aluPortEtherQosGroupV6v1     OBJECT-GROUP
    OBJECTS {
                aluExtPortEtherAccEgrShaper,
                aluExtPortEtherNetEgrShaper,
                aluPortEtherEgrUnshapedNwIfCir
            }
    STATUS      current
    DESCRIPTION
        "The group of objects supporting QOS management of ethernet ports
        on Nokia SAR series systems."
    ::= { aluPortGroups 51 }

aluGnssPortGroup   OBJECT-GROUP
    OBJECTS {
                aluGnssPortLastChangeTime,
                aluGnssPortType,
                aluGnssPortAntennaCableDelay,
                aluGnssPortElevationMaskAngle,
                aluGnssPortVisibleSatelliteCount,
                aluGnssPortUsedSatelliteCount,
                aluGnssPortAntennaStatus,
                aluGnssPortSyncStatus,
                aluGnssPortPositionLatitude,
                aluGnssPortPositionLongitude,
                aluGnssPortPositionAltitude,
                aluGnssPortDateAndTime,
                aluGnssPortReceiverStatus,
                aluGnssPortCurUtcOffset,
                aluGnssPortCurUtcOffsetValid
            }
    STATUS      current
    DESCRIPTION
        "The group of objects supporting management of GNSS type ports
        on Nokia SAR series systems."
    ::= { aluPortGroups 52 }

aluPortDiscardStatsGroupV6v1     OBJECT-GROUP
    OBJECTS {
               aluPortInL2MacDADiscards,
               aluPortInL2ETypeDiscards
            }
    STATUS      current
    DESCRIPTION
        "The group of objects supporting retrieval of the detailed packet
         discard statistics for revision 6.1 on Nokia SAR series systems"
    ::= { aluPortGroups 53 }

aluPortObsoleteGroupV6v0    OBJECT-GROUP
    OBJECTS {
                aluEthPtpInFcsErrorCount,
                aluEthPtpOutFcsErrorCount,
                aluPortCfmLbVlanId,
                aluPortCfmLbVlanRowStatus
            }
    STATUS      current
    DESCRIPTION
        "The group of objects obsoleted in the 7705 SAR series 6.0 release"
    ::= { aluPortGroups 54 }

aluDataPortNotifyObjsGroup   OBJECT-GROUP
    OBJECTS {   aluPortNotifyDataAlarmReason
            }
    STATUS        current
    DESCRIPTION
        "The group of objects supporting TDM Data type port notifications
         introduced for release 5.0 on Nokia SAR series systems."
    ::= { aluPortGroups 55 }

aluGnssPortNotifGroup NOTIFICATION-GROUP
    NOTIFICATIONS {
               aluGnssPortStatusChange
            }
    STATUS     current
    DESCRIPTION
        "The group of notifications supporting the management of GNSS ports
         for revision 6.1 on Nokia SAR series systems."
    ::= { aluPortGroups 56 }

aluScadaBridgeGroupV7v1   OBJECT-GROUP
    OBJECTS {
                aluScadaBridgeType,
                aluScadaBridgeAdminStatus,
                aluScadaBridgeOperStatus,
                aluScadaBridgeDescription,
                aluSerialMddbReportAlarms,
                aluSerialMddbForceActive,
                aluSerialMddbSquelchStatus,
                aluSerialMddbSquelchEnable,
                aluSerialMddbSquelchTimeout,
                aluSerialMddbSquelchReset,
                aluSerialMddbSpeed,
                aluSerialMddbSquelchResetMode,
                aluSerialMddbSquelchResetTimeout,
                aluSerialMddbRedMode,
                aluPcmForceActive,
                aluPcmSquelchStatus,
                aluPcmSquelchEnable,
                aluPcmSquelchTimeout,
                aluPcmSquelchReset,
                aluPcmSquelchResetMode,
                aluPcmSquelchResetTimeout,
                aluPcmRedMode,
                aluScadaBranchRowStatus,
                aluScadaBranchAdminStatus,
                aluScadaBranchOperStatus,
                aluScadaBranchMultiDrop,
                aluScadaBranchAlarmStatus,
                aluScadaBranchDescription,
                aluScadaBranchEncapType,
                aluScadaBranchMode
            }
    STATUS      current
    DESCRIPTION
        "The group of objects supporting management of scada bridges
        for version 6.1 on Nokia SAR series systems"
    ::= { aluPortGroups 57 }

aluScadaBridgeNotificationGroupV7v1 NOTIFICATION-GROUP
    NOTIFICATIONS {
               aluSerialMddbSquelchStatusChanged,
               aluSerialMddbSquelchResetIssued,
               aluPcmSquelchStatusChanged,
               aluPcmSquelchResetIssued
            }
    STATUS     current
    DESCRIPTION
        "The group of notifications supporting the management of
         scada bridges for revision 7.0 on Nokia SAR series
         systems."
    ::= { aluPortGroups 58 }

aluExtDS1PortLineEncodingGroup     OBJECT-GROUP
    OBJECTS {   aluExtDS1PortLineEncoding
            }
    STATUS      current
    DESCRIPTION
        "The group of objects supporting management of the line encoding
         of DS1/E1 physical ports on Nokia SAR series systems."
    ::= { aluPortGroups 59 }

aluPortCemStatsGroup     OBJECT-GROUP
    OBJECTS {   aluPortCemStatsEgressSamplingDoneCnt,
                aluPortCemStatsEgressAdjustDoneCnt
            }
    STATUS      current
    DESCRIPTION
        "The group of objects which provides 7705 specific cem stats."
    ::= { aluPortGroups 60 }

aluRS232ControlLeadsSignalGroup OBJECT-GROUP
    OBJECTS {
                aluRS232ControlLeadsSignal
            }
    STATUS      current
    DESCRIPTION
        "The group of objects supporting management of control lead signals
         on Serial type ports on Nokia SAR series systems."
    ::= { aluPortGroups 61 }

 aluPortEtherQosGroupV7v1     OBJECT-GROUP
    OBJECTS {
                aluExtPortEtherEgrRateIncludeFCS
            }
    STATUS      current
    DESCRIPTION
        "The group of objects supporting QOS management of ethernet ports
        for revision 7.0 on Nokia SAR series systems."
    ::= { aluPortGroups 62 }

aluRS232ControlLeadsNotifGroup NOTIFICATION-GROUP
    NOTIFICATIONS {
               aluRS232ControlLeadsSignalChange
            }
    STATUS     current
    DESCRIPTION
        "The group of notifications supporting the management of Serial control
         leads on Nokia SAR series systems."
    ::= { aluPortGroups 63 }

aluRS232ControlLeadsNotifObjsGroup   OBJECT-GROUP
    OBJECTS {   aluPortNotifyRS232ControlLeadsSignalChange
            }
    STATUS        current
    DESCRIPTION
        "The group of objects supporting Serial control leads notifications
         introduced for release 7.0 on Nokia SAR series systems."
    ::= { aluPortGroups 64 }

aluRS232ControlLeadsMonGroup OBJECT-GROUP
    OBJECTS {
                aluRS232ControlLeadMonDtrDsr,
                aluRS232ControlLeadMonRtsDcdC,
                aluRS232ControlLeadMonAlbCts,
                aluRS232ControlLeadMonRdlRi
            }
    STATUS      current
    DESCRIPTION
        "The group of objects supporting management of monitoring control leads
         on Serial type ports on Nokia SAR series systems."
    ::= { aluPortGroups 65 }

aluRS232SocketGroup              OBJECT-GROUP
    OBJECTS {
                aluRS232SocketRowStatus,
                aluRS232SocketLastChangeTime,
                aluRS232SocketEopLength,
                aluRS232SocketEopIdleTimeout,
                aluRS232SocketEopSpecialChar,
                aluRS232SocketSquelchDelay,
                aluRS232SocketUnsquelchDelay,
                aluRS232SocketInterSessionDelay,
                aluRS232SocketSquelchStatus,
                aluRS232SocketSquelchReset
            }
    STATUS      current
    DESCRIPTION
        "The group of objects supporting management of Serial socket channels
         on Nokia SAR series systems."
    ::= { aluPortGroups 66 }

aluRS232SocketNotifGroup         NOTIFICATION-GROUP
    NOTIFICATIONS {
                aluRS232SquelchStatusChange,
                aluRS232SquelchResetIssued
            }
    STATUS     current
    DESCRIPTION
        "The group of notifications supporting the management of Serial socket
         channels on Nokia SAR series systems."
    ::= { aluPortGroups 67 }

aluDot1xAuthGroup              OBJECT-GROUP
    OBJECTS {
                aluDot1xAuthMacAuthEnabled,
                aluDot1xAuthMacAuthWait,
                aluDot1xAuthLastAuthMethod,
                aluDot1xAuthMacAuthFramesRx
            }
    STATUS      current
    DESCRIPTION
        "The group of objects supporting management of Mac-Based Authentication
         on Nokia SAR series systems."
    ::= { aluPortGroups 68 }

aluRS232SocketStatsGroup         OBJECT-GROUP
    OBJECTS {
                aluRS232SocketRxChars,
                aluRS232SocketTxChars,
                aluRS232SocketEopIdleTimeoutCnt,
                aluRS232SocketEopLengthCnt,
                aluRS232SocketEopSpecialCharCnt,
                aluRS232SocketIngrForwardedPkts,
                aluRS232SocketEgrForwardedPkts,
                aluRS232SocketIngrDroppedPkts,
                aluRS232SocketEgrDroppedPkts,
                aluRS232SocketSquelchCnt
            }
    STATUS      current
    DESCRIPTION
        "The group of objects supporting retrieval of the detailed
         RS232Socket statistics on Nokia SAR series systems."
    ::= { aluPortGroups 69 }

aluGnssPortReceiverFwVersGroup   OBJECT-GROUP
    OBJECTS {
                aluGnssPortReceiverFwVersion
            }
    STATUS      current
    DESCRIPTION
        "The group of objects supporting retrieval of the version of firmware
         running on a particular GNSS receiver module on Nokia SAR series
         systems."
    ::= { aluPortGroups 70 }

aluScadaVcbGroup                 OBJECT-GROUP
    OBJECTS {
                aluScadaVcbIdleCode,
                aluScadaVcbSeizedCode,
                aluScadaVcbSignalMode
            }
    STATUS      current
    DESCRIPTION
        "The group of objects supporting management of SCADA VCBs on Nokia SAR
         series systems."
    ::= { aluPortGroups 71 }

aluScadaBranchGainGroup          OBJECT-GROUP
    OBJECTS {
                aluScadaBranchGainInput,
                aluScadaBranchGainOutput,
                aluScadaBranchGainSidetoneEnable
            }
    STATUS      current
    DESCRIPTION
        "The group of objects supporting management of signal gain on SCADA
         branches on Nokia SAR series systems."
    ::= { aluPortGroups 72 }

aluPortEtherQosGroupV8v1     OBJECT-GROUP
   OBJECTS {
            aluExtPortEtherBnAllowed,
            aluExtPortEtherBnHoldTime,
            aluExtPortEtherBnEgressRateInUse,
            aluExtPortEtherBnLastRateChangeTime,
            aluExtPortEtherBnLastMgsRxTime,
            aluExtPortEtherBnNumRateChanges,
            aluExtPortEtherBnNumMsgRx,
            aluExtPortEtherBnNumInvalidMsgRx,
            aluExtPortEtherBnNumBWOutOfRange
           }
   STATUS      current
   DESCRIPTION
       "The group of objects supporting QOS management of ethernet ports
       for revision 8.0 on Nokia SAR series systems."
   ::= { aluPortGroups 73 }

aluPortLsrIpLoadBalGroupV8v0     OBJECT-GROUP
    OBJECTS {
                aluLsrIpLoadBalBtmOfStk,
                aluLsrIpLoadBalIngressPort
            }
    STATUS      current
    DESCRIPTION
        "The group of objects supporting management of lsr load balancing
        on Alcatel-Lucent SAR series systems"
    ::= { aluPortGroups 74 }

aluRS232ClockSyncGroup           OBJECT-GROUP
    OBJECTS {
                aluRS232ClockSyncState,
                aluRS232ClockMasterPortId
            }
    STATUS      current
    DESCRIPTION
        "The group of objects supporting clock synchronization objects
         on Serial type ports on Nokia SAR series systems."
    ::= { aluPortGroups 75 }

aluRS232ClockSyncNotifGroup      NOTIFICATION-GROUP
    NOTIFICATIONS {
                aluRS232ClockSyncStateChange
            }
    STATUS     current
    DESCRIPTION
        "The group of notifications supporting clock synchronization objects
         on Serial type ports on Nokia SAR series systems."
    ::= { aluPortGroups 76 }

aluRS232InvertClockGroup         OBJECT-GROUP
    OBJECTS {
                aluRS232InvertClock
            }
    STATUS      current
    DESCRIPTION
        "The group of objects supporting clock inversion objects
         on Serial type ports on Nokia SAR series systems."
    ::= { aluPortGroups 77 }

aluPortEtherObsoleteV9v0Group       OBJECT-GROUP
    OBJECTS {  aluEthPtpAsymmetry
            }
    STATUS      obsolete
    DESCRIPTION
        "The objects which were obsoleted for revision 9.0 on Nokia
         7705 SROS series systems."
    ::= { aluPortGroups 78 }

aluRS232MonClockDataGroup        OBJECT-GROUP
    OBJECTS {
                aluRS232MonClockDeviationRaise,
                aluRS232MonClockDeviationClear,
                aluRS232MonDataInactivityRaise,
                aluRS232MonDataInactivityClear
            }
    STATUS      current
    DESCRIPTION
        "The group of objects supporting monitor of clock and data faults
         on Serial type ports on Nokia SAR series systems."
    ::= { aluPortGroups 79 }

aluScadaNameGroup                OBJECT-GROUP
    OBJECTS {
                aluScadaBridgeName,
                aluScadaBranchName
            }
    STATUS      current
    DESCRIPTION
        "The group of objects supporting names of Scada entities on
         Nokia SAR series systems."
    ::= { aluPortGroups 80 }

aluExtDS0ChanGroupLoopbackGroup  OBJECT-GROUP
    OBJECTS {
                aluExtDS0ChanGroupLoopback
            }
    STATUS      current
    DESCRIPTION
        "The group of objects supporting loopbacks on DS0 channel groups on
         Nokia SAR series systems."
    ::= { aluPortGroups 81 }

aluExtDS0ChanGrpLpbckNotifGroup  NOTIFICATION-GROUP
    NOTIFICATIONS {
                aluExtDS0ChanGrpLoopbackStarted,
                aluExtDS0ChanGrpLoopbackStopped
            }
    STATUS        current
    DESCRIPTION
        "The group of notifications supporting management of DS0 channel group
         loopbacks on Nokia SAR series systems."
    ::= { aluPortGroups 82 }

aluPortNgeGroup OBJECT-GROUP
    OBJECTS {
        aluPortNgeL2KeygroupTxFrames,
        aluPortNgeL2KeygroupTxBytes,
        aluPortNgeL2KeygroupRxFrames,
        aluPortNgeL2KeygroupRxBytes,
        aluPortNgeL2KGRxDropOtherFrames,
        aluPortNgeL2KGRxDropOtherBytes,
        aluPortNgeL2KeygroupTxDropFrames,
        aluPortNgeL2KeygroupTxDropBytes,
        aluPortNgeL2KGRxDrpInvldSpiFrms,
        aluPortNgeL2KGRxDrpInvldSpiBytes
    }
    STATUS current
    DESCRIPTION
        "The group of objects supporting group encryption stats on a port."
    ::= { aluPortGroups 83 }

aluPortPtpTimestampStatsV9v0Group OBJECT-GROUP
    OBJECTS {
        aluEthPtpOutFollowUpPktTimestamped
    }
    STATUS current
    DESCRIPTION
        "The group was introduced in release 9 of Nokia SAR series systems to support
        management of the PTP IPv6 two-step functionality."
    ::= { aluPortGroups 84 }
END
