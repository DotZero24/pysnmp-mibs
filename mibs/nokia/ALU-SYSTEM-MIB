ALU-SYSTEM-MIB DEFINITIONS ::= BEGIN

IMPORTS
        MODULE-IDENTITY, OBJECT-TYPE,
        NOTIFICATION-TYPE, Unsigned32,
        Integer32                                 FROM SNMPv2-SMI

        TEXTUAL-CONVENTION, TruthValue,
        TimeStamp, RowStatus                      FROM SNMPv2-TC

        TPortSchedulerPIR,
        TmnxAdminState                            FROM TIMETRA-TC-MIB

        MODULE-COMPLIANCE, OBJECT-GROUP,
        NOTIFICATION-GROUP                        FROM SNMPv2-CONF

        aluSARMIBModules, aluSARObjs,
        aluSARNotifyPrefix, aluSARConfs           FROM ALU-SAR-GLOBAL-MIB

        aluHwObjs                                 FROM ALU-CHASSIS-MIB
        ;

aluSystemMIBModule MODULE-IDENTITY
        LAST-UPDATED    "1402100000Z"
        ORGANIZATION    "Nokia"
        CONTACT-INFO
            "Nokia 7x50 Support
             Web: http://www.nokia.com/comps/pages/carrier_support.jhtml"
        DESCRIPTION
        "This document is the SNMP MIB module to manage and provision extended
        system functionality for the Nokia 7705 SAR series devices.

        Copyright 2003-2015 Nokia. All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."
--
--  Revision History
--
        REVISION        "1106140000Z"
        DESCRIPTION     "Rev 1.0                14 Jun 2011 00:00
                         Initial version of the ALU-SYSTEM-MIB."

        REVISION        "1402100000Z"
        DESCRIPTION     "Rev 2.0                10 Feb 2014 00:00
                         6.1 release of the ALU-SYSTEM-MIB."

        ::= { aluSARMIBModules 13 }

--%%%%%%%%%%%%%%%%%%%%%%%%%%%%%%%%%%%%%%%%%%%%%%%%%%%%%%%%%%%%%%%%%%%%%%
--
--  Nokia 7705 SAR series extensions
--

aluSystemObjs            OBJECT IDENTIFIER ::= { aluSARObjs 13 }
aluSystemMIBConformance  OBJECT IDENTIFIER ::= { aluSARConfs 13 }
aluSystemNotifyPrefix    OBJECT IDENTIFIER ::= { aluSARNotifyPrefix 9 }
  aluSystemNotification      OBJECT IDENTIFIER ::= { aluSystemNotifyPrefix 0 }

aluSystemNotificationObjs      OBJECT IDENTIFIER ::= { aluHwObjs 8 }

-- --------------------------------------------------------------------
--
--      ALU-SYSTEM-MIB Textual Conventions
--
AluTod1PpsMessageType ::= TEXTUAL-CONVENTION
    STATUS      current
    DESCRIPTION
        "The AluTod1PpsMessageType specifies the format of the message used
        on the ToD 1PPS connector.

        none (0) - specifies that no messages are sent after the 1 second pulse.
        cm (1) - specifies the China Mobile format is generated after the 1
                 second pulse
        ct (2) - specifies the China Telecom format is generated after the 1
                 second pulse.

        The IRIGB message format is fully described in IRIG STANDARD 200-04. The
        message formats are described with respect to the tuple (Format,
        Modulation Type, Frequency, Coded Expression). The following message
        formats are defined:

        irig-b000-b120 (3) -
            b000 - Format: B,
                   Modulation: Pulse width code,
                   Frequency: No carrier/index count interval
                   Coded Expression: BCDTOY, CF, SBS
            b120 - Format: B,
                   Modulation: Sine wave, amplitude modulated,
                   Frequency: 1000 Hz/1 ms
                   Coded Expression: BCDTOY, CF, SBS
        irig-b001-b121 (4) -
            b001 - Format: B,
                   Modulation: Pulse width code,
                   Frequency: No carrier/index count interval
                   Coded Expression: BCDTOY, CF
            b121 - Format: B,
                   Modulation: Sine wave, amplitude modulated,
                   Frequency: 1000 Hz/1 ms
                   Coded Expression: BCDTOY, CF
        irig-b002-b122 (5),
            b001 - Format: B,
                   Modulation: Pulse width code,
                   Frequency: No carrier/index count interval
                   Coded Expression: BCDTOY
            b121 - Format: B,
                   Modulation: Sine wave, amplitude modulated,
                   Frequency: 1000 Hz/1 ms
                   Coded Expression: BCDTOY
        irig-b003-b123 (6),
            b001 - Format: B,
                   Modulation: Pulse width code,
                   Frequency: No carrier/index count interval
                   Coded Expression: BCDTOY, SBS
            b121 - Format: B,
                   Modulation: Sine wave, amplitude modulated,
                   Frequency: 1000 Hz/1 ms
                   Coded Expression: BCDTOY, SBS
        irig-b004-b124 (7),
            b001 - Format: B,
                   Modulation: Pulse width code,
                   Frequency: No carrier/index count interval
                   Coded Expression: BCDTOY, BCDYEAR, CF, SBS
            b121 - Format: B,
                   Modulation: Sine wave, amplitude modulated,
                   Frequency: 1000 Hz/1 ms
                   Coded Expression: BCDTOY, BCDYEAR, CF, SBS
        irig-b005-b125 (8),
            b001 - Format: B,
                   Modulation: Pulse width code,
                   Frequency: No carrier/index count interval
                   Coded Expression: BCDTOY, BCDYEAR, CF
            b121 - Format: B,
                   Modulation: Sine wave, amplitude modulated,
                   Frequency: 1000 Hz/1 ms
                   Coded Expression: BCDTOY, BCDYEAR, CF
        irig-b006-b126 (9),
            b001 - Format: B,
                   Modulation: Pulse width code,
                   Frequency: No carrier/index count interval
                   Coded Expression: BCDTOY, BCDYEAR
            b121 - Format: B,
                   Modulation: Sine wave, amplitude modulated,
                   Frequency: 1000 Hz/1 ms
                   Coded Expression: BCDTOY, BCDYEAR
        irig-b007-b127 (10)
            b001 - Format: B,
                   Modulation: Pulse width code,
                   Frequency: No carrier/index count interval
                   Coded Expression: BCDTOY, BCDYEAR, SBS
            b121 - Format: B,
                   Modulation: Sine wave, amplitude modulated,
                   Frequency: 1000 Hz/1 ms
                   Coded Expression: BCDTOY, BCDYEAR, SBS. "
    SYNTAX  INTEGER {
                none (0),
                cm   (1),
                ct   (2),
                irig-b000-b120 (3),
                irig-b001-b121 (4),
                irig-b002-b122 (5),
                irig-b003-b123 (6),
                irig-b004-b124 (7),
                irig-b005-b125 (8),
                irig-b006-b126 (9),
                irig-b007-b127 (10)
            }

AluSysTimePriorityType ::= TEXTUAL-CONVENTION
    STATUS      current
    DESCRIPTION
        "The AluSysTimePriorityType specifies the relative priority of
        system time inputs. The highest priority (lowest numerical value)
        qualified input to system time will be the selected system time
        source."
    SYNTAX  INTEGER {
                none           (0),
                priority1      (1),
                priority2      (2),
                priority3      (3),
                priority4      (4),
                priority5      (5),
                priority6      (6),
                priority7      (7),
                priority8      (8),
                priority9      (9),
                priority10     (10),
                priority11     (11),
                priority12     (12),
                priority13     (13),
                priority14     (14),
                priority15     (15),
                priority16     (16),
                priority17     (17),
                holdover       (18)
            }

AluSysTimeRefLeapSecSchedType ::= TEXTUAL-CONVENTION
    STATUS      current
    DESCRIPTION
        "The AluSysTimeRefLeapSecSchedType value indicates whether a leap second
        is scheduled. The encoding allows for scheduling a forward or a backwards
        leap second."
    SYNTAX  INTEGER {
                notScheduled      (0),
                forwardScheduled  (1),
                backwardScheduled (2)
            }

AluSysTimeReferenceType ::= TEXTUAL-CONVENTION
    STATUS      current
    DESCRIPTION
        "The AluSysTimeReferenceType value indicates the type of system time
        reference."
    SYNTAX  INTEGER {
                notApplic (0),
                gnss (1),
                ptp (2),
                ntp (3),
                sntp (4),
                holdover (5)
            }

AluSysTimeReferenceId ::= TEXTUAL-CONVENTION
    STATUS      current
    DESCRIPTION
        "The AluSysTimeReferenceId is an identifier that is unique for its
        associated AluSysTimeReferenceType. The following AluSysTimeReferenceId
        type are defined:

         AluSysTimeReferenceType | AluSysTimeReferenceId
        ---------------------------------------------------------------------
        'gnss (1)'               | TmnxPortID
        'ptp (2)'                | Alu1588PtpClockIndex
        'ntp (3)'                | 1
        'sntp (4)'               | 1
        'holdover (5)'           | 1

        When the time reference type is 'ptp (2)', reference ids in the range
        1..31 identify PTP clocks that are configured in the table
        aluPtpClockTable.  A PTP reference id of 32 corresponds to the PTP
        clock on the CSM, which is configured with the tmnxPtpClockConfig
        objects.
        "
    SYNTAX  Unsigned32 (0..4294967295)

--
-- ToD-1PPS: Time Of Day and 1 Pulse Per Second
--

aluTod1PpsInfo         OBJECT IDENTIFIER ::= { aluSystemObjs 1 }

aluTod1PpsMessageType  OBJECT-TYPE
    SYNTAX      AluTod1PpsMessageType
    MAX-ACCESS  read-write
    STATUS      current
    DESCRIPTION
        "The aluTod1PpsMessageType indicated the message type that is
        sent after the 1 second pulse."
    DEFVAL { none }
    ::= { aluTod1PpsInfo 1 }

aluTod1PpsOutput OBJECT-TYPE
    SYNTAX      TmnxAdminState
    MAX-ACCESS  read-write
    STATUS      current
    DESCRIPTION
        "The admin state of the Time Of Day - 1 Pulse Per Second (TOD-1PPS) output
        port. On systems that do not support a TOD-1PPS output port the default
        value is 'noop (0)'."
    DEFVAL { outOfService }
    ::= { aluTod1PpsInfo 2 }

aluTod1PpsInput OBJECT-TYPE
    SYNTAX      TmnxAdminState
    MAX-ACCESS  read-write
    STATUS      current
    DESCRIPTION
        "The admin state of the Time Of Day - 1 Pulse Per Second (TOD-1PPS) input
         port. On systems that do not support a TOD-1PPS input port the default
         value is 'noop (0)'."
    DEFVAL { outOfService }
    ::= { aluTod1PpsInfo 3 }

aluNtpSystem  OBJECT IDENTIFIER ::= { aluSystemObjs 2 }

aluNtpMdaTimestamp OBJECT-TYPE
    SYNTAX      TruthValue
    MAX-ACCESS  read-write
    STATUS      current
    DESCRIPTION
        "The value of aluNtpMdaTimestamp specifies whether the NTP
        origin timestamp is generated by the MDA. Also the
        aluNtpMdaTimestamp indicates that the reception time
        of NTP packets is performed by the MDA. Timestamping
        closer to the point of ingress and egress improves NTP
        time recovery accuracy.

        MDA timestamping cannot be enabled if servers are configured
        with authentication enabled.

        Enabling MDA timestamping will not affect NTP packets that
        are transmitted or received on the management port."
    DEFVAL { false }
    ::= { aluNtpSystem 1 }

aluSysTimeSelector  OBJECT IDENTIFIER ::= { aluSystemObjs 3 }

aluActiveTimeSourceType OBJECT-TYPE
    SYNTAX      AluSysTimeReferenceType
    MAX-ACCESS  read-only
    STATUS      current
    DESCRIPTION
        " "
    ::= { aluSysTimeSelector 1 }

aluActiveTimeSourceId OBJECT-TYPE
    SYNTAX      AluSysTimeReferenceId
    MAX-ACCESS  read-only
    STATUS      current
    DESCRIPTION
        " "
    ::= { aluSysTimeSelector 2 }

aluActiveTimeSourceChange OBJECT-TYPE
    SYNTAX      TimeStamp
    MAX-ACCESS  read-only
    STATUS      current
    DESCRIPTION
        "The value of aluActiveTimeSourceChange is the last time that the active
         system time source changed."
    ::= { aluSysTimeSelector 3 }

aluTimeSelectorTable OBJECT-TYPE
    SYNTAX      SEQUENCE OF AluTimeReferenceEntry
    MAX-ACCESS  not-accessible
    STATUS      current
    DESCRIPTION
        " "
    ::= { aluSysTimeSelector 4 }

aluTimeReferenceEntry OBJECT-TYPE
    SYNTAX      AluTimeReferenceEntry
    MAX-ACCESS  not-accessible
    STATUS      current
    DESCRIPTION
        "Each row entry contains information about system time input
        reference."
    INDEX {timeRefType, timeRefId}
    ::= { aluTimeSelectorTable 1 }

AluTimeReferenceEntry ::=
    SEQUENCE {
        timeRefType                 AluSysTimeReferenceType,
        timeRefId                   AluSysTimeReferenceId,
        timeRefPriority             AluSysTimePriorityType,
        timeRefRowStatus            RowStatus,
        timeRefQualified            TruthValue,
        timeRefQualifiedChange      TimeStamp,
        timeRefPropertiesUpdate     TimeStamp,
        timeRefDeltaSec             Integer32,
        timeRefDeltaNs              Integer32,
        timeRefLeapSecSched         AluSysTimeRefLeapSecSchedType,
        timeRefLeapSecValid         TruthValue,
        timeRefLeapSec              Unsigned32,
        timeRefLeapSecUpdTime       TimeStamp

    }

timeRefType   OBJECT-TYPE
    SYNTAX      AluSysTimeReferenceType
    MAX-ACCESS  not-accessible
    STATUS      current
    DESCRIPTION
        "The value of timeRefType is the type of the system time reference."
    ::= { aluTimeReferenceEntry 1 }

timeRefId OBJECT-TYPE
    SYNTAX      AluSysTimeReferenceId
    MAX-ACCESS  not-accessible
    STATUS      current
    DESCRIPTION
        "The value of timeRefId is the unique identifier for this type
        system time reference."
    ::= { aluTimeReferenceEntry 2 }

timeRefPriority OBJECT-TYPE
    SYNTAX      AluSysTimePriorityType
    MAX-ACCESS  read-create
    STATUS      current
    DESCRIPTION
        "The value timeRefPriority is the priority of this time reference. A
        lower numeric values represents a higher priority. The timeRefPriority
        must be present when the time reference is created."
    ::= { aluTimeReferenceEntry 3 }

timeRefRowStatus OBJECT-TYPE
    SYNTAX      RowStatus
    MAX-ACCESS  read-create
    STATUS      current
    DESCRIPTION
        "The row status used to create and delete rows in this table. When the
        row is created the timeRefPriority must be present."
    ::= { aluTimeReferenceEntry 4 }

timeRefQualified OBJECT-TYPE
    SYNTAX      TruthValue
    MAX-ACCESS  read-only
    STATUS      current
    DESCRIPTION
        "The time reference is providing time updates."
    DEFVAL { false }
    ::= { aluTimeReferenceEntry 5 }

timeRefQualifiedChange OBJECT-TYPE
    SYNTAX      TimeStamp
    MAX-ACCESS  read-only
    STATUS      current
    DESCRIPTION
        "The time since the first time update for this reference."
    ::= { aluTimeReferenceEntry 6 }

timeRefPropertiesUpdate OBJECT-TYPE
    SYNTAX      TimeStamp
    MAX-ACCESS  read-only
    STATUS      current
    DESCRIPTION
        "The time of the last time update for this time reference."
    ::= { aluTimeReferenceEntry 7 }

timeRefDeltaSec OBJECT-TYPE
    SYNTAX      Integer32
    MAX-ACCESS  read-only
    STATUS      current
    DESCRIPTION
        "The time difference between this reference and the currently selected
        time reference is determined by subtracting this reference's time
        from the currently active time reference. The resulting value is a
        tuple of seconds and nano seconds. The timeRefDeltaSec represents
        seconds component of the difference between these time values. If this
        time reference is not qualified the timeRefDeltaSec will be 0."
    ::= { aluTimeReferenceEntry 8 }

timeRefDeltaNs OBJECT-TYPE
    SYNTAX      Integer32
    MAX-ACCESS  read-only
    STATUS      current
    DESCRIPTION
        "The time difference between this reference and the currently selected
        time reference is determined by subtracting this reference's time
        from the currently active time reference. The resulting value is a
        tuple of seconds and nano seconds. The timeRefDeltaNs represents
        nano-seconds component of the difference between these time values. If
        this time reference is not qualified the timeRefDeltaNs will be 0."
    ::= { aluTimeReferenceEntry 9 }

timeRefLeapSecSched OBJECT-TYPE
    SYNTAX      AluSysTimeRefLeapSecSchedType
    MAX-ACCESS  read-only
    STATUS      current
    DESCRIPTION
        "An indicator whether there is a scheduled leap second."
    ::= { aluTimeReferenceEntry 10 }

timeRefLeapSecValid OBJECT-TYPE
    SYNTAX      TruthValue
    MAX-ACCESS  read-only
    STATUS      obsolete
    DESCRIPTION
        "The timeRefLeapSecValid is an indicator of the validity of
        the timeRefLeapSec value."
    DEFVAL { false }
    ::= { aluTimeReferenceEntry 11 }

timeRefLeapSec OBJECT-TYPE
    SYNTAX      Unsigned32
    MAX-ACCESS  read-only
    STATUS      obsolete
    DESCRIPTION
        "The number of leap seconds that this time reference is including
        in its time value."
    ::= { aluTimeReferenceEntry 12 }

timeRefLeapSecUpdTime OBJECT-TYPE
    SYNTAX      TimeStamp
    MAX-ACCESS  read-only
    STATUS      current
    DESCRIPTION
        "timeRefLeapSecUpdTime is the UTC time that the pending leap sec
        adjustment will occur. timeRefLeapSecUpdTime is 0 when
        ALU-SYSTEM-MIB::timeRefLeapSecSched is 'notScheduled (0)'. "
    ::= { aluTimeReferenceEntry 13 }


aluSystemSptConfig         OBJECT IDENTIFIER ::= { aluSystemObjs 4 }

aluSystemSptSecAggRate OBJECT-TYPE
    SYNTAX       TPortSchedulerPIR
    MAX-ACCESS   read-write
    STATUS       current
    DESCRIPTION
        "System-wide aggregate rate limit to be applied to self processed security traffic.
         aluSystemSptSecAggRate is only supported on Nokia SAR-M family.
         The value '-1' means that there is no limit."
    DEFVAL { 50000 }
    ::= { aluSystemSptConfig 1 }

--%%%%%%%%%%%%%%%%%%%%%%%%%%%%%%%%%%%%%%%%%%%%%%%%%%%%%%%%%%%%%%%%%%%%%
-- Notifications for 6.1
--%%%%%%%%%%%%%%%%%%%%%%%%%%%%%%%%%%%%%%%%%%%%%%%%%%%%%%%%%%%%%%%%%%%%%

aluSystemNotifyTimeRefType  OBJECT-TYPE
    SYNTAX      AluSysTimeReferenceType
    MAX-ACCESS  accessible-for-notify
    STATUS      current
    DESCRIPTION
        "Indicates the system time reference type associated with the trap."
    ::= { aluSystemNotificationObjs 1 }

aluSystemNotifyTimeRefId  OBJECT-TYPE
    SYNTAX      AluSysTimeReferenceId
    MAX-ACCESS  accessible-for-notify
    STATUS      current
    DESCRIPTION
        "Indicates the system time reference identifier associated with the trap."
    ::= { aluSystemNotificationObjs 2 }

aluTimeRefCreated NOTIFICATION-TYPE
    OBJECTS {
        aluSystemNotifyTimeRefType,
        aluSystemNotifyTimeRefId,
        timeRefPriority
    }
    STATUS  current
    DESCRIPTION
        " "
    ::= { aluSystemNotification 1 }

aluTimeRefDeleted NOTIFICATION-TYPE
    OBJECTS {
        aluSystemNotifyTimeRefType,
        aluSystemNotifyTimeRefId
    }
    STATUS  current
    DESCRIPTION
        " "
    ::= { aluSystemNotification 2 }


aluTimeRefQualified NOTIFICATION-TYPE
    OBJECTS {
        aluSystemNotifyTimeRefType,
        aluSystemNotifyTimeRefId
    }
    STATUS  current
    DESCRIPTION
        " "
    ::= { aluSystemNotification 3 }

aluTimeRefDisqualified NOTIFICATION-TYPE
    OBJECTS {
        aluSystemNotifyTimeRefType,
        aluSystemNotifyTimeRefId
    }
    STATUS  current
    DESCRIPTION
        " "
    ::= { aluSystemNotification 4 }

aluTimeRefSelect NOTIFICATION-TYPE
    OBJECTS {
        aluSystemNotifyTimeRefType,
        aluSystemNotifyTimeRefId
    }
    STATUS  current
    DESCRIPTION
        " "
    ::= { aluSystemNotification 5 }

--
-- Conformance Information
--
aluSystemMIBCompliances  OBJECT IDENTIFIER ::= { aluSystemMIBConformance 1 }
aluSystemMIBGroups       OBJECT IDENTIFIER ::= { aluSystemMIBConformance 2 }

-- compliance statements

aluSystemMIBCompliance  MODULE-COMPLIANCE
    STATUS  obsolete
    DESCRIPTION
            "The compliance statement for revision 1.0 of ALU-SYSTEM-MIB."
    MODULE  -- this module
        MANDATORY-GROUPS {
            aluTod1PpsGroup
        }
    ::= { aluSystemMIBCompliances 1 }

aluSystemV6v1MIBCompliance  MODULE-COMPLIANCE
    STATUS  obsolete
    DESCRIPTION
            "The compliance statement for revision 1.0 of ALU-SYSTEM-MIB."
    MODULE  -- this module
        MANDATORY-GROUPS {
            aluTod1PpsGroup,
            aluNtpMdaTimestamp,
            aluSysTimeReferenceGroup,
            aluSysTimeNotificationV6v1Group
        }
    ::= { aluSystemMIBCompliances 2 }

aluSystemV7v0MIBCompliance  MODULE-COMPLIANCE
    STATUS  current
    DESCRIPTION
            "The compliance statement for revision 7.0 of ALU-SYSTEM-MIB."
    MODULE  -- this module
        MANDATORY-GROUPS {
            aluTod1PpsGroup,
            aluNtpMdaTimestamp,
            aluSysTimeReferenceGroup,
            aluSysTimeNotificationV6v1Group,
            aluSystemSptGroup
        }
    ::= { aluSystemMIBCompliances 3 }

-- units of conformance

aluTod1PpsGroup  OBJECT-GROUP
    OBJECTS {   aluTod1PpsMessageType,
                aluTod1PpsOutput,
                aluTod1PpsInput
            }
    STATUS      current
    DESCRIPTION
        "The group of objects supporting management of the
         Time Of Day - 1 PPS port on the Nokia
         7705 SAR series systems."
    ::= { aluSystemMIBGroups 1 }

aluNtpGroup  OBJECT-GROUP
    OBJECTS {   aluNtpMdaTimestamp
            }
    STATUS      current
    DESCRIPTION
        "The group of objects supporting management of the
         NTP on the Nokia 7705 SAR series systems."
    ::= { aluSystemMIBGroups 2 }

aluSysTimeReferenceGroup  OBJECT-GROUP
    OBJECTS {   aluActiveTimeSourceType,
                aluActiveTimeSourceId,
                aluActiveTimeSourceChange,
                timeRefPriority,
                timeRefRowStatus,
                timeRefQualified,
                timeRefQualifiedChange,
                timeRefPropertiesUpdate,
                timeRefDeltaSec,
                timeRefDeltaNs,
                timeRefLeapSecSched,
                timeRefLeapSecValid,
                timeRefLeapSec
            }
    STATUS      current
    DESCRIPTION
        "The group of objects supporting management of the System Time
        Selection on the Nokia 7705 SAR series systems."
    ::= { aluSystemMIBGroups 3 }

aluSysTimeNotifyObjsV6v1Group  OBJECT-GROUP
    OBJECTS {   aluSystemNotifyTimeRefId,
                aluSystemNotifyTimeRefType
            }
    STATUS      current
    DESCRIPTION
        "The group of objects added in 6.1 release to support alu system
         notifications."
    ::= { aluSystemMIBGroups 4 }

aluSysTimeNotificationV6v1Group NOTIFICATION-GROUP
    NOTIFICATIONS {
        aluTimeRefCreated,
		aluTimeRefDeleted,
		aluTimeRefQualified,
		aluTimeRefDisqualified,
		aluTimeRefSelect
    }
    STATUS  current
    DESCRIPTION
        "The group of notifications supporting management of the
         System Time Reference Selection Nokia 7705."
    ::= { aluSystemMIBGroups 5 }

aluSysTimeReferenceV6v1Group  OBJECT-GROUP
    OBJECTS {   aluActiveTimeSourceType,
                aluActiveTimeSourceId,
                aluActiveTimeSourceChange,
                timeRefPriority,
                timeRefRowStatus,
                timeRefQualified,
                timeRefQualifiedChange,
                timeRefPropertiesUpdate,
                timeRefDeltaSec,
                timeRefDeltaNs,
                timeRefLeapSecSched,
                timeRefLeapSecUpdTime
            }
    STATUS      current
    DESCRIPTION
        "The group of objects supporting management of the System Time
        Source Selection in release 6.1 on the Nokia 7705 SAR series
        systems."
    ::= { aluSystemMIBGroups 6 }

aluSysTimeReferenceObsoleteGroup  OBJECT-GROUP
    OBJECTS { timeRefLeapSecValid,
              timeRefLeapSec
            }
    STATUS      current
    DESCRIPTION
        "The group of obsolete objects supporting management of the System Time
        Source Selection on the Nokia 7705 SAR series systems."
    ::= { aluSystemMIBGroups 7 }

aluSystemSptGroup  OBJECT-GROUP
    OBJECTS { aluSystemSptSecAggRate
            }
    STATUS      current
    DESCRIPTION
        "The group of objects supporting self proccessed traffic management of the
          Nokia 7705 SAR series systems."
    ::= { aluSystemMIBGroups 8 }


END
