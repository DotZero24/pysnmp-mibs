ALU-ATM-MIB DEFINITIONS ::= BEGIN

IMPORTS
        Integer32, MODULE-IDENTITY,
        OBJECT-TYPE, Counter32, Counter64,
        Unsigned32, NOTIFICATION-TYPE                 FROM SNMPv2-SMI

        RowStatus, TimeStamp, TEXTUAL-CONVENTION      FROM SNMPv2-TC

        MODULE-COMPLIANCE, OBJECT-GROUP,
        NOTIFICATION-GROUP                            FROM SNMPv2-CONF

        atmVclEntry, atmVplEntry, aal5VccEntry        FROM ATM-MIB

		tAtmIntfStatsEntry							  FROM TIMETRA-ATM-MIB

        aluSARMIBModules, aluSARObjs,
        aluSARNotifyPrefix, aluSARConfs               FROM ALU-SAR-GLOBAL-MIB
        ;

aluATMMIBModule MODULE-IDENTITY
        LAST-UPDATED    "0801180000Z"
        ORGANIZATION    "Nokia"
        CONTACT-INFO
            "Nokia 7x50 Support
             Web: http://www.nokia.com/comps/pages/carrier_support.jhtml"
        DESCRIPTION
        "This document is the SNMP MIB module to manage and provision extended
        ATM functionality for the Nokia 7705 SAR series devices.

        Copyright 2003-2014 Nokia. All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."
--
--  Revision History
--
        REVISION        "0801180000Z"
        DESCRIPTION     "Rev 1.0                18 Jan 2008 00:00
                         Initial version of the TIMETRA-ATM-MIB."

        ::= { aluSARMIBModules 4 }

--%%%%%%%%%%%%%%%%%%%%%%%%%%%%%%%%%%%%%%%%%%%%%%%%%%%%%%%%%%%%%%%%%%%%%%
--
--  Nokia 7705 SAR series ATM extensions
--

aluAtmObjs             OBJECT IDENTIFIER ::= { aluSARObjs 3 }
aluAtmMIBConformance   OBJECT IDENTIFIER ::= { aluSARConfs 3 }
aluAtmExtensionObjs   OBJECT IDENTIFIER ::= { aluAtmObjs 1 }

aluAtmNotifyPrefix    OBJECT IDENTIFIER ::= { aluSARNotifyPrefix 3 }


-- --------------------------------------------------------------------
--
--      ALU-ATM-MIB Textual Conventions
--


--
-- Nokia 7705 SAR series Extended ATM Interface Stats Table
--

aeTAtmIntfStatsTable OBJECT-TYPE
    SYNTAX      SEQUENCE OF AeTAtmIntfStatsEntry
    MAX-ACCESS  not-accessible
    STATUS      current
    DESCRIPTION
        "The aeTAtmIntfStatsTable contains additional ATM interface
         statistics at the ATM Layer."
    ::= { aluAtmExtensionObjs 1 }

aeTAtmIntfStatsEntry  OBJECT-TYPE
        SYNTAX          AeTAtmIntfStatsEntry
        MAX-ACCESS      not-accessible
        STATUS          current
        DESCRIPTION
            "An entry in the aeTAtmIntfStatsEntry containing additional
             statistics information applicable to an ATM interface."
        AUGMENTS { tAtmIntfStatsEntry }
        ::= { aeTAtmIntfStatsTable 1 }

    AeTAtmIntfStatsEntry ::=
        SEQUENCE {
          aeAtmIntfStatsTotalOamCellsRxd        Counter64,
          aeAtmIntfStatsTotalOamCellsTxd        Counter64
        }

    aeAtmIntfStatsTotalOamCellsRxd OBJECT-TYPE
        SYNTAX       Counter64
        MAX-ACCESS   read-only
        STATUS       current
        DESCRIPTION
           "The value of aeAtmIntfStatsTotalOamCellsRxd indicates
            the total number of OAM cells received by the ATM
            interface from the line."
    ::= { aeTAtmIntfStatsEntry 1 }

    aeAtmIntfStatsTotalOamCellsTxd OBJECT-TYPE
        SYNTAX       Counter64
        MAX-ACCESS   read-only
        STATUS       current
        DESCRIPTION
          "The value of aeAtmIntfStatsTotalOamCellsTxd indicates
            the total number of OAM cells transmitted out the ATM
            interface to the line."
    ::= { aeTAtmIntfStatsEntry 2 }

--
--  Nokia 7705 SAR series ATM Extended OAM Statistics Tables
--
aeTAtmOamVclStatisticsTable OBJECT-TYPE
    SYNTAX        SEQUENCE OF AeTAtmOamVclStatisticsEntry
    MAX-ACCESS    not-accessible
    STATUS        current
    DESCRIPTION
        "The aeTAtmOamVclStatisticsTable is used to gather the extended
         OAM statistics for Nokia 7705 SAR series devices on
         a particular VCL entry."
    ::= { aluAtmExtensionObjs 2 }

    aeTAtmOamVclStatisticsEntry OBJECT-TYPE
        SYNTAX        AeTAtmOamVclStatisticsEntry
        MAX-ACCESS    not-accessible
        STATUS        current
        DESCRIPTION
            "An entry in the aeTAtmOamVclStatisticsTable containing statistics
             information applicable to a particular VCL entry in the
             AToM MIB."
        AUGMENTS  { atmVclEntry }
        ::= { aeTAtmOamVclStatisticsTable 1 }

    AeTAtmOamVclStatisticsEntry ::=
        SEQUENCE {
           aeAtmVclStatsOamCellsGenerated       Counter32,
           aeAtmVclStatsOamCellsGeneratedTxd    Counter32
        }

   aeAtmVclStatsOamCellsGenerated OBJECT-TYPE
        SYNTAX       Counter32
        MAX-ACCESS   read-only
        STATUS       current
        DESCRIPTION
           "The value of aeAtmVclStatsOamCellsGenerated indicates the
            number of AIS cells generated on this VC towards the fabric."
        ::= { aeTAtmOamVclStatisticsEntry 1 }

   aeAtmVclStatsOamCellsGeneratedTxd OBJECT-TYPE
        SYNTAX       Counter32
        MAX-ACCESS   read-only
        STATUS       current
        DESCRIPTION
           "The value of aeAtmVclStatsOamCellsGeneratedTxd indicates the
            number of AIS cells generated on this VC towards the line."
        ::= { aeTAtmOamVclStatisticsEntry 2 }

aeTAtmOamVplStatisticsTable OBJECT-TYPE
    SYNTAX        SEQUENCE OF AeTAtmOamVplStatisticsEntry
    MAX-ACCESS    not-accessible
    STATUS        current
    DESCRIPTION
        "The aeTAtmOamVplStatisticsTable is used to gather the extended
         OAM statistics for Nokia 7705 SAR series devices on
         a particular VPL entry."
    ::= { aluAtmExtensionObjs 3 }

    aeTAtmOamVplStatisticsEntry OBJECT-TYPE
        SYNTAX        AeTAtmOamVplStatisticsEntry
        MAX-ACCESS    not-accessible
        STATUS        current
        DESCRIPTION
            "An entry in the aeTAtmOamVplStatisticsTable containing statistics
             information applicable to a particular VPL entry in the
             AToM MIB."
        AUGMENTS  { atmVplEntry }
         ::= { aeTAtmOamVplStatisticsTable 1 }

    AeTAtmOamVplStatisticsEntry ::=
        SEQUENCE {
           aeAtmVplStatsOamCellsGenerated     Counter32,
           aeAtmVplStatsOamCellsGeneratedTxd  Counter32
        }

   aeAtmVplStatsOamCellsGenerated OBJECT-TYPE
        SYNTAX       Counter32
        MAX-ACCESS   read-only
        STATUS       current
        DESCRIPTION
           "The value of aeAtmVplStatsOamCellsGenerated indicates the
            number of AIS cells generated on this VP towards the fabric."
        ::= { aeTAtmOamVplStatisticsEntry 1 }

   aeAtmVplStatsOamCellsGeneratedTxd OBJECT-TYPE
        SYNTAX       Counter32
        MAX-ACCESS   read-only
        STATUS       current
        DESCRIPTION
           "The value of aeAtmVplStatsOamCellsGeneratedTxd indicates the
            number of AIS cells generated on this VP towards the line."
        ::= { aeTAtmOamVplStatisticsEntry 2 }

--
--  Nokia 7705 SAR series PPP0E Relay Statistics Tables
--
aeAal5VccPppoERelayStatsTable OBJECT-TYPE
    SYNTAX        SEQUENCE OF AeAal5VccPppoERelayStatsEntry
    MAX-ACCESS    not-accessible
    STATUS        current
    DESCRIPTION
        "aeAal5VccPppoERelayStatsTable is used to gather PPPoE relay statistics
         on a particular AAL5 VCC entry."
    ::= { aluAtmExtensionObjs 4 }

    aeAal5VccPppoERelayStatsEntry OBJECT-TYPE
        SYNTAX        AeAal5VccPppoERelayStatsEntry
        MAX-ACCESS    not-accessible
        STATUS        current
        DESCRIPTION
            "An entry in the aeAal5VccPppoERelayStatsTable containing statistics
             information applicable to a particular AAL5 VCC entry."
        AUGMENTS { aal5VccEntry }
        ::= { aeAal5VccPppoERelayStatsTable 1 }

    AeAal5VccPppoERelayStatsEntry ::=
        SEQUENCE {
            aeAal5VccStatsPPPoERelayRxd          Counter64,
            aeAal5VccStatsPPPoERelayMalformed    Counter64,
            aeAal5VccStatsPPPoERelayOverflow     Counter64,
            aeAal5VccStatsPPPoERelayErrors       Counter64
        }

    aeAal5VccStatsPPPoERelayRxd OBJECT-TYPE
        SYNTAX       Counter64
        MAX-ACCESS   read-only
        STATUS       current
        DESCRIPTION
           "The value of aeAal5VccStatsPPPoERelayRxd indicates the
            total number of frames recieved with PPPoE discovery ethertype
            and PADI or PADR frame type."
        ::= { aeAal5VccPppoERelayStatsEntry 1 }

    aeAal5VccStatsPPPoERelayMalformed OBJECT-TYPE
        SYNTAX       Counter64
        MAX-ACCESS   read-only
        STATUS       current
        DESCRIPTION
           "The value of aeAal5VccStatsPPPoERelayMalformed indicates the
            number of frames discarded due to to TLV processing failure.
            (eg. malformed frames)"
        ::= { aeAal5VccPppoERelayStatsEntry 2 }

    aeAal5VccStatsPPPoERelayOverflow OBJECT-TYPE
        SYNTAX       Counter64
        MAX-ACCESS   read-only
        STATUS       current
        DESCRIPTION
           "The value of aeAal5VccStatsPPPoERelayOverflow indicates the
            number of frames discarded due to receiving more than
            1 frame/sec."
        ::= { aeAal5VccPppoERelayStatsEntry 3 }

    aeAal5VccStatsPPPoERelayErrors OBJECT-TYPE
        SYNTAX       Counter64
        MAX-ACCESS   read-only
        STATUS       current
        DESCRIPTION
           "The value of aeAal5VccStatsPPPoERelayErrors indicates the
            total number of frames discarded due to errors."
        ::= { aeAal5VccPppoERelayStatsEntry 4 }

--
-- Conformance Information
--
aluAtmMIBCompliances  OBJECT IDENTIFIER ::= { aluAtmMIBConformance 1 }
aluAtmMIBGroups      OBJECT IDENTIFIER ::= { aluAtmMIBConformance 2 }

-- compliance statements

aluAtmMIBCompliance  MODULE-COMPLIANCE
    STATUS  current
    DESCRIPTION
            "The compliance statement for revision 1.0 of ALU-ATM-MIB."
    MODULE  -- this module
        MANDATORY-GROUPS {
            aluExtAtmIntfOamStatsGroup,
            aluExtAtmVclVplOamStatsGroup
        }
    ::= { aluAtmMIBCompliances 1 }


-- units of conformance

aluExtAtmIntfOamStatsGroup     OBJECT-GROUP
    OBJECTS   {
           aeAtmIntfStatsTotalOamCellsRxd,
           aeAtmIntfStatsTotalOamCellsTxd
    }
    STATUS    current
    DESCRIPTION
        "The group of objects providing statistics access of
         additional OAM ATM interface statistics on Nokia
         7705 SAR series systems."
    ::= { aluAtmMIBGroups 1 }

aluExtAtmVclVplOamStatsGroup    OBJECT-GROUP
    OBJECTS   {
           aeAtmVclStatsOamCellsGenerated,
           aeAtmVplStatsOamCellsGenerated
    }
    STATUS    obsolete
    DESCRIPTION
        "The group of objects providing statistics access of
         additional OAM ATM statistics for VCs and VPs on
         Nokia 7705 SAR series systems."
    ::= { aluAtmMIBGroups 2 }

aluExtAtmVclVplOamStatsGroupV3v0    OBJECT-GROUP
    OBJECTS   {
           aeAtmVclStatsOamCellsGenerated,
           aeAtmVclStatsOamCellsGeneratedTxd,
           aeAtmVplStatsOamCellsGenerated,
           aeAtmVplStatsOamCellsGeneratedTxd
    }
    STATUS    current
    DESCRIPTION
        "The group of objects providing statistics access of
         additional OAM ATM statistics for VCs and VPs on
         Nokia 7705 SAR series systems."
    ::= { aluAtmMIBGroups 3 }

aeAal5VccPppoERelayStatsGroup    OBJECT-GROUP
    OBJECTS   {
           aeAal5VccStatsPPPoERelayRxd,
           aeAal5VccStatsPPPoERelayMalformed,
           aeAal5VccStatsPPPoERelayOverflow,
           aeAal5VccStatsPPPoERelayErrors
    }
    STATUS    current
    DESCRIPTION
        "The group of objects providing statistics access of
         additional AAL5 PPPoE Relay statistics for VCs on
         Nokia 7705 SAR series systems."
    ::= { aluAtmMIBGroups 4 }

END
