TIMETRA-SAS-SDP-MIB DEFINITIONS ::= BEGIN

IMPORTS
    MODULE-IDENTITY, OBJECT-TYPE,
    NOTIFICATION-TYPE, Gauge32,
    Integer32, Unsigned32, IpAddress,
    Counter64, Counter32                        FROM SNMPv2-SMI

    OBJECT-GROUP, NOTIFICATION-GROUP, MODULE-COMPLIANCE
                                                FROM SNMPv2-CONF

    RowStatus, MacAddress, TimeStamp, DisplayString,
    TruthValue FROM SNMPv2-TC

    timetraSASObjs, timetraSASNotifyPrefix,
    timetraSASConfs, timetraSASModules          FROM TIMETRA-SAS-GLOBAL-MIB

    tmnxSASServConformance                      FROM TIMETRA-SAS-SERV-MIB

    sdpBindEntry, sdpBindBaseStatsEntry                                FROM TIMETRA-SDP-MIB

    InetAddressType, InetAddress                FROM INET-ADDRESS-MIB

    ServiceAdminStatus, TmnxActionType,
    TmnxServId, TmnxCustId, TNamedItem, SdpBindId, TNamedItemOrEmpty,
    TmnxVRtrMplsLspID, TmnxOperState, TmnxIgmpVersion,
    TmnxEnabledDisabled, TItemDescription, TPolicyStatementNameOrEmpty,
    TmnxVPNRouteDistinguisher                   FROM TIMETRA-TC-MIB

    tmnxServObjs, tmnxServConformance, tmnxServNotifications, tmnxSvcObjs,
    custId, svcId, svcVpnId, tstpTraps,
    tmnxOtherBridgeId, tmnxCustomerBridgeId, tmnxCustomerRootBridgeId,
    tmnxOldSdpBindTlsStpPortState, svcTlsStpDesignatedRoot,
    tlsDhcpPacketProblem, svcDhcpLseStateNewCiAddr,
    svcDhcpLseStateNewChAddr, svcDhcpLseStateOldCiAddr,
    svcDhcpLseStateOldChAddr, svcDhcpClientLease, svcDhcpLseStatePopulateError,
    svcTlsMacMoveMaxRate, svcDhcpProxyError, svcDhcpCoAError,
    svcDhcpPacketProblem, svcDhcpSubAuthError,
    ServObjName, ServObjDesc,
    VpnId, SdpId, PWTemplateId,
    TlsLimitMacMoveLevel, TlsLimitMacMove, SdpBindVcType,
    StpExceptionCondition, LspIdList, BridgeId, TStpPortState,
    StpPortRole, StpProtocol, MvplsPruneState, TdmOptionsSigPkts,
    TdmOptionsCasTrunkFraming, SdpBFHundredthsOfPercent, SdpBindBandwidth,
    L2ptProtocols, ConfigStatus                 FROM TIMETRA-SERV-MIB

    timetraSRMIBModules                         FROM TIMETRA-GLOBAL-MIB

    TFilterID                                   FROM TIMETRA-FILTER-MIB
    tmnxChassisIndex, tmnxCardSlotNum,
    tmnxMDASlotNum                              FROM TIMETRA-CHASSIS-MIB;

timetraSASServicesSdpMIBModule   MODULE-IDENTITY
    LAST-UPDATED    "1102010000Z"
    ORGANIZATION    "Alcatel"
    CONTACT-INFO
        "Alcatel 7210 Support
         Web: http://www.alcatel.com/comps/pages/carrier_support.jhtml"
    DESCRIPTION
        "This  document  is the SNMP MIB module to manage and provision
        the various services of the Alcatel 7210 SR system.

        Copyright  2011-2013 Alcatel-Lucent. All rights reserved. Reproduction
        of  this  document  is  authorized  on  the  condition that the
        foregoing copyright notice is included.

        This   SNMP   MIB  module  (Specification)  embodies  Alcatel's
        proprietary  intellectual  property.  Alcatel retains all title
        and ownership in the Specification, including any revisions.

        Alcatel  grants  all interested parties a non-exclusive license
        to  use and distribute an unmodified copy of this Specification
        in  connection with management of Alcatel products, and without
        fee,  provided  this copyright notice and license appear on all
        copies.

        This  Specification  is  supplied `as is', and Alcatel makes no
        warranty,  either express or implied, as to the use, operation,
        condition, or performance of the Specification."

--
--  Revision History
--

    REVISION        "0710010000Z"
    DESCRIPTION     "Rev 1.0                01 FEB 2011 00:00
                     1.0 release of the TIMETRA-SAS-SDP-MIB from TIMETRA-SAS-SERV-MIB."

    ::= { timetraSASModules 12 }

-- --------------------------------------------------------------------
--      TIMETRA-SERV-MIB organisation
-- --------------------------------------------------------------------
tmnxSASSdpObjs             OBJECT IDENTIFIER ::= { timetraSASObjs 12 }

tmnxSASSdpConformance      OBJECT IDENTIFIER ::= { timetraSASConfs 13 }

-- -------------------------
-- SDP Bind Extension Table
-- -------------------------
sdpBindExtnTable OBJECT-TYPE
    SYNTAX          SEQUENCE OF SdpBindExtnEntry
    MAX-ACCESS      not-accessible
    STATUS          current
    DESCRIPTION     "This table extends the SDP binding information
                     available in sdpBindTable"
    ::= { tmnxSASSdpObjs 4 }

sdpBindExtnEntry OBJECT-TYPE
    SYNTAX          SdpBindExtnEntry
    MAX-ACCESS      not-accessible
    STATUS          current
    DESCRIPTION     "Information about a specific SDP binding."
    AUGMENTS   { sdpBindEntry }
    ::= { sdpBindExtnTable 1 }

SdpBindExtnEntry ::=
    SEQUENCE {
        sdpBindIngressExtraVlanTagDropCount   TruthValue
    }

sdpBindIngressExtraVlanTagDropCount   OBJECT-TYPE
    SYNTAX TruthValue
    MAX-ACCESS read-create
    STATUS current
    DESCRIPTION
        "When set to 'true', couting of extra tag dropped packet will be
         enabled, It will be set only for required SDP's"
    DEFVAL { false }
    ::= { sdpBindExtnEntry 1 }


-- ----------------------------------
-- SDP Bind Base stats Extension Table
-- ----------------------------------

sdpBindBaseStatsExtnTable OBJECT-TYPE
    SYNTAX          SEQUENCE OF SdpBindBaseStatsExtnEntry
    MAX-ACCESS      not-accessible
    STATUS          current
    DESCRIPTION     "This table extends the SDP binding stats information
                     available in sdpBindBaseStatsTable"
    ::= { tmnxSASSdpObjs 5 }

 sdpBindBaseStatsExtnEntry OBJECT-TYPE
    SYNTAX          SdpBindBaseStatsExtnEntry
    MAX-ACCESS      not-accessible
    STATUS          current
    DESCRIPTION     "Basic statistics about a specific SDP binding."
    AUGMENTS   { sdpBindBaseStatsEntry }
    ::= { sdpBindBaseStatsExtnTable 1 }

SdpBindBaseStatsExtnEntry ::=
    SEQUENCE {
         sdpBindIngressExtraVlanTagDroppedPackets      Counter64,
         sdpBindIngressExtraVlanTagDroppedOctets        Counter64
         }

sdpBindIngressExtraVlanTagDroppedPackets   OBJECT-TYPE
    SYNTAX Counter64
    MAX-ACCESS read-only
    STATUS current
    DESCRIPTION
        "Counter to track of extra v-lan tag dropped packets"
    ::= { sdpBindBaseStatsExtnEntry 1 }

sdpBindIngressExtraVlanTagDroppedOctets   OBJECT-TYPE
    SYNTAX Counter64
    MAX-ACCESS read-only
    STATUS current
    DESCRIPTION
        "Counter to track of extra v-lan tag dropped octets"
    ::= { sdpBindBaseStatsExtnEntry 2 }

-- ----------------------------------------------------------------------------
-- Conformance Information
-- ----------------------------------------------------------------------------
tmnxSASSdpCompliances  OBJECT IDENTIFIER ::= { tmnxSASSdpConformance 1 }
tmnxSASSdpGroups       OBJECT IDENTIFIER ::= { tmnxSASSdpConformance 2 }

-- ----------------------------------------------
-- Compliance Statements
-- ----------------------------------------------

tmnxSASSdp7210V3v0Compliance MODULE-COMPLIANCE
    STATUS  current
    DESCRIPTION
        "The compliance statement for management of services SDPs
         on Alcatel 7210 series systems."
    MODULE  -- this module
        MANDATORY-GROUPS
        {
             tmnxSASSdpV3v0Group
        }
    ::= { tmnxSASSdpCompliances 1 }


tmnxSASSdpV3v0Group OBJECT-GROUP
    OBJECTS {
      sdpBindIngressExtraVlanTagDropCount,
      sdpBindIngressExtraVlanTagDroppedPackets,
      sdpBindIngressExtraVlanTagDroppedOctets
    }
    STATUS      current
    DESCRIPTION
        "he  group  of objects supporting SDP base feature
         on Alcatel-Lucent 7210 series systems."
    ::= { tmnxSASSdpGroups 1 }


END
