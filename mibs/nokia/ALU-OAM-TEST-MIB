ALU-OAM-TEST-MIB DEFINITIONS ::= BEGIN

IMPORTS
        MODULE-IDENTITY, OBJECT-TYPE, NOTIFICATION-TYPE, IpAddress,
        Integer32, Unsigned32, Gauge32, Counter32, Counter64
            FROM SNMPv2-SMI

        MODULE-COMPLIANCE, OBJECT-GROUP, NOTIFICATION-GROUP
            FROM SNMPv2-CONF

        TEXTUAL-CONVENTION, RowStatus, StorageType, TruthValue,
        DateAndTime, MacAddress, TimeStamp, DisplayString
            FROM SNMPv2-TC

        SnmpAdminString
            FROM SNMP-FRAMEWORK-MIB

        InetAddressType, InetAddress, InetAddressPrefixLength
            FROM INET-ADDRESS-MIB

        InterfaceIndex, InterfaceIndexOrZero
            FROM IF-MIB

        -- Alphasort
        IpAddressPrefixLength, SdpBindId, TFCName, TItemDescription,
        TLNamedItemOrEmpty, TNamedItemOrEmpty, TPolicyStatementNameOrEmpty,
        TProfile, TmnxAdminState, TmnxBgpRouteTarget, TmnxEncapVal, TmnxPortID,
        TmnxPwGlobalIdOrZero, TmnxServId, TmnxSpokeSdpIdOrZero, TmnxStrSapId,
        TmnxTunnelID, TmnxTunnelType, TmnxVPNRouteDistinguisher, TmnxVRtrID,
        TmnxVcId, TmnxVcIdOrNone, TDSCPNameOrEmpty, TNamedItem, Dot1PPriority
            FROM TIMETRA-TC-MIB

        timetraSRMIBModules, tmnxSRObjs,
        tmnxSRNotifyPrefix, tmnxSRConfs
            FROM TIMETRA-GLOBAL-MIB

--     timetraSASObjs, timetraSASNotifyPrefix,
--     timetraSASConfs, timetraSASModules
--          FROM TIMETRA-SAS-GLOBAL-MIB

       aluSARObjs, aluSARNotifyPrefix,
       aluSARConfs, aluSARMIBModules
            FROM ALU-SAR-GLOBAL-MIB

       InetAddressPrefixLength,
       InetAddressIPv6,
       InetAddressType, InetAddress
           FROM INET-ADDRESS-MIB

       svcId
               FROM TIMETRA-SERV-MIB

       sapPortId, sapEncapValue
               FROM TIMETRA-SAP-MIB

       tmnxOamPingCtlEntry
               FROM TIMETRA-OAM-TEST-MIB
        ;

aluOamTestMIBModule MODULE-IDENTITY
        LAST-UPDATED "201102010000Z"
        ORGANIZATION "Nokia"
        CONTACT-INFO
            "Nokia SROS Support
             Web: http://support.nokia.com"

        DESCRIPTION
        "This document is the SNMP MIB module to manage and provision the
        Nokia SROS OAM tests.

        Copyright 2013-2015 Nokia.  All rights reserved.
        Reproduction of this document is authorized on the condition that
        the foregoing copyright notice is included.

        This SNMP MIB module (Specification) embodies Nokia's
        proprietary intellectual property.  Nokia retains
        all title and ownership in the Specification, including any
        revisions.

        Nokia grants all interested parties a non-exclusive
        license to use and distribute an unmodified copy of this
        Specification in connection with management of Nokia
        products, and without fee, provided this copyright notice and
        license appear on all copies.

        This Specification is supplied 'as is', and Nokia
        makes no warranty, either express or implied, as to the use,
        operation, condition, or performance of the Specification."
--
--  Revision History
--
        REVISION        "1210010000Z"
        DESCRIPTION     "Rev 1.0                1 Nov 2012 00:00
                         7.0 release of the ALU-OAM-TEST-MIB."

        ::= { aluSARMIBModules 19 }


aluOamTestObjs         OBJECT IDENTIFIER ::= { aluSARObjs 21 }
    tmnxTestHdProfObjects                     OBJECT IDENTIFIER
        ::= { aluOamTestObjs 1 }
    tmnxTestHdProfNotifyObjs                  OBJECT IDENTIFIER
        ::= { aluOamTestObjs 2 }
    tmnxTestHdObjects                         OBJECT IDENTIFIER
        ::= { aluOamTestObjs 3 }

aluOamNotifyPrefix    OBJECT IDENTIFIER ::= { aluSARNotifyPrefix 17 }
    aluOamNotifications   OBJECT IDENTIFIER ::= { aluOamNotifyPrefix 1 }


aluOamTestConformance          OBJECT IDENTIFIER ::= { aluSARConfs 21 }
    tmnxTestHdProfConformance              OBJECT IDENTIFIER
        ::= { aluOamTestConformance 1 }
    tmnxTestHdObjsGroups           OBJECT IDENTIFIER
        ::= { tmnxTestHdProfConformance 1 }
    aluOamPingGroups               OBJECT IDENTIFIER
        ::= { aluOamTestConformance 2 }

--

TTestHdCIRRate ::= TEXTUAL-CONVENTION
    STATUS       current
    DESCRIPTION
        "The rate to be used in kbps. "
    SYNTAX       INTEGER (0 | 10..10000000)

TTestHdPIRRate ::= TEXTUAL-CONVENTION
    STATUS       current
    DESCRIPTION
        "The rate to be used in kbps. The value -1 means pir rate not used."
    SYNTAX       INTEGER (-1 | 10..10000000)

--

tmnxTestHdProfTable OBJECT-TYPE
    SYNTAX       SEQUENCE OF TmnxTestHdProfEntry
    MAX-ACCESS   not-accessible
    STATUS       current
    DESCRIPTION  "  "
    ::= { tmnxTestHdProfObjects 1 }

tmnxTestHdProfEntry OBJECT-TYPE
    SYNTAX       TmnxTestHdProfEntry
    MAX-ACCESS   not-accessible
    STATUS       current
    DESCRIPTION
        ""
    INDEX { tmnxTestHdProfIndex }
    ::= { tmnxTestHdProfTable 1 }

TmnxTestHdProfEntry ::= SEQUENCE
    {
        tmnxTestHdProfIndex                 INTEGER,
        tmnxTestHdProfRowStatus             RowStatus,
        tmnxTestHdProfDescription           TItemDescription,
        tmnxTestHdProfDurHr                 Integer32,
        tmnxTestHdProfDurMin                Integer32,
        tmnxTestHdProfDurSec                Integer32,
        tmnxTestHdProfTrapEnable            TruthValue,
        tmnxTestHdLastChanged               TimeStamp,
        tmnxTestHdProfAdminCIR              TTestHdCIRRate,
        tmnxTestHdProfAdminPIR              TTestHdPIRRate,
        tmnxTestHdProfActiveTests           OCTET STRING,
        tmnxTestHdProfCompetedTests         OCTET STRING
    }

tmnxTestHdProfIndex OBJECT-TYPE
    SYNTAX       INTEGER (0..32)
    MAX-ACCESS   accessible-for-notify
    STATUS       current
    DESCRIPTION
        "tmnxTestHdProfIndex profile index for this entry"
    ::= { tmnxTestHdProfEntry 1 }

tmnxTestHdProfRowStatus OBJECT-TYPE
    SYNTAX       RowStatus
    MAX-ACCESS   read-create
    STATUS       current
    DESCRIPTION
        "RowStatus for this entry"
    ::= { tmnxTestHdProfEntry 2 }

tmnxTestHdProfDescription OBJECT-TYPE
    SYNTAX       TItemDescription
    MAX-ACCESS   read-create
    STATUS       current
    DESCRIPTION
        "user description for this profile"
    DEFVAL { ''H }
    ::= { tmnxTestHdProfEntry 3 }

tmnxTestHdProfDurHr  OBJECT-TYPE
    SYNTAX      Integer32 (0..24)
    UNITS       "hours"
    MAX-ACCESS  read-create
    STATUS      current
    DESCRIPTION
        "tmnxTestHdProfDurHr is the number of hours the test head
        test to be run"
    DEFVAL { 0 }
    ::= { tmnxTestHdProfEntry 4 }

tmnxTestHdProfDurMin  OBJECT-TYPE
    SYNTAX      Integer32 (0..60)
    UNITS       "minutes"
    MAX-ACCESS  read-create
    STATUS      current
    DESCRIPTION
        "tmnxTestHdProfDurMin is the number of minutes the test head
        test to be run"
    DEFVAL { 2 }
    ::= { tmnxTestHdProfEntry 5 }

tmnxTestHdProfDurSec  OBJECT-TYPE
    SYNTAX      Integer32 (0..60)
    UNITS       "seconds"
    MAX-ACCESS  read-create
    STATUS      current
    DESCRIPTION
        "tmnxTestHdProfDurSec is the number of seconds the test head
        test to be run"
    DEFVAL { 0 }
    ::= { tmnxTestHdProfEntry 6 }

tmnxTestHdProfTrapEnable OBJECT-TYPE
    SYNTAX       TruthValue
    MAX-ACCESS   read-create
    STATUS       current
    DESCRIPTION
        "tmnxTestHdProfTrapEnable when set to true tmnxOamTestHeadTestCompleted
        trap will be sent when the test run completes."
    DEFVAL { false }
    ::= { tmnxTestHdProfEntry 7 }

tmnxTestHdLastChanged OBJECT-TYPE
    SYNTAX       TimeStamp
    MAX-ACCESS   read-only
    STATUS       current
    DESCRIPTION
        "The value tmnxTestHdLastChanged indicates the system uptime when
        an entry in tmnxTestHdProfTable was last changed."
    ::= { tmnxTestHdProfEntry 8 }

tmnxTestHdProfAdminCIR OBJECT-TYPE
    SYNTAX       TTestHdCIRRate
    MAX-ACCESS   read-create
    STATUS       current
    DESCRIPTION
        "admin cir to be used in the payload"
    DEFVAL { 1000 }
    ::= { tmnxTestHdProfEntry 9 }


tmnxTestHdProfAdminPIR OBJECT-TYPE
    SYNTAX       TTestHdPIRRate
    MAX-ACCESS   read-create
    STATUS       current
    DESCRIPTION
        "admin pir to be used in the payload"
    DEFVAL { -1 }
    ::= { tmnxTestHdProfEntry 10 }

tmnxTestHdProfActiveTests OBJECT-TYPE
    SYNTAX       OCTET STRING
    MAX-ACCESS   read-only
    STATUS       current
    DESCRIPTION
        "Active tests that are using this profile
        "
    ::= { tmnxTestHdProfEntry 11 }

tmnxTestHdProfCompetedTests OBJECT-TYPE
    SYNTAX       OCTET STRING
    MAX-ACCESS   read-only
    STATUS       current
    DESCRIPTION
        "Completed tests that have used this profile
        "
    ::= { tmnxTestHdProfEntry 12 }

--

tmnxTestHdPayLdTable OBJECT-TYPE
    SYNTAX       SEQUENCE OF TmnxTestHdPayLdEntry
    MAX-ACCESS   not-accessible
    STATUS       current
    DESCRIPTION
        "This table maintains information of frame-payload which can be
         used for testhead test sessions."
    ::= { tmnxTestHdProfObjects 2 }

tmnxTestHdPayLdEntry OBJECT-TYPE
    SYNTAX       TmnxTestHdPayLdEntry
    MAX-ACCESS   not-accessible
    STATUS       current
    DESCRIPTION
        "Information about a particular frame-payload.

         Entries are created and deleted by user. They have
         a presumed StorageType of nonVolatile."
    INDEX { tmnxTestHdProfIndex, tmnxTestHdPayLdIndex }
    ::= { tmnxTestHdPayLdTable 1 }

TmnxTestHdPayLdEntry ::= SEQUENCE
    {
        tmnxTestHdPayLdIndex             INTEGER,
        tmnxTestHdPayLdRowStatus         RowStatus,
        tmnxTestHdPayLdDesc              TItemDescription,
        tmnxTestHdPayLddataPattrn        OCTET STRING,
        tmnxTestHdPayLdSrcIpv4Addr       IpAddress,
        tmnxTestHdPayLdDstIpv4Addr       IpAddress,
        tmnxTestHdPayLdDSCP              TDSCPNameOrEmpty,
        tmnxTestHdPayLdIpProto           INTEGER,
        tmnxTestHdPayLdIpTos             INTEGER,
        tmnxTestHdPayLdIpTTL             INTEGER,
        tmnxTestHdPayLdSrcMac            MacAddress,
        tmnxTestHdPayLdDstMac            MacAddress,
        tmnxTestHdPayLdSrcPort           INTEGER,
        tmnxTestHdPayLdDstPort           INTEGER,
        tmnxTestHdPayLdLastChanged       TimeStamp,
        tmnxTestHdPayLdType              INTEGER,
        tmnxTestHdPayLdVTagOne           Integer32,
        tmnxTestHdPayLdVTagOneTpid       Unsigned32,
        tmnxTestHdPayLdVTagOneDot1p      Dot1PPriority,
        tmnxTestHdPayLdVTagTwo           Integer32,
        tmnxTestHdPayLdVTagTwoTpid       Unsigned32,
        tmnxTestHdPayLdVTagTwoDot1p      Dot1PPriority,
        tmnxTestHdPayLdEthertype         Unsigned32,
        tmnxTestHdPayLdVTagOneDei        Unsigned32,
        tmnxTestHdPayLdVTagTwoDei        Unsigned32,
        tmnxTestHdPayLdFrameSize         INTEGER,
        tmnxTestHdPayLdRate              INTEGER
    }

tmnxTestHdPayLdIndex OBJECT-TYPE
    SYNTAX       INTEGER (1..8)
    MAX-ACCESS   accessible-for-notify
    STATUS       current
    DESCRIPTION
        "tmnxTestHdPayLdIndex is the payload index"
    ::= { tmnxTestHdPayLdEntry 1 }

tmnxTestHdPayLdRowStatus OBJECT-TYPE
    SYNTAX       RowStatus
    MAX-ACCESS   read-create
    STATUS       current
    DESCRIPTION
        "Row Status for this entry."
    ::= { tmnxTestHdPayLdEntry 2 }

tmnxTestHdPayLdDesc OBJECT-TYPE
    SYNTAX       TItemDescription
    MAX-ACCESS   read-create
    STATUS       current
    DESCRIPTION "tmnxTestHdPayLdDesc is the textual description
                entered by user for this payload"
    DEFVAL { ''H }
    ::= { tmnxTestHdPayLdEntry 3 }

tmnxTestHdPayLddataPattrn OBJECT-TYPE
    SYNTAX       OCTET STRING (SIZE (0..64))
    MAX-ACCESS   read-create
    STATUS       current
    DESCRIPTION
        "tmnxTestHdPayLddataPattrn is hex string of characters 0-9,a-f
        It is used to fill up the data field of the payload of the frame,
        repeating it in the payload field as many time as need to fill
        up the entire length of the payload.

        Note: if non hex string is set from snmp, it will be converted
        to hex for corresponding characters."
    DEFVAL { "a1b2c3d4e5f6" }
    ::= { tmnxTestHdPayLdEntry 4 }

tmnxTestHdPayLdSrcIpv4Addr  OBJECT-TYPE
    SYNTAX      IpAddress
    MAX-ACCESS  read-create
    STATUS      current
    DESCRIPTION
        "tmnxTestHdPayLdSrcIpv4Addr is the source ip address to be used
        in frame payload"
    DEFVAL { 0 }
    ::= { tmnxTestHdPayLdEntry 5 }


tmnxTestHdPayLdDstIpv4Addr  OBJECT-TYPE
    SYNTAX      IpAddress
    MAX-ACCESS  read-create
    STATUS      current
    DESCRIPTION
        "tmnxTestHdPayLdDstIpv4Addr is the destination ip address to be used
        in frame payload"
    DEFVAL { 0 }
    ::= { tmnxTestHdPayLdEntry 6 }


tmnxTestHdPayLdDSCP OBJECT-TYPE
    SYNTAX       TDSCPNameOrEmpty
    MAX-ACCESS   read-create
    STATUS       current
    DESCRIPTION
        "tmnxTestHdPayLdDSCP is the dscp value  to be used in frame payload"
    DEFVAL { "be" }
    ::= { tmnxTestHdPayLdEntry 7 }

tmnxTestHdPayLdIpProto OBJECT-TYPE
    SYNTAX       INTEGER (0..255)
    MAX-ACCESS   read-create
    STATUS       current
    DESCRIPTION
        "tmnxTestHdPayLdIpProto is the ip protocal value  to be used in frame
        payload"
    DEFVAL { 0 }
    ::= { tmnxTestHdPayLdEntry 8 }

tmnxTestHdPayLdIpTos OBJECT-TYPE
    SYNTAX       INTEGER (0..255)
    MAX-ACCESS   read-create
    STATUS       current
    DESCRIPTION
        "tmnxTestHdPayLdIpTos is the ip type of service value  to be used in frame
        payload"
    DEFVAL { 0 }
    ::= { tmnxTestHdPayLdEntry 9 }

tmnxTestHdPayLdIpTTL OBJECT-TYPE
    SYNTAX       INTEGER (1..255)
    MAX-ACCESS   read-create
    STATUS       current
    DESCRIPTION
        "tmnxTestHdPayLdIpTTL is the ip time to live value  to be used in frame
        payload"
    DEFVAL { 255 }
    ::= { tmnxTestHdPayLdEntry 10 }

tmnxTestHdPayLdSrcMac OBJECT-TYPE
    SYNTAX          MacAddress
    MAX-ACCESS      read-create
    STATUS          current
    DESCRIPTION
        "Source MAC to be used in the frame payload."
    DEFVAL { '000000000000'H }
    ::= { tmnxTestHdPayLdEntry 11 }


tmnxTestHdPayLdDstMac OBJECT-TYPE
    SYNTAX          MacAddress
    MAX-ACCESS      read-create
    STATUS          current
    DESCRIPTION
        "Destination MAC to be used in the frame payload."
    DEFVAL { '000000000000'H }
    ::= { tmnxTestHdPayLdEntry 12 }

tmnxTestHdPayLdSrcPort OBJECT-TYPE
    SYNTAX          INTEGER(0..65535)
    MAX-ACCESS      read-create
    STATUS          current
    DESCRIPTION
        "Source Port to be used in the frame payload."
    DEFVAL { 0 }
    ::= { tmnxTestHdPayLdEntry 13 }


tmnxTestHdPayLdDstPort OBJECT-TYPE
    SYNTAX          INTEGER(0..65535)
    MAX-ACCESS      read-create
    STATUS          current
    DESCRIPTION
        "Destination Port to be used in the frame payload."
    DEFVAL { 0 }
    ::= { tmnxTestHdPayLdEntry 14 }

tmnxTestHdPayLdLastChanged OBJECT-TYPE
    SYNTAX       TimeStamp
    MAX-ACCESS   read-only
    STATUS       current
    DESCRIPTION
        "The value tmnxTestHdPayLdLastChanged indicates the system
        uptime when an entry in tmnxTestHdPayLdTable was last changed."
    ::= { tmnxTestHdPayLdEntry 15 }

tmnxTestHdPayLdType OBJECT-TYPE
    SYNTAX       INTEGER {
                          tcp-ipv4 (1),
                          l2 (2),
                          udp-ipv4 (3),
                          ipv4 (4)
                        }
    MAX-ACCESS   read-create
    STATUS       current
    DESCRIPTION
        "tmnxTestHdPayLdType indicates the payload type for
        this frame payload."
    DEFVAL { tcp-ipv4 }
    ::= { tmnxTestHdPayLdEntry 16 }

tmnxTestHdPayLdVTagOne  OBJECT-TYPE
    SYNTAX      Integer32 (-1..4094)
    MAX-ACCESS  read-create
    STATUS      current
    DESCRIPTION
        "Vlan tag one to be used in payload , if set to -1 packets are sent out without
         vlan tag"
    DEFVAL { -1 }
    ::= { tmnxTestHdPayLdEntry 17 }

tmnxTestHdPayLdVTagOneTpid         OBJECT-TYPE
    SYNTAX      Unsigned32 ('600'H..'ffff'H)
    MAX-ACCESS  read-create
    STATUS      current
    DESCRIPTION
        "The tmnxTestHdPayLdVTagOneTpid variable indicates the ethertype to be set
        in the payload."
    DEFVAL { '8100'H }
    ::= { tmnxTestHdPayLdEntry 18 }

tmnxTestHdPayLdVTagOneDot1p OBJECT-TYPE
    SYNTAX          Dot1PPriority
    MAX-ACCESS      read-create
    STATUS          current
    DESCRIPTION
         "IEEE 802.1p priority value for this frame payload.
         "
    DEFVAL { 0 }
    ::= { tmnxTestHdPayLdEntry 19 }

tmnxTestHdPayLdVTagTwo  OBJECT-TYPE
    SYNTAX      Integer32 (-1..4094)
    MAX-ACCESS  read-create
    STATUS      current
    DESCRIPTION
        "Vlan tag two to be used in payload , if set to -1 packets are sent out without
         vlan tag"
    DEFVAL { -1 }
    ::= { tmnxTestHdPayLdEntry 20 }

tmnxTestHdPayLdVTagTwoTpid         OBJECT-TYPE
    SYNTAX      Unsigned32 ('600'H..'ffff'H)
    MAX-ACCESS  read-create
    STATUS      current
    DESCRIPTION
        "The tmnxTestHdPayLdVTagTwoTpid variable indicates the ethertype to be set
        in the payload."
    DEFVAL { '8100'H }
    ::= { tmnxTestHdPayLdEntry 21 }

tmnxTestHdPayLdVTagTwoDot1p OBJECT-TYPE
    SYNTAX          Dot1PPriority
    MAX-ACCESS      read-create
    STATUS          current
    DESCRIPTION
         "IEEE 802.1p priority value for this frame payload.
         "
    DEFVAL { 0 }
    ::= { tmnxTestHdPayLdEntry 22 }

tmnxTestHdPayLdEthertype         OBJECT-TYPE
    SYNTAX      Unsigned32 ('600'H..'ffff'H)
    MAX-ACCESS  read-create
    STATUS      current
    DESCRIPTION
        "The tmnxTestHdPayLdEthertype variable indicates the ethertype to be set
        in the payload. For L2, it should be 0xffff."
    DEFVAL { '800'H }
    ::= { tmnxTestHdPayLdEntry 23 }

tmnxTestHdPayLdVTagOneDei OBJECT-TYPE
    SYNTAX     Unsigned32(0|1)
    MAX-ACCESS  read-create
    STATUS      current
    DESCRIPTION
       "tmnxTestHdPayLdVTagOneDei can have value one or zero."
    DEFVAL { 0 }
    ::= { tmnxTestHdPayLdEntry 24 }


tmnxTestHdPayLdVTagTwoDei OBJECT-TYPE
    SYNTAX      Unsigned32 (0|1)
    MAX-ACCESS  read-create
    STATUS      current
    DESCRIPTION
    "tmnxTestHdPayLdVTagTwoDei can have value one or zero."
    DEFVAL { 0 }
    ::= { tmnxTestHdPayLdEntry 25 }

tmnxTestHdPayLdFrameSize OBJECT-TYPE
    SYNTAX      INTEGER (64..9732)
    MAX-ACCESS  read-create
    STATUS      current
    DESCRIPTION
        "tmnxTestHdPayLdFrameSize is the frame size to be used in the frame
        payload"
    DEFVAL { 1514 }
    ::= { tmnxTestHdPayLdEntry 26 }

tmnxTestHdPayLdRate OBJECT-TYPE
    SYNTAX       INTEGER (10..1000000)
    MAX-ACCESS   read-create
    STATUS       current
    DESCRIPTION
        "rate to be used in the payload"
    DEFVAL { 1000 }
    ::= { tmnxTestHdPayLdEntry 27 }

tmnxTestHdAccCritTable OBJECT-TYPE
    SYNTAX       SEQUENCE OF TmnxTestHdAccCritEntry
    MAX-ACCESS   not-accessible
    STATUS       current
    DESCRIPTION
        "This table maintains information about acceptance criteria which can be
         used by testhead test sessions."
    ::= { tmnxTestHdProfObjects 3 }

tmnxTestHdAccCritEntry OBJECT-TYPE
    SYNTAX       TmnxTestHdAccCritEntry
    MAX-ACCESS   not-accessible
    STATUS       current
    DESCRIPTION
        "Information about a particular acceptance criteria.

         Entries are created and deleted by user. They have
         a presumed StorageType of nonVolatile."
    INDEX { tmnxTestHdProfIndex, tmnxTestHdAccCritIndex }
    ::= { tmnxTestHdAccCritTable 1 }

TmnxTestHdAccCritEntry ::= SEQUENCE
    {
        tmnxTestHdAccCritIndex             INTEGER,
        tmnxTestHdAccCritRowStatus         RowStatus,
        tmnxTestHdAccCritJittrRiseThres    INTEGER,
        tmnxTestHdAccCritLatRiseThres      INTEGER,
        tmnxTestHdAccCritLossRiseThres     INTEGER,
        tmnxTestHdAccCritLastChanged       TimeStamp,
        tmnxTestHdAccCritLossRiseThresIn   INTEGER,
        tmnxTestHdAccCritLossRiseThresOut  INTEGER,
        tmnxTestHdAccCritCirThres          INTEGER,
        tmnxTestHdAccCritPirThres          INTEGER,
        tmnxTestHdAccCritLatRiseThresIn    INTEGER,
        tmnxTestHdAccCritLatRiseThresOut   INTEGER,
        tmnxTestHdAccCritJittrRiseThresIn  INTEGER,
        tmnxTestHdAccCritJittrRiseThresOut INTEGER
     }

tmnxTestHdAccCritIndex OBJECT-TYPE
    SYNTAX       INTEGER (1..8)
    MAX-ACCESS   accessible-for-notify
    STATUS       current
    DESCRIPTION
        ""
    ::= { tmnxTestHdAccCritEntry 1 }

tmnxTestHdAccCritRowStatus OBJECT-TYPE
    SYNTAX       RowStatus
    MAX-ACCESS   read-create
    STATUS       current
    DESCRIPTION
        "Row Status for this entry."
    ::= { tmnxTestHdAccCritEntry 2 }

tmnxTestHdAccCritJittrRiseThres OBJECT-TYPE
    SYNTAX      INTEGER (-1 | 0..2147483000)
    UNITS       "microseconds"
    MAX-ACCESS   read-create
    STATUS       current
    DESCRIPTION
        "tmnxTestHdAccCritJittrRiseThres is the acceptance criteria
        jitter rising threshold to be used for test run"
    DEFVAL { -1 }
    ::= { tmnxTestHdAccCritEntry 3 }

tmnxTestHdAccCritLatRiseThres OBJECT-TYPE
    SYNTAX      INTEGER (-1 | 0..2147483000)
    UNITS       "microseconds"
    MAX-ACCESS   read-create
    STATUS       current
    DESCRIPTION
        "tmnxTestHdAccCritLatRiseThres is the acceptance criteria
        latency rising threshold to be used for test run"
    DEFVAL { -1 }
    ::= { tmnxTestHdAccCritEntry 4 }

tmnxTestHdAccCritLossRiseThres OBJECT-TYPE
    SYNTAX      INTEGER (-1 | 0..1000000)
    UNITS       "10000 of a percent"
    MAX-ACCESS   read-create
    STATUS       current
    DESCRIPTION
        "tmnxTestHdAccCritLossRiseThres is the acceptance criteria
        loss rising threshold to be used for test run"
    DEFVAL { -1 }
    ::= { tmnxTestHdAccCritEntry 5 }

tmnxTestHdAccCritLastChanged OBJECT-TYPE
    SYNTAX       TimeStamp
    MAX-ACCESS   read-only
    STATUS       current
    DESCRIPTION
        "The value tmnxTestHdAccCritLastChanged indicates the system
        uptime when an entry in tmnxTestHdAccCritTable was last changed."
    ::= { tmnxTestHdAccCritEntry 6 }

tmnxTestHdAccCritLossRiseThresIn OBJECT-TYPE
    SYNTAX      INTEGER (-1 | 0..1000000)
    UNITS       "10000of a percent"
    MAX-ACCESS   read-create
    STATUS       current
    DESCRIPTION
        "tmnxTestHdAccCritLossRiseThresIn is the acceptance criteria
        loss rising threshold in to be used for test run"
    DEFVAL { -1 }
    ::= { tmnxTestHdAccCritEntry 7 }

tmnxTestHdAccCritLossRiseThresOut OBJECT-TYPE
    SYNTAX      INTEGER (-1 | 0..1000000)
    UNITS       "10000of a percent"
    MAX-ACCESS   read-create
    STATUS       current
    DESCRIPTION
        "tmnxTestHdAccCritLossRiseThresOut is the acceptance criteria
        out loss rising threshold to be used for test run"
    DEFVAL { -1 }
    ::= { tmnxTestHdAccCritEntry 8 }

tmnxTestHdAccCritCirThres OBJECT-TYPE
    SYNTAX      INTEGER (-1 | 0..1000000)
    MAX-ACCESS   read-create
    STATUS       current
    DESCRIPTION
        "tmnxTestHdAccCritCirThres is the acceptance criteria
        cir threshold to be used for test run"
    DEFVAL { -1 }
    ::= { tmnxTestHdAccCritEntry 9 }

tmnxTestHdAccCritPirThres OBJECT-TYPE
    SYNTAX      INTEGER (-1 | 0..1000000)
    MAX-ACCESS   read-create
    STATUS       current
    DESCRIPTION
        "tmnxTestHdAccCritPirThres is the acceptance criteria
        pir threshold to be used for test run"
    DEFVAL { -1 }
    ::= { tmnxTestHdAccCritEntry 10 }

tmnxTestHdAccCritLatRiseThresIn OBJECT-TYPE
    SYNTAX      INTEGER (-1 | 0..2147483000)
    UNITS       "microseconds"
    MAX-ACCESS   read-create
    STATUS       current
    DESCRIPTION
        "tmnxTestHdAccCritLatRiseThresIn is the acceptance criteria
        latency rising threshold-in to be used for test run"
    DEFVAL { -1 }
    ::= { tmnxTestHdAccCritEntry 11 }

tmnxTestHdAccCritLatRiseThresOut OBJECT-TYPE
    SYNTAX      INTEGER (-1 | 0..2147483000)
    UNITS       "microseconds"
    MAX-ACCESS   read-create
    STATUS       current
    DESCRIPTION
        "tmnxTestHdAccCritLatRiseThresOut is the acceptance criteria
        latency rising threshold out to be used for test run"
    DEFVAL { -1 }
    ::= { tmnxTestHdAccCritEntry 12 }

tmnxTestHdAccCritJittrRiseThresIn OBJECT-TYPE
    SYNTAX      INTEGER (-1 | 0..2147483000)
    UNITS       "microseconds"
    MAX-ACCESS   read-create
    STATUS       current
    DESCRIPTION
        "tmnxTestHdAccCritJittrRiseThresIn is the acceptance criteria
        jitter rising threshold-in to be used for test run"
    DEFVAL { -1 }
    ::= { tmnxTestHdAccCritEntry 13 }

tmnxTestHdAccCritJittrRiseThresOut OBJECT-TYPE
    SYNTAX      INTEGER (-1 | 0..2147483000)
    UNITS       "microseconds"
    MAX-ACCESS   read-create
    STATUS       current
    DESCRIPTION
        "tmnxTestHdAccCritJittrRiseThresOut is the acceptance criteria
        jitter rising threshold-out to be used for test run"
    DEFVAL { -1 }
    ::= { tmnxTestHdAccCritEntry 14 }


--

tmnxTestHdSessTable OBJECT-TYPE
    SYNTAX       SEQUENCE OF TmnxTestHdSessEntry
    MAX-ACCESS   not-accessible
    STATUS       current
    DESCRIPTION
        "This table maintains the information of test sessions."
    ::= { tmnxTestHdProfObjects 4 }

tmnxTestHdSessEntry OBJECT-TYPE
    SYNTAX       TmnxTestHdSessEntry
    MAX-ACCESS   not-accessible
    STATUS       current
    DESCRIPTION
        "Information about a particular testhead session.

         Entries are read-only for the user."
    INDEX { tmnxTestHdSessOwnerName, tmnxTestHdSessTestName  }
    ::= { tmnxTestHdSessTable 1 }

TmnxTestHdSessEntry ::= SEQUENCE
    {
        tmnxTestHdSessOwnerName                   SnmpAdminString,
        tmnxTestHdSessTestName                    SnmpAdminString,
        tmnxTestHdSessStartTime                   DateAndTime,
        tmnxTestHdSessCompletedTime               DateAndTime,
        tmnxTestHdSessTotalTime                   INTEGER,
--      tmnxTestHdSessFc                          TFCName,
        tmnxTestHdSessCompleted                   TruthValue,
        tmnxTestHdSessStopped                     TruthValue,
        tmnxTestHdSessProfId                      INTEGER,
        tmnxTestHdSessPayLdId                     Counter64,
--        tmnxTestHdSessPayLdId                     INTEGER,
        tmnxTestHdSessAccCritId                   INTEGER,
        tmnxTestHdSessSapPortId                   TmnxPortID,
        tmnxTestHdSessSapEncapValue               TmnxEncapVal,
        tmnxTestHdSessTransCount                  Counter64,
        tmnxTestHdSessRecvCount                   Counter64,
        tmnxTestHdSessMinLatency                  Counter64,
        tmnxTestHdSessMaxLatency                  Counter64,
        tmnxTestHdSessMeasuredLatency             Counter64,
        tmnxTestHdSessMeasuredJitter              INTEGER,
        tmnxTestHdSessColorAware                  TruthValue,
        tmnxTestHdSessStatus                      INTEGER,
        tmnxTestHdSessPerfMon                     TruthValue
    }

tmnxTestHdSessOwnerName OBJECT-TYPE
    SYNTAX      SnmpAdminString (SIZE(1..32))
    MAX-ACCESS  not-accessible
    STATUS      current
    DESCRIPTION
        "The test name index of this Test head test session.
         "
    ::= { tmnxTestHdSessEntry 1 }

tmnxTestHdSessTestName OBJECT-TYPE
    SYNTAX      SnmpAdminString (SIZE(1..32))
    MAX-ACCESS  not-accessible
    STATUS      current
    DESCRIPTION
        "The test name index of this Test head test session.
         "
    ::= { tmnxTestHdSessEntry 2 }

tmnxTestHdSessStartTime OBJECT-TYPE
    SYNTAX      DateAndTime
    MAX-ACCESS  read-only
    STATUS      current
    DESCRIPTION
        "tmnxTestHdSessStartTime test head start time for this session"
    ::= { tmnxTestHdSessEntry 3 }


tmnxTestHdSessCompletedTime OBJECT-TYPE
    SYNTAX      DateAndTime
    MAX-ACCESS  read-only
    STATUS      current
    DESCRIPTION
        "tmnxTestHdSessCompletedTime is the time stamp at which this
        test head run session has completed."
    ::= { tmnxTestHdSessEntry 4 }


tmnxTestHdSessTotalTime OBJECT-TYPE
    SYNTAX      INTEGER
    UNITS       "seconds"
    MAX-ACCESS  read-only
    STATUS      current
    DESCRIPTION
        "tmnxTestHdSessTotalTime is the total time since test head test
        has started"
    ::= { tmnxTestHdSessEntry 5 }

--tmnxTestHdSessFc OBJECT-TYPE
--    SYNTAX       TFCName
--    MAX-ACCESS   read-only
--    STATUS       obsolete
--    DESCRIPTION
--        "tmnxTestHdFc is the fc used in this test head session"
--    ::= { tmnxTestHdSessEntry 6 }

tmnxTestHdSessCompleted OBJECT-TYPE
    SYNTAX       TruthValue
    MAX-ACCESS   read-only
    STATUS       current
    DESCRIPTION
        "tmnxTestHdSessCompleted is true if the test is completed else it is
        false. "
    ::= { tmnxTestHdSessEntry 6 }

tmnxTestHdSessStopped OBJECT-TYPE
    SYNTAX       TruthValue
    MAX-ACCESS   read-only
    STATUS       current
    DESCRIPTION
        "tmnxTestHdStopped is true if the test is stopped midway else it is
        false. "
    ::= { tmnxTestHdSessEntry 7 }

tmnxTestHdSessProfId OBJECT-TYPE
    SYNTAX       INTEGER (0..32)
    MAX-ACCESS   read-only
    STATUS       current
    DESCRIPTION
        "tmnxTestHdSessProfId is the profile index for this session"
    ::= { tmnxTestHdSessEntry 8 }


tmnxTestHdSessPayLdId OBJECT-TYPE
    SYNTAX       Counter64
--    SYNTAX       INTEGER
    MAX-ACCESS   read-only
    STATUS       current
    DESCRIPTION
        "tmnxTestHdSessPayLdId is a 64 bit integer, every 8 bits represents a payload.
         for this release, we support up to 4 payloads per test session. So only 32 bits will be used.
         With each 8 bits, one bit will be set to represent the payload indexes used for the payload.
         e.g 0x020104 means payload 3,1 and 2 are used"
    ::= { tmnxTestHdSessEntry 9 }

tmnxTestHdSessAccCritId OBJECT-TYPE
    SYNTAX       INTEGER (1..8)
    MAX-ACCESS   read-only
    STATUS       current
    DESCRIPTION
        "tmnxTestHdSessAccCritId is the acceptance criteria id used for
        this test run"
    ::= { tmnxTestHdSessEntry 10 }

tmnxTestHdSessSapPortId OBJECT-TYPE
    SYNTAX          TmnxPortID
    MAX-ACCESS      read-only
    STATUS          current
    DESCRIPTION     "The sap port id ID used in for this test run."
    ::= { tmnxTestHdSessEntry 11 }

tmnxTestHdSessSapEncapValue OBJECT-TYPE
    SYNTAX          TmnxEncapVal
    MAX-ACCESS      read-only
    STATUS          current
    DESCRIPTION     "The sap encap value used in this test run."
    ::= { tmnxTestHdSessEntry 12 }

tmnxTestHdSessTransCount OBJECT-TYPE
    SYNTAX          Counter64
    MAX-ACCESS      read-only
    STATUS          current
    DESCRIPTION     "The total number of packets injected"
    ::= { tmnxTestHdSessEntry 13 }


tmnxTestHdSessRecvCount OBJECT-TYPE
    SYNTAX          Counter64
    MAX-ACCESS      read-only
    STATUS          current
    DESCRIPTION     "The total number of packets received"
    ::= { tmnxTestHdSessEntry 14 }

tmnxTestHdSessMinLatency OBJECT-TYPE
    SYNTAX          Counter64
    UNITS           "microseconds"
    MAX-ACCESS      read-only
    STATUS          current
    DESCRIPTION     "The Latency measured minimum for this test"
    ::= { tmnxTestHdSessEntry 15 }

tmnxTestHdSessMaxLatency OBJECT-TYPE
    SYNTAX          Counter64
    UNITS           "microseconds"
    MAX-ACCESS      read-only
    STATUS          current
    DESCRIPTION     "The Latency measured maximum for this test"
    ::= { tmnxTestHdSessEntry 16 }

tmnxTestHdSessMeasuredLatency OBJECT-TYPE
    SYNTAX          Counter64
    UNITS           "microseconds"
    MAX-ACCESS      read-only
    STATUS          current
    DESCRIPTION     "The Latency measured for this test"
    ::= { tmnxTestHdSessEntry 17 }


tmnxTestHdSessMeasuredJitter OBJECT-TYPE
    SYNTAX          INTEGER
    UNITS           "microseconds"
    MAX-ACCESS      read-only
    STATUS          current
    DESCRIPTION     "The Jitter measured for this test"
    ::= { tmnxTestHdSessEntry 18 }

tmnxTestHdSessColorAware     OBJECT-TYPE
    SYNTAX          TruthValue
    MAX-ACCESS      read-only
    STATUS          current
    DESCRIPTION     "tmnxTestHdSessColorAware indicate if this is a color aware test."
    ::= { tmnxTestHdSessEntry 19 }

tmnxTestHdSessStatus OBJECT-TYPE
    SYNTAX      INTEGER {
                    pass (1),
                    fail (2),
                    not-available(3)
                }
    MAX-ACCESS   read-only
    STATUS       current
    DESCRIPTION
        "tmnxTestHdSessStatus is the combination of the total test results for the session.
         tmnxTestHdSessStatus is pass if all desired test results are
        acheived."
    ::= { tmnxTestHdSessEntry 20 }

tmnxTestHdSessPerfMon      OBJECT-TYPE
    SYNTAX          TruthValue
    MAX-ACCESS      read-only
    STATUS          current
    DESCRIPTION     "tmnxTestHdSessPerfMon indicate if marker packet performance monitoring is enabled or disabled"
    ::= { tmnxTestHdSessEntry 21 }

--

tmnxTestHdResultsTable OBJECT-TYPE
    SYNTAX       SEQUENCE OF TmnxTestHdResultsEntry
    MAX-ACCESS   not-accessible
    STATUS       current
    DESCRIPTION
        "This table maintains the information of testhead session results."
    ::= { tmnxTestHdProfObjects 5 }

tmnxTestHdResultsEntry OBJECT-TYPE
    SYNTAX       TmnxTestHdResultsEntry
    MAX-ACCESS   not-accessible
    STATUS       current
    DESCRIPTION
        "Information about a particular testhead session result.

         Entries are read-only for the user."
    INDEX { tmnxTestHdOwnerName, tmnxTestHdTestName  }
    ::= { tmnxTestHdResultsTable 1 }

TmnxTestHdResultsEntry ::= SEQUENCE
    {
        tmnxTestHdOwnerName                          SnmpAdminString,
        tmnxTestHdTestName                           SnmpAdminString,
        tmnxTestHdResProfId                          INTEGER,
        tmnxTestHdResProfPayLdId                     Counter64,
        tmnxTestHdResProfAccCritId                   INTEGER,
        tmnxTestHdResTransCount                      Counter64,
        tmnxTestHdResRecvCount                       Counter64,
        tmnxTestHdResMeasuredThruput                 INTEGER,
        tmnxTestHdResMeasuredFLR                     INTEGER,
        tmnxTestHdResMeasuredLatency                 Counter64,
        tmnxTestHdResLatencyAccptanceResult          INTEGER,
        tmnxTestHdResMeasuredJitter                  INTEGER,
        tmnxTestHdResJitterAccptanceResult           INTEGER,
        tmnxTestHdResSapPortId                       TmnxPortID,
        tmnxTestHdResSapEncapValue                   TmnxEncapVal,
        tmnxTestHdResFLRAccptanceResult              INTEGER,
        tmnxTestHdResMinLatency                      Counter64,
        tmnxTestHdResMaxLatency                      Counter64,
        tmnxTestHdResThruputAccptanceResult          INTEGER,
        tmnxTestHdResInProfTransCount                Counter64,
        tmnxTestHdResInProfRecvCount                 Counter64,
        tmnxTestHdResInProfMeasuredThruput           INTEGER,
        tmnxTestHdResInProfMeasuredFLR               INTEGER,
        tmnxTestHdResInProfMeasuredLatency           Counter64,
        tmnxTestHdResInProfLatencyAccptanceResult    INTEGER,
        tmnxTestHdResInProfMeasuredJitter            INTEGER,
        tmnxTestHdResInProfJitterAccptanceResult     INTEGER,
        tmnxTestHdResInProfFLRAccptanceResult        INTEGER,
        tmnxTestHdResInProfMinLatency                Counter64,
        tmnxTestHdResInProfMaxLatency                Counter64,
        tmnxTestHdResInProfThruputAccptanceResult    INTEGER,
        tmnxTestHdResOutProfTransCount               Counter64,
        tmnxTestHdResOutProfRecvCount                Counter64,
        tmnxTestHdResOutProfMeasuredThruput          INTEGER,
        tmnxTestHdResOutProfMeasuredFLR              INTEGER,
        tmnxTestHdResOutProfMeasuredLatency          Counter64,
        tmnxTestHdResOutProfLatencyAccptanceResult   INTEGER,
        tmnxTestHdResOutProfMeasuredJitter           INTEGER,
        tmnxTestHdResOutProfJitterAccptanceResult    INTEGER,
        tmnxTestHdResOutProfFLRAccptanceResult       INTEGER,
        tmnxTestHdResOutProfMinLatency               Counter64,
        tmnxTestHdResOutProfMaxLatency               Counter64,
        tmnxTestHdResOutProfThruputAccptanceResult   INTEGER,
        tmnxTestHdResMarkerPktBandwidth              INTEGER,
        tmnxTestHdResOperThruput                     INTEGER
    }

tmnxTestHdOwnerName OBJECT-TYPE
    SYNTAX      SnmpAdminString (SIZE(1..32))
    MAX-ACCESS  not-accessible
    STATUS      current
    DESCRIPTION
        "The owner name index of the Test head test.
         "
    ::= { tmnxTestHdResultsEntry 1 }

tmnxTestHdTestName OBJECT-TYPE
    SYNTAX      SnmpAdminString (SIZE(1..32))
    MAX-ACCESS  not-accessible
    STATUS      current
    DESCRIPTION
        "The test name index of the Test head test.
         "
    ::= { tmnxTestHdResultsEntry 2 }

tmnxTestHdResProfId OBJECT-TYPE
    SYNTAX          INTEGER
    MAX-ACCESS      read-only
    STATUS          current
    DESCRIPTION     "The Testhead profile Id used for this test"
    ::= { tmnxTestHdResultsEntry 3 }

tmnxTestHdResProfPayLdId OBJECT-TYPE
    SYNTAX          Counter64
    MAX-ACCESS      read-only
    STATUS          current
    DESCRIPTION     "The Testhead profile Pay Load Ids used for this
                     test. It is same as  tmnxTestHdSessPayLdId which
                     is a 64 bit integer, every 8 bits represents a payload.
                     For this release, we support up to 4 payloads per test session.
                     So only 32 bits will be used.
                     With each 8 bits, one bit will be set to represent the payload indexes used for the payload.
                     e.g 0x020104 means payload 3,1 and 2 are used"
    ::= { tmnxTestHdResultsEntry 4 }

tmnxTestHdResProfAccCritId OBJECT-TYPE
    SYNTAX          INTEGER
    MAX-ACCESS      read-only
    STATUS          current
    DESCRIPTION     "The Testhead profile Acceptance Criteria Id used
                     for this test"
    ::= { tmnxTestHdResultsEntry 5 }

tmnxTestHdResTransCount OBJECT-TYPE
    SYNTAX          Counter64
    MAX-ACCESS      read-only
    STATUS          current
    DESCRIPTION     "The total number of packets injected"
    ::= { tmnxTestHdResultsEntry 6 }


tmnxTestHdResRecvCount OBJECT-TYPE
    SYNTAX          Counter64
    MAX-ACCESS      read-only
    STATUS          current
    DESCRIPTION     "The total number of packets received"
    ::= { tmnxTestHdResultsEntry 7 }

tmnxTestHdResMeasuredThruput OBJECT-TYPE
    SYNTAX          INTEGER
    UNITS           "kbps"
    MAX-ACCESS      read-only
    STATUS          current
    DESCRIPTION     "The throughput measured for this test"
    ::= { tmnxTestHdResultsEntry 8 }

tmnxTestHdResMeasuredFLR OBJECT-TYPE
    SYNTAX          INTEGER
    UNITS           "10000th of a percent"
    MAX-ACCESS      read-only
    STATUS          current
    DESCRIPTION     "The frame loss ratio measured for this test, if
                     set to -1 tmnxTestHdResMeasuredFLR is not applicable
                     for this test"
    ::= { tmnxTestHdResultsEntry 9 }

tmnxTestHdResMeasuredLatency OBJECT-TYPE
    SYNTAX          Counter64
    UNITS           "microseconds"
    MAX-ACCESS      read-only
    STATUS          current
    DESCRIPTION     "The Latency measured for this test"
    ::= { tmnxTestHdResultsEntry 10 }

tmnxTestHdResLatencyAccptanceResult OBJECT-TYPE
    SYNTAX          INTEGER {
                        pass (1),
                        fail (2),
                        not-applicable(3)
                    }
    MAX-ACCESS      read-only
    STATUS          current
    DESCRIPTION     "The Latency Acceptance for this test"
    ::= { tmnxTestHdResultsEntry 11 }

tmnxTestHdResMeasuredJitter OBJECT-TYPE
    SYNTAX          INTEGER
    UNITS           "microseconds"
    MAX-ACCESS      read-only
    STATUS          current
    DESCRIPTION     "The Jitter measured for this test"
    ::= { tmnxTestHdResultsEntry 12 }

tmnxTestHdResJitterAccptanceResult OBJECT-TYPE
    SYNTAX          INTEGER {
                        pass (1),
                        fail (2),
                        not-applicable(3)
                    }
    MAX-ACCESS      read-only
    STATUS          current
    DESCRIPTION     "The Jitter Acceptance for this test"
    ::= { tmnxTestHdResultsEntry 13 }

tmnxTestHdResSapPortId OBJECT-TYPE
    SYNTAX          TmnxPortID
    MAX-ACCESS      read-only
    STATUS          current
    DESCRIPTION     "The sap port id ID used in for this test run."
    ::= { tmnxTestHdResultsEntry 14 }

tmnxTestHdResSapEncapValue OBJECT-TYPE
    SYNTAX          TmnxEncapVal
    MAX-ACCESS      read-only
    STATUS          current
    DESCRIPTION     "The sap encap value used in this test run."
    ::= { tmnxTestHdResultsEntry 15 }

tmnxTestHdResFLRAccptanceResult OBJECT-TYPE
    SYNTAX          INTEGER {
                        pass (1),
                        fail (2),
                        not-applicable(3)
                    }
    MAX-ACCESS      read-only
    STATUS          current
    DESCRIPTION     "The FLR Acceptance for this test"
    ::= { tmnxTestHdResultsEntry 16 }


tmnxTestHdResMinLatency OBJECT-TYPE
    SYNTAX          Counter64
    UNITS           "microseconds"
    MAX-ACCESS      read-only
    STATUS          current
    DESCRIPTION     "The Latency measured minimum for this test"
    ::= { tmnxTestHdResultsEntry 17 }

tmnxTestHdResMaxLatency OBJECT-TYPE
    SYNTAX          Counter64
    UNITS           "microseconds"
    MAX-ACCESS      read-only
    STATUS          current
    DESCRIPTION     "The Latency measured maximum for this test"
    ::= { tmnxTestHdResultsEntry 18 }

tmnxTestHdResThruputAccptanceResult OBJECT-TYPE
    SYNTAX          INTEGER {
                        pass (1),
                        fail (2),
                        not-applicable(3)
                    }
    MAX-ACCESS      read-only
    STATUS          current
    DESCRIPTION     "The Thruput Acceptance test result for this test"
    ::= { tmnxTestHdResultsEntry 19 }

tmnxTestHdResInProfTransCount OBJECT-TYPE
    SYNTAX          Counter64
    MAX-ACCESS      read-only
    STATUS          current
    DESCRIPTION     "The total number of in profile packets injected"
    ::= { tmnxTestHdResultsEntry 20 }

tmnxTestHdResInProfRecvCount OBJECT-TYPE
    SYNTAX          Counter64
    MAX-ACCESS      read-only
    STATUS          current
    DESCRIPTION     "The total number of in profile packets received"
    ::= { tmnxTestHdResultsEntry 21 }

tmnxTestHdResInProfMeasuredThruput OBJECT-TYPE
    SYNTAX          INTEGER
    UNITS           "kbps"
    MAX-ACCESS      read-only
    STATUS          current
    DESCRIPTION     "The in profile throughput measured for this test"
    ::= { tmnxTestHdResultsEntry 22 }

tmnxTestHdResInProfMeasuredFLR OBJECT-TYPE
    SYNTAX          INTEGER
    UNITS           "10000th of a percent"
    MAX-ACCESS      read-only
    STATUS          current
    DESCRIPTION     "The in profile frame loss ratio measured for this test, if
                     set to -1 tmnxTestHdResInProfMeasuredFLR is not applicable
                     for this test"
    ::= { tmnxTestHdResultsEntry 23 }

tmnxTestHdResInProfMeasuredLatency OBJECT-TYPE
    SYNTAX          Counter64
    UNITS           "microseconds"
    MAX-ACCESS      read-only
    STATUS          current
    DESCRIPTION     "The in profile Latency measured for this test"
    ::= { tmnxTestHdResultsEntry 24 }

tmnxTestHdResInProfLatencyAccptanceResult OBJECT-TYPE
    SYNTAX          INTEGER {
                        pass (1),
                        fail (2),
                        not-applicable(3)
                    }
    MAX-ACCESS      read-only
    STATUS          current
    DESCRIPTION     "The in profile Latency Acceptance for this test"
    ::= { tmnxTestHdResultsEntry 25 }

tmnxTestHdResInProfMeasuredJitter OBJECT-TYPE
    SYNTAX          INTEGER
    UNITS           "microseconds"
    MAX-ACCESS      read-only
    STATUS          current
    DESCRIPTION     "The in profile Jitter measured for this test"
    ::= { tmnxTestHdResultsEntry 26 }

tmnxTestHdResInProfJitterAccptanceResult OBJECT-TYPE
    SYNTAX          INTEGER {
                        pass (1),
                        fail (2),
                        not-applicable(3)
                    }
    MAX-ACCESS      read-only
    STATUS          current
    DESCRIPTION     "The in profile Jitter Acceptance for this test"
    ::= { tmnxTestHdResultsEntry 27 }

tmnxTestHdResInProfFLRAccptanceResult OBJECT-TYPE
    SYNTAX          INTEGER {
                        pass (1),
                        fail (2),
                        not-applicable(3)
                    }
    MAX-ACCESS      read-only
    STATUS          current
    DESCRIPTION     "The in profile FLR Acceptance for this test"
    ::= { tmnxTestHdResultsEntry 28 }

tmnxTestHdResInProfMinLatency OBJECT-TYPE
    SYNTAX          Counter64
    UNITS           "microseconds"
    MAX-ACCESS      read-only
    STATUS          current
    DESCRIPTION     "The in profile Latency measured minimum for this test"
    ::= { tmnxTestHdResultsEntry 29 }

tmnxTestHdResInProfMaxLatency OBJECT-TYPE
    SYNTAX          Counter64
    UNITS           "microseconds"
    MAX-ACCESS      read-only
    STATUS          current
    DESCRIPTION     "The in profile Latency measured maximum for this test"
    ::= { tmnxTestHdResultsEntry 30 }

tmnxTestHdResInProfThruputAccptanceResult OBJECT-TYPE
    SYNTAX          INTEGER {
                        pass (1),
                        fail (2),
                        not-applicable(3)
                    }
    MAX-ACCESS      read-only
    STATUS          current
    DESCRIPTION     "The Thruput Acceptance test result for this test"
    ::= { tmnxTestHdResultsEntry 31 }

tmnxTestHdResOutProfTransCount OBJECT-TYPE
    SYNTAX          Counter64
    MAX-ACCESS      read-only
    STATUS          current
    DESCRIPTION     "The total number of out profile packets injected"
    ::= { tmnxTestHdResultsEntry 32 }

tmnxTestHdResOutProfRecvCount OBJECT-TYPE
    SYNTAX          Counter64
    MAX-ACCESS      read-only
    STATUS          current
    DESCRIPTION     "The total number of out profile packets received"
    ::= { tmnxTestHdResultsEntry 33 }

tmnxTestHdResOutProfMeasuredThruput OBJECT-TYPE
    SYNTAX          INTEGER
    UNITS           "kbps"
    MAX-ACCESS      read-only
    STATUS          current
    DESCRIPTION     "The out profile throughput measured for this test"
    ::= { tmnxTestHdResultsEntry 34 }

tmnxTestHdResOutProfMeasuredFLR OBJECT-TYPE
    SYNTAX          INTEGER
    UNITS           "10000th of a percent"
    MAX-ACCESS      read-only
    STATUS          current
    DESCRIPTION     "The out profile frame loss ratio measured for this test, if
                     set to -1 tmnxTestHdResOutProfMeasuredFLR is not applicable
                     for this test"
    ::= { tmnxTestHdResultsEntry 35 }

tmnxTestHdResOutProfMeasuredLatency OBJECT-TYPE
    SYNTAX          Counter64
    UNITS           "microseconds"
    MAX-ACCESS      read-only
    STATUS          current
    DESCRIPTION     "The out profile Latency measured for this test"
    ::= { tmnxTestHdResultsEntry 36 }

tmnxTestHdResOutProfLatencyAccptanceResult OBJECT-TYPE
    SYNTAX          INTEGER {
                        pass (1),
                        fail (2),
                        not-applicable(3)
                    }
    MAX-ACCESS      read-only
    STATUS          current
    DESCRIPTION     "The out profile Latency Acceptance for this test"
    ::= { tmnxTestHdResultsEntry 37 }

tmnxTestHdResOutProfMeasuredJitter OBJECT-TYPE
    SYNTAX          INTEGER
    UNITS           "microseconds"
    MAX-ACCESS      read-only
    STATUS          current
    DESCRIPTION     "The out profile Jitter measured for this test"
    ::= { tmnxTestHdResultsEntry 38 }

tmnxTestHdResOutProfJitterAccptanceResult OBJECT-TYPE
    SYNTAX          INTEGER {
                        pass (1),
                        fail (2),
                        not-applicable(3)
                    }
    MAX-ACCESS      read-only
    STATUS          current
    DESCRIPTION     "The out profile Jitter Acceptance for this test"
    ::= { tmnxTestHdResultsEntry 39 }

tmnxTestHdResOutProfFLRAccptanceResult OBJECT-TYPE
    SYNTAX          INTEGER {
                        pass (1),
                        fail (2),
                        not-applicable(3)
                    }
    MAX-ACCESS      read-only
    STATUS          current
    DESCRIPTION     "The out profile FLR Acceptance for this test"
    ::= { tmnxTestHdResultsEntry 40 }

tmnxTestHdResOutProfMinLatency OBJECT-TYPE
    SYNTAX          Counter64
    UNITS           "microseconds"
    MAX-ACCESS      read-only
    STATUS          current
    DESCRIPTION     "The out profile Latency measured minimum for this test"
    ::= { tmnxTestHdResultsEntry 41 }

tmnxTestHdResOutProfMaxLatency OBJECT-TYPE
    SYNTAX          Counter64
    UNITS           "microseconds"
    MAX-ACCESS      read-only
    STATUS          current
    DESCRIPTION     "The out profile Latency measured maximum for this test"
    ::= { tmnxTestHdResultsEntry 42 }

tmnxTestHdResOutProfThruputAccptanceResult OBJECT-TYPE
    SYNTAX          INTEGER {
                        pass (1),
                        fail (2),
                        not-applicable(3)
                    }
    MAX-ACCESS      read-only
    STATUS          current
    DESCRIPTION     "The out profile Thruput Acceptance test result for this test"
    ::= { tmnxTestHdResultsEntry 43 }

tmnxTestHdResMarkerPktBandwidth OBJECT-TYPE
    SYNTAX          INTEGER
    MAX-ACCESS      read-only
    STATUS          current
    DESCRIPTION     "The bandwidth (kbps) consumed by marker packets"
    ::= { tmnxTestHdResultsEntry 44 }

tmnxTestHdResOperThruput   OBJECT-TYPE
    SYNTAX          INTEGER
    MAX-ACCESS      read-only
    STATUS          current
    DESCRIPTION     "oper throughput at sap ingress as an aggregate value of
                     all payload throughput used for this test"
    ::= { tmnxTestHdResultsEntry 45 }

tmnxTestHdProfScalarObjs OBJECT IDENTIFIER       ::= { tmnxTestHdProfObjects 6 }

tmnxTestHdName OBJECT-TYPE
    SYNTAX      SnmpAdminString (SIZE(1..32))
    MAX-ACCESS  read-write
    STATUS      current
    DESCRIPTION
        "tmnxTestHdName is a mandatory parameter that needs to be
        set along with tmnxTestHdAdminStatus to start a test head
        test.
        "
    ::= { tmnxTestHdProfScalarObjs 1 }


tmnxTestHdOwner OBJECT-TYPE
    SYNTAX      SnmpAdminString (SIZE(1..32))
    MAX-ACCESS  read-write
    STATUS      current
    DESCRIPTION
        "tmnxTestHdOwner is a mandatory parameter that needs to be
        set along with tmnxTestHdAdminStatus to start a test head
        test."
    ::= { tmnxTestHdProfScalarObjs 2 }

tmnxTestHdStartTime OBJECT-TYPE
    SYNTAX      DateAndTime
    MAX-ACCESS  accessible-for-notify
    STATUS      current
    DESCRIPTION
        "tmnxTestHdStartTime test head start time sent in the trap
        message"
    ::= { tmnxTestHdProfScalarObjs 3 }

tmnxTestHdElapsedTime OBJECT-TYPE
    SYNTAX      INTEGER
    UNITS       "seconds"
    MAX-ACCESS  accessible-for-notify
    STATUS      current
    DESCRIPTION
        "tmnxTestHdElapsedTime is the elapsed time since test head test
        has started"
    ::= { tmnxTestHdProfScalarObjs 4 }

--tmnxTestHdFc OBJECT-TYPE
--    SYNTAX       TFCName
--    MAX-ACCESS   read-write
--    STATUS       obsolete
--    DESCRIPTION
--        "tmnxTestHdFc is an  optional parameter that needs to be
--        set along with tmnxTestHdAdminStatus to start a test head
--        test.If tmnxTestHdFc is not given along with
--        tmnxTestHdAdminStatus default forwarding class 'be' would be
--        used"
--    DEFVAL { "be" }
--    ::= { tmnxTestHdProfScalarObjs 5 }

tmnxTestHdAvgLatency OBJECT-TYPE
    SYNTAX      INTEGER (0..2147483000)
    UNITS       "microseconds"
    MAX-ACCESS   accessible-for-notify
    STATUS       current
    DESCRIPTION
        "tmnxTestHdAvgLatency is the measured average latency in the
        test head run. tmnxTestHdAvgLatency is sent in the trap upon
        test completion"
    ::= { tmnxTestHdProfScalarObjs 5 }


tmnxTestHdFrLossRatio OBJECT-TYPE
    SYNTAX      INTEGER (0..10000000)
    UNITS       "10000th of a percent"
    MAX-ACCESS   accessible-for-notify
    STATUS       current
    DESCRIPTION
        "tmnxTestHdFrLossRatio is the measured frame loss ratio
        in the test head run. tmnxTestHdFrLossRatio is sent in the
        trap upon test completion"
    ::= { tmnxTestHdProfScalarObjs 6 }

tmnxTestHdJitter OBJECT-TYPE
    SYNTAX      INTEGER (0..2147483000)
    UNITS       "microseconds"
    MAX-ACCESS   accessible-for-notify
    STATUS       current
    DESCRIPTION
        "tmnxTestHdJitter is the measured jitter  in the test head run.
        tmnxTestHdJitter is sent in the trap upon test completion"
    ::= { tmnxTestHdProfScalarObjs 7 }

tmnxTestHdDsiredThrpt OBJECT-TYPE
    SYNTAX      INTEGER
    MAX-ACCESS   accessible-for-notify
    STATUS       current
    DESCRIPTION
        "tmnxTestHdDsiredThrpt is the desired through put in the test head
        run. tmnxTestHdDsiredThrpt is sent in the trap upon test completion"
    ::= { tmnxTestHdProfScalarObjs 8 }


tmnxTestHdAchvdThrpt OBJECT-TYPE
    SYNTAX      INTEGER
    MAX-ACCESS   accessible-for-notify
    STATUS       current
    DESCRIPTION
        "tmnxTestHdAchvdThrpt is the acheived through put in the test head
        run. tmnxTestHdAchvdThrpt is sent in the trap upon test completion"
    ::= { tmnxTestHdProfScalarObjs 9 }

tmnxTestHdCompleted OBJECT-TYPE
    SYNTAX      TruthValue
    MAX-ACCESS   accessible-for-notify
    STATUS       current
    DESCRIPTION
        "tmnxTestHdCompleted is true if the test is completed else it is
        false. tmnxTestHdCompleted is sent in the trap upon test completion"
    ::= { tmnxTestHdProfScalarObjs 10 }

tmnxTestHdStopped OBJECT-TYPE
    SYNTAX      TruthValue
    MAX-ACCESS   accessible-for-notify
    STATUS       current
    DESCRIPTION
        "tmnxTestHdStopped is true if the test is stopped midway else it is
        false. tmnxTestHdStopped is sent in the trap upon test completion"
    ::= { tmnxTestHdProfScalarObjs 11 }

tmnxTestHdTestStatus OBJECT-TYPE
    SYNTAX      INTEGER {
                    pass (1),
                    fail (2),
                    not-available(3)
                }
    MAX-ACCESS   accessible-for-notify
    STATUS       current
    DESCRIPTION
        "tmnxTestHdTestStatus is sent in the trap upon test completion.
        tmnxTestHdTestStatus is pass if the desired test results are
        acheived."
    ::= { tmnxTestHdProfScalarObjs 12 }

tmnxTestHdCompletedTime OBJECT-TYPE
    SYNTAX      DateAndTime
    MAX-ACCESS  accessible-for-notify
    STATUS      current
    DESCRIPTION
        "tmnxTestHdCompletedTime is the time at which test head run
        has completed. tmnxTestHdCompletedTime is sent in the trap upon
        test completion."
    ::= { tmnxTestHdProfScalarObjs 13 }

tmnxTestHdSapPortId OBJECT-TYPE
    SYNTAX          TmnxPortID
    MAX-ACCESS      read-write
    STATUS          current
    DESCRIPTION
         "The Sap Port ID to be used for the test run, it has to be supplied
         along with tmnxTestHdSapEncapValue when the test is started.
         "
    ::= { tmnxTestHdProfScalarObjs 14 }

tmnxTestHdSapEncapValue OBJECT-TYPE
    SYNTAX          TmnxEncapVal
    MAX-ACCESS      read-write
    STATUS          current
    DESCRIPTION
         "The Sap Encap value to be used for the test run, it has to be supplied
         along with tmnxTestHdSapPortId when the test is started.
         "
    ::= { tmnxTestHdProfScalarObjs 15 }

tmnxTestHdAdminStatus OBJECT-TYPE
    SYNTAX      INTEGER {
                          enabled(1), -- test should be started
                          disabled(2),-- test should be stopped
                          clear(3)    -- clear all test data
                        }
    MAX-ACCESS  read-write
    STATUS      current
    DESCRIPTION
        "Reflects the desired state that a Test Head should be
         in:

           enabled(1)  - Attempt to activate the test as defined by
            tmnxTestHdName, tmnxTestHdOwner, tmnxTestHdProfId,
            tmnxTestHdPayLdId, tmnxTestHdAccCritId, tmnxTestHdSapPortId,
            tmnxTestHdSapEncapValue, tmnxTestHdFc
                         .
           disabled(2) - Deactivate the test as defined by this
                         tmnxOamPingCtlEntry.

         An attempt to set tmnxOamPingCtlAdminStatus to 'enabled' will fail
         if the parameters required by a particular TestHead test have
         not been set along with tmnxTestHdAdminStatus  Upon completion of
         a Test head test, he agent will reset the value of this object to
         'disabled'. When this object has the value 'enabled' an attempt to modify
         any of the test parameters will fail with an inconsistentValue
         error."
    DEFVAL { disabled }
    ::= { tmnxTestHdProfScalarObjs 16 }

tmnxTestHdProfId OBJECT-TYPE
    SYNTAX       INTEGER (0..32)
    MAX-ACCESS   read-write
    STATUS       current
    DESCRIPTION
         "tmnxTestHdProfId is the test head profile to be used for
         the test run, it has to be supplied along with tmnxTestHdAdminStatus
         when the test is started. tmnxTestHdProfEntry corresponding to
         tmnxTestHdProfId should be creted before starting the test.
         "
    ::= { tmnxTestHdProfScalarObjs 17 }

tmnxTestHdAccCritId OBJECT-TYPE
    SYNTAX       INTEGER (1..8)
    MAX-ACCESS   read-write
    STATUS       current
    DESCRIPTION
         "tmnxTestHdAccCritId is the acceptance criteria to be used for
         the test run, it is an optional parameter to be supplied along
         with tmnxTestHdAdminStatus when the test is started.
         tmnxTestHdAccCritEntry corresponding to tmnxTestHdAccCritId
         should be creted before starting the test.
         "
    ::= { tmnxTestHdProfScalarObjs 18 }

tmnxTestHdPayLdId OBJECT-TYPE
    SYNTAX       Unsigned32
    MAX-ACCESS   read-write
    STATUS       current
    DESCRIPTION
         "tmnxTestHdPayLd are bitmap for the frame payloads to be used for
         the test run, it is an optional parameter to be supplied along
         with tmnxTestHdAdminStatus when the test is started.
         Every 8 bits represents a payload.  For this release,
         we support up to 4 payloads per test session.  So only 32 bits will be used.
         With each 8 bits, one bit will be set to represent the payload indexes used for the payload.
         e.g 0x020104 means payload 3,1 and 2 are used.
         "
    ::= { tmnxTestHdProfScalarObjs 19 }

tmnxTestHdColorAware OBJECT-TYPE
    SYNTAX       TruthValue
    MAX-ACCESS   read-write
    STATUS       current
    DESCRIPTION
         "tmnxTestHdColorAware can be set to true to run when the test
         is started to run color-aware tests.
         "
    ::= { tmnxTestHdProfScalarObjs 20 }

tmnxTestHdEnPerfMon OBJECT-TYPE
    SYNTAX       TruthValue
    MAX-ACCESS   read-write
    STATUS       current
    DESCRIPTION
         "tmnxTestHdEnPerfMon can be used to enable the marker pkt performance monitoring when the test
         is started.
         "
    ::= { tmnxTestHdProfScalarObjs 21 }

tmnxTestHdScalarObjs OBJECT IDENTIFIER       ::= { tmnxTestHdObjects 1 }

tmnxTestHdMarkerSrcMacAddr OBJECT-TYPE
    SYNTAX       MacAddress
    MAX-ACCESS   read-write
    STATUS       current
    DESCRIPTION
         "Source Mac address used in testhead marker packets.
         "
    ::= { tmnxTestHdScalarObjs 1 }

--
-- tmnxOamPingCtlTable Extension Table
--
aluExtOamPingCtlTable OBJECT-TYPE
    SYNTAX       SEQUENCE OF AluExtOamPingCtlEntry
    MAX-ACCESS   not-accessible
    STATUS       current
    DESCRIPTION
        "Information about the Nokia 7705 SAR extensions to tmnxOamPingCtlTable."
    ::= { aluOamTestObjs 4 }

aluExtOamPingCtlEntry OBJECT-TYPE
    SYNTAX       AluExtOamPingCtlEntry
    MAX-ACCESS   not-accessible
    STATUS       current
    DESCRIPTION
        "Information about the extensions of tmnxOamPingCtlEntry."
    AUGMENTS  { tmnxOamPingCtlEntry }
    ::= { aluExtOamPingCtlTable 1 }

AluExtOamPingCtlEntry ::= SEQUENCE
{
    aluExtOamPingCtlUseDataQueue        TruthValue
}

aluExtOamPingCtlUseDataQueue OBJECT-TYPE
    SYNTAX      TruthValue
    MAX-ACCESS  read-write
    STATUS      current
    DESCRIPTION
        "The value of aluExtOamPingCtlUseDataQueue being 'true' indicates to send
        test frames using egress data queue indicated by tmnxOamPingCtlFcName,
        otherwise use control queue.

        For now aluExtOamPingCtlUseDataQueue can be true only when
        tmnxOamPingCtlTestMode is 'icmpPing'.

        Default of aluExtOamPingCtlUseDataQueue is 'false', except for when
        tmnxOamPingCtlTestMode is 'icmpIng' and tmnxOamPingCtlSAA is 'true', in which case,
        aluExtOamPingCtlUseDataQueue is defaulted to 'true' and cannot be changed."
    DEFVAL { false }
    ::= { aluExtOamPingCtlEntry 1 }


tmnxOamTestHeadTestCompleted NOTIFICATION-TYPE
    OBJECTS {
        tmnxTestHdName,
        tmnxTestHdOwner,
        tmnxTestHdStartTime,
        tmnxTestHdCompletedTime,
        tmnxTestHdElapsedTime,
        tmnxTestHdProfIndex,
        tmnxTestHdAccCritIndex,
        tmnxTestHdPayLdIndex,
        svcId,
        tmnxTestHdSapPortId,
        tmnxTestHdSapEncapValue,
        tmnxTestHdDsiredThrpt,
        tmnxTestHdCompleted,
        tmnxTestHdStopped,
        tmnxTestHdTestStatus,
        tmnxTestHdAvgLatency,
        tmnxTestHdFrLossRatio,
        tmnxTestHdJitter,
        tmnxTestHdAchvdThrpt
    }
    STATUS  current
    DESCRIPTION
        "Generated at the completion of Test Head completion."
    ::= { aluOamNotifications 1 }

tmnxTestHdObjsV7v0Group OBJECT-GROUP
    OBJECTS {
       tmnxTestHdAccCritId,
       tmnxTestHdAccCritIndex,
       tmnxTestHdAccCritJittrRiseThres,
       tmnxTestHdAccCritLastChanged,
       tmnxTestHdAccCritLatRiseThres,
       tmnxTestHdAccCritLossRiseThres,
       tmnxTestHdAccCritRowStatus,
       tmnxTestHdAchvdThrpt,
       tmnxTestHdAdminStatus,
       tmnxTestHdAvgLatency,
       tmnxTestHdCompleted,
       tmnxTestHdCompletedTime,
       tmnxTestHdDsiredThrpt,
       tmnxTestHdElapsedTime,
       tmnxTestHdFrLossRatio,
       tmnxTestHdJitter,
       tmnxTestHdLastChanged,
       tmnxTestHdName,
       tmnxTestHdOwner,
       tmnxTestHdPayLdDSCP,
       tmnxTestHdPayLdDesc,
       tmnxTestHdPayLdDstIpv4Addr,
       tmnxTestHdPayLdDstMac,
       tmnxTestHdPayLdDstPort,
       tmnxTestHdPayLdEthertype,
       tmnxTestHdPayLdId,
       tmnxTestHdPayLdIndex,
       tmnxTestHdPayLdIpProto,
       tmnxTestHdPayLdIpTTL,
       tmnxTestHdPayLdIpTos,
       tmnxTestHdPayLdLastChanged,
       tmnxTestHdPayLdRowStatus,
       tmnxTestHdPayLdSrcIpv4Addr,
       tmnxTestHdPayLdSrcMac,
       tmnxTestHdPayLdSrcPort,
       tmnxTestHdPayLdType,
       tmnxTestHdPayLdVTagOne,
       tmnxTestHdPayLdVTagOneDot1p,
       tmnxTestHdPayLdVTagOneTpid,
       tmnxTestHdPayLdVTagTwo,
       tmnxTestHdPayLdVTagTwoDot1p,
       tmnxTestHdPayLdVTagTwoTpid,
       tmnxTestHdPayLddataPattrn,
       tmnxTestHdProfAdminCIR,
       tmnxTestHdPayLdFrameSize,
       tmnxTestHdPayLdRate,
       tmnxTestHdProfDescription,
       tmnxTestHdProfDurHr,
       tmnxTestHdProfDurMin,
       tmnxTestHdProfDurSec,
       tmnxTestHdProfId,
       tmnxTestHdProfIndex,
       tmnxTestHdProfRowStatus,
       tmnxTestHdProfTrapEnable,
       tmnxTestHdResFLRAccptanceResult,
       tmnxTestHdResJitterAccptanceResult,
       tmnxTestHdResLatencyAccptanceResult,
       tmnxTestHdResMaxLatency,
       tmnxTestHdResMeasuredFLR,
       tmnxTestHdResMeasuredJitter,
       tmnxTestHdResMeasuredLatency,
       tmnxTestHdResMeasuredThruput,
       tmnxTestHdResMinLatency,
       tmnxTestHdResProfAccCritId,
       tmnxTestHdResProfId,
       tmnxTestHdResProfPayLdId,
       tmnxTestHdResRecvCount,
       tmnxTestHdResSapEncapValue,
       tmnxTestHdResSapPortId,
       tmnxTestHdResTransCount,
       tmnxTestHdResThruputAccptanceResult,
       tmnxTestHdResInProfTransCount,
       tmnxTestHdResInProfRecvCount,
       tmnxTestHdResInProfMeasuredThruput,
       tmnxTestHdResInProfMeasuredFLR,
       tmnxTestHdResInProfMeasuredLatency,
       tmnxTestHdResInProfLatencyAccptanceResult,
       tmnxTestHdResInProfMeasuredJitter,
       tmnxTestHdResInProfJitterAccptanceResult,
       tmnxTestHdResInProfFLRAccptanceResult,
       tmnxTestHdResInProfMinLatency,
       tmnxTestHdResInProfMaxLatency,
       tmnxTestHdResInProfThruputAccptanceResult,
       tmnxTestHdResOutProfTransCount,
       tmnxTestHdResOutProfRecvCount,
       tmnxTestHdResOutProfMeasuredThruput,
       tmnxTestHdResOutProfMeasuredFLR,
       tmnxTestHdResOutProfMeasuredLatency,
       tmnxTestHdResOutProfLatencyAccptanceResult,
       tmnxTestHdResOutProfMeasuredJitter,
       tmnxTestHdResOutProfJitterAccptanceResult,
       tmnxTestHdResOutProfFLRAccptanceResult,
       tmnxTestHdResOutProfMinLatency,
       tmnxTestHdResOutProfMaxLatency,
       tmnxTestHdResOutProfThruputAccptanceResult,
       tmnxTestHdResMarkerPktBandwidth,
       tmnxTestHdSapEncapValue,
       tmnxTestHdSapPortId,
       tmnxTestHdSessAccCritId,
       tmnxTestHdSessCompleted,
       tmnxTestHdSessCompletedTime,
--     tmnxTestHdSessFc,
       tmnxTestHdSessPayLdId,
       tmnxTestHdSessProfId,
       tmnxTestHdSessSapEncapValue,
       tmnxTestHdSessSapPortId,
       tmnxTestHdSessStartTime,
       tmnxTestHdSessStopped,
       tmnxTestHdSessTotalTime,
       tmnxTestHdSessColorAware,
       tmnxTestHdSessStatus,
       tmnxTestHdSessPerfMon,
       tmnxTestHdStartTime,
       tmnxTestHdStopped,
       tmnxTestHdTestStatus,
       tmnxTestHdAccCritLossRiseThresIn,
       tmnxTestHdAccCritLossRiseThresOut,
       tmnxTestHdAccCritCirThres,
       tmnxTestHdAccCritPirThres,
       tmnxTestHdAccCritLatRiseThresIn,
       tmnxTestHdAccCritLatRiseThresOut,
       tmnxTestHdAccCritJittrRiseThresIn,
       tmnxTestHdAccCritJittrRiseThresOut,
       tmnxTestHdProfAdminPIR,
       tmnxTestHdColorAware,
       tmnxTestHdProfActiveTests,
       tmnxTestHdProfCompetedTests,
       tmnxTestHdMarkerSrcMacAddr,
       tmnxTestHdEnPerfMon
    }
    STATUS      current
    DESCRIPTION
        "The group of Test Head objects supported in 7705 7.0
         release"
    ::= { tmnxTestHdObjsGroups 1 }

tmnxTestHdNotifyV7v0Group NOTIFICATION-GROUP
    NOTIFICATIONS {
        tmnxOamTestHeadTestCompleted
   }
    STATUS    current
    DESCRIPTION
        "The group of notifications supported in 7705 7.0 release"
    ::= { tmnxTestHdObjsGroups 2 }

aluOamPingV8v0Group OBJECT-GROUP
    OBJECTS {
        aluExtOamPingCtlUseDataQueue
    }
    STATUS      current
    DESCRIPTION
        "The group of OAM Test Objects supported in 7705 8.0 release."
    ::= { aluOamPingGroups 1 }

END
