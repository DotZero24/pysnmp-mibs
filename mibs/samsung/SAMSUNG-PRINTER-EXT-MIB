--
-- SamsungPrint.mib
-- MIB generated by MG-SOFT Visual MIB Builder Version 3.0 Build 253
-- Friday, October 14, 2005 at 09:22:29
--
--  SamsungPrint.mib
-- MIB generated by MG-SOFT Visual MIB Builder Version 3.0 Build 253
-- Thursday, October 13, 2005 at 08:41:43
--
--  SamsungPrint.mib
-- MIB generated by MG-SOFT Visual MIB Builder Version 3.0 Build 253
-- Monday, September 26, 2005 at 18:58:05
--
--  SamsungPrint.mib
-- MIB generated by MG-SOFT Visual MIB Builder Version 3.0 Build 253
-- Thursday, September 22, 2005 at 13:53:14
--
--  SamsungPrint.mib
-- MIB generated by MG-SOFT Visual MIB Builder Version 3.0 Build 253
-- Thursday, September 22, 2005 at 10:45:37
--
--  SamsungPrint.mib
-- MIB generated by MG-SOFT Visual MIB Builder Version 3.0 Build 253
-- Tuesday, May 24, 2005 at 14:58:52
--
--  SamsungPrint.mib
-- MIB generated by MG-SOFT Visual MIB Builder Version 3.0 Build 253
-- Tuesday, May 24, 2005 at 14:55:26
--
--  SamsungPrint.mib
-- MIB generated by MG-SOFT Visual MIB Builder Version 3.0 Build 253
-- Tuesday, May 24, 2005 at 14:10:20
--

	SAMSUNG-PRINTER-EXT-MIB DEFINITIONS ::= BEGIN

		IMPORTS
			hrDeviceIndex
				FROM HOST-RESOURCES-MIB
			prtGeneralEntry, prtInputEntry, prtOutputEntry, prtChannelEntry, prtInterpreterIndex,
			prtInterpreterEntry, PresentOnOff
				FROM Printer-MIB
			samsungCommonMIB
				FROM SAMSUNG-COMMON-MIB
			Ordinal32, Cardinal32
				FROM SAMSUNG-GENERAL-TC
			ScmPrtOutputOffsetStackingType
				FROM SAMSUNG-PRINTER-EXT-TC
			OBJECT-GROUP, MODULE-COMPLIANCE
				FROM SNMPv2-CONF
			Integer32, OBJECT-TYPE, MODULE-IDENTITY
				FROM SNMPv2-SMI
			RowStatus, DisplayString
				FROM SNMPv2-TC;


--         Module:  Printer MIB
-- File: SamsungPrint.mib
-- Editors: wono.song@samsung.com
-- Date:    July 17, 2004
-- Version: 1.00
-- RFC 1442/1902/2578
-- RFC 1443/1903/2579
-- RFC 1444/1904/2580
-- Successor to RFC 1759
-- 17 Jul 2004
-- July 17, 1904 at 00:00 GMT
-- July 17, 1904 at 00:00 GMT
-- July 17, 1904 at 00:00 GMT
		scmPrintMIB MODULE-IDENTITY
			LAST-UPDATED "190407170000Z"		-- July 17, 1904 at 00:00 GMT
			ORGANIZATION
				"Samsung Common Management Interface Working Group"
			CONTACT-INFO
				"
				SCMI Editors
				E-Mail:       wono.song@samsung.com

				--
				--
				"
			DESCRIPTION
				"
				Version:    1.00


				Samsung SCMI Extension to IETF Printer MIB Module.
				This Module provides extension to the IETF Printer MIB.

				Copyright (C) 2003-2004 Samsung Corporation. All Rights Reserved."
			::= { samsungCommonMIB 55 }



--
-- Node definitions
--

--  Node definitions
--
-- Node definitions
--
-- Groups in the SAMSUNG-PRINTER-EXT-MIB
--
-- 1.3.6.1.4.1.236.11.5.11.55.1
		-- 1.3.6.1.4.1.236.11.5.11.55.1
		scmPrtBase OBJECT IDENTIFIER ::= { scmPrintMIB 1 }

--   1.3.6.1.4.1.236.11.5.11.55.1.2
		-- 1.3.6.1.4.1.236.11.5.11.55.1.2
		scmPrtBaseTable OBJECT-TYPE
			SYNTAX SEQUENCE OF ScmPrtBaseEntry
			MAX-ACCESS not-accessible
			STATUS current
			DESCRIPTION
				"A table of general counters and information for ease of use of
				the SCMI Extension to IETF Printer MIB Module and the
				IETF Printer MIB on this host system.

				Usage:  The ONLY valid row in the 'scmPrtBaseTable'
				shall ALWAYS have an 'scmPrtBaseIndex' of one ('1')."
			::= { scmPrtBase 2 }

--   1.3.6.1.4.1.236.11.5.11.55.1.2.1
		-- 1.3.6.1.4.1.236.11.5.11.55.1.2.1
		scmPrtBaseEntry OBJECT-TYPE
			SYNTAX ScmPrtBaseEntry
			MAX-ACCESS not-accessible
			STATUS current
			DESCRIPTION
				"An entry of general counters and information for ease of use of
				the SCMI Extension to IETF Printer MIB Module and the
				IETF Printer MIB on this host system.

				Usage:  The ONLY valid row in the 'scmPrtBaseTable'
				shall ALWAYS have an 'scmPrtBaseIndex' of one ('1')."
			INDEX { scmPrtBaseIndex }
			::= { scmPrtBaseTable 1 }

		ScmPrtBaseEntry ::=
			SEQUENCE {
				scmPrtBaseIndex
					Ordinal32,
				scmPrtBaseRowStatus
					RowStatus
			 }

--   1.3.6.1.4.1.236.11.5.11.55.1.2.1.1
		-- 1.3.6.1.4.1.236.11.5.11.55.1.2.1.1
		scmPrtBaseIndex OBJECT-TYPE
			SYNTAX Ordinal32
			MAX-ACCESS not-accessible
			STATUS current
			DESCRIPTION
				"A unique value used by this host system to identify this
				conceptual row in the 'scmPrtBaseTable'.

				Usage:  The ONLY valid row in the 'scmPrtBaseTable'
				shall ALWAYS have an 'scmPrtBaseIndex' of one ('1')."
			::= { scmPrtBaseEntry 1 }

--   1.3.6.1.4.1.236.11.5.11.55.1.2.1.2
		-- 1.3.6.1.4.1.236.11.5.11.55.1.2.1.2
		scmPrtBaseRowStatus OBJECT-TYPE
			SYNTAX RowStatus
			MAX-ACCESS read-only
			STATUS current
			DESCRIPTION
				"This object is used to display status of the ONLY valid
				conceptual row in the 'scmPrtBaseTable'.

				Usage:  'scmPrtBaseRowStatus' is 'read-only' because
				the ONLY valid conceptual row shall NOT be deleted."
			::= { scmPrtBaseEntry 2 }

--   1.3.6.1.4.1.236.11.5.11.55.2
		-- 1.3.6.1.4.1.236.11.5.11.55.2
		scmPrtMIBConformance OBJECT IDENTIFIER ::= { scmPrintMIB 2 }

--         Compliance statements
--
-- this module
--
-- Compliance Statements for the Conditionally Mandatory Groups.
--
--
-- MIN Compliance statements for the scmPrtBaseGroup
--
-- subset of RowStatus
--
-- MIN Compliance statements for the scmPrtGeneralGroup
--
-- subset of RowStatus
--
-- MIN Compliance statements for the scmPrtInputGroup
--
-- subset of RowStatus
--
-- MIN Compliance statements for the scmPrtOutputGroup
--
-- subset of RowStatus
--
-- MAX-ACCESS statements for the scmPrtChannelGroup
--
-- subset of RowStatus
--
-- MAX-ACCESS statements for the scmPrtInterpreterGroup
--
-- subset of RowStatus
--
--
-- MAX-ACCESS statements for the scmPrtMakerGroup
--
-- subset of RowStatus
--
-- MAX-ACCESS statements for the scmPrtOperationGroup
--
-- subset of RowStatus
--
-- MAX-ACCESS statements for the scmPrtConfigurationGroup
--
-- subset of RowStatus
--
-- MAX-ACCESS statements for the scmPrtCountGroup
--
-- subset of RowStatus
--
-- MAX-ACCESS statements for the scmPrtSerialGroup
--
-- subset of RowStatus
--
-- MAX-ACCESS statements for the scmPrtPCLGroup
--
-- subset of RowStatus
--
-- MAX-ACCESS statements for the scmPrtKS5843Group
--
-- subset of RowStatus
--
-- MAX-ACCESS statements for the scmPrtKSSMGroup
--
-- subset of RowStatus
--
-- MAX-ACCESS statements for the scmPrtIPPGroup
--
-- subset of RowStatus
--
-- MAX-ACCESS statements for the scmPrtAlertGroup
--
-- subset of RowStatus
--
-- MAX-ACCESS statements for the scmPrtConsoleDisplayBufferGroup
--
-- subset of RowStatus
--
-- ##########################################
--
--
-- 1.3.6.1.4.1.236.11.5.11.55.2.1
-- this module
-- this module
-- this module
		-- 1.3.6.1.4.1.236.11.5.11.55.2.1
		scmPrtMIBCompliance MODULE-COMPLIANCE
			STATUS current
			DESCRIPTION
				"
				The compliance statement for agents that implement the
				printer MIB extension module."
			MODULE -- this module
				MANDATORY-GROUPS { scmPrtBaseGroup }
				GROUP scmPrtGeneralGroup
					DESCRIPTION
						"
						Implementation of this group is conditionally mandatory."
				GROUP scmPrtInputGroup
					DESCRIPTION
						"
						Implementation of this group is conditionally mandatory."
				GROUP scmPrtOutputGroup
					DESCRIPTION
						"
						Implementation of this group is conditionally mandatory."
				GROUP scmPrtChannelGroup
					DESCRIPTION
						"
						Implementation of this group is conditionally mandatory."
				GROUP scmPrtInterpreterGroup
					DESCRIPTION
						"
						Implementation of this group is conditionally mandatory."
				GROUP scmPrtMarkerGroup
					DESCRIPTION
						"
						Implementation of this group is conditionally mandatory."
				GROUP scmPrtOperationGroup
					DESCRIPTION
						"
						Implementation of this group is conditionally mandatory."
				GROUP scmPrtConfiguratioinGroup
					DESCRIPTION
						"
						Implementation of this group is conditionally mandatory."
				GROUP scmPrtCountGroup
					DESCRIPTION
						"
						Implementation of this group is conditionally mandatory."
				GROUP scmPrtSerialGroup
					DESCRIPTION
						"
						Implementation of this group is conditionally mandatory."
				GROUP scmPrtPCLGroup
					DESCRIPTION
						"
						Implementation of this group is conditionally mandatory."
				GROUP scmPrtKS5843Group
					DESCRIPTION
						"
						Implementation of this group is conditionally mandatory."
				GROUP scmPrtKSSMGroup
					DESCRIPTION
						"
						Implementation of this group is conditionally mandatory."
				GROUP scmPrtIPPGroup
					DESCRIPTION
						"
						Implementation of this group is conditionally mandatory."
				GROUP scmPrtAlertGroup
					DESCRIPTION
						"
						Implementation of this group is conditionally mandatory."
				GROUP scmPrtConsoleDisplayBufferGroup
					DESCRIPTION
						"
						Implementation of this group is conditionally mandatory."
			::= { scmPrtMIBConformance 1 }

--   1.3.6.1.4.1.236.11.5.11.55.2.3
		-- 1.3.6.1.4.1.236.11.5.11.55.2.3
		scmPrtMIBGroups OBJECT IDENTIFIER ::= { scmPrtMIBConformance 3 }

--   1.3.6.1.4.1.236.11.5.11.55.2.3.1
		-- 1.3.6.1.4.1.236.11.5.11.55.2.3.1
		scmPrtBaseGroup OBJECT-GROUP
			OBJECTS { scmPrtBaseRowStatus }
			STATUS current
			DESCRIPTION
				"
				The general printer group extension."
			::= { scmPrtMIBGroups 1 }

--   1.3.6.1.4.1.236.11.5.11.55.2.3.5
		-- 1.3.6.1.4.1.236.11.5.11.55.2.3.5
		scmPrtGeneralGroup OBJECT-GROUP
			OBJECTS { scmPrtGeneralRowStatus, scmPrtGeneralPrnModelName, scmPrtGeneralPrnModelVer, scmPrtGeneralPrnOSFWVer, scmPrtGeneralPrnSerialNo,
				scmPrtGeneralPrnPCLFWVer, scmPrtGeneralPrnEngFWVer, scmPrtGeneralPrnSCFFWVer, scmPrtGeneralPrnEpsonVer, scmPrtGeneralPrnPCL5eVer,
				scmPrtGeneralPrnPSFWVer, scmPrtGeneralPrnScanFWVer, scmPrtGeneralPrnKS5843Ver, scmPrtGeneralPrnKSSMVer, scmPrtGeneralPrnKS5895Ver,
				scmPrtGeneralPrnMainSystemVer, scmPrtGeneralPrnSPLVer, scmPrtGeneralPrncolorPPM, scmPrtGeneralPrnPCL5CeVer, scmPrtGeneralPrnModelDescr,
				scmPrtGeneralPrnManufacture, scmPrtGeneralPrnVendor }
			STATUS current
			DESCRIPTION
				"
				The general printer group extension."
			::= { scmPrtMIBGroups 5 }

--   1.3.6.1.4.1.236.11.5.11.55.2.3.8
		-- 1.3.6.1.4.1.236.11.5.11.55.2.3.8
		scmPrtInputGroup OBJECT-GROUP
			OBJECTS { scmPrtInputRowStatus, scmPrtInputNextPrtInputIndex, scmPrtInputUseCustomSize, scmPrtInputCustDimFeedDirDecl, scmPrtInputCustDimXFeedDirDecl,
				scmPrtInputTrayPriority, scmPrtInputPaperSize, scmPrtInputPaperSizeOptions, scmPrtInputTrayNum, scmPrtInputTrayNumOptions,
				scmPrtInputTraySwitch, scmPrtInputTraySwitchOptions, scmPrtInputLockTray, scmPrtInputLockTrayOptions, scmPrtInputPaperType,
				scmPrtInputPaperTypeOptions }
			STATUS current
			DESCRIPTION
				"
				The input group extension."
			::= { scmPrtMIBGroups 8 }

--   1.3.6.1.4.1.236.11.5.11.55.2.3.9
		-- 1.3.6.1.4.1.236.11.5.11.55.2.3.9
		scmPrtOutputGroup OBJECT-GROUP
			OBJECTS { scmPrtOutputRowStatus, scmPrtOutputNextIndex, scmPrtOutputPassword, scmPrtOutputOffsetStackingType, scmPrtOutputTrayTimeoutSupport,
				scmPrtOutputTrayTimeout, scmPrtOutputFinishier, scmPrtOutputFinishierOptions }
			STATUS current
			DESCRIPTION
				"
				The output group extension."
			::= { scmPrtMIBGroups 9 }

--   1.3.6.1.4.1.236.11.5.11.55.2.3.14
		-- 1.3.6.1.4.1.236.11.5.11.55.2.3.14
		scmPrtChannelGroup OBJECT-GROUP
			OBJECTS { scmPrtChannelRowStatus, scmPrtChannelEOJTimeout }
			STATUS current
			DESCRIPTION
				"
				The Channel group extension."
			::= { scmPrtMIBGroups 14 }

--   1.3.6.1.4.1.236.11.5.11.55.2.3.15
		-- 1.3.6.1.4.1.236.11.5.11.55.2.3.15
		scmPrtInterpreterGroup OBJECT-GROUP
			OBJECTS { scmPrtInterpRowStatus, scmPrtInterpJobCopiesDefault, scmPrtInterpLineTerm, scmPrtInterpProcessBarcodes, scmPrtInterpOrientation,
				scmPrtInterpOrientationOptions, scmPrtInterpreterCopyNum, scmPrtInterpreterEmulation, scmPrtInterpreterEmulationOptions }
			STATUS current
			DESCRIPTION
				"
				The interpreter group extension."
			::= { scmPrtMIBGroups 15 }

--   1.3.6.1.4.1.236.11.5.11.55.2.3.17
		-- 1.3.6.1.4.1.236.11.5.11.55.2.3.17
		scmPrtMarkerGroup OBJECT-GROUP
			OBJECTS { scmPrtMarkerResolution, scmPrtMarkerResolutionOptions, scmPrtMarkerTonerIndex, scmPrtMarkerTonerColor, scmPrtMarkerTonerColorDescription,
				scmPrtMarkerSrt, scmPrtMarkerMarginUnit, scmPrtMarkerTonerLevel, scmPrtMarkerDensity, scmPrtMarkerSrtOptions,
				scmPrtMarkerDensityOptions, scmPrtMarkerSmetMode, scmPrtMarkerSmetModeOptions, scmPrtMarkerduplexTopMargin, scmPrtMarkerduplexLeftMargin,
				scmPrtMarkerShortEdgeBindingMargin, scmPrtMarkerLongEdgeBindingMargin, scmPrtMarkerTonerSave, scmPrtMarkerTonerSaveOptions, scmPrtMarkerTonerOutAction,
				scmPrtMarkerTonerOutActionOptions }
			STATUS current
			DESCRIPTION
				"
				The Marker Group."
			::= { scmPrtMIBGroups 17 }

--   1.3.6.1.4.1.236.11.5.11.55.2.3.18
		-- 1.3.6.1.4.1.236.11.5.11.55.2.3.18
		scmPrtOperationGroup OBJECT-GROUP
			OBJECTS { scmPrtOperationJobCancel, scmPrtOperarionMenuClear, scmPrtOperationMenuClearOptions, scmPrtOperationFuserClean, scmPrtOperationFuserCleanOptions,
				scmPrtOperationOpcClean, scmPrtOperationOpcCleanOptions, scmPrtOperationTestPrtRequest, scmPrtOperationPrintFontRequest, scmPrtOperationIndex,
				scmPrtOperationPrintBlackOnly }
			STATUS current
			DESCRIPTION
				"Description."
			::= { scmPrtMIBGroups 18 }

--   1.3.6.1.4.1.236.11.5.11.55.2.3.19
		-- 1.3.6.1.4.1.236.11.5.11.55.2.3.19
		scmPrtConfiguratioinGroup OBJECT-GROUP
			OBJECTS { scmPrtConfigurationPowerSave, scmPrtConfigurationPowerSaveOptions, scmPrtConfigurationAutocont, scmPrtConfigurationAutoCountOptions, scmPrtConfigurationJam2Recover,
				scmPrtConfigurationJam2RecOptions, scmPrtConfigurationAltitudeAction, scmPrtConfigurationAltitudeActionOptions, scmPrtConfigurationIndex }
			STATUS current
			DESCRIPTION
				"Description."
			::= { scmPrtMIBGroups 19 }

--   1.3.6.1.4.1.236.11.5.11.55.2.3.20
		-- 1.3.6.1.4.1.236.11.5.11.55.2.3.20
		scmPrtCountGroup OBJECT-GROUP
			OBJECTS { scmPrtCountDrumImageCount, scmPrtCountDrumImageCountReset, scmPrtCountTransferImageCount, scmPrtCountTransferImageCountReset, scmPrtCountFuserImageCount,
				scmPrtCountFuserImageCountReset, scmPrtCountTwoRollerCount, scmPrtCountTwoRollerReset, scmPrtCountPickupMPCount, scmPrtCountPickupMPReset,
				scmPrtCountPickupTray1Count, scmPrtCountPickupTray1Reset, scmPrtCountPickupTray2Count, scmPrtCountPickupTray2Reset, scmPrtCountIndex,
				scmPrtCountType, scmPrtCountMediaSize, scmPrtCountColorant, scmPrtCountDuplex, scmPrtCountUnit,
				scmPrtCountResolution, scmPrtCountValue, scmPrtCountDeviceType }
			STATUS current
			DESCRIPTION
				"Description."
			::= { scmPrtMIBGroups 20 }

--   1.3.6.1.4.1.236.11.5.11.55.2.3.21
		-- 1.3.6.1.4.1.236.11.5.11.55.2.3.21
		scmPrtSerialGroup OBJECT-GROUP
			OBJECTS { scmPrtSerialNbaudRate, scmPrtSerialBrOptions, scmPrtSerialBobuxon, scmPrtSerialBobuxonOptions }
			STATUS current
			DESCRIPTION
				"
				The Serial group."
			::= { scmPrtMIBGroups 21 }

--   1.3.6.1.4.1.236.11.5.11.55.2.3.22
		-- 1.3.6.1.4.1.236.11.5.11.55.2.3.22
		scmPrtPCLGroup OBJECT-GROUP
			OBJECTS { scmPrtPCLFont, scmPrtPCLSymbolSet, scmPrtPCLFormLine, scmPrtPCLPitch, scmPrtPCLPointSize,
				scmPrtPCLCourier, scmPrtPCLCourierOptions, scmPrtPCLAppendCR, scmPrtPCLAppendCROptions, scmPrtPCLWideA4,
				scmPrtPCLWideA4Options, scmPrtPCLTopMargin, scmPrtPCLLeftMargin, scmPrtPCLIndex }
			STATUS current
			DESCRIPTION
				"Description."
			::= { scmPrtMIBGroups 22 }

--   1.3.6.1.4.1.236.11.5.11.55.2.3.23
		-- 1.3.6.1.4.1.236.11.5.11.55.2.3.23
		scmPrtKS5843Group OBJECT-GROUP
			OBJECTS { scmPrtKS5843Font, scmPrtKS5843FontOptions, scmPrtKS5843Code, scmPrtKS5843CodeOptions, scmPrtKS5843cpi,
				scmPrtKS5843cpiOptions, scmPrtKS5843Lines, scmPrtKS5843Zoom, scmPrtKS5843AutoWrap, scmPrtKS5843AutoWrapOptions,
				scmPrtKS5843Topmargin, scmPrtKS5843Sitemode }
			STATUS current
			DESCRIPTION
				"Description."
			::= { scmPrtMIBGroups 23 }

--   1.3.6.1.4.1.236.11.5.11.55.2.3.24
		-- 1.3.6.1.4.1.236.11.5.11.55.2.3.24
		scmPrtKSSMGroup OBJECT-GROUP
			OBJECTS { scmPrtKSSMFont, scmPrtKSSMFontOptions, scmPrtKSSMCode, scmPrtKSSMCodeOptions, scmPrtKSSMCPI,
				scmPrtKSSMCPIOptions, scmPrtKSSMLines, scmPrtKSSMZoom, scmPrtKSSMAutoWrap, scmPrtKSSMAutoWrapOptions,
				scmPrtKSSMTopMargin, scmPrtKSSMSiteMode }
			STATUS current
			DESCRIPTION
				"Description."
			::= { scmPrtMIBGroups 24 }

--   1.3.6.1.4.1.236.11.5.11.55.2.3.25
		-- 1.3.6.1.4.1.236.11.5.11.55.2.3.25
		scmPrtIPPGroup OBJECT-GROUP
			OBJECTS { scmPrtIPPColorSupported, scmPrtIPPJobKOctetsSupportedLBound, scmPrtIPPJobKOctetsSupportedUBound, scmPrtIPPJobImpressionsSupportedLBound, scmPrtIPPJobImpressionsSupportedUBound,
				scmPrtIPPJobMediaSheetsSupportedLBound, scmPrtIPPJobMediaSheetsSupportedUBound, scmPrtIPPJobSheets, scmPrtIPPCollatedCopiesLBound, scmPrtIPPCollatedCopiesUBound,
				scmPrtIPPCollatedCopies, scmPrtIPPFinishingsSupported, scmPrtIPPFinishings, scmPrtIPPPageRangesSupported, scmPrtIPPNumberUp,
				scmPrtIPPNumberUpOptions, scmPrtIPPPrintQuality, scmPrtIPPPrintQualityOptions, scmPrtIPPJobKOctetsProcessed, scmPrtIPPJobImpressionsCompleted,
				scmPrtIPPJobMediaSheetsCompleted }
			STATUS current
			DESCRIPTION
				"Description."
			::= { scmPrtMIBGroups 25 }

--   1.3.6.1.4.1.236.11.5.11.55.2.3.26
		-- 1.3.6.1.4.1.236.11.5.11.55.2.3.26
		scmPrtAlertGroup OBJECT-GROUP
			OBJECTS { scmPrtAlertAlarmShortage, scmPrtAlertAlarmShortageOptions }
			STATUS current
			DESCRIPTION
				"Description."
			::= { scmPrtMIBGroups 26 }

--   1.3.6.1.4.1.236.11.5.11.55.2.3.27
		-- 1.3.6.1.4.1.236.11.5.11.55.2.3.27
		scmPrtConsoleDisplayBufferGroup OBJECT-GROUP
			OBJECTS { scmPrtConsoleDisplayBufferLcdLangType, scmPrtConsoleDisplayBufferLcdLangTypeOptions }
			STATUS current
			DESCRIPTION
				"Description."
			::= { scmPrtMIBGroups 27 }

--   1.3.6.1.4.1.236.11.5.11.55.5
		-- 1.3.6.1.4.1.236.11.5.11.55.5
		scmPrtGeneral OBJECT IDENTIFIER ::= { scmPrintMIB 5 }

--   1.3.6.1.4.1.236.11.5.11.55.5.1
		-- 1.3.6.1.4.1.236.11.5.11.55.5.1
		scmPrtGeneralSimple OBJECT IDENTIFIER ::= { scmPrtGeneral 1 }

--   1.3.6.1.4.1.236.11.5.11.55.5.1.1
		-- 1.3.6.1.4.1.236.11.5.11.55.5.1.1
		scmPrtGeneralPrnModelName OBJECT-TYPE
			SYNTAX DisplayString (SIZE (0..31))
			MAX-ACCESS read-only
			STATUS current
			DESCRIPTION
				" Represent the printer model name currently being
				connected with NPC."
			::= { scmPrtGeneralSimple 1 }

--   1.3.6.1.4.1.236.11.5.11.55.5.1.2
		-- 1.3.6.1.4.1.236.11.5.11.55.5.1.2
		scmPrtGeneralPrnOSFWVer OBJECT-TYPE
			SYNTAX DisplayString (SIZE (0..31))
			MAX-ACCESS read-only
			STATUS current
			DESCRIPTION
				" Printer Software version number."
			::= { scmPrtGeneralSimple 2 }

--   1.3.6.1.4.1.236.11.5.11.55.5.1.3
		-- 1.3.6.1.4.1.236.11.5.11.55.5.1.3
		scmPrtGeneralPrnModelVer OBJECT-TYPE
			SYNTAX OCTET STRING (SIZE (0..31))
			MAX-ACCESS read-only
			STATUS current
			DESCRIPTION
				" Model version number."
			::= { scmPrtGeneralSimple 3 }

--   1.3.6.1.4.1.236.11.5.11.55.5.1.4
		-- 1.3.6.1.4.1.236.11.5.11.55.5.1.4
		scmPrtGeneralPrnSerialNo OBJECT-TYPE
			SYNTAX DisplayString (SIZE (0..31))
			MAX-ACCESS read-only
			STATUS current
			DESCRIPTION
				" Printer Serial number."
			::= { scmPrtGeneralSimple 4 }

--   1.3.6.1.4.1.236.11.5.11.55.5.1.5
		-- 1.3.6.1.4.1.236.11.5.11.55.5.1.5
		scmPrtGeneralPrnModelDescr OBJECT-TYPE
			SYNTAX OCTET STRING (SIZE (0..255))
			MAX-ACCESS read-only
			STATUS current
			DESCRIPTION
				" Printer HDD Size."
			::= { scmPrtGeneralSimple 5 }

--   1.3.6.1.4.1.236.11.5.11.55.5.1.6
		-- 1.3.6.1.4.1.236.11.5.11.55.5.1.6
		scmPrtGeneralPrnManufacture OBJECT-TYPE
			SYNTAX OCTET STRING (SIZE (0..31))
			MAX-ACCESS read-only
			STATUS current
			DESCRIPTION
				" Printer DRAM Size."
			::= { scmPrtGeneralSimple 6 }

--   1.3.6.1.4.1.236.11.5.11.55.5.1.7
		-- 1.3.6.1.4.1.236.11.5.11.55.5.1.7
		scmPrtGeneralPrnVendor OBJECT-TYPE
			SYNTAX OCTET STRING (SIZE (0..31))
			MAX-ACCESS read-only
			STATUS current
			DESCRIPTION
				" Print Per Minute"
			::= { scmPrtGeneralSimple 7 }

--   1.3.6.1.4.1.236.11.5.11.55.5.1.11
		-- 1.3.6.1.4.1.236.11.5.11.55.5.1.11
		scmPrtGeneralPrnPCLFWVer OBJECT-TYPE
			SYNTAX DisplayString (SIZE (0..31))
			MAX-ACCESS read-only
			STATUS current
			DESCRIPTION
				"PCL Version information of printer"
			::= { scmPrtGeneralSimple 11 }

--   1.3.6.1.4.1.236.11.5.11.55.5.1.12
		-- 1.3.6.1.4.1.236.11.5.11.55.5.1.12
		scmPrtGeneralPrnEngFWVer OBJECT-TYPE
			SYNTAX DisplayString (SIZE (0..31))
			MAX-ACCESS read-only
			STATUS current
			DESCRIPTION
				" Print Engine FW Version"
			::= { scmPrtGeneralSimple 12 }

--   1.3.6.1.4.1.236.11.5.11.55.5.1.13
		-- 1.3.6.1.4.1.236.11.5.11.55.5.1.13
		scmPrtGeneralPrnSCFFWVer OBJECT-TYPE
			SYNTAX DisplayString (SIZE (0..31))
			MAX-ACCESS read-only
			STATUS current
			DESCRIPTION
				"Print SCF FW Version"
			::= { scmPrtGeneralSimple 13 }

--   1.3.6.1.4.1.236.11.5.11.55.5.1.14
		-- 1.3.6.1.4.1.236.11.5.11.55.5.1.14
		scmPrtGeneralPrnEpsonVer OBJECT-TYPE
			SYNTAX DisplayString (SIZE (0..31))
			MAX-ACCESS read-only
			STATUS current
			DESCRIPTION
				" Print Epson Version"
			::= { scmPrtGeneralSimple 14 }

--   1.3.6.1.4.1.236.11.5.11.55.5.1.15
		-- 1.3.6.1.4.1.236.11.5.11.55.5.1.15
		scmPrtGeneralPrnPCL5eVer OBJECT-TYPE
			SYNTAX DisplayString (SIZE (0..31))
			MAX-ACCESS read-only
			STATUS current
			DESCRIPTION
				" Print PCL5e Version"
			::= { scmPrtGeneralSimple 15 }

--   1.3.6.1.4.1.236.11.5.11.55.5.1.16
		-- 1.3.6.1.4.1.236.11.5.11.55.5.1.16
		scmPrtGeneralPrnPSFWVer OBJECT-TYPE
			SYNTAX DisplayString (SIZE (0..31))
			MAX-ACCESS read-only
			STATUS current
			DESCRIPTION
				"PS Version information of printer"
			::= { scmPrtGeneralSimple 16 }

--   1.3.6.1.4.1.236.11.5.11.55.5.1.17
		-- 1.3.6.1.4.1.236.11.5.11.55.5.1.17
		scmPrtGeneralPrnScanFWVer OBJECT-TYPE
			SYNTAX DisplayString (SIZE (0..31))
			MAX-ACCESS read-only
			STATUS current
			DESCRIPTION
				" Scanner FW Version"
			::= { scmPrtGeneralSimple 17 }

--   1.3.6.1.4.1.236.11.5.11.55.5.1.18
		-- 1.3.6.1.4.1.236.11.5.11.55.5.1.18
		scmPrtGeneralPrnKS5843Ver OBJECT-TYPE
			SYNTAX DisplayString (SIZE (0..31))
			MAX-ACCESS read-only
			STATUS current
			DESCRIPTION
				" Printer KS5843 Version."
			::= { scmPrtGeneralSimple 18 }

--   1.3.6.1.4.1.236.11.5.11.55.5.1.19
		-- 1.3.6.1.4.1.236.11.5.11.55.5.1.19
		scmPrtGeneralPrnKSSMVer OBJECT-TYPE
			SYNTAX DisplayString (SIZE (0..31))
			MAX-ACCESS read-only
			STATUS current
			DESCRIPTION
				" Printer KSSM Version."
			::= { scmPrtGeneralSimple 19 }

--   1.3.6.1.4.1.236.11.5.11.55.5.1.20
		-- 1.3.6.1.4.1.236.11.5.11.55.5.1.20
		scmPrtGeneralPrnKS5895Ver OBJECT-TYPE
			SYNTAX DisplayString (SIZE (0..31))
			MAX-ACCESS read-only
			STATUS current
			DESCRIPTION
				" Printer KS5895 Version."
			::= { scmPrtGeneralSimple 20 }

--   1.3.6.1.4.1.236.11.5.11.55.5.1.21
		-- 1.3.6.1.4.1.236.11.5.11.55.5.1.21
		scmPrtGeneralPrnMainSystemVer OBJECT-TYPE
			SYNTAX DisplayString (SIZE (0..31))
			MAX-ACCESS read-only
			STATUS current
			DESCRIPTION
				" Printer Main System Versio."
			::= { scmPrtGeneralSimple 21 }

--   1.3.6.1.4.1.236.11.5.11.55.5.1.22
		-- 1.3.6.1.4.1.236.11.5.11.55.5.1.22
		scmPrtGeneralPrnSPLVer OBJECT-TYPE
			SYNTAX DisplayString (SIZE (0..31))
			MAX-ACCESS read-only
			STATUS current
			DESCRIPTION
				" Print SPL Version"
			::= { scmPrtGeneralSimple 22 }

--   1.3.6.1.4.1.236.11.5.11.55.5.1.23
		-- 1.3.6.1.4.1.236.11.5.11.55.5.1.23
		scmPrtGeneralPrncolorPPM OBJECT-TYPE
			SYNTAX INTEGER (0..255)
			MAX-ACCESS read-only
			STATUS current
			DESCRIPTION
				" Color Printing PPM"
			::= { scmPrtGeneralSimple 23 }

--   1.3.6.1.4.1.236.11.5.11.55.5.1.24
		-- 1.3.6.1.4.1.236.11.5.11.55.5.1.24
		scmPrtGeneralPrnPCL5CeVer OBJECT-TYPE
			SYNTAX DisplayString (SIZE (0..31))
			MAX-ACCESS read-only
			STATUS current
			DESCRIPTION
				" Print PCL5Ce Version"
			::= { scmPrtGeneralSimple 24 }

--   1.3.6.1.4.1.236.11.5.11.55.5.2
		-- 1.3.6.1.4.1.236.11.5.11.55.5.2
		scmPrtGeneralTable OBJECT-TYPE
			SYNTAX SEQUENCE OF ScmPrtGeneralEntry
			MAX-ACCESS not-accessible
			STATUS current
			DESCRIPTION
				"
				A table of general information per printer.
				This table augments the prtGeneralTable."
			::= { scmPrtGeneral 2 }

--   1.3.6.1.4.1.236.11.5.11.55.5.2.1
		-- 1.3.6.1.4.1.236.11.5.11.55.5.2.1
		scmPrtGeneralEntry OBJECT-TYPE
			SYNTAX ScmPrtGeneralEntry
			MAX-ACCESS not-accessible
			STATUS current
			DESCRIPTION
				"
				An entry exists in this table for each device entry in the
				hostmib device table whose type is printer."
			AUGMENTS { prtGeneralEntry }
			::= { scmPrtGeneralTable 1 }

		ScmPrtGeneralEntry ::=
			SEQUENCE {
				scmPrtGeneralRowStatus
					RowStatus
			 }

--         scmPrtGeneralGroup
-- scmPrtGeneralAuxSheetPackage      Cardinal32,
-- scmPrtGeneralManualFeedTimeout    Integer32,
-- scmPrtGeneralInputAutoSwitch      PresentOnOff,
-- scmPrtGeneralOutputAutoSwitch     PresentOnOff,
--
-- scmPrtGeneralMediumClassDefault   ScmPrtMediumClassType,
-- scmPrtGeneralDarknessLevels       Cardinal32,
-- scmPrtGeneralDarknessLevelNorm    Cardinal32,
-- scmPrtGeneralDarknessLevelDflt    Integer32,
-- scmPrtGeneralHexDumpEnable        PresentOnOff,
-- scmPrtGeneralTonerLowStop         PresentOnOff,
--
-- scmPrtGeneralAuxSheetGroup
-- scmPrtGeneralStartupPage          PresentOnOff,
-- scmPrtGeneralBannerPage           PresentOnOff,
-- scmPrtGeneralEndBannerPage        PresentOnOff,
--
-- scmPrtGeneralProdSpecificGroup
-- scmPrtGeneralScanlineCompaction   PresentOnOff,
-- scmPrtGeneralMonoPrintOptimization ScmPrtGeneralMonoPrintOpt
--
-- 1.3.6.1.4.1.236.11.5.11.55.5.2.1.1
		-- 1.3.6.1.4.1.236.11.5.11.55.5.2.1.1
		scmPrtGeneralRowStatus OBJECT-TYPE
			SYNTAX RowStatus
			MAX-ACCESS read-create
			STATUS current
			DESCRIPTION
				"
				Manages the status of this conceptual row in the
				scmPrtGeneralTable."
			::= { scmPrtGeneralEntry 1 }

--   1.3.6.1.4.1.236.11.5.11.55.8
		-- 1.3.6.1.4.1.236.11.5.11.55.8
		scmPrtInput OBJECT IDENTIFIER ::= { scmPrintMIB 8 }

--   1.3.6.1.4.1.236.11.5.11.55.8.1
		-- 1.3.6.1.4.1.236.11.5.11.55.8.1
		scmPrtInputSimple OBJECT IDENTIFIER ::= { scmPrtInput 1 }

--   1.3.6.1.4.1.236.11.5.11.55.8.1.1
		-- 1.3.6.1.4.1.236.11.5.11.55.8.1.1
		scmPrtInputTraySwitch OBJECT-TYPE
			SYNTAX Integer32
			MAX-ACCESS read-write
			STATUS current
			DESCRIPTION
				"
				if language is set to AUTO, this options can
				the printer anlyzes the stream of data being
				sent to determine which language is being used
				by the printer job, and the printer's emulation
				language automatically be switched if this options
				is set. "
			::= { scmPrtInputSimple 1 }

--   1.3.6.1.4.1.236.11.5.11.55.8.1.2
		-- 1.3.6.1.4.1.236.11.5.11.55.8.1.2
		scmPrtInputTraySwitchOptions OBJECT-TYPE
			SYNTAX INTEGER
				{
				off(1),
				auto(2),
				tray1(4),
				tray2(8)
				}
			MAX-ACCESS read-write
			STATUS current
			DESCRIPTION
				"
				available options of the model"
			::= { scmPrtInputSimple 2 }

--   1.3.6.1.4.1.236.11.5.11.55.8.1.3
		-- 1.3.6.1.4.1.236.11.5.11.55.8.1.3
		scmPrtInputLockTray OBJECT-TYPE
			SYNTAX Integer32
			MAX-ACCESS read-write
			STATUS current
			DESCRIPTION
				"
				Trays and combination trays can be locked out of
				the paper selection process. The available options
				depend on the configuration of MP tray."
			::= { scmPrtInputSimple 3 }

--   1.3.6.1.4.1.236.11.5.11.55.8.1.4
		-- 1.3.6.1.4.1.236.11.5.11.55.8.1.4
		scmPrtInputLockTrayOptions OBJECT-TYPE
			SYNTAX Integer32
			MAX-ACCESS read-write
			STATUS current
			DESCRIPTION
				"
				available options of the model"
			::= { scmPrtInputSimple 4 }

--   1.3.6.1.4.1.236.11.5.11.55.8.1.5
		-- 1.3.6.1.4.1.236.11.5.11.55.8.1.5
		scmPrtInputPaperType OBJECT-TYPE
			SYNTAX Integer32
			MAX-ACCESS read-write
			STATUS current
			DESCRIPTION
				"
				It determines paper thickness."
			::= { scmPrtInputSimple 5 }

--   1.3.6.1.4.1.236.11.5.11.55.8.1.6
		-- 1.3.6.1.4.1.236.11.5.11.55.8.1.6
		scmPrtInputPaperTypeOptions OBJECT-TYPE
			SYNTAX INTEGER
				{
				normal(1),
				thick(2),
				wet(4),
				transparency(8)
				}
			MAX-ACCESS read-write
			STATUS current
			DESCRIPTION
				"
				available options of current model"
			::= { scmPrtInputSimple 6 }

--   1.3.6.1.4.1.236.11.5.11.55.8.2
		-- 1.3.6.1.4.1.236.11.5.11.55.8.2
		scmPrtInputTable OBJECT-TYPE
			SYNTAX SEQUENCE OF ScmPrtInputEntry
			MAX-ACCESS not-accessible
			STATUS current
			DESCRIPTION
				"This table logically augments the Printer MIB's prtInputTable."
			::= { scmPrtInput 2 }

--   1.3.6.1.4.1.236.11.5.11.55.8.2.1
		-- 1.3.6.1.4.1.236.11.5.11.55.8.2.1
		scmPrtInputEntry OBJECT-TYPE
			SYNTAX ScmPrtInputEntry
			MAX-ACCESS not-accessible
			STATUS current
			DESCRIPTION
				"Entries may exist for each entry in the prtInputTable."
			AUGMENTS { prtInputEntry }
			::= { scmPrtInputTable 1 }

		ScmPrtInputEntry ::=
			SEQUENCE {
				scmPrtInputRowStatus
					RowStatus,
				scmPrtInputNextPrtInputIndex
					Integer32,
				scmPrtInputUseCustomSize
					PresentOnOff,
				scmPrtInputCustDimFeedDirDecl
					Integer32,
				scmPrtInputCustDimXFeedDirDecl
					Integer32,
				scmPrtInputTrayPriority
					Integer32,
				scmPrtInputPaperSize
					Integer32,
				scmPrtInputPaperSizeOptions
					INTEGER,
				scmPrtInputTrayNum
					Integer32,
				scmPrtInputTrayNumOptions
					Integer32
			 }

--   1.3.6.1.4.1.236.11.5.11.55.8.2.1.1
		-- 1.3.6.1.4.1.236.11.5.11.55.8.2.1.1
		scmPrtInputRowStatus OBJECT-TYPE
			SYNTAX RowStatus
			MAX-ACCESS read-create
			STATUS current
			DESCRIPTION
				"
				Manages the status of this conceptual row
				in the scmPrtInputTable."
			::= { scmPrtInputEntry 1 }

--   1.3.6.1.4.1.236.11.5.11.55.8.2.1.2
		-- 1.3.6.1.4.1.236.11.5.11.55.8.2.1.2
		scmPrtInputNextPrtInputIndex OBJECT-TYPE
			SYNTAX Integer32
			MAX-ACCESS read-create
			STATUS current
			DESCRIPTION
				"
				The value of prtInputIndex corresponding to the input subunit


				which will be used when this input subunit is emptied.

				The value of zero indicates that auto input switching will not
				occur when this input subunit is emptied.

				Two different mechanisms for input tray switching,
				scmPrtNextPrtInputIndex and scmPrtInputAliasGroup, are provided.
				A device agent may make use of one or the other, none, or both.
				Use the model that fits best for the given application.

				Usage:  Conforming management agents, which ALSO implement the
				the Printer MIB v2, SHALL set 'scmPrtInputNextPrtInputIndex'
				to the SAME value as 'prtInputNextIndex' (i.e., the values of
				these two objects SHALL be interlocked)."
			REFERENCE
				"
				See: scmPrtInputAliasGroup
				See: scmPrtInterpTraySwitch"
			DEFVAL { 0 }
			::= { scmPrtInputEntry 2 }

--         not specified
-- 1.3.6.1.4.1.236.11.5.11.55.8.2.1.3
		-- 1.3.6.1.4.1.236.11.5.11.55.8.2.1.3
		scmPrtInputUseCustomSize OBJECT-TYPE
			SYNTAX PresentOnOff
			MAX-ACCESS read-create
			STATUS current
			DESCRIPTION
				"
				Specifies how this input subunit determines the paper size to
				use.

				If the value is 'Off' this input subunit uses the paper size
				automatically sensed by the subunit.

				If the value is 'On' this input subunit uses the custom
				dimensions provided by scmPrtInputCustDimFeedDirDecl and
				scmPrtInputCustDimXFeedDirDecl."
			REFERENCE
				"
				See: scmPrtInputCustDimFeedDirDecl
				See: scmPrtInputCustDimXFeedDirDecl"
			DEFVAL { other }
			::= { scmPrtInputEntry 3 }

--   1.3.6.1.4.1.236.11.5.11.55.8.2.1.4
		-- 1.3.6.1.4.1.236.11.5.11.55.8.2.1.4
		scmPrtInputCustDimFeedDirDecl OBJECT-TYPE
			SYNTAX Integer32
			MAX-ACCESS read-create
			STATUS current
			DESCRIPTION
				"
				Provides the dimension, in the feed direction, of the media in
				this input subunit, when the value of scmPrtInputUseCustomSize
				is set to 'On'.

				When scmPrtInputUseCustomSize is set to On, this value is copied
				to prtInputMediaDimFeedDirDeclared and
				prtInputMediaDimFeedDirChosen."
			REFERENCE
				"
				See: scmPrtInputUseCustomSize


				See: scmPrtInputCustDimXFeedDirDecl"
			DEFVAL { 0 }
			::= { scmPrtInputEntry 4 }

--   1.3.6.1.4.1.236.11.5.11.55.8.2.1.5
		-- 1.3.6.1.4.1.236.11.5.11.55.8.2.1.5
		scmPrtInputCustDimXFeedDirDecl OBJECT-TYPE
			SYNTAX Integer32
			MAX-ACCESS read-create
			STATUS current
			DESCRIPTION
				"
				Provides the dimension, in the feed direction, of the media in
				this input subunit, when the value of scmPrtInputUseCustomSize
				is set to 'On'.

				When scmPrtInputUseCustomSize is set to 'On', this value is
				copied to prtInputMediaDimFeedDirDeclared and
				prtInputMediaDimFeedDirChosen."
			REFERENCE
				"
				See: scmPrtInputUseCustomSize
				See: scmPrtInputCustDimFeedDirDecl"
			DEFVAL { 0 }
			::= { scmPrtInputEntry 5 }

--         unspecified device priority
-- 1.3.6.1.4.1.236.11.5.11.55.8.2.1.6
		-- 1.3.6.1.4.1.236.11.5.11.55.8.2.1.6
		scmPrtInputTrayPriority OBJECT-TYPE
			SYNTAX Integer32
			MAX-ACCESS read-create
			STATUS current
			DESCRIPTION
				"
				The current priority of this tray.  This value/mechanism
				is independent of scmPrtNextPrtInputIndex and
				scmPrtInputAliasGroup.

				Usage:  The priority of this device, where '0' is
				unspecified (default), '1' is lowest, and '100' is highest."
			REFERENCE
				"
				See: scmPrtNextPrtInputIndex
				See: scmPrtInputAliasGroup"
			DEFVAL { 0 }
			::= { scmPrtInputEntry 6 }

--   1.3.6.1.4.1.236.11.5.11.55.8.2.1.7
		-- 1.3.6.1.4.1.236.11.5.11.55.8.2.1.7
		scmPrtInputPaperSize OBJECT-TYPE
			SYNTAX Integer32
			MAX-ACCESS read-create
			STATUS current
			DESCRIPTION
				"
				Value of Paper size for printing.
				Some printer such like ML6060 or Modena have a  4 bytes data length.
				So, to distinguish these models we have to check model id or version."
			::= { scmPrtInputEntry 7 }

--   1.3.6.1.4.1.236.11.5.11.55.8.2.1.8
		-- 1.3.6.1.4.1.236.11.5.11.55.8.2.1.8
		scmPrtInputPaperSizeOptions OBJECT-TYPE
			SYNTAX INTEGER
				{
				letter(1),
				legal(2),
				a4(4),
				executive(8),
				jisB5(16),
				isoB5(32),
				com10(64),
				monarch(128),
				dl(256),
				c5(512),
				postA6(1024),
				c6(2048),
				folio(4096),
				a5(8192),
				statement(16384),
				a6(32768),
				ledger(65536),
				a3(131072),
				jisB4(262144),
				jpost(524288),
				jpostd(1048576),
				custom(2097152),
				letterP(4194304),
				a4P(8388608),
				jisB5P(16777216),
				a5P(33554432),
				executiveP(67108864),
				statementP(134217728),
				a3Over(268435456),
				b5Envelope(536870912)
				}
			MAX-ACCESS read-only
			STATUS current
			DESCRIPTION
				"
				Paper size options that are available in this model.
				Some printer such like ML6060 or Modena have a  4 bytes data length.
				So, to distinguish these models we have to check model id or version. "
			::= { scmPrtInputEntry 8 }

--   1.3.6.1.4.1.236.11.5.11.55.8.2.1.9
		-- 1.3.6.1.4.1.236.11.5.11.55.8.2.1.9
		scmPrtInputTrayNum OBJECT-TYPE
			SYNTAX Integer32
			MAX-ACCESS read-create
			STATUS current
			DESCRIPTION
				"
				It can select the type of paper tray. The types of
				tray can be varied according to the printer model"
			::= { scmPrtInputEntry 9 }

--   1.3.6.1.4.1.236.11.5.11.55.8.2.1.10
		-- 1.3.6.1.4.1.236.11.5.11.55.8.2.1.10
		scmPrtInputTrayNumOptions OBJECT-TYPE
			SYNTAX Integer32
			MAX-ACCESS read-create
			STATUS current
			DESCRIPTION
				"
				available options of tray types"
			::= { scmPrtInputEntry 10 }

--   1.3.6.1.4.1.236.11.5.11.55.9
		-- 1.3.6.1.4.1.236.11.5.11.55.9
		scmPrtOutput OBJECT IDENTIFIER ::= { scmPrintMIB 9 }

--         The Printer MIB Output group extension (scmPrtOutputGroup)
--
-- This group logically augments the Printer MIB's prtOutput group.
--
-- Implementation of every object in this group is conditionally
-- mandatory:  if the SNMP agent implements the semantics of any of
-- these objects outside of the SCMI MIB, the agent shall also implement
-- this group in order to claim SCMI conformance.
--
-- 1.3.6.1.4.1.236.11.5.11.55.9.1
		-- 1.3.6.1.4.1.236.11.5.11.55.9.1
		scmPrtOutputTable OBJECT-TYPE
			SYNTAX SEQUENCE OF ScmPrtOutputEntry
			MAX-ACCESS not-accessible
			STATUS current
			DESCRIPTION
				"
				This table logically augments the prtOutputTable in the
				Printer MIB."
			::= { scmPrtOutput 1 }

--   1.3.6.1.4.1.236.11.5.11.55.9.1.1
		-- 1.3.6.1.4.1.236.11.5.11.55.9.1.1
		scmPrtOutputEntry OBJECT-TYPE
			SYNTAX ScmPrtOutputEntry
			MAX-ACCESS not-accessible
			STATUS current
			DESCRIPTION
				"
				Entries may exist for each entry in the prtOutputTable."
			AUGMENTS { prtOutputEntry }
			::= { scmPrtOutputTable 1 }

		ScmPrtOutputEntry ::=
			SEQUENCE {
				scmPrtOutputRowStatus
					RowStatus,
				scmPrtOutputNextIndex
					Integer32,
				scmPrtOutputPassword
					OCTET STRING,
				scmPrtOutputOffsetStackingType
					ScmPrtOutputOffsetStackingType,
				scmPrtOutputTrayTimeoutSupport
					PresentOnOff,
				scmPrtOutputTrayTimeout
					Cardinal32,
				scmPrtOutputFinishier
					Integer32,
				scmPrtOutputFinishierOptions
					Integer32
			 }

--         scmPrtOutputGroup
-- scmPrtOutputFinishingGroup
-- scmPrtOutputStaple              PresentOnOff,
-- scmPrtOutputStaplePosSupported  ScmPrtOutputStaplePosition,
-- scmPrtOutputStapleDefault       PresentOnOff,
-- scmPrtOutputStaplePosDefault    ScmPrtOutputStaplePosition,
-- scmPrtOutputPunch               PresentOnOff,
-- scmPrtOutputPunchDefault        PresentOnOff
-- 1.3.6.1.4.1.236.11.5.11.55.9.1.1.1
		-- 1.3.6.1.4.1.236.11.5.11.55.9.1.1.1
		scmPrtOutputRowStatus OBJECT-TYPE
			SYNTAX RowStatus
			MAX-ACCESS read-create
			STATUS current
			DESCRIPTION
				"
				Manages the status of this conceptual row in the
				scmPrtOutputTable."
			::= { scmPrtOutputEntry 1 }

--   1.3.6.1.4.1.236.11.5.11.55.9.1.1.2
		-- 1.3.6.1.4.1.236.11.5.11.55.9.1.1.2
		scmPrtOutputNextIndex OBJECT-TYPE
			SYNTAX Integer32
			MAX-ACCESS read-create
			STATUS current
			DESCRIPTION
				"
				The value of prtOutputIndex corresponding to the output subunit
				which will be used when this output subunit is filled.
				A value of zero(0) indicates that auto output switching will not
				occur when this output subunit is filled."
			DEFVAL { 0 }
			::= { scmPrtOutputEntry 2 }

--   1.3.6.1.4.1.236.11.5.11.55.9.1.1.3
		-- 1.3.6.1.4.1.236.11.5.11.55.9.1.1.3
		scmPrtOutputPassword OBJECT-TYPE
			SYNTAX OCTET STRING (SIZE (0..255))
			MAX-ACCESS read-create
			STATUS current
			DESCRIPTION
				"
				This object is used as the password for an Output Tray, e.g. an
				output mailbox.  It is the value that must be entered to open
				the output tray."
			REFERENCE
				"See: prtOutputSecurity."
			DEFVAL { ''h }
			::= { scmPrtOutputEntry 3 }

--   1.3.6.1.4.1.236.11.5.11.55.9.1.1.4
		-- 1.3.6.1.4.1.236.11.5.11.55.9.1.1.4
		scmPrtOutputOffsetStackingType OBJECT-TYPE
			SYNTAX ScmPrtOutputOffsetStackingType
			MAX-ACCESS read-create
			STATUS current
			DESCRIPTION
				"
				This object further refines the type of offset stacking from
				that specified by the object prtOutputOffsetStacking in the
				Printer MIB."
			REFERENCE
				"
				See: prtOutputOffsetStacking
				See: scmPrtInterpOffsetStackingType"
			DEFVAL { notSpecified }
			::= { scmPrtOutputEntry 4 }

--         not specified
-- 1.3.6.1.4.1.236.11.5.11.55.9.1.1.5
		-- 1.3.6.1.4.1.236.11.5.11.55.9.1.1.5
		scmPrtOutputTrayTimeoutSupport OBJECT-TYPE
			SYNTAX PresentOnOff
			MAX-ACCESS read-create
			STATUS current
			DESCRIPTION
				"
				Determines whether the printer should wait before sending
				the printed output to another output destination when the
				selected or default destination is full.

				'On' indicates that would should wait as specified by
				scmPrtOutputTrayTimeout.

				'Off' indicates this feature is off and should immediately
				seek to send the printed output to another destination.

				The value 'other' shall mean not specified."
			REFERENCE
				"See: scmPrtOutputTrayTimeout"
			DEFVAL { other }
			::= { scmPrtOutputEntry 5 }

--         other or infinite
-- 1.3.6.1.4.1.236.11.5.11.55.9.1.1.6
		-- 1.3.6.1.4.1.236.11.5.11.55.9.1.1.6
		scmPrtOutputTrayTimeout OBJECT-TYPE
			SYNTAX Cardinal32
			UNITS "Seconds"
			MAX-ACCESS read-create
			STATUS current
			DESCRIPTION
				"
				Determines how long the printer should wait before sending
				the printed output to another output destination when the
				selected or default destination is full.


				A value of (0) implies 'other' or 'infinite' which translates
				to this input subunit does not support this feature."
			DEFVAL { 0 }
			::= { scmPrtOutputEntry 6 }

--         The Output Finishing Group (scmPrtOutputFinishingGroup)
--
-- Implementation of every object in this group is conditionally
-- mandatory:  if the SNMP agent implements the semantics of any of
-- these objects outside of the SCMI MIB, the agent shall also implement
-- this group in order to claim SCMI conformance.
--
-- new scmPrtOutputFinishier
-- 1.3.6.1.4.1.236.11.5.11.55.9.1.1.51
		-- 1.3.6.1.4.1.236.11.5.11.55.9.1.1.51
		scmPrtOutputFinishier OBJECT-TYPE
			SYNTAX Integer32
			MAX-ACCESS read-create
			STATUS current
			DESCRIPTION
				"
				This object declares the printer output finishier."
			::= { scmPrtOutputEntry 51 }

--   1.3.6.1.4.1.236.11.5.11.55.9.1.1.52
		-- 1.3.6.1.4.1.236.11.5.11.55.9.1.1.52
		scmPrtOutputFinishierOptions OBJECT-TYPE
			SYNTAX Integer32
			MAX-ACCESS read-create
			STATUS current
			DESCRIPTION
				"
				This object declares the printer output finishier option.

				options   1. staple
				          2. punch  "
			::= { scmPrtOutputEntry 52 }

--   1.3.6.1.4.1.236.11.5.11.55.14
		-- 1.3.6.1.4.1.236.11.5.11.55.14
		scmPrtChannel OBJECT IDENTIFIER ::= { scmPrintMIB 14 }

--   1.3.6.1.4.1.236.11.5.11.55.14.1
		-- 1.3.6.1.4.1.236.11.5.11.55.14.1
		scmPrtChannelSimple OBJECT IDENTIFIER ::= { scmPrtChannel 1 }

--         table
-- 1.3.6.1.4.1.236.11.5.11.55.14.2
		-- 1.3.6.1.4.1.236.11.5.11.55.14.2
		scmPrtChannelTable OBJECT-TYPE
			SYNTAX SEQUENCE OF ScmPrtChannelEntry
			MAX-ACCESS not-accessible
			STATUS current
			DESCRIPTION
				"
				This table logically augments Printer MIB's prtChannelTable."
			::= { scmPrtChannel 2 }

--   1.3.6.1.4.1.236.11.5.11.55.14.2.1
		-- 1.3.6.1.4.1.236.11.5.11.55.14.2.1
		scmPrtChannelEntry OBJECT-TYPE
			SYNTAX ScmPrtChannelEntry
			MAX-ACCESS not-accessible
			STATUS current
			DESCRIPTION
				"
				An entry exists corresponding to each entry in the
				prtChannelTable."
			AUGMENTS { prtChannelEntry }
			::= { scmPrtChannelTable 1 }

		ScmPrtChannelEntry ::=
			SEQUENCE {
				scmPrtChannelRowStatus
					RowStatus,
				scmPrtChannelEOJTimeout
					Cardinal32
			 }

--   1.3.6.1.4.1.236.11.5.11.55.14.2.1.1
		-- 1.3.6.1.4.1.236.11.5.11.55.14.2.1.1
		scmPrtChannelRowStatus OBJECT-TYPE
			SYNTAX RowStatus
			MAX-ACCESS read-create
			STATUS current
			DESCRIPTION
				"
				Manages the status of this conceptual row in the
				scmPrtChannelTable."
			::= { scmPrtChannelEntry 1 }

--         No timeout
-- 1.3.6.1.4.1.236.11.5.11.55.14.2.1.2
		-- 1.3.6.1.4.1.236.11.5.11.55.14.2.1.2
		scmPrtChannelEOJTimeout OBJECT-TYPE
			SYNTAX Cardinal32
			UNITS "Seconds"
			MAX-ACCESS read-create
			STATUS current
			DESCRIPTION
				"
				Defines the number of  seconds that the channel waits before
				timing out. For example, this may be used for the parallel
				channel.

				The value zero means infinite or no timeout on the channel."
			DEFVAL { 0 }
			::= { scmPrtChannelEntry 2 }

--   1.3.6.1.4.1.236.11.5.11.55.15
		-- 1.3.6.1.4.1.236.11.5.11.55.15
		scmPrtInterpreter OBJECT IDENTIFIER ::= { scmPrintMIB 15 }

--   1.3.6.1.4.1.236.11.5.11.55.15.1
		-- 1.3.6.1.4.1.236.11.5.11.55.15.1
		scmPrtInterpreterSimple OBJECT IDENTIFIER ::= { scmPrtInterpreter 1 }

--   1.3.6.1.4.1.236.11.5.11.55.15.1.1
		-- 1.3.6.1.4.1.236.11.5.11.55.15.1.1
		scmPrtInterpreterCopyNum OBJECT-TYPE
			SYNTAX INTEGER (1..999)
			MAX-ACCESS read-write
			STATUS current
			DESCRIPTION
				" It can select how many papers are printed
				Normally it can be selected 1- 999."
			DEFVAL { 1 }
			::= { scmPrtInterpreterSimple 1 }

--   1.3.6.1.4.1.236.11.5.11.55.15.1.2
		-- 1.3.6.1.4.1.236.11.5.11.55.15.1.2
		scmPrtInterpreterEmulation OBJECT-TYPE
			SYNTAX Integer32
			MAX-ACCESS read-write
			STATUS current
			DESCRIPTION
				"
				Emulation option"
			::= { scmPrtInterpreterSimple 2 }

--   1.3.6.1.4.1.236.11.5.11.55.15.1.3
		-- 1.3.6.1.4.1.236.11.5.11.55.15.1.3
		scmPrtInterpreterEmulationOptions OBJECT-TYPE
			SYNTAX INTEGER
				{
				auto(1),
				pcl5e(2),
				pcl4(4),
				wps3(8),
				wps6(16),
				ksc5843(32),
				kssm(64),
				ksc5895(128),
				hwp(256),
				pclxl(512),
				ps2(1024),
				hexDump(2048),
				epson(4096),
				ps3swrender(8192),
				ps3(16384),
				colorGDI(32768)
				}
			MAX-ACCESS read-write
			STATUS current
			DESCRIPTION
				"
				available options of the model"
			::= { scmPrtInterpreterSimple 3 }

--   1.3.6.1.4.1.236.11.5.11.55.15.2
		-- 1.3.6.1.4.1.236.11.5.11.55.15.2
		scmPrtInterpreterTable OBJECT-TYPE
			SYNTAX SEQUENCE OF ScmPrtInterpreterEntry
			MAX-ACCESS not-accessible
			STATUS current
			DESCRIPTION
				"
				This table logically augments the Printer MIB's
				prtInterpreterTable."
			::= { scmPrtInterpreter 2 }

--   1.3.6.1.4.1.236.11.5.11.55.15.2.1
		-- 1.3.6.1.4.1.236.11.5.11.55.15.2.1
		scmPrtInterpreterEntry OBJECT-TYPE
			SYNTAX ScmPrtInterpreterEntry
			MAX-ACCESS not-accessible
			STATUS current
			DESCRIPTION
				"
				An entry exists corresponding to each entry in the
				prtInterpreterTable."
			AUGMENTS { prtInterpreterEntry }
			::= { scmPrtInterpreterTable 1 }

		ScmPrtInterpreterEntry ::=
			SEQUENCE {
				scmPrtInterpRowStatus
					RowStatus,
				scmPrtInterpJobCopiesDefault
					Ordinal32,
				scmPrtInterpLineTerm
					PresentOnOff,
				scmPrtInterpProcessBarcodes
					PresentOnOff,
				scmPrtInterpOrientation
					Integer32,
				scmPrtInterpOrientationOptions
					INTEGER
			 }

--   1.3.6.1.4.1.236.11.5.11.55.15.2.1.1
		-- 1.3.6.1.4.1.236.11.5.11.55.15.2.1.1
		scmPrtInterpRowStatus OBJECT-TYPE
			SYNTAX RowStatus
			MAX-ACCESS read-create
			STATUS current
			DESCRIPTION
				"
				Manages the status of this conceptual row in the
				scmPrtInterpreterTable."
			::= { scmPrtInterpreterEntry 1 }

--   1.3.6.1.4.1.236.11.5.11.55.15.2.1.9
		-- 1.3.6.1.4.1.236.11.5.11.55.15.2.1.9
		scmPrtInterpJobCopiesDefault OBJECT-TYPE
			SYNTAX Ordinal32
			MAX-ACCESS read-create
			STATUS current
			DESCRIPTION
				"
				This defines the default number of job copies to be printed
				by this interpreter.

				If set incorrectly, this object may cause difficulties at
				customer sites.  Agent developers should consider making this
				object read-only, permanently set to one copy."
			::= { scmPrtInterpreterEntry 9 }

--         not specified
-- 1.3.6.1.4.1.236.11.5.11.55.15.2.1.33
		-- 1.3.6.1.4.1.236.11.5.11.55.15.2.1.33
		scmPrtInterpLineTerm OBJECT-TYPE
			SYNTAX PresentOnOff
			MAX-ACCESS read-create
			STATUS current
			DESCRIPTION
				"
				Enables adding a Carriage Return after every Line Feed.

				The value 'On' indicates that a Carriage Return will be
				added after every Line Feed.

				Usage example:  This is a useful feature when printing text
				jobs via PCL through a standard queue in UNIX.

				The value 'other' shall mean not specified."
			DEFVAL { other }
			::= { scmPrtInterpreterEntry 33 }

--   1.3.6.1.4.1.236.11.5.11.55.15.2.1.54
		-- 1.3.6.1.4.1.236.11.5.11.55.15.2.1.54
		scmPrtInterpProcessBarcodes OBJECT-TYPE
			SYNTAX PresentOnOff
			MAX-ACCESS read-create
			STATUS current
			DESCRIPTION
				"
				Specifies whether the 'extra' barcode processing within
				the interpreter should be used."
			DEFVAL { other }
			::= { scmPrtInterpreterEntry 54 }

--   1.3.6.1.4.1.236.11.5.11.55.15.2.1.60
		-- 1.3.6.1.4.1.236.11.5.11.55.15.2.1.60
		scmPrtInterpOrientation OBJECT-TYPE
			SYNTAX Integer32
			MAX-ACCESS read-create
			STATUS current
			DESCRIPTION
				"
				It determines the direction of the print image on the
				page. The first two kinds of options are portrait(tall)
				and landscape(wide). reversePortrait is 180 degrees
				rotation of portrait. reverseLandscape is 180 degrees
				rotation of landscape."
			::= { scmPrtInterpreterEntry 60 }

--   1.3.6.1.4.1.236.11.5.11.55.15.2.1.61
		-- 1.3.6.1.4.1.236.11.5.11.55.15.2.1.61
		scmPrtInterpOrientationOptions OBJECT-TYPE
			SYNTAX INTEGER
				{
				portrait(1),
				landscape(2),
				reverseLandscape(4),
				reversePortrait(8)
				}
			MAX-ACCESS read-only
			STATUS current
			DESCRIPTION
				"
				available options in orientation"
			::= { scmPrtInterpreterEntry 61 }

--   1.3.6.1.4.1.236.11.5.11.55.16
		-- 1.3.6.1.4.1.236.11.5.11.55.16
		scmPrtMediaPath OBJECT IDENTIFIER ::= { scmPrintMIB 16 }

--   1.3.6.1.4.1.236.11.5.11.55.17
		-- 1.3.6.1.4.1.236.11.5.11.55.17
		scmPrtMarker OBJECT IDENTIFIER ::= { scmPrintMIB 17 }

--         scmPrtMarker
--
-- 1.3.6.1.4.1.236.11.5.11.55.17.1
		-- 1.3.6.1.4.1.236.11.5.11.55.17.1
		scmPrtMarkerSimple OBJECT IDENTIFIER ::= { scmPrtMarker 1 }

--   1.3.6.1.4.1.236.11.5.11.55.17.1.1
		-- 1.3.6.1.4.1.236.11.5.11.55.17.1.1
		scmPrtMarkerMarginUnit OBJECT-TYPE
			SYNTAX INTEGER
				{
				mm(1),
				inch(2)
				}
			MAX-ACCESS read-only
			STATUS current
			DESCRIPTION
				"
				"
			::= { scmPrtMarkerSimple 1 }

--   1.3.6.1.4.1.236.11.5.11.55.17.1.2
		-- 1.3.6.1.4.1.236.11.5.11.55.17.1.2
		scmPrtMarkerSrt OBJECT-TYPE
			SYNTAX Integer32
			MAX-ACCESS read-write
			STATUS current
			DESCRIPTION
				"
				It determin Samsung Resolution Technology option
				when it is ON."
			::= { scmPrtMarkerSimple 2 }

--   1.3.6.1.4.1.236.11.5.11.55.17.1.3
		-- 1.3.6.1.4.1.236.11.5.11.55.17.1.3
		scmPrtMarkerSrtOptions OBJECT-TYPE
			SYNTAX INTEGER
				{
				enhance(1),
				normal(2),
				grayPlus(4),
				gray(8),
				res1200fast(16),
				res1200true(32)
				}
			MAX-ACCESS read-only
			STATUS current
			DESCRIPTION
				"
				available options of current model"
			::= { scmPrtMarkerSimple 3 }

--   1.3.6.1.4.1.236.11.5.11.55.17.1.4
		-- 1.3.6.1.4.1.236.11.5.11.55.17.1.4
		scmPrtMarkerDensity OBJECT-TYPE
			SYNTAX Integer32
			MAX-ACCESS read-only
			STATUS current
			DESCRIPTION
				"It determines the overall density of page"
			::= { scmPrtMarkerSimple 4 }

--   1.3.6.1.4.1.236.11.5.11.55.17.1.5
		-- 1.3.6.1.4.1.236.11.5.11.55.17.1.5
		scmPrtMarkerDensityOptions OBJECT-TYPE
			SYNTAX INTEGER
				{
				light(1),
				medium(2),
				dark(4)
				}
			MAX-ACCESS read-only
			STATUS current
			DESCRIPTION
				"available options of current model"
			::= { scmPrtMarkerSimple 5 }

--   1.3.6.1.4.1.236.11.5.11.55.17.1.6
		-- 1.3.6.1.4.1.236.11.5.11.55.17.1.6
		scmPrtMarkerSmetMode OBJECT-TYPE
			SYNTAX Integer32
			MAX-ACCESS read-only
			STATUS current
			DESCRIPTION
				"The value of this object indicates whether the SMET mode is
				currently enabled."
			::= { scmPrtMarkerSimple 6 }

--   1.3.6.1.4.1.236.11.5.11.55.17.1.7
		-- 1.3.6.1.4.1.236.11.5.11.55.17.1.7
		scmPrtMarkerSmetModeOptions OBJECT-TYPE
			SYNTAX INTEGER
				{
				off(1),
				on(2)
				}
			MAX-ACCESS read-only
			STATUS current
			DESCRIPTION
				"The value of this object will be the bitwise OR of the supported
				values for smetMode in this printer."
			::= { scmPrtMarkerSimple 7 }

--   1.3.6.1.4.1.236.11.5.11.55.17.1.8
		-- 1.3.6.1.4.1.236.11.5.11.55.17.1.8
		scmPrtMarkerduplexTopMargin OBJECT-TYPE
			SYNTAX INTEGER (0..99)
			MAX-ACCESS read-only
			STATUS current
			DESCRIPTION
				"The value of this object gives the top margin on the backside of
				a page when printing in duplex mode. The actual value used in the
				printer is the value of this object divided by 10. The unit is inch."
			::= { scmPrtMarkerSimple 8 }

--   1.3.6.1.4.1.236.11.5.11.55.17.1.9
		-- 1.3.6.1.4.1.236.11.5.11.55.17.1.9
		scmPrtMarkerduplexLeftMargin OBJECT-TYPE
			SYNTAX INTEGER (0..99)
			MAX-ACCESS read-only
			STATUS current
			DESCRIPTION
				"The value of this object gives the left margin on the backside of
				a page when printing in duplex mode. The actual value used in the
				printer is the value of this object divided by 10. The unit is inch."
			::= { scmPrtMarkerSimple 9 }

--   1.3.6.1.4.1.236.11.5.11.55.17.1.10
		-- 1.3.6.1.4.1.236.11.5.11.55.17.1.10
		scmPrtMarkerShortEdgeBindingMargin OBJECT-TYPE
			SYNTAX INTEGER (0..99)
			MAX-ACCESS read-only
			STATUS current
			DESCRIPTION
				"The value of this object gives the margin left for binding on the
				short edge of the paper when printing is done in short edge duplex
				mode. The actual value used in the printer is the value of this
				object divided by 10. The unit is inch."
			::= { scmPrtMarkerSimple 10 }

--   1.3.6.1.4.1.236.11.5.11.55.17.1.11
		-- 1.3.6.1.4.1.236.11.5.11.55.17.1.11
		scmPrtMarkerLongEdgeBindingMargin OBJECT-TYPE
			SYNTAX INTEGER (0..99)
			MAX-ACCESS read-only
			STATUS current
			DESCRIPTION
				"The value of this object gives the margin left for binding on the
				long edge of the paper when printing is done in long edge duplex
				mode. The actual value used in the printer is the value of this
				object divided by 10. The unit is inch."
			::= { scmPrtMarkerSimple 11 }

--   1.3.6.1.4.1.236.11.5.11.55.17.1.12
		-- 1.3.6.1.4.1.236.11.5.11.55.17.1.12
		scmPrtMarkerTonerSave OBJECT-TYPE
			SYNTAX Integer32
			MAX-ACCESS read-only
			STATUS current
			DESCRIPTION
				"
				Echo mode option.
				Echo mode Off
				Echo mode On"
			::= { scmPrtMarkerSimple 12 }

--   1.3.6.1.4.1.236.11.5.11.55.17.1.13
		-- 1.3.6.1.4.1.236.11.5.11.55.17.1.13
		scmPrtMarkerTonerSaveOptions OBJECT-TYPE
			SYNTAX Integer32
			MAX-ACCESS read-only
			STATUS current
			DESCRIPTION
				"
				available options of the model"
			::= { scmPrtMarkerSimple 13 }

--   1.3.6.1.4.1.236.11.5.11.55.17.1.14
		-- 1.3.6.1.4.1.236.11.5.11.55.17.1.14
		scmPrtMarkerTonerOutAction OBJECT-TYPE
			SYNTAX Integer32
			MAX-ACCESS read-only
			STATUS current
			DESCRIPTION
				"
				The value of this object gives the action taken by the printer
				when the tonerLow condition occurs. If the value is continue(1),
				the printer continues to print in spite of the toner being low.
				If the value is stop(2), the printer stops printing when the toner
				is low."
			::= { scmPrtMarkerSimple 14 }

--   1.3.6.1.4.1.236.11.5.11.55.17.1.15
		-- 1.3.6.1.4.1.236.11.5.11.55.17.1.15
		scmPrtMarkerTonerOutActionOptions OBJECT-TYPE
			SYNTAX INTEGER
				{
				continue(1),
				stop(2)
				}
			MAX-ACCESS read-only
			STATUS current
			DESCRIPTION
				"
				The value of this object will be the bitwise OR of the supported
				values for tonerLowAction in this printer."
			::= { scmPrtMarkerSimple 15 }

--   1.3.6.1.4.1.236.11.5.11.55.17.2
		-- 1.3.6.1.4.1.236.11.5.11.55.17.2
		scmPrtMarkerTable OBJECT-TYPE
			SYNTAX SEQUENCE OF ScmPrtMarkerEntry
			MAX-ACCESS not-accessible
			STATUS current
			DESCRIPTION
				"
				"
			::= { scmPrtMarker 2 }

--   1.3.6.1.4.1.236.11.5.11.55.17.2.1
		-- 1.3.6.1.4.1.236.11.5.11.55.17.2.1
		scmPrtMarkerEntry OBJECT-TYPE
			SYNTAX ScmPrtMarkerEntry
			MAX-ACCESS not-accessible
			STATUS current
			DESCRIPTION
				"
				Entries may exist in the table for each device
				index who's device type is printer"
			INDEX { hrDeviceIndex, scmPrtMarkerTonerIndex }
			::= { scmPrtMarkerTable 1 }

		ScmPrtMarkerEntry ::=
			SEQUENCE {
				scmPrtMarkerTonerIndex
					Ordinal32,
				scmPrtMarkerResolution
					Integer32,
				scmPrtMarkerResolutionOptions
					INTEGER,
				scmPrtMarkerTonerColor
					Integer32,
				scmPrtMarkerTonerColorDescription
					OCTET STRING,
				scmPrtMarkerTonerLevel
					Integer32
			 }

--   1.3.6.1.4.1.236.11.5.11.55.17.2.1.1
		-- 1.3.6.1.4.1.236.11.5.11.55.17.2.1.1
		scmPrtMarkerTonerIndex OBJECT-TYPE
			SYNTAX Ordinal32
			MAX-ACCESS read-only
			STATUS current
			DESCRIPTION
				"Index of the Toner number"
			::= { scmPrtMarkerEntry 1 }

--         scmPrtMarkerGroup
-- 1.3.6.1.4.1.236.11.5.11.55.17.2.1.2
		-- 1.3.6.1.4.1.236.11.5.11.55.17.2.1.2
		scmPrtMarkerResolution OBJECT-TYPE
			SYNTAX Integer32
			MAX-ACCESS read-write
			STATUS current
			DESCRIPTION
				"
				The value of this object gives the current resolution used while
				printing. The value res300(1) means 300X300 dpi resolution. The
				value res600(2) means 600X600 dpi resolution. The value res1200(4)
				means 1200X1200 dpi resolution."
			::= { scmPrtMarkerEntry 2 }

--   1.3.6.1.4.1.236.11.5.11.55.17.2.1.3
		-- 1.3.6.1.4.1.236.11.5.11.55.17.2.1.3
		scmPrtMarkerResolutionOptions OBJECT-TYPE
			SYNTAX INTEGER
				{
				res300(1),
				res600(2),
				res1200(4),
				res1200fast(8),
				res1200best(16)
				}
			MAX-ACCESS read-only
			STATUS current
			DESCRIPTION
				"
				The value of this object will be the bitwise OR of all the supported
				values for resolution in this printer."
			::= { scmPrtMarkerEntry 3 }

--   1.3.6.1.4.1.236.11.5.11.55.17.2.1.4
		-- 1.3.6.1.4.1.236.11.5.11.55.17.2.1.4
		scmPrtMarkerTonerColor OBJECT-TYPE
			SYNTAX Integer32
			MAX-ACCESS read-only
			STATUS current
			DESCRIPTION
				"color of Toner"
			::= { scmPrtMarkerEntry 4 }

--   1.3.6.1.4.1.236.11.5.11.55.17.2.1.5
		-- 1.3.6.1.4.1.236.11.5.11.55.17.2.1.5
		scmPrtMarkerTonerColorDescription OBJECT-TYPE
			SYNTAX OCTET STRING
			MAX-ACCESS read-only
			STATUS current
			DESCRIPTION
				"Description of Toner"
			::= { scmPrtMarkerEntry 5 }

--   1.3.6.1.4.1.236.11.5.11.55.17.2.1.6
		-- 1.3.6.1.4.1.236.11.5.11.55.17.2.1.6
		scmPrtMarkerTonerLevel OBJECT-TYPE
			SYNTAX Integer32
			MAX-ACCESS read-only
			STATUS current
			DESCRIPTION
				"Indication of Toner remainder"
			::= { scmPrtMarkerEntry 6 }

--   1.3.6.1.4.1.236.11.5.11.55.18
		-- 1.3.6.1.4.1.236.11.5.11.55.18
		scmPrtOperation OBJECT IDENTIFIER ::= { scmPrintMIB 18 }

--         scmPrtOperation
--
-- 1.3.6.1.4.1.236.11.5.11.55.18.1
		-- 1.3.6.1.4.1.236.11.5.11.55.18.1
		scmPrtOperationSimple OBJECT IDENTIFIER ::= { scmPrtOperation 1 }

--   1.3.6.1.4.1.236.11.5.11.55.18.1.1
		-- 1.3.6.1.4.1.236.11.5.11.55.18.1.1
		scmPrtOperationJobCancel OBJECT-TYPE
			SYNTAX INTEGER { cancelJob(1) }
			MAX-ACCESS read-write
			STATUS current
			DESCRIPTION
				"Printer Operation Job Cancel Request"
			::= { scmPrtOperationSimple 1 }

--   1.3.6.1.4.1.236.11.5.11.55.18.1.2
		-- 1.3.6.1.4.1.236.11.5.11.55.18.1.2
		scmPrtOperarionMenuClear OBJECT-TYPE
			SYNTAX INTEGER
				{
				on(1),
				off(2)
				}
			MAX-ACCESS read-write
			STATUS current
			DESCRIPTION
				"When the value of this object is set to clearMenus(1), the values of
				all the printer properties in all the menus will be set to default
				values."
			::= { scmPrtOperationSimple 2 }

--   1.3.6.1.4.1.236.11.5.11.55.18.1.3
		-- 1.3.6.1.4.1.236.11.5.11.55.18.1.3
		scmPrtOperationMenuClearOptions OBJECT-TYPE
			SYNTAX INTEGER
				{
				disable(1),
				enable(2)
				}
			MAX-ACCESS read-only
			STATUS current
			DESCRIPTION
				"The value of this object will be the bitwise OR of the supported
				values for menuClear in this printer."
			::= { scmPrtOperationSimple 3 }

--   1.3.6.1.4.1.236.11.5.11.55.18.1.4
		-- 1.3.6.1.4.1.236.11.5.11.55.18.1.4
		scmPrtOperationFuserClean OBJECT-TYPE
			SYNTAX INTEGER
				{
				off(1),
				on(2)
				}
			MAX-ACCESS read-write
			STATUS current
			DESCRIPTION
				"When the value of this object is set to fuserClean(2),the printer fuser will be clear"
			::= { scmPrtOperationSimple 4 }

--   1.3.6.1.4.1.236.11.5.11.55.18.1.5
		-- 1.3.6.1.4.1.236.11.5.11.55.18.1.5
		scmPrtOperationFuserCleanOptions OBJECT-TYPE
			SYNTAX INTEGER
				{
				disable(1),
				enable(2)
				}
			MAX-ACCESS read-only
			STATUS current
			DESCRIPTION
				"The value of this object will be the bitwise OR of the supported
				values for nfuserClean in this printer."
			::= { scmPrtOperationSimple 5 }

--   1.3.6.1.4.1.236.11.5.11.55.18.1.6
		-- 1.3.6.1.4.1.236.11.5.11.55.18.1.6
		scmPrtOperationOpcClean OBJECT-TYPE
			SYNTAX INTEGER
				{
				off(1),
				on(2)
				}
			MAX-ACCESS read-write
			STATUS current
			DESCRIPTION
				"When the value of this object is set to opcClean(2),the printer OPC will be clear"
			::= { scmPrtOperationSimple 6 }

--   1.3.6.1.4.1.236.11.5.11.55.18.1.7
		-- 1.3.6.1.4.1.236.11.5.11.55.18.1.7
		scmPrtOperationOpcCleanOptions OBJECT-TYPE
			SYNTAX INTEGER
				{
				disable(1),
				enable(2)
				}
			MAX-ACCESS read-only
			STATUS current
			DESCRIPTION
				"The value of this object will be the bitwise OR of the supported
				values for nopcClean in this printer."
			::= { scmPrtOperationSimple 7 }

--   1.3.6.1.4.1.236.11.5.11.55.18.1.8
		-- 1.3.6.1.4.1.236.11.5.11.55.18.1.8
		scmPrtOperationTestPrtRequest OBJECT-TYPE
			SYNTAX Integer32
			MAX-ACCESS read-write
			STATUS current
			DESCRIPTION
				" request test printing
				1: request "
			::= { scmPrtOperationSimple 8 }

--   1.3.6.1.4.1.236.11.5.11.55.18.1.9
		-- 1.3.6.1.4.1.236.11.5.11.55.18.1.9
		scmPrtOperationPrintFontRequest OBJECT-TYPE
			SYNTAX INTEGER
				{
				pcl(1),
				ps(2),
				ks5843(3),
				kssm(4),
				ks5895(5),
				epson(6),
				opcClean(7),
				fuserClean(8),
				configpage(9),
				demopage(10),
				menuMap(11),
				psFlashDirectory(12)
				}
			MAX-ACCESS read-write
			STATUS current
			DESCRIPTION
				" request test printing
				1: pcl request
				2: ps request
				3: ks5843 request
				4: kssm request
				5: ks5895 request
				6: epson requese,
				7: opcClean request,
				8: fuserClean request,
				9: configpage request,
				10: kssm request,
				11: menuMap request,
				12: psFlashDirectory requese,
				"
			::= { scmPrtOperationSimple 9 }

--   1.3.6.1.4.1.236.11.5.11.55.18.1.10
		-- 1.3.6.1.4.1.236.11.5.11.55.18.1.10
		scmPrtOperationPrintBlackOnly OBJECT-TYPE
			SYNTAX INTEGER
				{
				on(1),
				off(2)
				}
			MAX-ACCESS read-write
			STATUS current
			DESCRIPTION
				"Description."
			::= { scmPrtOperationSimple 10 }

--         table  --
-- 1.3.6.1.4.1.236.11.5.11.55.18.2
		-- 1.3.6.1.4.1.236.11.5.11.55.18.2
		scmPrtOperationTable OBJECT-TYPE
			SYNTAX SEQUENCE OF ScmPrtOperationEntry
			MAX-ACCESS not-accessible
			STATUS current
			DESCRIPTION
				"
				"
			::= { scmPrtOperation 2 }

--   1.3.6.1.4.1.236.11.5.11.55.18.2.1
		-- 1.3.6.1.4.1.236.11.5.11.55.18.2.1
		scmPrtOperationEntry OBJECT-TYPE
			SYNTAX ScmPrtOperationEntry
			MAX-ACCESS not-accessible
			STATUS current
			DESCRIPTION
				"
				"
			INDEX { scmPrtOperationIndex, hrDeviceIndex }
			::= { scmPrtOperationTable 1 }

		ScmPrtOperationEntry ::=
			SEQUENCE {
				scmPrtOperationIndex
					Ordinal32
			 }

--         scmPrtOperationGroup
-- 1.3.6.1.4.1.236.11.5.11.55.18.2.1.1
		-- 1.3.6.1.4.1.236.11.5.11.55.18.2.1.1
		scmPrtOperationIndex OBJECT-TYPE
			SYNTAX Ordinal32
			MAX-ACCESS read-only
			STATUS current
			DESCRIPTION
				"
				"
			::= { scmPrtOperationEntry 1 }

--   1.3.6.1.4.1.236.11.5.11.55.19
		-- 1.3.6.1.4.1.236.11.5.11.55.19
		scmPrtConfiguration OBJECT IDENTIFIER ::= { scmPrintMIB 19 }

--         scmPrtConfiguration
--
-- 1.3.6.1.4.1.236.11.5.11.55.19.1
		-- 1.3.6.1.4.1.236.11.5.11.55.19.1
		scmPrtConfigurationSimple OBJECT IDENTIFIER ::= { scmPrtConfiguration 1 }

--   1.3.6.1.4.1.236.11.5.11.55.19.1.1
		-- 1.3.6.1.4.1.236.11.5.11.55.19.1.1
		scmPrtConfigurationPowerSave OBJECT-TYPE
			SYNTAX Integer32
			MAX-ACCESS read-write
			STATUS current
			DESCRIPTION
				" set power save mode 1: power save mode"
			::= { scmPrtConfigurationSimple 1 }

--   1.3.6.1.4.1.236.11.5.11.55.19.1.2
		-- 1.3.6.1.4.1.236.11.5.11.55.19.1.2
		scmPrtConfigurationPowerSaveOptions OBJECT-TYPE
			SYNTAX INTEGER
				{
				pwSaveoff(1),
				pwSave15(2),
				pwSave30(4),
				pwSave45(8),
				pwSave60(16)
				}
			MAX-ACCESS read-only
			STATUS current
			DESCRIPTION
				" available options of the model"
			::= { scmPrtConfigurationSimple 2 }

--   1.3.6.1.4.1.236.11.5.11.55.19.1.3
		-- 1.3.6.1.4.1.236.11.5.11.55.19.1.3
		scmPrtConfigurationAutocont OBJECT-TYPE
			SYNTAX Integer32
			MAX-ACCESS read-write
			STATUS current
			DESCRIPTION
				"It determines the printer action when the user
				prints a page without paper in the manual feed
				slot but the paper source is set to manual feed.
				If Auto Continue is ON the printer pick up the
				paper from the tray after few second. If it is
				OFF the printer wait forever until user insert
				paper into a manual feed slot."
			::= { scmPrtConfigurationSimple 3 }

--   1.3.6.1.4.1.236.11.5.11.55.19.1.4
		-- 1.3.6.1.4.1.236.11.5.11.55.19.1.4
		scmPrtConfigurationAutoCountOptions OBJECT-TYPE
			SYNTAX INTEGER
				{
				off(1),
				on(2)
				}
			MAX-ACCESS read-only
			STATUS current
			DESCRIPTION
				" available options of the model"
			::= { scmPrtConfigurationSimple 4 }

--   1.3.6.1.4.1.236.11.5.11.55.19.1.5
		-- 1.3.6.1.4.1.236.11.5.11.55.19.1.5
		scmPrtConfigurationJam2Recover OBJECT-TYPE
			SYNTAX Integer32
			MAX-ACCESS read-write
			STATUS current
			DESCRIPTION
				"if it is on and occur JAM at Jam2 point
				printer will print this page again."
			::= { scmPrtConfigurationSimple 5 }

--   1.3.6.1.4.1.236.11.5.11.55.19.1.6
		-- 1.3.6.1.4.1.236.11.5.11.55.19.1.6
		scmPrtConfigurationJam2RecOptions OBJECT-TYPE
			SYNTAX INTEGER
				{
				off(1),
				on(2)
				}
			MAX-ACCESS read-only
			STATUS current
			DESCRIPTION
				" available options of the model"
			::= { scmPrtConfigurationSimple 6 }

--   1.3.6.1.4.1.236.11.5.11.55.19.1.7
		-- 1.3.6.1.4.1.236.11.5.11.55.19.1.7
		scmPrtConfigurationAltitudeAction OBJECT-TYPE
			SYNTAX Integer32
			MAX-ACCESS read-write
			STATUS current
			DESCRIPTION
				"The value 'low(1)' will be used when the printer is in the low altitude
				location. The value 'high(2)' will be used when the printer is in
				the high altitude location. "
			::= { scmPrtConfigurationSimple 7 }

--   1.3.6.1.4.1.236.11.5.11.55.19.1.8
		-- 1.3.6.1.4.1.236.11.5.11.55.19.1.8
		scmPrtConfigurationAltitudeActionOptions OBJECT-TYPE
			SYNTAX INTEGER
				{
				low(1),
				high(2)
				}
			MAX-ACCESS read-only
			STATUS current
			DESCRIPTION
				"The value of this object will be the bitwise OR of the supported
				values for altitudeAction in this printer."
			::= { scmPrtConfigurationSimple 8 }

--         table
-- 1.3.6.1.4.1.236.11.5.11.55.19.2
		-- 1.3.6.1.4.1.236.11.5.11.55.19.2
		scmPrtConfigurationTable OBJECT-TYPE
			SYNTAX SEQUENCE OF ScmPrtConfigurationEntry
			MAX-ACCESS not-accessible
			STATUS current
			DESCRIPTION
				"
				"
			::= { scmPrtConfiguration 2 }

--   1.3.6.1.4.1.236.11.5.11.55.19.2.1
		-- 1.3.6.1.4.1.236.11.5.11.55.19.2.1
		scmPrtConfigurationEntry OBJECT-TYPE
			SYNTAX ScmPrtConfigurationEntry
			MAX-ACCESS not-accessible
			STATUS current
			DESCRIPTION
				"
				"
			INDEX { scmPrtConfigurationIndex, hrDeviceIndex }
			::= { scmPrtConfigurationTable 1 }

		ScmPrtConfigurationEntry ::=
			SEQUENCE {
				scmPrtConfigurationIndex
					Ordinal32
			 }

--         scmPrtConfigurationGroup
-- 1.3.6.1.4.1.236.11.5.11.55.19.2.1.1
		-- 1.3.6.1.4.1.236.11.5.11.55.19.2.1.1
		scmPrtConfigurationIndex OBJECT-TYPE
			SYNTAX Ordinal32
			MAX-ACCESS read-only
			STATUS current
			DESCRIPTION
				"
				"
			::= { scmPrtConfigurationEntry 1 }

--   1.3.6.1.4.1.236.11.5.11.55.20
		-- 1.3.6.1.4.1.236.11.5.11.55.20
		scmPrtCount OBJECT IDENTIFIER ::= { scmPrintMIB 20 }

--         scmPrtCount
--
-- 1.3.6.1.4.1.236.11.5.11.55.20.1
		-- 1.3.6.1.4.1.236.11.5.11.55.20.1
		scmPrtCountSimple OBJECT IDENTIFIER ::= { scmPrtCount 1 }

--   1.3.6.1.4.1.236.11.5.11.55.20.1.1
		-- 1.3.6.1.4.1.236.11.5.11.55.20.1.1
		scmPrtCountDrumImageCount OBJECT-TYPE
			SYNTAX Integer32
			MAX-ACCESS read-only
			STATUS current
			DESCRIPTION
				"
				"
			::= { scmPrtCountSimple 1 }

--   1.3.6.1.4.1.236.11.5.11.55.20.1.2
		-- 1.3.6.1.4.1.236.11.5.11.55.20.1.2
		scmPrtCountDrumImageCountReset OBJECT-TYPE
			SYNTAX INTEGER
				{
				off(1),
				on(2)
				}
			MAX-ACCESS read-write
			STATUS current
			DESCRIPTION
				"
				"
			::= { scmPrtCountSimple 2 }

--   1.3.6.1.4.1.236.11.5.11.55.20.1.3
		-- 1.3.6.1.4.1.236.11.5.11.55.20.1.3
		scmPrtCountTransferImageCount OBJECT-TYPE
			SYNTAX Integer32
			MAX-ACCESS read-only
			STATUS current
			DESCRIPTION
				"
				"
			::= { scmPrtCountSimple 3 }

--   1.3.6.1.4.1.236.11.5.11.55.20.1.4
		-- 1.3.6.1.4.1.236.11.5.11.55.20.1.4
		scmPrtCountTransferImageCountReset OBJECT-TYPE
			SYNTAX INTEGER
				{
				off(1),
				on(2)
				}
			MAX-ACCESS read-write
			STATUS current
			DESCRIPTION
				"
				"
			::= { scmPrtCountSimple 4 }

--   1.3.6.1.4.1.236.11.5.11.55.20.1.5
		-- 1.3.6.1.4.1.236.11.5.11.55.20.1.5
		scmPrtCountFuserImageCount OBJECT-TYPE
			SYNTAX Integer32
			MAX-ACCESS read-only
			STATUS current
			DESCRIPTION
				"
				"
			::= { scmPrtCountSimple 5 }

--   1.3.6.1.4.1.236.11.5.11.55.20.1.6
		-- 1.3.6.1.4.1.236.11.5.11.55.20.1.6
		scmPrtCountFuserImageCountReset OBJECT-TYPE
			SYNTAX INTEGER
				{
				off(1),
				on(2)
				}
			MAX-ACCESS read-write
			STATUS current
			DESCRIPTION
				"
				"
			::= { scmPrtCountSimple 6 }

--   1.3.6.1.4.1.236.11.5.11.55.20.1.7
		-- 1.3.6.1.4.1.236.11.5.11.55.20.1.7
		scmPrtCountTwoRollerCount OBJECT-TYPE
			SYNTAX Integer32
			MAX-ACCESS read-only
			STATUS current
			DESCRIPTION
				"
				"
			::= { scmPrtCountSimple 7 }

--   1.3.6.1.4.1.236.11.5.11.55.20.1.8
		-- 1.3.6.1.4.1.236.11.5.11.55.20.1.8
		scmPrtCountTwoRollerReset OBJECT-TYPE
			SYNTAX INTEGER { on(1) }
			MAX-ACCESS read-write
			STATUS current
			DESCRIPTION
				"
				"
			::= { scmPrtCountSimple 8 }

--   1.3.6.1.4.1.236.11.5.11.55.20.1.9
		-- 1.3.6.1.4.1.236.11.5.11.55.20.1.9
		scmPrtCountPickupMPCount OBJECT-TYPE
			SYNTAX Integer32
			MAX-ACCESS read-only
			STATUS current
			DESCRIPTION
				"
				"
			::= { scmPrtCountSimple 9 }

--   1.3.6.1.4.1.236.11.5.11.55.20.1.10
		-- 1.3.6.1.4.1.236.11.5.11.55.20.1.10
		scmPrtCountPickupMPReset OBJECT-TYPE
			SYNTAX INTEGER { on(1) }
			MAX-ACCESS read-write
			STATUS current
			DESCRIPTION
				"
				"
			::= { scmPrtCountSimple 10 }

--   1.3.6.1.4.1.236.11.5.11.55.20.1.11
		-- 1.3.6.1.4.1.236.11.5.11.55.20.1.11
		scmPrtCountPickupTray1Count OBJECT-TYPE
			SYNTAX Integer32
			MAX-ACCESS read-only
			STATUS current
			DESCRIPTION
				"
				"
			::= { scmPrtCountSimple 11 }

--   1.3.6.1.4.1.236.11.5.11.55.20.1.12
		-- 1.3.6.1.4.1.236.11.5.11.55.20.1.12
		scmPrtCountPickupTray1Reset OBJECT-TYPE
			SYNTAX INTEGER { on(1) }
			MAX-ACCESS read-write
			STATUS current
			DESCRIPTION
				"
				"
			::= { scmPrtCountSimple 12 }

--   1.3.6.1.4.1.236.11.5.11.55.20.1.13
		-- 1.3.6.1.4.1.236.11.5.11.55.20.1.13
		scmPrtCountPickupTray2Count OBJECT-TYPE
			SYNTAX Integer32
			MAX-ACCESS read-only
			STATUS current
			DESCRIPTION
				"
				"
			::= { scmPrtCountSimple 13 }

--   1.3.6.1.4.1.236.11.5.11.55.20.1.14
		-- 1.3.6.1.4.1.236.11.5.11.55.20.1.14
		scmPrtCountPickupTray2Reset OBJECT-TYPE
			SYNTAX INTEGER { on(1) }
			MAX-ACCESS read-write
			STATUS current
			DESCRIPTION
				"
				"
			::= { scmPrtCountSimple 14 }

--         table
-- 1.3.6.1.4.1.236.11.5.11.55.20.2
		-- 1.3.6.1.4.1.236.11.5.11.55.20.2
		scmPrtCountTable OBJECT-TYPE
			SYNTAX SEQUENCE OF ScmPrtCountEntry
			MAX-ACCESS not-accessible
			STATUS current
			DESCRIPTION
				"
				"
			::= { scmPrtCount 2 }

--   1.3.6.1.4.1.236.11.5.11.55.20.2.1
		-- 1.3.6.1.4.1.236.11.5.11.55.20.2.1
		scmPrtCountEntry OBJECT-TYPE
			SYNTAX ScmPrtCountEntry
			MAX-ACCESS not-accessible
			STATUS current
			DESCRIPTION
				"
				"
			INDEX { scmPrtCountIndex }
			::= { scmPrtCountTable 1 }

		ScmPrtCountEntry ::=
			SEQUENCE {
				scmPrtCountIndex
					Integer32,
				scmPrtCountDeviceType
					INTEGER,
				scmPrtCountType
					INTEGER,
				scmPrtCountMediaSize
					INTEGER,
				scmPrtCountColorant
					INTEGER,
				scmPrtCountDuplex
					INTEGER,
				scmPrtCountResolution
					INTEGER,
				scmPrtCountUnit
					INTEGER,
				scmPrtCountValue
					Integer32
			 }

--         scmPrtCountGroup
-- 1.3.6.1.4.1.236.11.5.11.55.20.2.1.1
		-- 1.3.6.1.4.1.236.11.5.11.55.20.2.1.1
		scmPrtCountIndex OBJECT-TYPE
			SYNTAX Integer32 (1..2147483647)
			MAX-ACCESS read-only
			STATUS current
			DESCRIPTION
				"
				"
			::= { scmPrtCountEntry 1 }

		-- 1.3.6.1.4.1.236.11.5.11.55.20.2.1.2
		scmPrtCountDeviceType OBJECT-TYPE
			SYNTAX INTEGER
				{
				printer(1),
				scanner(2),
				copier(3),
				fax(4),
				mailbox(5),
				finisher(6),
				feeder(7),
				sorter(8),
				marker(9),
				basicFunctionFinisher(10),
				multiFunctionFinisher(11),
				externalIFFinisher(12),
				thirdPartyFinisher(13),
				payment(14)
				}
			MAX-ACCESS read-only
			STATUS current
			DESCRIPTION
				"Description."
			::= { scmPrtCountEntry 2 }

--   1.3.6.1.4.1.236.11.5.11.55.20.2.1.2
		-- 1.3.6.1.4.1.236.11.5.11.55.20.2.1.3
		scmPrtCountType OBJECT-TYPE
			SYNTAX INTEGER
				{
				other(1),
				unknown(2),
				copy(3),
				faxIn(4),
				faxout(5),
				digitalSend(6),
				digitalReceive(7),
				scan(8),
				print(9)
				}
			MAX-ACCESS read-only
			STATUS current
			DESCRIPTION
				"Description."
			::= { scmPrtCountEntry 3 }

--   1.3.6.1.4.1.236.11.5.11.55.20.2.1.3
		-- 1.3.6.1.4.1.236.11.5.11.55.20.2.1.4
		scmPrtCountMediaSize OBJECT-TYPE
			SYNTAX INTEGER
				{
				unknown(1),
				letter(2),
				legal(3),
				a4(4),
				executive(5),
				jisB5(6),
				isoB5(7),
				com10(8),
				monarch(9),
				dl(10),
				c5(11),
				postA6(12),
				c6(13),
				folio(14),
				a5(15),
				statement(16),
				a6(17),
				ledger(18),
				a3(19),
				jisB4(20),
				jpost(21),
				jpostd(22),
				custom(23),
				letterP(24),
				a4P(25),
				jisB5P(26),
				a5P(27),
				executiveP(28),
				statementP(29),
				a3Over(30),
				b5Envelope(31)
				}
			MAX-ACCESS read-only
			STATUS current
			DESCRIPTION
				"
				Paper size options that are available in this model.
				Some printer such like ML6060 or Modena have a  4 bytes data length.
				So, to distinguish these models we have to check model id or version. "
			::= { scmPrtCountEntry 4 }

--   1.3.6.1.4.1.236.11.5.11.55.20.2.1.4
		-- 1.3.6.1.4.1.236.11.5.11.55.20.2.1.5
		scmPrtCountColorant OBJECT-TYPE
			SYNTAX INTEGER
				{
				mono(1),
				color(2)
				}
			MAX-ACCESS read-only
			STATUS current
			DESCRIPTION
				"Description."
			::= { scmPrtCountEntry 5 }

--   1.3.6.1.4.1.236.11.5.11.55.20.2.1.5
		-- 1.3.6.1.4.1.236.11.5.11.55.20.2.1.6
		scmPrtCountDuplex OBJECT-TYPE
			SYNTAX INTEGER
				{
				simplex(1),
				duplex(2)
				}
			MAX-ACCESS read-only
			STATUS current
			DESCRIPTION
				"Description."
			::= { scmPrtCountEntry 6 }

		-- 1.3.6.1.4.1.236.11.5.11.55.20.2.1.7
		scmPrtCountResolution OBJECT-TYPE
			SYNTAX INTEGER
				{
				low300dpi(1),
				normal600dpi(2),
				high1200dpi(3)
				}
			MAX-ACCESS read-write
			STATUS current
			DESCRIPTION
				"Description."
			::= { scmPrtCountEntry 7 }

--   1.3.6.1.4.1.236.11.5.11.55.20.2.1.6
		-- 1.3.6.1.4.1.236.11.5.11.55.20.2.1.8
		scmPrtCountUnit OBJECT-TYPE
			SYNTAX INTEGER
				{
				tenThousandthsOfInches(3),
				micrometers(4),
				characters(5),
				lines(6),
				impressions(7),
				sheets(8),
				dotRow(9),
				hours(11),
				feet(16),
				meters(17)
				}
			MAX-ACCESS read-only
			STATUS current
			DESCRIPTION
				"Description."
			::= { scmPrtCountEntry 8 }

--   1.3.6.1.4.1.236.11.5.11.55.20.2.1.7
		-- 1.3.6.1.4.1.236.11.5.11.55.20.2.1.9
		scmPrtCountValue OBJECT-TYPE
			SYNTAX Integer32
			MAX-ACCESS read-only
			STATUS current
			DESCRIPTION
				"Description."
			::= { scmPrtCountEntry 9 }

--   1.3.6.1.4.1.236.11.5.11.55.21
		-- 1.3.6.1.4.1.236.11.5.11.55.21
		scmPrtSerial OBJECT IDENTIFIER ::= { scmPrintMIB 21 }

--         scmPrtSerial
--
-- 1.3.6.1.4.1.236.11.5.11.55.21.1
		-- 1.3.6.1.4.1.236.11.5.11.55.21.1
		scmPrtSerialSimple OBJECT IDENTIFIER ::= { scmPrtSerial 1 }

--         table
-- 1.3.6.1.4.1.236.11.5.11.55.21.2
		-- 1.3.6.1.4.1.236.11.5.11.55.21.2
		scmPrtSerialTable OBJECT-TYPE
			SYNTAX SEQUENCE OF ScmPrtSerialEntry
			MAX-ACCESS not-accessible
			STATUS current
			DESCRIPTION
				"
				"
			::= { scmPrtSerial 2 }

--   1.3.6.1.4.1.236.11.5.11.55.21.2.1
		-- 1.3.6.1.4.1.236.11.5.11.55.21.2.1
		scmPrtSerialEntry OBJECT-TYPE
			SYNTAX ScmPrtSerialEntry
			MAX-ACCESS not-accessible
			STATUS current
			DESCRIPTION
				"
				"
			INDEX { scmPrtSerialIndex }
			::= { scmPrtSerialTable 1 }

		ScmPrtSerialEntry ::=
			SEQUENCE {
				scmPrtSerialIndex
					Ordinal32,
				scmPrtSerialNbaudRate
					Integer32,
				scmPrtSerialBrOptions
					Integer32,
				scmPrtSerialBobuxon
					INTEGER,
				scmPrtSerialBobuxonOptions
					Integer32
			 }

--         scmPrtSerialGroup
-- 1.3.6.1.4.1.236.11.5.11.55.21.2.1.1
		-- 1.3.6.1.4.1.236.11.5.11.55.21.2.1.1
		scmPrtSerialIndex OBJECT-TYPE
			SYNTAX Ordinal32
			MAX-ACCESS not-accessible
			STATUS current
			DESCRIPTION
				"
				"
			::= { scmPrtSerialEntry 1 }

--   1.3.6.1.4.1.236.11.5.11.55.21.2.1.2
		-- 1.3.6.1.4.1.236.11.5.11.55.21.2.1.2
		scmPrtSerialNbaudRate OBJECT-TYPE
			SYNTAX Integer32
			MAX-ACCESS read-write
			STATUS current
			DESCRIPTION
				"the speed when user use a serial port"
			::= { scmPrtSerialEntry 2 }

--   1.3.6.1.4.1.236.11.5.11.55.21.2.1.3
		-- 1.3.6.1.4.1.236.11.5.11.55.21.2.1.3
		scmPrtSerialBrOptions OBJECT-TYPE
			SYNTAX Integer32
			MAX-ACCESS read-only
			STATUS current
			DESCRIPTION
				"available options of printer "
			::= { scmPrtSerialEntry 3 }

--   1.3.6.1.4.1.236.11.5.11.55.21.2.1.4
		-- 1.3.6.1.4.1.236.11.5.11.55.21.2.1.4
		scmPrtSerialBobuxon OBJECT-TYPE
			SYNTAX INTEGER
				{
				on(1),
				off(2)
				}
			MAX-ACCESS read-write
			STATUS current
			DESCRIPTION
				"
				"
			::= { scmPrtSerialEntry 4 }

--   1.3.6.1.4.1.236.11.5.11.55.21.2.1.5
		-- 1.3.6.1.4.1.236.11.5.11.55.21.2.1.5
		scmPrtSerialBobuxonOptions OBJECT-TYPE
			SYNTAX Integer32
			MAX-ACCESS read-only
			STATUS current
			DESCRIPTION
				"The value of this object will be the bitwise OR of the supported
				values for robuxon in this printer."
			::= { scmPrtSerialEntry 5 }

--   1.3.6.1.4.1.236.11.5.11.55.22
		-- 1.3.6.1.4.1.236.11.5.11.55.22
		scmPrtPCL OBJECT IDENTIFIER ::= { scmPrintMIB 22 }

--         scmPrtPCL
--
-- 1.3.6.1.4.1.236.11.5.11.55.22.1
		-- 1.3.6.1.4.1.236.11.5.11.55.22.1
		scmPrtPCLSimple OBJECT IDENTIFIER ::= { scmPrtPCL 1 }

--   1.3.6.1.4.1.236.11.5.11.55.22.1.1
		-- 1.3.6.1.4.1.236.11.5.11.55.22.1.1
		scmPrtPCLFont OBJECT-TYPE
			SYNTAX INTEGER (0..53)
			MAX-ACCESS read-write
			STATUS current
			DESCRIPTION
				" "
			::= { scmPrtPCLSimple 1 }

--   1.3.6.1.4.1.236.11.5.11.55.22.1.2
		-- 1.3.6.1.4.1.236.11.5.11.55.22.1.2
		scmPrtPCLSymbolSet OBJECT-TYPE
			SYNTAX INTEGER (0..37)
			MAX-ACCESS read-write
			STATUS current
			DESCRIPTION
				" "
			::= { scmPrtPCLSimple 2 }

--   1.3.6.1.4.1.236.11.5.11.55.22.1.3
		-- 1.3.6.1.4.1.236.11.5.11.55.22.1.3
		scmPrtPCLFormLine OBJECT-TYPE
			SYNTAX INTEGER (5..128)
			MAX-ACCESS read-write
			STATUS current
			DESCRIPTION
				" "
			::= { scmPrtPCLSimple 3 }

--   1.3.6.1.4.1.236.11.5.11.55.22.1.4
		-- 1.3.6.1.4.1.236.11.5.11.55.22.1.4
		scmPrtPCLPitch OBJECT-TYPE
			SYNTAX INTEGER (16..399)
			MAX-ACCESS read-write
			STATUS current
			DESCRIPTION
				" "
			::= { scmPrtPCLSimple 4 }

--   1.3.6.1.4.1.236.11.5.11.55.22.1.5
		-- 1.3.6.1.4.1.236.11.5.11.55.22.1.5
		scmPrtPCLPointSize OBJECT-TYPE
			SYNTAX INTEGER (16..399)
			MAX-ACCESS read-write
			STATUS current
			DESCRIPTION
				" "
			::= { scmPrtPCLSimple 5 }

--   1.3.6.1.4.1.236.11.5.11.55.22.1.6
		-- 1.3.6.1.4.1.236.11.5.11.55.22.1.6
		scmPrtPCLCourier OBJECT-TYPE
			SYNTAX Integer32
			MAX-ACCESS read-write
			STATUS current
			DESCRIPTION
				" "
			::= { scmPrtPCLSimple 6 }

--   1.3.6.1.4.1.236.11.5.11.55.22.1.7
		-- 1.3.6.1.4.1.236.11.5.11.55.22.1.7
		scmPrtPCLCourierOptions OBJECT-TYPE
			SYNTAX INTEGER
				{
				regular(1),
				dark(2)
				}
			MAX-ACCESS read-only
			STATUS current
			DESCRIPTION
				" "
			::= { scmPrtPCLSimple 7 }

--   1.3.6.1.4.1.236.11.5.11.55.22.1.8
		-- 1.3.6.1.4.1.236.11.5.11.55.22.1.8
		scmPrtPCLAppendCR OBJECT-TYPE
			SYNTAX Integer32
			MAX-ACCESS read-write
			STATUS current
			DESCRIPTION
				" "
			::= { scmPrtPCLSimple 8 }

--   1.3.6.1.4.1.236.11.5.11.55.22.1.9
		-- 1.3.6.1.4.1.236.11.5.11.55.22.1.9
		scmPrtPCLAppendCROptions OBJECT-TYPE
			SYNTAX INTEGER
				{
				lf(1),
				lfCR(2)
				}
			MAX-ACCESS read-only
			STATUS current
			DESCRIPTION
				" "
			::= { scmPrtPCLSimple 9 }

--   1.3.6.1.4.1.236.11.5.11.55.22.1.10
		-- 1.3.6.1.4.1.236.11.5.11.55.22.1.10
		scmPrtPCLWideA4 OBJECT-TYPE
			SYNTAX Integer32
			MAX-ACCESS read-write
			STATUS current
			DESCRIPTION
				" "
			::= { scmPrtPCLSimple 10 }

--   1.3.6.1.4.1.236.11.5.11.55.22.1.11
		-- 1.3.6.1.4.1.236.11.5.11.55.22.1.11
		scmPrtPCLWideA4Options OBJECT-TYPE
			SYNTAX INTEGER
				{
				off(1),
				on(2)
				}
			MAX-ACCESS read-only
			STATUS current
			DESCRIPTION
				" "
			::= { scmPrtPCLSimple 11 }

--   1.3.6.1.4.1.236.11.5.11.55.22.1.12
		-- 1.3.6.1.4.1.236.11.5.11.55.22.1.12
		scmPrtPCLTopMargin OBJECT-TYPE
			SYNTAX INTEGER (0..250)
			MAX-ACCESS read-write
			STATUS current
			DESCRIPTION
				" Margine between top and first line of this page
				,actuall value of printing is a value divided by 10.
				basic unit is inch. If Orientation is portrait or reverse
				portrait, then the range of topMargine is 0 to 99 and if
				Orientation is landscape or reverse landscape, then range is 0 to 170"
			::= { scmPrtPCLSimple 12 }

--   1.3.6.1.4.1.236.11.5.11.55.22.1.13
		-- 1.3.6.1.4.1.236.11.5.11.55.22.1.13
		scmPrtPCLLeftMargin OBJECT-TYPE
			SYNTAX INTEGER (0..250)
			MAX-ACCESS read-write
			STATUS current
			DESCRIPTION
				" Left margine of printed page, actual value is
				a value divided by 10. Basic unit is inch.
				If Orentation is landscape or reverse landscape, the range is 0
				to 99 and if the Orientation is portrait or reverse portrait,
				the range is 0 to 170."
			::= { scmPrtPCLSimple 13 }

--          table
-- 1.3.6.1.4.1.236.11.5.11.55.22.2
		-- 1.3.6.1.4.1.236.11.5.11.55.22.2
		scmPrtPCLTable OBJECT-TYPE
			SYNTAX SEQUENCE OF ScmPrtPCLEntry
			MAX-ACCESS not-accessible
			STATUS current
			DESCRIPTION
				"
				"
			::= { scmPrtPCL 2 }

--   1.3.6.1.4.1.236.11.5.11.55.22.2.1
		-- 1.3.6.1.4.1.236.11.5.11.55.22.2.1
		scmPrtPCLEntry OBJECT-TYPE
			SYNTAX ScmPrtPCLEntry
			MAX-ACCESS not-accessible
			STATUS current
			DESCRIPTION
				"
				"
			INDEX { scmPrtPCLIndex }
			::= { scmPrtPCLTable 1 }

		ScmPrtPCLEntry ::=
			SEQUENCE {
				scmPrtPCLIndex
					Ordinal32
			 }

--         scmPrtPCLGroup
-- 1.3.6.1.4.1.236.11.5.11.55.22.2.1.1
		-- 1.3.6.1.4.1.236.11.5.11.55.22.2.1.1
		scmPrtPCLIndex OBJECT-TYPE
			SYNTAX Ordinal32
			MAX-ACCESS read-only
			STATUS current
			DESCRIPTION
				"
				"
			::= { scmPrtPCLEntry 1 }

--   1.3.6.1.4.1.236.11.5.11.55.23
		-- 1.3.6.1.4.1.236.11.5.11.55.23
		scmPrtKS5843 OBJECT IDENTIFIER ::= { scmPrintMIB 23 }

--         scmPrtKS5843
--
-- 1.3.6.1.4.1.236.11.5.11.55.23.1
		-- 1.3.6.1.4.1.236.11.5.11.55.23.1
		scmPrtKS5843Simple OBJECT IDENTIFIER ::= { scmPrtKS5843 1 }

--   1.3.6.1.4.1.236.11.5.11.55.23.1.1
		-- 1.3.6.1.4.1.236.11.5.11.55.23.1.1
		scmPrtKS5843Font OBJECT-TYPE
			SYNTAX Integer32
			MAX-ACCESS read-write
			STATUS current
			DESCRIPTION
				" "
			::= { scmPrtKS5843Simple 1 }

--   1.3.6.1.4.1.236.11.5.11.55.23.1.2
		-- 1.3.6.1.4.1.236.11.5.11.55.23.1.2
		scmPrtKS5843FontOptions OBJECT-TYPE
			SYNTAX INTEGER
				{
				myoungjo(1),
				gothic(2),
				gungseo(4),
				gullim(8),
				sammool(16),
				yetche(32),
				post(64),
				newgraph(128),
				sunmyun(256),
				pilgi(512),
				headline(1024),
				ocrB1(2048)
				}
			MAX-ACCESS read-only
			STATUS current
			DESCRIPTION
				" "
			::= { scmPrtKS5843Simple 2 }

--   1.3.6.1.4.1.236.11.5.11.55.23.1.3
		-- 1.3.6.1.4.1.236.11.5.11.55.23.1.3
		scmPrtKS5843Code OBJECT-TYPE
			SYNTAX Integer32
			MAX-ACCESS read-write
			STATUS current
			DESCRIPTION
				" "
			::= { scmPrtKS5843Simple 3 }

--   1.3.6.1.4.1.236.11.5.11.55.23.1.4
		-- 1.3.6.1.4.1.236.11.5.11.55.23.1.4
		scmPrtKS5843CodeOptions OBJECT-TYPE
			SYNTAX INTEGER
				{
				wansung(1),
				johap(2)
				}
			MAX-ACCESS read-only
			STATUS current
			DESCRIPTION
				" "
			::= { scmPrtKS5843Simple 4 }

--   1.3.6.1.4.1.236.11.5.11.55.23.1.5
		-- 1.3.6.1.4.1.236.11.5.11.55.23.1.5
		scmPrtKS5843cpi OBJECT-TYPE
			SYNTAX Integer32
			MAX-ACCESS read-write
			STATUS current
			DESCRIPTION
				" "
			::= { scmPrtKS5843Simple 5 }

--   1.3.6.1.4.1.236.11.5.11.55.23.1.6
		-- 1.3.6.1.4.1.236.11.5.11.55.23.1.6
		scmPrtKS5843cpiOptions OBJECT-TYPE
			SYNTAX INTEGER
				{
				kscpi10(1),
				kscpi12(2),
				kscpi133(4),
				kscpi15(8),
				kscpi20(16),
				kscpi24(32),
				kscpi267(64),
				kscpi30(128)
				}
			MAX-ACCESS read-only
			STATUS current
			DESCRIPTION
				" "
			::= { scmPrtKS5843Simple 6 }

--   1.3.6.1.4.1.236.11.5.11.55.23.1.7
		-- 1.3.6.1.4.1.236.11.5.11.55.23.1.7
		scmPrtKS5843Lines OBJECT-TYPE
			SYNTAX INTEGER (5..10)
			MAX-ACCESS read-write
			STATUS current
			DESCRIPTION
				" "
			::= { scmPrtKS5843Simple 7 }

--   1.3.6.1.4.1.236.11.5.11.55.23.1.8
		-- 1.3.6.1.4.1.236.11.5.11.55.23.1.8
		scmPrtKS5843Zoom OBJECT-TYPE
			SYNTAX INTEGER (50..200)
			MAX-ACCESS read-write
			STATUS current
			DESCRIPTION
				" "
			::= { scmPrtKS5843Simple 8 }

--   1.3.6.1.4.1.236.11.5.11.55.23.1.9
		-- 1.3.6.1.4.1.236.11.5.11.55.23.1.9
		scmPrtKS5843AutoWrap OBJECT-TYPE
			SYNTAX Integer32
			MAX-ACCESS read-write
			STATUS current
			DESCRIPTION
				" "
			::= { scmPrtKS5843Simple 9 }

--   1.3.6.1.4.1.236.11.5.11.55.23.1.10
		-- 1.3.6.1.4.1.236.11.5.11.55.23.1.10
		scmPrtKS5843AutoWrapOptions OBJECT-TYPE
			SYNTAX INTEGER
				{
				off(1),
				on(2)
				}
			MAX-ACCESS read-only
			STATUS current
			DESCRIPTION
				" "
			::= { scmPrtKS5843Simple 10 }

--   1.3.6.1.4.1.236.11.5.11.55.23.1.11
		-- 1.3.6.1.4.1.236.11.5.11.55.23.1.11
		scmPrtKS5843Topmargin OBJECT-TYPE
			SYNTAX INTEGER (0..8)
			MAX-ACCESS read-write
			STATUS current
			DESCRIPTION
				" "
			::= { scmPrtKS5843Simple 11 }

--   1.3.6.1.4.1.236.11.5.11.55.23.1.12
		-- 1.3.6.1.4.1.236.11.5.11.55.23.1.12
		scmPrtKS5843Sitemode OBJECT-TYPE
			SYNTAX INTEGER (0..9)
			MAX-ACCESS read-write
			STATUS current
			DESCRIPTION
				"Each site special Mode except ksc5843 standard"
			::= { scmPrtKS5843Simple 12 }

--   1.3.6.1.4.1.236.11.5.11.55.24
		-- 1.3.6.1.4.1.236.11.5.11.55.24
		scmPrtKSSM OBJECT IDENTIFIER ::= { scmPrintMIB 24 }

--         scmPrtKSSM
--
-- 1.3.6.1.4.1.236.11.5.11.55.24.1
		-- 1.3.6.1.4.1.236.11.5.11.55.24.1
		scmPrtKSSMSimple OBJECT IDENTIFIER ::= { scmPrtKSSM 1 }

--   1.3.6.1.4.1.236.11.5.11.55.24.1.1
		-- 1.3.6.1.4.1.236.11.5.11.55.24.1.1
		scmPrtKSSMFont OBJECT-TYPE
			SYNTAX Integer32
			MAX-ACCESS read-write
			STATUS current
			DESCRIPTION
				" "
			::= { scmPrtKSSMSimple 1 }

--   1.3.6.1.4.1.236.11.5.11.55.24.1.2
		-- 1.3.6.1.4.1.236.11.5.11.55.24.1.2
		scmPrtKSSMFontOptions OBJECT-TYPE
			SYNTAX INTEGER
				{
				myoungjo(1),
				gothic(2),
				gungseo(4),
				gullim(8),
				sammool(16),
				yetche(32),
				post(64),
				newgraph(128),
				sunmyun(256),
				pilgi(512),
				headline(1024),
				ocrB1(2048)
				}
			MAX-ACCESS read-only
			STATUS current
			DESCRIPTION
				" "
			::= { scmPrtKSSMSimple 2 }

--   1.3.6.1.4.1.236.11.5.11.55.24.1.3
		-- 1.3.6.1.4.1.236.11.5.11.55.24.1.3
		scmPrtKSSMCode OBJECT-TYPE
			SYNTAX Integer32
			MAX-ACCESS read-write
			STATUS current
			DESCRIPTION
				" "
			::= { scmPrtKSSMSimple 3 }

--   1.3.6.1.4.1.236.11.5.11.55.24.1.4
		-- 1.3.6.1.4.1.236.11.5.11.55.24.1.4
		scmPrtKSSMCodeOptions OBJECT-TYPE
			SYNTAX INTEGER
				{
				wansung(1),
				johap(2)
				}
			MAX-ACCESS read-only
			STATUS current
			DESCRIPTION
				" "
			::= { scmPrtKSSMSimple 4 }

--   1.3.6.1.4.1.236.11.5.11.55.24.1.5
		-- 1.3.6.1.4.1.236.11.5.11.55.24.1.5
		scmPrtKSSMCPI OBJECT-TYPE
			SYNTAX Integer32
			MAX-ACCESS read-write
			STATUS current
			DESCRIPTION
				" "
			::= { scmPrtKSSMSimple 5 }

--   1.3.6.1.4.1.236.11.5.11.55.24.1.6
		-- 1.3.6.1.4.1.236.11.5.11.55.24.1.6
		scmPrtKSSMCPIOptions OBJECT-TYPE
			SYNTAX INTEGER
				{
				kscpi10(1),
				kscpi12(2),
				kscpi133(4),
				kscpi15(8),
				kscpi20(16),
				kscpi24(32),
				kscpi267(64),
				kscpi30(128)
				}
			MAX-ACCESS read-only
			STATUS current
			DESCRIPTION
				" "
			::= { scmPrtKSSMSimple 6 }

--   1.3.6.1.4.1.236.11.5.11.55.24.1.7
		-- 1.3.6.1.4.1.236.11.5.11.55.24.1.7
		scmPrtKSSMLines OBJECT-TYPE
			SYNTAX INTEGER (5..10)
			MAX-ACCESS read-write
			STATUS current
			DESCRIPTION
				" "
			::= { scmPrtKSSMSimple 7 }

--   1.3.6.1.4.1.236.11.5.11.55.24.1.8
		-- 1.3.6.1.4.1.236.11.5.11.55.24.1.8
		scmPrtKSSMZoom OBJECT-TYPE
			SYNTAX INTEGER (50..200)
			MAX-ACCESS read-write
			STATUS current
			DESCRIPTION
				" "
			::= { scmPrtKSSMSimple 8 }

--   1.3.6.1.4.1.236.11.5.11.55.24.1.9
		-- 1.3.6.1.4.1.236.11.5.11.55.24.1.9
		scmPrtKSSMAutoWrap OBJECT-TYPE
			SYNTAX Integer32
			MAX-ACCESS read-write
			STATUS current
			DESCRIPTION
				" "
			::= { scmPrtKSSMSimple 9 }

--   1.3.6.1.4.1.236.11.5.11.55.24.1.10
		-- 1.3.6.1.4.1.236.11.5.11.55.24.1.10
		scmPrtKSSMAutoWrapOptions OBJECT-TYPE
			SYNTAX INTEGER
				{
				off(1),
				on(2)
				}
			MAX-ACCESS read-only
			STATUS current
			DESCRIPTION
				" "
			::= { scmPrtKSSMSimple 10 }

--   1.3.6.1.4.1.236.11.5.11.55.24.1.11
		-- 1.3.6.1.4.1.236.11.5.11.55.24.1.11
		scmPrtKSSMTopMargin OBJECT-TYPE
			SYNTAX INTEGER (0..8)
			MAX-ACCESS read-write
			STATUS current
			DESCRIPTION
				" "
			::= { scmPrtKSSMSimple 11 }

--   1.3.6.1.4.1.236.11.5.11.55.24.1.12
		-- 1.3.6.1.4.1.236.11.5.11.55.24.1.12
		scmPrtKSSMSiteMode OBJECT-TYPE
			SYNTAX INTEGER (0..9)
			MAX-ACCESS read-write
			STATUS current
			DESCRIPTION
				" "
			::= { scmPrtKSSMSimple 12 }

--   1.3.6.1.4.1.236.11.5.11.55.25
		-- 1.3.6.1.4.1.236.11.5.11.55.25
		scmPrtIPP OBJECT IDENTIFIER ::= { scmPrintMIB 25 }

--          scmPrtIPP
--
-- 1.3.6.1.4.1.236.11.5.11.55.25.1
		-- 1.3.6.1.4.1.236.11.5.11.55.25.1
		scmPrtIPPSimple OBJECT IDENTIFIER ::= { scmPrtIPP 1 }

--   1.3.6.1.4.1.236.11.5.11.55.25.1.1
		-- 1.3.6.1.4.1.236.11.5.11.55.25.1.1
		scmPrtIPPColorSupported OBJECT-TYPE
			SYNTAX INTEGER
				{
				yes(1),
				no(2)
				}
			MAX-ACCESS read-only
			STATUS current
			DESCRIPTION
				"The value of this object indicates whether the printer supports
				color printing."
			::= { scmPrtIPPSimple 1 }

--   1.3.6.1.4.1.236.11.5.11.55.25.1.2
		-- 1.3.6.1.4.1.236.11.5.11.55.25.1.2
		scmPrtIPPJobKOctetsSupportedLBound OBJECT-TYPE
			SYNTAX Integer32
			MAX-ACCESS read-only
			STATUS current
			DESCRIPTION
				"The value of this object gives the lower bound of the size in
				units of 1024 octets for jobs accepted by the printer."
			::= { scmPrtIPPSimple 2 }

--   1.3.6.1.4.1.236.11.5.11.55.25.1.3
		-- 1.3.6.1.4.1.236.11.5.11.55.25.1.3
		scmPrtIPPJobKOctetsSupportedUBound OBJECT-TYPE
			SYNTAX Integer32
			MAX-ACCESS read-only
			STATUS current
			DESCRIPTION
				"The value of this object gives the upper bound of the size in
				units of 1024 octets for jobs accepted by the printer."
			::= { scmPrtIPPSimple 3 }

--   1.3.6.1.4.1.236.11.5.11.55.25.1.4
		-- 1.3.6.1.4.1.236.11.5.11.55.25.1.4
		scmPrtIPPJobImpressionsSupportedLBound OBJECT-TYPE
			SYNTAX Integer32
			MAX-ACCESS read-only
			STATUS current
			DESCRIPTION
				"The value of this object gives the lower bound of the number of
				print images for a job."
			::= { scmPrtIPPSimple 4 }

--   1.3.6.1.4.1.236.11.5.11.55.25.1.5
		-- 1.3.6.1.4.1.236.11.5.11.55.25.1.5
		scmPrtIPPJobImpressionsSupportedUBound OBJECT-TYPE
			SYNTAX Integer32
			MAX-ACCESS read-only
			STATUS current
			DESCRIPTION
				"The value of this object gives the upper bound of the number of
				print images for a job."
			::= { scmPrtIPPSimple 5 }

--   1.3.6.1.4.1.236.11.5.11.55.25.1.6
		-- 1.3.6.1.4.1.236.11.5.11.55.25.1.6
		scmPrtIPPJobMediaSheetsSupportedLBound OBJECT-TYPE
			SYNTAX Integer32
			MAX-ACCESS read-only
			STATUS current
			DESCRIPTION
				"The value of this object gives the lower bound of the number of
				pages printed for a job."
			::= { scmPrtIPPSimple 6 }

--   1.3.6.1.4.1.236.11.5.11.55.25.1.7
		-- 1.3.6.1.4.1.236.11.5.11.55.25.1.7
		scmPrtIPPJobMediaSheetsSupportedUBound OBJECT-TYPE
			SYNTAX Integer32
			MAX-ACCESS read-only
			STATUS current
			DESCRIPTION
				"The value of this object gives the upper bound of the number of
				pages printed for a job."
			::= { scmPrtIPPSimple 7 }

--   1.3.6.1.4.1.236.11.5.11.55.25.1.8
		-- 1.3.6.1.4.1.236.11.5.11.55.25.1.8
		scmPrtIPPJobSheets OBJECT-TYPE
			SYNTAX INTEGER
				{
				standard(1),
				none(2)
				}
			MAX-ACCESS read-write
			STATUS current
			DESCRIPTION
				"The value of this object specifies the type of job start/end sheets
				printed with every IPP job. If the value is standard(1), the
				printer specific standard job start/end sheets will be printed for
				each job."
			::= { scmPrtIPPSimple 8 }

--   1.3.6.1.4.1.236.11.5.11.55.25.1.9
		-- 1.3.6.1.4.1.236.11.5.11.55.25.1.9
		scmPrtIPPCollatedCopiesLBound OBJECT-TYPE
			SYNTAX Integer32
			MAX-ACCESS read-only
			STATUS current
			DESCRIPTION
				"The value of this object gives the lower bound of the number of
				collated copies supported in this printer."
			::= { scmPrtIPPSimple 9 }

--   1.3.6.1.4.1.236.11.5.11.55.25.1.10
		-- 1.3.6.1.4.1.236.11.5.11.55.25.1.10
		scmPrtIPPCollatedCopiesUBound OBJECT-TYPE
			SYNTAX Integer32
			MAX-ACCESS read-only
			STATUS current
			DESCRIPTION
				"The value of this object gives the upper bound of the number of
				collated copies supported in this printer."
			::= { scmPrtIPPSimple 10 }

--   1.3.6.1.4.1.236.11.5.11.55.25.1.11
		-- 1.3.6.1.4.1.236.11.5.11.55.25.1.11
		scmPrtIPPCollatedCopies OBJECT-TYPE
			SYNTAX Integer32
			MAX-ACCESS read-write
			STATUS current
			DESCRIPTION
				"The value of this object gives the number of collated copies
				printed for the each job."
			::= { scmPrtIPPSimple 11 }

--   1.3.6.1.4.1.236.11.5.11.55.25.1.12
		-- 1.3.6.1.4.1.236.11.5.11.55.25.1.12
		scmPrtIPPFinishingsSupported OBJECT-TYPE
			SYNTAX Integer32
			MAX-ACCESS read-only
			STATUS current
			DESCRIPTION
				"The value of this object gives the type of finishings supported
				in the printer. If bit 1 is set, stapling is supported. If bit 2
				is set, punching is supported. If bit 3 is set, covering of printed
				document is supported. If bit 4 is set, binding is supported. If
				bit 0 is set, the option of no finishings is supported."
			::= { scmPrtIPPSimple 12 }

--   1.3.6.1.4.1.236.11.5.11.55.25.1.13
		-- 1.3.6.1.4.1.236.11.5.11.55.25.1.13
		scmPrtIPPFinishings OBJECT-TYPE
			SYNTAX Integer32
			MAX-ACCESS read-write
			STATUS current
			DESCRIPTION
				"The value of this object gives the set of finishings applied for
				each job. If bit 0 is set, no finishings are applied. If bit 1
				is set, stapling is done for each job. If bit 2 is set, punching
				is done for each job. If bit 3 is set, the printed document will
				be covered. If bit 4 is set, binding will be done for each job."
			::= { scmPrtIPPSimple 13 }

--   1.3.6.1.4.1.236.11.5.11.55.25.1.14
		-- 1.3.6.1.4.1.236.11.5.11.55.25.1.14
		scmPrtIPPPageRangesSupported OBJECT-TYPE
			SYNTAX INTEGER
				{
				on(1),
				off(2)
				}
			MAX-ACCESS read-write
			STATUS current
			DESCRIPTION
				"The value of this object indicates whether printing only a range
				of pages for IPP jobs is supported. If the value is on(1),
				printing only specified page ranges of the given IPP job is
				supported."
			::= { scmPrtIPPSimple 14 }

--   1.3.6.1.4.1.236.11.5.11.55.25.1.15
		-- 1.3.6.1.4.1.236.11.5.11.55.25.1.15
		scmPrtIPPNumberUp OBJECT-TYPE
			SYNTAX Integer32
			MAX-ACCESS read-write
			STATUS current
			DESCRIPTION
				"The value of this object indicates the number of print images
				imposed on one side of a page."
			::= { scmPrtIPPSimple 15 }

--   1.3.6.1.4.1.236.11.5.11.55.25.1.16
		-- 1.3.6.1.4.1.236.11.5.11.55.25.1.16
		scmPrtIPPNumberUpOptions OBJECT-TYPE
			SYNTAX INTEGER
				{
				numberUp1(1),
				numberUp2(2),
				numberUp4(4),
				numberUp6(8),
				numberUp9(16),
				numberUp16(32)
				}
			MAX-ACCESS read-only
			STATUS current
			DESCRIPTION
				"The value of this object will be the bitwise OR of the supported
				values for numberUp in this printer."
			::= { scmPrtIPPSimple 16 }

--   1.3.6.1.4.1.236.11.5.11.55.25.1.17
		-- 1.3.6.1.4.1.236.11.5.11.55.25.1.17
		scmPrtIPPPrintQuality OBJECT-TYPE
			SYNTAX Integer32
			MAX-ACCESS read-write
			STATUS current
			DESCRIPTION
				"The value of this object indicates the print quality that the
				printer uses for a print job. The value draft(1) means lowest
				quality available on the printer. Tha value normal(2) means
				normal or intermediate quality on the printer. The value high(4)
				means highest quality available on the printer."
			::= { scmPrtIPPSimple 17 }

--   1.3.6.1.4.1.236.11.5.11.55.25.1.18
		-- 1.3.6.1.4.1.236.11.5.11.55.25.1.18
		scmPrtIPPPrintQualityOptions OBJECT-TYPE
			SYNTAX INTEGER
				{
				draft(1),
				normal(2),
				high(4)
				}
			MAX-ACCESS read-only
			STATUS current
			DESCRIPTION
				"The value of this object will be the bitwise OR of the supported
				values for printQuality in this printer."
			::= { scmPrtIPPSimple 18 }

--   1.3.6.1.4.1.236.11.5.11.55.25.1.19
		-- 1.3.6.1.4.1.236.11.5.11.55.25.1.19
		scmPrtIPPJobKOctetsProcessed OBJECT-TYPE
			SYNTAX Integer32
			MAX-ACCESS read-only
			STATUS current
			DESCRIPTION
				"The value of this object gives the number of units of 1024 octets
				printed for the current job."
			::= { scmPrtIPPSimple 19 }

--   1.3.6.1.4.1.236.11.5.11.55.25.1.20
		-- 1.3.6.1.4.1.236.11.5.11.55.25.1.20
		scmPrtIPPJobImpressionsCompleted OBJECT-TYPE
			SYNTAX Integer32
			MAX-ACCESS read-only
			STATUS current
			DESCRIPTION
				"The value of this object gives the number of print images printed
				for the current job."
			::= { scmPrtIPPSimple 20 }

--   1.3.6.1.4.1.236.11.5.11.55.25.1.21
		-- 1.3.6.1.4.1.236.11.5.11.55.25.1.21
		scmPrtIPPJobMediaSheetsCompleted OBJECT-TYPE
			SYNTAX Integer32
			MAX-ACCESS read-only
			STATUS current
			DESCRIPTION
				"The value of this object gives the number of pages printed
				for the current job."
			::= { scmPrtIPPSimple 21 }

--   1.3.6.1.4.1.236.11.5.11.55.26
		-- 1.3.6.1.4.1.236.11.5.11.55.26
		scmPrtAlert OBJECT IDENTIFIER ::= { scmPrintMIB 26 }

--         scmPrtAlert
--
-- 1.3.6.1.4.1.236.11.5.11.55.26.1
		-- 1.3.6.1.4.1.236.11.5.11.55.26.1
		scmPrtAlertSimple OBJECT IDENTIFIER ::= { scmPrtAlert 1 }

--   1.3.6.1.4.1.236.11.5.11.55.26.1.1
		-- 1.3.6.1.4.1.236.11.5.11.55.26.1.1
		scmPrtAlertAlarmShortage OBJECT-TYPE
			SYNTAX INTEGER
				{
				off(1),
				on(2)
				}
			MAX-ACCESS read-write
			STATUS current
			DESCRIPTION
				"Printer Alert Alarm Shortage"
			::= { scmPrtAlertSimple 1 }

--   1.3.6.1.4.1.236.11.5.11.55.26.1.2
		-- 1.3.6.1.4.1.236.11.5.11.55.26.1.2
		scmPrtAlertAlarmShortageOptions OBJECT-TYPE
			SYNTAX Integer32
			MAX-ACCESS read-only
			STATUS current
			DESCRIPTION
				"Printer Alert Shortage Oprions"
			::= { scmPrtAlertSimple 2 }

--   1.3.6.1.4.1.236.11.5.11.55.27
		-- 1.3.6.1.4.1.236.11.5.11.55.27
		scmPrtConsoleDisplayBuffer OBJECT IDENTIFIER ::= { scmPrintMIB 27 }

--         scmPrtConsoleDisplayBuffer
--
-- 1.3.6.1.4.1.236.11.5.11.55.27.1
		-- 1.3.6.1.4.1.236.11.5.11.55.27.1
		scmPrtConsoleDisplayBufferSimple OBJECT IDENTIFIER ::= { scmPrtConsoleDisplayBuffer 1 }

--   1.3.6.1.4.1.236.11.5.11.55.27.1.1
		-- 1.3.6.1.4.1.236.11.5.11.55.27.1.1
		scmPrtConsoleDisplayBufferLcdLangType OBJECT-TYPE
			SYNTAX INTEGER
				{
				english(1),
				german(2),
				french(4),
				italian(8),
				spanish(16)
				}
			MAX-ACCESS read-write
			STATUS current
			DESCRIPTION
				"Printer Console (LCD) Display String Language Type"
			::= { scmPrtConsoleDisplayBufferSimple 1 }

--   1.3.6.1.4.1.236.11.5.11.55.27.1.2
		-- 1.3.6.1.4.1.236.11.5.11.55.27.1.2
		scmPrtConsoleDisplayBufferLcdLangTypeOptions OBJECT-TYPE
			SYNTAX Integer32
			MAX-ACCESS read-write
			STATUS current
			DESCRIPTION
				"Printer Console (LCD) Display String Language Type Option"
			::= { scmPrtConsoleDisplayBufferSimple 2 }


	END

--
-- SamsungPrint.mib
--
