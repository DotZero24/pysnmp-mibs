SAMSUNG-DIAGNOSTICS-MIB DEFINITIONS ::= BEGIN

-- Module:  Diagnostics MIB
-- File: SamsungDiagnostics.mib
-- Editors: wani.kang@samsung.com
-- Date:    August 24, 2004
-- Version: 1.00


IMPORTS
	MODULE-IDENTITY,OBJECT-TYPE
			FROM SNMPv2-SMI         -- RFC 1442/1902/2578
	DisplayString
			FROM SNMPv2-TC          -- RFC 1443/1903/2579
	Counter
			FROM RFC1155-SMI         -- RFC 1155
	samsungCommonMIB
                FROM SAMSUNG-COMMON-MIB;

scmDiagnostics MODULE-IDENTITY
    LAST-UPDATED "0408240000Z" -- 24 Aug 2004
    ORGANIZATION "Samsung Corporation -
        Samsung Common Management Interface (SCMI) Working Group"
    CONTACT-INFO "
                      SCMI Editors
        E-Mail:       wani.kang@samsung.com

        --
        --
        "
    DESCRIPTION "
        SCMI Document Diagnostics MIB,
        Version 1.00

        Copyright (C) 2003-2004 Samsung Corporation. All Rights Reserved."
    ::= { samsungCommonMIB 64 }

--
--      Document Resources General Group (Mandatory)
--

scmDiagnosticsDevice OBJECT IDENTIFIER ::= { scmDiagnostics 1 }

-- The Document Resources General table contains general counters and
-- summary information for ease of use of the overall Document Resources
-- MIB.
--
-- The Document Resources General table has exactly one row, which row
-- has an scmDiagnosticsIndex value of 1.
--
-- For conformance to this MIB module, implementation of all objects in
-- this group is mandatory.


scmDiagnosticsDeviceTable OBJECT-TYPE
        SYNTAX          SEQUENCE OF ScmDiagnosticsDeviceEntry
        MAX-ACCESS      not-accessible
        STATUS          current
        DESCRIPTION
                "A table of general counters and summary information for
                ease of use of the overall Document Resources MIB on
                this host system.

                This Document Resources General table has exactly one
                row, with an scmDiagnosticsIndex value of 1."
        ::= { scmDiagnosticsDevice 2 }

scmDiagnosticsDeviceEntry OBJECT-TYPE
        SYNTAX          ScmDiagnosticsDeviceEntry
        MAX-ACCESS      not-accessible
        STATUS          current
        DESCRIPTION
                "A row entry of general counters and summary information
                for ease of use of the overall Document Resources MIB on
                this host system.

                The Document Resources General table has exactly one row
                entry, with an scmDiagnosticsIndex value of 1."
        INDEX { scmDiagnosticsDeviceIndex }
        ::= { scmDiagnosticsDeviceTable 1 }

ScmDiagnosticsDeviceEntry ::= SEQUENCE {
        scmDiagnosticsDeviceIndex       INTEGER,
        scmDiagnosticsDeviceItem		DisplayString,
        scmDiagnosticsDeviceType        INTEGER,
        scmDiagnosticsDeviceDescr      	DisplayString,
        scmDiagnosticsDeviceID     	INTEGER,
        scmDiagnosticsDeviceStatus    	INTEGER,
        scmDiagnosticsDeviceErrors    	Counter,
        scmDiagnosticsRequest           INTEGER,
        scmGenBaseDeviceImageFileName   DisplayString
        }

scmDiagnosticsDeviceIndex OBJECT-TYPE
        SYNTAX          INTEGER (1..2147483647)
        MAX-ACCESS      read-only
        STATUS          current
        DESCRIPTION
                "A unique value for each device contained by the
 	host.  The value for each device must remain
 	constant at least from one re-initialization of the
 	agent to the next re-initialization."
        ::= { scmDiagnosticsDeviceEntry 1 }

scmDiagnosticsDeviceItem OBJECT-TYPE
        SYNTAX DisplayString (SIZE (0..64))
        MAX-ACCESS      read-only
        STATUS          current
        DESCRIPTION
                "An indication of the Item of device."

        ::= { scmDiagnosticsDeviceEntry 2 }

scmDiagnosticsDeviceType OBJECT-TYPE
	 	SYNTAX INTEGER
			{
			input(1),
			output(2),
			cover(3),
			geeralPrinter(4),
			mediaPath(5),
			marker(6),
			markerSupplies(7),
			markerColorant(8),
			fax(21),
			scanner(22),
			network(23),
			usb(24),
			parallel(25),
			finisher(26),
			motor(41),
			smps(42),
			memory(43)
			}

        MAX-ACCESS      read-only
        STATUS          current
        DESCRIPTION
                "An indication of the type of device.

 	If this value is `hrDeviceProcessor  hrDeviceTypes
 	3 ' then an entry exists in the hrProcessorTable
 	which corresponds to this device.

 	If this value is `hrDeviceNetwork  hrDeviceTypes 4
 	', then an entry exists in the hrNetworkTable
 	which corresponds to this device.

 	If this value is `hrDevicePrinter  hrDeviceTypes 5
 	', then an entry exists in the hrPrinterTable
 	which corresponds to this device.

 	If this value is `hrDeviceDiskStorage
 	hrDeviceTypes 6 ', then an entry exists in the
 	hrDiskStorageTable which corresponds to this
 	device.
	"
        ::= { scmDiagnosticsDeviceEntry 3 }

scmDiagnosticsDeviceDescr  OBJECT-TYPE
	SYNTAX DisplayString (SIZE (0..64))
	MAX-ACCESS read-only
	STATUS current
	DESCRIPTION
		"A description of the type and instance of the
		storage described by this entry."
        ::= { scmDiagnosticsDeviceEntry 4 }

scmDiagnosticsDeviceID OBJECT-TYPE
        SYNTAX          INTEGER (1..2147483647)
        MAX-ACCESS      read-only
        STATUS          current
        DESCRIPTION
                "The product ID for this device."
        ::= { scmDiagnosticsDeviceEntry 5 }

scmDiagnosticsDeviceStatus OBJECT-TYPE
 	SYNTAX INTEGER
		{
		unknown(1),
		running(2),
		warning(3),
		testing(4),
		down(5),
		printing(6)
		}
        MAX-ACCESS      read-only
        STATUS          current
        DESCRIPTION
                "The current operational state of the device
 	described by this row of the table.  A value
 	unknown(1) indicates that the current state of the
 	device is unknown.  running(2) indicates that the
 	device is up and running and that no unusual error
 	conditions are known.  The warning(3) state
 	indicates that agent has been informed of an
 	unusual error condition by the operational software
 	(e.g., a disk device driver) but that the device is
 	still 'operational'.  An example would be high
 	number of soft errors on a disk.  A value of
 	testing(4), indicates that the device is not
 	available for use because it is in the testing
 	state.  The state of down(5) is used only when the
 	agent has been informed that the device is not
 	available for any use."
        ::= { scmDiagnosticsDeviceEntry 6 }

scmDiagnosticsDeviceErrors OBJECT-TYPE
        SYNTAX          Counter
        MAX-ACCESS      read-only
        STATUS          current
        DESCRIPTION
                "The number of errors detected on this device.  It
 	should be noted that as this object has a SYNTAX
 	of Counter, that it does not have a defined
 	initial value.  However, it is recommended that
 	this object be initialized to zero."
        ::= { scmDiagnosticsDeviceEntry 7 }

scmDiagnosticsRequest OBJECT-TYPE
        SYNTAX	INTEGER
        	{
		on(1),
		off(2)
		}
        MAX-ACCESS      read-write
        STATUS          current
        DESCRIPTION
                "Diagnotics Request"
        ::= { scmDiagnosticsDeviceEntry 8 }

scmGenBaseDeviceImageFileName OBJECT-TYPE
        SYNTAX	DisplayString (SIZE (0..31))
        MAX-ACCESS      read-only
        STATUS          current
        DESCRIPTION
                "It is the temporay Value.
                --> It will be moved to SCM General Mib"
        ::= { scmDiagnosticsDeviceEntry 999 }
END
