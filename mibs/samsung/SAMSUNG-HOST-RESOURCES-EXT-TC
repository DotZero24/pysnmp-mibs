SAMSUNG-HOST-RESOURCES-EXT-TC DEFINITIONS ::= BEGIN

-- Module:  Host Resources TC
-- File: SamsungHosttc.mib
-- Editors: wono.song@samsung.com
-- Date:    July 17, 2004
-- Version: 1.00

--  Textual Conventions companion to the Host Resources Extensions MIB
--  Contains the REGISTRY of SCMI Standard Device Types,
--  the REGISTRY of SCMI Standard CRU Types,
--  the REGISTRY of SCMI HRX Admin Service Types, and
--  the REGISTRY of SCMI HRX Admin Device Operation Types.

IMPORTS
    MODULE-IDENTITY, OBJECT-IDENTITY,
        OBJECT-TYPE
            FROM SNMPv2-SMI             -- IETF RFC 1442/1902/2578
    TEXTUAL-CONVENTION
            FROM SNMPv2-TC              -- IETF RFC 1443/1903/2579
    samsungCommonMIB
            FROM SAMSUNG-COMMON-MIB;

scmHrTC MODULE-IDENTITY
    LAST-UPDATED "0407170000Z" -- 17 Jul 2004
    ORGANIZATION "Samsung Corporation - SCMI Working Group"
    CONTACT-INFO
        "           SCMI Editors
        Email:      coherence@crt.samsung.com
        "
    DESCRIPTION
        "Version:    1.00

        The TC module for textual conventions, enumerated types, OIDs,
        and other volatile elements of the companion Host Resources
        Extensions MIB ('scmHrMIB'), which supports extended
        configuration and management of various host resources for
        network accessible host systems.  These modules augment and
        extend the original IETF Host Resources MIB (RFC 2790).

        Usage:  This MIB module introduces support for the 'realization'
        of both 'physical' and 'logical' devices, consistent with ISO
        DPA (Document Printing Application), ISO/IEC 10175, as reflected
        in the object 'scmHrDevInfoRealization'.

        Note:   Conforming implementations SHALL NOT 'bubble up' status
        from 'physical' devices to associated 'logical' devices.  All


        devices SHALL report their own status ONLY.

        See:    Section 9 'Supplement' in SCMI Extensions to IETF Host
        Resources TC, for implementation guidance for this TC module.

        Copyright (C) 1995-2003 Samsung Corporation. All Rights Reserved."
    ::= { samsungCommonMIB 52 }

--
--          SCMI Extensions to IETF Host Resources (HRX) TC
--

--          REGISTRY of SCMI Standard Device Types
--          (used with 'hrDeviceType' in Device Group
--          of the IETF Host Resources MIB, RFC 2790).
--
--  Usage:  Developers SHOULD request registration of appropriate
--  SCMI standard device types when they design or integrate a device
--  (with some physical, and NOT merely logical, realization)
--  which is network manageable on a host system.
--
--  Usage:  Logical devices (ie, services of some sort) SHOULD
--  be represented by: a) their own fully free-standing MIBs; and/or
--  b) elaboration of an existing IETF or SCMI standard device type into
--  a 'logical' sibling.
--
--  The final arc of IETF standard device types is within the
--  range '1..49'.
--  The final arc of SCMI standard device types is within the
--  range '101..149'.
--
--  In the future, SCMI MAY add types for 'marker', 'input tray', etc,
--  to enable support of managed host systems which do NOT have printer
--  capabilities (and therefore do NOT implement the Printer MIB),
--  and to support installation and configuration information for
--  their component physical subunits.

scmHrDeviceTypes OBJECT-IDENTITY
    STATUS      current
    DESCRIPTION
        "The root of all additional device types defined in HRX TC."
    ::= { scmHrTC 2 }

scmHrDeviceHostSystem OBJECT-IDENTITY
    STATUS      current
    DESCRIPTION
        "Host system device type - manufacturer independent.
        For host systems which instrument multiple devices and
        support MIBs with tables INDEXed by 'hrDeviceIndex', the single
        'scmHrDeviceHostSystem' device represents the 'root' device
        which MAY be used to manage overall host system defaults,
        configuration, status, etc."
    REFERENCE
        "See:   'scmHrDeviceHostSystemHistory' in this SCMI HRX TC."


    ::= { scmHrDeviceTypes 101 }

scmHrDeviceScanner OBJECT-IDENTITY
    STATUS      current
    DESCRIPTION
        "Scanner device type - manufacturer independent.
        An 'scmHrDeviceScanner' device with 'scmHrDevInfoRealization' of
        'physical' is a 'real' input device (eg, a 'scan channel' on a
        multifunction printer).
        An 'scmHrDeviceScanner' device with 'scmHrDevInfoRealization' of
        'logical' is a 'virtual' input device (eg, a 'personality' of a
        'scan channel' on a multifunction printer)."
    REFERENCE
        "See:   'scmHrDeviceScannerHistory' in this SCMI HRX TC."
    ::= { scmHrDeviceTypes 102 }

scmHrDeviceCopier OBJECT-IDENTITY
    STATUS      current
    DESCRIPTION
        "Copier device type - manufacturer independent.
        An 'scmHrDeviceCopier' device with 'scmHrDevInfoRealization' of
        'physical' is a 'real' I/O device (eg, a 'copier' on a
        multifunction printer).
        An 'scmHrDeviceCopier' device with 'scmHrDevInfoRealization' of
        'logical' is a 'virtual' I/O device (eg, a 'personality' of a
        'copier' on a multifunction printer)."
    REFERENCE
        "See:   'scmHrDeviceCopierHistory' in this SCMI HRX TC."
    ::= { scmHrDeviceTypes 103 }

scmHrDeviceFax OBJECT-IDENTITY
    STATUS      current
    DESCRIPTION
        "Fax device type - manufacturer independent.
        An 'scmHrDeviceFax' device with 'scmHrDevInfoRealization' of
        'physical' is a 'real' I/O device (eg, a 'fax channel' on a
        multifunction printer).
        An 'scmHrDeviceFax' device with 'scmHrDevInfoRealization' of
        'logical' is a 'virtual' I/O device (eg, a 'personality' of a
        'fax channel' on a multifunction printer)."
    REFERENCE
        "See:   'scmHrDeviceFaxHistory' in this SCMI HRX TC."
    ::= { scmHrDeviceTypes 104 }

scmHrDeviceMailbox OBJECT-IDENTITY
    STATUS      current
    DESCRIPTION
        "Mailbox device type - manufacturer independent.
        An 'scmHrDeviceMailbox' device is a 'multi-bin' output device,
        with each 'bin' assigned to a user, group, account, etc, and
        (optionally) physical security associated with each 'bin'.
        An 'scmHrDeviceMailbox' device with 'scmHrDevInfoRealization' of
        'physical' is a 'real' output device (eg, a 'tower mailbox' on
        a high-end printer).


        An 'scmHrDeviceMailbox' device with 'scmHrDevInfoRealization' of
        'logical' is a 'virtual' output device (eg, a 'personality' of a
        'tower mailbox' on a high-end printer).

        An 'scmHrDeviceMailbox' device with 'scmHrDevInfoRealization' of
        'logical' MAY also indicate the current configuration of a
        'physical' device of type 'scmHrDeviceMailboxSorter'."
    REFERENCE
        "See:   'scmHrDeviceMailboxSorter' and 'scmHrDeviceSorter'."
    ::= { scmHrDeviceTypes 105 }

scmHrDeviceFinisher OBJECT-IDENTITY
    STATUS      current
    DESCRIPTION
        "Finisher device type - manufacturer independent.
        An 'scmHrDeviceFinisher' device is an output finishing device.
        An 'scmHrDeviceFinisher' device with 'scmHrDevInfoRealization'
        of 'physical' is a 'real' output device (eg, a 'stapler'
        on a high-end printer).
        An 'scmHrDeviceFinisher' device with 'scmHrDevInfoRealization'
        of 'logical' is a 'virtual' output device (eg, a 'personality'
        of a 'stapler' on a high-end printer)."
    ::= { scmHrDeviceTypes 106 }

scmHrDeviceFeeder OBJECT-IDENTITY
    STATUS      current
    DESCRIPTION
        "Feeder device type - manufacturer independent.
        An 'scmHrDeviceFeeder' device is an input device.
        An 'scmHrDeviceFeeder' device with 'scmHrDevInfoRealization'
        of 'physical' is a 'real' output device (eg, a 'high-capacity
        feeder' on a high-end printer).
        An 'scmHrDeviceFeeder' device with 'scmHrDevInfoRealization'
        of 'logical' is a 'virtual' output device (eg, a 'personality'
        of a 'high-capacity feeder' on a high-end printer)."
    ::= { scmHrDeviceTypes 107 }

scmHrDeviceSorter OBJECT-IDENTITY
    STATUS      current
    DESCRIPTION
        "Sorter device type - manufacturer independent.
        An 'scmHrDeviceSorter' device is a 'multi-bin' output device,
        with each 'bin' assigned to a copy of the current job, and
        NO physical security associated with each 'bin'.
        An 'scmHrDeviceSorter' device with 'scmHrDevInfoRealization' of
        'physical' is a 'real' output device (eg, a '10-bin sorter' on
        a mid-range printer).
        An 'scmHrDeviceSorter' device with 'scmHrDevInfoRealization' of
        'logical' is a 'virtual' output device (eg, a 'personality' of a
        '10-bin sorter' on a mid-range printer).

        An 'scmHrDeviceSorter' device with 'scmHrDevInfoRealization' of
        'logical' MAY also indicate the current configuration of a
        'physical' device of type 'scmHrDeviceMailboxSorter'."


    REFERENCE
        "See:   'scmHrDeviceMailboxSorter' and 'scmHrDeviceMailbox'."
    ::= { scmHrDeviceTypes 108 }

scmHrDeviceMailboxSorter OBJECT-IDENTITY
    STATUS      current
    DESCRIPTION
        "MailboxSorter device type - manufacturer independent.
        An 'scmHrDeviceMailboxSorter' is a 'multi-bin' output device,
        which MAY be configured as either a 'mailbox' or a 'sorter',
        by a system adminstrator or by default product configuration.
        An 'scmHrDeviceMailboxSorter' with 'scmHrDevInfoRealization' of
        'physical' is a 'real' output device and associated with
        associated with exactly two 'logical' output devices of types
        'scmHrDeviceMailbox' and 'scmHrDeviceSorter' - one of these
        'logical' devices MAY be 'running' (currently configured) - at
        least one SHALL be 'down' (NOT currently configured)."
    ::= { scmHrDeviceTypes 109 }

scmHrDevicePrintAppliance OBJECT-IDENTITY
    STATUS      current
    DESCRIPTION
        "Print appliance device type - manufacturer independent.
        An 'scmHrDevicePrintAppliance' is a network printing appliance
        with 'scmHrDevInfoRealization' of 'physical'.
        An 'scmHrDevicePrintAppliance' SHALL statically and/or actively
        discover available network printers and SHOULD advertise them
        as supported output devices, using rows in 'hrDeviceTable' of
        IETF HR MIB (RFC 2790) and 'prtGeneralTable' of the Printer MIB
        (RFC 1759 or successor), with 'hrDeviceType' set to
        'hrDevicePrinter'.
        An 'scmHrDevicePrintAppliance' SHALL NOT use 'hrDeviceIndex' of
        '1' (first row) for an 'hrDevicePrinter' row, because a network
        printing appliance is an enhanced spooler and NOT a printer."
    REFERENCE
        "See:   'hrDevicePrinter' in IETF Host Resources MIB (RFC 2790).
        See:    'scmHrDevicePrinterHistory' in this SCMI HRX TC."
    ::= { scmHrDeviceTypes 110 }

scmHrDeviceMarker OBJECT-IDENTITY
    STATUS      current
    DESCRIPTION
        "Marker Engine device type - manufacturer independent.
        An 'scmHrDeviceMarker' device with 'scmHrDevInfoRealization'
        of 'physical' is a 'real' output device (eg, the
        'marking engine' on a multifunction printer or copier).  The
        marking engine is the module that accepts a print ready image
        and physical media as input and outputs physical media with a
        physical representation of the print ready input image.  The
        'scmHrDeviceMarker' is a
        single module within a group of modules that cumulatively are
        represented by 'hrDevicePrinter'. The marker shall represent the
        whole marker as a single physical unit and should maintain a
        single entry in the 'hrDeviceTable' for all products that


        support a single marking engine regardless of internal engine
        mark points.
        (e.g. B&W, Highlight Color and Full Color Presses shall have a
        single entry in 'hrDeviceTable'). Multiple entries of
        'scmHrDeviceMarker' may exist in the 'hrDeviceTable' if the
        system supports multiple print engines whether chained, in
        parallel or in any other configuration.
        An 'scmHrDeviceMarker' SHALL NOT use 'hrDeviceIndex' of
        '1' (first row).  The index 1 is reserved for an
        'hrDevicePrinter' row."
    ::= { scmHrDeviceTypes 111 }

scmHrDeviceFinisherBFM OBJECT-IDENTITY
    STATUS      current
    DESCRIPTION
        "Basic Finisher Module device type - manufacturer independent.
        An 'scmHrDeviceFinisherBFM' device is a basic output finishing
        device. An 'scmHrDeviceFinisherBFM' device with
        'scmHrDevInfoRealization' of 'physical' is a 'real' output
        device (eg, a 'stapler' on a high-end printer).
        An 'scmHrDeviceFinisherBFM' device with
        'scmHrDevInfoRealization' of 'logical' is a 'virtual' output
        device (eg, a 'personality' of a 'stapler' on a high-end
        printer)."
    ::= { scmHrDeviceTypes 112 }

scmHrDeviceFinisherMFF OBJECT-IDENTITY
    STATUS      current
    DESCRIPTION
        "Multi-Function Finisher device type - manufacturer
         independent.
        An 'scmHrDeviceFinisherMFF' device is a multi-function output
         finishing device. An 'scmHrDeviceFinisherMFF' device with
         'scmHrDevInfoRealization' of 'physical' is a 'real' output
         device (eg, a 'saddle stitcher', 'C-Folder', 'Z-Folder',
         'Hole Puncher' on a high-end printer).
        An 'scmHrDeviceFinisherMFF' device with
         'scmHrDevInfoRealization' of 'logical' is a 'virtual' output
         device (eg, a 'personality' of a 'saddle stitcher',
         'C-Folder', 'Z-Folder', 'Hole Puncher' on a
        high-end printer)."
    ::= { scmHrDeviceTypes 113 }

scmHrDeviceFinisherXIM OBJECT-IDENTITY
    STATUS      current
    DESCRIPTION
         "eXternal Interface Module Finisher device type.
        An 'scmHrDeviceFinisherXIM' device is a hardware interface
        used to pass media from a Samsung printing device to a 3rd party
        finishing devices. The 'scmHrDeviceFinihserXIM' may or may not
        contain its own output trays or finishing capabilities.
        An 'scmHrDeviceFinisherXIM' device with
        'scmHrDevInfoRealization' of 'physical' is a 'real' output
        device (e.g., an 'output bridge' on a high-end printer)."


    ::= { scmHrDeviceTypes 114 }

scmHrDeviceFinisher3rdParty OBJECT-IDENTITY
    STATUS      current
    DESCRIPTION
         "3rd Party Finisher device type - manufacturer independent.
        An 'scmHrDeviceFinisher3rdParty' device is an output finishing
        device. An 'scmHrDeviceFinisher3rdParty' device with
        'scmHrDevInfoRealization'
        of 'physical' is a 'real' output device (eg, a 'stapler' on
        a high-end printer). An 'scmHrDeviceFinisher3rdParty' device
        with 'scmHrDevInfoRealization' of 'logical' is a 'virtual'
        output device (eg, a 'personality' of a 'stapler' on a high-end
        printer)."
    ::= { scmHrDeviceTypes 115 }

scmHrDevicePaymentInterface OBJECT-IDENTITY
    STATUS      current
    DESCRIPTION
        "Payment Interface device type - manufacturer independent.
        An 'scmHrDevicePaymentInterface' device is an payment
        authorization device.
        An 'scmHrDevicePaymentInterface' device with
        'scmHrDevInfoRealization' of 'physical' is a 'real' point of
        purchase validation device (eg, a 'coin operated', 'smart card'
        or other form of point of purchase payment for services
        rendered on a multi-function printer or copier).
        An 'scmHrDevicePaymentInterface' device with
        'scmHrDevInfoRealization' of 'logical' is a 'virtual' point
        of purchase validation device (eg, a software service that
        accepts payment through the Web or some other form of remote
        point of purchase payment for services rendered on a
        multi-function printer or copier)."
    ::= { scmHrDeviceTypes 116 }

scmHrDeviceInterposer OBJECT-IDENTITY
    STATUS      current
    DESCRIPTION
        "Interposer device type - manufacturer independent.
        An 'scmHrDeviceInterposer' device is an input device which
        physically resides downstream of the print engine amongst
        finishing modules.
        An 'scmHrDeviceInterposer' device with
        'scmHrDevInfoRealization' of 'physical' is a 'real' input
        device (eg, a 'high-capacity Interposing feeder' that
        physically resides amongst finishing modules
        on a high-end printer).
        An 'scmHrDeviceInterposer' device with
        'scmHrDevInfoRealization' of 'logical' is a 'virtual'
        input device (eg, a 'personality' of a
        'high-capacity Interposing feeder' that physically resides
        amongst finishing modules on a high-end printer).
        Interposers are essentially feeders that are placed
        downstream of the print engine paper path and upstream of


        finishing devices.  Interposer fed media is not marked by the
        print engine; instead media fed from an interposer is inserted
        before, between or after marked pages.  The media constitutes
        covers, separators etc."
    ::= { scmHrDeviceTypes 117 }

--          REGISTRY of SCMI Standard History Device Types
--          (used with 'hrDeviceType' in Device Group
--          of the IETF Host Resources MIB, RFC 2790).
--
--  Usage:  May be used to segregate historical information for any
--  standard device type in any MIB table indexed by 'hrDeviceIndex'.
--
--  Eg, the 'scmJobGenBasicTable' in the SCMI Job Monitoring MIB and/or
--  the 'jm[Job|Attribute]Table' in the PWG Job Monitoring MIB could
--  have a segment for an 'hrDevicePrinter' device type (current and
--  very recent jobs) and a segment for an 'scmHrDevicePrinterHistory'
--  device type (longer-term job history of completed jobs).
--  Entries in the 'scmHrDevDetailTable' SHOULD cross-link these related
--  devices (using 'deviceJob[Service|History]DeviceIndex').
--
--  Algorithm:  The final arc of each standard job history device type
--  is derived by adding decimal '50' to the final arc of the companion
--  standard job service device type.

scmHrDeviceHostSystemHistory OBJECT-IDENTITY
    STATUS      current
    DESCRIPTION
        "Host system history device type - manufacturer independent."
    REFERENCE
        "See:   'scmHrDeviceHostSystem' in this SCMI HRX TC."
    ::= { scmHrDeviceTypes 151 }

scmHrDeviceScannerHistory OBJECT-IDENTITY
    STATUS      current
    DESCRIPTION
        "Scanner history device type - manufacturer independent."
    REFERENCE
        "See:   'scmHrDeviceScanner' in this SCMI HRX TC."
    ::= { scmHrDeviceTypes 152 }

scmHrDeviceCopierHistory OBJECT-IDENTITY
    STATUS      current
    DESCRIPTION
        "Copier history device type - manufacturer independent."
    REFERENCE
        "See:   'scmHrDeviceCopier' in this SCMI HRX TC."
    ::= { scmHrDeviceTypes 153 }

scmHrDeviceFaxHistory OBJECT-IDENTITY
    STATUS      current
    DESCRIPTION
        "Fax history device type - manufacturer independent."
    REFERENCE


        "See:   'scmHrDeviceFax' in this SCMI HRX TC."
    ::= { scmHrDeviceTypes 154 }

scmHrDevicePrinterHistory OBJECT-IDENTITY
    STATUS      current
    DESCRIPTION
        "Printer history device type - manufacturer independent."
    REFERENCE
        "See:   'hrDevicePrinter' in the IETF HR MIB."
    ::= { scmHrDeviceTypes 55 }         -- 'hrDevicePrinter' + 50

--          REGISTRY of SCMI Standard CRU Types
--          (used with 'hrDeviceType' in Device Group
--          of the IETF Host Resources MIB, RFC 2790).

scmHrCruXerographicModule OBJECT-IDENTITY
    STATUS      current
    DESCRIPTION
        "CRU xerographic module - manufacturer independent.
        An 'scmHrCruXerographicModule' device is a customer
        replaceable unit, with 'scmHrDevInfoRealization' of 'physical'."
    ::= { scmHrDeviceTypes 201 }

scmHrCruFuserModule OBJECT-IDENTITY
    STATUS      current
    DESCRIPTION
        "CRU fuser module - manufacturer independent.
        An 'scmHrCruFuserModule' device is a customer
        replaceable unit, with 'scmHrDevInfoRealization' of 'physical'."
    ::= { scmHrDeviceTypes 202 }

scmHrCruTonerBottleModule OBJECT-IDENTITY
    STATUS      current
    DESCRIPTION
        "CRU toner bottle module - manufacturer independent.
        An 'scmHrCruTonerBottleModule' device is a customer
        replaceable unit, with 'scmHrDevInfoRealization' of 'physical'."
    ::= { scmHrDeviceTypes 203 }

scmHrCruCollectorBottleModule OBJECT-IDENTITY
    STATUS      current
    DESCRIPTION
        "CRU (developer) collector bottle - manufacturer independent.
        An 'scmHrCruCollectorBottleModule' device is a customer
        replaceable unit, with 'scmHrDevInfoRealization' of 'physical'."
    ::= { scmHrDeviceTypes 204 }

scmHrCruTrayFeedHeadModule OBJECT-IDENTITY
    STATUS      current
    DESCRIPTION
        "CRU tray feed head module - manufacturer independent.
        An 'scmHrCruTrayFeedHeadModule' device is a customer
        replaceable unit, with 'scmHrDevInfoRealization' of 'physical'."
    ::= { scmHrDeviceTypes 205 }


scmHrCruAdfFeedHeadModule OBJECT-IDENTITY
    STATUS      current
    DESCRIPTION
        "CRU ADF feed head module - manufacturer independent.
        An 'scmHrCruAdfFeedHeadModule' device is a customer
        replaceable unit, with 'scmHrDevInfoRealization' of 'physical'.
        Note:   ADF is an acronym for 'automatic document feeder'."
    ::= { scmHrDeviceTypes 206 }

scmHrCruFuserWebModule OBJECT-IDENTITY
    STATUS      current
    DESCRIPTION
        "CRU fuser web module - manufacturer independent.
        An 'scmHrCruFuserWebModule' device is a customer
        replaceable unit, with 'scmHrDevInfoRealization' of 'physical'.
        Note:   A 'fuser web' is an oil-soaked fiber roll in a fuser,
        which prevents toner from getting on the fuser roll.  The 'fuser
        web' device would normally be replaced several times before the
        actual fuser device ('scmHrCRUFuserModule') is replaced."
    ::= { scmHrDeviceTypes 207 }

scmHrCruFilterModule OBJECT-IDENTITY
    STATUS      current
    DESCRIPTION
        "CRU filter module - manufacturer independent.
        An 'scmHrCruFilterModule' device is a customer replaceable
        filter or filter unit, with 'scmHrDevInfoRealization' of
        'physical'."
    ::= { scmHrDeviceTypes 208 }

scmHrCruCleanerUnitModule OBJECT-IDENTITY
    STATUS      current
    DESCRIPTION
        "CRU cleaner unit module - manufacturer independent.
        An 'scmHrCruCleanerUnitModule' device is a customer
        replaceable cleaner unit, with 'scmHrDevInfoRealization' of
        'physical' (eg, a belt cleaner or a photoreceptor cleaner)."
    REFERENCE
        "See:   'cleanerUnit' in 'PrtMarkerSuppliesTypeTC' in
                the Printer MIB v2."
    ::= { scmHrDeviceTypes 209 }

scmHrCruTransferUnitModule OBJECT-IDENTITY
    STATUS      current
    DESCRIPTION
        "CRU transfer unit module - manufacturer independent.
        An 'scmHrCruTransferUnitModule' device is a customer
        replaceable transfer unit, with 'scmHrDevInfoRealization' of
        'physical'."
    REFERENCE
        "See:   'transferUnit' in 'PrtMarkerSuppliesTypeTC' in
                the Printer MIB v2."
    ::= { scmHrDeviceTypes 210 }


scmHrCruTransferRollerModule OBJECT-IDENTITY
    STATUS      current
    DESCRIPTION
        "CRU transfer roller module - manufacturer independent.
        An 'scmHrCruTransferRollerModule' device is a customer
        replaceable transfer roller, with 'scmHrDevInfoRealization' of
        'physical' (eg, a biased transfer roller)."
    REFERENCE
        "See:   'transferUnit' in 'PrtMarkerSuppliesTypeTC' in
                the Printer MIB v2."
    ::= { scmHrDeviceTypes 211 }

scmHrCruPFPFeedRollModule OBJECT-IDENTITY
    STATUS      current
    DESCRIPTION
        "CRU Paper Feed Platform module - manufacturer independent.
        An 'scmHrCruPaperFeedModule' device is a customer
        replaceable unit, with 'scmHrDevInfoRealization' of 'physical'."
    ::= { scmHrDeviceTypes 212 }

scmHrCruPFPRetardRollModule OBJECT-IDENTITY
    STATUS    current
    DESCRIPTION
        "CRU PFP Retard Roll module - manufacturer independent.
        An 'scmHrCruPFPRetardRollModule' device is a customer
        replaceable unit, with 'scmHrDevInfoRealization' of 'physical'."
    ::= { scmHrDeviceTypes 213 }

scmHrDeviceUSBPort  OBJECT-IDENTITY
 STATUS current
 DESCRIPTION
  "The device type identifier used for a
  Universal Serial Bus port."
 ::= { scmHrDeviceTypes 250 }

scmHrDeviceFlashDIMMFileStore  OBJECT-IDENTITY
 STATUS current
 DESCRIPTION
  " The device type identifier used for a Flash DIMM that contains
                  a file system that is used to store files such as font
    opposed to a Flash DIMM that contains a boot loader."
 ::= { scmHrDeviceTypes 260 }

scmHrDeviceFlashDIMMBootLoader  OBJECT-IDENTITY
 STATUS current
 DESCRIPTION
  "The device type identifier used for a Flash DIMM that contains
  the boot loader for a device. Files may or may not be stored on
  this device. As opposed to a Flash DIMM that contains a file
  store system."
 ::= { scmHrDeviceTypes 261 }


--          REGISTRY of SCMI HRX Admin Service Types (Classes)
--          (MAY be used in the 'scmSec[Service|PolicyService]TypeOID'
--          objects in the closely related SCMI Security MIB, in
--          conforming management agents which do NOT implement the
--          related SCMI System Admin MIB).

scmHrAdminServiceTypes OBJECT-IDENTITY
    STATUS      current
    DESCRIPTION
        "The root of all host system management service types (classes)
        defined in the Host Resources Extensions TC."
    REFERENCE
        "See:   'ScmSecPosixVerbs' and 'scmSecServiceTypeOID'
                in SCMI Security TC/MIB."
    ::= { scmHrTC 3 }

scmHrAdminObjectService OBJECT-IDENTITY
    STATUS      current
    DESCRIPTION
        "The host system object management service."
    REFERENCE
        "See:   'scmSysAdminObject...' in SCMI System Admin MIB.
        See:    'ScmSecPosixVerbs' and 'scmSecServiceTypeOID'
                in SCMI Security TC/MIB."
    ::= { scmHrAdminServiceTypes 1 }

scmHrAdminServerService OBJECT-IDENTITY
    STATUS      current
    DESCRIPTION
        "The host system server management service."
    REFERENCE
        "See:   'scmSysAdminServer...' in SCMI System Admin MIB,
                'hrSW[Running|Installed]Table' in IETF HR MIB, and
                'scmHrSW[Running|Installed]ExtTable' in SCMI HRX MIB.
        See:    'ScmSecPosixVerbs' and 'scmSecServiceTypeOID'
                in SCMI Security TC/MIB."
    ::= { scmHrAdminServiceTypes 2 }

scmHrAdminDeviceService OBJECT-IDENTITY
    STATUS      current
    DESCRIPTION
        "The host system device management service."
    REFERENCE
        "See:   'scmSysAdminDevice...' in SCMI System Admin MIB,
                'hrDeviceTable' in IETF HR MIB, and
                'scmHrDev[Info|Help|Mgmt|Power|Traffic|Calendar]Table'
                in SCMI HRX MIB.
        See:    'ScmSecPosixVerbs' and 'scmSecServiceTypeOID'
                in SCMI Security TC/MIB."
    ::= { scmHrAdminServiceTypes 3 }

scmHrAdminJobService OBJECT-IDENTITY
    STATUS      current
    DESCRIPTION


        "The host system job management service."
    REFERENCE
        "See:   'scmSysAdminJob...' in SCMI System Admin MIB, and
                'scmJob[...]Table' in SCMI Job Monitoring MIB.
        See:    'ScmSecPosixVerbs' and 'scmSecServiceTypeOID'
                in SCMI Security TC/MIB."
    ::= { scmHrAdminServiceTypes 4 }

scmHrAdminDocService OBJECT-IDENTITY
    STATUS      current
    DESCRIPTION
        "The host system document management service."
    REFERENCE
        "See:   'scmSysAdminDoc...' in SCMI System Admin MIB, and
                'scmDoc[...]Table' in SCMI Job Monitoring MIB.
        See:    'ScmSecPosixVerbs' and 'scmSecServiceTypeOID'
                in SCMI Security TC/MIB."
    ::= { scmHrAdminServiceTypes 5 }

scmHrAdminSecurityService OBJECT-IDENTITY
    STATUS      current
    DESCRIPTION
        "The host system security management service."
    REFERENCE
        "See:   'scmSysAdminSecurity...' in SCMI System Admin MIB.
        See:    'ScmSecPosixVerbs' and 'scmSecServiceTypeOID'
                in SCMI Security TC/MIB."
    ::= { scmHrAdminServiceTypes 6 }

scmHrAdminCommsService OBJECT-IDENTITY
    STATUS      current
    DESCRIPTION
        "The host system communications management service."
    REFERENCE
        "See:   'scmSysAdminComms...' in SCMI System Admin MIB and
                SCMI Comms Config and Comms Engine MIBs.
        See:    'ScmSecPosixVerbs' and 'scmSecServiceTypeOID'
                in SCMI Security TC/MIB."
    ::= { scmHrAdminServiceTypes 7 }

--          REGISTRY of SCMI HRX Admin Device Operation Types
--          (MAY be used in the 'scmSecPolicyVerbTypeOID'
--          object in the closely related SCMI Security MIB, for
--          fine-grained access control to device management verbs, in
--          conforming management agents which do NOT implement the
--          related SCMI System Admin MIB).

scmHrAdminDeviceOperationTypes OBJECT-IDENTITY
    STATUS      current
    DESCRIPTION
        "The root of all host resources admin device operation types
        defined in the Host Resources Extensions TC.

        Usage:  The following OIDs support access control for the simple


        device admin operations defined in 'ScmHrDevMgmtCommandRequest'
        and used in 'scmHrDevMgmtCommandRequest' in the SCMI HRX MIB,
        via 'scmSec[Master|Policy]VerbTypeOID' in the SCMI Security MIB,
        WITHOUT requiring implementation of the SCMI System Admin MIB."
    REFERENCE
        "See:   'scmSec[Master|Policy]VerbTypeOID' in
                SCMI Security MIB."
    ::= { scmHrTC 4 }

scmHrAdminDeviceNone            OBJECT IDENTIFIER
    ::= { scmHrAdminDeviceOperationTypes 1 }
scmHrAdminDeviceStartup         OBJECT IDENTIFIER
    ::= { scmHrAdminDeviceOperationTypes 2 }
scmHrAdminDeviceResetWarning    OBJECT IDENTIFIER
    ::= { scmHrAdminDeviceOperationTypes 3 }
scmHrAdminDeviceTest            OBJECT IDENTIFIER
    ::= { scmHrAdminDeviceOperationTypes 4 }
scmHrAdminDeviceShutdown        OBJECT IDENTIFIER
    ::= { scmHrAdminDeviceOperationTypes 5 }
scmHrAdminDeviceQuiesce         OBJECT IDENTIFIER
    ::= { scmHrAdminDeviceOperationTypes 6 }
scmHrAdminDeviceResetCounters   OBJECT IDENTIFIER
    ::= { scmHrAdminDeviceOperationTypes 7 }
scmHrAdminDeviceResetWarm       OBJECT IDENTIFIER
    ::= { scmHrAdminDeviceOperationTypes 8 }
scmHrAdminDeviceResetCold       OBJECT IDENTIFIER
    ::= { scmHrAdminDeviceOperationTypes 9 }
scmHrAdminDeviceResetFactory    OBJECT IDENTIFIER
    ::= { scmHrAdminDeviceOperationTypes 10 }
scmHrAdminDeviceFlushInput      OBJECT IDENTIFIER
    ::= { scmHrAdminDeviceOperationTypes 11 }
scmHrAdminDeviceFlushOutput     OBJECT IDENTIFIER
    ::= { scmHrAdminDeviceOperationTypes 12 }
scmHrAdminDeviceFlushInOut      OBJECT IDENTIFIER
    ::= { scmHrAdminDeviceOperationTypes 13 }
scmHrAdminDeviceManage          OBJECT IDENTIFIER
    ::= { scmHrAdminDeviceOperationTypes 14 }
scmHrAdminDeviceRefresh         OBJECT IDENTIFIER
    ::= { scmHrAdminDeviceOperationTypes 15 }
scmHrAdminDeviceWarmUp          OBJECT IDENTIFIER
    ::= { scmHrAdminDeviceOperationTypes 16 }
scmHrAdminDeviceCoolDown        OBJECT IDENTIFIER
    ::= { scmHrAdminDeviceOperationTypes 17 }
scmHrAdminDeviceEnergySave      OBJECT IDENTIFIER
    ::= { scmHrAdminDeviceOperationTypes 18 }
scmHrAdminDeviceWakeUp          OBJECT IDENTIFIER
    ::= { scmHrAdminDeviceOperationTypes 19 }
scmHrAdminDevicePowerToReady    OBJECT IDENTIFIER
    ::= { scmHrAdminDeviceOperationTypes 20 }
scmHrAdminDevicePowerToStandby  OBJECT IDENTIFIER
    ::= { scmHrAdminDeviceOperationTypes 21 }
scmHrAdminDevicePowerToSleep    OBJECT IDENTIFIER
    ::= { scmHrAdminDeviceOperationTypes 22 }


--
--          The Host Resources Extensions (HRX) TC
--
--          Textual Conventions

ScmHrDevCalendarDayOfWeek ::= TEXTUAL-CONVENTION
    STATUS      current
    DESCRIPTION
        "The day of week when the command specified in a conceptual
        row in the 'scmHrDevCalendarTable' SHALL be invoked."
    SYNTAX      INTEGER {
        monday(1),
        tuesday(2),
        wednesday(3),
        thursday(4),
        friday(5),
        saturday(6),
        sunday(7),
        everyDay(8),                    -- monday through sunday
        businessOpenDay(9),             -- site specific
        businessClosedDay(10),          -- site specific
        businessHoliday(11)             -- site specific
    }

ScmHrDevCalendarTimeOfDay ::= TEXTUAL-CONVENTION
    STATUS      current
    DESCRIPTION
        "The time of day when the command specified in a conceptual
        row in the 'scmHrDevCalendarTable' SHALL be invoked, specified
        as hours (0..23) multiplied by 100, added to minutes (0..59),
        added to a constant bias of 10000 (avoids an index value of zero
        in 'scmHrDevCalendarTimeOfDay')."
    SYNTAX      INTEGER (10000..12359)

ScmHrDevDetailType ::= TEXTUAL-CONVENTION
    STATUS      current
    DESCRIPTION
        "The type of the device detail information specified
        in this conceptual row in the 'scmHrDevDetailTable'.

        Usage:  Conforming management stations and management agents
        SHALL implement specified semantics for device detail types."

--      -   Device other/unknown details
--    * 'other'
--    * 'unknown'
--
--      -   Device general info
--    * 'deviceName'
--      - device administrative name in directory (primary name)
--      - (same usage as 'scmCOSpecialName' in SCMI Comms Config TC)
--      - type - (ScmFixedLocaleDisplayString)
--      - subtype - '...ValueOID' (directory in SCMI Comms Config TC)


--      - (eg, 'scmCOInternetDNS')
--      - data - '...ValueString'
--      - (eg, 'showstopper.sample.com')
--      - see - 'scmCOSpecialName' in SCMI Comms Config TC
--      - see - 'deviceAlias' in SCMI HRX TC
--      - see - 'scmHrDevInfoName' in SCMI HRX MIB
--      - see - DPA-1 9.4.1 'Printer-name'
--      - see - DPA-1 9.5.1 'Server-name'
--    * 'deviceAlias'
--      - device administrative alias in directory (alternate name)
--      - (same usage as 'scmCOSpecialName' in SCMI Comms Config TC)
--      - type - (ScmFixedLocaleDisplayString)
--      - subtype - '...ValueOID' (directory in SCMI Comms Config TC)
--      - (eg, 'scmCOInternetDNS')
--      - data - '...ValueString'
--      - (eg, 'LaserRat')
--      - see - 'scmCOSpecialName' in SCMI Comms Config TC
--      - see - 'deviceName' in SCMI HRX TC
--      - see - DPA-1 9.4.2 'Printer-name-aliases'
--      - see - DPA-1 9.5.2 'Server-name-aliases'
--    * 'deviceType'
--      - device type
--      - type - (OBJECT IDENTIFIER)
--      - data - '...ValueOID'
--      - (eg, 'hrDevicePrinter')
--      - see - 'hrDeviceType' in IETF HR MIB
--      - see - 'Usage of hrDeviceType and hrDeviceDescr' section of
--      - 'SCMI Supplement to IETF Host Resources MIB' in SCMI HRX TC
--    * 'deviceDescription'
--      - device description
--      - type - (ScmFixedLocaleDisplayString)
--      - data - '...ValueString'
--      - (eg, 'Samsung DocuCentre 230 ST v1.0 - Printer')
--      - see - 'hrDeviceDescr' in IETF HR MIB
--      - see - 'Usage of hrDeviceType and hrDeviceDescr' section of
--      - 'SCMI Supplement to IETF Host Resources MIB' in SCMI HRX TC
--    * 'deviceID'
--      - device (product) ID
--      - type - (ProductID)
--      - data - '...ValueOID'
--      - (eg, 'scmPidDC230STV1')
--      - see - 'ProductID' and 'hrDeviceID' in IETF HR MIB
--      - see - 'IETF HR DeviceTable' section of
--      - 'SCMI Supplement to IETF Host Resources MIB' in SCMI HRX TC
--    * 'deviceTree'
--      - device tree prefix to name/alias in directory
--      - type - (ScmFixedLocaleDisplayString)
--      - subtype - '...ValueOID' (directory in SCMI Comms Config TC)
--      - (eg, 'scmCONetwareNDS')
--      - data - '...ValueString'
--      - (MAY also appear in 'deviceName')
--    * 'deviceContext'
--      - device context prefix to name/alias in directory
--      - type - (ScmFixedLocaleDisplayString)


--      - subtype - '...ValueOID' (directory in SCMI Comms Config TC)
--      - (eg, 'scmCONetwareNDS')
--      - data - '...ValueString'
--      - (MAY also appear in 'deviceName')
--    * 'deviceManufacturer'
--      - device manufacturer (or OEM) name
--      - type - (ScmFixedLocaleDisplayString)
--      - data - '...ValueString'
--      - compare - 'hrDeviceDescr' in IETF HR MIB
--    * 'deviceModel'
--      - device model (alphanumeric)
--      - type - (ScmFixedLocaleDisplayString)
--      - data - '...ValueString'
--      - see - DPA-1 9.4.4 'Printer-model'
--      - compare - 'hrDeviceDescr' in IETF HR MIB
--    * 'deviceSerialNumber'
--      - device serial number
--      - see - 'scmHrDevInfoSerialNumber' in SCMI HRX MIB
--      - type - (ScmFixedLocaleDisplayString)
--      - data - '...ValueString'
--    * 'deviceVendor'
--      - device vendor (to customer)
--      - type - (ScmFixedLocaleDisplayString)
--      - data - '...ValueString'
--      - compare - 'hrDeviceDescr' in IETF HR MIB
--    * 'deviceVersion'
--      - device version (alphanumeric)
--      - type - (ScmFixedLocaleDisplayString)
--      - data - '...ValueString'
--      - compare - 'hrDeviceDescr' in IETF HR MIB
--
--      -   Device service info
--    * 'deviceServiceByCustomer'
--      - device serviced by customer (rather than vendor)
--      - type - (TruthValue)
--      - data - '...ValueInteger'
--      - 'true' = serviced by customer
--      - 'false' = serviced by vendor
--    * 'deviceReplaceByCustomer'
--      - device replaced by customer (rather than vendor)
--      - type - (TruthValue)
--      - data - '...ValueInteger'
--      - 'true' = replaced by customer
--      - 'false' = replaced by vendor
--    * 'deviceServicePlanName'
--      - device service plan name
--      - type - (ScmFixedLocaleDisplayString)
--      - data - '...ValueString'
--      - (eg, 'Goldspot77')
--    * deviceServicePlanPassword'
--      - device service plan password (protected/encrypted)
--      - type - (ScmFixedLocaleDisplayString)
--      - data - '...ValueString'
--      - (eg, 'EA123456')


--    * 'deviceReplaceByWarranty'
--      - device replaced by warranty (rather than at end-of-life)
--      - type - (TruthValue)
--      - data - '...ValueInteger'
--      - 'true' = replaced by warranty (by some date or usage limit)
--      - 'false' = replaced at end-of-life
--
--      -   Device lifetime usage and limits
--      -   (several usage counters MAY be defined for a single device)
--      -   (several usage limits MAY be defined for a single counter)
--      -   (usage counter and usage limit groups are defined as sharing
--      -   the same value of 'scmHrDevDetailIndex')
--    * 'deviceLifetimeUsage'
--      - device lifetime usage counter (MAY be multi-valued)
--      - (SHALL NOT be remotely reset, unlike 'deviceAccountingUsage')
--      - type - (Counter32)
--      - subtype - '...ValueString' (ScmGenMessageMapStringLabel)
--      - and (optional) trailing description after whitespace
--      - data - '...ValueInteger'
--      - (eg, monochrome and color page counters)
--      - note - SHOULD be subtyped by well-formed Samsung message
--      - string label of the 'ScmGenMessageMapStringLabel' syntax
--      - defined in the SCMI General TC (06gentc)
--      - for example:
--      - 'xs-iso-101715-mediaSize-na-letter'
--      -   - counts any DPA media size (w/out type/color)
--      - 'xs-ietf-rfc2911-media-iso-a4-...'
--      -   - counts any IETF IPP 'media' (w/ size, type, or color)
--      - 'xs-scmi-40jobtc-ScmJMImpsCountType-blackAndWhiteCount'
--      -   - counts monochrome impressions
--      - 'xs-scmi-40jobtc-ScmJMImpsCountType-highlightColorCount'
--      -   - counts highlight color impressions
--    * 'deviceReorderLifetimeLimit'
--      - device reorder at limit (MAY be multi-valued)
--      - type - (Cardinal32)
--      - subtype - see parallel 'deviceLifetimeUsage'
--      - data - '...ValueInteger'
--      - positive integer = limit in 'scmHrDevDetailUnit' units
--      - zero = no limit specified
--    * 'deviceWarningLifetimeLimit'
--      - warn device user at usage limit (MAY be multi-valued)
--      - type - (Cardinal32)
--      - subtype - see parallel 'deviceLifetimeUsage'
--      - data - '...ValueInteger'
--      - positive integer = limit in 'scmHrDevDetailUnit' units
--      - zero = no limit specified
--    * 'deviceReplaceLifetimeLimit'
--      - replace device at usage limit (MAY be multi-valued)
--      - type - (Cardinal32)
--      - subtype - see parallel 'deviceLifetimeUsage'
--      - data - '...ValueInteger'
--      - positive integer = limit in 'scmHrDevDetailUnit' units
--      - zero = no limit specified
--    * 'deviceMaximumLifetimeLimit'


--      - stop device at usage limit (MAY be multi-valued)
--      - type - (Cardinal32)
--      - subtype - see parallel 'deviceLifetimeUsage'
--      - data - '...ValueInteger'
--      - positive integer = limit in 'scmHrDevDetailUnit' units
--      - zero = no limit specified
--
--      -   Device message to user time remaining
--      -   (estimated dates when messages will be sent to the user)
--      -   (estimated by the device, based on current rate of usage)
--    * 'deviceDaysUntilReorderMsg'
--      - days left until reorder msg (estimated from rate of usage)
--      - type - (Cardinal32) days
--      - data - '...ValueInteger'
--    * 'deviceDaysUntilWarningMsg'
--      - days left until warning msg (estimated from rate of usage)
--      - type - (Cardinal32) days
--      - data - '...ValueInteger'
--    * 'deviceDaysUntilReplaceMsg'
--      - days left until replace msg (estimated from rate of usage)
--      - type - (Cardinal32) days
--      - data - '...ValueInteger'
--    * 'deviceDaysUntilMaximumMsg'
--      - days left until stop msg (estimated from rate of usage)
--      - type - (Cardinal32) days
--      - data - '...ValueInteger'
--    * 'deviceLifetimeMsgDisplay'
--      - where to send lifetime msgs to user
--      - type - (Cardinal32) local enum below
--      - data - '...ValueInteger'
--      - '0' = none (no msg sent)
--      - '1' = local device UI only
--      - '2' = remote clients only
--      - '3' = both (local and remote)
--
--      -   Device accounting usage
--    * 'deviceAccountingUsage'
--      - device accounting usage counter (MAY be multi-valued)
--      - (MAY be remotely reset, unlike 'deviceLifetimeUsage')
--      - type - (Counter32)
--      - subtype - '...ValueString' (ScmGenMessageMapStringLabel)
--      - and (optional) trailing description after whitespace
--      - data - '...ValueInteger'
--      - (eg, monochrome and color page counters)
--      - see - 'deviceLifetimeUsage' (which is NOT reset remotely)
--      - note - SHOULD be subtyped by a well-formed Samsung message
--      - string label of the 'ScmGenMessageMapStringLabel' syntax
--      - defined in the SCMI General TC (06gentc)
--      - for example:
--      - 'xs-iso-101715-mediaSize-na-letter'
--      -   - counts any DPA media size (w/out type/color)
--      - 'xs-ietf-rfc2911-media-iso-a4-...'
--      -   - counts any IETF IPP 'media' (w/ size, type, or color)
--      - 'xs-scmi-40jobtc-ScmJMImpsCountType-blackAndWhiteCount'


--      -   - counts monochrome impressions
--      - 'xs-scmi-40jobtc-ScmJMImpsCountType-highlightColorCount'
--      -   - counts highlight color impressions
--
--      -   Device message to user and reorder dates
--      -   (fixed dates when messages will be sent to the user)
--      -   (fixed by system administrator)
--    * 'deviceReorderOnDate'
--      - reorder device on fixed date (and send message to user)
--      - type - (DateAndTime)
--      - data - '...ValueString'
--    * 'deviceWarningOnDate'
--      - warn device user on fixed date
--      - type - (DateAndTime)
--      - data - '...ValueString'
--    * 'deviceReplaceOnDate'
--      - replace device on fixed date (and send message to user)
--      - type - (DateAndTime)
--      - data - '...ValueString'
--    * 'deviceMaximumOnDate'
--      - stop device on fixed date (and send message to user)
--      - type - (DateAndTime)
--      - data - '...ValueString'
--
--      -   Device lifetime errors and warnings
--      -   (several error counters MAY be defined for a single device)
--      -   (one error limit MAY be defined for a single error counter)
--      -   (error counter and error limit pairs are defined as sharing
--      -   the same value of 'scmHrDevDetailIndex')
--    * 'deviceLifetimeErrorCount'
--      - device lifetime error counter (MAY be multi-valued)
--      - type - (Counter32)
--      - subtype - '...ValueString' (ScmGenMessageMapStringLabel)
--      - and (optional) trailing description after whitespace
--      - data - '...ValueInteger'
--      - note - SHOULD be subtyped by a well-formed Samsung message
--      - string label of the 'ScmGenMessageMapStringLabel' syntax
--      - defined in the SCMI General TC (06gentc)
--      - for example:
--      - 'xs-ietf-rfc1759-prtAlertCode-jam'
--      -   - paper jam - see 'prtAlertCode' in Printer MIB
--    * 'deviceLifetimeErrorLimit'
--      - device lifetime error limit (MAY be multi-valued)
--      - type - (Cardinal32)
--      - subtype - see parallel 'deviceLifetimeErrorCount'
--      - data - '...ValueInteger'
--      - positive integer = limit in 'deviceLifetimeErrorCount' units
--      - zero = no limit specified
--      - note - product-unique error handling at this limit
--    * 'deviceLifetimeWarningCount'
--      - device lifetime warning counter (MAY be multi-valued)
--      - type - (Counter32)
--      - subtype - '...ValueString' (ScmGenMessageMapStringLabel)
--      - and (optional) trailing description after whitespace


--      - data - '...ValueInteger'
--      - note - SHOULD be subtyped by a well-formed Samsung message
--      - string label of the 'ScmGenMessageMapStringLabel' syntax
--      - defined in the SCMI General TC (06gentc)
--      - for example:
--      - 'xs-ietf-rfc1759-prtAlertCode-inputMediaSupplyLow'
--      -   - paper low - see 'prtAlertCode' in Printer MIB
--    * 'deviceLifetimeWarningLimit'
--      - device lifetime warning limit (MAY be multi-valued)
--      - type - (Cardinal32)
--      - subtype - see parallel 'deviceLifetimeWarningCount'
--      - data - '...ValueInteger'
--      - positive integer = limit in 'deviceLifetimeWarningCount' units
--      - zero = no limit specified
--      - note - product-unique warning handling at this limit
--
--      -   Device message to user triggers
--      -   (actual days before an estimated limit date, when messages
--      -   SHALL be sent to users)
--      -   (while the 'triggers' are in terms of actual days, the
--      -   determination of the [future] limit reached date is based
--      -   on estimation by the device from current rate of usage)
--    * 'deviceTriggerDaysForReorder'
--      - days to reorder msg trigger (send before reorder limit)
--      - type - (DateAndTime)
--      - data - '...ValueString'
--    * 'deviceTriggerDaysForWarning'
--      - days to warning msg trigger (send before warning limit)
--      - type - (DateAndTime)
--      - data - '...ValueString'
--    * 'deviceTriggerDaysForReplace'
--      - days to replace msg trigger (send before replace limit)
--      - type - (DateAndTime)
--      - data - '...ValueString'
--    * 'deviceTriggerDaysForMaximum'
--      - days to stop msg trigger (send before stop limit)
--      - type - (DateAndTime)
--      - data - '...ValueString'
--
--      -   Device message to user dates actually sent
--      -   (log of dates when messages were actually sent to user,
--      -   based on estimates, actual limits, actual dates, etc)
--    * 'deviceReorderMsgSentDate'
--      - date of reorder msg to user (MAY be multi-valued)
--      - type - (DateAndTime)
--      - data - '...ValueString'
--    * deviceWarningMsgSentDate'
--      - date of warning msg to user (MAY be multi-valued)
--      - type - (DateAndTime)
--      - data - '...ValueString'
--    * 'deviceReplaceMsgSentDate'
--      - date of replace msg to user (MAY be multi-valued)
--      - type - (DateAndTime)
--      - data - '...ValueString'


--    * 'deviceMaximumMsgSentDate'
--      - date of maximum msg to user (MAY be multi-valued)
--      - type - (DateAndTime)
--      - data - '...ValueString'
--
--      -   Device reorder and replace actual dates
--      -   (log of dates when reorder and replacement were actually
--      -   done for this device)
--    * 'deviceReorderToVendorDate'
--      - date reorder to vendor sent (MAY be multi-valued)
--      - type - (DateAndTime)
--      - data - '...ValueString'
--    * 'deviceReorderConfirmDate'
--      - date reorder confirm received (MAY be multi-valued)
--      - type - (DateAndTime)
--      - data - '...ValueString'
--    * 'deviceReplaceDate'
--      - date of replacement (MAY be multi-valued)
--      - type - (DateAndTime)
--      - data - '...ValueString'
--    * 'deviceReplaceSystemUsage'
--      - system usage at date of replacement (MAY be multi-valued)
--      - type - (Counter32) some usage counter
--      - (eg, 'total marked images')
--      - date - '...ValueInteger'
--    * 'deviceReplaceWithGeneric'
--      - device MAY be replaced with generic (third-party) part
--      - (MAY indicate that a package is installed to support generics)
--      - type - (TruthValue)
--      - data - '...ValueInteger'
--      - 'true' = device MAY be replaced with a generic part
--      - 'false' = device MAY NOT be replaced with a generic part
--
--      -   Device help info (contact info)
--      - NOTE - Device Help group is DEPRECATED (as of SCMI v4.1)
--      - The following device details SHOULD be used instead
--    * 'deviceHelpName'
--      - device help person name and role
--      - type - (ScmFixedLocaleDisplayString)
--      - subtype - '...ValueOID' (directory in SCMI Comms Config TC)
--      - (eg, 'scmCONetwareBindery')
--      - data - '...ValueString'
--      - (eg, 'Joe Hampton')
--      - role - '...ValueInteger' (ScmSecUserRole in SCMI Security TC)
--      - (eg, 'systemOperator')
--    * 'deviceHelpAddress'
--      - device help person address and role
--      - type - (ScmFixedLocaleDisplayString)
--      - subtype - '...ValueOID' (protocol in SCMI Comms Config TC)
--      - (eg, 'scmCOOsiwanFax')
--      - data - '...ValueString'
--      - (eg, '1-800-232-7979')
--      - role - '...ValueInteger' (ScmSecUserRole in SCMI Security TC)
--      - (eg, 'systemOperator')


--    * 'deviceHelpDescription'
--      - device help person description
--      - type - (ScmFixedLocaleDisplayString)
--      - data - '...ValueString'
--      - (eg, 'has keys to supplies')
--    * 'deviceHelpLocation'
--      - device help person physical location
--      - type - (ScmFixedLocaleDisplayString)
--      - data - '...ValueString'
--      - (eg, '3rd floor lobby')
--      - see - DPA-1 9.4.3 'Printer-locations'
--    * 'deviceHelpURI'
--      - device help person URI (Uniform Resource Identifier)
--      - (same usage as 'scmCOInternetHTTPAddressURI' in SCMI CC TC)
--      - type - (ScmFixedLocaleDisplayString)
--      - subtype - '...ValueOID' (protocol in SCMI Comms Config TC)
--      - (eg, 'scmCOInternetHTTP' (HTTP))
--      - data - '...ValueString'
--      - (eg, 'http://www.foo.com' (HTTP))
--      - see - 'scmCOInternetHTTPAddressURI' in SCMI Comms Config TC
--      - see - Generic URI Syntax (RFC 2396)
--      - compare - 'system[Protocol|ProtocolDetail' in SCMI Svc Mon TC
--      - compare - 'systemURI' in SCMI Svc Mon TC
--
--      -   Device supported and ready info
--      -   (from ISO 10175 DPA-1 Section 9.4 'Printer Object')
--      -   (see 9.4.74 'Common Printer and Server object attributes')
--    * 'deviceTranslatorSupport'
--      - type - (ScmFixedLocaleDisplayString)
--      - data - '...ValueString'
--      - see - DPA-1 9.4.74.5 'Translators-supported'
--    * 'deviceTranslatorReady'
--      - type - (ScmFixedLocaleDisplayString)
--      - data - '...ValueString'
--      - see - DPA-1 9.4.74.6 'Translators-ready'
--    * 'deviceInitialValueJobSupport'
--      - type - (ScmFixedLocaleDisplayString)
--      - data - '...ValueString'
--      - see - DPA-1 9.4.74.13 'Initial-value-jobs-supported'
--    * 'deviceInitialValueDocSupport'
--      - type - (ScmFixedLocaleDisplayString)
--      - data - '...ValueString'
--      - see - DPA-1 9.4.74.14 'Initial-value-documents-supported'
--    * 'deviceMultipleDocSupport'
--      - type - (TruthValue)
--      - data - '...ValueInteger'
--      - see - DPA-1 9.4.74.3 'Multiple-documents-supported'
--    * 'deviceCancelDocSupport'
--      - type - (TruthValue)
--      - data - '...ValueInteger'
--      - see - DPA-1 9.4.74.4 'Cancel-individual-documents-supported'
--    * 'deviceForeignJobsVisible'
--      - type - (TruthValue)
--      - data - '...ValueInteger'


--      - see - DPA-1 9.4.74.15 'Are-foreign-jobs-visible'
--    * 'deviceInitialValueJobDefault'
--      - type - (ScmFixedLocaleDisplayString)
--      - data - '...ValueString'
--      - see - DPA-1 9.4.12 'Printer-initial-value-job'
--    * 'deviceInitialValueDocDefault'
--      - type - (ScmFixedLocaleDisplayString)
--      - data - '...ValueString'
--      - see - DPA-1 9.4.13 'Printer-initial-value-document'
--    * 'deviceInputMaxSpeedTrafficUnit'
--      - traffic unit of numerator of device input max speed
--      - type - (ScmHrDevTrafficUnit)
--      - data - '...ValueInteger'
--      - see - DPA-1 9.4.7 'Maximum-printer-speed'
--    * 'deviceInputMaxSpeedTimeUnit'
--      - time unit of divisor of device input max speed
--      - type - (ScmHrDevPowerTimeUnit)
--      - data - '...ValueInteger'
--      - see - DPA-1 9.4.7 'Maximum-printer-speed'
--    * 'deviceInputMaxSpeed'
--      - device input max speed
--      - type - (Cardinal32)
--      - data - '...ValueInteger'
--      - see - DPA-1 9.4.7 'Maximum-printer-speed'
--    * 'deviceOutputMaxSpeedTrafficUnit'
--      - traffic unit of numerator of device output max speed
--      - type - (ScmHrDevTrafficUnit)
--      - data - '...ValueInteger'
--      - see - DPA-1 9.4.7 'Maximum-printer-speed'
--    * 'deviceOutputMaxSpeedTimeUnit'
--      - time unit of divisor of device output max speed
--      - type - (ScmHrDevPowerTimeUnit)
--      - data - '...ValueInteger'
--      - see - DPA-1 9.4.7 'Maximum-printer-speed'
--    * 'deviceOutputMaxSpeed'
--      - device output max speed
--      - type - (Cardinal32)
--      - data - '...ValueInteger'
--      - see - DPA-1 9.4.7 'Maximum-printer-speed'
--    * 'deviceFeedResolutionSupport'
--      - type - (Cardinal32) DPI (dots per inch)
--      - data - '...ValueInteger'
--      - see - DPA-1 9.4.8 'Printer-resolutions-supported'
--    * 'deviceXFeedResolutionSupport'
--      - type - (Cardinal32) DPI (dots per inch)
--      - data - '...ValueInteger'
--      - see - DPA-1 9.4.8 'Printer-resolutions-supported'
--    * 'deviceSchedulerSupport'
--      - type - (ScmFixedLocaleDisplayString)
--      - data - '...ValueString'
--      - see - DPA-1 9.4.63 'Schedulers-supported'
--    * 'deviceSchedulerReady'
--      - type - (ScmFixedLocaleDisplayString)
--      - data - '...ValueString'


--      - see - DPA-1 9.4.64 'Scheduler-ready'
--
--      -   Device supported and ready device name info (list)
--    * 'devicePhysicalNameSupport'
--      - type - (ScmFixedLocaleDisplayString)
--      - data - '...ValueString'
--      - see - DPA-1 9.4.10 'Printer-associated-printers'
--      - see - DPA-1 9.5.6 'Physical-printers-supported' (servers)
--    * 'devicePhysicalNameReady'
--      - type - (ScmFixedLocaleDisplayString)
--      - data - '...ValueString'
--      - see - DPA-1 9.4.11 'Printers-ready'
--      - see - DPA-1 9.5.7 'Physical-printers-ready' (servers)
--    * 'deviceLogicalNameSupport'
--      - type - (ScmFixedLocaleDisplayString)
--      - data - '...ValueString'
--      - see - DPA-1 9.4.10 'Printer-associated-printers'
--      - see - DPA-1 9.5.8 'Logical-printers-supported' (servers)
--    * 'deviceLogicalNameReady'
--      - type - (ScmFixedLocaleDisplayString)
--      - data - '...ValueString'
--      - see - DPA-1 9.4.11 'Printers-ready'
--      - see - DPA-1 9.5.9 'Logical-printers-ready' (servers)
--
--      -   Device supported and ready device index info (list)
--    * 'devicePhysicalIndexSupport'
--      - type - (Cardinal32) 'hrDeviceIndex'
--      - data - '...ValueInteger'
--      - see - DPA-1 9.4.10 'Printer-associated-printers'
--      - see - DPA-1 9.5.6 'Physical-printers-supported' (servers)
--    * 'devicePhysicalIndexReady'
--      - type - (Cardinal32) 'hrDeviceIndex'
--      - data - '...ValueInteger'
--      - see - DPA-1 9.4.11 'Printers-ready'
--      - see - DPA-1 9.5.7 'Physical-printers-ready' (servers)
--    * 'deviceLogicalIndexSupport'
--      - type - (Cardinal32) 'hrDeviceIndex'
--      - data - '...ValueInteger'
--      - see - DPA-1 9.4.10 'Printer-associated-printers'
--      - see - DPA-1 9.5.8 'Logical-printers-supported' (servers)
--    * 'deviceLogicalIndexReady'
--      - type - (Cardinal32) 'hrDeviceIndex'
--      - data - '...ValueInteger'
--      - see - DPA-1 9.4.11 'Printers-ready'
--      - see - DPA-1 9.5.9 'Logical-printers-ready' (servers)
--
--      -   Device job service and job history device index info
--    * 'deviceJobServiceDeviceIndex'
--      - device service device index (reference from history device)
--      - type - (Cardinal32) 'hrDeviceIndex'
--      - data - '...ValueInteger'
--      - see - 'scmHrDevice...' types in SCMI HRX TC
--    * 'deviceJobHistoryDeviceIndex'
--      - device history device index (reference from service device)


--      - type - (Cardinal32) 'hrDeviceIndex'
--      - data - '...ValueInteger'
--      - see - 'scmHrDevice...History' types in SCMI HRX TC
--
--      -   Device supported and ready font/resource index info (list)
--    * 'deviceFontIndexSupport'
--      - type - (Cardinal32) 'scmFontIndex' in SCMI Resources MIB
--      - data - '...ValueInteger'
--      - see - DPA-1 9.4.19 'Fonts-supported'
--    * 'deviceFontIndexReady'
--      - type - (Cardinal32) 'scmFontIndex' in SCMI Resources MIB
--      - data - '...ValueInteger'
--      - see - DPA-1 9.4.20 'Fonts-ready'
--    * 'deviceResourceIndexSupport'
--      - type - (Cardinal32) 'scmRsrcIndex' in SCMI Resources MIB
--      - data - '...ValueInteger'
--      - see - DPA-1 9.4.21 'Resources-supported'
--    * 'deviceResourceIndexReady'
--      - type - (Cardinal32) 'scmRsrcIndex' in SCMI Resources MIB
--      - data - '...ValueInteger'
--      - see - DPA-1 9.4.22 'Resources-ready'
--
--      -   Device power management
--    * 'devicePowerModeName'
--      - device power mode administrative name (locale dependent)
--      - type - (ScmFixedLocaleDisplayString)
--      - data - '...ValueString'
--    * 'devicePowerModeType'
--      - device power mode type (locale independent)
--      - type - (ScmHrDevPowerModeType)
--      - data - '...ValueInteger'
--    * 'devicePowerModeDescription'
--      - device power mode description (locale dependent)
--      - type - (ScmFixedLocaleDisplayString)
--      - data - '...ValueString'
--    * 'devicePowerModeSupport'
--      - device power mode support (MAY be used to disable a mode)
--      - type - (PresentOnOff)
--      - data - '...ValueInteger'
--    * 'devicePowerTimeUnit'
--      - device power mode transition time unit (defaults to seconds)
--      - type - (ScmHrDevPowerTimeUnit)
--      - data - '...ValueString'
--    * 'devicePowerWarmerSupport'
--      - device power mode to warmer mode transition support
--      - type - (PresentOnOff)
--      - data - '...ValueInteger'
--    * 'devicePowerCoolerSupport'
--      - device power mode to cooler mode transition support
--      - type - (PresentOnOff)
--      - data - '...ValueInteger'
--    * 'devicePowerWarmerDelay'
--      - device power mode to warmer mode transition delay
--      - (delay after trigger event until transition begins)


--      - type - (ScmHrDevPowerTimeUnit)
--      - data - '...ValueInteger'
--    * 'devicePowerWarmerDuration'
--      - device power mode to warmer mode transition duration
--      - (duration after transition begins until transition completes)
--      - type - (ScmHrDevPowerTimeUnit)
--      - data - '...ValueInteger'
--    * 'devicePowerCoolerDelay'
--      - device power mode to cooler mode transition delay
--      - (delay after trigger event until transition begins)
--      - type - (ScmHrDevPowerTimeUnit)
--      - data - '...ValueInteger'
--    * 'devicePowerCoolerDuration'
--      - device power mode to cooler mode transition duration
--      - (duration after transition begins until transition completes)
--      - type - (ScmHrDevPowerTimeUnit)
--      - data - '...ValueInteger'
--    * 'devicePowerWarmerTrigger'
--      - device warmer mode trigger description
--      - type - (ScmFixedLocaleDisplayString)
--      - data - '...ValueString'
--    * 'devicePowerCoolerTrigger'
--      - device cooler mode trigger description
--      - type - (ScmFixedLocaleDisplayString)
--      - data - '...ValueString'
--    * 'deviceNextWarmerModeIndex'
--      - device next warmer mode pointer (in device details)
--      - type - (Cardinal32) 'scmHrDevDetailIndex'
--      - data - '...ValueInteger'
--    * 'deviceNextCoolerModeIndex'
--      - device next cooler mode pointer (in device details)
--      - type - (Cardinal32) 'scmHrDevDetailIndex'
--      - data - '...ValueInteger'
--    * 'deviceEnergyStarSuspendMode'
--      - device (in device details)
--      - type - (Cardinal32) 'scmHrDevDetailIndex'
--      - data - '...ValueInteger'
--
--      -   Device 'hrDeviceProcessor' details
--    * 'deviceProcessorFrwID'
--      - device firmware ID
--      - type - (ProductID) 'hrProcessorFrwID'
--      - data - '...ValueOID'
--
--      -   Device 'hrDeviceNetwork' details
--    * 'deviceNetworkIfIndex'
--      - device interface index
--      - type - (Cardinal32) 'hrNetworkIfIndex'
--      - data - '...ValueInteger'
--
--      -   Device 'hrDeviceDiskStorage' details
--    * 'deviceDiskStorageAccess'
--      - device disk access
--      - type - (Cardinal32) 'hrDiskStorageAccess'


--      - data - '...ValueInteger'
--    * 'deviceDiskStorageMedia'
--      - device disk media
--      - type - (Cardinal32) 'hrDiskStorageMedia'
--      - data - '...ValueInteger'
--    * 'deviceDiskStorageRemovable'
--      - device removable
--      - type - (Cardinal32) 'hrDiskStorageRemoveble' ('removable')
--      - data - '...ValueInteger'
--    * 'deviceDiskStorageCapacity'
--      - device capacity
--      - type - (Cardinal32) 'hrDiskStorageCapacity'
--      - data - '...ValueInteger'
--
--      -   Device job service timeouts
--    * 'deviceJobIncompleteTimeout'
--      - device job incomplete timeout
--      - (delay until job with incomplete input is deleted)
--      - type - (Cardinal32) seconds
--      - data - '...ValueInteger'
--      - (zero=none or 1..n seconds)
--      - see - 'scmCOInternetLPRJobTimeout' in SCMI CC TC
--      - compare - 'systemJobIncompleteTimeout' in SCMI Svc Mon TC
--    * 'deviceJobProgrammingTimeout'
--      - device job programming timeout
--      - (delay until job programming settings are deleted)
--      - type - (Cardinal32) seconds
--      - data - '...ValueInteger'
--      - (zero=none or 1..n seconds)
--      - see - 'deviceJobIncompleteTimeout' above
--      - compare - 'systemJobProgrammingTimeout' in SCMI Svc Mon TC
--    * 'deviceJobHoldDeleteTimeout'
--      - device job hold until delete timeout
--      - (delay until held job is automatically deleted)
--      - type - (Cardinal32) seconds
--      - data - '...ValueInteger'
--      - (zero=none or 1..n seconds)
--      - see - 'deviceJobIncompleteTimeout' above
--      - see - 'jobPause' in 'ScmSimpleJobMgmtOperation' in SCMI SJM TC
--      - compare - 'systemJobHoldDeleteTimeout' in SCMI Svc Mon TC
--    * 'deviceJobPauseResumeTimeout'
--      - device job pause until resume timeout
--      - (delay until paused job is automatically resumed)
--      - type - (Cardinal32) seconds
--      - data - '...ValueInteger'
--      - (zero=none or 1..n seconds)
--      - see - 'deviceJobIncompleteTimeout' above
--      - see - 'jobPause' in 'ScmSimpleJobMgmtOperation' in SCMI SJM TC
--      - compare - 'systemJobPauseResumeTimeout' in SCMI Svc Mon TC
--
--      -   Device guest/alien job and log full policies
--    * 'deviceGuestJobPolicy'
--      - device policy for jobs with 'guest' (empty) user/account
--      - type - (ScmSecGuestJobPolicy)


--      - data - '...ValueInteger'
--      - see - 'scmSecServiceGuestJobPolicy' in SCMI Security MIB
--    * 'deviceAlienJobPolicy'
--      - device policy for jobs with 'alien' (invalid) user/account
--      - type - (ScmSecGuestJobPolicy)
--      - data - '...ValueInteger'
--      - see - 'scmSecServiceAlienJobPolicy' in SCMI Security MIB
--    * 'deviceEventLogFullPolicy'
--      - device policy for handling event log full conditions
--      - type - (ScmGenLogFullPolicy)
--      - data - '...ValueInteger'
--      - see - 'scmSecServiceEventLogFullPolicy' in SCMI Security MIB
--      - see - DPA-1 9.1.6.8 'Notification-profile' (events)
--      - see - DPA-1 9.4 'Printer Object attributes' (generic)
--    * 'deviceJobLogFullPolicy'
--      - device policy for handling job log full conditions
--      - type - (ScmGenLogFullPolicy)
--      - data - '...ValueInteger'
--      - see - 'scmSecServiceJobLogFullPolicy' in SCMI Security MIB
--      - see - DPA-1 9.1.6.9 'Logging-profile' (jobs)
--      - see - DPA-1 9.4 'Printer Object attributes' (generic)
--    * 'deviceRequestLogFullPolicy'
--      - device policy for handling request log full conditions
--      - type - (ScmGenLogFullPolicy)
--      - data - '...ValueInteger'
--      - see - 'scmSecServiceRequestLogFullPolicy' in SCMI Security MIB
--
--      -   Device model info
--    * 'deviceUniversalProductCode'
--      - device UPC (alphanumeric)
--      - type - (ScmFixedLocaleDisplayString)
--      - data - '...ValueString'
--      - see - 'deviceSerialNumber'
--      - see - 'hrDeviceDescr' in IETF HR MIB (RFC 2790)
--    * 'deviceModelName'
--      - device model name (alphanumeric)
--      - type - (ScmFixedLocaleDisplayString)
--      - data - '...ValueString'
--      - see - 'deviceModel' and 'deviceDescription'
--      - see - 'hrDeviceDescr' in IETF HR MIB (RFC 2790)
--      - see - section 9.1.3.1.1 of SCMI HRX TC for mapping and terms
--    * 'deviceModelDescription'
--      - device model description (alphanumeric)
--      - type - (ScmFixedLocaleDisplayString)
--      - data - '...ValueString'
--      - see - 'deviceModel' and 'deviceDescription'
--      - see - 'hrDeviceDescr' in IETF HR MIB (RFC 2790)
--      - see - section 9.1.3.1.1 of SCMI HRX TC for mapping and terms
--    * 'deviceModelNumber'
--      - device model number (alphanumeric)
--      - type - (ScmFixedLocaleDisplayString)
--      - data - '...ValueString'
--      - see - 'deviceModel' and 'deviceDescription'
--      - see - 'hrDeviceDescr' in IETF HR MIB (RFC 2790)


--      - see - section 9.1.3.1.1 of SCMI HRX TC for mapping and terms
--    * 'deviceManufacturerURI'
--      - device manufacturer URI (per RFC 2396)
--      - type - (ScmFixedLocaleDisplayString)
--      - data - '...ValueString'
--      - (eg, 'http://www.samsung.com')
--      - see - 'deviceManufacturer'
--      - see - 'sysContact' in IETF MIB-II (RFC 1213)
--    * 'deviceModelURI'
--      - device model-specific URI (per RFC 2396)
--      - type - (ScmFixedLocaleDisplayString)
--      - data - '...ValueString'
--      - (eg, 'http://www.samsung.com/docucentre/470')
--      - see - 'deviceModel'
--      - see - 'sysContact' in IETF MIB-II (RFC 1213)
--
--      - Service Usage Counters
--      -   Counters which can be used by a billing system to adjust
--      -   deviceLifetimeUsage counters.  These counters are set by
--      -   service to reflect the usage of the machine during the
--      -   service call which should not be billed separately to the
--      -   customer.
--      -   (several usage counters MAY be defined for a single device)
--      -   (usage counter and service usage groups are defined as shari
--      -   the same value of 'scmHrDevDetailIndex')
--    * 'deviceServiceUsage'(230)
--      - device lifetime service usage counter (MAY be multi-valued)
--      - type - (Counter32)
--      - subtype - '...ValueString' counter description
--      - data - '...ValueInteger'
--      -
--    * 'deviceDeltaServiceUsage'(231)
--      - Delta for the sevice usage counter (MAY be multi-valued)
--      - A SET to scmHrDevDetailValueInteger.1.231.X will increase
--      - the counter scmHrDevDetailValueInteger.1.230.X by the amount
--      - of the SET integer.  A GET on the same value will return the
--      - last value set or 0 if there has been no set since reboot.
--      - type - (Counter32)
--      - data - '...ValueInteger'
--      - (eg, monochrome and color page counters)
--      -
--    * 'deviceRolloverValue' (232)
--      - The maximum value of a usage counter before it rolls over.
--      - For example if the counters are 6 digits, then this value
--      -    should be 999999
--      - If it is a 32 bit integer then this value should be
--      -     2,147,483,647   (2^31 - 1)
--      - When the counter reaches 999999 (first example) and 1
--      -     more print is made, then the counter becomes 1
--      -     (rolls over to 1)

    REFERENCE
        "See:   'scmHrDevDetailUnitClass' and
                'scmHrDevDetailUnit' for syntax of device detail."


    SYNTAX      INTEGER {
        --  Device other/unknown details
        other(1),
        unknown(2),
        --  Device general info
        deviceName(3),
        deviceAlias(4),
        deviceType(5),
        deviceDescription(6),
        deviceID(7),
        deviceTree(8),
        deviceContext(9),
        deviceManufacturer(10),
        deviceModel(11),
        deviceSerialNumber(12),
        deviceVendor(13),
        deviceVersion(14),
        --  Device service info
        deviceServiceByCustomer(15),
        deviceReplaceByCustomer(16),
        deviceServicePlanName(17),
        deviceServicePlanPassword(18),
        deviceReplaceByWarranty(19),
        --  Device lifetime usage and limits
        deviceLifetimeUsage(20),
        deviceReorderLifetimeLimit(21),
        deviceWarningLifetimeLimit(22),
        deviceReplaceLifetimeLimit(23),
        deviceMaximumLifetimeLimit(24),
        --  Device message to user time remaining
        deviceDaysUntilReorderMsg(25),
        deviceDaysUntilWarningMsg(26),
        deviceDaysUntilReplaceMsg(27),
        deviceDaysUntilMaximumMsg(28),
        deviceLifetimeMsgDisplay(29),
        --  Device accounting usage
        deviceAccountingUsage(30),
        --  Device message to user and reorder dates
        deviceReorderOnDate(31),
        deviceWarningOnDate(32),
        deviceReplaceOnDate(33),
        deviceMaximumOnDate(34),
        --  Device lifetime errors and warnings
        deviceLifetimeErrorCount(35),
        deviceLifetimeErrorLimit(36),
        deviceLifetimeWarningCount(37),
        deviceLifetimeWarningLimit(38),
        --  Device message to user triggers
        deviceTriggerDaysForReorder(41),
        deviceTriggerDaysForWarning(42),
        deviceTriggerDaysForReplace(43),
        deviceTriggerDaysForMaximum(44),
        --  Device message to user dates actually sent
        deviceReorderMsgSentDate(51),


        deviceWarningMsgSentDate(52),
        deviceReplaceMsgSentDate(53),
        deviceMaximumMsgSentDate(54),
        --  Device reorder and replace actual dates
        deviceReorderToVendorDate(55),
        deviceReorderConfirmDate(56),
        deviceReplaceDate(57),
        deviceReplaceSystemUsage(58),
        deviceReplaceWithGeneric(59),
        --  Device help info (contact info)
        deviceHelpName(60),
        deviceHelpAddress(61),
        deviceHelpDescription(62),
        deviceHelpLocation(63),
        deviceHelpURI(64),
        --  Device supported and ready info
        deviceTranslatorSupport(71),
        deviceTranslatorReady(72),
        deviceInitialValueJobSupport(73),
        deviceInitialValueDocSupport(74),
        deviceMultipleDocSupport(75),
        deviceCancelDocSupport(76),
        deviceForeignJobsVisible(77),
        deviceInitialValueJobDefault(78),
        deviceInitialValueDocDefault(79),
        deviceInputMaxSpeedTrafficUnit(80),
        deviceInputMaxSpeedTimeUnit(81),
        deviceInputMaxSpeed(82),
        deviceOutputMaxSpeedTrafficUnit(83),
        deviceOutputMaxSpeedTimeUnit(84),
        deviceOutputMaxSpeed(85),
        deviceFeedResolutionSupport(86),
        deviceXFeedResolutionSupport(87),
        deviceSchedulerSupport(88),
        deviceSchedulerReady(89),
        --  Device supported and ready device name info (list)
        devicePhysicalNameSupport(90),
        devicePhysicalNameReady(91),
        deviceLogicalNameSupport(92),
        deviceLogicalNameReady(93),
        --  Device supported and ready device index info (list)
        devicePhysicalIndexSupport(94),
        devicePhysicalIndexReady(95),
        deviceLogicalIndexSupport(96),
        deviceLogicalIndexReady(97),
        --  Device job service and job history device index info
        deviceJobServiceDeviceIndex(98),
        deviceJobHistoryDeviceIndex(99),
        --  Device supported and ready font/resource index info (list)
        deviceFontIndexSupport(100),
        deviceFontIndexReady(101),
        deviceResourceIndexSupport(102),
        deviceResourceIndexReady(103),
        --  Device power management


        devicePowerModeName(110),
        devicePowerModeType(111),
        devicePowerModeDescription(112),
        devicePowerModeSupport(113),
        devicePowerTimeUnit(114),
        devicePowerWarmerSupport(115),
        devicePowerCoolerSupport(116),
        devicePowerWarmerDelay(117),
        devicePowerWarmerDuration(118),
        devicePowerCoolerDelay(119),
        devicePowerCoolerDuration(120),
        devicePowerWarmerTrigger(121),
        devicePowerCoolerTrigger(122),
        deviceNextWarmerModeIndex(123),
        deviceNextCoolerModeIndex(124),
 -- per Hao Zou Request 8/12/03
        deviceEnergyStarSuspendMode(125),
        --  Device 'hrDeviceProcessor' details
        deviceProcessorFrwID(130),
        --  Device 'hrDeviceNetwork' details
        deviceNetworkIfIndex(140),
        --  Device 'hrDeviceDiskStorage' details
        deviceDiskStorageAccess(160),
        deviceDiskStorageMedia(161),
        deviceDiskStorageRemovable(162),
        deviceDiskStorageCapacity(163),
        --  Device job service timeouts
        deviceJobIncompleteTimeout(191),
        deviceJobProgrammingTimeout(192),
        deviceJobHoldDeleteTimeout(193),
        deviceJobPauseResumeTimeout(194),
        --  Device guest/alien job and log full policies
        deviceGuestJobPolicy(200),
        deviceAlienJobPolicy(201),
        deviceEventLogFullPolicy(202),
        deviceJobLogFullPolicy(203),
        deviceRequestLogFullPolicy(204),
        --  Device model info
        deviceUniversalProductCode(210),
        deviceModelName(211),
        deviceModelDescription(212),
        deviceModelNumber(213),
        deviceManufacturerURI(220),
        deviceModelURI(221),
        --  Service Usage counters for billing.
        deviceServiceUsage(230),
        deviceDeltaServiceUsage(231),
        deviceRolloverValue(232)
    }


ScmHrDevDetailUnitClass ::= TEXTUAL-CONVENTION
    STATUS      current
    DESCRIPTION
        "The value unit class of the device detail information specified
        in this conceptual row in the 'scmHrDevDetailTable'.

        Usage:  Used to select a textual convention for specifying the
        units of this device detail value.

        Usage:  Some of the value unit class enumerations specify that
        the actual unit is REQUIRED to be selected in '...DetailUnit'
        and REQUIRE '...DetailValueString' contains a value in units
        (and are commented as such below).

        Usage:  Some of the value unit class enumerations specify the
        actual unit DIRECTLY and REQUIRE that '...DetailUnit' be zero
        and REQUIRE '...DetailValueString' contains a value in the
        named textual convention (or a bit-mask derived from it)
        (and are commented as such below).

        Usage:  Some of the value unit class enumerations specify that
        '...DetailValueString' SHALL contain a bit-mask which is
        formed via the bit-wise OR of '2**(n)', where (n) is each
        selected enumerated value in the named textual convention.
        (see 'scmGenBaseSNMPDomainSupport' object in SCMI General MIB)."
    SYNTAX      INTEGER {
        other(1),
        unknown(2),
        --  The following values specify that the actual unit
        --  is REQUIRED to be selected in the '...DetailUnit' object
        --  and REQUIRE '...DetailValueString' contains a value in units
        classGenOptionValueSyntax(3),   -- ScmGenOptionValueSyntax
        --  The following values specify the actual unit
        --  DIRECTLY and REQUIRE that '...DetailUnit' be zero
        --  and REQUIRE '...DetailValueString' contains a value in the
        --  named textual convention (or a bit-mask derived from it)
        classDateAndTime(4),            -- DateAndTime (from SNMPv2-TC)
        classHrDevCalendarDayOfWeek(5), -- ScmHrDevCalendarDayOfWeek
        classHrDevCalendarTimeOfDay(6), -- ScmHrDevCalendarTimeOfDay
        classHrDevMgmtCommandRequest(7),-- ScmHrDevMgmtCommandRequest
        --  The following values specify that the actual unit
        --  is REQUIRED to be selected in the '...DetailUnit' object
        --  and REQUIRE '...DetailValueString' contains a value in units
        classHrDevPowerTimeUnit(8),     -- ScmHrDevPowerTimeUnit
        classHrDevTrafficUnit(9),       -- ScmHrDevTrafficUnit
        --  The following values specify the actual unit
        --  DIRECTLY and REQUIRE that '...DetailUnit' be zero
        --  and REQUIRE '...DetailValueString' contains a value in the
        --  named textual convention (or a bit-mask derived from it)
        classRowPersistence(10),        -- ScmGenRowPersistence
        classRowPersistenceMask(11),    -- ScmGenRowPersistence -> mask
        classLogFullPolicy(12),         -- ScmGenLogFullPolicy
        classLogFullPolicyMask(13),     -- ScmGenLogFullPolicy -> mask
        classHrDevInfoStatus(14),       -- ScmHrDevInfoStatus


        classHrDevInfoStatusMask(15),   -- ScmHrDevInfoStatus -> mask
        classHrDevInfoXStatus(16),      -- ScmHrDevInfoXStatus
        classHrDpaState(17),            -- ScmHrDpaState
        classHrDpaConditions(18),       -- ScmHrDpaConditions
        classHrDpaAvailability(19),     -- ScmHrDpaAvailability
        classHrDpaObjectClassSupport(20), -- ScmHrDpaObjectClassSupport
                                          -- (is already bit-mask)
        classHrDpaJobValidateSupport(21), -- ScmHrDpaJobValidateSupport
                                          -- (is already bit-mask)
        classJMJobState(22),            -- ScmJMJobState
        classJMJobStateMask(23),        -- ScmJMJobState -> mask
        classSecGuestJobPolicy(24),     -- ScmSecGuestJobPolicy
        classSecGuestJobPolicyMask(25), -- ScmSecGuestJobPolicy -> mask
        classSecPosixRights(26),        -- ScmSecPosixRights
                                        -- (is already bit-mask)
        classSecPosixVerbs(27),         -- ScmSecPosixVerbs
                                        -- (is already bit-mask)
        classSvcMonJobConfirmSupport(28), -- ScmSvcMonJobConfirmSupport
                                          -- (is already bit-mask)

        --  The following values specify the actual unit
        --  DIRECTLY and REQUIRE that '...DetailUnit' be zero
        --  and REQUIRE '...DetailValueString' and
        --  '...DetailValueInteger' contain a bit-mask in the named
        --  textual convention
        classSvcMonAttachmentPDLSupport(29)
                                        -- ScmSvcMonAttachmentPDLSupport
                                        -- (is already a bit-mask)
    }

ScmHrDevInfoRealization ::= TEXTUAL-CONVENTION
    STATUS      current
    DESCRIPTION
        "An extended device type (or device 'realization'),
        used by system administrators and end users of this device.

        Usage:  The use of either 'other' or 'unknown' is uninformative
        and SHOULD be avoided by conforming implementations.

      * 'physical' - 'real' device installed on this managed system;
      * 'logical' - 'virtual' device configured on this managed system;
      * 'logicalAndPhysical' - 'combined' device (from ISO DPA ??)."
    REFERENCE
        "See:   'hrDeviceType' in the basic Device Group of the
        IETF Host Resources MIB (RFC 2790).
        See:    Section 9.4 'Printer Object attributes' of ISO DPA
        (Document Printing Application) ISO/IEC 10175 (Final Text, March
        1996) for a discussion of 'printer realizations' of 'physical',
        'logical', and 'logical-and-physical' types (the latter unique
        to DPA)."
    SYNTAX      INTEGER {
        other(1),                       -- other device
        unknown(2),                     -- unknown device
        physical(11),                   -- 'real' device


        logical(12),                    -- 'virtual' device
        logicalAndPhysical(13)          -- 'combined' device
    }

ScmHrDevInfoStatus ::= TEXTUAL-CONVENTION
    STATUS      current
    DESCRIPTION
        "The current operational state of the device
        described by this row of the table.  A value
        'unknown(1)' indicates that the current state of the
        device is unknown.  'running(2)' indicates that the
        device is up and running and that no unusual error
        conditions are known.  The 'warning(3)' state
        indicates that agent has been informed of an
        unusual error condition by the operational software
        (eg, a disk device driver) but that the device is
        still 'operational'.  An example would be a high
        number of soft errors on a disk.  A value of
        'testing(4)', indicates that the device is not
        available for use because it is in the testing
        state.  The state of 'down(5)' is used only when the
        agent has been informed that the device is not
        available for any use.

        Usage:  Conforming implementations SHALL NOT 'bubble up' status
        from 'physical' devices to associated 'logical' devices.  All
        devices SHALL report their own status ONLY.

        Usage:  Devices in the 'down' state SHOULD NOT be accepting new
        work (or still processing old work).  Devices in the 'running'
        state SHOULD be prepared to accept new work.

        Usage:  The use of the state 'unknown' is uninformative
        and SHOULD be avoided by conforming implementations.

        Usage:  This is a textual convention representation of the
        'hrDeviceStatus' enumeration in the IETF Host Resources MIB
        (RFC 2790), rewritten from SMIv1 style (RFCs 1155 and 1212) into
        SMIv2 style (RFCs 1902/2578, 1903/2579, and 1904/2580)."
    REFERENCE
        "See:   'hrDeviceStatus' in the basic Device Group of the
        IETF Host Resources MIB (RFC 2790).
        See:    'scmHrDevInfoXStatus', 'scmHrDevInfoConditions', and
        'scmHrDevInfoXConditions' in the Host Resources Extensions MIB."
    SYNTAX      INTEGER {
        unknown(1),                     -- indeterminate
        running(2),                     -- normally operational, started
        warning(3),                     -- operational, but alert posted
        testing(4),                     -- NOT operational, testing
        down(5)                         -- NOT operational, shutdown
    }


ScmHrDevInfoXStatus ::= TEXTUAL-CONVENTION
    STATUS      current
    DESCRIPTION
        "An extended device status, used by system administrators
        and end users of this device (here, read 'state' for 'status').

        Usage:  Conforming implementations SHALL NOT 'bubble up' status
        from 'physical' devices to associated 'logical' devices.  All
        devices SHALL report their own status ONLY.

        Usage:  Exactly one enumeration of extended device status
        SHALL be defined, with ranges for each basic device type (eg,
        'hrDevicePrinter').  The legal range for extended device status
        for a given device type (either defined by RFC 2790 or by this
        MIB) is found by multiplying the final arc of the the device
        type OID by 100 - the result is the device specific range base -
        the end of the device specific range is 99 larger.  These device
        specific extended device status values SHALL be reissued
        periodically in the 'ScmHrDevInfoXStatus' textual convention."
    REFERENCE
        "See:   Section 9.4.9 'Printer-state' of ISO DPA
        (Document Printing Application) ISO/IEC 10175 (Final Text,
        18 May 1995) for a discussion of the printer states used here.
        Note that the DPA state 'connecting-to-printer' has no meaning
        in the context of a 'physical' printer device, but only in the
        context of an intermediate DP-Server presenting a 'logical'
        printer device.
        See:    'hrPrinterStatus' and 'hrPrinterDetectedErrorState' in
        the IETF Host Resources MIB (RFC 2790) for related discussion.

        See:    'hrDeviceStatus' in the basic Device Group of the
        IETF Host Resources MIB (RFC 2790).
        See:    'scmHrDevInfoConditions' and 'scmHrDevInfoXConditions'
        in the Host Resources Extensions MIB."
    SYNTAX      INTEGER {
        --  Common extended device status
        commonNone(0),
        commonOther(1),
        commonUnknown(2),
        commonLast(99),

        --  'hrDeviceOther'
        otherNone(100),

        --  'hrDeviceUnknown'
        unknownNone(200),

        --  'hrDeviceProcessor'
        processorNone(300),

        --  'hrDeviceNetwork'
        networkNone(400),

        --  'hrDevicePrinter'


        --  See:    Section 9.4.9 'Printer-state' of ISO/IEC 10175
        --          (was on page 185 in earlier text, May 1995)
        --  See:    'id-val-printer-state-...' in Annex A of ISO/IEC
        --          10175 (was on page 307 in earlier text, May 1995)
        --  If 'dpaPrinterStateFinalArc' is truncated from an OID
        --  'id-val-printer-state-...' in Annex A of ISO/IEC 10175
        --  and 'scmiPrinterStatus' is the corresponding enum value of
        --  'printer...' in 'ScmHrDevInfoXStatus' (below),
        --  then:
        --      scmiPrinterStatus = (dpaPrinterStateFinalArc + 502)
        printerNone(500),               -- SCMI extension to ISO DPA
        printerOther(501),              -- SCMI extension to ISO DPA
        printerUnknown(502),            -- unknown or indeterminate
        printerIdle(503),               -- ready to accept jobs
        printerPrinting(504),           -- currently printing a job
        printerNeedsAttention(505),     -- needs general human attention
        printerPaused(506),             -- paused by user or operator
        printerShutdown(507),           -- taken out of service
        printerJobStartWait(508),       -- see ISO DPA 'job-start-wait'
        printerJobEndWait(509),         -- see ISO DPA 'job-end-wait'
        printerNeedsKeyOperator(510),   -- needs toner, developer, etc
        printerJobPasswordWait(511),    -- see ISO DPA 'job-password'
        printerTimedOut(512),           -- ISO DPA Servers only
        printerConnectingToPrinter(513),-- ISO DPA Servers only

        --  'hrDeviceDiskStorage'
        diskStorageNone(600),

        --  'hrDeviceVideo'
        videoNone(1000),

        --  'hrDeviceAudio'
        audioNone(1100),

        --  'hrDeviceCoprocessor'
        coprocessorNone(1200),

        --  'hrDeviceKeyboard'
        keyboardNone(1300),

        --  'hrDeviceModem'
        modemNone(1400),

        --  'hrDeviceParallelPort'
        parallelPortNone(1500),

        --  'hrDevicePointing'
        pointingNone(1600),

        --  'hrDeviceSerialPort'
        serialPortNone(1700),

        --  'hrDeviceTape'
        tapeNone(1800),


        --  'hrDeviceClock'
        clockNone(1900),

        --  'hrDeviceVolatileMemory'
        volatileMemoryNone(2000),

        --  'hrDeviceNonVolatileMemory'
        nonVolatileMemoryNone(2100),

        --  'scmHrDeviceHostSystem'
        hostSystemNone(10100),

        --  'scmHrDeviceScanner'
        scannerNone(10200),

        --  'scmHrDeviceCopier'
        copierNone(10300),

        --  'scmHrDeviceFax'
        faxNone(10400),

        --  'scmHrDeviceMailbox'
        mailboxNone(10500),

        --  'scmHrDeviceMarker'
        markerNone(11100),

        --  'scmHrDeviceFinisherBFM'
        finisherBFMNone(11200),

        --  'scmHrDeviceFinisherMFF'
        finisherMFFNone(11300),

        --  'scmHrDeviceFinisherXIM'
        finisherXIMNone(11400),

        --  'scmHrDeviceFinisher3rdParty'
        finisher3rdPartyNone(11500),

        --  'scmHrDevicePaymentInterface'
        paymentInterfaceNone(11600),

        --  'scmHrDeviceInterposer'
        interposerNone(11700),

        --  'scmHrCru...' - Customer Replaceable Units
        cruNone(20000),                 -- CRU no status
        cruOther(20001),                -- CRU other status
        cruUnknown(20002),              -- CRU unknown status
        cruReady(20003),                -- CRU OK (normal wear)
        cruReorder(20004),              -- CRU should be reordered
        cruReplace(20005),              -- CRU should be replaced
        cruFault(20006),                -- CRU has one or more faults


        reserved(40000)                 -- placeholder
    }

ScmHrDevInfoConditions ::= TEXTUAL-CONVENTION
    STATUS      current
    DESCRIPTION
        "A relatively generic description of the current 'conditions'
        of this device, specified in a bit-mask.

              1 : startupInProgress             -- 2**0
              2 : resetWarningInProgresss       -- 2**1       (optional)
              4 : testInProgress                -- 2**2
              8 : shutdownInProgress            -- 2**3       (optional)
             16 : quiesceInProgress             -- 2**4       (optional)
             32 : resetCountersInProgress       -- 2**5       (optional)
             64 : resetWarmInProgress           -- 2**6
            128 : resetColdInProgress           -- 2**7
            256 : resetFactoryInProgress        -- 2**8
            512 : flushInputInProgress          -- 2**9
           1024 : flushOutputInProgress         -- 2**10
           2048 : flushInOutInProgress          -- 2**11
           4096 : manageInProgress              -- 2**12      (optional)

        The above basic 'conditions' record the original intent of the
        current command, when it results in delayed state transitions
        before arriving at the 'target' state.  They augment the state
        information available from 'hrDeviceStatus'.

           8192 : warmUpDelayInProgress         -- 2**13      (optional)
          16384 : warmUpCycleInProgress         -- 2**14      (optional)
          32768 : readyMode                     -- 2**15      (optional)
          65536 : coolDownDelayInProgress       -- 2**16      (optional)
         131072 : coolDownCycleInProgress       -- 2**17      (optional)
         262144 : standbyMode                   -- 2**18      (optional)
         524288 : energySaveDelayInProgress     -- 2**19      (optional)
        1048576 : energySaveCycleInProgress     -- 2**20      (optional)
        2097152 : sleepMode                     -- 2**21      (optional)
        4194304 : wakeUpDelayInProgress         -- 2**22      (optional)
        8388608 : wakeUpCycleInProgress         -- 2**23      (optional)
       16777216 : powerToReadyInProgress        -- 2**24      (optional)
       33554432 : powerToStandbyInProgress      -- 2**25      (optional)
       67108864 : powerToSleepInProgress        -- 2**26      (optional)

        The above optional 'conditions' record the progress of device
        'warm up', 'cool down', 'energy save', and 'wake up' power mgmt
        cycles and also define the device 'readyMode', 'standbyMode',
        and 'sleepMode' qualifiers to the generic 'hrDeviceStatus' of
        'running(2)', 'warning(3)', or 'testing(4)' (but NOT 'down(5)').
        See the power management cycle feature support and feature time
        objects in the Device Power Group of the Host Resources Ext MIB.

        Usage:  It is desirable that the implementor report 'conditions'
        of all devices corresponding to conceptual rows in the


        'hrDeviceTable' as accurately as feasible.  'Conditions' occur
        within or across 'states' in a finite state machine (FSM)
        implementation of a device.  They represent both short term and
        long term conditions.

        Usage:  A device with 'hrDeviceStatus' of 'running(2)' might
        have 'scmHrDevInfoConditions' of 'quiesceInProgress', indicating
        that the device will soon transition to 'hrDeviceStatus' of
        'down(5)'.

        Usage:  A multi-bit example of 'scmHrDevInfoConditions' is
        'quiesceInProgress' concurrently with 'standbyMode', ie, the
        device has previously 'cooled down' and will soon transition
        from 'hrDeviceStatus' of 'running(2)' to 'down(5)'."
    REFERENCE
        "See:   'hrDeviceStatus' in the basic Device Group of the
        IETF Host Resources MIB (RFC 2790).
        See:    'scmHrDevInfoXStatus' and 'scmHrDevInfoXConditions'
        in the Host Resources Extensions MIB."
    SYNTAX      INTEGER (0..2147483647)  -- biggest int = 2**31-1

ScmHrDevInfoXConditions ::= TEXTUAL-CONVENTION
    STATUS      current
    DESCRIPTION
        "A device specific description of the extended 'conditions'
        of this device, specified in a bit-mask.

        Usage:  For FUTURE expansion.

        Usage:  Exactly one bit mask of extended device conditions SHALL
        be defined for each basic device type (eg, 'hrDevicePrinter').
        These device specific extended device conditions values SHALL be
        reissued periodically in the 'ScmHrDevInfoXConditions' textual
        convention.  These device specific extended device conditions
        are mutually exclusive and 'overloaded' in the single reporting
        object 'scmHrDevInfoXConditions'."
    REFERENCE
        "See:   'hrDeviceStatus' in the basic Device Group of the
        IETF Host Resources MIB (RFC 2790).
        See:    'scmHrDevInfoXStatus' and 'scmHrDevInfoConditions'
        in the Host Resources Extensions MIB."
    SYNTAX      INTEGER (0..2147483647)  -- biggest int = 2**31-1

ScmHrDevMgmtCommandRequest ::= TEXTUAL-CONVENTION
    STATUS      current
    DESCRIPTION
        "A write of this type by an (authorized) management station
        invokes a command for this device.
        A read of this type always returns the command currently in
        progress or last completed.
        It is mandatory that a conforming management agent ensure that
        the contents of this object remain 'in bounds' - an undefined
        value SHALL be replaced by 'none' - ie, although rejected with
        error in the SetResponse PDU, this object SHALL NOT contain any


        such undefined value.  At system initialization, this object
        SHALL contain 'none'.

      * 'none' - NO action(s) SHALL be taken, except to clear
        '...CommandData' and set '...CommandStatus' to 'noError'.
      * 'test' or 'manage' - the associated '...CommandData' object
        SHOULD/SHALL be specified in the same SetRequest PDU.
      * all other commands - the associated '...CommandData' object
        MAY be specified in the same SetRequest PDU.
      * 'startup', 'resetWarm', 'resetCold', or 'resetFactory' - the
        final state SHALL be 'running' (after cycle completes) - the
        sequence of states SHOULD be 'down' -> 'testing' -> 'running' -
        the final power mode SHALL be 'ready'.
      * 'startup' - this device SHALL transition from the 'down' state
        to the 'running' state and 'ready' power mode.
      * 'resetWarning' - this device SHALL transition from the 'warning'
        state to the 'running' state (because a management station has
        acknowledged the management agent's previous warning).
      * 'test' - this device SHALL transition immediately (ie, without
        attempting graceful quiesce) to the 'testing' state; it is a
        local matter (ie, device specific) how this command is
        processed; however, '...CommandData' SHOULD be specified.
      * 'shutdown' - this device SHALL transition immediately (ie,
        without attempting graceful quiesce) to the 'down' state and
        'off' power mode.
      * 'quiesce' - this device MAY transition gracefully to the 'down'
        state, or it MAY choose to treat a 'quiesce' as 'shutdown'.
      * 'resetCounters' - all device counters SHALL be reset to zero and
        the device SHALL remain in the same state and power mode.
      * 'resetWarm' - a device 'warm restart' SHALL be performed (ie,
        without a power cycle reset).
      * 'resetCold' - a device 'cold restart' SHALL be performed (ie,
        with a power cycle reset).
      * 'resetFactory' - all factory defaults SHALL be restored, and a
        device 'cold restart' SHALL be performed (ie, with a power cycle
        reset).
      * 'flushInput' - all device input (in progress or internally
        queued) SHALL be gracefully flushed.
      * 'flushOutput' - all device output (in progress or internally
        queued) SHALL be gracefully flushed.
      * 'flushInOut' - all device input and output output (in progress
        or internally queued) SHALL be gracefully flushed.
      * 'manage' - it is a local matter (ie, device specific) how this
        command is processed; however, '...CommandData' SHALL be
        specified.
      * 'refresh' - the device SHALL promptly read all of its manageable
        configuration parameters, but SHALL NOT perform a reset.
      * 'warmUp' - the device SHALL transition from the 'standby' mode
        to the 'ready' mode - invalid from any other power mode
        (optional command for remote device power management).
      * 'coolDown' - the device SHALL transition from the 'ready' mode
        to the 'standby' mode - invalid from any other power mode
        (optional command for remote device power management).
      * 'energySave' - the device SHALL transition from the 'standby'


        mode to the 'sleep' mode - invalid from any other power mode
        (optional command for remote device power management).
      * 'wakeUp' - the device SHALL transition from the 'sleep'
        mode to the 'standby' mode - invalid from any other power mode
        (optional command for remote device power management).
      * 'powerToReady' - the device SHALL transition from the 'standby'
        mode or the 'sleep' mode to the 'ready' mode
        (optional command for remote device power management).
      * 'powerToStandby' - the device SHALL transition from the 'ready'
        mode or the 'sleep' mode to the 'standby' mode
        (optional command for remote device power management).
      * 'powerToSleep' - the device SHALL transition from the 'ready'
        mode or the 'standby' mode to the 'sleep' mode
        (optional command for remote device power management).

        Note:   All of the POSIX and SCMI device level operations are
        taken from the POSIX System Admin std (IEEE 1387.4) and aligned
        with the high-end SCMI System Admin MIB."
    REFERENCE
        "See:   'dot5Commands' in IEEE 802.5 Token Ring MIB (RFC 1748)
        and 'hrDeviceStatus' in IETF Host Resources MIB (RFC 2790).
        Compare:    'ifOperStatus' (current) and 'ifAdminStatus'
        (desired) in the Interfaces Group of IETF MIB-II (RFC 1213);
        'RowStatus' textual convention in IETF SMIv2 (RFC 1902/2578).

        See:    Section 4 'Print Utilities' (pages 71 to 212) of
                POSIX Sys Admin (IEEE 1387.4 / Draft 8, October 1994).
        See:    OBJECT clause in MODULE-COMPLIANCE macro of
                SCMI Ext to Host Resources MIB, for compliance info.
        See:    Section 3.4 'SCMI Standard Tagged Management Data' and
                Section 3.5 'Simple Device Management Requests' in
                SCMI Ext to Host Resources TC.
        See:    Section 3.5.3 'Secure Simple Device Mgmt Requests' in
                SCMI Security TC."
    SYNTAX      INTEGER {
        none(1),                        -- no operation
        startup(2),                     -- to 'running'
        resetWarning(3),                -- from 'warning' to 'running'
        test(4),                        -- to 'testing' immediately
        shutdown(5),                    -- to 'down' immediately
        quiesce(6),                     -- to 'down' gracefully
        resetCounters(7),               -- reset all device counters
        resetWarm(8),                   -- warm restart to 'running'
        resetCold(9),                   -- cold restart to 'running'
        resetFactory(10),               -- factory defaults cold restart
        flushInput(11),                 -- flush all input
        flushOutput(12),                -- flush all output
        flushInOut(13),                 -- flush all input and output
        manage(14),                     -- manage command, any state
        refresh(15),                    -- refresh device w/out reset
        warmUp(16),                     -- 'standby' to 'ready' ONLY
        coolDown(17),                   -- 'ready' to 'standby' ONLY
        energySave(18),                 -- 'standby' to 'sleep' ONLY
        wakeUp(19),                     -- 'sleep' to 'standby' ONLY


        powerToReady(20),               -- 'standby|sleep' to 'ready'
        powerToStandby(21),             -- 'ready|sleep' to 'standby'
        powerToSleep(22),               -- 'ready|standby' to 'sleep'
        --  POSIX - Device level operations (on host system)
        deviceCreate(1301),             -- 'pdcreate' (create device)
        deviceDelete(1302),             -- 'pddelete' (delete device)
        deviceList(1303),               -- 'pdls' (list attributes)
        deviceSet(1304),                -- 'pdset' (set attributes)
        deviceClean(1305),              -- 'pdclean' (remove all jobs)
        deviceDisable(1306),            -- 'pddisable' (stop new jobs)
        deviceEnable(1307),             -- 'pdenable' (allow new jobs)
        devicePause(1308),              -- 'pdpause' (pause device)
        deviceResume(1309),             -- 'pdresume' (resume device)
        deviceShutdown(1310),           -- 'pdshutdown' (end device)
        deviceQueueList(1311),          -- 'pdq' (list device job queue)
        deviceJobCreate(1312),          -- 'pdpr' (submit job to device)
        --  SCMI - Device level extensions (on host system)
        deviceManage(2301),             -- manage device object(s)
        deviceRestart(2302),            -- restart device
        deviceInstall(2321),            -- install device object(s)
        deviceUpgrade(2322),            -- upgrade device object(s)
        deviceBackup(2323),             -- backup device object(s)
        deviceRestore(2324),            -- restore device object(s)
        deviceConfigure(2325),          -- configure device object(s)
        deviceDiagnose(2326),           -- diagnose device object(s)
        deviceResetCounters(2331),      -- reset device counters
        deviceResetWarm(2332),          -- warm reset (no power cycle)
        deviceResetCold(2333),          -- cold reset (w/ power cycle)
        deviceResetFactory(2334),       -- factory defaults reset
        deviceFormat(2335),             -- format device (storage)
        deviceRefresh(2336),            -- refresh device (comms)
        deviceLogin(2341),              -- login w/ authentication
        deviceLogout(2342),             -- logout w/ authentication
        --  POSIX - Entity level operations (on host system)
        entityCreate(1901),             -- 'pdcreate' (create entity)
        entityDelete(1902),             -- 'pddelete' (delete entity)
        entityList(1903),               -- 'pdls' (list attributes)
        entitySet(1904),                -- 'pdset' (set attributes)
        entityClean(1905),              -- 'pdclean' (remove all jobs)
        entityDisable(1906),            -- 'pddisable' (stop new jobs)
        entityEnable(1907),             -- 'pdenable' (allow new jobs)
        entityPause(1908),              -- 'pdpause' (pause entity)
        entityResume(1909),             -- 'pdresume' (resume entity)
        entityShutdown(1910),           -- 'pdshutdown' (end entity)
        entityQueueList(1911),          -- 'pdq' (list entity job queue)
        entityJobCreate(1912),          -- 'pdpr' (submit job to entity)
        --  SCMI - Entity level extensions (on host system)
        entityManage(2901),             -- manage entity object(s)
        entityRestart(2902),            -- restart entity
        entityInstall(2921),            -- install entity object(s)
        entityUpgrade(2922),            -- upgrade entity object(s)
        entityBackup(2923),             -- backup entity object(s)
        entityRestore(2924),            -- restore entity object(s)
        entityConfigure(2925),          -- configure entity object(s)


        entityDiagnose(2926),           -- diagnose entity object(s)
        entityResetCounters(2931),      -- reset entity counters
        entityResetWarm(2932),          -- warm reset (no power cycle)
        entityResetCold(2933),          -- cold reset (w/ power cycle)
        entityResetFactory(2934),       -- factory defaults reset
        entityFormat(2935),             -- format entity (storage)
        entityRefresh(2936),            -- refresh entity (comms)
        entityLogin(2941),              -- login w/ authentication
        entityLogout(2942)              -- logout w/ authentication
    }

ScmHrDevMgmtCommandData ::= TEXTUAL-CONVENTION
    STATUS      current
    DESCRIPTION
        "A write of this type specifies:  a) a 'test' command subtype
        and any accompanying 'test' device specific data; or b) a
        'manage' command subtype and any accompanying 'manage' device
        specific data; or c) device specific data accompanying any
        other command.
        A read of this type always returns the data (if any) which
        accompanied the current or last completed command."
    REFERENCE
        "See:   Section 4 'Print Utilities' (pages 71 to 212) of
                POSIX Sys Admin (IEEE 1387.4 / Draft 8, October 1994).
        See:    'hrDeviceStatus' in the Device group of the
                IETF Host Resources MIB (RFC 2790).
        See:    Section 3.4 'SCMI Standard Tagged Management Data' and
                Section 3.5 'Simple Device Management Requests' in
                SCMI Ext to Host Resources TC.
        See:    Section 3.5.3 'Secure Simple Device Mgmt Requests' in
                SCMI Security TC."
    SYNTAX      OCTET STRING (SIZE (0..255))

ScmHrDevMgmtCommandDataTag ::= TEXTUAL-CONVENTION
    STATUS      current
    DESCRIPTION
        "SCMI device management commands are passed as enumerated types
        in 'scmHrDevMgmtCommandRequest' in the SCMI HRX MIB.
        Other SCMI management commands are passed as enumerated types in
        'scmCommsMgmtCommandRequest', 'scmSimpleJobMgmtOperation', etc,
        in the SCMI Comms Engine, Simple Job Mgmt, and other MIBs.

        SCMI management commands MAY also require one or more arguments
        (in addition to any specific variable bindings of MIB objects).
        Required arguments are passed as 'tagged string arguments' in
        'scmHrDevMgmtCommandData', 'scmSimpleJobMgmtData', etc.
        Each 'tagged string argument' substring is of the form:

            'TT=value:'

        where:
            'TT'        two-character 'tag', naming argument type
            '='         literal equal sign, beginning argument value
            'value'     human-readable string, encoding argument value


            ':'         literal colon, terminating argument value

        SCMI conforming management stations SHALL terminate ALL
        'tagged string argument' substrings properly with colon (':').

        SCMI standard 'tagged string arguments' MAY pass colon (':')
        in their 'value' by escaping it with backslash ('\').  SCMI
        conforming management agents SHALL interpret backslash
        followed by ANY other character as the literal value of the
        second character (ie, backslash is permitted, and is NOT
        restricted to certain following characters).

        SCMI standard 'tags' for data in 'tagged string arguments',
        (in 'scmHrDevMgmtCommandData', 'scmSimpleJobMgmtData', etc)
        are as follows:

        --  Generic Data (no object mapping to MIBs)
        --  For domain-specific future extensions to operations
      * SC  [Sub-Command - domain-specific, must be FIRST tag present]
        --  syntax 'ScmFixedLocaleDisplayString (SIZE (0..255))'
        --  domain-specific sub-command for management request
        --  passed in fixed locale (see 'scmGenFixedLocalizationIndex')
        --  passed as character string, NOT as binary value

        --  For generic access to any IETF or SCMI defined objects
      * OI  [Object Identifier - no object mapping]
        --  syntax 'OBJECT IDENTIFIER'
        --  object identifier of object (WITHOUT instance qualifiers)
        --  passed as dotted decimal OID or as object label
        --  (eg, 'hrDeviceID'), NOT as binary object identifier

      * OV  [Object Value - no object mapping]
        --  syntax 'ScmFixedLocaleDisplayString (SIZE (0..255))'
        --  object value of object
        --  passed as character string, NOT as binary value
        --  passed in fixed locale (see 'scmGenFixedLocalizationIndex')

        --  For protection against 'replay' attacks
      * DT  [Date and Time - no object mapping]
        --  (see 'hrSystemDate' in System group of IETF HR MIB)
        --  syntax 'DateAndTime'
        --  date and time stamp for management request
        --  passed as dotted decimal string (ie, 'yyyy.mm.dd.hh.mm.ss'),
        --  NOT as binary value

      * NI  [Noise Information - no object mapping]
        --  syntax 'ScmFixedLocaleDisplayString (SIZE (0..255))'
        --  arbitrary noise info for management request
        --  passed as hexadecimal string, NOT as binary value

      * SI  [Sequence Identifier - no object mapping]
        --  syntax 'Ordinal32'
        --  sequence ID for management request (for 'secure streams')
        --  passed as decimal string, NOT as binary value


        --  Security Data from SCMI Security MIB (63sec)
        --  For account-based authentication
      * AI  'scmSecAccountIndex'
        --  syntax 'Ordinal32'
        --  index of account (ie, account ID)
        --  passed as decimal string, NOT as binary value

      * AN  'scmSecAccountName'
        --  syntax 'ScmFixedLocaleDisplayString (SIZE (0..255))'
        --  human-readable name of account (ie, account label)
        --  passed in fixed locale (see 'scmGenFixedLocalizationIndex')

      * AC  'scmSecAccountPasscode'
        --  syntax 'ScmFixedLocaleDisplayString (SIZE (0..255))'
        --  protected numeric password of account
        --  passed as hexadecimal string, NOT as binary value
        --  (protected text form, NOT cleartext password)

      * AW  'scmSecAccountPassword'
        --  syntax 'ScmFixedLocaleDisplayString (SIZE (0..255))'
        --  protected alphanumeric password of account
        --  passed as hexadecimal string, NOT as binary value
        --  (protected text form, NOT cleartext password)

        --  For user-based authentication
      * UI  'scmSecUserIndex'
        --  syntax 'Ordinal32'
        --  index of user (ie, user ID)
        --  passed as decimal string, NOT as binary value

      * UN  'scmSecUserName'
        --  syntax 'ScmFixedLocaleDisplayString (SIZE (0..255))'
        --  human-readable name of user (ie, user label)
        --  passed in fixed locale (see 'scmGenFixedLocalizationIndex')

      * UC  'scmSecUserPasscode'
        --  syntax 'ScmFixedLocaleDisplayString (SIZE (0..255))'
        --  protected numeric password of user
        --  passed as hexadecimal string, NOT as binary value
        --  (protected text form, NOT cleartext password)

      * UW  'scmSecUserPassword'
        --  syntax 'ScmFixedLocaleDisplayString (SIZE (0..255))'
        --  protected alphanumeric password of user
        --  passed as hexadecimal string, NOT as binary value
        --  (protected text form, NOT cleartext password)

        --  System group of IETF MIB-II (RFC 1213)
      * ZD  'sysDescr'
        --  syntax 'DisplayString (SIZE (0..255))'
        --  (NVT ASCII string)
        --  textual description of host system,
        --  passed as ASCII string, NOT as localized string


        --  (see SCMI MIB Implementer's Guide for the format
        --   of sysDescr).
        --  (see 'hrDeviceDescr' of type 'DisplayString' in IETF HR MIB)

      * ZI  'sysObjectID'
        --  syntax 'OBJECT IDENTIFIER'
        --  product ID of host system
        --  passed as dotted decimal OID or as system product ID label
        --  (eg, 'scmPidStarship20'), NOT as binary object identifier
        --  (see 'hrDeviceID' of type 'ProductID' in IETF HR MIB)

      * ZS  'sysServices'
        --  syntax 'INTEGER (0..127)'
        --  bit-mask of services host system offers
        --  passed as decimal string, NOT as binary value

        --  Interface group of IETF MIB-II (RFC 1213)
      * IX  'ifIndex'
        --  syntax 'INTEGER (1..2147483647)'
        --  index of host system interface conceptual row
        --  (REQUIRED for 'entityCreate')
        --  passed as decimal string, NOT as binary index

      * ID  'ifDescr'
        --  syntax 'DisplayString (SIZE (0..255))'
        --  (NVT ASCII string)
        --  textual description of host system interface,
        --  including manufacturer, product name, version of hardware

      * IY  'ifType'
        --  syntax 'INTEGER (1..2147483647)' (enumeration)
        --  (see 'IANAifType' textual convention in 'IANAifType-MIB')
        --  type of host system interface
        --  passed as decimal string or as interface type enum label
        --  (eg, 'iso88025-tokenRing'), NOT as binary value

      * IM  'ifMtu'
        --  syntax 'INTEGER (0..2147483647)'
        --  max transmission unit (datagram) on host system interface
        --  passed as decimal string, NOT as binary value

      * IS  'ifSpeed'
        --  syntax 'INTEGER (0..2147483647)'
        --  speed (bits/second) of host system interface
        --  passed as decimal string, NOT as binary value

      * IP  'ifPhysAddress'
        --  syntax 'PhysAddress'
        --  physical address of host system interface
        --  passed as hexadecimal string, NOT as binary value

      * IZ  'ifSpecific'
        --  syntax 'OBJECT IDENTIFIER'
        --  reference to media-specific MIB for host system interface


        --  passed as dotted decimal OID or as media-specific MIB label
        --  (eg, 'EtherLike-MIB'), NOT as binary value

        --  System group of IETF HR MIB (RFC 2790)
      * ZA  'hrSystemDate'
        --  syntax 'DateAndTime'
        --  local date and time on host system
        --  passed as dotted decimal string (ie, 'yyyy.mm.dd.hh.mm.ss'),
        --  NOT as binary value

      * ZL  'hrSystemInitialLoadDevice'
        --  syntax 'INTEGER (1..2147483647)'
        --  (see 'hrDeviceIndex' in IETF HR MIB)
        --  index of 'hrDeviceEntry' for host system boot device
        --  (usually a disk drive or ROM)
        --  passed as decimal string, NOT as binary value

      * ZP  'hrSystemInitialLoadParameters'
        --  syntax 'InternationalDisplayString (SIZE (0..128))'
        --  host system boot parameters (eg, pathname and options)
        --  passed in dynamic locale
        --  (see 'scmGenCurrentLocalizationIndex')

      * ZM  'hrSystemMaxProcesses'
        --  syntax 'INTEGER (0..2147483647)'
        --  max number of process contexts supported on host system
        --  or zero (if no fixed limit)
        --  passed as decimal string, NOT as binary value

        --  Storage group of IETF HR MIB (RFC 2790)
      * SX  'hrStorageIndex'
        --  syntax 'INTEGER (1..2147483647)'
        --  index of host system storage conceptual row
        --  (REQUIRED for 'entityCreate')
        --  passed as decimal string, NOT as binary index

      * SY  'hrStorageType'
        --  syntax 'OBJECT IDENTIFIER'
        --  (see 'hrStorageTypes' in IETF HR MIB)
        --  type of host system storage
        --  passed as dotted decimal OID or as storage type label

      * SD  'hrStorageDescr'
        --  syntax 'DisplayString (SIZE (0..64))'
        --  (NVT ASCII string)
        --  textual description of host system storage,
        --  including the type and instance of the storage
        --  passed as ASCII string, NOT as localized string

      * SU  'hrStorageAllocationUnits'
        --  syntax 'INTEGER (1..2147483647)'
        --  (size in bytes)
        --  size of allocation units on host system storage
        --  passed as decimal string, NOT as binary value


      * SS  'hrStorageSize'
        --  syntax 'INTEGER (1..2147483647)'
        --  (size in allocation units)
        --  size in 'hrStorageAllocationUnits' of host system storage
        --  passed as decimal string, NOT as binary value

        --  Device table in Device group of IETF HR MIB (RFC 2790)
      * DX  'hrDeviceIndex'
        --  syntax 'INTEGER (1..2147483647)'
        --  index of host system device conceptual row
        --  (REQUIRED for 'deviceCreate')
        --  passed as decimal string, NOT as binary index

      * DY  'hrDeviceType'
        --  syntax 'OBJECT IDENTIFIER'
        --  (see 'hrDeviceTypes' in IETF HR MIB)
        --  type of host system device
        --  (certain device types make related table entries MANDATORY)
        --  passed as dotted decimal OID or as device type label
        --  (eg, 'hrDevicePrinter'), NOT as binary 'OBJECT IDENTIFIER'

      * DD  'hrDeviceDescr'
        --  syntax 'DisplayString' (SIZE (0..64))
        --  (NVT ASCII string)
        --  textual description of host system device,
        --  including manufacturer and revision, and
        --  (optionally) serial number
        --  passed as ASCII string, NOT as localized string

      * DI  'hrDeviceID'
        --  syntax 'ProductID'
        --  (manufacturer defined object identifier)
        --  product ID of host system device
        --  passed as dotted decimal OID or as device product ID label
        --  (eg, 'scmPidStarship20'), NOT as binary object identifier

        --  Processor table in Device group of IETF HR MIB (RFC 2790)
      * PI  'hrProcessorFrwID'
        --  syntax 'ProductID'
        --  (manufacturer defined object identifier)
        --  product ID of firmware associated with processor device
        --  passed as dotted decimal OID or as firmware product ID label
        --  (for device types 'hrDeviceProcessor' in HR Device table)

        --  Network table in Device group of IETF HR MIB (RFC 2790)
      * NI  'hrNetworkIfIndex'
        --  syntax 'INTEGER (1..2147483647)'
        --  (see 'ifIndex' in IETF MIB-II)
        --  index of 'ifEntry' associated with network device
        --  passed as decimal string, NOT as binary index
        --  (for device types 'hrDeviceNetwork' in HR Device table)

        --  Disk Storage table in Device group of IETF HR MIB (RFC 2790)


      * KA  'hrDiskStorageAccess'
        --  syntax 'INTEGER (1..2)' (enumeration)
        --  access (including write-protect) of disk storage device
        --  passed as decimal string or as access enum label
        --  (eg, 'readOnly'), NOT as binary value
        --  (for device types 'hrDeviceDiskStorage' in HR Device table)

      * KM  'hrDiskStorageMedia'
        --  syntax 'INTEGER (1..8)' (enumeration)
        --  type of media used in disk storage device
        --  passed as decimal string or as media enum label
        --  (eg, 'hardDisk'), NOT as binary value
        --  (for device types 'hrDeviceDiskStorage' in HR Device table)

      * KR  'hrDiskStorageRemoveble'
        --  syntax 'Boolean' (true/false, defined in IETF HR MIB)
        --  indicates if media MAY be removed for disk storage device
        --  (note the spelling error in 'hrDiskStorageRemoveble' !!)
        --  passed as decimal string or as boolean enum label
        --  (eg, 'true'), NOT as binary value
        --  (for device types 'hrDeviceDiskStorage' in HR Device table)

      * KC  'hrDiskStorageCapacity'
        --  syntax 'KBytes' (kilobytes, defined in IETF HR MIB)
        --  total size of disk storage device
        --  passed as decimal string, NOT as binary value
        --  (for device types 'hrDeviceDiskStorage' in HR Device table)

        --  Partition table in Device group of IETF HR MIB (RFC 2790)
      * XX  'hrPartitionIndex'
        --  syntax 'INTEGER (1..2147483647)'
        --  index of disk storage partition
        --  (REQUIRED for 'entityCreate')
        --  passed as decimal string, NOT as binary index
        --  (for device types 'hrDeviceDiskStorage' in HR Device table)

      * XL  'hrPartitionLabel'
        --  syntax 'InternationalDisplayString (SIZE (0..128))'
        --  textual description of disk storage partition
        --  passed in dynamic locale
        --  (see 'scmGenCurrentLocalizationIndex')
        --  (for device types 'hrDeviceDiskStorage' in HR Device table)

      * XI  'hrPartitionID'
        --  syntax 'OCTET STRING (SIZE (0..128))'
        --  descriptor (possibly binary) of disk storage partition
        --  passed as hexadecimal string, NOT as binary value
        --  (for device types 'hrDeviceDiskStorage' in HR Device table)

      * XS  'hrPartitionSize'
        --  syntax 'KBytes' (kilobytes, defined in IETF HR MIB)
        --  total size of disk storage partition
        --  passed as decimal string, NOT as binary value
        --  (for device types 'hrDeviceDiskStorage' in HR Device table)


      * XF  'hrPartitionFSIndex'
        --  syntax 'INTEGER (0..2147483647)'
        --  (see 'hrFSIndex' in IETF HR MIB)
        --  index of 'hrFSEntry' mounted on disk storage partition
        --  or zero, if none
        --  passed as decimal string, NOT as binary value
        --  (exactly ONE file system MAY be mounted on a partition)
        --  (note that multiple partitions MAY support ONE file system,
        --  but multiple file systems MAY NOT reside on ONE partition)
        --  (for device types 'hrDeviceDiskStorage' in HR Device table)

        --  File System table in Device group of IETF HR MIB (RFC 2790)
      * FX  'hrFSIndex'
        --  syntax 'INTEGER (1..2147483647)'
        --  index of file system
        --  (REQUIRED for 'entityCreate')
        --  passed as decimal string, NOT as binary index
        --  (for device types 'hrDeviceDiskStorage' in HR Device table)

      * FM  'hrFSMountPoint'
        --  syntax 'InternationalDisplayString (SIZE (0..128))'
        --  path name of the root of file system
        --  passed in dynamic locale
        --  (see 'scmGenCurrentLocalizationIndex')
        --  (for device types 'hrDeviceDiskStorage' in HR Device table)

      * FR  'hrFSRemoteMountPoint'
        --  syntax 'InternationalDisplayString (SIZE (0..128))'
        --  name or address of server file system is mounted from
        --  passed in dynamic locale
        --  (see 'scmGenCurrentLocalizationIndex')
        --  (for device types 'hrDeviceDiskStorage' in HR Device table)

      * FY  'hrFSType'
        --  syntax 'OBJECT IDENTIFIER'
        --  (see 'hrFSTypes' in IETF HR MIB)
        --  type of file system
        --  passed as dotted decimal OID or as file system type label
        --  (eg, 'hrFSiso9660'), NOT as binary 'OBJECT IDENTIFIER'
        --  (for device types 'hrDeviceDiskStorage' in HR Device table)

      * FA  'hrFSAccess'
        --  syntax 'INTEGER (1..2)' (enumeration)
        --  access of WHOLE file system (NOT individual files)
        --  passed as decimal string or as access enum label
        --  (eg, 'readOnly'), NOT as binary value
        --  (for device types 'hrDeviceDiskStorage' in HR Device table)

      * FB  'hrFSBootable'
        --  syntax 'Boolean' (true/false, defined in IETF HR MIB)
        --  indicates if file system is bootable
        --  passed as decimal string or as boolean enum label
        --  (eg, 'true'), NOT as binary value


        --  (for device types 'hrDeviceDiskStorage' in HR Device table)

      * FS  'hrFSStorageIndex'
        --  syntax 'INTEGER (0..2147483647)'
        --  (see 'hrStorageIndex' in IETF HR MIB)
        --  index of 'hrStorageEntry' for file system
        --  or zero, if none
        --  passed as decimal string, NOT as binary value
        --  (exactly ONE file system MAY be mounted on a partition)
        --  (note that multiple partitions MAY support ONE file system,
        --  but multiple file systems MAY NOT reside on ONE partition)
        --  (for device types 'hrDeviceDiskStorage' in HR Device table)

        --  Software Running group of IETF HR MIB (RFC 2790)
      * RO  'hrSWOSIndex'
        --  syntax 'INTEGER (1..2147483647)'
        --  index of operating system running software conceptual row
        --  passed as decimal string, NOT as binary index

      * RX  'hrSWRunIndex'
        --  syntax 'INTEGER (1..2147483647)'
        --  index of host system running software conceptual row
        --  (REQUIRED for 'entityCreate')
        --  passed as decimal string, NOT as binary index

      * RN  'hrSWRunName'
        --  syntax 'InternationalDisplayString (SIZE (0..64))'
        --  textual description of running software,
        --  including manufacturer, revision, local name, and
        --  (optionally) serial number
        --  passed in dynamic locale
        --  (see 'scmGenCurrentLocalizationIndex')

      * RI  'hrSWRunID'
        --  syntax 'ProductID'
        --  (manufacturer defined object identifier)
        --  product ID of running software
        --  passed as dotted decimal OID or as software product ID label
        --  (eg, 'scmPidStarship20'), NOT as binary object identifier

      * RF  'hrSWRunPath'
        --  syntax 'InternationalDisplayString (SIZE (0..128))'
        --  initial load path (file) of running software
        --  passed in dynamic locale
        --  (see 'scmGenCurrentLocalizationIndex')

      * RP  'hrSWRunParameters'
        --  syntax 'InternationalDisplayString (SIZE (0..128))'
        --  initial load parameters (arguments) of running software
        --  passed in dynamic locale
        --  (see 'scmGenCurrentLocalizationIndex')

      * RY  'hrSWRunType'
        --  syntax 'INTEGER (1..4)' (enumeration)


        --  type of running software
        --  passed as decimal string or as software type enum label
        --  (eg, 'application'), NOT as binary value

        --  Software Installed group of IETF HR MIB (RFC 2790)
      * WX  'hrSWInstalledIndex'
        --  syntax 'INTEGER (1..2147483647)'
        --  index of host system installed software conceptual row
        --  (REQUIRED for 'entityCreate')
        --  passed as decimal string, NOT as binary index

      * WN  'hrSWInstalledName'
        --  syntax 'InternationalDisplayString (SIZE (0..64))'
        --  textual description of installed software,
        --  including manufacturer, revision, local name, and
        --  (optionally) serial number
        --  passed in dynamic locale
        --  (see 'scmGenCurrentLocalizationIndex')

      * WI  'hrSWInstalledID'
        --  syntax 'ProductID'
        --  (manufacturer defined object identifier)
        --  product ID of installed software
        --  passed as dotted decimal OID or as software product ID label
        --  (eg, 'scmPidStarship20'), NOT as binary object identifier

      * WY  'hrSWInstalledType'
        --  syntax 'INTEGER (1..4)' (enumeration)
        --  type of installed software
        --  passed as decimal string or as software type enum label
        --  (eg, 'application'), NOT as binary value

        --  Color Calibration Information
      * CN  [Color Name - no object mapping]
        --  syntax 'DisplayString (SIZE (2))'
        --  name of a color (color plus level)
        --  color:  C=cyan, M=magenta, Y=yellow, K=Black
        --  color:  R=red, G=green, B=blue
        --  level:  S=shadow, M=midbalance, H=highlight, W=whitepoint
        --  (eg, 'CN=CS:' specifies a color name of 'cyan-shadow')
        --  (see 'TCxx' system color calibration tests below)
      * CV  [Color Value - no object mapping]
        --  syntax 'INTEGER (0..100)'
        --  value of a color (specified by previous 'CN=xx' element)
        --  (eg, 'CV=20:' specifies a color value of '20')
        --  (see 'TCxx' system color calibration tests below)

        --  SNMP Community Names (for SNMPv1c and SNMPv2c)
      * CO  [Community Name Ordinal - no direct object mapping]
        --  syntax 'Ordinal32'
        --  ordinal for storing the 'CR|CW|CT' value below to an array
        --  (eg, 'CO=1' refers to object 'scmGenBaseSNMPxxxCommunity')
        --  (see 'CR', 'CW', and 'CT' below)
      * CR  'scmGenBaseSNMPReadCommunity'


        --  syntax 'ScmFixedLocaleDisplayString (SIZE (0..255))'
        --  read community name for SNMP 'Get|GetNext|GetBulk' PDUs
        --  passed in fixed locale (see 'scmGenFixedLocalizationIndex')
        --  (eg, 'CR=:' clears all read community names)
        --  (eg, 'CR=public:' sets a read community name of 'public')
      * CW  'scmGenBaseSNMPWriteCommunity'
        --  syntax 'ScmFixedLocaleDisplayString (SIZE (0..255))'
        --  write community name for SNMP 'Set|Get|GetNext|GetBulk' PDUs
        --  passed in fixed locale (see 'scmGenFixedLocalizationIndex')
      * CT  'scmGenBaseSNMPTrapCommunity'
        --  syntax 'ScmFixedLocaleDisplayString (SIZE (0..255))'
        --  trap community name for SNMP 'Inform|Trap' PDUs
        --  passed in fixed locale (see 'scmGenFixedLocalizationIndex')

        --  Job Data from SCMI Job Monitoring MIB (41jobmon)
      * JA  'scmJobSubmittingApplication'
        --  syntax 'CodeIndexedStringIndex'
        --  job programmatic originator (as opposed to job human owner)
        --  passed in fixed locale (see 'scmGenFixedLocalizationIndex')

      * JC  'scmJobClientId'
        --  syntax 'ScmGlobalUniqueID'
        --  job client-assigned identifier
        --  passed as dotted decimal string, NOT as a binary OID

      * JD  'scmDocName'
        --  syntax 'CodeIndexedStringIndex'
        --  document name
        --  passed in fixed locale (see 'scmGenFixedLocalizationIndex')

      * JF  'scmDocFileName'
        --  syntax 'CodeIndexedStringIndex'
        --  document filename (MAY be used for print-by-reference)
        --  passed in fixed locale (see 'scmGenFixedLocalizationIndex')

      * JH  'jobHoldSet' in 'scmJobStateReasons'
        --  syntax 'TruthValue'
        --  job hold (for creating job with held-by-user condition)
        --  passed as '1' (true) or '2' (false), NOT as binary value

      * JM  'scmJobMessageFromAdministrator'
        --  syntax 'CodeIndexedStringIndex'
        --  job message from system administrator
        --  passed in fixed locale (see 'scmGenFixedLocalizationIndex')

      * JN  'scmJobName'
        --  syntax 'CodeIndexedStringIndex'
        --  job name
        --  passed in fixed locale (see 'scmGenFixedLocalizationIndex')

      * JO  'scmJobOwner'
        --  syntax 'CodeIndexedStringIndex'
        --  job human owner (as opposed to job programmatic originator)
        --  passed in fixed locale (see 'scmGenFixedLocalizationIndex')


      * JP  'scmJobPriority'
        --  syntax 'INTEGER (0..100)'
        --  job priority (0=unspecified, 1=lowest, 100=highest)
        --  passed as decimal string, NOT as binary index

      * JR  'scmJobRetentionPeriod'
        --  syntax 'Cardinal32'
        --  job retention period (in seconds after completion)
        --  passed as decimal string, NOT as binary value

      * JS  'scmJobServiceType'
        --  syntax 'ScmJMJobServiceTypeOID' (OBJECT IDENTIFIER)
        --  job service type
        --  passed as dotted decimal OID or as job service type label
        --  (eg, 'scmJobServicePrintOID'),
        --  NOT as binary 'OBJECT IDENTIFIER'

      * JT  'scmJobProcessAfter'
        --  syntax 'DateAndTime'
        --  job process after calendar date and time
        --  passed as dotted decimal string (ie, 'yyyy.mm.dd.hh.mm.ss'),
        --  NOT as binary value

      * JU  'scmJobComment'
        --  syntax 'CodeIndexedStringIndex'
        --  job comment from user (eg, for banner sheet)
        --  passed in fixed locale (see 'scmGenFixedLocalizationIndex')

      * JW  ['system job' standard type - no object mapping]
        --  syntax 'DisplayString'
        --  'system job' standard type (standardized below)
        --  (REQUIRED for 'deviceJobCreate')
        --  passed as ASCII string, NOT as localized string
        --  (copied to 'scmJobName', unless 'JN' tag is specified)

      * JX  ['system job' extended type - no object mapping]
        --  syntax 'DisplayString'
        --  'system job' extended type (freeform, no standards)
        --  (OPTIONAL for 'deviceJobCreate')
        --  passed as ASCII string, NOT as localized string
        --  (appended to 'scmJobName', unless 'JN' tag is specified)

        SCMI standard 'system job' types for use in 'JW' arguments
        (in 'scmHrDevMgmtCommandData' and 'scmSimpleJobMgmtData') and
        for the value of 'scmJobName' (unless 'JN' tag is specified)
        are as follows:

        --  Accounting Reports
      * ACCT    (basic) accounting report
      * AEXT    (extended) accounting report

        --  Configuration Reports
      * CONF    (basic) system configuration report


      * CEXT    (extended) system configuration report
      * CMEM    (installed) memory configuration report
      * CMSR    media (supported and ready) configuration report
      * CNET    network interfaces configuration report
      * COPT    (installed) optional devices configuration report
      * CPDL    (JCL and/or PDL) interpreters configuration report
      * CPRO    network protocols configuration report
      * CSWI    (installed) software configuration report

        --  Demos
      * DEMO    (basic) demo job
      * DEXT    (extended) demo job

        --  Font Reports
      * FONT    (basic) fonts report
      * FEXT    (extended) fonts report
      * FPCL    (installed) HP PCL fonts report
      * FPSX    (installed) Adobe PostScript fonts report

        --  List Directories and/or Files
        --  See section 3.4.1 'List Directory (LIST) Requests'
        --  in SCMI Ext to Host Resources TC.
      * LIST    list tree of disk directories (but NOT contents)
      * LALL    list tree of disk directories (including all files)
      * LDIR    list (specific) disk directory
      * LERR    list system error file
      * LLOG    list system log file
      * LFIL    list (specific) file

        --  Local UI Menu Reports
      * MENU    (basic) local UI menu tree report
      * MEXT    (extended) local UI menu tree report

        --  Document Resources Reports
      * RSRC    (basic) document resources report
      * REXT    (extended) document resources report

        --  System Tests
      * TEST    (basic) system test
      * TEXT    (extended) system test
      * TMEM    (installed) memory verfication test report
      * TNET    network interfaces verification test report
      * TOPT    (installed) optional devices test report
      * TPAT    print test pattern (especially for printers and copiers)
      * TPDL    (JCL and/or PDL) interpreters system test report
      * TPRO    network protocols verification test report
      * TSWI    (installed) software verfication test report

        --  System Color Calibration Tests
      * TCAC    print automatic color chart (auto calibration)
      * TCBC    print balance chart (manual calibration)
      * TCCC    print corrected color chart (color calibration)
      * TCSC    scan automatic color chart (auto calibration)
      * TCTC    print tone chart (manual calibration)


      * TCUC    print uncorrected color chart (color calibration)
      * TCBV    set balance values (manual calibration)
      * TCTV    set tone values (manual calibration)

        --  User Reports
      * USER    (basic) configured users report
      * UEXT    (extended) configured users report

        The above SCMI standard 'tags' MAY be extended in the future."
    REFERENCE
        "See:   Section 4 'Print Utilities' (pages 71 to 212) of
                POSIX Sys Admin (IEEE 1387.4 / Draft 8, October 1994).
        See:    'hrDeviceStatus' in the Device group of the
                IETF Host Resources MIB (RFC 2790).
        See:    Section 3.4 'SCMI Standard Tagged Management Data' and
                Section 3.5 'Simple Device Management Requests' in
                SCMI Ext to Host Resources TC.
        See:    Section 3.5.3 'Secure Simple Device Mgmt Requests' in
                SCMI Security TC."
    SYNTAX      OCTET STRING (SIZE (2))

ScmHrDevPowerModeType ::= TEXTUAL-CONVENTION
    STATUS      current
    DESCRIPTION
        "A device power mode type, used by system administrators
        of this device for power management details.

        Usage:  Used in 'devicePowerModeType' Device Detail, to clearly
        identify the referenced power mode (without resort to strings)."
    SYNTAX      INTEGER {
        other(1),                       -- other power mode type
        unknown(2),                     -- unknown power mode type
        --  SCMI simple device power modes, supported in
        --  Device Calendar, Device Mgmt, and Device Power groups via
        --  'ScmHrDevMgmtCommandRequest' and 'ScmHrDevInfoConditions'
        readyMode(3),                   -- 'warmUp|powerToReady' in
                                        -- 'ScmHrDevMgmtCommandRequest'
        standbyMode(4),                 -- 'coolDown|powerToStandby' in
                                        -- 'ScmHrDevMgmtCommandRequest'
        sleepMode(5),                   -- 'energySave|powerToSleep' in
                                        -- 'ScmHrDevMgmtCommandRequest'
        offMode(6)                      -- 'shutdown|quiesce' in
                                        -- 'ScmHrDevMgmtCommandRequest'
        --  SCMI advanced device power modes, supported in
        --  Device Detail group via
        --  'ScmHrDevDetailType' of 'devicePowerModeType'
        --  ...to be supplied
    }


ScmHrDevPowerTimeUnit ::= TEXTUAL-CONVENTION
    STATUS      current
    DESCRIPTION
        "A device power cycle time unit, used by system administrators
        of this device for power management cycle times.

        Usage:  Used to scale the values in the Device Power group, for
        convenience and (optional) high resolution."
    SYNTAX      INTEGER {
        other(1),                       -- other time unit
        unknown(2),                     -- unknown time unit
        microsecond(3),                 -- 1 microsecond
        millisecond(4),                 -- 1 millisecond
        second(5),                      -- 1 second
        kilosecond(6),                  -- 1 kilosecond
        megasecond(7),                  -- 1 megasecond
        minute(8),                      -- 1 minute
        hour(9),                        -- 1 hour
        day(10),                        -- 1 day
        week(11),                       -- 1 week
        month(12),                      -- 1 month
        year(13)                        -- 1 year
    }

ScmHrDevTrafficUnit ::= TEXTUAL-CONVENTION
    STATUS      current
    DESCRIPTION
        "The type of traffic unit used to measure input and/or output
        traffic for this device.

        Usage:  The use of either 'other' or 'unknown' is uninformative
        and SHOULD be avoided by conforming implementations.

        Usage:  'mediaImage' - SHOULD be used ONLY for softcopy
                INPUT page images (scan, copy, fax, etc.).
                'mediaImpression' - SHOULD be used ONLY for hardcopy
                OUTPUT page impressions (print, copy, fax, etc.)
                'mediaSheet' - SHOULD be used ONLY for hardcopy
                OUTPUT and does NOT always equal output pages
                (e.g., duplex or N-up printing)."
    SYNTAX      INTEGER {
        other(1),                       -- other traffic unit
        unknown(2),                     -- unknown traffic unit
        binaryBit(11),                  -- 1 bit
        binaryNibble(12),               -- 4 bits
        binaryOctet(13),                -- 8 bits
        binaryLine(14),                 -- 1 to N bits (eg, video line)
        textCharacter(15),              -- 5 to 8 bits
        textWord(16),                   -- 1 to N characters
        textLine(17),                   -- 1 to N characters
        textSentence(18),               -- 1 to N words
        textParagraph(19),              -- 1 to N sentences
        mediaBlock(20),                 -- 1 media-specific block
        mediaSector(21),                -- 1 media-specific sector


        mediaRow(22),                   -- 1 media-specific row
        mediaColumn(23),                -- 1 media-specific column
        mediaPacket(24),                -- 1 media-specific packet
        mediaCell(25),                  -- 1 media-specific cell
        mediaImage(26),                 -- 1 media-specific image
        mediaImpression(27),            -- 1 media-specific impression
        mediaSheet(28),                 -- 1 media-specific sheet
        lengthInch(29),                 -- 1 English inch
        lengthFoot(30),                 -- 1 English foot
        lengthYard(31),                 -- 1 English yard
        lengthMile(32),                 -- 1 English mile
        lengthMicrometer(33),           -- 1 micrometer
        lengthMillimeter(34),           -- 1 millimeter
        lengthCentimeter(35),           -- 1 centimeter
        lengthMeter(36),                -- 1 meter
        lengthKilometer(37),            -- 1 kilometer
        volumeMicroliter(38),           -- 1 microliter
        volumeMilliliter(39),           -- 1 milliliter
        volumeLiter(40),                -- 1 liter
        volumeKiloliter(41),            -- 1 kiloliter
        weightMicrogram(42),            -- 1 microgram
        weightMilligram(43),            -- 1 milligram
        weightGram(44),                 -- 1 gram
        weightKilogram(45),             -- 1 kilogram
        areaSqInch(50),                 -- 1 square inch
        areaSqFoot(51),                 -- 1 square Foot
        areaSqYard(52),                 -- 1 square Yard
        areaSqMile(53),                 -- 1 square Mile
        areaSqMicrometer(54),           -- 1 square Micrometer
        areaSqMillimeter(55),           -- 1 square Millimeter
        areaSqCentimeter(56),           -- 1 square Centimeter
        areaSqMeter(57),                -- 1 square Meter
        areaSqKilometer(58),            -- 1 square Kilometer
        areaSheet(59),                  -- Area in "sheets"
        media100Image(60),              -- 100 media-specific image
        media100Impression(61),         -- 100 media-specific impression
        media100Sheet(62),              -- 100 media-specific sheet
        length100Foot(63),              -- 100 English feet
        length100Meter(64),             -- 100 meter (a hectometer)
        area100SqFoot(65),              -- 100 square Feet
        area10SqMeter(66),              -- 10 square Meters
        area100Sheet(67)                -- 100 times area of a sheet

--      Note that 10 sqMeters = 107.584 sqFeet.
--      The area of a "sheet" is defined as the area in square meters
--      divided by 16 rounded to the nearest integer but at least 1.
    }

ScmHrGroupSupport ::= TEXTUAL-CONVENTION
    STATUS      current
    DESCRIPTION
        "The terse conformance statement of ALL mandatory, conditionally
        mandatory, and optional IETF Host Resources MIB (RFC 2790)
        and SCMI Ext to Host Resources MIB objects which are


        supported by this management agent implementation (ie, version)
        on this host system, specified in a bit-mask.

        The current set of values (which MAY be extended in the future)
        is given below:

        --  IETF Host Resources MIB object groups
              1 : hrSystemGroup                 -- 2**0
              2 : hrStorageGroup                -- 2**1
              4 : hrDeviceGroup                 -- 2**2
              8 : hrSWRunGroup                  -- 2**3
             16 : hrSWRunPerfGroup              -- 2**4
             32 : hrSWInstalledGroup            -- 2**5
        --  SCMI Ext to Host Resources MIB object groups
             64 : scmHrDevInfoGroup             -- 2**6
            128 : scmHrDevHelpGroup             -- 2**7
            256 : scmHrDevMgmtGroup             -- 2**8
            512 : scmHrDevPowerGroup            -- 2**9
           1024 : scmHrDevTrafficGroup          -- 2**10
           2048 : scmHrSystemFaultGroup         -- 2**11
           4096 : scmHrGeneralGroup             -- 2**12
           8192 : scmHrDevCalendarGroup         -- 2**13
          16384 : scmHrSWRunGroup               -- 2**14
          32768 : scmHrSWInstalledGroup         -- 2**15
          65536 : scmHrDevDetailGroup           -- 2**16
         131072 : scmHrStorageExtGroup          -- 2**17
         262144 : scmHrStorageDetailGroup       -- 2**18
         524288 : scmHrDevCoverGroup            -- 2**19
        1048576 : scmHrDevAlertGroup            -- 2**20
        2097152 : scmHrConsoleScreenGroup       -- 2**21
        4194304 : scmHrConsoleTabGroup          -- 2**22
        --  IETF Host Resources MIB tables for specific device types
       33554432 : hrProcessorTable              -- 2**25
       67108864 : hrNetworkTable                -- 2**26
      134217728 : hrPrinterTable                -- 2**27
      268435456 : hrDiskStorageTable            -- 2**28
      536870912 : hrPartitionTable              -- 2**29
     1073741824 : hrFSTable                     -- 2**30

        -- 2**31 NOT used, due to 'Integer32|Cardinal32' semantics

        Usage:  Conforming management agents SHALL accurately
        report their support for IETF Host Resources MIB (RFC 2790)
        and SCMI Ext to Host Resources MIB object groups."
    SYNTAX      INTEGER (0..2147483647)  -- biggest int = 2**31-1

ScmHrSWRunXStatus ::= TEXTUAL-CONVENTION
    STATUS      current
    DESCRIPTION
        "An extended software status, used by system administrators and
        end users of this software (here, read 'state' for 'status').

        Note:   This extended software status is present for future
        extensions."


    REFERENCE
        "See:   'hrSWRunStatus' in the basic Software Running Group
        of the IETF Host Resources MIB (RFC 2790)."
    SYNTAX      INTEGER {
        none(0),
        other(1),
        unknown(2)
    }

ScmHrStorageDetailType ::= TEXTUAL-CONVENTION
    STATUS      current
    DESCRIPTION
        "The type of the storage detail information specified
        in this conceptual row in the 'scmHrStorageDetailTable'.

        Usage:  Used to describe system-, program-, or thread-level
        memory allocations/reservations.

        Usage:  'hrStorageEntry' and (optionally) 'scmHrStorageEntry'
        MAY be referenced via 'scmSecServiceHrStorageIndex' in the
        Service group of the SCMI Security MIB.

        Usage:  Conforming management stations and management agents
        SHALL implement specified semantics for storage detail types."

--    * 'other'
--    * 'unknown'
--
--      -   Storage general info
--    * 'storageName'
--      - storage administrative name in directory (primary name)
--      - type - (ScmFixedLocaleDisplayString)
--      - subtype - '...ValueOID' (directory in SCMI Comms Config TC)
--      - (eg, 'scmCOInternetDNS')
--      - data - '...ValueString'
--      - (eg, 'showstopper.sample.com')
--    * 'storageAlias'
--      - storage administrative alias in directory (alternate name)
--      - type - (ScmFixedLocaleDisplayString)
--      - subtype - '...ValueOID' (directory in SCMI Comms Config TC)
--      - (eg, 'scmCOInternetDNS')
--      - data - '...ValueString'
--      - (eg, 'LaserRat')
--    * 'storageType'
--      - storage type
--      - see - 'hrStorageType' in IETF HR MIB
--      - type - (OBJECT IDENTIFIER)
--      - data - '...ValueOID'
--      - (eg, 'hrStorageRam')
--    * 'storageDescription'
--      - storage description
--      - see - 'hrStorageDescr' in IETF HR MIB
--      - type - (ScmFixedLocaleDisplayString)
--      - data - '...ValueString'


--      - (eg, 'RAM Memory')
--    * 'storageAllocationUnits'
--      - storage allocation block size (in octets)
--      - type - (Cardinal32) 'hrStorageAllocationUnits'
--      - data - '...ValueInteger'
--      - (eg, '4096')
--    * 'storageTree'
--      - storage tree prefix to name/alias in directory
--      - type - (ScmFixedLocaleDisplayString)
--      - subtype - '...ValueOID' (directory in SCMI Comms Config TC)
--      - (eg, 'scmCONetwareNDS')
--      - data - '...ValueString'
--      - (MAY also appear in 'storageName')
--    * 'storageContext'
--      - storage context prefix to name/alias in directory
--      - type - (ScmFixedLocaleDisplayString)
--      - subtype - '...ValueOID' (directory in SCMI Comms Config TC)
--      - (eg, 'scmCONetwareNDS')
--      - data - '...ValueString'
--      - (MAY also appear in 'storageName')
--
--      -   System/Program/Thread storage details
--    * 'storageInputBuffer'
--      - network or standard input buffer size
--      - type - (Cardinal32)
--      - data - '...ValueInteger'
--      - positive integer = size in 'hrStorageAllocationUnits'
--      - zero = no size specified
--    * 'storageOutputBuffer'
--      - network or standard output buffer size
--      - type - (Cardinal32)
--      - data - '...ValueInteger'
--      - positive integer = size in 'hrStorageAllocationUnits'
--      - zero = no size specified
--    * 'storageImageBuffer'
--      - frame buffer size
--      - type - (Cardinal32)
--      - data - '...ValueInteger'
--      - positive integer = size in 'hrStorageAllocationUnits'
--      - zero = no size specified
--    * 'storageMarkerBuffer'
--      - marker buffer size (for hardcopy)
--      - type - (Cardinal32)
--      - data - '...ValueInteger'
--      - positive integer = size in 'hrStorageAllocationUnits'
--      - zero = no size specified
--    * 'storagePageBuffer'
--      - interpreter buffer size (for softcopy)
--      - type - (Cardinal32)
--      - data - '...ValueInteger'
--      - positive integer = size in 'hrStorageAllocationUnits'
--      - zero = no size specified
--    * 'storageTranslationBuffer'
--      - translation/localization buffer size


--      - type - (Cardinal32)
--      - data - '...ValueInteger'
--      - positive integer = size in 'hrStorageAllocationUnits'
--      - zero = no size specified
--    * 'storageWorkingBuffer'
--      - working buffer size
--      - type - (Cardinal32)
--      - data - '...ValueInteger'
--      - positive integer = size in 'hrStorageAllocationUnits'
--      - zero = no size specified
--
--      -   Interpreter storage details
--    * 'storageFontCache'
--      - interpreter font cache size
--      - type - (Cardinal32)
--      - data - '...ValueInteger'
--      - positive integer = size in 'hrStorageAllocationUnits'
--      - zero = no size specified
--    * 'storageFormCache'
--      - interpreter form cache size
--      - type - (Cardinal32)
--      - data - '...ValueInteger'
--      - positive integer = size in 'hrStorageAllocationUnits'
--      - zero = no size specified
--    * 'storageLogoCache'
--      - interpreter logo cache size
--      - type - (Cardinal32)
--      - data - '...ValueInteger'
--      - positive integer = size in 'hrStorageAllocationUnits'
--      - zero = no size specified
--    * 'storageMacroCache'
--      - interpreter macro cache size
--      - type - (Cardinal32)
--      - data - '...ValueInteger'
--      - positive integer = size in 'hrStorageAllocationUnits'
--      - zero = no size specified
--    * 'storageStyleCache'
--      - interpreter style cache size
--      - type - (Cardinal32)
--      - data - '...ValueInteger'
--      - positive integer = size in 'hrStorageAllocationUnits'
--      - zero = no size specified
--
--      -   Program/Thread storage details
--    * 'storageHeapMemory'
--      - program/thread heap memory size
--      - type - (Cardinal32)
--      - data - '...ValueInteger'
--      - positive integer = size in 'hrStorageAllocationUnits'
--      - zero = no size specified
--    * 'storagePrefixMemory'
--      - program/thread prefix memory size
--      - type - (Cardinal32)
--      - data - '...ValueInteger'


--      - positive integer = size in 'hrStorageAllocationUnits'
--      - zero = no size specified
--    * 'storageStackMemory'
--      - program/thread stack memory size
--      - type - (Cardinal32)
--      - data - '...ValueInteger'
--      - positive integer = size in 'hrStorageAllocationUnits'
--      - zero = no size specified
--    * 'storageWorkingMemory'
--      - program/thread working memory size
--      - type - (Cardinal32)
--      - data - '...ValueInteger'
--      - positive integer = size in 'hrStorageAllocationUnits'
--      - zero = no size specified
--
--      -   Storage addressing details
--    * 'storageBaseAddress'
--      - storage base address (physical or logical)
--      - type - (Cardinal32)
--      - data - '...ValueInteger'
--      - (eg, '0xF800')
--    * 'storageWordSize'
--      - storage addressability (word size in octets)
--      - type - (Cardinal32)
--      - data - '...ValueInteger'
--      - (eg, '4')
--    * 'storagePageSize'
--      - storage page size (in octets)
--      - type - (Cardinal32)
--      - data - '...ValueInteger'
--      - (eg, '8192')
    REFERENCE
        "See:   'scmHrStorageDetailUnit' for units of storage detail."
    SYNTAX      INTEGER {
        other(1),
        unknown(2),
        --  Storage general info
        storageName(3),                 -- storage name (primary name)
        storageAlias(4),                -- storage alias (other name)
        storageType(5),                 -- storage type (R/W)
        storageDescription(6),          -- storage description (R/W)
        storageAllocationUnits(7),      -- storage allocation block size
        storageTree(8),                 -- storage directory tree
        storageContext(9),              -- storage context
        --  System/Program/Thread storage details
        storageInputBuffer(10),         -- network or standard input
        storageOutputBuffer(11),        -- network or standard output
        storageImageBuffer(12),         -- frame buffer
        storageMarkerBuffer(13),        -- marker buffer (hardcopy)
        storagePageBuffer(14),          -- interpreter buffer (softcopy)
        storageTranslationBuffer(15),   -- translate/localize buffer
        storageWorkingBuffer(16),       -- working buffer
        --  Interpreter storage details
        storageFontCache(20),           -- interpreter font cache


        storageFormCache(21),           -- interpreter form cache
        storageLogoCache(22),           -- interpreter logo cache
        storageMacroCache(23),          -- interpreter macro cache
        storageStyleCache(24),          -- interpreter style cache
        --  Program/Thread storage details
        storageHeapMemory(30),          -- program/thread heap memory
        storagePrefixMemory(31),        -- program/thread prefix memory
        storageStackMemory(32),         -- program/thread stack memory
        storageWorkingMemory(33),       -- program/thread working memory
        --  Storage addressing details
        storageBaseAddress(40),         -- storage base address
        storageWordSize(41),            -- storage addressability
        storagePageSize(42)             -- storage page size
    }

ScmHrStorageRealization ::= TEXTUAL-CONVENTION
    STATUS      current
    DESCRIPTION
        "An extended storage type (or storage 'realization'),
        used by system administrators and end users of this storage.

        Usage:  The use of either 'other' or 'unknown' is uninformative
        and SHOULD be avoided by conforming implementations.

      * 'physicalSystem' - 'real' memory installed on a 'system'
        whose product is found via 'scmHrStorageProductDeviceIndex' and
        whose CPU is found via 'scmHrStoragePlatformDeviceIndex' and
        whose self is found via 'scmHrStorageMatchingDeviceIndex';
      * 'physicalProgram' - 'real' memory assigned to a 'program'
        (memory which is 'pinned' and is NOT paged to disk storage)
        whose program is found via 'scmHrStorageSWRunIndex';
      * 'physicalThread' - 'real' memory assigned to a 'thread'
        (memory which is 'pinned' and is NOT paged to disk storage)
        whose program/thread is found via 'scmHrStorageSWRunIndex';
      * 'logicalSystem' - 'virtual' memory assigned to a 'system'
        (memory which is NOT 'pinned' and MAY be paged to disk storage)
        whose product is found via 'scmHrStorageProductDeviceIndex' and
        whose CPU is found via 'scmHrStoragePlatformDeviceIndex' and
        whose self is found via 'scmHrStorageMatchingDeviceIndex';
      * 'logicalProgram' - 'virtual' memory assigned to a 'program'
        (memory which is NOT 'pinned' and MAY be paged to disk storage)
        whose program is found via 'scmHrStorageSWRunIndex';
      * 'logicalThread' - 'virtual' memory assigned to a 'thread'
        (memory which is NOT 'pinned' and MAY be paged to disk storage)
        whose program/thread is found via 'scmHrStorageSWRunIndex'."
    REFERENCE
        "See:   'ScmHrDevInfoRealization' textual convention in
                the SCMI Ext to Host Resources TC.
        See:    'scmHrDevInfoRealization' in the Device Info group of
                the SCMI Ext to Host Resources MIB."
    SYNTAX      INTEGER {
        other(1),                       -- other storage
        unknown(2),                     -- unknown storage
        physicalSystem(10),             -- 'real' system storage


        physicalProgram(11),            -- 'real' program storage
        physicalThread(12),             -- 'real' thread storage
        logicalSystem(20),              -- 'virtual' system storage
        logicalProgram(21),             -- 'virtual' program storage
        logicalThread(22)               -- 'virtual' thread storage
    }

ScmHrDpaAvailability ::= TEXTUAL-CONVENTION
    STATUS      current
    DESCRIPTION
        "The generic availability of this system, device, service, etc."
    REFERENCE
        "See:   Section 9.1.6.6 '[Generic attribute] Availability' and
                Annex A 'id-val-availability-...'
                in DPA (ISO/IEC 10175-1 Final Text, March 1996)."
    --  The following enum values are identical to the final arcs of
    --  the ISO DPA 'id-val-availability-...' OIDs
    SYNTAX      INTEGER {
        high(1),
        normal(2),
        low(3),
        none(5),
        unknown(6)
    }

ScmHrDpaConditions ::= TEXTUAL-CONVENTION
    STATUS      current
    DESCRIPTION
        "The generic conditions (ie, state reasons) of this system,
        device, service, etc, specified in a bit-mask.

        --  DPA - Service level operations
        --  See section D.2.3 of DPA Mgmt Service (ISO 10175-3)
        --  and section 4 of POSIX DPA Client (IEEE 1387.4)
              1 : cleanedByOperator             -- 2**0
              2 : cleanedBySystem               -- 2**1
                --  all jobs deleted by operator/system
                --  'serviceClean' in 'ScmSvcMonServiceMgmtOperation'
                --  'pdclean' in POSIX DPA Client
              4 : disabledByOperator            -- 2**2
              8 : disabledBySystem              -- 2**3
                --  all new jobs rejected by system
                --  'serviceDisable' in 'ScmSvcMonServiceMgmtOperation'
                --  'pddisable' in POSIX DPA Client
             16 : pausedByOperator              -- 2**4
             32 : pausedBySystem                -- 2**5
                --  all existing job output suspended on system
                --  'servicePause' in 'ScmSvcMonServiceMgmtOperation'
                --  'pdpause' in POSIX DPA Client
             64 : shutdownByOperator            -- 2**6 - 'pdshutdown'
            128 : shutdownBySystem              -- 2**7 - 'pdshutdown'
                --  service state is 'terminating', then 'unavailable'
                --  'serviceShutdown' in 'ScmSvcMonServiceMgmtOperation'
                --  'pdshutdown' in POSIX DPA Client


        --  SCMI - Service level extended operations
            256 : diagnosedByOperator           -- 2**8
            512 : diagnosedBySystem             -- 2**9
                --  'serviceDiagnose' in 'ScmSvcMonServiceMgmtOperation'
           1024 : resetByOperator               -- 2**10
           2048 : resetBySystem                 -- 2**11
                --  'serviceReset[Cold|Warm|Factory]'
                --  in 'ScmSvcMonServiceMgmtOperation'
           4096 : startedByOperator             -- 2**12
           8192 : startedBySystem               -- 2**13
                --  'service[Create|Install|Upgrade|Restart]'
                --  in 'ScmSvcMonServiceMgmtOperation'

        --  SCMI - Document service activities (during 'ready' state)
          65536 : activeCopy                    -- 2**16
         131072 : activePrint                   -- 2**17
         262144 : activeScan                    -- 2**18
         524288 : activeFaxReceive              -- 2**19
        1048576 : activeFaxSend                 -- 2**20
        2097152 : activeFileReceive             -- 2**21
        4194304 : activeFileSend                -- 2**22
        8388608 : activeMailReceive             -- 2**23
       16777216 : activeMailSend                -- 2**24
       33554432 : activeImageProcess            -- 2**25
       67108864 : activeOCR                     -- 2**26
      134217728 : activeDistribute              -- 2**27

        Usage:  The above 'conditions' augment the service state in
        'scmSvcMonService[Current|Previous]State' and the service mgmt
        information in 'scmSvcMonServiceMgmt[Operation|InProgress]'.

        Usage:  Conforming management agents SHALL report all
        'conditions' of entities accurately.  'Conditions' occur within
        or across 'states' in a finite state machine implementation of a
        system, device, service, etc.

        Usage:  A service with 'scmSvcMonServiceCurrentState' of
        'ready(1)' might have 'scmSvcMonServiceConditions' of
        'disabledByOperator', indicating that the service will not
        accept new jobs.

        Usage:  Multi-bit examples of 'scmSvcMonServiceConditions' are
        'disabledByOperator' concurrently with 'pausedByOperator' and
        'activePrint' concurrently with 'activeMailSend'."
    REFERENCE
        "See:   Section 9.5.4 'Server-state',
                section 9.1.6.4 '[Generic attribute] State', and
                Annex A 'id-val-state-...'
                in DPA (ISO/IEC 10175-1 Final Text, March 1996).
        See:    Section D.2.3 'Server State Transitions'
                in DPA Mgmt Service (ISO 10175-3 Draft, October 1996).
        See:    Section 4 'Printing Utilities - Command Line Interface'
                in POSIX DPA Client (IEEE 1387.4, October 1994)."


    SYNTAX      INTEGER (0..2147483647)  -- biggest int = 2**31-1

ScmHrDpaJobValidateSupport ::= TEXTUAL-CONVENTION
    STATUS      current
    DESCRIPTION
        "The job validation support of this system, service, etc,
        specified in a bit-mask.

        The current set of values (which MAY be extended in the future)
        is given below:

            --  ISO DPA standard values
              1 : validateAndProcess    -- generalized from DPA 'print'
              2 : validateSubmitOnly    -- error check, do NOT process
            --  SCMI standard values
              4 : validateSyntaxOnly    -- check syntax only
              8 : validateSemanticsOnly -- check syntax/ranges/states
             16 : validateLocalOnly     -- check semantic/local services
             32 : validateDistributed   -- check distributed services
             64 : validateCreateLocal   -- create local child jobs
            128 : validateCreateRemote  -- create remote child jobs

        Usage:  Conforming management agents SHALL accurately
        report their support for job validation modes."
    REFERENCE
        "See:   Section 9.5.10 'Job-validates-supported' (server),
                section 9.2.4.12 'Job-validate' (job), and
                Annex A 'id-val-job-validate-...'
                in DPA (ISO/IEC 10175-1 Final Text, March 1996)."
    SYNTAX      INTEGER (0..2147483647)  -- biggest int = 2**31-1

ScmHrDpaObjectClassSupport ::= TEXTUAL-CONVENTION
    STATUS      current
    DESCRIPTION
        "The object class support of this system, service, etc,
        specified in a bit-mask.

        The current set of values (which MAY be extended in the future)
        is given below:

            --  ISO DPA standard values
              1 : generic                       -- 2**0
              2 : job                           -- 2**1
              4 : printer                       -- 2**2
              8 : server                        -- 2**3
             16 : medium                        -- 2**4
             32 : font                          -- 2**5
            256 : transferMethod                -- 2**8
            512 : deliveryMethod                -- 2**9
           1024 : auxiliarySheet                -- 2**10
           2048 : finishing                     -- 2**11
           4096 : output                        -- 2**12
           8192 : imposition                    -- 2**13
          16384 : scheduler                     -- 2**14


          32768 : document                      -- 2**15
          65536 : resource                      -- 2**16
         131072 : initialValueJob               -- 2**17
         262144 : initialValueDocument          -- 2**18
         524288 : resourceContext               -- 2**19
        1048576 : auxiliarySheetPackage         -- 2**20
            --  SCMI standard values
       16777216 : deviceHostSystem              -- 2**24
       33554432 : deviceScanner                 -- 2**25
       67108864 : deviceCopier                  -- 2**26
      134217728 : deviceFax                     -- 2**27
      268435456 : deviceMailbox                 -- 2**28
      536870912 : deviceFinisher                -- 2**29
     1073741824 : deviceCRU                     -- 2**30

        -- 2**31 NOT used, due to 'Integer32|Cardinal32' semantics

        Usage:  Conforming management agents SHALL accurately
        report their support for object classes (ISO DPA and SCMI)."
    REFERENCE
        "See:   Section 9.5.5 'Object-classes-supported' (server),
                section 9.1.6.1 'Object-class' (system),
                Annex A 'id-oc-...'
                in DPA (ISO/IEC 10175-1 Final Text, March 1996)."
    SYNTAX      INTEGER (0..2147483647)  -- biggest int = 2**31-1

ScmHrDpaState ::= TEXTUAL-CONVENTION
    STATUS      current
    DESCRIPTION
        "The generic state of this object (system, device, service,
        etc.).  The following standard values are defined (in section
        9.1.6.4 'State' of ISO 10175-1):

      * 'ready' - This object is ready to be used without human
        intervention.
      * 'onRequest' - This object requires human intervention in order
        to be used.
      * 'unavailable' - This object is NOT available for use even with
        human intervention.
      * 'unknown' - This state of this object is NOT known.
      * 'busy' - This object is temporarily inaccessible due to dynamic
        constraints, but will become 'ready' without human intervention.
      * 'initializing' - This object is being initialized (and is
        therefore temporarily inaccessible).
      * 'terminating' - This object is being terminated (and is
        therefore permanently inaccessible)."
    REFERENCE
        "See:   Section 9.1.6.4 '[Generic attribute] State' and
                Annex A 'id-val-state-...'
                in DPA (ISO/IEC 10175-1 Final Text, March 1996)."
    --  The following enum values are identical to the final arcs of
    --  the ISO DPA 'id-val-state-...' OIDs
    SYNTAX      INTEGER {
        ready(1),


        onRequest(2),
        unavailable(3),
        unknown(4),
        busy(5),
        initializing(6),
        terminating(7)
    }

--
--          The HRX TC Dummy Group (DO NOT USE)
--
--          DO NOT USE - Present to suppress compiler warnings ONLY!
--
--          Note:  The following objects have 'odd' use of case in their
--          names (ie, 'sCm...'), in order to make obvious their related
--          textual conventions

sCmHrDummy          OBJECT IDENTIFIER ::= { scmHrTC 999 }

sCmHrDevCalendarDayOfWeek OBJECT-TYPE
    SYNTAX      ScmHrDevCalendarDayOfWeek
    MAX-ACCESS  not-accessible
    STATUS      current
    DESCRIPTION "Dummy - DO NOT USE"
    ::= { sCmHrDummy 1 }

sCmHrDevCalendarTimeOfDay OBJECT-TYPE
    SYNTAX      ScmHrDevCalendarTimeOfDay
    MAX-ACCESS  not-accessible
    STATUS      current
    DESCRIPTION "Dummy - DO NOT USE"
    ::= { sCmHrDummy 2 }

sCmHrDevDetailType OBJECT-TYPE
    SYNTAX      ScmHrDevDetailType
    MAX-ACCESS  not-accessible
    STATUS      current
    DESCRIPTION "Dummy - DO NOT USE"
    ::= { sCmHrDummy 3 }

sCmHrDevDetailUnitClass OBJECT-TYPE
    SYNTAX      ScmHrDevDetailUnitClass
    MAX-ACCESS  not-accessible
    STATUS      current
    DESCRIPTION "Dummy - DO NOT USE"
    ::= { sCmHrDummy 4 }

sCmHrDevInfoRealization OBJECT-TYPE
    SYNTAX      ScmHrDevInfoRealization
    MAX-ACCESS  not-accessible
    STATUS      current
    DESCRIPTION "Dummy - DO NOT USE"
    ::= { sCmHrDummy 5 }


sCmHrDevInfoStatus OBJECT-TYPE
    SYNTAX      ScmHrDevInfoStatus
    MAX-ACCESS  not-accessible
    STATUS      current
    DESCRIPTION "Dummy - DO NOT USE"
    ::= { sCmHrDummy 6 }

sCmHrDevInfoXStatus OBJECT-TYPE
    SYNTAX      ScmHrDevInfoXStatus
    MAX-ACCESS  not-accessible
    STATUS      current
    DESCRIPTION "Dummy - DO NOT USE"
    ::= { sCmHrDummy 7 }

sCmHrDevInfoConditions OBJECT-TYPE
    SYNTAX      ScmHrDevInfoConditions
    MAX-ACCESS  not-accessible
    STATUS      current
    DESCRIPTION "Dummy - DO NOT USE"
    ::= { sCmHrDummy 8 }

sCmHrDevInfoXConditions OBJECT-TYPE
    SYNTAX      ScmHrDevInfoXConditions
    MAX-ACCESS  not-accessible
    STATUS      current
    DESCRIPTION "Dummy - DO NOT USE"
    ::= { sCmHrDummy 9 }

sCmHrDevMgmtCommandRequest OBJECT-TYPE
    SYNTAX      ScmHrDevMgmtCommandRequest
    MAX-ACCESS  not-accessible
    STATUS      current
    DESCRIPTION "Dummy - DO NOT USE"
    ::= { sCmHrDummy 10 }

sCmHrDevMgmtCommandData OBJECT-TYPE
    SYNTAX      ScmHrDevMgmtCommandData
    MAX-ACCESS  not-accessible
    STATUS      current
    DESCRIPTION "Dummy - DO NOT USE"
    ::= { sCmHrDummy 11 }

sCmHrDevMgmtCommandDataTag OBJECT-TYPE
    SYNTAX      ScmHrDevMgmtCommandDataTag
    MAX-ACCESS  not-accessible
    STATUS      current
    DESCRIPTION "Dummy - DO NOT USE"
    ::= { sCmHrDummy 12 }

sCmHrDevPowerModeType OBJECT-TYPE
    SYNTAX      ScmHrDevPowerModeType
    MAX-ACCESS  not-accessible
    STATUS      current


    DESCRIPTION "Dummy - DO NOT USE"
    ::= { sCmHrDummy 13 }

sCmHrDevPowerTimeUnit OBJECT-TYPE
    SYNTAX      ScmHrDevPowerTimeUnit
    MAX-ACCESS  not-accessible
    STATUS      current
    DESCRIPTION "Dummy - DO NOT USE"
    ::= { sCmHrDummy 14 }

sCmHrDevTrafficUnit OBJECT-TYPE
    SYNTAX      ScmHrDevTrafficUnit
    MAX-ACCESS  not-accessible
    STATUS      current
    DESCRIPTION "Dummy - DO NOT USE"
    ::= { sCmHrDummy 15 }

sCmHrGroupSupport OBJECT-TYPE
    SYNTAX      ScmHrGroupSupport
    MAX-ACCESS  not-accessible
    STATUS      current
    DESCRIPTION "Dummy - DO NOT USE"
    ::= { sCmHrDummy 16 }

sCmHrSWRunXStatus OBJECT-TYPE
    SYNTAX      ScmHrSWRunXStatus
    MAX-ACCESS  not-accessible
    STATUS      current
    DESCRIPTION "Dummy - DO NOT USE"
    ::= { sCmHrDummy 17 }

sCmHrStorageDetailType OBJECT-TYPE
    SYNTAX      ScmHrStorageDetailType
    MAX-ACCESS  not-accessible
    STATUS      current
    DESCRIPTION "Dummy - DO NOT USE"
    ::= { sCmHrDummy 18 }

sCmHrStorageRealization OBJECT-TYPE
    SYNTAX      ScmHrStorageRealization
    MAX-ACCESS  not-accessible
    STATUS      current
    DESCRIPTION "Dummy - DO NOT USE"
    ::= { sCmHrDummy 19 }

sCmHrDpaAvailability OBJECT-TYPE
    SYNTAX      ScmHrDpaAvailability
    MAX-ACCESS  not-accessible
    STATUS      current
    DESCRIPTION "Dummy - DO NOT USE"
    ::= { sCmHrDummy 20 }

sCmHrDpaConditions OBJECT-TYPE
    SYNTAX      ScmHrDpaConditions


    MAX-ACCESS  not-accessible
    STATUS      current
    DESCRIPTION "Dummy - DO NOT USE"
    ::= { sCmHrDummy 21 }

sCmHrDpaJobValidateSupport OBJECT-TYPE
    SYNTAX      ScmHrDpaJobValidateSupport
    MAX-ACCESS  not-accessible
    STATUS      current
    DESCRIPTION "Dummy - DO NOT USE"
    ::= { sCmHrDummy 22 }

sCmHrDpaObjectClassSupport OBJECT-TYPE
    SYNTAX      ScmHrDpaObjectClassSupport
    MAX-ACCESS  not-accessible
    STATUS      current
    DESCRIPTION "Dummy - DO NOT USE"
    ::= { sCmHrDummy 23 }

sCmHrDpaState OBJECT-TYPE
    SYNTAX      ScmHrDpaState
    MAX-ACCESS  not-accessible
    STATUS      current
    DESCRIPTION "Dummy - DO NOT USE"
    ::= { sCmHrDummy 24 }

END
