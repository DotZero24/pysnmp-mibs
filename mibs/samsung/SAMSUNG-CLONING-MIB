--
-- SamsungCloning.mib
-- MIB generated by MG-SOFT Visual MIB Builder Version 3.0 Build 253
-- Friday, March 17, 2006 at 14:36:37
--

--  samsungJobAcoount.mib
-- MIB generated by MG-SOFT Visual MIB Builder Version 3.0 Build 253
-- Friday, November 11, 2005 at 17:08:35
--
--
--

	SAMSUNG-CLONING-MIB DEFINITIONS ::= BEGIN

		IMPORTS
			hrDeviceIndex
				FROM HOST-RESOURCES-MIB
			samsungCommonMIB
				FROM SAMSUNG-COMMON-MIB
			OBJECT-GROUP
				FROM SNMPv2-CONF
			IpAddress, Integer32, OBJECT-TYPE, MODULE-IDENTITY, OBJECT-IDENTITY,
			NOTIFICATION-TYPE
				FROM SNMPv2-SMI;


--            Module:  Cloning Mib
-- File: SamsungCloning.mib
-- Editors: wani.kang@samsung.com
-- Date:    November 17, 2004
-- Version: 1.00
-- RFC 1442/1902/2578
-- RFC 1443/1903/2579
-- RFC 1444/1904/2580
-- Successor to RFC 1759
-- 17 Jul 2004
-- July 17, 1904 at 00:00 GMT
		scmCloningMIB MODULE-IDENTITY
			LAST-UPDATED "200511090000Z"		-- November 09, 2005 at 00:00 GMT
			ORGANIZATION
				"Samsung Common Management Interface Working Group"
			CONTACT-INFO
				"
				SCMI Editors
				E-Mail:       wani.kang@samsung.com

				--
				--
				"
			DESCRIPTION
				"
				Version:    1.00


				Samsung SCMI Extension to IETF Printer MIB Module.
				This Module provides extension to the IETF Printer MIB.

				Copyright (C) 2003-2004 Samsung Corporation. All Rights Reserved."
			::= { samsungCommonMIB 82 }



--
-- Node definitions
--

--  Node definitions
--
-- 1.3.6.1.4.1.236.11.5.11.55.18
		scmCloning OBJECT IDENTIFIER ::= { scmCloningMIB 1 }

--            table  --
-- 1.3.6.1.4.1.236.11.5.11.55.18.2
		scmCloningTable OBJECT-TYPE
			SYNTAX SEQUENCE OF ScmCloningEntry
			MAX-ACCESS not-accessible
			STATUS current
			DESCRIPTION
				"
				"
			::= { scmCloning 1 }

--   1.3.6.1.4.1.236.11.5.11.55.18.2.1
		scmCloningEntry OBJECT-TYPE
			SYNTAX ScmCloningEntry
			MAX-ACCESS not-accessible
			STATUS current
			DESCRIPTION
				"A set of result for clonning on this device.
				If the device has no cloning result, this table is empty.
				 	"
			INDEX { scmCloningIndex }
			::= { scmCloningTable 1 }

		ScmCloningEntry ::=
			SEQUENCE {
				scmCloningIndex
					Integer32,
				scmCloningIPAddress
					IpAddress,
				scmCloningResult
					INTEGER,
				scmCloningDate
					OCTET STRING
			 }

		scmCloningIndex OBJECT-TYPE
			SYNTAX Integer32
			MAX-ACCESS read-only
			STATUS current
			DESCRIPTION
				"
				"
			::= { scmCloningEntry 1 }

		scmCloningIPAddress OBJECT-TYPE
			SYNTAX IpAddress
			MAX-ACCESS read-only
			STATUS current
			DESCRIPTION
				"This object indicates IPAdderss of device executing cloning "
			::= { scmCloningEntry 2 }

		scmCloningResult OBJECT-TYPE
			SYNTAX INTEGER
				{
				completed(1),
				processing(2),
				invalidFile(3),
				versionMismatch(4),
				notSupportedCloning(5),
				busy(6)
				}
			MAX-ACCESS read-only
			STATUS current
			DESCRIPTION
				"This object indicates result of the cloning"
			::= { scmCloningEntry 3 }

		scmCloningDate OBJECT-TYPE
			SYNTAX OCTET STRING
			MAX-ACCESS read-only
			STATUS current
			DESCRIPTION
				"This date represents when cloning is executed.
				Format of date is yyyy/mm/dd/hh/mm/ss"
			::= { scmCloningEntry 4 }

--            scmPrtOperation
--
-- 1.3.6.1.4.1.236.11.5.11.55.18.1
		scmCloningSimple OBJECT IDENTIFIER ::= { scmCloning 2 }

		scmCloningLastIPAddress OBJECT-TYPE
			SYNTAX IpAddress
			MAX-ACCESS read-only
			STATUS current
			DESCRIPTION
				"This object indicates IPAdderss of device executing cloning lately"
			::= { scmCloningSimple 1 }

		scmCloningLastResult OBJECT-TYPE
			SYNTAX INTEGER
				{
				completed(1),
				processing(2),
				invalidFile(3),
				versionMismatch(4),
				notSupportedCloning(5),
				busy(6)
				}
			MAX-ACCESS read-only
			STATUS current
			DESCRIPTION
				"This object indicates result of the latest cloning"
			::= { scmCloningSimple 2 }

		scmCloningLastDate OBJECT-TYPE
			SYNTAX OCTET STRING
			MAX-ACCESS read-only
			STATUS current
			DESCRIPTION
				"This object indicates date of the latest cloning.
				Format of date is yyyy/mm/dd/hh/mm/ss"
			::= { scmCloningSimple 3 }

		scmCloningSupported OBJECT-TYPE
			SYNTAX INTEGER
				{
				supported(1),
				notSupported(2)
				}
			MAX-ACCESS read-only
			STATUS current
			DESCRIPTION
				"This object indicates whethere device supports cloning or not"
			::= { scmCloningSimple 4 }

		scmCloningTrap OBJECT-IDENTITY
			STATUS current
			DESCRIPTION
				"The value of the enterprise-specific oid in a SNMPv1 trap sent signalling a critical event in the JobAccounting"
			::= { scmCloning 3 }

		scmCloningTrapSimple OBJECT IDENTIFIER ::= { scmCloningTrap 1 }

--
		scmCloningTrapResult NOTIFICATION-TYPE
			OBJECTS { scmCloningLastIPAddress, scmCloningLastResult }
			STATUS current
			DESCRIPTION
				"This trap is sent whenever clone is completed"
			::= { scmCloningTrapSimple 1 }


	END

--
-- SamsungCloning.mib
--
