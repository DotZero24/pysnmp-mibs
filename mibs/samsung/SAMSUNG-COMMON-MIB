SAMSUNG-COMMON-MIB DEFINITIONS ::= BEGIN

-- Module : Samsung Common Mib
-- Team   : Solution SW
-- Date   : November 24, 2004
-- Version: 1.00

IMPORTS
    enterprises, OBJECT-IDENTITY, MODULE-IDENTITY
    FROM SNMPv2-SMI;                            -- IETF RFC 1442

samsung MODULE-IDENTITY
    LAST-UPDATED "0209170000Z"
    ORGANIZATION "Samsung Corporation -
                  Samsung DPD Solution SW Team"
    CONTACT-INFO "
                    SCMI Editors
        			Samsung DPD Solution SW Team
    "
    DESCRIPTION
        "Samsung Printer Common MIB Root Module, Version 1.00.

        Copyright (C) 2003-2004 Samsung Corporation. All Rights Reserved."
    ::= { enterprises 236 }

division OBJECT-IDENTITY
	STATUS		current
	DESCRIPTION   "Distinguish Samsung Company"
    ::= { samsung 11 }

oadivision OBJECT-IDENTITY
	STATUS		current
	DESCRIPTION   "Distinguish Samsung Electronics Division"
	::= { division 5 }

samsungCommonMIB OBJECT-IDENTITY
	STATUS		current
	DESCRIPTION   "Samsung Common MIB"

    ::= { oadivision 11 }
END
