-- These MIBs were created on 1/2/2003
-- This module defines enterprise MIBs for NS BGP
--
-- Copyright (c) 1999-2004, Juniper Networks, Inc.
-- All rights reserved.

NETSCREEN-BGP4-MIB DEFINITIONS ::= BEGIN

                IMPORTS
                    MODULE-IDENTITY, OBJECT-TYPE, NOTIFICATION-TYPE,
                    IpAddress, Integer32, Counter32, Gauge32
                        FROM SNMPv2-SMI
                    netscreenTrapDesc, netscreenTrapType
                        FROM NETSCREEN-TRAP-MIB
                    netscreenVR
                        FROM NETSCREEN-SMI;

                nsBgp MODULE-IDENTITY
                    LAST-UPDATED  "200506032022Z" -- June 20, 2005
                    ORGANIZATION
                        "Juniper Networks, Inc."
                    CONTACT-INFO
                        "Customer Support

                         1194 North Mathilda Avenue
                         Sunnyvale, California 94089-1206
                         USA

                         Tel: 1-800-638-8296
                         E-mail: customerservice@juniper.net
                         HTTP://www.juniper.net"
                    DESCRIPTION
                        "The MIB module for NS-BGP-4."
                    ::= { netscreenVR 3 }

                -- BGP Info table.  This table contains, one entry per
                -- VR, information about the BGP's Version, LocalAs and Identifier.

                nsBgpInfoTable OBJECT-TYPE
                    SYNTAX     SEQUENCE OF NsBgpInfoEntry
                    MAX-ACCESS not-accessible
                    STATUS     deprecated
                    DESCRIPTION
                            "BGP info table.  This table contains,
                            one entry per VR, information about
                            the BGP's Version, LocalAs and Identifier."
                    ::= { nsBgp 1 }

                nsBgpInfoEntry OBJECT-TYPE
                    SYNTAX     NsBgpInfoEntry
                    MAX-ACCESS not-accessible
                    STATUS     deprecated
                    DESCRIPTION
                            "Entry containing information about the
                            BGP's Version, LocalAs and Identifier"
                    INDEX { nsBgpInfoVRID }
                    ::= { nsBgpInfoTable 1 }

                NsBgpInfoEntry ::= SEQUENCE {
                        nsBgpInfoVersion
                            OCTET STRING,
                        nsBgpInfoLocalAs
                            INTEGER,
                        nsBgpInfoIdentifier
                            IpAddress,
                        nsBgpInfoVRID
                            INTEGER
						}

                nsBgpInfoVersion OBJECT-TYPE
                    SYNTAX     OCTET STRING (SIZE (1..255))
                    MAX-ACCESS read-only
                    STATUS     deprecated
                    DESCRIPTION
                            "Vector of supported BGP protocol version
                            numbers.  Each peer negotiates the version
                            from this vector.  Versions are identified
                            via the string of bits contained within this
                            object.  The first octet contains bits 0 to
                            7, the second octet contains bits 8 to 15,
                            and so on, with the most significant bit
                            referring to the lowest bit number in the
                            octet (e.g., the MSB of the first octet
                            refers to bit 0).  If a bit, i, is present
                            and set, then the version (i+1) of the BGP
                            is supported."
                    ::= { nsBgpInfoEntry 1 }

                nsBgpInfoLocalAs OBJECT-TYPE
                    SYNTAX     INTEGER (0..65535)
                    MAX-ACCESS read-only
                    STATUS     deprecated
                    DESCRIPTION
                            "The local autonomous system number."
                    ::= { nsBgpInfoEntry 2 }

                nsBgpInfoIdentifier OBJECT-TYPE
                    SYNTAX     IpAddress
                    MAX-ACCESS read-only
                    STATUS     deprecated
                    DESCRIPTION
                            "The BGP Identifier of local system."
                    ::= { nsBgpInfoEntry 3 }

                nsBgpInfoVRID OBJECT-TYPE
                    SYNTAX     INTEGER (0..65535)
                    MAX-ACCESS read-only
                    STATUS     deprecated
                    DESCRIPTION
                            "Virtual Router ID"
                    ::= { nsBgpInfoEntry 4 }

                -- BGP Peer table.  This table contains, one entry per
                -- BGP peer, information about the BGP peer.

                nsBgpPeerTable OBJECT-TYPE
                    SYNTAX     SEQUENCE OF NsBgpPeerEntry
                    MAX-ACCESS not-accessible
                    STATUS     deprecated
                    DESCRIPTION
                            "BGP peer table.  This table contains,
                            one entry per BGP peer, information about
                            the connections with BGP peers."
                    ::= { nsBgp 3 }

                nsBgpPeerEntry OBJECT-TYPE
                    SYNTAX     NsBgpPeerEntry
                    MAX-ACCESS not-accessible
                    STATUS     deprecated
                    DESCRIPTION
                            "Entry containing information about the
                            connection with a BGP peer."
                    INDEX { nsBgpPeerRemoteAddr,
                            nsBgpPeerVRID }
                    ::= { nsBgpPeerTable 1 }

                NsBgpPeerEntry ::= SEQUENCE {
                        nsBgpPeerIdentifier
                            IpAddress,
                        nsBgpPeerState
                            INTEGER,
                        nsBgpPeerAdminStatus
                            INTEGER,
                        nsBgpPeerNegotiatedVersion
                            Integer32,
                        nsBgpPeerLocalAddr
                            IpAddress,
                        nsBgpPeerLocalPort
                            INTEGER,
                        nsBgpPeerRemoteAddr
                            IpAddress,
                        nsBgpPeerRemotePort
                            INTEGER,
                        nsBgpPeerRemoteAs
                            INTEGER,
                        nsBgpPeerInUpdates
                            Counter32,
                        nsBgpPeerOutUpdates
                            Counter32,
                        nsBgpPeerInTotalMessages
                            Counter32,
                        nsBgpPeerOutTotalMessages
                            Counter32,
                        nsBgpPeerLastError
                            OCTET STRING,
                        nsBgpPeerFsmEstablishedTransitions
                            Counter32,
                        nsBgpPeerFsmEstablishedTime
                            Gauge32,
                        nsBgpPeerConnectRetryInterval
                            INTEGER,
                        nsBgpPeerHoldTime
                            INTEGER,
                        nsBgpPeerKeepAlive

                            INTEGER,
                        nsBgpPeerHoldTimeConfigured
                            INTEGER,
                        nsBgpPeerKeepAliveConfigured
                            INTEGER,
                        nsBgpPeerMinASOriginationInterval
                            INTEGER,
                        nsBgpPeerMinRouteAdvertisementInterval
                            INTEGER,
                        nsBgpPeerInUpdateElapsedTime
                            Gauge32,
                        nsBgpPeerVRID
                            INTEGER
                        }

                nsBgpPeerIdentifier OBJECT-TYPE
                    SYNTAX     IpAddress
                    MAX-ACCESS read-only
                    STATUS     deprecated
                    DESCRIPTION
                            "The BGP Identifier of this entry's BGP
                            peer."
                    ::= { nsBgpPeerEntry 1 }

                nsBgpPeerState OBJECT-TYPE
                    SYNTAX     INTEGER {
                                        idle(1),
                                        connect(2),
                                        active(3),
                                        opensent(4),
                                        openconfirm(5),
                                        established(6)
                               }
                    MAX-ACCESS read-only
                    STATUS     deprecated
                    DESCRIPTION
                            "The BGP peer connection state."
                    ::= { nsBgpPeerEntry 2 }

                nsBgpPeerAdminStatus OBJECT-TYPE
                    SYNTAX     INTEGER {
                                        stop(1),
                                        start(2)
                               }
                    MAX-ACCESS read-only
                    STATUS     deprecated
                    DESCRIPTION
                            "The desired state of the BGP connection.
                            A transition from 'stop' to 'start' will
                            cause the BGP Start Event to be generated.

                            A transition from 'start' to 'stop' will
                            cause the BGP Stop Event to be generated.
                            This parameter can be used to restart BGP
                            peer connections.  Care should be used in
                            providing write access to this object
                            without adequate authentication."
                    ::= { nsBgpPeerEntry 3 }

                nsBgpPeerNegotiatedVersion OBJECT-TYPE
                    SYNTAX     Integer32
                    MAX-ACCESS read-only
                    STATUS     deprecated
                    DESCRIPTION
                            "The negotiated version of BGP running
                            between the two peers."
                    ::= { nsBgpPeerEntry 4 }

                nsBgpPeerLocalAddr OBJECT-TYPE
                    SYNTAX     IpAddress
                    MAX-ACCESS read-only
                    STATUS     deprecated
                    DESCRIPTION
                            "The local IP address of this entry's BGP
                            connection."
                    ::= { nsBgpPeerEntry 5 }

                nsBgpPeerLocalPort OBJECT-TYPE
                    SYNTAX     INTEGER (0..65535)
                    MAX-ACCESS read-only
                    STATUS     deprecated
                    DESCRIPTION
                            "The local port for the TCP connection
                            between the BGP peers."
                    ::= { nsBgpPeerEntry 6 }

                nsBgpPeerRemoteAddr OBJECT-TYPE
                    SYNTAX     IpAddress
                    MAX-ACCESS read-only
                    STATUS     deprecated
                    DESCRIPTION
                            "The remote IP address of this entry's BGP
                            peer."
                    ::= { nsBgpPeerEntry 7 }

                nsBgpPeerRemotePort OBJECT-TYPE
                    SYNTAX     INTEGER (0..65535)
                    MAX-ACCESS read-only
                    STATUS     deprecated

                    DESCRIPTION
                            "The remote port for the TCP connection
                            between the BGP peers.  Note that the
                            objects nsBgpPeerLocalAddr,
                            nsBgpPeerLocalPort, nsBgpPeerRemoteAddr and
                            nsBgpPeerRemotePort provide the appropriate
                            reference to the standard MIB TCP
                            connection table."
                    ::= { nsBgpPeerEntry 8 }

                nsBgpPeerRemoteAs OBJECT-TYPE
                    SYNTAX     INTEGER (0..65535)
                    MAX-ACCESS read-only
                    STATUS     deprecated
                    DESCRIPTION
                            "The remote autonomous system number."
                    ::= { nsBgpPeerEntry 9 }

                nsBgpPeerInUpdates OBJECT-TYPE
                    SYNTAX     Counter32
                    MAX-ACCESS read-only
                    STATUS     deprecated
                    DESCRIPTION
                            "The number of BGP UPDATE messages
                            received on this connection.  This object
                            should be initialized to zero (0) when the
                            connection is established."
                    ::= { nsBgpPeerEntry 10 }

                nsBgpPeerOutUpdates OBJECT-TYPE
                    SYNTAX     Counter32
                    MAX-ACCESS read-only
                    STATUS     deprecated
                    DESCRIPTION
                            "The number of BGP UPDATE messages
                            transmitted on this connection.  This
                            object should be initialized to zero (0)
                            when the connection is established."
                    ::= { nsBgpPeerEntry 11 }

                nsBgpPeerInTotalMessages OBJECT-TYPE
                    SYNTAX     Counter32
                    MAX-ACCESS read-only
                    STATUS     deprecated
                    DESCRIPTION
                            "The total number of messages received
                            from the remote peer on this connection.
                            This object should be initialized to zero

                            when the connection is established."
                    ::= { nsBgpPeerEntry 12 }

                nsBgpPeerOutTotalMessages OBJECT-TYPE
                    SYNTAX     Counter32
                    MAX-ACCESS read-only
                    STATUS     deprecated
                    DESCRIPTION
                            "The total number of messages transmitted to
                            the remote peer on this connection.  This
                            object should be initialized to zero when
                            the connection is established."
                    ::= { nsBgpPeerEntry 13 }

                nsBgpPeerLastError OBJECT-TYPE
                    SYNTAX     OCTET STRING (SIZE (2))
                    MAX-ACCESS read-only
                    STATUS     deprecated
                    DESCRIPTION
                            "The last error code and subcode seen by this
                            peer on this connection.  If no error has
                            occurred, this field is zero.  Otherwise, the
                            first byte of this two byte OCTET STRING
                            contains the error code, and the second byte
                            contains the subcode."
                    ::= { nsBgpPeerEntry 14 }

                nsBgpPeerFsmEstablishedTransitions OBJECT-TYPE
                    SYNTAX     Counter32
                    MAX-ACCESS read-only
                    STATUS     deprecated
                    DESCRIPTION
                            "The total number of times the BGP FSM
                            transitioned into the established state."
                    ::= { nsBgpPeerEntry 15 }

                nsBgpPeerFsmEstablishedTime OBJECT-TYPE
                    SYNTAX     Gauge32
                    MAX-ACCESS read-only
                    STATUS     deprecated
                    DESCRIPTION
                            "This timer indicates how long (in
                            seconds) this peer has been in the
                            Established state or how long
                            since this peer was last in the
                            Established state.  It is set to zero when
                            a new peer is configured or the router is
                            booted."

                    ::= { nsBgpPeerEntry 16 }

                nsBgpPeerConnectRetryInterval OBJECT-TYPE
                    SYNTAX     INTEGER (1..65535)
                    MAX-ACCESS read-only
                    STATUS     deprecated
                    DESCRIPTION
                            "Time interval in seconds for the
                            ConnectRetry timer.  The suggested value
                            for this timer is 120 seconds."
                    ::= { nsBgpPeerEntry 17 }

                nsBgpPeerHoldTime OBJECT-TYPE
                    SYNTAX     INTEGER  ( 0 | 3..65535 )
                    MAX-ACCESS read-only
                    STATUS     deprecated
                    DESCRIPTION
                            "Time interval in seconds for the Hold
                            Timer established with the peer.  The
                            value of this object is calculated by this
                            BGP speaker by using the smaller of the
                            value in nsBgpPeerHoldTimeConfigured and the
                            Hold Time received in the OPEN message.
                            This value must be at lease three seconds
                            if it is not zero (0) in which case the
                            Hold Timer has not been established with
                            the peer, or, the value of
                            nsBgpPeerHoldTimeConfigured is zero (0)."
                    ::= { nsBgpPeerEntry 18 }

                nsBgpPeerKeepAlive OBJECT-TYPE
                    SYNTAX     INTEGER ( 0 | 1..21845 )
                    MAX-ACCESS read-only
                    STATUS     deprecated
                    DESCRIPTION
                            "Time interval in seconds for the KeepAlive
                            timer established with the peer.  The value
                            of this object is calculated by this BGP
                            speaker such that, when compared with
                            nsBgpPeerHoldTime, it has the same
                            proportion as what
                            nsBgpPeerKeepAliveConfigured has when
                            compared with nsBgpPeerHoldTimeConfigured.
                            If the value of this object is zero (0),
                            it indicates that the KeepAlive timer has
                            not been established with the peer, or,
                            the value of nsBgpPeerKeepAliveConfigured is
                            zero (0)."

                    ::= { nsBgpPeerEntry 19 }

                nsBgpPeerHoldTimeConfigured OBJECT-TYPE
                    SYNTAX     INTEGER ( 0 | 3..65535 )
                    MAX-ACCESS read-only
                    STATUS     deprecated
                    DESCRIPTION
                            "Time interval in seconds for the Hold Time
                            configured for this BGP speaker with this
                            peer.  This value is placed in an OPEN
                            message sent to this peer by this BGP
                            speaker, and is compared with the Hold
                            Time field in an OPEN message received
                            from the peer when determining the Hold
                            Time (nsBgpPeerHoldTime) with the peer.
                            This value must not be less than three
                            seconds if it is not zero (0) in which
                            case the Hold Time is NOT to be
                            established with the peer.  The suggested
                            value for this timer is 90 seconds."
                    ::= { nsBgpPeerEntry 20 }

                nsBgpPeerKeepAliveConfigured OBJECT-TYPE
                    SYNTAX     INTEGER ( 0 | 1..21845 )
                    MAX-ACCESS read-only
                    STATUS     deprecated
                    DESCRIPTION
                            "Time interval in seconds for the
                            KeepAlive timer configured for this BGP
                            speaker with this peer.  The value of this
                            object will only determine the
                            KEEPALIVE messages' frequency relative to
                            the value specified in
                            nsBgpPeerHoldTimeConfigured; the actual
                            time interval for the KEEPALIVE messages
                            is indicated by nsBgpPeerKeepAlive.  A
                            reasonable maximum value for this timer
                            would be configured to be one
                            third of that of
                            nsBgpPeerHoldTimeConfigured.
                            If the value of this object is zero (0),
                            no periodical KEEPALIVE messages are sent
                            to the peer after the BGP connection has
                            been established.  The suggested value for
                            this timer is 30 seconds."
                    ::= { nsBgpPeerEntry 21 }

                nsBgpPeerMinASOriginationInterval OBJECT-TYPE
                    SYNTAX     INTEGER (1..65535)
                    MAX-ACCESS read-only
                    STATUS     deprecated
                    DESCRIPTION
                            "Time interval in seconds for the
                            MinASOriginationInterval timer.
                            The suggested value for this timer is 15
                            seconds."
                    ::= { nsBgpPeerEntry 22 }

                nsBgpPeerMinRouteAdvertisementInterval OBJECT-TYPE
                    SYNTAX     INTEGER (1..65535)
                    MAX-ACCESS read-only
                    STATUS     deprecated
                    DESCRIPTION
                            "Time interval in seconds for the
                            MinRouteAdvertisementInterval timer.
                            The suggested value for this timer is 30
                            seconds."
                    ::= { nsBgpPeerEntry 23 }

                nsBgpPeerInUpdateElapsedTime OBJECT-TYPE
                    SYNTAX     Gauge32
                    MAX-ACCESS read-only
                    STATUS     deprecated
                    DESCRIPTION
                            "Elapsed time in seconds since the last BGP
                            UPDATE message was received from the peer.
                            Each time nsBgpPeerInUpdates is incremented,
                            the value of this object is set to zero
                            (0)."
                    ::= { nsBgpPeerEntry 24 }

                nsBgpPeerVRID OBJECT-TYPE
                    SYNTAX     INTEGER (0..65535)
                    MAX-ACCESS read-only
                    STATUS     deprecated
                    DESCRIPTION
                            "Virtual Router ID"
                    ::= { nsBgpPeerEntry 25 }


                -- BGP-4 Received Path Attribute Table.  This table
                -- contains, one entry per path to a network, path
                -- attributes received from all peers running BGP-4.

                nsBgp4PathAttrTable OBJECT-TYPE
                    SYNTAX     SEQUENCE OF NsBgp4PathAttrEntry
                    MAX-ACCESS not-accessible
                    STATUS     deprecated
                    DESCRIPTION
                            "The BGP-4 Received Path Attribute Table
                            contains information about paths to
                            destination networks received from all
                            BGP4 peers."
                    ::= { nsBgp 6 }

                nsBgp4PathAttrEntry OBJECT-TYPE
                    SYNTAX     NsBgp4PathAttrEntry
                    MAX-ACCESS not-accessible
                    STATUS     deprecated
                    DESCRIPTION
                            "Information about a path to a network."
                    INDEX { nsBgp4PathAttrIpAddrPrefix,
                            nsBgp4PathAttrIpAddrPrefixLen,
                            nsBgp4PathAttrPeer,
                            nsBgp4PathAttrVRID            }
                    ::= { nsBgp4PathAttrTable 1 }

                NsBgp4PathAttrEntry ::= SEQUENCE {
                    nsBgp4PathAttrPeer
                         IpAddress,
                    nsBgp4PathAttrIpAddrPrefixLen
                         INTEGER,
                    nsBgp4PathAttrIpAddrPrefix
                         IpAddress,
                    nsBgp4PathAttrOrigin
                         INTEGER,
                    nsBgp4PathAttrASPathSegment

                         OCTET STRING,
                    nsBgp4PathAttrNextHop
                         IpAddress,
                    nsBgp4PathAttrMultiExitDisc
                         INTEGER,
                    nsBgp4PathAttrLocalPref
                         INTEGER,
                    nsBgp4PathAttrAtomicAggregate
                         INTEGER,
                    nsBgp4PathAttrAggregatorAS
                         INTEGER,
                    nsBgp4PathAttrAggregatorAddr
                         IpAddress,
                    nsBgp4PathAttrCalcLocalPref
                         INTEGER,
                    nsBgp4PathAttrBest
                         INTEGER,
                    nsBgp4PathAttrUnknown
                         OCTET STRING,
                    nsBgp4PathAttrVRID
                         INTEGER

                }

                nsBgp4PathAttrPeer OBJECT-TYPE
                    SYNTAX     IpAddress
                    MAX-ACCESS read-only
                    STATUS     deprecated
                    DESCRIPTION
                            "The IP address of the peer where the path
                            information was learned."
                    ::= { nsBgp4PathAttrEntry 1 }

                nsBgp4PathAttrIpAddrPrefixLen OBJECT-TYPE
                    SYNTAX     INTEGER (0..32)
                    MAX-ACCESS read-only
                    STATUS     deprecated
                    DESCRIPTION
                            "Length in bits of the IP address prefix
                            in the Network Layer Reachability
                            Information field."
                    ::= { nsBgp4PathAttrEntry 2 }

                nsBgp4PathAttrIpAddrPrefix OBJECT-TYPE
                    SYNTAX     IpAddress
                    MAX-ACCESS read-only
                    STATUS     deprecated
                    DESCRIPTION
                            "An IP address prefix in the Network Layer
                            Reachability Information field.  This object

                            is an IP address containing the prefix with
                            length specified by
                            nsBgp4PathAttrIpAddrPrefixLen.
                            Any bits beyond the length specified by
                            nsBgp4PathAttrIpAddrPrefixLen are zeroed."
                    ::= { nsBgp4PathAttrEntry 3 }

                nsBgp4PathAttrOrigin OBJECT-TYPE
                    SYNTAX     INTEGER {
                                         igp(1),-- networks are interior
                                         egp(2),-- networks learned
                                                -- via EGP
                                         incomplete(3) -- undetermined
                                       }
                    MAX-ACCESS read-only
                    STATUS     deprecated
                    DESCRIPTION
                            "The ultimate origin of the path
                            information."
                    ::= { nsBgp4PathAttrEntry 4 }

                nsBgp4PathAttrASPathSegment OBJECT-TYPE
                    SYNTAX     OCTET STRING (SIZE (2..255))
                    MAX-ACCESS read-only
                    STATUS     deprecated
                    DESCRIPTION
                            "The sequence of AS path segments.  Each AS
                            path segment is represented by a triple
                            <type, length, value>.

                            The type is a 1-octet field which has two
                            possible values:
                                 1      AS_SET: unordered set of ASs a
                                             route in the UPDATE
                                             message has traversed
                                 2      AS_SEQUENCE: ordered set of ASs
                                             a route in the UPDATE
                                             message has traversed.

                            The length is a 1-octet field containing the
                            number of ASs in the value field.

                            The value field contains one or more AS
                            numbers, each AS is represented in the octet
                            string as a pair of octets according to the
                            following algorithm:

                                first-byte-of-pair = ASNumber / 256;
                                second-byte-of-pair = ASNumber & 255;"
                    ::= { nsBgp4PathAttrEntry 5 }

                nsBgp4PathAttrNextHop OBJECT-TYPE
                    SYNTAX     IpAddress
                    MAX-ACCESS read-only
                    STATUS     deprecated
                    DESCRIPTION
                            "The address of the border router that
                            should be used for the destination
                            network."
                    ::= { nsBgp4PathAttrEntry 6 }

                nsBgp4PathAttrMultiExitDisc OBJECT-TYPE
                    SYNTAX     INTEGER (-1..2147483647)
                    MAX-ACCESS read-only
                    STATUS     deprecated
                    DESCRIPTION
                            "This metric is used to discriminate
                            between multiple exit points to an
                            adjacent autonomous system.  A value of -1
                            indicates the absence of this attribute."
                    ::= { nsBgp4PathAttrEntry 7 }

                nsBgp4PathAttrLocalPref OBJECT-TYPE
                    SYNTAX     INTEGER (-1..2147483647)
                    MAX-ACCESS read-only
                    STATUS     deprecated
                    DESCRIPTION
                            "The originating BGP4 speaker's degree of
                            preference for an advertised route.  A
                            value of -1 indicates the absence of this
                            attribute."
                    ::= { nsBgp4PathAttrEntry 8 }

                nsBgp4PathAttrAtomicAggregate OBJECT-TYPE
                    SYNTAX     INTEGER {
                                   lessSpecificRrouteNotSelected(1),
                                   lessSpecificRouteSelected(2)
                               }
                    MAX-ACCESS read-only
                    STATUS     deprecated
                    DESCRIPTION
                            "Whether or not the local system has
                            selected a less specific route without
                            selecting a more specific route."
                    ::= { nsBgp4PathAttrEntry 9 }

                nsBgp4PathAttrAggregatorAS OBJECT-TYPE
                    SYNTAX     INTEGER (0..65535)
                    MAX-ACCESS read-only
                    STATUS     deprecated
                    DESCRIPTION
                            "The AS number of the last BGP4 speaker that
                            performed route aggregation.  A value of
                            zero (0) indicates the absence of this
                            attribute."
                    ::= { nsBgp4PathAttrEntry 10 }

                nsBgp4PathAttrAggregatorAddr OBJECT-TYPE
                    SYNTAX     IpAddress
                    MAX-ACCESS read-only
                    STATUS     deprecated
                    DESCRIPTION
                            "The IP address of the last BGP4 speaker
                            that performed route aggregation.  A value
                            of 0.0.0.0 indicates the absence of this
                            attribute."
                    ::= { nsBgp4PathAttrEntry 11 }

                nsBgp4PathAttrCalcLocalPref OBJECT-TYPE
                    SYNTAX     INTEGER (-1..2147483647)
                    MAX-ACCESS read-only
                    STATUS     deprecated
                    DESCRIPTION
                            "The degree of preference calculated by the
                            receiving BGP4 speaker for an advertised
                            route.  A value of -1 indicates the
                            absence of this attribute."
                    ::= { nsBgp4PathAttrEntry 12 }

                nsBgp4PathAttrBest OBJECT-TYPE
                    SYNTAX     INTEGER {
                                   false(1),-- not chosen as best route
                                   true(2) -- chosen as best route
                               }
                    MAX-ACCESS read-only
                    STATUS     deprecated
                    DESCRIPTION
                            "An indication of whether or not this route
                            was chosen as the best BGP4 route."
                    ::= { nsBgp4PathAttrEntry 13 }

               nsBgp4PathAttrUnknown OBJECT-TYPE
                    SYNTAX     OCTET STRING (SIZE(0..255))
                    MAX-ACCESS read-only

                    STATUS     deprecated
                    DESCRIPTION
                            "One or more path attributes not understood
                             by this BGP4 speaker.  Size zero (0)
                             indicates the absence of such
                             attribute(s).  Octets beyond the maximum
                             size, if any, are not recorded by this
                             object."
                    ::= { nsBgp4PathAttrEntry 14 }

                nsBgp4PathAttrVRID OBJECT-TYPE
                    SYNTAX     INTEGER (0..65535)
                    MAX-ACCESS read-only
                    STATUS     deprecated
                    DESCRIPTION
                            "Virtual Router ID"
                    ::= { nsBgp4PathAttrEntry 15 }

                -- Traps.

                nsBgpTraps                OBJECT IDENTIFIER ::= { nsBgp 7 }

                nsBgpEstablished NOTIFICATION-TYPE
                    OBJECTS { netscreenTrapType,
                              netscreenTrapDesc,
                              nsBgpPeerIdentifier,
                              nsBgpPeerVRID,
                              nsBgpPeerLastError,
                              nsBgpPeerState      }
                    STATUS  deprecated
                    DESCRIPTION
                            "The BGP Established event is generated when
                            the BGP FSM enters the ESTABLISHED state."
                    ::= { nsBgpTraps 1 }


END
