--  ============================================================================
-- AT-HHM-MIB, Allied Telesis enterprise MIB:
-- Hardware Health Monitoring
--
-- Copyright (c) 2013 by Allied Telesis, Inc.
-- All rights reserved.
--
-- ============================================================================

    AT-HHM-MIB DEFINITIONS ::= BEGIN

        IMPORTS
            DisplayStringUnsized
                FROM AT-SMI-MIB
            sysinfo
                FROM AT-SYSINFO-MIB
            OBJECT-TYPE, MODULE-IDENTITY, NOTIFICATION-TYPE
                FROM SNMPv2-SMI;


        atHwHealthMon MODULE-IDENTITY
            LAST-UPDATED "201306280000Z"
            ORGANIZATION
                "Allied Telesis, Inc"
            CONTACT-INFO
                "http://www.alliedtelesis.com"
            DESCRIPTION
                "The AT Hardware Health Monitoring MIB."
            REVISION "201306280000Z"
            DESCRIPTION
                "Initial Revision"
            ::= { sysinfo 24 }


        atHhmNotifications OBJECT IDENTIFIER ::= { atHwHealthMon 0 }

        atHhmLogNotify NOTIFICATION-TYPE
            OBJECTS { atHhmLogMessage }
            STATUS current
            DESCRIPTION
                "A notification generated when Hardware Health Monitoring
                generates a new log message."
            ::= { atHhmNotifications 1 }


        atHhmNotificationVariables OBJECT IDENTIFIER ::= { atHwHealthMon 1 }

        atHhmLogMessage OBJECT-TYPE
            SYNTAX DisplayStringUnsized (SIZE (0..200))
            MAX-ACCESS accessible-for-notify
            STATUS current
            DESCRIPTION
                "The most recent log message generated by Hardware Health
                Monitoring."
            ::= { atHhmNotificationVariables 1 }

    END

--
-- at-hhm.mib
--
