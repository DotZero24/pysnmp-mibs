EATON-EPDU-PU-MI-MIB DEFINITIONS ::= BEGIN


IMPORTS
	OBJECT-TYPE, MODULE-IDENTITY, enterprises,
	IpAddress, Integer32, TimeTicks
		FROM SNMPv2-SMI
	OBJECT-GROUP, MODULE-COMPLIANCE
		FROM SNMPv2-CONF;

pulizzi MODULE-IDENTITY
	LAST-UPDATED "201002031200Z"
	ORGANIZATION
		"Eaton Corporation"
	CONTACT-INFO
		"Eaton Corporation
            Technical Resource Center phone numbers
            United States:  1.800.843.9433 or 919.870.3028
            Canada:  1.800.461.9166 ext. 260
            All other countries:  Call your local service representative."
	DESCRIPTION
	"The MIB module for Eaton Monitored ePDUs (Enclosed Power Distribution Units)
	 with blue local display."

	REVISION "201002031200Z"
	DESCRIPTION
		"
		Added additional monitoring types for the currentMonitorType object.
		"

	REVISION "200901081200Z"
	DESCRIPTION
		"
		Updated the units for tempChan1 and tempChan2 objects to Degrees Fahrenheit.
		"

	REVISION "200812191200Z"
	DESCRIPTION
		"
		 Updated to fix syntax errors:
		   - Changed temperature1Enable and temperature2Enable enums from 'Enable' to 'enable'
		     and 'Disable' to 'disable'
		   - Renamed lowCurrentThreshold and highCurrentThreshold objects within unitConfig
		     by appending 'old' to their names
		   - Added conformance groups
		   - Filled in descriptions for all variables
		   - monitoredepdu was previously defined as { pulizzi 3 1 1 }
		     this was changed so that monitoredepdu is {pulizzi 3 }
		                              epdum1 is { monitoredepdu 1 }
		                              epdum11 is { epdum1 1 }
		     All the main branches (unitConfig, networkSettings, etc.) are now under epdum11
		     rather than directly under the monitoredpdu definition as it was defined before
		"

	REVISION "200811061200Z"
	DESCRIPTION
		"
		 ADDED A FOURTH ENUMERATED OPTION 'phaseCurrent (4)' TO currentMonitorType
		"

	REVISION "200808251200Z"
	DESCRIPTION
		"
		 CHANGED DATA TYPE OF temperature1Enable AND temperature2Enable
		    FROM OCTET STRING TO INTEGER; THIS CHANGE ONLY WORKS WITH
		 FIRMWARE VERSION 1.0.F AND HIGHER
		"

	REVISION "200807091200Z"
	DESCRIPTION
		"
		 RENAMED icm2483c TO monitoredepdu
		    ADDED chanNames WHICH CONTAINS OBJECTS FOR 32 CURRENT CHANNELS
		      AND 2 TEMPERATURE CHANNELS
		    MOVED ACTIVE lowCurrentThreshold OBJECTS FROM unitConfig TO A
		      NEW lowCurrentThresh TREE STRUCTURE
		    MOVED ACTIVE highCurrentThreshold OBJECTS FROM unitConfig TO A
		      NEW highCurrentThresh TREE STRUCTURE
		    ADDED NEW TREE LEVELS FOR lowTempThresh AND highTempThresh
		    CHANGED UNITS FOR MEASUREMENTS FROM '1 AMP' TO '0.1 AMP'
		    ADDED assetID & numCurrentChannels UNDER unitConfig
		"
::= { enterprises 20677 }

monitoredepdu        OBJECT IDENTIFIER ::= { pulizzi 3 }
epdum1               OBJECT IDENTIFIER ::= { monitoredepdu 1 }
epdum11              OBJECT IDENTIFIER ::= { epdum1 1 }
unitConfig           OBJECT IDENTIFIER ::= { epdum11 1 }
networkSettings      OBJECT IDENTIFIER ::= { epdum11 2 }
measurements         OBJECT IDENTIFIER ::= { epdum11 3 }
chanNames            OBJECT IDENTIFIER ::= { epdum11 4 }
lowCurrentThresh     OBJECT IDENTIFIER ::= { epdum11 5 }
highCurrentThresh    OBJECT IDENTIFIER ::= { epdum11 6 }
lowTempThresh        OBJECT IDENTIFIER ::= { epdum11 7 }
highTempThresh       OBJECT IDENTIFIER ::= { epdum11 8 }
conformance          OBJECT IDENTIFIER ::= { epdum11 25 }
groups               OBJECT IDENTIFIER ::= { conformance 5 }

uptime  OBJECT-TYPE
	SYNTAX     TimeTicks
	MAX-ACCESS read-only
	STATUS     current
	DESCRIPTION
		"Up-time since last power cycle or reboot.  Note that some setting changes will cause an automatic reboot."
	::= { unitConfig 1 }

unitName  OBJECT-TYPE
	SYNTAX     OCTET STRING (SIZE(1..19))
	MAX-ACCESS read-write
	STATUS     current
	DESCRIPTION
		"Unit Name"
	::= { unitConfig 2 }

lowCurrentThreshold1old  OBJECT-TYPE
	SYNTAX     Integer32
	UNITS 	"Amps"
	MAX-ACCESS read-write
	STATUS     deprecated
	DESCRIPTION
		"Low current threshold channel-1.  Firmware 1.0.F and greater no longer support this object."
	::= { unitConfig 3 }

lowCurrentThreshold2old  OBJECT-TYPE
	SYNTAX     Integer32
	UNITS 	"Amps"
	MAX-ACCESS read-write
	STATUS     deprecated
	DESCRIPTION
		"Low current threshold channel-2.  Firmware 1.0.F and greater no longer support this object."
	::= { unitConfig 4 }

lowCurrentThreshold3old  OBJECT-TYPE
	SYNTAX     Integer32
	UNITS 	"Amps"
	MAX-ACCESS read-write
	STATUS     deprecated
	DESCRIPTION
		"Low current threshold channel-3.  Firmware 1.0.F and greater no longer support this object."
	::= { unitConfig 5 }

lowCurrentThreshold4old  OBJECT-TYPE
	SYNTAX     Integer32
	UNITS 	"Amps"
	MAX-ACCESS read-write
	STATUS     deprecated
	DESCRIPTION
		"Low current threshold channel-4.  Firmware 1.0.F and greater no longer support this object."
	::= { unitConfig 6 }

lowCurrentThreshold5old  OBJECT-TYPE
	SYNTAX     Integer32
	UNITS 	"Amps"
	MAX-ACCESS read-write
	STATUS     deprecated
	DESCRIPTION
		"Low current threshold channel-5.  Firmware 1.0.F and greater no longer support this object."
	::= { unitConfig 7 }

lowCurrentThreshold6old  OBJECT-TYPE
	SYNTAX     Integer32
	UNITS 	"Amps"
	MAX-ACCESS read-write
	STATUS     deprecated
	DESCRIPTION
		"Low current threshold channel-6.  Firmware 1.0.F and greater no longer support this object."
	::= { unitConfig 8 }

lowCurrentThreshold7old  OBJECT-TYPE
	SYNTAX     Integer32
	UNITS 	"Amps or Degrees Farenheit"
	MAX-ACCESS read-write
	STATUS     deprecated
	DESCRIPTION
		"Low current threshold channel-7.  Firmware 1.0.F and greater no longer support this object."
	::= { unitConfig 9 }

lowCurrentThreshold8old  OBJECT-TYPE
	SYNTAX     Integer32
	UNITS 	"Amps or Degrees Farenheit"
	MAX-ACCESS read-write
	STATUS     deprecated
	DESCRIPTION
		"Low current threshold channel-8.  Firmware 1.0.F and greater no longer support this object."
	::= { unitConfig 10 }

highCurrentThreshold1old  OBJECT-TYPE
	SYNTAX     Integer32
	UNITS 	"Amps"
	MAX-ACCESS read-write
	STATUS     deprecated
	DESCRIPTION
		"High current threshold channel-1.  Firmware 1.0.F and greater no longer support this object."
	::= { unitConfig 11 }

highCurrentThreshold2old  OBJECT-TYPE
	SYNTAX     Integer32
	UNITS 	"Amps"
	MAX-ACCESS read-write
	STATUS     deprecated
	DESCRIPTION
		"High current threshold channel-2.  Firmware 1.0.F and greater no longer support this object."
	::= { unitConfig 12 }

highCurrentThreshold3old  OBJECT-TYPE
	SYNTAX     Integer32
	UNITS 	"Amps"
	MAX-ACCESS read-write
	STATUS     deprecated
	DESCRIPTION
		"High current threshold channel-3.  Firmware 1.0.F and greater no longer support this object."
	::= { unitConfig 13 }

highCurrentThreshold4old  OBJECT-TYPE
	SYNTAX     Integer32
	UNITS 	"Amps"
	MAX-ACCESS read-write
	STATUS     deprecated
	DESCRIPTION
		"High current threshold channel-4.  Firmware 1.0.F and greater no longer support this object."
	::= { unitConfig 14 }

highCurrentThreshold5old  OBJECT-TYPE
	SYNTAX     Integer32
	UNITS 	"Amps"
	MAX-ACCESS read-write
	STATUS     deprecated
	DESCRIPTION
		"High current threshold channel-5.  Firmware 1.0.F and greater no longer support this object."
	::= { unitConfig 15 }

highCurrentThreshold6old  OBJECT-TYPE
	SYNTAX     Integer32
	UNITS 	"Amps"
	MAX-ACCESS read-write
	STATUS     deprecated
	DESCRIPTION
		"High current threshold channel-6.  Firmware 1.0.F and greater no longer support this object."
	::= { unitConfig 16 }

highCurrentThreshold7old  OBJECT-TYPE
	SYNTAX     Integer32
	UNITS 	"Amps or Degrees Farenheit"
	MAX-ACCESS read-write
	STATUS     deprecated
	DESCRIPTION
		"High current threshold channel-7.  Firmware 1.0.F and greater no longer support this object."
	::= { unitConfig 17 }

highCurrentThreshold8old  OBJECT-TYPE
	SYNTAX     Integer32
	UNITS 	"Amps or Degrees Farenheit"
	MAX-ACCESS read-write
	STATUS     deprecated
	DESCRIPTION
		"High current threshold channel-8.  Firmware 1.0.F and greater no longer support this object."
	::= { unitConfig 18 }

temperature1Enable  OBJECT-TYPE
	SYNTAX     INTEGER {
		disabled (0),
		enabled (1)
	}
	MAX-ACCESS read-write
	STATUS     current
	DESCRIPTION
		"Enables the Temperature 1 sensor value display on the web page."
	::= { unitConfig 19 }

temperature2Enable  OBJECT-TYPE
	SYNTAX     INTEGER {
		disabled (0),
		enabled (1)
	}
	MAX-ACCESS read-write
	STATUS     current
	DESCRIPTION
		"Enables the Temperature 2 sensor value display on the web page."
	::= { unitConfig 20 }

firmwareRevision  OBJECT-TYPE
	SYNTAX     OCTET STRING
	MAX-ACCESS read-only
	STATUS     current
	DESCRIPTION
		"Firmware version."
	::= { unitConfig 21 }

assetID  OBJECT-TYPE
	SYNTAX     OCTET STRING (SIZE(0..19))
	MAX-ACCESS read-write
	STATUS     current
	DESCRIPTION
		"Asset ID"
	::= { unitConfig 22 }

numCurrentChannels  OBJECT-TYPE
	SYNTAX     Integer32
	MAX-ACCESS read-only
	STATUS     current
	DESCRIPTION
		"Number of active current measurement channels on this ePDU."
	::= { unitConfig 23 }

currentMonitorType  OBJECT-TYPE
	SYNTAX     INTEGER {
		totalUnitCurrent (1),
		branchCurrent (2),
		outletCurrent (3),
		threePhaseCurrent (4),
		splitPhaseCurrent (5),
		singlePhaseWithBranch (6),
		threePhaseWithBranch (7),
		splitPhaseWithBranch (8)
	}
	MAX-ACCESS read-only
	STATUS     current
	DESCRIPTION
		"Type of current monitoring: total unit current, branch current,
      individual outlet current, three-phase current, split-phase current,
      single-phase + two branches, three-phase + three branches, or
      split-phase + two branches."
	::= { unitConfig 24 }

unitIPAddress  OBJECT-TYPE
	SYNTAX     IpAddress
	MAX-ACCESS read-write
	STATUS     current
	DESCRIPTION
		"Network IP address"
	::= { networkSettings 1 }

unitSubnetMask  OBJECT-TYPE
	SYNTAX     IpAddress
	MAX-ACCESS read-write
	STATUS     current
	DESCRIPTION
		"Network Subnet Mask"
	::= { networkSettings 2 }

unitGateway  OBJECT-TYPE
	SYNTAX     IpAddress
	MAX-ACCESS read-write
	STATUS     current
	DESCRIPTION
		"Network Default Gateway"
	::= { networkSettings 3 }

unitMACAddress  OBJECT-TYPE
	SYNTAX     OCTET STRING
	MAX-ACCESS read-only
	STATUS     current
	DESCRIPTION
		"Network MAC address"
	::= { networkSettings 4 }

trapDestIP  OBJECT-TYPE
	SYNTAX     IpAddress
	MAX-ACCESS read-write
	STATUS     current
	DESCRIPTION
		"SNMP Trap Send-to IP Address"
	::= { networkSettings 5 }

mailServerIP  OBJECT-TYPE
	SYNTAX     IpAddress
	MAX-ACCESS read-write
	STATUS     current
	DESCRIPTION
		"IP address of mail server.  This is used to send email alerts for threshold events."
	::= { networkSettings 6 }

alertEmailAddress  OBJECT-TYPE
	SYNTAX     OCTET STRING (SIZE(1..49))
	MAX-ACCESS read-write
	STATUS     current
	DESCRIPTION
		"Email address to which to send alerts for threshold events."
	::= { networkSettings 7 }

chan1  OBJECT-TYPE
	SYNTAX     Integer32
	UNITS 	"0.1 Amps RMS"
	MAX-ACCESS read-only
	STATUS     current
	DESCRIPTION
		"Current Measurement channel 1, 0.1 Amps RMS.  A value of 57 means 5.7A."
	::= { measurements 1 }

chan2  OBJECT-TYPE
	SYNTAX     Integer32
	UNITS 	"0.1 Amps RMS"
	MAX-ACCESS read-only
	STATUS     current
	DESCRIPTION
		"Current Measurement channel 2, 0.1 Amps RMS.  A value of 57 means 5.7A."
	::= { measurements 2 }

chan3  OBJECT-TYPE
	SYNTAX     Integer32
	UNITS 	"0.1 Amps RMS"
	MAX-ACCESS read-only
	STATUS     current
	DESCRIPTION
		"Current Measurement channel 3, 0.1 Amps RMS.  A value of 57 means 5.7A."
	::= { measurements 3 }

chan4  OBJECT-TYPE
	SYNTAX     Integer32
	UNITS 	"0.1 Amps RMS"
	MAX-ACCESS read-only
	STATUS     current
	DESCRIPTION
		"Current Measurement channel 4, 0.1 Amps RMS.  A value of 57 means 5.7A."
	::= { measurements 4 }

chan5  OBJECT-TYPE
	SYNTAX     Integer32
	UNITS 	"0.1 Amps RMS"
	MAX-ACCESS read-only
	STATUS     current
	DESCRIPTION
		"Current Measurement channel 5, 0.1 Amps RMS.  A value of 57 means 5.7A."
	::= { measurements 5 }

chan6  OBJECT-TYPE
	SYNTAX     Integer32
	UNITS 	"0.1 Amps RMS"
	MAX-ACCESS read-only
	STATUS     current
	DESCRIPTION
		"Current Measurement channel 6, 0.1 Amps RMS.  A value of 57 means 5.7A."
	::= { measurements 6 }

chan7  OBJECT-TYPE
	SYNTAX     Integer32
	UNITS 	"0.1 Amps RMS"
	MAX-ACCESS read-only
	STATUS     current
	DESCRIPTION
		"Current Measurement channel 7, 0.1 Amps RMS.  A value of 57 means 5.7A."
	::= { measurements 7 }

chan8  OBJECT-TYPE
	SYNTAX     Integer32
	UNITS 	"0.1 Amps RMS"
	MAX-ACCESS read-only
	STATUS     current
	DESCRIPTION
		"Current Measurement channel 8, 0.1 Amps RMS.  A value of 57 means 5.7A."
	::= { measurements 8 }

chan9  OBJECT-TYPE
	SYNTAX     Integer32
	UNITS 	"0.1 Amps RMS"
	MAX-ACCESS read-only
	STATUS     current
	DESCRIPTION
		"Current Measurement channel 9, 0.1 Amps RMS.  A value of 57 means 5.7A."
	::= { measurements 9 }

chan10  OBJECT-TYPE
	SYNTAX     Integer32
	UNITS 	"0.1 Amps RMS"
	MAX-ACCESS read-only
	STATUS     current
	DESCRIPTION
		"Current Measurement channel 10, 0.1 Amps RMS.  A value of 57 means 5.7A."
	::= { measurements 10 }

chan11  OBJECT-TYPE
	SYNTAX     Integer32
	UNITS 	"0.1 Amps RMS"
	MAX-ACCESS read-only
	STATUS     current
	DESCRIPTION
		"Current Measurement channel 11, 0.1 Amps RMS.  A value of 57 means 5.7A."
	::= { measurements 11 }

chan12  OBJECT-TYPE
	SYNTAX     Integer32
	UNITS 	"0.1 Amps RMS"
	MAX-ACCESS read-only
	STATUS     current
	DESCRIPTION
		"Current Measurement channel 12, 0.1 Amps RMS.  A value of 57 means 5.7A."
	::= { measurements 12 }

chan13  OBJECT-TYPE
	SYNTAX     Integer32
	UNITS 	"0.1 Amps RMS"
	MAX-ACCESS read-only
	STATUS     current
	DESCRIPTION
		"Current Measurement channel 13, 0.1 Amps RMS.  A value of 57 means 5.7A."
	::= { measurements 13 }

chan14  OBJECT-TYPE
	SYNTAX     Integer32
	UNITS 	"0.1 Amps RMS"
	MAX-ACCESS read-only
	STATUS     current
	DESCRIPTION
		"Current Measurement channel 14, 0.1 Amps RMS.  A value of 57 means 5.7A."
	::= { measurements 14 }

chan15  OBJECT-TYPE
	SYNTAX     Integer32
	UNITS 	"0.1 Amps RMS"
	MAX-ACCESS read-only
	STATUS     current
	DESCRIPTION
		"Current Measurement channel 15, 0.1 Amps RMS.  A value of 57 means 5.7A."
	::= { measurements 15 }

chan16  OBJECT-TYPE
	SYNTAX     Integer32
	UNITS 	"0.1 Amps RMS"
	MAX-ACCESS read-only
	STATUS     current
	DESCRIPTION
		"Current Measurement channel 16, 0.1 Amps RMS.  A value of 57 means 5.7A."
	::= { measurements 16 }

chan17  OBJECT-TYPE
	SYNTAX     Integer32
	UNITS 	"0.1 Amps RMS"
	MAX-ACCESS read-only
	STATUS     current
	DESCRIPTION
		"Current Measurement channel 17, 0.1 Amps RMS.  A value of 57 means 5.7A."
	::= { measurements 17 }

chan18  OBJECT-TYPE
	SYNTAX     Integer32
	UNITS 	"0.1 Amps RMS"
	MAX-ACCESS read-only
	STATUS     current
	DESCRIPTION
		"Current Measurement channel 18, 0.1 Amps RMS.  A value of 57 means 5.7A."
	::= { measurements 18 }

chan19  OBJECT-TYPE
	SYNTAX     Integer32
	UNITS 	"0.1 Amps RMS"
	MAX-ACCESS read-only
	STATUS     current
	DESCRIPTION
		"Current Measurement channel 19, 0.1 Amps RMS.  A value of 57 means 5.7A."
	::= { measurements 19 }

chan20  OBJECT-TYPE
	SYNTAX     Integer32
	UNITS 	"0.1 Amps RMS"
	MAX-ACCESS read-only
	STATUS     current
	DESCRIPTION
		"Current Measurement channel 20, 0.1 Amps RMS.  A value of 57 means 5.7A."
	::= { measurements 20 }

chan21  OBJECT-TYPE
	SYNTAX     Integer32
	UNITS 	"0.1 Amps RMS"
	MAX-ACCESS read-only
	STATUS     current
	DESCRIPTION
		"Current Measurement channel 21, 0.1 Amps RMS.  A value of 57 means 5.7A."
	::= { measurements 21 }

chan22  OBJECT-TYPE
	SYNTAX     Integer32
	UNITS 	"0.1 Amps RMS"
	MAX-ACCESS read-only
	STATUS     current
	DESCRIPTION
		"Current Measurement channel 22, 0.1 Amps RMS.  A value of 57 means 5.7A."
	::= { measurements 22 }

chan23  OBJECT-TYPE
	SYNTAX     Integer32
	UNITS 	"0.1 Amps RMS"
	MAX-ACCESS read-only
	STATUS     current
	DESCRIPTION
		"Current Measurement channel 23, 0.1 Amps RMS.  A value of 57 means 5.7A."
	::= { measurements 23 }

chan24  OBJECT-TYPE
	SYNTAX     Integer32
	UNITS 	"0.1 Amps RMS"
	MAX-ACCESS read-only
	STATUS     current
	DESCRIPTION
		"Current Measurement channel 24, 0.1 Amps RMS.  A value of 57 means 5.7A."
	::= { measurements 24 }

chan25  OBJECT-TYPE
	SYNTAX     Integer32
	UNITS 	"0.1 Amps RMS"
	MAX-ACCESS read-only
	STATUS     current
	DESCRIPTION
		"Current Measurement channel 25, 0.1 Amps RMS.  A value of 57 means 5.7A."
	::= { measurements 25 }

chan26  OBJECT-TYPE
	SYNTAX     Integer32
	UNITS 	"0.1 Amps RMS"
	MAX-ACCESS read-only
	STATUS     current
	DESCRIPTION
		"Current Measurement channel 26, 0.1 Amps RMS.  A value of 57 means 5.7A."
	::= { measurements 26 }

chan27  OBJECT-TYPE
	SYNTAX     Integer32
	UNITS 	"0.1 Amps RMS"
	MAX-ACCESS read-only
	STATUS     current
	DESCRIPTION
		"Current Measurement channel 27, 0.1 Amps RMS.  A value of 57 means 5.7A."
	::= { measurements 27 }

chan28  OBJECT-TYPE
	SYNTAX     Integer32
	UNITS 	"0.1 Amps RMS"
	MAX-ACCESS read-only
	STATUS     current
	DESCRIPTION
		"Current Measurement channel 28, 0.1 Amps RMS.  A value of 57 means 5.7A."
	::= { measurements 28 }

chan29  OBJECT-TYPE
	SYNTAX     Integer32
	UNITS 	"0.1 Amps RMS"
	MAX-ACCESS read-only
	STATUS     current
	DESCRIPTION
		"Current Measurement channel 29, 0.1 Amps RMS.  A value of 57 means 5.7A."
	::= { measurements 29 }

chan30  OBJECT-TYPE
	SYNTAX     Integer32
	UNITS 	"0.1 Amps RMS"
	MAX-ACCESS read-only
	STATUS     current
	DESCRIPTION
		"Current Measurement channel 30, 0.1 Amps RMS.  A value of 57 means 5.7A."
	::= { measurements 30 }

chan31  OBJECT-TYPE
	SYNTAX     Integer32
	UNITS 	"0.1 Amps RMS"
	MAX-ACCESS read-only
	STATUS     current
	DESCRIPTION
		"Current Measurement channel 31, 0.1 Amps RMS.  A value of 57 means 5.7A."
	::= { measurements 31 }

chan32  OBJECT-TYPE
	SYNTAX     Integer32
	UNITS 	"0.1 Amps RMS"
	MAX-ACCESS read-only
	STATUS     current
	DESCRIPTION
		"Current Measurement channel 32, 0.1 Amps RMS.  A value of 57 means 5.7A."
	::= { measurements 32 }

tempChan1  OBJECT-TYPE
	SYNTAX     Integer32
	UNITS 	"Degrees Fahrenheit"
	MAX-ACCESS read-only
	STATUS     current
	DESCRIPTION
		"Temperature 1 Measurement"
	::= { measurements 248 }

tempChan2  OBJECT-TYPE
	SYNTAX     Integer32
	UNITS 	"Degrees Fahrenheit"
	MAX-ACCESS read-only
	STATUS     current
	DESCRIPTION
		"Temperature 2 Measurement"
	::= { measurements 249 }

chan1Name  OBJECT-TYPE
	SYNTAX     OCTET STRING (SIZE(1..31))
	MAX-ACCESS read-write
	STATUS     current
	DESCRIPTION
		"Current measurement channel 1 name"
	::= { chanNames 1 }

chan2Name  OBJECT-TYPE
	SYNTAX     OCTET STRING (SIZE(1..31))
	MAX-ACCESS read-write
	STATUS     current
	DESCRIPTION
		"Current measurement channel 2 name"
	::= { chanNames 2 }

chan3Name  OBJECT-TYPE
	SYNTAX     OCTET STRING (SIZE(1..31))
	MAX-ACCESS read-write
	STATUS     current
	DESCRIPTION
		"Current measurement channel 3 name"
	::= { chanNames 3 }

chan4Name  OBJECT-TYPE
	SYNTAX     OCTET STRING (SIZE(1..31))
	MAX-ACCESS read-write
	STATUS     current
	DESCRIPTION
		"Current measurement channel 4 name"
	::= { chanNames 4 }

chan5Name  OBJECT-TYPE
	SYNTAX     OCTET STRING (SIZE(1..31))
	MAX-ACCESS read-write
	STATUS     current
	DESCRIPTION
		"Current measurement channel 5 name"
	::= { chanNames 5 }

chan6Name  OBJECT-TYPE
	SYNTAX     OCTET STRING (SIZE(1..31))
	MAX-ACCESS read-write
	STATUS     current
	DESCRIPTION
		"Current measurement channel 6 name"
	::= { chanNames 6 }

chan7Name  OBJECT-TYPE
	SYNTAX     OCTET STRING (SIZE(1..31))
	MAX-ACCESS read-write
	STATUS     current
	DESCRIPTION
		"Current measurement channel 7 name"
	::= { chanNames 7 }

chan8Name  OBJECT-TYPE
	SYNTAX     OCTET STRING (SIZE(1..31))
	MAX-ACCESS read-write
	STATUS     current
	DESCRIPTION
		"Current measurement channel 8 name"
	::= { chanNames 8 }

chan9Name  OBJECT-TYPE
	SYNTAX     OCTET STRING (SIZE(1..31))
	MAX-ACCESS read-write
	STATUS     current
	DESCRIPTION
		"Current measurement channel 9 name"
	::= { chanNames 9 }

chan10Name  OBJECT-TYPE
	SYNTAX     OCTET STRING (SIZE(1..31))
	MAX-ACCESS read-write
	STATUS     current
	DESCRIPTION
		"Current measurement channel 10 name"
	::= { chanNames 10 }

chan11Name  OBJECT-TYPE
	SYNTAX     OCTET STRING (SIZE(1..31))
	MAX-ACCESS read-write
	STATUS     current
	DESCRIPTION
		"Current measurement channel 11 name"
	::= { chanNames 11 }

chan12Name  OBJECT-TYPE
	SYNTAX     OCTET STRING (SIZE(1..31))
	MAX-ACCESS read-write
	STATUS     current
	DESCRIPTION
		"Current measurement channel 12 name"
	::= { chanNames 12 }

chan13Name  OBJECT-TYPE
	SYNTAX     OCTET STRING (SIZE(1..31))
	MAX-ACCESS read-write
	STATUS     current
	DESCRIPTION
		"Current measurement channel 13 name"
	::= { chanNames 13 }

chan14Name  OBJECT-TYPE
	SYNTAX     OCTET STRING (SIZE(1..31))
	MAX-ACCESS read-write
	STATUS     current
	DESCRIPTION
		"Current measurement channel 14 name"
	::= { chanNames 14 }

chan15Name  OBJECT-TYPE
	SYNTAX     OCTET STRING (SIZE(1..31))
	MAX-ACCESS read-write
	STATUS     current
	DESCRIPTION
		"Current measurement channel 15 name"
	::= { chanNames 15 }

chan16Name  OBJECT-TYPE
	SYNTAX     OCTET STRING (SIZE(1..31))
	MAX-ACCESS read-write
	STATUS     current
	DESCRIPTION
		"Current measurement channel 16 name"
	::= { chanNames 16 }

chan17Name  OBJECT-TYPE
	SYNTAX     OCTET STRING (SIZE(1..31))
	MAX-ACCESS read-write
	STATUS     current
	DESCRIPTION
		"Current measurement channel 17 name"
	::= { chanNames 17 }

chan18Name  OBJECT-TYPE
	SYNTAX     OCTET STRING (SIZE(1..31))
	MAX-ACCESS read-write
	STATUS     current
	DESCRIPTION
		"Current measurement channel 18 name"
	::= { chanNames 18 }

chan19Name  OBJECT-TYPE
	SYNTAX     OCTET STRING (SIZE(1..31))
	MAX-ACCESS read-write
	STATUS     current
	DESCRIPTION
		"Current measurement channel 19 name"
	::= { chanNames 19 }

chan20Name  OBJECT-TYPE
	SYNTAX     OCTET STRING (SIZE(1..31))
	MAX-ACCESS read-write
	STATUS     current
	DESCRIPTION
		"Current measurement channel 20 name"
	::= { chanNames 20 }

chan21Name  OBJECT-TYPE
	SYNTAX     OCTET STRING (SIZE(1..31))
	MAX-ACCESS read-write
	STATUS     current
	DESCRIPTION
		"Current measurement channel 21 name"
	::= { chanNames 21 }

chan22Name  OBJECT-TYPE
	SYNTAX     OCTET STRING (SIZE(1..31))
	MAX-ACCESS read-write
	STATUS     current
	DESCRIPTION
		"Current measurement channel 22 name"
	::= { chanNames 22 }

chan23Name  OBJECT-TYPE
	SYNTAX     OCTET STRING (SIZE(1..31))
	MAX-ACCESS read-write
	STATUS     current
	DESCRIPTION
		"Current measurement channel 23 name"
	::= { chanNames 23 }

chan24Name  OBJECT-TYPE
	SYNTAX     OCTET STRING (SIZE(1..31))
	MAX-ACCESS read-write
	STATUS     current
	DESCRIPTION
		"Current measurement channel 24 name"
	::= { chanNames 24 }

chan25Name  OBJECT-TYPE
	SYNTAX     OCTET STRING (SIZE(1..31))
	MAX-ACCESS read-write
	STATUS     current
	DESCRIPTION
		"Current measurement channel 25 name"
	::= { chanNames 25 }

chan26Name  OBJECT-TYPE
	SYNTAX     OCTET STRING (SIZE(1..31))
	MAX-ACCESS read-write
	STATUS     current
	DESCRIPTION
		"Current measurement channel 26 name"
	::= { chanNames 26 }

chan27Name  OBJECT-TYPE
	SYNTAX     OCTET STRING (SIZE(1..31))
	MAX-ACCESS read-write
	STATUS     current
	DESCRIPTION
		"Current measurement channel 27 name"
	::= { chanNames 27 }

chan28Name  OBJECT-TYPE
	SYNTAX     OCTET STRING (SIZE(1..31))
	MAX-ACCESS read-write
	STATUS     current
	DESCRIPTION
		"Current measurement channel 28 name"
	::= { chanNames 28 }

chan29Name  OBJECT-TYPE
	SYNTAX     OCTET STRING (SIZE(1..31))
	MAX-ACCESS read-write
	STATUS     current
	DESCRIPTION
		"Current measurement channel 29 name"
	::= { chanNames 29 }

chan30Name  OBJECT-TYPE
	SYNTAX     OCTET STRING (SIZE(1..31))
	MAX-ACCESS read-write
	STATUS     current
	DESCRIPTION
		"Current measurement channel 30 name"
	::= { chanNames 30 }

chan31Name  OBJECT-TYPE
	SYNTAX     OCTET STRING (SIZE(1..31))
	MAX-ACCESS read-write
	STATUS     current
	DESCRIPTION
		"Current measurement channel 31 name"
	::= { chanNames 31 }

chan32Name  OBJECT-TYPE
	SYNTAX     OCTET STRING (SIZE(1..31))
	MAX-ACCESS read-write
	STATUS     current
	DESCRIPTION
		"Current measurement channel 32 name"
	::= { chanNames 32 }

temp1Name  OBJECT-TYPE
	SYNTAX     OCTET STRING (SIZE(1..31))
	MAX-ACCESS read-write
	STATUS     current
	DESCRIPTION
		"Temperature measurement channel 1 name"
	::= { chanNames 248 }

temp2Name  OBJECT-TYPE
	SYNTAX     OCTET STRING (SIZE(1..31))
	MAX-ACCESS read-write
	STATUS     current
	DESCRIPTION
		"Temperature measurement channel 2 name"
	::= { chanNames 249 }

lowCurrentThreshold1  OBJECT-TYPE
	SYNTAX     Integer32 (0..100)
	UNITS 	"Amps"
	MAX-ACCESS read-write
	STATUS     current
	DESCRIPTION
		"Low current threshold channel 1"
	::= { lowCurrentThresh 1 }

lowCurrentThreshold2  OBJECT-TYPE
	SYNTAX     Integer32 (0..100)
	UNITS 	"Amps"
	MAX-ACCESS read-write
	STATUS     current
	DESCRIPTION
		"Low current threshold channel 2"
	::= { lowCurrentThresh 2 }

lowCurrentThreshold3  OBJECT-TYPE
	SYNTAX     Integer32 (0..100)
	UNITS 	"Amps"
	MAX-ACCESS read-write
	STATUS     current
	DESCRIPTION
		"Low current threshold channel 3"
	::= { lowCurrentThresh 3 }

lowCurrentThreshold4  OBJECT-TYPE
	SYNTAX     Integer32 (0..100)
	UNITS 	"Amps"
	MAX-ACCESS read-write
	STATUS     current
	DESCRIPTION
		"Low current threshold channel 4"
	::= { lowCurrentThresh 4 }

lowCurrentThreshold5  OBJECT-TYPE
	SYNTAX     Integer32 (0..100)
	UNITS 	"Amps"
	MAX-ACCESS read-write
	STATUS     current
	DESCRIPTION
		"Low current threshold channel 5"
	::= { lowCurrentThresh 5 }

lowCurrentThreshold6  OBJECT-TYPE
	SYNTAX     Integer32 (0..100)
	UNITS 	"Amps"
	MAX-ACCESS read-write
	STATUS     current
	DESCRIPTION
		"Low current threshold channel 6"
	::= { lowCurrentThresh 6 }

lowCurrentThreshold7  OBJECT-TYPE
	SYNTAX     Integer32 (0..100)
	UNITS 	"Amps"
	MAX-ACCESS read-write
	STATUS     current
	DESCRIPTION
		"Low current threshold channel 7"
	::= { lowCurrentThresh 7 }

lowCurrentThreshold8  OBJECT-TYPE
	SYNTAX     Integer32 (0..100)
	UNITS 	"Amps"
	MAX-ACCESS read-write
	STATUS     current
	DESCRIPTION
		"Low current threshold channel 8"
	::= { lowCurrentThresh 8 }

lowCurrentThreshold9  OBJECT-TYPE
	SYNTAX     Integer32 (0..100)
	UNITS 	"Amps"
	MAX-ACCESS read-write
	STATUS     current
	DESCRIPTION
		"Low current threshold channel 9"
	::= { lowCurrentThresh 9 }

lowCurrentThreshold10  OBJECT-TYPE
	SYNTAX     Integer32 (0..100)
	UNITS 	"Amps"
	MAX-ACCESS read-write
	STATUS     current
	DESCRIPTION
		"Low current threshold channel 10"
	::= { lowCurrentThresh 10 }

lowCurrentThreshold11  OBJECT-TYPE
	SYNTAX     Integer32 (0..100)
	UNITS 	"Amps"
	MAX-ACCESS read-write
	STATUS     current
	DESCRIPTION
		"Low current threshold channel 11"
	::= { lowCurrentThresh 11 }

lowCurrentThreshold12  OBJECT-TYPE
	SYNTAX     Integer32 (0..100)
	UNITS 	"Amps"
	MAX-ACCESS read-write
	STATUS     current
	DESCRIPTION
		"Low current threshold channel 12"
	::= { lowCurrentThresh 12 }

lowCurrentThreshold13  OBJECT-TYPE
	SYNTAX     Integer32 (0..100)
	UNITS 	"Amps"
	MAX-ACCESS read-write
	STATUS     current
	DESCRIPTION
		"Low current threshold channel 13"
	::= { lowCurrentThresh 13 }

lowCurrentThreshold14  OBJECT-TYPE
	SYNTAX     Integer32 (0..100)
	UNITS 	"Amps"
	MAX-ACCESS read-write
	STATUS     current
	DESCRIPTION
		"Low current threshold channel 14"
	::= { lowCurrentThresh 14 }

lowCurrentThreshold15  OBJECT-TYPE
	SYNTAX     Integer32 (0..100)
	UNITS 	"Amps"
	MAX-ACCESS read-write
	STATUS     current
	DESCRIPTION
		"Low current threshold channel 15"
	::= { lowCurrentThresh 15 }

lowCurrentThreshold16  OBJECT-TYPE
	SYNTAX     Integer32 (0..100)
	UNITS 	"Amps"
	MAX-ACCESS read-write
	STATUS     current
	DESCRIPTION
		"Low current threshold channel 16"
	::= { lowCurrentThresh 16 }

lowCurrentThreshold17  OBJECT-TYPE
	SYNTAX     Integer32 (0..100)
	UNITS 	"Amps"
	MAX-ACCESS read-write
	STATUS     current
	DESCRIPTION
		"Low current threshold channel 17"
	::= { lowCurrentThresh 17 }

lowCurrentThreshold18  OBJECT-TYPE
	SYNTAX     Integer32 (0..100)
	UNITS 	"Amps"
	MAX-ACCESS read-write
	STATUS     current
	DESCRIPTION
		"Low current threshold channel 18"
	::= { lowCurrentThresh 18 }

lowCurrentThreshold19  OBJECT-TYPE
	SYNTAX     Integer32 (0..100)
	UNITS 	"Amps"
	MAX-ACCESS read-write
	STATUS     current
	DESCRIPTION
		"Low current threshold channel 19"
	::= { lowCurrentThresh 19 }

lowCurrentThreshold20  OBJECT-TYPE
	SYNTAX     Integer32 (0..100)
	UNITS 	"Amps"
	MAX-ACCESS read-write
	STATUS     current
	DESCRIPTION
		"Low current threshold channel 20"
	::= { lowCurrentThresh 20 }

lowCurrentThreshold21  OBJECT-TYPE
	SYNTAX     Integer32 (0..100)
	UNITS 	"Amps"
	MAX-ACCESS read-write
	STATUS     current
	DESCRIPTION
		"Low current threshold channel 21"
	::= { lowCurrentThresh 21 }

lowCurrentThreshold22  OBJECT-TYPE
	SYNTAX     Integer32 (0..100)
	UNITS 	"Amps"
	MAX-ACCESS read-write
	STATUS     current
	DESCRIPTION
		"Low current threshold channel 22"
	::= { lowCurrentThresh 22 }

lowCurrentThreshold23  OBJECT-TYPE
	SYNTAX     Integer32 (0..100)
	UNITS 	"Amps"
	MAX-ACCESS read-write
	STATUS     current
	DESCRIPTION
		"Low current threshold channel 23"
	::= { lowCurrentThresh 23 }

lowCurrentThreshold24  OBJECT-TYPE
	SYNTAX     Integer32 (0..100)
	UNITS 	"Amps"
	MAX-ACCESS read-write
	STATUS     current
	DESCRIPTION
		"Low current threshold channel 24"
	::= { lowCurrentThresh 24 }

lowCurrentThreshold25  OBJECT-TYPE
	SYNTAX     Integer32 (0..100)
	UNITS 	"Amps"
	MAX-ACCESS read-write
	STATUS     current
	DESCRIPTION
		"Low current threshold channel 25"
	::= { lowCurrentThresh 25 }

lowCurrentThreshold26  OBJECT-TYPE
	SYNTAX     Integer32 (0..100)
	UNITS 	"Amps"
	MAX-ACCESS read-write
	STATUS     current
	DESCRIPTION
		"Low current threshold channel 26"
	::= { lowCurrentThresh 26 }

lowCurrentThreshold27  OBJECT-TYPE
	SYNTAX     Integer32 (0..100)
	UNITS 	"Amps"
	MAX-ACCESS read-write
	STATUS     current
	DESCRIPTION
		"Low current threshold channel 27"
	::= { lowCurrentThresh 27 }

lowCurrentThreshold28  OBJECT-TYPE
	SYNTAX     Integer32 (0..100)
	UNITS 	"Amps"
	MAX-ACCESS read-write
	STATUS     current
	DESCRIPTION
		"Low current threshold channel 28"
	::= { lowCurrentThresh 28 }

lowCurrentThreshold29  OBJECT-TYPE
	SYNTAX     Integer32 (0..100)
	UNITS 	"Amps"
	MAX-ACCESS read-write
	STATUS     current
	DESCRIPTION
		"Low current threshold channel 29"
	::= { lowCurrentThresh 29 }

lowCurrentThreshold30  OBJECT-TYPE
	SYNTAX     Integer32 (0..100)
	UNITS 	"Amps"
	MAX-ACCESS read-write
	STATUS     current
	DESCRIPTION
		"Low current threshold channel 30"
	::= { lowCurrentThresh 30 }

lowCurrentThreshold31  OBJECT-TYPE
	SYNTAX     Integer32 (0..100)
	UNITS 	"Amps"
	MAX-ACCESS read-write
	STATUS     current
	DESCRIPTION
		"Low current threshold channel 31"
	::= { lowCurrentThresh 31 }

lowCurrentThreshold32  OBJECT-TYPE
	SYNTAX     Integer32 (0..100)
	UNITS 	"Amps"
	MAX-ACCESS read-write
	STATUS     current
	DESCRIPTION
		"Low current threshold channel 32"
	::= { lowCurrentThresh 32 }

highCurrentThreshold1  OBJECT-TYPE
	SYNTAX     Integer32 (1..100)
	UNITS 	"Amps"
	MAX-ACCESS read-write
	STATUS     current
	DESCRIPTION
		"High Current threshold channel 1"
	::= { highCurrentThresh 1 }

highCurrentThreshold2  OBJECT-TYPE
	SYNTAX     Integer32 (1..100)
	UNITS 	"Amps"
	MAX-ACCESS read-write
	STATUS     current
	DESCRIPTION
		"High Current threshold channel 2"
	::= { highCurrentThresh 2 }

highCurrentThreshold3  OBJECT-TYPE
	SYNTAX     Integer32 (1..100)
	UNITS 	"Amps"
	MAX-ACCESS read-write
	STATUS     current
	DESCRIPTION
		"High Current threshold channel 3"
	::= { highCurrentThresh 3 }

highCurrentThreshold4  OBJECT-TYPE
	SYNTAX     Integer32 (1..100)
	UNITS 	"Amps"
	MAX-ACCESS read-write
	STATUS     current
	DESCRIPTION
		"High Current threshold channel 4"
	::= { highCurrentThresh 4 }

highCurrentThreshold5  OBJECT-TYPE
	SYNTAX     Integer32 (1..100)
	UNITS 	"Amps"
	MAX-ACCESS read-write
	STATUS     current
	DESCRIPTION
		"High Current threshold channel 5"
	::= { highCurrentThresh 5 }

highCurrentThreshold6  OBJECT-TYPE
	SYNTAX     Integer32 (1..100)
	UNITS 	"Amps"
	MAX-ACCESS read-write
	STATUS     current
	DESCRIPTION
		"High Current threshold channel 6"
	::= { highCurrentThresh 6 }

highCurrentThreshold7  OBJECT-TYPE
	SYNTAX     Integer32 (1..100)
	UNITS 	"Amps"
	MAX-ACCESS read-write
	STATUS     current
	DESCRIPTION
		"High Current threshold channel 7"
	::= { highCurrentThresh 7 }

highCurrentThreshold8  OBJECT-TYPE
	SYNTAX     Integer32 (1..100)
	UNITS 	"Amps"
	MAX-ACCESS read-write
	STATUS     current
	DESCRIPTION
		"High Current threshold channel 8"
	::= { highCurrentThresh 8 }

highCurrentThreshold9  OBJECT-TYPE
	SYNTAX     Integer32 (1..100)
	UNITS 	"Amps"
	MAX-ACCESS read-write
	STATUS     current
	DESCRIPTION
		"High Current threshold channel 9"
	::= { highCurrentThresh 9 }

highCurrentThreshold10  OBJECT-TYPE
	SYNTAX     Integer32 (1..100)
	UNITS 	"Amps"
	MAX-ACCESS read-write
	STATUS     current
	DESCRIPTION
		"High Current threshold channel 10"
	::= { highCurrentThresh 10 }

highCurrentThreshold11  OBJECT-TYPE
	SYNTAX     Integer32 (1..100)
	UNITS 	"Amps"
	MAX-ACCESS read-write
	STATUS     current
	DESCRIPTION
		"High Current threshold channel 11"
	::= { highCurrentThresh 11 }

highCurrentThreshold12  OBJECT-TYPE
	SYNTAX     Integer32 (1..100)
	UNITS 	"Amps"
	MAX-ACCESS read-write
	STATUS     current
	DESCRIPTION
		"High Current threshold channel 12"
	::= { highCurrentThresh 12 }

highCurrentThreshold13  OBJECT-TYPE
	SYNTAX     Integer32 (1..100)
	UNITS 	"Amps"
	MAX-ACCESS read-write
	STATUS     current
	DESCRIPTION
		"High Current threshold channel 13"
	::= { highCurrentThresh 13 }

highCurrentThreshold14  OBJECT-TYPE
	SYNTAX     Integer32 (1..100)
	UNITS 	"Amps"
	MAX-ACCESS read-write
	STATUS     current
	DESCRIPTION
		"High Current threshold channel 14"
	::= { highCurrentThresh 14 }

highCurrentThreshold15  OBJECT-TYPE
	SYNTAX     Integer32 (1..100)
	UNITS 	"Amps"
	MAX-ACCESS read-write
	STATUS     current
	DESCRIPTION
		"High Current threshold channel 15"
	::= { highCurrentThresh 15 }

highCurrentThreshold16  OBJECT-TYPE
	SYNTAX     Integer32 (1..100)
	UNITS 	"Amps"
	MAX-ACCESS read-write
	STATUS     current
	DESCRIPTION
		"High Current threshold channel 16"
	::= { highCurrentThresh 16 }

highCurrentThreshold17  OBJECT-TYPE
	SYNTAX     Integer32 (1..100)
	UNITS 	"Amps"
	MAX-ACCESS read-write
	STATUS     current
	DESCRIPTION
		"High Current threshold channel 17"
	::= { highCurrentThresh 17 }

highCurrentThreshold18  OBJECT-TYPE
	SYNTAX     Integer32 (1..100)
	UNITS 	"Amps"
	MAX-ACCESS read-write
	STATUS     current
	DESCRIPTION
		"High Current threshold channel 18"
	::= { highCurrentThresh 18 }

highCurrentThreshold19  OBJECT-TYPE
	SYNTAX     Integer32 (1..100)
	UNITS 	"Amps"
	MAX-ACCESS read-write
	STATUS     current
	DESCRIPTION
		"High Current threshold channel 19"
	::= { highCurrentThresh 19 }

highCurrentThreshold20  OBJECT-TYPE
	SYNTAX     Integer32 (1..100)
	UNITS 	"Amps"
	MAX-ACCESS read-write
	STATUS     current
	DESCRIPTION
		"High Current threshold channel 20"
	::= { highCurrentThresh 20 }

highCurrentThreshold21  OBJECT-TYPE
	SYNTAX     Integer32 (1..100)
	UNITS 	"Amps"
	MAX-ACCESS read-write
	STATUS     current
	DESCRIPTION
		"High Current threshold channel 21"
	::= { highCurrentThresh 21 }

highCurrentThreshold22  OBJECT-TYPE
	SYNTAX     Integer32 (1..100)
	UNITS 	"Amps"
	MAX-ACCESS read-write
	STATUS     current
	DESCRIPTION
		"High Current threshold channel 22"
	::= { highCurrentThresh 22 }

highCurrentThreshold23  OBJECT-TYPE
	SYNTAX     Integer32 (1..100)
	UNITS 	"Amps"
	MAX-ACCESS read-write
	STATUS     current
	DESCRIPTION
		"High Current threshold channel 23"
	::= { highCurrentThresh 23 }

highCurrentThreshold24  OBJECT-TYPE
	SYNTAX     Integer32 (1..100)
	UNITS 	"Amps"
	MAX-ACCESS read-write
	STATUS     current
	DESCRIPTION
		"High Current threshold channel 24"
	::= { highCurrentThresh 24 }

highCurrentThreshold25  OBJECT-TYPE
	SYNTAX     Integer32 (1..100)
	UNITS 	"Amps"
	MAX-ACCESS read-write
	STATUS     current
	DESCRIPTION
		"High Current threshold channel 25"
	::= { highCurrentThresh 25 }

highCurrentThreshold26  OBJECT-TYPE
	SYNTAX     Integer32 (1..100)
	UNITS 	"Amps"
	MAX-ACCESS read-write
	STATUS     current
	DESCRIPTION
		"High Current threshold channel 26"
	::= { highCurrentThresh 26 }

highCurrentThreshold27  OBJECT-TYPE
	SYNTAX     Integer32 (1..100)
	UNITS 	"Amps"
	MAX-ACCESS read-write
	STATUS     current
	DESCRIPTION
		"High Current threshold channel 27"
	::= { highCurrentThresh 27 }

highCurrentThreshold28  OBJECT-TYPE
	SYNTAX     Integer32 (1..100)
	UNITS 	"Amps"
	MAX-ACCESS read-write
	STATUS     current
	DESCRIPTION
		"High Current threshold channel 28"
	::= { highCurrentThresh 28 }

highCurrentThreshold29  OBJECT-TYPE
	SYNTAX     Integer32 (1..100)
	UNITS 	"Amps"
	MAX-ACCESS read-write
	STATUS     current
	DESCRIPTION
		"High Current threshold channel 29"
	::= { highCurrentThresh 29 }

highCurrentThreshold30  OBJECT-TYPE
	SYNTAX     Integer32 (1..100)
	UNITS 	"Amps"
	MAX-ACCESS read-write
	STATUS     current
	DESCRIPTION
		"High Current threshold channel 30"
	::= { highCurrentThresh 30 }

highCurrentThreshold31  OBJECT-TYPE
	SYNTAX     Integer32 (1..100)
	UNITS 	"Amps"
	MAX-ACCESS read-write
	STATUS     current
	DESCRIPTION
		"High Current threshold channel 31"
	::= { highCurrentThresh 31 }

highCurrentThreshold32  OBJECT-TYPE
	SYNTAX     Integer32 (1..100)
	UNITS 	"Amps"
	MAX-ACCESS read-write
	STATUS     current
	DESCRIPTION
		"High Current threshold channel 32"
	::= { highCurrentThresh 32 }

lowTempThreshold1  OBJECT-TYPE
	SYNTAX     Integer32 (0..150)
	UNITS 	"Degrees"
	MAX-ACCESS read-write
	STATUS     current
	DESCRIPTION
		"Low temperature threshold 1"
	::= { lowTempThresh 1 }

lowTempThreshold2  OBJECT-TYPE
	SYNTAX     Integer32 (0..150)
	UNITS 	"Degrees"
	MAX-ACCESS read-write
	STATUS     current
	DESCRIPTION
		"Low temperature threshold 2"
	::= { lowTempThresh 2 }

highTempThreshold1  OBJECT-TYPE
	SYNTAX     Integer32 (0..150)
	UNITS 	"Degrees"
	MAX-ACCESS read-write
	STATUS     current
	DESCRIPTION
		"High temperature threshold 1"
	::= { highTempThresh 1 }

highTempThreshold2  OBJECT-TYPE
	SYNTAX     Integer32 (0..150)
	UNITS 	"Degrees"
	MAX-ACCESS read-write
	STATUS     current
	DESCRIPTION
		"High temperature threshold 2"
	::= { highTempThresh 2 }

compliances  MODULE-COMPLIANCE
	STATUS     current
	DESCRIPTION
		"The requirements for conforming to the Monitored ePDU MIB."
	MODULE
		GROUP thresholdGroup
		DESCRIPTION
		"The current and temperature thresholds group."
		GROUP unitGroup
		DESCRIPTION
		"The unit configuration and channel naming group."
		GROUP measurementGroup
		DESCRIPTION
		"The measurement readings group."
	::= { conformance 1 }

oldCompliances  MODULE-COMPLIANCE
	STATUS     deprecated
	DESCRIPTION
		"Deprecated requirements for conforming to the Monitored ePDU MIB."
	MODULE
		GROUP thresholdGroupOld
		DESCRIPTION
		"The deprecated thresholds group."
	::= { conformance 2 }

unitGroup  OBJECT-GROUP
	OBJECTS { mailServerIP,
		alertEmailAddress,
		assetID,
		chan10Name,
		chan11Name,
		chan12Name,
		chan13Name,
		chan14Name,
		chan15Name,
		chan16Name,
		chan17Name,
		chan18Name,
		chan19Name,
		chan1Name,
		chan20Name,
		chan21Name,
		chan22Name,
		chan23Name,
		chan24Name,
		chan25Name,
		chan26Name,
		chan27Name,
		chan28Name,
		chan29Name,
		chan2Name,
		chan30Name,
		chan31Name,
		chan32Name,
		chan3Name,
		chan4Name,
		chan5Name,
		chan6Name,
		chan7Name,
		chan8Name,
		chan9Name,
		currentMonitorType,
		firmwareRevision,
		numCurrentChannels,
		temp1Name,
		temp2Name,
		temperature1Enable,
		temperature2Enable,
		trapDestIP,
		unitGateway,
		unitIPAddress,
		unitMACAddress,
		unitName,
		unitSubnetMask,
		uptime }
	STATUS     current
	DESCRIPTION
		"The unit configuration and channel naming group."
	::= { groups 1 }

measurementGroup  OBJECT-GROUP
	OBJECTS { chan1,
		chan10,
		chan11,
		chan12,
		chan13,
		chan14,
		chan15,
		chan16,
		chan17,
		chan18,
		chan19,
		chan2,
		chan20,
		chan21,
		chan22,
		chan23,
		chan24,
		chan25,
		chan26,
		chan27,
		chan28,
		chan29,
		chan3,
		chan30,
		chan31,
		chan32,
		chan4,
		chan5,
		chan6,
		chan7,
		chan8,
		chan9,
		tempChan1,
		tempChan2 }
	STATUS     current
	DESCRIPTION
		"The measurement readings group."
	::= { groups 2 }

thresholdGroup  OBJECT-GROUP
	OBJECTS { highCurrentThreshold1,
		highCurrentThreshold10,
		highCurrentThreshold11,
		highCurrentThreshold12,
		highCurrentThreshold13,
		highCurrentThreshold14,
		highCurrentThreshold15,
		highCurrentThreshold16,
		highCurrentThreshold17,
		highCurrentThreshold18,
		highCurrentThreshold19,
		highCurrentThreshold2,
		highCurrentThreshold20,
		highCurrentThreshold21,
		highCurrentThreshold22,
		highCurrentThreshold23,
		highCurrentThreshold24,
		highCurrentThreshold25,
		highCurrentThreshold26,
		highCurrentThreshold27,
		highCurrentThreshold28,
		highCurrentThreshold29,
		highCurrentThreshold3,
		highCurrentThreshold30,
		highCurrentThreshold31,
		highCurrentThreshold32,
		highCurrentThreshold4,
		highCurrentThreshold5,
		highCurrentThreshold6,
		highCurrentThreshold7,
		highCurrentThreshold8,
		highCurrentThreshold9,
		highTempThreshold1,
		highTempThreshold2,
		lowCurrentThreshold1,
		lowCurrentThreshold10,
		lowCurrentThreshold11,
		lowCurrentThreshold12,
		lowCurrentThreshold13,
		lowCurrentThreshold14,
		lowCurrentThreshold15,
		lowCurrentThreshold16,
		lowCurrentThreshold17,
		lowCurrentThreshold18,
		lowCurrentThreshold19,
		lowCurrentThreshold2,
		lowCurrentThreshold20,
		lowCurrentThreshold21,
		lowCurrentThreshold22,
		lowCurrentThreshold23,
		lowCurrentThreshold24,
		lowCurrentThreshold25,
		lowCurrentThreshold26,
		lowCurrentThreshold27,
		lowCurrentThreshold28,
		lowCurrentThreshold29,
		lowCurrentThreshold3,
		lowCurrentThreshold30,
		lowCurrentThreshold31,
		lowCurrentThreshold32,
		lowCurrentThreshold4,
		lowCurrentThreshold5,
		lowCurrentThreshold6,
		lowCurrentThreshold7,
		lowCurrentThreshold8,
		lowCurrentThreshold9,
		lowTempThreshold1,
		lowTempThreshold2 }
	STATUS     current
	DESCRIPTION
		"The current and temperature thresholds group."
	::= { groups 3 }

thresholdGroupOld  OBJECT-GROUP
	OBJECTS { highCurrentThreshold1old,
		highCurrentThreshold2old,
		highCurrentThreshold3old,
		highCurrentThreshold4old,
		highCurrentThreshold5old,
		highCurrentThreshold6old,
		highCurrentThreshold7old,
		highCurrentThreshold8old,
		lowCurrentThreshold1old,
		lowCurrentThreshold2old,
		lowCurrentThreshold3old,
		lowCurrentThreshold4old,
		lowCurrentThreshold5old,
		lowCurrentThreshold6old,
		lowCurrentThreshold7old,
		lowCurrentThreshold8old }
	STATUS     deprecated
	DESCRIPTION
		"The deprecated thresholds group."
	::= { groups 4 }
END
