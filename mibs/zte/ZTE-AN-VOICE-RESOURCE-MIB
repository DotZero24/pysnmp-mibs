-------------------------------------------------------------------------------
-- File Name : ZTE-AN-VOICE-RESOURCE-MIB.mib
-- Date      : 2010-08-24
-- Author    : ZTE Nms dept.

--
-- Zte Voip Base Mib for Access Node
--
--
-------------------------------------------------------------------------------


ZTE-AN-VOICE-RESOURCE-MIB DEFINITIONS ::= BEGIN

    IMPORTS
        MODULE-IDENTITY, NOTIFICATION-TYPE, OBJECT-TYPE, enterprises,
        IpAddress, Counter32, Integer32, Counter64, Unsigned32, Gauge32
                            FROM SNMPv2-SMI
        TEXTUAL-CONVENTION, MacAddress, DateAndTime, RowStatus, DisplayString,
        TruthValue          FROM SNMPv2-TC
        InetAddressType, InetAddress         FROM INET-ADDRESS-MIB;

    zxAnVoiceResourceMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."

    ::= { zxAn 5200 }

    zte OBJECT IDENTIFIER ::= { enterprises 3902 }
    zxAn OBJECT IDENTIFIER ::= { zte 1015 }
    zxAnVoiceMgmt OBJECT IDENTIFIER ::= { zxAnVoiceResourceMib 3 }
    zxAnVoipResource OBJECT IDENTIFIER ::= { zxAnVoiceMgmt 3 }
    zxAnSlcVoipStatsMgmt OBJECT IDENTIFIER ::= { zxAnVoipResource 52 }

-------------------------------------------------------------------------------
-- Following objects are defined.
-- 1. a200IpsTable
-- 3. a200MprbParTable
-- 4. zxAnRtpStatsMgmt
-- 5. zxAnNarrowbandCircuitResTable
-- 6. zxAnToneTable
-- 7. a200AsigTable
-- 8. a200ConfTable
-- 9. zxAnVoipResourceGlobalObjects
-- 10. zxAnIpsStaticTerminationIdTable
-- 11. zxAnSlcVoipStatsEnable
-- 12. zxAnSlcVoipStatsTable
-------------------------------------------------------------------------------


-------------------------------------------------------------------------------
-- 1. a200IpsTable
-------------------------------------------------------------------------------
    a200IpsTable OBJECT-TYPE
        SYNTAX      SEQUENCE OF A200IpsEntry
        MAX-ACCESS  not-accessible
        STATUS      current
        DESCRIPTION
            "ips\u7535\u8def\u63cf\u8ff0\u8868\uff0c\u63cf\u8ff0MG\
             u4e2dips\u7535\u8def\u7684\u72b6\u6001\u53ca\u5c5e\u6027"
        ::= { zxAnVoipResource 2 }

    a200IpsEntry OBJECT-TYPE
        SYNTAX      A200IpsEntry
        MAX-ACCESS  not-accessible
        STATUS      current
        DESCRIPTION
            "describe colunms and index in slc table"
        INDEX { a200ipsrackno, a200ipsshelfno,
                a200ipsslotno, a200ipsubdevno, a200ipsindex}
        ::={a200IpsTable 1}

    A200IpsEntry ::= SEQUENCE {
        a200ipsrackno        Integer32,
        a200ipsshelfno       Integer32,
        a200ipsslotno        Integer32,
        a200ipsubdevno       Integer32,
        a200ipsindex         Integer32,
        a200ipsstatus        Integer32,
        a200ipspkg           Unsigned32,
        a200ipsmuxtype       INTEGER,
        a200ipsmodmtype      Integer32,
        a200ipslpt           Unsigned32,
        a200ipsrpt           Unsigned32,
        a200ipslptimmin      Integer32,
        a200ipslptimmax      Integer32,
        a200ipsrptimmin      Integer32,
        a200ipsrptimmax      Integer32,
        a200ipstmmdtyp       Integer32,
        a200ipscallerid      Integer32,
        a200ipsoperNum       Integer32,
        a200ipsblockoper     INTEGER,
        a200ipsunblockoper   INTEGER
        }

    a200ipsrackno     OBJECT-TYPE
        SYNTAX      Integer32
        MAX-ACCESS  not-accessible
        STATUS      current
        DESCRIPTION ""
        ::= { a200IpsEntry 1 }

    a200ipsshelfno     OBJECT-TYPE
        SYNTAX      Integer32
        MAX-ACCESS  not-accessible
        STATUS      current
        DESCRIPTION ""
        ::= { a200IpsEntry 2 }

    a200ipsslotno     OBJECT-TYPE
        SYNTAX      Integer32
        MAX-ACCESS  not-accessible
        STATUS      current
        DESCRIPTION ""
        ::= { a200IpsEntry 3 }

    a200ipsubdevno     OBJECT-TYPE
        SYNTAX      Integer32
        MAX-ACCESS  not-accessible
        STATUS      current
        DESCRIPTION "ips\u7535\u8def\u6240\u5728\u7684\u677f\u5185\u5b50\
                     u8bbe\u5907\u7f16\u53f7"
        ::= { a200IpsEntry 4 }

    a200ipsindex     OBJECT-TYPE
        SYNTAX      Integer32
        MAX-ACCESS  not-accessible
        STATUS      current
        DESCRIPTION "ips\u7535\u8def\u5728\u677f\u5185\u5b50\u8bbe\u5907\
                     u4e2d\u7684\u5e8f\u53f7"
        ::= { a200IpsEntry 5 }

    a200ipsstatus   OBJECT-TYPE
        SYNTAX      Integer32
        MAX-ACCESS  read-only
        STATUS      current
        DESCRIPTION "\u7535\u8def\u72b6\u6001\uff0c\u6309\u4f4d\u53d6\u503c"
        ::= { a200IpsEntry 6 }

    a200ipspkg    OBJECT-TYPE
        SYNTAX      Unsigned32
        MAX-ACCESS  read-only
        STATUS      current
        DESCRIPTION "\u7535\u8def\u652f\u6301\u7684\u5305\u7c7b\u578b\uff0c
                     \u6309\u4f4d\u53d6\u503c"
        ::= { a200IpsEntry 7 }

    a200ipsmuxtype   OBJECT-TYPE
        SYNTAX      INTEGER(0..65535)
        MAX-ACCESS  read-write
        STATUS      current
        DESCRIPTION "\u590d\u7528\u7c7b\u578b"
        ::= { a200IpsEntry 8 }

    a200ipsmodmtype OBJECT-TYPE
        SYNTAX    Integer32
        MAX-ACCESS  read-only
        STATUS    current
        DESCRIPTION  "Modem\u7c7b\u578b"
        ::={a200IpsEntry 9}

    a200ipslpt    OBJECT-TYPE
        SYNTAX      Unsigned32
        MAX-ACCESS  read-only
        STATUS      current
        DESCRIPTION "\u7535\u8def\u652f\u6301\u7684\u63a5\u6536\uff08\u672c
                     \u7aef\uff09\u51c0\u8377\u7c7b\u578b\uff0c\u6309\u4f4d
                     \u53d6\u503c"
        ::= { a200IpsEntry 10 }

    a200ipsrpt  OBJECT-TYPE
        SYNTAX      Unsigned32
        MAX-ACCESS  read-only
        STATUS      current
        DESCRIPTION "\u7535\u8def\u652f\u6301\u7684\u53d1\u9001\uff08\u8fdc
                     \u7aef\uff09\u51c0\u8377\u7c7b\u578b\uff0c\u6309\u4f4d
                     \u53d6\u503c"
        ::= { a200IpsEntry 11 }

    a200ipslptimmin OBJECT-TYPE
        SYNTAX      Integer32
        MAX-ACCESS  read-write
        STATUS      current
        DESCRIPTION "\u63a5\u6536\uff08\u672c\u7aef\uff09\u7aef\u53e3\u6253
                     \u5305\u65f6\u957f\u6700\u5c0f\u503c"
        ::= { a200IpsEntry 12 }

    a200ipslptimmax OBJECT-TYPE
        SYNTAX      Integer32
        MAX-ACCESS  read-write
        STATUS      current
        DESCRIPTION "\u63a5\u6536\uff08\u672c\u7aef\uff09\u7aef\u53e3\u6253
                     \u5305\u65f6\u957f\u6700\u5927\u503c"
        ::= { a200IpsEntry 13 }

    a200ipsrptimmin OBJECT-TYPE
        SYNTAX      Integer32
        MAX-ACCESS  read-write
        STATUS      current
        DESCRIPTION "\u53d1\u9001\uff08\u8fdc\u7aef\uff09\u7aef\u53e3\u6253
                     \u5305\u65f6\u957f\u6700\u5c0f\u503c"
        ::= { a200IpsEntry 14 }

    a200ipsrptimmax OBJECT-TYPE
        SYNTAX      Integer32
        MAX-ACCESS  read-write
        STATUS      current
        DESCRIPTION "\u53d1\u9001\uff08\u8fdc\u7aef\uff09\u7aef\u53e3\u6253
                     \u5305\u65f6\u957f\u6700\u5927\u503c"
        ::= { a200IpsEntry 15 }

    a200ipstmmdtyp   OBJECT-TYPE
        SYNTAX      Integer32
        MAX-ACCESS  read-only
        STATUS      current
        DESCRIPTION "\u5a92\u4f53\u7c7b\u578b"
        ::= { a200IpsEntry 16 }

    a200ipscallerid OBJECT-TYPE
        SYNTAX      Integer32
        MAX-ACCESS  read-only
        STATUS      current
        DESCRIPTION "\u662f\u5426\u652f\u6301\u6765\u7535\u663e\u793a\uff0c
                     =0: \u4e0d\u652f\u6301\uff0c  =1: \u652f\u6301"
        ::= { a200IpsEntry 17 }

    a200ipsoperNum   OBJECT-TYPE
        SYNTAX      Integer32(1..1024)
        MAX-ACCESS  read-write
        STATUS      current
        DESCRIPTION ""
        ::= { a200IpsEntry 18 }

    a200ipsblockoper   OBJECT-TYPE
        SYNTAX      INTEGER(1)
        MAX-ACCESS  read-write
        STATUS      current
        DESCRIPTION "block ips"
        ::= { a200IpsEntry 19 }

    a200ipsunblockoper   OBJECT-TYPE
        SYNTAX      INTEGER(1)
        MAX-ACCESS  read-write
        STATUS      current
        DESCRIPTION "unblock ips"
        ::= { a200IpsEntry 20 }

-------------------------------------------------------------------------------
-- 3. a200MprbParTable
-------------------------------------------------------------------------------
    a200MprbParTable OBJECT-TYPE
        SYNTAX      SEQUENCE OF A200MprbParEntry
        MAX-ACCESS  not-accessible
        STATUS      current
        DESCRIPTION ""
        ::= { zxAnVoipResource 9 }

    a200MprbParEntry OBJECT-TYPE
        SYNTAX      A200MprbParEntry
        MAX-ACCESS  not-accessible
        STATUS      current
        DESCRIPTION
            "describe colunms and index in mprbpar table"
        INDEX { a200mprbparparid }
        ::= { a200MprbParTable 1 }

    A200MprbParEntry ::= SEQUENCE {
        a200mprbparparid              INTEGER,
        a200mprbpardtmfrelaymode      INTEGER,
        a200mprbpardtmfpayload        INTEGER,
        a200mprbpardtmfredundant      INTEGER,
        a200mprbparecenable           INTEGER,
        a200mprbparectaillen          INTEGER,
        a200mprbparectxf              INTEGER,
        a200mprbparnlpaggress         INTEGER,
        a200mprbparg711redundancy     INTEGER,
        a200mprbparfaxmode            INTEGER,
        a200mprbparmodemmode          INTEGER,
        a200mprbparecmenable          INTEGER,
        a200mprbparfaxpage            INTEGER,
        a200mprbpart30message         INTEGER,
        a200mprbparspeedlimit         INTEGER,
        a200mprbpartcfprocedure       INTEGER,
        a200mprbparfaxswtime          INTEGER,
        a200mprbparmindelay           INTEGER,
        a200mprbparmaxdelay           INTEGER,
        a200mprbparnomdelay           INTEGER,
        a200mprbparvadvalue           INTEGER,
        a200mprbparg723rate           INTEGER,
        a200mprbpardcfilter           INTEGER,
        a200mprbparsilencetopcm       INTEGER,
        a200mprbparpcmlaw             INTEGER,
        a200mprbparpcmtopkggain       INTEGER,
        a200mprbparpkgtopcmgain       INTEGER,
        a200mprbparfsklevel           INTEGER,
        a200mprbpardtmfcidelec        INTEGER,
        a200mprbparnortppktcheck      INTEGER
        }

    a200mprbparparid  OBJECT-TYPE
        SYNTAX      INTEGER(1..255)
        MAX-ACCESS  not-accessible
        STATUS      current
        DESCRIPTION ""
        ::= { a200MprbParEntry 1 }

    a200mprbpardtmfrelaymode  OBJECT-TYPE
        SYNTAX      INTEGER {
            voiceCoding(1),
            redRfc2833(2),
            aal2Ietf(4),
            nredRfc2833(6),
            notRelay(0)
            }
        MAX-ACCESS  read-write
        STATUS      current
        DESCRIPTION
            "The value:aal2Ietf(4) is not used for narrowband platform."
        ::= { a200MprbParEntry 2 }

    a200mprbpardtmfpayload  OBJECT-TYPE
        SYNTAX      INTEGER(0..255)
        MAX-ACCESS  read-write
        STATUS      current
        DESCRIPTION ""
        ::= { a200MprbParEntry 3 }

    a200mprbpardtmfredundant  OBJECT-TYPE
        SYNTAX      INTEGER(0..255)
        MAX-ACCESS  read-write
        STATUS      current
        DESCRIPTION ""
        ::= { a200MprbParEntry 4 }

    a200mprbparecenable  OBJECT-TYPE
        SYNTAX      INTEGER {
            disable(0),
            enable(1)
            }
        MAX-ACCESS  read-write
        STATUS      current
        DESCRIPTION ""
        ::= { a200MprbParEntry 5 }

    a200mprbparectaillen  OBJECT-TYPE
        SYNTAX      INTEGER {
            is8ms(0),
            is16ms(1),
            is24ms(2),
            is32ms(3),
            is64ms(7),
            is128ms(15)
            }
        MAX-ACCESS  read-write
        STATUS      current
        DESCRIPTION ""
        ::= { a200MprbParEntry 6 }

    a200mprbparectxf  OBJECT-TYPE
        SYNTAX      INTEGER{notLinear(0),fixedTransmit(1)}
        MAX-ACCESS  read-write
        STATUS      current
        DESCRIPTION ""
        ::= { a200MprbParEntry 7 }

    a200mprbparnlpaggress  OBJECT-TYPE
        SYNTAX      INTEGER(-32767..32767)
        MAX-ACCESS  read-write
        STATUS      current
        DESCRIPTION ""
        ::= { a200MprbParEntry 8 }

    a200mprbparg711redundancy  OBJECT-TYPE
        SYNTAX      INTEGER(0..3)
        MAX-ACCESS  read-write
        STATUS      current
        DESCRIPTION ""
        ::= { a200MprbParEntry 9 }

    a200mprbparfaxmode  OBJECT-TYPE
        SYNTAX      INTEGER {
            selfNegotiation(0),
            --t38Faxmode(1),
            --t30Transparent(2),
            selfSwitch(6),
            ssControl(11)
            }
        MAX-ACCESS  read-write
        STATUS      current
        DESCRIPTION
            "The 2 values:t38Faxmode(1),t30Transparent(2)
            are no longer in use."
        DEFVAL { ssControl }
        ::= { a200MprbParEntry 10 }

    a200mprbparmodemmode  OBJECT-TYPE
        SYNTAX      INTEGER {
            selfNegotiation(0),
            --transparent(2),
            --modemImmediate(3),
            --faxImmediate(4),
            --cidImmediate(5),
            selfSwitch(6),
            ssControl(11)
            }
        MAX-ACCESS  read-write
        STATUS      current
        DESCRIPTION
            "The 4 values:transparent(2),modemImmediate(3),faxImmediate(4),
            cidImmediate(5) are no longer in use."
        DEFVAL { ssControl }
        ::= { a200MprbParEntry 11 }

    a200mprbparecmenable  OBJECT-TYPE
        SYNTAX      INTEGER {
            preventEcm(0),
            allowEcm(1)
            }
        MAX-ACCESS  read-write
        STATUS      current
        DESCRIPTION ""
        ::= { a200MprbParEntry 12 }

    a200mprbparfaxpage  OBJECT-TYPE
        SYNTAX      INTEGER(0..3)
        MAX-ACCESS  read-write
        STATUS      current
        DESCRIPTION ""
        ::= { a200MprbParEntry 13 }

    a200mprbpart30message  OBJECT-TYPE
        SYNTAX      INTEGER(0..7)
        MAX-ACCESS  read-write
        STATUS      current
        DESCRIPTION ""
        ::= { a200MprbParEntry 14 }

    a200mprbparspeedlimit  OBJECT-TYPE
        SYNTAX    INTEGER {
            noLimit(0),
            is2400bps(1),
            is4800bps(2),
            is7200bps(3),
            is9600bps(4),
            is12000bps(5),
            is14400bps(6)
            }
        MAX-ACCESS  read-write
        STATUS      current
        DESCRIPTION ""
        ::= { a200MprbParEntry 15 }

    a200mprbpartcfprocedure  OBJECT-TYPE
        SYNTAX      INTEGER {
            procedure2(0),
            procedure1(1)
            }
        MAX-ACCESS  read-write
        STATUS      current
        DESCRIPTION ""
        ::= { a200MprbParEntry 16 }

    a200mprbparfaxswtime  OBJECT-TYPE
        SYNTAX      INTEGER(1..100)
        UNITS       "100ms"
        MAX-ACCESS  read-write
        STATUS      current
        DESCRIPTION
            "The time of switching from fax mode to voice mode
             or from voice mode to fax mode."
        DEFVAL { 5 }
        ::= { a200MprbParEntry 17}

    a200mprbparmindelay  OBJECT-TYPE
        SYNTAX      INTEGER(0..200)
        MAX-ACCESS  read-write
        STATUS      current
        DESCRIPTION ""
        ::= { a200MprbParEntry 18 }

    a200mprbparmaxdelay  OBJECT-TYPE
        SYNTAX      INTEGER(0..200)
        MAX-ACCESS  read-write
        STATUS      current
        DESCRIPTION ""
        ::= { a200MprbParEntry 19 }

    a200mprbparnomdelay  OBJECT-TYPE
        SYNTAX      INTEGER(0..200)
        MAX-ACCESS  read-write
        STATUS      current
        DESCRIPTION ""
        ::= { a200MprbParEntry 20 }

    a200mprbparvadvalue  OBJECT-TYPE
        SYNTAX      INTEGER {
            disableVAD(0),
            defaultScheme(1),
            reserved(2)
            }
        MAX-ACCESS  read-write
        STATUS      current
        DESCRIPTION ""
        ::= { a200MprbParEntry 21 }

    a200mprbparg723rate  OBJECT-TYPE
        SYNTAX      INTEGER {
            highRT6point3kbps(1),
            lowRT5point3kbps(0)
            }
        MAX-ACCESS  read-write
        STATUS      current
        DESCRIPTION ""
        ::= { a200MprbParEntry 22 }

    a200mprbpardcfilter  OBJECT-TYPE
        SYNTAX      INTEGER {
            enabledc(0),
            disabledc(1)
            }
        MAX-ACCESS  read-write
        STATUS      current
        DESCRIPTION ""
        ::= { a200MprbParEntry 23 }

    a200mprbparsilencetopcm  OBJECT-TYPE
        SYNTAX      INTEGER {
            comfortNoise(0),
            silence(1)
            }
        MAX-ACCESS  read-write
        STATUS      current
        DESCRIPTION ""
        ::= { a200MprbParEntry 24 }

    a200mprbparpcmlaw  OBJECT-TYPE
        SYNTAX      INTEGER {
           aLaw(0),
           muLaw(1)
           }
        MAX-ACCESS  read-write
        STATUS      current
        DESCRIPTION ""
        ::= { a200MprbParEntry 25 }

    a200mprbparpcmtopkggain  OBJECT-TYPE
        SYNTAX      INTEGER(-20..20)
        MAX-ACCESS  read-write
        STATUS      current
        DESCRIPTION ""
        ::= { a200MprbParEntry 26 }

    a200mprbparpkgtopcmgain  OBJECT-TYPE
        SYNTAX      INTEGER(-20..20)
        MAX-ACCESS  read-write
        STATUS      current
        DESCRIPTION ""
        ::= { a200MprbParEntry 27 }

    a200mprbparfsklevel  OBJECT-TYPE
        SYNTAX      INTEGER(62..212)
        MAX-ACCESS  read-write
        STATUS      current
        DESCRIPTION ""
        ::= { a200MprbParEntry 28 }

    a200mprbpardtmfcidelec  OBJECT-TYPE
        SYNTAX      INTEGER(100..630)
        MAX-ACCESS  read-write
        STATUS      current
        DESCRIPTION ""
        ::= { a200MprbParEntry 29 }

    a200mprbparnortppktcheck  OBJECT-TYPE
        SYNTAX      INTEGER(0..65535)
        MAX-ACCESS  read-write
        STATUS      current
        DESCRIPTION ""
        ::= { a200MprbParEntry 30 }


-------------------------------------------------------------------------------
-- 4. zxAnRtpStatsMgmt
-------------------------------------------------------------------------------
    zxAnRtpStatsMgmt  OBJECT IDENTIFIER  ::= { zxAnVoipResource 50 }
    zxAnRtpPerfEnable  OBJECT-TYPE
        SYNTAX      INTEGER {
            enable(1),
            disable(2)
            }
        MAX-ACCESS  read-write
        STATUS      current
        DESCRIPTION
            " "
        ::= { zxAnRtpStatsMgmt 1 }

    zxAnRtpSenderPackets   OBJECT-TYPE
        SYNTAX          Counter64
        MAX-ACCESS      read-only
        STATUS          current
        DESCRIPTION
            "Count of RTP packets sent by this sender"
        ::= { zxAnRtpStatsMgmt 2 }

    zxAnRtpSenderOctets   OBJECT-TYPE
        SYNTAX          Counter64
        MAX-ACCESS      read-only
        STATUS          current
        DESCRIPTION
            "Count of non-header RTP octets sent by this sender,
             or observed  by an RTP monitor"
        ::= { zxAnRtpStatsMgmt 3 }

    zxAnRtpRcvrPackets   OBJECT-TYPE
        SYNTAX          Counter64
        MAX-ACCESS      read-only
        STATUS          current
        DESCRIPTION
            "Count of RTP packets received by this RTP host receiver"
        ::= { zxAnRtpStatsMgmt 4 }

    zxAnRtpRcvrOctets    OBJECT-TYPE
        SYNTAX          Counter64
        MAX-ACCESS      read-only
        STATUS          current
        DESCRIPTION
            "Count of non-header RTP octets received by this receiving RTP host"
        ::= { zxAnRtpStatsMgmt 5 }

    zxAnRtpRcvrAvgPacketLossRate   OBJECT-TYPE
        SYNTAX          INTEGER(0..100)
        MAX-ACCESS      read-only
        STATUS          current
        DESCRIPTION
            "Rate of RTP  packets lost as observed by this receiver"
        ::= { zxAnRtpStatsMgmt 6 }


    zxAnRtpRcvrAvgDelay   OBJECT-TYPE
        SYNTAX          Integer32
        UNITS           "milliseconds"
        MAX-ACCESS      read-only
        STATUS          current
        DESCRIPTION
            "Between receiving the last SR packet from source SSRC_n
             and sending this reception report block."
        ::= { zxAnRtpStatsMgmt 7 }

    zxAnRtpRcvrAvgJitter   OBJECT-TYPE
        SYNTAX          Integer32
        UNITS           "milliseconds"
        MAX-ACCESS      read-only
        STATUS          current
        DESCRIPTION
            "An estimate of delay variation as observed by this receiver."
        ::= { zxAnRtpStatsMgmt 8 }

-------------------------------------------------------------------------------
-- 5. zxAnNarrowbandCircuitResTable
-------------------------------------------------------------------------------
    zxAnNarrowbandCircuitResTable OBJECT-TYPE
        SYNTAX      SEQUENCE OF ZxAnNarrowbandCircuitResEntry
        MAX-ACCESS  not-accessible
        STATUS      current
        DESCRIPTION
            "ASASP"
        ::= { zxAnVoipResource 51 }

    zxAnNarrowbandCircuitResEntry OBJECT-TYPE
        SYNTAX       ZxAnNarrowbandCircuitResEntry
        MAX-ACCESS   not-accessible
        STATUS       current
        DESCRIPTION  ""
        INDEX {zxAnCircuitType}
        ::= { zxAnNarrowbandCircuitResTable 1 }

    ZxAnNarrowbandCircuitResEntry ::= SEQUENCE {
        zxAnCircuitType                 INTEGER,
        zxAnCircuitTotalNum             Integer32,
        zxAnCircuitBusyNum              Integer32,
        zxAnCircuitIdleNum              Integer32,
        zxAnCircuitBlockedNum           Integer32,
        zxAnCircuitOccupancy            INTEGER
        }

    zxAnCircuitType OBJECT-TYPE
        SYNTAX      INTEGER {
            typeSLC(1),
            typeIPS(2)
            }
        MAX-ACCESS  not-accessible
        STATUS      current
        DESCRIPTION ""
        ::= { zxAnNarrowbandCircuitResEntry 1 }

    zxAnCircuitTotalNum OBJECT-TYPE
        SYNTAX      Integer32
        MAX-ACCESS  read-only
        STATUS      current
        DESCRIPTION ""
        ::= { zxAnNarrowbandCircuitResEntry 2 }

    zxAnCircuitBusyNum OBJECT-TYPE
        SYNTAX      Integer32
        MAX-ACCESS  read-only
        STATUS      current
        DESCRIPTION ""
        ::= { zxAnNarrowbandCircuitResEntry 3 }

    zxAnCircuitIdleNum OBJECT-TYPE
        SYNTAX      Integer32
        MAX-ACCESS  read-only
        STATUS      current
        DESCRIPTION ""
        ::= { zxAnNarrowbandCircuitResEntry 4 }

    zxAnCircuitBlockedNum OBJECT-TYPE
        SYNTAX      Integer32
        MAX-ACCESS  read-only
        STATUS      current
        DESCRIPTION ""
        ::= { zxAnNarrowbandCircuitResEntry 5 }

    zxAnCircuitOccupancy  OBJECT-TYPE
        SYNTAX      INTEGER(0..100)
        MAX-ACCESS  read-only
        STATUS      current
        DESCRIPTION ""
        ::= { zxAnNarrowbandCircuitResEntry 6 }

-------------------------------------------------------------------------------
-- 6. zxAnToneTable
-------------------------------------------------------------------------------
    --msagChangeOidFromCallCtrl OBJECT IDENTIFIER ::= { zxAnVoiceMgmt 6 }

    zxAnToneTable OBJECT-TYPE
        SYNTAX      SEQUENCE OF ZxAnToneEntry
        MAX-ACCESS  not-accessible
        STATUS      current
        DESCRIPTION ""
        --::= { msagChangeOidFromCallCtrl 2 }
        ::= { zxAnVoipResource 1201 }

    zxAnToneEntry OBJECT-TYPE
        SYNTAX      ZxAnToneEntry
        MAX-ACCESS  not-accessible
        STATUS      current
        DESCRIPTION ""
        INDEX { zxAnToneMgId }
        ::={ zxAnToneTable 1 }

    ZxAnToneEntry ::= SEQUENCE {
        zxAnToneMgId                  INTEGER,
        zxAnToneFaxcngTone            INTEGER,
        zxAnToneV21FlagsTone          INTEGER,
        zxAnToneT38FaxEnd             INTEGER,
        zxAnToneAnsamwiTone           INTEGER,
        zxAnToneAnsamwoTone           INTEGER,
        zxAnToneAnswiTone             INTEGER,
        zxAnToneAnswoTone             INTEGER
        }

    zxAnToneMgId  OBJECT-TYPE
        SYNTAX      INTEGER(1..255)
        MAX-ACCESS  not-accessible
        STATUS      current
        DESCRIPTION ""
        ::= { zxAnToneEntry 1 }

    zxAnToneFaxcngTone  OBJECT-TYPE
        SYNTAX      INTEGER {
            notReport(0),
            report(1)
            }
        MAX-ACCESS  read-write
        STATUS      current
        DESCRIPTION ""
        ::= { zxAnToneEntry 2 }

    zxAnToneV21FlagsTone  OBJECT-TYPE
        SYNTAX      INTEGER {
            notReport(0),
            report(1)
            }
        MAX-ACCESS  read-write
        STATUS      current
        DESCRIPTION ""
        ::= { zxAnToneEntry 3 }

    zxAnToneT38FaxEnd  OBJECT-TYPE
        SYNTAX      INTEGER {
            notReport(0),
            report(1)
            }
        MAX-ACCESS  read-write
        STATUS      current
        DESCRIPTION ""
        ::= { zxAnToneEntry 4 }

    zxAnToneAnsamwiTone  OBJECT-TYPE
        SYNTAX      INTEGER {
            notReport(0),
            report(1)
            }
        MAX-ACCESS  read-write
        STATUS      current
        DESCRIPTION ""
        ::= { zxAnToneEntry 5 }

    zxAnToneAnsamwoTone  OBJECT-TYPE
        SYNTAX      INTEGER {
            notReport(0),
            report(1)
            }
        MAX-ACCESS  read-write
        STATUS      current
        DESCRIPTION ""
        ::= { zxAnToneEntry 6 }

    zxAnToneAnswiTone  OBJECT-TYPE
        SYNTAX      INTEGER {
            notReport(0),
            report(1)
            }
        MAX-ACCESS  read-write
        STATUS      current
        DESCRIPTION ""
        ::= { zxAnToneEntry 7 }

    zxAnToneAnswoTone  OBJECT-TYPE
        SYNTAX      INTEGER {
            notReport(0),
            report(1)
            }
        MAX-ACCESS  read-write
        STATUS      current
        DESCRIPTION ""
        ::= { zxAnToneEntry 8 }

-------------------------------------------------------------------------------
-- 7. a200AsigTable
-------------------------------------------------------------------------------
    a200AsigTable OBJECT-TYPE
        SYNTAX      SEQUENCE OF A200AsigEntry
        MAX-ACCESS  not-accessible
        STATUS      current
        DESCRIPTION
            "\u4fe1\u4ee4\u7535\u8def\u63cf\u8ff0\u8868\uff0c\u63cf\u8ff0MG
             \u4e2d\u4fe1\u4ee4\u7535\u8def\u7684\u72b6\u6001\u3001\u7c7b\u578b"
        ::= { zxAnVoipResource 3 }

    a200AsigEntry OBJECT-TYPE
        SYNTAX      A200AsigEntry
        MAX-ACCESS  not-accessible
        STATUS      current
        DESCRIPTION
            "describe colunms and index in slc table"
        INDEX { a200asigrackno, a200asigshelfno, a200asigslotno,
                a200asigsubdevno,a200asigindex }
        ::= { a200AsigTable 1 }

    A200AsigEntry ::= SEQUENCE {
        a200asigrackno        Integer32,
        a200asigshelfno       Integer32,
        a200asigslotno        Integer32,
        a200asigsubdevno      Integer32,
        a200asigindex         Integer32,
        a200asigstatus        Integer32,
        a200asigkind          INTEGER,
        a200asigoperNum       INTEGER,
        a200asigBlockOper     INTEGER,
        a200asigUnblockOper   INTEGER
        }

    a200asigrackno  OBJECT-TYPE
        SYNTAX      Integer32
        MAX-ACCESS  not-accessible
        STATUS      current
        DESCRIPTION ""
        ::= { a200AsigEntry 1 }

    a200asigshelfno  OBJECT-TYPE
        SYNTAX      Integer32
        MAX-ACCESS  not-accessible
        STATUS      current
        DESCRIPTION ""
        ::= { a200AsigEntry 2 }

    a200asigslotno  OBJECT-TYPE
        SYNTAX      Integer32
        MAX-ACCESS  not-accessible
        STATUS      current
        DESCRIPTION ""
        ::= { a200AsigEntry 3 }

    a200asigsubdevno  OBJECT-TYPE
        SYNTAX      Integer32
        MAX-ACCESS  not-accessible
        STATUS      current
        DESCRIPTION
            "\u4fe1\u4ee4\u7535\u8def\u6240\u5728\u7684\u677f\u5185
             \u5b50\u8bbe\u5907\u7f16\u53f7"
        ::= { a200AsigEntry 4 }

    a200asigindex   OBJECT-TYPE
        SYNTAX      Integer32
        MAX-ACCESS  not-accessible
        STATUS      current
        DESCRIPTION
            "\u4fe1\u4ee4\u7535\u8def\u5728\u677f\u5185\u5b50\u8bbe\u5907\u4e2d
             \u5e8f\u53f7"
        ::= { a200AsigEntry 5 }

    a200asigstatus   OBJECT-TYPE
        SYNTAX      Integer32
        MAX-ACCESS  read-only
        STATUS      current
        DESCRIPTION
            "\u7535\u8def\u72b6\u6001\uff0c\u6309\u4f4d\u53d6\u503c "
        ::= { a200AsigEntry 6 }

    a200asigkind  OBJECT-TYPE
        SYNTAX    INTEGER {
            dtmf(1),
            tone(2),
            cid(3),
            mfc(4),
            conf(5),
            mf(6)
            }
        MAX-ACCESS  read-write
        STATUS      current
        DESCRIPTION
            "\u7535\u8def\u7c7b\u578b:
             =1: DTMF
             =2: TONE
             =3: CID
             =4: MFC
             =5: CONF
             =6: MF "
        ::= { a200AsigEntry 7 }

    a200asigoperNum   OBJECT-TYPE
        SYNTAX      INTEGER(0..65535)
        MAX-ACCESS  read-write
        STATUS      current
        DESCRIPTION
             "end of the circuit No.,should be larger or equal to msagDspBegin"
        ::= { a200AsigEntry 8 }

    a200asigBlockOper   OBJECT-TYPE
        SYNTAX      INTEGER(1)
        MAX-ACCESS  read-write
        STATUS      current
        DESCRIPTION
            "block dsp"
        ::= { a200AsigEntry 9 }

    a200asigUnblockOper   OBJECT-TYPE
        SYNTAX      INTEGER(1)
        MAX-ACCESS  read-write
        STATUS      current
        DESCRIPTION
            "unblock dsp"
        ::= { a200AsigEntry 10 }


-------------------------------------------------------------------------------
-- 8. a200ConfTable
-------------------------------------------------------------------------------
    a200ConfTable OBJECT-TYPE
        SYNTAX      SEQUENCE OF A200ConfEntry
        MAX-ACCESS  not-accessible
        STATUS      current
        DESCRIPTION
            "\u4f1a\u8bae\u7535\u8bdd\u7535\u8def\u63cf\u8ff0\u8868\uff0c\u63cf
             \u8ff0\u4f1a\u8bae\u7535\u8bdd\u7535\u8def\u8d44\u6e90\u7684\u72b6
             \u6001\u3001\u7c7b\u578b"
        ::= { zxAnVoipResource 4 }

    a200ConfEntry OBJECT-TYPE
        SYNTAX      A200ConfEntry
        MAX-ACCESS  not-accessible
        STATUS      current
        DESCRIPTION
            "describe colunms and index in conf table"
        INDEX { a200confrackno, a200confshelfno, a200confslotno,
                a200confsubdevno,a200confindex }
        ::= { a200ConfTable 1 }

    A200ConfEntry ::= SEQUENCE {
        a200confrackno       Integer32,
        a200confshelfno      Integer32,
        a200confslotno       Integer32,
        a200confsubdevno     Integer32,
        a200confindex        Integer32,
        a200confstatus       Integer32,
        a200confset          Integer32,
        a200confgroup        Integer32,
        a200confoperNum      Integer32,
        a200confblockoper    INTEGER,
        a200confunblockoper  INTEGER
        }

    a200confrackno    OBJECT-TYPE
        SYNTAX      Integer32
        MAX-ACCESS  not-accessible
        STATUS      current
        DESCRIPTION ""
        ::= { a200ConfEntry 1 }

    a200confshelfno    OBJECT-TYPE
        SYNTAX      Integer32
        MAX-ACCESS  not-accessible
        STATUS      current
        DESCRIPTION ""
        ::= { a200ConfEntry 2 }

    a200confslotno    OBJECT-TYPE
        SYNTAX      Integer32
        MAX-ACCESS  not-accessible
        STATUS      current
        DESCRIPTION ""
        ::= { a200ConfEntry 3 }

    a200confsubdevno    OBJECT-TYPE
        SYNTAX      Integer32
        MAX-ACCESS  not-accessible
        STATUS      current
        DESCRIPTION
            "\u4f1a\u8bae\u7535\u8def\u6240\u5728\u7684\u677f\u5185\u5b50
             \u8bbe\u5907\u7f16\u53f7"
        ::= { a200ConfEntry 4 }

    a200confindex   OBJECT-TYPE
        SYNTAX      Integer32
        MAX-ACCESS  not-accessible
        STATUS      current
        DESCRIPTION
            "\u4f1a\u8bae\u7535\u8def\u5728\u677f\u5185\u5b50\u8bbe\u5907
            \u4e2d\u7684\u5e8f\u53f7"
        ::= { a200ConfEntry 5 }

    a200confstatus   OBJECT-TYPE
        SYNTAX      Integer32
        MAX-ACCESS  read-only
        STATUS      current
        DESCRIPTION
            "\u7535\u8def\u72b6\u6001\uff0c\u6309\u4f4d\u53d6\u503c"
        ::= { a200ConfEntry 6 }

    a200confset   OBJECT-TYPE
        SYNTAX      Integer32
        MAX-ACCESS  read-only
        STATUS      current
        DESCRIPTION
            "\u7535\u8def\u5f53\u524d\u6240\u5c5e\u7684\u4f1a\u8bae\u7ec4\u53f7"
        ::= { a200ConfEntry 7 }

    a200confgroup   OBJECT-TYPE
        SYNTAX      Integer32
        MAX-ACCESS  read-only
        STATUS      current
        DESCRIPTION
            "\u7535\u8def\u5f53\u524d\u6240\u5c5e\u7684\u4f1a\u8bae\u7fa4\u53f7"
        ::= { a200ConfEntry 8 }

    a200confoperNum   OBJECT-TYPE
        SYNTAX      Integer32
        MAX-ACCESS  read-write
        STATUS      current
        DESCRIPTION
            "end of the circuit No.,should be larger or equal to msagConfBegin"
        ::= { a200ConfEntry 9 }

    a200confblockoper   OBJECT-TYPE
        SYNTAX      INTEGER(1)
        MAX-ACCESS  read-write
        STATUS      current
        DESCRIPTION
            "block conferrence"
        ::= { a200ConfEntry 10 }

    a200confunblockoper   OBJECT-TYPE
        SYNTAX      INTEGER(1)
        MAX-ACCESS  read-write
        STATUS      current
        DESCRIPTION
            "unblock conferrence"
        ::= { a200ConfEntry 11 }

--------------------------------------------------------------------------------
-- 9. zxAnVoipResourceGlobalObjects
--------------------------------------------------------------------------------

    zxAnVoipResourceGlobalObjects OBJECT IDENTIFIER ::= { zxAnVoipResource 1200 }

    zxAnVoipResourceMgmtCapabilities OBJECT-TYPE
        SYNTAX      BITS {
            nbPlatform(0)
            }
        MAX-ACCESS  read-only
        STATUS      current
        DESCRIPTION
            "The VOIP resource management capabilities of this equipment.
            The bit value 1 means the function represented by this bit is
            supported by this equipment.
            bit 1: value 1 means support narrowband platform.
            NOTE: No recommended to display it in NMS."
        ::= { zxAnVoipResourceGlobalObjects 1 }

-------------------------------------------------------------------------------
-- 10. zxAnIpsStaticTerminationIdTable
-------------------------------------------------------------------------------
    zxAnIpsStaticTerminationIdTable OBJECT-TYPE
        SYNTAX      SEQUENCE OF ZxAnIpsStaticTerminationIdEntry
        MAX-ACCESS  not-accessible
        STATUS      current
        DESCRIPTION
            "IPS static termination ID table."
        ::= { zxAnVoipResource 1202 }

    zxAnIpsStaticTerminationIdEntry OBJECT-TYPE
        SYNTAX      ZxAnIpsStaticTerminationIdEntry
        MAX-ACCESS  not-accessible
        STATUS      current
        DESCRIPTION
            "IPS static termination ID entry."
        INDEX { zxAnIpsStaticTidRack, zxAnIpsStaticTidShelf,
                zxAnIpsStaticTidSlot, zxAnIpsStaticTidSubcard,
                zxAnIpsStaticTidSequenceNumber }
        ::= {zxAnIpsStaticTerminationIdTable 1 }

    ZxAnIpsStaticTerminationIdEntry ::= SEQUENCE {
        zxAnIpsStaticTidRack            Integer32,
        zxAnIpsStaticTidShelf           Integer32,
        zxAnIpsStaticTidSlot            Integer32,
        zxAnIpsStaticTidSubcard         Integer32,
        zxAnIpsStaticTidSequenceNumber  Integer32,
        zxAnIpsStaticTidOperNum         Integer32,
        zxAnIpsStaticTidType            INTEGER,
        zxAnIpsStaticTidPrefix          DisplayString,
        zxAnIpsStaticTidDigitLength     Integer32,
        zxAnIpsStaticTerminationId      DisplayString,
        zxAnIpsStaticTidRowStatus       RowStatus
        }

    zxAnIpsStaticTidRack  OBJECT-TYPE
        SYNTAX      Integer32
        MAX-ACCESS  not-accessible
        STATUS      current
        DESCRIPTION
            "Rack of IPS static termination ID."
        ::= { zxAnIpsStaticTerminationIdEntry 1 }

    zxAnIpsStaticTidShelf  OBJECT-TYPE
        SYNTAX      Integer32
        MAX-ACCESS  not-accessible
        STATUS      current
        DESCRIPTION
            "Shelf of IPS static termination ID."
        ::= { zxAnIpsStaticTerminationIdEntry 2 }

    zxAnIpsStaticTidSlot  OBJECT-TYPE
        SYNTAX      Integer32
        MAX-ACCESS  not-accessible
        STATUS      current
        DESCRIPTION
            "Slot of IPS static termination ID."
        ::= { zxAnIpsStaticTerminationIdEntry 3 }

    zxAnIpsStaticTidSubcard  OBJECT-TYPE
        SYNTAX      Integer32
        MAX-ACCESS  not-accessible
        STATUS      current
        DESCRIPTION
            "Sub-card of IPS static termination ID."
        ::= { zxAnIpsStaticTerminationIdEntry 4 }

    zxAnIpsStaticTidSequenceNumber  OBJECT-TYPE
        SYNTAX      Integer32
        MAX-ACCESS  not-accessible
        STATUS      current
        DESCRIPTION
            "Sequence number of IPS static termination ID."
        ::= { zxAnIpsStaticTerminationIdEntry 5 }

    zxAnIpsStaticTidOperNum  OBJECT-TYPE
        SYNTAX      Integer32
        MAX-ACCESS  read-create
        STATUS      current
        DESCRIPTION
            "Batch operation number.
             zxAnIpsStaticTidSequenceNumber means the start index number in
             batch operation."
        ::= { zxAnIpsStaticTerminationIdEntry 6 }

    zxAnIpsStaticTidType  OBJECT-TYPE
        SYNTAX      INTEGER {
            type1(1),
            type2(2),
            type3(3)
        }
        MAX-ACCESS  read-create
        STATUS      current
        DESCRIPTION
            "type1(1):RTP00100100000-RTP09909909999
             type2(2):RTP0-RTP9999
             type3(3):RTP00000-RTP09999."
        ::= { zxAnIpsStaticTerminationIdEntry 7 }

    zxAnIpsStaticTidPrefix  OBJECT-TYPE
        SYNTAX      DisplayString(SIZE (1..64))
        MAX-ACCESS  read-create
        STATUS      current
        DESCRIPTION
            "The termination ID's prefix.
            The termination ID's total length(prefix and digit) is 64."
        ::= { zxAnIpsStaticTerminationIdEntry 8 }

    zxAnIpsStaticTidDigitLength  OBJECT-TYPE
        SYNTAX      Integer32(0..64)
        MAX-ACCESS  read-create
        STATUS      current
        DESCRIPTION
            "The termination ID's digit length.
             Only valid when zxAnIpsStaticTidType is type3(3).
             The termination ID's total length(prefix and digit) is 64."
        ::= { zxAnIpsStaticTerminationIdEntry 9 }

    zxAnIpsStaticTerminationId  OBJECT-TYPE
        SYNTAX      DisplayString(SIZE (1..64))
        MAX-ACCESS  read-only
        STATUS      current
        DESCRIPTION
            "The termination ID of the IPS resource."
        ::= { zxAnIpsStaticTerminationIdEntry 10 }

    zxAnIpsStaticTidRowStatus  OBJECT-TYPE
        SYNTAX      RowStatus
        MAX-ACCESS  read-create
        STATUS      current
        DESCRIPTION
            "The row status of this entry."
        ::= { zxAnIpsStaticTerminationIdEntry 30}


-------------------------------------------------------------------------------
-- 11. zxAnSlcVoipStatsEnable
-------------------------------------------------------------------------------
    zxAnSlcVoipStatsEnable  OBJECT-TYPE
        SYNTAX      INTEGER {
            enable(1),
            disable(2)
            }
        MAX-ACCESS   read-write
        STATUS       current
        DESCRIPTION
           ""
        ::= {zxAnSlcVoipStatsMgmt 1}

-------------------------------------------------------------------------------
-- 12. zxAnSlcVoipStatsTable
-------------------------------------------------------------------------------
    zxAnSlcVoipStatsTable OBJECT-TYPE
        SYNTAX      SEQUENCE OF ZxAnSlcVoipStatsEntry
        MAX-ACCESS  not-accessible
        STATUS      current
        DESCRIPTION
            "ASASP"
        ::={zxAnSlcVoipStatsMgmt 10}

    zxAnSlcVoipStatsEntry OBJECT-TYPE
        SYNTAX      ZxAnSlcVoipStatsEntry
        MAX-ACCESS  not-accessible
        STATUS      current
        DESCRIPTION
            ""
        INDEX {zxAnSlcVoipRack, zxAnSlcVoipShelf, zxAnSlcVoipSlot,
               zxAnSlcVoipPort }
        ::={zxAnSlcVoipStatsTable 1}


    ZxAnSlcVoipStatsEntry ::=
        SEQUENCE    {
           zxAnSlcVoipRack                              Integer32,
           zxAnSlcVoipShelf                             Integer32,
           zxAnSlcVoipSlot                              Integer32,
           zxAnSlcVoipPort                              Integer32,

           zxAnSlcVoipRtpSenderPackets                  Counter64,
           zxAnSlcVoipRtpRcvrPackets                    Counter64,

           zxAnSlcVoipSipIncomingCalls                  Counter32,
           zxAnSlcVoipSipOutgoingCalls                  Counter32,

           zxAnSlcVoipH248IncomingCalls                 Counter32,
           zxAnSlcVoipH248OutgoingCalls                 Counter32,

           zxAnSlcRtpSessionRecordTime                  DisplayString,
           zxAnSlcRtpSessionSenderPkts                  Counter32,
           zxAnSlcRtpSessionRcvrPkts                    Counter32,
           zxAnSlcRtpSessionSenderOctets                Counter32,
           zxAnSlcRtpSessionRcvrOctets                  Counter32,
           zxAnSlcRtpSessionRcvrPlr                     Integer32,
           zxAnSlcRtpSessionRcvrAvgDelay                Integer32,
           zxAnSlcRtpSessionRcvrAvgJitter               Gauge32,

           zxAnSlcVoipIncomingCalls                     Counter32,
           zxAnSlcVoipOutgoingCalls                     Counter32,
           zxAnSlcVoipIncomingCallKeepTime              Integer32,
           zxAnSlcVoipOutgoingCallKeepTime              Integer32,
           zxAnSlcVoipCurrInCallKeepTime                Integer32,
           zxAnSlcVoipCurrOutCallKeepTime               Integer32
        }

    zxAnSlcVoipRack         OBJECT-TYPE
        SYNTAX          Integer32
        MAX-ACCESS      not-accessible
        STATUS          current
        DESCRIPTION
            "Rack of media session statistics item "
        DEFVAL{1}
        ::={zxAnSlcVoipStatsEntry 1}

    zxAnSlcVoipShelf        OBJECT-TYPE
        SYNTAX          Integer32
        MAX-ACCESS      not-accessible
        STATUS          current
        DESCRIPTION
            "Shelf of media session statistics item"
        DEFVAL { 1 }
        ::={zxAnSlcVoipStatsEntry 2}

    zxAnSlcVoipSlot         OBJECT-TYPE
        SYNTAX          Integer32
        MAX-ACCESS      not-accessible
        STATUS          current
        DESCRIPTION
            "Slot of media session statistics  item"
        DEFVAL { 3 }
        ::={zxAnSlcVoipStatsEntry 3}

    zxAnSlcVoipPort         OBJECT-TYPE
        SYNTAX          Integer32
        MAX-ACCESS      not-accessible
        STATUS          current
        DESCRIPTION
            "Port of media session statistics item"
        DEFVAL { 1 }
        ::={zxAnSlcVoipStatsEntry 4}

    zxAnSlcVoipRtpSenderPackets   OBJECT-TYPE
        SYNTAX          Counter64
        MAX-ACCESS      read-only
        STATUS          current
        DESCRIPTION
            "Count of RTP sent packets."
        ::= { zxAnSlcVoipStatsEntry 5 }

    zxAnSlcVoipRtpRcvrPackets   OBJECT-TYPE
        SYNTAX          Counter64
        MAX-ACCESS      read-only
        STATUS          current
        DESCRIPTION
            "Count of RTP receive packets ."
        ::= { zxAnSlcVoipStatsEntry 6 }

    zxAnSlcVoipSipIncomingCalls   OBJECT-TYPE
        SYNTAX          Counter32
        MAX-ACCESS      read-only
        STATUS          current
        DESCRIPTION
            "Count of the  SIP incomming calls."
        ::= { zxAnSlcVoipStatsEntry 7}

    zxAnSlcVoipSipOutgoingCalls   OBJECT-TYPE
        SYNTAX          Counter32
        MAX-ACCESS      read-only
        STATUS          current
        DESCRIPTION     "Count of the SIP outgoing calls ."
        ::= { zxAnSlcVoipStatsEntry 8 }

    zxAnSlcVoipH248IncomingCalls   OBJECT-TYPE
        SYNTAX          Counter32
        MAX-ACCESS      read-only
        STATUS          current
        DESCRIPTION     "Count of the  H.248 incomming calls."
        ::= { zxAnSlcVoipStatsEntry 9}

    zxAnSlcVoipH248OutgoingCalls   OBJECT-TYPE
        SYNTAX          Counter32
        MAX-ACCESS      read-only
        STATUS          current
        DESCRIPTION     "Count of the  H.248 outgoing calls."
        ::= { zxAnSlcVoipStatsEntry 10 }

    zxAnSlcRtpSessionRecordTime      OBJECT-TYPE
        SYNTAX          DisplayString  ( SIZE ( 1 .. 20  ) )
        MAX-ACCESS      read-only
        STATUS          current
        DESCRIPTION     "Time Stamp of the updated session record.For example:
          yyyy-mm-dd HH:MM:SS.(2001-01-01 02:22:33)."
        ::= { zxAnSlcVoipStatsEntry 11 }

    zxAnSlcRtpSessionSenderPkts   OBJECT-TYPE
        SYNTAX          Counter32
        MAX-ACCESS      read-only
        STATUS          current
        DESCRIPTION     "Count of RTP packets sent by this sender of the last
          session"
        ::= { zxAnSlcVoipStatsEntry 12 }

    zxAnSlcRtpSessionRcvrPkts   OBJECT-TYPE
        SYNTAX          Counter32
        MAX-ACCESS      read-only
        STATUS          current
        DESCRIPTION     "Count of RTP packets received by this RTP host
          receiver of the last session"
        ::= { zxAnSlcVoipStatsEntry 13 }

    zxAnSlcRtpSessionSenderOctets   OBJECT-TYPE
        SYNTAX          Counter32
        MAX-ACCESS      read-only
        STATUS          current
        DESCRIPTION     "Count of non-header RTP octets sent by this sender,
          or observed  by an RTP monitor of the last session"
        ::= { zxAnSlcVoipStatsEntry 14 }

    zxAnSlcRtpSessionRcvrOctets    OBJECT-TYPE
        SYNTAX          Counter32
        MAX-ACCESS      read-only
        STATUS          current
        DESCRIPTION     "Count of non-header RTP octets received by this
          receiving RTP host of the last session"
        ::= { zxAnSlcVoipStatsEntry 15 }

    zxAnSlcRtpSessionRcvrPlr   OBJECT-TYPE
        SYNTAX          Integer32(1..100)
        MAX-ACCESS      read-only
        STATUS          current
        DESCRIPTION     "Rate of RTP  packets lost as observed by this
          receiver of the last session"
        ::= { zxAnSlcVoipStatsEntry 16 }

    zxAnSlcRtpSessionRcvrAvgDelay   OBJECT-TYPE
        SYNTAX          Integer32
        UNITS           "milli-seconds"
        MAX-ACCESS      read-only
        STATUS          current
        DESCRIPTION     "The average time between receiving the last SR packet
          from source SSRC_n and sending this reception report block of this
          session"
        ::= { zxAnSlcVoipStatsEntry 17 }

    zxAnSlcRtpSessionRcvrAvgJitter   OBJECT-TYPE
        SYNTAX          Gauge32
        MAX-ACCESS      read-only
        STATUS          current
        DESCRIPTION     "An estimate of delay variation as observed by
          this receiver of this session"
        ::= { zxAnSlcVoipStatsEntry 18 }

    zxAnSlcVoipIncomingCalls   OBJECT-TYPE
        SYNTAX          Counter32
        MAX-ACCESS      read-only
        STATUS          current
        DESCRIPTION     "Count of incoming calls of this port."
        ::= { zxAnSlcVoipStatsEntry 31 }

    zxAnSlcVoipOutgoingCalls   OBJECT-TYPE
        SYNTAX          Counter32
        MAX-ACCESS      read-only
        STATUS          current
        DESCRIPTION     "Count of outgoing calls of this port."
        ::= { zxAnSlcVoipStatsEntry 32 }

    zxAnSlcVoipIncomingCallKeepTime   OBJECT-TYPE
        SYNTAX          Integer32
        UNITS           "seconds"
        MAX-ACCESS      read-only
        STATUS          current
        DESCRIPTION     "Total incoming call keeping time of this port."
        ::= { zxAnSlcVoipStatsEntry 33 }

    zxAnSlcVoipOutgoingCallKeepTime   OBJECT-TYPE
        SYNTAX          Integer32
        UNITS           "seconds"
        MAX-ACCESS      read-only
        STATUS          current
        DESCRIPTION     "Total outgoing call keeping time of this port."
        ::= { zxAnSlcVoipStatsEntry 34 }


    zxAnSlcVoipCurrInCallKeepTime   OBJECT-TYPE
        SYNTAX          Integer32
        UNITS           "seconds"
        MAX-ACCESS      read-only
        STATUS          current
        DESCRIPTION     "Current incoming call keeping time of this port.
                        When current call is outgoing call,
                        the value must be zero."
        ::= { zxAnSlcVoipStatsEntry 35 }

    zxAnSlcVoipCurrOutCallKeepTime   OBJECT-TYPE
        SYNTAX          Integer32
        UNITS           "seconds"
        MAX-ACCESS      read-only
        STATUS          current
        DESCRIPTION     "Current outgoing call keeping time of this port.
                        When current call is incoming call,
                        the value must be zero."
        ::= { zxAnSlcVoipStatsEntry 36 }
END
