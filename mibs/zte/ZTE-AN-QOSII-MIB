--------------------------------------------------------------------------------
-- File Name : ZTE-AN-QOSII-MIB.mib
-- Date      : 2008-07-18
-- Author    : ZTE Nms dept.

--
-- Zte Qos Mib for Access Node
--
--
--------------------------------------------------------------------------------
    ZTE-AN-QOSII-MIB    DEFINITIONS ::= BEGIN
        IMPORTS
            RowStatus                                   FROM SNMPv2-TC
            MODULE-IDENTITY, OBJECT-TYPE,Integer32      FROM SNMPv2-SMI
            ifIndex                                     FROM IF-MIB
            zxAn                                        FROM ZTE-AN-TC-MIB
            DisplayString                               FROM RFC1213-MIB;

    zxAnQosMib    MODULE-IDENTITY
        LAST-UPDATED    "200807181326Z"
        ORGANIZATION    "ZTE Corporation"
        CONTACT-INFO    "
                        Mail: @zte.com.cn
                        Tel : "
        DESCRIPTION     "This MIB defines zte Access Node Qos managed objects."
        ::=  {  zxAn  21  }

    zxAnQosIIObjects       OBJECT IDENTIFIER   ::=  { zxAnQosMib 3 }

    zxAnQosIINniGlobal       OBJECT IDENTIFIER   ::=  { zxAnQosIIObjects 5 }
--------------------------------------------------------------------------------
-- Following objects are defined.

-- Nni qos objects
-- 1. zxAnQosIINniCos2DropMap
-- 2. zxAnQosIINniCos2LocalMap
-- 3. zxAnQosIINniDscpMappingTable
-- 4. zxAnQosIINniPortCfgTable
-- 5. zxAnQosIINniGlobal

-- Global qos objects
-- 6. zxAnQosIICos2DscpTable
-- 7. zxAnQosIIDscp2CosTable
-- 17.zxAnQosIIMVlan2CosTable

-- Qos profile objects
-- 8. zxAnQosIICosQueuesProfileTable
-- 9. zxAnQosIIQueuesBlockProfileTable
-- 10.zxAnQosIICosRemarkProfileTable
-- 11.zxAnQosIITrafficProfileTable
-- 12.zxAnQosIIVportProfileTable

-- Physical port profile binding objects
-- 13.zxAnQosIIPortCfgTable

-- Virtual port profile binding objects
-- 14.zxAnQosIIVPortCfgTable
-- 15.zxAnQosIITrafficCfgTable
-- 16.zxAnQosIIRemainingBandwidthTable

--------------------------------------------------------------------------------
-- 1. zxAnQosIINniCos2DropMap
--------------------------------------------------------------------------------
    zxAnQosIINniCos2DropMap OBJECT-TYPE
        SYNTAX      OCTET STRING(SIZE (8))
        MAX-ACCESS  read-write
        STATUS      current
        DESCRIPTION
            "Configure cos drop map parameters"
        ::= { zxAnQosIIObjects 1 }

--------------------------------------------------------------------------------
-- 2. zxAnQosIINniCos2LocalMap
--------------------------------------------------------------------------------
    zxAnQosIINniCos2LocalMap OBJECT-TYPE
        SYNTAX      OCTET STRING(SIZE (8))
        MAX-ACCESS  read-write
        STATUS      current
        DESCRIPTION
            "Configure cos local map parameters"
        ::= { zxAnQosIIObjects 2 }

--------------------------------------------------------------------------------
-- 3. zxAnQosIINniDscpMappingTable
--------------------------------------------------------------------------------
    zxAnQosIINniDscpMappingTable OBJECT-TYPE
        SYNTAX      SEQUENCE OF ZxAnQosIINniDscpMappingEntry
        MAX-ACCESS  not-accessible
        STATUS      current
        DESCRIPTION
            "This table qos Dscp map configuration.It is used
            for a network-side."
        ::=  { zxAnQosIIObjects  3 }

    zxAnQosIINniDscpMappingEntry OBJECT-TYPE
        SYNTAX      ZxAnQosIINniDscpMappingEntry
        MAX-ACCESS  not-accessible
        STATUS      current
        DESCRIPTION
            "An entry for zxAnQosIINniDscpMappingTable."
        INDEX   {  zxAnQosIINniIngressDscp }
        ::=  { zxAnQosIINniDscpMappingTable 1 }

    ZxAnQosIINniDscpMappingEntry  ::=
        SEQUENCE {
            zxAnQosIINniIngressDscp             INTEGER,
            zxAnQosIINniEgressDscp              INTEGER,
            zxAnQosIINniEgressCos               INTEGER,
            zxAnQosIINniEgressDropPrecedence    INTEGER
        }

    zxAnQosIINniIngressDscp  OBJECT-TYPE
        SYNTAX      INTEGER(0..63)
        MAX-ACCESS  not-accessible
        STATUS      current
        DESCRIPTION
            "Dscp index."
        ::= { zxAnQosIINniDscpMappingEntry 1 }

    zxAnQosIINniEgressDscp  OBJECT-TYPE
        SYNTAX      INTEGER(0..63)
        MAX-ACCESS  read-write
        STATUS      current
        DESCRIPTION
            "Map Dscp value."
        DEFVAL      { 0 }
        ::= { zxAnQosIINniDscpMappingEntry 2 }

    zxAnQosIINniEgressCos  OBJECT-TYPE
        SYNTAX      INTEGER(0..7)
        MAX-ACCESS  read-write
        STATUS      current
        DESCRIPTION
            "Map Cos value."
        DEFVAL      { 0 }
        ::= { zxAnQosIINniDscpMappingEntry 3 }

    zxAnQosIINniEgressDropPrecedence  OBJECT-TYPE
        SYNTAX      INTEGER(0..2)
        MAX-ACCESS  read-write
        STATUS      current
        DESCRIPTION
            "Map drop precedence value."
        DEFVAL      { 0 }
        ::= { zxAnQosIINniDscpMappingEntry 4 }

--------------------------------------------------------------------------------
-- 4. zxAnQosIINniPortCfgTable
--------------------------------------------------------------------------------
    zxAnQosIINniPortCfgTable OBJECT-TYPE
        SYNTAX      SEQUENCE  OF ZxAnQosIINniPortCfgEntry
        MAX-ACCESS  not-accessible
        STATUS      current
        DESCRIPTION
            "This table includes interface qos configuration.It is used
            for a Network-side port(interface)."
        ::=  { zxAnQosIIObjects  4 }

    zxAnQosIINniPortCfgEntry OBJECT-TYPE
        SYNTAX      ZxAnQosIINniPortCfgEntry
        MAX-ACCESS  not-accessible
        STATUS      current
        DESCRIPTION
            "An entry in zxAnQosIINniPortProfileTable."
        INDEX       { ifIndex }
        ::=  { zxAnQosIINniPortCfgTable 1 }

    ZxAnQosIINniPortCfgEntry  ::=
        SEQUENCE {
            zxAnQosIINniDefPriority            INTEGER,
            zxAnQosIINniTrustDscp              INTEGER,
            zxAnQosIINniTrustCos               INTEGER,
            zxAnQosIINniQueuesAlgorithm        INTEGER,
            zxAnQosIINniQueuesWeight           OBJECT IDENTIFIER,
            zxAnQosIINniQueuesMinRate          OBJECT IDENTIFIER,
            zxAnQosIINniQueuesMaxRate          OBJECT IDENTIFIER,
            zxAnQosIINniShapeRateLimit         Integer32,
            zxAnQosIINniShapeBurstSize         Integer32,
            zxAnQosIINniQueuesDepth            OBJECT IDENTIFIER
        }

    zxAnQosIINniDefPriority  OBJECT-TYPE
        SYNTAX      INTEGER(0..7)
        MAX-ACCESS  read-create
        STATUS      current
        DESCRIPTION
            "The default priority for untag packets"
        ::= { zxAnQosIINniPortCfgEntry 1 }

    zxAnQosIINniTrustDscp  OBJECT-TYPE
        SYNTAX      INTEGER
        {
            enable(1),
            disable(2),
            notsupport(255)
        }
        MAX-ACCESS  read-create
        STATUS      current
        DESCRIPTION
            "Enable or Disable the Dscp trust."
        DEFVAL      { disable }
        ::= { zxAnQosIINniPortCfgEntry 2 }

    zxAnQosIINniTrustCos  OBJECT-TYPE
        SYNTAX      INTEGER
        {
            enable(1),
            disable(2),
            notsupport(255)
        }
        MAX-ACCESS  read-create
        STATUS      current
        DESCRIPTION
            "Enable or Disable the Cos trust."
        DEFVAL      { disable }
        ::= { zxAnQosIINniPortCfgEntry 3 }

    zxAnQosIINniQueuesAlgorithm OBJECT-TYPE
        SYNTAX  INTEGER
        {
            sp(1),     -- Strict Priority (SP)
            wrr(2),    -- Weighted Round Robin (WRR)
            fq(3)      -- Fair Queue (FQ)
        }
        MAX-ACCESS  read-create
        STATUS      current
        DESCRIPTION
            "The scheduling algorithm of queues. "
        DEFVAL      { sp }
        ::=  {  zxAnQosIINniPortCfgEntry  4  }

    zxAnQosIINniQueuesWeight     OBJECT-TYPE
        SYNTAX      OBJECT IDENTIFIER
        MAX-ACCESS  read-create
        STATUS      current
        DESCRIPTION
            "The integer sequence of queque's weight.The size of
            sequence is 8 and it presents weights for 8 queques.
            For example,the value {1.2.3.4.5.6.7.8 } means weight of queue0 is 1,
            weight of queue1 is 2,...,weight of queue7 is 8.
            The range of each weight is 0 to 15.
            The weight is relevant only when the same Queue Priority value is
            assigned to multiple queues and they are scheduled according to a
            weighted algorithm. "
        ::=  {  zxAnQosIINniPortCfgEntry  5  }

    zxAnQosIINniQueuesMinRate     OBJECT-TYPE
        SYNTAX      OBJECT IDENTIFIER
        MAX-ACCESS  read-create
        STATUS      current
        DESCRIPTION
            "The integer sequence of queue's minrate.The size of
            sequence is 8 and it presents min rate for 8 queques.
            For example,the value {100.200.300.400.
            500.600.700.800} means queue1's min rate
            is both 100kbps,....,
            The range of each rate is 0 to 1000000.
            The unit is kbps."
        ::=  {  zxAnQosIINniPortCfgEntry  6  }

    zxAnQosIINniQueuesMaxRate     OBJECT-TYPE
        SYNTAX      OBJECT IDENTIFIER
        MAX-ACCESS  read-create
        STATUS      current
        DESCRIPTION
            "The integer sequence of queue's max rate.The size of
            sequence is 8 and it presents max rate for 8 queques.
            For example,the value {100.200.300.400.
            500.600.700.800} means queue1's max rate
            is both 100kbps,....,
            The range of each rate is 0 to 1000000.
            The unit is kbps."
        ::=  {  zxAnQosIINniPortCfgEntry  7  }

    zxAnQosIINniShapeRateLimit  OBJECT-TYPE
        SYNTAX      Integer32(0|64..1000000)
        UNITS       "kbps"
        MAX-ACCESS  read-create
        STATUS      current
        DESCRIPTION
            "The rate-limit of interface's Sharp,
            0 as not limit"
        ::=  {  zxAnQosIINniPortCfgEntry  8  }

    zxAnQosIINniShapeBurstSize OBJECT-TYPE
        SYNTAX      Integer32(0|4..16000)
        UNITS       "kbps"
        MAX-ACCESS  read-create
        STATUS      current
        DESCRIPTION
            "The burst-size of interface's Sharp,
            0 as not sharp."
        ::=  {  zxAnQosIINniPortCfgEntry  9  }

     zxAnQosIINniQueuesDepth     OBJECT-TYPE
         SYNTAX      OBJECT IDENTIFIER
         MAX-ACCESS  read-create
         STATUS      current
         DESCRIPTION
             "The integer sequence of queque's depth,The range of each maxSize is 1 to 256,units is 2k bytes."
        ::=  {  zxAnQosIINniPortCfgEntry  10 }

--------------------------------------------------------------------------------
-- 5. zxAnQosIINniGlobal
--------------------------------------------------------------------------------
    zxAnQosIINniGlobalTrustMode  OBJECT-TYPE
        SYNTAX      INTEGER
        {
            untrust(1),
            trustcosonly(2),
            trustdscponly(3),
            notsupport(255)
        }
        MAX-ACCESS  read-create
        STATUS      current
        DESCRIPTION
            "NNI Trust Mode."
        DEFVAL      { untrust }
        ::= { zxAnQosIINniGlobal 1 }
--------------------------------------------------------------------------------
-- 6. zxAnQosIICos2DscpTable
--------------------------------------------------------------------------------
    zxAnQosIICos2DscpTable OBJECT-TYPE
        SYNTAX      SEQUENCE OF ZxAnQosIICos2DscpEntry
        MAX-ACCESS  not-accessible
        STATUS      current
        DESCRIPTION
            "The CoS mapping table given DSCP value."
        ::=  { zxAnQosIIObjects  10 }

    zxAnQosIICos2DscpEntry OBJECT-TYPE
        SYNTAX      ZxAnQosIICos2DscpEntry
        MAX-ACCESS  not-accessible
        STATUS      current
        DESCRIPTION
            "An entry (conceptual row) representing a CoS to DSCP
            mapping table."
        INDEX       { zxAnQosIICos2DscpCosValue }
        ::=  { zxAnQosIICos2DscpTable 1 }

    ZxAnQosIICos2DscpEntry  ::=  SEQUENCE
    {
        zxAnQosIICos2DscpCosValue    INTEGER,
        zxAnQosIICos2DscpDscpValue   INTEGER
    }

    zxAnQosIICos2DscpCosValue OBJECT-TYPE
        SYNTAX      INTEGER(0..7)
        MAX-ACCESS  not-accessible
        STATUS      current
        DESCRIPTION
            "The CoS value."
        ::=  {  zxAnQosIICos2DscpEntry  1  }

    zxAnQosIICos2DscpDscpValue OBJECT-TYPE
        SYNTAX      INTEGER(0..63)
        MAX-ACCESS  read-write
        STATUS      current
        DESCRIPTION
            "DSCP value corresponding to zxAnQosIICos2DscpCosValue."
        ::=  {  zxAnQosIICos2DscpEntry  2  }

--------------------------------------------------------------------------------
-- 7. zxAnQosIIDscp2CosTable
--------------------------------------------------------------------------------

    zxAnQosIIDscp2CosTable OBJECT-TYPE
        SYNTAX      SEQUENCE OF ZxAnQosIIDscp2CosEntry
        MAX-ACCESS  not-accessible
        STATUS      current
        DESCRIPTION
            "The DSCP mapping table given CoS value."
        ::=  { zxAnQosIIObjects  11 }

    zxAnQosIIDscp2CosEntry OBJECT-TYPE
        SYNTAX      ZxAnQosIIDscp2CosEntry
        MAX-ACCESS  not-accessible
        STATUS      current
        DESCRIPTION
            "An entry (conceptual row) representing a DSCP to CoS
            mapping table."
        INDEX       {  zxAnQosIIDscp2CosDscpValue  }
        ::=  { zxAnQosIIDscp2CosTable 1 }

    ZxAnQosIIDscp2CosEntry  ::=  SEQUENCE
    {
        zxAnQosIIDscp2CosDscpValue   INTEGER,
        zxAnQosIIDscp2CosCosValue    INTEGER
    }

    zxAnQosIIDscp2CosDscpValue OBJECT-TYPE
        SYNTAX      INTEGER(0..63)
        MAX-ACCESS  not-accessible
        STATUS      current
        DESCRIPTION
            "DSCP value."
        ::=  {  zxAnQosIIDscp2CosEntry  1  }

    zxAnQosIIDscp2CosCosValue OBJECT-TYPE
        SYNTAX      INTEGER(0..7)
        MAX-ACCESS  read-write
        STATUS      current
        DESCRIPTION
            "The CoS value corresponding to zxAnQosIIDscp2CosDscp."
        ::=  {  zxAnQosIIDscp2CosEntry  2  }

--------------------------------------------------------------------------------
-- 17. zxAnQosIIMVlan2CosTable
--------------------------------------------------------------------------------

    zxAnQosIIMVlan2CosTable OBJECT-TYPE
        SYNTAX      SEQUENCE OF ZxAnQosIIMVlan2CosEntry
        MAX-ACCESS  not-accessible
        STATUS      current
        DESCRIPTION
            "MVLAN-to-CoS mapping table. The table contains MVLAN-to-CoS mapping
            information used to remark CoS for the egress traffic of UNI port."
        ::=  { zxAnQosIIObjects  25 }

    zxAnQosIIMVlan2CosEntry OBJECT-TYPE
        SYNTAX      ZxAnQosIIMVlan2CosEntry
        MAX-ACCESS  not-accessible
        STATUS      current
        DESCRIPTION
            "MVLAN-to-CoS mapping entry."
        INDEX       {  zxAnQosIIMVlan2CosMVlanValue  }
        ::=  { zxAnQosIIMVlan2CosTable 1 }

    ZxAnQosIIMVlan2CosEntry  ::=  SEQUENCE
    {
        zxAnQosIIMVlan2CosMVlanValue   INTEGER,
        zxAnQosIIMVlan2CosCosValue     INTEGER,
        zxAnQosIIMVlan2CosRowStatus    RowStatus
    }

    zxAnQosIIMVlan2CosMVlanValue OBJECT-TYPE
        SYNTAX      INTEGER(1..4095)
        MAX-ACCESS  not-accessible
        STATUS      current
        DESCRIPTION
            "MVLAN."
        ::=  {  zxAnQosIIMVlan2CosEntry  1  }

    zxAnQosIIMVlan2CosCosValue OBJECT-TYPE
        SYNTAX      INTEGER(0..7)
        MAX-ACCESS  read-create
        STATUS      current
        DESCRIPTION
            "The CoS value corresponding to MVLAN."
        ::=  {  zxAnQosIIMVlan2CosEntry  2  }

    zxAnQosIIMVlan2CosRowStatus OBJECT-TYPE
        SYNTAX      RowStatus
        MAX-ACCESS  read-create
        STATUS      current
        DESCRIPTION
            "The row status of this entry."
        ::= { zxAnQosIIMVlan2CosEntry 20 }

--------------------------------------------------------------------------------
-- 8. zxAnQosIICosQueuesProfileTable
--------------------------------------------------------------------------------
    zxAnQosIICos2QueuesProfileTable  OBJECT-TYPE
        SYNTAX      SEQUENCE  OF  ZxAnQosIICos2QueuesProfileEntry
        MAX-ACCESS  not-accessible
        STATUS      current
        DESCRIPTION
            "This table includes CoS queue mapping profile configuration."
        ::=  { zxAnQosIIObjects  13 }

    zxAnQosIICos2QueuesProfileEntry  OBJECT-TYPE
        SYNTAX      ZxAnQosIICos2QueuesProfileEntry
        MAX-ACCESS  not-accessible
        STATUS      current
        DESCRIPTION
            "An entry in zxAnQosIICosQueuesProfileTable."
        INDEX       { zxAnQosIICos2QueuesPrfName }
        ::=  { zxAnQosIICos2QueuesProfileTable 1 }

    ZxAnQosIICos2QueuesProfileEntry  ::=
        SEQUENCE {
            zxAnQosIICos2QueuesPrfName      DisplayString,
            zxAnQosIICos2Queues             OBJECT IDENTIFIER,
            zxAnQosIIDropPrecedence         OBJECT IDENTIFIER,
            zxAnQosIICos2QueuesRowStatus    RowStatus
        }

    zxAnQosIICos2QueuesPrfName  OBJECT-TYPE
        SYNTAX      DisplayString(SIZE(1..32))
        MAX-ACCESS  not-accessible
        STATUS      current
        DESCRIPTION
            "The profile name is a display string.It is a index of
            this table."
        ::=  {  zxAnQosIICos2QueuesProfileEntry  1  }

    zxAnQosIICos2Queues OBJECT-TYPE
        SYNTAX      OBJECT IDENTIFIER
        MAX-ACCESS  read-create
        STATUS      current
        DESCRIPTION
            "The integer sequence of queues id mapped to priority .
            The size of sequence is 8 and it presents 8 queque id for 8 priority.
            For example,the value {1.2.3.4.5.6.7.8 } means priority0 is mapping to
            queue0,priority1 is mapping to queue1,...,priority7 is mapping to
            queue7."
        ::=  {  zxAnQosIICos2QueuesProfileEntry  2  }

    zxAnQosIIDropPrecedence OBJECT-TYPE
        SYNTAX      OBJECT IDENTIFIER
        MAX-ACCESS  read-create
        STATUS      current
        DESCRIPTION
            "The integer sequence of drop-precedence if congestion occurs.
            The size of sequence is 8 and it presents 8 drop-precedence for 8 priority.
            For example,the value {1.2.2.2.2.2.2.0 } means drop-precedence of priority0 is 1,
            ...,drop-precedence of priority7 is 0.
            255.255.255.255.255.255.255.255 means not support"
        ::= { zxAnQosIICos2QueuesProfileEntry 3 }

    zxAnQosIICos2QueuesRowStatus  OBJECT-TYPE
        SYNTAX      RowStatus
        MAX-ACCESS  read-create
        STATUS      current
        DESCRIPTION
            "This object is used to create a new row or to modify or
           delete an existing row in this table"
        ::=  {  zxAnQosIICos2QueuesProfileEntry  20  }

--------------------------------------------------------------------------------
-- 9. zxAnQosIIQueuesBlockProfileTable
--------------------------------------------------------------------------------
    zxAnQosIIQueuesBlockProfileTable OBJECT-TYPE
        SYNTAX      SEQUENCE  OF  ZxAnQosIIQueuesBlockProfileEntry
        MAX-ACCESS  not-accessible
        STATUS      current
        DESCRIPTION
            "This table includes queue block profile configuration."
        ::=  { zxAnQosIIObjects  14 }

    zxAnQosIIQueuesBlockProfileEntry OBJECT-TYPE
        SYNTAX      ZxAnQosIIQueuesBlockProfileEntry
        MAX-ACCESS  not-accessible
        STATUS      current
        DESCRIPTION
            "An entry in zxAnQosIIQueuesBlockProfileTable."
        INDEX   {  zxAnQosIIQueuesBlockPrfName }
        ::=  { zxAnQosIIQueuesBlockProfileTable 1 }

    ZxAnQosIIQueuesBlockProfileEntry  ::=
        SEQUENCE {
            zxAnQosIIQueuesBlockPrfName      DisplayString,
            zxAnQosIIQueuesPriority          OBJECT IDENTIFIER,
            zxAnQosIIQueuesWeight            OBJECT IDENTIFIER,
            zxAnQosIIQueuesDepth             OBJECT IDENTIFIER,
            zxAnQosIIQueuesBlockRowStatus    RowStatus
        }

    zxAnQosIIQueuesBlockPrfName OBJECT-TYPE
        SYNTAX      DisplayString(SIZE(1..32))
        MAX-ACCESS  not-accessible
        STATUS      current
        DESCRIPTION
            "The profile name is a display string.It is a index of
            this table."
        ::=  {  zxAnQosIIQueuesBlockProfileEntry  1  }

     zxAnQosIIQueuesPriority     OBJECT-TYPE
        SYNTAX      OBJECT IDENTIFIER
        MAX-ACCESS  read-create
        STATUS      current
        DESCRIPTION
            "The integer sequence of queque's priority.
            For example,the value {0.1.2.3.4.5.6.7 } means "
        ::=  {  zxAnQosIIQueuesBlockProfileEntry  2  }


    zxAnQosIIQueuesWeight     OBJECT-TYPE
        SYNTAX      OBJECT IDENTIFIER
        MAX-ACCESS  read-create
        STATUS      current
        DESCRIPTION
            "The integer sequence of queque's weight.The size of
            sequence is 8 and it presents weights for 8 queques.
            For example,the value {1.2.3.4.5.6.7.8 } means weight of queue0 is 1,
            weight of queue1 is 2,...,weight of queue7 is 8.
            The range of each weight is 0 to 63.
            The weight is relevant only when the same Queue Priority value is
            assigned to multiple queues and they are scheduled according to a
            weighted algorithm. "
        ::=  {  zxAnQosIIQueuesBlockProfileEntry  3  }

     zxAnQosIIQueuesDepth     OBJECT-TYPE
         SYNTAX      OBJECT IDENTIFIER
         MAX-ACCESS  read-create
         STATUS      current
         DESCRIPTION
             "The integer sequence of queque's depth."
        ::=  {  zxAnQosIIQueuesBlockProfileEntry  4  }

    zxAnQosIIQueuesBlockRowStatus OBJECT-TYPE
        SYNTAX      RowStatus
        MAX-ACCESS  read-create
        STATUS      current
        DESCRIPTION
            "This object is used to create a new row or to modify or
            delete an existing row in this table."
        ::=  {  zxAnQosIIQueuesBlockProfileEntry  20  }

--------------------------------------------------------------------------------
-- 10. zxAnQosIICosRemarkProfileTable
--------------------------------------------------------------------------------
    zxAnQosIICosRemarkProfileTable  OBJECT-TYPE
        SYNTAX      SEQUENCE  OF  ZxAnQosIICosRemarkProfileEntry
        MAX-ACCESS  not-accessible
        STATUS      current
        DESCRIPTION
            "Ingress priority to Egress priority mapping table"
        ::=  { zxAnQosIIObjects  15 }

    zxAnQosIICosRemarkProfileEntry  OBJECT-TYPE
        SYNTAX      ZxAnQosIICosRemarkProfileEntry
        MAX-ACCESS  not-accessible
        STATUS      current
        DESCRIPTION
            "An entry in zxAnQosIICosRemarkProfileTable."
        INDEX   {  zxAnQosIICosRemarkPrfName }
        ::=  { zxAnQosIICosRemarkProfileTable 1 }

    ZxAnQosIICosRemarkProfileEntry  ::=
        SEQUENCE {
            zxAnQosIICosRemarkPrfName     DisplayString,
            zxAnQosIIEgressPriority       OBJECT IDENTIFIER,
            zxAnQosIICosRemarkRowStatus   RowStatus
        }

    zxAnQosIICosRemarkPrfName OBJECT-TYPE
        SYNTAX      DisplayString(SIZE(1..32))
        MAX-ACCESS  not-accessible
        STATUS      current
        DESCRIPTION
            "The profile name is a display string.It is a index of
            this table."
        ::=  {  zxAnQosIICosRemarkProfileEntry  1  }

    zxAnQosIIEgressPriority    OBJECT-TYPE
        SYNTAX      OBJECT IDENTIFIER
        MAX-ACCESS  read-create
        STATUS      current
        DESCRIPTION
            "The integer sequence of priority remarking,ie.
            Ingress to Egress Priority Mapping information.
            The size of sequence is 8 and it presents 8 egress priority for 8
            ingress priority.
            For example,the value {0.1.2.3.4.5.6.7 } means ingress priority 0 is
            mapping to egress priority 0,...,ingress priority 7 is mapping to
            egress priority 7."
        ::=  {  zxAnQosIICosRemarkProfileEntry  2  }

    zxAnQosIICosRemarkRowStatus  OBJECT-TYPE
        SYNTAX      RowStatus
        MAX-ACCESS  read-create
        STATUS      current
        DESCRIPTION
            "This object is used to create a new row or to modify or
            delete an existing row in this table."
        ::=  {  zxAnQosIICosRemarkProfileEntry  20  }


------------------------------------------------------------------------------
-- 11.zxAnQosIITrafficProfileTable
------------------------------------------------------------------------------
    zxAnQosIITrafficProfileTable OBJECT-TYPE
        SYNTAX      SEQUENCE OF ZxAnQosIITrafficProfileEntry
        MAX-ACCESS  not-accessible
        STATUS      current
        DESCRIPTION
            "A table of Traffic Configuration Profile."
        ::= { zxAnQosIIObjects 16 }

    zxAnQosIITrafficProfileEntry OBJECT-TYPE
        SYNTAX      ZxAnQosIITrafficProfileEntry
        MAX-ACCESS  not-accessible
        STATUS      current
        DESCRIPTION
            "An entry in zxAnQosIITrafficProfileTable."
        INDEX { zxAnQosIITrafficPrfName }
        ::= { zxAnQosIITrafficProfileTable 1 }

    ZxAnQosIITrafficProfileEntry ::= SEQUENCE {
        zxAnQosIITrafficPrfName           DisplayString,
        zxAnQosIITrafficConfCir           INTEGER,
        zxAnQosIITrafficConfCbs           INTEGER,
        zxAnQosIITrafficConfPir           INTEGER,
        zxAnQosIITrafficConfPbs           INTEGER,
        zxAnQosIITrafficCosPriorityTrust  INTEGER,
        zxAnQosIITrafficCosPriority       INTEGER,
        zxAnQosIITrafficDiscardMode       INTEGER,
        zxAnQosIITrafficRowStatus         RowStatus
    }

    zxAnQosIITrafficPrfName  OBJECT-TYPE
        SYNTAX      DisplayString(SIZE(1..32))
        MAX-ACCESS  not-accessible
        STATUS      current
        DESCRIPTION
            "Traffic profile name which applies for a interface."
        ::= { zxAnQosIITrafficProfileEntry 1 }

    zxAnQosIITrafficConfCir OBJECT-TYPE
        SYNTAX      INTEGER(0..2621440)
        UNITS       "kbps"
        MAX-ACCESS  read-create
        STATUS      current
        DESCRIPTION
            "Committed Information Rate(CIR) in kbps.
            Reserved now."
         ::= { zxAnQosIITrafficProfileEntry 2 }

    zxAnQosIITrafficConfCbs OBJECT-TYPE
        SYNTAX      INTEGER(0..1023)
        UNITS       "kbytes"
        MAX-ACCESS  read-create
        STATUS      current
        DESCRIPTION
            "Committed Burst Rate(CBS) in kbyte.
            Reserved now."
         ::= { zxAnQosIITrafficProfileEntry 3 }

    zxAnQosIITrafficConfPir OBJECT-TYPE
        SYNTAX      INTEGER(0..2621440)
        UNITS       "kbps"
        MAX-ACCESS  read-create
        STATUS      current
        DESCRIPTION
            "Peak Information Rate(PIR) in kbps."
         ::= { zxAnQosIITrafficProfileEntry 4 }

    zxAnQosIITrafficConfPbs OBJECT-TYPE
        SYNTAX      INTEGER(0..1023)
        UNITS       "kbytes"
        MAX-ACCESS  read-create
        STATUS      current
        DESCRIPTION
            "Peak Burst Rate(PBS) in kbyte."
         ::= { zxAnQosIITrafficProfileEntry 5 }

    zxAnQosIITrafficCosPriorityTrust OBJECT-TYPE
        SYNTAX      INTEGER
        {
            override(1),
            trust(2),
            notSupport(255)
        }
        MAX-ACCESS  read-create
        STATUS      current
        DESCRIPTION
            "Mode of COS priority trust mode.
             override(1) -- Untrust and Override the COS value of the traffic
                            by zxAnQosIITrafficCosPriority.
             trust(2)    -- trust the COS priority of the traffic and not to
                            override it."
        ::= { zxAnQosIITrafficProfileEntry 6 }


    zxAnQosIITrafficCosPriority OBJECT-TYPE
        SYNTAX      INTEGER(0..7|255)
        MAX-ACCESS  read-create
        STATUS      current
        DESCRIPTION
            "The overriding COS priority.255 means not support"
         ::= { zxAnQosIITrafficProfileEntry 7 }


    zxAnQosIITrafficDiscardMode OBJECT-TYPE
        SYNTAX      INTEGER
        {
            noDistinction(1),
            lowPriorityFirst(2)
        }
        MAX-ACCESS  read-create
        STATUS      current
        DESCRIPTION
            "The discard mode is used when the traffic exceeds the limit.
             noDistinction(1)    -- discard extra flow equally.
             lowPriorityFirst(2) -- discard  low priority first."
        ::= { zxAnQosIITrafficProfileEntry 8 }

    zxAnQosIITrafficRowStatus OBJECT-TYPE
        SYNTAX      RowStatus
        MAX-ACCESS  read-create
        STATUS      current
        DESCRIPTION
            "This object is used to create a new row or modify or
            delete an existing row in this table."
        ::= { zxAnQosIITrafficProfileEntry 20 }

--------------------------------------------------------------------------------
-- 12.zxAnQosIIVPortProfileTable
--------------------------------------------------------------------------------
    zxAnQosIIVPortProfileTable OBJECT-TYPE
        SYNTAX      SEQUENCE  OF  ZxAnQosIIVPortProfileEntry
        MAX-ACCESS  not-accessible
        STATUS      current
        DESCRIPTION
            "A table of Virtual interface Configuration Profile."
        ::=  { zxAnQosIIObjects  17 }

    zxAnQosIIVPortProfileEntry OBJECT-TYPE
        SYNTAX      ZxAnQosIIVPortProfileEntry
        MAX-ACCESS  not-accessible
        STATUS      current
        DESCRIPTION
            "An entry in zxAnQosIIVPortProfileTable."
        INDEX       { zxAnQosIIVPortPrfName }
        ::=  { zxAnQosIIVPortProfileTable 1 }

    ZxAnQosIIVPortProfileEntry  ::=
        SEQUENCE {
            zxAnQosIIVPortPrfName            DisplayString,
            zxAnQosIIConfCosRemark           DisplayString,
            zxAnQosIIConfDefCos              INTEGER,
            zxAnQosIIConfDefCtagCos          INTEGER,
            zxAnQosIIConfCosFilter           INTEGER,
            zxAnQosIIConfCosMode             INTEGER,
            zxAnQosIIConfCtagCosMode         INTEGER,
            zxAnQosIIConfDscpMode            INTEGER,
            zxAnQosIIConfDefScos             INTEGER,
            zxAnQosIIConfIngressCosMode      INTEGER,
            zxAnQosIIConfEgressCosMode       INTEGER,
            zxAnQosIIConfIngressDscpMode     INTEGER,
            zxAnQosIIVPortPrfType            INTEGER,
            zxAnQosIIConfEgressCosRemark     DisplayString,
            zxAnQosIIVPortPrfRowStatus       RowStatus
        }

    zxAnQosIIVPortPrfName  OBJECT-TYPE
        SYNTAX      DisplayString(SIZE(1..32))
        MAX-ACCESS  not-accessible
        STATUS      current
        DESCRIPTION
            "The profile name is a display string.It is a index of
            this table."
        ::=  { zxAnQosIIVPortProfileEntry  1  }

    zxAnQosIIConfCosRemark OBJECT-TYPE
        SYNTAX      DisplayString(SIZE(1..32))
        MAX-ACCESS  read-create
        STATUS      current
        DESCRIPTION
            "Associate CoS remark profile. If agent supports
            zxAnQosIIConfEgressCosRemark, this field in valid only for ingress
            direction."
        ::=  { zxAnQosIIVPortProfileEntry  2  }

    zxAnQosIIConfDefCos  OBJECT-TYPE
        SYNTAX      INTEGER(0..7|255)
        MAX-ACCESS  read-create
        STATUS      current
        DESCRIPTION
            "Default Cos vlaue,255 meas not support."
        ::=  { zxAnQosIIVPortProfileEntry  3  }

    zxAnQosIIConfDefCtagCos OBJECT-TYPE
        SYNTAX      INTEGER(0..7|255)
        MAX-ACCESS  read-create
        STATUS      current
        DESCRIPTION
            "Default ctag cos valus,255 meas not support."
        ::=  { zxAnQosIIVPortProfileEntry  4  }

    zxAnQosIIConfCosFilter OBJECT-TYPE
        SYNTAX      INTEGER
        {
            enable(1),
            disable(2)
        }
        MAX-ACCESS  read-create
        STATUS      current
        DESCRIPTION
            "Enable or Disable Cos filter."
        ::=  {  zxAnQosIIVPortProfileEntry  5  }

    zxAnQosIIConfCosMode OBJECT-TYPE
        SYNTAX      INTEGER
        {
            trust(1),
            override(2),
            remark(3),
            trustDscpMap(4),
            notsupport(255)
        }
        MAX-ACCESS  read-create
        STATUS      current
        DESCRIPTION
            "Cos set Mode."
        ::=  {  zxAnQosIIVPortProfileEntry  6 }

    zxAnQosIIConfCtagCosMode OBJECT-TYPE
        SYNTAX      INTEGER
        {
            trust(1),
            override(2),
            remark(3),
            trustDscpMap(4),
            notsupport(255)
        }
        MAX-ACCESS  read-create
        STATUS      current
        DESCRIPTION
            "Ctag Cos set Mode."
        ::=  {  zxAnQosIIVPortProfileEntry  7  }

    zxAnQosIIConfDscpMode  OBJECT-TYPE
        SYNTAX      INTEGER
        {
            trust(1),
            trustCosMap(2),
            notsupport(255)
        }
        MAX-ACCESS  read-create
        STATUS      current
        DESCRIPTION
            "Conf dscp mode."
        ::=  {  zxAnQosIIVPortProfileEntry  8  }

    zxAnQosIIConfDefScos  OBJECT-TYPE
        SYNTAX      INTEGER(0..7|255)
        MAX-ACCESS  read-create
        STATUS      current
        DESCRIPTION
            "Conf scos value,255 means not support"
        ::=  {  zxAnQosIIVPortProfileEntry  9  }

    zxAnQosIIConfIngressCosMode  OBJECT-TYPE
        SYNTAX      INTEGER
        {
            trust(1),
            scosOverride(2),
            scosRemark(3),
            ccosScosRemark(4),
            ccosScosOverride(5),
            notSupport(255)
        }
        MAX-ACCESS  read-create
        STATUS      current
        DESCRIPTION
            "Conf ingress CoS mode."
        ::=  {  zxAnQosIIVPortProfileEntry  10  }

    zxAnQosIIConfEgressCosMode  OBJECT-TYPE
        SYNTAX      INTEGER
        {
            trust(1),
            remark(2),
            trustDscpMap(3),
            notSupport(255)
        }
        MAX-ACCESS  read-create
        STATUS      current
        DESCRIPTION
            "Conf egress cos mode."
        ::=  {  zxAnQosIIVPortProfileEntry  11  }

    zxAnQosIIConfIngressDscpMode  OBJECT-TYPE
        SYNTAX      INTEGER
        {
            trust(1),
            trustCosMap(2),
            notSupport(255)
        }
        MAX-ACCESS  read-create
        STATUS      current
        DESCRIPTION
            "Conf ingress dscp mode."
        ::=  {  zxAnQosIIVPortProfileEntry  12  }

    zxAnQosIIVPortPrfType  OBJECT-TYPE
        SYNTAX      INTEGER
        {
            pon(1),
            dsl(2)
        }
        MAX-ACCESS  read-create
        STATUS      current
        DESCRIPTION
            "Virtual port profile type."
        ::= { zxAnQosIIVPortProfileEntry 13 }

    zxAnQosIIConfEgressCosRemark OBJECT-TYPE
        SYNTAX      DisplayString(SIZE(1..32))
        MAX-ACCESS  read-create
        STATUS      current
        DESCRIPTION
            "Associate egress-direction CoS Remark profile."
        ::=  { zxAnQosIIVPortProfileEntry 14 }

    zxAnQosIIVPortPrfRowStatus OBJECT-TYPE
        SYNTAX      RowStatus
        MAX-ACCESS  read-create
        STATUS      current
        DESCRIPTION
            "This object is used to create a new row or modify or
            delete an existing row in this table."
        ::=  {  zxAnQosIIVPortProfileEntry  20 }

--------------------------------------------------------------------------------
-- 13.zxAnQosIIPortCfgTable
--------------------------------------------------------------------------------
    zxAnQosIIPortCfgTable  OBJECT-TYPE
        SYNTAX      SEQUENCE  OF  ZxAnQosIIPortCfgEntry
        MAX-ACCESS  not-accessible
        STATUS      current
        DESCRIPTION
            "This table includes interface qos configuration.It is used
            for a User-side port(Physical interface)."
        ::=  { zxAnQosIIObjects  21 }

    zxAnQosIIPortCfgEntry  OBJECT-TYPE
        SYNTAX      ZxAnQosIIPortCfgEntry
        MAX-ACCESS  not-accessible
        STATUS      current
        DESCRIPTION
            "An entry in zxAnQosIIPortCfgTable."
        INDEX       { ifIndex }
        ::=  { zxAnQosIIPortCfgTable 1 }

    ZxAnQosIIPortCfgEntry  ::=
        SEQUENCE {
            zxAnQosIICosQueuePrf            DisplayString,
            zxAnQosIIQueueBlockPrf          DisplayString,
            zxAnQosIICosRemarkPrf           DisplayString
        }

    zxAnQosIICosQueuePrf OBJECT-TYPE
        SYNTAX      DisplayString(SIZE(1..32))
        MAX-ACCESS  read-create
        STATUS      current
        DESCRIPTION
            "Conf Cos queue profile."
        ::=  {  zxAnQosIIPortCfgEntry  1  }

    zxAnQosIIQueueBlockPrf OBJECT-TYPE
      SYNTAX      DisplayString(SIZE(1..32))
      MAX-ACCESS  read-create
      STATUS      current
      DESCRIPTION
          "Conf queue block profile."
      ::=  {  zxAnQosIIPortCfgEntry  2  }

    zxAnQosIICosRemarkPrf OBJECT-TYPE
      SYNTAX      DisplayString(SIZE(0..32))
      MAX-ACCESS  read-create
      STATUS      current
      DESCRIPTION
          "This object configures CoS remark profile for this interface.
           The value of this object is the name of the referenced profile in
           the zxAnQosIICosRemarkProfileTable,or a zero-length String.
           A zero-length means not support."
      REFERENCE
          "Only Used by FT Test."
      ::=  {  zxAnQosIIPortCfgEntry  3  }

--------------------------------------------------------------------------------
-- 14.zxAnQosIIVPortCfgTable
--------------------------------------------------------------------------------

    zxAnQosIIVPortCfgTable  OBJECT-TYPE
        SYNTAX      SEQUENCE  OF  ZxAnQosIIVPortCfgEntry
        MAX-ACCESS  not-accessible
        STATUS      current
        DESCRIPTION
            "This table includes interface qos configuration.It is used
            for subscriber ports."
        ::=  { zxAnQosIIObjects  22 }

    zxAnQosIIVPortCfgEntry  OBJECT-TYPE
        SYNTAX      ZxAnQosIIVPortCfgEntry
        MAX-ACCESS  not-accessible
        STATUS      current
        DESCRIPTION
            "An entry in zxAnQosIIVPortCfgTable."
        INDEX   {  zxAnQosIIRack,zxAnQosIIShelf,zxAnQosIISlot,
                   zxAnQosIIPort,zxAnQosIIOnu,
                   zxAnQosIIVCircuitType,zxAnQosIILogicalId}
        ::=  { zxAnQosIIVPortCfgTable 1 }

    ZxAnQosIIVPortCfgEntry  ::=
        SEQUENCE {
            zxAnQosIIRack                    Integer32,
            zxAnQosIIShelf                   Integer32,
            zxAnQosIISlot                    Integer32,
            zxAnQosIIPort                    Integer32,
            zxAnQosIIOnu                     Integer32,
            zxAnQosIIVCircuitType            INTEGER,
            zxAnQosIILogicalId               Integer32,
            zxAnQosIIVPortCfgPrf             DisplayString,
            zxAnQosIIVPortMapQueue           INTEGER,
            zxAnQosIIVPortServiceCategory    INTEGER,
            zxAnQosIIVPortPcr                INTEGER,
            zxAnQosIIVPortMcr                INTEGER,
            zxAnQosIIVPortScr                INTEGER,
            zxAnQosIIVPortPcrRemarkCos       INTEGER,
            zxAnQosIIVPortMcrRemarkCos       INTEGER,
            zxAnQosIIVPortScrRemarkCos       INTEGER
        }

    zxAnQosIIRack  OBJECT-TYPE
        SYNTAX      Integer32
        MAX-ACCESS  not-accessible
        STATUS      current
        DESCRIPTION
            "Rack number of the port."
        ::= { zxAnQosIIVPortCfgEntry 1 }

    zxAnQosIIShelf  OBJECT-TYPE
        SYNTAX      Integer32
        MAX-ACCESS  not-accessible
        STATUS      current
        DESCRIPTION
            "Shelf number of the port."
        ::= { zxAnQosIIVPortCfgEntry 2 }

    zxAnQosIISlot  OBJECT-TYPE
        SYNTAX      Integer32
        MAX-ACCESS  not-accessible
        STATUS      current
        DESCRIPTION
            "Slot number of the port."
        ::= { zxAnQosIIVPortCfgEntry 3 }

    zxAnQosIIPort  OBJECT-TYPE
        SYNTAX      Integer32
        MAX-ACCESS  not-accessible
        STATUS      current
        DESCRIPTION
            "The port number."
        ::= { zxAnQosIIVPortCfgEntry 4 }

    zxAnQosIIOnu  OBJECT-TYPE
        SYNTAX      Integer32
        MAX-ACCESS  not-accessible
        STATUS      current
        DESCRIPTION
             "The Onu number.It is 0 in DSL port."
        ::= { zxAnQosIIVPortCfgEntry 5 }

    zxAnQosIIVCircuitType  OBJECT-TYPE
        SYNTAX      INTEGER
        {
            physicalport(1),
            bridgeport(2),
            epononu(3),
            gpon(4),
            serviceport(11),
            vlan(12)
        }
        MAX-ACCESS  not-accessible
        STATUS      current
        DESCRIPTION
            "Virtual circuit type."
        ::= { zxAnQosIIVPortCfgEntry 6 }

    zxAnQosIILogicalId OBJECT-TYPE
        SYNTAX      Integer32
        MAX-ACCESS  not-accessible
        STATUS      current
        DESCRIPTION
            "Logical id of this port.
            If zxAnQosIIPortServiceType is physicalport,
            zxAnQosIILogicalId is filled by 0."
        ::=  {  zxAnQosIIVPortCfgEntry  7  }

    zxAnQosIIVPortCfgPrf OBJECT-TYPE
        SYNTAX      DisplayString( SIZE ( 1 .. 32  ) )
        MAX-ACCESS  read-create
        STATUS      current
        DESCRIPTION
            ""
        ::=  {  zxAnQosIIVPortCfgEntry 8 }

    zxAnQosIIVPortMapQueue OBJECT-TYPE
        SYNTAX      INTEGER(0..8)
        MAX-ACCESS  read-create
        STATUS      current
        DESCRIPTION
            "Queue value corresponding to Pvc."
        ::=  { zxAnQosIIVPortCfgEntry  9 }

    zxAnQosIIVPortServiceCategory OBJECT-TYPE
        SYNTAX      INTEGER
        {
            cbr(1),
            ubr(2),
            vbr(3),
            unconfigured(255)
        }
        MAX-ACCESS  read-create
        STATUS      current
        DESCRIPTION
            "Service category of VPort.
             The value 255 indicates that no service category is configured
             to this VPort.
            "
        DEFVAL      { unconfigured }
        ::=  { zxAnQosIIVPortCfgEntry  10 }

    zxAnQosIIVPortPcr OBJECT-TYPE
        SYNTAX      INTEGER(0..20480)
        UNITS       "kbps"
        MAX-ACCESS  read-create
        STATUS      current
        DESCRIPTION
            "Peak cell rate(PCR) in kbps."
        DEFVAL      { 0 }
        ::=  { zxAnQosIIVPortCfgEntry  11 }

    zxAnQosIIVPortMcr OBJECT-TYPE
        SYNTAX      INTEGER(0..20480)
        UNITS       "kbps"
        MAX-ACCESS  read-create
        STATUS      current
        DESCRIPTION
            "Minimum cell rate(MCR) in kbps.
             zxAnQosIIVPortMcr is valid when zxAnQosIIVPortServiceCategory is
             UBR."
        DEFVAL      { 0 }
        ::=  { zxAnQosIIVPortCfgEntry  12 }

    zxAnQosIIVPortScr OBJECT-TYPE
        SYNTAX      INTEGER(0..20480)
        UNITS       "kbps"
        MAX-ACCESS  read-create
        STATUS      current
        DESCRIPTION
            "Sustained cell rate(SCR) in kbps.
             zxAnQosIIVPortScr is valid when zxAnQosIIVPortServiceCategory is
             VBR."
        DEFVAL      { 0 }
        ::=  { zxAnQosIIVPortCfgEntry  13 }

    zxAnQosIIVPortPcrRemarkCos OBJECT-TYPE
        SYNTAX      INTEGER(0..7|255)
        MAX-ACCESS  read-create
        STATUS      current
        DESCRIPTION
            "CoS remark value for traffic lower than PCR and higher than
             SCR/MCR.
             The value 255 indicates that no remark CoS is configured."
        DEFVAL      { 255 }
        ::=  { zxAnQosIIVPortCfgEntry  14 }

    zxAnQosIIVPortMcrRemarkCos OBJECT-TYPE
        SYNTAX      INTEGER(0..7|255)
        MAX-ACCESS  read-create
        STATUS      current
        DESCRIPTION
            "CoS remark value for traffic lower than MCR.
             The value 255 indicates that no remark CoS is configured."
        DEFVAL      { 255 }
        ::=  { zxAnQosIIVPortCfgEntry  15 }

    zxAnQosIIVPortScrRemarkCos OBJECT-TYPE
        SYNTAX      INTEGER(0..7|255)
        MAX-ACCESS  read-create
        STATUS      current
        DESCRIPTION
            "CoS remark value for traffic lower than SCR.
             The value 255 indicates that no remark CoS is configured."
        DEFVAL      { 255 }
        ::=  { zxAnQosIIVPortCfgEntry  16 }

--------------------------------------------------------------------------------
-- 15.zxAnQosIITrafficCfgTable
--------------------------------------------------------------------------------

    zxAnQosIITrafficCfgTable  OBJECT-TYPE
        SYNTAX      SEQUENCE  OF  ZxAnQosIITrafficCfgEntry
        MAX-ACCESS  not-accessible
        STATUS      current
        DESCRIPTION
            "This table includes interface qos Traffic configuration.It is used
            for subscriber ports."
        ::=  { zxAnQosIIObjects  23 }

    zxAnQosIITrafficCfgEntry  OBJECT-TYPE
        SYNTAX      ZxAnQosIITrafficCfgEntry
        MAX-ACCESS  not-accessible
        STATUS      current
        DESCRIPTION
            "An entry in zxAnQosIITrafficCfgTable."
        INDEX   {  zxAnQosIITrafficRack,zxAnQosIITrafficShelf,zxAnQosIITrafficSlot,
                   zxAnQosIITrafficPort,zxAnQosIITrafficOnu,
                   zxAnQosIITrafficVCircuitType,zxAnQosIITrafficLogicalId,zxAnQosIITrafficDirection}
        ::=  { zxAnQosIITrafficCfgTable 1 }

    ZxAnQosIITrafficCfgEntry  ::=
        SEQUENCE {
            zxAnQosIITrafficRack             Integer32,
            zxAnQosIITrafficShelf            Integer32,
            zxAnQosIITrafficSlot             Integer32,
            zxAnQosIITrafficPort             Integer32,
            zxAnQosIITrafficOnu              Integer32,
            zxAnQosIITrafficVCircuitType     INTEGER,
            zxAnQosIITrafficLogicalId        OBJECT IDENTIFIER,
            zxAnQosIITrafficDirection        INTEGER,
            zxAnQosIITrafficSvcEncapType     INTEGER,
            zxAnQosIITrafficPrf              DisplayString,
            zxAnQosIITrafficCfgRowStatus     RowStatus
        }

    zxAnQosIITrafficRack  OBJECT-TYPE
        SYNTAX      Integer32
        MAX-ACCESS  not-accessible
        STATUS      current
        DESCRIPTION
            "Rack number of the port."
        ::= { zxAnQosIITrafficCfgEntry 1 }

    zxAnQosIITrafficShelf  OBJECT-TYPE
        SYNTAX      Integer32
        MAX-ACCESS  not-accessible
        STATUS      current
        DESCRIPTION
            "Shelf number of the port."
        ::= { zxAnQosIITrafficCfgEntry 2 }

    zxAnQosIITrafficSlot  OBJECT-TYPE
        SYNTAX      Integer32
        MAX-ACCESS  not-accessible
        STATUS      current
        DESCRIPTION
            "Slot number of the port."
        ::= { zxAnQosIITrafficCfgEntry 3 }

    zxAnQosIITrafficPort  OBJECT-TYPE
        SYNTAX      Integer32
        MAX-ACCESS  not-accessible
        STATUS      current
        DESCRIPTION
            "The port number."
        ::= { zxAnQosIITrafficCfgEntry 4 }

    zxAnQosIITrafficOnu  OBJECT-TYPE
        SYNTAX      Integer32
        MAX-ACCESS  not-accessible
        STATUS      current
        DESCRIPTION
             "The Onu number.It is 0 in DSL port."
        ::= { zxAnQosIITrafficCfgEntry 5 }

    zxAnQosIITrafficVCircuitType  OBJECT-TYPE
        SYNTAX      INTEGER
        {
            physicalport(1),
            bridgeport(2),
            epononu(3),
            gpon(4),
            serviceport(11),
            vlan(12)
        }
        MAX-ACCESS  not-accessible
        STATUS      current
        DESCRIPTION
            "Virtual circuit type."
        ::= { zxAnQosIITrafficCfgEntry 6 }

    zxAnQosIITrafficLogicalId OBJECT-TYPE
        SYNTAX      OBJECT IDENTIFIER
        MAX-ACCESS  not-accessible
        STATUS      current
        DESCRIPTION
            "Logical id of this port.
            If zxAnQosIIPortServiceType is physicalport,zxAnQosIILogicalId
            is filled by 0.
            If zxAnQosIIPortServiceType is vlan,zxAnQosIILogicalId is filled
            by svlanId.cvlanId."
        ::=  {  zxAnQosIITrafficCfgEntry  7  }

    zxAnQosIITrafficDirection OBJECT-TYPE
        SYNTAX      INTEGER
        {
            ingress(1),
            egress(2)
        }
        MAX-ACCESS  not-accessible
        STATUS      current
        DESCRIPTION
            "Egress direction or ingress dirction on a service interface."
        ::= { zxAnQosIITrafficCfgEntry 8 }

    zxAnQosIITrafficSvcEncapType OBJECT-TYPE
        SYNTAX      INTEGER
        {
            pppoe(1),
            ipoe(2),
            all(3),
            notsupport(255)
        }
        MAX-ACCESS  read-create
        STATUS      current
        DESCRIPTION
            "The encapsulation type on a service interface."
        ::= { zxAnQosIITrafficCfgEntry 9 }

    zxAnQosIITrafficPrf OBJECT-TYPE
        SYNTAX      DisplayString
        MAX-ACCESS  read-create
        STATUS      current
        DESCRIPTION
            "The traffic profile of ingress or egress direction."
        ::= { zxAnQosIITrafficCfgEntry 10 }

    zxAnQosIITrafficCfgRowStatus  OBJECT-TYPE
        SYNTAX      RowStatus
        MAX-ACCESS  read-create
        STATUS      current
        DESCRIPTION
            "This object is used to create a new row or modify or
            delete an existing row in this table."
        ::=  { zxAnQosIITrafficCfgEntry  20 }

--------------------------------------------------------------------------------
-- 16.zxAnQosIIRemainingBandwidthTable
--------------------------------------------------------------------------------

    zxAnQosIITrafficBandwidthTable  OBJECT-TYPE
        SYNTAX      SEQUENCE  OF  ZxAnQosIITrafficBandwidthEntry
        MAX-ACCESS  not-accessible
        STATUS      current
        DESCRIPTION
            "This table includes interface BandWidth.It is used
            for physical ports."
        ::=  { zxAnQosIIObjects  24 }

    zxAnQosIITrafficBandwidthEntry  OBJECT-TYPE
        SYNTAX      ZxAnQosIITrafficBandwidthEntry
        MAX-ACCESS  not-accessible
        STATUS      current
        DESCRIPTION
            "An entry in zxAnQosIITrafficBandwidthTable."
            INDEX   { ifIndex }
        ::=  { zxAnQosIITrafficBandwidthTable 1 }

    ZxAnQosIITrafficBandwidthEntry  ::=
        SEQUENCE {
            zxAnQosIITrafficTotalBandwidth        Integer32,
            zxAnQosIITrafficRemainBandwidth    Integer32
        }

    zxAnQosIITrafficTotalBandwidth  OBJECT-TYPE
        SYNTAX      Integer32
        UNITS       "kbps"
        MAX-ACCESS  read-only
        STATUS      current
        DESCRIPTION
             "Total bandwidth of the interface."
        ::= { zxAnQosIITrafficBandwidthEntry 1 }

    zxAnQosIITrafficRemainBandwidth  OBJECT-TYPE
        SYNTAX      Integer32
        UNITS       "kbps"
        MAX-ACCESS  read-only
        STATUS      current
        DESCRIPTION
            "Remaining bandwidth of the interface."
        ::= { zxAnQosIITrafficBandwidthEntry 2 }
END
