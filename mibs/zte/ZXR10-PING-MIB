--  ************************************************
--  $Id: zxr10ping.mib 8 2005-07-28 12:17:08Z zhanglh $
--
--  zxr10ping.mib: ZXR10 Ping MIB file
--
--  JUL. 2005, Zhang lihui
--
--  Copyright(c) 2005 by ZTE Corporaton
--  All rights reservered
--
--  ************************************************

ZXR10-PING-MIB DEFINITIONS ::= BEGIN

IMPORTS
    MODULE-IDENTITY,
    OBJECT-TYPE,
    NOTIFICATION-TYPE,
    experimental,
    Integer32,
    Unsigned32,
    Counter32
        FROM SNMPv2-SMI

    MODULE-COMPLIANCE,
    OBJECT-GROUP,
    NOTIFICATION-GROUP
        FROM SNMPv2-CONF
    enterprises
        FROM SNMPv2-SMI
    MacAddress,RowStatus,TruthValue
        FROM SNMPv2-TC

    zxr10L2vpn
        FROM ZXR10-SMI

    mgmt,
    NetworkAddress,
    IpAddress,
    Counter,
    Gauge
        FROM RFC1155-SMI;


    zxr10PingMIB OBJECT IDENTIFIER ::= { zxr10L2vpn 2}

    DisplayString ::= OCTET STRING
    --  This data type is used to model textual information taken
    --  from the NVT ASCII character set.  By convention, objects
    --  with this syntax are declared as having
    --  SIZE (0..255)

    zxr10PingTable  OBJECT-TYPE
        SYNTAX  SEQUENCE OF Zxr10pingCommonEntry
        MAX-ACCESS  not-accessible
        STATUS  current
        DESCRIPTION
            "ping information table."
        ::= { zxr10PingMIB 1 }

    zxr10pingCommonEntry  OBJECT-TYPE
        SYNTAX  Zxr10pingCommonEntry
        MAX-ACCESS  not-accessible
        STATUS  current
        DESCRIPTION
            ""
        INDEX  { zxr10PingCommonSerial }
        ::= { zxr10PingTable 1 }

    Zxr10pingCommonEntry ::=
        SEQUENCE {
            zxr10PingCommonSerial
                Integer32,
            zxr10PingCommonPingType
                INTEGER,
            zxr10PingCommonDestAddr
                IpAddress,
            zxr10PingCommonVrfName
                DisplayString,
            zxr10PingCommonIfOption
                INTEGER,
            zxr10PingCommonPacketCount
                Integer32,
            zxr10PingCommonTimeOut
                Integer32,
            zxr10PingCommonDataLen
                Integer32,
            zxr10PingCommonIfExtOption
                INTEGER,
            zxr10PingCommonExtSourceAddr
                IpAddress,
            zxr10PingCommonExtTos
                Integer32,
            zxr10PingCommonExtTTL
                Integer32,
            zxr10PingCommonExtFragement
                Integer32,
            zxr10PingCommonExtOpType
                INTEGER,
            zxr10PingCommonExtOpIpAddr1
                IpAddress,
            zxr10PingCommonExtOpIpAddr2
                IpAddress,
            zxr10PingCommonExtOpIpAddr3
                IpAddress,
            zxr10PingCommonExtOpIpAddr4
                IpAddress,
            zxr10PingCommonExtOpIpAddr5
                IpAddress,
            zxr10PingCommonExtOpIpAddr6
                IpAddress,
            zxr10PingCommonExtOpIpAddr7
                IpAddress,
            zxr10PingCommonExtOpIpAddr8
                IpAddress,
            zxr10PingCommonExtOpIpAddr9
                IpAddress,
            zxr10PingCommonExtOpRecordNum
                Integer32,
            zxr10PingCommonExtOpTimestampNum
                Integer32,
            zxr10PingCommonRosStatus
                INTEGER,
            zxr10PingCommonEntryOwner
                DisplayString,
            zxr10PingCommonTrapOncompletion
                TruthValue

    }

    zxr10PingCommonSerial  OBJECT-TYPE
        SYNTAX  Integer32
        MAX-ACCESS  read-only
        STATUS  current
        DESCRIPTION
            ""
        ::= { zxr10pingCommonEntry 1 }

    zxr10PingCommonPingType  OBJECT-TYPE
        SYNTAX   INTEGER{common(0),mng(1),vrf(2)}
        MAX-ACCESS  read-write
        STATUS  current
        DESCRIPTION
            "ping type,default:common "
        ::= { zxr10pingCommonEntry 2 }

    zxr10PingCommonDestAddr OBJECT-TYPE
        SYNTAX  IpAddress
        MAX-ACCESS  read-write
        STATUS  current
        DESCRIPTION
            "target IP address "
        ::= { zxr10pingCommonEntry 3 }

    zxr10PingCommonVrfName OBJECT-TYPE
        SYNTAX  DisplayString(SIZE(0..16))
        MAX-ACCESS  read-write
        STATUS  current
        DESCRIPTION
            "vrf name  "
        ::= { zxr10pingCommonEntry 4 }


    zxr10PingCommonIfOption OBJECT-TYPE
        SYNTAX  INTEGER{none(0),option(1)}
        MAX-ACCESS  read-write
        STATUS  current
        DESCRIPTION
            "option,default:none  "
        ::= { zxr10pingCommonEntry 5 }


    zxr10PingCommonPacketCount OBJECT-TYPE
        SYNTAX    Integer32
        MAX-ACCESS  read-write
        STATUS  current
        DESCRIPTION
            "repeat count,default:5    "
        ::= { zxr10pingCommonEntry 6 }

    zxr10PingCommonTimeOut OBJECT-TYPE
        SYNTAX   Integer32 (1..60)
        MAX-ACCESS  read-write
        STATUS  current
        DESCRIPTION
            "timeout in seconds,default:2   "
        ::= { zxr10pingCommonEntry 7 }

    zxr10PingCommonDataLen OBJECT-TYPE
        SYNTAX   Integer32 (36..8192)
        MAX-ACCESS  read-write
        STATUS  current
        DESCRIPTION
            "datagram size,default:  100"
        ::= { zxr10pingCommonEntry 8 }

    zxr10PingCommonIfExtOption OBJECT-TYPE
        SYNTAX   INTEGER{none(0),extcom(1)}
        MAX-ACCESS  read-write
        STATUS  current
        DESCRIPTION
            "extended commands,default:none  "
        ::= { zxr10pingCommonEntry 9 }


    zxr10PingCommonExtSourceAddr OBJECT-TYPE
        SYNTAX   IpAddress
        MAX-ACCESS  read-write
        STATUS  current
        DESCRIPTION
            "source address   "
        ::= { zxr10pingCommonEntry 10 }

    zxr10PingCommonExtTos OBJECT-TYPE
        SYNTAX   Integer32 (0..255)
        MAX-ACCESS  read-write
        STATUS  current
        DESCRIPTION
            "type of service,default:0   "
        ::= { zxr10pingCommonEntry 11 }

    zxr10PingCommonExtTTL OBJECT-TYPE
        SYNTAX   Integer32 (1..255)
        MAX-ACCESS  read-write
        STATUS  current
        DESCRIPTION
            "time to live,default:255    "
        ::= { zxr10pingCommonEntry 12 }

    zxr10PingCommonExtFragement OBJECT-TYPE
        SYNTAX   Integer32 (0..1)
        MAX-ACCESS  read-write
        STATUS  current
        DESCRIPTION
            "set DONT FRAG(0--may frag,1--don't frag)  "
        ::= { zxr10pingCommonEntry 13 }

    zxr10PingCommonExtOpType OBJECT-TYPE
        SYNTAX   INTEGER {none(0),loose(1),record(2),strict(3),timestamp(4)}
        MAX-ACCESS  read-write
        STATUS  current
        DESCRIPTION
            "extended commands  "
        ::= { zxr10pingCommonEntry 14 }

    zxr10PingCommonExtOpIpAddr1 OBJECT-TYPE
        SYNTAX   IpAddress
        MAX-ACCESS  read-write
        STATUS  current
        DESCRIPTION
            " ip address   "
        ::= { zxr10pingCommonEntry 15 }

    zxr10PingCommonExtOpIpAddr2 OBJECT-TYPE
        SYNTAX   IpAddress
        MAX-ACCESS  read-write
        STATUS  current
        DESCRIPTION
            " ip address   "
        ::= { zxr10pingCommonEntry 16 }


    zxr10PingCommonExtOpIpAddr3 OBJECT-TYPE
        SYNTAX   IpAddress
        MAX-ACCESS  read-write
        STATUS  current
        DESCRIPTION
            " ip address   "
        ::= { zxr10pingCommonEntry 17 }


    zxr10PingCommonExtOpIpAddr4 OBJECT-TYPE
        SYNTAX   IpAddress
        MAX-ACCESS  read-write
        STATUS  current
        DESCRIPTION
            " ip address   "
        ::= { zxr10pingCommonEntry 18 }


    zxr10PingCommonExtOpIpAddr5 OBJECT-TYPE
        SYNTAX   IpAddress
        MAX-ACCESS  read-write
        STATUS  current
        DESCRIPTION
            " ip address   "
        ::= { zxr10pingCommonEntry 19 }


    zxr10PingCommonExtOpIpAddr6 OBJECT-TYPE
        SYNTAX   IpAddress
        MAX-ACCESS  read-write
        STATUS  current
        DESCRIPTION
            " ip address   "
        ::= { zxr10pingCommonEntry 20 }


    zxr10PingCommonExtOpIpAddr7 OBJECT-TYPE
        SYNTAX   IpAddress
        MAX-ACCESS  read-write
        STATUS  current
        DESCRIPTION
            " ip address   "
        ::= { zxr10pingCommonEntry 21 }


    zxr10PingCommonExtOpIpAddr8 OBJECT-TYPE
        SYNTAX   IpAddress
        MAX-ACCESS  read-write
        STATUS  current
        DESCRIPTION
            " ip address   "
        ::= { zxr10pingCommonEntry 22 }


    zxr10PingCommonExtOpIpAddr9 OBJECT-TYPE
        SYNTAX   IpAddress
        MAX-ACCESS  read-write
        STATUS  current
        DESCRIPTION
            " ip address   "
        ::= { zxr10pingCommonEntry 23 }


    zxr10PingCommonExtOpRecordNum OBJECT-TYPE
        SYNTAX   Integer32 (1..9)
        MAX-ACCESS  read-write
        STATUS  current
        DESCRIPTION
            "number of hops"
        ::= { zxr10pingCommonEntry 24 }

    zxr10PingCommonExtOpTimestampNum OBJECT-TYPE
        SYNTAX   Integer32 (1..9)
        MAX-ACCESS  read-write
        STATUS  current
        DESCRIPTION
            "number of hops"
        ::= { zxr10pingCommonEntry 25 }

    zxr10PingCommonRosStatus OBJECT-TYPE
        SYNTAX   INTEGER{not-active(1),start-ping(2),ping-processing(3),ping-completed(4)}
        MAX-ACCESS  read-write
        STATUS  current
        DESCRIPTION
            "  port members    "
        ::= { zxr10pingCommonEntry 26 }

    zxr10PingCommonEntryOwner OBJECT-TYPE
        SYNTAX   DisplayString
        MAX-ACCESS  read-write
        STATUS  current
        DESCRIPTION
            "  port members    "
        ::= { zxr10pingCommonEntry 27 }


    zxr10PingCommonTrapOncompletion OBJECT-TYPE
        SYNTAX   TruthValue
        MAX-ACCESS  read-write
        STATUS  current
        DESCRIPTION
            " "
        DEFVAL       { true }
        ::= { zxr10pingCommonEntry 28 }


--- common ping result


    zxr10PingResultTable  OBJECT-TYPE
        SYNTAX  SEQUENCE OF Zxr10pingResultEntry
        MAX-ACCESS  not-accessible
        STATUS  current
        DESCRIPTION
            "ping result table."
        ::= { zxr10PingMIB 2 }

    zxr10pingResultEntry  OBJECT-TYPE
        SYNTAX  Zxr10pingResultEntry
        MAX-ACCESS  not-accessible
        STATUS  current
        DESCRIPTION
            ""
        INDEX  { zxr10PingCommResultSerial }
        ::= { zxr10PingResultTable 1 }


    Zxr10pingResultEntry ::=
        SEQUENCE {
            zxr10PingCommResultSerial
                Integer32,
            zxr10PingCommResultSentPkts
                Integer32,
            zxr10PingCommResultRcvPkts
                Integer32,
            zxr10PingCommResultRoundTripMinTime
                Integer32,
            zxr10PingCommResultRoundTripMaxTime
                Integer32,
            zxr10PingCommResultRoundTripAvgTime
                Integer32,
            zxr10PingCommExtResultTimeStampInfo
                DisplayString,
            zxr10PingCommExtResultIpAddrInfo
                DisplayString,
            zxr10PingCommResultEntryOwner
                DisplayString,
            zxr10PingCommResultRoundWobbleMinTime
                Integer32,
            zxr10PingCommResultRoundWobbleMaxTime
                Integer32,
            zxr10PingCommResultRoundWobbleAvgTime
                Integer32
    }

     zxr10PingCommResultSerial  OBJECT-TYPE
        SYNTAX  Integer32
        MAX-ACCESS  read-only
        STATUS  current
        DESCRIPTION
            ""
        ::= { zxr10pingResultEntry 1 }

     zxr10PingCommResultSentPkts  OBJECT-TYPE
        SYNTAX  Integer32
        MAX-ACCESS  read-only
        STATUS  current
        DESCRIPTION
            "send packet"
        ::= { zxr10pingResultEntry 2 }

     zxr10PingCommResultRcvPkts  OBJECT-TYPE
        SYNTAX  Integer32
        MAX-ACCESS  read-only
        STATUS  current
        DESCRIPTION
            "receive packet"
        ::= { zxr10pingResultEntry 3 }

     zxr10PingCommResultRoundTripMinTime  OBJECT-TYPE
        SYNTAX  Integer32
        MAX-ACCESS  read-only
        STATUS  current
        DESCRIPTION
            "min RTT"
        ::= { zxr10pingResultEntry 4 }

     zxr10PingCommResultRoundTripMaxTime  OBJECT-TYPE
        SYNTAX  Integer32
        MAX-ACCESS  read-only
        STATUS  current
        DESCRIPTION
            "max RTT"
        ::= { zxr10pingResultEntry 5 }

     zxr10PingCommResultRoundTripAvgTime  OBJECT-TYPE
        SYNTAX  Integer32
        MAX-ACCESS  read-only
        STATUS  current
        DESCRIPTION
            "average RTT"
        ::= { zxr10pingResultEntry 6 }

     zxr10PingCommExtResultTimeStampInfo  OBJECT-TYPE
        SYNTAX  DisplayString
        MAX-ACCESS  read-only
        STATUS  current
        DESCRIPTION
            "timestamp"
        ::= { zxr10pingResultEntry 7 }


     zxr10PingCommExtResultIpAddrInfo  OBJECT-TYPE
        SYNTAX  DisplayString
        MAX-ACCESS  read-only
        STATUS  current
        DESCRIPTION
            "ip address"
        ::= { zxr10pingResultEntry 8 }

     zxr10PingCommResultEntryOwner  OBJECT-TYPE
        SYNTAX  DisplayString
        MAX-ACCESS  read-only
        STATUS  current
        DESCRIPTION
            ""
        ::= { zxr10pingResultEntry 9 }

     zxr10PingCommResultRoundWobbleMinTime  OBJECT-TYPE
        SYNTAX  Integer32
        MAX-ACCESS  read-only
        STATUS  current
        DESCRIPTION
            "min wobble time"
        ::= { zxr10pingResultEntry 10 }

     zxr10PingCommResultRoundWobbleMaxTime  OBJECT-TYPE
        SYNTAX  Integer32
        MAX-ACCESS  read-only
        STATUS  current
        DESCRIPTION
            "max wobble time"
        ::= { zxr10pingResultEntry 11 }

     zxr10PingCommResultRoundWobbleAvgTime  OBJECT-TYPE
        SYNTAX  Integer32
        MAX-ACCESS  read-only
        STATUS  current
        DESCRIPTION
            "average wobble time"
        ::= { zxr10pingResultEntry 12 }

 -- *******************************************************************
--   Trap Definitions
-- *******************************************************************

 pingNotifications   OBJECT IDENTIFIER ::= { zxr10PingMIB 3 }




     pingTrapResult NOTIFICATION-TYPE
     OBJECTS      { zxr10PingCommResultSerial,
                    zxr10PingCommResultSentPkts,
                    zxr10PingCommResultRcvPkts,
                    zxr10PingCommResultRoundTripMinTime,
                    zxr10PingCommResultRoundTripMaxTime,
                    zxr10PingCommResultRoundTripAvgTime


                  }
     STATUS       current
     DESCRIPTION
         "The newMaster trap indicates that the sending agent
         has transitioned to 'Master' state."
     ::= { pingNotifications 1 }





  END
