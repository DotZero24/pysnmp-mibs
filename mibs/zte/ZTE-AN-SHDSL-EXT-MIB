--------------------------------------------------------------------------
-- File Name : ZTE-AN-SHDSL-EXT-MIB.mib
-- Date      : 2008-10-14
-- Author    : ZTE Nms dept.

--
-- Zte SHDSL Mib for Access Node
--------------------------------------------------------------------------
ZTE-AN-SHDSL-EXT-MIB DEFINITIONS ::= BEGIN

   IMPORTS
      Integer32,MODULE-IDENTITY,OBJECT-TYPE                            FROM SNMPv2-SMI

      ifIndex                              FROM IF-MIB
      enterprises                          FROM SNMPv2-SMI
      hdsl2ShdslSpanConfEntry,
      hdsl2ShdslMIB                        FROM HDSL2-SHDSL-LINE-MIB
      ;

    zxAnShdslExtMib MODULE-IDENTITY
        LAST-UPDATED    "200810141530Z"
        ORGANIZATION "ZTE Corporation"
        CONTACT-INFO "ZTE NMS dept.
                      Ma jian   68897122 "
        DESCRIPTION  "This MIB defines managed objects of zte SHDSL mgmt . "
        ::= { zxAn 1002 }

    zte OBJECT IDENTIFIER   ::= { enterprises 3902 }
    zxAn OBJECT IDENTIFIER  ::= { zte 1015 }

    zxAnShdslExtObjects         OBJECT IDENTIFIER ::= { zxAnShdslExtMib 1 }
    zxAnShdslExtGlobalObjects   OBJECT IDENTIFIER ::= { zxAnShdslExtMib 2 }

--------------------------------------------------------------------------------
-- Following objects are defined.
-- 1.SHDSL Interface Config table
-- 2.SHDSL Capabilities
--------------------------------------------------------------------------------
--------------------------------------------------------------------------------
-- 1.SHDSL Interface Config table
--------------------------------------------------------------------------------
    zxAnShdslSpanConfExtTable   OBJECT-TYPE
        SYNTAX      SEQUENCE  OF  ZxAnShdslSpanConfExtEntry
        MAX-ACCESS  not-accessible
        STATUS      current
        DESCRIPTION "This table includes the Shdsl interface infomation."
        ::=  { zxAnShdslExtObjects  1 }

    zxAnShdslSpanConfExtEntry   OBJECT-TYPE
        SYNTAX      ZxAnShdslSpanConfExtEntry
        MAX-ACCESS  not-accessible
        STATUS      current
        DESCRIPTION "An entry extends the Hdsl2ShdslSpanConfEntry defined in
                    HDSL2-SHDSL-LINE-MIB."
        AUGMENTS    { hdsl2ShdslSpanConfEntry }
        ::= { zxAnShdslSpanConfExtTable 1 }

    ZxAnShdslSpanConfExtEntry  ::=  SEQUENCE
    {
        zxAnShdslSpanConfDataPathType          INTEGER,
        zxAnShdslSpanActualDataPathType        INTEGER,

        zxAnShdslSpanConfPamConstellation      INTEGER,
        zxAnShdslSpanActualPamConstellation    INTEGER,
        zxAnShdslSpanActualTransmitPower       Integer32
    }

    zxAnShdslSpanConfDataPathType  OBJECT-TYPE
        SYNTAX      INTEGER {
            atm(1),
            efm(2),
            auto(4) -- negotiate automatically
        }
        MAX-ACCESS  read-write
        STATUS      current
        DESCRIPTION
             "Data path type of this Span."
        ::= { zxAnShdslSpanConfExtEntry 1 }

    zxAnShdslSpanActualDataPathType  OBJECT-TYPE
        SYNTAX      INTEGER {
            atm(1),
            efm(2)
        }
        MAX-ACCESS  read-only
        STATUS      current
        DESCRIPTION
             "the actual data path type of this Span."
        ::= { zxAnShdslSpanConfExtEntry 2 }

    zxAnShdslSpanConfPamConstellation  OBJECT-TYPE
        SYNTAX      INTEGER {
            tcpAM16(1),
            tcpAM32(2),
            auto(4) -- negotiate automatically
        }
        MAX-ACCESS  read-write
        STATUS      current
        DESCRIPTION
             "PAM Constellation type of this Span."
        ::= { zxAnShdslSpanConfExtEntry 3 }

    zxAnShdslSpanActualPamConstellation  OBJECT-TYPE
        SYNTAX      INTEGER {
            tcpAM16(1),
            tcpAM32(2)
        }
        MAX-ACCESS  read-only
        STATUS      current
        DESCRIPTION
             "the actual PAM Constellation type of this Span."
        ::= { zxAnShdslSpanConfExtEntry 4 }

    zxAnShdslSpanActualTransmitPower  OBJECT-TYPE
        SYNTAX      Integer32
        UNITS       "0.1 dBm"
        MAX-ACCESS  read-only
        STATUS      current
        DESCRIPTION
             "the actual Transmit Power of this Span."
        ::= { zxAnShdslSpanConfExtEntry 5 }

--------------------------------------------------------------------------------
-- 2.SHDSL Capabilities
--------------------------------------------------------------------------------

    zxAnShdslCapabilities  OBJECT-TYPE
        SYNTAX      BITS
            {
                rfc4319(0)
            }
        MAX-ACCESS  read-only
        STATUS      current
        DESCRIPTION
            "The management capabilities of SHDSL.
             The bit value 1 means the function represented by this bit is
             supported by this equipment.
             bit 0: value 1 means support RFC4319.

             NOTE: No recommended to display it in NMS."
        ::=  {  zxAnShdslExtGlobalObjects  1  }
END
