ZXPW-L2TPV3-EXT-MIB DEFINITIONS ::= BEGIN

    IMPORTS
       MODULE-IDENTITY, OBJECT-TYPE,
       Unsigned32
          FROM SNMPv2-SMI                    -- [RFC2578]

       zxAnCesMib
            FROM ZTE-MASTER-MIB

       zxPwIndex                              -- [PWMIB]
            FROM ZXPW-STD-MIB
    ;

    zxPwL2tpv3ExtMIB MODULE-IDENTITY
        LAST-UPDATED "200812090000Z"  -- Dec 9, 2008
        ORGANIZATION    "Zhongxing Telcom Co. Ltd."
        CONTACT-INFO    "Zhongxing Telcom Co. Ltd.
                         E-mail: info@mail.zte.com.cn
                         http  : www.zte.com.cn or www.zhongxing.com"

       DESCRIPTION
           "This MIB module complements the PW-STD-MIB module for PW
               operation over L2TPv3."

       ::= { zxAnCesMib 22 }

    -- Notifications
    -- zxPwL2tpv3ExtNotifications OBJECT IDENTIFIER   ::= { zxPwL2tpv3ExtMIB 0 }

    -- Tables, Scalars
    zxPwL2tpv3ExtObjects       OBJECT IDENTIFIER    ::= { zxPwL2tpv3ExtMIB 1 }

    -- Conformance
    -- zxPwL2tpv3ExtConformance   OBJECT IDENTIFIER   ::= { zxPwL2tpv3ExtMIB 2 }

    -- PW L2TPv3 Extended table

    zxPwL2tpv3ExtTable   OBJECT-TYPE
          SYNTAX        SEQUENCE OF ZxPwL2tpv3ExtEntry
          MAX-ACCESS    not-accessible
          STATUS        current
          DESCRIPTION
              "This table controls L2TPv3 specific parameters when the PW is
               going to be carried over L2TPv3 PSN."
          ::= { zxPwL2tpv3ExtObjects 1 }

    zxPwL2tpv3ExtEntry   OBJECT-TYPE
      SYNTAX        ZxPwL2tpv3ExtEntry
      MAX-ACCESS    not-accessible
      STATUS        current
      DESCRIPTION
           "A row in this table represents parameters
           specific to L2TPv3  for a pseudo wire (PW).

           A row MUST be created automatically by the local agent
           for every entry in the zxPwTable if the zxPwPsnType is
           l2tp. Each entry is indexed by zxPwIndex, which uniquely
           identifies a singular PW.

           A row can also be created manually in this table."

      INDEX  { zxPwIndex }

         ::= { zxPwL2tpv3ExtTable 1 }

    ZxPwL2tpv3ExtEntry ::= SEQUENCE {
        zxPwL2tpv3ExtLocalCookie1       Unsigned32,
        zxPwL2tpv3ExtLocalCookie2       Unsigned32,
        zxPwL2tpv3ExtRemoteCookie1      Unsigned32,
        zxPwL2tpv3ExtRemoteCookie2      Unsigned32,
        zxPwL2tpv3ExtServiceType        INTEGER,
        zxPwL2tpv3ExtLocalCookieSize    INTEGER,
        zxPwL2tpv3ExtRemoteCookieSize   INTEGER
      }

    zxPwL2tpv3ExtLocalCookie1 OBJECT-TYPE
        SYNTAX          Unsigned32
        MAX-ACCESS      read-create
        STATUS          current
        DESCRIPTION
           "The local L2TPv3 cookie1 for this PW."
        ::= { zxPwL2tpv3ExtEntry 1 }

    zxPwL2tpv3ExtLocalCookie2 OBJECT-TYPE
        SYNTAX          Unsigned32
        MAX-ACCESS      read-create
        STATUS          current
        DESCRIPTION
           "The local L2TPv3 cookie2 for this PW."
        ::= { zxPwL2tpv3ExtEntry 2 }

    zxPwL2tpv3ExtRemoteCookie1 OBJECT-TYPE
        SYNTAX          Unsigned32
        MAX-ACCESS      read-create
        STATUS          current
        DESCRIPTION
           "The Remote L2TPv3 cookie1 for this PW."
        ::= { zxPwL2tpv3ExtEntry 3 }

    zxPwL2tpv3ExtRemoteCookie2 OBJECT-TYPE
        SYNTAX          Unsigned32
        MAX-ACCESS      read-create
        STATUS          current
        DESCRIPTION
           "The Remote L2TPv3 cookie2 for this PW."
        ::= { zxPwL2tpv3ExtEntry 4 }

    zxPwL2tpv3ExtServiceType OBJECT-TYPE
        SYNTAX          INTEGER
            {
                tdm(1),
                ethernet(2)
            }
        MAX-ACCESS      read-create
        STATUS          current
        DESCRIPTION
           "The service type of this PW."
        DEFVAL {1}
        ::= { zxPwL2tpv3ExtEntry 5 }

    zxPwL2tpv3ExtLocalCookieSize OBJECT-TYPE
        SYNTAX          INTEGER(4..8)
        MAX-ACCESS      read-create
        STATUS          current
        DESCRIPTION
           "L2tpv3 local cookie size, only can be 4 bytes or 8 bytes."
        DEFVAL {8}
        ::= { zxPwL2tpv3ExtEntry 6 }

    zxPwL2tpv3ExtRemoteCookieSize OBJECT-TYPE
        SYNTAX          INTEGER(4..8)
        MAX-ACCESS      read-create
        STATUS          current
        DESCRIPTION
           "L2tpv3 remote cookie size, only can be 4 bytes or 8 bytes."
        DEFVAL {8}
        ::= { zxPwL2tpv3ExtEntry 7 }

    -- End of PW L2TPv3 Extended table

END
