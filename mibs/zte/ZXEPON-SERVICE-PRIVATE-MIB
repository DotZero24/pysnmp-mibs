-- *****************************************************************
-- ZTE EPON MIB
--
-- 03-06-2007
--
-- Copyright(c) 2007 ZTE Corporation
-- All rights reserved.
-- *****************************************************************

ZXEPON-SERVICE-PRIVATE-MIB DEFINITIONS ::= BEGIN
    IMPORTS
        ZxAnIdList                       FROM ZTE-AN-TC-MIB
        RowStatus                        FROM SNMPv2-TC
        TruthValue                       FROM SNMPv2-TC
        Integer32                        FROM SNMPv2-SMI
        Counter64                        FROM SNMPv2-SMI
        IpAddress                        FROM SNMPv2-SMI
        DateAndTime                      FROM SNMPv2-TC
        MacAddress                       FROM SNMPv2-TC
        OBJECT-TYPE                      FROM SNMPv2-SMI
        ifIndex                          FROM RFC1213-MIB
        DisplayString                    FROM RFC1213-MIB
        zxAnEponMib                      FROM ZTE-MASTER-MIB;

        privateObjects                OBJECT IDENTIFIER ::={zxAnEponMib 7}
        zxEponMgmtIndex               OBJECT IDENTIFIER ::={zxAnEponMib 8}
------------------------------------------------------------------------------
--  privateObjects
------------------------------------------------------------------------------
    sysAttrObjectTable OBJECT-TYPE
            SYNTAX         SEQUENCE OF SysAttrObjectEntry
            MAX-ACCESS     not-accessible
            STATUS         current
            DESCRIPTION
                ""
            ::= { privateObjects 1 }

    sysAttrObjectEntry OBJECT-TYPE
            SYNTAX         SysAttrObjectEntry
            MAX-ACCESS     not-accessible
            STATUS         current
            DESCRIPTION
                ""
            INDEX    { ifIndex }
            ::= { sysAttrObjectTable 1}

    SysAttrObjectEntry ::=
        SEQUENCE {
                sysOnuAdminAuthMode                     INTEGER,
                sysAttrAutoAuthEnable                   INTEGER,
                macHwAuthOnuState                       INTEGER,
                zxAnEponOnuSilenceEnable                 TruthValue
                }

    sysOnuAdminAuthMode OBJECT-TYPE
        SYNTAX      INTEGER{
                    mac(1),
                    sn(2),
                    hybrid(3),
                    loid(4),
                    snPlusMac(5)
                    }
        MAX-ACCESS  read-write
        STATUS      current
        DESCRIPTION
            "The value of this object indicates the ONU authentication mode.
       ONU authentication may be used in one of the following modes:
       mac - ONU registration using MAC address;
       sn -  ONU registration using SN;
       hybrid - ONU registration using SN,MAC address or authentication
                key and password;
       loid - ONU registration using authentication key and password;
       snPlusMac - ONU registration using both MAC address and SN."
        ::= { sysAttrObjectEntry 1 }

    sysAttrAutoAuthEnable OBJECT-TYPE
        SYNTAX      INTEGER{
                    enabled(1),
                    disabled(2)
                    }
        MAX-ACCESS  read-write
        STATUS      current
        DESCRIPTION
            ""
        ::= { sysAttrObjectEntry 2 }

    macHwAuthOnuState OBJECT-TYPE
        SYNTAX      INTEGER{
                    enabled(1),
                    disabled(2)
                    }
        MAX-ACCESS  read-write
        STATUS      current
        DESCRIPTION
            ""
        ::= { sysAttrObjectEntry 3 }


    zxAnEponOnuSilenceEnable  OBJECT-TYPE
       SYNTAX      TruthValue
       MAX-ACCESS  read-write
       STATUS      current
       DESCRIPTION
           "This attribute enables or disables the  ONU silence function
             of the EPON card. It is valid only to LOID or hybrid
             authentication mode.
            "
       DEFVAL      { true }
       ::=  {  sysAttrObjectEntry  4  }


    oltLinkAdminTestObjectTable OBJECT-TYPE
            SYNTAX         SEQUENCE OF OltLinkAdminTestObjectEntry
            MAX-ACCESS     not-accessible
            STATUS         current
            DESCRIPTION
                ""
            ::= { privateObjects 2 }

    oltLinkAdminTestObjectEntry OBJECT-TYPE
            SYNTAX         OltLinkAdminTestObjectEntry
            MAX-ACCESS     not-accessible
            STATUS         current
            DESCRIPTION
                ""
            INDEX    { ifIndex }
            ::= { oltLinkAdminTestObjectTable 1}

    OltLinkAdminTestObjectEntry ::=
        SEQUENCE {
                testControlMode                     INTEGER,
                testResult                          INTEGER
                }

    testControlMode OBJECT-TYPE
        SYNTAX       INTEGER{
                     enabled(1),
                     disabled(2)
                     }
        MAX-ACCESS   read-write
        STATUS       current
        DESCRIPTION
            ""
        ::= { oltLinkAdminTestObjectEntry 1 }

    testResult OBJECT-TYPE
        SYNTAX       INTEGER{
                     success(1),
                     fail(2)
                     }
        MAX-ACCESS   read-only
        STATUS       current
        DESCRIPTION
            ""
        ::= { oltLinkAdminTestObjectEntry 2 }

    oltLoopbackObjectTable OBJECT-TYPE
            SYNTAX         SEQUENCE OF OltLoopbackObjectEntry
            MAX-ACCESS     not-accessible
            STATUS         current
            DESCRIPTION
                ""
            ::= { privateObjects 3 }

    oltLoopbackObjectEntry OBJECT-TYPE
            SYNTAX         OltLoopbackObjectEntry
            MAX-ACCESS     not-accessible
            STATUS         current
            DESCRIPTION
                ""
            INDEX    { ifIndex }
            ::= { oltLoopbackObjectTable 1}

    OltLoopbackObjectEntry ::=
        SEQUENCE {
                loopbackStation                     INTEGER,
                loopbackDirection                   INTEGER,
                loopbackAdministration              INTEGER,
                loopbackState                       INTEGER
                }

    loopbackStation OBJECT-TYPE
        SYNTAX       INTEGER{
                     pon(1),
                     nni(2)
                     }
        MAX-ACCESS   read-write
        STATUS       current
        DESCRIPTION
            ""
        ::= { oltLoopbackObjectEntry 1 }

    loopbackDirection OBJECT-TYPE
        SYNTAX       INTEGER{
                     line(1),
                     system(2)
                     }
        MAX-ACCESS   read-write
        STATUS       current
        DESCRIPTION
            ""
        ::= { oltLoopbackObjectEntry 2 }

    loopbackAdministration OBJECT-TYPE
        SYNTAX       INTEGER{
                     mac(1),
                     phy(2)
                     }
        MAX-ACCESS   read-write
        STATUS       current
        DESCRIPTION
            ""
        ::= { oltLoopbackObjectEntry 3 }

    loopbackState OBJECT-TYPE
        SYNTAX       INTEGER{
                     noloopback(1),
                     loopback(2)
                     }
        MAX-ACCESS   read-write
        STATUS       current
        DESCRIPTION
            ""
        ::= { oltLoopbackObjectEntry 4 }

    onuAdminObjectTable OBJECT-TYPE
            SYNTAX         SEQUENCE OF OnuAdminObjectEntry
            MAX-ACCESS     not-accessible
            STATUS         current
            DESCRIPTION
                ""
            ::= { privateObjects 4 }

    onuAdminObjectEntry OBJECT-TYPE
            SYNTAX         OnuAdminObjectEntry
            MAX-ACCESS     not-accessible
            STATUS         current
            DESCRIPTION
                ""
            INDEX    { ifIndex }
            ::= { onuAdminObjectTable 1}

    OnuAdminObjectEntry ::=
        SEQUENCE {
                onuDescript                         DisplayString,
                onuSplitterSn                       INTEGER,
                onuOpticalLineSn                    INTEGER,
                onuUserInfo                         DisplayString,
                onuType                             DisplayString,
                onuAdminState                       INTEGER,
                onuAuthMACAddress                   MacAddress,
                onuRegisterMACAddress               MacAddress,
                onuAuthMACSn                        OCTET STRING,
                onuRegisterSn                       OCTET STRING,
                onuCurrentRegState                  INTEGER,
                onuRegisterTime                     DisplayString,
                onuCurrAdminAuthState               INTEGER,
                onuLatelyPassAdminAuthTime          DisplayString,
                onuCurrDot1xAuthState               INTEGER,
                onuLatelyPassDot1xAuthTime          DisplayString,
                onuMgmtOnlineStatus                 INTEGER,
                onuActiveStatus                     INTEGER,
                onuMgmtEntryStatus                  RowStatus,
                onuMgmtIpCfgMode                    INTEGER,
                onuAuthLoid                         DisplayString,
                onuAuthPassword                     DisplayString,
                onuRegisterLoid                     DisplayString,
                onuRegisterPassword                 DisplayString,
                zxAnEponOnuCreateTime               DisplayString,
                zxAnEponOnuLastOfflineTime          DisplayString
                }

    onuDescript OBJECT-TYPE
        SYNTAX       DisplayString
        MAX-ACCESS   read-write
        STATUS       current
        DESCRIPTION
            ""
        ::= { onuAdminObjectEntry 1 }

    onuSplitterSn OBJECT-TYPE
        SYNTAX       INTEGER
        MAX-ACCESS   read-write
        STATUS       current
        DESCRIPTION
            ""
        ::= { onuAdminObjectEntry 2 }

    onuOpticalLineSn OBJECT-TYPE
        SYNTAX       INTEGER
        MAX-ACCESS   read-write
        STATUS       current
        DESCRIPTION
            ""
        ::= { onuAdminObjectEntry 3 }

    onuUserInfo OBJECT-TYPE
        SYNTAX       DisplayString
        MAX-ACCESS   read-write
        STATUS       current
        DESCRIPTION
            ""
        ::= { onuAdminObjectEntry 4 }

    onuType OBJECT-TYPE
        SYNTAX       DisplayString
        MAX-ACCESS   read-write
        STATUS       current
        DESCRIPTION
            ""
        ::= { onuAdminObjectEntry 5 }

    onuAdminState OBJECT-TYPE
        SYNTAX       INTEGER{
                     enabled(1),
                     disabled(2)
                     }
        MAX-ACCESS   read-write
        STATUS       current
        DESCRIPTION
            ""
        ::= { onuAdminObjectEntry 6 }

    onuAuthMACAddress OBJECT-TYPE
        SYNTAX       MacAddress
        MAX-ACCESS   read-write
        STATUS       current
        DESCRIPTION
            ""
        ::= { onuAdminObjectEntry 7 }

    onuRegisterMACAddress OBJECT-TYPE
        SYNTAX       MacAddress
        MAX-ACCESS   read-only
        STATUS       current
        DESCRIPTION
            ""
        ::= { onuAdminObjectEntry 8 }

    onuAuthMACSn OBJECT-TYPE
        SYNTAX       OCTET STRING
        MAX-ACCESS   read-write
        STATUS       current
        DESCRIPTION
            ""
        ::= { onuAdminObjectEntry 9 }

    onuRegisterSn OBJECT-TYPE
        SYNTAX       OCTET STRING
        MAX-ACCESS   read-only
        STATUS       current
        DESCRIPTION
            ""
        ::= { onuAdminObjectEntry 10 }

    onuCurrentRegState OBJECT-TYPE
        SYNTAX       INTEGER{
                     unregister(1),
                     registering(2),
                     registered(3)
                     }
        MAX-ACCESS   read-only
        STATUS       current
        DESCRIPTION
            ""
        ::= { onuAdminObjectEntry 11 }

    onuRegisterTime OBJECT-TYPE
        SYNTAX       DisplayString
        MAX-ACCESS   read-only
        STATUS       current
        DESCRIPTION
            "EPON ONU latest online time. The format is 'yyyy-mm-dd HH:MM:SS'.
            For example, '2011-01-05 13:06:30'."
        ::= { onuAdminObjectEntry 12 }

    onuCurrAdminAuthState OBJECT-TYPE
        SYNTAX       INTEGER{
                     init(1),
                     authenticating(2),
                     pass(3),
                     deny(4)
                     }
        MAX-ACCESS   read-only
        STATUS       current
        DESCRIPTION
            ""
        ::= { onuAdminObjectEntry 13 }

    onuLatelyPassAdminAuthTime OBJECT-TYPE
        SYNTAX       DisplayString
        MAX-ACCESS   read-only
        STATUS       current
        DESCRIPTION
            ""
        ::= { onuAdminObjectEntry 14 }

    onuCurrDot1xAuthState OBJECT-TYPE
        SYNTAX       INTEGER
        MAX-ACCESS   read-only
        STATUS       current
        DESCRIPTION
            ""
        ::= { onuAdminObjectEntry 15 }

    onuLatelyPassDot1xAuthTime OBJECT-TYPE
        SYNTAX       DisplayString
        MAX-ACCESS   read-only
        STATUS       current
        DESCRIPTION
            ""
        ::= { onuAdminObjectEntry 16 }

    onuMgmtOnlineStatus OBJECT-TYPE
        SYNTAX      INTEGER{
                    poweroff(1),
                    offline(2),
                    online(3)
                    }
        MAX-ACCESS  read-only
        STATUS      current
        DESCRIPTION
            ""
        ::= { onuAdminObjectEntry 17 }

    onuActiveStatus OBJECT-TYPE
        SYNTAX      INTEGER{
                    active(1),
                    inactive(2)
                    }
        MAX-ACCESS  read-write
        STATUS      current
        DESCRIPTION
            ""
        ::= { onuAdminObjectEntry 18 }

    onuMgmtEntryStatus OBJECT-TYPE
        SYNTAX      RowStatus
        MAX-ACCESS  read-create
        STATUS      current
        DESCRIPTION
            ""
        ::= { onuAdminObjectEntry 19 }
    onuMgmtIpCfgMode    OBJECT-TYPE
        SYNTAX      INTEGER{
                    static(1),
                    dynatmic(2)
                    }
        MAX-ACCESS  read-write
        STATUS      current
        DESCRIPTION
            ""
        ::= { onuAdminObjectEntry 20 }

    onuAuthLoid OBJECT-TYPE
        SYNTAX       DisplayString(SIZE(0..24))
        MAX-ACCESS   read-write
        STATUS       current
        DESCRIPTION
            ""
        ::= { onuAdminObjectEntry 21 }

    onuAuthPassword OBJECT-TYPE
        SYNTAX       DisplayString(SIZE(0..12))
        MAX-ACCESS   read-write
        STATUS       current
        DESCRIPTION
            ""
        ::= { onuAdminObjectEntry 22 }

    onuRegisterLoid OBJECT-TYPE
        SYNTAX       DisplayString (SIZE(0..24))
        MAX-ACCESS   read-only
        STATUS       current
        DESCRIPTION
            ""
        ::= { onuAdminObjectEntry 23 }

    onuRegisterPassword OBJECT-TYPE
        SYNTAX       DisplayString(SIZE(0..12))
        MAX-ACCESS   read-only
        STATUS       current
        DESCRIPTION
            ""
        ::= { onuAdminObjectEntry 24 }

    zxAnEponOnuCreateTime OBJECT-TYPE
        SYNTAX       DisplayString(SIZE(1..19))
        MAX-ACCESS   read-only
        STATUS       current
        DESCRIPTION
            "EPON ONU create time. The format is 'yyyy-mm-dd HH:MM:SS'.
            For example, '2011-01-05 13:06:30'."
        ::= { onuAdminObjectEntry 25 }

    zxAnEponOnuLastOfflineTime OBJECT-TYPE
        SYNTAX       DisplayString(SIZE(1..19))
        MAX-ACCESS   read-only
        STATUS       current
        DESCRIPTION
            "EPON ONU last offline time. The format is 'yyyy-mm-dd HH:MM:SS'.
            For example, '2011-01-05 13:06:30'. Possible offline reasons
            associate with 'onuMgmtOnlineStatus'. The possible reason
            values are:
              poweroff (1)  - Power off
              offline  (2)  - Off-line."
        ::= { onuAdminObjectEntry 26 }

    oltEncryAdminObjectTable OBJECT-TYPE
            SYNTAX         SEQUENCE OF OltEncryAdminObjectEntry
            MAX-ACCESS     not-accessible
            STATUS         current
            DESCRIPTION
                ""
            ::= { privateObjects 5 }

    oltEncryAdminObjectEntry OBJECT-TYPE
            SYNTAX         OltEncryAdminObjectEntry
            MAX-ACCESS     not-accessible
            STATUS         current
            DESCRIPTION
                ""
            INDEX    { ifIndex }
            ::= { oltEncryAdminObjectTable 1}

    OltEncryAdminObjectEntry ::=
        SEQUENCE {
                encryptArithmetic                   INTEGER,
                keyUpdateTime                       Integer32,
                keyUpdateTimeout                    Integer32,
                startEncryptThreshold               Integer32
                }

    encryptArithmetic OBJECT-TYPE
        SYNTAX       INTEGER{
                     aes128(1),
                     triplechurning(2)
                     }
        MAX-ACCESS   read-write
        STATUS       current
        DESCRIPTION
            ""
        ::= { oltEncryAdminObjectEntry 1 }

    keyUpdateTime OBJECT-TYPE
        SYNTAX       Integer32
        MAX-ACCESS   read-write
        STATUS       current
        DESCRIPTION
            ""
        ::= { oltEncryAdminObjectEntry 2 }

    keyUpdateTimeout OBJECT-TYPE
        SYNTAX       Integer32
        MAX-ACCESS   read-write
        STATUS       current
        DESCRIPTION
            ""
        ::= { oltEncryAdminObjectEntry 3 }

    startEncryptThreshold OBJECT-TYPE
        SYNTAX       Integer32
        MAX-ACCESS   read-write
        STATUS       current
        DESCRIPTION
            ""
        ::= { oltEncryAdminObjectEntry 4 }

    lineEncryAdminObjectTable OBJECT-TYPE
            SYNTAX         SEQUENCE OF LineEncryAdminObjectEntry
            MAX-ACCESS     not-accessible
            STATUS         current
            DESCRIPTION
                ""
            ::= { privateObjects 6 }

    lineEncryAdminObjectEntry OBJECT-TYPE
            SYNTAX         LineEncryAdminObjectEntry
            MAX-ACCESS     not-accessible
            STATUS         current
            DESCRIPTION
                ""
            INDEX    { ifIndex }
            ::= { lineEncryAdminObjectTable 1}

    LineEncryAdminObjectEntry ::=
        SEQUENCE {
                encryptMode                   INTEGER,
                encrypeState                  TruthValue
                }

    encryptMode OBJECT-TYPE
        SYNTAX       INTEGER{
                     downlink(1),
                     both(2)
                     }
        MAX-ACCESS   read-write
        STATUS       current
        DESCRIPTION
            ""
        ::= { lineEncryAdminObjectEntry 1 }

    encrypeState OBJECT-TYPE
        SYNTAX       TruthValue
        MAX-ACCESS   read-write
        STATUS       current
        DESCRIPTION
            ""
        ::= { lineEncryAdminObjectEntry 2 }

    slaUpAdminObjectTable OBJECT-TYPE
            SYNTAX         SEQUENCE OF SlaUpAdminObjectEntry
            MAX-ACCESS     not-accessible
            STATUS         current
            DESCRIPTION
                ""
            ::= { privateObjects 7 }

    slaUpAdminObjectEntry OBJECT-TYPE
            SYNTAX         SlaUpAdminObjectEntry
            MAX-ACCESS     not-accessible
            STATUS         current
            DESCRIPTION
                ""
            INDEX    { ifIndex }
            ::= { slaUpAdminObjectTable 1}

    SlaUpAdminObjectEntry ::=
        SEQUENCE {
                upFixedBw               Integer32,
                upAssuredBw             Integer32,
                upMaximumBw             Integer32,
                upMaxBurstSize          Integer32,
                upPri                   INTEGER,
                upMaxTimeDelay          Integer32,
                upMaxDrift              Integer32,
                upFixedPacketSize       Integer32
               }

    upFixedBw OBJECT-TYPE
        SYNTAX       Integer32
        MAX-ACCESS   read-write
        STATUS       current
        DESCRIPTION
            ""
        ::= { slaUpAdminObjectEntry 1 }

    upAssuredBw OBJECT-TYPE
        SYNTAX       Integer32
        MAX-ACCESS   read-write
        STATUS       current
        DESCRIPTION
            "512k is upAssuredBw's minimum, 1G is upAssuredBw's maximum. "
        ::= { slaUpAdminObjectEntry 2 }

    upMaximumBw OBJECT-TYPE
        SYNTAX       Integer32
        MAX-ACCESS   read-write
        STATUS       current
        DESCRIPTION
            "512k is upAssuredBw's minimum, 1G is upAssuredBw's maximum. "
        ::= { slaUpAdminObjectEntry 3 }

    upMaxBurstSize OBJECT-TYPE
        SYNTAX       Integer32
        MAX-ACCESS   read-write
        STATUS       current
        DESCRIPTION
            ""
        ::= { slaUpAdminObjectEntry 4 }

    upPri OBJECT-TYPE
        SYNTAX       INTEGER(0..7)
        MAX-ACCESS   read-write
        STATUS       current
        DESCRIPTION
            ""
        ::= { slaUpAdminObjectEntry 5 }

    upMaxTimeDelay OBJECT-TYPE
        SYNTAX       Integer32
        MAX-ACCESS   read-write
        STATUS       current
        DESCRIPTION
            ""
        ::= { slaUpAdminObjectEntry 6 }

    upMaxDrift OBJECT-TYPE
        SYNTAX       Integer32
        MAX-ACCESS   read-write
        STATUS       current
        DESCRIPTION
            ""
        ::= { slaUpAdminObjectEntry 7 }

    upFixedPacketSize    OBJECT-TYPE
        SYNTAX       Integer32
        MAX-ACCESS   read-write
        STATUS       current
        DESCRIPTION
            ""
        ::= { slaUpAdminObjectEntry 8 }

    slaDownAdminObjectTable OBJECT-TYPE
            SYNTAX         SEQUENCE OF SlaDownAdminObjectEntry
            MAX-ACCESS     not-accessible
            STATUS         current
            DESCRIPTION
                ""
            ::= { privateObjects 8 }

    slaDownAdminObjectEntry OBJECT-TYPE
            SYNTAX         SlaDownAdminObjectEntry
            MAX-ACCESS     not-accessible
            STATUS         current
            DESCRIPTION
                ""
            INDEX    { ifIndex }
            ::= { slaDownAdminObjectTable 1}

    SlaDownAdminObjectEntry ::=
        SEQUENCE {
                downAssuredBw             Integer32,
                downMaximumBw             Integer32,
                downMaxBurstSize          Integer32,
                downPri                   INTEGER,
                downMaxTimeDelay          Integer32,
                downMaxDrift              Integer32
                }

        downAssuredBw OBJECT-TYPE
        SYNTAX       Integer32
        MAX-ACCESS   read-write
        STATUS       current
        DESCRIPTION
            "512k is downAssuredBw's minimum, 1G is downAssuredBw's maximum."
        ::= { slaDownAdminObjectEntry 1 }

    downMaximumBw OBJECT-TYPE
        SYNTAX       Integer32
        MAX-ACCESS   read-write
        STATUS       current
        DESCRIPTION
            "512k is downMaximumBw's minimum, 1G is downMaximumBw's maximum."
        ::= { slaDownAdminObjectEntry 2 }

    downMaxBurstSize OBJECT-TYPE
        SYNTAX       Integer32
        MAX-ACCESS   read-write
        STATUS       current
        DESCRIPTION
            ""
        ::= { slaDownAdminObjectEntry 3 }

    downPri OBJECT-TYPE
        SYNTAX       INTEGER(0..7)
        MAX-ACCESS   read-write
        STATUS       current
        DESCRIPTION
            ""
        ::= { slaDownAdminObjectEntry 4 }

    downMaxTimeDelay OBJECT-TYPE
        SYNTAX       Integer32
        MAX-ACCESS   read-write
        STATUS       current
        DESCRIPTION
            ""
        ::= { slaDownAdminObjectEntry 5 }

    downMaxDrift OBJECT-TYPE
        SYNTAX       Integer32
        MAX-ACCESS   read-write
        STATUS       current
        DESCRIPTION
            ""
        ::= { slaDownAdminObjectEntry 6 }

    slaP2pAdminObjectTable OBJECT-TYPE
            SYNTAX         SEQUENCE OF SlaP2pAdminObjectEntry
            MAX-ACCESS     not-accessible
            STATUS         current
            DESCRIPTION
                ""
            ::= { privateObjects 9 }

    slaP2pAdminObjectEntry OBJECT-TYPE
            SYNTAX         SlaP2pAdminObjectEntry
            MAX-ACCESS     not-accessible
            STATUS         current
            DESCRIPTION
                ""
            INDEX    { ifIndex }
            ::= { slaP2pAdminObjectTable 1}

    SlaP2pAdminObjectEntry ::=
        SEQUENCE {
                p2pAssuredBw              Integer32,
                p2pMaximumBw              Integer32,
                p2pMaxBurstSize           Integer32,
                p2pPri                    INTEGER,
                p2pMaxTimeDelay           Integer32,
                p2pMaxDrift               Integer32
                }

    p2pAssuredBw OBJECT-TYPE
        SYNTAX       Integer32
        MAX-ACCESS   read-write
        STATUS       current
        DESCRIPTION
            ""
        ::= { slaP2pAdminObjectEntry 1 }

    p2pMaximumBw OBJECT-TYPE
        SYNTAX       Integer32
        MAX-ACCESS   read-write
        STATUS       current
        DESCRIPTION
            ""
        ::= { slaP2pAdminObjectEntry 2 }

    p2pMaxBurstSize OBJECT-TYPE
        SYNTAX       Integer32
        MAX-ACCESS   read-write
        STATUS       current
        DESCRIPTION
            ""
        ::= { slaP2pAdminObjectEntry 3 }

    p2pPri OBJECT-TYPE
        SYNTAX       INTEGER(0..7)
        MAX-ACCESS   read-write
        STATUS       current
        DESCRIPTION
            ""
        ::= { slaP2pAdminObjectEntry 4 }

    p2pMaxTimeDelay OBJECT-TYPE
        SYNTAX       Integer32
        MAX-ACCESS   read-write
        STATUS       current
        DESCRIPTION
            ""
        ::= { slaP2pAdminObjectEntry 5 }

    p2pMaxDrift OBJECT-TYPE
        SYNTAX       Integer32
        MAX-ACCESS   read-write
        STATUS       current
        DESCRIPTION
            ""
        ::= { slaP2pAdminObjectEntry 6 }

   p2pModeAdminObjectTable OBJECT-TYPE
            SYNTAX         SEQUENCE OF P2pModeAdminObjectEntry
            MAX-ACCESS     not-accessible
            STATUS         current
            DESCRIPTION
                ""
            ::= { privateObjects 10 }

    p2pModeAdminObjectEntry OBJECT-TYPE
            SYNTAX         P2pModeAdminObjectEntry
            MAX-ACCESS     not-accessible
            STATUS         current
            DESCRIPTION
                ""
            INDEX    { ifIndex }
            ::= { p2pModeAdminObjectTable 1}

    P2pModeAdminObjectEntry ::=
        SEQUENCE {
                eponP2pMode               INTEGER
                }

   eponP2pMode OBJECT-TYPE
            SYNTAX         INTEGER{
                          full(1),
                          group(2)
                          }
            MAX-ACCESS     read-write
            STATUS         current
            DESCRIPTION
                ""
            ::= { p2pModeAdminObjectEntry 1 }

    p2pGroupAdminObjectTable OBJECT-TYPE
            SYNTAX         SEQUENCE OF P2pGroupAdminObjectEntry
            MAX-ACCESS     not-accessible
            STATUS         current
            DESCRIPTION
                ""
            ::= { privateObjects 12 }

    p2pGroupAdminObjectEntry OBJECT-TYPE
            SYNTAX         P2pGroupAdminObjectEntry
            MAX-ACCESS     not-accessible
            STATUS         current
            DESCRIPTION
                ""
            INDEX    { ifIndex, eponP2pGroupId }
            ::= { p2pGroupAdminObjectTable 1}

    P2pGroupAdminObjectEntry ::=
        SEQUENCE {
                eponP2pGroupId               INTEGER,
                eponP2pGroupName             DisplayString,
                eponP2pGroupOnus            ZxAnIdList,
                eponP2pGroupAdminStatus      INTEGER,
                eponP2pGroupOpStatus           INTEGER,
                eponP2pGroupRowStatus        RowStatus
                }

    eponP2pGroupId OBJECT-TYPE
        SYNTAX       INTEGER(1..2016)
        MAX-ACCESS   not-accessible
        STATUS       current
        DESCRIPTION
            "group index , 1- 2016"
        ::= { p2pGroupAdminObjectEntry 1 }

    eponP2pGroupName OBJECT-TYPE
        SYNTAX       DisplayString(SIZE(1..127))
        MAX-ACCESS   read-write
        STATUS       current
        DESCRIPTION
            "name length is 1-127"
        ::= { p2pGroupAdminObjectEntry 2 }

    eponP2pGroupOnus OBJECT-TYPE
        SYNTAX       ZxAnIdList(SIZE(8))
        MAX-ACCESS   read-write
        STATUS       current
        DESCRIPTION
            "64bits, each for an onu"
        ::= { p2pGroupAdminObjectEntry 3 }

    eponP2pGroupAdminStatus OBJECT-TYPE
        SYNTAX       INTEGER{
                     enabled(1),
                     disabled(2)
                     }
        MAX-ACCESS   read-write
        STATUS       current
        DESCRIPTION
            ""
        ::= { p2pGroupAdminObjectEntry 4}

    eponP2pGroupOpStatus OBJECT-TYPE
        SYNTAX       INTEGER{
                     enabled(1),
                     disabled(2)
                     }
        MAX-ACCESS   read-only
        STATUS       current
        DESCRIPTION
            ""
        ::= { p2pGroupAdminObjectEntry 5 }

    eponP2pGroupRowStatus   OBJECT-TYPE
        SYNTAX       RowStatus
        MAX-ACCESS  read-create
        STATUS      current
        DESCRIPTION
            ""
        ::= { p2pGroupAdminObjectEntry 6 }

    p2pTransmitAdminObjectTable OBJECT-TYPE
            SYNTAX         SEQUENCE OF P2pTransmitAdminObjectEntry
            MAX-ACCESS     not-accessible
            STATUS         current
            DESCRIPTION
                ""
            ::= { privateObjects 13 }

    p2pTransmitAdminObjectEntry OBJECT-TYPE
            SYNTAX         P2pTransmitAdminObjectEntry
            MAX-ACCESS     not-accessible
            STATUS         current
            DESCRIPTION
                ""
            INDEX    { ifIndex }
            ::= { p2pTransmitAdminObjectTable 1}

    P2pTransmitAdminObjectEntry ::=
        SEQUENCE {
                eponP2pCfgAddressNotFoundEnableFlood    TruthValue,
                eponP2pCfgBroadcastEnableFlood          TruthValue
                }

    eponP2pCfgAddressNotFoundEnableFlood OBJECT-TYPE
        SYNTAX       TruthValue
        MAX-ACCESS   read-write
        STATUS       current
        DESCRIPTION
            ""
        ::= { p2pTransmitAdminObjectEntry 1 }

    eponP2pCfgBroadcastEnableFlood OBJECT-TYPE
        SYNTAX       TruthValue
        MAX-ACCESS   read-write
        STATUS       current
        DESCRIPTION
            ""
        ::= { p2pTransmitAdminObjectEntry 2 }

    onuUnPassedAdminAuthInfoTable OBJECT-TYPE
            SYNTAX         SEQUENCE OF OnuUnPassedAdminAuthInfoEntry
            MAX-ACCESS     not-accessible
            STATUS         current
            DESCRIPTION
                ""
            ::= { privateObjects 14 }

    onuUnPassedAdminAuthInfoEntry OBJECT-TYPE
            SYNTAX         OnuUnPassedAdminAuthInfoEntry
            MAX-ACCESS     not-accessible
            STATUS         current
            DESCRIPTION
                ""
            INDEX    { ifIndex, onuIndex }
            ::= { onuUnPassedAdminAuthInfoTable 1}

    OnuUnPassedAdminAuthInfoEntry ::=
        SEQUENCE {
                onuIndex                     Integer32,
                onuRegisterMacAddress        MacAddress,
                onuReportSn                  OCTET STRING,
                onuAdminAuthState            INTEGER,
                onuDot1xAuthState            INTEGER,
                onuUplineTime                OCTET STRING,
                onuReportLoid                DisplayString,
                onuReportPassword            DisplayString,
                onuReportType                DisplayString,
                zxAnEponOnuSwVersion         DisplayString,
                zxAnEponOnuHwVersion         DisplayString,
                zxAnEponOnuOamBuildStatus    INTEGER
                }

    onuIndex OBJECT-TYPE
        SYNTAX       Integer32
        MAX-ACCESS   not-accessible
        STATUS       current
        DESCRIPTION
            ""
        ::= { onuUnPassedAdminAuthInfoEntry 1 }

    onuRegisterMacAddress OBJECT-TYPE
        SYNTAX       MacAddress
        MAX-ACCESS   read-only
        STATUS       current
        DESCRIPTION
            ""
        ::= { onuUnPassedAdminAuthInfoEntry 2 }

    onuReportSn OBJECT-TYPE
        SYNTAX       OCTET STRING
        MAX-ACCESS   read-only
        STATUS       current
        DESCRIPTION
            ""
        ::= { onuUnPassedAdminAuthInfoEntry 3 }

    onuAdminAuthState OBJECT-TYPE
        SYNTAX       INTEGER{
                     authenticating(1),
                     deny(2)
                     }
        MAX-ACCESS   read-only
        STATUS       current
        DESCRIPTION
            ""
        ::= { onuUnPassedAdminAuthInfoEntry 4 }

    onuDot1xAuthState OBJECT-TYPE
        SYNTAX       INTEGER{
                     authenticating(1),
                     deny(2)
                     }
        MAX-ACCESS   read-only
        STATUS       current
        DESCRIPTION
            ""
        ::= { onuUnPassedAdminAuthInfoEntry 5 }

    onuUplineTime OBJECT-TYPE
        SYNTAX       OCTET STRING
        MAX-ACCESS   read-only
        STATUS       current
        DESCRIPTION
            ""
        ::= { onuUnPassedAdminAuthInfoEntry 6 }

    onuReportLoid OBJECT-TYPE
        SYNTAX       DisplayString
        MAX-ACCESS   read-only
        STATUS       current
        DESCRIPTION
            ""
        ::= { onuUnPassedAdminAuthInfoEntry 7 }

    onuReportPassword OBJECT-TYPE
        SYNTAX       DisplayString
        MAX-ACCESS   read-only
        STATUS       current
        DESCRIPTION
            ""
        ::= { onuUnPassedAdminAuthInfoEntry 8 }

    onuReportType OBJECT-TYPE
        SYNTAX       DisplayString
        MAX-ACCESS   read-only
        STATUS       current
        DESCRIPTION
            "It indicate the type of ONU, such as ZTE-F820. If can't identify
             the type of ONU, this value is unknown.For the more information,
             please refer to onuAdminObjectTable."
        ::= { onuUnPassedAdminAuthInfoEntry 9 }

    zxAnEponOnuSwVersion OBJECT-TYPE
        SYNTAX       DisplayString
        MAX-ACCESS   read-only
        STATUS       current
        DESCRIPTION
            "ONU Software Version"
        ::= { onuUnPassedAdminAuthInfoEntry 10 }


    zxAnEponOnuHwVersion OBJECT-TYPE
        SYNTAX       DisplayString
        MAX-ACCESS   read-only
        STATUS       current
        DESCRIPTION
            "ONU Hardware Version"
        ::= { onuUnPassedAdminAuthInfoEntry 11 }


    zxAnEponOnuOamBuildStatus OBJECT-TYPE
        SYNTAX       INTEGER{
                     failed(1),
                     inProgress(2),
                     notSupport(3),
                     success(4)
                     }
        MAX-ACCESS   read-only
        STATUS       current
        DESCRIPTION
            "The OAM build status of ONU"
        ::= { onuUnPassedAdminAuthInfoEntry 12 }


    onuConfigAdminObjectTable OBJECT-TYPE
            SYNTAX         SEQUENCE OF OnuConfigAdminObjectEntry
            MAX-ACCESS     not-accessible
            STATUS         current
            DESCRIPTION
                ""
            ::= { privateObjects 15 }

    onuConfigAdminObjectEntry OBJECT-TYPE
            SYNTAX         OnuConfigAdminObjectEntry
            MAX-ACCESS     not-accessible
            STATUS         current
            DESCRIPTION
                ""
            INDEX    { ifIndex }
            ::= { onuConfigAdminObjectTable 1}

    OnuConfigAdminObjectEntry ::=
        SEQUENCE {
                onuConfigState               INTEGER,
                onuCfgErrObjTables           Integer32
                }

    onuConfigState OBJECT-TYPE
        SYNTAX       INTEGER{
                     notconfigure(1),
                     configuring(2),
                     configurationsucceeded(3),
                     configurationfailed(4)
                     }
        MAX-ACCESS   read-only
        STATUS       current
        DESCRIPTION
            ""
        ::= { onuConfigAdminObjectEntry 1 }

    onuCfgErrObjTables OBJECT-TYPE
        SYNTAX       Integer32
        MAX-ACCESS   read-only
        STATUS       current
        DESCRIPTION
            ""
        ::= { onuConfigAdminObjectEntry 2 }

    oltPonAttrObjectTable OBJECT-TYPE
            SYNTAX         SEQUENCE OF OltPonAttrObjectEntry
            MAX-ACCESS     not-accessible
            STATUS         current
            DESCRIPTION
                ""
            ::= { privateObjects 16 }

    oltPonAttrObjectEntry OBJECT-TYPE
            SYNTAX         OltPonAttrObjectEntry
            MAX-ACCESS     not-accessible
            STATUS         current
            DESCRIPTION
                ""
            INDEX    { ifIndex }
            ::= { oltPonAttrObjectTable 1}

    OltPonAttrObjectEntry ::=
        SEQUENCE {
                oltPonAttrName                   DisplayString,
                oltPonPonAttrDesc                DisplayString,
                oltPonAttrReset                  INTEGER,
                oltPonAttrResetCounters          INTEGER,
                oltPonAttrMultiLlidState         INTEGER,
                zxAnEponOnuMaxLlidNumber         INTEGER,
                oltPonAuthenticatedOnuIdList     DisplayString,
                oltPonDualRate                   INTEGER,
                zxAnEponIsUseOamCtc2Dot1OrMore   INTEGER
                }

    oltPonAttrName OBJECT-TYPE
        SYNTAX       DisplayString
        MAX-ACCESS   read-write
        STATUS       current
        DESCRIPTION
            ""
        ::= { oltPonAttrObjectEntry 1 }

    oltPonPonAttrDesc OBJECT-TYPE
        SYNTAX       DisplayString
        MAX-ACCESS   read-write
        STATUS       current
        DESCRIPTION
            ""
        ::= { oltPonAttrObjectEntry 2 }

    oltPonAttrReset OBJECT-TYPE
        SYNTAX       INTEGER{
                     running(1),
                     reset(2)
                     }
        MAX-ACCESS   read-write
        STATUS       current
        DESCRIPTION
            ""
        ::= { oltPonAttrObjectEntry 3 }

    oltPonAttrResetCounters OBJECT-TYPE
        SYNTAX       INTEGER{
                     true(1),
                     false(2)
                     }
        MAX-ACCESS   read-write
        STATUS       current
        DESCRIPTION
            ""
        ::= { oltPonAttrObjectEntry 4 }

    oltPonAttrMultiLlidState OBJECT-TYPE
        SYNTAX       INTEGER{
                     enable(1),
                     disable(2)
                     }
        MAX-ACCESS   read-write
        STATUS       current
        DESCRIPTION
            ""
        ::= { oltPonAttrObjectEntry 5 }

    zxAnEponOnuMaxLlidNumber OBJECT-TYPE
        SYNTAX       INTEGER(1..8)
        MAX-ACCESS   read-write
        STATUS       current
        DESCRIPTION
            ""
        ::= { oltPonAttrObjectEntry 6 }

    oltPonAuthenticatedOnuIdList OBJECT-TYPE
        SYNTAX       DisplayString
        MAX-ACCESS   read-only
        STATUS       current
        DESCRIPTION
            "It indicate the ONU's ID list in the PON port,which have
            been authenticated.For example ONU ID 1,2,3,4,10,61,62,63,
            it's value is 1-4,10,61-63."
        ::= { oltPonAttrObjectEntry 7 }

    oltPonDualRate OBJECT-TYPE
        SYNTAX       INTEGER{
                     oneG(1),
                     tenGSymmetric(2),
                     tenGAsymmetric(3)
                     }
        MAX-ACCESS   read-write
        STATUS       current
        DESCRIPTION
            "This object indicates the dual-rate of PON port."
        ::= { oltPonAttrObjectEntry 8 }

    zxAnEponIsUseOamCtc2Dot1OrMore OBJECT-TYPE
        SYNTAX  INTEGER {
                enable(1),
                disable(2)
                }
        MAX-ACCESS   read-write
        STATUS       current
        DESCRIPTION
            "Using OAM CTC2.1 or more version"
        DEFVAL  { enable }
        ::= { oltPonAttrObjectEntry 9 }

    onuUpStreamPriorityObjectTable OBJECT-TYPE
        SYNTAX         SEQUENCE OF OnuUpStreamPriorityObjectEntry
        MAX-ACCESS     not-accessible
        STATUS         current
        DESCRIPTION
                ""
        ::= { privateObjects 17 }

    onuUpStreamPriorityObjectEntry OBJECT-TYPE
            SYNTAX         OnuUpStreamPriorityObjectEntry
            MAX-ACCESS     not-accessible
            STATUS         current
            DESCRIPTION
                ""
            INDEX    { ifIndex }
            ::= { onuUpStreamPriorityObjectTable 1}

    OnuUpStreamPriorityObjectEntry ::=
        SEQUENCE {
                zxEponOnuUpstreamPriority           Integer32,
                zxEponOnuUpstreamDefaultVlan        Integer32,
                zxEponOnuUpStreamPriorityRegenerate INTEGER
                }

    zxEponOnuUpstreamPriority OBJECT-TYPE
        SYNTAX       Integer32
        MAX-ACCESS   read-write
        STATUS       current
        DESCRIPTION
            ""
        ::= { onuUpStreamPriorityObjectEntry 1 }

    zxEponOnuUpstreamDefaultVlan OBJECT-TYPE
        SYNTAX       Integer32
        MAX-ACCESS   read-write
        STATUS       current
        DESCRIPTION
            ""
        ::= { onuUpStreamPriorityObjectEntry 2 }

    zxEponOnuUpStreamPriorityRegenerate OBJECT-TYPE
        SYNTAX      INTEGER{
                        true(1),
                        false(2)
                        }
        MAX-ACCESS   read-write
        STATUS       current
        DESCRIPTION
            ""
        ::= { onuUpStreamPriorityObjectEntry 3 }

    onuDownStreamPriorityObjectTable OBJECT-TYPE
        SYNTAX         SEQUENCE OF OnuDownStreamPriorityObjectEntry
        MAX-ACCESS     not-accessible
        STATUS         current
        DESCRIPTION
                ""
        ::= { privateObjects 18 }

    onuDownStreamPriorityObjectEntry OBJECT-TYPE
            SYNTAX         OnuDownStreamPriorityObjectEntry
            MAX-ACCESS     not-accessible
            STATUS         current
            DESCRIPTION
                ""
            INDEX    { ifIndex }
            ::= { onuDownStreamPriorityObjectTable 1}

    OnuDownStreamPriorityObjectEntry ::=
        SEQUENCE {
                zxEponOnuDownstreamPriority             Integer32,
                zxEponOnuDownstreamDefaultVlan          Integer32,
                zxEponOnuDownStreamPriorityRegenerate   INTEGER
                }

    zxEponOnuDownstreamPriority OBJECT-TYPE
        SYNTAX       Integer32
        MAX-ACCESS   read-write
        STATUS       current
        DESCRIPTION
            ""
        ::= { onuDownStreamPriorityObjectEntry 1 }

    zxEponOnuDownstreamDefaultVlan OBJECT-TYPE
        SYNTAX       Integer32
        MAX-ACCESS   read-write
        STATUS       current
        DESCRIPTION
            ""
        ::= { onuDownStreamPriorityObjectEntry 2 }

    zxEponOnuDownStreamPriorityRegenerate OBJECT-TYPE
        SYNTAX       INTEGER{
                        true(1),
                        false(2)
                        }
        MAX-ACCESS   read-write
        STATUS       current
        DESCRIPTION
            ""
        ::= { onuDownStreamPriorityObjectEntry 3 }


    zxEponOnuDbaPriorityObjectTable OBJECT-TYPE
        SYNTAX         SEQUENCE OF ZxEponOnuDbaPriorityObjectEntry
        MAX-ACCESS     not-accessible
        STATUS         current
        DESCRIPTION
                ""
        ::= { privateObjects 19 }

    zxEponOnuDbaPriorityObjectEntry OBJECT-TYPE
            SYNTAX         ZxEponOnuDbaPriorityObjectEntry
            MAX-ACCESS     not-accessible
            STATUS         current
            DESCRIPTION
                ""
            INDEX    { ifIndex, zxDbaPriority }
            ::= { zxEponOnuDbaPriorityObjectTable 1}

    ZxEponOnuDbaPriorityObjectEntry ::=
        SEQUENCE {
                zxDbaPriority             INTEGER,
                zxCyccleTime              Integer32
                }

    zxDbaPriority OBJECT-TYPE
        SYNTAX       INTEGER
        MAX-ACCESS   not-accessible
        STATUS       current
        DESCRIPTION
            ""
        ::= { zxEponOnuDbaPriorityObjectEntry 1 }

    zxCyccleTime OBJECT-TYPE
        SYNTAX       Integer32
        MAX-ACCESS   read-write
        STATUS       current
        DESCRIPTION
            ""
        ::= { zxEponOnuDbaPriorityObjectEntry 2 }

    zxEponOnuOpticalPowerMeasureObjectTable OBJECT-TYPE
        SYNTAX         SEQUENCE OF ZxEponOnuOpticalPowerMeasureObjectEntry
        MAX-ACCESS     not-accessible
        STATUS         current
        DESCRIPTION
                "EPON ONU optical power measure"
        ::= { privateObjects 20 }

    zxEponOnuOpticalPowerMeasureObjectEntry OBJECT-TYPE
            SYNTAX         ZxEponOnuOpticalPowerMeasureObjectEntry
            MAX-ACCESS     not-accessible
            STATUS         current
            DESCRIPTION
                ""
            INDEX    { ifIndex}
            ::= { zxEponOnuOpticalPowerMeasureObjectTable 1}

    ZxEponOnuOpticalPowerMeasureObjectEntry ::=
        SEQUENCE {
                zxEponOnuTxOpticalPower              DisplayString    ,
                zxEponOnuRxOpticalPower              DisplayString
                }

    zxEponOnuTxOpticalPower OBJECT-TYPE
        SYNTAX       DisplayString(SIZE (1..32))
        MAX-ACCESS   read-only
        STATUS       current
        DESCRIPTION
            ""
        ::= { zxEponOnuOpticalPowerMeasureObjectEntry 1 }

    zxEponOnuRxOpticalPower OBJECT-TYPE
        SYNTAX       DisplayString(SIZE (1..32))
        MAX-ACCESS   read-only
        STATUS       current
        DESCRIPTION
            ""
        ::= { zxEponOnuOpticalPowerMeasureObjectEntry 2 }

    zxEponOltOpticalPowerMeasureObjectTable OBJECT-TYPE
        SYNTAX         SEQUENCE OF ZxEponOltOpticalPowerMeasureObjectEntry
        MAX-ACCESS     not-accessible
        STATUS         current
        DESCRIPTION
                "EPON OLT optical power measure"
        ::= { privateObjects 21 }

    zxEponOltOpticalPowerMeasureObjectEntry OBJECT-TYPE
            SYNTAX         ZxEponOltOpticalPowerMeasureObjectEntry
            MAX-ACCESS     not-accessible
            STATUS         current
            DESCRIPTION
                ""
            INDEX    { ifIndex}
            ::= { zxEponOltOpticalPowerMeasureObjectTable 1}

    ZxEponOltOpticalPowerMeasureObjectEntry ::=
        SEQUENCE {
                zxEponOltTxOpticalPower              DisplayString    ,
                zxEponOltRxOpticalPower              DisplayString
                }

    zxEponOltTxOpticalPower OBJECT-TYPE
        SYNTAX       DisplayString(SIZE (1..32))
        MAX-ACCESS   read-only
        STATUS       current
        DESCRIPTION
            ""
        ::= { zxEponOltOpticalPowerMeasureObjectEntry 1 }

    zxEponOltRxOpticalPower OBJECT-TYPE
        SYNTAX       DisplayString(SIZE (1..32))
        MAX-ACCESS   read-only
        STATUS       current
        DESCRIPTION
            ""
        ::= { zxEponOltOpticalPowerMeasureObjectEntry 2 }
    zxEponHighPriorityFrameObjectTable OBJECT-TYPE
        SYNTAX         SEQUENCE OF ZxEponHighPriorityFrameObjectEntry
        MAX-ACCESS     not-accessible
        STATUS         current
        DESCRIPTION
                ""
        ::= { privateObjects 22 }

    zxEponHighPriorityFrameObjectEntry OBJECT-TYPE
            SYNTAX         ZxEponHighPriorityFrameObjectEntry
            MAX-ACCESS     not-accessible
            STATUS         current
            DESCRIPTION
                "EPON OLT High Priority Frame"
            INDEX    { ifIndex }
            ::= { zxEponHighPriorityFrameObjectTable 1}

    ZxEponHighPriorityFrameObjectEntry ::=
        SEQUENCE {
                priority0                                   INTEGER,
                priority1                                   INTEGER,
                priority2                                   INTEGER,
                priority3                                   INTEGER,
                priority4                                   INTEGER,
                priority5                                   INTEGER,
                priority6                                   INTEGER,
                priority7                                   INTEGER
                }
    priority0 OBJECT-TYPE
        SYNTAX       INTEGER{
                        true(1),
                        false(2)
                        }
        MAX-ACCESS   read-write
        STATUS       current
        DESCRIPTION
            "EPON OLT High Priority Frame Priority0 Value"
        ::= { zxEponHighPriorityFrameObjectEntry 1 }
    priority1 OBJECT-TYPE
        SYNTAX       INTEGER{
                        true(1),
                        false(2)
                        }
        MAX-ACCESS   read-write
        STATUS       current
        DESCRIPTION
            "EPON OLT High Priority Frame Priority1 Value"
        ::= { zxEponHighPriorityFrameObjectEntry 2 }
    priority2 OBJECT-TYPE
        SYNTAX       INTEGER{
                        true(1),
                        false(2)
                        }
        MAX-ACCESS   read-write
        STATUS       current
        DESCRIPTION
            "EPON OLT High Priority Frame Priority2 Value"
        ::= { zxEponHighPriorityFrameObjectEntry 3 }
    priority3 OBJECT-TYPE
        SYNTAX       INTEGER{
                        true(1),
                        false(2)
                        }
        MAX-ACCESS   read-write
        STATUS       current
        DESCRIPTION
            "EPON OLT High Priority Frame Priority3 Value"
        ::= { zxEponHighPriorityFrameObjectEntry 4 }
    priority4 OBJECT-TYPE
        SYNTAX       INTEGER{
                        true(1),
                        false(2)
                        }
        MAX-ACCESS   read-write
        STATUS       current
        DESCRIPTION
            "EPON OLT High Priority Frame Priority4 Value"
        ::= { zxEponHighPriorityFrameObjectEntry 5 }
    priority5 OBJECT-TYPE
        SYNTAX       INTEGER{
                        true(1),
                        false(2)
                        }
        MAX-ACCESS   read-write
        STATUS       current
        DESCRIPTION
            "EPON OLT High Priority Frame Priority5 Value"
        ::= { zxEponHighPriorityFrameObjectEntry 6 }
    priority6 OBJECT-TYPE
        SYNTAX       INTEGER{
                        true(1),
                        false(2)
                        }
        MAX-ACCESS   read-write
        STATUS       current
        DESCRIPTION
            "EPON OLT High Priority Frame Priority6 Value"
        ::= { zxEponHighPriorityFrameObjectEntry 7 }
    priority7 OBJECT-TYPE
        SYNTAX       INTEGER{
                        true(1),
                        false(2)
                        }
        MAX-ACCESS   read-write
        STATUS       current
        DESCRIPTION
            "EPON OLT High Priority Frame Priority7 Value"
        ::= { zxEponHighPriorityFrameObjectEntry 8 }

    zxEponMaxrttObjectTable OBJECT-TYPE
        SYNTAX         SEQUENCE OF ZxEponMaxrttObjectEntry
        MAX-ACCESS     not-accessible
        STATUS         current
        DESCRIPTION
            "EPON OLT Maxrtt"
        ::= { privateObjects 23 }

    zxEponMaxrttObjectEntry OBJECT-TYPE
            SYNTAX         ZxEponMaxrttObjectEntry
            MAX-ACCESS     not-accessible
            STATUS         current
            DESCRIPTION
            "EPON OLT maxrtt"
            INDEX    { ifIndex }
            ::= { zxEponMaxrttObjectTable 1}

    ZxEponMaxrttObjectEntry ::=
        SEQUENCE {
                maxrtt              Integer32
                }
    maxrtt OBJECT-TYPE
        SYNTAX       Integer32
        MAX-ACCESS   read-write
        STATUS       current
        DESCRIPTION
            "EPON OLT maxrtt value"
        ::= { zxEponMaxrttObjectEntry 1 }

    zxEponPriorityQueueMapObjectTable OBJECT-TYPE
        SYNTAX         SEQUENCE OF ZxEponPriorityQueueMapObjectEntry
        MAX-ACCESS     not-accessible
        STATUS         current
        DESCRIPTION
            "EPON OLT priority queue map"
        ::= { privateObjects 24 }

    zxEponPriorityQueueMapObjectEntry OBJECT-TYPE
            SYNTAX         ZxEponPriorityQueueMapObjectEntry
            MAX-ACCESS     not-accessible
            STATUS         current
            DESCRIPTION
            "EPON OLT priority queue map value"
            INDEX    { ifIndex }
            ::= { zxEponPriorityQueueMapObjectTable 1}

    ZxEponPriorityQueueMapObjectEntry ::=
        SEQUENCE {
                downstreampri0Que                                   Integer32,
                downstreampri1Que                                   Integer32,
                downstreampri2Que                                   Integer32,
                downstreampri3Que                                   Integer32,
                downstreampri4Que                                   Integer32,
                downstreampri5Que                                   Integer32,
                downstreampri6Que                                   Integer32,
                downstreampri7Que                                   Integer32,
                upstreampri0Que                                   Integer32,
                upstreampri1Que                                   Integer32,
                upstreampri2Que                                   Integer32,
                upstreampri3Que                                   Integer32,
                upstreampri4Que                                   Integer32,
                upstreampri5Que                                   Integer32,
                upstreampri6Que                                   Integer32,
                upstreampri7Que                                   Integer32
                }
    downstreampri0Que OBJECT-TYPE
        SYNTAX       Integer32
        MAX-ACCESS   read-write
        STATUS       current
        DESCRIPTION
            "EPON OLT priority0 value"
        ::= { zxEponPriorityQueueMapObjectEntry 1 }
    downstreampri1Que OBJECT-TYPE
        SYNTAX       Integer32
        MAX-ACCESS   read-write
        STATUS       current
        DESCRIPTION
            "EPON OLT priority1 value"
        ::= { zxEponPriorityQueueMapObjectEntry 2 }
    downstreampri2Que OBJECT-TYPE
        SYNTAX       Integer32
        MAX-ACCESS   read-write
        STATUS       current
        DESCRIPTION
            "EPON OLT priority2 value"
        ::= { zxEponPriorityQueueMapObjectEntry 3 }
    downstreampri3Que OBJECT-TYPE
        SYNTAX       Integer32
        MAX-ACCESS   read-write
        STATUS       current
        DESCRIPTION
            "EPON OLT priority3 value"
        ::= { zxEponPriorityQueueMapObjectEntry 4 }
    downstreampri4Que OBJECT-TYPE
        SYNTAX       Integer32
        MAX-ACCESS   read-write
        STATUS       current
        DESCRIPTION
            "EPON OLT priority4 value"
        ::= { zxEponPriorityQueueMapObjectEntry 5 }
    downstreampri5Que OBJECT-TYPE
        SYNTAX       Integer32
        MAX-ACCESS   read-write
        STATUS       current
        DESCRIPTION
            "EPON OLT priority5 value"
        ::= { zxEponPriorityQueueMapObjectEntry 6 }
    downstreampri6Que OBJECT-TYPE
        SYNTAX       Integer32
        MAX-ACCESS   read-write
        STATUS       current
        DESCRIPTION
            "EPON OLT priority6 value"
        ::= { zxEponPriorityQueueMapObjectEntry 7 }
    downstreampri7Que OBJECT-TYPE
        SYNTAX       Integer32
        MAX-ACCESS   read-write
        STATUS       current
        DESCRIPTION
            "EPON OLT priority7 value"
        ::= { zxEponPriorityQueueMapObjectEntry 8 }
    upstreampri0Que OBJECT-TYPE
        SYNTAX       Integer32
        MAX-ACCESS   read-write
        STATUS       current
        DESCRIPTION
            "EPON OLT priority0 value"
        ::= { zxEponPriorityQueueMapObjectEntry 9 }
    upstreampri1Que OBJECT-TYPE
        SYNTAX       Integer32
        MAX-ACCESS   read-write
        STATUS       current
        DESCRIPTION
            "EPON OLT priority1 value"
        ::= { zxEponPriorityQueueMapObjectEntry 10 }
    upstreampri2Que OBJECT-TYPE
        SYNTAX       Integer32
        MAX-ACCESS   read-write
        STATUS       current
        DESCRIPTION
            "EPON OLT priority2 value"
        ::= { zxEponPriorityQueueMapObjectEntry 11 }
    upstreampri3Que OBJECT-TYPE
        SYNTAX       Integer32
        MAX-ACCESS   read-write
        STATUS       current
        DESCRIPTION
            "EPON OLT priority3 value"
        ::= { zxEponPriorityQueueMapObjectEntry 12 }
    upstreampri4Que OBJECT-TYPE
        SYNTAX       Integer32
        MAX-ACCESS   read-write
        STATUS       current
        DESCRIPTION
            "EPON OLT priority4 value"
        ::= { zxEponPriorityQueueMapObjectEntry 13 }
    upstreampri5Que OBJECT-TYPE
        SYNTAX       Integer32
        MAX-ACCESS   read-write
        STATUS       current
        DESCRIPTION
            "EPON OLT priority5 value"
        ::= { zxEponPriorityQueueMapObjectEntry 14 }
    upstreampri6Que OBJECT-TYPE
        SYNTAX       Integer32
        MAX-ACCESS   read-write
        STATUS       current
        DESCRIPTION
            "EPON OLT priority6 value"
        ::= { zxEponPriorityQueueMapObjectEntry 15 }
    upstreampri7Que OBJECT-TYPE
        SYNTAX       Integer32
        MAX-ACCESS   read-write
        STATUS       current
        DESCRIPTION
            "EPON OLT priority7 value"
        ::= { zxEponPriorityQueueMapObjectEntry 16 }

    zxEponRxHecObjectTable OBJECT-TYPE
        SYNTAX         SEQUENCE OF ZxEponRxHecObjectEntry
        MAX-ACCESS     not-accessible
        STATUS         current
        DESCRIPTION
            "EPON OLT rxhec"
        ::= { privateObjects 25 }

    zxEponRxHecObjectEntry OBJECT-TYPE
            SYNTAX         ZxEponRxHecObjectEntry
            MAX-ACCESS     not-accessible
            STATUS         current
            DESCRIPTION
            "EPON OLT rxhec"
            INDEX    { ifIndex }
            ::= { zxEponRxHecObjectTable 1}

    ZxEponRxHecObjectEntry ::=
        SEQUENCE {
                rxhec              INTEGER
                }
    rxhec OBJECT-TYPE
        SYNTAX       INTEGER{
                        ahDraft8023(1),
                        ahStandard8023(2),
                        both(3),
                        no(4)
                        }
        MAX-ACCESS   read-write
        STATUS       current
        DESCRIPTION
            "EPON OLT rxhec value: ahDraft8023|ahStandard8023|both|no"
        ::= { zxEponRxHecObjectEntry 1 }

    zxEponOnuAutoCfgObjectTable OBJECT-TYPE
        SYNTAX         SEQUENCE OF ZxEponOnuAutoCfgObjectEntry
        MAX-ACCESS     not-accessible
        STATUS         current
        DESCRIPTION
            "EPON Onu AutoCfg"
        ::= { privateObjects 26 }

    zxEponOnuAutoCfgObjectEntry OBJECT-TYPE
            SYNTAX         ZxEponOnuAutoCfgObjectEntry
            MAX-ACCESS     not-accessible
            STATUS         current
            DESCRIPTION
            "EPON Onu AutoCfg"
            INDEX    { ifIndex }
            ::= { zxEponOnuAutoCfgObjectTable 1}

    ZxEponOnuAutoCfgObjectEntry ::=
        SEQUENCE {
                onuBindStatus              INTEGER,
                onuAutoCfgStatus          INTEGER
                }
    onuBindStatus OBJECT-TYPE
        SYNTAX       INTEGER{
                        enable(1),
                        disable(2)
                        }
        MAX-ACCESS   read-write
        STATUS       current
        DESCRIPTION
            "EPON ONU BindStatus value: disable|enable"
        ::= { zxEponOnuAutoCfgObjectEntry 1 }
    onuAutoCfgStatus OBJECT-TYPE
        SYNTAX       INTEGER{
                        enable(1),
                        disable(2)
                        }
        MAX-ACCESS   read-write
        STATUS       current
        DESCRIPTION
            "EPON ONU AutoCfgStatus value: disable|enable"
        ::= { zxEponOnuAutoCfgObjectEntry 2 }

    zxEponIpPoolObjectTable OBJECT-TYPE
        SYNTAX         SEQUENCE OF ZxEponIpPoolObjectEntry
        MAX-ACCESS     not-accessible
        STATUS         current
        DESCRIPTION
            "EPON Ip Pool"
        ::= { privateObjects 27 }

    zxEponIpPoolObjectEntry OBJECT-TYPE
            SYNTAX         ZxEponIpPoolObjectEntry
            MAX-ACCESS     not-accessible
            STATUS         current
            DESCRIPTION
            "EPON Ip Pool"
            INDEX    { zxEponIpPoolName }
            ::= { zxEponIpPoolObjectTable 1}

    ZxEponIpPoolObjectEntry ::=
        SEQUENCE {
                zxEponIpPoolName              OCTET STRING,
                zxEponIpPoolIpBegin           IpAddress,
                zxEponIpPoolIpEnd             IpAddress,
                zxEponIpPoolMask              IpAddress,
                zxEponIpPoolpriority          INTEGER,
                zxEponIpPoolVlan              INTEGER,
                zxEponIpPoolNetIp             IpAddress,
                zxEponIpPoolNetMask           IpAddress,
                zxEponIpPoolGateway           IpAddress,
                zxEponIpPoolRowStatus         RowStatus
                }
    zxEponIpPoolName OBJECT-TYPE
        SYNTAX       OCTET STRING(SIZE(1..63))
        MAX-ACCESS   not-accessible
        STATUS       current
        DESCRIPTION
            "EPON Ip Pool Name value"
        ::= { zxEponIpPoolObjectEntry 1 }
    zxEponIpPoolIpBegin OBJECT-TYPE
        SYNTAX       IpAddress
        MAX-ACCESS   read-write
        STATUS       current
        DESCRIPTION
            "EPON Ip Addr"
        ::= { zxEponIpPoolObjectEntry 2 }
    zxEponIpPoolIpEnd OBJECT-TYPE
        SYNTAX       IpAddress
        MAX-ACCESS   read-write
        STATUS       current
        DESCRIPTION
            "EPON Ip Addr"
        ::= { zxEponIpPoolObjectEntry 3 }
    zxEponIpPoolMask OBJECT-TYPE
        SYNTAX       IpAddress
        MAX-ACCESS   read-write
        STATUS       current
        DESCRIPTION
            "EPON Ip Mask"
        ::= { zxEponIpPoolObjectEntry 4 }
    zxEponIpPoolpriority OBJECT-TYPE
        SYNTAX       INTEGER
        MAX-ACCESS   read-write
        STATUS       current
        DESCRIPTION
            "EPON Ip Pool Priority value:0~7"
        ::= { zxEponIpPoolObjectEntry 5 }
    zxEponIpPoolVlan OBJECT-TYPE
        SYNTAX       INTEGER
        MAX-ACCESS   read-write
        STATUS       current
        DESCRIPTION
            "EPON Ip Pool Vlan value:1-4094"
        ::= { zxEponIpPoolObjectEntry 6 }
    zxEponIpPoolNetIp OBJECT-TYPE
        SYNTAX      IpAddress
        MAX-ACCESS   read-write
        STATUS       current
        DESCRIPTION
            "EPON IP addr"
        ::= { zxEponIpPoolObjectEntry 7 }
    zxEponIpPoolNetMask OBJECT-TYPE
        SYNTAX      IpAddress
        MAX-ACCESS   read-write
        STATUS       current
        DESCRIPTION
            "EPON IP addr"
        ::= { zxEponIpPoolObjectEntry 8 }
    zxEponIpPoolGateway OBJECT-TYPE
        SYNTAX      IpAddress
        MAX-ACCESS   read-write
        STATUS       current
        DESCRIPTION
            "EPON Ip Mask"
        ::= { zxEponIpPoolObjectEntry 9 }

    zxEponIpPoolRowStatus OBJECT-TYPE
        SYNTAX      RowStatus
        MAX-ACCESS  read-create
        STATUS      current
        DESCRIPTION
            "EPON Ip RowStatus"
        ::= { zxEponIpPoolObjectEntry 10}

        zxEponRunIpObjectTable OBJECT-TYPE
        SYNTAX         SEQUENCE OF ZxEponRunIpObjectEntry
        MAX-ACCESS     not-accessible
        STATUS         current
        DESCRIPTION
            "EPON Run Ip"
        ::= { privateObjects 28 }

    zxEponRunIpObjectEntry OBJECT-TYPE
            SYNTAX         ZxEponRunIpObjectEntry
            MAX-ACCESS     not-accessible
            STATUS         current
            DESCRIPTION
            "EPON Run Ip"
            INDEX    { zxEponRunIp }
            ::= { zxEponRunIpObjectTable 1}

    ZxEponRunIpObjectEntry ::=
        SEQUENCE {
                zxEponRunIp            INTEGER,
                zxEponRunMask          IpAddress,
                zxEponRunOnuIfIndex    INTEGER,
                zxEponRunIpPriority    INTEGER,
                zxEponRunIpVlan        INTEGER,
                zxEponRunIpNetIp       IpAddress,
                zxEponRunIpNetMask     IpAddress,
                zxEponRunIpGateway     IpAddress,
                zxEponRunIpStatus      INTEGER,
                zxEponRunIpCfgMode     INTEGER
                }
    zxEponRunIp OBJECT-TYPE
        SYNTAX       INTEGER
        MAX-ACCESS   not-accessible
        STATUS       current
        DESCRIPTION
            "EPON Run Ip value"
        ::= { zxEponRunIpObjectEntry 1 }
    zxEponRunMask OBJECT-TYPE
        SYNTAX       IpAddress
        MAX-ACCESS  read-only
        STATUS       current
        DESCRIPTION
            "EPON Run Mask value"
        ::= { zxEponRunIpObjectEntry 2 }
    zxEponRunOnuIfIndex OBJECT-TYPE
        SYNTAX       INTEGER
        MAX-ACCESS  read-only
        STATUS       current
        DESCRIPTION
            "EPON Run OnuIfIndex value"
        ::= { zxEponRunIpObjectEntry 3 }
    zxEponRunIpPriority OBJECT-TYPE
        SYNTAX       INTEGER
        MAX-ACCESS  read-only
        STATUS       current
        DESCRIPTION
            "EPON Run Ip Priority value:0~7"
        ::= { zxEponRunIpObjectEntry 4 }
    zxEponRunIpVlan OBJECT-TYPE
        SYNTAX       INTEGER
        MAX-ACCESS  read-only
        STATUS       current
        DESCRIPTION
            "EPON Run Ip Vlan value"
        ::= { zxEponRunIpObjectEntry 5 }
    zxEponRunIpNetIp OBJECT-TYPE
        SYNTAX       IpAddress
        MAX-ACCESS  read-only
        STATUS       current
        DESCRIPTION
            "EPON Run Ip NetIp value"
        ::= { zxEponRunIpObjectEntry 6 }
    zxEponRunIpNetMask OBJECT-TYPE
        SYNTAX       IpAddress
        MAX-ACCESS  read-only
        STATUS       current
        DESCRIPTION
            "EPON Run Ip NetMask value"
        ::= { zxEponRunIpObjectEntry 7 }
    zxEponRunIpGateway OBJECT-TYPE
        SYNTAX       IpAddress
        MAX-ACCESS  read-only
        STATUS       current
        DESCRIPTION
            "EPON Run IpGateway value"
        ::= { zxEponRunIpObjectEntry 8 }
    zxEponRunIpStatus OBJECT-TYPE
        SYNTAX       INTEGER{
                        enable(1),
                        disable(2)
                        }
        MAX-ACCESS  read-only
        STATUS       current
        DESCRIPTION
            "EPON Ip Mask"
        ::= { zxEponRunIpObjectEntry 9 }
    zxEponRunIpCfgMode OBJECT-TYPE
        SYNTAX       INTEGER{
                        static(1),
                        dynamic(2)
                        }
        MAX-ACCESS  read-only
        STATUS       current
        DESCRIPTION
            "EPON Ip CfgMode"
        ::= { zxEponRunIpObjectEntry 10 }

    zxEponIpPoolConjPonObjectTable OBJECT-TYPE
        SYNTAX         SEQUENCE OF ZxEponIpPoolConjPonObjectEntry
        MAX-ACCESS     not-accessible
        STATUS         current
        DESCRIPTION
            "EPON Ip PoolConjPon"
        ::= { privateObjects 29 }

    zxEponIpPoolConjPonObjectEntry OBJECT-TYPE
            SYNTAX         ZxEponIpPoolConjPonObjectEntry
            MAX-ACCESS     not-accessible
            STATUS         current
            DESCRIPTION
            "EPON Ip Pool ConjPon"
            INDEX    { ifIndex }
            ::= { zxEponIpPoolConjPonObjectTable 1}

    ZxEponIpPoolConjPonObjectEntry ::=
        SEQUENCE {
                 zxEponIpPoolConjPonName          OCTET STRING,
                 zxEponIpPoolConjRowStatus        RowStatus
                 }
    zxEponIpPoolConjPonName OBJECT-TYPE
        SYNTAX       OCTET STRING(SIZE(1..63))
        MAX-ACCESS   read-write
        STATUS       current
        DESCRIPTION
            "EPON Ip Pool Name value"
        ::= { zxEponIpPoolConjPonObjectEntry 1 }

    zxEponIpPoolConjRowStatus OBJECT-TYPE
        SYNTAX      RowStatus
        MAX-ACCESS  read-create
        STATUS      current
        DESCRIPTION
            "EPON IpPoolConj RowStatus "
        ::= { zxEponIpPoolConjPonObjectEntry 2}

    zxEponBwProfileAdmin  OBJECT IDENTIFIER ::= { privateObjects 30}

    zxEponBwProfileTable  OBJECT-TYPE
        SYNTAX         SEQUENCE OF ZxEponBwProfileEntry
        MAX-ACCESS     not-accessible
        STATUS         current
        DESCRIPTION
            "EPON up bandwidth profile table"
        ::= { zxEponBwProfileAdmin 1 }

    zxEponBwProfileEntry OBJECT-TYPE
            SYNTAX         ZxEponBwProfileEntry
            MAX-ACCESS     not-accessible
            STATUS         current
            DESCRIPTION
            "EPON up bandwidth profile entry"
            INDEX    { profileIndex }
            ::= { zxEponBwProfileTable 1}

    ZxEponBwProfileEntry ::=
        SEQUENCE {
                profileIndex                INTEGER,
                profileName                 DisplayString,
                upBwProfileFixedBw          Integer32,
                upBwProfileAssuredBw        Integer32,
                upBwProfileMaximumBw        Integer32,
                upBwProfileMaxBurstSize     Integer32,
                upBwProfilePri              Integer32,
                upBwProfileFixedPacketSize  Integer32,
                downBwProfileMaximumBw      Integer32,
                downBwProfileMaxBurstSize   Integer32,
                bwProfileRowStatus          RowStatus
                 }
   profileIndex     OBJECT-TYPE
        SYNTAX       INTEGER(1..256)
        MAX-ACCESS   not-accessible
        STATUS       current
        DESCRIPTION
            ""
        ::= { zxEponBwProfileEntry 1 }


   profileName    OBJECT-TYPE
        SYNTAX      DisplayString(SIZE(1..31))
        MAX-ACCESS  read-write
        STATUS      current
        DESCRIPTION
            "This object identifies a row in this table."
          ::= { zxEponBwProfileEntry 2 }

   upBwProfileFixedBw    OBJECT-TYPE
        SYNTAX       Integer32(0..1000000)
        MAX-ACCESS   read-write
        STATUS       current
        DESCRIPTION
            ""
        ::= { zxEponBwProfileEntry 3 }

   upBwProfileAssuredBw    OBJECT-TYPE
        SYNTAX       Integer32(512..1000000)
        MAX-ACCESS   read-write
        STATUS       current
        DESCRIPTION
            "512k is upAssuredBw's minimum, 1G is upAssuredBw's maximum. "
        ::= { zxEponBwProfileEntry  4 }

   upBwProfileMaximumBw   OBJECT-TYPE
        SYNTAX       Integer32(512..1000000)
        MAX-ACCESS   read-write
        STATUS       current
        DESCRIPTION
            ". "
        ::= { zxEponBwProfileEntry 5 }

    upBwProfileMaxBurstSize OBJECT-TYPE
        SYNTAX       Integer32(1..16777215)
        MAX-ACCESS   read-write
        STATUS       current
        DESCRIPTION
            ""
        ::= { zxEponBwProfileEntry 6 }

    upBwProfilePri         OBJECT-TYPE
        SYNTAX       Integer32(0..7)
        MAX-ACCESS   read-write
        STATUS       current
        DESCRIPTION
            ""
        ::= { zxEponBwProfileEntry 7 }

    upBwProfileFixedPacketSize    OBJECT-TYPE
        SYNTAX       Integer32(0..1582)
        MAX-ACCESS   read-write
        STATUS       current
        DESCRIPTION
            ""
        ::= { zxEponBwProfileEntry 8 }

    downBwProfileMaximumBw   OBJECT-TYPE
        SYNTAX       Integer32(512..999994)
        MAX-ACCESS   read-write
        STATUS       current
        DESCRIPTION
            ""
        ::= { zxEponBwProfileEntry 9 }

    downBwProfileMaxBurstSize   OBJECT-TYPE
        SYNTAX       Integer32(1..16777215)
        MAX-ACCESS   read-write
        STATUS       current
        DESCRIPTION
            ""
        ::= { zxEponBwProfileEntry 10 }

    bwProfileRowStatus     OBJECT-TYPE
        SYNTAX      RowStatus
        MAX-ACCESS  read-create
        STATUS      current
        DESCRIPTION
            "EPON up bandwidth RowStatus "
        ::= { zxEponBwProfileEntry 11 }

    bwProfileNextIndex     OBJECT-TYPE
        SYNTAX      INTEGER
        MAX-ACCESS  read-only
        STATUS      current
        DESCRIPTION
            "Next available index of profile table "
        ::= { zxEponBwProfileAdmin 2 }

    zxEponOnuBwCfgTable  OBJECT-TYPE
        SYNTAX         SEQUENCE OF ZxEponOnuBwCfgEntry
        MAX-ACCESS     not-accessible
        STATUS         current
        DESCRIPTION
            "EPON onu bandwidth profile config table"
        ::= { privateObjects 32 }

    zxEponOnuBwCfgEntry OBJECT-TYPE
            SYNTAX         ZxEponOnuBwCfgEntry
            MAX-ACCESS     not-accessible
            STATUS         current
            DESCRIPTION
            "EPON onu bandwidth profile config entry"
            INDEX    { ifIndex }
            ::= { zxEponOnuBwCfgTable 1}

    ZxEponOnuBwCfgEntry ::=
        SEQUENCE {
                onuCfgBwProfileIndex             INTEGER
                 }

    onuCfgBwProfileIndex    OBJECT-TYPE
        SYNTAX      INTEGER(0..256)
        MAX-ACCESS  read-write
        STATUS      current
        DESCRIPTION
            "onu up bandwidth profile name, 0 for no profile."
          ::= { zxEponOnuBwCfgEntry 1 }


    zxEponOnuIpCfgTable  OBJECT-TYPE
        SYNTAX         SEQUENCE OF ZxEponOnuIpCfgEntry
        MAX-ACCESS     not-accessible
        STATUS         current
        DESCRIPTION
            "EPON Onu Ip Configure table"
        ::= { privateObjects 33 }

    zxEponOnuIpCfgEntry OBJECT-TYPE
            SYNTAX         ZxEponOnuIpCfgEntry
            MAX-ACCESS     not-accessible
            STATUS         current
            DESCRIPTION
            "EPON Onu Ip config entry"
            INDEX    { ifIndex }
            ::= { zxEponOnuIpCfgTable 1}

    ZxEponOnuIpCfgEntry ::=
        SEQUENCE {
                  zxEponOnuIpCfgIpAddr        IpAddress,
                  zxEponOnuIpCfgOperator    INTEGER
                  }
    zxEponOnuIpCfgIpAddr OBJECT-TYPE
        SYNTAX       IpAddress
        MAX-ACCESS   read-only
        STATUS       current
        DESCRIPTION
            "EPON Onu Ip Address"
        ::= { zxEponOnuIpCfgEntry 1 }

    zxEponOnuIpCfgOperator OBJECT-TYPE
        SYNTAX       INTEGER{
                        assign(1),
                        release(2)
                        }
        MAX-ACCESS   read-write
        STATUS       current
        DESCRIPTION
            "EPON Onu Ip operator, assign(1) | release(2)"
        ::= { zxEponOnuIpCfgEntry 2 }


-- ONU auto config when onu online

    zxEponOnuAutoConfigTable OBJECT-TYPE
            SYNTAX         SEQUENCE OF ZxEponOnuAutoConfigEntry
            MAX-ACCESS     not-accessible
            STATUS         current
            DESCRIPTION
                "Determin if config is automaticly send to onu when onu online."
            ::= { privateObjects 34 }

    zxEponOnuAutoConfigEntry OBJECT-TYPE
            SYNTAX         ZxEponOnuAutoConfigEntry
            MAX-ACCESS     not-accessible
            STATUS         current
            DESCRIPTION
                ""
            INDEX    { ifIndex }
            ::= { zxEponOnuAutoConfigTable 1}

    ZxEponOnuAutoConfigEntry ::=
        SEQUENCE {
                zxEponOnuAutoConfigStatus     INTEGER,
                zxEponOnuVoipAutoConfigStatus     INTEGER
                }

    zxEponOnuAutoConfigStatus OBJECT-TYPE
        SYNTAX       INTEGER{
                     off(1),
                     on(2)
                     }
        MAX-ACCESS   read-write
        STATUS       current
        DESCRIPTION
            "Determin if configuration is automaticly send to onu when onu online."
        ::= { zxEponOnuAutoConfigEntry 1 }

    zxEponOnuVoipAutoConfigStatus OBJECT-TYPE
        SYNTAX       INTEGER{
                     off(1),
                     on(2)
                     }
        MAX-ACCESS   read-write
        STATUS       current
        DESCRIPTION
            "Determin if voip configuration is automaticly send to onu when onu online."
        ::= { zxEponOnuAutoConfigEntry 2 }

    zxEponRunningCtrl OBJECT IDENTIFIER  ::=  { privateObjects 35 }

    zxEponRevision     OBJECT-TYPE
           SYNTAX           BITS
               {
                   ctc21(1)
               }
           MAX-ACCESS       read-only
           STATUS           current
           DESCRIPTION      "Module revision flag."
           ::=  {  zxEponRunningCtrl  1  }

    onuCustomObjectTable OBJECT-TYPE
            SYNTAX         SEQUENCE OF OnuCustomObjectEntry
            MAX-ACCESS     not-accessible
            STATUS         current
            DESCRIPTION
                ""
            ::= { privateObjects 36 }

    onuCustomObjectEntry OBJECT-TYPE
            SYNTAX         OnuCustomObjectEntry
            MAX-ACCESS     not-accessible
            STATUS         current
            DESCRIPTION
                ""
            INDEX    { ifIndex }
            ::= { onuCustomObjectTable 1}

    OnuCustomObjectEntry ::=
        SEQUENCE {
                onuOnlineForwardAction              INTEGER
                 }

    onuOnlineForwardAction OBJECT-TYPE
        SYNTAX       INTEGER (1..2147483647)
        MAX-ACCESS   read-write
        STATUS       current
        DESCRIPTION
            "This variable indicates the ONU online forwarding actions.
             The onuOnlineForwardAction is a bit map represented as a
            sum, therefore, it can represent multiple forwarding action.
            The various bit positions are:
                     1     CNC mode  1:enable,0:disable
                     2     to define
                     4     to define
                   ...
            2147483647     to define
            note: if all bit is 0,OLT will not report trap to NMS.
            "
        ::= { onuCustomObjectEntry 1 }


    zxAnEponOnuVportMgmtTable  OBJECT-TYPE
            SYNTAX      SEQUENCE OF ZxAnEponOnuVportMgmtTableEntry
            MAX-ACCESS  not-accessible
            STATUS      current
            DESCRIPTION
                "EPON vport management table."
            ::= {privateObjects 37}

    zxAnEponOnuVportMgmtTableEntry  OBJECT-TYPE
            SYNTAX      ZxAnEponOnuVportMgmtTableEntry
            MAX-ACCESS  not-accessible
            STATUS      current
            DESCRIPTION
                "EPON vport management table."
            INDEX    { ifIndex }
            ::= {zxAnEponOnuVportMgmtTable 1}

    ZxAnEponOnuVportMgmtTableEntry ::=
            SEQUENCE {
                zxAnEponOnuVportMacAddress      MacAddress,
                zxAnEponOnuVportCurrAuthState   INTEGER
                }

    zxAnEponOnuVportMacAddress  OBJECT-TYPE
            SYNTAX      MacAddress
            MAX-ACCESS  read-write
            STATUS      current
            DESCRIPTION
                 "ONU vport mac address."
            ::= { zxAnEponOnuVportMgmtTableEntry 1 }

    zxAnEponOnuVportCurrAuthState  OBJECT-TYPE
            SYNTAX      INTEGER {
                init(1),
                authenticating(2),
                pass(3),
                deny(4)
                }
            MAX-ACCESS  read-only
            STATUS      current
            DESCRIPTION
                 "ONU vport current auth state."
            ::= { zxAnEponOnuVportMgmtTableEntry 2 }

    zxEponQueueBufferObjectTable OBJECT-TYPE
        SYNTAX     SEQUENCE OF  ZxEponQueueBufferObjectEntry
        MAX-ACCESS not-accessible
        STATUS     current
        DESCRIPTION
            "Epon Queue Buffer Size Config table. This table contains
            information about buffer size configured of ifIndex.
            The level of the ifIndex is card number of OLT."
        ::= { privateObjects 38 }

    zxEponQueueBufferObjectEntry OBJECT-TYPE
        SYNTAX      ZxEponQueueBufferObjectEntry
        MAX-ACCESS  not-accessible
        STATUS      current
        DESCRIPTION
            "Entry contains queue buffer size config information."
        INDEX { zxEponQueueRackNo, zxEponQueueShelfNo, zxEponQueueSlotNo }
        ::= { zxEponQueueBufferObjectTable 1}

    ZxEponQueueBufferObjectEntry ::=
        SEQUENCE {
            zxEponQueueRackNo            Integer32,
            zxEponQueueShelfNo           Integer32,
            zxEponQueueSlotNo            Integer32,
            zxEponQueueBufferSize        INTEGER
        }

    zxEponQueueRackNo OBJECT-TYPE
        SYNTAX        Integer32
        MAX-ACCESS    not-accessible
        STATUS        current
        DESCRIPTION
            "Rack number."
        ::= { zxEponQueueBufferObjectEntry 1 }

    zxEponQueueShelfNo OBJECT-TYPE
        SYNTAX        Integer32
        MAX-ACCESS    not-accessible
        STATUS        current
        DESCRIPTION
            "Shelf number."
        ::= { zxEponQueueBufferObjectEntry 2 }

    zxEponQueueSlotNo OBJECT-TYPE
        SYNTAX        Integer32
        MAX-ACCESS    not-accessible
        STATUS        current
        DESCRIPTION
            "Slot number."
        ::= { zxEponQueueBufferObjectEntry 3 }

    zxEponQueueBufferSize OBJECT-TYPE
        SYNTAX      INTEGER(4..1020)
        UNITS       "kbytes"
        MAX-ACCESS  read-write
        STATUS      current
        DESCRIPTION
            "The buffer size of the pon queue in kbyte. The config buffer
            size should be integer multiple of 4."
        DEFVAL { 128 }
        ::= { zxEponQueueBufferObjectEntry 4 }

------------------------------------------------------------------------------
-- zxEponMgmtIndex
------------------------------------------------------------------------------
    -- ifIndex Index table
    -- Olt and LLID board agent

    zxEponIfIndexTable OBJECT-TYPE
        SYNTAX      SEQUENCE OF ZxEponIfIndexEntry
        MAX-ACCESS  not-accessible
        STATUS      current
        DESCRIPTION
            "ifIndex table."
        ::= { zxEponMgmtIndex 1 }

    zxEponIfIndexEntry OBJECT-TYPE
        SYNTAX      ZxEponIfIndexEntry
        MAX-ACCESS  not-accessible
        STATUS      current
        DESCRIPTION
            "An entry in the ifIndex table."
        INDEX   { ifIndex }
        ::= { zxEponIfIndexTable 1 }

    ZxEponIfIndexEntry ::=
        SEQUENCE {
            zxEponifIndex                    INTEGER,
            zxEponEntryStatus                RowStatus
        }

    zxEponifIndex OBJECT-TYPE
        SYNTAX      INTEGER
        MAX-ACCESS  read-only
        STATUS      current
        DESCRIPTION
            ""
        ::= { zxEponIfIndexEntry 1}

    zxEponEntryStatus OBJECT-TYPE
        SYNTAX      RowStatus
        MAX-ACCESS  read-create
        STATUS      current
        DESCRIPTION
            ""
        ::= { zxEponIfIndexEntry 2}

END
