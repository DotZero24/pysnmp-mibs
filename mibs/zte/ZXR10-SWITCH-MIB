--  ************************************************
--  $Id: zxr10switch.mib 8 2005-04-05 12:17:08Z taowq $
--
--  zxr10switch.mib: ZXR10 Switch MIB file
--
--  Mar. 2005, Tao wenqiang
--
--  Copyright(c) 2005 by ZTE Corporaton
--  All rights reservered
--
--  ************************************************

ZXR10-SWITCH-MIB DEFINITIONS ::= BEGIN

IMPORTS
    MODULE-IDENTITY,
    OBJECT-TYPE,
    NOTIFICATION-TYPE,
    experimental,
    Integer32,
    Unsigned32,
    Counter32
        FROM SNMPv2-SMI

    MODULE-COMPLIANCE,
    OBJECT-GROUP,
    NOTIFICATION-GROUP
        FROM SNMPv2-CONF
    enterprises
        FROM SNMPv2-SMI
    MacAddress,RowStatus
        FROM SNMPv2-TC

    mgmt,
    NetworkAddress,
    IpAddress,
    Counter,
    Gauge
        FROM RFC1155-SMI

    ifIndex
		 FROM RFC1213-MIB;

    zte OBJECT IDENTIFIER ::= { enterprises 3902 }
    zxr10 OBJECT IDENTIFIER ::= { zte 3}

    zxr10switch OBJECT IDENTIFIER ::= { zxr10 102}
    zxr10vlan OBJECT IDENTIFIER ::= { zxr10switch 1}
    zxr10igmpSnooping OBJECT IDENTIFIER ::= {  zxr10switch 5}
    zxr10extAlarm OBJECT IDENTIFIER ::= {  zxr10switch 6 }
    zxr10QinQ  OBJECT IDENTIFIER   ::= { zxr10vlan 3 }
    zxr10MemberShip OBJECT IDENTIFIER ::={ zxr10vlan 4}
    zess OBJECT IDENTIFIER ::= { zxr10switch 13}

    vct	        OBJECT IDENTIFIER		::=  {  zxr10switch 14 } --add by jiaolin
    loopdetect	OBJECT IDENTIFIER		::=  {  zxr10switch 15 }
    svlan       OBJECT IDENTIFIER		::=  {  zxr10switch 17 } --add by jiangyan
    vfp         OBJECT IDENTIFIER		::=  {  zxr10switch 18 } --add by jiangyan
    dhcp        OBJECT IDENTIFIER       ::= { zxr10switch 23 } --fzl for ip source guard test

    DisplayString ::= OCTET STRING
    --  This data type is used to model textual information taken
    --  from the NVT ASCII character set.  By convention, objects
    --  with this syntax are declared as having
    --  SIZE (0..255)

     zxr10CpuVlanPvidTable  OBJECT-TYPE
        SYNTAX  SEQUENCE OF Zxr10CpuVlanPvidEntry
        MAX-ACCESS  not-accessible
        STATUS  current
        DESCRIPTION
            "vlan information table."
        ::= { zxr10vlan 1 }

    zxr10CpuVlanPvidEntry  OBJECT-TYPE
        SYNTAX  Zxr10CpuVlanPvidEntry
        MAX-ACCESS  not-accessible
        STATUS  current
        DESCRIPTION
            ""
        INDEX  { zxr10CpuVlanId }
        ::= { zxr10CpuVlanPvidTable 1 }

    Zxr10CpuVlanPvidEntry ::=
        SEQUENCE {
            zxr10CpuVlanId
                Integer32,
            zxr10CpuVlanIf
                Integer32,
            zxr10CpuVlanMtu
                Integer32,
            zxr10CpuVlanState
                INTEGER,
            zxr10CpuVlanSaid
                Integer32,
            zxr10CpuVlanVpnid
                Integer32,
            zxr10CpuVlanRowStatus
                RowStatus,
            zxr10CpuVlanName
                DisplayString,
            zxr10CpuVlanMemPortsPvid
                DisplayString
    }

    zxr10CpuVlanId  OBJECT-TYPE
        SYNTAX  Integer32
        MAX-ACCESS  read-only
        STATUS  current
        DESCRIPTION
            "The vlan id (1-4094)"
        ::= { zxr10CpuVlanPvidEntry 1 }

    zxr10CpuVlanIf  OBJECT-TYPE
        SYNTAX  Integer32
        MAX-ACCESS  read-only
        STATUS  current
        DESCRIPTION
            "The vlan entry -> L3 interface "
        ::= { zxr10CpuVlanPvidEntry 2 }

    zxr10CpuVlanMtu OBJECT-TYPE
        SYNTAX  Integer32 (1..65534)
        MAX-ACCESS  read-only
        STATUS  current
        DESCRIPTION
            "vlan MTU size   "
        ::= { zxr10CpuVlanPvidEntry 3 }

    zxr10CpuVlanState OBJECT-TYPE
        SYNTAX    INTEGER{up(1),down(0)}
        MAX-ACCESS  read-only
        STATUS  current
        DESCRIPTION
            "vlan state:active or suspend  "
        ::= { zxr10CpuVlanPvidEntry 4 }

    zxr10CpuVlanSaid OBJECT-TYPE
        SYNTAX   Integer32
        MAX-ACCESS  read-only
        STATUS  current
        DESCRIPTION
            "Security Association Identifier(SAID)  "
        ::= { zxr10CpuVlanPvidEntry 5 }

    zxr10CpuVlanVpnid  OBJECT-TYPE
        SYNTAX  Integer32
        MAX-ACCESS  read-only
        STATUS  current
        DESCRIPTION
            "The vlan entry -> Vpnid "
        ::= { zxr10CpuVlanPvidEntry 6 }

    zxr10CpuVlanRowStatus OBJECT-TYPE
     SYNTAX       RowStatus
     MAX-ACCESS   read-create
        STATUS  current
        DESCRIPTION
        "creat or delete vlan "
        ::= { zxr10CpuVlanPvidEntry 7 }

    zxr10CpuVlanName OBJECT-TYPE
        SYNTAX   DisplayString
        MAX-ACCESS  read-write
        STATUS  current
        DESCRIPTION
            " vlan name  "
        ::= { zxr10CpuVlanPvidEntry 8 }

    zxr10CpuVlanMemPortsPvid OBJECT-TYPE
        SYNTAX   DisplayString
        MAX-ACCESS  read-write
        STATUS  current
        DESCRIPTION
            "  pvid of port members    "
        ::= { zxr10CpuVlanPvidEntry 9 }

    zxr10CpuVlanTagTable  OBJECT-TYPE
        SYNTAX  SEQUENCE OF Zxr10CpuVlanTagEntry
        MAX-ACCESS  not-accessible
        STATUS  current
        DESCRIPTION
            "vlan information table."
        ::= { zxr10vlan 2 }

    zxr10CpuVlanTagEntry  OBJECT-TYPE
        SYNTAX  Zxr10CpuVlanTagEntry
        MAX-ACCESS  not-accessible
        STATUS  current
        DESCRIPTION
            ""
        INDEX  { zxr10CpuVlanId }
        ::= { zxr10CpuVlanTagTable 1 }

    Zxr10CpuVlanTagEntry ::=
        SEQUENCE {
            zxr10CpuVlanid
                Integer32,
            zxr10CpuVlanvpnid
                Integer32,
            zxr10CpuVlanname
                DisplayString,
            zxr10CpuVlanMemPortsTag
                DisplayString
                         }

    zxr10CpuVlanid  OBJECT-TYPE
        SYNTAX  Integer32
        MAX-ACCESS  read-only
        STATUS  current
        DESCRIPTION
            "The vlan id (1-4094)"
        ::= { zxr10CpuVlanTagEntry 1 }

    zxr10CpuVlanvpnid  OBJECT-TYPE
        SYNTAX  Integer32
        MAX-ACCESS  read-only
        STATUS  current
        DESCRIPTION
            "The vlan entry -> Vpnid "
        ::= { zxr10CpuVlanTagEntry 2 }

    zxr10CpuVlanname OBJECT-TYPE
        SYNTAX   DisplayString
        MAX-ACCESS  read-write
        STATUS  current
        DESCRIPTION
            " vlan name  "
        ::= { zxr10CpuVlanTagEntry 3 }

    zxr10CpuVlanMemPortsTag OBJECT-TYPE
        SYNTAX   DisplayString
        MAX-ACCESS  read-write
        STATUS  current
        DESCRIPTION
            "  tag port members    "
        ::= { zxr10CpuVlanTagEntry 4 }

    zxr10CpuVlanUntagTable  OBJECT-TYPE
        SYNTAX  SEQUENCE OF Zxr10CpuVlanUntagEntry
        MAX-ACCESS  not-accessible
        STATUS  current
        DESCRIPTION
            "vlan information table."
        ::= { zxr10vlan 5 }

    zxr10CpuVlanUntagEntry  OBJECT-TYPE
        SYNTAX  Zxr10CpuVlanUntagEntry
        MAX-ACCESS  not-accessible
        STATUS  current
        DESCRIPTION
            ""
        INDEX  { zxr10CpuVlanId }
        ::= { zxr10CpuVlanUntagTable 1 }

    Zxr10CpuVlanUntagEntry ::=
        SEQUENCE {
            zxr10Cpuvlanid
                Integer32,
            zxr10CpuVlanvpnId
                Integer32,
            zxr10Cpuvlanname
                DisplayString,
            zxr10CpuVlanMemPortsUntag
                DisplayString
                }

    zxr10Cpuvlanid  OBJECT-TYPE
        SYNTAX  Integer32
        MAX-ACCESS  read-only
        STATUS  current
        DESCRIPTION
            "The vlan id (1-4094)"
        ::= { zxr10CpuVlanUntagEntry 1 }

    zxr10CpuVlanvpnId  OBJECT-TYPE
        SYNTAX  Integer32
        MAX-ACCESS  read-only
        STATUS  current
        DESCRIPTION
            "The vlan entry -> Vpnid "
        ::= { zxr10CpuVlanUntagEntry 2 }

    zxr10Cpuvlanname OBJECT-TYPE
        SYNTAX   DisplayString
        MAX-ACCESS  read-write
        STATUS  current
        DESCRIPTION
            " vlan name  "
        ::= { zxr10CpuVlanUntagEntry 3 }

    zxr10CpuVlanMemPortsUntag OBJECT-TYPE
        SYNTAX   DisplayString
        MAX-ACCESS  read-write
        STATUS  current
        DESCRIPTION
            "  pvid of port members    "
        ::= { zxr10CpuVlanUntagEntry 4 }

    zxr10IgmpSnoopingTable  OBJECT-TYPE
        SYNTAX  SEQUENCE OF Zxr10IgmpSnoopingEntry
        MAX-ACCESS  not-accessible
        STATUS  current
        DESCRIPTION
            "ZXR10 igmp snooping table."
        ::= { zxr10igmpSnooping 1 }

    zxr10IgmpSnoopingEntry  OBJECT-TYPE
        SYNTAX  Zxr10IgmpSnoopingEntry
        MAX-ACCESS  not-accessible
        STATUS  current
        DESCRIPTION
            "zxr10 Igmp Snooping Entry"
        INDEX  { zxr10igmpSnoopingGroupId }
        ::= { zxr10IgmpSnoopingTable 1 }

    Zxr10IgmpSnoopingEntry ::=
        SEQUENCE {
            zxr10igmpSnoopingValid
                INTEGER,
            zxr10igmpSnoopingVlanId
                Integer32,
            zxr10igmpSnoopingGroupId
                Integer32,
            zxr10igmpSnoopingDropEnable
                INTEGER,
            zxr10igmpSnoopingMaxHostNum
                Integer32,
            zxr10igmpSnoopingIpAddr
                IpAddress,
            zxr10igmpSnoopingGroupMac
                MacAddress,
            zxr10igmpSnoopingMemPorts0
                OCTET STRING (SIZE(0..64)),
            zxr10igmpSnoopingMemPorts1
                OCTET STRING (SIZE(0..64)),
            zxr10igmpSnoopingMemPorts2
                OCTET STRING (SIZE(0..64)),
            zxr10igmpSnoopingMemPorts3
                OCTET STRING (SIZE(0..64)),
            zxr10igmpSnoopingMemPorts4
                OCTET STRING (SIZE(0..64)),
            zxr10igmpSnoopingMemPorts5
                OCTET STRING (SIZE(0..64)),
            zxr10igmpSnoopingMemPorts6
                OCTET STRING (SIZE(0..64)),
            zxr10igmpSnoopingMemPorts7
                OCTET STRING (SIZE(0..64)),
            zxr10igmpSnoopingMemPorts8
                OCTET STRING (SIZE(0..64)),

            zxr10igmpSnoopingMemPorts9
                OCTET STRING (SIZE(0..64)),
            zxr10igmpSnoopingMemPorts10
                OCTET STRING (SIZE(0..64)),
            zxr10igmpSnoopingMemPorts11
                OCTET STRING (SIZE(0..64)),
            zxr10igmpSnoopingMemPorts12
                OCTET STRING (SIZE(0..64)),

            zxr10pimSnoopingMemPorts0
                OCTET STRING (SIZE(0..64)),
            zxr10pimSnoopingMemPorts1
                OCTET STRING (SIZE(0..64)),
            zxr10pimSnoopingMemPorts2
                OCTET STRING (SIZE(0..64)),
            zxr10pimSnoopingMemPorts3
                OCTET STRING (SIZE(0..64)),
            zxr10pimSnoopingMemPorts4
                OCTET STRING (SIZE(0..64)),
            zxr10pimSnoopingMemPorts5
                OCTET STRING (SIZE(0..64)),
            zxr10pimSnoopingMemPorts6
                OCTET STRING (SIZE(0..64)),
            zxr10pimSnoopingMemPorts7
                OCTET STRING (SIZE(0..64)),
            zxr10pimSnoopingMemPorts8
                OCTET STRING (SIZE(0..64)),

            zxr10pimSnoopingMemPorts9
                OCTET STRING (SIZE(0..64)),
            zxr10pimSnoopingMemPorts10
                OCTET STRING (SIZE(0..64)),
            zxr10pimSnoopingMemPorts11
                OCTET STRING (SIZE(0..64)),
            zxr10pimSnoopingMemPorts12
                OCTET STRING (SIZE(0..64))
    }

    zxr10igmpSnoopingValid  OBJECT-TYPE
        SYNTAX   INTEGER{invalid(0),valid(1)}
        MAX-ACCESS  read-only
        STATUS  current
        DESCRIPTION
            "0 is invalid,1 is valid."
        ::= { zxr10IgmpSnoopingEntry 1 }


    zxr10igmpSnoopingVlanId  OBJECT-TYPE
        SYNTAX  Integer32
        MAX-ACCESS  read-only
        STATUS  current
        DESCRIPTION
            "ZXR10 igmp snooping Vlan Id"
        ::= { zxr10IgmpSnoopingEntry 2 }

    zxr10igmpSnoopingGroupId  OBJECT-TYPE
        SYNTAX  Integer32
        MAX-ACCESS  read-only
        STATUS  current
        DESCRIPTION
            "zxr10 Igmp Snooping Entry"
        ::= { zxr10IgmpSnoopingEntry 3 }

    zxr10igmpSnoopingDropEnable  OBJECT-TYPE
        SYNTAX   INTEGER{enable(0),disable(1)}
        MAX-ACCESS  read-only
        STATUS  current
        DESCRIPTION
            "Enabled/Disables IGMP Multicast."
        ::= { zxr10IgmpSnoopingEntry 4 }

    zxr10igmpSnoopingMaxHostNum  OBJECT-TYPE
        SYNTAX  Integer32
        MAX-ACCESS  read-only
        STATUS  current
        DESCRIPTION
            "MAX hosts can access in this group."
        ::= { zxr10IgmpSnoopingEntry 5 }

    zxr10igmpSnoopingIpAddr  OBJECT-TYPE
        SYNTAX  IpAddress
        MAX-ACCESS  read-only
        STATUS  current
        DESCRIPTION
            "ZXR10 igmp snooping Ip Addr"
        ::= { zxr10IgmpSnoopingEntry 6 }

    zxr10igmpSnoopingGroupMac  OBJECT-TYPE
        SYNTAX  MacAddress
        MAX-ACCESS  read-only
        STATUS  current
        DESCRIPTION
            "ZXR10 igmp snooping Group Mac"
        ::= { zxr10IgmpSnoopingEntry 7 }

    zxr10igmpSnoopingMemPorts0  OBJECT-TYPE
        SYNTAX  OCTET STRING (SIZE(0..64))
        MAX-ACCESS  read-only
        STATUS  current
        DESCRIPTION
            "ZXR10 igmp snooping MemPorts 0"
        ::= { zxr10IgmpSnoopingEntry 8 }

    zxr10igmpSnoopingMemPorts1  OBJECT-TYPE
        SYNTAX  OCTET STRING (SIZE(0..64))
        MAX-ACCESS  read-only
        STATUS  current
        DESCRIPTION
            "ZXR10 igmp snooping MemPorts 1"
        ::= { zxr10IgmpSnoopingEntry 9 }

    zxr10igmpSnoopingMemPorts2  OBJECT-TYPE
        SYNTAX  OCTET STRING (SIZE(0..64))
        MAX-ACCESS  read-only
        STATUS  current
        DESCRIPTION
            "ZXR10 igmp snooping MemPorts 2"
        ::= { zxr10IgmpSnoopingEntry 10 }

    zxr10igmpSnoopingMemPorts3  OBJECT-TYPE
        SYNTAX  OCTET STRING (SIZE(0..64))
        MAX-ACCESS  read-only
        STATUS  current
        DESCRIPTION
            "ZXR10 igmp snooping MemPorts 3"
        ::= { zxr10IgmpSnoopingEntry 11 }

    zxr10igmpSnoopingMemPorts4  OBJECT-TYPE
        SYNTAX  OCTET STRING (SIZE(0..64))
        MAX-ACCESS  read-only
        STATUS  current
        DESCRIPTION
            "ZXR10 igmp snooping MemPorts 4"
        ::= { zxr10IgmpSnoopingEntry 12 }

    zxr10igmpSnoopingMemPorts5  OBJECT-TYPE
        SYNTAX  OCTET STRING (SIZE(0..64))
        MAX-ACCESS  read-only
        STATUS  current
        DESCRIPTION
            "ZXR10 igmp snooping MemPorts 5"
        ::= { zxr10IgmpSnoopingEntry 13 }

    zxr10igmpSnoopingMemPorts6  OBJECT-TYPE
        SYNTAX  OCTET STRING (SIZE(0..64))
        MAX-ACCESS  read-only
        STATUS  current
        DESCRIPTION
            "ZXR10 igmp snooping MemPorts 6"
        ::= { zxr10IgmpSnoopingEntry 14 }

    zxr10igmpSnoopingMemPorts7  OBJECT-TYPE
        SYNTAX  OCTET STRING (SIZE(0..64))
        MAX-ACCESS  read-only
        STATUS  current
        DESCRIPTION
            "ZXR10 igmp snooping MemPorts 7"
        ::= { zxr10IgmpSnoopingEntry 15 }

    zxr10igmpSnoopingMemPorts8  OBJECT-TYPE
        SYNTAX  OCTET STRING (SIZE(0..64))
        MAX-ACCESS  read-only
        STATUS  current
        DESCRIPTION
            "ZXR10 igmp snooping MemPorts 8"
        ::= { zxr10IgmpSnoopingEntry 16 }

   zxr10igmpSnoopingMemPorts9  OBJECT-TYPE
        SYNTAX  OCTET STRING (SIZE(0..64))
        MAX-ACCESS  read-only
        STATUS  current
        DESCRIPTION
            "ZXR10 igmp snooping MemPorts 9"
        ::= { zxr10IgmpSnoopingEntry 17 }

   zxr10igmpSnoopingMemPorts10  OBJECT-TYPE
        SYNTAX  OCTET STRING (SIZE(0..64))
        MAX-ACCESS  read-only
        STATUS  current
        DESCRIPTION
            "ZXR10 igmp snooping MemPorts 10"
        ::= { zxr10IgmpSnoopingEntry 18 }

    zxr10igmpSnoopingMemPorts11  OBJECT-TYPE
        SYNTAX  OCTET STRING (SIZE(0..64))
        MAX-ACCESS  read-only
        STATUS  current
        DESCRIPTION
            "ZXR10 igmp snooping MemPorts 11"
        ::= { zxr10IgmpSnoopingEntry 19 }

    zxr10igmpSnoopingMemPorts12  OBJECT-TYPE
        SYNTAX  OCTET STRING (SIZE(0..64))
        MAX-ACCESS  read-only
        STATUS  current
        DESCRIPTION
            "ZXR10 igmp snooping MemPorts 12"
        ::= { zxr10IgmpSnoopingEntry 20 }

    zxr10pimSnoopingMemPorts0  OBJECT-TYPE
        SYNTAX  OCTET STRING (SIZE(0..64))
        MAX-ACCESS  read-only
        STATUS  current
        DESCRIPTION
            "zxr10 pim Snooping MemPorts 0"
        ::= { zxr10IgmpSnoopingEntry 31 }

    zxr10pimSnoopingMemPorts1  OBJECT-TYPE
        SYNTAX  OCTET STRING (SIZE(0..64))
        MAX-ACCESS  read-only
        STATUS  current
        DESCRIPTION
            "zxr10 pim Snooping MemPorts 1"
        ::= { zxr10IgmpSnoopingEntry 32 }

    zxr10pimSnoopingMemPorts2  OBJECT-TYPE
        SYNTAX  OCTET STRING (SIZE(0..64))
        MAX-ACCESS  read-only
        STATUS  current
        DESCRIPTION
            "zxr10 pim Snooping MemPorts 2"
        ::= { zxr10IgmpSnoopingEntry 33 }

    zxr10pimSnoopingMemPorts3  OBJECT-TYPE
        SYNTAX  OCTET STRING (SIZE(0..64))
        MAX-ACCESS  read-only
        STATUS  current
        DESCRIPTION
            "zxr10 pim Snooping MemPorts 3"
        ::= { zxr10IgmpSnoopingEntry 34 }

    zxr10pimSnoopingMemPorts4  OBJECT-TYPE
        SYNTAX  OCTET STRING (SIZE(0..64))
        MAX-ACCESS  read-only
        STATUS  current
        DESCRIPTION
            "zxr10 pim Snooping MemPorts 4"
        ::= { zxr10IgmpSnoopingEntry 35 }

    zxr10pimSnoopingMemPorts5  OBJECT-TYPE
        SYNTAX  OCTET STRING (SIZE(0..64))
        MAX-ACCESS  read-only
        STATUS  current
        DESCRIPTION
            "zxr10 pim Snooping MemPorts 5"
        ::= { zxr10IgmpSnoopingEntry 36 }

    zxr10pimSnoopingMemPorts6  OBJECT-TYPE
        SYNTAX  OCTET STRING (SIZE(0..64))
        MAX-ACCESS  read-only
        STATUS  current
        DESCRIPTION
            "zxr10 pim Snooping MemPorts 6"
        ::= { zxr10IgmpSnoopingEntry 37 }

    zxr10pimSnoopingMemPorts7  OBJECT-TYPE
        SYNTAX  OCTET STRING (SIZE(0..64))
        MAX-ACCESS  read-only
        STATUS  current
        DESCRIPTION
            "zxr10 pim Snooping MemPorts 7"
        ::= { zxr10IgmpSnoopingEntry 38 }

    zxr10pimSnoopingMemPorts8  OBJECT-TYPE
        SYNTAX  OCTET STRING (SIZE(0..64))
        MAX-ACCESS  read-only
        STATUS  current
        DESCRIPTION
            "zxr10 pim Snooping MemPorts 8"
        ::= { zxr10IgmpSnoopingEntry 39 }

    zxr10pimSnoopingMemPorts9  OBJECT-TYPE
        SYNTAX  OCTET STRING (SIZE(0..64))
        MAX-ACCESS  read-only
        STATUS  current
        DESCRIPTION
            "zxr10 pim Snooping MemPorts 9"
        ::= { zxr10IgmpSnoopingEntry 40 }

    zxr10pimSnoopingMemPorts10  OBJECT-TYPE
        SYNTAX  OCTET STRING (SIZE(0..64))
        MAX-ACCESS  read-only
        STATUS  current
        DESCRIPTION
            "zxr10 pim Snooping MemPorts 10"
        ::= { zxr10IgmpSnoopingEntry 41 }

    zxr10pimSnoopingMemPorts11  OBJECT-TYPE
        SYNTAX  OCTET STRING (SIZE(0..64))
        MAX-ACCESS  read-only
        STATUS  current
        DESCRIPTION
            "zxr10 pim Snooping MemPorts 11"
        ::= { zxr10IgmpSnoopingEntry 42 }

    zxr10pimSnoopingMemPorts12  OBJECT-TYPE
        SYNTAX  OCTET STRING (SIZE(0..64))
        MAX-ACCESS  read-only
        STATUS  current
        DESCRIPTION
            "zxr10 pim Snooping MemPorts 12"
        ::= { zxr10IgmpSnoopingEntry 43 }

    zxr10PimSnoopingNeighborTable  OBJECT-TYPE
        SYNTAX  SEQUENCE OF Zxr10PimSnoopingNeighborEntry
        MAX-ACCESS  not-accessible
        STATUS  current
        DESCRIPTION
            "ZXR10 pim snooping neighbor table."
        ::= { zxr10igmpSnooping 2 }

    zxr10PimSnoopingNeighborEntry  OBJECT-TYPE
        SYNTAX  Zxr10PimSnoopingNeighborEntry
        MAX-ACCESS  not-accessible
        STATUS  current
        DESCRIPTION
            "zxr10 Pim Snooping Neighbor Entry"
        INDEX  { zxr10pimSnoopingNeighborId }
        ::= { zxr10PimSnoopingNeighborTable 1 }

    Zxr10PimSnoopingNeighborEntry ::=
        SEQUENCE {
            zxr10pimSnoopingNeighborValid
                INTEGER,
            zxr10pimSnoopingNeighborVlanId
                Integer32,
            zxr10pimSnoopingNeighborVpnId
                Integer32,
            zxr10pimSnoopingNeighborId
                Integer32,
            zxr10pimSnoopingNeighborSourceIpAddr
                IpAddress,
            zxr10pimSnoopingNeighborPort
                OCTET STRING
    }

    zxr10pimSnoopingNeighborValid  OBJECT-TYPE
        SYNTAX   INTEGER{invalid(0),valid(1)}
        MAX-ACCESS  read-only
        STATUS  current
        DESCRIPTION
            "0 is invalid,1 is valid."
        ::= { zxr10PimSnoopingNeighborEntry 1 }


    zxr10pimSnoopingNeighborVlanId  OBJECT-TYPE
        SYNTAX  Integer32
        MAX-ACCESS  read-only
        STATUS  current
        DESCRIPTION
            "zxr10 pim Snooping Neighbor Vlan Id"
        ::= { zxr10PimSnoopingNeighborEntry 2 }

    zxr10pimSnoopingNeighborVpnId  OBJECT-TYPE
        SYNTAX  Integer32
        MAX-ACCESS  read-only
        STATUS  current
        DESCRIPTION
            "zxr10 pim Snooping Neighbor Vpn Id"
        ::= { zxr10PimSnoopingNeighborEntry 3 }


    zxr10pimSnoopingNeighborId  OBJECT-TYPE
        SYNTAX  Integer32
        MAX-ACCESS  read-only
        STATUS  current
        DESCRIPTION
            "zxr10 pim Snooping Neighbor Id"
        ::= { zxr10PimSnoopingNeighborEntry 4 }

    zxr10pimSnoopingNeighborSourceIpAddr  OBJECT-TYPE
        SYNTAX  IpAddress
        MAX-ACCESS  read-only
        STATUS  current
        DESCRIPTION
            "zxr10 pim Snooping Neighbor Source Ip Addr"
        ::= { zxr10PimSnoopingNeighborEntry 5 }

    zxr10pimSnoopingNeighborPort  OBJECT-TYPE
        SYNTAX  OCTET STRING
        MAX-ACCESS  read-only
        STATUS  current
        DESCRIPTION
            "zxr10 pim Snooping Neighbor Port"
        ::= { zxr10PimSnoopingNeighborEntry 6 }

    zxr10IgmpSnoopingVlanTable  OBJECT-TYPE
        SYNTAX  SEQUENCE OF Zxr10IgmpSnoopingVlanEntry
        MAX-ACCESS  not-accessible
        STATUS  current
        DESCRIPTION
            "ZXR10 igmp snooping vlan table."
        ::= { zxr10igmpSnooping 3 }

    zxr10IgmpSnoopingVlanEntry  OBJECT-TYPE
        SYNTAX  Zxr10IgmpSnoopingVlanEntry
        MAX-ACCESS  not-accessible
        STATUS  current
        DESCRIPTION
            "zxr10 Igmp Snooping Vlan Entry"
        INDEX  { zxr10igmpSnoopingVlanId }
        ::= { zxr10IgmpSnoopingVlanTable 1 }

    Zxr10IgmpSnoopingVlanEntry ::=
        SEQUENCE {
            zxr10igmpSnoopingVlanEntryVlanId
                Integer32,
            zxr10igmpSnoopingVlanEntryEnable
                INTEGER,
            zxr10pimSnoopingVlanEntryEnable
                INTEGER,
            zxr10igmpSnoopingFastLeave
                INTEGER,
            zxr10igmpSnoopingLastMemberQueryInterval
                Integer32,
            zxr10igmpSnoopingMaxGroupNum
                Integer32,
            zxr10igmpSnoopingGroupNum
                Integer32,
            zxr10igmpSnoopingHostTimeOut
                Integer32,
            zxr10igmpSnoopingMrTimeOut
                Integer32

    }

    zxr10igmpSnoopingVlanEntryVlanId  OBJECT-TYPE
        SYNTAX   Integer32
        MAX-ACCESS  read-only
        STATUS  current
        DESCRIPTION
            "zxr10 igmp Snooping Vlan Entry Vlan Id"
        ::= { zxr10IgmpSnoopingVlanEntry 1 }

    zxr10igmpSnoopingVlanEntryEnable  OBJECT-TYPE
        SYNTAX   INTEGER{enable(0),disable(1)}
        MAX-ACCESS  read-only
        STATUS  current
        DESCRIPTION
            "  Enables/disables IGMP Snooping on this vlan"
        ::= { zxr10IgmpSnoopingVlanEntry 2 }

    zxr10pimSnoopingVlanEntryEnable  OBJECT-TYPE
        SYNTAX   INTEGER{enable(0),disable(1)}
        MAX-ACCESS  read-only
        STATUS  current
        DESCRIPTION
            "  Enables/disables PIM Snooping on this vlan"
        ::= { zxr10IgmpSnoopingVlanEntry 3 }

    zxr10igmpSnoopingFastLeave  OBJECT-TYPE
        SYNTAX    INTEGER{fast-leave(0),slow-leave(1)}
        MAX-ACCESS  read-only
        STATUS  current
        DESCRIPTION
            " Enables/disables group membership fast leave "
        ::= { zxr10IgmpSnoopingVlanEntry 4 }

    zxr10igmpSnoopingLastMemberQueryInterval  OBJECT-TYPE
        SYNTAX   Integer32
        MAX-ACCESS  read-only
        STATUS  current
        DESCRIPTION
            " The Last Member Query Interval is the Max Response
              Time inserted into Group-Specific Queries sent in
              response to Leave Group messages, and is also the
              amount of time between Group-Specific Query messages."
        ::= { zxr10IgmpSnoopingVlanEntry 5 }

    zxr10igmpSnoopingMaxGroupNum  OBJECT-TYPE
        SYNTAX   Integer32
        MAX-ACCESS  read-only
        STATUS  current
        DESCRIPTION
            " MAX multicast groups can access in this vlan"
        ::= { zxr10IgmpSnoopingVlanEntry 6 }


    zxr10igmpSnoopingGroupNum  OBJECT-TYPE
        SYNTAX   Integer32
        MAX-ACCESS  read-only
        STATUS  current
        DESCRIPTION
            "  Number of multicast groups access in this vlan currently"
        ::= { zxr10IgmpSnoopingVlanEntry 7 }

    zxr10igmpSnoopingHostTimeOut  OBJECT-TYPE
        SYNTAX   Integer32
        MAX-ACCESS  read-only
        STATUS  current
        DESCRIPTION
            " Host aging-time"
        ::= { zxr10IgmpSnoopingVlanEntry 8 }

    zxr10igmpSnoopingMrTimeOut  OBJECT-TYPE
        SYNTAX   Integer32
        MAX-ACCESS  read-only
        STATUS  current
        DESCRIPTION
            " Router aging-time"
        ::= { zxr10IgmpSnoopingVlanEntry 9 }


    zxr10igmpSnoopingEnable  OBJECT-TYPE
        SYNTAX   INTEGER{enable(0),disable(1)}
        MAX-ACCESS  read-only
        STATUS  current
        DESCRIPTION
            " Enables/disables IGMP Snooping on this device"
        ::= { zxr10igmpSnooping 4 }

    zxr10pimSnoopingEnable  OBJECT-TYPE
        SYNTAX   INTEGER{enable(0),disable(1)}
        MAX-ACCESS  read-only
        STATUS  current
        DESCRIPTION
            " Enables/disables PIM Snooping on this device"
        ::= { zxr10igmpSnooping 5 }

    zxr10igmpSnoopingGlobalQuery  OBJECT-TYPE
        SYNTAX   INTEGER{enable(0),disable(1)}
        MAX-ACCESS  read-only
        STATUS  current
        DESCRIPTION
            " Enabled/Disables IGMP Queries for this device"
        ::= { zxr10igmpSnooping 6}

    zxr10igmpSnoopingQueryInterval  OBJECT-TYPE
        SYNTAX   Integer32
        MAX-ACCESS  read-only
        STATUS  current
        DESCRIPTION
            " The Query Interval is the interval between
              General Queries sent by the Querier.
              Default: 125 seconds.  "
        ::= {zxr10igmpSnooping 7 }

    zxr10igmpSnoopingQueryResponseInterval  OBJECT-TYPE
        SYNTAX   Integer32
        MAX-ACCESS  read-only
        STATUS  current
        DESCRIPTION
            " The Max Response Time inserted into the periodic General Queries"
        ::= { zxr10igmpSnooping 8 }

    zxr10InputAlarmTable    OBJECT-TYPE
    SYNTAX      SEQUENCE OF Zxr10InputAlarmEntry
    MAX-ACCESS  not-accessible
    STATUS      current
    DESCRIPTION
       "the table of input alarm. "
    ::= { zxr10extAlarm 1}

	zxr10InputAlarmEntry    OBJECT-TYPE
	   SYNTAX      Zxr10InputAlarmEntry
	   MAX-ACCESS  not-accessible
	   STATUS      current
	   DESCRIPTION
	      "the table of input alarm. "
	   INDEX  {zxr10InputAlarmIndex }
	   ::= { zxr10InputAlarmTable 1}

	Zxr10InputAlarmEntry ::=
	SEQUENCE {   zxr10InputAlarmIndex  INTEGER,
	             zxr10InputAlarmStatus   INTEGER,
	             zxr10InputAlarmDescription     DisplayString
	}

	zxr10InputAlarmIndex     OBJECT-TYPE
	   SYNTAX      INTEGER
	   MAX-ACCESS  read-only
	   STATUS      current
	   DESCRIPTION
	      "the type of alarm. "
	   ::= { zxr10InputAlarmEntry 1}

	zxr10InputAlarmStatus     OBJECT-TYPE
	   SYNTAX      INTEGER{alarm(1),clear(0) }
	   MAX-ACCESS  read-only
	   STATUS      current
	   DESCRIPTION
	      "the status of alarm. "
	   ::= { zxr10InputAlarmEntry 2}

	zxr10InputAlarmDescription     OBJECT-TYPE
	   SYNTAX      DisplayString(SIZE(0..255))
	   MAX-ACCESS  read-only
	   STATUS      current
	   DESCRIPTION
	      "the description of alarm. "
	   ::= { zxr10InputAlarmEntry 3}

	zxr10OutputAlarmTable    OBJECT-TYPE
	   SYNTAX      SEQUENCE OF Zxr10OutputAlarmEntry
	   MAX-ACCESS  not-accessible
	   STATUS      current
	   DESCRIPTION
	      "the table of input alarm. "
	   ::= { zxr10extAlarm 2}

	zxr10OutputAlarmEntry    OBJECT-TYPE
	   SYNTAX      Zxr10OutputAlarmEntry
	   MAX-ACCESS  not-accessible
	   STATUS      current
	   DESCRIPTION
	      "the table of input alarm. "
	   INDEX  {zxr10OutputAlarmIndex }
	   ::= { zxr10OutputAlarmTable 1}

	Zxr10OutputAlarmEntry ::=
	SEQUENCE {   zxr10OutputAlarmIndex  INTEGER,
	             zxr10OutputAlarmStatus   INTEGER,
	             zxr10OutputAlarmDescription     DisplayString
	        }


	zxr10OutputAlarmIndex     OBJECT-TYPE
	   SYNTAX      INTEGER
	   MAX-ACCESS  read-only
	   STATUS      current
	   DESCRIPTION
	      "the type of alarm. "
	   ::= { zxr10OutputAlarmEntry 1}

	zxr10OutputAlarmStatus     OBJECT-TYPE
	   SYNTAX      INTEGER{alarm(1),clear(0) }
	   MAX-ACCESS  read-write
	   STATUS      current
	   DESCRIPTION
	      "the status of alarm. "
	   ::= { zxr10OutputAlarmEntry 2}

	zxr10OutputAlarmDescription     OBJECT-TYPE
	   SYNTAX      DisplayString(SIZE(0..255))
	   MAX-ACCESS  read-only
	   STATUS      current
	   DESCRIPTION
	      "the description of alarm. "
	   ::= { zxr10OutputAlarmEntry 3}

    zxr10QinQTable  OBJECT-TYPE
        SYNTAX  SEQUENCE OF Zxr10QinQEntry
        MAX-ACCESS  not-accessible
        STATUS  current
        DESCRIPTION
            "switchport qinq(802.1q in 802.1q) configuration table."
        ::= { zxr10QinQ 1 }

    zxr10QinQEntry  OBJECT-TYPE
        SYNTAX  Zxr10QinQEntry
        MAX-ACCESS  not-accessible
        STATUS  current
        DESCRIPTION
            ""
        INDEX  { ifIndex }
        ::= { zxr10QinQTable 1 }

    Zxr10QinQEntry ::=
        SEQUENCE {
            zxr10QinQPortName
                DisplayString,
            zxr10QinQMode
                 INTEGER,
            zxr10QinQTpid
                Integer32,
            zxr10QinQPvid
                Integer32
    }


    zxr10QinQPortName  OBJECT-TYPE
        SYNTAX  DisplayString
        MAX-ACCESS  read-only
        STATUS  current
        DESCRIPTION
            "Name of this port"
        ::= { zxr10QinQEntry 1 }

    zxr10QinQMode  OBJECT-TYPE
        SYNTAX   INTEGER{normal(0),customer(1),uplink(2)}
        MAX-ACCESS  read-write
        STATUS  current
        DESCRIPTION
            "The qinq mode of switchport "
        ::= { zxr10QinQEntry 2 }

    zxr10QinQTpid  OBJECT-TYPE
        SYNTAX   Integer32
        MAX-ACCESS  read-write
        STATUS  current
        DESCRIPTION
            "The qinq tpid of switchport "
        ::= { zxr10QinQEntry 3 }

    zxr10QinQPvid  OBJECT-TYPE
        SYNTAX  Integer32
        MAX-ACCESS  read-only
        STATUS  current
        DESCRIPTION
            "The native vlan id of switchport "
        ::= { zxr10QinQEntry 4 }


    zxr10QinQExtendTpid  OBJECT-TYPE
        SYNTAX   Integer32
        MAX-ACCESS  read-write
        STATUS  current
        DESCRIPTION
            "The extend qinq tpid"
        ::= { zxr10QinQ 2 }

    zxr10QinQStandardTpid  OBJECT-TYPE
        SYNTAX   Integer32
        MAX-ACCESS  read-write --not-accessible
        STATUS  current
        DESCRIPTION
            "The standard qinq tpid"
        ::= { zxr10QinQ 3 }


    zxr10MemberShipTable  OBJECT-TYPE
        SYNTAX  SEQUENCE OF Zxr10MemberShipEntry
        MAX-ACCESS  not-accessible
        STATUS  current
        DESCRIPTION
            "vlan membership information table."
        ::= { zxr10MemberShip 1 }

    zxr10MemberShipEntry  OBJECT-TYPE
        SYNTAX  Zxr10MemberShipEntry
        MAX-ACCESS  not-accessible
        STATUS  current
        DESCRIPTION
            ""
        INDEX  { ifIndex }
        ::= { zxr10MemberShipTable 1 }

    Zxr10MemberShipEntry ::=
        SEQUENCE {
            zxr10MemberShipPortName
                DisplayString,
            zxr10MemberShipPvid
                Integer32,
            zxr10MemberShipMode
                INTEGER,
            zxr10MemberShipVlansTag
                OCTET STRING,
            zxr10MemberShipVlansHybridUnTag
                OCTET STRING,
            zxr10MemberShipVlansTag2k
                OCTET STRING,
            zxr10MemberShipVlansHybridUnTag2k
                OCTET STRING,
            zxr10MemberShipVlansTag3k
                OCTET STRING,
            zxr10MemberShipVlansHybridUnTag3k
                OCTET STRING,
            zxr10MemberShipVlansTag4k
                OCTET STRING,
            zxr10MemberShipVlansHybridUnTag4k
                OCTET STRING
    }


    zxr10MemberShipPortName  OBJECT-TYPE
        SYNTAX  DisplayString
        MAX-ACCESS  read-only
        STATUS  current
        DESCRIPTION
            "Name of this port"
        ::= { zxr10MemberShipEntry 1 }

    zxr10MemberShipPvid  OBJECT-TYPE
        SYNTAX  Integer32
        MAX-ACCESS  read-write
        STATUS  current
        DESCRIPTION
            "The native vlan id of this interface"
        ::= { zxr10MemberShipEntry 2 }

    zxr10MemberShipMode  OBJECT-TYPE
        SYNTAX   INTEGER{access(0),trunk(1), hybrid(2)}
        MAX-ACCESS  read-write
        STATUS  current
        DESCRIPTION
            "Vlan mode of this interface."
        ::= { zxr10MemberShipEntry 3 }

    zxr10MemberShipVlansTag OBJECT-TYPE
        SYNTAX   OCTET STRING (SIZE(0..128))
        MAX-ACCESS  read-write
        STATUS  current
        DESCRIPTION
            "  vlan tag bitMap (1-1023) "
        ::= { zxr10MemberShipEntry 4 }

    zxr10MemberShipVlansHybridUnTag OBJECT-TYPE
        SYNTAX   OCTET STRING (SIZE(0..128))
        MAX-ACCESS  read-write
        STATUS  current
        DESCRIPTION
            "  vlan untag bitMap(1-1023) of hybrid ports "
        ::= { zxr10MemberShipEntry 5 }

    zxr10MemberShipVlansTag2k OBJECT-TYPE
        SYNTAX   OCTET STRING (SIZE(0..128))
        MAX-ACCESS  read-write
        STATUS  current
        DESCRIPTION
            "  vlan bitMap (1024-2047) "
        ::= { zxr10MemberShipEntry 6 }

    zxr10MemberShipVlansHybridUnTag2k OBJECT-TYPE
        SYNTAX   OCTET STRING (SIZE(0..128))
        MAX-ACCESS  read-write
        STATUS  current
        DESCRIPTION
            "  vlan untag bitMap(1024-2047) of hybrid ports "
        ::= { zxr10MemberShipEntry 7 }

    zxr10MemberShipVlansTag3k OBJECT-TYPE
        SYNTAX   OCTET STRING (SIZE(0..128))
        MAX-ACCESS  read-write
        STATUS  current
        DESCRIPTION
            "  vlan tag bitMap (2048-3071) "
        ::= { zxr10MemberShipEntry 8 }

    zxr10MemberShipVlansHybridUnTag3k OBJECT-TYPE
        SYNTAX   OCTET STRING (SIZE(0..128))
        MAX-ACCESS  read-write
        STATUS  current
        DESCRIPTION
            "  vlan untag bitMap(2048-3071) of hybrid ports "
        ::= { zxr10MemberShipEntry 9 }

    zxr10MemberShipVlansTag4k OBJECT-TYPE
        SYNTAX   OCTET STRING (SIZE(0..128))
        MAX-ACCESS  read-write
        STATUS  current
        DESCRIPTION
            "  vlan tag bitMap (3072-4094) "
        ::= { zxr10MemberShipEntry 10 }

    zxr10MemberShipVlansHybridUnTag4k OBJECT-TYPE
        SYNTAX   OCTET STRING (SIZE(0..128))
        MAX-ACCESS  read-write
        STATUS  current
        DESCRIPTION
            "  vlan untag bitMap(3072-4094) of hybrid ports "
        ::= { zxr10MemberShipEntry 11 }

    zessClearAllChangeTimes  OBJECT-TYPE
    	SYNTAX      INTEGER{
                      reset(1)
                    }
        MAX-ACCESS      read-write
        STATUS          current
        DESCRIPTION
            " Clear all zessChangeTimes of the domain table."
    ::= { zess 1 }

    zessDomainTable OBJECT-TYPE
        SYNTAX  SEQUENCE OF ZessDomainEntry
        MAX-ACCESS  not-accessible
        STATUS  current
        DESCRIPTION
            "A table that contains ZESS domain info."
        ::= { zess 2 }

    zessDomainEntry  OBJECT-TYPE
        SYNTAX  ZessDomainEntry
        MAX-ACCESS  not-accessible
        STATUS  current
        DESCRIPTION
            "A list of  entries of ZESS domain information."
        INDEX  { zessDomainId }
        ::= { zessDomainTable 1 }

    ZessDomainEntry ::=
        SEQUENCE {
            zessDomainId
                Integer32,
            zessProtectInstanceId
                Integer32,
            zessPrimaryPort
                DisplayString,
            zessSecondaryPort
                DisplayString,
            zessPreupDelayTime
                Integer32,
            zessDomainMode
                INTEGER,
            zessDomainState
                INTEGER,
            zessPriIfState
                INTEGER,
            zessSecIfState
                INTEGER,
            zessChangeTimes
                INTEGER,
            zessClearChangeTimes
                INTEGER,
            zessDomainRowStatus
                RowStatus
    }

    zessDomainId OBJECT-TYPE
        SYNTAX  Integer32(1..4)
        MAX-ACCESS  read-only
        STATUS  current
        DESCRIPTION
            "The id of a ZESS domain."
        ::= { zessDomainEntry 1 }

    zessProtectInstanceId OBJECT-TYPE
        SYNTAX  Integer32(0..16)
        MAX-ACCESS  read-create
        STATUS  current
        DESCRIPTION
            "The protect instance id of a ZESS domain."
        ::= { zessDomainEntry 2 }

    zessPrimaryPort OBJECT-TYPE
        SYNTAX  DisplayString
        MAX-ACCESS  read-create
        STATUS  current
        DESCRIPTION
            "The primary port name of the domain."
        ::= { zessDomainEntry 3 }

    zessSecondaryPort OBJECT-TYPE
        SYNTAX  DisplayString
        MAX-ACCESS  read-create
        STATUS  current
        DESCRIPTION
            "The second port name of the domain."
        ::= { zessDomainEntry 4 }

    zessPreupDelayTime OBJECT-TYPE
        SYNTAX  Integer32(1..600)
        MAX-ACCESS  read-create
        STATUS  current
        DESCRIPTION
            "The preup deley time of the domain, it's default value is 2s."
        ::= { zessDomainEntry 5 }

    zessDomainMode OBJECT-TYPE
    	SYNTAX          INTEGER{
                          revertive(0),
                          nonrevertive(1)
                        }

        MAX-ACCESS  read-create
        STATUS  current
        DESCRIPTION
            "The mode of the domain."
        ::= { zessDomainEntry 6 }

    zessDomainState OBJECT-TYPE
    	SYNTAX   INTEGER{
    				unknown(0),
                    up(1),
                    down(2),
                    init(3),
                    preup(4)
                 }
        MAX-ACCESS  read-only
        STATUS  current
        DESCRIPTION
            "The state of the domain."
        ::= { zessDomainEntry 7 }

    zessPriIfState OBJECT-TYPE
    	SYNTAX   INTEGER{
                    unknown(0),
                    block(1),
                    forward(3)
                 }
        MAX-ACCESS  read-only
        STATUS  current
        DESCRIPTION
            "The state of the primary port."
        ::= { zessDomainEntry 8 }

    zessSecIfState OBJECT-TYPE
    	SYNTAX    INTEGER{
                    unknown(0),
                    block(1),
                    forward(3)
                  }
        MAX-ACCESS  read-only
        STATUS  current
        DESCRIPTION
            "The state of the second port."
        ::= { zessDomainEntry 9 }

    zessChangeTimes OBJECT-TYPE
    	SYNTAX      INTEGER
        MAX-ACCESS  read-only
        STATUS  current
        DESCRIPTION
            "The change times of the domain."
        ::= { zessDomainEntry 10 }

    zessClearChangeTimes  OBJECT-TYPE
    	SYNTAX      INTEGER{
                      reset(1)
                    }
        MAX-ACCESS      read-create
        STATUS          current
        DESCRIPTION
            " Clear zessChangeTimes of the domain."
    ::= { zessDomainEntry 11 }

    zessDomainRowStatus  OBJECT-TYPE
        SYNTAX          RowStatus
        MAX-ACCESS      read-create
        STATUS          current
        DESCRIPTION
            "The RowStatus of this row instance.It could be used for creating,modify or remove instance.
            createAndGo(4) is to create primary port and secondary port for a domain,
            destroy(6) is to delete a domain,
            notInService(2) is to delete primary port and secondary port in a domain."
        ::= { zessDomainEntry 12 }

        vctPortTable	OBJECT-TYPE
		SYNTAX		SEQUENCE  OF  VctPortEntry
		MAX-ACCESS	not-accessible
		STATUS		current
		DESCRIPTION	"The table of all ports' virtual cable test."
		::=  { vct  1 }

    -------------------------------------------------------------------
    --     vct port table added by jiaolin                           --
    -------------------------------------------------------------------
	vctPortEntry	OBJECT-TYPE
		SYNTAX		VctPortEntry
		MAX-ACCESS	not-accessible
		STATUS		current
		DESCRIPTION	"Each entry contains port config for VCT."
		INDEX		{  vctPortName  }
		::=  { vctPortTable 1 }

	VctPortEntry  ::=  SEQUENCE {
		vctPortName      DisplayString,
		vctIsValid       INTEGER,
		vctCableStatus   INTEGER,
		vctPair1Result   DisplayString,
		vctPair1Lenth    DisplayString,
		vctPair2Result   DisplayString,
		vctPair2Lenth    DisplayString,
		vctPair3Result   DisplayString,
		vctPair3Lenth    DisplayString,
		vctPair4Result   DisplayString,
		vctPair4Lenth    DisplayString,
		vctRowStatus     RowStatus
		}


    vctPortName	OBJECT-TYPE
		SYNTAX			DisplayString (SIZE(1..32))
		MAX-ACCESS		read-only
	    STATUS			current
		DESCRIPTION		"The port name to index vct config."
		::=  {  vctPortEntry  1  }

     vctIsValid	OBJECT-TYPE
        SYNTAX			INTEGER {
                            invalid ( 0 ) ,
                            valid   ( 1 )
                            }
		MAX-ACCESS		read-only
		STATUS			current
		DESCRIPTION		"0 means invalid,may be get message fail.
		                 1 means valid  "
        ::=  {  vctPortEntry  2 }


    vctCableStatus	OBJECT-TYPE
        SYNTAX			INTEGER {
                            good  ( 0 ) ,
                            fault ( 1 ) ,
                            not-support ( 2 )
                            }
		MAX-ACCESS		read-only
		STATUS			current
		DESCRIPTION		"This item indicates vct CableStatus.
		                 default fault"
        ::=  {  vctPortEntry  3  }

    vctPair1Result	OBJECT-TYPE
        SYNTAX			DisplayString (SIZE(0..10))
     	MAX-ACCESS		read-only
		STATUS			current
		DESCRIPTION		"This item indicates the cable status: open,
		                short or impedance mismatch."
        ::=  {  vctPortEntry  4  }

    vctPair1Lenth	OBJECT-TYPE
        SYNTAX			DisplayString (SIZE(0..10))
		MAX-ACCESS		read-only
		STATUS			current
		DESCRIPTION		"This item indicates fault position."
        ::=  {  vctPortEntry  5  }

    vctPair2Result	OBJECT-TYPE
        SYNTAX		    DisplayString (SIZE(0..10))
        MAX-ACCESS		read-only
		STATUS			current
		DESCRIPTION		"This item indicates the cable status: open,
		                short or impedance mismatch."
        ::=  {  vctPortEntry  6  }

    vctPair2Lenth	OBJECT-TYPE
        SYNTAX			DisplayString (SIZE(0..10))
        MAX-ACCESS		read-only
		STATUS			current
		DESCRIPTION		"This item indicates fault position."
        ::=  {  vctPortEntry  7  }

    vctPair3Result	OBJECT-TYPE
        SYNTAX			DisplayString (SIZE(0..10))
        MAX-ACCESS		read-only
		STATUS			current
		DESCRIPTION		"This item indicates the cable status: open,
		                short or impedance mismatch."
        ::=  {  vctPortEntry  8 }

    vctPair3Lenth	OBJECT-TYPE
        SYNTAX			DisplayString (SIZE(0..10))
		MAX-ACCESS		read-only
		STATUS			current
		DESCRIPTION		"This item indicates fault position."
        ::=  {  vctPortEntry  9  }

    vctPair4Result	OBJECT-TYPE
        SYNTAX			DisplayString (SIZE(0..10))
		MAX-ACCESS		read-only
		STATUS			current
		DESCRIPTION		"This item indicates the cable status: open,
		                short or impedance mismatch."
        ::=  {  vctPortEntry  10  }

    vctPair4Lenth	OBJECT-TYPE
        SYNTAX			DisplayString (SIZE(0..10))
		MAX-ACCESS		read-only
		STATUS			current
		DESCRIPTION		"This item indicates fault position."
        ::=  {  vctPortEntry  11  }

    vctRowStatus OBJECT-TYPE
        SYNTAX          RowStatus
        MAX-ACCESS      read-create
        STATUS          current
        DESCRIPTION
            "The RowStatus of this row instance.It could be used for creating
             instance.createAndGo(4) is to create a new row."
    ::= { vctPortEntry 12 }

      	-- The mib about vct and loopdetect

    vctTable  OBJECT-TYPE
        SYNTAX  SEQUENCE OF VctEntry
        MAX-ACCESS  not-accessible
        STATUS  current
        DESCRIPTION
            "The vctTable contains the parameter of cable."
        ::= { vct 2 }

    vctEntry  OBJECT-TYPE
        SYNTAX  VctEntry
        MAX-ACCESS  not-accessible
        STATUS  current
        DESCRIPTION
            "The parameter list of cable."
        INDEX  { vctIfindex }
        ::= { vctTable 1 }

    VctEntry ::=
        SEQUENCE {
        	vctIfindex
        		 Integer32,
        	vctSetIfindex
        		 INTEGER,
            cableStatus
                 INTEGER,
            doubleCableStatus1-2
                 INTEGER,
            doubleCableStatus3-6
                 INTEGER,
            doubleCableStatus4-5
                 INTEGER,
			doubleCableStatus7-8
                 INTEGER,
            doubleCableLength1-2
                 INTEGER,
            doubleCableLength3-6
                 INTEGER,
            doubleCableLength4-5
                 INTEGER,
            doubleCableLength7-8
                 INTEGER
                }
    vctIfindex  OBJECT-TYPE
        SYNTAX   Integer32
        MAX-ACCESS  not-accessible
        STATUS      current
        DESCRIPTION
            "The ifindex of port,it is same to ifindex."
        ::= { vctEntry 1 }

    vctSetIfindex  OBJECT-TYPE
        SYNTAX   INTEGER{enable(1),disable(0)}
        MAX-ACCESS  read-write
        STATUS      current
        DESCRIPTION
            "The ifindex of port, which need to be checked."
        ::= { vctEntry 2 }

    cableStatus  OBJECT-TYPE
        SYNTAX   INTEGER{good(1),fault(0)}
        MAX-ACCESS  read-only
        STATUS      current
        DESCRIPTION
            "The status of cable, either good or fault."
        ::= { vctEntry 3 }

    doubleCableStatus1-2  OBJECT-TYPE
        SYNTAX   INTEGER{
        			good(0),
        			open(1),
        			short(2),
        			broken(3),
        			mismatch(4),
        			fail(5),
        			unknown(6),
        			null(7)
        			}
        MAX-ACCESS  read-only
        STATUS      current
        DESCRIPTION
            "The status of cable pair 1-2."
        ::= { vctEntry 4 }

    doubleCableStatus3-6  OBJECT-TYPE
        SYNTAX   INTEGER{
        			good(0),
        			open(1),
        			short(2),
        			broken(3),
        			mismatch(4),
        			fail(5),
        			unknown(6),
        			null(7)
        			}
        MAX-ACCESS  read-only
        STATUS      current
        DESCRIPTION
            "The status of cable pair 3-6."
        ::= { vctEntry 5 }


    doubleCableStatus4-5  OBJECT-TYPE
        SYNTAX   INTEGER{
        			good(0),
        			open(1),
        			short(2),
        			broken(3),
        			mismatch(4),
        			fail(5),
        			unknown(6),
        			null(7)
        			}
        MAX-ACCESS  read-only
        STATUS      current
        DESCRIPTION
            "The status of cable pair 4-5."
        ::= { vctEntry 6 }
    doubleCableStatus7-8  OBJECT-TYPE
        SYNTAX   INTEGER{
        			good(0),
        			open(1),
        			short(2),
        			broken(3),
        			mismatch(4),
        			fail(5),
        			unknown(6),
        			null(7)
           			}
        MAX-ACCESS  read-only
        STATUS      current
        DESCRIPTION
            "The status of cable pair 7-8."
        ::= { vctEntry 7 }

    doubleCableLength1-2  OBJECT-TYPE
        SYNTAX   INTEGER{
        			lessthan50(200),
        			from50to80(201),
        			from80to110(202),
        			from110to140(203),
        			morethan140(204),
        			unknow(205),
        			null(206)
        			}
        MAX-ACCESS  read-only
        STATUS  current
        DESCRIPTION
            "The length of cable pair 1-2."
        ::= { vctEntry 8 }

    doubleCableLength3-6  OBJECT-TYPE
        SYNTAX   INTEGER{
        			lessthan50(200),
        			from50to80(201),
        			from80to110(202),
        			from110to140(203),
        			morethan140(204),
        			unknow(205),
        			null(206)
        			}
        MAX-ACCESS  read-only
        STATUS  current
        DESCRIPTION
            "The length of cable pair 3-6."
        ::= { vctEntry 9 }


    doubleCableLength4-5  OBJECT-TYPE
        SYNTAX   INTEGER{
        			lessthan50(200),
        			from50to80(201),
        			from80to110(202),
        			from110to140(203),
        			morethan140(204),
        			unknow(205),
        			null(206)
        			}
        MAX-ACCESS  read-only
        STATUS  current
        DESCRIPTION
            "The length of cable pair 4-5."
        ::= { vctEntry 10 }

    doubleCableLength7-8  OBJECT-TYPE
        SYNTAX   INTEGER{
        			lessthan50(200),
        			from50to80(201),
        			from80to110(202),
        			from110to140(203),
        			morethan140(204),
        			unknow(205),
        			null(206)
        			}
        MAX-ACCESS  read-only
        STATUS  current
        DESCRIPTION
            "The length of cable pair 7-8."
        ::= { vctEntry 11 }


    -------------------------------------------------------------------
    --     loop detect table added by jiaolin                        --
    -------------------------------------------------------------------
    loopdetectReopenTime  OBJECT-TYPE
        SYNTAX  Integer32 (1..16777216)
        MAX-ACCESS  read-write
        STATUS  current
        DESCRIPTION
            "The delay(minute) reopenning the interface after it was shut down.
              default 10 minute"
        ::= { loopdetect 1 }

    loopdetectTable  OBJECT-TYPE
        SYNTAX  SEQUENCE OF LoopdetectEntry
        MAX-ACCESS  not-accessible
        STATUS  current
        DESCRIPTION
            "The parameter which the loopdetectTable contains."
        ::= { loopdetect 2 }

    loopdetectEntry  OBJECT-TYPE
        SYNTAX  LoopdetectEntry
        MAX-ACCESS  not-accessible
        STATUS  current
        DESCRIPTION
            "The parameter list shows the happened loopdetect."
        INDEX  { loopdetectPanelNum, loopdetectPortNum  }
        ::= { loopdetectTable 1 }

    LoopdetectEntry ::=
        SEQUENCE {
        	loopdetectPanelNum
        		 Integer32,
            loopdetectPortNum
        		 Integer32,
            loopdetectPortName
                 DisplayString,
            loopdetectPortOperStatus
                 INTEGER,
            loopdetectPortVlan
                 DisplayString,
            loopdetectPortMonitor
                 INTEGER,
            loopdetectPortRowStatus
                 RowStatus
            }

    loopdetectPanelNum  OBJECT-TYPE
        SYNTAX      Integer32 (1..12)
        MAX-ACCESS  read-only
        STATUS      current
        DESCRIPTION
            "panel num ."
        ::= { loopdetectEntry 1 }

    loopdetectPortNum  OBJECT-TYPE
        SYNTAX      Integer32 (1..48)
        MAX-ACCESS  read-only
        STATUS      current
        DESCRIPTION
            "port num ."
        ::= { loopdetectEntry 2 }


    loopdetectPortName  OBJECT-TYPE
        SYNTAX      DisplayString (SIZE(0..32))
        MAX-ACCESS  read-only
        STATUS      current
        DESCRIPTION
            "The name of port, it is same to ifindex."
        ::= { loopdetectEntry 3 }

    loopdetectPortOperStatus  OBJECT-TYPE
        SYNTAX   INTEGER{
                   normal ( 0 ),
                   protect ( 1 ),
                   block ( 2 )
                   }
        MAX-ACCESS  read-create
        STATUS      current
        DESCRIPTION
            "The status of the port."
        ::= { loopdetectEntry 4 }

    loopdetectPortVlan  OBJECT-TYPE
        SYNTAX      DisplayString(SIZE(0..40))
        MAX-ACCESS  read-create
        STATUS  current
        DESCRIPTION
            "The vlan list which the loopdetect port belong to."
        ::= { loopdetectEntry 5 }

    loopdetectPortMonitor  OBJECT-TYPE
        SYNTAX   INTEGER{
                    enable ( 1 ),
                    disable ( 0 )
                    }
        MAX-ACCESS  read-create
        STATUS      current
        DESCRIPTION
            "The loopdetect protocol enable/disable."
        ::= { loopdetectEntry 6 }

    loopdetectPortRowStatus OBJECT-TYPE
        SYNTAX          RowStatus
        MAX-ACCESS      read-create
        STATUS          current
        DESCRIPTION
            "The RowStatus of this row instance.It could be used for creating,
            modify  instance.createAndGo(4) is to create a new row."
    ::= { loopdetectEntry 7 }


    ----------------------------------------------------------------
    -- svlan session table add by jiangyan
    ----------------------------------------------------------------
    zxr10svlanCount        OBJECT-TYPE
        SYNTAX         Integer32(1..4000)
        MAX-ACCESS     read-only
        STATUS         current
        DESCRIPTION
            "The count of svlan session which has been used."
    ::= { svlan 10}

    zxr10svlanFreeCount        OBJECT-TYPE
        SYNTAX         Integer32(1..4000)
        MAX-ACCESS     read-only
        STATUS         current
        DESCRIPTION
            "The count of svlan session which has been not used."
    ::= { svlan 11}

	zxr10svlanTable        OBJECT-TYPE
        SYNTAX         SEQUENCE OF Zxr10svlanEntry
        MAX-ACCESS     not-accessible
        STATUS         current
        DESCRIPTION
            "A table that contains SVLAN session config info."
    ::= { svlan 12 }

    zxr10svlanEntry         OBJECT-TYPE
        SYNTAX          Zxr10svlanEntry
        MAX-ACCESS      not-accessible
        STATUS          current
        DESCRIPTION
            "A list of  entries of SVLAN session config information."
        INDEX  { zxr10svlanSessionNo }
    ::= { zxr10svlanTable 1 }

    Zxr10svlanEntry ::= SEQUENCE {
        zxr10svlanSessionNo               Integer32,
        zxr10svlanDescription             DisplayString,
        zxr10svlanCustomerPort            DisplayString,
        zxr10svlanUplinkPort              DisplayString,
        zxr10svlanInvlan                  DisplayString,
        zxr10svlanOvlan                   DisplayString,
        zxr10svlanRedirect                INTEGER,
        zxr10svlanAdvanced                INTEGER,
        zxr10svlanPriority                Integer32,
        zxr10svlanHelperVlan              DisplayString
        }

    zxr10svlanSessionNo        OBJECT-TYPE
        SYNTAX         Integer32(1..4000)
        MAX-ACCESS     read-only
        STATUS         current
        DESCRIPTION
            "The session number of a session."
    ::= { zxr10svlanEntry 1}

    zxr10svlanDescription  OBJECT-TYPE
    	SYNTAX          DisplayString(SIZE(1..30))
        MAX-ACCESS      read-only
        STATUS          current
        DESCRIPTION
            " The description of a session."
    ::= { zxr10svlanEntry 2 }

    zxr10svlanCustomerPort        OBJECT-TYPE
        SYNTAX         DisplayString(SIZE(1..32))
        MAX-ACCESS     read-only
        STATUS         current
        DESCRIPTION
            "The customer port name of a session."
    ::= { zxr10svlanEntry 3}

    zxr10svlanUplinkPort        OBJECT-TYPE
        SYNTAX         DisplayString(SIZE(1..32))
        MAX-ACCESS     read-only
        STATUS         current
        DESCRIPTION
            "The uplink port name of a session."
    ::= { zxr10svlanEntry 4}

    zxr10svlanInvlan  OBJECT-TYPE
        SYNTAX           DisplayString(SIZE(1..254))
        MAX-ACCESS       read-only
        STATUS           current
        DESCRIPTION
            "svlan invlan ID,if invlan doesn't have value, this string will be null. "
    ::= { zxr10svlanEntry 5 }

    zxr10svlanOvlan  	OBJECT-TYPE
        SYNTAX 		    DisplayString(SIZE(1..31))
        MAX-ACCESS 	    read-only
        STATUS          current
        DESCRIPTION
            "The out vlan id of a session in no inner tag mode,
            if outvlan doesn't have value, this string will be null."
    ::= { zxr10svlanEntry 6 }

     zxr10svlanRedirect     OBJECT-TYPE
        SYNTAX 		    INTEGER{
                        undirect(1)
                        }
        MAX-ACCESS 	    read-only
        STATUS          current
        DESCRIPTION
            "The undirect flag of a session, default value 255 means redirect."
    ::= { zxr10svlanEntry 7 }

    zxr10svlanAdvanced      OBJECT-TYPE
        SYNTAX           INTEGER{
                         normal(0),
                         special(1)
                         }
        MAX-ACCESS       read-only
        STATUS           current
        DESCRIPTION
            "The advanced flag of a session, 0--normal,1--special,default value 255 means not config. "
    ::= { zxr10svlanEntry 8 }

    zxr10svlanPriority       OBJECT-TYPE
        SYNTAX           Integer32(0..8)
        MAX-ACCESS       read-only
        STATUS           current
        DESCRIPTION
            "Svlan priority can be mapping(8) or be a number of 0..7,
            default value 255 means that priority has no value."
    ::= { zxr10svlanEntry 9 }

    zxr10svlanHelperVlan  OBJECT-TYPE
        SYNTAX           DisplayString(SIZE(1..31))
        MAX-ACCESS       read-only
        STATUS           current
        DESCRIPTION
            "Svlan helper vlan ID, if helper vlan ID doesn't have value,
            this string will be null."
    ::= { zxr10svlanEntry 10 }

    ----------------------------------------------------------------
    -- vfp session table add by jiangyan
    ----------------------------------------------------------------

    zxr10vfpTable        OBJECT-TYPE
        SYNTAX         SEQUENCE OF Zxr10vfpEntry
        MAX-ACCESS     not-accessible
        STATUS         current
        DESCRIPTION
            "A table that contains VFP session config info."
    ::= { vfp 1 }

    zxr10vfpEntry         OBJECT-TYPE
        SYNTAX          Zxr10vfpEntry
        MAX-ACCESS      not-accessible
        STATUS          current
        DESCRIPTION
            "A list of  entries of VFP session config information."
        INDEX  { zxr10vfpInterfaceName,zxr10vfpSessionId }
    ::= { zxr10vfpTable 1 }

    Zxr10vfpEntry   ::= SEQUENCE {
        zxr10vfpInterfaceName           DisplayString,
        zxr10vfpSessionId               Integer32,
        zxr10vfpDescription             DisplayString,
        zxr10vfpInVlan                  DisplayString,
        zxr10vfpAclNO                   Integer32,
        zxr10vfpRuleNo                  Integer32,
        zxr10vfpOvlan                   DisplayString,
        zxr10vfpPriority                Integer32,
        zxr10vfpUntagAppFlag            INTEGER,
        zxr10vfpClassId                 Integer32,
        zxr10vfpVrfId                   Integer32
        }

     zxr10vfpInterfaceName  OBJECT-TYPE
    	SYNTAX          DisplayString(SIZE(1..32))
        MAX-ACCESS      read-only
        STATUS          current
        DESCRIPTION
            "The interface name in a session."
    ::= { zxr10vfpEntry 1 }

    zxr10vfpSessionId        OBJECT-TYPE
        SYNTAX         Integer32(1..4000)
        MAX-ACCESS     read-only
        STATUS         current
        DESCRIPTION
            "The session id of a session."
    ::= { zxr10vfpEntry 2}

    zxr10vfpDescription  OBJECT-TYPE
    	SYNTAX      DisplayString(SIZE(1..30))
        MAX-ACCESS      read-only
        STATUS          current
        DESCRIPTION
            "The description of a session."
    ::= { zxr10vfpEntry 3 }

    zxr10vfpInVlan  OBJECT-TYPE
    	SYNTAX          DisplayString(SIZE(1..254))
    	MAX-ACCESS      read-only
        STATUS          current
        DESCRIPTION
            "Svlan invlan ID,if invlan doesn't have value, this string will be null."
    ::= { zxr10vfpEntry 4 }

    zxr10vfpAclNO  OBJECT-TYPE
    	SYNTAX          Integer32(1..2999)
        MAX-ACCESS      read-only
        STATUS          current
        DESCRIPTION
            "Acl number of a session."
    ::= { zxr10vfpEntry 5 }

    zxr10vfpRuleNo  OBJECT-TYPE
    	SYNTAX          Integer32(1..100)
        MAX-ACCESS      read-only
        STATUS          current
        DESCRIPTION
            "Rule number of a session."
    ::= { zxr10vfpEntry 6 }

    zxr10vfpOvlan  OBJECT-TYPE
    	SYNTAX          DisplayString(SIZE(1..31))
        MAX-ACCESS      read-only
        STATUS          current
        DESCRIPTION
            "The out vlan id of a session in no inner tag mode,
            if outvlan doesn't have value, this string will be null."
    ::= { zxr10vfpEntry 7 }

    zxr10vfpPriority  OBJECT-TYPE
    	SYNTAX          Integer32(0..8)
    	MAX-ACCESS      read-only
        STATUS          current
        DESCRIPTION
            "Svlan priority can be mapping(8) or be a number of 0..7,
            default value 255 means that priority has no value."
    ::= { zxr10vfpEntry 8 }

    zxr10vfpUntagAppFlag    OBJECT-TYPE
    	SYNTAX          INTEGER{
    	                global(0),
    	                pinpoint(1)
    	                }
        MAX-ACCESS      read-only
        STATUS          current
        DESCRIPTION
            "0--global,1--pinpoint,2--notconfig,default value 255 means not config."
    ::= { zxr10vfpEntry 9 }

    zxr10vfpClassId  OBJECT-TYPE
    	SYNTAX          Integer32(0..31)
        MAX-ACCESS      read-only
        STATUS          current
        DESCRIPTION
            "Classid of a session,default value 255 means that classid has no value."
    ::= { zxr10vfpEntry 10 }

    zxr10vfpVrfId  OBJECT-TYPE
    	SYNTAX          Integer32(0..63)
        MAX-ACCESS      read-only
        STATUS          current
        DESCRIPTION
            "Vrfid of a session,default value 255 means that vrfid has no value."
    ::= { zxr10vfpEntry 11 }

    dhcpIpSourceGuardIfNumber   OBJECT-TYPE
        SYNTAX          Integer32
        MAX-ACCESS      read-only
        STATUS          current
        DESCRIPTION
            "It shows how many ports enable ip-source-guard configure "
    ::= { dhcp 1 }

    dhcpIpSourceGuardTable   OBJECT-TYPE
        SYNTAX          SEQUENCE OF DhcpIpSourceGuardEntry
        MAX-ACCESS      not-accessible
        STATUS          current
        DESCRIPTION
            "Control the ip-source-guard configure, "
    ::= { dhcp 2 }

    dhcpIpSourceGuardEntry   OBJECT-TYPE
        SYNTAX          DhcpIpSourceGuardEntry
        MAX-ACCESS      not-accessible
        STATUS          current
        DESCRIPTION
            "Control the ip-source-guard configure, "
        INDEX {dhcpIpSourceGuardSlot, dhcpIpSourceGuardPort }
    ::= { dhcpIpSourceGuardTable 1 }

    DhcpIpSourceGuardEntry   ::= SEQUENCE
                     {
                     	  dhcpIpSourceGuardSlot
                     	  	INTEGER,
                     	  dhcpIpSourceGuardPort
                     	  	INTEGER,
                          dhcpIpSourceGuardControl
                          	INTEGER
                     }

    dhcpIpSourceGuardSlot   OBJECT-TYPE
        SYNTAX          INTEGER
        MAX-ACCESS      not-accessible
        STATUS          current
        DESCRIPTION
            ""
    ::= { dhcpIpSourceGuardEntry 1 }

    dhcpIpSourceGuardPort   OBJECT-TYPE
        SYNTAX          INTEGER
        MAX-ACCESS      not-accessible
        STATUS          current
        DESCRIPTION
            ""
    ::= { dhcpIpSourceGuardEntry 2 }

    dhcpIpSourceGuardControl   OBJECT-TYPE
        SYNTAX          INTEGER{ disable(0), ip-base(1), mac-base(2), mac-ip-base(3)}
        MAX-ACCESS      read-write
        STATUS          current
        DESCRIPTION
            "Control the ip-source-guard configure,
            if 0, disable current function;
            if 1, ip-source-guard is based on ip;
            if 2, ip-source-guard is based on mac;
            if 3, ip-source-guard is based on mac and ip."
    ::= { dhcpIpSourceGuardEntry 3 }

    END
