-------------------------------------------------------------------------------
-- File Name : ZTE-AN-VOICE-GLOBAL-MIB.mib
-- Date      : 2010-08-24
-- Author    : ZTE Nms dept.

--
-- Zte Voice Global Mib for Access Node
--
-------------------------------------------------------------------------------

ZTE-AN-VOICE-GLOBAL-MIB DEFINITIONS ::= BEGIN

IMPORTS
        MODULE-IDENTITY, NOTIFICATION-TYPE, OBJECT-TYPE, enterprises,
        IpAddress, Counter32, Integer32, Counter64, Unsigned32, Gauge32
                            FROM SNMPv2-SMI
        TEXTUAL-CONVENTION, MacAddress, DateAndTime, RowStatus, DisplayString,
        TruthValue          FROM SNMPv2-TC
        InetAddressType, InetAddress         FROM INET-ADDRESS-MIB;

zxAnVoiceGlobalMib MODULE-IDENTITY
    LAST-UPDATED    "0608140000Z"
    ORGANIZATION    "zte Telcom Co. Ltd."
    CONTACT-INFO    "E-mail: fu.hua@zte.com.cn
                    Tel: 021-68896250"
    DESCRIPTION     "This MIB defines voice global managed objects for Access Node."

    ::= { zxAn 5200 }

-------------------------------------------------------------------------------
-- Following objects are defined.
-- 1. msagRingProfileTable
-- 2. Voice Global Objects
-- 3. zxAnVoiceFirstRingingTable
-- 4. zxAnVoiceToneProfileTable
-- 5. zxAnVoiceCtrlPortTable
-- 6. zxAnVoiceDigitMapTable
-- 7. Voice Port Number Stats Objects
-- 8. zxAnDsx1Table
-------------------------------------------------------------------------------
zte OBJECT IDENTIFIER ::= { enterprises 3902 }
zxAn OBJECT IDENTIFIER ::= { zte 1015 }
zxAnVoiceMgmt OBJECT IDENTIFIER ::= { zxAnVoiceGlobalMib 3 }
zxAnVoiceGlobalConfig OBJECT IDENTIFIER ::= { zxAnVoiceMgmt 1 }

-------------------------------------------------------------------------------
-- 1. msagRingProfileTable
-------------------------------------------------------------------------------
    msagRingProfileTable OBJECT-TYPE
        SYNTAX      SEQUENCE OF MsagRingProfileEntry
        MAX-ACCESS  not-accessible
        STATUS      current
        DESCRIPTION ""
        ::= { zxAnVoiceGlobalConfig 6 }

    msagRingProfileEntry OBJECT-TYPE
        SYNTAX      MsagRingProfileEntry
        MAX-ACCESS  not-accessible
        STATUS      current
        DESCRIPTION ""
        INDEX { msagRPRingProfile,msagRPId }
        ::= { msagRingProfileTable 1 }

    MsagRingProfileEntry ::= SEQUENCE {
        msagRPRingProfile               INTEGER,
        msagRPId                        INTEGER,
        msagRPTime                      INTEGER,
        msagRPOn1                       INTEGER,
        msagRPOff1                      INTEGER,
        msagRPOn2                       INTEGER,
        msagRPOff2                      INTEGER,
        msagRPOn3                       INTEGER,
        msagRPOff3                      INTEGER,
        msagRPOn4                       INTEGER,
        msagRPOff4                      INTEGER,
        msagRPOn5                       INTEGER,
        msagRPOff5                      INTEGER,
        msagRPRowStatus                 RowStatus
        }

    msagRPRingProfile  OBJECT-TYPE
        SYNTAX      INTEGER {
            profMainLand(1),
            profHongkong(2),
            profSingapore(3),
            profRussia(4),
            profEurope(5),
            profBELGIUM(12),
            profSrilanka(15)
        }
        MAX-ACCESS  not-accessible
        STATUS      current
        DESCRIPTION ""
        ::= { msagRingProfileEntry 1 }

    msagRPId  OBJECT-TYPE
        SYNTAX       INTEGER(0..15)
        MAX-ACCESS   not-accessible
        STATUS       current
        DESCRIPTION  ""
        ::= { msagRingProfileEntry 2 }

        msagRPTime  OBJECT-TYPE
        SYNTAX      INTEGER(0..65535)
        MAX-ACCESS  read-create
        STATUS      current
        DESCRIPTION ""
       ::= { msagRingProfileEntry 3 }

    msagRPOn1  OBJECT-TYPE
        SYNTAX      INTEGER(0..65535)
        MAX-ACCESS  read-create
        STATUS      current
        DESCRIPTION ""
        ::= { msagRingProfileEntry 4 }

    msagRPOff1  OBJECT-TYPE
        SYNTAX      INTEGER(0..65535)
        MAX-ACCESS  read-create
        STATUS      current
        DESCRIPTION ""
        ::= { msagRingProfileEntry 5 }

    msagRPOn2  OBJECT-TYPE
        SYNTAX      INTEGER(0..65535)
        MAX-ACCESS  read-create
        STATUS      current
        DESCRIPTION ""
        ::= { msagRingProfileEntry 6 }

    msagRPOff2  OBJECT-TYPE
        SYNTAX      INTEGER(0..65535)
        MAX-ACCESS  read-create
        STATUS      current
        DESCRIPTION ""
        ::= { msagRingProfileEntry 7 }

    msagRPOn3  OBJECT-TYPE
        SYNTAX      INTEGER(0..65535)
        MAX-ACCESS  read-create
        STATUS      current
        DESCRIPTION ""
        ::= { msagRingProfileEntry 8 }

    msagRPOff3  OBJECT-TYPE
        SYNTAX      INTEGER(0..65535)
        MAX-ACCESS  read-create
        STATUS      current
        DESCRIPTION ""
        ::= { msagRingProfileEntry 9 }

    msagRPOn4  OBJECT-TYPE
        SYNTAX      INTEGER(0..65535)
        MAX-ACCESS  read-create
        STATUS      current
        DESCRIPTION ""
        ::= { msagRingProfileEntry 10 }

    msagRPOff4  OBJECT-TYPE
        SYNTAX      INTEGER(0..65535)
        MAX-ACCESS  read-create
        STATUS      current
        DESCRIPTION ""
        ::= { msagRingProfileEntry 11 }

    msagRPOn5  OBJECT-TYPE
        SYNTAX      INTEGER(0..65535)
        MAX-ACCESS  read-create
        STATUS      current
        DESCRIPTION ""
        ::= { msagRingProfileEntry 12 }

    msagRPOff5  OBJECT-TYPE
        SYNTAX      INTEGER(0..65535)
        MAX-ACCESS  read-create
        STATUS      current
        DESCRIPTION ""
        ::= { msagRingProfileEntry 13 }

    msagRPRowStatus  OBJECT-TYPE
        SYNTAX      RowStatus
        MAX-ACCESS  read-create
        STATUS      current
        DESCRIPTION ""
        ::= { msagRingProfileEntry 14 }

--------------------------------------------------------------------------------
-- 8. zxAnDsx1Table
--------------------------------------------------------------------------------
    zxAnDsx1Table OBJECT-TYPE
        SYNTAX  SEQUENCE OF ZxAnDsx1Entry
        MAX-ACCESS  not-accessible
        STATUS  current
        DESCRIPTION  "The E1/T1 Configuration table."
    ::={zxAnVoiceGlobalConfig 16}

    zxAnDsx1Entry OBJECT-TYPE
        SYNTAX  ZxAnDsx1Entry
        MAX-ACCESS  not-accessible
        STATUS  current
        DESCRIPTION  "An entry in the E1/T1 Configuration table."
        INDEX { zxAnDsx1Rack, zxAnDsx1Shelf, zxAnDsx1Slot, zxAnDsx1LinkNo }
    ::={zxAnDsx1Table 1}

    ZxAnDsx1Entry::=
        SEQUENCE{
            zxAnDsx1Rack  Integer32,
            zxAnDsx1Shelf  Integer32,
            zxAnDsx1Slot  Integer32,
            zxAnDsx1LinkNo  Integer32,
            zxAnDsx1Loopback  INTEGER,
            zxAnDsx1FramingMode  INTEGER
        }

    zxAnDsx1Rack  OBJECT-TYPE
        SYNTAX  Integer32(1..3)
        MAX-ACCESS  not-accessible
        STATUS  current
        DESCRIPTION  "Rack of E1/T1 interface."
        ::={zxAnDsx1Entry 1}

    zxAnDsx1Shelf  OBJECT-TYPE
        SYNTAX  Integer32(1..5)
        MAX-ACCESS  not-accessible
        STATUS  current
        DESCRIPTION  "Shelf of E1/T1 interface."
        ::={zxAnDsx1Entry 2}

    zxAnDsx1Slot  OBJECT-TYPE
        SYNTAX  Integer32(1..24)
        MAX-ACCESS  not-accessible
        STATUS  current
        DESCRIPTION  "Slot of E1/T1 interface."
        ::={zxAnDsx1Entry 3}

    zxAnDsx1LinkNo  OBJECT-TYPE
        SYNTAX  Integer32(1..8)
        MAX-ACCESS  not-accessible
        STATUS  current
        DESCRIPTION  "Index of E1/T1 interface."
        ::={zxAnDsx1Entry 4}

    zxAnDsx1Loopback  OBJECT-TYPE
        SYNTAX  INTEGER{
            noLoopback(1),
            localLoopback(2),
            remoteLineLoopback(3)
        }
        MAX-ACCESS  read-write
        STATUS  current
        DESCRIPTION
            "This variable represents the loopback configuration of E1/T1 interface.
            The values mean:
            noLoopback
                Not in the loopback state.
            localLoopback
                The E1/T1 interface can transmit packets to the LE, but receives its own transmission back again and ignores data from the LE.
            remoteLineLoopback
                With remote line loopback ,packets sent from the LE are received by the E1/T1 interface but also are immediately retransmitted to the LE."
        DEFVAL{1}
        ::={zxAnDsx1Entry 5}

    zxAnDsx1FramingMode  OBJECT-TYPE
        SYNTAX  INTEGER{
            withoutCrc(1),
            withCrc(2),
            sameAsPeers(3)
        }
        MAX-ACCESS  read-write
        STATUS  current
        DESCRIPTION
            "This variable represents the framing mode configuration of E1/T1 interface.
            The values mean:
            withoutCrc
                select E1/T1 framing without CRC generation.
            withCrc
                specifies CRC enabled E1/T1 framing.
            sameAsPeers
                Specifies E1/T1 framing mode same as peers."
        DEFVAL{2}
        ::={zxAnDsx1Entry 6}


--------------------------------------------------------------------------------
-- 2. Voice Global Objects
--------------------------------------------------------------------------------

    zxAnVoiceGlobalObjects OBJECT IDENTIFIER ::= { zxAnVoiceGlobalConfig 1000 }

    zxAnVoiceSysMgmtObjects OBJECT IDENTIFIER ::= { zxAnVoiceGlobalObjects 10 }

    zxAnVoiceGlobalMgmtCapabilities OBJECT-TYPE
        SYNTAX      BITS {
            nbPlatform(0)
            }
        MAX-ACCESS  read-only
        STATUS      current
        DESCRIPTION
            "The voice global management capabilities of this equipment.
            The bit value 1 means the function represented by this bit is
            supported by this equipment.
            bit 1: value 1 means support narrowband platform.
            NOTE: No recommended to display it in NMS."
        ::= {zxAnVoiceGlobalObjects 1}

    zxAnVoiceServiceLicense  OBJECT-TYPE
        SYNTAX      BITS {
            h248(0),
            mgcp(1),
            v5(2),
            voipIsdn(3),
            reserved1(4),
            reserved2(5),
            sip(6)
            }
        MAX-ACCESS  read-write
        STATUS      current
        DESCRIPTION
            "The licenses of voice service."
        ::={zxAnVoiceGlobalObjects 2}

    zxAnVoiceSysArea  OBJECT-TYPE
        SYNTAX       INTEGER
            {
                mainland(1),
                hongkong(2),
                singapore(3),
                russia(4),
                europe(5),
                srilanka(15)
            }
        MAX-ACCESS   read-write
        STATUS       current
        DESCRIPTION  "The area of system."
        ::= {zxAnVoiceSysMgmtObjects 1}

    zxAnVoiceSysCallMatchType  OBJECT-TYPE
        SYNTAX       INTEGER
            {
                longMatch(1),
                shortMatch(2)
            }
        MAX-ACCESS   read-write
        STATUS       current
        DESCRIPTION  "The match type of called telephone number."
        DEFVAL      {longMatch}
        ::= {zxAnVoiceSysMgmtObjects 2}

    zxAnVoiceSysLoadDftRingProfile  OBJECT-TYPE
        SYNTAX       INTEGER
            {
                load(1)
            }
        MAX-ACCESS   read-write
        STATUS       current
        DESCRIPTION  "To load default ring profile.
                     This object differs from msagLoadDefaultRingProfile.
                     This object is applied to uniform narrowband platform."
        ::= {zxAnVoiceSysMgmtObjects 3}

-------------------------------------------------------------------------------
-- 3. zxAnVoiceFirstRingingTable
-------------------------------------------------------------------------------
    zxAnVoiceFirstRingingTable OBJECT-TYPE
        SYNTAX      SEQUENCE OF ZxAnVoiceFirstRingingEntry
        MAX-ACCESS  not-accessible
        STATUS      current
        DESCRIPTION
            "First ringing table."
        ::= {zxAnVoiceGlobalConfig 1002}

    zxAnVoiceFirstRingingEntry OBJECT-TYPE
        SYNTAX      ZxAnVoiceFirstRingingEntry
        MAX-ACCESS  not-accessible
        STATUS      current
        DESCRIPTION
            "First ringing entry."
        INDEX { zxAnVoiceFirstRingingMgId }
        ::= {zxAnVoiceFirstRingingTable 1}

    ZxAnVoiceFirstRingingEntry::= SEQUENCE {
        zxAnVoiceFirstRingingMgId            Integer32,
        zxAnVoiceFirstRingingType            INTEGER,
        zxAnVoiceFirstRingingTime            Integer32,
        zxAnVoiceFirstRingingInterval        Integer32
        }

    zxAnVoiceFirstRingingMgId  OBJECT-TYPE
        SYNTAX      Integer32
        MAX-ACCESS  not-accessible
        STATUS      current
        DESCRIPTION
            "MG ID."
        ::= {zxAnVoiceFirstRingingEntry 1}

    zxAnVoiceFirstRingingType  OBJECT-TYPE
        SYNTAX      INTEGER {
            accordingToCid(1),
            differentFromOtherRings(2),
            sameWithOtherRings(3)
        }
        MAX-ACCESS  read-write
        STATUS      current
        DESCRIPTION
            "First ringing type, indicates whether the first ring is same with
            other rings or not.
            CID(Caller ID) signal is between the first and second ring.
            accordingToCid(1) means that first ring is different
            from other ring only when CID signal should be sent.
            differentFromOtherRings(2) means that first ring is always different
            from other rings.
            sameWithOtherRings(3) means that first ring is always same with
            other rings."
        DEFVAL { accordingToCid }
        ::= {zxAnVoiceFirstRingingEntry 2}

    zxAnVoiceFirstRingingTime  OBJECT-TYPE
        SYNTAX      Integer32(30..120)
        UNITS       "10ms"
        MAX-ACCESS  read-write
        STATUS      current
        DESCRIPTION
            "The time of first ringing.
            Not valid when zxAnVoiceFirstRingingType is
            sameWithOtherRings(3)."
        DEFVAL { 60 }
        ::= {zxAnVoiceFirstRingingEntry 3}

    zxAnVoiceFirstRingingInterval  OBJECT-TYPE
        SYNTAX      Integer32(200..400)
        UNITS       "10ms"
        MAX-ACCESS  read-write
        STATUS      current
        DESCRIPTION
            "The interval of first ring and second ring.
            Not valid when zxAnVoiceFirstRingingType is
            sameWithOtherRings(3)."
        DEFVAL { 400 }
        ::= {zxAnVoiceFirstRingingEntry 4}

-------------------------------------------------------------------------------
-- 4. zxAnVoiceToneProfileTable
-------------------------------------------------------------------------------
    zxAnVoiceToneProfileTable OBJECT-TYPE
        SYNTAX      SEQUENCE OF ZxAnVoiceToneProfileEntry
        MAX-ACCESS  not-accessible
        STATUS      current
        DESCRIPTION
            "Tone profile table."
        ::= {zxAnVoiceGlobalConfig 1003}

    zxAnVoiceToneProfileEntry OBJECT-TYPE
        SYNTAX      ZxAnVoiceToneProfileEntry
        MAX-ACCESS  not-accessible
        STATUS      current
        DESCRIPTION
            "Tone profile entry."
        INDEX { zxAnVoiceToneArea, zxAnVoiceToneCategory }
        ::= {zxAnVoiceToneProfileTable 1}

    ZxAnVoiceToneProfileEntry::= SEQUENCE {
        zxAnVoiceToneArea                       INTEGER,
        zxAnVoiceToneCategory                   INTEGER,
        zxAnVoiceToneDuration                   Integer32,
        zxAnVoiceToneFirstWaveFrequency         Integer32,
        zxAnVoiceToneFirstWaveAmplitude         Integer32,
        zxAnVoiceToneSecondWaveFrequency        Integer32,
        zxAnVoiceToneSecondWaveAmplitude        Integer32,
        zxAnVoiceToneThirdWaveFrequency         Integer32,
        zxAnVoiceToneThirdWaveAmplitude         Integer32,
        zxAnVoicFirstWaveTimeSlot               Integer32,
        zxAnVoicSecondWaveTimeSlot              Integer32,
        zxAnVoicThirdWaveTimeSlot               Integer32,
        zxAnVoiceFirstToneSendingTime           Integer32,
        zxAnVoiceFirstToneBreakTime             Integer32,
        zxAnVoiceSecondToneSendingTime          Integer32,
        zxAnVoiceSecondToneBreakTime            Integer32,
        zxAnVoiceThirdToneSendingTime           Integer32,
        zxAnVoiceThirdToneBreakTime             Integer32
        }

    zxAnVoiceToneArea  OBJECT-TYPE
        SYNTAX      INTEGER {
            mainland(1),
            hongkong(2),
            singapore(3),
            russia(4),
            europe(5),
            srilanka(15)
        }
        MAX-ACCESS   not-accessible
        STATUS       current
        DESCRIPTION
            "The area of system."
        ::= {zxAnVoiceToneProfileEntry 1}

    zxAnVoiceToneCategory  OBJECT-TYPE
        SYNTAX      INTEGER {
            dialTone(1),
            ringbackTone(2),
            busyTone(3),
            congestionTone(4),
            specialDialTone(5),
            howlerTone(6),
            verificationTone(7),
            callWaitingTone(8),
            stutterDialTone(9),
            numberUnobtainableTone(10),
            recallDialTone(11),
            holdingTone(12),
            callWaitingToneA(10013),
            callWaitingToneB(10014),
            callWaitingToneC(10015),
            callWaitingToneD(10016),
            callWaitingToneE(10017),
            expensiveRouteWarningTone(10018),
            bargeInTone(10019),
            testNumberTone(10020),
            intrusionTone(10021),
            sitTone(10025),
            busyHowlerTone(10031),
            conferenceNoReadyTone(10032),
            conferenceExitTone(10033),
            advancedSpecialInfoTone(10035),
            trunkBusyTone(10036),
            advancedHoldingTone(10037),
            interventionTone(10038),
            wrongDialTone(10039)
        }
        MAX-ACCESS   not-accessible
        STATUS       current
        DESCRIPTION
            "Tone category."
        ::= {zxAnVoiceToneProfileEntry 2}

    zxAnVoiceToneDuration  OBJECT-TYPE
        SYNTAX      Integer32(1..65535)
        UNITS       "100ms"
        MAX-ACCESS  read-write
        STATUS      current
        DESCRIPTION
            "Duration of the tone sent."
        ::= {zxAnVoiceToneProfileEntry 3}

    zxAnVoiceToneFirstWaveFrequency  OBJECT-TYPE
        SYNTAX      Integer32(0..65535)
        UNITS       "Hz"
        MAX-ACCESS  read-write
        STATUS      current
        DESCRIPTION
            "Frequency of the first wave."
        ::= {zxAnVoiceToneProfileEntry 4}

    zxAnVoiceToneFirstWaveAmplitude  OBJECT-TYPE
        SYNTAX      Integer32(0..1000)
        UNITS       "0.1dBov"
        MAX-ACCESS  read-write
        STATUS      current
        DESCRIPTION
            "Amplitude of the first wave."
        ::= {zxAnVoiceToneProfileEntry 5}

    zxAnVoiceToneSecondWaveFrequency  OBJECT-TYPE
        SYNTAX      Integer32(0..65535)
        UNITS       "Hz"
        MAX-ACCESS  read-write
        STATUS      current
        DESCRIPTION
            "Frequency of the second wave."
        ::= {zxAnVoiceToneProfileEntry 6}

    zxAnVoiceToneSecondWaveAmplitude  OBJECT-TYPE
        SYNTAX      Integer32(0..1000)
        UNITS       "0.1dBov"
        MAX-ACCESS  read-write
        STATUS      current
        DESCRIPTION
            "Amplitude of the second wave."
        ::= {zxAnVoiceToneProfileEntry 7}

    zxAnVoiceToneThirdWaveFrequency  OBJECT-TYPE
        SYNTAX      Integer32(0..65535)
        UNITS       "Hz"
        MAX-ACCESS  read-write
        STATUS      current
        DESCRIPTION
            "Frequency of the third wave."
        ::= {zxAnVoiceToneProfileEntry 8}

    zxAnVoiceToneThirdWaveAmplitude  OBJECT-TYPE
        SYNTAX      Integer32(0..1000)
        UNITS       "0.1dBov"
        MAX-ACCESS  read-write
        STATUS      current
        DESCRIPTION
            "Amplitude of the third wave."
        ::= {zxAnVoiceToneProfileEntry 9}

    zxAnVoicFirstWaveTimeSlot  OBJECT-TYPE
        SYNTAX      Integer32(0..255)
        MAX-ACCESS  read-write
        STATUS      current
        DESCRIPTION
            "DSP time slot used for first wave.
            Only valid when system uses DSP to make tone."
        ::= {zxAnVoiceToneProfileEntry 10}

    zxAnVoicSecondWaveTimeSlot  OBJECT-TYPE
        SYNTAX      Integer32(0..255)
        MAX-ACCESS  read-write
        STATUS      current
        DESCRIPTION
            "DSP time slot used for second wave.
            Only valid when system uses DSP to make tone."
        ::= {zxAnVoiceToneProfileEntry 11}

    zxAnVoicThirdWaveTimeSlot  OBJECT-TYPE
        SYNTAX      Integer32(0..255)
        MAX-ACCESS  read-write
        STATUS      current
        DESCRIPTION
            "DSP time slot used for third wave.
            Only valid when system uses DSP to make tone."
        ::= {zxAnVoiceToneProfileEntry 12}

    zxAnVoiceFirstToneSendingTime  OBJECT-TYPE
        SYNTAX      Integer32(0..65535)
        UNITS       "10ms"
        MAX-ACCESS  read-write
        STATUS      current
        DESCRIPTION
            "The sending time of first tone."
        ::= {zxAnVoiceToneProfileEntry 13}

    zxAnVoiceFirstToneBreakTime  OBJECT-TYPE
        SYNTAX      Integer32(0..65535)
        UNITS       "10ms"
        MAX-ACCESS  read-write
        STATUS      current
        DESCRIPTION
            "The break time of first tone."
        ::= {zxAnVoiceToneProfileEntry 14}

    zxAnVoiceSecondToneSendingTime  OBJECT-TYPE
        SYNTAX      Integer32(0..65535)
        UNITS       "10ms"
        MAX-ACCESS  read-write
        STATUS      current
        DESCRIPTION
            "The sending time of second tone."
        ::= {zxAnVoiceToneProfileEntry 15}

    zxAnVoiceSecondToneBreakTime  OBJECT-TYPE
        SYNTAX      Integer32(0..65535)
        UNITS       "10ms"
        MAX-ACCESS  read-write
        STATUS      current
        DESCRIPTION
            "The break time of second tone."
        ::= {zxAnVoiceToneProfileEntry 16}

    zxAnVoiceThirdToneSendingTime  OBJECT-TYPE
        SYNTAX      Integer32(0..65535)
        UNITS       "10ms"
        MAX-ACCESS  read-write
        STATUS      current
        DESCRIPTION
            "The sending time of third tone."
        ::= {zxAnVoiceToneProfileEntry 17}

    zxAnVoiceThirdToneBreakTime  OBJECT-TYPE
        SYNTAX      Integer32(0..65535)
        UNITS       "10ms"
        MAX-ACCESS  read-write
        STATUS      current
        DESCRIPTION
            "The break time of third tone."
        ::= {zxAnVoiceToneProfileEntry 18}

-------------------------------------------------------------------------------
-- 5. zxAnVoiceCtrlPortTable
-------------------------------------------------------------------------------
    zxAnVoiceCtrlPortTable OBJECT-TYPE
        SYNTAX      SEQUENCE OF ZxAnVoiceCtrlPortEntry
        MAX-ACCESS  not-accessible
        STATUS      current
        DESCRIPTION
            "Control port table."
        ::= {zxAnVoiceGlobalConfig 1004}

    zxAnVoiceCtrlPortEntry OBJECT-TYPE
        SYNTAX      ZxAnVoiceCtrlPortEntry
        MAX-ACCESS  not-accessible
        STATUS      current
        DESCRIPTION
            "Control port entry."
        INDEX       { zxAnVoiceCtrlPortId }
        ::= {zxAnVoiceCtrlPortTable 1}

    ZxAnVoiceCtrlPortEntry::= SEQUENCE {
        zxAnVoiceCtrlPortId        Integer32,
        zxAnVoiceCtrlPortType      INTEGER,
        zxAnVoiceCtrlPortNo        Integer32,
        zxAnVoiceCtrlPortRowStatus RowStatus
        }

    zxAnVoiceCtrlPortId  OBJECT-TYPE
        SYNTAX       Integer32(2..40)
        MAX-ACCESS   not-accessible
        STATUS       current
        DESCRIPTION  "Control port index."
        ::= {zxAnVoiceCtrlPortEntry 1}

    zxAnVoiceCtrlPortType  OBJECT-TYPE
        SYNTAX       INTEGER
            {
                udp(1),
                tcp(2)
            }
        MAX-ACCESS   read-create
        STATUS       current
        DESCRIPTION  "Control port type."
        DEFVAL      {udp}
        ::= {zxAnVoiceCtrlPortEntry 2}

    zxAnVoiceCtrlPortNo  OBJECT-TYPE
        SYNTAX       Integer32(0..65535)
        MAX-ACCESS   read-create
        STATUS       current
        DESCRIPTION  "Control port number."
        ::= {zxAnVoiceCtrlPortEntry 3}

    zxAnVoiceCtrlPortRowStatus  OBJECT-TYPE
        SYNTAX       RowStatus
        MAX-ACCESS   read-create
        STATUS       current
        DESCRIPTION  "The row status of this entry."
        ::= {zxAnVoiceCtrlPortEntry 20}

-------------------------------------------------------------------------------
-- 6. zxAnVoiceDigitMapTable
-------------------------------------------------------------------------------

    zxAnVoiceDigitMapTable OBJECT-TYPE
        SYNTAX      SEQUENCE OF ZxAnVoiceDigitMapEntry
        MAX-ACCESS  not-accessible
        STATUS      current
        DESCRIPTION
            "Digit map table."
        ::={zxAnVoiceGlobalConfig 1005}

    zxAnVoiceDigitMapEntry OBJECT-TYPE
        SYNTAX      ZxAnVoiceDigitMapEntry
        MAX-ACCESS  not-accessible
        STATUS      current
        DESCRIPTION
            "Digit map entry."
        INDEX { zxAnVoiceDigitMapName }
        ::= { zxAnVoiceDigitMapTable 1 }

    ZxAnVoiceDigitMapEntry ::= SEQUENCE {
        zxAnVoiceDigitMapName           DisplayString,
        zxAnVoiceDigitMapType           INTEGER,
        zxAnVoiceDigitMapBody           DisplayString,
        zxAnVoiceDigitMapRowStatus      RowStatus
    }

    zxAnVoiceDigitMapName  OBJECT-TYPE
        SYNTAX      DisplayString(SIZE(1..20))
        MAX-ACCESS  not-accessible
        STATUS      current
        DESCRIPTION
            "Digit map name."
        ::= { zxAnVoiceDigitMapEntry 1 }

   zxAnVoiceDigitMapType  OBJECT-TYPE
        SYNTAX      INTEGER {
            selfSwitch(1),
            sip(2),
            emergencyCall(3)
            }
        MAX-ACCESS  read-create
        STATUS      current
        DESCRIPTION
            "selfSwitch(1) means this digit map rule will be used
             when using self-switch.
             sip(2) means this digit map rule will be used
             when the caller is SIP user.
             emergencyCall(3) defined the emergency number,
             such as 112, 119 and so on."
        ::= { zxAnVoiceDigitMapEntry 2 }

    zxAnVoiceDigitMapBody  OBJECT-TYPE
        SYNTAX      DisplayString(SIZE(1..4095))
        MAX-ACCESS  read-create
        STATUS      current
        DESCRIPTION
           "Digit map body.
            eg. 9xxxxxxx|[5-8][0-8][0-8]xxxx|725xxxx|4568xxxx|458xxxx|1xx|2xxx"
        ::= { zxAnVoiceDigitMapEntry 3 }

    zxAnVoiceDigitMapRowStatus  OBJECT-TYPE
        SYNTAX      RowStatus
        MAX-ACCESS  read-create
        STATUS      current
        DESCRIPTION
            "The row status of this entry."
        ::= { zxAnVoiceDigitMapEntry 30 }

--------------------------------------------------------------------------------
-- 7. Voice Port Number Stats Objects
--------------------------------------------------------------------------------

    zxAnVoicePortNumberStatsObjects OBJECT IDENTIFIER
    ::= { zxAnVoiceGlobalConfig 1050 }
    zxAnVoiceActivePortStatsObjects OBJECT IDENTIFIER
    ::= { zxAnVoicePortNumberStatsObjects 1 }
    zxAnVoiceActiveV5PotsPorts  OBJECT-TYPE
        SYNTAX      Integer32
        MAX-ACCESS  read-only
        STATUS      current
        DESCRIPTION
            "The number of active V5 POTS ports."
        ::= {zxAnVoiceActivePortStatsObjects 1}

    zxAnVoiceActiveV5BriPorts OBJECT-TYPE
        SYNTAX      Integer32
        MAX-ACCESS  read-only
        STATUS      current
        DESCRIPTION
            "The number of active V5 BRI ports."
        ::= {zxAnVoiceActivePortStatsObjects 2}

    zxAnVoiceActiveV5PriPorts  OBJECT-TYPE
        SYNTAX      Integer32
        MAX-ACCESS  read-only
        STATUS      current
        DESCRIPTION
            "The number of active V5 PRI ports."
        ::= {zxAnVoiceActivePortStatsObjects 3}

    zxAnVoiceActiveH248PotsPorts OBJECT-TYPE
        SYNTAX      Integer32
        MAX-ACCESS  read-only
        STATUS      current
        DESCRIPTION
            "The number of active H248 POTS ports."
        ::= {zxAnVoiceActivePortStatsObjects 4}

    zxAnVoiceActiveH248BriPorts  OBJECT-TYPE
        SYNTAX      Integer32
        MAX-ACCESS  read-only
        STATUS      current
        DESCRIPTION
            "The number of active H248 BRI ports."
        ::= {zxAnVoiceActivePortStatsObjects 5}

    zxAnVoiceActiveH248PriPorts  OBJECT-TYPE
        SYNTAX      Integer32
        MAX-ACCESS  read-only
        STATUS      current
        DESCRIPTION
            "The number of active H248 PRI ports."
        ::= {zxAnVoiceActivePortStatsObjects 6}

    zxAnVoiceActiveSipPotsPorts  OBJECT-TYPE
        SYNTAX      Integer32
        MAX-ACCESS  read-only
        STATUS      current
        DESCRIPTION
            "The number of active SIP POTS ports."
        ::= {zxAnVoiceActivePortStatsObjects 7}

    zxAnVoiceActiveSipBriPorts  OBJECT-TYPE
        SYNTAX      Integer32
        MAX-ACCESS  read-only
        STATUS      current
        DESCRIPTION
            "The number of active SIP BRI ports."
        ::= {zxAnVoiceActivePortStatsObjects 8}

    zxAnVoiceActiveSipPriPorts  OBJECT-TYPE
        SYNTAX      Integer32
        MAX-ACCESS  read-only
        STATUS      current
        DESCRIPTION
            "The number of active SIP PRI ports."
        ::= {zxAnVoiceActivePortStatsObjects 9}

    zxAnVoiceActiveLeasedLinePorts  OBJECT-TYPE
        SYNTAX       Integer32
        MAX-ACCESS   read-only
        STATUS       current
        DESCRIPTION  "The number of active leased line ports."
        ::= {zxAnVoiceActivePortStatsObjects 10}

END
