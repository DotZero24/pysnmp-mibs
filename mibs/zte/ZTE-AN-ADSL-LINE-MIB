--------------------------------------------------------------------------
-- File Name : ZTE-AN-EVENT-MIB.mib
-- Date      : 2007-01-25
-- Author    : ZTE Nms dept.

--
-- Zte Adsl Mib for Access Node
--
--
--------------------------------------------------------------------------


ZTE-AN-ADSL-LINE-MIB DEFINITIONS ::= BEGIN
    IMPORTS
        MODULE-IDENTITY, OBJECT-TYPE,
        TimeTicks,Counter32, Gauge32,Unsigned32,
        NOTIFICATION-TYPE ,Integer32    FROM SNMPv2-SMI
        MODULE-COMPLIANCE, OBJECT-GROUP FROM SNMPv2-CONF
        SnmpAdminString                 FROM SNMP-FRAMEWORK-MIB
        ifIndex                         FROM IF-MIB
        adslLineConfProfileName,
        adslLineConfProfileEntry,adslLineAlarmConfProfileEntry,
        adslAtucChanConfInterleaveMaxTxRate,adslAtucChanCurrTxRate,
        adslAturChanConfInterleaveMaxTxRate,adslAturChanCurrTxRate,
        adslAtucChanIntervalEntry,adslAturChanIntervalEntry
                                        FROM ADSL-LINE-MIB
        RowStatus                       FROM SNMPv2-TC
        zxAn                            FROM ZTE-AN-TC-MIB;


-- ZTE Dsl line ext MIB objects

    zxAnAdslMib MODULE-IDENTITY
            LAST-UPDATED "200701251300Z"
            ORGANIZATION "zte dsl product line"
            CONTACT-INFO
                " su chunshan
                  Mail: suchunshan@zte.com.cn
                  Tel : 021-68896292,68896251"
            DESCRIPTION
                "This mib defines extended dsl line mo (managed object ) for adsl2,
                 adsl+ and dsl loop test.

                 Naming Conventions:
                 Atuc -- (ATUC) modem at near (Central) end of line
                 Atur -- (ATUR) modem at Remote end of line "
         ::= {zxAn 1000}


    zxAnAdslMibObjects OBJECT IDENTIFIER ::= { zxAnAdslMib 1 }




--------------------------------------------------------------------------------
-- Following objects are defined.
-- Adsl Line Extended Table
-- Adsl Line Config Profile Extended Table
-- Atuc Channel Table
-- Atur Channel Table
-- Adsl Line Alarm Profile Extended Table
-- Atuc Performance Data Table
-- Atur Performance Data Table
-- Atuc Channel Performance Data Table
-- Atur Channel Performance Data Table
-- Atuc Channel Interval Performance Table
-- Atur Channel Interval Performance Table
-- Atuc Channel history 1 Day Performance Table
-- Atur Channel history 1 Day Performance Table
-- Dsl Loopback Test Table
-- trap definitions
--------------------------------------------------------------------------------



------------------------------------------------------------------------------
-- Adsl Line Extended Table
------------------------------------------------------------------------------

    zxAnAdslLineTable  OBJECT-TYPE
            SYNTAX      SEQUENCE OF ZxAnAdslLineEntry
            MAX-ACCESS  not-accessible
            STATUS      current
            DESCRIPTION
                "Adsl line additional information table."
            ::= {zxAnAdslMibObjects 1}


    zxAnAdslLineEntry  OBJECT-TYPE
            SYNTAX      ZxAnAdslLineEntry
            MAX-ACCESS  not-accessible
            STATUS      current
            DESCRIPTION
                "Adsl line additional information entry"
            INDEX    { ifIndex }
            ::= {zxAnAdslLineTable 1}


    ZxAnAdslLineEntry ::=
            SEQUENCE {
                zxAnAdslLineTxDataRate         Gauge32,
                zxAnAdslLineRxDataRate         Gauge32,
                zxAnAdslAtucActInp             Integer32,
                zxAnAdslAturActInp             Integer32,
                zxAnAdslLineExtConfPrf         SnmpAdminString
                }

    zxAnAdslLineTxDataRate  OBJECT-TYPE
            SYNTAX      Gauge32
            UNITS       "kbps"
            MAX-ACCESS  read-only
            STATUS      current
            DESCRIPTION
                 "Transmitted net data rate on this line."
            ::= { zxAnAdslLineEntry 1 }

    zxAnAdslLineRxDataRate  OBJECT-TYPE
            SYNTAX      Gauge32
            UNITS       "kbps"
            MAX-ACCESS  read-only
            STATUS      current
            DESCRIPTION
                 "Recieved net data rate on this line."
            ::= { zxAnAdslLineEntry 2 }


    zxAnAdslAtucActInp  OBJECT-TYPE
            SYNTAX      Integer32(0..255)
            UNITS       "0.1 symbols"
            MAX-ACCESS  read-only
            STATUS      current
            DESCRIPTION
                 "Actual impulse noise protection.
               This parameter reports the actual impulse noise
               protection (INP) on the channel in the L0
               state. In the L1 or L2 state, the parameter contains the
               INP in the previous L0 state.
            "
            ::= { zxAnAdslLineEntry 3 }


    zxAnAdslAturActInp  OBJECT-TYPE
            SYNTAX      Integer32(0..255)
            UNITS       "0.1 symbols"
            MAX-ACCESS  read-only
            STATUS      current
            DESCRIPTION
                 "Actual impulse noise protection.
               This parameter reports the actual impulse noise
               protection (INP) on the channel in the L0
               state. In the L1 or L2 state, the parameter contains the
               INP in the previous L0 state.
            "
            ::= { zxAnAdslLineEntry 4 }

    zxAnAdslLineExtConfPrf OBJECT-TYPE
        SYNTAX      SnmpAdminString (SIZE (1..32))
        MAX-ACCESS  read-write
        STATUS      current
        DESCRIPTION
            "The value of this object identifies the row in the XDSL2
             Line Ext Profile Table, (zxAnXdsl2LnExtConfPrfTable),
             which applies for this line."
        ::= { zxAnAdslLineEntry 5 }

------------------------------------------------------------------------------
-- Adsl Line Config Profile Extended Table
------------------------------------------------------------------------------


    zxAnAdslLineConfProfileExtTable  OBJECT-TYPE
            SYNTAX      SEQUENCE OF ZxAnAdslLineConfProfileExtEntry
            MAX-ACCESS  not-accessible
            STATUS      current
            DESCRIPTION
                "Adsl line config profile extended information table."
            ::= {zxAnAdslMibObjects 2}


    zxAnAdslLineConfProfileExtEntry  OBJECT-TYPE
            SYNTAX      ZxAnAdslLineConfProfileExtEntry
            MAX-ACCESS  not-accessible
            STATUS      current
            DESCRIPTION
               "An entry extends the adslLineConfProfileEntry defined in
               [RFC2662]. Each entry corresponds to an ADSL line profile."

            AUGMENTS    { adslLineConfProfileEntry }
            ::= {zxAnAdslLineConfProfileExtTable 1}


    ZxAnAdslLineConfProfileExtEntry ::=
            SEQUENCE {
                zxAnAdslLineConfTxStartBin         Integer32,
                zxAnAdslLineConfTxEndBin           INTEGER,
                zxAnAdslLineConfRxStartBin         Integer32,
                zxAnAdslLineConfRxEndBin           INTEGER,
                zxAnAdslLineConfUseCustomBins      INTEGER,
                zxAnAdslAtucConfPsdMaskType      Integer32,
                zxAnAdslLineConfPMMode           BITS,
                zxAnAdslLineConfPML2Rate         INTEGER,
                zxAnAdsl2ConfMinProtectionDs     INTEGER,
                zxAnAdslLineConfMinProtectionUs     INTEGER,
                zxAnAdslConfDMTConfTrellis       INTEGER,
                zxAnAdslAtucConfMaxBitsPerBin    INTEGER,
                zxAnAdslAtucConfBitSwapDs        INTEGER,
                zxAnAdslAtucConfBitSwapUs        INTEGER,
                zxAnAdslAtucConfReAdsl2Enable    INTEGER,
                zxAnAdslAtucConfPmL0Time         INTEGER,
                zxAnAdslAtucConfPmL2Time         INTEGER,
                zxAnAdslAtucConfPmL2Atpr         INTEGER,
                zxAdsl2ConfPsdMaskSelectUs       INTEGER
                }


    zxAnAdslLineConfTxStartBin  OBJECT-TYPE
            SYNTAX      Integer32
            MAX-ACCESS  read-create
            STATUS      current
            DESCRIPTION
                "Specifies lowest bin number allowed for Tx signal.
                 Different line coding type has different default value.
                    0x20 (default for Annex A only)
                    0x20 (default for ADSL2/ADSL2plus)
                    0x06 (default for Annex A if G.Span and/or G.Span Plus are also defined)
                    0x40 (default for Annex B)
                    0x06 (default for Annex C/C.x)
                    0x06 (default for G.Span)
                    0x06 (default for G.Span Plus)"
            ::= { zxAnAdslLineConfProfileExtEntry 1 }

    zxAnAdslLineConfTxEndBin  OBJECT-TYPE
            SYNTAX      INTEGER(0..512)
            MAX-ACCESS  read-create
            STATUS      current
            DESCRIPTION
                "Specifies highest bin number allowed for Tx signal.
                 Default = 0x3ff (default for all Annexes and ADSL2/ADSL2plus)"
            ::= { zxAnAdslLineConfProfileExtEntry 2 }



    zxAnAdslLineConfRxStartBin  OBJECT-TYPE
            SYNTAX      Integer32
            MAX-ACCESS  read-create
            STATUS      current
            DESCRIPTION
                "Specifies lowest bin number allowed for Rx signal.
                 Different line coding type has different default value.
                    0x06 (default for Annex A)
                    0x01 (default for Annex B)
                    0x06 (default for Annex C/C.x)
                    0x06 (default for G.Span/ADSL+)
                    0x06 (default for G.Span Plus)
                    0x06 (default for ADSL2/ADLS2plus) "
            ::= { zxAnAdslLineConfProfileExtEntry 3 }



    zxAnAdslLineConfRxEndBin  OBJECT-TYPE
            SYNTAX      INTEGER(0..512)
            MAX-ACCESS  read-create
            STATUS      current
            DESCRIPTION
                "Specifies highest bin number allowed for Rx signal.
                Default = 0x3f (default for all Annexes and ADSL2/ADLS2plus)"
            ::= { zxAnAdslLineConfProfileExtEntry 4 }


    zxAnAdslLineConfUseCustomBins  OBJECT-TYPE
            SYNTAX      INTEGER {
                enable(1),  -- enable use custom Bins
                disable(2)  -- disable use custom Bins
                }
            MAX-ACCESS  read-create
            STATUS      current
            DESCRIPTION
                "Enable or disable custom bin selection for upstream/downstream
                transmission. This parameter is used in conjunction with the
                adslAtucDMTConfFreqBins and
                adslAturDMTConfFreqBins[ADSL-DMT-LINE-MIB] parameter."
            DEFVAL { 2 }
            ::= { zxAnAdslLineConfProfileExtEntry 5 }

    zxAnAdslAtucConfPsdMaskType  OBJECT-TYPE
            SYNTAX      Integer32
            MAX-ACCESS  read-create
            STATUS      current
            DESCRIPTION
                " It is supported by G.Span. Dsl card team will provide files
                about it in details."
            ::= { zxAnAdslLineConfProfileExtEntry 6 }

    zxAnAdslLineConfPMMode  OBJECT-TYPE
            SYNTAX      BITS {
                idle (0),
                lowPower(1)
                }
            MAX-ACCESS  read-create
            STATUS      current
            DESCRIPTION
                " This configuration parameter defines the line states the ATU-C
                may autonomously transition to on this line. It is coded in a
                bit map representation (0 if not allowed, 1 if allowed) with
                following definition:
                    Bit 0   L3 state (Idle state)
                    Bit 1   L1/L2 state (Low power state)."

            REFERENCE "Section 7.3.1.1.4 ITU G.997.1(05/2003) "
            ::= { zxAnAdslLineConfProfileExtEntry 7 }


    zxAnAdslLineConfPML2Rate  OBJECT-TYPE
            SYNTAX      INTEGER (256..1024)
            UNITS       "kbps"
            MAX-ACCESS  read-create
            STATUS      current
            DESCRIPTION
                " PM configuration parameter,related to the L2 low power state.
                This parameter specifies the minimum net data rate during the
                low power state (L2)."

            REFERENCE "Section 7.3.2.1.5 ITU G.997.1(05/2003) "
            ::= { zxAnAdslLineConfProfileExtEntry 8 }

    zxAnAdsl2ConfMinProtectionDs  OBJECT-TYPE
            SYNTAX      INTEGER
                {
                 autoAdaption (0),
                 noProtection (1),
                 halfSymbol (2),
                 singleSymbol (3),
                 twoSymbols (4),
                 fourSymbols (5),
                 eightSymbols (6),
                 sixteenSymbols (7)
                 }
            UNITS       "symbols"
            MAX-ACCESS  read-create
            STATUS      current
            DESCRIPTION
             "Minimum Impulse Noise Protection on Downstream direction.  The
              minimum impulse noise protection for the bearer channel,
              expressed in symbols.  The parameter can take the following
              values: noProtection (i.e., INP not required), halfSymbol
              (i.e., INP length is 1/2 symbol) and 1-16 symbols in steps
              of 1 symbol."
            REFERENCE    "ITU-T G.997.1, paragraph 7.3.2.3"
            DEFVAL       { halfSymbol }
            ::= { zxAnAdslLineConfProfileExtEntry 9 }

   zxAnAdslLineConfMinProtectionUs  OBJECT-TYPE
            SYNTAX      INTEGER
                {
                 autoAdaption (0),
                 noProtection (1),
                 halfSymbol (2),
                 singleSymbol (3),
                 twoSymbols (4),
                 fourSymbols (5),
                 eightSymbols (6),
                 sixteenSymbols (7)
                 }
            UNITS       "symbols"
            MAX-ACCESS  read-create
            STATUS      current
            DESCRIPTION
             "  Minimum Impulse Noise Protection on Upstream direction.  The
                minimum impulse noise protection for the bearer channel,
                expressed in symbols. "
            REFERENCE    "ITU-T G.997.1, paragraph 7.3.2.3"
            DEFVAL       { halfSymbol }
            ::= { zxAnAdslLineConfProfileExtEntry 10 }


   zxAnAdslConfDMTConfTrellis  OBJECT-TYPE
            SYNTAX      INTEGER {
                enable     (1),
                disable    (2)
                }
            MAX-ACCESS  read-create
            STATUS      current
            DESCRIPTION
                "Parameter that enable or disable trellis coding. Trellis coding
                should always be enabled for its clear performance advantage.
                Trellis coding is mandatory for ADSL/ADSL2plus.
                The value enable(1) is default for all Annexes and ADSL2/ADSL2plus."
            DEFVAL       { enable }
            ::= { zxAnAdslLineConfProfileExtEntry 11 }

   zxAnAdslAtucConfMaxBitsPerBin  OBJECT-TYPE
            SYNTAX      INTEGER (0..15)
            MAX-ACCESS  read-create
            STATUS      current
            DESCRIPTION
                "Specifies maximum Rx number of bits per bin."
            DEFVAL { 15 }
            ::= { zxAnAdslLineConfProfileExtEntry 12 }

   zxAnAdslAtucConfBitSwapDs  OBJECT-TYPE
            SYNTAX      INTEGER {
                enable(1),
                disable(2)
                }
            MAX-ACCESS  read-create
            STATUS      current
            DESCRIPTION
                "enables/disables downstream bit swapping.
                 Different line coding type has different default value.
                     disable(2)  (default for ADSL2/ADLS2plus, Annex B, Annex C
                                 C.x, G.Span/ADSL+ and G.Span Plus)
                     enable(1)   (default for Annex A) "
            DEFVAL { disable }
            ::= { zxAnAdslLineConfProfileExtEntry 13 }

   zxAnAdslAtucConfBitSwapUs  OBJECT-TYPE
            SYNTAX      INTEGER {
                enable(1),
                disable(2)
                }
            MAX-ACCESS  read-create
            STATUS      current
            DESCRIPTION
                "enables/disables upstream bit swapping.
                 Different line coding type has different default value.
                     disable(2)  (default for ADSL2/ADLS2plus, Annex B, Annex C
                                 C.x, G.Span/ADSL+ and G.Span Plus)
                     enable(1)   (default for Annex A) "
            DEFVAL { disable }
            ::= { zxAnAdslLineConfProfileExtEntry 14 }


   zxAnAdslAtucConfReAdsl2Enable  OBJECT-TYPE
            SYNTAX      INTEGER {
                enable(1),
                disable(2)
                }
            MAX-ACCESS  read-create
            STATUS      current
            DESCRIPTION
                "Defines whether downstream READSL2 operation should be forced
                by the ATU-C."
            REFERENCE "Section 6.10.1 on page 66,Annex L ITU G.992.3"
            DEFVAL { disable }
            ::= { zxAnAdslLineConfProfileExtEntry 15 }

   zxAnAdslAtucConfPmL0Time  OBJECT-TYPE
            SYNTAX      INTEGER (0..255)
            UNITS       "seconds"
            MAX-ACCESS  read-create
            STATUS      current
            DESCRIPTION
                " PM configuration parameter,related to the L2 low power state.
                This parameter represents the minimum time between an exit from
                the L2 state and the next entry into the L2 state. "
            REFERENCE "Section 7.3.1.1.5 ITU G.997.1(05/2003) "
            DEFVAL { 240 }
            ::= { zxAnAdslLineConfProfileExtEntry 16 }

   zxAnAdslAtucConfPmL2Time  OBJECT-TYPE
            SYNTAX      INTEGER (0..255)
            UNITS       "seconds"
            MAX-ACCESS  read-create
            STATUS      current
            DESCRIPTION
                " PM configuration parameter,related to the L2 low power state.
                This parameter represents the minimum time between an entry into
                the L2 state and the first Power Trim in the L2 state and between
                two consecutive Power Trims in the L2 State."
            REFERENCE "Section 7.3.1.1.6 ITU G.997.1(05/2003) "
            DEFVAL { 120 }
            ::= { zxAnAdslLineConfProfileExtEntry 17 }

   zxAnAdslAtucConfPmL2Atpr  OBJECT-TYPE
            SYNTAX      INTEGER (0..31)
            UNITS       "dB"
            MAX-ACCESS  read-create
            STATUS      current
            DESCRIPTION
                " PM configuration parameter,related to the L2 low power state.
                This parameter represents the Maximum Aggregate Transmit Power
                Reduction (in dB) that can be performed through a single Power
                Trim in the L2 state. It ranges from 0 dB to 31 dB."
            REFERENCE "Section 7.3.1.1.3 ITU G.997.1(05/2003) "
            DEFVAL { 3 }
            ::= { zxAnAdslLineConfProfileExtEntry 18 }

    zxAdsl2ConfPsdMaskSelectUs OBJECT-TYPE
            SYNTAX      INTEGER {
                adlu32Eu32(1),
                adlu36Eu36(2),
                adlu40Eu40(3),
                adlu44Eu44(4),
                adlu48Eu48(5),
                adlu52Eu52(6),
                adlu56Eu56(7),
                adlu60Eu60(8),
                adlu64Eu64(9)
                }
            MAX-ACCESS  read-create
            STATUS      current
            DESCRIPTION
                "The selected upstream PSD mask.  This parameter is used only
                for annexes J and M of G.992.3 and G.992.5, and the same
                selection is used for all relevant enabled bits in
                adslLineTransAtucConfig of ADSL-LINE-EXT-MIB.

                adlu32Eu32 (1),   - ADLU-32 / EU-32
                adlu36Eu36 (2),   - ADLU-36 / EU-36
                adlu40Eu40 (3),   - ADLU-40 / EU-40
                adlu44Eu44 (4),   - ADLU-44 / EU-44
                adlu48Eu48 (5),   - ADLU-48 / EU-48
                adlu52Eu52 (6),   - ADLU-52 / EU-52
                adlu56Eu56 (7),   - ADLU-56 / EU-56
                adlu60Eu60 (8),   - ADLU-60 / EU-60
                adlu64Eu64 (9)    - ADLU-64 / EU-61
                "
            REFERENCE    "ITU-T G.997.1, paragraph #7.3.1.2.11"
            DEFVAL       { adlu32Eu32 }
            ::= { zxAnAdslLineConfProfileExtEntry 19 }

------------------------------------------------------------------------------
-- Atuc Channel Table
------------------------------------------------------------------------------
    zxAnAdslAtucChanTable  OBJECT-TYPE
        SYNTAX      SEQUENCE OF ZxAnAdslAtucChanEntry
        MAX-ACCESS  not-accessible
        STATUS      current
        DESCRIPTION
            "This table provides one row for each Atuc channel.
            "
        ::= {zxAnAdslMibObjects 3}

    zxAnAdslAtucChanEntry  OBJECT-TYPE
        SYNTAX      ZxAnAdslAtucChanEntry
        MAX-ACCESS  not-accessible
        STATUS      current
        DESCRIPTION
            "Adsl channel layer line actuals information entry"
        INDEX    { ifIndex }
        ::= {zxAnAdslAtucChanTable 1}

    ZxAnAdslAtucChanEntry ::=
        SEQUENCE {
            zxAnAdslAtucChanInpEtr          Unsigned32,
            zxAnAdslAtucChanInpEftr         Unsigned32,
            zxAnAdslAtucChanInpMinEftr      Unsigned32,
            zxAnAdslAtucChanInpActDelay     INTEGER
        }

    zxAnAdslAtucChanInpEtr OBJECT-TYPE
        SYNTAX      Unsigned32(0..52000)
        UNITS       "kbps"
        MAX-ACCESS  read-only
        STATUS      current
        DESCRIPTION
            "GINP configuration parameters of downstream.
             The expected throughput (ETR)."
        ::= { zxAnAdslAtucChanEntry 1 }

    zxAnAdslAtucChanInpEftr OBJECT-TYPE
        SYNTAX      Unsigned32(0..52000)
        UNITS       "kbps"
        MAX-ACCESS  read-only
        STATUS      current
        DESCRIPTION
            "GINP configuration parameters of downstream.
             The error-free throughput (EFTR is defined as the average
             bit-rate at the alpha1/beta1 reference point, of bits
             originating from DTU's which have been detected to contain
             no error at the moment of crossing the alpha1/beta1 reference
             point."
        ::= { zxAnAdslAtucChanEntry 2 }

    zxAnAdslAtucChanInpMinEftr OBJECT-TYPE
        SYNTAX      Unsigned32(0..52000)
        UNITS       "kbps"
        MAX-ACCESS  read-only
        STATUS      current
        DESCRIPTION
            "GINP configuration parameters of downstream.
             The minimum error-free throughput (EFTR_min is defined as the
             minimum of the EFTR observed since the last reading of the
             EFTR_min."
        ::= { zxAnAdslAtucChanEntry 3 }

    zxAnAdslAtucChanInpActDelay OBJECT-TYPE
        SYNTAX      INTEGER(0..63)
        UNITS       "ms"
        MAX-ACCESS  read-only
        STATUS      current
        DESCRIPTION
            "GINP configuration parameters of downstream.
             If retransmission is used in a given transmit direction, this
             Object is defined as the actual value of the time-independent
             component of the delay between the alfa1 and beta1 reference
             points.
             This can be calculated as the minimum possible instantaneous
             delay between the alfa1 and beta1 reference points, based on
             the actual settings of the framing parameters."
        ::= { zxAnAdslAtucChanEntry 4 }

------------------------------------------------------------------------------
-- Atur Channel Table
------------------------------------------------------------------------------
    zxAnAdslAturChanTable  OBJECT-TYPE
        SYNTAX      SEQUENCE OF ZxAnAdslAturChanEntry
        MAX-ACCESS  not-accessible
        STATUS      current
        DESCRIPTION
            "This table provides one row for each ATUR channel.
            "
        ::= {zxAnAdslMibObjects 4}


    zxAnAdslAturChanEntry  OBJECT-TYPE
        SYNTAX      ZxAnAdslAturChanEntry
        MAX-ACCESS  not-accessible
        STATUS      current
        DESCRIPTION
            "Adsl channel layer line actuals information entry"
        INDEX    { ifIndex }
        ::= {zxAnAdslAturChanTable 1}


    ZxAnAdslAturChanEntry ::=
        SEQUENCE {
            zxAnAdslAturChanInpEtr          Unsigned32,
            zxAnAdslAturChanInpEftr         Unsigned32,
            zxAnAdslAturChanInpMinEftr      Unsigned32,
            zxAnAdslAturChanInpActDelay     INTEGER
        }

    zxAnAdslAturChanInpEtr OBJECT-TYPE
        SYNTAX      Unsigned32(0..52000)
        UNITS       "kbps"
        MAX-ACCESS  read-only
        STATUS      current
        DESCRIPTION
            "GINP configuration parameters of upstream.
             The expected throughput (ETR)."
        ::= { zxAnAdslAturChanEntry 1 }

    zxAnAdslAturChanInpEftr OBJECT-TYPE
        SYNTAX      Unsigned32(0..52000)
        UNITS       "kbps"
        MAX-ACCESS  read-only
        STATUS      current
        DESCRIPTION
            "GINP configuration parameters of upstream..
             The error-free throughput (EFTR is defined as the average
             bit-rate at the alpha1/beta1 reference point, of bits
             originating from DTU's which have been detected to contain
             no error at the moment of crossing the alpha1/beta1 reference
             point."
        ::= { zxAnAdslAturChanEntry 2 }

    zxAnAdslAturChanInpMinEftr OBJECT-TYPE
        SYNTAX      Unsigned32(0..52000)
        UNITS       "kbps"
        MAX-ACCESS  read-only
        STATUS      current
        DESCRIPTION
            "GINP configuration parameters of upstream.
             The minimum error-free throughput (EFTR_min is defined as the
             minimum of the EFTR observed since the last reading of the
             EFTR_min."
        ::= { zxAnAdslAturChanEntry 3 }

    zxAnAdslAturChanInpActDelay OBJECT-TYPE
        SYNTAX      INTEGER(0..63)
        UNITS       "ms"
        MAX-ACCESS  read-only
        STATUS      current
        DESCRIPTION
            "GINP configuration parameters of upstream.
             If retransmission is used in a given transmit direction, this
             Object is defined as the actual value of the time-independent
             component of the delay between the alfa1 and beta1 reference
             points.
             This can be calculated as the minimum possible instantaneous
             delay between the alfa1 and beta1 reference points, based on
             the actual settings of the framing parameters."
        ::= { zxAnAdslAturChanEntry 4 }

------------------------------------------------------------------------------
-- Adsl Line Alarm Profile Extended Table
------------------------------------------------------------------------------


    zxAnAdslLineAlarmConfProfileExtTable  OBJECT-TYPE
            SYNTAX      SEQUENCE OF ZxAnAdslLineAlarmConfProfileExtEntry
            MAX-ACCESS  not-accessible
            STATUS      current
            DESCRIPTION
                "Adsl line alarm config profile extended information table.
            The cycle of thresholds monitoring shoul be less than 5 minutes."
            ::= {zxAnAdslMibObjects 20}


    zxAnAdslLineAlarmConfProfileExtEntry  OBJECT-TYPE
            SYNTAX      ZxAnAdslLineAlarmConfProfileExtEntry
            MAX-ACCESS  not-accessible
            STATUS      current
            DESCRIPTION
               "An entry extends the adslLineAlarmConfProfileEntry defined in
               [RFC2662]. Each entry corresponds to an ADSL line alarm profile."

            AUGMENTS    { adslLineAlarmConfProfileEntry }
            ::= {zxAnAdslLineAlarmConfProfileExtTable 1}


    ZxAnAdslLineAlarmConfProfileExtEntry ::=
            SEQUENCE {
                zxAnAdslAtucConnRateTolerance          INTEGER,
                zxAnAdslAturConnRateTolerance          INTEGER,
                zxAnAdslAtucThreshConnRate             Integer32,
                zxAnAdslAturThreshConnRate             Integer32,
                zxAnAdslMaxAtucConnRateTolerance       INTEGER,
                zxAnAdslMaxAturConnRateTolerance       INTEGER,
                zxAnAdslMaxThreshAtucConnRate          Integer32,
                zxAnAdslMaxThreshAturConnRate          Integer32,
                zxAnAdslAturInitFailTrapEnable         BITS,
                zxAnAdslThreshAtucInpLeftr             INTEGER,
                zxAnAdslThreshAturInpLeftr             INTEGER
                }


    zxAnAdslAtucConnRateTolerance  OBJECT-TYPE
            SYNTAX      INTEGER(0..100)
            UNITS       "%"
            MAX-ACCESS  read-create
            STATUS      current
            DESCRIPTION
                " Tolerance between configured adslAtucChanConfInterleaveMaxTxRate and
                actual adslAtucChanCurrTxRate.

                Calculation:

                           100*(adslAtucChanConfInterleaveMaxTxRate - adslAtucChanCurrTxRate)
                Difference =-------------------------------------------------------------------
                                          adslAtucChanConfInterleaveMaxTxRate

                If Difference  is larger than zxAnAdslAtucConnRateTolerance,
                zxAnAdslAtucLowConnRateTrap trap will be sent.

                  A value of `0' will disable the trap. "

            DEFVAL { 0 }
            ::= { zxAnAdslLineAlarmConfProfileExtEntry 1 }



    zxAnAdslAturConnRateTolerance  OBJECT-TYPE
            SYNTAX      INTEGER(0..100)
            UNITS       "%"
            MAX-ACCESS  read-create
            STATUS      current
            DESCRIPTION
                " Tolerance between configured adslAturChanConfInterleaveMaxTxRate and
                actual adslAturChanCurrTxRate.

                Calculation:

                           100*(adslAturChanConfInterleaveMaxTxRate - adslAturChanCurrTxRate)
                Difference =-------------------------------------------------------------------
                                          adslAturChanConfInterleaveMaxTxRate


                If Difference  is larger than zxAnAdslAturConnRateTolerance,
                zxAnAdslAturLowConnRateTrap trap will be sent.

                  A value of `0' will disable the trap. "

            DEFVAL { 0 }
            ::= { zxAnAdslLineAlarmConfProfileExtEntry 2 }



    zxAnAdslAtucThreshConnRate  OBJECT-TYPE
            SYNTAX      Integer32
            UNITS       "kbps"
            MAX-ACCESS  read-create
            STATUS      current
            DESCRIPTION
                "   Threshold of Atuc connection rate.
                    If adslAtucChanCurrTxRate  is lower than zxAnAdslAtucThreshConnRate,
                zxAnAdslAtucLowConnRateTrap trap will be sent.
                    A value of `0' will disable the trap. "

            DEFVAL { 0 }
            ::= { zxAnAdslLineAlarmConfProfileExtEntry 3 }



    zxAnAdslAturThreshConnRate  OBJECT-TYPE
            SYNTAX      Integer32
            UNITS       "kbps"
            MAX-ACCESS  read-create
            STATUS      current
            DESCRIPTION
                "   Threshold of Atur connection rate.
                    If adslAturChanCurrTxRate  is lower than zxAnAdslAturThreshConnRate,
                zxAnAdslAturLowConnRateTrap trap will be sent.
                    A value of `0' will disable the trap. "

            DEFVAL { 0 }
            ::= { zxAnAdslLineAlarmConfProfileExtEntry 4 }



    zxAnAdslMaxAtucConnRateTolerance  OBJECT-TYPE
            SYNTAX      INTEGER(0..100)
            UNITS       "%"
            MAX-ACCESS  read-create
            STATUS      current
            DESCRIPTION
                " Tolerance between configured adslAtucChanConfInterleaveMaxTxRate and
                actual adslAtucChanCurrTxRate.

                Calculation:

                           100*(adslAtucChanCurrTxRate - adslAtucChanConfInterleaveMaxTxRate)
                Difference =-------------------------------------------------------------------
                                          adslAtucChanConfInterleaveMaxTxRate

                If Difference  is larger than zxAnMaxAdslAtucConnRateTolerance,
                zxAnAdslAtucHighConnRateTrap trap will be sent.

                  A value of `0' will disable the trap. "

            DEFVAL { 0 }
            ::= { zxAnAdslLineAlarmConfProfileExtEntry 5 }



    zxAnAdslMaxAturConnRateTolerance  OBJECT-TYPE
            SYNTAX      INTEGER(0..100)
            UNITS       "%"
            MAX-ACCESS  read-create
            STATUS      current
            DESCRIPTION
                " Tolerance between configured adslAturChanConfInterleaveMaxTxRate and
                actual adslAturChanCurrTxRate.

                Calculation:

                           100*(adslAturChanCurrTxRate - adslAturChanConfInterleaveMaxTxRate)
                Difference =-------------------------------------------------------------------
                                          adslAturChanConfInterleaveMaxTxRate


                If Difference  is larger than zxAnAdslMaxAturConnRateTolerance,
                zxAnAdslAturHighConnRateTrap trap will be sent.

                  A value of `0' will disable the trap. "

            DEFVAL { 0 }
            ::= { zxAnAdslLineAlarmConfProfileExtEntry 6 }



    zxAnAdslMaxThreshAtucConnRate  OBJECT-TYPE
            SYNTAX      Integer32
            UNITS       "kbps"
            MAX-ACCESS  read-create
            STATUS      current
            DESCRIPTION
                "   Threshold of Atuc connection rate.
                    If adslAtucChanCurrTxRate  is higher than zxAnAdslMaxThreshAtucConnRate,
                zxAnAdslAtucHighConnRateTrap trap will be sent.
                    A value of `0' will disable the trap. "

            DEFVAL { 0 }
            ::= { zxAnAdslLineAlarmConfProfileExtEntry 7 }



    zxAnAdslMaxThreshAturConnRate  OBJECT-TYPE
            SYNTAX      Integer32
            UNITS       "kbps"
            MAX-ACCESS  read-create
            STATUS      current
            DESCRIPTION
                "   Threshold of Atur connection rate.
                    If adslAturChanCurrTxRate  is higher than zxAnAdslMaxThreshAturConnRate,
                zxAnAdslAturHighConnRateTrap trap will be sent.
                    A value of `0' will disable the trap. "

            DEFVAL { 0 }
            ::= { zxAnAdslLineAlarmConfProfileExtEntry 8 }

    zxAnAdslAturInitFailTrapEnable OBJECT-TYPE
            SYNTAX      BITS{
                unused1             (0),
                lossOfFraming       (1),
                lossOfSignal        (2),
                lossOfPower         (3),
                unused2             (4),
                lossOfSignalQuality (5)
            }
            MAX-ACCESS  read-create
            STATUS      current
            DESCRIPTION
                "Enables and disables the InitFailureTrap on the atur interface.

                 unused1             (0) - This bit is no use to enable or
                                           disable the the InitFailureTrap
                                           on the atur interface.

                 lossOfFraming       (1) - Value 0 means disable the loss of
                                           frame trap on the atur interface.

                 lossOfSignal        (2) - Value 0 means disable the loss of
                                           signal trap on the atur interface.

                 lossOfPower         (3) - Value 0 means disable the loss of
                                           power trap on the atur interface.

                 unused2             (4) - This bit is no use to enable or
                                           disable the InitFailureTrap on the
                                           atur interface.

                 lossOfSignalQuality (5) - Value 0 means disable the loss of
                                           signal quality trap on the atur
                                           interface.
                "
            ::= { zxAnAdslLineAlarmConfProfileExtEntry 9 }

    zxAnAdslThreshAtucInpLeftr OBJECT-TYPE
        SYNTAX      INTEGER(0..100)
        MAX-ACCESS  read-create
        STATUS      current
        DESCRIPTION
            "GINP configuration parameters of downstream.
             The fraction of NDR that shall be used as the threshold for
             leftr defects.
             lefter (The low error-free throughput rate) defect is defined as:
               A leftr defect occuurs when EFTR < EFTR_THRESH * NDR
               A leftr defect terminates when EFTR >= EFTR_THRESH * NDR
             When EFTR_THRESH is set to the special value of 0, ETR shall be
             used as the threshold in above inequalities:
               A leftr defect occurs when EFTR < ETR
               A leftr defect terminates when EFTR >=ETR.
             Valid values are from 0 to 100 in increments of 0.01.
             "
        DEFVAL       { 0 }
        ::= { zxAnAdslLineAlarmConfProfileExtEntry 10 }

    zxAnAdslThreshAturInpLeftr OBJECT-TYPE
        SYNTAX      INTEGER(0..100)
        MAX-ACCESS  read-create
        STATUS      current
        DESCRIPTION
            "GINP configuration parameters of upstream.
             The fraction of NDR that shall be used as the threshold for
             leftr defects.
             lefter (The low error-free throughput rate) defect is defined as:
               A leftr defect occuurs when EFTR < EFTR_THRESH * NDR
               A leftr defect terminates when EFTR >= EFTR_THRESH * NDR
             When EFTR_THRESH is set to the special value of 0, ETR shall be
             used as the threshold in above inequalities:
               A leftr defect occurs when EFTR < ETR
               A leftr defect terminates when EFTR >=ETR.
             Valid values are from 0 to 100 in increments of 0.01.
            "
        DEFVAL       { 0 }
        ::= { zxAnAdslLineAlarmConfProfileExtEntry 11 }

--------------------------------------------------------------------------------
-- Atuc Performance Data Table
--------------------------------------------------------------------------------

    zxAnAdslAtucPerfDataTable  OBJECT-TYPE
            SYNTAX      SEQUENCE OF ZxAnAdslAtucPerfDataEntry
            MAX-ACCESS  not-accessible
            STATUS      current
            DESCRIPTION
                 "This table provides atuc performance."
            ::= {zxAnAdslMibObjects 21}

    zxAnAdslAtucPerfDataEntry  OBJECT-TYPE
            SYNTAX      ZxAnAdslAtucPerfDataEntry
            MAX-ACCESS  not-accessible
            STATUS      current
            DESCRIPTION
                "the entry for atuc channel performance."
            INDEX    { ifIndex }
            ::= {zxAnAdslAtucPerfDataTable 1}

    ZxAnAdslAtucPerfDataEntry ::=
            SEQUENCE {
                zxAnAdslAtucPerfDataFecs          Counter32,
                zxAnAdslAtucPerfDataCurr15Fecs    Counter32,
                zxAnAdslAtucPerfDataCurr1DayFecs  Counter32,
                zxAnAdslAtucPerfDataPrev1DayFecs  Counter32
                }

    zxAnAdslAtucPerfDataFecs  OBJECT-TYPE
            SYNTAX      Counter32
            UNITS       "seconds"
            MAX-ACCESS  read-only
            STATUS      current
            DESCRIPTION
               "Count of seconds during this interval that there was at
                least one FEC correction event on this channel."
            REFERENCE    "ITU-T G.997.1, paragraph #7.2.1"
            ::= { zxAnAdslAtucPerfDataEntry 1 }

    zxAnAdslAtucPerfDataCurr15Fecs  OBJECT-TYPE
            SYNTAX      Counter32
            UNITS       "seconds"
            MAX-ACCESS  read-only
            STATUS      current
            DESCRIPTION
               "Count of seconds during this interval that there was at
                least one FEC correction event on this channel
                in this line within the current 15 minute time interval."
            REFERENCE    "ITU-T G.997.1, paragraph #7.2.1"
            ::= { zxAnAdslAtucPerfDataEntry 2 }

    zxAnAdslAtucPerfDataCurr1DayFecs  OBJECT-TYPE
            SYNTAX      Counter32
            UNITS       "seconds"
            MAX-ACCESS  read-only
            STATUS      current
            DESCRIPTION
               "Count of seconds during this interval that there was at
                least one FEC correction event on this channel
                in this line within the current 1 day interval."
            REFERENCE    "ITU-T G.997.1, paragraph #7.2.1"
            ::= { zxAnAdslAtucPerfDataEntry 3 }

    zxAnAdslAtucPerfDataPrev1DayFecs  OBJECT-TYPE
            SYNTAX      Counter32
            UNITS       "seconds"
            MAX-ACCESS  read-only
            STATUS      current
            DESCRIPTION
               "Count of seconds during this interval that there was at
                least one FEC correction event on this channel
                in this line within the most recent previous 1-day period."
            REFERENCE    "ITU-T G.997.1, paragraph #7.2.1"
            ::= { zxAnAdslAtucPerfDataEntry 4 }
--------------------------------------------------------------------------------
-- Atur Performance Data Table
--------------------------------------------------------------------------------

    zxAnAdslAturPerfDataTable  OBJECT-TYPE
            SYNTAX      SEQUENCE OF ZxAnAdslAturPerfDataEntry
            MAX-ACCESS  not-accessible
            STATUS      current
            DESCRIPTION
                 "This table provides atur performance."
            ::= {zxAnAdslMibObjects 22}

    zxAnAdslAturPerfDataEntry  OBJECT-TYPE
            SYNTAX      ZxAnAdslAturPerfDataEntry
            MAX-ACCESS  not-accessible
            STATUS      current
            DESCRIPTION
                "the entry for atur performance."
            INDEX    { ifIndex }
            ::= {zxAnAdslAturPerfDataTable 1}

    ZxAnAdslAturPerfDataEntry ::=
            SEQUENCE {
                zxAnAdslAturPerfDataFecs          Counter32,
                zxAnAdslAturPerfDataCurr15Fecs    Counter32,
                zxAnAdslAturPerfDataCurr1DayFecs  Counter32,
                zxAnAdslAturPerfDataPrev1DayFecs  Counter32
                }

    zxAnAdslAturPerfDataFecs  OBJECT-TYPE
            SYNTAX      Counter32
            UNITS       "seconds"
            MAX-ACCESS  read-only
            STATUS      current
            DESCRIPTION
               "Count of seconds during this interval that there was at
                least one FEC correction event on this channel."
            REFERENCE    "ITU-T G.997.1, paragraph #7.2.1"
            ::= { zxAnAdslAturPerfDataEntry 1 }

    zxAnAdslAturPerfDataCurr15Fecs  OBJECT-TYPE
            SYNTAX      Counter32
            UNITS       "seconds"
            MAX-ACCESS  read-only
            STATUS      current
            DESCRIPTION
               "Count of seconds during this interval that there was at
                least one FEC correction event on this channel
                in this line within the current 15 minute time interval."
            REFERENCE    "ITU-T G.997.1, paragraph #7.2.1"
            ::= { zxAnAdslAturPerfDataEntry 2 }

    zxAnAdslAturPerfDataCurr1DayFecs  OBJECT-TYPE
            SYNTAX      Counter32
            UNITS       "seconds"
            MAX-ACCESS  read-only
            STATUS      current
            DESCRIPTION
               "Count of seconds during this interval that there was at
                least one FEC correction event on this channel
                in this line within the current 1 day interval."
            REFERENCE    "ITU-T G.997.1, paragraph #7.2.1"
            ::= { zxAnAdslAturPerfDataEntry 3 }

    zxAnAdslAturPerfDataPrev1DayFecs  OBJECT-TYPE
            SYNTAX      Counter32
            UNITS       "seconds"
            MAX-ACCESS  read-only
            STATUS      current
            DESCRIPTION
               "Count of seconds during this interval that there was at
                least one FEC correction event on this channel
                in this line within the most recent previous 1-day period."
            REFERENCE    "ITU-T G.997.1, paragraph #7.2.1"
            ::= { zxAnAdslAturPerfDataEntry 4 }

--------------------------------------------------------------------------------
-- Atuc Channel Performance Data Table
--------------------------------------------------------------------------------
    zxAnAdslAtucChanPerfDataTable  OBJECT-TYPE
        SYNTAX      SEQUENCE OF ZxAnAdslAtucChanPerfDataEntry
        MAX-ACCESS  not-accessible
        STATUS      current
        DESCRIPTION
            "This table provides atuc channel performance."
        ::= {zxAnAdslMibObjects 23}

    zxAnAdslAtucChanPerfDataEntry  OBJECT-TYPE
        SYNTAX      ZxAnAdslAtucChanPerfDataEntry
        MAX-ACCESS  not-accessible
        STATUS      current
        DESCRIPTION
            "the entry for atuc channel performance."
        INDEX    { ifIndex }
        ::= {zxAnAdslAtucChanPerfDataTable 1}

    ZxAnAdslAtucChanPerfDataEntry ::=
        SEQUENCE {
            zxAnAtucChanPerfCurr15RtxDtu      Counter32,
            zxAnAtucChanPerfCurr15RtxCDtu     Counter32,
            zxAnAtucChanPerfCurr15RtxUcDtu    Counter32,
            zxAnAtucChanPerfCurr1DRtxDtu      Counter32,
            zxAnAtucChanPerfCurr1DRtxCDtu     Counter32,
            zxAnAtucChanPerfCurr1DRtxUcDtu    Counter32
        }

   zxAnAtucChanPerfCurr15RtxDtu  OBJECT-TYPE
        SYNTAX      Counter32
        MAX-ACCESS  read-only
        STATUS      current
        DESCRIPTION
            "GINP configuration parameters.
             this is a counter that is incremented each time a DTU has been
             retransmitted by the transmitter in the current 15 minute
             interval. Multiple retransmission of the same DTU is counted
             as many times as it has been retransmitted.
             "
        ::= { zxAnAdslAtucChanPerfDataEntry 1 }

    zxAnAtucChanPerfCurr15RtxCDtu  OBJECT-TYPE
        SYNTAX      Counter32
        MAX-ACCESS  read-only
        STATUS      current
        DESCRIPTION
            "GINP configuration parameters.
             this is a counter that is incremented each time a DTU has been
             detected in error and has been successfully corrected by a
             retransmission in the current 15 minute interval"
        ::= { zxAnAdslAtucChanPerfDataEntry 2 }

    zxAnAtucChanPerfCurr15RtxUcDtu  OBJECT-TYPE
        SYNTAX      Counter32
        MAX-ACCESS  read-only
        STATUS      current
        DESCRIPTION
            "GINP configuration parameters.
             this is a counter that is incremented each time a DTU is detected
             in error and has not been corrected by a retransmission in the
             current 15 minute interval."
        ::= { zxAnAdslAtucChanPerfDataEntry 3 }

    zxAnAtucChanPerfCurr1DRtxDtu  OBJECT-TYPE
        SYNTAX      Counter32
        MAX-ACCESS  read-only
        STATUS      current
        DESCRIPTION
            "GINP configuration parameters.
             this is a counter that is incremented each time a DTU has been
             retransmitted by the transmitter in the current day interval.
             Multiple retransmission of the same DTU is counted as many times
             as it has been retransmitted.
             "
        ::= { zxAnAdslAtucChanPerfDataEntry 4 }

    zxAnAtucChanPerfCurr1DRtxCDtu  OBJECT-TYPE
        SYNTAX      Counter32
        MAX-ACCESS  read-only
        STATUS      current
        DESCRIPTION
            "GINP configuration parameters.
             this is a counter that is incremented each time a DTU has been
             detected in error and has been successfully corrected by a
             retransmission in the current day interval"
        ::= { zxAnAdslAtucChanPerfDataEntry 5 }

    zxAnAtucChanPerfCurr1DRtxUcDtu  OBJECT-TYPE
        SYNTAX      Counter32
        MAX-ACCESS  read-only
        STATUS      current
        DESCRIPTION
            "GINP configuration parameters.
             this is a counter that is incremented each time a DTU is detected
             in error and has not been corrected by a retransmission."
        ::= { zxAnAdslAtucChanPerfDataEntry 6 }

--------------------------------------------------------------------------------
-- Atur Channel Performance Data Table
--------------------------------------------------------------------------------

    zxAnAdslAturChanPerfDataTable  OBJECT-TYPE
        SYNTAX      SEQUENCE OF ZxAnAdslAturChanPerfDataEntry
        MAX-ACCESS  not-accessible
        STATUS      current
        DESCRIPTION
            "This table provides atur channel performance."
        ::= {zxAnAdslMibObjects 24}

    zxAnAdslAturChanPerfDataEntry  OBJECT-TYPE
        SYNTAX      ZxAnAdslAturChanPerfDataEntry
        MAX-ACCESS  not-accessible
        STATUS      current
        DESCRIPTION
            "the entry for atur channel performance."
        INDEX    { ifIndex }
        ::= {zxAnAdslAturChanPerfDataTable 1}

    ZxAnAdslAturChanPerfDataEntry ::=
        SEQUENCE {
            zxAnAturChanPerfCurr15RtxDtu      Counter32,
            zxAnAturChanPerfCurr15RtxCDtu     Counter32,
            zxAnAturChanPerfCurr15RtxUcDtu    Counter32,
            zxAnAturChanPerfCurr1DRtxDtu      Counter32,
            zxAnAturChanPerfCurr1DRtxCDtu     Counter32,
            zxAnAturChanPerfCurr1DRtxUcDtu    Counter32
        }

    zxAnAturChanPerfCurr15RtxDtu  OBJECT-TYPE
        SYNTAX      Counter32
        MAX-ACCESS  read-only
        STATUS      current
        DESCRIPTION
            "GINP configuration parameters.
             this is a counter that is incremented each time a DTU has been
             retransmitted by the transmitter in the current 15 minute
             interval. Multiple retransmission of the same DTU is counted
             as many times as it has been retransmitted.
            "
        ::= { zxAnAdslAturChanPerfDataEntry 1 }

    zxAnAturChanPerfCurr15RtxCDtu  OBJECT-TYPE
        SYNTAX      Counter32
        MAX-ACCESS  read-only
        STATUS      current
        DESCRIPTION
            "GINP configuration parameters.
             this is a counter that is incremented each time a DTU has been
             detected in error and has been successfully corrected by a
             retransmission in the current 15 minute interval"
        ::= { zxAnAdslAturChanPerfDataEntry 2 }

    zxAnAturChanPerfCurr15RtxUcDtu  OBJECT-TYPE
        SYNTAX      Counter32
        MAX-ACCESS  read-only
        STATUS      current
        DESCRIPTION
            "GINP configuration parameters.
             this is a counter that is incremented each time a DTU is detected
             in error and has not been corrected by a retransmission in the
             current 15 minute interval."
        ::= { zxAnAdslAturChanPerfDataEntry 3 }

    zxAnAturChanPerfCurr1DRtxDtu  OBJECT-TYPE
        SYNTAX      Counter32
        MAX-ACCESS  read-only
        STATUS      current
        DESCRIPTION
            "GINP configuration parameters.
             this is a counter that is incremented each time a DTU has been
             retransmitted by the transmitter in the current day interval.
             Multiple retransmission of the same DTU is counted as many times
             as it has been retransmitted.
             "
        ::= { zxAnAdslAturChanPerfDataEntry 4 }

    zxAnAturChanPerfCurr1DRtxCDtu  OBJECT-TYPE
        SYNTAX      Counter32
        MAX-ACCESS  read-only
        STATUS      current
        DESCRIPTION
            "GINP configuration parameters.
             this is a counter that is incremented each time a DTU has been
             detected in error and has been successfully corrected by a
             retransmission in the current day interval"
        ::= { zxAnAdslAturChanPerfDataEntry 5 }

    zxAnAturChanPerfCurr1DRtxUcDtu  OBJECT-TYPE
        SYNTAX      Counter32
        MAX-ACCESS  read-only
        STATUS      current
        DESCRIPTION
            "GINP configuration parameters.
             this is a counter that is incremented each time a DTU is detected
             in error and has not been corrected by a retransmission."
        ::= { zxAnAdslAturChanPerfDataEntry 6 }

------------------------------------------------------------------------------
-- Atuc Channel Interval Performance Table
------------------------------------------------------------------------------

    zxAnAdslAtucChanIntervalTable  OBJECT-TYPE
        SYNTAX      SEQUENCE  OF  ZxAnAdslAtucChanIntervalEntry
        MAX-ACCESS  not-accessible
        STATUS      current
        DESCRIPTION
            "The table zxAnAdslAtucChanIntervalTable contains history
             Performance Monitoring results for 15min of DSL channel. "
       ::= { zxAnAdslMibObjects 25 }

    zxAnAdslAtucChanIntervalEntry  OBJECT-TYPE
        SYNTAX      ZxAnAdslAtucChanIntervalEntry
        MAX-ACCESS  not-accessible
        STATUS      current
        DESCRIPTION
            "The table zxAnAdslAtucChanIntervalTable contains history
             Performance Monitoring results for 15min of DSL channel.
            "
       AUGMENTS  { adslAtucChanIntervalEntry }
       ::= { zxAnAdslAtucChanIntervalTable 1 }

    ZxAnAdslAtucChanIntervalEntry  ::=
        SEQUENCE {
            zxAnAdslAtucChanIntervalRtxDtu                  Counter32,
            zxAnAdslAtucChanIntervalRtxCDtu                 Counter32,
            zxAnAdslAtucChanIntervalRtxUcDtu                Counter32
        }

    zxAnAdslAtucChanIntervalRtxDtu  OBJECT-TYPE
        SYNTAX      Counter32
        MAX-ACCESS  read-only
        STATUS      current
        DESCRIPTION
            "GINP configuration parameters.
             this is a counter that is incremented each time a DTU has been
             retransmitted by the transmitter during this interval. Multiple
             retransmission of the same DTU is counted as many times as it
             has been retransmitted.
             "
       ::= { zxAnAdslAtucChanIntervalEntry 1 }

    zxAnAdslAtucChanIntervalRtxCDtu  OBJECT-TYPE
        SYNTAX      Counter32
        MAX-ACCESS  read-only
        STATUS      current
        DESCRIPTION
            "GINP configuration parameters.
             this is a counter that is incremented each time a DTU has been
             detected in error and has been successfully corrected by a
             retransmission during this interval."
        ::= { zxAnAdslAtucChanIntervalEntry 2 }

    zxAnAdslAtucChanIntervalRtxUcDtu OBJECT-TYPE
        SYNTAX      Counter32
        MAX-ACCESS  read-only
        STATUS      current
        DESCRIPTION
            "GINP configuration parameters.
             this is a counter that is incremented each time a DTU is detected
             in error and has not been corrected by a retransmission. during
             this interval."
        ::= { zxAnAdslAtucChanIntervalEntry 3 }

------------------------------------------------------------------------------
-- Atur Channel Interval Performance Table
------------------------------------------------------------------------------
    zxAnAdslAturChanIntervalTable  OBJECT-TYPE
        SYNTAX      SEQUENCE  OF  ZxAnAdslAturChanIntervalEntry
        MAX-ACCESS  not-accessible
        STATUS      current
        DESCRIPTION
            "The table zxAnAdslAturChanIntervalTable contains history
             Performance Monitoring results for 15min of DSL channel. "
       ::= { zxAnAdslMibObjects 26 }

    zxAnAdslAturChanIntervalEntry  OBJECT-TYPE
        SYNTAX      ZxAnAdslAturChanIntervalEntry
        MAX-ACCESS  not-accessible
        STATUS      current
        DESCRIPTION
            "The table zxAnAdslAturChanIntervalTable contains history
             Performance Monitoring results for 15min of DSL channel.
          "
       AUGMENTS  { adslAturChanIntervalEntry }
       ::= { zxAnAdslAturChanIntervalTable 1 }

    ZxAnAdslAturChanIntervalEntry  ::=
        SEQUENCE {
            zxAnAdslAturChanIntervalRtxDtu                  Counter32,
            zxAnAdslAturChanIntervalRtxCDtu                 Counter32,
            zxAnAdslAturChanIntervalRtxUcDtu                Counter32
        }

    zxAnAdslAturChanIntervalRtxDtu  OBJECT-TYPE
        SYNTAX      Counter32
        MAX-ACCESS  read-only
        STATUS      current
        DESCRIPTION
            "GINP configuration parameters.
             this is a counter that is incremented each time a DTU has been
             retransmitted by the transmitter during this interval. Multiple
             retransmission of the same DTU is counted as many times as it
             has been retransmitted.
             "
       ::= { zxAnAdslAturChanIntervalEntry 1 }

    zxAnAdslAturChanIntervalRtxCDtu  OBJECT-TYPE
        SYNTAX      Counter32
        MAX-ACCESS  read-only
        STATUS      current
        DESCRIPTION
            "GINP configuration parameters.
             this is a counter that is incremented each time a DTU has been
             detected in error and has been successfully corrected by a
             retransmission during this interval."
        ::= { zxAnAdslAturChanIntervalEntry 2 }

    zxAnAdslAturChanIntervalRtxUcDtu OBJECT-TYPE
        SYNTAX      Counter32
        MAX-ACCESS  read-only
        STATUS      current
        DESCRIPTION
            "GINP configuration parameters.
             this is a counter that is incremented each time a DTU is detected
             in error and has not been corrected by a retransmission. during
             this interval."
        ::= { zxAnAdslAturChanIntervalEntry 3 }

------------------------------------------------------------------------------
-- Atuc Channel history 1 Day Performance Table
------------------------------------------------------------------------------

    zxAnAdslAtucChanHist1DayTable         OBJECT-TYPE
        SYNTAX      SEQUENCE  OF  ZxAnAdslAtucChanHist1DayEntry
        MAX-ACCESS  not-accessible
        STATUS      current
        DESCRIPTION
            "The table zxAnAdslAtucChanHist1DayTable contains channel history
             for 1 day intervals of DSL. "
        ::= { zxAnAdslMibObjects 27 }

    zxAnAdslAtucChanHist1DayEntry  OBJECT-TYPE
        SYNTAX      ZxAnAdslAtucChanHist1DayEntry
        MAX-ACCESS  not-accessible
        STATUS      current
        DESCRIPTION
            "The table zxAnAdslAtucChanHist1DayTable contains PM channel
             history for 1 day intervals of DSL.
             The indexes of this table is an interface index where
             the interface has an ifType value which is applicable
             for a DSL channel, the termination unit and the
             interval number."
        INDEX  { ifIndex,zxAnAdslAtucChanHist1DayNumber }
        ::= { zxAnAdslAtucChanHist1DayTable 1 }

    ZxAnAdslAtucChanHist1DayEntry  ::= SEQUENCE {
        zxAnAdslAtucChanHist1DayNumber         INTEGER,
        zxAnAdslAtucChanHist1DayRtxDtu         Counter32,
        zxAnAdslAtucChanHist1DayRtxCDtu        Counter32,
        zxAnAdslAtucChanHist1DayRtxUcDtu       Counter32
    }

    zxAnAdslAtucChanHist1DayNumber OBJECT-TYPE
        SYNTAX      INTEGER(1..30)
        MAX-ACCESS  not-accessible
        STATUS      current
        DESCRIPTION
            "The interval number."
        ::= { zxAnAdslAtucChanHist1DayEntry 1 }

    zxAnAdslAtucChanHist1DayRtxDtu  OBJECT-TYPE
        SYNTAX      Counter32
        MAX-ACCESS  read-only
        STATUS      current
        DESCRIPTION
            "GINP configuration parameters.
             this is a counter that is incremented each time a DTU has been
             retransmitted by the transmitter during this interval. Multiple
             retransmission of the same DTU is counted as many times as it
             has been retransmitted."
        ::= { zxAnAdslAtucChanHist1DayEntry 2 }

    zxAnAdslAtucChanHist1DayRtxCDtu  OBJECT-TYPE
        SYNTAX      Counter32
        MAX-ACCESS  read-only
        STATUS      current
        DESCRIPTION
            "GINP configuration parameters.
             this is a counter that is incremented each time a DTU has been
             detected in error and has been successfully corrected by a
             retransmission during this interval."
        ::= { zxAnAdslAtucChanHist1DayEntry 3 }

    zxAnAdslAtucChanHist1DayRtxUcDtu  OBJECT-TYPE
        SYNTAX      Counter32
        MAX-ACCESS  read-only
        STATUS      current
        DESCRIPTION
            "GINP configuration parameters.
             this is a counter that is incremented each time a DTU is detected
             in error and has not been corrected by a retransmission during
             this interval."
        ::= { zxAnAdslAtucChanHist1DayEntry 4 }

------------------------------------------------------------------------------
-- Atur Channel history 1 Day Performance Table
------------------------------------------------------------------------------
    zxAnAdslAturChanHist1DayTable         OBJECT-TYPE
        SYNTAX      SEQUENCE  OF  ZxAnAdslAturChanHist1DayEntry
        MAX-ACCESS  not-accessible
        STATUS      current
        DESCRIPTION
            "The table zxAnAdslAturChanHist1DayTable contains channel history
             for 1 day intervals of DSL. "
        ::= { zxAnAdslMibObjects 28 }

    zxAnAdslAturChanHist1DayEntry  OBJECT-TYPE
        SYNTAX      ZxAnAdslAturChanHist1DayEntry
        MAX-ACCESS  not-accessible
        STATUS      current
        DESCRIPTION
            "The table zxAnAdslAturChanHist1DayTable contains PM channel
             history for 1 day intervals of DSL.
             The indexes of this table is an interface index where
             the interface has an ifType value which is applicable
             for a DSL channel, the termination unit and the
             interval number."
        INDEX  { ifIndex,zxAnAdslAturChanHist1DayNumber }
        ::= { zxAnAdslAturChanHist1DayTable 1 }

    ZxAnAdslAturChanHist1DayEntry  ::= SEQUENCE {
        zxAnAdslAturChanHist1DayNumber         INTEGER,
        zxAnAdslAturChanHist1DayRtxDtu         Counter32,
        zxAnAdslAturChanHist1DayRtxCDtu        Counter32,
        zxAnAdslAturChanHist1DayRtxUcDtu       Counter32
    }

    zxAnAdslAturChanHist1DayNumber OBJECT-TYPE
        SYNTAX      INTEGER(1..30)
        MAX-ACCESS  not-accessible
        STATUS      current
        DESCRIPTION
            "The interval number."
        ::= { zxAnAdslAturChanHist1DayEntry 1 }

    zxAnAdslAturChanHist1DayRtxDtu  OBJECT-TYPE
        SYNTAX      Counter32
        MAX-ACCESS  read-only
        STATUS      current
        DESCRIPTION
            "GINP configuration parameters.
             this is a counter that is incremented each time a DTU has been
             retransmitted by the transmitter during this interval. Multiple
             retransmission of the same DTU is counted as many times as it
             has been retransmitted."
        ::= { zxAnAdslAturChanHist1DayEntry 2 }

    zxAnAdslAturChanHist1DayRtxCDtu  OBJECT-TYPE
        SYNTAX      Counter32
        MAX-ACCESS  read-only
        STATUS      current
        DESCRIPTION
            "GINP configuration parameters.
             this is a counter that is incremented each time a DTU has been
             detected in error and has been successfully corrected by a
             retransmission during this interval."
        ::= { zxAnAdslAturChanHist1DayEntry 3 }

    zxAnAdslAturChanHist1DayRtxUcDtu  OBJECT-TYPE
        SYNTAX      Counter32
        MAX-ACCESS  read-only
        STATUS      current
        DESCRIPTION
            "GINP configuration parameters.
             this is a counter that is incremented each time a DTU is detected
             in error and has not been corrected by a retransmission during
             this interval."
        ::= { zxAnAdslAturChanHist1DayEntry 4 }

--------------------------------------------------------------------------------
-- Dsl Loopback Test Table
--------------------------------------------------------------------------------

    zxAnDslLoopBackTestTable  OBJECT-TYPE
            SYNTAX      SEQUENCE OF ZxAnDslLoopBackTestEntry
            MAX-ACCESS  not-accessible
            STATUS      current
            DESCRIPTION
                 "This table provides one row for each DSL line loopback test."
            ::= {zxAnAdslMibObjects 30}


    zxAnDslLoopBackTestEntry  OBJECT-TYPE
            SYNTAX      ZxAnDslLoopBackTestEntry
            MAX-ACCESS  not-accessible
            STATUS      current
            DESCRIPTION
                "DSL line loopback test information entry"
            INDEX    { zxAnDslLoopBackTestRack,zxAnDslLoopBackTestShelf,
                       zxAnDslLoopBackTestSlot,zxAnDslLoopBackTestPort,
                       zxAnDslLoopBackTestBridgePort  }
            ::= {zxAnDslLoopBackTestTable 1}


    ZxAnDslLoopBackTestEntry ::=
            SEQUENCE {
                zxAnDslLoopBackTestRack               Integer32,
                zxAnDslLoopBackTestShelf              Integer32,
                zxAnDslLoopBackTestSlot               Integer32,
                zxAnDslLoopBackTestPort               Integer32,
                zxAnDslLoopBackTestBridgePort         Integer32,
                zxAnDslLoopBackTestType               INTEGER,
                zxAnDslLoopBackTestOperStatus         INTEGER,
                zxAnDslLoopBackTestResult             INTEGER,
                zxAnDslLoopBackTestConfSendCells      Integer32,
                zxAnDslLoopBackTestResultRecivedCells Integer32,
                zxAnDslLoopBackTestRowStatus          RowStatus
                }

    zxAnDslLoopBackTestRack  OBJECT-TYPE
            SYNTAX      Integer32
            MAX-ACCESS  not-accessible
            STATUS      current
            DESCRIPTION
                 "Rack number of the dsl port."
            ::= { zxAnDslLoopBackTestEntry 1 }



    zxAnDslLoopBackTestShelf  OBJECT-TYPE
            SYNTAX      Integer32
            MAX-ACCESS  not-accessible
            STATUS      current
            DESCRIPTION
                 "Shelf number of the dsl port."
            ::= { zxAnDslLoopBackTestEntry 2 }


    zxAnDslLoopBackTestSlot  OBJECT-TYPE
            SYNTAX      Integer32
            MAX-ACCESS  not-accessible
            STATUS      current
            DESCRIPTION
                 "Slot number of the dsl port."
            ::= { zxAnDslLoopBackTestEntry 3 }


    zxAnDslLoopBackTestPort  OBJECT-TYPE
            SYNTAX      Integer32
            MAX-ACCESS  not-accessible
            STATUS      current
            DESCRIPTION
                 "The dsl port number."
            ::= { zxAnDslLoopBackTestEntry 4 }



    zxAnDslLoopBackTestBridgePort  OBJECT-TYPE
            SYNTAX      Integer32
            MAX-ACCESS  not-accessible
            STATUS      current
            DESCRIPTION
                 "Dsl bridge port index. eg.It is PVC ID in  ADSL port.
                 If the test is only in the physical port,then this fileds will be 0"
            ::= { zxAnDslLoopBackTestEntry 5 }


    zxAnDslLoopBackTestType  OBJECT-TYPE
            SYNTAX      INTEGER {
                noOper(0),  -- No operation
                cancle(1),  -- Cancle this test
                utopia(2),  -- Utopia loopback test
                afe(3),     -- AFE loopback test
                hybrid(4),  -- Hybrid loopback test
                xTUC_OAM(5),-- ATUC data path loopback test,such as ATM OAM loopback.
                xTUR_OAM(6), -- ATUR data path loopback test,such as ATM OAM loopback.
                xTUR_CC(7), -- ATUR ATM continuity cell test.
                digital(8)  -- ATUC DSP module loopback test.
                }
            MAX-ACCESS  read-create
            STATUS      current
            DESCRIPTION
                 "This is loop test action expected.

                 NOTES:

                 "
            ::= { zxAnDslLoopBackTestEntry 6 }


    zxAnDslLoopBackTestOperStatus  OBJECT-TYPE
            SYNTAX      INTEGER {
                neverExcute(0),   -- Never excute test
                excuting(1),      -- Excuting test now
                excuted(2),       -- Test has been excuted
                faliedToCommit(3) -- Falied to commit test command to DSL card.
                }
            MAX-ACCESS  read-only
            STATUS      current
            DESCRIPTION
                 "This is loop test operational status.

                  Note: if zxAnDslLoopBackTestOperStatus equal to Excuting(1),
                  ifOperStaus should be loopback test(3). "
            ::= { zxAnDslLoopBackTestEntry 7 }


    zxAnDslLoopBackTestResult  OBJECT-TYPE
            SYNTAX      INTEGER {
                noResult(0),
                success(1),
                generalFailed(2), -- Test failed but no detailed reason.
                noSupport(3),     -- Current DSL card doesn't support this test.
                unkown(4),        -- Unkown the test result.
                noSuchPort(5),    -- No this port on dsl card
                loopBackFailed(6),-- Loop back failed on dsl card
                portNotActive(7), -- Some test can't be excuted when port is not actived.
                portInTesting(8), -- Port in testing and can't excute the new test
                portInService(9), -- Port in service and can't excute the test
                portFailures(10), -- Port has failures and can't excute the test
                cardFailures(11), -- Dsl card has failures and can't excute the test
                noPvcFound(12),   -- No PVC found on the test port
                unknownTestType(13) -- The test type is not UTOPIA,AFE,HYBRID,ATUC-OAM or ATUR-OAM
            }
            MAX-ACCESS  read-only
            STATUS      current
            DESCRIPTION
                 "This is loop test result and includes reasons for test failures."
            ::= { zxAnDslLoopBackTestEntry 8 }


    zxAnDslLoopBackTestConfSendCells  OBJECT-TYPE
            SYNTAX      Integer32
            MAX-ACCESS  read-create
            STATUS      current
            DESCRIPTION
                 "The count of cells will be sent in the loopback test."

             ::= { zxAnDslLoopBackTestEntry 9 }


    zxAnDslLoopBackTestResultRecivedCells  OBJECT-TYPE
            SYNTAX      Integer32
            MAX-ACCESS  read-only
            STATUS      current
            DESCRIPTION
                 "The count of recived cells in the loopback test."
             ::= { zxAnDslLoopBackTestEntry 10 }


    zxAnDslLoopBackTestRowStatus  OBJECT-TYPE
            SYNTAX      RowStatus
            MAX-ACCESS  read-create
            STATUS      current
            DESCRIPTION
                 "Loop test table RowStatus . "
             ::= { zxAnDslLoopBackTestEntry 15 }


------------------------------------------------------------------------------
-- trap definitions
------------------------------------------------------------------------------

    zxAnAdslTraps OBJECT IDENTIFIER ::= { zxAnAdslMib 2 }

    zxAnAdslAtuxConnRateOverThreshTrap      NOTIFICATION-TYPE
            OBJECTS { adslAtucChanConfInterleaveMaxTxRate,
                      adslAtucChanCurrTxRate  }
            STATUS  current
            DESCRIPTION
                "zxAnAdslAtucConnRateTolerance threshold or zxAnAdslAtucThreshConnRate reached."
            ::= { zxAnAdslTraps 1 }


    zxAnAdslAtuxConnRateUnderThreshTrap      NOTIFICATION-TYPE
            OBJECTS { adslAtucChanConfInterleaveMaxTxRate,
                      adslAtucChanCurrTxRate  }
            STATUS  current
            DESCRIPTION
                " AtucConnRate Difference is below threshold of zxAnAdslAtucConnRateTolerance.
                 Or adslAtucChanCurrTxRate is below threshold of zxAnAdslAtucThreshConnRate. "
            ::= { zxAnAdslTraps 2 }


    zxAnAdslAtucHighConnRateTrap        NOTIFICATION-TYPE
            OBJECTS { adslAtucChanConfInterleaveMaxTxRate, adslAtucChanCurrTxRate,
                      zxAnAdslMaxThreshAtucConnRate, zxAnAdslMaxAtucConnRateTolerance}
            STATUS  current
            DESCRIPTION
                "zxAnAdslMaxAtucConnRateTolerance threshold or zxAnAdslMaxThreshAtucConnRate reached."
            ::= { zxAnAdslTraps 3 }


    zxAnAdslAtucHighConnRateClearTrap        NOTIFICATION-TYPE
            OBJECTS { adslAtucChanConfInterleaveMaxTxRate, adslAtucChanCurrTxRate,
                      zxAnAdslMaxThreshAtucConnRate, zxAnAdslMaxAtucConnRateTolerance}
            STATUS  current
            DESCRIPTION
                "zxAnAdslAtucHighConnRateTrap clear."
            ::= { zxAnAdslTraps 4 }


    zxAnAdslAtucLowConnRateTrap        NOTIFICATION-TYPE
            OBJECTS { adslAtucChanConfInterleaveMaxTxRate, adslAtucChanCurrTxRate,
                      zxAnAdslAtucThreshConnRate, zxAnAdslAtucConnRateTolerance}
            STATUS  current
            DESCRIPTION
                "zxAnAdslAtucConnRateTolerance threshold or zxAnAdslAtucThreshConnRate reached."
            ::= { zxAnAdslTraps 5 }


    zxAnAdslAtucLowConnRateClearTrap        NOTIFICATION-TYPE
            OBJECTS { adslAtucChanConfInterleaveMaxTxRate, adslAtucChanCurrTxRate,
                      zxAnAdslAtucThreshConnRate, zxAnAdslAtucConnRateTolerance}
            STATUS  current
            DESCRIPTION
                " zxAnAdslAtucLowConnRateTrap clear."
            ::= { zxAnAdslTraps 6 }


    zxAnAdslAturHighConnRateTrap        NOTIFICATION-TYPE
            OBJECTS { adslAturChanConfInterleaveMaxTxRate, adslAturChanCurrTxRate,
                      zxAnAdslMaxThreshAturConnRate, zxAnAdslMaxAturConnRateTolerance}
            STATUS  current
            DESCRIPTION
                "zxAnAdslMaxAturConnRateTolerance threshold or zxAnAdslMaxThreshAturConnRate reached."
            ::= { zxAnAdslTraps 7 }


    zxAnAdslAturHighConnRateClearTrap        NOTIFICATION-TYPE
            OBJECTS { adslAturChanConfInterleaveMaxTxRate, adslAturChanCurrTxRate,
                      zxAnAdslMaxThreshAturConnRate, zxAnAdslMaxAturConnRateTolerance}
            STATUS  current
            DESCRIPTION
                "zxAnAdslAturHighConnRateTrap clear."
            ::= { zxAnAdslTraps 8 }


    zxAnAdslAturLowConnRateTrap        NOTIFICATION-TYPE
            OBJECTS { adslAturChanConfInterleaveMaxTxRate, adslAturChanCurrTxRate,
                      zxAnAdslAturThreshConnRate, zxAnAdslAturConnRateTolerance}
            STATUS  current
            DESCRIPTION
                "zxAnAdslAturConnRateTolerance threshold or zxAnAdslAturThreshConnRate reached."
            ::= { zxAnAdslTraps 9 }


    zxAnAdslAturLowConnRateClearTrap        NOTIFICATION-TYPE
            OBJECTS { adslAturChanConfInterleaveMaxTxRate, adslAturChanCurrTxRate,
                      zxAnAdslAturThreshConnRate, zxAnAdslAturConnRateTolerance}
            STATUS  current
            DESCRIPTION
                " zxAnAdslAturLowConnRateTrap clear."
            ::= { zxAnAdslTraps 10 }

END
