-- File Name : ZTE-DSL-Route-MIB.mib
-- Date      : Mon Oct 17 13:48:13 GMT+08:00 2005
-- Author    : AdventNet Agent Toolkit C Edition - MibEditor 6

--
-- Zte Dsl Route Ext Mib
--
--


ZTE-DSL-Route-MIB	DEFINITIONS ::= BEGIN
	IMPORTS
		zxDsl
			FROM ZTE-DSL-MIB
		DisplayString, MacAddress, RowStatus, TruthValue
			FROM SNMPv2-TC
		MODULE-COMPLIANCE, OBJECT-GROUP
			FROM SNMPv2-CONF
		ifIndex
			FROM IF-MIB
		MODULE-IDENTITY, OBJECT-TYPE, TimeTicks, Counter32, Gauge32, IpAddress, enterprises
			FROM SNMPv2-SMI
		adslLineConfProfileName, adslLineConfProfileEntry, adslLineAlarmConfProfileEntry
			FROM ADSL-LINE-MIB
		SnmpAdminString
			FROM SNMP-FRAMEWORK-MIB;

	zxDslRouteMib	MODULE-IDENTITY
		LAST-UPDATED	"200510080948Z"
		ORGANIZATION	"zte dsl product line"
		CONTACT-INFO	"ma ke
                  Mail: ma.ke@zte.com.cn
                  Tel : 021-68896477"
		DESCRIPTION		"This mib defines adsl route mo (managed object ) for adsl2,
                 adsl+ and dsl loop test.

                 Naming Conventions:
                 Atuc -- (ATUC) modem at near (Central) end of line
                 Atur -- (ATUR) modem at Remote end of line"
		::=  {  zxDsl  11  }

	zxDslIpStaticRouteTable	OBJECT-TYPE
                SYNTAX        SEQUENCE  OF  ZxDslIpStaticRouteEntry
		MAX-ACCESS	not-accessible
		STATUS		current
		DESCRIPTION	"A table entry containing Adsl Route Static information  for each
		port. These variables are not in RFC2495 configuration table."
		::=  { zxDslRouteMib  1 }

	zxDslIpStaticRouteEntry	OBJECT-TYPE
                SYNTAX        ZxDslIpStaticRouteEntry
		MAX-ACCESS	not-accessible
		STATUS		current
		DESCRIPTION	"Adsl Route static information entry"
		INDEX		{  zxDslIpStaticDestIpAddr  }
		::=  { zxDslIpStaticRouteTable 1 }

	ZxDslIpStaticRouteEntry  ::=  SEQUENCE {
		zxDslIpStaticDestIpAddr  IpAddress,
		zxDslIpStaticMask  IpAddress,
		zxDslIpStaticNextHop  IpAddress,
		zxDslIpStaticName  DisplayString,
		zxDslIpStaticUseHw  TruthValue,
		zxDslIpStaticInHw  TruthValue,
		zxDslIpStaticRowStatus  RowStatus
		}


	zxDslIpStaticDestIpAddr	OBJECT-TYPE
		SYNTAX			IpAddress
		MAX-ACCESS		not-accessible
		STATUS			current
		DESCRIPTION		"DURABLE:
             The static route host or subnet IP destination address.
             Note that TMS supports up to one default route (0.0.0.0) entry.
             All other IP destination addresses must be non-zero."
		::=  {  zxDslIpStaticRouteEntry  1  }


	zxDslIpStaticMask	OBJECT-TYPE
		SYNTAX			IpAddress
		MAX-ACCESS		read-create
		STATUS			current
		DESCRIPTION		"DURABLE:
             The mask for this IP destination.  It contains 1's in the
             bit positions for the net and subnet IDs and 0's in the
             bit positions for host ID.  The 1's must be contiguous,
             starting with the left most bit.

             Note that a host route uses a 255.255.255.255 mask."
		::=  {  zxDslIpStaticRouteEntry  2  }


	zxDslIpStaticNextHop	OBJECT-TYPE
		SYNTAX			IpAddress
		MAX-ACCESS		read-create
		STATUS			current
		DESCRIPTION		"The IP address of the next hop of this route.
            (In the case of a route bound to an interface
            which is realized via a broadcast media, the value
            of this field is the agent's IP address on that
            interface.)"
		::=  {  zxDslIpStaticRouteEntry  3  }


	zxDslIpStaticName	OBJECT-TYPE
		SYNTAX			DisplayString  ( SIZE ( 0 .. 16  ) )
		MAX-ACCESS		read-create
		STATUS			current
		DESCRIPTION		"DURABLE:  { '':all )
             A user reference name for this Static Route."
		::=  {  zxDslIpStaticRouteEntry  4  }


	zxDslIpStaticUseHw	OBJECT-TYPE
		SYNTAX			TruthValue
		MAX-ACCESS		read-create
		STATUS			current
		DESCRIPTION		"DURABLE: { false:all )
             By setting this object to true(1), the user indicates the
             desire to use hardware routing for this entry.  To disable
             hardware routing for this entry, set this object to false(2).
             If the underlying switch fabric does not support hardware
             routing, this object is ignored.

             There is usually limited space in the hardware routing table.
             Consequently, if the user enables hardware routing on 'too'
             many entries, the agent assigns routes on a first come, first
             serve basis (i.e., the user may not get the expected results)."
		::=  {  zxDslIpStaticRouteEntry  5  }


	zxDslIpStaticInHw	OBJECT-TYPE
		SYNTAX			TruthValue
		MAX-ACCESS		read-only
		STATUS			current
		DESCRIPTION		"If this object is true(1), this static route is actually in
             the hardware Route Table.  Otherwise it is false(2)."
		::=  {  zxDslIpStaticRouteEntry  6  }


	zxDslIpStaticRowStatus	OBJECT-TYPE
		SYNTAX			RowStatus
		MAX-ACCESS		read-create
		STATUS			current
		DESCRIPTION		"DURABLE:
             This object indicates the status of this entry.  A row in this
             table must be created using the createAndWait(5) action state
             (i.e., createAndGo(4) is not supported).  This object can only
             be set to active(1) after all objects for this row are valid.
             The 'tmsL3IpStaticName' is optional.

             Note that the notInService(2) state is not supported.  Objects
             in this table row can be changed when this object is notReady(3)
             or active(1)."
		::=  {  zxDslIpStaticRouteEntry  7  }

END
