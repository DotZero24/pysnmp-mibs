--  ************************************************
--  $Id: ZXR10-VOIP.mib 3 2005-12-20 01:34:21Z taowq $
--
--  ZZXR10-VOIP.mib: ZXR10 voip  MIB file
--
--  Dec. 2005, Tao wenqiang
--
--  Copyright(c) 2005 by ZTE Corporaton
--  All rights reservered
--
--  ************************************************

ZXR10-OAM-MIB DEFINITIONS ::= BEGIN

IMPORTS
       OBJECT-TYPE,
       enterprises,
       Unsigned32
       	FROM SNMPv2-SMI

       ifIndex            		        FROM RFC1213-MIB;

--       RowStatus
--                                       FROM SNMPv2-TC
--       mgmt, NetworkAddress, IpAddress, Counter, Gauge
--                         FROM RFC1155-SMI
      --         Counter, TimeTicks     FROM RFC1155-SMI
      -- IpAddress,DisplayString, mib-2   FROM RFC1213-MIB

      -- TRAP-TYPE              FROM RFC-1215;

    zte OBJECT IDENTIFIER ::= { enterprises 3902 }
    zxr10 OBJECT IDENTIFIER ::= { zte 3}

    DisplayString ::= OCTET STRING

    zxr10switch OBJECT IDENTIFIER ::= { zxr10 102}
    zxr10ethernetOam OBJECT IDENTIFIER ::= { zxr10switch 20}

    zxr10ethernetOamGlobalConfig OBJECT IDENTIFIER ::= { zxr10ethernetOam 1}

    zxr10ethernetOamGlobalEnable	OBJECT-TYPE
		SYNTAX			INTEGER{disnable(0),enable(1)}
		MAX-ACCESS		read-write
		STATUS			current
		DESCRIPTION
		"Configure Ethernet oam enable."
		::=  {  zxr10ethernetOamGlobalConfig  1  }

   	zxr10ethernetOamOuiInformation	OBJECT-TYPE
		SYNTAX			DisplayString(SIZE(1..3))
		MAX-ACCESS		read-write
		STATUS			current
		DESCRIPTION
		"Config Ethernet oam oui information."
		::=  {  zxr10ethernetOamGlobalConfig  2  }

    zxr10ethernetOamRemoteLoopbackTimeout	OBJECT-TYPE
		SYNTAX			Unsigned32(1..10)
		MAX-ACCESS		read-write
		STATUS			current
		DESCRIPTION
		"Config Ethernet oam remote loopback time-out."
		::=  {  zxr10ethernetOamGlobalConfig  3  }


	zxr10ethernetOamIfConfigTable	OBJECT-TYPE
		SYNTAX		SEQUENCE  OF  Zxr10ethernetOamIfConfigEntry
		MAX-ACCESS	not-accessible
		STATUS		current
		DESCRIPTION
		"Configure Ethernet Oam interface parameters."
		::=  { zxr10ethernetOam 2 }

	zxr10ethernetOamIfConfigEntry	OBJECT-TYPE
		SYNTAX		Zxr10ethernetOamIfConfigEntry
		MAX-ACCESS	not-accessible
		STATUS		current
		DESCRIPTION
		     ""

		INDEX		{  ifIndex  }
		::=  { zxr10ethernetOamIfConfigTable 1 }

	Zxr10ethernetOamIfConfigEntry  ::=  SEQUENCE {
            zxr10ethernetOamIfEnable
                INTEGER,
            zxr10ethernetOamRemoteLoopbackEnable
                INTEGER,
            zxr10ethernetOamifperiod
                Unsigned32,
            zxr10ethernetOamifmode
                Unsigned32,
            zxr10ethernetOamiftimeout
                Unsigned32,
            zxr10ethernetOamifLinkMonitorEnable
                INTEGER,
            zxr10ethernetOamifLinkMonitorSymbolPeriodthreshold
                Unsigned32,
            zxr10ethernetOamifLinkMonitorSymbolPeriodwindow
                Unsigned32,
            zxr10ethernetOamifLinkMonitorFramethreshold
                Unsigned32,
            zxr10ethernetOamifLinkMonitorFramewindow
                Unsigned32,
            zxr10ethernetOamifLinkMonitorFramePeriodthreshold
                Unsigned32,
            zxr10ethernetOamifLinkMonitorFramePeriodwindow
                Unsigned32,
            zxr10ethernetOamifLinkMonitorFrameSecondsthreshold
                Unsigned32,
            zxr10ethernetOamifLinkMonitorFrameSecondswindow
                Unsigned32,
            zxr10ethernetOamifName
                DisplayString
       }

    zxr10ethernetOamIfEnable	OBJECT-TYPE
		SYNTAX			INTEGER{disnable(0),enable(1)}
		MAX-ACCESS		read-write
		STATUS			current
		DESCRIPTION
		"Config Interface Ethernet oam enable."
		::=  {  zxr10ethernetOamIfConfigEntry  1  }

    zxr10ethernetOamRemoteLoopbackEnable	OBJECT-TYPE
		SYNTAX			INTEGER{disnable(0),enable(1)}
		MAX-ACCESS		read-write
		STATUS			current
		DESCRIPTION
		"Config Ethernet oam remote loopback start/stop."
		::=  {  zxr10ethernetOamIfConfigEntry  2  }

    zxr10ethernetOamifperiod	OBJECT-TYPE
		SYNTAX			Unsigned32(1..10)
		MAX-ACCESS		read-write
		STATUS			current
		DESCRIPTION
		"Config Ethernet oam period time."
		::=  {  zxr10ethernetOamIfConfigEntry  3  }

    zxr10ethernetOamifmode	OBJECT-TYPE
		SYNTAX			Unsigned32(0..1)
		MAX-ACCESS		read-write
		STATUS			current
		DESCRIPTION
		"Config Ethernet oam period mode."
		::=  {  zxr10ethernetOamIfConfigEntry  4  }

    zxr10ethernetOamiftimeout	OBJECT-TYPE
		SYNTAX			Unsigned32(2..20)
		MAX-ACCESS		read-write
		STATUS			current
		DESCRIPTION
		"Config Ethernet oam period timeout."
		::=  {  zxr10ethernetOamIfConfigEntry  5  }

    zxr10ethernetOamifLinkMonitorEnable	OBJECT-TYPE
		SYNTAX			INTEGER{disnable(0),enable(1)}
		MAX-ACCESS		read-write
		STATUS			current
		DESCRIPTION
		"Config link monitor enable."
		::=  {  zxr10ethernetOamIfConfigEntry  6  }

    zxr10ethernetOamifLinkMonitorSymbolPeriodthreshold	OBJECT-TYPE
		SYNTAX			Unsigned32(1..65535)
		MAX-ACCESS		read-write
		STATUS			current
		DESCRIPTION
		"Config link monitor Symbol-Period threshold."
		::=  {  zxr10ethernetOamIfConfigEntry  7  }

    zxr10ethernetOamifLinkMonitorSymbolPeriodwindow	OBJECT-TYPE
		SYNTAX			Unsigned32(1..65535)
		MAX-ACCESS		read-write
		STATUS			current
		DESCRIPTION
		"Config link monitor Symbol-Period window."
		::=  {  zxr10ethernetOamIfConfigEntry  8  }

    zxr10ethernetOamifLinkMonitorFramethreshold	OBJECT-TYPE
		SYNTAX			Unsigned32(1..65535)
		MAX-ACCESS		read-write
		STATUS			current
		DESCRIPTION
		"Config link monitor Frame threshold."
		::=  {  zxr10ethernetOamIfConfigEntry  9  }

    zxr10ethernetOamifLinkMonitorFramewindow	OBJECT-TYPE
		SYNTAX			Unsigned32(1..60)
		MAX-ACCESS		read-write
		STATUS			current
		DESCRIPTION
		"Config link monitor Frame window."
		::=  {  zxr10ethernetOamIfConfigEntry  10  }

    zxr10ethernetOamifLinkMonitorFramePeriodthreshold	OBJECT-TYPE
		SYNTAX			Unsigned32(1..65535)
		MAX-ACCESS		read-write
		STATUS			current
		DESCRIPTION
		"Config link monitor Frame-Period threshold."
		::=  {  zxr10ethernetOamIfConfigEntry  11  }

    zxr10ethernetOamifLinkMonitorFramePeriodwindow	OBJECT-TYPE
		SYNTAX			Unsigned32(1..600000)
		MAX-ACCESS		read-write
		STATUS			current
		DESCRIPTION
		"Config link monitor Frame-Period window."
		::=  {  zxr10ethernetOamIfConfigEntry  12  }

    zxr10ethernetOamifLinkMonitorFrameSecondsthreshold	OBJECT-TYPE
		SYNTAX			Unsigned32(1..900)
		MAX-ACCESS		read-write
		STATUS			current
		DESCRIPTION
		"Config link monitor Frame-Seconds threshold."
		::=  {  zxr10ethernetOamIfConfigEntry  13  }

    zxr10ethernetOamifLinkMonitorFrameSecondswindow	OBJECT-TYPE
		SYNTAX			Unsigned32(10..900)
		MAX-ACCESS		read-write
		STATUS			current
		DESCRIPTION
		"Config link monitor Frame-Seconds threshold."
		::=  {  zxr10ethernetOamIfConfigEntry  14  }

    zxr10ethernetOamifName	OBJECT-TYPE
		SYNTAX			DisplayString
		MAX-ACCESS		read-only
		STATUS			current
		DESCRIPTION
		"Show interface name."
		::=  {  zxr10ethernetOamIfConfigEntry  15  }

	zxr10ethernetOamShowTable	OBJECT-TYPE
		SYNTAX		SEQUENCE  OF  Zxr10ethernetOamShowEntry
		MAX-ACCESS	not-accessible
		STATUS		current
		DESCRIPTION
		"Show EthernetOam config parameters"
		::=  { zxr10ethernetOam 3 }

	zxr10ethernetOamShowEntry	OBJECT-TYPE
		SYNTAX		Zxr10ethernetOamShowEntry
		MAX-ACCESS	not-accessible
		STATUS		current
		DESCRIPTION
		     ""
		INDEX		{  ifIndex  }
		::=  { zxr10ethernetOamShowTable 1 }

	Zxr10ethernetOamShowEntry  ::=  SEQUENCE {
            zxr10ethernetOamShowDiscovery
                DisplayString,
            zxr10ethernetOamShowLinkMonitor
                DisplayString,
            zxr10ethernetOamShowStatistics
                DisplayString
     }

    zxr10ethernetOamShowDiscovery	OBJECT-TYPE
		SYNTAX			DisplayString
		MAX-ACCESS		read-only
		STATUS			current
		DESCRIPTION
		"Show ethernet oam Discovery."
		::=  {  zxr10ethernetOamShowEntry  1  }

   	zxr10ethernetOamShowLinkMonitor	OBJECT-TYPE
		SYNTAX			DisplayString
		MAX-ACCESS		read-only
		STATUS			current
		DESCRIPTION
		"Show ethernet oam Link Monitor."
		::=  {  zxr10ethernetOamShowEntry  2  }

    zxr10ethernetOamShowStatistics	OBJECT-TYPE
		SYNTAX			DisplayString
		MAX-ACCESS		read-only
		STATUS			current
		DESCRIPTION
		"Show ethernet oam Statistics."
		::=  {  zxr10ethernetOamShowEntry  3  }


	END
