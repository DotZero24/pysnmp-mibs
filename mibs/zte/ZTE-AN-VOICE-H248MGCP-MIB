--------------------------------------------------------------------------------
-- File Name : ZTE-AN-VOICE-H248MGCP-MIB.mib
-- Date      : 2010-08-24
-- Author    : ZTE NMS Dept.
--
-- ZTE Voice H.248/MGCP MIB for Access Node
--
--------------------------------------------------------------------------------


ZTE-AN-VOICE-H248MGCP-MIB DEFINITIONS ::= BEGIN

    IMPORTS
        MODULE-IDENTITY, NOTIFICATION-TYPE, OBJECT-TYPE, enterprises,
        IpAddress, Counter32, Integer32, Counter64, Unsigned32, Gauge32
                            FROM SNMPv2-SMI
        TEXTUAL-CONVENTION, MacAddress, DateAndTime, RowStatus, DisplayString,
        TruthValue          FROM SNMPv2-TC
        InetAddressType, InetAddress         FROM INET-ADDRESS-MIB;

    zxAnVoiceH248MgcpMib MODULE-IDENTITY
        LAST-UPDATED "201008241400Z"
        ORGANIZATION "ZTE Corporation"
        CONTACT-INFO "Fuhua
                      Mail: fu.hua@zte.com.cn
                      Tel : 021-68896250"
        DESCRIPTION  "The MIB module for the management of voice H.248/MGCP."
    ::= { zxAn 5200 }

    zte OBJECT IDENTIFIER ::= { enterprises 3902 }
    zxAn OBJECT IDENTIFIER ::= { zte 1015 }
    zxAnVoiceMgmt OBJECT IDENTIFIER ::= { zxAnVoiceH248MgcpMib 3 }
    zxAnH248MgcpConfig OBJECT IDENTIFIER ::= { zxAnVoiceMgmt 1 }

-------------------------------------------------------------------------------
-- Following objects are defined.
-- 1. zxAnMgCfgTable
-- 2. zxAnMgcCfgTable
-- 4. md5InfoTable
-- 5. zxAnSlcTermIDTable
-- 6. zxAnH248Perf
-- 7. zxAnH248MgcpGlobalObjects
-- 8. zxAnH248ProtocolTable
-- 9. zxAnMgcTypeTable
-- 10.zxAnMgcpConfig
-------------------------------------------------------------------------------

-------------------------------------------------------------------------------
-- 1. zxAnMgCfgTable
-------------------------------------------------------------------------------
    zxAnMgCfgTable OBJECT-TYPE
        SYNTAX      SEQUENCE OF ZxAnMgCfgEntry
        MAX-ACCESS  not-accessible
        STATUS      current
        DESCRIPTION
            "MG table."
        ::= { zxAnH248MgcpConfig 1110 }

    zxAnMgCfgEntry OBJECT-TYPE
        SYNTAX      ZxAnMgCfgEntry
        MAX-ACCESS  not-accessible
        STATUS      current
        DESCRIPTION
            "MG entry."
        INDEX { zxAnMgId }
        ::= { zxAnMgCfgTable 1 }

    ZxAnMgCfgEntry ::= SEQUENCE {
        zxAnMgId                        Integer32,
        zxAnMgProtocolType              INTEGER,
        zxAnMgCfgPort                   Integer32,
        zxAnMgCfgDomainName             DisplayString,
        zxAnMgDescription               DisplayString,
        zxAnMgNamingType                INTEGER,
        zxAnMgcId1                      Integer32,
        zxAnMgcId2                      Integer32,
        zxAnMgcId3                      Integer32,
        zxAnMgcId4                      Integer32,
        zxAnCurrentMgcId                Integer32,
        zxAnMgTranslay                  INTEGER,
        zxAnMgTransProtocol             INTEGER,
        zxAnTransactionNum              Integer32,
        zxAnRtpFaxPri1                  INTEGER,
        zxAnRtpFaxPri2                  INTEGER,
        zxAnSelfExchange                TruthValue,
        zxAnProtectCall                 TruthValue,
        zxAnRtp2833PayloadTypeCode      INTEGER,
        zxAnPacketMaxTransactionNumber  Integer32,
        zxAnHotlineWithSpace            INTEGER,
        zxAnAlwaysReportOffhookEvent    TruthValue,
        zxAnAlwaysReportOnhookEvent     TruthValue,
        zxAnSubSuspendRtp               TruthValue,
        zxAnDisasterProt                TruthValue,
        zxAnMgCfgRowStatus              RowStatus
        }

    zxAnMgId    OBJECT-TYPE
        SYNTAX      Integer32(1..3)
        MAX-ACCESS  not-accessible
        STATUS      current
        DESCRIPTION
            "MG ID."
        DEFVAL {1}
        ::={zxAnMgCfgEntry 1}

    zxAnMgProtocolType  OBJECT-TYPE
        SYNTAX      INTEGER {
            h248(1),
            mgcp(2)
            }
        MAX-ACCESS  read-create
        STATUS      deprecated
        DESCRIPTION
            "MG protocol type."
        DEFVAL {h248}
        ::={zxAnMgCfgEntry 2}

    zxAnMgCfgPort  OBJECT-TYPE
        SYNTAX      Integer32(0..65535)
        MAX-ACCESS  read-create
        STATUS      current
        DESCRIPTION
            "MG port."
        DEFVAL {2944}
        ::={zxAnMgCfgEntry 3}

    zxAnMgCfgDomainName OBJECT-TYPE
        SYNTAX      DisplayString(SIZE (0..32))
        MAX-ACCESS  read-create
        STATUS      current
        DESCRIPTION ""
        ::={zxAnMgCfgEntry 4}

    zxAnMgDescription   OBJECT-TYPE
        SYNTAX      DisplayString(SIZE (0..32))
        MAX-ACCESS  read-create
        STATUS      current
        DESCRIPTION
            "MG description."
        ::={zxAnMgCfgEntry 5}

    zxAnMgNamingType   OBJECT-TYPE
        SYNTAX      INTEGER {
            useIp(1),
            useDomainName(2)
        }
        MAX-ACCESS  read-create
        STATUS      current
        DESCRIPTION
            "MG naming type."
        DEFVAL { useIp }
        ::={zxAnMgCfgEntry 6}

    zxAnMgcId1  OBJECT-TYPE
        SYNTAX      Integer32(0..255)
        MAX-ACCESS  read-create
        STATUS      current
        DESCRIPTION
            "MGC ID 1."
        ::={zxAnMgCfgEntry 7}

    zxAnMgcId2  OBJECT-TYPE
        SYNTAX      Integer32(0..255)
        MAX-ACCESS  read-create
        STATUS      current
        DESCRIPTION
            "MGC ID 2."
        ::={zxAnMgCfgEntry 8}

    zxAnMgcId3  OBJECT-TYPE
        SYNTAX      Integer32(0..255)
        MAX-ACCESS  read-create
        STATUS      current
        DESCRIPTION
            "MGC ID 3."
        ::={zxAnMgCfgEntry 9}

    zxAnMgcId4  OBJECT-TYPE
        SYNTAX      Integer32(0..255)
        MAX-ACCESS  read-create
        STATUS      current
        DESCRIPTION
            "MGC ID 4."
        ::={zxAnMgCfgEntry 10}

    zxAnCurrentMgcId    OBJECT-TYPE
        SYNTAX      Integer32(1..255)
        MAX-ACCESS  read-create
        STATUS      current
        DESCRIPTION
            "Current MGC ID."
        ::={zxAnMgCfgEntry 11}

    zxAnMgTranslay  OBJECT-TYPE
        SYNTAX      INTEGER {
            ip(1),
            atm(2)
            }
        MAX-ACCESS  read-create
        STATUS      current
        DESCRIPTION
            ""
        DEFVAL {ip}
        ::={zxAnMgCfgEntry 12}

    zxAnMgTransProtocol OBJECT-TYPE
        SYNTAX      INTEGER {
            udp(1),
            tcp(2)
            }
        MAX-ACCESS  read-create
        STATUS      current
        DESCRIPTION
            ""
        DEFVAL {udp}
        ::={zxAnMgCfgEntry 13}

    zxAnTransactionNum  OBJECT-TYPE
        SYNTAX      Integer32(5000..7000)
        MAX-ACCESS  read-create
        STATUS      current
        DESCRIPTION
            ""
        DEFVAL {6000}
        ::={zxAnMgCfgEntry 14}

    zxAnRtpFaxPri1  OBJECT-TYPE
        SYNTAX      INTEGER {
            faxVbd(1),
            faxT38(2)
            }
        MAX-ACCESS  read-create
        STATUS      current
        DESCRIPTION
            ""
        DEFVAL {faxVbd}
        ::={zxAnMgCfgEntry 15}

    zxAnRtpFaxPri2  OBJECT-TYPE
        SYNTAX      INTEGER {
            faxVBD(1),
            faxT38(2)
            }
        MAX-ACCESS  read-create
        STATUS      current
        DESCRIPTION
            ""
        DEFVAL {faxT38}
        ::={zxAnMgCfgEntry 16}

    zxAnSelfExchange    OBJECT-TYPE
        SYNTAX      TruthValue
        MAX-ACCESS  read-create
        STATUS      current
        DESCRIPTION
            ""
        DEFVAL {false}
        ::={zxAnMgCfgEntry 17}

    zxAnProtectCall     OBJECT-TYPE
        SYNTAX      TruthValue
        MAX-ACCESS  read-create
        STATUS      current
        DESCRIPTION
            ""
        DEFVAL {false}
        ::={zxAnMgCfgEntry 18}

    zxAnRtp2833PayloadTypeCode     OBJECT-TYPE
        SYNTAX      INTEGER {
            negotiatedBySdp(1),
            specifiedByLocalRtpParameter(2)
            }
        MAX-ACCESS  read-create
        STATUS      current
        DESCRIPTION
            "RTP payload type code of sending DTMF digits
            using RFC2833 standard."
        DEFVAL { negotiatedBySdp }
        ::={zxAnMgCfgEntry 19}

    zxAnPacketMaxTransactionNumber  OBJECT-TYPE
        SYNTAX      Integer32(1..3)
        MAX-ACCESS  read-create
        STATUS      current
        DESCRIPTION
            "Maximum transaction number per packet."
        DEFVAL {1}
        ::={zxAnMgCfgEntry 20}

    zxAnHotlineWithSpace    OBJECT-TYPE
        SYNTAX      INTEGER {
            withoutSpace(1),
            withSpace(2),
            withT(3)
            }
        MAX-ACCESS  read-create
        STATUS      current
        DESCRIPTION
            ""
        DEFVAL {withoutSpace}
        ::={zxAnMgCfgEntry 21}

    zxAnAlwaysReportOffhookEvent     OBJECT-TYPE
        SYNTAX      TruthValue
        MAX-ACCESS  read-create
        STATUS      current
        DESCRIPTION
            "Reports Off-hook event to MGC,
             whether received MGC's command of report off-hook event or not."
        DEFVAL {true}
        ::={zxAnMgCfgEntry 22}

    zxAnAlwaysReportOnhookEvent      OBJECT-TYPE
        SYNTAX      TruthValue
        MAX-ACCESS  read-create
        STATUS      current
        DESCRIPTION
            "Reports On-hook event to MGC,
             whether received MGC's command of report on-hook event or not."
        DEFVAL {true}
        ::={zxAnMgCfgEntry 23}

    zxAnSubSuspendRtp   OBJECT-TYPE
        SYNTAX      TruthValue
        MAX-ACCESS  read-create
        STATUS      current
        DESCRIPTION
            ""
        DEFVAL {true}
        ::={zxAnMgCfgEntry 24}

    zxAnDisasterProt    OBJECT-TYPE
        SYNTAX      TruthValue
        MAX-ACCESS  read-create
        STATUS      current
        DESCRIPTION
            ""
        DEFVAL {true}
        ::={zxAnMgCfgEntry 25}

    zxAnMgCfgRowStatus  OBJECT-TYPE
        SYNTAX      RowStatus
        MAX-ACCESS  read-create
        STATUS      current
        DESCRIPTION
            "The row status of this entry."
        ::={zxAnMgCfgEntry 100}

-------------------------------------------------------------------------------
-- 2. zxAnMgcCfgTable
-------------------------------------------------------------------------------
    zxAnMgcCfgTable OBJECT-TYPE
        SYNTAX      SEQUENCE OF ZxAnMgcCfgEntry
        MAX-ACCESS  not-accessible
        STATUS      current
        DESCRIPTION
            "MGC config table."
        ::= { zxAnH248MgcpConfig 1102 }

    zxAnMgcCfgEntry OBJECT-TYPE
        SYNTAX      ZxAnMgcCfgEntry
        MAX-ACCESS  not-accessible
        STATUS      current
        DESCRIPTION
            "MGC config entry."
        INDEX { zxAnMgcId }
        ::= { zxAnMgcCfgTable 1 }

    ZxAnMgcCfgEntry::= SEQUENCE {
        zxAnMgcId           Integer32,
        zxAnMgcTypeId       INTEGER,
        zxAnMgcCfgPort      Integer32,
        zxAnMgcNamingType   INTEGER,
        zxAnMgcIpAddress    IpAddress,
        zxAnMgcDomainName   DisplayString,
        zxAnMgcMd5Id        Integer32,
        zxAnMgcDescription  DisplayString,
        zxAnMgcRowStatus    RowStatus
   }

    zxAnMgcId  OBJECT-TYPE
        SYNTAX      Integer32(1..9)
        MAX-ACCESS  not-accessible
        STATUS      current
        DESCRIPTION
            "MGC ID."
        ::={zxAnMgcCfgEntry 1}

    zxAnMgcTypeId   OBJECT-TYPE
        SYNTAX      INTEGER {
            zte(1),
            hw(2),
            cisco(3),
            alcatel(4),
            nortelMgcp(5),
            nortelH248(6),
            siemens(7),
            ericsson(8),
            metaswitch(9)
        }
        MAX-ACCESS  read-create
        STATUS      current
        DESCRIPTION
            "MGC type ID, which defined in zxAnMgcTypeTable."
        ::={zxAnMgcCfgEntry 2}

    zxAnMgcCfgPort  OBJECT-TYPE
        SYNTAX      Integer32(0..65535)
        MAX-ACCESS  read-create
        STATUS      current
        DESCRIPTION
            "MGC port."
        ::={zxAnMgcCfgEntry 3}

    zxAnMgcNamingType  OBJECT-TYPE
        SYNTAX      INTEGER {
            useIp(1),
            useDomainName(2)
        }
        MAX-ACCESS  read-create
        STATUS      current
        DESCRIPTION
            "MGC naming type."
        DEFVAL { useIp }
        ::={zxAnMgcCfgEntry 4}

    zxAnMgcIpAddress   OBJECT-TYPE
        SYNTAX      IpAddress
        MAX-ACCESS  read-create
        STATUS      current
        DESCRIPTION
            "MGC ip address."
        ::={zxAnMgcCfgEntry 5}

   zxAnMgcDomainName   OBJECT-TYPE
        SYNTAX      DisplayString(SIZE(0..32))
        MAX-ACCESS  read-create
        STATUS      current
        DESCRIPTION
            "MGC domain name."
        ::={zxAnMgcCfgEntry 6}

    zxAnMgcMd5Id  OBJECT-TYPE
        SYNTAX      Integer32(0..9)
        MAX-ACCESS  read-create
        STATUS      current
        DESCRIPTION
            "MGC MD5 ID.
             0 means that MD5 is not used."
        DEFVAL { 0 }
        ::={zxAnMgcCfgEntry 7}

     zxAnMgcDescription   OBJECT-TYPE
        SYNTAX      DisplayString(SIZE(0..32))
        MAX-ACCESS  read-create
        STATUS      current
        DESCRIPTION
            "MGC description."
        ::= { zxAnMgcCfgEntry 8 }

    zxAnMgcRowStatus   OBJECT-TYPE
        SYNTAX      RowStatus
        MAX-ACCESS  read-create
        STATUS      current
        DESCRIPTION
            "The row status of this entry."
        ::={zxAnMgcCfgEntry 30}


-------------------------------------------------------------------------------
-- 4. md5InfoTable
-------------------------------------------------------------------------------
   md5InfoTable OBJECT-TYPE
   SYNTAX       SEQUENCE OF Md5InfoEntry
   MAX-ACCESS   not-accessible
   STATUS       current
   DESCRIPTION  ""
   ::= { zxAnH248MgcpConfig 12 }

   md5InfoEntry OBJECT-TYPE
   SYNTAX       Md5InfoEntry
   MAX-ACCESS   not-accessible
   STATUS       current
   DESCRIPTION  ""
   INDEX {md5infoID}
   ::= { md5InfoTable 1 }

   Md5InfoEntry ::=
      SEQUENCE{
      md5infoID        INTEGER,
      md5infoG         INTEGER,
      md5infoKi        DisplayString,
      md5infoMginfo    DisplayString,
      md5infoPLenth    INTEGER,
      md5infoP         DisplayString,
      md5infoRowStatus RowStatus
   }

   md5infoID  OBJECT-TYPE
   SYNTAX    INTEGER(1..9)
   MAX-ACCESS  not-accessible
   STATUS    current
   DESCRIPTION  ""
  ::={md5InfoEntry 1}

   md5infoG  OBJECT-TYPE
   SYNTAX    INTEGER(1..10)
   MAX-ACCESS  read-create
   STATUS    current
   DESCRIPTION
       "Only five values are vaild:2,3,5,7,9."
  ::={md5InfoEntry 2}

   md5infoKi  OBJECT-TYPE
   SYNTAX    DisplayString(SIZE (1..16))
   MAX-ACCESS  read-create
   STATUS    current
   DESCRIPTION  ""
  ::={md5InfoEntry 3}

   md5infoMginfo  OBJECT-TYPE
   SYNTAX    DisplayString(SIZE (1..16))
   MAX-ACCESS  read-create
   STATUS    current
   DESCRIPTION  ""
  ::={md5InfoEntry 4}

   md5infoPLenth  OBJECT-TYPE
   SYNTAX    INTEGER(1..256)
   MAX-ACCESS  read-create
   STATUS    current
   DESCRIPTION
       "Only two values are valid:192,256."
  ::={md5InfoEntry 5}

   md5infoP  OBJECT-TYPE
   SYNTAX    DisplayString(SIZE (1..256))
   MAX-ACCESS  read-create
   STATUS    current
   DESCRIPTION
       "Only two size values are valid:192,256."
  ::={md5InfoEntry 6}

   md5infoRowStatus  OBJECT-TYPE
   SYNTAX    RowStatus
   MAX-ACCESS  read-create
   STATUS    current
   DESCRIPTION  ""
  ::={md5InfoEntry 7}

-------------------------------------------------------------------------------
-- 5. zxAnSlcTermIDTable
-------------------------------------------------------------------------------

   --msagChangeOidFromResouce OBJECT IDENTIFIER ::= { zxAnVoiceMgmt 3 }

    zxAnSlcTermIDTable OBJECT-TYPE
        SYNTAX      SEQUENCE OF ZxAnSlcTermIDEntry
        MAX-ACCESS  not-accessible
        STATUS      current
        DESCRIPTION ""
        ::= { zxAnH248MgcpConfig 1120 }

    zxAnSlcTermIDEntry OBJECT-TYPE
        SYNTAX      ZxAnSlcTermIDEntry
        MAX-ACCESS  not-accessible
        STATUS      current
        DESCRIPTION
            "describe colunms and index in TerminationIDOperation table"
        INDEX { zxAnSlcTermIDRackNo,zxAnSlcTermIDShelfNo,
                zxAnSlcTermIDSlotNo,zxAnSlcTermIDBeginIndex}
        ::= { zxAnSlcTermIDTable 1 }

    ZxAnSlcTermIDEntry ::= SEQUENCE {
        zxAnSlcTermIDRackNo       Integer32,
        zxAnSlcTermIDShelfNo      Integer32,
        zxAnSlcTermIDSlotNo       Integer32,
        zxAnSlcTermIDBeginIndex   INTEGER,
        zxAnSlcTermIDOperSum      INTEGER,
        zxAnSlcTermIDTMID         DisplayString,
        zxAnSlcTermIDType         INTEGER,
        zxAnSlcTermIDBeginNo      Integer32,
        zxAnSlcTermIDDigitLen     INTEGER,
        zxAnSlcTermIDMgId         INTEGER,
        zxAnSlcTerminationID      DisplayString,
        zxAnSlcTermIDRowStatus    RowStatus
        }

    zxAnSlcTermIDRackNo  OBJECT-TYPE
        SYNTAX      Integer32
        MAX-ACCESS  not-accessible
        STATUS      current
        DESCRIPTION ""
        ::= { zxAnSlcTermIDEntry 1 }

    zxAnSlcTermIDShelfNo OBJECT-TYPE
        SYNTAX      Integer32
        MAX-ACCESS  not-accessible
        STATUS      current
        DESCRIPTION  ""
        ::= { zxAnSlcTermIDEntry 2 }

    zxAnSlcTermIDSlotNo   OBJECT-TYPE
        SYNTAX      Integer32
        MAX-ACCESS  not-accessible
        STATUS      current
        DESCRIPTION ""
        ::= { zxAnSlcTermIDEntry 3 }

    zxAnSlcTermIDBeginIndex   OBJECT-TYPE
        SYNTAX      INTEGER(1..64)
        MAX-ACCESS  not-accessible
        STATUS      current
        DESCRIPTION ""
        ::= { zxAnSlcTermIDEntry 4 }

    zxAnSlcTermIDOperSum       OBJECT-TYPE
        SYNTAX      INTEGER(1..192)
        MAX-ACCESS  read-create
        STATUS      current
        DESCRIPTION ""
        ::= { zxAnSlcTermIDEntry 5 }

    zxAnSlcTermIDTMID  OBJECT-TYPE
        SYNTAX      DisplayString(SIZE (1..64))
        MAX-ACCESS  read-create
        STATUS      current
        DESCRIPTION ""
        ::= { zxAnSlcTermIDEntry 6 }

    zxAnSlcTermIDType  OBJECT-TYPE
        SYNTAX      INTEGER{
            type1(1),
            type2(2),
            type3(3)
            }
        MAX-ACCESS  read-create
        STATUS      current
        DESCRIPTION
            "Type 1:USER00100100000-USER00100100031,
             type 2:USER0-USER31
             type 3:User000-USER031"
        ::= { zxAnSlcTermIDEntry 7 }

    zxAnSlcTermIDBeginNo  OBJECT-TYPE
        SYNTAX      Integer32
        MAX-ACCESS  read-create
        STATUS      current
        DESCRIPTION
            "Use for type 2 and 3"
        ::= { zxAnSlcTermIDEntry 8 }

    zxAnSlcTermIDDigitLen    OBJECT-TYPE
        SYNTAX      INTEGER(0..63)
        MAX-ACCESS  read-create
        STATUS      current
        DESCRIPTION ""
        ::= { zxAnSlcTermIDEntry 9 }

    zxAnSlcTermIDMgId       OBJECT-TYPE
        SYNTAX      INTEGER(1..255)
        MAX-ACCESS  read-create
        STATUS      current
        DESCRIPTION ""
        ::= { zxAnSlcTermIDEntry 11 }

    zxAnSlcTerminationID    OBJECT-TYPE
        SYNTAX      DisplayString(SIZE (1..64))
        MAX-ACCESS  read-only
        STATUS      current
        DESCRIPTION ""
        ::= { zxAnSlcTermIDEntry 12 }

    zxAnSlcTermIDRowStatus  OBJECT-TYPE
        SYNTAX      RowStatus
        MAX-ACCESS  read-create
        STATUS      current
        DESCRIPTION
            "insert,delete"
        ::= { zxAnSlcTermIDEntry 13 }

-------------------------------------------------------------------------------
-- 6. zxAnH248Perf
-------------------------------------------------------------------------------

    --msagChangeOidFromCallCtrl OBJECT IDENTIFIER ::= { zxAnVoiceMgmt 6 }
    --msagH248Perform  OBJECT IDENTIFIER ::= { msagChangeOidFromCallCtrl 6 }
    zxAnH248Perf  OBJECT IDENTIFIER ::= { zxAnH248MgcpConfig 1170 }

    zxAnH248PSRecMsg    OBJECT-TYPE
        SYNTAX      Integer32
        MAX-ACCESS  read-only
        STATUS      current
        DESCRIPTION ""
        ::= { zxAnH248Perf 1 }

    zxAnH248PSSendMsg    OBJECT-TYPE
        SYNTAX      Integer32
        MAX-ACCESS  read-only
        STATUS      current
        DESCRIPTION ""
        ::= { zxAnH248Perf 2 }

    zxAnH248PSRecMsgByte    OBJECT-TYPE
        SYNTAX      Integer32
        MAX-ACCESS  read-only
        STATUS      current
        DESCRIPTION ""
        ::= { zxAnH248Perf 3 }

    zxAnH248PSSendMsgByte    OBJECT-TYPE
        SYNTAX      Integer32
        MAX-ACCESS  read-only
        STATUS      current
        DESCRIPTION ""
        ::= { zxAnH248Perf 4 }

    zxAnH248PSProtocolError    OBJECT-TYPE
        SYNTAX      Integer32
        MAX-ACCESS  read-only
        STATUS      current
        DESCRIPTION ""
        ::= { zxAnH248Perf 5 }

    zxAnH248PSTimerOut    OBJECT-TYPE
        SYNTAX      Integer32
        MAX-ACCESS  read-only
        STATUS      current
        DESCRIPTION ""
        ::= { zxAnH248Perf 6 }

    zxAnH248PSDisconnect    OBJECT-TYPE
        SYNTAX      Integer32
        MAX-ACCESS  read-only
        STATUS      current
        DESCRIPTION ""
        ::= { zxAnH248Perf 7 }

    zxAnH248PSMGCChange    OBJECT-TYPE
        SYNTAX      Integer32
        MAX-ACCESS  read-only
        STATUS      current
        DESCRIPTION ""
        ::= { zxAnH248Perf 8 }

    zxAnH248PSTransmitError    OBJECT-TYPE
        SYNTAX      Integer32
        MAX-ACCESS  read-only
        STATUS      current
        DESCRIPTION ""
        ::= { zxAnH248Perf 9 }

--------------------------------------------------------------------------------
-- 7. zxAnH248MgcpGlobalObjects
--------------------------------------------------------------------------------

    zxAnH248MgcpGlobalObjects OBJECT IDENTIFIER ::= { zxAnH248MgcpConfig 1100 }

    zxAnH248MgcpMgmtCapabilities OBJECT-TYPE
        SYNTAX      BITS {
            nbPlatform(0)
            }
        MAX-ACCESS  read-only
        STATUS      current
        DESCRIPTION
            "The h248/mgcp management capabilities of this equipment.
            The bit value 1 means the function represented by this bit is
            supported by this equipment.
            bit 1: value 1 means support narrowband platform.
            NOTE: No recommended to display it in NMS."
        ::= { zxAnH248MgcpGlobalObjects 1 }

    zxAnH248MgcpLinkStatus OBJECT-TYPE
        SYNTAX      INTEGER {
            normal(1),
            broken(2)
            }
        MAX-ACCESS  read-only
        STATUS      current
        DESCRIPTION
            "The link status between MG and MGC,
             using H.248 protocol or MGCP protocol."
        ::= { zxAnH248MgcpGlobalObjects 2 }

--------------------------------------------------------------------------------
-- 8. zxAnH248ProtocolTable
--------------------------------------------------------------------------------
    zxAnH248ProtocolTable OBJECT-TYPE
        SYNTAX      SEQUENCE OF ZxAnH248ProtocolEntry
        MAX-ACCESS  not-accessible
        STATUS      current
        DESCRIPTION
            "H.248 protocol table."
        ::= { zxAnH248MgcpConfig 1111 }

    zxAnH248ProtocolEntry OBJECT-TYPE
        SYNTAX      ZxAnH248ProtocolEntry
        MAX-ACCESS  not-accessible
        STATUS      current
        DESCRIPTION
            "H.248 protocol entry."
        INDEX { zxAnH248ProtocolMgId }
        ::={zxAnH248ProtocolTable 1}

    ZxAnH248ProtocolEntry ::= SEQUENCE {
        zxAnH248ProtocolMgId            Integer32,
        zxAnH248ProtocolVersion         INTEGER,
        zxAnH248EncodingType            INTEGER,
        zxAnH248PacketTokenAbbreviated  TruthValue,
        zxAnH248MinTransactionId        Integer32,
        zxAnH248MaxTransactionId        Integer32,
        zxAnH248SendResponseAck         TruthValue,
        zxAnH248ResponseCacheTime       Integer32,
        zxAnH248SendTransactionPending  TruthValue,
        zxAnH248ProfileNegotiation      TruthValue,
        zxAnH248RebootMaxWaitingDelay   Integer32,
        zxAnH248MgcMaxInactivityTime    Integer32,
        zxAnH248TranRetranMode          INTEGER,
        zxAnH248TranRetranInterval      Integer32,
        zxAnH248TranMaxRetries          Integer32,
        zxAnH248TranPendInterval        Integer32,
        zxAnH248TranPendLimit           Integer32,
        zxAnH248HeartbeatMechanism      INTEGER,
        zxAnH248MgcHbMaxInactivityTime  Integer32,
        zxAnH248HeartbeatFormat         INTEGER,
        zxAnH248HbRetranInterval        Integer32,
        zxAnH248HbMaxRetries            Integer32
        }

    zxAnH248ProtocolMgId  OBJECT-TYPE
        SYNTAX      Integer32(1..3)
        MAX-ACCESS  not-accessible
        STATUS      current
        DESCRIPTION
            "MG ID."
        DEFVAL { 1 }
        ::= { zxAnH248ProtocolEntry 1 }

    zxAnH248ProtocolVersion  OBJECT-TYPE
        SYNTAX      INTEGER {
            v1(1),
            v2(2),
            v3(3)
        }
        MAX-ACCESS  read-write
        STATUS      current
        DESCRIPTION
            "H.248 protocol version."
        DEFVAL { v1 }
        ::= { zxAnH248ProtocolEntry 2 }

    zxAnH248EncodingType  OBJECT-TYPE
        SYNTAX      INTEGER {
            text(1),
            binary(2)
        }
        MAX-ACCESS  read-write
        STATUS      current
        DESCRIPTION
            "H.248 protocol encoding type."
        DEFVAL { text }
        ::= { zxAnH248ProtocolEntry 3 }

    zxAnH248PacketTokenAbbreviated  OBJECT-TYPE
        SYNTAX      TruthValue
        MAX-ACCESS  read-write
        STATUS      current
        DESCRIPTION
            "H.248 packet token is abbreviated or not."
        DEFVAL { true }
        ::= { zxAnH248ProtocolEntry 4 }

    zxAnH248MinTransactionId  OBJECT-TYPE
        SYNTAX      Integer32(0..6000)
        MAX-ACCESS  read-write
        STATUS      current
        DESCRIPTION
            "Minimum transaction ID."
        DEFVAL { 0 }
        ::= { zxAnH248ProtocolEntry 5 }

    zxAnH248MaxTransactionId  OBJECT-TYPE
        SYNTAX      Integer32(0..429496729)
        MAX-ACCESS  read-write
        STATUS      current
        DESCRIPTION
            "Maximum Transaction ID."
        DEFVAL { 8000 }
        ::= { zxAnH248ProtocolEntry 6 }

    zxAnH248SendResponseAck  OBJECT-TYPE
        SYNTAX      TruthValue
        MAX-ACCESS  read-write
        STATUS      current
        DESCRIPTION
            "If transaction reply received,
             response acknowledge is sent or not."
        DEFVAL { true }
        ::= { zxAnH248ProtocolEntry 7 }

    zxAnH248ResponseCacheTime  OBJECT-TYPE
        SYNTAX      Integer32(0..30)
        UNITS       "second"
        MAX-ACCESS  read-write
        STATUS      current
        DESCRIPTION
            "The time of reply saved in cache.
             If same request received, MG will find reply from cache firstly."
        DEFVAL { 12 }
        ::= { zxAnH248ProtocolEntry 8 }

    zxAnH248SendTransactionPending  OBJECT-TYPE
        SYNTAX      TruthValue
        MAX-ACCESS  read-write
        STATUS      current
        DESCRIPTION
            "During processing a transaction,
             transaction pending is sent or not."
        DEFVAL { true }
        ::= { zxAnH248ProtocolEntry 9 }

    zxAnH248ProfileNegotiation  OBJECT-TYPE
        SYNTAX      TruthValue
        MAX-ACCESS  read-write
        STATUS      current
        DESCRIPTION
            "Profile name and profile version can be changed with MGC or not."
        DEFVAL { false }
        ::= { zxAnH248ProtocolEntry 10 }

    zxAnH248RebootMaxWaitingDelay  OBJECT-TYPE
        SYNTAX      Integer32(10..600)
        UNITS       "second"
        MAX-ACCESS  read-write
        STATUS      current
        DESCRIPTION
            "Maximum waiting delay of MG connecting to MGC after reboot."
        DEFVAL { 1 }
        ::= { zxAnH248ProtocolEntry 11 }

    zxAnH248MgcMaxInactivityTime  OBJECT-TYPE
        SYNTAX      Integer32(20..300)
        UNITS       "second"
        MAX-ACCESS  read-write
        STATUS      current
        DESCRIPTION
            "The allowable time of no packet received from MGC."
        DEFVAL { 1 }
        ::= { zxAnH248ProtocolEntry 12 }

    zxAnH248TranRetranMode  OBJECT-TYPE
        SYNTAX      INTEGER {
            fixedInteval(1),
            exponentialGrowthInteval(2)
        }
        MAX-ACCESS  read-write
        STATUS      current
        DESCRIPTION
            "Transaction retransmission mode.
             fixedInteval(1) means that request will be retransmitted
             every fixed interval (the value is defined by
             zxAnH248TranRetranInterval) if no reply received after
             sending request.
             exponentialGrowthInteval(2) means the retransmission interval
             will exponentially grow."
        DEFVAL { exponentialGrowthInteval }
        ::= { zxAnH248ProtocolEntry 13 }

    zxAnH248TranRetranInterval  OBJECT-TYPE
        SYNTAX      Integer32(2..10)
        UNITS       "second"
        MAX-ACCESS  read-write
        STATUS      current
        DESCRIPTION
            "Transaction retransmission interval.
            If no reply received after sending request,
            MG will retransmit request."
        DEFVAL { 4 }
        ::= { zxAnH248ProtocolEntry 14 }

    zxAnH248TranMaxRetries  OBJECT-TYPE
        SYNTAX      Integer32(2..10)
        MAX-ACCESS  read-write
        STATUS      current
        DESCRIPTION
            "The maximum retransmission number of sending a transaction
             request."
        DEFVAL { 3 }
        ::= { zxAnH248ProtocolEntry 15 }

    zxAnH248TranPendInterval  OBJECT-TYPE
        SYNTAX      Integer32(2..8)
        UNITS       "second"
        MAX-ACCESS  read-write
        STATUS      current
        DESCRIPTION
            "The interval of sending transaction pending."
        DEFVAL { 4 }
        ::= { zxAnH248ProtocolEntry 16 }

    zxAnH248TranPendLimit  OBJECT-TYPE
        SYNTAX      Integer32(20..40)
        MAX-ACCESS  read-write
        STATUS      current
        DESCRIPTION
            "The maximum number of transactions pending that can be sent."
        DEFVAL { 30 }
        ::= { zxAnH248ProtocolEntry 17 }

    zxAnH248HeartbeatMechanism  OBJECT-TYPE
        SYNTAX      INTEGER {
            controlByMgc(1),
            controlByMg(2)
        }
        MAX-ACCESS  read-write
        STATUS      current
        DESCRIPTION
            "H248 heartbeat mechanism.
             controlByMgc(1) means MGC sending heartbeat packet,
             controlByMg(2) means MG sending heartbeat packet."
        DEFVAL { controlByMg }
        ::= { zxAnH248ProtocolEntry 18 }

    zxAnH248MgcHbMaxInactivityTime  OBJECT-TYPE
        SYNTAX      Integer32(0..600)
        UNITS       "second"
        MAX-ACCESS  read-write
        STATUS      current
        DESCRIPTION
            "The allowable time of no heartbeat packet received from MGC.
             Only used when zxAnH248HeartbeatMechanism is controlWithMgc(2)."
        DEFVAL { 0 }
        ::= { zxAnH248ProtocolEntry 19 }

    zxAnH248HeartbeatFormat  OBJECT-TYPE
        SYNTAX      INTEGER {
            sv(1),
            itito(2)
        }
        MAX-ACCESS  read-write
        STATUS      current
        DESCRIPTION
            "The heartbeat packet's format."
        DEFVAL { sv }
        ::= { zxAnH248ProtocolEntry 20 }

    zxAnH248HbRetranInterval  OBJECT-TYPE
        SYNTAX      Integer32(1..100)
       UNITS        "second"
        MAX-ACCESS  read-write
        STATUS      current
        DESCRIPTION
            "Heartbeat retransmission interval."
        DEFVAL { 100 }
        ::= { zxAnH248ProtocolEntry 21 }

    zxAnH248HbMaxRetries  OBJECT-TYPE
        SYNTAX      Integer32(2..10)
        MAX-ACCESS  read-write
        STATUS      current
        DESCRIPTION
            "The maximum retransmission number of sending heartbeat packet
             without reply received."
        DEFVAL { 3 }
        ::= { zxAnH248ProtocolEntry 22 }

--------------------------------------------------------------------------------
-- 9. zxAnMgcTypeTable
--------------------------------------------------------------------------------
    zxAnMgcTypeTable OBJECT-TYPE
        SYNTAX      SEQUENCE OF ZxAnMgcTypeEntry
        MAX-ACCESS  not-accessible
        STATUS      current
        DESCRIPTION
            "MGC type table."
        ::= { zxAnH248MgcpConfig 1101 }

    zxAnMgcTypeEntry OBJECT-TYPE
        SYNTAX      ZxAnMgcTypeEntry
        MAX-ACCESS  not-accessible
        STATUS      current
        DESCRIPTION
            "MGC type entry."
        INDEX { zxAnMgcType }
        ::= { zxAnMgcTypeTable 1 }

    ZxAnMgcTypeEntry ::= SEQUENCE {
        zxAnMgcType                     INTEGER,
        --zxAnMgcNamingType               INTEGER,
        --zxAnMgcMd5Id                    Integer32,
        zxAnMgcRegPktWithAddress        TruthValue,
        zxAnMgcRegPktWithVersion        TruthValue,
        zxAnMgcRegPktWithDelay          TruthValue,
        zxAnMgcRegPktWithProfile        TruthValue,
        zxAnMgcRegPktWithTimeStamp      TruthValue,
        zxAnMgcRegPktWithReason         TruthValue,
        zxAnMgcRegPktBraceDblQuotation  TruthValue,
        zxAnMgcRegPktMethod             INTEGER,
        zxAnMgcRegPktVersion            Integer32,
        zxAnMgcRegPktDelay              Integer32,
        zxAnMgcRegPktProfile            DisplayString,
        zxAnMgcRegPktReason             Integer32
        }

    zxAnMgcType    OBJECT-TYPE
        SYNTAX      INTEGER {
            zte(1),
            hw(2),
            cisco(3),
            alcatel(4),
            nortelMgcp(5),
            nortelH248(6),
            siemens(7),
            ericsson(8),
            metaswitch(9)
        }
        MAX-ACCESS  not-accessible
        STATUS      current
        DESCRIPTION
            "MGC type."
        ::= { zxAnMgcTypeEntry 1 }

    zxAnMgcRegPktWithAddress  OBJECT-TYPE
        SYNTAX      TruthValue
        MAX-ACCESS  read-write
        STATUS      current
        DESCRIPTION
            "Whether H.248 register packet is attached with keyword AD(address)
             or not."
        DEFVAL { true }
        ::= { zxAnMgcTypeEntry 4 }

    zxAnMgcRegPktWithVersion  OBJECT-TYPE
        SYNTAX      TruthValue
        MAX-ACCESS  read-write
        STATUS      current
        DESCRIPTION
            "Whether H.248 register packet is attached with keyword V(version)
             or not."
        DEFVAL { true }
        ::= { zxAnMgcTypeEntry 5 }

    zxAnMgcRegPktWithDelay  OBJECT-TYPE
        SYNTAX      TruthValue
        MAX-ACCESS  read-write
        STATUS      current
        DESCRIPTION
            "Whether H.248 register packet is attached with keyword DL(delay)
             or not."
        DEFVAL { false }
        ::= { zxAnMgcTypeEntry 6 }

    zxAnMgcRegPktWithProfile  OBJECT-TYPE
        SYNTAX      TruthValue
        MAX-ACCESS  read-write
        STATUS      current
        DESCRIPTION
            "Whether H.248 register packet is attached with keyword PF(profile)
             or not."
        DEFVAL { true }
        ::= { zxAnMgcTypeEntry 7 }

    zxAnMgcRegPktWithTimeStamp  OBJECT-TYPE
        SYNTAX      TruthValue
        MAX-ACCESS  read-write
        STATUS      current
        DESCRIPTION
            "Whether H.248 register packet is attached with keyword TimeStamp
             or not."
        DEFVAL { false }
        ::= { zxAnMgcTypeEntry 8 }

    zxAnMgcRegPktWithReason  OBJECT-TYPE
        SYNTAX      TruthValue
        MAX-ACCESS  read-write
        STATUS      current
        DESCRIPTION
            "Whether H.248 register packet is attached with keyword RE(reason)
             or not."
        DEFVAL { true }
        ::= { zxAnMgcTypeEntry 9 }

    zxAnMgcRegPktBraceDblQuotation  OBJECT-TYPE
        SYNTAX      TruthValue
        MAX-ACCESS  read-write
        STATUS      current
        DESCRIPTION
            "Whether H.248 register packet's value field is braced by
             double quotation masks or not."
        DEFVAL { false }
        ::= { zxAnMgcTypeEntry 10 }

    zxAnMgcRegPktMethod  OBJECT-TYPE
        SYNTAX      INTEGER {
            failover(1),
            restart(2),
            graceful(3),
            forced(4),
            disconnected(5),
            handoff(6)
        }
        MAX-ACCESS  read-write
        STATUS      current
        DESCRIPTION
            "Defined the value of H.248 register packet's keyword MT(method)."
        DEFVAL { restart }
        ::= { zxAnMgcTypeEntry 11 }

    zxAnMgcRegPktVersion  OBJECT-TYPE
        SYNTAX      Integer32(1..3)
        MAX-ACCESS  read-write
        STATUS      current
        DESCRIPTION
            "Defined the value of H.248 register packet's keyword V(version).
             Valid only zxAnMgcRegPktWithVersion is true."
        DEFVAL { 1 }
        ::= { zxAnMgcTypeEntry 12 }

    zxAnMgcRegPktDelay  OBJECT-TYPE
        SYNTAX      Integer32(0..65535)
        MAX-ACCESS  read-write
        STATUS      current
        DESCRIPTION
            "Defined the value of H.248 register packet's keyword DL(delay).
             Valid only zxAnMgcRegPktWithDelay is true."
        DEFVAL { 0 }
        ::= { zxAnMgcTypeEntry 13 }

    zxAnMgcRegPktProfile  OBJECT-TYPE
        SYNTAX      DisplayString(SIZE (0..10))
        MAX-ACCESS  read-write
        STATUS      current
        DESCRIPTION
            "Defined the value of H.248 register packet's keyword PF(profile).
             Valid only zxAnMgcRegPktWithProfile is true."
        ::= { zxAnMgcTypeEntry 14 }

    zxAnMgcRegPktReason  OBJECT-TYPE
        SYNTAX      Integer32(900..903)
        MAX-ACCESS  read-write
        STATUS      current
        DESCRIPTION
            "Defined the value of H.248 register packet's keyword RE(reason).
             Valid only zxAnMgcRegPktWithReason is true."
        DEFVAL { 901 }
        ::= { zxAnMgcTypeEntry 15 }

-------------------------------------------------------------------------------
-- 10. zxAnMgcpConfig
-------------------------------------------------------------------------------
    zxAnMgcpConfig  OBJECT IDENTIFIER ::= { zxAnH248MgcpConfig 1150 }
-------------------------------------------------------------------------------
-- 1.zxAnMgcpMgcCfgTable
-------------------------------------------------------------------------------
    zxAnMgcpMgcCfgTable OBJECT-TYPE
        SYNTAX      SEQUENCE OF ZxAnMgcpMgcCfgEntry
        MAX-ACCESS  not-accessible
        STATUS      current
        DESCRIPTION
            "MGC config table."
        ::= { zxAnMgcpConfig 1 }

    zxAnMgcpMgcCfgEntry OBJECT-TYPE
        SYNTAX      ZxAnMgcpMgcCfgEntry
        MAX-ACCESS  not-accessible
        STATUS      current
        DESCRIPTION
            "MGC config entry."
        INDEX { zxAnMgcpMgcId }
        ::= { zxAnMgcpMgcCfgTable 1 }

    ZxAnMgcpMgcCfgEntry ::= SEQUENCE {
        zxAnMgcpMgcId                   Integer32,
        zxAnMgcpMgcTypeId               INTEGER,
        zxAnMgcpMgcPort                 Integer32,
        zxAnMgcpMgcIpAddrType           InetAddressType,
        zxAnMgcpMgcIpAddress            InetAddress,
        zxAnMgcpMgcDomainName           DisplayString,
        zxAnMgcpMgcDescription          DisplayString,
        zxAnMgcpMgcRowStatus            RowStatus
        }

    zxAnMgcpMgcId  OBJECT-TYPE
        SYNTAX      Integer32(1..12)
        MAX-ACCESS  not-accessible
        STATUS      current
        DESCRIPTION
            "MGC ID."
        DEFVAL { 1 }
        ::= { zxAnMgcpMgcCfgEntry 1 }

    zxAnMgcpMgcTypeId    OBJECT-TYPE
        SYNTAX      INTEGER {
            zte(1),
            hw(2),
            cisco(3),
            alcatel(4),
            nortelMgcp(5),
            siemens(7)
        }
        MAX-ACCESS  read-create
        STATUS      current
        DESCRIPTION
            "MGC type ID, which defined in zxAnMgcTypeTable."
        ::= { zxAnMgcpMgcCfgEntry 2 }

    zxAnMgcpMgcPort  OBJECT-TYPE
        SYNTAX      Integer32(0..65535)
        MAX-ACCESS  read-create
        STATUS      current
        DESCRIPTION
            "MGC port."
        DEFVAL {2727}
        ::={zxAnMgcpMgcCfgEntry 3}

    zxAnMgcpMgcIpAddrType  OBJECT-TYPE
        SYNTAX          InetAddressType
        MAX-ACCESS      read-create
        STATUS          current
        DESCRIPTION
            "IP address type of the MGC IP address."
        DEFVAL  { ipv4 }
        ::=  {  zxAnMgcpMgcCfgEntry  4  }

    zxAnMgcpMgcIpAddress   OBJECT-TYPE
        SYNTAX      InetAddress
        MAX-ACCESS  read-create
        STATUS      current
        DESCRIPTION
            "MGC IP address."
        ::={zxAnMgcpMgcCfgEntry 5}

    zxAnMgcpMgcDomainName OBJECT-TYPE
        SYNTAX      DisplayString(SIZE (0..80))
        MAX-ACCESS  read-create
        STATUS      current
        DESCRIPTION
            "MGC domain name."
        ::={zxAnMgcpMgcCfgEntry 6}

    zxAnMgcpMgcDescription   OBJECT-TYPE
        SYNTAX      DisplayString(SIZE (0..32))
        MAX-ACCESS  read-create
        STATUS      current
        DESCRIPTION
            "MGC description."
        ::={zxAnMgcpMgcCfgEntry 7}

    zxAnMgcpMgcRowStatus  OBJECT-TYPE
        SYNTAX      RowStatus
        MAX-ACCESS  read-create
        STATUS      current
        DESCRIPTION
            "The row status of this entry."
        ::={zxAnMgcpMgcCfgEntry 100}
-------------------------------------------------------------------------------
-- 2.zxAnMgcpMgCfgTable
-------------------------------------------------------------------------------
    zxAnMgcpMgCfgTable OBJECT-TYPE
        SYNTAX      SEQUENCE OF ZxAnMgcpMgCfgEntry
        MAX-ACCESS  not-accessible
        STATUS      current
        DESCRIPTION
            "MG config table."
        ::= { zxAnMgcpConfig 2 }

    zxAnMgcpMgCfgEntry OBJECT-TYPE
        SYNTAX      ZxAnMgcpMgCfgEntry
        MAX-ACCESS  not-accessible
        STATUS      current
        DESCRIPTION
            "MG config entry."
        INDEX { zxAnMgcpMgId }
        ::= { zxAnMgcpMgCfgTable 1 }

    ZxAnMgcpMgCfgEntry ::= SEQUENCE {
        zxAnMgcpMgId                    Integer32,
        zxAnMgcpMgPort                  Integer32,
        zxAnMgcpMgDomainName            DisplayString,
        zxAnMgcpMgDescription           DisplayString,
        zxAnMgcpMgcId1                  Integer32,
        zxAnMgcpMgcId2                  Integer32,
        zxAnMgcpMgcId3                  Integer32,
        zxAnMgcpMgcId4                  Integer32,
        zxAnMgcpRtpFaxPri1              INTEGER,
        zxAnMgcpRtpFaxPri2              INTEGER,
        zxAnMgcpMgSelfSwitch            INTEGER,
        zxAnMgcpMgProtectCall           INTEGER,
        zxAnMgcpMgRtp2833Type           INTEGER,
        zxAnMgcpMgRowStatus             RowStatus
        }

    zxAnMgcpMgId    OBJECT-TYPE
        SYNTAX      Integer32(1..3)
        MAX-ACCESS  not-accessible
        STATUS      current
        DESCRIPTION
            "MG ID."
        DEFVAL {1}
        ::={zxAnMgcpMgCfgEntry 1}

    zxAnMgcpMgPort  OBJECT-TYPE
        SYNTAX      Integer32(0..65535)
        MAX-ACCESS  read-create
        STATUS      current
        DESCRIPTION
            "MG port."
        DEFVAL {2427}
        ::={zxAnMgcpMgCfgEntry 2}

    zxAnMgcpMgDomainName OBJECT-TYPE
        SYNTAX      DisplayString(SIZE (0..80))
        MAX-ACCESS  read-create
        STATUS      current
        DESCRIPTION "MG domain name."
        ::={zxAnMgcpMgCfgEntry 3}

    zxAnMgcpMgDescription   OBJECT-TYPE
        SYNTAX      DisplayString(SIZE (0..32))
        MAX-ACCESS  read-create
        STATUS      current
        DESCRIPTION
            "MG description."
        ::={zxAnMgcpMgCfgEntry 4}

    zxAnMgcpMgcId1  OBJECT-TYPE
        SYNTAX      Integer32(0..12)
        MAX-ACCESS  read-create
        STATUS      current
        DESCRIPTION
            "MGC ID 1."
        DEFVAL {1}
        ::={zxAnMgcpMgCfgEntry 5}

    zxAnMgcpMgcId2  OBJECT-TYPE
        SYNTAX      Integer32(0..12)
        MAX-ACCESS  read-create
        STATUS      current
        DESCRIPTION
            "MGC ID 2."
        DEFVAL {0}
        ::={zxAnMgcpMgCfgEntry 6}

    zxAnMgcpMgcId3  OBJECT-TYPE
        SYNTAX      Integer32(0..12)
        MAX-ACCESS  read-create
        STATUS      current
        DESCRIPTION
            "MGC ID 3."
        DEFVAL {0}
        ::={zxAnMgcpMgCfgEntry 7}

    zxAnMgcpMgcId4  OBJECT-TYPE
        SYNTAX      Integer32(0..12)
        MAX-ACCESS  read-create
        STATUS      current
        DESCRIPTION
            "MGC ID 4."
        DEFVAL {0}
        ::={zxAnMgcpMgCfgEntry 8}

    zxAnMgcpRtpFaxPri1  OBJECT-TYPE
        SYNTAX      INTEGER {
            faxVbd(1),
            faxT38(2)
            }
        MAX-ACCESS  read-create
        STATUS      current
        DESCRIPTION
            "Fax priority 1."
        DEFVAL {faxVbd}
        ::={zxAnMgcpMgCfgEntry 9}

    zxAnMgcpRtpFaxPri2  OBJECT-TYPE
        SYNTAX      INTEGER {
            faxVbd(1),
            faxT38(2)
            }
        MAX-ACCESS  read-create
        STATUS      current
        DESCRIPTION
            "Fax priority 2."
        DEFVAL {faxT38}
        ::={zxAnMgcpMgCfgEntry 10}

    zxAnMgcpMgSelfSwitch    OBJECT-TYPE
        SYNTAX      INTEGER {
            enable(1),
            disable(2)
            }
        MAX-ACCESS  read-create
        STATUS      current
        DESCRIPTION
            "Self Switch."
        DEFVAL {disable}
        ::={zxAnMgcpMgCfgEntry 11}

    zxAnMgcpMgProtectCall     OBJECT-TYPE
        SYNTAX      INTEGER {
            enable(1),
            disable(2)
            }
        MAX-ACCESS  read-create
        STATUS      current
        DESCRIPTION
            "This value depends on zxAnMgcpMgSelfSwitch.
             enable(1):It will Protect call when the control exchange."
        DEFVAL {disable}
        ::={zxAnMgcpMgCfgEntry 12}

    zxAnMgcpMgRtp2833Type     OBJECT-TYPE
        SYNTAX      INTEGER {
            type2833Redun(1),
            typeRtp(2)
        }
        MAX-ACCESS  read-create
        STATUS      current
        DESCRIPTION
            "type2833Redun(1):RFC2833.
             typeRtp(2):Transparent transmission."
        DEFVAL {type2833Redun}
        ::={zxAnMgcpMgCfgEntry 13}

    zxAnMgcpMgRowStatus  OBJECT-TYPE
        SYNTAX      RowStatus
        MAX-ACCESS  read-create
        STATUS      current
        DESCRIPTION
            "The row status of this entry."
        ::={zxAnMgcpMgCfgEntry 100}

--------------------------------------------------------------------------------
-- 3.zxAnMgcpProtocolTable
--------------------------------------------------------------------------------
    zxAnMgcpProtocolTable OBJECT-TYPE
        SYNTAX      SEQUENCE OF ZxAnMgcpProtocolEntry
        MAX-ACCESS  not-accessible
        STATUS      current
        DESCRIPTION
            "Media Gateway Control Protocol config table."
        ::= { zxAnMgcpConfig 3 }

    zxAnMgcpProtocolEntry OBJECT-TYPE
        SYNTAX      ZxAnMgcpProtocolEntry
        MAX-ACCESS  not-accessible
        STATUS      current
        DESCRIPTION
            "Media Gateway Control Protocol config entry."
        INDEX { zxAnMgcpProtocolMgId }
        ::={zxAnMgcpProtocolTable 1}

    ZxAnMgcpProtocolEntry ::= SEQUENCE {
        zxAnMgcpProtocolMgId               Integer32,
        zxAnMgcpProtocolVersion            INTEGER,
        zxAnMgcpMgcMaxInactivityTime       Integer32,
        zxAnMgcpMinTransactionId           Integer32,
        zxAnMgcpMaxTransactionId           Integer32,
        zxAnMgcpResponseCacheTime          Integer32,
        zxAnMgcpTranMaxRetries             Integer32,
        zxAnMgcpTranPendInterval           Integer32,
        zxAnMgcpTranPendLimit              Integer32,
        zxAnMgcpRebootMaxWaitingDelay      Integer32
        }

    zxAnMgcpProtocolMgId  OBJECT-TYPE
        SYNTAX      Integer32(1..3)
        MAX-ACCESS  not-accessible
        STATUS      current
        DESCRIPTION
            "MG ID."
        DEFVAL { 1 }
        ::= { zxAnMgcpProtocolEntry 1 }

    zxAnMgcpProtocolVersion  OBJECT-TYPE
        SYNTAX      INTEGER {
            v1(1),
            v2(2)
        }
        MAX-ACCESS  read-write
        STATUS      current
        DESCRIPTION
            "MGCP Stack version."
        DEFVAL { v1 }
        ::= { zxAnMgcpProtocolEntry 2 }

    zxAnMgcpMgcMaxInactivityTime  OBJECT-TYPE
        SYNTAX      Integer32(20..300)
        UNITS       "second"
        MAX-ACCESS  read-write
        STATUS      current
        DESCRIPTION
            "The allowable time of no packet received from MGC."
        DEFVAL { 126 }
        ::= { zxAnMgcpProtocolEntry 3 }

    zxAnMgcpMinTransactionId  OBJECT-TYPE
        SYNTAX      Integer32(0..60000)
        MAX-ACCESS  read-write
        STATUS      current
        DESCRIPTION
            "Minimum transaction ID."
        DEFVAL { 0 }
        ::= { zxAnMgcpProtocolEntry 4 }

    zxAnMgcpMaxTransactionId  OBJECT-TYPE
        SYNTAX      Integer32(0..4294967295)
        MAX-ACCESS  read-write
        STATUS      current
        DESCRIPTION
            "Maximum transaction ID."
        DEFVAL { 80000 }
        ::= { zxAnMgcpProtocolEntry 5 }

    zxAnMgcpResponseCacheTime  OBJECT-TYPE
        SYNTAX      Integer32(0..30)
        UNITS       "second"
        MAX-ACCESS  read-write
        STATUS      current
        DESCRIPTION
            "The time of reply saved in cache.
             If same request received, MG will find reply from cache firstly."
        DEFVAL { 12 }
        ::= { zxAnMgcpProtocolEntry 6}

    zxAnMgcpTranMaxRetries  OBJECT-TYPE
        SYNTAX      Integer32(2..10)
        MAX-ACCESS  read-write
        STATUS      current
        DESCRIPTION
            "The maximum retransmission number of sending a transaction
             request."
        DEFVAL { 3 }
        ::= { zxAnMgcpProtocolEntry 7 }

    zxAnMgcpTranPendInterval  OBJECT-TYPE
        SYNTAX      Integer32(2..8)
        UNITS       "second"
        MAX-ACCESS  read-write
        STATUS      current
        DESCRIPTION
            "The interval of sending transaction pending."
        DEFVAL { 4 }
        ::= { zxAnMgcpProtocolEntry 8 }

    zxAnMgcpTranPendLimit  OBJECT-TYPE
        SYNTAX      Integer32(20..40)
        MAX-ACCESS  read-write
        STATUS      current
        DESCRIPTION
            "The maximum number of transactions pending that can be sent."
        DEFVAL { 30 }
        ::= { zxAnMgcpProtocolEntry 9 }

    zxAnMgcpRebootMaxWaitingDelay  OBJECT-TYPE
        SYNTAX      Integer32(10..600)
        UNITS       "second"
        MAX-ACCESS  read-write
        STATUS      current
        DESCRIPTION
            "MWD: The maximum waiting delay.
            This value is used for the MG to send the first
            Restart In Progress to the MGC.Without this value,
            when MG is powered on, it will send registration information
            immediately.If the total amount of registration information
            is huge, it will lead to MGC fault."
        DEFVAL { 60 }
        ::= { zxAnMgcpProtocolEntry 10 }

END
