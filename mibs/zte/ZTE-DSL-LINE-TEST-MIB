--
-- Zte Dsl Line Test Mib
--
--

ZTE-DSL-LINE-TEST-MIB DEFINITIONS ::= BEGIN
    IMPORTS
        MODULE-IDENTITY, OBJECT-TYPE,
        IpAddress,Counter32, Gauge32    FROM SNMPv2-SMI
        MODULE-COMPLIANCE, OBJECT-GROUP FROM SNMPv2-CONF
        SnmpAdminString                 FROM SNMP-FRAMEWORK-MIB
        ifIndex                         FROM IF-MIB
        RowStatus                       FROM SNMPv2-TC
        zxDsl                         	FROM ZTE-DSL-MIB     ;


-- ZTE Dsl line test MIB objects

    zxDslLineTestMib MODULE-IDENTITY
            LAST-UPDATED "200611171300Z"
            ORGANIZATION "zte dsl product line"
            CONTACT-INFO
                " su chunshan
                  Mail: suchunshan@zte.com.cn
                  Tel : 021-68896292,68896251"
            DESCRIPTION
                "This mib defines dsl line test mo (managed object ).

                 Naming Conventions:
                 Atuc -- (ATUC) modem at near (Central) end of line
                 Atur -- (ATUR) modem at Remote end of line "
    ::= {zxDsl 29}



    zxDslLineTestMibObjects  OBJECT IDENTIFIER ::= { zxDslLineTestMib 1 }
    zxDslLineTestTrapObjects OBJECT IDENTIFIER ::= { zxDslLineTestMib 2 }


--------------------------------------------------------------------------------
-- Following objects are defined.
-- 1.Testing System Mgmt
-- 2.TAM configuration
-- 3.dsl Line test server Table
--------------------------------------------------------------------------------


------------------------------------------------------------------------------
-- 1.Testing System Mgmt
------------------------------------------------------------------------------
    zxDslLineTestUnitType  OBJECT-TYPE
            SYNTAX      INTEGER
                    {
                        tam(1),  -- outside line test matrix
                        ltc(2)   -- line test card
                    }
            MAX-ACCESS  read-write
            STATUS      current
            DESCRIPTION
                "Testing unit type."
            ::= {zxDslLineTestMibObjects 5}

------------------------------------------------------------------------------
-- 2.TAM configuration
------------------------------------------------------------------------------

    zxDslLineTestTam OBJECT IDENTIFIER ::= { zxDslLineTestMibObjects 10 }

    zxDslLineTestTamIp  OBJECT-TYPE
            SYNTAX      IpAddress
            MAX-ACCESS  read-write
            STATUS      current
            DESCRIPTION
                "TAM's IpAddress."
            ::= {zxDslLineTestTam 1}

    zxDslLineTestTamIpMask  OBJECT-TYPE
            SYNTAX      IpAddress
            MAX-ACCESS  read-write
            STATUS      current
            DESCRIPTION
                "TAM's Ip Mask."
            ::= {zxDslLineTestTam 2}


------------------------------------------------------------------------------
-- 3.dsl Line test server Table
------------------------------------------------------------------------------

    zxDslLineTestServerTable  OBJECT-TYPE
            SYNTAX      SEQUENCE OF ZxDslLineTestServerEntry
            MAX-ACCESS  not-accessible
            STATUS      current
            DESCRIPTION
                "Dsl line test server information table."
            ::= {zxDslLineTestMibObjects 50}


    zxDslLineTestServerEntry  OBJECT-TYPE
            SYNTAX      ZxDslLineTestServerEntry
            MAX-ACCESS  not-accessible
            STATUS      current
            DESCRIPTION
                "Dsl line test server information entry"
            INDEX    { zxDslLineTestServerIndex }
            ::= {zxDslLineTestServerTable 1}


    ZxDslLineTestServerEntry ::=
            SEQUENCE {
                zxDslLineTestServerIndex              INTEGER,
                zxDslLineTestServerIp                 IpAddress,
                zxDslLineTestServerNatMode            INTEGER,
                zxDslLineTestServerRowStatus          RowStatus
                }

    zxDslLineTestServerIndex  OBJECT-TYPE
        SYNTAX      INTEGER (0..9)
        MAX-ACCESS  not-accessible
        STATUS      current
        DESCRIPTION
            "Index of line test server."
        ::= { zxDslLineTestServerEntry 1 }

    zxDslLineTestServerIp  OBJECT-TYPE
        SYNTAX      IpAddress
        MAX-ACCESS  read-create
        STATUS      current
        DESCRIPTION
            "Ip of line test server."
        ::= { zxDslLineTestServerEntry 2 }


    zxDslLineTestServerNatMode  OBJECT-TYPE
        SYNTAX      INTEGER {
            noNAT     (1),
            inBandNAT (2),
            outBandNAT (3),
            bridging_in_out_band(4)
            }
        MAX-ACCESS  read-create
        STATUS      current
        DESCRIPTION
            "NAT mode for line test management path.It means that if the dslam
        begin to use NAT mode to transmit line test command and response.

             noNAT(1)      -- no NAT on management path for line test
             inBandNAT(2)  -- enable NAT on in-band management path for line test
             outBandNAT(3) -- enable NAT on out-band management path for line test
             bridging_in_out_band(4) -- enable bidirection NAT between in-band
                           and out-band management path for line test.
             "
        ::= { zxDslLineTestServerEntry 3 }


    zxDslLineTestServerRowStatus  OBJECT-TYPE
        SYNTAX      RowStatus
        MAX-ACCESS  read-create
        STATUS      current
        DESCRIPTION
            "RowStatus of this entry."
        ::= { zxDslLineTestServerEntry 4 }


END
