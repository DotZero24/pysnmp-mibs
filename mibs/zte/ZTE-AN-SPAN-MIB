--
--
-- MIB generated by MG-SOFT Visual MIB Builder Version 6.0  Build 88
-- Wednesday, November 21, 2012 at 10:42:55
--

ZTE-AN-SPAN-MIB DEFINITIONS ::= BEGIN

    IMPORTS
        ifIndex     FROM IF-MIB
        OBJECT-GROUP, MODULE-COMPLIANCE               FROM SNMPv2-CONF
        InetAddressType, InetAddress                  FROM INET-ADDRESS-MIB
        IpAddress, Integer32, OBJECT-TYPE,
        MODULE-IDENTITY                               FROM SNMPv2-SMI
        RowStatus, TEXTUAL-CONVENTION                 FROM SNMPv2-TC
        zxAnInterfaceMib                              FROM ZTE-AN-INTERFACE-MIB;


    zxAnSpanMib MODULE-IDENTITY
        LAST-UPDATED    "201212101114Z"    -- December 10, 2012 at 11:14 GMT
        ORGANIZATION    "ZTE Corporation"
        CONTACT-INFO    "Zhang Zhengyi
                         ZTE Corporation
                         Mail: zhang.zhengyi@zte.com.cn
                         Tel : +86-21-68896470"
        DESCRIPTION     "This MIB defines managed objects of ZTE SPAN."
        REVISION        "201212101114Z"    -- December 10, 2012 at 11:14 GMT
        DESCRIPTION     "Initial version of this MIB module."
        REVISION        "201212061215Z"    -- December 06, 2012 at 12:15 GMT
        DESCRIPTION     "Add the group: zxAnSpanGroup."
        ::= { zxAnInterfaceMib 21 }


-- Node definitions
--

    zxAnSpanObjects OBJECT IDENTIFIER ::= { zxAnSpanMib 2 }


    zxAnSpanTable    OBJECT-TYPE
        SYNTAX      SEQUENCE OF ZxAnSpanEntry
        MAX-ACCESS  not-accessible
        STATUS      current
        DESCRIPTION
            "This table represents the switched port
            analyzer related parameters."
        ::= { zxAnSpanObjects 2 }


    zxAnSpanEntry    OBJECT-TYPE
        SYNTAX      ZxAnSpanEntry
        MAX-ACCESS  not-accessible
        STATUS      current
        DESCRIPTION
            "An entry in zxAnSpanTable.

            The multi-variables binding rule should be complied with when a
            manager creates an entry. According to this rule, all the related
            mib variables must be included in one SNMP set operation.

            There are two types of variables: mandatory and optional.
            All of the mandatory variables must be included in one SNMP set
            operation. Optional variables may be included in one SNMP set
            operation with the mandatory variables, but must not be used alone.

            To create an entry of this table, the mandatory and optional
            variables are as below.
            mandatory: zxAnSpanSessionId,zxAnSpanType,zxAnSpanSrcPortList,
                       zxAnSpanSrcDirectionList
            optional : the other

            After an entry is created, every variable can be modified.
            "
        INDEX { zxAnSpanSessionId }
        ::= { zxAnSpanTable 1 }


    ZxAnSpanEntry ::=
        SEQUENCE {
            zxAnSpanSessionId                   Integer32,
            zxAnSpanType                        INTEGER,
            zxAnSpanSrcPortList                 OBJECT IDENTIFIER,
            zxAnSpanSrcDirectionList            OBJECT IDENTIFIER,
            zxAnSpanDstPort                     Integer32,
            zxAnSpanVid                         Integer32,
            zxAnSpanCos                         Integer32,
            zxAnSpanTpid                        Integer32,
            zxAnSpanDstIpType                   InetAddressType,
            zxAnSpanDstIpAddr                   InetAddress,
            zxAnSpanSrcIpType                   InetAddressType,
            zxAnSpanSrcIpAddr                   InetAddress,
            zxAnSpanTtl                         Integer32,
            zxAnSpanDscp                        Integer32,
            zxAnSpanRowStatus                   RowStatus
       }


    zxAnSpanSessionId      OBJECT-TYPE
        SYNTAX      Integer32 (1..16)
        MAX-ACCESS  not-accessible
        STATUS      current
        DESCRIPTION
            "The index of a session."
        ::= { zxAnSpanEntry 1 }


    zxAnSpanType     OBJECT-TYPE
        SYNTAX      INTEGER  {
            span(1),
            rspan(2),
            erspan(3)
        }
        MAX-ACCESS  read-create
        STATUS      current
        DESCRIPTION
            "The SPAN type of a session.
            span(1)            - Local Switched Port Analyzer.
            rspan(2)           - Remote SPAN.
            erspan(3)          - Enhanced Remoted SPAN."
        ::= { zxAnSpanEntry 2 }

    zxAnSpanSrcPortList      OBJECT-TYPE
        SYNTAX      OBJECT IDENTIFIER
        MAX-ACCESS  read-create
        STATUS      current
        DESCRIPTION
            "It is a sequence of some source ports.
             Supports Ethernet interface, inner port, smartgroup and CPU.
             The format of portlist is like this:
             .ifIndex1.ifIndex2....
             |port1   |port2   |...
             "
        ::= { zxAnSpanEntry 3 }


    zxAnSpanSrcDirectionList      OBJECT-TYPE
        SYNTAX      OBJECT IDENTIFIER
        MAX-ACCESS  read-create
        STATUS      current
        DESCRIPTION
            "The traffic direction list of the source port list.
             The format of  direction list is like this:
             .direction1.direction2...
             |port1     |port2    |...

             Each value of the sequence represents a traffic direction.
             The value may be followings:
             both(1),
             egress(2),
             ingress(3).
            "
        ::= { zxAnSpanEntry 4 }


    zxAnSpanDstPort      OBJECT-TYPE
        SYNTAX      Integer32
        MAX-ACCESS  read-create
        STATUS      current
        DESCRIPTION
            "The ifIndex of SPAN and RSPAN destination port.
            Supports Ethernet interface and smartgroup."
        DEFVAL { 0 }
        ::= { zxAnSpanEntry 20 }


    zxAnSpanVid      OBJECT-TYPE
        SYNTAX      Integer32 (1..4094|65535)
        MAX-ACCESS  read-create
        STATUS      current
        DESCRIPTION
            "The traffic VLAN ID of RSPAN or ERSPAN."
        DEFVAL { 65535 }
        ::= { zxAnSpanEntry 21 }


    zxAnSpanCos      OBJECT-TYPE
        SYNTAX      Integer32 (0..7)
        MAX-ACCESS  read-create
        STATUS      current
        DESCRIPTION
            "The traffic CoS of RSPAN or ERSPAN."
        DEFVAL { 0 }
        ::= { zxAnSpanEntry 22 }


    zxAnSpanTpid      OBJECT-TYPE
        SYNTAX      Integer32 (0..65535)
        MAX-ACCESS  read-create
        STATUS      current
        DESCRIPTION
            "The traffic TPID of RSPAN or ERSPAN."
        DEFVAL { 33024 }
        ::= { zxAnSpanEntry 23 }


     zxAnSpanDstIpType      OBJECT-TYPE
         SYNTAX      InetAddressType
         MAX-ACCESS  read-create
         STATUS      current
         DESCRIPTION
             "The type of IP address about destination IP."
         DEFVAL { ipv4 }
         ::= { zxAnSpanEntry 24 }


    zxAnSpanDstIpAddr      OBJECT-TYPE
        SYNTAX      InetAddress
        MAX-ACCESS  read-create
        STATUS      current
        DESCRIPTION
            "The destination IP of ERSPAN."
        DEFVAL { '00000000'h }
        ::= { zxAnSpanEntry 25 }

    zxAnSpanSrcIpType      OBJECT-TYPE
        SYNTAX      InetAddressType
        MAX-ACCESS  read-create
        STATUS      current
        DESCRIPTION
            "The type of IP address about source IP."
        DEFVAL { ipv4 }
        ::= { zxAnSpanEntry 26 }


    zxAnSpanSrcIpAddr      OBJECT-TYPE
        SYNTAX      InetAddress
        MAX-ACCESS  read-create
        STATUS      current
        DESCRIPTION
            "The source IP of ERSPAN."
        DEFVAL { '00000000'h }
        ::= { zxAnSpanEntry 27 }


    zxAnSpanTtl      OBJECT-TYPE
        SYNTAX      Integer32 (0..255)
        MAX-ACCESS  read-create
        STATUS      current
        DESCRIPTION
            "The TTL of ERSPAN."
        DEFVAL { 128 }
        ::= { zxAnSpanEntry 28 }


    zxAnSpanDscp      OBJECT-TYPE
        SYNTAX      Integer32 (0..63)
        MAX-ACCESS  read-create
        STATUS      current
        DESCRIPTION
             "The DSCP of ERSPAN."
        DEFVAL { 0 }
        ::= { zxAnSpanEntry 29 }


    zxAnSpanRowStatus      OBJECT-TYPE
        SYNTAX      RowStatus
        MAX-ACCESS  read-create
        STATUS      current
        DESCRIPTION
            "The status of this conceptual row.

            The supported actions of this conceptual row only include:
            'createAndGo' and 'destroy'.

            To create a row in this table, a manager must set this object to
            createAndGo(4), and must comply with the multi-variables binding
            rule described in zxAnAclEntry.

            To delete a row in this table, a manager must set this object to
            destroy(6).

            To get this object, the agent always returns active(1)."
        ::= { zxAnSpanEntry 50 }



    zxAnSpanNotifications OBJECT IDENTIFIER ::= { zxAnSpanMib 3 }



    zxAnSpanConformance OBJECT IDENTIFIER ::= { zxAnSpanMib 4 }



    zxAnSpanCompliances OBJECT IDENTIFIER ::= { zxAnSpanConformance 1 }



    zxAnSpanCompliance      MODULE-COMPLIANCE
        STATUS      current
        DESCRIPTION
            "The compliance statement for the ZTE-AN-MONITOR-MIB."
        MODULE -- this module
        MANDATORY-GROUPS { zxAnSpanGroup }
        ::= { zxAnSpanCompliances 1 }


    zxAnSpanGroups OBJECT IDENTIFIER ::= { zxAnSpanConformance 2 }


    zxAnSpanGroup OBJECT-GROUP
        OBJECTS { zxAnSpanType,
                zxAnSpanSrcPortList,
                zxAnSpanSrcDirectionList,
                zxAnSpanDstPort,
                zxAnSpanVid,
                zxAnSpanCos,
                zxAnSpanTpid,
                zxAnSpanDstIpType,
                zxAnSpanDstIpAddr,
                zxAnSpanSrcIpType,
                zxAnSpanSrcIpAddr,
                zxAnSpanTtl,
                zxAnSpanDscp,
                zxAnSpanRowStatus
              }
        STATUS current
        DESCRIPTION
            "A collection of objects providing the access control list
            configuration information."
        ::= { zxAnSpanGroups 1 }



  END

--
--
--
