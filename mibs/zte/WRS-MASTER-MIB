------------------------------------------------------------------------------
------------------------------------------------------------------------------
--
--  File         : wrsMasterMib.mi2
--  Description  : Sample WRS Master OID Definition MIB
--  Version      : 0.6
--  Date         : August 29, 2000
--
--  Copyright (c) 2000 Wind River Systems, Inc.  All Rights Reserved.
--
--  Reproduction of this document is authorized on condition that this
--  copyright notice is included.  This sample WRS Master Enterprise MIB
--  embodies proprietary intellectual property of Wind River Systems (WRS).
--  WRS retains all title and ownership in the specification, including any
--  revisions.
--
--  It is the intent of WRS to encourage the widespread use of this
--  specification in connection with the management of TMS-based products.
--  WRS grants vendors, end-users, and other interested parties a
--  non-exclusive license to use this specification in connection with the
--  management of TMS products.
--
--  This specification is supplied "AS IS", and WRS makes no warranty,
--  either express or implied, as to the use, operations, condition,
--  or performance of this specification.
--
------------------------------------------------------------------------------
------------------------------------------------------------------------------
--  Sample WRS Master Enterprise MIB
--
--  NOTES:
--   1. This is a SMIv2 MIB - all definitions are automatically 'exported'.
--
--   2. This MIB:
--        - defines the 'WRS Product' OIDs (used as IMPORTS)
--        - defines the 'TMS Major Category' OIDs (used as IMPORTS)
--        - defines the 'TMS Internal MIB Module' OIDs (used as IMPORTS)
--        - defines/documents the 'TMS Generic' MIB OIDs
--        - documents the 'TMS OEM swAPI' MIB OIDs
--        - documents the 'TMS OEM Product' MIB OIDs
--
--   3. Note that the 'defined/documents' items provide a common place to
--      define or document the required OIDs.  SMIv1 MIBs can be defined
--      here and then imported into the corresponding MIB.  The SMIv2
--      'MODULE-IDENTITY' macro does not allow the second OID parameter to
--      be imported from an external MIB file.  The authors of these
--      'documented' MIBs must verify, by procedure, that the values used
--      match the values in this document.
--
--   4. Note that some MIB compilers do not accept two sets of comments on the
--      same line.  Consequently, for commented out document items, do not
--      use a second comment on the same line.
--
--   5. Note that the Wind River enterprise ID (731) is used in the sample
--      MIBs.  The customer "must" replace the Wind River enterprise ID with
--      the registered enterprise identifier for the specific company or
--      product.  The customer must also replace the WRS information
--      located in the 'MODULE-IDENTITY' in each sample MIB.
--
------------------------------------------------------------------------------
------------------------------------------------------------------------------

WRS-MASTER-MIB DEFINITIONS ::= BEGIN

IMPORTS
    MODULE-IDENTITY, enterprises              FROM SNMPv2-SMI;

    zte MODULE-IDENTITY
        LAST-UPDATED    "0110290000Z"  -- Octember 29, 2001
        ORGANIZATION    "Zhongxing Telcom Co. Ltd."
        CONTACT-INFO    "Zhongxing Telcom Co. Ltd.
                         E-mail: info@mail.zte.com.cn
                         http	: www.zte.com.cn or www.zhongxing.com"

        DESCRIPTION     "zte MIB OID defines and documentation."

        REVISION        "0110290000Z"  -- Octember 29, 2001
        DESCRIPTION     "Initial MIB creation."

        ::= { enterprises 3902 }

-- zte Products
    zxEdsl	        OBJECT IDENTIFIER ::= { zte 1008 }
   zxEdslOwn	OBJECT IDENTIFIER ::= { zxEdsl  1 }
   zxEdslLR1	        OBJECT IDENTIFIER ::= { zxEdslOwn 1 }

    tms             OBJECT IDENTIFIER ::= { zxEdslLR1 1 }
--  tms1_0          OBJECT IDENTIFIER ::= { wrs 1 } Obsolete

-- TMS Major MIB Categories
    idb             OBJECT IDENTIFIER ::= { tms 1 }     -- IDB MIBs
    tmsGeneric      OBJECT IDENTIFIER ::= { tms 2 }     -- TMS Generic MIBs
    oemSwapi        OBJECT IDENTIFIER ::= { tms 3 }     -- OEM swAPI MIBs
    oemProd         OBJECT IDENTIFIER ::= { tms 4 }     -- OEM Product MIBs

-- TMS IDB Internal Module MIBs
    rmonMib         OBJECT IDENTIFIER ::= { idb 1 }
--  garpMib         OBJECT IDENTIFIER ::= { idb 2 }         SMIv2
--  stpMib          OBJECT IDENTIFIER ::= { idb 3 }         SMIv2

-- TMS Generic MIBs
--  tmsCommonMib    OBJECT IDENTIFIER ::= { tmsGeneric 1 }  SMIv2
--  tmsL3Mib        OBJECT IDENTIFIER ::= { tmsGeneric 2 }  SMIv2

-- OEM swAPI MIBs
--  pmSwapi         OBJECT IDENTIFIER ::= { oemSwapi 1 }    SMIv2
--  galSwapi        OBJECT IDENTIFIER ::= { oemSwapi 2 }    SMIv2
--  pcSwapi         OBJECT IDENTIFIER ::= { oemSwapi 3 }    SMIv2

-- OEM Product MIBs
--  pm3575          OBJECT IDENTIFIER ::= { oemProd 1 }     SMIv2
--  galnet         OBJECT IDENTIFIER ::= { oemProd 2 }     SMIv2
--  pcSwitch        OBJECT IDENTIFIER ::= { oemProd 3 }     SMIv2

--
-- END of WRS-MASTER-MIB
--

END
