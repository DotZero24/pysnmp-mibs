------------------------------------------------------------------------------
------------------------------------------------------------------------------
--
--  File         : ZTE-DSL-MIB.mib
--  Description  : ZTE DSL OID Definition MIB
--  Version      : 1.0
--  Date         : 2005-10-22
--
------------------------------------------------------------------------------

ZTE-DSL-MIB DEFINITIONS ::= BEGIN

IMPORTS
    MODULE-IDENTITY, enterprises              FROM SNMPv2-SMI;

    zte MODULE-IDENTITY
        LAST-UPDATED    "0110290000Z"  -- Octember 29, 2001
        ORGANIZATION    "Zhongxing Telcom Co. Ltd."
        CONTACT-INFO    "Zhongxing Telcom Co. Ltd.
                         E-mail: info@mail.zte.com.cn
                         http	: www.zte.com.cn or www.zhongxing.com"

        DESCRIPTION     "zte MIB OID defines and documentation."

        REVISION        "0409220000Z"  -- 2004-09-22
        DESCRIPTION     "Initial MIB creation."

        ::= { enterprises 3902 }

-- zte Products
   zxDsl	        OBJECT IDENTIFIER ::= { zte 1004 }
   zxPON                OBJECT IDENTIFIER ::= { zte 1012}

-- END of ZTE-MASTER-MIB
--

END
