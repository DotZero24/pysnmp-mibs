ZXCESCARDPROP-MIB DEFINITIONS ::= BEGIN

IMPORTS
     MODULE-IDENTITY, OBJECT-TYPE
          FROM SNMPv2-SMI                    -- [RFC2578]
     TruthValue
          FROM SNMPv2-TC                     -- [RFC2579]
     InterfaceIndex
          FROM IF-MIB                        -- [RFC2863]
     PhysAddress
          FROM RFC1213-MIB
    InetAddressType, InetAddress
          FROM INET-ADDRESS-MIB              -- [RFC4001]
     zxPwCETH
          FROM ZTE-MASTER-MIB
    ;

zxCesCardPropMIB MODULE-IDENTITY
    LAST-UPDATED "200609190000Z"  -- Sep 19, 2006
    ORGANIZATION    "Zhongxing Telcom Co. Ltd."
    CONTACT-INFO    "Zhongxing Telcom Co. Ltd.
                     E-mail: info@mail.zte.com.cn
                     http  : www.zte.com.cn or www.zhongxing.com"

    DESCRIPTION
         "The MIB module to describe global
         parameters objects of CES card .
         "
    ::= { zxPwCETH 1 }

------------------------------------------------------------------------------
--  define objects in ZXCESCARDPROP-MIB
------------------------------------------------------------------------------

zxCesCardPropTable OBJECT-TYPE
     SYNTAX  SEQUENCE OF ZxCesCardPropEntry
     MAX-ACCESS  not-accessible
     STATUS  current
     DESCRIPTION
            "The global parameters configuration table."
     ::= { zxCesCardPropMIB 1 }

zxCesCardPropEntry OBJECT-TYPE
     SYNTAX  ZxCesCardPropEntry
     MAX-ACCESS  not-accessible
     STATUS  current
     DESCRIPTION
            "An entry in the global parameters Configuration table."
     INDEX   { zxCesCardIndex }
     ::= { zxCesCardPropTable 1 }

ZxCesCardPropEntry ::=
     SEQUENCE {
           zxCesCardIndex                      InterfaceIndex,
           zxCesCardPhysAddress                PhysAddress,
           zxCesCardAddrType                   InetAddressType,
           zxCesCardAddress                    InetAddress,
           zxCesCardCfgInfoSend                TruthValue
     }

zxCesCardIndex OBJECT-TYPE
     SYNTAX  InterfaceIndex
     MAX-ACCESS not-accessible
     STATUS  current
     DESCRIPTION
            "The 4 bytes index includes:
            interface type(bit31~28);shelfId(bit27~24);slotId(bit23~16);portId(bit15~bit8);reserved(bit7~bit0)"
     ::= { zxCesCardPropEntry 1 }

zxCesCardPhysAddress OBJECT-TYPE
     SYNTAX  PhysAddress
     MAX-ACCESS  read-write
     STATUS  current
     DESCRIPTION
             "The interface's address at the protocol layer
             immediately `below' the network layer in the
             protocol stack.  For interfaces which do not have
             such an address (e.g., a serial line), this object
             should contain an octet string of zero length."
     REFERENCE "Used by MAP"
     ::= { zxCesCardPropEntry 2 }

zxCesCardAddrType OBJECT-TYPE
   SYNTAX        InetAddressType
   MAX-ACCESS    read-write
   STATUS        current
   DESCRIPTION
        "Denotes the address type of the local node. "
   DEFVAL { ipv4 }
   ::= { zxCesCardPropEntry 3 }

zxCesCardAddress OBJECT-TYPE
   SYNTAX        InetAddress
   MAX-ACCESS    read-write
   STATUS        current
   DESCRIPTION
        "This object contains the value of the local node address. This object
         SHOULD contain a value of all zeroes if not applicable
         (zxCesCardAddrType is 'unknown')."
   ::= { zxCesCardPropEntry 4 }

zxCesCardCfgInfoSend  OBJECT-TYPE
     SYNTAX               TruthValue
     MAX-ACCESS           read-write
     STATUS               current
     DESCRIPTION
            "The action to send the configuration on
             global parameters to corresponding card."
     ::= { zxCesCardPropEntry 5 }

END
