-- File Name : ZTE-DSL-CPE-MGMT-MIB.mib
-- Date      : Mon Oct 17 13:55:29 GMT+08:00 2005
-- Author    : AdventNet Agent Toolkit C Edition - MibEditor 6

--
-- Zte Dsl CPE Mib for 8220v3.x platform.
--
--


ZTE-DSL-CPE-MGMT-MIB	DEFINITIONS ::= BEGIN
	IMPORTS
		zxDsl
			FROM ZTE-DSL-MIB
		RowStatus,DisplayString
			FROM SNMPv2-TC
		MODULE-COMPLIANCE, OBJECT-GROUP
			FROM SNMPv2-CONF
		ifIndex
			FROM IF-MIB
		MODULE-IDENTITY, OBJECT-TYPE, TimeTicks, Counter32, Gauge32, enterprises, IpAddress
			FROM SNMPv2-SMI
--        dsx1LineIndex
--            FROM DS1-MIB
		adslLineConfProfileName, adslLineConfProfileEntry, adslLineAlarmConfProfileEntry
			FROM ADSL-LINE-MIB
		SnmpAdminString
			FROM SNMP-FRAMEWORK-MIB;

	zxDslCPEMib	MODULE-IDENTITY
		LAST-UPDATED	"200510080948Z"
		ORGANIZATION	"zte dsl product line"
		CONTACT-INFO	"ma ke
                  Mail: ma.ke@zte.com.cn
                  Tel : 021-68896477"
		DESCRIPTION		"This mib defines extended E1 mo (managed object ) for adsl2,
                 adsl+ and dsl loop test.

                 Naming Conventions:
                 Atuc -- (ATUC) CPE at near (Central) end of line
                 Atur -- (ATUR) CPE at Remote end of line"
		::=  {  zxDsl  17  }


--------------------------------------------------------------------------
-- 1.port CPE table. Configuring CPE IP
--------------------------------------------------------------------------

	zxDslPortCPETable	OBJECT-TYPE
		SYNTAX		SEQUENCE  OF  ZxDslPortCPEEntry
		MAX-ACCESS	not-accessible
		STATUS		current
		DESCRIPTION	"A table entry containing Port CPE information  for each
		port. "
		::=  { zxDslCPEMib  1 }

	zxDslPortCPEEntry	OBJECT-TYPE
		SYNTAX		ZxDslPortCPEEntry
		MAX-ACCESS	not-accessible
		STATUS		current
		DESCRIPTION	"Dsl Port CPE information entry"
		INDEX		{  ifIndex  }
		::=  { zxDslPortCPETable 1 }

	ZxDslPortCPEEntry  ::=  SEQUENCE
	    {
		zxDslPortCPEIpAddr            IpAddress,
		zxDslPortMgmtPvcEncapsType    INTEGER
		}


	zxDslPortCPEIpAddr	OBJECT-TYPE
		SYNTAX			IpAddress
		MAX-ACCESS		read-write
		STATUS			current
		DESCRIPTION		""
		::=  {  zxDslPortCPEEntry  1  }


	zxDslPortMgmtPvcEncapsType 	OBJECT-TYPE
		SYNTAX			INTEGER
	    {
          	rfc1483b(1),
          	rfc1483r(2),
          	noEncaps(3)
     	}
		MAX-ACCESS		read-write
		STATUS			current
		DESCRIPTION
		   "RFC 1483 Multiprotocol Encapsulation for CPE management PVC."

        DEFVAL      { RFC1483b }
		::=  {  zxDslPortCPEEntry  2  }



--------------------------------------------------------------------------
-- 2.CPE ConifgInfo table
--------------------------------------------------------------------------

    zxcpeConifgInfoTable OBJECT-TYPE
		SYNTAX SEQUENCE OF ZxcpeConifgInfoEntry
		MAX-ACCESS not-accessible
		STATUS current
		DESCRIPTION
			"
			CPE configuration table
			"
		::= { zxDslCPEMib  2 }

	zxcpeConifgInfoEntry OBJECT-TYPE
		SYNTAX ZxcpeConifgInfoEntry
		MAX-ACCESS not-accessible
		STATUS current
		DESCRIPTION
			"
			CPE configuration entry
			"
		INDEX { ifIndex}
		::= { zxcpeConifgInfoTable 1 }

	ZxcpeConifgInfoEntry ::=
		SEQUENCE {
			zxcpeAutoCfgAdminStatus
				Integer32,
			zxcpePvcAdminStatus
				Integer32,
			zxcpePvcVpi
				Integer32,
			zxcpePvcVci
				Integer32,
			zxcpeSysInfoConfigId
				DisplayString
		 }

      	zxcpeAutoCfgAdminStatus OBJECT-TYPE
     		SYNTAX Integer32 {
			enable(1),
			disable(2)
			}
     		MAX-ACCESS read-write
     		STATUS current
     		DESCRIPTION
	     	"
	 	Auto configuration administatus of CPE"
                     DEFVAL { disable }
     		::= { zxcpeConifgInfoEntry 1 }

	zxcpePvcAdminStatus OBJECT-TYPE
		SYNTAX Integer32 {
			create(1),
			delete(2)
			}
		MAX-ACCESS read-write
		STATUS current
		DESCRIPTION
			"
			CPE base PVC administatus
			"
                    DEFVAL { delete }
		::= { zxcpeConifgInfoEntry 2 }

	zxcpePvcVpi OBJECT-TYPE
		SYNTAX Integer32
		MAX-ACCESS read-write
		STATUS current
		DESCRIPTION
			"
			CPE PVC VPI
			"
		::= { zxcpeConifgInfoEntry 3 }

	zxcpePvcVci OBJECT-TYPE
		SYNTAX Integer32
		MAX-ACCESS read-write
		STATUS current
		DESCRIPTION
			"
			CPE PVC VCI
			"
		::= { zxcpeConifgInfoEntry 4 }

	zxcpeSysInfoConfigId OBJECT-TYPE
		SYNTAX DisplayString (SIZE (0..16))
		MAX-ACCESS read-only
		STATUS current
		DESCRIPTION
			"
			CPE configuration id"
		::= { zxcpeConifgInfoEntry 5 }




--------------------------------------------------------------------------
-- 3.CPE trap info table
--------------------------------------------------------------------------
    zxcpeTrapInfoTable OBJECT-TYPE
		SYNTAX SEQUENCE OF ZxcpeTrapInfoEntry
		MAX-ACCESS not-accessible
		STATUS current
		DESCRIPTION
			"
			CPE trap infomation table
			"
		::= { zxDslCPEMib  3 }



	zxcpeTrapInfoEntry  OBJECT-TYPE
		SYNTAX ZxcpeTrapInfoEntry
		MAX-ACCESS not-accessible
		STATUS current
		DESCRIPTION
			"
			CPE trap infomation entry
			"
		INDEX { ifIndex}
		::= { zxcpeTrapInfoTable 1 }

	ZxcpeTrapInfoEntry  ::=
		SEQUENCE {
			zxcpeAdministrableStatus
				Integer32,
			zxcpeAutoCfgOperStatus
				Integer32,
			cpeSysInfoChipSet
				DisplayString,
			zxcpeSysInfoSystemVersion
				DisplayString,
			zxcpeSysInfoProductId
				DisplayString,
			zxcpeSysInfoVendorId
				DisplayString,
			zxcpeSysInfoManufacturerOui
				DisplayString,
			zxcpeSysInfoWorkMode
				Integer32,
		    zxcpeSysInfoSerialNumber
		    	OCTET STRING,
			zxcpeSysInfoMibVersion
				DisplayString
		 }

      	zxcpeAdministrableStatus OBJECT-TYPE
     		SYNTAX Integer32 {
			up(1),
			down(2)
			}
     		MAX-ACCESS read-only
     		STATUS current
     		DESCRIPTION
	     	"
	 	status of CPE"
                    DEFVAL { down }
     		::= { zxcpeTrapInfoEntry  1 }

	zxcpeAutoCfgOperStatus OBJECT-TYPE
		SYNTAX Integer32 {
			yes(1),
			no(2),
			timeout(3)
			}
		MAX-ACCESS read-only
		STATUS current
		DESCRIPTION
			"
			CPE auto configuration status
			"
                    DEFVAL { no }
		::= { zxcpeTrapInfoEntry  2 }

	cpeSysInfoChipSet OBJECT-TYPE
		SYNTAX DisplayString (SIZE (0..64))
		MAX-ACCESS read-only
		STATUS current
		DESCRIPTION
			"
			Chipset Vendor ID, chipset type and firmware information.
			"
		::= { zxcpeTrapInfoEntry  3 }

	zxcpeSysInfoSystemVersion OBJECT-TYPE
		SYNTAX DisplayString (SIZE (0..64))
		MAX-ACCESS read-only
		STATUS current
		DESCRIPTION
			"
			CPE system vresion
			"
		::= { zxcpeTrapInfoEntry  4 }

	zxcpeSysInfoProductId OBJECT-TYPE
		SYNTAX  DisplayString (SIZE (0..16))
		MAX-ACCESS read-only
		STATUS current
		DESCRIPTION
			"
			CPE product id"
		::= { zxcpeTrapInfoEntry  5 }

	zxcpeSysInfoVendorId OBJECT-TYPE
		SYNTAX DisplayString (SIZE (0..32))
		MAX-ACCESS read-only
		STATUS current
		DESCRIPTION
			"
			CPE vendor id
			"
		::= { zxcpeTrapInfoEntry  6 }

	zxcpeSysInfoManufacturerOui OBJECT-TYPE
		SYNTAX DisplayString (SIZE (0..3))
		MAX-ACCESS read-only
		STATUS current
		DESCRIPTION
			"
			CPE Manufacturer Oui
			"
		::= { zxcpeTrapInfoEntry  7 }

	zxcpeSysInfoWorkMode OBJECT-TYPE
		SYNTAX Integer32 {
			bridge(1),
			router(2)
			}
		MAX-ACCESS read-only
		STATUS current
		DESCRIPTION
			"
			CPE Work Mode
			"
		::= { zxcpeTrapInfoEntry  8 }

	zxcpeSysInfoSerialNumber OBJECT-TYPE
		SYNTAX OCTET STRING (SIZE (0..32))
		MAX-ACCESS read-only
		STATUS current
		DESCRIPTION "CPE?‘s physical number "
		::= { zxcpeTrapInfoEntry 9 }

	zxcpeSysInfoMibVersion OBJECT-TYPE
		SYNTAX DisplayString (SIZE (0..8))
		MAX-ACCESS read-only
		STATUS current
		DESCRIPTION
			"
			CPE Mib Version"
		::= { zxcpeTrapInfoEntry  10 }



--------------------------------------------------------------------------
-- 4.cpe mgmt sys config
--------------------------------------------------------------------------
   	zxcpeSnmpProxy OBJECT-TYPE
   		SYNTAX Integer32
		    {
		    transmitAndSaveCpeConfig(1),
		    transmitOnly(2)
		    }
	   MAX-ACCESS read-write
	   STATUS current
	   DESCRIPTION
	        "DSLAM's proxy type for CPE. "
	   ::= { zxDslCPEMib  4 }


	zxcpeCfgFlashClear OBJECT-TYPE
		SYNTAX INTEGER
		{
			clear(1)
		}
		MAX-ACCESS read-write
		STATUS current
		DESCRIPTION
			" Clear part of flash for CPE configuration data section."
		::= { zxDslCPEMib  5 }



	zxcpeCfgMgmtVlan OBJECT-TYPE
		SYNTAX Integer32 (2..4094)
		MAX-ACCESS read-write
		STATUS current
		DESCRIPTION
			" Vlan used to support cpe management,such as cpe version download
		and configuration.It is used by VDSL cpe only now."
		DEFVAL { 4014 }
		::= { zxDslCPEMib  6 }


    importZteCpeMib OBJECT IDENTIFIER ::= { zxcpeConifgInfoTable 1000 }


END
