--  ******************************************************
--  $Id: hqos.mib 2008-07$
--
--  hqos.mib: ZXR10 Access List MIB file
--
--  JUL. 2008, Jiang Yan
--
--  Copyright(c) 2008 by ZTE Corporaton
--  All rights reservered
--  ******************************************************

HQOS-MIB DEFINITIONS ::= BEGIN

IMPORTS
   OBJECT-TYPE,
   Integer32
   		FROM SNMPv2-SMI

   DisplayString,
   RowStatus
   		FROM SNMPv2-TC

   zxr10switch
        FROM ZXR10-SMI;

   hqos                   OBJECT IDENTIFIER ::= { zxr10switch 16}
    ----------------------------------------------------------------------
	-- 1.The table of Flow class info
	----------------------------------------------------------------------
	hqosFlowClassTable    OBJECT-TYPE
        SYNTAX         SEQUENCE OF HqosFlowClassEntry
        MAX-ACCESS     not-accessible
        STATUS         current
        DESCRIPTION
            "A table that contains HQOS Flow info."
    ::= { hqos 1 }

    hqosFlowClassEntry    OBJECT-TYPE
        SYNTAX          HqosFlowClassEntry
        MAX-ACCESS      not-accessible
        STATUS          current
        DESCRIPTION
            "A list of  entries of HQOS Flow information."
        INDEX  { hqosFlowClassName }
    ::= { hqosFlowClassTable 1 }

    HqosFlowClassEntry ::= SEQUENCE {
        hqosFlowClassName              DisplayString
                   }

    hqosFlowClassName     OBJECT-TYPE
        SYNTAX          DisplayString(SIZE(1..32))
        MAX-ACCESS      read-only
        STATUS          current
        DESCRIPTION
            " The name of a Flow class."
    ::= { hqosFlowClassEntry 1 }

    ----------------------------------------------------------------------
	-- 2.The table of Flow Match info
	----------------------------------------------------------------------

    hqosFlowMatchTable    OBJECT-TYPE
        SYNTAX         SEQUENCE OF HqosFlowMatchEntry
        MAX-ACCESS     not-accessible
        STATUS         current
        DESCRIPTION
            "A table that contains HQOS Flow Match info."
    ::= { hqos 2 }

    hqosFlowMatchEntry    OBJECT-TYPE
        SYNTAX          HqosFlowMatchEntry
        MAX-ACCESS      not-accessible
        STATUS          current
        DESCRIPTION
            "A list of  entries of HQOS Flow Match information."
        INDEX  { hqosFlowClassName
                 }
    ::= { hqosFlowMatchTable 1 }

    HqosFlowMatchEntry ::= SEQUENCE {
        hqosMatchFlowclass             DisplayString,
        hqosMatchType                  INTEGER,
        hqosMatchAclNo                 Integer32,
        hqosMatchRuleNo                Integer32,
        hqosMatchVlanID                Integer32,
        hqosMatchPhb                   INTEGER,
        hqosMatchSvlan                 Integer32,
        hqosMatchCvlan                 Integer32
        }

    hqosMatchFlowclass     OBJECT-TYPE
        SYNTAX          DisplayString(SIZE(1..32))
        MAX-ACCESS      read-only
        STATUS          current
        DESCRIPTION
            " The name of a Flow class for match."
    ::= { hqosFlowMatchEntry 1 }

    hqosMatchType            OBJECT-TYPE
        SYNTAX 		    INTEGER{
                            unvalid(0),
                            acl(1),
                            vlan(3),
                            phb(5),
                            svlan(6),
                            cvlan(7)
                            }
        MAX-ACCESS 	    read-only
        STATUS          current
        DESCRIPTION
            "The match type of a match."
    ::= { hqosFlowMatchEntry 2 }

    hqosMatchAclNo            OBJECT-TYPE
        SYNTAX 		    Integer32
        MAX-ACCESS 	    read-only
        STATUS          current
        DESCRIPTION
            "The alc number of a match."
    ::= { hqosFlowMatchEntry 3 }

    hqosMatchRuleNo           OBJECT-TYPE
        SYNTAX 		    Integer32
        MAX-ACCESS 	    read-only
        STATUS          current
        DESCRIPTION
            "The rule number of a match."
    ::= { hqosFlowMatchEntry 4 }

    hqosMatchVlanID         OBJECT-TYPE
        SYNTAX 		    Integer32(1..4094)
        MAX-ACCESS 	    read-only
        STATUS          current
        DESCRIPTION
            "The Vlan id of a match."
    ::= { hqosFlowMatchEntry 5 }

    hqosMatchPhb          OBJECT-TYPE
        SYNTAX 		    INTEGER{
                            be(0),
                          	af1(1),
                          	af2(2),
                          	af3(3),
                          	af4(4),
                          	ef(5),
                          	cs6(6),
                          	cs7(7),
                          	notconfig(8)
                      }
        MAX-ACCESS 	    read-only
        STATUS          current
        DESCRIPTION
            "The phb of a match."
    ::= { hqosFlowMatchEntry 6 }

    hqosMatchSvlan         OBJECT-TYPE
        SYNTAX 		    Integer32(1..4094)
        MAX-ACCESS 	    read-only
        STATUS          current
        DESCRIPTION
            "The Svlan id of a match."
    ::= { hqosFlowMatchEntry 7 }

    hqosMatchCvlan         OBJECT-TYPE
        SYNTAX 		    Integer32(1..4094)
        MAX-ACCESS 	    read-only
        STATUS          current
        DESCRIPTION
            "The Cvlan id of a match."
    ::= { hqosFlowMatchEntry 8 }

    ----------------------------------------------------------------------
	-- 3.The table of Wred info
	----------------------------------------------------------------------
    hqosWredTable        OBJECT-TYPE
        SYNTAX         SEQUENCE OF HqosWredEntry
        MAX-ACCESS     not-accessible
        STATUS         current
        DESCRIPTION
            "A table that contains WRED info."
    ::= { hqos 3 }

    hqosWredEntry         OBJECT-TYPE
        SYNTAX          HqosWredEntry
        MAX-ACCESS      not-accessible
        STATUS          current
        DESCRIPTION
            "A list of  entries of WRED information."
        INDEX  { hqosWredProfileName }
    ::= { hqosWredTable 1 }

    HqosWredEntry ::= SEQUENCE {
        hqosWredProfileName          DisplayString,
        hqosWredLevelID              Integer32
        }

    hqosWredProfileName   OBJECT-TYPE
        SYNTAX          DisplayString(SIZE(1..32))
        MAX-ACCESS      read-only
        STATUS          current
        DESCRIPTION
            " The name of a wred profile."
    ::= { hqosWredEntry 1 }

    hqosWredLevelID       OBJECT-TYPE
        SYNTAX 		    Integer32(1..3)
        MAX-ACCESS 	    read-only
        STATUS          current
        DESCRIPTION
            "The level id of a wred profile."
    ::= { hqosWredEntry 2 }

    ----------------------------------------------------------------------
	-- 4.The table of Wred Color info
	----------------------------------------------------------------------

    hqosWredColorTable        OBJECT-TYPE
        SYNTAX         SEQUENCE OF HqosWredColorEntry
        MAX-ACCESS     not-accessible
        STATUS         current
        DESCRIPTION
            "A table that contains WRED Color info."
    ::= { hqos 4 }

    hqosWredColorEntry         OBJECT-TYPE
        SYNTAX          HqosWredColorEntry
        MAX-ACCESS      not-accessible
        STATUS          current
        DESCRIPTION
            "A list of  entries of WRED Color information."
        INDEX  { hqosWredProfileName,
               hqosWredColor }
    ::= { hqosWredColorTable 1 }

    HqosWredColorEntry ::= SEQUENCE {
        hqosWredColor                INTEGER,
        hqosWredMin                  Integer32,
        hqosWredMax                  Integer32,
        hqosWredPercent              Integer32
        }

    hqosWredColor          OBJECT-TYPE
        SYNTAX 		    INTEGER{
                            red(1),
                          	yellow(2),
                          	green(3),
                          	notconfig(4)
                             }
        MAX-ACCESS 	    read-only
        STATUS          current
        DESCRIPTION
            "The color information of a wred profile."
    ::= { hqosWredColorEntry 1 }

    hqosWredMin           OBJECT-TYPE
        SYNTAX 		    Integer32(0..511)
        MAX-ACCESS 	    read-only
        STATUS          current
        DESCRIPTION
            "The min value of a wred profile,its default value is 0."
    ::= { hqosWredColorEntry 2 }

    hqosWredMax           OBJECT-TYPE
        SYNTAX 		    Integer32(0..511)
        MAX-ACCESS 	    read-only
        STATUS          current
        DESCRIPTION
            "The max value of a wred profile,its default value is 500."
    ::= { hqosWredColorEntry 3 }

    hqosWredPercent       OBJECT-TYPE
        SYNTAX 		    Integer32(0..100)
        MAX-ACCESS 	    read-only
        STATUS          current
        DESCRIPTION
            "The percent value of a wred profile,its default value is 0."
    ::= { hqosWredColorEntry 4 }

    ----------------------------------------------------------------------
	-- 5.The table of Wfq info
	----------------------------------------------------------------------
    hqosWfqTable         OBJECT-TYPE
        SYNTAX         SEQUENCE OF HqosWfqEntry
        MAX-ACCESS     not-accessible
        STATUS         current
        DESCRIPTION
            "A table that contains WFQ info."
    ::= { hqos 5 }

    hqosWfqEntry          OBJECT-TYPE
        SYNTAX          HqosWfqEntry
        MAX-ACCESS      not-accessible
        STATUS          current
        DESCRIPTION
            "A list of  entries of WFQ information."
        INDEX  { hqosWfqProfileName  }
    ::= { hqosWfqTable 1 }

    HqosWfqEntry ::= SEQUENCE {
        hqosWfqProfileName          DisplayString,
        hqosWfqLevelID              Integer32,
        hqosWfqWeight               Integer32
        }

    hqosWfqProfileName    OBJECT-TYPE
        SYNTAX          DisplayString(SIZE(1..32))
        MAX-ACCESS      read-only
        STATUS          current
        DESCRIPTION
            " The name of a wfq profile."
    ::= { hqosWfqEntry 1 }

    hqosWfqLevelID        OBJECT-TYPE
        SYNTAX 		    Integer32(1..3)
        MAX-ACCESS 	    read-only
        STATUS          current
        DESCRIPTION
            "The level id of a wfq profile."
    ::= { hqosWfqEntry 2 }

    hqosWfqWeight         OBJECT-TYPE
        SYNTAX 		    Integer32(1..255)
        MAX-ACCESS 	    read-only
        STATUS          current
        DESCRIPTION
            "The weigh value of a wfq profile, its default value is the levelid of this policy."
    ::= { hqosWfqEntry 3 }

    ----------------------------------------------------------------------
	-- 6.The table of Shaping info
	----------------------------------------------------------------------
    hqosShapingTable     OBJECT-TYPE
        SYNTAX         SEQUENCE OF HqosShapingEntry
        MAX-ACCESS     not-accessible
        STATUS         current
        DESCRIPTION
            "A table that contains HQOS Match info."
    ::= { hqos 6 }

    hqosShapingEntry      OBJECT-TYPE
        SYNTAX          HqosShapingEntry
        MAX-ACCESS      not-accessible
        STATUS          current
        DESCRIPTION
            "A list of  entries of HQOS Match information."
        INDEX  { hqosShapingProfileName }
    ::= { hqosShapingTable 1 }

    HqosShapingEntry ::= SEQUENCE {
        hqosShapingProfileName        DisplayString,
        hqosShapingLevelID            Integer32,
        hqosShapingCir                Integer32,
        hqosShapingCbs                Integer32,
        hqosShapingPir                Integer32,
        hqosShapingPbs                Integer32
        }

    hqosShapingProfileName    OBJECT-TYPE
        SYNTAX          DisplayString(SIZE(1..32))
        MAX-ACCESS      read-only
        STATUS          current
        DESCRIPTION
            " The name of a shaping profile."
    ::= { hqosShapingEntry 1 }

    hqosShapingLevelID    OBJECT-TYPE
        SYNTAX 		    Integer32(2..4)
        MAX-ACCESS 	    read-only
        STATUS          current
        DESCRIPTION
            "The level id of a shaping profile."
    ::= { hqosShapingEntry 2 }

    hqosShapingCir        OBJECT-TYPE
        SYNTAX 		    Integer32(180..10000000)
        MAX-ACCESS 	    read-only
        STATUS          current
        DESCRIPTION
            "The cir value of a shaping profile, its default value is 10000000 kbps."
    ::= { hqosShapingEntry 3 }

    hqosShapingCbs        OBJECT-TYPE
        SYNTAX 		    Integer32(1024..16711680)
        MAX-ACCESS 	    read-only
        STATUS          current
        DESCRIPTION
            "The cbs value of a shaping profile, its default value is 16711680 byte."
    ::= { hqosShapingEntry 4 }

    hqosShapingPir        OBJECT-TYPE
        SYNTAX 		    Integer32(180..10000000)
        MAX-ACCESS 	    read-only
        STATUS          current
        DESCRIPTION
            "The pir value of a shaping profile, its default value is 10000000 kbps."
    ::= { hqosShapingEntry 5 }

    hqosShapingPbs        OBJECT-TYPE
        SYNTAX 		    Integer32(1024..16711680)
        MAX-ACCESS 	    read-only
        STATUS          current
        DESCRIPTION
            "The pbs value of a shaping profile, its default value is 16711680 byte."
    ::= { hqosShapingEntry 6 }

    ----------------------------------------------------------------------
	-- 7.The table of Priority info
	----------------------------------------------------------------------

	hqosPriorityTable    OBJECT-TYPE
        SYNTAX         SEQUENCE OF HqosPriorityEntry
        MAX-ACCESS     not-accessible
        STATUS         current
        DESCRIPTION
            "A table that contains HQOS Priority info."
    ::= { hqos 7 }

    hqosPriorityEntry         OBJECT-TYPE
        SYNTAX          HqosPriorityEntry
        MAX-ACCESS      not-accessible
        STATUS          current
        DESCRIPTION
            "A list of  entries of HQOS Priority information."
        INDEX  { hqosPriorityProfileName  }
    ::= { hqosPriorityTable 1 }

    HqosPriorityEntry ::= SEQUENCE {
        hqosPriorityProfileName           DisplayString
                }

    hqosPriorityProfileName   OBJECT-TYPE
        SYNTAX          DisplayString(SIZE(1..32))
        MAX-ACCESS      read-only
        STATUS          current
        DESCRIPTION
            " The name of a priority profile."
    ::= { hqosPriorityEntry 1 }

    ----------------------------------------------------------------------
	-- 8.The table of Priority Flow-class info
	----------------------------------------------------------------------

    hqosPriorityFlowTable    OBJECT-TYPE
        SYNTAX         SEQUENCE OF HqosPriorityFlowEntry
        MAX-ACCESS     not-accessible
        STATUS         current
        DESCRIPTION
            "A table that contains HQOS Priority Flow-class info."
    ::= { hqos 8 }

    hqosPriorityFlowEntry         OBJECT-TYPE
        SYNTAX          HqosPriorityFlowEntry
        MAX-ACCESS      not-accessible
        STATUS          current
        DESCRIPTION
            "A list of  entries of HQOS Priority Flow-class information."
        INDEX  { hqosPriorityProfileName,
               hqosPriorityFlowClass  }
    ::= { hqosPriorityFlowTable 1 }

    HqosPriorityFlowEntry ::= SEQUENCE {
        hqosPriorityFlowClass             INTEGER,
        hqosPriorityMode                  INTEGER,
        hqosPriorityGreen                 DisplayString,
        hqosPriorityYellow                DisplayString
        }

    hqosPriorityFlowClass   OBJECT-TYPE
        SYNTAX 		    INTEGER{
                            be(0),
                          	af1(1),
                          	af2(2),
                          	af3(3),
                          	af4(4),
                          	ef(5),
                          	cs6(6),
                          	cs7(7)
                      }
        MAX-ACCESS 	    read-only
        STATUS          current
        DESCRIPTION
            "The flow class of a priority profile."
    ::= { hqosPriorityFlowEntry 1 }

    hqosPriorityMode      OBJECT-TYPE
        SYNTAX 		    INTEGER{
                            single(0),
                          	dual(1)
                          	}
        MAX-ACCESS 	    read-only
        STATUS          current
        DESCRIPTION
            "The priority mode of a priority profile,its default value is single."
    ::= { hqosPriorityFlowEntry 2 }

	hqosPriorityGreen     OBJECT-TYPE
        SYNTAX 		    DisplayString(SIZE(1..32))
        MAX-ACCESS 	    read-only
        STATUS          current
        DESCRIPTION
            "The priority of the green priority."
    ::= { hqosPriorityFlowEntry 3 }

	hqosPriorityYellow     OBJECT-TYPE
        SYNTAX 		    DisplayString(SIZE(1..32))
        MAX-ACCESS 	    read-only
        STATUS          current
        DESCRIPTION
            "The priority of the yellow priority."
    ::= { hqosPriorityFlowEntry 4 }

    ----------------------------------------------------------------------
	-- 9.The table of HQos info
	----------------------------------------------------------------------

    hqosHQosTable        OBJECT-TYPE
        SYNTAX         SEQUENCE OF HqosHQosEntry
        MAX-ACCESS     not-accessible
        STATUS         current
        DESCRIPTION
            "A table that contains HQOS info."
    ::= { hqos 9 }

    hqosHQosEntry         OBJECT-TYPE
        SYNTAX          HqosHQosEntry
        MAX-ACCESS      not-accessible
        STATUS          current
        DESCRIPTION
            "A list of  entries of HQOS information."
        INDEX  { hqosHQosPolicyName  }
    ::= { hqosHQosTable 1 }

    HqosHQosEntry ::= SEQUENCE {
        hqosHQosPolicyName           DisplayString,
        hqosHQosLevelID              Integer32,
        hqosHQosMode                 INTEGER,
        hqosHQosDiscripString        DisplayString
        }

    hqosHQosPolicyName    OBJECT-TYPE
        SYNTAX          DisplayString(SIZE(1..32))
        MAX-ACCESS      read-only
        STATUS          current
        DESCRIPTION
            " The name of a hqos policy."
    ::= { hqosHQosEntry 1 }

    hqosHQosLevelID       OBJECT-TYPE
        SYNTAX 		    Integer32(1..3)
        MAX-ACCESS 	    read-only
        STATUS          current
        DESCRIPTION
            "The level id a hqos policy."
    ::= { hqosHQosEntry 2 }

    hqosHQosMode          OBJECT-TYPE
        SYNTAX 		    INTEGER{
                           vlan(1),
                           svlan(2)
                           }
        MAX-ACCESS 	    read-only
        STATUS          current
        DESCRIPTION
            "The hqos mode of a hqos policy."
    ::= { hqosHQosEntry 3 }

    hqosHQosDiscripString     OBJECT-TYPE
        SYNTAX          DisplayString(SIZE(1..200))
        MAX-ACCESS      read-only
        STATUS          current
        DESCRIPTION
            " The discription of a hqos policy."
    ::= { hqosHQosEntry 4 }

    ----------------------------------------------------------------------
	-- 10.The table of HQos-Flow class info
	----------------------------------------------------------------------
    hqosHQosFlowTable    OBJECT-TYPE
        SYNTAX         SEQUENCE OF HqosHQosFlowEntry
        MAX-ACCESS     not-accessible
        STATUS         current
        DESCRIPTION
            "A table that contains HQOS-Flow class info."
    ::= { hqos 10 }

    hqosHQosFlowEntry         OBJECT-TYPE
        SYNTAX          HqosHQosFlowEntry
        MAX-ACCESS      not-accessible
        STATUS          current
        DESCRIPTION
            "A list of  entries of HQOS-Flow class information."
        INDEX  { hqosHQosPolicyName,
                hqosHQosFlowClassName }
    ::= { hqosHQosFlowTable 1 }

    HqosHQosFlowEntry ::= SEQUENCE {
        hqosHQosFlowClassName             DisplayString,
        hqosHQosFlowPriority              DisplayString,
        hqosHQosFlowWredProfName          DisplayString,
        hqosHQosFlowWfqProfName           DisplayString,
        hqosHQosFlowShapingProfName       DisplayString,
        hqosHQosFlowPriorityProfName      DisplayString,
        hqosHQosSubPolicyName             DisplayString
        }

    hqosHQosFlowClassName         OBJECT-TYPE
        SYNTAX          DisplayString(SIZE(1..32))
        MAX-ACCESS      read-only
        STATUS          current
        DESCRIPTION
            " The name of a flow class in a hqos policy."
    ::= { hqosHQosFlowEntry 1 }

    hqosHQosFlowPriority          OBJECT-TYPE
        SYNTAX 		    DisplayString(SIZE(1..32))
        MAX-ACCESS 	    read-only
        STATUS          current
        DESCRIPTION
            "The priority of a flow class in a hqos policy, its default value is high."
    ::= { hqosHQosFlowEntry 2 }

    hqosHQosFlowWredProfName      OBJECT-TYPE
        SYNTAX          DisplayString(SIZE(1..32))
        MAX-ACCESS      read-only
        STATUS          current
        DESCRIPTION
            " The name of a wred profile in a hqos policy."
    ::= { hqosHQosFlowEntry 3 }

    hqosHQosFlowWfqProfName    OBJECT-TYPE
        SYNTAX          DisplayString(SIZE(1..32))
        MAX-ACCESS      read-only
        STATUS          current
        DESCRIPTION
            " The name of a wfq profile in a hqos policy."
    ::= { hqosHQosFlowEntry 4 }

    hqosHQosFlowShapingProfName   OBJECT-TYPE
        SYNTAX          DisplayString(SIZE(1..32))
        MAX-ACCESS      read-only
        STATUS          current
        DESCRIPTION
            " The name of a shaping profile in a hqos policy."
    ::= { hqosHQosFlowEntry 5 }

    hqosHQosFlowPriorityProfName   OBJECT-TYPE
        SYNTAX          DisplayString(SIZE(1..32))
        MAX-ACCESS      read-only
        STATUS          current
        DESCRIPTION
            " The name of a priority profile in a hqos policy."
    ::= { hqosHQosFlowEntry 6 }

    hqosHQosSubPolicyName         OBJECT-TYPE
        SYNTAX          DisplayString(SIZE(1..32))
        MAX-ACCESS      read-only
        STATUS          current
        DESCRIPTION
            " The name of sub-policy in a hqos policy."
    ::= { hqosHQosFlowEntry 7 }

    ----------------------------------------------------------------------
	-- 11.The table of HQos Interface class info
	----------------------------------------------------------------------
    hqosHQosInterfaceTable    OBJECT-TYPE
        SYNTAX         SEQUENCE OF HqosHQosInterfaceEntry
        MAX-ACCESS     not-accessible
        STATUS         current
        DESCRIPTION
            "A table that contains HQOS Interface info."
    ::= { hqos 11 }

    hqosHQosInterfaceEntry         OBJECT-TYPE
        SYNTAX          HqosHQosInterfaceEntry
        MAX-ACCESS      not-accessible
        STATUS          current
        DESCRIPTION
            "A list of  entries of HQOS Interface information."
        INDEX  { hqosHQosInterface }
    ::= { hqosHQosInterfaceTable 1 }

    HqosHQosInterfaceEntry ::= SEQUENCE {
        hqosHQosInterface             DisplayString,
        hqosHQosPolicyNameIN          DisplayString,
        hqosInterfaceShapingIN        DisplayString,
        hqosHQosPolicyNameOUT         DisplayString,
        hqosInterfaceShapingOUT       DisplayString
        }

    hqosHQosInterface      OBJECT-TYPE
        SYNTAX          DisplayString(SIZE(1..32))
        MAX-ACCESS      read-only
        STATUS          current
        DESCRIPTION
            " The name of an interface in a hqos policy."
    ::= { hqosHQosInterfaceEntry 1 }

    hqosHQosPolicyNameIN    OBJECT-TYPE
        SYNTAX          DisplayString(SIZE(1..32))
        MAX-ACCESS      read-only
        STATUS          current
        DESCRIPTION
            " The name of a hqos policy, the direction of the interface is in."
    ::= { hqosHQosInterfaceEntry 2 }

    hqosInterfaceShapingIN        OBJECT-TYPE
        SYNTAX          DisplayString(SIZE(1..32))
        MAX-ACCESS      read-only
        STATUS          current
        DESCRIPTION
            " The shaping name of an interface in a hqos policy, and the direction of the interface is in."
    ::= { hqosHQosInterfaceEntry 3 }

    hqosHQosPolicyNameOUT    OBJECT-TYPE
        SYNTAX          DisplayString(SIZE(1..32))
        MAX-ACCESS      read-only
        STATUS          current
        DESCRIPTION
            " The name of a hqos policy, the direction of the interface is out."
    ::= { hqosHQosInterfaceEntry 4 }

    hqosInterfaceShapingOUT        OBJECT-TYPE
        SYNTAX          DisplayString(SIZE(1..32))
        MAX-ACCESS      read-only
        STATUS          current
        DESCRIPTION
            " The shaping name of an interface in a hqos policy, and the direction of the interface is out."
    ::= { hqosHQosInterfaceEntry 5 }


    END
