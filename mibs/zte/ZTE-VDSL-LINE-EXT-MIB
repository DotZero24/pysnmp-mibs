--
-- Zte Dsl Line Ext Mib
--
--

ZTE-VDSL-LINE-EXT-MIB DEFINITIONS ::= BEGIN
    IMPORTS
        MODULE-IDENTITY, OBJECT-TYPE, enterprises,
        TimeTicks,Counter32, Gauge32    FROM SNMPv2-SMI
        MODULE-COMPLIANCE, OBJECT-GROUP FROM SNMPv2-CONF
        SnmpAdminString                 FROM SNMP-FRAMEWORK-MIB
        ifIndex                         FROM IF-MIB
        xdsl2LineConfProfEntry          FROM VDSL2-LINE-MIB
        Xdsl2LineProfiles,Xdsl2LineUs0Mask  FROM VDSL2-LINE-TC-MIB
        RowStatus                       FROM SNMPv2-TC;


-- ZTE vdsl line ext MIB objects

    zxVdsl2ExtMib MODULE-IDENTITY
            LAST-UPDATED "200607071000Z"
            ORGANIZATION "zte dsl product line"
            CONTACT-INFO
                " su chunshan
                  Mail: suchunshan@zte.com.cn
                  Tel : 021-68896292,68896251"
            DESCRIPTION
                "This mib defines extended vdsl line mo (managed object ) for adsl2,
                 adsl+ and dsl loop test.

                 Naming Conventions:
                 Atuc -- (ATUC) modem at near (Central) end of line
                 Atur -- (ATUR) modem at Remote end of line "
    ::= {zxDsl 23}


    zxDsl OBJECT IDENTIFIER ::= { enterprises 3902  1004 }
    zxVdsl2ExtMibObjects OBJECT IDENTIFIER ::= { zxVdsl2ExtMib 1 }



--  Vdsl line Extended Table


--  Vdsl line Config Profile Extended Table

    zxVdsl2LineConfProfExtTable  OBJECT-TYPE
            SYNTAX      SEQUENCE OF zxVdsl2LineConfProfExtEntry
            MAX-ACCESS  not-accessible
            STATUS      current
            DESCRIPTION
                "Vdsl line config profile extended information table."
            ::= {zxVdsl2ExtMibObjects 2}


    zxVdsl2LineConfProfExtEntry  OBJECT-TYPE
            SYNTAX      zxVdsl2LineConfProfExtEntry
            MAX-ACCESS  not-accessible
            STATUS      current
            DESCRIPTION
               "An entry extends the xdsl2LineConfProfEntry defined in
               [RFCxxxx]. Each entry corresponds to an Vdsl line profile."

            AUGMENTS { xdsl2LineConfProfEntry }
            ::= {zxVdsl2LineConfProfExtTable 1}


    zxVdsl2LineConfProfExtEntry ::=
            SEQUENCE {
                zxVdsl2LineConfProfStandardProfile  BITS,
                zxVdsl2LineConfProfUs0Mask	        Xdsl2LineProfiles   --  zte added, 2006-11-27
                }

    zxVdsl2LineConfProfStandardProfile  OBJECT-TYPE
            SYNTAX      Xdsl2LineProfiles
            MAX-ACCESS  read-create
            STATUS      current
            DESCRIPTION
                "The set of profiles which allows the transceivers to support
                a subset of allowed settings, as defined in G.993.2 Recommendation."
            ::= { zxVdsl2LineConfProfExtEntry 1 }


    zxVdsl2LineConfProfUs0Mask  OBJECT-TYPE
            SYNTAX      Xdsl2LineUs0Mask
            MAX-ACCESS  read-create
            STATUS      current
            DESCRIPTION
                "The set of profiles which allows the transceivers to support
                a subset of allowed settings, as defined in G.993.2 Recommendation."
            ::= { zxVdsl2LineConfProfExtEntry 2 }


END
