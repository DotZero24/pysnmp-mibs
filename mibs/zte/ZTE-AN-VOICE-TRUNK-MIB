--------------------------------------------------------------------------
-- File Name : ZTE-AN-VOICE-TRUNK-MIB.mib
-- Date      : 2009-12-01
-- Author    : ZTE Nms dept.

--
-- Zte Voice Trunk Mib for Access Node
--
--------------------------------------------------------------------------

ZTE-AN-VOICE-TRUNK-MIB DEFINITIONS ::= BEGIN

    IMPORTS
        MODULE-IDENTITY,NOTIFICATION-TYPE,OBJECT-TYPE,enterprises,Counter32,Integer32,Counter64,Unsigned32,Gauge32    FROM SNMPv2-SMI
        TEXTUAL-CONVENTION,RowStatus,DisplayString,TruthValue    FROM SNMPv2-TC;

    zxAnVoiceTrunkMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines voice trunk management objects for Access Node."

    ::= { zxAn 5200 }

    zte OBJECT IDENTIFIER ::= { enterprises 3902 }
    zxAn OBJECT IDENTIFIER ::= { zte 1015 }
    msagmajorVersion OBJECT IDENTIFIER ::= { zxAnVoiceTrunkMib 3 }
    msagEmConfig OBJECT IDENTIFIER ::= { msagmajorVersion 11 }

--  zxAnEmCfgTable Definition Begin

    zxAnEmCfgTable OBJECT-TYPE
        SYNTAX  SEQUENCE OF ZxAnEmCfgEntry
        MAX-ACCESS  not-accessible
        STATUS  current
        DESCRIPTION  "The EMC Card Configruation Table"
        ::={msagEmConfig 1}

    zxAnEmCfgEntry OBJECT-TYPE
        SYNTAX  ZxAnEmCfgEntry
        MAX-ACCESS  not-accessible
        STATUS  current
        DESCRIPTION  "An entry in the EMC Card Configuration Table"
        INDEX { zxAnEmRack,zxAnEmShelf,zxAnEmSlot }
        ::={zxAnEmCfgTable 1}

    ZxAnEmCfgEntry::=
        SEQUENCE{
            zxAnEmRack  Integer32,
            zxAnEmShelf  Integer32,
            zxAnEmSlot  Integer32,
            zxAnEmAudioIfType  INTEGER,
            zxAnEmIfType  INTEGER,
            zxAnEmOutGain  Integer32,
            zxAnEmInGain  Integer32
        }

    zxAnEmRack  OBJECT-TYPE
        SYNTAX  Integer32(1..3)
        MAX-ACCESS  not-accessible
        STATUS  current
        DESCRIPTION  "Rack of EMC Card"
        ::= { zxAnEmCfgEntry 1 }

    zxAnEmShelf  OBJECT-TYPE
        SYNTAX  Integer32(1..5)
        MAX-ACCESS  not-accessible
        STATUS  current
        DESCRIPTION  "Shelf of EMC Card"
        ::= { zxAnEmCfgEntry 2 }

    zxAnEmSlot  OBJECT-TYPE
        SYNTAX  Integer32(1..24)
        MAX-ACCESS  not-accessible
        STATUS  current
        DESCRIPTION  "Slot of EMC Card"
        ::= { zxAnEmCfgEntry 3 }

    zxAnEmAudioIfType OBJECT-TYPE
        SYNTAX  INTEGER{
            twoWire(2),
            fourWire(4)
        }
        MAX-ACCESS  read-write
        STATUS  current
        DESCRIPTION
            "There are two distinct types of audio interface(two-wire or four-wire). These implementations describe the number of wires used in order to transmit audio signals.
            The values mean:
            two-wire
                With the two-wire implementation, full-duplex audio signals are transmitted over a single pair which consists of tip(T) and ring(R)leads.
            four-wire
                The four-wire implementation provides separate paths to receive and send audio signals which consists of T, R and T1, R1 leads."
        DEFVAL{4}
        ::= { zxAnEmCfgEntry 4 }

    zxAnEmIfType  OBJECT-TYPE
        SYNTAX  INTEGER{
            emTypeI(1),
            emTypeV(5)
        }
        MAX-ACCESS  read-write
        STATUS  current
        DESCRIPTION
            "This variable represents the EM interface type.
            The values mean:
            em-type-I
                This is the most common interface in North America. Type I uses two leads for supervisor signaling: E and M. During inactivity, the E-lead is open and the M-lead is connected to the ground. The Trunk Circuit Side connects the M-lead to the battery in order to indicate the off-hook condition. The Signaling Unit connect the E-lead to the ground in order to indicate the off-hook condition.
            em-type-V
                Type V is symmetrical and allows two signaling nodes to be connected back-to-back. This is the most common interface type used outside of North America. Type V uses two leads for supervisor signaling: E and M. During inactivity the E-lead and M-lead are open. The Trunk Circuit connects the M-lead to the ground in order to indicate the off-hook condition. The signaling Unit connects the E-lead to the ground in order to indicate off-hook condition."
        DEFVAL{5}
        ::= { zxAnEmCfgEntry 5 }

    zxAnEmOutGain  OBJECT-TYPE
        SYNTAX  Integer32(0..12)
        MAX-ACCESS  read-write
        STATUS  current
        DESCRIPTION  "Configure the output gain for voice."
        DEFVAL{3}
        ::= { zxAnEmCfgEntry 6 }

    zxAnEmInGain  OBJECT-TYPE
        SYNTAX  Integer32(0..12)
        MAX-ACCESS  read-write
        STATUS  current
        DESCRIPTION  "Configure the input gain for voice"
        DEFVAL{3}
        ::= { zxAnEmCfgEntry 7 }

--  End of zxAnEmCfgTable

END
