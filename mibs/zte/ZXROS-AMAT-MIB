--  ******************************************************
--  $Id: zxrosAMAT.mib  2006-05-25 14:10:20  zhongyan$
--
--  zxrosAMAT.mib: zxros 18&28&38 AMAT MIB file
--
--  May 2006, zhongyan
--
--  Copyright(c) 2006 by ZTE Corporation
--  All rights reservered
--
--
--  ******************************************************

ZXROS-AMAT-MIB DEFINITIONS ::= BEGIN

IMPORTS
    MODULE-IDENTITY,
    OBJECT-TYPE,
    Integer32
        FROM SNMPv2-SMI
    enterprises
        FROM SNMPv2-SMI
    RowStatus
        FROM SNMPv2-TC
    TimeTicks, IpAddress
        FROM RFC1155-SMI;


    zte OBJECT IDENTIFIER ::= { enterprises 3902 }
    zxros  OBJECT IDENTIFIER ::= { zte 100 }
    zxrosAMAT OBJECT IDENTIFIER ::= { zxros 1000 }


    DisplayString ::= OCTET STRING
    --  This data type is used to model textual information taken
    --  from the NVT ASCII character set.  By convention, objects
    --  with this syntax are declared as having
    --  SIZE (0..255)

zxrosAMATconfig OBJECT IDENTIFIER ::= { zxrosAMAT 1 }

    -- mib object in zxrosAMATconfig group
       zxrosAMATAttackAgingTime OBJECT-TYPE
              SYNTAX  Integer32
              MAX-ACCESS  read-write
              STATUS  current
              DESCRIPTION
                      "An 32 bit unsigned integer description of the zxrosAMATAttackAgingTime."
              ::= { zxrosAMATconfig 1 }

       zxrosAMATState OBJECT-TYPE
              SYNTAX  INTEGER{enable(1),disable(0)}
              MAX-ACCESS  read-write
              STATUS  current
              DESCRIPTION
                      "Using enable and disable to describe amat state."
              ::= { zxrosAMATconfig 2 }

       zxrosAMATHashOverNum OBJECT-TYPE
              SYNTAX  Integer32
              MAX-ACCESS  read-write
              STATUS  current
              DESCRIPTION
                      "An 32 bit unsigned integer description of the zxrosAMATHashOverNum."
              ::= { zxrosAMATconfig 3 }

       zxrosAMATHashUpdateTime OBJECT-TYPE
              SYNTAX  Integer32
              MAX-ACCESS  read-write
              STATUS  current
              DESCRIPTION
                      "An 32 bit unsigned integer description of the zxrosAMATHashUpdateTime."
              ::= { zxrosAMATconfig 4 }

       zxrosAMATIcmpConn OBJECT-TYPE
              SYNTAX  Integer32
              MAX-ACCESS  read-write
              STATUS  current
              DESCRIPTION
                      "An 32 bit unsigned integer description of the zxrosAMATIcmpConn."
              ::= { zxrosAMATconfig 5 }

       zxrosAMATIcmpRate OBJECT-TYPE
              SYNTAX  Integer32
              MAX-ACCESS  read-write
              STATUS  current
              DESCRIPTION
                      "An 32 bit unsigned integer description of the zxrosAMATIcmpRate."
              ::= { zxrosAMATconfig 6 }

       zxrosAMATIntervalSampleRate OBJECT-TYPE
              SYNTAX  Integer32
              MAX-ACCESS  read-write
              STATUS  current
              DESCRIPTION
                      "An 32 bit unsigned integer description of the zxrosAMATIntervalSampleRate."
              ::= { zxrosAMATconfig 7 }

       zxrosAMATLogging OBJECT-TYPE
              SYNTAX  INTEGER{on(1),off(0)}
              MAX-ACCESS  read-write
              STATUS  current
              DESCRIPTION
                      "Using on and off to describe amat Logging state."
              ::= { zxrosAMATconfig 8 }

       zxrosAMATRateLimit OBJECT-TYPE
              SYNTAX  Integer32
              MAX-ACCESS  read-write
              STATUS  current
              DESCRIPTION
                      "An 32 bit unsigned integer description of the zxrosAMATRateLimit."
              ::= { zxrosAMATconfig 9 }

       zxrosAMATRuleUpdateTime OBJECT-TYPE
              SYNTAX  Integer32
              MAX-ACCESS  read-write
              STATUS  current
              DESCRIPTION
                      "An 32 bit unsigned integer description of the zxrosAMATRuleUpdateTime."
              ::= { zxrosAMATconfig 10 }

       zxrosAMATSampleCode OBJECT-TYPE
              SYNTAX  Integer32
              MAX-ACCESS  read-write
              STATUS  current
              DESCRIPTION
                      "An 32 bit unsigned integer description of the zxrosAMATSampleCode."
              ::= { zxrosAMATconfig 11 }

       zxrosAMATSampleMatchCode OBJECT-TYPE
              SYNTAX  Integer32
              MAX-ACCESS  read-write
              STATUS  current
              DESCRIPTION
                      "An 32 bit unsigned integer description of the zxrosAMATSampleMatchCode."
              ::= { zxrosAMATconfig 12 }

       zxrosAMATTcpConn OBJECT-TYPE
              SYNTAX  Integer32
              MAX-ACCESS  read-write
              STATUS  current
              DESCRIPTION
                      "An 32 bit unsigned integer description of the zxrosAMATTcpConn."
              ::= { zxrosAMATconfig 13 }

       zxrosAMATTcpProportion OBJECT-TYPE
              SYNTAX  Integer32
              MAX-ACCESS  read-write
              STATUS  current
              DESCRIPTION
                      "An 32 bit unsigned integer description of the zxrosAMATTcpProportion."
              ::= { zxrosAMATconfig 14 }

       zxrosAMATTcpRate OBJECT-TYPE
              SYNTAX  Integer32
              MAX-ACCESS  read-write
              STATUS  current
              DESCRIPTION
                      "An 32 bit unsigned integer description of the zxrosAMATTcpRate."
              ::= { zxrosAMATconfig 15 }

       zxrosAMATUdpConn OBJECT-TYPE
              SYNTAX  Integer32
              MAX-ACCESS  read-write
              STATUS  current
              DESCRIPTION
                      "An 32 bit unsigned integer description of the zxrosAMATUdpConn."
              ::= { zxrosAMATconfig 16 }

       zxrosAMATUdpRate OBJECT-TYPE
              SYNTAX  Integer32
              MAX-ACCESS  read-write
              STATUS  current
              DESCRIPTION
                      "An 32 bit unsigned integer description of the zxrosAMATUdpRate."
              ::= { zxrosAMATconfig 17 }

zxrosAMATIgnoreIpAddressTable  OBJECT-TYPE
        SYNTAX  SEQUENCE OF ZxrosAMATIgnoreIpAddressEntry
        MAX-ACCESS  not-accessible
        STATUS  current
        DESCRIPTION
            "AMAT ignore ip address table"
        ::= { zxrosAMAT 2 }

zxrosAMATIgnoreIpAddressEntry  OBJECT-TYPE
        SYNTAX  ZxrosAMATIgnoreIpAddressEntry
        MAX-ACCESS  not-accessible
        STATUS  current
        DESCRIPTION
            "AMAT ignore ip address entry"
        INDEX  { zxrosAMATIgnoreIpAddressIpAddress, zxrosAMATIgnoreIpAddressVpnName }
        ::= { zxrosAMATIgnoreIpAddressTable 1 }

 ZxrosAMATIgnoreIpAddressEntry ::=
     SEQUENCE {
         zxrosAMATIgnoreIpAddressIpAddress
             IpAddress,
         zxrosAMATIgnoreIpAddressVpnName
             DisplayString,
         zxrosAMATIgnoreIpAddressRowStatus
             RowStatus
 }

 zxrosAMATIgnoreIpAddressIpAddress  OBJECT-TYPE
        SYNTAX   IpAddress
        MAX-ACCESS  read-only
        STATUS  current
        DESCRIPTION
            "AMAT ignore ip address."
        ::= { zxrosAMATIgnoreIpAddressEntry 1 }

 zxrosAMATIgnoreIpAddressVpnName  OBJECT-TYPE
        SYNTAX   DisplayString
        MAX-ACCESS  read-only
        STATUS  current
        DESCRIPTION
            "A string description of the zxrosAMATIgnoreIpAddressVpnName."
        ::= { zxrosAMATIgnoreIpAddressEntry 2 }

 zxrosAMATIgnoreIpAddressRowStatus  OBJECT-TYPE
        SYNTAX          RowStatus
        MAX-ACCESS      read-write
        STATUS          current
        DESCRIPTION
              "This variable is used to create, modify, and/or delete a row in this table."
        ::= { zxrosAMATIgnoreIpAddressEntry  3 }

 zxrosAMATAttackLoggingTable  OBJECT-TYPE
        SYNTAX  SEQUENCE OF ZxrosAMATAttackLoggingEntry
        MAX-ACCESS  not-accessible
        STATUS  current
        DESCRIPTION
            "AMAT attack logging table"
        ::= { zxrosAMAT 3 }

 zxrosAMATAttackLoggingEntry  OBJECT-TYPE
        SYNTAX  ZxrosAMATAttackLoggingEntry
        MAX-ACCESS  not-accessible
        STATUS  current
        DESCRIPTION
            "AMAT attack logging entry"
        INDEX  { zxrosAMATAttackLoggingNo }
        ::= { zxrosAMATAttackLoggingTable 1 }

 ZxrosAMATAttackLoggingEntry ::=
     SEQUENCE {
         zxrosAMATAttackLoggingNo
             INTEGER,
         zxrosAMATAttackDetectedTime
             TimeTicks,
         zxrosAMATAttackOverTime
             TimeTicks,
         zxrosAMATVpnName
             DisplayString,
         zxrosAMATIpAddress
             IpAddress,
         zxrosAMATAttackMode
             DisplayString,
         zxrosAMATTcpPassPacket
             Integer32,
         zxrosAMATTcpFilterPacket
             Integer32,
         zxrosAMATUdpPassPacket
             Integer32,
         zxrosAMATUdpFilterPacket
             Integer32,
         zxrosAMATIcmpPassPacket
             Integer32,
         zxrosAMATIcmpFilterPacket
             Integer32,
         zxrosAMATTcpAttackOverValue
             Integer32,
         zxrosAMATUdpAttackOverValue
             Integer32,
         zxrosAMATIcmpAttackOverValue
             Integer32,
         zxrosAMATPassPacketsBeforeRuleCreated
             Integer32
 }

 zxrosAMATAttackLoggingNo  OBJECT-TYPE
        SYNTAX   INTEGER
        MAX-ACCESS  read-only
        STATUS  current
        DESCRIPTION
            "An 32 bit unsigned integer description of the zxrosAMATAttackLoggingNo."
        ::= { zxrosAMATAttackLoggingEntry 1 }

 zxrosAMATAttackDetectedTime  OBJECT-TYPE
        SYNTAX   TimeTicks
        MAX-ACCESS  read-only
        STATUS  current
        DESCRIPTION
            "The time when attack is been detected."
        ::= { zxrosAMATAttackLoggingEntry 2 }

 zxrosAMATAttackOverTime  OBJECT-TYPE
        SYNTAX   TimeTicks
        MAX-ACCESS  read-only
        STATUS  current
        DESCRIPTION
            "The time when attack is over."
        ::= { zxrosAMATAttackLoggingEntry 3 }

 zxrosAMATVpnName  OBJECT-TYPE
        SYNTAX   DisplayString
        MAX-ACCESS  read-only
        STATUS  current
        DESCRIPTION
            "A string description of the zxrosAMATVpnName."
        ::= { zxrosAMATAttackLoggingEntry 4 }

 zxrosAMATIpAddress  OBJECT-TYPE
        SYNTAX   IpAddress
        MAX-ACCESS  read-only
        STATUS  current
        DESCRIPTION
            "AMAT ignore ip address."
        ::= { zxrosAMATAttackLoggingEntry 5 }

 zxrosAMATAttackMode  OBJECT-TYPE
        SYNTAX   DisplayString
        MAX-ACCESS  read-only
        STATUS  current
        DESCRIPTION
            "A string description of the zxrosAMATAttackMode."
        ::= { zxrosAMATAttackLoggingEntry 6 }

 zxrosAMATTcpPassPacket  OBJECT-TYPE
        SYNTAX   Integer32
        MAX-ACCESS  read-only
        STATUS  current
        DESCRIPTION
            "An 32 bit unsigned integer description of the zxrosAMATTcpPassPacket."
        ::= { zxrosAMATAttackLoggingEntry 7 }

 zxrosAMATTcpFilterPacket  OBJECT-TYPE
        SYNTAX   Integer32
        MAX-ACCESS  read-only
        STATUS  current
        DESCRIPTION
            "An 32 bit unsigned integer description of the zxrosAMATTcpFilterPacket."
        ::= { zxrosAMATAttackLoggingEntry 8 }

 zxrosAMATUdpPassPacket  OBJECT-TYPE
        SYNTAX   Integer32
        MAX-ACCESS  read-only
        STATUS  current
        DESCRIPTION
            "An 32 bit unsigned integer description of the zxrosAMATUdpPassPacket."
        ::= { zxrosAMATAttackLoggingEntry 9 }

 zxrosAMATUdpFilterPacket  OBJECT-TYPE
        SYNTAX   Integer32
        MAX-ACCESS  read-only
        STATUS  current
        DESCRIPTION
            "An 32 bit unsigned integer description of the zxrosAMATUdpFilterPacket."
        ::= { zxrosAMATAttackLoggingEntry 10 }

  zxrosAMATIcmpPassPacket  OBJECT-TYPE
        SYNTAX   Integer32
        MAX-ACCESS  read-only
        STATUS  current
        DESCRIPTION
            "An 32 bit unsigned integer description of the zxrosAMATIcmpPassPacket."
        ::= { zxrosAMATAttackLoggingEntry 11 }

 zxrosAMATIcmpFilterPacket  OBJECT-TYPE
        SYNTAX   Integer32
        MAX-ACCESS  read-only
        STATUS  current
        DESCRIPTION
            "An 32 bit unsigned integer description of the zxrosAMATIcmpFilterPacket."
        ::= { zxrosAMATAttackLoggingEntry 12 }

 zxrosAMATTcpAttackOverValue  OBJECT-TYPE
        SYNTAX   Integer32
        MAX-ACCESS  read-only
        STATUS  current
        DESCRIPTION
            "An 32 bit unsigned integer description of the zxrosAMATTcpAttackOverValue."
        ::= { zxrosAMATAttackLoggingEntry 13 }

 zxrosAMATUdpAttackOverValue  OBJECT-TYPE
        SYNTAX   Integer32
        MAX-ACCESS  read-only
        STATUS  current
        DESCRIPTION
            "An 32 bit unsigned integer description of the zxrosAMATUdpAttackOverValue."
        ::= { zxrosAMATAttackLoggingEntry 14 }

 zxrosAMATIcmpAttackOverValue  OBJECT-TYPE
        SYNTAX   Integer32
        MAX-ACCESS  read-only
        STATUS  current
        DESCRIPTION
            "An 32 bit unsigned integer description of the zxrosAMATIcmpAttackOverValue."
        ::= { zxrosAMATAttackLoggingEntry 15 }

 zxrosAMATPassPacketsBeforeRuleCreated  OBJECT-TYPE
        SYNTAX   Integer32
        MAX-ACCESS  read-only
        STATUS  current
        DESCRIPTION
            "An 32 bit unsigned integer description of the zxrosAMATPassPacketsBeforeRuleCreated."
        ::= { zxrosAMATAttackLoggingEntry 16 }

 zxrosAMATShutDownLoggingTable  OBJECT-TYPE
        SYNTAX  SEQUENCE OF ZxrosAMATShutDownLoggingEntry
        MAX-ACCESS  not-accessible
        STATUS  current
        DESCRIPTION
            "AMAT shut down logging table"
        ::= { zxrosAMAT 4 }

 zxrosAMATShutDownLoggingEntry  OBJECT-TYPE
        SYNTAX  ZxrosAMATShutDownLoggingEntry
        MAX-ACCESS  not-accessible
        STATUS  current
        DESCRIPTION
            "AMAT shut down logging entry"
        INDEX  { zxrosAMATShutDownLoggingNo }
        ::= { zxrosAMATShutDownLoggingTable 1 }

 ZxrosAMATShutDownLoggingEntry ::=
     SEQUENCE {
         zxrosAMATShutDownLoggingNo
             Integer32,
         zxrosAMATStartUpTime
             TimeTicks,
         zxrosAMATShutDownTime
             TimeTicks,
         zxrosAMATNoAmatPackets
             Integer32,
         zxrosAMATTotalPassPackets
             Integer32,
         zxrosAMATTotalFilterPackets
             Integer32,
         zxrosAMATTcpPassPackets
             Integer32,
         zxrosAMATTcpFilterPackets
             Integer32,
         zxrosAMATUdpPassPackets
             Integer32,
         zxrosAMATUdpFilterPackets
             Integer32,
         zxrosAMATIcmpPassPackets
             Integer32,
         zxrosAMATIcmpFilterPackets
             Integer32
 }

 zxrosAMATShutDownLoggingNo  OBJECT-TYPE
        SYNTAX   Integer32
        MAX-ACCESS  read-only
        STATUS  current
        DESCRIPTION
            "An 32 bit unsigned integer description of the zxrosAMATShutDownLoggingNo."
        ::= { zxrosAMATShutDownLoggingEntry 1 }

 zxrosAMATStartUpTime  OBJECT-TYPE
        SYNTAX   TimeTicks
        MAX-ACCESS  read-only
        STATUS  current
        DESCRIPTION
            "The time when AMAT module is start up."
        ::= { zxrosAMATShutDownLoggingEntry 2 }

 zxrosAMATShutDownTime  OBJECT-TYPE
        SYNTAX   TimeTicks
        MAX-ACCESS  read-only
        STATUS  current
        DESCRIPTION
            "The time when AMAT module is shut down."
        ::= { zxrosAMATShutDownLoggingEntry 3 }

 zxrosAMATNoAmatPackets  OBJECT-TYPE
        SYNTAX   Integer32
        MAX-ACCESS  read-only
        STATUS  current
        DESCRIPTION
            "An 32 bit unsigned integer description of the zxrosAMATNoAmatPackets."
        ::= { zxrosAMATShutDownLoggingEntry 4 }

 zxrosAMATTotalPassPackets  OBJECT-TYPE
        SYNTAX   Integer32
        MAX-ACCESS  read-only
        STATUS  current
        DESCRIPTION
            "An 32 bit unsigned integer description of the zxrosAMATTotalPassPackets."
        ::= { zxrosAMATShutDownLoggingEntry 5 }

 zxrosAMATTotalFilterPackets  OBJECT-TYPE
        SYNTAX   Integer32
        MAX-ACCESS  read-only
        STATUS  current
        DESCRIPTION
            "An 32 bit unsigned integer description of the zxrosAMATTotalFilterPackets."
        ::= { zxrosAMATShutDownLoggingEntry 6 }

 zxrosAMATTcpPassPackets  OBJECT-TYPE
        SYNTAX   Integer32
        MAX-ACCESS  read-only
        STATUS  current
        DESCRIPTION
            "An 32 bit unsigned integer description of the zxrosAMATTcpPassPackets."
        ::= { zxrosAMATShutDownLoggingEntry 7 }

 zxrosAMATTcpFilterPackets  OBJECT-TYPE
        SYNTAX   Integer32
        MAX-ACCESS  read-only
        STATUS  current
        DESCRIPTION
            "An 32 bit unsigned integer description of the zxrosAMATTcpFilterPackets."
        ::= { zxrosAMATShutDownLoggingEntry 8 }

 zxrosAMATUdpPassPackets  OBJECT-TYPE
        SYNTAX   Integer32
        MAX-ACCESS  read-only
        STATUS  current
        DESCRIPTION
            "An 32 bit unsigned integer description of the zxrosAMATUdpPassPackets."
        ::= { zxrosAMATShutDownLoggingEntry 9 }

 zxrosAMATUdpFilterPackets  OBJECT-TYPE
        SYNTAX   Integer32
        MAX-ACCESS  read-only
        STATUS  current
        DESCRIPTION
            "An 32 bit unsigned integer description of the zxrosAMATUdpFilterPackets."
        ::= { zxrosAMATShutDownLoggingEntry 10 }

 zxrosAMATIcmpPassPackets  OBJECT-TYPE
        SYNTAX   Integer32
        MAX-ACCESS  read-only
        STATUS  current
        DESCRIPTION
            "An 32 bit unsigned integer description of the zxrosAMATIcmpPassPackets."
        ::= { zxrosAMATShutDownLoggingEntry 11 }

 zxrosAMATIcmpFilterPackets  OBJECT-TYPE
        SYNTAX   Integer32
        MAX-ACCESS  read-only
        STATUS  current
        DESCRIPTION
            "An 32 bit unsigned integer description of the zxrosAMATIcmpFilterPackets."
        ::= { zxrosAMATShutDownLoggingEntry 12 }

        END
