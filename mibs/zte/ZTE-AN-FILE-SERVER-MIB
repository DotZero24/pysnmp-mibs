ZTE-AN-FILE-SERVER-MIB    DEFINITIONS ::= BEGIN
    IMPORTS
        RowStatus                         FROM SNMPv2-TC
        DisplayString                     FROM SNMPv2-TC
        TruthValue                        FROM SNMPv2-TC
        MODULE-IDENTITY                   FROM SNMPv2-SMI
        OBJECT-TYPE                       FROM SNMPv2-SMI
        Integer32                         FROM SNMPv2-SMI
        IpAddress                         FROM SNMPv2-SMI
        Counter64                         FROM SNMPv2-SMI
        Unsigned32                        FROM SNMPv2-SMI
        NOTIFICATION-TYPE                 FROM SNMPv2-SMI
        InetAddressType                   FROM INET-ADDRESS-MIB
        InetAddress                       FROM INET-ADDRESS-MIB
        MODULE-COMPLIANCE                 FROM SNMPv2-CONF
        OBJECT-GROUP                      FROM SNMPv2-CONF
        NOTIFICATION-GROUP                FROM SNMPv2-CONF
        zxAn                              FROM ZTE-AN-TC-MIB;


    zxAnFileServerMib  MODULE-IDENTITY
        LAST-UPDATED    "201105260000Z"
        ORGANIZATION    "ZTE Corporation"
        CONTACT-INFO    "Zhou YuBin     ZTE Corporation
                         Mail: zhou.yubing@zte.com.cn
                         Tel : +86-21-68897315"
        DESCRIPTION     "This MIB defines zte Access Node file server
                        configuration."

        REVISION        "201105260000Z"
        DESCRIPTION
        "Initial version of this MIB module."
        ::=  {  zxAn  17  }

-------------------------------------------------------------------------------
-- Following management objects are defined.
-- 1. File Server Group Management Table
-- 2. File Server Management Table

-- Following conformance information is defined.
-- 21. File Server Conformance

-------------------------------------------------------------------------------

    zxAnFileServerObjects OBJECT IDENTIFIER ::= { zxAnFileServerMib  2  }

-------------------------------------------------------------------------------
-- 1. File Server Group Management Table
-------------------------------------------------------------------------------
    zxAnFileServerGroupTable   OBJECT-TYPE
        SYNTAX          SEQUENCE  OF  ZxAnFileServerGroupEntry
        MAX-ACCESS      not-accessible
        STATUS          current
        DESCRIPTION
            "File server group configuration table."
        ::=  { zxAnFileServerObjects  2 }

    zxAnFileServerGroupEntry   OBJECT-TYPE
        SYNTAX          ZxAnFileServerGroupEntry
        MAX-ACCESS      not-accessible
        STATUS          current
        DESCRIPTION
            "File server configuration entry."
        INDEX   { zxAnFileServerGroupUsage }
        ::=  { zxAnFileServerGroupTable 1 }

    ZxAnFileServerGroupEntry  ::=  SEQUENCE {
        zxAnFileServerGroupUsage           INTEGER,
        zxAnFileServerGroupWorkMode        INTEGER
        }

    zxAnFileServerGroupUsage       OBJECT-TYPE
        SYNTAX          INTEGER  {
            autoBackupConfiguration(1),
            manualBackupConfiguration(2),
            autoBackupLog(3),
            manualBackupLog(4),
            autoBackupSoftware(5),
            manualBackupSoftware(6),
            downloadPerformance(7),
            uploadPerformance(8),
            autoUpdateSoftware(31)
        }
        MAX-ACCESS      not-accessible
        STATUS          current
        DESCRIPTION
            "File server usage.
            autoBackupConfiguration(1),   File server configure for auto backup
                                          configuration
            manualBackupConfiguration(2), File server configure for manual
                                          backup configuration
            autoBackupLog(3),             File server configure for auto backup
                                          log
            manualBackupLog(4),           File server configure for manual
                                          backup log
            autoBackupSoftware(5),        File server configure for auto backup
                                          software
            manualBackupSoftware(6),      File server configure for manual
                                          backup software
            downloadPerformance(7),       File server configure for download
                                          performance
            uploadPerformance(8),         File server configure for upload
                                          backup performance
            autoUpdateSoftware(31)        File server configure for software
                                          automatic update
            "
        ::=  {  zxAnFileServerGroupEntry  1  }

    zxAnFileServerGroupWorkMode       OBJECT-TYPE
        SYNTAX          INTEGER{
            roundRobin(1)
        }
        MAX-ACCESS      read-write
        STATUS          current
        DESCRIPTION     "File server group work mode."
        ::=  {  zxAnFileServerGroupEntry  2  }

-------------------------------------------------------------------------------
--2. File Server Management Table
-------------------------------------------------------------------------------

    zxAnFileServerTable   OBJECT-TYPE
        SYNTAX          SEQUENCE  OF  ZxAnFileServerEntry
        MAX-ACCESS      not-accessible
        STATUS          current
        DESCRIPTION
            "File server configuration table."
        ::=  { zxAnFileServerObjects  3 }

    zxAnFileServerEntry   OBJECT-TYPE
        SYNTAX          ZxAnFileServerEntry
        MAX-ACCESS      not-accessible
        STATUS          current
        DESCRIPTION
            "File server configuration entry.

            The multi-variables binding rule should be complied with when a
            manager configure a file server. According to this rule, all the
            related mib variables must be included in one SNMP set operation.

            There are two types of variables: mandatory and optional.
            All of the mandatory variables must be included in one SNMP set
            operation. Optional variables may be included in one SNMP set
            operation with the mandatory variables, but must not be used alone.

            To configure a file server, there are several cases based on the
            variable zxAnFileServerGroupUsage and zxAnFileServerIndex.
            The mandatory and optional variables are same in each case.

            mandatoty: zxAnFileServerIpAddressType, zxAnFileServerIpAddress,
                       zxAnFileServerProtocolType,zxAnFileServerUserName,
                       zxAnFileServerUserPwd
            optional : none
            "

        INDEX   { zxAnFileServerGroupUsage, zxAnFileServerIndex}
        ::=  { zxAnFileServerTable 1 }

    ZxAnFileServerEntry  ::=  SEQUENCE {
        zxAnFileServerIndex             Integer32,
        zxAnFileServerIpAddressType     InetAddressType,
        zxAnFileServerIpAddress         InetAddress,
        zxAnFileServerProtocolType      INTEGER,
        zxAnFileServerUserName          DisplayString,
        zxAnFileServerUserPwd           DisplayString,
        zxAnFileServerPath              DisplayString
        }

    zxAnFileServerIndex       OBJECT-TYPE
        SYNTAX          Integer32(1..2)
        MAX-ACCESS      not-accessible
        STATUS          current
        DESCRIPTION     "File server primary/secondary status, if primary
                        server is invaild, try secondary server."
        ::=  {  zxAnFileServerEntry  1  }

    zxAnFileServerIpAddressType  OBJECT-TYPE
        SYNTAX          InetAddressType
        MAX-ACCESS      read-write
        STATUS          current
        DESCRIPTION
            "IP address type of the file server."
        DEFVAL  { ipv4 }
        ::=  {  zxAnFileServerEntry  2  }

    zxAnFileServerIpAddress  OBJECT-TYPE
        SYNTAX          InetAddress
        MAX-ACCESS      read-write
        STATUS          current
        DESCRIPTION
            "IP address of the file server.
            NE returns 0.0.0.0 when it's unconfigured
            and IP address type is IPv4. Not support IPv6 presently."
        ::=  {  zxAnFileServerEntry  3  }

    zxAnFileServerProtocolType       OBJECT-TYPE
        SYNTAX          INTEGER {
            ftp(1),
            sftp(2),
            none(3)
        }
        MAX-ACCESS      read-write
        STATUS          current
        DESCRIPTION
            "Protocol type of the file server.
            ftp(1):    File Transfer Protocol
            sftp(2):   Ssh File Transfer Protocol
            none(3):   Protocol is not configure
            "
        DEFVAL  { ftp }
        ::=  {  zxAnFileServerEntry  4 }

    zxAnFileServerUserName   OBJECT-TYPE
        SYNTAX          DisplayString  ( SIZE ( 0 .. 32  ) )
        MAX-ACCESS      read-write
        STATUS          current
        DESCRIPTION
            "User name of the file server.
            NE returns empty string when it's unconfigured.
            "
        ::=  {  zxAnFileServerEntry  5  }

    zxAnFileServerUserPwd    OBJECT-TYPE
        SYNTAX          DisplayString  ( SIZE ( 0 .. 32  ) )
        MAX-ACCESS      read-write
        STATUS          current
        DESCRIPTION
            "User password of the file server.
            NE returns empty string when it's unconfigured."
        ::=  {  zxAnFileServerEntry  6  }

    zxAnFileServerPath   OBJECT-TYPE
        SYNTAX          DisplayString  ( SIZE ( 0 .. 255  ) )
        MAX-ACCESS      read-write
        STATUS          current
        DESCRIPTION
            "File path which starts from the root directory.
            NE returns empty string when it's unconfigured."
        ::=  {  zxAnFileServerEntry  7 }

-------------------------------------------------------------------------------
-- 21. zxAnBackupMgmtConformance
-------------------------------------------------------------------------------
    zxAnFileServerConformance OBJECT IDENTIFIER::={zxAnFileServerMib         4}

    zxAnFileServerCompliances OBJECT IDENTIFIER::={zxAnFileServerConformance 1}
    zxAnFileServerGroups      OBJECT IDENTIFIER::={zxAnFileServerConformance 2}

    zxAnFileServerCompliance MODULE-COMPLIANCE
        STATUS current
        DESCRIPTION
            "The compliance statement for SNMP entities which implement the
            ZTE-AN-FILE-SERVER-MGMT-MIB."
        MODULE -- this module

            MANDATORY-GROUPS {
                  zxAnFileServerGroupGroup,
                  zxAnFileServerGroup
                }
        ::= { zxAnFileServerCompliances 1 }

    zxAnFileServerGroupGroup OBJECT-GROUP
        OBJECTS { zxAnFileServerGroupWorkMode
        }
        STATUS current
        DESCRIPTION
            "The collection of objects which are used to set file server
            configuration group."
        ::= { zxAnFileServerGroups 1 }

    zxAnFileServerGroup OBJECT-GROUP
        OBJECTS { zxAnFileServerIpAddressType,
                  zxAnFileServerIpAddress,
                  zxAnFileServerProtocolType,
                  zxAnFileServerUserName,
                  zxAnFileServerUserPwd,
                  zxAnFileServerPath
        }
        STATUS current
        DESCRIPTION
            "The collection of objects which are used to set file server
            configuration for automatic software updating and file backup."
        ::= { zxAnFileServerGroups 2 }

END
