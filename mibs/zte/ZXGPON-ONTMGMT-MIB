-- *****************************************************************
-- ZTE GPON ONT MANAGEMENT MIB
--
-- 12-26-2006
--
-- Copyright(c) 2006 ZTE Corporation
-- All rights reserved.
-- *****************************************************************

ZXGPON-ONTMGMT-MIB DEFINITIONS ::= BEGIN
    IMPORTS
        enterprises                      FROM RFC1155-SMI
        RowStatus                        FROM SNMPv2-TC
        TruthValue                       FROM SNMPv2-TC
        InetAddress,InetAddressType      FROM INET-ADDRESS-MIB
        IpAddress,Integer32              FROM SNMPv2-SMI
        Unsigned32                       FROM SNMPv2-SMI
        Counter64                        FROM SNMPv2-SMI
        MacAddress                       FROM SNMPv2-TC
        TEXTUAL-CONVENTION               FROM SNMPv2-TC
        MODULE-IDENTITY                  FROM SNMPv2-SMI
        OBJECT-TYPE                      FROM SNMPv2-SMI
        NOTIFICATION-TYPE                FROM SNMPv2-SMI
        DisplayString                    FROM RFC1213-MIB
        ifIndex                          FROM RFC1213-MIB
        InetAddressType,
        InetAddress ,
        InetAddressPrefixLength          FROM INET-ADDRESS-MIB
        zxGponOntDevMgmtName,
        zxGponOntDevMgmtTypeName,
        zxGponOntDevMgmtDescription      FROM ZXGPON-SERVICE-MIB;

    zxGponOntMgmt MODULE-IDENTITY
        LAST-UPDATED "200810070000Z"  -- Oct 7, 2008"
        ORGANIZATION "ZTE Corp."
        CONTACT-INFO
            "ZTE GPON Working Group:
            http://www.zte.com.cn
            e-mail:
            guo.hongjian@zte.com.cn
            "
        DESCRIPTION
            "zxGponRootMib 50    , ONT management and control interface(zxGponOMCI)"
        ::= { zxGponRootMib 50 }

--------------------------------------------------------------------------

-- 22. zxGponRmFirewallMgmt
-- 22.1 zxGponOnuIpFilterTable
-- 22.2 zxGponPortForwardTable
    zxEnterpriseMib   OBJECT IDENTIFIER ::= { enterprises 3902}
    zxPON             OBJECT IDENTIFIER ::= { zxEnterpriseMib 1012}
    zxGponRootMib     OBJECT IDENTIFIER ::= { zxPON 3 }

        zxGponOmciTrapsInfo   OBJECT IDENTIFIER ::= { zxGponOntMgmt 6}
        zxGponOmciTraps       OBJECT IDENTIFIER ::= { zxGponOntMgmt 7}
        zxGponOmciStatistics  OBJECT IDENTIFIER ::= { zxGponOntMgmt 8}

        zxGponRmONTEquipMgmt    OBJECT IDENTIFIER ::= { zxGponOntMgmt 11}
        zxGponRmANIMgmt         OBJECT IDENTIFIER ::= { zxGponOntMgmt 12}
        zxGponRmFlowMgmt        OBJECT IDENTIFIER ::= { zxGponOntMgmt 13}
        zxGponRmEthMgmt         OBJECT IDENTIFIER ::= { zxGponOntMgmt 14}
        zxGponRmL2Mgmt          OBJECT IDENTIFIER ::= { zxGponOntMgmt 15}
        zxGponRmL3Mgmt          OBJECT IDENTIFIER ::= { zxGponOntMgmt 16}
        zxGponRmVoiceMgmt       OBJECT IDENTIFIER ::= { zxGponOntMgmt 17}
        zxGponRmTDMMgmt         OBJECT IDENTIFIER ::= { zxGponOntMgmt 18}
        zxGponRmMiscMgmt        OBJECT IDENTIFIER ::= { zxGponOntMgmt 19}
        zxGponRmProfileMgmt     OBJECT IDENTIFIER ::= { zxGponOntMgmt 20}
        zxGponRmServiceMgmt     OBJECT IDENTIFIER ::= { zxGponOntMgmt 21}
        zxGponRmFirewallMgmt    OBJECT IDENTIFIER ::= { zxGponOntMgmt 22}
        zxGponRmSecurityMgmt    OBJECT IDENTIFIER ::= { zxGponOntMgmt 23}
        zxGponRmQosMgmt         OBJECT IDENTIFIER ::= { zxGponOntMgmt 24}
        zxGponRmVeipMgmt        OBJECT IDENTIFIER ::= { zxGponOntMgmt 25}
        zxGponRmTr069Mgmt       OBJECT IDENTIFIER ::= { zxGponOntMgmt 26}
        zxGponRmTestMgmt        OBJECT IDENTIFIER ::= { zxGponOntMgmt 27}
        zxGponRmWanMgmt         OBJECT IDENTIFIER ::= { zxGponOntMgmt 28}

    OntVendorId ::= TEXTUAL-CONVENTION
        STATUS       current
        DESCRIPTION
            "Represents the vendor of the ONT."
        SYNTAX       OCTET STRING (SIZE (4))

    OntVersionId ::= TEXTUAL-CONVENTION
        STATUS       current
        DESCRIPTION
            "Represents the version of the ONT."
        SYNTAX       OCTET STRING (SIZE (14))

    OntSerialNumber ::= TEXTUAL-CONVENTION
        STATUS       current
        DESCRIPTION
            "Represents the unique for each ONT."
        SYNTAX       OCTET STRING (SIZE (8))

    OntEquipmentId ::= TEXTUAL-CONVENTION
        STATUS       current
        DESCRIPTION
            "Represents the specific type of ONT."
        SYNTAX       OCTET STRING (SIZE (20))

    zxGponOntIndexTable OBJECT-TYPE
        SYNTAX      SEQUENCE OF ZxGponOntIndexEntry
        MAX-ACCESS  not-accessible
        STATUS      current
        DESCRIPTION
            "Define the index of ONT."
        ::= { zxGponRmONTEquipMgmt 1 }

    zxGponOntIndexEntry OBJECT-TYPE
        SYNTAX      ZxGponOntIndexEntry
        MAX-ACCESS  not-accessible
        STATUS      current
        DESCRIPTION
            ""
        INDEX   { zxGponOltIndex, zxGponONTIndex }
        ::= { zxGponOntIndexTable 1 }

    ZxGponOntIndexEntry ::=
        SEQUENCE {
            zxGponOltIndex               INTEGER,
            zxGponONTIndex               INTEGER,
            zxGponUNIIndex               INTEGER,
            zxGponFlowIndex              INTEGER,
            zxGponPonIndex               INTEGER,
            zxGponTcontIndex             INTEGER,
            zxGponSwitchIndex            INTEGER,
            zxGponGemPortIndex           INTEGER,
            zxGponBridgePortType         INTEGER,
            zxGponBridgePortIndex        INTEGER,
            zxGponServiceIndex           INTEGER
        }

    zxGponOltIndex OBJECT-TYPE
        SYNTAX      INTEGER
        MAX-ACCESS  not-accessible
        STATUS      current
        DESCRIPTION
            "The 4 bytes index includes:
            interface type(bit31~28);shelfId(bit27~24);slotId(bit23~16);oltId(bit16~8);reserved(bit7~bit0)"
        ::= { zxGponOntIndexEntry 1}

    zxGponONTIndex OBJECT-TYPE
        SYNTAX      INTEGER
        MAX-ACCESS  not-accessible
        STATUS      current
        DESCRIPTION
            "This attribute indicates the index of ONT, from 1 to M."
        ::= { zxGponOntIndexEntry 2}

    zxGponUNIIndex OBJECT-TYPE
        SYNTAX      INTEGER
        MAX-ACCESS  read-only
        STATUS      current
        DESCRIPTION
            "This attribute reprensents the index of interface in ONU.
             The definition is as follows:
        | MSB  Byte 4          |     Byte 3     |    Byte 2    |  Byte 1  LSB |
        |   Type               |    Reserved    |              |              |
        |----------------------+----------------+--------------+--------------|
        | 0: ETH UNI           |       0        |  Slot No.    |  Port No.    |
        | 1: WiFi UNI          |       0        |  Slot No.    |  Port No.    |
        | 2: VEIP              |       0        |      0       |  Index       |
        |---------------------------------------------------------------------|"
        ::= { zxGponOntIndexEntry 3}

    zxGponFlowIndex OBJECT-TYPE
        SYNTAX      INTEGER(1..255)
        MAX-ACCESS  read-only
        STATUS      current
        DESCRIPTION
            "This attribute indicates the index of flow in ONT, from 1 to M.(1 bytes)"
        ::= { zxGponOntIndexEntry 4}

    zxGponPonIndex OBJECT-TYPE
        SYNTAX      INTEGER
        MAX-ACCESS  read-only
        STATUS      current
        DESCRIPTION
            "This attribute indicates the index of ANI in ONT, from 1 to M.
            The first byte specifies the slot Id associated with this PON;
            the second byte specifies the port Id associated with this PON.(2 bytes)"
        ::= { zxGponOntIndexEntry 5}

    zxGponTcontIndex OBJECT-TYPE
        SYNTAX      INTEGER
        MAX-ACCESS  read-only
        STATUS      current
        DESCRIPTION
            "This attribute indicates the index of T-CONT in ONT, from 1 to M."
        ::= { zxGponOntIndexEntry 6}

    zxGponSwitchIndex OBJECT-TYPE
        SYNTAX      INTEGER
        MAX-ACCESS  read-only
        STATUS      current
        DESCRIPTION
            "This attribute indicates the index of MAC bridge in ONT, from 1 to M.
            The first byte specifies the slot Id associated with this MAC bridge;
            the second byte specifies the bridge group Id associated with this MAC bridge.(2 bytes)"
        ::= { zxGponOntIndexEntry 7}

    zxGponGemPortIndex OBJECT-TYPE
        SYNTAX      INTEGER
        MAX-ACCESS  read-only
        STATUS      current
        DESCRIPTION
        "This attribute specifies the gemport id."
        REFERENCE   "G.984.4 & G.983.2"
        ::= { zxGponOntIndexEntry 8 }

    zxGponBridgePortType OBJECT-TYPE
        SYNTAX      INTEGER{
                    ethuni(1),
                    flow(2),
                    iphost(3)
                    }
        MAX-ACCESS  read-only
        STATUS      current
        DESCRIPTION
        "This attribute specifies the bridge port type.
         UNI/FLOW/IPHOST"
        REFERENCE   "G.984.4"
        ::= { zxGponOntIndexEntry 9 }

    zxGponBridgePortIndex OBJECT-TYPE
        SYNTAX      INTEGER
        MAX-ACCESS  read-only
        STATUS      current
        DESCRIPTION
        "This attribute specifies the bridge port index.
        type    size         MSB                LSB
        ------------------------------------------------
        UNI:    2bytes ----- slot(1byte)/port(1byte)
        FLOW:   1byte  ----- flowid(1byte)
        IPHOST: 1byte  ----- hostid(1byte)
        "
        REFERENCE   "G.984.4"
        ::= { zxGponOntIndexEntry 10 }

    zxGponServiceIndex OBJECT-TYPE
        SYNTAX      INTEGER
        MAX-ACCESS  not-accessible
        STATUS      current
        DESCRIPTION
        "This attribute specifies the index of the service."
        REFERENCE   "G.984.4"
        ::= { zxGponOntIndexEntry 11 }

    zxGponONTTable    OBJECT-TYPE
        SYNTAX      SEQUENCE OF ZxGponONTEntry
        MAX-ACCESS  not-accessible
        STATUS      current
        DESCRIPTION
            ""
        ::= { zxGponRmONTEquipMgmt 2 }

    zxGponONTEntry OBJECT-TYPE
        SYNTAX      ZxGponONTEntry
        MAX-ACCESS  not-accessible
        STATUS      current
        DESCRIPTION
            "It is entry in the zxGponONTTable."
        INDEX   { zxGponOltIndex, zxGponONTIndex }
        ::= { zxGponONTTable 1 }

    ZxGponONTEntry ::=
        SEQUENCE {
            zxGponONTVendorId              OntVendorId,
            zxGponONTVersion               OntVersionId,
            zxGponONTSerialNum             OntSerialNumber,
            zxGponONTTrafficOpt            INTEGER,
            zxGponONTVpVcCrossOpt          INTEGER,
            zxGponONTBatteryBackup         TruthValue,
            zxGponONTAdminState            INTEGER,
            zxGponONTOperState             INTEGER,
            zxGponONTEquipId               OntEquipmentId,
            zxGponONTOmccVersion           INTEGER,
            zxGponONTVendorProductCode     INTEGER,
            zxGponONTSecurityCap           INTEGER,
            zxGponONTSecurityMode          INTEGER,
            zxGponONTTotalPrioQueueNum     INTEGER,
            zxGponONTTotalTrafficSchNum    INTEGER,
            zxGponONTMode                  INTEGER,
            zxGponOnuActualType            DisplayString,
            zxGponOnuSurvivalTime          Integer32,
            zxGponOnuTotalGemPortNum       Integer32,
            zxGponOnuSysUpTime             TimeTicks,
            zxGponOnuAlias                 DisplayString
        }

    zxGponONTVendorId OBJECT-TYPE
        SYNTAX      OntVendorId
        MAX-ACCESS  read-only
        STATUS      current
        DESCRIPTION
        "This attribute identifies the vendor of the ONT, and is the same as the 4 most significant bytes of the ONT serial number as specified in ITU-T Rec. G.983.1.
        Upon autonomous instantiation, this attribute consists of all spaces.(4 bytes)"
        REFERENCE   "G.984.4 section 9.1.1 ONT-G"
        ::= { zxGponONTEntry 1 }

    zxGponONTVersion OBJECT-TYPE
        SYNTAX      OntVersionId
        MAX-ACCESS  read-only
        STATUS      current
        DESCRIPTION
        "This attribute identifies the version of the ONT as defined by the vendor. The printable value of '0'
        is used when version information is not available or applicable to the ONT being represented.
        Upon autonomous instantiation, this attribute consists of all spaces.(14 bytes)"
        REFERENCE   "G.984.4 section 9.1.1 ONT-G"
        ::= { zxGponONTEntry 2 }

    zxGponONTSerialNum OBJECT-TYPE
        SYNTAX      OntSerialNumber
        MAX-ACCESS  read-only
        STATUS      current
        DESCRIPTION
        "The serial number is unique for each ONT.
        The first four bytes are the ASCII encoded vendor ID four letter mnemonic.
        The second four bytes are a binary encoded 'serial number', under the complete control
        of the vendor in question.
        Upon autonomous instantiation, this attribute consists of four spaces and four null characters.(8 bytes)"
        REFERENCE   "G.984.4 section 9.1.1 ONT-G"
        ::= { zxGponONTEntry 3 }

    zxGponONTTrafficOpt OBJECT-TYPE
        SYNTAX      INTEGER{
                    priQueueScheduler(1),
                    cellRateControl(2)
                    }
        MAX-ACCESS  read-only
        STATUS      current
        DESCRIPTION
        "This attribute identifies the upstream traffic management function implememted
        in the ONT.
        1) 'Priority controlled and flexibly scheduled upstream traffic' (0x00): The traffic
        scheduler and priority queue mechanism are used for the upstream traffic.
        2) 'Cell rate controlled upstream traffic' (0x01): The maximum upstream traffic of each
        individual connection is guaranteed.
        Note that the Traffic management option will not apply to downstream traffic.
        In other words, there is no need for a traffic descriptor for the downstream direction
        and downstream priority queues can be used.
        Upon autonomous instantiation, this attribute is set to the value that describes the
        ONT's implementation. The OLT must adapt its model to conform to the ONT's selection.(1 byte)"
        REFERENCE   "G.984.4 section 9.1.1 ONT-G"
        ::= { zxGponONTEntry 4 }

    zxGponONTVpVcCrossOpt OBJECT-TYPE
        SYNTAX      INTEGER{
                    null(1),
                    vp(2),
                    vpvc(3)
                    }
        MAX-ACCESS  read-only
        STATUS      current
        DESCRIPTION
            "It identifies the support of ATM VP or VC cross-connection management
             functions for the interworking connections to non ATM UNIs.
             0 means no cross-connection management functions are modelled.
             1 means ATM VP cross-connection management functions are modelled.
             2 means ATM VP and VC cross-connection management functions are modelled."
        REFERENCE
            "G.984.4 Section 9.1.1 ONT-G"
        ::= { zxGponONTEntry 5}

    zxGponONTBatteryBackup OBJECT-TYPE
        SYNTAX      TruthValue
        MAX-ACCESS  read-write
        STATUS      current
        DESCRIPTION
            "This attribute provides a Boolean indication of whether or not the ONT/NT supports battery backup.
            False will indicate that no battery is provisioned; true indicates that a battery is provisioned.
            Upon autonomous instantiation, this attribute is set to false.(1 byte)"
        REFERENCE
            "G.984.4 Section 9.1.1 ONT-G"
        ::= { zxGponONTEntry 6}

    zxGponONTAdminState OBJECT-TYPE
        SYNTAX      INTEGER{
                    unlock(1),
                    lock(2)
                    }
        MAX-ACCESS  read-write
        STATUS      current
        DESCRIPTION
            "This attribute is used to activate (unlock: value 0x00) and deactivate (lock: value 0x01)
            the functions performed by instances of this managed entity.(1 byte)"
        REFERENCE
            "G.984.4 Section 9.1.1 ONT-G"
        ::= { zxGponONTEntry 7}

    zxGponONTOperState OBJECT-TYPE
        SYNTAX      INTEGER{
                    enable(1),
                    disable(2)
                    }
        MAX-ACCESS  read-only
        STATUS      current
        DESCRIPTION
            "This attribute indicates whether or not a managed entity is capable of
            performing its task. Valid values are enabled (0x00) and disabled (0x01).(1 byte)"
        REFERENCE
            "G.984.4 Section 9.1.1 ONT-G"
        ::= { zxGponONTEntry 8}

    zxGponONTEquipId OBJECT-TYPE
        SYNTAX      OntEquipmentId
        MAX-ACCESS  read-only
        STATUS      current
        DESCRIPTION
        "This attribute may be used to identify the specific type of ONT. In North America,
        this may be used for the equipment CLEI code.(20 bytes)"
        REFERENCE   "G.984.4 section 9.1.2 ONT2-G"
        ::= { zxGponONTEntry 9 }

    zxGponONTOmccVersion OBJECT-TYPE
        SYNTAX      INTEGER
        MAX-ACCESS  read-only
        STATUS      current
        DESCRIPTION
        "This attribute is used to identify the specific version of the OMCC
        protocol being used by the ONT. This is used to allow the OLT to manage a
        network with ONTs that support different OMCC versions.
        The only valid value at this time is 0x80. Future versions will be added sequentially.
        Upon autonomous instantiation, this attribute consists of the value 0x80.(1 byte)"
        REFERENCE   "G.984.4 section 9.1.2 ONT2-G"
        ::= { zxGponONTEntry 10 }

    zxGponONTVendorProductCode OBJECT-TYPE
        SYNTAX      INTEGER
        MAX-ACCESS  read-only
        STATUS      current
        DESCRIPTION
        "This attribute is used to provide a vendor-specific product code for the ONT.(2 bytes)"
        REFERENCE   "G.984.4 section 9.1.2 ONT2-G"
        ::= { zxGponONTEntry 11 }

    zxGponONTSecurityCap OBJECT-TYPE
        SYNTAX      INTEGER(0..255)
        MAX-ACCESS  read-only
        STATUS      current
        DESCRIPTION
        "This attribute is used to advertise the advanced security modes of the ONT.
        The following codepoints are defined:
        0: Reserved for future use;
        1: AES encryption of the downstream payload is supported;
        2..255: Reserved for future use.(1 byte)"
        REFERENCE   "G.984.4 section 9.1.2 ONT2-G"
        ::= { zxGponONTEntry 12 }

    zxGponONTSecurityMode OBJECT-TYPE
        SYNTAX      INTEGER(0..255)
        MAX-ACCESS  read-write
        STATUS      current
        DESCRIPTION
            "This attribute is used to select the advanced security mode for the ONT.
             Note that all secure VPs/VCs or GEM ports in an ONT must use the same security mode at
             any time. The following codepoints are defined:
             0: Reserved for future use;
             1: AES algorithm for unicast traffic will be used;
             2..255: Reserved for future use.
             Upon autonomous instantiation this attribute consists of the value 0x01.(1 byte)"
        REFERENCE
            "G.984.4 Section 9.1.2 ONT2-G"
        ::= { zxGponONTEntry 13}

    zxGponONTTotalPrioQueueNum OBJECT-TYPE
        SYNTAX      INTEGER
        MAX-ACCESS  read-only
        STATUS      current
        DESCRIPTION
            "This attribute provides a total number of priority queues which are not associated with the PON IF circuit pack.
            Maximum value is 0x0FFF. Upautonomous instantiation, this attribute is set to zero.(2 bytes)"
        REFERENCE
            "G.984.4 Section 9.1.2 ONT2-G"
        ::= { zxGponONTEntry 14}

    zxGponONTTotalTrafficSchNum OBJECT-TYPE
        SYNTAX      INTEGER
        MAX-ACCESS  read-only
        STATUS      current
        DESCRIPTION
            "This attribute provides a total number of Traffic Schedulers which
            are not associated with the PON IF circuit pack. The ONT supports NULL function,
            HOL scheduling and WRR from the priority control and guarantee of
            minimum rate control points of view, respectively.
            If the ONT does noScheduler, this attribute should be 0x00.
            Upon autonomous instantiation, this attribute is set to zero.(1 byte)"
        REFERENCE
            "G.984.4 Section 9.1.2 ONT2-G"
        ::= { zxGponONTEntry 15}

    zxGponONTMode OBJECT-TYPE
        SYNTAX      INTEGER{
                    atmOnly(1),
                    gemOnly(2),
                    dual(3)
                    }
        MAX-ACCESS  read-only
        STATUS      current
        DESCRIPTION
            "This attribute identifies whether the ONT can operate in ATM-only mode (0x00),
            GEM-only mode (0x01), or dual (both ATM and GEM) mode (0x02).(1 byte)"
        REFERENCE
            "G.984.4 Section 9.1.2 ONT2-G"
        ::= { zxGponONTEntry 16}

    zxGponOnuActualType   OBJECT-TYPE
        SYNTAX      DisplayString (SIZE (0..14))
        MAX-ACCESS  read-only
        STATUS      current
        DESCRIPTION
            "This attribute identifies ONU actual type."
        ::= { zxGponONTEntry 17 }

    zxGponOnuSurvivalTime   OBJECT-TYPE
        SYNTAX      Integer32
        MAX-ACCESS  read-only
        STATUS      current
        DESCRIPTION
            "This attribute indicates the minimum guaranteed time in
            milliseconds between the loss of external power and the silence of
            the ONU. This does not include survival time attributable to a
            backup battery. The value zero implies that the actual time is not
            known. (R) (optional) (1 byte)"
        ::= { zxGponONTEntry 18 }

    zxGponOnuTotalGemPortNum   OBJECT-TYPE
        SYNTAX      Integer32
        MAX-ACCESS  read-only
        STATUS      current
        DESCRIPTION
            "This attribute reports the total number of GEM port-IDs
            supported by the ONU. The maximum value is specified in the
            corresponding TC recommendation [ITU-T G.984.3] or [ITU-T G.987.3].
            Upon ME instantiation, the ONU sets this attribute to the value
            that represents its capabilities. (R) (optional) (2 bytes)"
        ::= { zxGponONTEntry 19 }

    zxGponOnuSysUpTime   OBJECT-TYPE
        SYNTAX      TimeTicks
        MAX-ACCESS  read-only
        STATUS      current
        DESCRIPTION
            "This attribute counts 10 ms intervals since the ONU was last
            initialized. It rolls over to 0 when full (see [IETF RFC 1213]).
            (R) (optional) (4 bytes)"
        ::= { zxGponONTEntry 20 }

    zxGponOnuAlias       OBJECT-TYPE
        SYNTAX      DisplayString (SIZE (0..16))
        MAX-ACCESS  read-write
        STATUS      current
        DESCRIPTION
            "This attribute identifies ONU alias."
        ::= { zxGponONTEntry 21 }



--ONT action
    zxGponONTActionTable    OBJECT-TYPE
        SYNTAX      SEQUENCE OF ZxGponONTActionEntry
        MAX-ACCESS  not-accessible
        STATUS      current
        DESCRIPTION
            ""
        ::= { zxGponRmONTEquipMgmt 3 }

    zxGponONTActionEntry OBJECT-TYPE
        SYNTAX      ZxGponONTActionEntry
        MAX-ACCESS  not-accessible
        STATUS      current
        DESCRIPTION
            "It is entry in the zxGponONTActionTable."
        INDEX   { zxGponOltIndex, zxGponONTIndex }
        ::= { zxGponONTActionTable 1 }

    ZxGponONTActionEntry ::=
        SEQUENCE {
            zxGponONTReboot              TruthValue,
            zxGponONTTest                TruthValue,
            zxGponONTSyncTime            TruthValue,
            zxGponONTRestore             TruthValue,
            zxGponONTTestResult          INTEGER,
            zxGponONTRestoreFactory      TruthValue
        }

    zxGponONTReboot OBJECT-TYPE
        SYNTAX      TruthValue
        MAX-ACCESS  read-write
        STATUS      current
        DESCRIPTION
        "This attribute identifies the action of the ONT."
        REFERENCE   "G.984.4 section 9.1.1 ONT-G"
        ::= { zxGponONTActionEntry 1 }

    zxGponONTTest OBJECT-TYPE
        SYNTAX      TruthValue
        MAX-ACCESS  read-write
        STATUS      current
        DESCRIPTION
        "This attribute identifies the action of the ONT."
        REFERENCE   "G.984.4 section 9.1.1 ONT-G"
        ::= { zxGponONTActionEntry 2 }

    zxGponONTSyncTime OBJECT-TYPE
        SYNTAX      TruthValue
        MAX-ACCESS  read-write
        STATUS      current
        DESCRIPTION
        "This attribute identifies the action of the ONT."
        REFERENCE   "G.984.4 section 9.1.1 ONT-G"
        ::= { zxGponONTActionEntry 3 }

    zxGponONTRestore OBJECT-TYPE
        SYNTAX      TruthValue
        MAX-ACCESS  read-write
        STATUS      current
        DESCRIPTION
        "This attribute identifies the action of the ONT. That is resetting the ONT's MIB."
        REFERENCE   "G.984.4 section 9.1.1 ONT-G"
        ::= { zxGponONTActionEntry 4 }

    zxGponONTTestResult OBJECT-TYPE
        SYNTAX      INTEGER{
                    pass(1),
                    fail(2)
                    }
        MAX-ACCESS  read-only
        STATUS      current
        DESCRIPTION
        "This attribute identifies the result of testing ONT."
        REFERENCE   "G.984.4 section 9.1.1 ONT-G"
        ::= { zxGponONTActionEntry 5 }

    zxGponONTRestoreFactory OBJECT-TYPE
        SYNTAX      TruthValue
        MAX-ACCESS  read-write
        STATUS      current
        DESCRIPTION
            "This attribute identifies the action of the ONT,
                restores the ONT's factory set."
        REFERENCE   "Private OMCI ME, ONT3-G"
        ::= { zxGponONTActionEntry 6 }

--software image
    zxGponSoftwareImageTable    OBJECT-TYPE
        SYNTAX      SEQUENCE OF ZxGponSoftwareImageEntry
        MAX-ACCESS  not-accessible
        STATUS      current
        DESCRIPTION
            "This managed entity represents a program stored in the ONT.
            Two instances of the software image managed entity are contained in an instance of
            an ONT or equipment managed entity whose software is independently managed."
        REFERENCE   "G.983.2 section 7.1.7 Software image"
        ::= { zxGponRmONTEquipMgmt 4 }

    zxGponSoftwareImageEntry OBJECT-TYPE
        SYNTAX      ZxGponSoftwareImageEntry
        MAX-ACCESS  not-accessible
        STATUS      current
        DESCRIPTION
            "It is entry in the zxGponSoftwareImageTable."
        INDEX   { zxGponOltIndex, zxGponONTIndex, zxGponSoftwareImageIndex }
        ::= { zxGponSoftwareImageTable 1 }

    ZxGponSoftwareImageEntry ::=
        SEQUENCE {
            zxGponSoftwareImageIndex                   INTEGER,
            zxGponSoftwareImageVersion                 OCTET STRING,
            zxGponSoftwareImageIsCommitted             TruthValue,
            zxGponSoftwareImageIsActive                TruthValue,
            zxGponSoftwareImageIsValid                 TruthValue
        }

    zxGponSoftwareImageIndex OBJECT-TYPE
        SYNTAX      INTEGER
        MAX-ACCESS  read-only
        STATUS      current
        DESCRIPTION
        "This attribute provides a unique number for each instance of this managed entity.
        The number consists of a two-byte field. The first field (MSB) identifies the ME
        instance (ONT (value 0x00) or circuit pack slot (value 0x01-0xFF) containing the
        associated software image ME. The second field (LSB) distinguishes between the
        two (redundant) software image ME instances (values 0x00 and 0x01).(2 bytes)"
        REFERENCE   "G.983.2 section 7.1.7 Software image"
        ::= { zxGponSoftwareImageEntry 1 }

    zxGponSoftwareImageVersion OBJECT-TYPE
        SYNTAX      OCTET STRING(SIZE(0..14))
        MAX-ACCESS  read-only
        STATUS      current
        DESCRIPTION
        "This attribute identifies the version of the software.
        Upon autonomous instantiation, this attribute consists of all spaces.(14 bytes)"
        REFERENCE   "G.983.2 section 7.1.7 Software image"
        ::= { zxGponSoftwareImageEntry 2 }

    zxGponSoftwareImageIsCommitted OBJECT-TYPE
        SYNTAX      TruthValue
        MAX-ACCESS  read-only
        STATUS      current
        DESCRIPTION
        "This attribute indicates whether the associated software image is 'committed' (value 0x01)
        or 'uncommitted' (value 0x00). By definition, the 'committed' software image will be loaded
        and executed upon a reboot of the ONT and/or associated circuit pack.Upon autonomous
        instantiation, this attribute of instance 0 shall be initialized to 'committed' and
        this attribute of instance 1 shall be initialized to 'uncommitted'.(1 byte)"
        REFERENCE   "G.983.2 section 7.1.7 Software image"
        ::= { zxGponSoftwareImageEntry 3 }

    zxGponSoftwareImageIsActive OBJECT-TYPE
        SYNTAX      TruthValue
        MAX-ACCESS  read-only
        STATUS      current
        DESCRIPTION
        "This attribute indicates whether the associated software image is 'active' (value 0x01)
        or 'inactive' (value 0x00). By definition, the active software image is one that is
        currently loaded and executing in the ONT (or associated circuit pack).Upon autonomous
        instantiation, this attribute of instance 0 shall be initialized to 'active' and this
        attribute of instance 1 shall be initialized to 'inactive'.(1 byte)"
        REFERENCE   "G.983.2 section 7.1.7 Software image"
        ::= { zxGponSoftwareImageEntry 4 }

    zxGponSoftwareImageIsValid OBJECT-TYPE
        SYNTAX      TruthValue
        MAX-ACCESS  read-only
        STATUS      current
        DESCRIPTION
        "This attribute indicates whether the associated software image is 'valid' (value 0x01)
        or 'invalid (value 0x00). By definition, a software image is 'valid' if it has been
        verified to be an executable code image.Upon autonomous instantiation, the associated
        code image is verified and this attribute is set according to the result of this verification.(1 byte)"
        REFERENCE   "G.983.2 section 7.1.7 Software image"
        ::= { zxGponSoftwareImageEntry 5 }

--software image action
    zxGponSoftwareImageActionTable    OBJECT-TYPE
        SYNTAX      SEQUENCE OF ZxGponSoftwareImageActionEntry
        MAX-ACCESS  not-accessible
        STATUS      current
        DESCRIPTION
            "This managed entity represents a program management in the ONT."
        REFERENCE   "G.983.2 section 7.1.7 Software image"
        ::= { zxGponRmONTEquipMgmt 5 }

    zxGponSoftwareImageActionEntry OBJECT-TYPE
        SYNTAX      ZxGponSoftwareImageActionEntry
        MAX-ACCESS  not-accessible
        STATUS      current
        DESCRIPTION
            "It is entry in the zxGponSoftwareImageActionTable."
        INDEX   { zxGponOltIndex }
        ::= { zxGponSoftwareImageActionTable 1 }

    ZxGponSoftwareImageActionEntry ::=
        SEQUENCE {
            zxGponSoftwareImageActionType                  INTEGER,
            zxGponSoftwareImageActionVersion               OCTET STRING,
            zxGponSoftwareImageActionOntList               OCTET STRING,
            zxGponSoftwareImageActionOntNum                INTEGER,
            zxGponSoftwareImageActionOntSlot               INTEGER
        }

    zxGponSoftwareImageActionType OBJECT-TYPE
        SYNTAX      INTEGER{
                    update(1),
                    updateAbort(2),
                    updateAndReboot(3)
                    }
        MAX-ACCESS  read-write
        STATUS      current
        DESCRIPTION
        "This attribute initiates the action type of image update.
        In updating, 'zxGponSoftwareImageActionVersion',
        'zxGponSoftwareImageActionOntList','zxGponSoftwareImageActionOntNum'
        and 'zxGponSoftwareImageActionOntSlot'must be specified.
        If no slots exist, specify 'slot' as 0 or do not specify it.

        In aborting, 'zxGponSoftwareImageActionOntList' and
        'zxGponSoftwareImageActionOntNum' must be specified."
        REFERENCE   "G.983.2 section 7.1.7 Software image"
        ::= { zxGponSoftwareImageActionEntry 1 }

    zxGponSoftwareImageActionVersion OBJECT-TYPE
        SYNTAX      OCTET STRING(SIZE(0..14))
        MAX-ACCESS  read-write
        STATUS      current
        DESCRIPTION
        "This attribute specifies the version name."
        REFERENCE   "G.983.2 section 7.1.7 Software image"
        ::= { zxGponSoftwareImageActionEntry 2 }

    zxGponSoftwareImageActionOntList OBJECT-TYPE
        SYNTAX      OCTET STRING(SIZE(1..128))
        MAX-ACCESS  read-write
        STATUS      current
        DESCRIPTION
        "This attribute specifies the ONT list who will be told to update the version."
        REFERENCE   "G.983.2 section 7.1.7 Software image"
        ::= { zxGponSoftwareImageActionEntry 3 }

    zxGponSoftwareImageActionOntNum OBJECT-TYPE
        SYNTAX      INTEGER(1..128)
        MAX-ACCESS  read-write
        STATUS      current
        DESCRIPTION
        "This attribute specifies the ONT number who will be told to update the version."
        REFERENCE   "G.983.2 section 7.1.7 Software image"
        ::= { zxGponSoftwareImageActionEntry 4 }

    zxGponSoftwareImageActionOntSlot OBJECT-TYPE
        SYNTAX      INTEGER(0..255)
        MAX-ACCESS  read-write
        STATUS      current
        DESCRIPTION
        "This attribute specifies the ONT slot who will be told to update the version.
         Default as 0, for update the version of ONT itself;
         Otherwise, the line card version of such a slot will be updated."
        REFERENCE   "G.983.2 section 7.1.7 Software image"
        ::= { zxGponSoftwareImageActionEntry 5 }

--software image maintenance
    zxGponSoftwareImageMaintTable    OBJECT-TYPE
        SYNTAX      SEQUENCE OF ZxGponSoftwareImageMaintEntry
        MAX-ACCESS  not-accessible
        STATUS      current
        DESCRIPTION
            "This managed entity represents the image maintenance in the ONT."
        REFERENCE   "G.983.2 section 7.1.7 Software image"
        ::= { zxGponRmONTEquipMgmt 6 }

    zxGponSoftwareImageMaintEntry OBJECT-TYPE
        SYNTAX      ZxGponSoftwareImageMaintEntry
        MAX-ACCESS  not-accessible
        STATUS      current
        DESCRIPTION
            "It is entry in the zxGponSoftwareImageMaintTable."
        INDEX   { zxGponOltIndex }
        ::= { zxGponSoftwareImageMaintTable 1 }

    ZxGponSoftwareImageMaintEntry ::=
        SEQUENCE {
            zxGponSoftwareImageMaintType                  INTEGER,
            zxGponSoftwareImageMaintOntList               OCTET STRING,
            zxGponSoftwareImageMaintOntNum                INTEGER,
            zxGponSoftwareImageMaintImgIndex              INTEGER
        }

    zxGponSoftwareImageMaintType OBJECT-TYPE
        SYNTAX      INTEGER{
                    activate(1),
                    commit(2)
                    }
        MAX-ACCESS  read-write
        STATUS      current
        DESCRIPTION
        "This attribute initiates the maintenance type of image(activate or commit)."
        REFERENCE   "G.983.2 section 7.1.7 Software image"
        ::= { zxGponSoftwareImageMaintEntry 1 }

    zxGponSoftwareImageMaintOntList OBJECT-TYPE
        SYNTAX      OCTET STRING(SIZE(1..128))
        MAX-ACCESS  read-write
        STATUS      current
        DESCRIPTION
        "This attribute specifies the ONT list who will be told to activate or commit the version."
        REFERENCE   "G.983.2 section 7.1.7 Software image"
        ::= { zxGponSoftwareImageMaintEntry 2 }

    zxGponSoftwareImageMaintOntNum OBJECT-TYPE
        SYNTAX      INTEGER(1..128)
        MAX-ACCESS  read-write
        STATUS      current
        DESCRIPTION
        "This attribute specifies the ONT number who will be told to update the version."
        REFERENCE   "G.983.2 section 7.1.7 Software image"
        ::= { zxGponSoftwareImageMaintEntry 3 }

    zxGponSoftwareImageMaintImgIndex OBJECT-TYPE
        SYNTAX      INTEGER
        MAX-ACCESS  read-write
        STATUS      current
        DESCRIPTION
        "This two-byte field is composed of 'onu slot' and 'region id'.
        The MSB is 'onu slot', usually as 0;
        The LSB is 'region id', sepecified as 0 or 1."
        REFERENCE   "G.983.2 section 7.1.7 Software image"
        ::= { zxGponSoftwareImageMaintEntry 4 }

--software image update status
    zxGponSoftwareImageUpdateStatusTable    OBJECT-TYPE
        SYNTAX      SEQUENCE OF ZxGponSoftwareImageUpdateStatusEntry
        MAX-ACCESS  not-accessible
        STATUS      current
        DESCRIPTION
            "This managed entity represents the image update status of the ONT."
        REFERENCE   "G.983.2 section 7.1.7 Software image"
        ::= { zxGponRmONTEquipMgmt 7 }

    zxGponSoftwareImageUpdateStatusEntry OBJECT-TYPE
        SYNTAX      ZxGponSoftwareImageUpdateStatusEntry
        MAX-ACCESS  not-accessible
        STATUS      current
        DESCRIPTION
            "It is entry in the zxGponSoftwareImageUpdateStatusTable."
        INDEX   { zxGponOltIndex, zxGponONTIndex }
        ::= { zxGponSoftwareImageUpdateStatusTable 1 }

    ZxGponSoftwareImageUpdateStatusEntry ::=
        SEQUENCE {
            zxGponSoftwareImageUpdateStatus                  INTEGER,
            zxGponSoftwareImageUpdateStatusAbortReason       INTEGER,
            zxGponSoftwareImageUpdateStatusPercent           INTEGER,
            zxGponSoftwareImageUpdateStatusCurUsedVerName    OCTET STRING,
            zxGponSoftwareImageUpdateStatusCurUsedVerTime    OCTET STRING,
            zxGponSoftwareImageUpdateStatusUpdatingVerName   OCTET STRING,
            zxGponSoftwareImageUpdateStatusUpdatingVerTime   OCTET STRING
        }

    zxGponSoftwareImageUpdateStatus OBJECT-TYPE
        SYNTAX      INTEGER{
                    not-start(1),
                    abort(2),
                    downloading(3),
                    commiting(4),
                    activating(5),
                    done(6)
                    }
        MAX-ACCESS  read-only
        STATUS      current
        DESCRIPTION
        "This attribute indicates the status of updaing.0xFFFF indicates status of 'NA'."
        REFERENCE   "G.983.2 section 7.1.7 Software image"
        ::= { zxGponSoftwareImageUpdateStatusEntry 1 }

    zxGponSoftwareImageUpdateStatusAbortReason OBJECT-TYPE
        SYNTAX      INTEGER{
                    none(1),
                    download-error(2),
                    commit-error(3),
                    activate-error(4),
                    crc-error(5),
                    valid-error(6),
                    user-abort(7)
                    }
        MAX-ACCESS  read-only
        STATUS      current
        DESCRIPTION
        "This attribute indicates the reason when abort."
        REFERENCE   "G.983.2 section 7.1.7 Software image"
        ::= { zxGponSoftwareImageUpdateStatusEntry 2 }

    zxGponSoftwareImageUpdateStatusPercent OBJECT-TYPE
        SYNTAX      INTEGER(0..100)
        MAX-ACCESS  read-only
        STATUS      current
        DESCRIPTION
        "This attribute indicates the percent of updating."
        REFERENCE   "G.983.2 section 7.1.7 Software image"
        ::= { zxGponSoftwareImageUpdateStatusEntry 3 }

    zxGponSoftwareImageUpdateStatusCurUsedVerName OBJECT-TYPE
        SYNTAX      OCTET STRING
        MAX-ACCESS  read-only
        STATUS      current
        DESCRIPTION
        "This attribute indicates the name of the version current used."
        REFERENCE   "G.983.2 section 7.1.7 Software image"
        ::= { zxGponSoftwareImageUpdateStatusEntry 4 }

    zxGponSoftwareImageUpdateStatusCurUsedVerTime OBJECT-TYPE
        SYNTAX      OCTET STRING
        MAX-ACCESS  read-only
        STATUS      current
        DESCRIPTION
        "This attribute indicates the time of the version current used."
        REFERENCE   "G.983.2 section 7.1.7 Software image"
        ::= { zxGponSoftwareImageUpdateStatusEntry 5 }

    zxGponSoftwareImageUpdateStatusUpdatingVerName OBJECT-TYPE
        SYNTAX      OCTET STRING
        MAX-ACCESS  read-only
        STATUS      current
        DESCRIPTION
        "This attribute indicates the name of the version updating."
        REFERENCE   "G.983.2 section 7.1.7 Software image"
        ::= { zxGponSoftwareImageUpdateStatusEntry 6 }

    zxGponSoftwareImageUpdateStatusUpdatingVerTime OBJECT-TYPE
        SYNTAX      OCTET STRING
        MAX-ACCESS  read-only
        STATUS      current
        DESCRIPTION
        "This attribute indicates the time of the version updating."
        REFERENCE   "G.983.2 section 7.1.7 Software image"
        ::= { zxGponSoftwareImageUpdateStatusEntry 7 }


    zxGponONTPowerSheddingTable    OBJECT-TYPE
        SYNTAX      SEQUENCE OF ZxGponONTPowerSheddingEntry
        MAX-ACCESS  not-accessible
        STATUS      current
        DESCRIPTION
            "This managed entity models the ONT's ability to shed services
             when the ONT goes into battery operation mode after AC power failure."
        ::= { zxGponRmONTEquipMgmt 8 }

    zxGponONTPowerSheddingEntry OBJECT-TYPE
        SYNTAX      ZxGponONTPowerSheddingEntry
        MAX-ACCESS  not-accessible
        STATUS      current
        DESCRIPTION
            "It is entry in the zxGponONTPowerSheddingTable."
        INDEX   { zxGponOltIndex, zxGponONTIndex }
        ::= { zxGponONTPowerSheddingTable 1 }

    ZxGponONTPowerSheddingEntry ::=
        SEQUENCE {
            zxGponONTPowerSheddingRestoreInterval                INTEGER,
            zxGponONTPowerSheddingDataSheddingInterval           INTEGER,
            zxGponONTPowerSheddingVoiceSheddingInterval          INTEGER,
            zxGponONTPowerSheddingVideoOverlaySheddingInterval   INTEGER,
            zxGponONTPowerSheddingVideoReturnSheddingInterval    INTEGER,
            zxGponONTPowerSheddingDSLSheddingInterval            INTEGER,
            zxGponONTPowerSheddingATMSheddingInterval            INTEGER,
            zxGponONTPowerSheddingCESSheddingInterval            INTEGER,
            zxGponONTPowerSheddingFrameSheddingInterval          INTEGER,
            zxGponONTPowerSheddingSONETSheddingInterval          INTEGER,
            zxGponONTPowerSheddingSheddingStatus                 INTEGER
        }

    zxGponONTPowerSheddingRestoreInterval OBJECT-TYPE
        SYNTAX      INTEGER
        MAX-ACCESS  read-write
        STATUS      current
        DESCRIPTION
        "The time delay, in seconds, before resetting shedding timers after full power restoration.
              Upon ME instantiation, the ONT sets this attribute to 0. (R, W) (mandatory) (2 bytes)"
        REFERENCE   "G.984.4 section 9.1.7 ONT power shedding"
        ::= { zxGponONTPowerSheddingEntry 1 }

    zxGponONTPowerSheddingDataSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 2 }

    zxGponONTPowerSheddingVoiceSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 3 }

    zxGponONTPowerSheddingVideoOverlaySheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 4 }

    zxGponONTPowerSheddingVideoReturnSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 5 }

    zxGponONTPowerSheddingDSLSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 6 }

    zxGponONTPowerSheddingATMSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 7 }

    zxGponONTPowerSheddingCESSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 8 }

    zxGponONTPowerSheddingFrameSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 9 }

    zxGponONTPowerSheddingSONETSheddingInterval OBJECT-TYPE
        SYNTAX      INTEGER
        MAX-ACCESS  read-write
        STATUS      current
        DESCRIPTION
        "For each class of service, an interval attribute is defined below.
               The value 0 disables power shedding, while the value 1 enables immediate power shed, that is, as soon as AC power fails.
              Other values specify the time, in seconds, to keep the service active after AC failure before shutting them down and shedding power.
              Upon ME instantiation, the ONT sets each of the interval attributes to 0.(2 bytes)"
        REFERENCE   "G.984.4 section 9.1.7 ONT power shedding"
        ::= { zxGponONTPowerSheddingEntry 10 }

    zxGponONTPowerSheddingSheddingStatus OBJECT-TYPE
        SYNTAX      INTEGER
        MAX-ACCESS  read-only
        STATUS      current
        DESCRIPTION
        "Boolean indication of power shedding status for each shedding class.
         If this two-byte field is depicted 0b ABCD EFGH IJKL MNOP, its bits are assigned:
         A    Data class
         B    Voice class
         C    Video overlay class
         D    Video return class
         E    DSL class
         F    ATM class
         G    CES class
         H    Frame class
         I    Sonet class
         J..P    Reserved and set to 0
         The ONT sets each bit when power shedding is active, and clears it when the service is restored. (R) (optional) (2 bytes)"
        REFERENCE   "G.984.4 section 9.1.7 ONT power shedding"
        ::= { zxGponONTPowerSheddingEntry 11 }

--  Beijing HomeGateway

     zxGponOnuHgConfigTable OBJECT-TYPE
        SYNTAX       SEQUENCE OF ZxGponOnuHgConfigEntry
        MAX-ACCESS   not-accessible
        STATUS       current
        DESCRIPTION
          "ONU Home Gateway MAC Code."
          ::= { zxGponRmONTEquipMgmt 9 }

    zxGponOnuHgConfigEntry OBJECT-TYPE
        SYNTAX      ZxGponOnuHgConfigEntry
        MAX-ACCESS  not-accessible
        STATUS      current
        DESCRIPTION " "
        INDEX   { zxGponOltIndex, zxGponONTIndex}
        ::= { zxGponOnuHgConfigTable 1 }

    ZxGponOnuHgConfigEntry ::=
        SEQUENCE {
                 zxGponOnuHgMacWildcard         DisplayString,
                 zxGponOnuHgVlan         INTEGER
                }

    zxGponOnuHgMacWildcard OBJECT-TYPE
        SYNTAX      DisplayString  (SIZE ( 1..385  ))
        MAX-ACCESS  read-write
        STATUS      current
        DESCRIPTION
                "ONU Home Gateway wildcard MAC"
        ::= { zxGponOnuHgConfigEntry 1}

    zxGponOnuHgVlan OBJECT-TYPE
        SYNTAX      INTEGER(0..4094)
        MAX-ACCESS  read-write
        STATUS      current
        DESCRIPTION
                "ONU Home Gateway Vlan. 0 indicated no concern about whether the connected home gateway."
        ::= { zxGponOnuHgConfigEntry 2}


    zxGponOnuHgStateTable OBJECT-TYPE
        SYNTAX       SEQUENCE OF ZxGponOnuHgStateEntry
        MAX-ACCESS   not-accessible
        STATUS       current
        DESCRIPTION
          "ONU Home Gateway state."
          ::= { zxGponRmONTEquipMgmt 10 }

    zxGponOnuHgStateEntry OBJECT-TYPE
        SYNTAX      ZxGponOnuHgStateEntry
        MAX-ACCESS  not-accessible
        STATUS      current
        DESCRIPTION " "
        INDEX       { zxGponOltIndex,zxGponONTIndex,zxGponUNIIndex }
        ::= { zxGponOnuHgStateTable 1 }

    ZxGponOnuHgStateEntry ::=
        SEQUENCE {
                zxGponOnuHgMac            MacAddress,
                zxGponOnuHgState          INTEGER
                }

    zxGponOnuHgMac OBJECT-TYPE
        SYNTAX      MacAddress
        MAX-ACCESS  read-write
        STATUS      current
        DESCRIPTION
                "ONU Home Gateway MAC Address."
        ::= { zxGponOnuHgStateEntry 1}

    zxGponOnuHgState  OBJECT-TYPE
        SYNTAX      INTEGER{
                      unbind(1),
                      bind(2)
                      }
        MAX-ACCESS  read-write
        STATUS      current
        DESCRIPTION
                "ONU Home Gateway state."
        DEFVAL  {unbind}
        ::= { zxGponOnuHgStateEntry 2 }


    zxGponOnuVersionUpdate    OBJECT IDENTIFIER   ::=  {  zxGponRmONTEquipMgmt  11  }

    zxGponOnuType OBJECT-TYPE
        SYNTAX      OCTET STRING(SIZE(0..64))
        MAX-ACCESS  read-write
        STATUS      current
        DESCRIPTION
        "This attribute specifies the ONT type who will be told to update the version."
        REFERENCE   ""
        ::= { zxGponOnuVersionUpdate 1 }

    zxGponOnuUpdateVerFile OBJECT-TYPE
        SYNTAX      OCTET STRING(SIZE(0..14))
        MAX-ACCESS  read-write
        STATUS      current
        DESCRIPTION
        "This attribute specifies the version file name."
        REFERENCE   ""
        ::= { zxGponOnuVersionUpdate 2 }

    zxGponOnuUpdateAction OBJECT-TYPE
        SYNTAX      INTEGER{
                    update(1),
                    abort(2)
                    }
        MAX-ACCESS  read-write
        STATUS      current
        DESCRIPTION
        ""
        REFERENCE   ""
        ::= { zxGponOnuVersionUpdate 3 }



    zxGponOnuAutoUpdateTable    OBJECT-TYPE
        SYNTAX      SEQUENCE OF ZxGponOnuAutoUpdateEntry
        MAX-ACCESS  not-accessible
        STATUS      current
        DESCRIPTION
            ""
        ::= { zxGponRmONTEquipMgmt 12 }

    zxGponOnuAutoUpdateEntry OBJECT-TYPE
        SYNTAX      ZxGponOnuAutoUpdateEntry
        MAX-ACCESS  not-accessible
        STATUS      current
        DESCRIPTION
            "It is entry in the zxGponOnuAutoUpdateTable."
        INDEX   { zxGponOltIndex, zxGponONTIndex }
        ::= { zxGponOnuAutoUpdateTable 1 }

    ZxGponOnuAutoUpdateEntry ::=
        SEQUENCE {
            zxGponOnuAutoUpdateEnable                TruthValue,
            zxGponOnuAutoUpdateVerFile               OCTET STRING
        }

    zxGponOnuAutoUpdateEnable OBJECT-TYPE
        SYNTAX      TruthValue
        MAX-ACCESS  read-write
        STATUS      current
        DESCRIPTION
        ""
        REFERENCE   ""
        ::= { zxGponOnuAutoUpdateEntry 1 }

    zxGponOnuAutoUpdateVerFile  OBJECT-TYPE
        SYNTAX      OCTET STRING(SIZE(0..14))
        MAX-ACCESS  read-write
        STATUS      current
        DESCRIPTION
            "NULL string means that version file not specified."
        ::= { zxGponOnuAutoUpdateEntry 2}


    zxGponOnuCapabilityTable    OBJECT-TYPE
        SYNTAX      SEQUENCE OF ZxGponOnuCapabilityEntry
        MAX-ACCESS  not-accessible
        STATUS      current
        DESCRIPTION
            "GPON ONU capability table"
        ::= { zxGponRmONTEquipMgmt 14 }

    zxGponOnuCapabilityEntry OBJECT-TYPE
        SYNTAX      ZxGponOnuCapabilityEntry
        MAX-ACCESS  not-accessible
        STATUS      current
        DESCRIPTION
            "It is entry in the zxGponOnuCapabilityTable."
        INDEX   { zxGponOltIndex, zxGponONTIndex }
        ::= { zxGponOnuCapabilityTable 1 }

    ZxGponOnuCapabilityEntry ::=
        SEQUENCE {
            zxGponOnuCapTcontNum                Integer32,
            zxGponOnuCapGemPortNum              Integer32,
            zxGponOnuCapTotalPriQueueNum        Integer32,
            zxGponOnuCapUpPriQueueNum           Integer32,
            zxGponOnuCapDownPriQueueNum         Integer32,
            zxGponOnuCapTrafficScheduleNum      Integer32,
            zxGponOnuCapTrafficMngMode          INTEGER,
            zxGponOnuCapTotalUniNum             Integer32,
            zxGponOnuCapEthUniNum               Integer32,
            zxGponOnuCapGeUniNum                Integer32,
            zxGponOnuCapFeUniNum                Integer32,
            zxGponOnuCapCesUniNum               Integer32,
            zxGponOnuCapPotsUniNum              Integer32,
            zxGponOnuCapVideoUniNum             Integer32,
            zxGponOnuCapWifiUniNum              Integer32,
            zxGponOnuCapIpHostNum               Integer32,
            zxGponOnuCapVeipNum                 Integer32,
            zxGponOnuCapOperatorId              DisplayString,
            zxGponOnuCapCtcSpecVersion          INTEGER,
            zxGponOnuCapOnuApplyType            INTEGER,
            zxGponOnuCapTxPowerSupplyCtrl       INTEGER
        }

    zxGponOnuCapTcontNum OBJECT-TYPE
        SYNTAX      Integer32
        MAX-ACCESS  read-only
        STATUS      current
        DESCRIPTION
        "This attribute reports the total number of TCONT-IDs supported
        by the ONU."
        ::= { zxGponOnuCapabilityEntry 1 }

    zxGponOnuCapGemPortNum OBJECT-TYPE
        SYNTAX      Integer32
        MAX-ACCESS  read-only
        STATUS      current
        DESCRIPTION
        "This attribute reports the total number of GEM port-IDs supported
        by the ONU."
        ::= { zxGponOnuCapabilityEntry 2 }

    zxGponOnuCapTotalPriQueueNum OBJECT-TYPE
        SYNTAX      Integer32
        MAX-ACCESS  read-only
        STATUS      current
        DESCRIPTION
        "This attribute reports the total number of priority queues
         supported by the ONU."
        ::= { zxGponOnuCapabilityEntry 3 }

    zxGponOnuCapUpPriQueueNum OBJECT-TYPE
        SYNTAX      Integer32
        MAX-ACCESS  read-only
        STATUS      current
        DESCRIPTION
        "This attribute reports the total number of upstream priority queues
         supported by the ONU."
        ::= { zxGponOnuCapabilityEntry 4 }

    zxGponOnuCapDownPriQueueNum OBJECT-TYPE
        SYNTAX      Integer32
        MAX-ACCESS  read-only
        STATUS      current
        DESCRIPTION
        "This attribute reports the total number of downstream priority queues
         supported by the ONU."
        ::= { zxGponOnuCapabilityEntry 5 }

    zxGponOnuCapTrafficScheduleNum OBJECT-TYPE
        SYNTAX      Integer32
        MAX-ACCESS  read-only
        STATUS      current
        DESCRIPTION
        "This attribute reports the total number of traffic schedule
         supported by the ONU."
        ::= { zxGponOnuCapabilityEntry 6 }

    zxGponOnuCapTrafficMngMode OBJECT-TYPE
        SYNTAX      INTEGER{
                    priority(1),
                    rate(2),
                    priorityAndRate(3),
                    unknown(65535)
                    }
        MAX-ACCESS  read-only
        STATUS      current
        DESCRIPTION
        "This attribute indicates that the mode of traffic management."
        ::= { zxGponOnuCapabilityEntry 7 }

    zxGponOnuCapTotalUniNum OBJECT-TYPE
        SYNTAX      Integer32
        MAX-ACCESS  read-only
        STATUS      current
        DESCRIPTION
        "This attribute reports the total number of UNI supported by the ONU."
        ::= { zxGponOnuCapabilityEntry 8 }

    zxGponOnuCapEthUniNum OBJECT-TYPE
        SYNTAX      Integer32
        MAX-ACCESS  read-only
        STATUS      current
        DESCRIPTION
        "This attribute reports the number of ethernet UNI supported
        by the ONU."
        ::= { zxGponOnuCapabilityEntry 9 }

    zxGponOnuCapGeUniNum OBJECT-TYPE
        SYNTAX      Integer32
        MAX-ACCESS  read-only
        STATUS      current
        DESCRIPTION
        "This attribute reports the number of GE UNI supported by the ONU."
        ::= { zxGponOnuCapabilityEntry 10 }

    zxGponOnuCapFeUniNum OBJECT-TYPE
        SYNTAX      Integer32
        MAX-ACCESS  read-only
        STATUS      current
        DESCRIPTION
        "This attribute reports the number of FE UNI supported by the ONU."
        ::= { zxGponOnuCapabilityEntry 11 }

    zxGponOnuCapCesUniNum OBJECT-TYPE
        SYNTAX      Integer32
        MAX-ACCESS  read-only
        STATUS      current
        DESCRIPTION
        "This attribute reports the number of CES UNI supported by the ONU."
        ::= { zxGponOnuCapabilityEntry 12 }

    zxGponOnuCapPotsUniNum OBJECT-TYPE
        SYNTAX      Integer32
        MAX-ACCESS  read-only
        STATUS      current
        DESCRIPTION
        "This attribute reports the number of POTS UNI supported by the ONU."
        ::= { zxGponOnuCapabilityEntry 13 }

    zxGponOnuCapVideoUniNum OBJECT-TYPE
        SYNTAX      Integer32
        MAX-ACCESS  read-only
        STATUS      current
        DESCRIPTION
        "This attribute reports the number of video UNI supported by the ONU."
        ::= { zxGponOnuCapabilityEntry 14 }

    zxGponOnuCapWifiUniNum OBJECT-TYPE
        SYNTAX      Integer32
        MAX-ACCESS  read-only
        STATUS      current
        DESCRIPTION
        "This attribute reports the number of WIFI UNI supported by the ONU."
        ::= { zxGponOnuCapabilityEntry 15 }

    zxGponOnuCapIpHostNum OBJECT-TYPE
        SYNTAX      Integer32
        MAX-ACCESS  read-only
        STATUS      current
        DESCRIPTION
        "This attribute reports the number of IP Host supported by the ONU."
        ::= { zxGponOnuCapabilityEntry 16 }

    zxGponOnuCapVeipNum OBJECT-TYPE
        SYNTAX      Integer32
        MAX-ACCESS  read-only
        STATUS      current
        DESCRIPTION
        "This attribute reports the number of virtual ethernet interface point
         supported by the ONU."
        ::= { zxGponOnuCapabilityEntry 17 }

    zxGponOnuCapOperatorId OBJECT-TYPE
        SYNTAX      DisplayString ( SIZE ( 0 .. 4 ) )
        MAX-ACCESS  read-only
        STATUS      current
        DESCRIPTION
        "This attribute indicates that the Operator id."
        ::= { zxGponOnuCapabilityEntry 18 }

    zxGponOnuCapCtcSpecVersion OBJECT-TYPE
         SYNTAX      INTEGER{
                     ctc2dot0(1),
                     unknown(65535)
                    }
        MAX-ACCESS  read-only
        STATUS      current
        DESCRIPTION
        "This attribute indicates that the CTC specific version."
        ::= { zxGponOnuCapabilityEntry 19 }

    zxGponOnuCapOnuApplyType OBJECT-TYPE
         SYNTAX      INTEGER{
                     sfu(1),
                     hgu(2),
                     sbu(3),
                     cbu(4),
                     mdu(5),
                     mtu(6),
                     unknown(65535)
                    }
        MAX-ACCESS  read-only
        STATUS      current
        DESCRIPTION
        "This attribute indicates that the type of ONU application."
        ::= { zxGponOnuCapabilityEntry 20 }

    zxGponOnuCapTxPowerSupplyCtrl OBJECT-TYPE
         SYNTAX      INTEGER{
                     notSupport(1),
                     supportTxCtrlOnly(2),
                     supportTxAndRxCtrlIndependently(3),
                     unknown(65535)
                    }
        MAX-ACCESS  read-only
        STATUS      current
        DESCRIPTION
        "This attribute indicates that the ONU type."
        ::= { zxGponOnuCapabilityEntry 21 }


--ONT DHCP Option60
    zxGponOnuDhcpOption60Table    OBJECT-TYPE
        SYNTAX      SEQUENCE OF ZxGponOnuDhcpOption60Entry
        MAX-ACCESS  not-accessible
        STATUS      current
        DESCRIPTION
            "Configuration of ONT DHCP Option60"
        REFERENCE   "Private OMCI ME, ONT3-G"
        ::= { zxGponRmONTEquipMgmt 15 }

    zxGponOnuDhcpOption60Entry OBJECT-TYPE
        SYNTAX      ZxGponOnuDhcpOption60Entry
        MAX-ACCESS  not-accessible
        STATUS      current
        DESCRIPTION
            "It is entry in the zxGponOnuDhcpOption60Table."
        INDEX   { zxGponOltIndex, zxGponONTIndex }
        ::= { zxGponOnuDhcpOption60Table 1 }

     ZxGponOnuDhcpOption60Entry ::=
        SEQUENCE {
            zxGponOnuDhcpOption60Enable             INTEGER,
            zxGponOnuDhcpOption60VendorId        DisplayString
        }

     zxGponOnuDhcpOption60Enable OBJECT-TYPE
        SYNTAX      INTEGER{
                    enabled(1),
                    disabled(2)
                    }
        MAX-ACCESS  read-write
        STATUS      current
        DESCRIPTION
        "This attribute controls whether the ONU should insert option60 string
        or not."
        REFERENCE   "OAM & PLOAM defined by ZTE section 3.1.2 ONT3-G"
        ::= { zxGponOnuDhcpOption60Entry 1 }

     zxGponOnuDhcpOption60VendorId OBJECT-TYPE
        SYNTAX      DisplayString(SIZE (0..128))
        MAX-ACCESS  read-write
        STATUS      current
        DESCRIPTION
        "This attribute contains the vendor class identifier when option60
        insertion is enabled on ONU.If option60 is disabled,
        'zxGponOnuDhcpOption60VendorId' size is 0."
        REFERENCE   "OAM & PLOAM defined by ZTE section 3.1.2 ONT3-G"
        ::= { zxGponOnuDhcpOption60Entry 2 }

--ANI management/9.2
    zxGponPonTable    OBJECT-TYPE
        SYNTAX      SEQUENCE OF ZxGponPonEntry
        MAX-ACCESS  not-accessible
        STATUS      current
        DESCRIPTION
            "This managed entity is used to organize data associated with the
            Access Network Interface supported by the ONT.
            One instance of this managed entity exists for each PON physical port.
            One or more instance of this managed entity are contained in an instance of
            a circuit pack that supports a PON IF function."
        ::= { zxGponRmANIMgmt 1 }

    zxGponPonEntry OBJECT-TYPE
        SYNTAX      ZxGponPonEntry
        MAX-ACCESS  not-accessible
        STATUS      current
        DESCRIPTION
            "It is entry in the zxGponPonTable."
        INDEX   { zxGponOltIndex, zxGponONTIndex, zxGponPonIndex }
        ::= { zxGponPonTable 1 }

    ZxGponPonEntry ::=
        SEQUENCE {
            zxGponPonSRInd                     TruthValue,
            zxGponPonTotalTcontNum             INTEGER,
            zxGponPonGemBlockLen               INTEGER,
            zxGponPonPiggybackDBAReporting     INTEGER,
            zxGponPonWholeOnuDBAReporting      INTEGER,
            zxGponPonSFThreshold               INTEGER,
            zxGponPonSDThreshold               INTEGER,
            zxGponPonAlarmReport               INTEGER,
            zxGponPonAlarmDisableInterval      INTEGER,
            zxGponPonRxOpticalLevel            INTEGER,
            zxGponPonLowerRxOpticalThreshold   INTEGER,
            zxGponPonUpperRxOpticalThreshold   INTEGER,
            zxGponPonOntResponseTime           INTEGER,
            zxGponPonTxOpticalLevel            INTEGER,
            zxGponPonLowerTxOpticalThreshold   INTEGER,
            zxGponPonUpperTxOpticalThreshold   INTEGER,
            zxGponPonPowerFeedVoltage          INTEGER,
            zxGponPonLaserBiasCurrent          INTEGER,
            zxGponPonTemperature               INTEGER,
            zxGponPonLowerVoltageThreshold     INTEGER,
            zxGponPonUpperVoltageThreshold     INTEGER,
            zxGponPonLowerCurrentThreshold     INTEGER,
            zxGponPonUpperCurrentThreshold     INTEGER,
            zxGponPonLowerTemperatureThreshold INTEGER,
            zxGponPonUpperTemperatureThreshold INTEGER
        }

    zxGponPonSRInd OBJECT-TYPE
        SYNTAX      TruthValue
        MAX-ACCESS  read-only
        STATUS      current
        DESCRIPTION
        "This Boolean attribute indicates the capability of status reporting. The
        value TRUE means that the status reporting is available for all T-CONTs which
        are associated with the ANI. The default value is false.(1 bytes)"
        REFERENCE   "G.984.4 section 9.2.1 ANI-G"
        DEFVAL {false}
        ::= { zxGponPonEntry 1 }

    zxGponPonTotalTcontNum OBJECT-TYPE
        SYNTAX      INTEGER
        MAX-ACCESS  read-only
        STATUS      current
        DESCRIPTION
        "This attribu provides the total number of T-CONTs that are able to be supported
        in this ANI port.(2 bytes)"
        REFERENCE   "G.984.4 section 9.2.1 ANI-G"
        ::= { zxGponPonEntry 2 }

    zxGponPonGemBlockLen OBJECT-TYPE
        SYNTAX      INTEGER
        MAX-ACCESS  read-write
        STATUS      current
        DESCRIPTION
        "This attribute indicates the reporting block size for GEM mode in units of bytes.
        The value which the OLT sets is used by all T-CONTs in this ANI.
        Upon autonomous instantiation this attribute consists of the value 0x0030.(2 bytes)"
        REFERENCE   "G.984.4 section 9.2.1 ONT2-G"
        ::= { zxGponPonEntry 3 }

    zxGponPonPiggybackDBAReporting OBJECT-TYPE
        SYNTAX      INTEGER{
                    mode0Only(1),
                    mode01(2),
                    mode02(3),
                    mode012(4),
                    notsupport(5)
                    }
        MAX-ACCESS  read-only
        STATUS      current
        DESCRIPTION
        "The following coding is used to indicate the ONT's piggyback DBA reporting
        mode capabilities:
        0x00: supports mode 0 only;
        0x01: supports modes 0 and 1;
        0x02: supports modes 0 and 2;
        0x03: supports modes 0,1,and 2;
        0x04: piggyback DBA reporting not supported.(1 byte)"
        REFERENCE   "G.984.4 section 9.2.1 ANI-G"
        ::= { zxGponPonEntry 4 }

    zxGponPonWholeOnuDBAReporting OBJECT-TYPE
        SYNTAX      INTEGER{
                    notsupport(1),
                    support(2)
                    }
        MAX-ACCESS  read-only
        STATUS      current
        DESCRIPTION
            "Valid values are 0x00 (whole ONU DBA reporting is not supported)
            and 0x01 (whole ONU DBA reporting is supported).(1 byte)"
        REFERENCE
            "G.984.4 Section 9.2.1 ANI-G"
        ::= { zxGponPonEntry 5}

    zxGponPonSFThreshold OBJECT-TYPE
        SYNTAX      INTEGER
        MAX-ACCESS  read-write
        STATUS      current
        DESCRIPTION
            "This attribute represents the upstream/downstream BER threshold to detect SFi/SF alarm.
            When this value is y in decimal, the BER threshold for SFi/SF is 10^(-y).
            The valid values are from 3 to 8 inclusive.
            Upon autonomous instantiation, this attribute consists of 5.(1 byte)"
        REFERENCE
            "G.984.4 Section 9.2.1 ANI-G"
        ::= { zxGponPonEntry 6}

    zxGponPonSDThreshold OBJECT-TYPE
        SYNTAX      INTEGER
        MAX-ACCESS  read-write
        STATUS      current
        DESCRIPTION
            "This attribute represents the upstream/downstream BER threshold to detect SDi/SD alarm.
            When this value is x in decimal, the BER threshold for SDi/SD is 10^(-x).
            The valid values are from 4 to 10 inclusive. Please note that the SD threshold shall be
            smaller than the SF threshold. This means that the value of x shall be larger than the value of y.
            Upon autonomous instantiation, this attribute consists of 9.(1 byte)"
        REFERENCE
            "G.984.4 Section 9.2.1 ANI-G"
        ::= { zxGponPonEntry 7}

    zxGponPonAlarmReport OBJECT-TYPE
        SYNTAX      INTEGER
        MAX-ACCESS  read-write
        STATUS      current
        DESCRIPTION
            "Alarm reporting control.
             0(enable): Allow alarm reporting, 1(disable): Suppress alarm reporting.(1 byte)"
        REFERENCE
            "G.984.4 Section 9.2.1 ANI-G"
        ::= { zxGponPonEntry 8}

    zxGponPonAlarmDisableInterval OBJECT-TYPE
        SYNTAX      INTEGER
        MAX-ACCESS  read-write
        STATUS      current
        DESCRIPTION
            "Alarm reporting control interval.
             0: Allow alarm reporting immediately when port is trouble free.
             1-254: The duration in minutes for alarm suppression.
             255: Suppress alarm reporting until alarm is enabled. (1 byte)"
        REFERENCE
            "G.984.4 Section 9.2.1 ANI-G"
        ::= { zxGponPonEntry 9}

    zxGponPonRxOpticalLevel OBJECT-TYPE
        SYNTAX      INTEGER
        MAX-ACCESS  read-only
        STATUS      current
        DESCRIPTION
            "This attribute reports the current measurement of total
             optical signal level at 1490 nm. Its value is a 2s complement
             integer referred to 1 mW (ie dBm), with 0.002 dB granularity.(2 byte)"
        REFERENCE
            "G.984.4 Section 9.2.1 ANI-G"
        ::= { zxGponPonEntry 10}

    zxGponPonLowerRxOpticalThreshold OBJECT-TYPE
        SYNTAX      INTEGER
        MAX-ACCESS  read-write
        STATUS      current
        DESCRIPTION
            "This attribute specifies the optical level the ONT uses to
            declare the 1490 nm low received optical power alarm.
            Valid values are -127 dBm (coded as 254) to 0 dBm (coded as 0)
            in 0.5 dB increments. The default value 0xFF selects the ONT's internal policy.(1 byte)"
        REFERENCE
            "G.984.4 Section 9.2.1 ANI-G"
        ::= { zxGponPonEntry 11}

    zxGponPonUpperRxOpticalThreshold OBJECT-TYPE
        SYNTAX      INTEGER
        MAX-ACCESS  read-write
        STATUS      current
        DESCRIPTION
            "This attribute specifies the optical level the ONT uses to
            declare the 1490 nm high received optical power alarm.
            Valid values are -127 dBm (coded as 254) to 0 dBm (coded as 0)
            in 0.5 dB increments. The default value 0xFF selects the ONT's internal policy.(1 byte)"
        REFERENCE
            "G.984.4 Section 9.2.1 ANI-G"
        ::= { zxGponPonEntry 12}

    zxGponPonOntResponseTime OBJECT-TYPE
        SYNTAX      INTEGER
        MAX-ACCESS  read-only
        STATUS      current
        DESCRIPTION
            "This attribute indicates actual ONT response time recorded by ONT.
             The unit is nanoseconds.(2 byte)"
        REFERENCE
            "G.984.4 Section 9.2.1 ANI-G"
        ::= { zxGponPonEntry 13}

    zxGponPonTxOpticalLevel OBJECT-TYPE
        SYNTAX      INTEGER
        MAX-ACCESS  read-only
        STATUS      current
        DESCRIPTION
            "This attribute reports the current measurement of optical
             transmit power level. Its value is a 2s complement integer
             referred to 1 mW (ie dBm), with 0.002 dB granularity.(2 byte)"
        REFERENCE
            "G.984.4 Section 9.2.1 ANI-G"
        ::= { zxGponPonEntry 14}

    zxGponPonLowerTxOpticalThreshold OBJECT-TYPE
        SYNTAX      INTEGER
        MAX-ACCESS  read-write
        STATUS      current
        DESCRIPTION
            "This attribute specifies the transmit power level the ONT uses to
            declare the low transmit optical power alarm. Its value is a 2s complement
            integer referred to 1 mW (ie dBm), with 0.5 dB granularity.
            The default value -63.5 (0x81) selects the ONT's internal policy.(1 byte)"
        REFERENCE
            "G.984.4 Section 9.2.1 ANI-G"
        ::= { zxGponPonEntry 15}

    zxGponPonUpperTxOpticalThreshold OBJECT-TYPE
        SYNTAX      INTEGER
        MAX-ACCESS  read-write
        STATUS      current
        DESCRIPTION
            "This attribute specifies the transmit power level the ONT uses to
            declare the high transmit optical power alarm. Its value is a 2s complement
            integer referred to 1 mW (ie dBm), with 0.5 dB granularity.
            The default value -63.5 (0x81) selects the ONT's internal policy.(1 byte)"
        REFERENCE
            "G.984.4 Section 9.2.1 ANI-G"
        ::= { zxGponPonEntry 16}

    zxGponPonPowerFeedVoltage OBJECT-TYPE
        SYNTAX      INTEGER
        MAX-ACCESS  read-only
        STATUS      current
        DESCRIPTION
            "DC voltage, 2s complement, 20 mV resolution.(2 byte)"
        REFERENCE
            "G.984.4 Section 11.1.10 Test result enumeration"
        ::= { zxGponPonEntry 17}

    zxGponPonLaserBiasCurrent OBJECT-TYPE
        SYNTAX      INTEGER
        MAX-ACCESS  read-only
        STATUS      current
        DESCRIPTION
            "2s complement, 2 uA resolution.(2 byte)"
        REFERENCE
            "G.984.4 Section 11.1.10 Test result enumeration"
        ::= { zxGponPonEntry 18}

    zxGponPonTemperature OBJECT-TYPE
        SYNTAX      INTEGER
        MAX-ACCESS  read-only
        STATUS      current
        DESCRIPTION
            "2s complement, 1/256 degree C resolution.(2 byte)"
        REFERENCE
            "G.984.4 Section 11.1.10 Test result enumeration"
        ::= { zxGponPonEntry 19}

    zxGponPonLowerVoltageThreshold OBJECT-TYPE
        SYNTAX      INTEGER
        MAX-ACCESS  read-write
        STATUS      current
        DESCRIPTION
            "(2 byte)"
        REFERENCE
            "G.984.4 Section 9.2.1 ANI-G"
        ::= { zxGponPonEntry 20}

    zxGponPonUpperVoltageThreshold OBJECT-TYPE
        SYNTAX      INTEGER
        MAX-ACCESS  read-write
        STATUS      current
        DESCRIPTION
            "(2 byte)"
        REFERENCE
            "G.984.4 Section 9.2.1 ANI-G"
        ::= { zxGponPonEntry 21}

    zxGponPonLowerCurrentThreshold OBJECT-TYPE
        SYNTAX      INTEGER
        MAX-ACCESS  read-write
        STATUS      current
        DESCRIPTION
            "(2 byte)"
        REFERENCE
            "G.984.4 Section 9.2.1 ANI-G"
        ::= { zxGponPonEntry 22}

    zxGponPonUpperCurrentThreshold OBJECT-TYPE
        SYNTAX      INTEGER
        MAX-ACCESS  read-write
        STATUS      current
        DESCRIPTION
            "(2 byte)"
        REFERENCE
            "G.984.4 Section 9.2.1 ANI-G"
        ::= { zxGponPonEntry 23}

    zxGponPonLowerTemperatureThreshold OBJECT-TYPE
        SYNTAX      INTEGER
        MAX-ACCESS  read-write
        STATUS      current
        DESCRIPTION
            "(2 byte)"
        REFERENCE
            "G.984.4 Section 9.2.1 ANI-G"
        ::= { zxGponPonEntry 24}

    zxGponPonUpperTemperatureThreshold OBJECT-TYPE
        SYNTAX      INTEGER
        MAX-ACCESS  read-write
        STATUS      current
        DESCRIPTION
            "(2 byte)"
        REFERENCE
            "G.984.4 Section 9.2.1 ANI-G"
        ::= { zxGponPonEntry 25}


--flow management
    zxGponFlowTable    OBJECT-TYPE
        SYNTAX      SEQUENCE OF ZxGponFlowEntry
        MAX-ACCESS  not-accessible
        STATUS      current
        DESCRIPTION
            "Configuration of flow."
        ::= { zxGponRmFlowMgmt 1 }

    zxGponFlowEntry OBJECT-TYPE
        SYNTAX      ZxGponFlowEntry
        MAX-ACCESS  not-accessible
        STATUS      current
        DESCRIPTION
            "It is entry in the zxGponFlowTable."
        INDEX   { zxGponOltIndex, zxGponONTIndex, zxGponFlowIndex }
        ::= { zxGponFlowTable 1 }

    ZxGponFlowEntry ::=
        SEQUENCE {
            zxGponFlowType                   INTEGER,
            zxGponFlowIfId                   INTEGER,
            zxGponFlowEntryStatus            RowStatus
        }

    zxGponFlowType OBJECT-TYPE
        SYNTAX      INTEGER{
                    switch(1),
                    ethuni(2),
                    ethflow(3),
                    iphost(4)
                    }
        MAX-ACCESS  read-write
        STATUS      current
        DESCRIPTION
        "This attribute indicates the upstream mapping type of flow. Default as type of 'switch'."
        REFERENCE   ""
        ::= { zxGponFlowEntry 1 }

    zxGponFlowIfId OBJECT-TYPE
        SYNTAX      INTEGER
        MAX-ACCESS  read-write
        STATUS      current
        DESCRIPTION
        "The interface id which is related with this flow.
         It can be the IfId of switch, ethuni, ethflow or iphost, according to the zxGponFlowType.
         The format as below:
         zxGponFlowType      1st byte       2nd byte           3rd byte              4th byte
           switch            reserved       reserved      slot of switch(0~255)    switch index(1~255)
           ethuni            reserved       reserved      slot of ethuni(0~255)    ethuni index(1~255)
           ethflow           reserved       reserved      slot of cesuni(0~255)    cesuni index(1~255)
           iphost            reserved       reserved           reserved            iphost index(1~255)
         (4 bytes)"
        REFERENCE   ""
        ::= { zxGponFlowEntry 2 }

    zxGponFlowEntryStatus OBJECT-TYPE
        SYNTAX      RowStatus
        MAX-ACCESS  read-write
        STATUS      current
        DESCRIPTION
        "This attribute indicates the operation of the entry."
        REFERENCE   ""
        ::= { zxGponFlowEntry 3 }

    zxGponFlowTciModeTable    OBJECT-TYPE
        SYNTAX      SEQUENCE OF ZxGponFlowTciModeEntry
        MAX-ACCESS  not-accessible
        STATUS      current
        DESCRIPTION
            "This managed entity is used to set the upstream tci mapping mode of the flow.
             It only can be set if the 'type' of flow is 'switch'.
             It also can say that if the 'tciMode' is not 'NA(65535)'."
        REFERENCE   "G.984.4"
        ::= { zxGponRmFlowMgmt 2 }

    zxGponFlowTciModeEntry OBJECT-TYPE
        SYNTAX      ZxGponFlowTciModeEntry
        MAX-ACCESS  not-accessible
        STATUS      current
        DESCRIPTION
            "It is entry in the zxGponFlowTciModeTable."
        INDEX   { zxGponOltIndex, zxGponONTIndex, zxGponFlowIndex }
        ::= { zxGponFlowTciModeTable 1 }

    ZxGponFlowTciModeEntry ::=
        SEQUENCE {
            zxGponFlowTciModeForwardOper            INTEGER
        }

    zxGponFlowTciModeForwardOper OBJECT-TYPE
        SYNTAX      INTEGER{
                    mode0(1),
                    mode1(2),
                    mode2(3),
                    mode3(4),
                    mode4(5),
                    mode5(6),
                    mode6(7),
                    mode7(8),
                    mode8(9),
                    mode9(10),
                    mode10(11),
                    mode11(12),
                    mode12(13),
                    mode13(14),
                    mode14(15),
                    mode15(16),
                    mode16(17),
                    mode17(18),
                    mode18(19),
                    mode19(20),
                    mode20(21),
                    mode21(22)
                    }
        MAX-ACCESS  read-write
        STATUS      current
        DESCRIPTION
        "When a frame is received, the frame is processed according to the following Forward
        Operations. The operations are invoked based on the value of VID, user priority, or
        the entire TCI or whether or not the TCI field exists. This attribute indicates the
        received frame is treated as indicated below.(1 byte)
        !!!!!!mode5/6/9/10/13/14 is no used currently!!!!!!!
        tag-filter-action      untag-filter-action      forward-mode
        'transparent'          'transparent'            'mode0'
        'discard'              'transparent'            'mode1'
        'transparent'          'discard'                'mode2'
        'vid-filter'           'transparent'            'mode3'
        'vid-filter'           'discard'                'mode4'
        'prio-filter'          'transparent'            'mode7'
        'prio-filter'          'discard'                'mode8'
        'prio-vid-filter'      'transparent'            'mode11'
        'prio-vid-filter'      'discard'                'mode12'
        'vid-match'            'transparent'            'mode15'
        'vid-match'            'discard'                'mode16'
        'prio-match'           'transparent'            'mode17'
        'prio-match'           'discard'                'mode18'
        'prio-vid-match'       'transparent'            'mode19'
        'prio-vid-match'       'discard'                'mode20'
        'forward'              'discard'                'mode21'
        The action of filter means that if the tci of a flow is not in the filer-list, it will be forwarded by l2 address;
        The action of match means that if the tci of a flow is not in the filer-list, it will be discarded;
        "
        REFERENCE   "G.983.2 section 7.3.50 VLAN tagging filter data"
        ::= { zxGponFlowTciModeEntry 1 }

    zxGponFlowTciTable    OBJECT-TYPE
        SYNTAX      SEQUENCE OF ZxGponFlowTciEntry
        MAX-ACCESS  not-accessible
        STATUS      current
        DESCRIPTION
            "When the tci mode of the flow is vid-filter/prio-filter/prio-vid-filter/vid-match/prio-match/prio-vid-match,
             the tci entries can be added."
        REFERENCE   "G.983.2 section 7.3.50 VLAN tagging filter data"
        ::= { zxGponRmFlowMgmt 3 }

    zxGponFlowTciEntry OBJECT-TYPE
        SYNTAX      ZxGponFlowTciEntry
        MAX-ACCESS  not-accessible
        STATUS      current
        DESCRIPTION
            "It is entry in the zxGponFlowTciTable."
        INDEX   { zxGponOltIndex, zxGponONTIndex, zxGponFlowIndex, zxGponFlowTciIndex }
        ::= { zxGponFlowTciTable 1 }

    ZxGponFlowTciEntry ::=
        SEQUENCE {
            zxGponFlowTciIndex                  INTEGER,
            zxGponFlowTciEntryStatus            RowStatus
        }

    zxGponFlowTciIndex OBJECT-TYPE
        SYNTAX      INTEGER
        MAX-ACCESS  read-write
        STATUS      current
        DESCRIPTION
        "This attribute specifies the TCI value which is provisioned at a bridging port.(2 bytes)"
        REFERENCE   "G.983.2 section 7.3.50 VLAN tagging filter data"
        ::= { zxGponFlowTciEntry 1 }

    zxGponFlowTciEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponFlowTciEntry 2 }

    zxGponGemFlowTable    OBJECT-TYPE
        SYNTAX      SEQUENCE OF ZxGponGemFlowEntry
        MAX-ACCESS  not-accessible
        STATUS      current
        DESCRIPTION
            "Configuration of GEM flow."
        ::= { zxGponRmFlowMgmt 4 }

    zxGponGemFlowEntry OBJECT-TYPE
        SYNTAX      ZxGponGemFlowEntry
        MAX-ACCESS  not-accessible
        STATUS      current
        DESCRIPTION
            "It is entry in the zxGponGemFlowTable."
        INDEX   { zxGponOltIndex, zxGponONTIndex, zxGponGemPortIndex }
        ::= { zxGponGemFlowTable 1 }

    ZxGponGemFlowEntry ::=
        SEQUENCE {
            zxGponGemFlowId                   INTEGER,
            zxGponGemFlowPriBitMap            INTEGER,
            zxGponGemFlowEntryStatus          RowStatus
        }

    zxGponGemFlowId OBJECT-TYPE
        SYNTAX      INTEGER(1..255)
        MAX-ACCESS  read-write
        STATUS      current
        DESCRIPTION
        "This attribute indicates the flow id related with this GEM flow."
        REFERENCE   ""
        ::= { zxGponGemFlowEntry 1 }

    zxGponGemFlowPriBitMap OBJECT-TYPE
        SYNTAX      INTEGER
        MAX-ACCESS  read-write
        STATUS      current
        DESCRIPTION
        "This attribute indicates the priority bit map of this GEM flow.
         This bitmap specifies the priorities used by this connection when using 802.1p mapping.
        Each bit from bit0(LSB) to bit7(MSB) indicates whether priority0~priority7 is occupied.
        When the flow type of zxGponGemFlowId is not 'switch', zxGponGemFlowPriBitMap must be assigned non-zero;
        Otherwise, zxGponGemFlowPriBitMap is optional which can be assigned as zero.(1 byte)"
        REFERENCE   ""
        ::= { zxGponGemFlowEntry 2 }

    zxGponGemFlowEntryStatus OBJECT-TYPE
        SYNTAX      RowStatus
        MAX-ACCESS  read-write
        STATUS      current
        DESCRIPTION
        "This attribute indicates the operation of the entry."
        REFERENCE   ""
        ::= { zxGponGemFlowEntry 3 }

--GEMPort Loopback
    zxGponGemLoopTable    OBJECT-TYPE
        SYNTAX      SEQUENCE OF ZxGponGemLoopEntry
        MAX-ACCESS  not-accessible
        STATUS      current
        DESCRIPTION
            "Configuration of GEM loopback."
        ::= { zxGponRmFlowMgmt 5 }

    zxGponGemLoopEntry OBJECT-TYPE
        SYNTAX      ZxGponGemLoopEntry
        MAX-ACCESS  not-accessible
        STATUS      current
        DESCRIPTION
            "It is entry in the zxGponGemLoopTable."
        INDEX   { zxGponOltIndex, zxGponONTIndex, zxGponGemPortIndex }
        ::= { zxGponGemLoopTable 1 }

    ZxGponGemLoopEntry ::=
        SEQUENCE {
            zxGponGemLoopConfig                   INTEGER
        }

    zxGponGemLoopConfig OBJECT-TYPE
        SYNTAX      INTEGER{
                    no-loop(1),
                    loop(2)
                    }
        MAX-ACCESS  read-write
        STATUS      current
        DESCRIPTION
        "This attribute indicates the loop configuration with this GEMPort."
        REFERENCE   ""
        ::= { zxGponGemLoopEntry 1 }


--Ethernet management
--PPTP ETH UNI
    zxGponPptpEthUNITable    OBJECT-TYPE
        SYNTAX      SEQUENCE OF ZxGponPptpEthUNIEntry
        MAX-ACCESS  not-accessible
        STATUS      current
        DESCRIPTION
            "This managed entity represents the points at an Ethernet UNI in the ONT where physical paths
            terminate and physical path level functions (e.g., Ethernet function) are performed.
            One or more instances of this managed entity shall be contained in an instance of a Circuit Pack
            managed entity classified as a native LAN type (e.g., Ethernet)."
        REFERENCE   "G.983.2 section 7.3.2 Physical path termination point Ethernet UNI"
        ::= { zxGponRmEthMgmt 1 }

    zxGponPptpEthUNIEntry OBJECT-TYPE
        SYNTAX      ZxGponPptpEthUNIEntry
        MAX-ACCESS  not-accessible
        STATUS      current
        DESCRIPTION
            "It is entry in the zxGponPptpEthUNITable."
        INDEX   { zxGponOltIndex, zxGponONTIndex, zxGponUNIIndex }
        ::= { zxGponPptpEthUNITable 1 }

    ZxGponPptpEthUNIEntry ::=
        SEQUENCE {
            zxGponPptpEthUNIExpectedType            INTEGER,
            zxGponPptpEthUNISensedType              INTEGER,
            zxGponPptpEthUNIIfSpeedConfig           INTEGER,
            zxGponPptpEthUNIEthLookbackConfig       INTEGER,
            zxGponPptpEthUNIAdminState              INTEGER,
            zxGponPptpEthUNIOperState               INTEGER,
            zxGponPptpEthUNIIfSpeedStatus           INTEGER,
            zxGponPptpEthUNIMaxFrameSize            INTEGER,
            zxGponPptpEthUNIDteOrDceInd             INTEGER,
            zxGponPptpEthUNIPauseTime               INTEGER,
            zxGponPptpEthUNIBridgeOrIpInd           INTEGER,
            zxGponPptpEthUNIARC                     INTEGER,
            zxGponPptpEthUNIARCInterval             INTEGER,
            zxGponPptpEthUNIPPPoEFilter             INTEGER,
            zxGponPptpEthUNIPowerControl            INTEGER
        }

    zxGponPptpEthUNIExpectedType OBJECT-TYPE
        SYNTAX      INTEGER
        MAX-ACCESS  read-write
        STATUS      current
        DESCRIPTION
        "The following coding is used for this attribute: 0x00 = by autosensing,
        0x01 to 0xFE (1 to 254) = one of the values from Table 3 that is compatible with the
        type of the LIM. Upon autonomous instantiation, the value 0x00 is used.(1 byte)"
        REFERENCE   "G.983.2 section 7.3.2 Physical path termination point Ethernet UNI"
        ::= { zxGponPptpEthUNIEntry 1 }

    zxGponPptpEthUNISensedType OBJECT-TYPE
        SYNTAX      INTEGER
        MAX-ACCESS  read-only
        STATUS      current
        DESCRIPTION
        "If the value of 'Expected type' is not equal to 0x00, then the value of 'Sensed type'
        equals the value of 'Expected type'. If the value of 'Expected type' equals 0x00, then
        the value of 'Sensed type' equals one of the values from Table 3 (0x01 to 0xFE) and by
        necessity is compatible with the Type of the Circuit Pack managed entity.
        Upon autonomous instantiation, the value 0x00 is used.(1 byte)"
        REFERENCE   "G.983.2 section 7.3.2 Physical path termination point Ethernet UNI"
        ::= { zxGponPptpEthUNIEntry 2 }

    zxGponPptpEthUNIIfSpeedConfig OBJECT-TYPE
        SYNTAX      INTEGER{
                    auto(1),
                    half10(2),
                    full10(3),
                    half100(4),
                    full100(5),
                    full1000(6)
                    }
        MAX-ACCESS  read-write
        STATUS      current
        DESCRIPTION
        "For 10/100 Base-Tx Ethernet interfaces, this attribute is used to set the configuration
        options:
        Auto-sensing: 0x00;
        10BaseT: 0x01;
        100BaseT: 0x02:
        Gigabit Ethernet: 0x03;
        10BaseT Auto-sensing: 0x10;
        10BaseT (half duplex): 0x11;
        100BaseT (half duplex): 0x12;
        Gigabit Ethernet (half duplex): 0x13;
        Gigabit Ethernet Auto-sensing: 0x20.
        Upon autonomous instantiation, the value 0x00 is used.(1 byte)"
        REFERENCE   "G.983.2 section 7.3.2 Physical path termination point Ethernet UNI"
        ::= { zxGponPptpEthUNIEntry 3 }

    zxGponPptpEthUNIEthLookbackConfig OBJECT-TYPE
        SYNTAX      INTEGER{
                    noloop(1),
                    loop3(4)
                    }
        MAX-ACCESS  read-write
        STATUS      current
        DESCRIPTION
        "This attribute is used to set the Ethernet loopback configuration:
        No loopback (value 0x00), Loop3 (value 0x03, Loopback of downstream traffic after PHY transceiver).
        Upon autonomous instantiation, the value 0x00 is used.(1 byte)"
        REFERENCE   "G.983.2 section 7.3.2 Physical path termination point Ethernet UNI"
        ::= { zxGponPptpEthUNIEntry 4 }

    zxGponPptpEthUNIAdminState OBJECT-TYPE
        SYNTAX      INTEGER{
                    unlock(1),
                    lock(2)
                    }
        MAX-ACCESS  read-write
        STATUS      current
        DESCRIPTION
        "This attribute is used to activate (unlock: value 0x00) and deactivate (lock: value 0x01)
        the functions performed by instances of this managed entity.(1 byte)"
        REFERENCE   "G.983.2 section 7.3.2 Physical path termination point Ethernet UNI"
        ::= { zxGponPptpEthUNIEntry 5 }

    zxGponPptpEthUNIOperState OBJECT-TYPE
        SYNTAX      INTEGER{
                    enable(1),
                    disable(2)
                    }
        MAX-ACCESS  read-only
        STATUS      current
        DESCRIPTION
        "This attribute indicates whether or not this managed entity is capable of performing
        its task. The operational state reflects the perceived ability to receive or to generate
        a valid signal. Valid values are enabled (0x00) and disabled (0x01).(1 byte)"
        REFERENCE   "G.983.2 section 7.3.2 Physical path termination point Ethernet UNI"
        ::= { zxGponPptpEthUNIEntry 6 }

    zxGponPptpEthUNIIfSpeedStatus OBJECT-TYPE
        SYNTAX      INTEGER{
                    auto(1),
                    half10(2),
                    full10(3),
                    half100(4),
                    full100(5),
                    full1000(6)
                    }
        MAX-ACCESS  read-only
        STATUS      current
        DESCRIPTION
        "This attribute indicates the configuration status of the Ethernet UNI.
        10BaseT (full duplex): 0x01;
        100BaseT (full duplex): 0x02;
        Gigabit Ethernet (full duplex): 0x03;
        10BaseT (half duplex): 0x11;
        100BaseT (half duplex): 0x12
        Gigabit Ethernet (half duplex): 0x13;
        When the configuration status is not detected (e.g., Ethernet link is not
        established or line card is not yet installed), the value 0x00 is used.
        Upon autonomous instantiation, the value 0x00 is used.(1 byte)"
        REFERENCE   "G.983.2 section 7.3.2 Physical path termination point Ethernet UNI"
        ::= { zxGponPptpEthUNIEntry 7 }

    zxGponPptpEthUNIMaxFrameSize OBJECT-TYPE
        SYNTAX      INTEGER
        MAX-ACCESS  read-write
        STATUS      current
        DESCRIPTION
        "This attribute denotes the maximum allowed frame size to be transmitted across this interface.
        Upon autonomous instantiation, the value 1518 is used.(2 bytes)"
        REFERENCE   "G.983.2 section 7.3.2 Physical path termination point Ethernet UNI"
        ::= { zxGponPptpEthUNIEntry 8 }

    zxGponPptpEthUNIDteOrDceInd OBJECT-TYPE
        SYNTAX      INTEGER{
                    dce(1),
                    dte(2)
                    }
        MAX-ACCESS  read-write
        STATUS      current
        DESCRIPTION
        "This attribute indicates whether the Ethernet interface wiring is DTE or DCE (DCE: 0x00; DTE: 0x01).
        Upon autonomous instantiation, the value 0x00 is used.(1 byte)"
        REFERENCE   "G.983.2 section 7.3.2 Physical path termination point Ethernet UNI"
        ::= { zxGponPptpEthUNIEntry 9 }

    zxGponPptpEthUNIPauseTime OBJECT-TYPE
        SYNTAX      INTEGER
        MAX-ACCESS  read-write
        STATUS      current
        DESCRIPTION
        "This attribute allows the ONT line card to request that the customer terminal temporarily
        suspend sending data. Units are in 'pause_quanta' (1 pause_quantum equals 512 bits times of
        the particular implementation). Values: 0x0000 to 0xFFFF.
        Upon autonomous instantiation, the value 0x0000 is used.(2 bytes)"
        REFERENCE   "G.983.2 section 7.3.2 Physical path termination point Ethernet UNI"
        ::= { zxGponPptpEthUNIEntry 10 }

    zxGponPptpEthUNIBridgeOrIpInd OBJECT-TYPE
        SYNTAX      INTEGER{
                    bridged(1),
                    ipRouter(2),
                    either(3)
                    }
        MAX-ACCESS  read-write
        STATUS      current
        DESCRIPTION
        "This attribute indicates whether the Ethernet interface is bridged or derived from an
        IP router function (Bridged: 0x00; IP router: 0x01; 0x02: depends on Circuit Pack.)
        0x02 means that the SLC 'BridgedorIPInd' attribute will be either 0x00 or 0x01.
        Upon autonomous instantiation, the value 0x02 is used.(1 byte)"
        REFERENCE   "G.983.2 section 7.3.2 Physical path termination point Ethernet UNI"
        ::= { zxGponPptpEthUNIEntry 11 }

    zxGponPptpEthUNIARC OBJECT-TYPE
        SYNTAX      INTEGER
        MAX-ACCESS  read-write
        STATUS      current
        DESCRIPTION
        "This attribute is used to control alarm reporting from this managed entity.
        See I.1.8 for a complete description.(1 byte)"
        REFERENCE   "G.983.2 section 7.3.2 Physical path termination point Ethernet UNI"
        ::= { zxGponPptpEthUNIEntry 12 }

    zxGponPptpEthUNIARCInterval OBJECT-TYPE
        SYNTAX      INTEGER
        MAX-ACCESS  read-write
        STATUS      current
        DESCRIPTION
        "This attribute provides a provisionable length of time. See I.1.8 for a complete description.(1 byte)"
        REFERENCE   "G.983.2 section 7.3.2 Physical path termination point Ethernet UNI"
        ::= { zxGponPptpEthUNIEntry 13 }

    zxGponPptpEthUNIPPPoEFilter OBJECT-TYPE
        SYNTAX      INTEGER{
                    filterDisable(1),
                    filterEnable(2)
                    }
        MAX-ACCESS  read-write
        STATUS      current
        DESCRIPTION
        "This attribute may be used to control filtering of PPPoE packets on this Ethernet port.
        The value 0x00 is used to disable filtering. The value 0x01 is used to enable filtering.
        When filtering is enabled, all packets other than PPPoE packets will be discarded.
        Default value is 0x00.(1 byte)"
        REFERENCE   "G.983.2 section 7.3.2 Physical path termination point Ethernet UNI"
        ::= { zxGponPptpEthUNIEntry 14 }

    zxGponPptpEthUNIPowerControl OBJECT-TYPE
        SYNTAX      INTEGER{
                    controlDisable(1),
                    controlEnable(2)
                    }
        MAX-ACCESS  read-write
        STATUS      current
        DESCRIPTION
        "This attribute controls whether power is provided to an external equipment over the
        Ethernet PPTP. Value 0x01 enables power over Ethernet.
        The default value 0x00 disables power feed.(1 byte)"
        REFERENCE   "G.983.2 section 7.3.2 Physical path termination point Ethernet UNI"
        ::= { zxGponPptpEthUNIEntry 15 }

    zxGponUniMirrorTable    OBJECT-TYPE
        SYNTAX      SEQUENCE OF ZxGponUniMirrorEntry
        MAX-ACCESS  not-accessible
        STATUS      current
        DESCRIPTION
            ""
        REFERENCE   "G.984.4"
        ::= { zxGponRmEthMgmt 2}

    zxGponUniMirrorEntry OBJECT-TYPE
        SYNTAX      ZxGponUniMirrorEntry
        MAX-ACCESS  not-accessible
        STATUS      current
        DESCRIPTION
            "It is entry in the zxGponUniMirrorTable."
        INDEX   { zxGponOltIndex, zxGponONTIndex, zxGponUNIIndex }
        ::= { zxGponUniMirrorTable 1 }

    ZxGponUniMirrorEntry ::=
        SEQUENCE {
            zxGponUniMirrorGemPortIndex             INTEGER,
            zxGponUniMirrorDirection                INTEGER,
            zxGponUniMirrorRowStatus                RowStatus
        }


    zxGponUniMirrorGemPortIndex OBJECT-TYPE
        SYNTAX      INTEGER(1..256)
        MAX-ACCESS  read-create
        STATUS      current
        DESCRIPTION
        "This attribute specifies the gemport for mirror.
        zxGponUniMirrorGemPortIndex depends on the records
        of zxGponGemFlowTable"
        REFERENCE   "G.984.4 private ME PPTP UNI mirror GEM port network CTP"
        ::= { zxGponUniMirrorEntry 1 }

    zxGponUniMirrorDirection OBJECT-TYPE
        SYNTAX      INTEGER{
                    ingress(1),
                    egress(2),
                    both(3)
                    }
        MAX-ACCESS  read-create
        STATUS      current
        DESCRIPTION
        "This attribute specifies the direction of mirror."
        REFERENCE   "G.984.4 private ME PPTP UNI mirror GEM port network CTP"
        ::= { zxGponUniMirrorEntry 2 }

    zxGponUniMirrorRowStatus OBJECT-TYPE
        SYNTAX      RowStatus
        MAX-ACCESS  read-create
        STATUS      current
        DESCRIPTION
        "RowStatus of  this table"
        REFERENCE   "G.984.4 private ME PPTP UNI mirror GEM port network CTP"
        ::= { zxGponUniMirrorEntry 30 }


    zxGponUniDhcpIpRetrieveTable    OBJECT-TYPE
        SYNTAX      SEQUENCE OF ZxGponUniDhcpIpRetrieveEntry
        MAX-ACCESS  not-accessible
        STATUS      current
        DESCRIPTION
            ""
        REFERENCE   "G.984.4"
        ::= { zxGponRmEthMgmt 3 }

    zxGponUniDhcpIpRetrieveEntry OBJECT-TYPE
        SYNTAX      ZxGponUniDhcpIpRetrieveEntry
        MAX-ACCESS  not-accessible
        STATUS      current
        DESCRIPTION
            "It is entry in the zxGponUniDhcpIpRetrieveTable."
        INDEX   { zxGponOltIndex, zxGponONTIndex, zxGponUNIIndex }
        ::= { zxGponUniDhcpIpRetrieveTable 1 }

    ZxGponUniDhcpIpRetrieveEntry ::=
        SEQUENCE {
            zxGponUniDhcpIpRetrieveMode             INTEGER
        }

    zxGponUniDhcpIpRetrieveMode OBJECT-TYPE
        SYNTAX      INTEGER{
                    noSpecify(1),
                    fromOnu(2),
                    fromNetwork(3),
                    forbidden(4)
                    }
        MAX-ACCESS  read-write
        STATUS      current
        DESCRIPTION
        "This attribute specifies the PPTP Ethernet UNI how to obtain its
        ip address(from ONU or network), when ONU enables the DHCP Server
        function."
        REFERENCE   "G.984.4 private ME
        Extended Physical path termination point Ethernet UNI"
        DEFVAL  { noSpecify }
        ::= { zxGponUniDhcpIpRetrieveEntry 1 }




--L2 management
--MAC Bridge service profile
    zxGponMACBridgeServiceProfileTable    OBJECT-TYPE
        SYNTAX      SEQUENCE OF ZxGponMACBridgeServiceProfileEntry
        MAX-ACCESS  not-accessible
        STATUS      current
        DESCRIPTION
            "This managed entity is used to organize data that affects all ports
            on a MAC Bridge at a bridged LAN Ethernet UNI interface on the ONT.
            Zero or more instances of this managed entity shall be referred to
            by the Physical Path Termination Point Ethernet UNI managed entity."
        REFERENCE   "G.983.2 section 7.3.29 MAC Bridge service profile"
        ::= { zxGponRmL2Mgmt 1 }

    zxGponMACBridgeServiceProfileEntry OBJECT-TYPE
        SYNTAX      ZxGponMACBridgeServiceProfileEntry
        MAX-ACCESS  not-accessible
        STATUS      current
        DESCRIPTION
            "It is entry in the zxGponMACBridgeServiceProfileTable."
        INDEX   { zxGponOltIndex, zxGponONTIndex, zxGponSwitchIndex }
        ::= { zxGponMACBridgeServiceProfileTable 1 }

    ZxGponMACBridgeServiceProfileEntry ::=
        SEQUENCE {
            zxGponMACBridgeServiceProfileSpanTreeInd           TruthValue,
            zxGponMACBridgeServiceProfileLearningInd           TruthValue,
            zxGponMACBridgeServiceProfileATMPortBridgeInd      TruthValue,
            zxGponMACBridgeServiceProfilePriority              INTEGER,
            zxGponMACBridgeServiceProfileMaxAge                INTEGER,
            zxGponMACBridgeServiceProfileHelloTime             INTEGER,
            zxGponMACBridgeServiceProfileForwardDelay          INTEGER,
            zxGponMACBridgeServiceProfileUnknownMACAddrDiscard TruthValue,
            zxGponMACBridgeServiceProfileMACLearningDepth      INTEGER
        }

    zxGponMACBridgeServiceProfileSpanTreeInd OBJECT-TYPE
        SYNTAX      TruthValue
        MAX-ACCESS  read-write
        STATUS      current
        DESCRIPTION
        "This Boolean attribute indicates whether or not a spanning tree algorithm is
        enabled. The value TRUE means enabled.(1 byte)"
        REFERENCE   "G.983.2 section 7.3.29 MAC Bridge service profile"
        ::= { zxGponMACBridgeServiceProfileEntry 1 }

    zxGponMACBridgeServiceProfileLearningInd OBJECT-TYPE
        SYNTAX      TruthValue
        MAX-ACCESS  read-write
        STATUS      current
        DESCRIPTION
        "This Boolean attribute indicates whether or not the learning functions of the
        bridge are enabled. The value TRUE means enabled.(1 byte)"
        REFERENCE   "G.983.2 section 7.3.29 MAC Bridge service profile"
        ::= { zxGponMACBridgeServiceProfileEntry 2 }

    zxGponMACBridgeServiceProfileATMPortBridgeInd OBJECT-TYPE
        SYNTAX      TruthValue
        MAX-ACCESS  read-write
        STATUS      current
        DESCRIPTION
        "This Boolean attribute indicates whether or not bridging between ATM ports on this
        bridge service is enabled. The value TRUE means enabled. (1 byte)"
        REFERENCE   "G.983.2 section 7.3.29 MAC Bridge service profile"
        ::= { zxGponMACBridgeServiceProfileEntry 3 }

    zxGponMACBridgeServiceProfilePriority OBJECT-TYPE
        SYNTAX      INTEGER
        MAX-ACCESS  read-write
        STATUS      current
        DESCRIPTION
        "This attribute indicates the bridge priority set on the LAN card. The range is 0x00 to
        0xFFFF (0 to 65535). The value of this attribute is copied to the BridgePriority attribute
        of the MAC Bridge Configuration Data managed entity.(2 bytes)"
        REFERENCE   "G.983.2 section 7.3.29 MAC Bridge service profile"
        ::= { zxGponMACBridgeServiceProfileEntry 4 }

    zxGponMACBridgeServiceProfileMaxAge OBJECT-TYPE
        SYNTAX      INTEGER
        MAX-ACCESS  read-write
        STATUS      current
        DESCRIPTION
        "This attribute indicates the maximum age (in 256ths of a second) for an entry in the
        spanning tree listing. It indicates the maximum age in 256ths of a second for received
        protocol information before it is discarded. The range is 0x0600 to 0x2800 (6 s to 40 s)
        in accordance with IEEE 802.1D [13].(2 bytes)"
        REFERENCE   "G.983.2 section 7.3.29 MAC Bridge service profile"
        ::= { zxGponMACBridgeServiceProfileEntry 5 }

    zxGponMACBridgeServiceProfileHelloTime OBJECT-TYPE
        SYNTAX      INTEGER
        MAX-ACCESS  read-write
        STATUS      current
        DESCRIPTION
        "This attribute provides the time interval (in 256ths of a second) between hello packets.
        It is the time interval, in 256ths of a second, that a bridge advertises its presence
        while as a root or attempting to become a root. The range is 0x0100 to 0x0a00 (1 s to 10 s)
        in accordance with IEEE 802.1D [13].(2 bytes)"
        REFERENCE   "G.983.2 section 7.3.29 MAC Bridge service profile"
        ::= { zxGponMACBridgeServiceProfileEntry 6 }

    zxGponMACBridgeServiceProfileForwardDelay OBJECT-TYPE
        SYNTAX      INTEGER
        MAX-ACCESS  read-write
        STATUS      current
        DESCRIPTION
        "This attribute gives the time (in 256ths of a second) that the bridge on the Ethernet
        card in the ONT retains a packet before forwarding it. (It indicates the value in 256ths
        of a second that the bridge uses for Forward Delay when the bridge acts as the root.)
        The range is 0x0400 to 0x1e00 (4 s to 30 s) in accordance with IEEE 802.1D [13].(2 bytes)"
        REFERENCE   "G.983.2 section 7.3.29 MAC Bridge service profile"
        ::= { zxGponMACBridgeServiceProfileEntry 7 }

    zxGponMACBridgeServiceProfileUnknownMACAddrDiscard OBJECT-TYPE
        SYNTAX      TruthValue
        MAX-ACCESS  read-write
        STATUS      current
        DESCRIPTION
        "This Boolean attribute indicates the treatment of MAC frames with unknown destination
        addresses.  The value TRUE means that frames with unknown destination addresses will be
        discarded.  The value FALSE means that such frames will be forwarded to all allowed ports.(1 byte)"
        REFERENCE   "G.983.2 section 7.3.29 MAC Bridge service profile"
        ::= { zxGponMACBridgeServiceProfileEntry 8 }

    zxGponMACBridgeServiceProfileMACLearningDepth OBJECT-TYPE
        SYNTAX      INTEGER(0..255)
        MAX-ACCESS  read-write
        STATUS      current
        DESCRIPTION
        "This attribute specifies the maximum number of UNI MAC addresses to be learned by the bridge.
         The default value 0 specifies that there is no administratively-imposed limit.
         (R, W, Set-by-create) (optional) (1 byte)"
        REFERENCE   "G.983.2 section 7.3.29 MAC Bridge service profile"
        ::= { zxGponMACBridgeServiceProfileEntry 9 }


--MAC Bridge configuration data
--not implemented yet!
    zxGponMACBridgeConfigDataTable    OBJECT-TYPE
        SYNTAX      SEQUENCE OF ZxGponMACBridgeConfigDataEntry
        MAX-ACCESS  not-accessible
        STATUS      current
        DESCRIPTION
            "This managed entity is used to organize and record data that is associated with bridged
            LAN configurations. Some of the data is volatile.
            This managed entity is associated with one instance of a MACBridgeServiceProfile."
        REFERENCE   "G.983.2 section 7.3.30 MAC Bridge configuration data"
        ::= { zxGponRmL2Mgmt 2 }

    zxGponMACBridgeConfigDataEntry OBJECT-TYPE
        SYNTAX      ZxGponMACBridgeConfigDataEntry
        MAX-ACCESS  not-accessible
        STATUS      current
        DESCRIPTION
            "It is entry in the zxGponMACBridgeConfigDataTable."
        INDEX   { zxGponOltIndex, zxGponONTIndex, zxGponSwitchIndex }
        ::= { zxGponMACBridgeConfigDataTable 1 }

    ZxGponMACBridgeConfigDataEntry ::=
        SEQUENCE {
            zxGponMACBridgeConfigDataBridgeMACAddr         MacAddress,
            zxGponMACBridgeConfigDataBridgePrio            INTEGER,
            zxGponMACBridgeConfigDataDesignatedRoot        INTEGER,
            zxGponMACBridgeConfigDataRootPathCost          INTEGER,
            zxGponMACBridgeConfigDataBridgePortCount       INTEGER,
            zxGponMACBridgeConfigDataRootPortNum           INTEGER,
            zxGponMACBridgeConfigDataHelloTime             INTEGER,
            zxGponMACBridgeConfigDataForwardDelay          INTEGER
        }

    zxGponMACBridgeConfigDataBridgeMACAddr OBJECT-TYPE
        SYNTAX      MacAddress
        MAX-ACCESS  read-only
        STATUS      current
        DESCRIPTION
        "This attribute indicates the MAC address used by the bridge.
        Upon autonomous instantiation, this attribute consists of all 0x00.(6 bytes)"
        REFERENCE   "G.983.2 section 7.3.30 MAC Bridge configuration data"
        ::= { zxGponMACBridgeConfigDataEntry 1 }

    zxGponMACBridgeConfigDataBridgePrio OBJECT-TYPE
        SYNTAX      INTEGER
        MAX-ACCESS  read-only
        STATUS      current
        DESCRIPTION
        "This attribute denotes the priority of the bridge and is positive integer-valued.
        Upon autonomous instantiation, the value 0x8000 is used. The value of this attribute
        follows the value of the associated MAC Bridge Service Profile: Priority attribute,
        if present.(2 bytes)"
        REFERENCE   "G.983.2 section 7.3.30 MAC Bridge configuration data"
        ::= { zxGponMACBridgeConfigDataEntry 2 }

    zxGponMACBridgeConfigDataDesignatedRoot OBJECT-TYPE
        SYNTAX      INTEGER
        MAX-ACCESS  read-only
        STATUS      current
        DESCRIPTION
        "This attribute provides the bridge identifier for the root of the spanning tree.
        This attribute consists of Bridge Priority (2 bytes) and MAC address (6 bytes).
        (8 bytes)"
        REFERENCE   "G.983.2 section 7.3.30 MAC Bridge configuration data"
        ::= { zxGponMACBridgeConfigDataEntry 3 }

    zxGponMACBridgeConfigDataRootPathCost OBJECT-TYPE
        SYNTAX      INTEGER
        MAX-ACCESS  read-only
        STATUS      current
        DESCRIPTION
        "This attribute provides the cost of the best path to the root as seen from the
        bridge. Upon autonomous instantiation, the value 0x00 is used.(4 bytes)"
        REFERENCE   "G.983.2 section 7.3.30 MAC Bridge configuration data"
        ::= { zxGponMACBridgeConfigDataEntry 4 }

    zxGponMACBridgeConfigDataBridgePortCount OBJECT-TYPE
        SYNTAX      INTEGER
        MAX-ACCESS  read-only
        STATUS      current
        DESCRIPTION
        "This attribute provides the number of existing ports controlled by this bridge.(1 byte)"
        REFERENCE   "G.983.2 section 7.3.30 MAC Bridge configuration data"
        ::= { zxGponMACBridgeConfigDataEntry 5 }

    zxGponMACBridgeConfigDataRootPortNum OBJECT-TYPE
        SYNTAX      INTEGER
        MAX-ACCESS  read-only
        STATUS      current
        DESCRIPTION
        "This attribute provides the port number that has the lowest cost from the bridge to
        the root bridge. The value 0x00 means that the bridge itself is the root.
        Upon autonomous instantiation, the value 0x00 is used.(2 bytes)"
        REFERENCE   "G.983.2 section 7.3.30 MAC Bridge configuration data"
        ::= { zxGponMACBridgeConfigDataEntry 6 }

    zxGponMACBridgeConfigDataHelloTime OBJECT-TYPE
        SYNTAX      INTEGER
        MAX-ACCESS  read-only
        STATUS      current
        DESCRIPTION
        "This attribute provides the time interval (in 256ths of a second) between hello
        packets. It is the 'HelloTime' received from the designated root.
        The range is 0x0100 to 0x0a00 (1 s to 10 s) in accordance with IEEE 802.1D [13].(2 bytes)"
        REFERENCE   "G.983.2 section 7.3.30 MAC Bridge configuration data"
        ::= { zxGponMACBridgeConfigDataEntry 7 }

    zxGponMACBridgeConfigDataForwardDelay OBJECT-TYPE
        SYNTAX      INTEGER
        MAX-ACCESS  read-only
        STATUS      current
        DESCRIPTION
        "This attribute gives the time (in 256ths of a second) that the bridge on the Ethernet
        card in the ONT retains a packet before forwarding it. It is the 'ForwardDelay' time
        received from the designated root. The range is 0x0400 to 0x1e00 (4 s to 30 s) in
        accordance with IEEE 802.1D [13].(2 bytes)"
        REFERENCE   "G.983.2 section 7.3.30 MAC Bridge configuration data"
        ::= { zxGponMACBridgeConfigDataEntry 8 }


--G.984.4 MAC Bridge Port Configuration Data
    zxGponUNIMACBridgePortConfigTable    OBJECT-TYPE
        SYNTAX      SEQUENCE OF ZxGponUNIMACBridgePortConfigEntry
        MAX-ACCESS  not-accessible
        STATUS      current
        DESCRIPTION
            "This managed entity is used to organize and record data that is associated with
            a bridge port. Some of the data is volatile.
            Zero or more instances of this managed entity shall be contained in an instance of the
            MACBridgeServiceProfile."
        REFERENCE   "G.984.4 MAC Bridge Port Configuation Data, details in G.983.2"
        ::= { zxGponRmL2Mgmt 3 }

    zxGponUNIMACBridgePortConfigEntry OBJECT-TYPE
        SYNTAX      ZxGponUNIMACBridgePortConfigEntry
        MAX-ACCESS  not-accessible
        STATUS      current
        DESCRIPTION
            "It is entry in the zxGponUNIMACBridgePortConfigTable."
        INDEX   { zxGponOltIndex, zxGponONTIndex, zxGponUNIIndex }
        ::= { zxGponUNIMACBridgePortConfigTable 1 }

    ZxGponUNIMACBridgePortConfigEntry ::=
        SEQUENCE {
            zxGponUNIMACBridgePortConfigBridgeId                INTEGER,
            zxGponUNIMACBridgePortConfigBridgePort              INTEGER,
            zxGponUNIMACBridgePortConfigPortPrio                INTEGER,
            zxGponUNIMACBridgePortConfigPortPathCost            INTEGER,
            zxGponUNIMACBridgePortConfigPortSpanTreeInd         TruthValue,
            zxGponUNIMACBridgePortConfigEncapMethod             INTEGER,
            zxGponUNIMACBridgePortConfigLANFCSInd               INTEGER,
            zxGponUNIMACBridgePortConfigPortMACAddr             MacAddress,
            zxGponUNIMACBridgePortConfigEntryStatus             RowStatus,
            zxGponUNIMACBridgePortConfigOutboundTDPtr           INTEGER,
            zxGponUNIMACBridgePortConfigInboundTDPtr            INTEGER,
            zxGponUniMacBPortAddrLearnDepth                     INTEGER,
            zxGponUniMacBPortOutboundTdPrf                      DisplayString,
            zxGponUniMacBPortInboundTdPrf                       DisplayString
        }

    zxGponUNIMACBridgePortConfigBridgeId OBJECT-TYPE
        SYNTAX      INTEGER
        MAX-ACCESS  read-write
        STATUS      current
        DESCRIPTION
        "This attribute is set-by-create, indicating the bridge when create an UNI bridge port."
        REFERENCE   "G.984.4 MAC Bridge Port Configuation Data"
        ::= { zxGponUNIMACBridgePortConfigEntry 1 }

    zxGponUNIMACBridgePortConfigBridgePort OBJECT-TYPE
        SYNTAX      INTEGER
        MAX-ACCESS  read-only
        STATUS      current
        DESCRIPTION
        "This attribute identifies the MAC bridge port associated with the port.
        The first 2 bytes stand for the slot and bridge group id;
        The second 2 bytes stand for the bridge port num.(4 bytes)"
        REFERENCE   "G.984.4 MAC Bridge Port Configuation Data"
        ::= { zxGponUNIMACBridgePortConfigEntry 2 }

    zxGponUNIMACBridgePortConfigPortPrio OBJECT-TYPE
        SYNTAX      INTEGER
        MAX-ACCESS  read-write
        STATUS      current
        DESCRIPTION
        "This attribute denotes the priority of the port.
        The range is 0x00 to 0x00FF (0 to 255).(2 bytes)"
        REFERENCE   "G.984.4 MAC Bridge Port Configuation Data"
        ::= { zxGponUNIMACBridgePortConfigEntry 3 }

    zxGponUNIMACBridgePortConfigPortPathCost OBJECT-TYPE
        SYNTAX      INTEGER
        MAX-ACCESS  read-write
        STATUS      current
        DESCRIPTION
        "This attribute provides the cost contribution of the port to the path cost
        towards the spanning tree root bridge. The range is 0x0001 to 0xFFFF (1 to 65535).(2 bytes)"
        REFERENCE   "G.984.4 MAC Bridge Port Configuation Data"
        ::= { zxGponUNIMACBridgePortConfigEntry 4 }

    zxGponUNIMACBridgePortConfigPortSpanTreeInd OBJECT-TYPE
        SYNTAX      TruthValue
        MAX-ACCESS  read-write
        STATUS      current
        DESCRIPTION
        "This Boolean attribute indicates whether or not STP LAN topology change detection
        is enabled at this port. The value TRUE means enabled.(1 byte)"
        REFERENCE   "G.984.4 MAC Bridge Port Configuation Data"
        ::= { zxGponUNIMACBridgePortConfigEntry 5 }

    zxGponUNIMACBridgePortConfigEncapMethod OBJECT-TYPE
        SYNTAX      INTEGER{
                    atmvc(1),
                    llc(2)
                    }
        MAX-ACCESS  read-write
        STATUS      current
        DESCRIPTION
        "This attribute identifies the frame encapsulation method that is used.
        0x00: identification by ATM VC;
        0x01: LLC encapsulation;
        This attribute is effective only for ports towards the ANI side of the MAC bridge.
        Upon autonomous instantiation, the value 0x00 is used.
        (1 byte)"
        REFERENCE   "G.984.4 MAC Bridge Port Configuation Data"
        ::= { zxGponUNIMACBridgePortConfigEntry 6 }

    zxGponUNIMACBridgePortConfigLANFCSInd OBJECT-TYPE
        SYNTAX      INTEGER{
                    forward(1),
                    discard(2)
                    }
        MAX-ACCESS  read-write
        STATUS      current
        DESCRIPTION
        "This attribute indicates whether LAN FCS (Frame Check Sequence) bytes are
        forwarded (value 0x00) or discarded (value 0x01). This applies in both directions of
        transmission, and applies regardless of EncapsulationMethod.
        This attribute is effective only for ports towards the ANI side of the MAC bridge.
        Upon autonomous instantiation, the value 0x00 is used.(1 byte)"
        REFERENCE   "G.984.4 MAC Bridge Port Configuation Data"
        ::= { zxGponUNIMACBridgePortConfigEntry 7 }

    zxGponUNIMACBridgePortConfigPortMACAddr OBJECT-TYPE
        SYNTAX      MacAddress
        MAX-ACCESS  read-only
        STATUS      current
        DESCRIPTION
        "This attribute indicates the Physical MAC address used by the Port as defined by
        the TPPointer when the TPType is set to LAN.(6 bytes)"
        REFERENCE   "G.984.4 MAC Bridge Port Configuation Data"
        ::= { zxGponUNIMACBridgePortConfigEntry 8 }

    zxGponUNIMACBridgePortConfigEntryStatus OBJECT-TYPE
        SYNTAX      RowStatus
        MAX-ACCESS  read-write
        STATUS      current
        DESCRIPTION
        "This attribute indicates the Physical MAC address used by the Port as defined by
        the TPPointer when the TPType is set to LAN.(6 bytes)"
        REFERENCE   "G.984.4 MAC Bridge Port Configuation Data"
        ::= { zxGponUNIMACBridgePortConfigEntry 9 }

    zxGponUNIMACBridgePortConfigOutboundTDPtr OBJECT-TYPE
        SYNTAX      INTEGER
        MAX-ACCESS  read-write
        STATUS      current
        DESCRIPTION
        "This attribute points to a GEM traffic descriptor that limits the traffic rate
         leaving the MAC bridge(2 byte)"
        REFERENCE    "G.984.4 MAC Bridge Port Configuation Data and
            zxGponTrafficProfileTable in zxGponService.mib"
        ::= { zxGponUNIMACBridgePortConfigEntry 10 }

    zxGponUNIMACBridgePortConfigInboundTDPtr OBJECT-TYPE
        SYNTAX      INTEGER
        MAX-ACCESS  read-write
        STATUS      current
        DESCRIPTION
        "This attribute points to a GEM traffic descriptor that limits the traffic rate
         entering the MAC bridge(2 byte)"
        REFERENCE   "G.984.4 MAC Bridge Port Configuation Data and
            zxGponTrafficProfileTable in zxGponService.mib"
        ::= { zxGponUNIMACBridgePortConfigEntry 11 }

    zxGponUniMacBPortAddrLearnDepth OBJECT-TYPE
        SYNTAX      INTEGER(0..255)
        MAX-ACCESS  read-write
        STATUS      current
        DESCRIPTION
          "This attribute specifies the maximum number of MAC addresses
           to be learned by  this MAC bridge port. The default value 0
           specifies that there is no administratively-imposed limit.
           (R, W, Set-by-create) (optional) (1 byte)"
        REFERENCE   "G.984.4 MAC Bridge Port Configuation Data"
        DEFVAL  { 0 }
        ::= { zxGponUNIMACBridgePortConfigEntry 12 }

    zxGponUniMacBPortOutboundTdPrf OBJECT-TYPE
        SYNTAX      DisplayString(SIZE(0..64))
        MAX-ACCESS  read-write
        STATUS      current
        DESCRIPTION
            "This name points to a GEM traffic descriptor that limits
             the traffic rate leaving the MAC bridge.
             It indicates no rate limiting when the length of value is 0."
        REFERENCE   "G.984.4 MAC Bridge Port Configuation Data and
            zxGponRmTrafficPrfTable in this file."
        ::= { zxGponUNIMACBridgePortConfigEntry 13 }

    zxGponUniMacBPortInboundTdPrf OBJECT-TYPE
        SYNTAX      DisplayString(SIZE(0..64))
        MAX-ACCESS  read-write
        STATUS      current
        DESCRIPTION
            "This name points to a GEM traffic descriptor  that limits
             the traffic rate entering the MAC bridge.
             It indicates no rate limiting when the length of value is 0."
        REFERENCE   "G.984.4 MAC Bridge Port Configuation Data and
            zxGponRmTrafficPrfTable in this file."
        ::= { zxGponUNIMACBridgePortConfigEntry 14 }


    zxGponHostMACBridgePortConfigTable    OBJECT-TYPE
        SYNTAX      SEQUENCE OF ZxGponHostMACBridgePortConfigEntry
        MAX-ACCESS  not-accessible
        STATUS      current
        DESCRIPTION
            "This managed entity is used to organize and record data that is associated with
            a bridge port. Some of the data is volatile.
            Zero or more instances of this managed entity shall be contained in an instance of the
            MACBridgeServiceProfile."
        REFERENCE   "G.984.4 section 9.3.9 MAC Bridge Port Configuation Data, details in G.983.2"
        ::= { zxGponRmL2Mgmt 4 }

    zxGponHostMACBridgePortConfigEntry OBJECT-TYPE
        SYNTAX      ZxGponHostMACBridgePortConfigEntry
        MAX-ACCESS  not-accessible
        STATUS      current
        DESCRIPTION
            "It is entry in the zxGponHostMACBridgePortConfigTable."
        INDEX   { zxGponOltIndex, zxGponONTIndex, zxGponIPHostConfigDataId }
        ::= { zxGponHostMACBridgePortConfigTable 1 }

    ZxGponHostMACBridgePortConfigEntry ::=
        SEQUENCE {
            zxGponHostMACBridgePortConfigBridgeId                INTEGER,
            zxGponHostMACBridgePortConfigBridgePort              INTEGER,
            zxGponHostMACBridgePortConfigPortPrio                INTEGER,
            zxGponHostMACBridgePortConfigPortPathCost            INTEGER,
            zxGponHostMACBridgePortConfigPortSpanTreeInd         TruthValue,
            zxGponHostMACBridgePortConfigEncapMethod             INTEGER,
            zxGponHostMACBridgePortConfigLANFCSInd               INTEGER,
            zxGponHostMACBridgePortConfigPortMACAddr             MacAddress,
            zxGponHostMACBridgePortConfigEntryStatus             RowStatus
        }

    zxGponHostMACBridgePortConfigBridgeId OBJECT-TYPE
        SYNTAX      INTEGER
        MAX-ACCESS  read-write
        STATUS      current
        DESCRIPTION
        "This attribute identifies the MAC bridge id associated with the ip host."
        REFERENCE   ""
        ::= { zxGponHostMACBridgePortConfigEntry 1 }

    zxGponHostMACBridgePortConfigBridgePort OBJECT-TYPE
        SYNTAX      INTEGER
        MAX-ACCESS  read-only
        STATUS      current
        DESCRIPTION
        "This attribute identifies the MAC bridge port associated with the port.
        The first 2 bytes stand for the slot and bridge group id;
        The second 2 bytes stand for the bridge port num.(4 bytes)"
        REFERENCE   "G.984.4 section 9.3.9 MAC Bridge Port Configuation Data"
        ::= { zxGponHostMACBridgePortConfigEntry 2 }

    zxGponHostMACBridgePortConfigPortPrio OBJECT-TYPE
        SYNTAX      INTEGER
        MAX-ACCESS  read-write
        STATUS      current
        DESCRIPTION
        "This attribute denotes the priority of the port.
        The range is 0x00 to 0x00FF (0 to 255).(2 bytes)"
        REFERENCE   "G.984.4 section 9.3.9 MAC Bridge Port Configuation Data"
        ::= { zxGponHostMACBridgePortConfigEntry 3 }

    zxGponHostMACBridgePortConfigPortPathCost OBJECT-TYPE
        SYNTAX      INTEGER
        MAX-ACCESS  read-write
        STATUS      current
        DESCRIPTION
        "This attribute provides the cost contribution of the port to the path cost
        towards the spanning tree root bridge. The range is 0x0001 to 0xFFFF (1 to 65535).(2 bytes)"
        REFERENCE   "G.984.4 section 9.3.9 MAC Bridge Port Configuation Data"
        ::= { zxGponHostMACBridgePortConfigEntry 4 }

    zxGponHostMACBridgePortConfigPortSpanTreeInd OBJECT-TYPE
        SYNTAX      TruthValue
        MAX-ACCESS  read-write
        STATUS      current
        DESCRIPTION
        "This Boolean attribute indicates whether or not STP LAN topology change detection
        is enabled at this port. The value TRUE means enabled.(1 byte)"
        REFERENCE   "G.984.4 section 9.3.9 MAC Bridge Port Configuation Data"
        ::= { zxGponHostMACBridgePortConfigEntry 5 }

    zxGponHostMACBridgePortConfigEncapMethod OBJECT-TYPE
        SYNTAX      INTEGER{
                    atmvc(1),
                    llc(2)
                    }
        MAX-ACCESS  read-write
        STATUS      current
        DESCRIPTION
        "This attribute identifies the frame encapsulation method that is used.
        0x00: identification by ATM VC;
        0x01: LLC encapsulation;
        This attribute is effective only for ports towards the ANI side of the MAC bridge.
        Upon autonomous instantiation, the value 0x00 is used.
        (1 byte)"
        REFERENCE   "G.984.4 section 9.3.9 MAC Bridge Port Configuation Data"
        ::= { zxGponHostMACBridgePortConfigEntry 6 }

    zxGponHostMACBridgePortConfigLANFCSInd OBJECT-TYPE
        SYNTAX      INTEGER{
                    forward(1),
                    discard(2)
                    }
        MAX-ACCESS  read-write
        STATUS      current
        DESCRIPTION
        "This attribute indicates whether LAN FCS (Frame Check Sequence) bytes are
        forwarded (value 0x00) or discarded (value 0x01). This applies in both directions of
        transmission, and applies regardless of EncapsulationMethod.
        This attribute is effective only for ports towards the ANI side of the MAC bridge.
        Upon autonomous instantiation, the value 0x00 is used.(1 byte)"
        REFERENCE   "G.984.4 section 9.3.9 MAC Bridge Port Configuation Data"
        ::= { zxGponHostMACBridgePortConfigEntry 7 }

    zxGponHostMACBridgePortConfigPortMACAddr OBJECT-TYPE
        SYNTAX      MacAddress
        MAX-ACCESS  read-only
        STATUS      current
        DESCRIPTION
        "This attribute indicates the Physical MAC address used by the Port as defined by
        the TPPointer when the TPType is set to LAN.(6 bytes)"
        REFERENCE   "G.984.4 section 9.3.9 MAC Bridge Port Configuation Data"
        ::= { zxGponHostMACBridgePortConfigEntry 8 }

    zxGponHostMACBridgePortConfigEntryStatus OBJECT-TYPE
        SYNTAX      RowStatus
        MAX-ACCESS  read-write
        STATUS      current
        DESCRIPTION
        "This attribute indicates the Physical MAC address used by the Port as defined by
        the TPPointer when the TPType is set to LAN.(6 bytes)"
        REFERENCE   "G.984.4 section 9.3.9 MAC Bridge Port Configuation Data"
        ::= { zxGponHostMACBridgePortConfigEntry 9 }


--MAC bridge port configuration for flow
    zxGponFlowMACBridgePortConfigTable    OBJECT-TYPE
        SYNTAX      SEQUENCE OF ZxGponFlowMACBridgePortConfigEntry
        MAX-ACCESS  not-accessible
        STATUS      current
        DESCRIPTION
            "This managed entity is used to organize and record data that is associated with
            a bridge port. Some of the data is volatile.
            Zero or more instances of this managed entity shall be contained in an instance of the
            MACBridgeServiceProfile."
        REFERENCE   "G.984.4 section 9.3.9 MAC Bridge Port Configuation Data, details in G.983.2"
        ::= { zxGponRmL2Mgmt 5 }

    zxGponFlowMACBridgePortConfigEntry OBJECT-TYPE
        SYNTAX      ZxGponFlowMACBridgePortConfigEntry
        MAX-ACCESS  not-accessible
        STATUS      current
        DESCRIPTION
            "It is entry in the zxGponFlowMACBridgePortConfigTable."
        INDEX   { zxGponOltIndex, zxGponONTIndex, zxGponFlowIndex }
        ::= { zxGponFlowMACBridgePortConfigTable 1 }

    ZxGponFlowMACBridgePortConfigEntry ::=
        SEQUENCE {
            zxGponFlowMACBridgePortConfigBridgePort              INTEGER,
            zxGponFlowMACBridgePortConfigPortPrio                INTEGER,
            zxGponFlowMACBridgePortConfigPortPathCost            INTEGER,
            zxGponFlowMACBridgePortConfigPortSpanTreeInd         TruthValue,
            zxGponFlowMACBridgePortConfigEncapMethod             INTEGER,
            zxGponFlowMACBridgePortConfigLANFCSInd               INTEGER,
            zxGponFlowMACBridgePortConfigPortMACAddr             MacAddress
        }

    zxGponFlowMACBridgePortConfigBridgePort OBJECT-TYPE
        SYNTAX      INTEGER
        MAX-ACCESS  read-only
        STATUS      current
        DESCRIPTION
        "This attribute identifies the MAC bridge port associated with the port.
        The first 2 bytes stand for the slot and bridge group id;
        The second 2 bytes stand for the bridge port num.(4 bytes)"
        REFERENCE   "G.984.4 section 9.3.9 MAC Bridge Port Configuation Data"
        ::= { zxGponFlowMACBridgePortConfigEntry 1 }

    zxGponFlowMACBridgePortConfigPortPrio OBJECT-TYPE
        SYNTAX      INTEGER
        MAX-ACCESS  read-write
        STATUS      current
        DESCRIPTION
        "This attribute denotes the priority of the port.
        The range is 0x00 to 0x00FF (0 to 255).(2 bytes)"
        REFERENCE   "G.984.4 section 9.3.9 MAC Bridge Port Configuation Data"
        ::= { zxGponFlowMACBridgePortConfigEntry 2 }

    zxGponFlowMACBridgePortConfigPortPathCost OBJECT-TYPE
        SYNTAX      INTEGER
        MAX-ACCESS  read-write
        STATUS      current
        DESCRIPTION
        "This attribute provides the cost contribution of the port to the path cost
        towards the spanning tree root bridge. The range is 0x0001 to 0xFFFF (1 to 65535).(2 bytes)"
        REFERENCE   "G.984.4 section 9.3.9 MAC Bridge Port Configuation Data"
        ::= { zxGponFlowMACBridgePortConfigEntry 3 }

    zxGponFlowMACBridgePortConfigPortSpanTreeInd OBJECT-TYPE
        SYNTAX      TruthValue
        MAX-ACCESS  read-write
        STATUS      current
        DESCRIPTION
        "This Boolean attribute indicates whether or not STP LAN topology change detection
        is enabled at this port. The value TRUE means enabled.(1 byte)"
        REFERENCE   "G.984.4 section 9.3.9 MAC Bridge Port Configuation Data"
        ::= { zxGponFlowMACBridgePortConfigEntry 4 }

    zxGponFlowMACBridgePortConfigEncapMethod OBJECT-TYPE
        SYNTAX      INTEGER{
                    atmvc(1),
                    llc(2)
                    }
        MAX-ACCESS  read-write
        STATUS      current
        DESCRIPTION
        "This attribute identifies the frame encapsulation method that is used.
        0x00: identification by ATM VC;
        0x01: LLC encapsulation;
        This attribute is effective only for ports towards the ANI side of the MAC bridge.
        Upon autonomous instantiation, the value 0x00 is used.
        (1 byte)"
        REFERENCE   "G.984.4 section 9.3.9 MAC Bridge Port Configuation Data"
        ::= { zxGponFlowMACBridgePortConfigEntry 5 }

    zxGponFlowMACBridgePortConfigLANFCSInd OBJECT-TYPE
        SYNTAX      INTEGER{
                    forward(1),
                    discard(2)
                    }
        MAX-ACCESS  read-write
        STATUS      current
        DESCRIPTION
        "This attribute indicates whether LAN FCS (Frame Check Sequence) bytes are
        forwarded (value 0x00) or discarded (value 0x01). This applies in both directions of
        transmission, and applies regardless of EncapsulationMethod.
        This attribute is effective only for ports towards the ANI side of the MAC bridge.
        Upon autonomous instantiation, the value 0x00 is used.(1 byte)"
        REFERENCE   "G.984.4 section 9.3.9 MAC Bridge Port Configuation Data"
        ::= { zxGponFlowMACBridgePortConfigEntry 6 }

    zxGponFlowMACBridgePortConfigPortMACAddr OBJECT-TYPE
        SYNTAX      MacAddress
        MAX-ACCESS  read-only
        STATUS      current
        DESCRIPTION
        "This attribute indicates the Physical MAC address used by the Port as defined by
        the TPPointer when the TPType is set to LAN.(6 bytes)"
        REFERENCE   "G.984.4 section 9.3.9 MAC Bridge Port Configuation Data"
        ::= { zxGponFlowMACBridgePortConfigEntry 7 }

--802.1p mapper service profile
    zxGponFlowDot1pMapServiceProfileTable    OBJECT-TYPE
        SYNTAX      SEQUENCE OF ZxGponFlowDot1pMapServiceProfileEntry
        MAX-ACCESS  not-accessible
        STATUS      current
        DESCRIPTION
            "This managed entity is used to associate the priorities of 802.1P priority tagged
            frames of a certain Ethernet UNI with a specific connection.
            One instance of this ME may be associated with zero or one instance of the PPTP UNI ME."
        REFERENCE   "G.983.2 section 7.3.95 802.1p mapper service profile"
        ::= { zxGponRmL2Mgmt 6 }

    zxGponFlowDot1pMapServiceProfileEntry OBJECT-TYPE
        SYNTAX      ZxGponFlowDot1pMapServiceProfileEntry
        MAX-ACCESS  not-accessible
        STATUS      current
        DESCRIPTION
            "It is entry in the zxGponFlowDot1pMapServiceProfileTable."
        INDEX   { zxGponOltIndex, zxGponONTIndex, zxGponFlowIndex }
        ::= { zxGponFlowDot1pMapServiceProfileTable 1 }

    ZxGponFlowDot1pMapServiceProfileEntry ::=
        SEQUENCE {
            zxGponFlowDot1pMapServiceProfilePrio0GemPortId          INTEGER,
            zxGponFlowDot1pMapServiceProfilePrio1GemPortId          INTEGER,
            zxGponFlowDot1pMapServiceProfilePrio2GemPortId          INTEGER,
            zxGponFlowDot1pMapServiceProfilePrio3GemPortId          INTEGER,
            zxGponFlowDot1pMapServiceProfilePrio4GemPortId          INTEGER,
            zxGponFlowDot1pMapServiceProfilePrio5GemPortId          INTEGER,
            zxGponFlowDot1pMapServiceProfilePrio6GemPortId          INTEGER,
            zxGponFlowDot1pMapServiceProfilePrio7GemPortId          INTEGER,
            zxGponFlowDot1pMapServiceProfileUnmarkedFrameOption     INTEGER,
            zxGponFlowDot1pMapServiceProfileDSCP2PBitMap            OCTET STRING,
            zxGponFlowDot1pMapServiceProfileDefPBitMarking          INTEGER
        }

    zxGponFlowDot1pMapServiceProfilePrio0GemPortId OBJECT-TYPE
        SYNTAX      INTEGER
        MAX-ACCESS  read-only
        STATUS      current
        DESCRIPTION
        "This attribute represents the GEM port id that is
        associated with P-Bit = 000 tagged frames. The value 0xFFFF is a null pointer.(2 bytes)"
        REFERENCE   "G.983.2 section 7.3.95 802.1p mapper service profile"
        ::= { zxGponFlowDot1pMapServiceProfileEntry 1 }

    zxGponFlowDot1pMapServiceProfilePrio1GemPortId OBJECT-TYPE
        SYNTAX      INTEGER
        MAX-ACCESS  read-only
        STATUS      current
        DESCRIPTION
        "This attribute represents a pointer to the Interworking Termination Point that is
        associated with P-Bit = 001 tagged frames. The value 0xFFFF is a null pointer.(2 bytes)"
        REFERENCE   "G.983.2 section 7.3.95 802.1p mapper service profile"
        ::= { zxGponFlowDot1pMapServiceProfileEntry 2 }

    zxGponFlowDot1pMapServiceProfilePrio2GemPortId OBJECT-TYPE
        SYNTAX      INTEGER
        MAX-ACCESS  read-only
        STATUS      current
        DESCRIPTION
        "This attribute represents a pointer to the Interworking Termination Point that is
        associated with P-Bit = 010 tagged frames. The value 0xFFFF is a null pointer.(2 bytes)"
        REFERENCE   "G.983.2 section 7.3.95 802.1p mapper service profile"
        ::= { zxGponFlowDot1pMapServiceProfileEntry 3 }

    zxGponFlowDot1pMapServiceProfilePrio3GemPortId OBJECT-TYPE
        SYNTAX      INTEGER
        MAX-ACCESS  read-only
        STATUS      current
        DESCRIPTION
        "This attribute represents a pointer to the Interworking Termination Point that is
        associated with P-Bit = 011 tagged frames. The value 0xFFFF is a null pointer.(2 bytes)"
        REFERENCE   "G.983.2 section 7.3.95 802.1p mapper service profile"
        ::= { zxGponFlowDot1pMapServiceProfileEntry 4 }

    zxGponFlowDot1pMapServiceProfilePrio4GemPortId OBJECT-TYPE
        SYNTAX      INTEGER
        MAX-ACCESS  read-only
        STATUS      current
        DESCRIPTION
        "This attribute represents a pointer to the Interworking Termination Point that is
        associated with P-Bit = 100 tagged frames. The value 0xFFFF is a null pointer.(2 bytes)"
        REFERENCE   "G.983.2 section 7.3.95 802.1p mapper service profile"
        ::= { zxGponFlowDot1pMapServiceProfileEntry 5 }

    zxGponFlowDot1pMapServiceProfilePrio5GemPortId OBJECT-TYPE
        SYNTAX      INTEGER
        MAX-ACCESS  read-only
        STATUS      current
        DESCRIPTION
        "This attribute represents a pointer to the Interworking Termination Point that is
        associated with P-Bit = 101 tagged frames. The value 0xFFFF is a null pointer.(2 bytes)"
        REFERENCE   "G.983.2 section 7.3.95 802.1p mapper service profile"
        ::= { zxGponFlowDot1pMapServiceProfileEntry 6 }

    zxGponFlowDot1pMapServiceProfilePrio6GemPortId OBJECT-TYPE
        SYNTAX      INTEGER
        MAX-ACCESS  read-only
        STATUS      current
        DESCRIPTION
        "This attribute represents a pointer to the Interworking Termination Point that is
        associated with P-Bit = 110 tagged frames. The value 0xFFFF is a null pointer.(2 bytes)"
        REFERENCE   "G.983.2 section 7.3.95 802.1p mapper service profile"
        ::= { zxGponFlowDot1pMapServiceProfileEntry 7 }

    zxGponFlowDot1pMapServiceProfilePrio7GemPortId OBJECT-TYPE
        SYNTAX      INTEGER
        MAX-ACCESS  read-only
        STATUS      current
        DESCRIPTION
        "This attribute represents a pointer to the Interworking Termination Point that is
        associated with P-Bit = 111 tagged frames. The value 0xFFFF is a null pointer.(2 bytes)"
        REFERENCE   "G.983.2 section 7.3.95 802.1p mapper service profile"
        ::= { zxGponFlowDot1pMapServiceProfileEntry 8 }

    zxGponFlowDot1pMapServiceProfileUnmarkedFrameOption OBJECT-TYPE
        SYNTAX      INTEGER{
                    dscp2Dot1p(1),
                    defaultTag(2)
                    }
        MAX-ACCESS  read-write
        STATUS      current
        DESCRIPTION
        "This attribute indicates how the ONT should handle Untagged Ethernet frames received
        across the associated Ethernet interface. Valid values include the following:
          0: Convert from DSCP to 802.1p;
          1: Tag frame to a certain value.
        (1 byte)"
        REFERENCE   "G.983.2 section 7.3.95 802.1p mapper service profile"
        ::= { zxGponFlowDot1pMapServiceProfileEntry 9 }

    zxGponFlowDot1pMapServiceProfileDSCP2PBitMap OBJECT-TYPE
        SYNTAX      OCTET STRING(SIZE(24))
        MAX-ACCESS  read-write
        STATUS      current
        DESCRIPTION
        "This attribute is used in conjunction with the Unmarked Frame Option attribute.
        If unmarked frame option is 0, this attribute structure can be considered a bitmap
        that represents a sequence of 64 '3-bit' groupings. Each of the 64 groupings represents
        the possible value of the 6-bit DSCP field. Each of the '3-bit' groupings represents
        the 'P-bit value' to which the associated DSCP value should be mapped. Once marked,
        the P-Bit marked frame will then be routed to the GEM Interwork Pointer as indicated
        by the P-Bit to Interwork Pointer mappings above.(24 bytes)"
        REFERENCE   "G.983.2 section 7.3.95 802.1p mapper service profile"
        ::= { zxGponFlowDot1pMapServiceProfileEntry 10 }

    zxGponFlowDot1pMapServiceProfileDefPBitMarking OBJECT-TYPE
        SYNTAX      INTEGER
        MAX-ACCESS  read-write
        STATUS      current
        DESCRIPTION
        "This attribute is used in conjunction with the Unmarked Frame Option attribute.
        If unmarked frame option is 1, this attribute contains the default P-Bit priority
        setting that will be applied to the frame. The P-Bit marked frame will then be
        routed to the GEM Interwork Pointer as indicated by the P-Bit to Interwork Pointer
        mappings above.(1 byte)"
        REFERENCE   "G.983.2 section 7.3.95 802.1p mapper service profile"
        ::= { zxGponFlowDot1pMapServiceProfileEntry 11 }


--G.983.2 7.3.33 MAC Bridge port filter table data
--for UNI
    zxGponUNIBridgePortMacFilterTable    OBJECT-TYPE
        SYNTAX      SEQUENCE OF ZxGponUNIBridgePortMacFilterEntry
        MAX-ACCESS  not-accessible
        STATUS      current
        DESCRIPTION
            "This managed entity is used to organize and record data that is associated with
            a bridge port. Some of the data is volatile.
            This managed entity is associated with one instance of a MACBridgePortConfigurationData."
        REFERENCE   "G.983.2 section 7.3.33 MAC Bridge port filter table data"
        ::= { zxGponRmL2Mgmt 7 }

    zxGponUNIBridgePortMacFilterEntry OBJECT-TYPE
        SYNTAX      ZxGponUNIBridgePortMacFilterEntry
        MAX-ACCESS  not-accessible
        STATUS      current
        DESCRIPTION
            "It is entry in the zxGponUNIBridgePortMacFilterTable."
        INDEX   { zxGponOltIndex, zxGponONTIndex, zxGponUNIIndex, zxGponUNIBridgePortMacFilterAddress }
        ::= { zxGponUNIBridgePortMacFilterTable 1 }

    ZxGponUNIBridgePortMacFilterEntry ::=
        SEQUENCE {
            zxGponUNIBridgePortMacFilterAddress                 MacAddress,
            zxGponUNIBridgePortMacFilterFilterMode              INTEGER,
            zxGponUNIBridgePortMacFilterEntryStatus             RowStatus,
            zxGponUNIBrgPortMacFilterType                       INTEGER
        }

    zxGponUNIBridgePortMacFilterAddress OBJECT-TYPE
        SYNTAX      MacAddress
        MAX-ACCESS  read-only
        STATUS      current
        DESCRIPTION
        "This attribute specifies the MAC address being filtered."
        REFERENCE   "G.983.2 section 7.3.33 MAC Bridge port filter table data"
        ::= { zxGponUNIBridgePortMacFilterEntry 1 }

    zxGponUNIBridgePortMacFilterFilterMode OBJECT-TYPE
        SYNTAX      INTEGER{
                    forward(1),
                    discard(2)
                    }
        MAX-ACCESS  read-write
        STATUS      current
        DESCRIPTION
        "This attribute specifies the filter action."
        REFERENCE   "G.983.2 section 7.3.33 MAC Bridge port filter table data"
        ::= { zxGponUNIBridgePortMacFilterEntry 2 }

    zxGponUNIBridgePortMacFilterEntryStatus OBJECT-TYPE
        SYNTAX      RowStatus
        MAX-ACCESS  read-write
        STATUS      current
        DESCRIPTION
        "This attribute specifies the operation of this entry."
        REFERENCE   "G.983.2 section 7.3.33 MAC Bridge port filter table data"
        ::= { zxGponUNIBridgePortMacFilterEntry 3 }

    zxGponUNIBrgPortMacFilterType OBJECT-TYPE
        SYNTAX      INTEGER{
                    sourceMac(1),
                    destinationMac(2)
                    }
        MAX-ACCESS  read-write
        STATUS      current
        DESCRIPTION
        "sourceMac: source MAC
         destinationMac: destination MAC"
        REFERENCE   "G.983.2 section 7.3.33 MAC Bridge port filter table data"
        DEFVAL      { destinationMac }
        ::= { zxGponUNIBridgePortMacFilterEntry 4 }

    --G.983.2 7.3.33 MAC Bridge port filter table data
    --for IP Host
    zxGponIPHostBridgePortMacFilterTable    OBJECT-TYPE
        SYNTAX      SEQUENCE OF ZxGponIPHostBridgePortMacFilterEntry
        MAX-ACCESS  not-accessible
        STATUS      current
        DESCRIPTION
            "This managed entity is used to organize and record data that is associated with
            a bridge port. Some of the data is volatile.
            This managed entity is associated with one instance of a MACBridgePortConfigurationData."
        REFERENCE   "G.983.2 section 7.3.33 MAC Bridge port filter table data"
        ::= { zxGponRmL2Mgmt 8 }

    zxGponIPHostBridgePortMacFilterEntry OBJECT-TYPE
        SYNTAX      ZxGponIPHostBridgePortMacFilterEntry
        MAX-ACCESS  not-accessible
        STATUS      current
        DESCRIPTION
            "It is entry in the zxGponIPHostBridgePortMacFilterTable."
        INDEX   { zxGponOltIndex, zxGponONTIndex, zxGponIPHostConfigDataId, zxGponIPHostBridgePortMacFilterAddress }
        ::= { zxGponIPHostBridgePortMacFilterTable 1 }

    ZxGponIPHostBridgePortMacFilterEntry ::=
        SEQUENCE {
            zxGponIPHostBridgePortMacFilterAddress                 MacAddress,
            zxGponIPHostBridgePortMacFilterFilterMode              INTEGER,
            zxGponIPHostBridgePortMacFilterEntryStatus             RowStatus,
            zxGponIpHostBrgPortMacFilterType                       INTEGER
        }

    zxGponIPHostBridgePortMacFilterAddress OBJECT-TYPE
        SYNTAX      MacAddress
        MAX-ACCESS  read-only
        STATUS      current
        DESCRIPTION
        "This attribute specifies the MAC address being filtered."
        REFERENCE   "G.983.2 section 7.3.33 MAC Bridge port filter table data"
        ::= { zxGponIPHostBridgePortMacFilterEntry 1 }

    zxGponIPHostBridgePortMacFilterFilterMode OBJECT-TYPE
        SYNTAX      INTEGER{
                    forward(1),
                    discard(2)
                    }
        MAX-ACCESS  read-write
        STATUS      current
        DESCRIPTION
        "This attribute specifies the filter action."
        REFERENCE   "G.983.2 section 7.3.33 MAC Bridge port filter table data"
        ::= { zxGponIPHostBridgePortMacFilterEntry 2 }

    zxGponIPHostBridgePortMacFilterEntryStatus OBJECT-TYPE
        SYNTAX      RowStatus
        MAX-ACCESS  read-write
        STATUS      current
        DESCRIPTION
        "This attribute specifies the operation of this entry."
        REFERENCE   "G.983.2 section 7.3.33 MAC Bridge port filter table data"
        ::= { zxGponIPHostBridgePortMacFilterEntry 3 }

    zxGponIpHostBrgPortMacFilterType OBJECT-TYPE
        SYNTAX      INTEGER{
                    sourceMac(1),
                    destinationMac(2)
                    }
        MAX-ACCESS  read-write
        STATUS      current
        DESCRIPTION
        "sourceMac: source MAC
         destinationMac: destination MAC"
        REFERENCE   "G.983.2 section 7.3.33 MAC Bridge port filter table data"
        DEFVAL      { destinationMac }
        ::= { zxGponIPHostBridgePortMacFilterEntry 4 }



--for flow
    zxGponFlowMacFilterTable    OBJECT-TYPE
        SYNTAX      SEQUENCE OF ZxGponFlowMacFilterEntry
        MAX-ACCESS  not-accessible
        STATUS      current
        DESCRIPTION
            "This managed entity is used to organize and record data that is associated with
            a bridge port. Some of the data is volatile.
            This managed entity is associated with one instance of a MACBridgePortConfigurationData."
        REFERENCE   "G.983.2 section 7.3.33 MAC Bridge port filter table data"
        ::= { zxGponRmL2Mgmt 9 }

    zxGponFlowMacFilterEntry OBJECT-TYPE
        SYNTAX      ZxGponFlowMacFilterEntry
        MAX-ACCESS  not-accessible
        STATUS      current
        DESCRIPTION
            "It is entry in the zxGponFlowMacFilterTable."
        INDEX   { zxGponOltIndex, zxGponONTIndex, zxGponFlowIndex, zxGponFlowMacFilterAddress }
        ::= { zxGponFlowMacFilterTable 1 }

    ZxGponFlowMacFilterEntry ::=
        SEQUENCE {
            zxGponFlowMacFilterAddress                 MacAddress,
            zxGponFlowMacFilterFilterMode              INTEGER,
            zxGponFlowMacFilterEntryStatus             RowStatus,
            zxGponFlowMacFilterType                    INTEGER
        }

    zxGponFlowMacFilterAddress OBJECT-TYPE
        SYNTAX      MacAddress
        MAX-ACCESS  read-only
        STATUS      current
        DESCRIPTION
        "This attribute specifies the MAC address being filtered."
        REFERENCE   "G.983.2 section 7.3.33 MAC Bridge port filter table data"
        ::= { zxGponFlowMacFilterEntry 1 }

    zxGponFlowMacFilterFilterMode OBJECT-TYPE
        SYNTAX      INTEGER{
                    forward(1),
                    discard(2)
                    }
        MAX-ACCESS  read-write
        STATUS      current
        DESCRIPTION
        "This attribute specifies the filter action."
        REFERENCE   "G.983.2 section 7.3.33 MAC Bridge port filter table data"
        ::= { zxGponFlowMacFilterEntry 2 }

    zxGponFlowMacFilterEntryStatus OBJECT-TYPE
        SYNTAX      RowStatus
        MAX-ACCESS  read-write
        STATUS      current
        DESCRIPTION
        "This attribute specifies the operation of this entry."
        REFERENCE   "G.983.2 section 7.3.33 MAC Bridge port filter table data"
        ::= { zxGponFlowMacFilterEntry 3 }

    zxGponFlowMacFilterType OBJECT-TYPE
         SYNTAX      INTEGER{
                    sourceMac(1),
                    destinationMac(2)
                    }
        MAX-ACCESS  read-write
        STATUS      current
        DESCRIPTION
        "sourceMac: source MAC
         destinationMac: destination MAC"
        REFERENCE   "G.983.2 section 7.3.33 MAC Bridge port filter table data"
        DEFVAL      { destinationMac }
        ::= { zxGponFlowMacFilterEntry 4 }


--G.983.2 7.3.51 MAC Bridge port filter preassign table
--for UNI
    zxGponUNIMACBridgePortEthFrameFilterTable    OBJECT-TYPE
        SYNTAX      SEQUENCE OF ZxGponUNIMACBridgePortEthFrameFilterEntry
        MAX-ACCESS  not-accessible
        STATUS      current
        DESCRIPTION
            "This managed entity provides an alternate approach to address filtering than that
            supported through MACBridgePortFilterTableData.
            This managed entity is associated with one instance of a MACBridgePortConfigurationData managed entity."
        REFERENCE   "G.983.2 section 7.3.51 MAC Bridge port filter preassign table"
        ::= { zxGponRmL2Mgmt 10 }

    zxGponUNIMACBridgePortEthFrameFilterEntry OBJECT-TYPE
        SYNTAX      ZxGponUNIMACBridgePortEthFrameFilterEntry
        MAX-ACCESS  not-accessible
        STATUS      current
        DESCRIPTION
            "It is entry in the zxGponUNIMACBridgePortEthFrameFilterTable."
        INDEX   { zxGponOltIndex, zxGponONTIndex, zxGponUNIIndex }
        ::= { zxGponUNIMACBridgePortEthFrameFilterTable 1 }

    ZxGponUNIMACBridgePortEthFrameFilterEntry ::=
        SEQUENCE {
            zxGponUNIMACBridgePortEthFrameFilterIPv4MCFilter            INTEGER,
            zxGponUNIMACBridgePortEthFrameFilterIPv6MCFilter            INTEGER,
            zxGponUNIMACBridgePortEthFrameFilterIPv4BCFilter            INTEGER,
            zxGponUNIMACBridgePortEthFrameFilterRARPFilter              INTEGER,
            zxGponUNIMACBridgePortEthFrameFilterIPXFilter               INTEGER,
            zxGponUNIMACBridgePortEthFrameFilterNetBEUIFilter           INTEGER,
            zxGponUNIMACBridgePortEthFrameFilterAppleTalkFilter         INTEGER,
            zxGponUNIMACBridgePortEthFrameFilterBPDUFilter              INTEGER,
            zxGponUNIMACBridgePortEthFrameFilterARPFilter               INTEGER,
            zxGponUNIMACBridgePortEthFrameFilterPPPoEFilter             INTEGER
        }

    zxGponUNIMACBridgePortEthFrameFilterIPv4MCFilter OBJECT-TYPE
        SYNTAX      INTEGER{
                    forward(1),
                    discard(2)
                    }
        MAX-ACCESS  read-write
        STATUS      current
        DESCRIPTION
        "This attribute indicates whether IPv4Multicast Ether types are forwarded (value 0x00)
        or filtered (value 0x01). Initial value is 0x00.(1 byte)"
        REFERENCE   "G.983.2 section 7.3.51 MAC Bridge port filter preassign table"
        ::= { zxGponUNIMACBridgePortEthFrameFilterEntry 1 }

    zxGponUNIMACBridgePortEthFrameFilterIPv6MCFilter OBJECT-TYPE
        SYNTAX      INTEGER{
                    forward(1),
                    discard(2)
                    }
        MAX-ACCESS  read-write
        STATUS      current
        DESCRIPTION
        "This attribute indicates whether Ipv6Multicast Ether types are forwarded (value 0x00)
        or filtered (value 0x01). Initial value is 0x00.(1 byte)"
        REFERENCE   "G.983.2 section 7.3.51 MAC Bridge port filter preassign table"
        ::= { zxGponUNIMACBridgePortEthFrameFilterEntry 2 }

    zxGponUNIMACBridgePortEthFrameFilterIPv4BCFilter OBJECT-TYPE
        SYNTAX      INTEGER{
                    forward(1),
                    discard(2)
                    }
        MAX-ACCESS  read-write
        STATUS      current
        DESCRIPTION
        "This attribute indicates whether IPv4Broadcast Ether types are forwarded (value 0x00)
        or filtered (value 0x01). Initial value is 0x00.(1 byte)"
        REFERENCE   "G.983.2 section 7.3.51 MAC Bridge port filter preassign table"
        ::= { zxGponUNIMACBridgePortEthFrameFilterEntry 3 }

    zxGponUNIMACBridgePortEthFrameFilterRARPFilter OBJECT-TYPE
        SYNTAX      INTEGER{
                    forward(1),
                    discard(2)
                    }
        MAX-ACCESS  read-write
        STATUS      current
        DESCRIPTION
        "This attribute indicates whether RARP Ether types are forwarded (value 0x00)
        or filtered (value 0x01). Initial value is 0x00.(1 byte)"
        REFERENCE   "G.983.2 section 7.3.51 MAC Bridge port filter preassign table"
        ::= { zxGponUNIMACBridgePortEthFrameFilterEntry 4 }

    zxGponUNIMACBridgePortEthFrameFilterIPXFilter OBJECT-TYPE
        SYNTAX      INTEGER{
                    forward(1),
                    discard(2)
                    }
        MAX-ACCESS  read-write
        STATUS      current
        DESCRIPTION
        "This attribute indicates whether IPX Ether types are forwarded (value 0x00)
        or filtered (value 0x01). Initial value is 0x00.(1 byte)"
        REFERENCE   "G.983.2 section 7.3.51 MAC Bridge port filter preassign table"
        ::= { zxGponUNIMACBridgePortEthFrameFilterEntry 5 }

    zxGponUNIMACBridgePortEthFrameFilterNetBEUIFilter OBJECT-TYPE
        SYNTAX      INTEGER{
                    forward(1),
                    discard(2)
                    }
        MAX-ACCESS  read-write
        STATUS      current
        DESCRIPTION
        "This attribute indicates whether NetBEUI Ether types are forwarded (value 0x00)
        or filtered (value 0x01). Initial value is 0x00.(1 byte)"
        REFERENCE   "G.983.2 section 7.3.51 MAC Bridge port filter preassign table"
        ::= { zxGponUNIMACBridgePortEthFrameFilterEntry 6 }

    zxGponUNIMACBridgePortEthFrameFilterAppleTalkFilter OBJECT-TYPE
        SYNTAX      INTEGER{
                    forward(1),
                    discard(2)
                    }
        MAX-ACCESS  read-write
        STATUS      current
        DESCRIPTION
        "This attribute indicates whether AppleTalk Ether types are forwarded (value 0x00)
        or filtered (value 0x01). Initial value is 0x00.(1 byte)"
        REFERENCE   "G.983.2 section 7.3.51 MAC Bridge port filter preassign table"
        ::= { zxGponUNIMACBridgePortEthFrameFilterEntry 7 }

    zxGponUNIMACBridgePortEthFrameFilterBPDUFilter OBJECT-TYPE
        SYNTAX      INTEGER{
                    forward(1),
                    discard(2)
                    }
        MAX-ACCESS  read-write
        STATUS      current
        DESCRIPTION
        "This attribute indicates whether BridgeManagementInformation Ether types are
        forwarded (value 0x00) or filtered (value 0x01). Initial value is 0x00.(1 byte)"
        REFERENCE   "G.983.2 section 7.3.51 MAC Bridge port filter preassign table"
        ::= { zxGponUNIMACBridgePortEthFrameFilterEntry 8 }

    zxGponUNIMACBridgePortEthFrameFilterARPFilter OBJECT-TYPE
        SYNTAX      INTEGER{
                    forward(1),
                    discard(2)
                    }
        MAX-ACCESS  read-write
        STATUS      current
        DESCRIPTION
        "This attribute indicates whether ARP Ether types are forwarded (value 0x00)
        or filtered (value 0x01). Initial value is 0x00.(1 byte)"
        REFERENCE   "G.983.2 section 7.3.51 MAC Bridge port filter preassign table"
        ::= { zxGponUNIMACBridgePortEthFrameFilterEntry 9 }

    zxGponUNIMACBridgePortEthFrameFilterPPPoEFilter OBJECT-TYPE
        SYNTAX      INTEGER{
                    forward(1),
                    discard(2)
                    }
        MAX-ACCESS  read-write
        STATUS      current
        DESCRIPTION
        "This attribute indicates whether PPPoE Ether types are forwarded (value 0x00)
        or filtered (value 0x01). Initial value is 0x00.(1 byte)"
        REFERENCE   "G.983.2 section 7.3.51 MAC Bridge port filter preassign table"
        ::= { zxGponUNIMACBridgePortEthFrameFilterEntry 10 }

--G.983.2 7.3.51 MAC Bridge port filter preassign table
--for IP Host
    zxGponIPHostMACBridgePortEthFrameFilterTable    OBJECT-TYPE
        SYNTAX      SEQUENCE OF ZxGponIPHostMACBridgePortEthFrameFilterEntry
        MAX-ACCESS  not-accessible
        STATUS      current
        DESCRIPTION
            "This managed entity provides an alternate approach to address filtering than that
            supported through MACBridgePortFilterTableData.
            This managed entity is associated with one instance of a MACBridgePortConfigurationData managed entity."
        REFERENCE   "G.983.2 section 7.3.51 MAC Bridge port filter preassign table"
        ::= { zxGponRmL2Mgmt 11 }

    zxGponIPHostMACBridgePortEthFrameFilterEntry OBJECT-TYPE
        SYNTAX      ZxGponIPHostMACBridgePortEthFrameFilterEntry
        MAX-ACCESS  not-accessible
        STATUS      current
        DESCRIPTION
            "It is entry in the zxGponIPHostMACBridgePortEthFrameFilterTable."
        INDEX   { zxGponOltIndex, zxGponONTIndex, zxGponIPHostConfigDataId }
        ::= { zxGponIPHostMACBridgePortEthFrameFilterTable 1 }

    ZxGponIPHostMACBridgePortEthFrameFilterEntry ::=
        SEQUENCE {
            zxGponIPHostMACBridgePortEthFrameFilterIPv4MCFilter            INTEGER,
            zxGponIPHostMACBridgePortEthFrameFilterIPv6MCFilter            INTEGER,
            zxGponIPHostMACBridgePortEthFrameFilterIPv4BCFilter            INTEGER,
            zxGponIPHostMACBridgePortEthFrameFilterRARPFilter              INTEGER,
            zxGponIPHostMACBridgePortEthFrameFilterIPXFilter               INTEGER,
            zxGponIPHostMACBridgePortEthFrameFilterNetBEUIFilter           INTEGER,
            zxGponIPHostMACBridgePortEthFrameFilterAppleTalkFilter         INTEGER,
            zxGponIPHostMACBridgePortEthFrameFilterBPDUFilter              INTEGER,
            zxGponIPHostMACBridgePortEthFrameFilterARPFilter               INTEGER,
            zxGponIPHostMACBridgePortEthFrameFilterPPPoEFilter             INTEGER
        }

    zxGponIPHostMACBridgePortEthFrameFilterIPv4MCFilter OBJECT-TYPE
        SYNTAX      INTEGER{
                    forward(1),
                    discard(2)
                    }
        MAX-ACCESS  read-write
        STATUS      current
        DESCRIPTION
        "This attribute indicates whether IPv4Multicast Ether types are forwarded (value 0x00)
        or filtered (value 0x01). Initial value is 0x00.(1 byte)"
        REFERENCE   "G.983.2 section 7.3.51 MAC Bridge port filter preassign table"
        ::= { zxGponIPHostMACBridgePortEthFrameFilterEntry 1 }

    zxGponIPHostMACBridgePortEthFrameFilterIPv6MCFilter OBJECT-TYPE
        SYNTAX      INTEGER{
                    forward(1),
                    discard(2)
                    }
        MAX-ACCESS  read-write
        STATUS      current
        DESCRIPTION
        "This attribute indicates whether Ipv6Multicast Ether types are forwarded (value 0x00)
        or filtered (value 0x01). Initial value is 0x00.(1 byte)"
        REFERENCE   "G.983.2 section 7.3.51 MAC Bridge port filter preassign table"
        ::= { zxGponIPHostMACBridgePortEthFrameFilterEntry 2 }

    zxGponIPHostMACBridgePortEthFrameFilterIPv4BCFilter OBJECT-TYPE
        SYNTAX      INTEGER{
                    forward(1),
                    discard(2)
                    }
        MAX-ACCESS  read-write
        STATUS      current
        DESCRIPTION
        "This attribute indicates whether IPv4Broadcast Ether types are forwarded (value 0x00)
        or filtered (value 0x01). Initial value is 0x00.(1 byte)"
        REFERENCE   "G.983.2 section 7.3.51 MAC Bridge port filter preassign table"
        ::= { zxGponIPHostMACBridgePortEthFrameFilterEntry 3 }

    zxGponIPHostMACBridgePortEthFrameFilterRARPFilter OBJECT-TYPE
        SYNTAX      INTEGER{
                    forward(1),
                    discard(2)
                    }
        MAX-ACCESS  read-write
        STATUS      current
        DESCRIPTION
        "This attribute indicates whether RARP Ether types are forwarded (value 0x00)
        or filtered (value 0x01). Initial value is 0x00.(1 byte)"
        REFERENCE   "G.983.2 section 7.3.51 MAC Bridge port filter preassign table"
        ::= { zxGponIPHostMACBridgePortEthFrameFilterEntry 4 }

    zxGponIPHostMACBridgePortEthFrameFilterIPXFilter OBJECT-TYPE
        SYNTAX      INTEGER{
                    forward(1),
                    discard(2)
                    }
        MAX-ACCESS  read-write
        STATUS      current
        DESCRIPTION
        "This attribute indicates whether IPX Ether types are forwarded (value 0x00)
        or filtered (value 0x01). Initial value is 0x00.(1 byte)"
        REFERENCE   "G.983.2 section 7.3.51 MAC Bridge port filter preassign table"
        ::= { zxGponIPHostMACBridgePortEthFrameFilterEntry 5 }

    zxGponIPHostMACBridgePortEthFrameFilterNetBEUIFilter OBJECT-TYPE
        SYNTAX      INTEGER{
                    forward(1),
                    discard(2)
                    }
        MAX-ACCESS  read-write
        STATUS      current
        DESCRIPTION
        "This attribute indicates whether NetBEUI Ether types are forwarded (value 0x00)
        or filtered (value 0x01). Initial value is 0x00.(1 byte)"
        REFERENCE   "G.983.2 section 7.3.51 MAC Bridge port filter preassign table"
        ::= { zxGponIPHostMACBridgePortEthFrameFilterEntry 6 }

    zxGponIPHostMACBridgePortEthFrameFilterAppleTalkFilter OBJECT-TYPE
        SYNTAX      INTEGER{
                    forward(1),
                    discard(2)
                    }
        MAX-ACCESS  read-write
        STATUS      current
        DESCRIPTION
        "This attribute indicates whether AppleTalk Ether types are forwarded (value 0x00)
        or filtered (value 0x01). Initial value is 0x00.(1 byte)"
        REFERENCE   "G.983.2 section 7.3.51 MAC Bridge port filter preassign table"
        ::= { zxGponIPHostMACBridgePortEthFrameFilterEntry 7 }

    zxGponIPHostMACBridgePortEthFrameFilterBPDUFilter OBJECT-TYPE
        SYNTAX      INTEGER{
                    forward(1),
                    discard(2)
                    }
        MAX-ACCESS  read-write
        STATUS      current
        DESCRIPTION
        "This attribute indicates whether BridgeManagementInformation Ether types are
        forwarded (value 0x00) or filtered (value 0x01). Initial value is 0x00.(1 byte)"
        REFERENCE   "G.983.2 section 7.3.51 MAC Bridge port filter preassign table"
        ::= { zxGponIPHostMACBridgePortEthFrameFilterEntry 8 }

    zxGponIPHostMACBridgePortEthFrameFilterARPFilter OBJECT-TYPE
        SYNTAX      INTEGER{
                    forward(1),
                    discard(2)
                    }
        MAX-ACCESS  read-write
        STATUS      current
        DESCRIPTION
        "This attribute indicates whether ARP Ether types are forwarded (value 0x00)
        or filtered (value 0x01). Initial value is 0x00.(1 byte)"
        REFERENCE   "G.983.2 section 7.3.51 MAC Bridge port filter preassign table"
        ::= { zxGponIPHostMACBridgePortEthFrameFilterEntry 9 }

    zxGponIPHostMACBridgePortEthFrameFilterPPPoEFilter OBJECT-TYPE
        SYNTAX      INTEGER{
                    forward(1),
                    discard(2)
                    }
        MAX-ACCESS  read-write
        STATUS      current
        DESCRIPTION
        "This attribute indicates whether PPPoE Ether types are forwarded (value 0x00)
        or filtered (value 0x01). Initial value is 0x00.(1 byte)"
        REFERENCE   "G.983.2 section 7.3.51 MAC Bridge port filter preassign table"
        ::= { zxGponIPHostMACBridgePortEthFrameFilterEntry 10 }


--for flow
    zxGponFlowEthFrameFilterTable    OBJECT-TYPE
        SYNTAX      SEQUENCE OF ZxGponFlowEthFrameFilterEntry
        MAX-ACCESS  not-accessible
        STATUS      current
        DESCRIPTION
            "This managed entity provides an alternate approach to address filtering than that
            supported through MACBridgePortFilterTableData.
            This managed entity is associated with one instance of a MACBridgePortConfigurationData managed entity."
        REFERENCE   "G.983.2 section 7.3.51 MAC Bridge port filter preassign table"
        ::= { zxGponRmL2Mgmt 12 }

    zxGponFlowEthFrameFilterEntry OBJECT-TYPE
        SYNTAX      ZxGponFlowEthFrameFilterEntry
        MAX-ACCESS  not-accessible
        STATUS      current
        DESCRIPTION
            "It is entry in the zxGponFlowEthFrameFilterTable."
        INDEX   { zxGponOltIndex, zxGponONTIndex, zxGponFlowIndex }
        ::= { zxGponFlowEthFrameFilterTable 1 }

    ZxGponFlowEthFrameFilterEntry ::=
        SEQUENCE {
            zxGponFlowEthFrameFilterIPv4MCFilter            INTEGER,
            zxGponFlowEthFrameFilterIPv6MCFilter            INTEGER,
            zxGponFlowEthFrameFilterIPv4BCFilter            INTEGER,
            zxGponFlowEthFrameFilterRARPFilter              INTEGER,
            zxGponFlowEthFrameFilterIPXFilter               INTEGER,
            zxGponFlowEthFrameFilterNetBEUIFilter           INTEGER,
            zxGponFlowEthFrameFilterAppleTalkFilter         INTEGER,
            zxGponFlowEthFrameFilterBPDUFilter              INTEGER,
            zxGponFlowEthFrameFilterARPFilter               INTEGER,
            zxGponFlowEthFrameFilterPPPoEFilter             INTEGER
        }

    zxGponFlowEthFrameFilterIPv4MCFilter OBJECT-TYPE
        SYNTAX      INTEGER{
                    forward(1),
                    discard(2)
                    }
        MAX-ACCESS  read-write
        STATUS      current
        DESCRIPTION
        "This attribute indicates whether IPv4Multicast Ether types are forwarded (value 0x00)
        or filtered (value 0x01). Initial value is 0x00.(1 byte)"
        REFERENCE   "G.983.2 section 7.3.51 MAC Bridge port filter preassign table"
        ::= { zxGponFlowEthFrameFilterEntry 1 }

    zxGponFlowEthFrameFilterIPv6MCFilter OBJECT-TYPE
        SYNTAX      INTEGER{
                    forward(1),
                    discard(2)
                    }
        MAX-ACCESS  read-write
        STATUS      current
        DESCRIPTION
        "This attribute indicates whether Ipv6Multicast Ether types are forwarded (value 0x00)
        or filtered (value 0x01). Initial value is 0x00.(1 byte)"
        REFERENCE   "G.983.2 section 7.3.51 MAC Bridge port filter preassign table"
        ::= { zxGponFlowEthFrameFilterEntry 2 }

    zxGponFlowEthFrameFilterIPv4BCFilter OBJECT-TYPE
        SYNTAX      INTEGER{
                    forward(1),
                    discard(2)
                    }
        MAX-ACCESS  read-write
        STATUS      current
        DESCRIPTION
        "This attribute indicates whether IPv4Broadcast Ether types are forwarded (value 0x00)
        or filtered (value 0x01). Initial value is 0x00.(1 byte)"
        REFERENCE   "G.983.2 section 7.3.51 MAC Bridge port filter preassign table"
        ::= { zxGponFlowEthFrameFilterEntry 3 }

    zxGponFlowEthFrameFilterRARPFilter OBJECT-TYPE
        SYNTAX      INTEGER{
                    forward(1),
                    discard(2)
                    }
        MAX-ACCESS  read-write
        STATUS      current
        DESCRIPTION
        "This attribute indicates whether RARP Ether types are forwarded (value 0x00)
        or filtered (value 0x01). Initial value is 0x00.(1 byte)"
        REFERENCE   "G.983.2 section 7.3.51 MAC Bridge port filter preassign table"
        ::= { zxGponFlowEthFrameFilterEntry 4 }

    zxGponFlowEthFrameFilterIPXFilter OBJECT-TYPE
        SYNTAX      INTEGER{
                    forward(1),
                    discard(2)
                    }
        MAX-ACCESS  read-write
        STATUS      current
        DESCRIPTION
        "This attribute indicates whether IPX Ether types are forwarded (value 0x00)
        or filtered (value 0x01). Initial value is 0x00.(1 byte)"
        REFERENCE   "G.983.2 section 7.3.51 MAC Bridge port filter preassign table"
        ::= { zxGponFlowEthFrameFilterEntry 5 }

    zxGponFlowEthFrameFilterNetBEUIFilter OBJECT-TYPE
        SYNTAX      INTEGER{
                    forward(1),
                    discard(2)
                    }
        MAX-ACCESS  read-write
        STATUS      current
        DESCRIPTION
        "This attribute indicates whether NetBEUI Ether types are forwarded (value 0x00)
        or filtered (value 0x01). Initial value is 0x00.(1 byte)"
        REFERENCE   "G.983.2 section 7.3.51 MAC Bridge port filter preassign table"
        ::= { zxGponFlowEthFrameFilterEntry 6 }

    zxGponFlowEthFrameFilterAppleTalkFilter OBJECT-TYPE
        SYNTAX      INTEGER{
                    forward(1),
                    discard(2)
                    }
        MAX-ACCESS  read-write
        STATUS      current
        DESCRIPTION
        "This attribute indicates whether AppleTalk Ether types are forwarded (value 0x00)
        or filtered (value 0x01). Initial value is 0x00.(1 byte)"
        REFERENCE   "G.983.2 section 7.3.51 MAC Bridge port filter preassign table"
        ::= { zxGponFlowEthFrameFilterEntry 7 }

    zxGponFlowEthFrameFilterBPDUFilter OBJECT-TYPE
        SYNTAX      INTEGER{
                    forward(1),
                    discard(2)
                    }
        MAX-ACCESS  read-write
        STATUS      current
        DESCRIPTION
        "This attribute indicates whether BridgeManagementInformation Ether types are
        forwarded (value 0x00) or filtered (value 0x01). Initial value is 0x00.(1 byte)"
        REFERENCE   "G.983.2 section 7.3.51 MAC Bridge port filter preassign table"
        ::= { zxGponFlowEthFrameFilterEntry 8 }

    zxGponFlowEthFrameFilterARPFilter OBJECT-TYPE
        SYNTAX      INTEGER{
                    forward(1),
                    discard(2)
                    }
        MAX-ACCESS  read-write
        STATUS      current
        DESCRIPTION
        "This attribute indicates whether ARP Ether types are forwarded (value 0x00)
        or filtered (value 0x01). Initial value is 0x00.(1 byte)"
        REFERENCE   "G.983.2 section 7.3.51 MAC Bridge port filter preassign table"
        ::= { zxGponFlowEthFrameFilterEntry 9 }

    zxGponFlowEthFrameFilterPPPoEFilter OBJECT-TYPE
        SYNTAX      INTEGER{
                    forward(1),
                    discard(2)
                    }
        MAX-ACCESS  read-write
        STATUS      current
        DESCRIPTION
        "This attribute indicates whether PPPoE Ether types are forwarded (value 0x00)
        or filtered (value 0x01). Initial value is 0x00.(1 byte)"
        REFERENCE   "G.983.2 section 7.3.51 MAC Bridge port filter preassign table"
        ::= { zxGponFlowEthFrameFilterEntry 10 }


--Filter...
--G.983.2 7.3.50 VLAN tagging filter data
--for UNI
    zxGponUNIVLANTagFilterModeTable    OBJECT-TYPE
        SYNTAX      SEQUENCE OF ZxGponUNIVLANTagFilterModeEntry
        MAX-ACCESS  not-accessible
        STATUS      current
        DESCRIPTION
            "This managed entity is used to organize data associated with VLAN tagging.
            Instances of this managed entity are created/deleted at the request of the OLT.
            Zero or one instance of this managed entity may exist for each instance of MAC
            Bridge Port Configuration Data which is associated with Interworking VCC Termination
            Point (PON side) or Physical Path Termination Point Ethernet UNI."
        REFERENCE   "G.983.2 section 7.3.50 VLAN tagging filter data"
        ::= { zxGponRmL2Mgmt 13 }

    zxGponUNIVLANTagFilterModeEntry OBJECT-TYPE
        SYNTAX      ZxGponUNIVLANTagFilterModeEntry
        MAX-ACCESS  not-accessible
        STATUS      current
        DESCRIPTION
            "It is entry in the zxGponUNIVLANTagFilterModeTable."
        INDEX   { zxGponOltIndex, zxGponONTIndex, zxGponUNIIndex }
        ::= { zxGponUNIVLANTagFilterModeTable 1 }

    ZxGponUNIVLANTagFilterModeEntry ::=
        SEQUENCE {
            zxGponUNIVLANTagFilterModeForwardOper             INTEGER,
            zxGponUNIVLANTagFilterModeEntryStatus             RowStatus
        }

    zxGponUNIVLANTagFilterModeForwardOper OBJECT-TYPE
        SYNTAX      INTEGER{
                    mode0(1),
                    mode1(2),
                    mode2(3),
                    mode3(4),
                    mode4(5),
                    mode5(6),
                    mode6(7),
                    mode7(8),
                    mode8(9),
                    mode9(10),
                    mode10(11),
                    mode11(12),
                    mode12(13),
                    mode13(14),
                    mode14(15),
                    mode15(16),
                    mode16(17),
                    mode17(18),
                    mode18(19),
                    mode19(20),
                    mode20(21),
                    mode21(22)
                    }
        MAX-ACCESS  read-write
        STATUS      current
        DESCRIPTION
        "When a frame is received, the frame is processed according to the following Forward
        Operations. The operations are invoked based on the value of VID, user priority, or
        the entire TCI or whether or not the TCI field exists. This attribute indicates the
        received frame is treated as indicated below.(1 byte)
        !!!!!!mode5/6/9/10 is no used currently!!!!!!!
        tag-filter-action      untag-filter-action      forward-mode
        'transparent'          'transparent'            'mode0'
        'discard'              'transparent'            'mode1'
        'transparent'          'discard'                'mode2'
        'vid-filter'           'transparent'            'mode3'
        'vid-filter'           'discard'                'mode4'
        'prio-filter'          'transparent'            'mode7'
        'prio-filter'          'discard'                'mode8'
        'prio-vid-filter'      'transparent'            'mode11'
        'prio-vid-filter'      'discard'                'mode12'
        'vid-match'            'transparent'            'mode15'
        'vid-match'            'discard'                'mode16'
        'prio-match'           'transparent'            'mode17'
        'prio-match'           'discard'                'mode18'
        'prio-vid-match'       'transparent'            'mode19'
        'prio-vid-match'       'discard'                'mode20'
        'forward'              'discard'                'mode21'
        "
        REFERENCE   "G.983.2 section 7.3.50 VLAN tagging filter data"
        ::= { zxGponUNIVLANTagFilterModeEntry 1 }

    zxGponUNIVLANTagFilterModeEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponUNIVLANTagFilterModeEntry 2 }

    zxGponUNIVLANTagFilterTable    OBJECT-TYPE
        SYNTAX      SEQUENCE OF ZxGponUNIVLANTagFilterEntry
        MAX-ACCESS  not-accessible
        STATUS      current
        DESCRIPTION
            "This managed entity is used to organize data associated with VLAN tagging.
            Instances of this managed entity are created/deleted at the request of the OLT.
            Zero or one instance of this managed entity may exist for each instance of MAC
            Bridge Port Configuration Data which is associated with Interworking VCC Termination
            Point (PON side) or Physical Path Termination Point Ethernet UNI."
        REFERENCE   "G.983.2 section 7.3.50 VLAN tagging filter data"
        ::= { zxGponRmL2Mgmt 14 }

    zxGponUNIVLANTagFilterEntry OBJECT-TYPE
        SYNTAX      ZxGponUNIVLANTagFilterEntry
        MAX-ACCESS  not-accessible
        STATUS      current
        DESCRIPTION
            "It is entry in the zxGponUNIVLANTagFilterTable."
        INDEX   { zxGponOltIndex, zxGponONTIndex, zxGponUNIIndex, zxGponUNIVLANTagFilterTCI }
        ::= { zxGponUNIVLANTagFilterTable 1 }

    ZxGponUNIVLANTagFilterEntry ::=
        SEQUENCE {
            zxGponUNIVLANTagFilterTCI                     INTEGER,
            zxGponUNIVLANTagFilterEntryStatus             RowStatus
        }

    zxGponUNIVLANTagFilterTCI OBJECT-TYPE
        SYNTAX      INTEGER
        MAX-ACCESS  read-write
        STATUS      current
        DESCRIPTION
        "This attribute specifies the TCI value which is provisioned at a bridging port.(2 bytes)"
        REFERENCE   "G.983.2 section 7.3.50 VLAN tagging filter data"
        ::= { zxGponUNIVLANTagFilterEntry 1 }

    zxGponUNIVLANTagFilterEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponUNIVLANTagFilterEntry 2 }

--Filter...
--G.983.2 7.3.50 VLAN tagging filter data
--for IP Host
    zxGponIPHostVLANTagFilterModeTable    OBJECT-TYPE
        SYNTAX      SEQUENCE OF ZxGponIPHostVLANTagFilterModeEntry
        MAX-ACCESS  not-accessible
        STATUS      current
        DESCRIPTION
            "This managed entity is used to organize data associated with VLAN tagging.
            Instances of this managed entity are created/deleted at the request of the OLT.
            Zero or one instance of this managed entity may exist for each instance of MAC
            Bridge Port Configuration Data which is associated with Interworking VCC Termination
            Point (PON side) or Physical Path Termination Point Ethernet UNI."
        REFERENCE   "G.983.2 section 7.3.50 VLAN tagging filter data"
        ::= { zxGponRmL2Mgmt 15 }

    zxGponIPHostVLANTagFilterModeEntry OBJECT-TYPE
        SYNTAX      ZxGponIPHostVLANTagFilterModeEntry
        MAX-ACCESS  not-accessible
        STATUS      current
        DESCRIPTION
            "It is entry in the zxGponIPHostVLANTagFilterModeTable."
        INDEX   { zxGponOltIndex, zxGponONTIndex, zxGponIPHostConfigDataId }
        ::= { zxGponIPHostVLANTagFilterModeTable 1 }

    ZxGponIPHostVLANTagFilterModeEntry ::=
        SEQUENCE {
            zxGponIPHostVLANTagFilterModeForwardOper             INTEGER,
            zxGponIPHostVLANTagFilterModeEntryStatus             RowStatus
        }

    zxGponIPHostVLANTagFilterModeForwardOper OBJECT-TYPE
        SYNTAX      INTEGER{
                    mode0(1),
                    mode1(2),
                    mode2(3),
                    mode3(4),
                    mode4(5),
                    mode5(6),
                    mode6(7),
                    mode7(8),
                    mode8(9),
                    mode9(10),
                    mode10(11),
                    mode11(12),
                    mode12(13),
                    mode13(14),
                    mode14(15)
                    }
        MAX-ACCESS  read-write
        STATUS      current
        DESCRIPTION
        "When a frame is received, the frame is processed according to the following Forward
        Operations. The operations are invoked based on the value of VID, user priority, or
        the entire TCI or whether or not the TCI field exists. This attribute indicates the
        received frame is treated as indicated below.(1 byte)
        !!!!!!mode5/6/9/10 is no used currently!!!!!!!
        tag-filter-action      untag-filter-action      forward-mode
        'transparent'          'transparent'            'mode0'
        'discard'              'transparent'            'mode1'
        'transparent'          'discard'                'mode2'
        'vid-filter'           'transparent'            'mode3'
        'vid-filter'           'discard'                'mode4'
        'prio-filter'          'transparent'            'mode7'
        'prio-filter'          'discard'                'mode8'
        'prio-vid-filter'      'transparent'            'mode11'
        'prio-vid-filter'      'discard'                'mode12'
        "
        REFERENCE   "G.983.2 section 7.3.50 VLAN tagging filter data"
        ::= { zxGponIPHostVLANTagFilterModeEntry 1 }

    zxGponIPHostVLANTagFilterModeEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponIPHostVLANTagFilterModeEntry 2 }

    zxGponIPHostVLANTagFilterTable    OBJECT-TYPE
        SYNTAX      SEQUENCE OF ZxGponIPHostVLANTagFilterEntry
        MAX-ACCESS  not-accessible
        STATUS      current
        DESCRIPTION
            "This managed entity is used to organize data associated with VLAN tagging.
            Instances of this managed entity are created/deleted at the request of the OLT.
            Zero or one instance of this managed entity may exist for each instance of MAC
            Bridge Port Configuration Data which is associated with Interworking VCC Termination
            Point (PON side) or Physical Path Termination Point Ethernet UNI."
        REFERENCE   "G.983.2 section 7.3.50 VLAN tagging filter data"
        ::= { zxGponRmL2Mgmt 16 }

    zxGponIPHostVLANTagFilterEntry OBJECT-TYPE
        SYNTAX      ZxGponIPHostVLANTagFilterEntry
        MAX-ACCESS  not-accessible
        STATUS      current
        DESCRIPTION
            "It is entry in the zxGponIPHostVLANTagFilterTable."
        INDEX   { zxGponOltIndex, zxGponONTIndex, zxGponIPHostConfigDataId, zxGponIPHostVLANTagFilterTCI }
        ::= { zxGponIPHostVLANTagFilterTable 1 }

    ZxGponIPHostVLANTagFilterEntry ::=
        SEQUENCE {
            zxGponIPHostVLANTagFilterTCI                     INTEGER,
            zxGponIPHostVLANTagFilterEntryStatus             RowStatus
        }

    zxGponIPHostVLANTagFilterTCI OBJECT-TYPE
        SYNTAX      INTEGER
        MAX-ACCESS  read-write
        STATUS      current
        DESCRIPTION
        "This attribute specifies the TCI value which is provisioned at a bridging port.(2 bytes)"
        REFERENCE   "G.983.2 section 7.3.50 VLAN tagging filter data"
        ::= { zxGponIPHostVLANTagFilterEntry 1 }

    zxGponIPHostVLANTagFilterEntryStatus OBJECT-TYPE
        SYNTAX      RowStatus
        MAX-ACCESS  read-write
        STATUS      current
        DESCRIPTION
        "This attribute provides the number of entries in the VLAN Filter Table that are valid.(1 byte)"
        REFERENCE   "G.983.2 section 7.3.50 VLAN tagging filter data"
        ::= { zxGponIPHostVLANTagFilterEntry 2 }

--G.983.2 7.3.49 VLAN tagging operation configuration data
    zxGponVLANTagOperConfigTable    OBJECT-TYPE
        SYNTAX      SEQUENCE OF ZxGponVLANTagOperConfigEntry
        MAX-ACCESS  not-accessible
        STATUS      current
        DESCRIPTION
            "This managed entity is used to organize data associated with VLAN tagging.
            Instances of this managed entity are created/deleted at the request of the OLT.
            Zero or one instance of this managed entity may exist for each instance of
            Physical Path Termination Point Ethernet UNI."
        REFERENCE   "G.983.2 section 7.3.49 VLAN tagging operation configuration data"
        ::= { zxGponRmL2Mgmt 17 }

    zxGponVLANTagOperConfigEntry OBJECT-TYPE
        SYNTAX      ZxGponVLANTagOperConfigEntry
        MAX-ACCESS  not-accessible
        STATUS      current
        DESCRIPTION
            "It is entry in the zxGponVLANTagOperConfigTable."
        INDEX   { zxGponOltIndex, zxGponONTIndex, zxGponUNIIndex }
        ::= { zxGponVLANTagOperConfigTable 1 }

    ZxGponVLANTagOperConfigEntry ::=
        SEQUENCE {
            zxGponVLANTagOperConfigUpTagOperMode           INTEGER,
            zxGponVLANTagOperConfigUpTagTCIVal             INTEGER,
            zxGponVLANTagOperConfigDownTagOperMode         INTEGER,
            zxGponVLANTagOperConfigEntryStatus             RowStatus
        }

    zxGponVLANTagOperConfigUpTagOperMode OBJECT-TYPE
        SYNTAX      INTEGER{
                    transparent(1),
                    overwrite(2),
                    add(3),
                    addPvid(4)
                    }
        MAX-ACCESS  read-write
        STATUS      current
        DESCRIPTION
        "This attribute selects how upstream VLAN tagging is sent.
        Valid values are:
        0x01 (upstream frame is sent 'as is,' regardless of whether or not the received frame is tagged)
        0x02 (The upstream frame is sent as tagged whether or not the received frame is tagged.  TCI, consisting of VID, CFI and user priority, is attached or overwritten by using the Upstream VLAN Tag TCI Value.).
        0x03 (The upstream frame is sent as tagged whether or not the received frame is tagged.  If the received frame is tagged, a second tag (Q-n-Q) is added to the frame. If the received frame is not tagged a tag is attached to the frame. TCI, consisting of VID, CFI and user priority, is attached or added by using the Upstream VLAN Tag TCI Value.).
        0x04 (The upstream untagged frame is attached with the defined VLAN tag TCI value. The upstream tagged frame is forwarded unchanged).
       (1 byte)"
        REFERENCE   "G.983.2 section 7.3.49 VLAN tagging operation configuration data"
        ::= { zxGponVLANTagOperConfigEntry 1 }

    zxGponVLANTagOperConfigUpTagTCIVal OBJECT-TYPE
        SYNTAX      INTEGER
        MAX-ACCESS  read-write
        STATUS      current
        DESCRIPTION
        "This attribute indicates the TCI value for upstream VLAN tagging. It is used when the Upstream VLAN Tagging Operation Mode is 0x02, 0x03, or 0x04. Any 2-byte value is acceptable.(2 bytes)"
        REFERENCE   "G.983.2 section 7.3.49 VLAN tagging operation configuration data"
        ::= { zxGponVLANTagOperConfigEntry 2 }

    zxGponVLANTagOperConfigDownTagOperMode OBJECT-TYPE
        SYNTAX      INTEGER{
                    transparent(1),
                    untag(2),
                    deletePvid(3)
                    }
        MAX-ACCESS  read-write
        STATUS      current
        DESCRIPTION
        "This attribute selects whether or not downstream VLAN tagging is sent.
        Valid values are as follows:
        0x01 (downstream frame is sent 'as is', regardless of whether or not the received frame is tagged)
        0x02 (The downstream frame is sent as untagged whether or not the received frame is tagged).
        0x03 (If the received frame is tagged with defined VLAN tag TCI value, the outer tag is stripped.
              Otherwise, the tagged frame is forwarded unchanged)(1 byte)"
        REFERENCE   "G.983.2 section 7.3.49 VLAN tagging operation configuration data"
        ::= { zxGponVLANTagOperConfigEntry 3 }

    zxGponVLANTagOperConfigEntryStatus OBJECT-TYPE
        SYNTAX      RowStatus
        MAX-ACCESS  read-write
        STATUS      current
        DESCRIPTION
        ""
        REFERENCE   "G.983.2 section 7.3.49 VLAN tagging operation configuration data"
        ::= { zxGponVLANTagOperConfigEntry 4 }

--Ip host VLAN TAG
    --G.983.2 7.3.49 VLAN tagging operation configuration data
    zxGponIPHostVLANTagOperConfigTable    OBJECT-TYPE
        SYNTAX      SEQUENCE OF ZxGponIPHostVLANTagOperConfigEntry
        MAX-ACCESS  not-accessible
        STATUS      current
        DESCRIPTION
            "This managed entity is used to organize data associated with VLAN tagging.
            Instances of this managed entity are created/deleted at the request of the OLT.
            Zero or one instance of this managed entity may exist for each instance of
            IP Host."
        REFERENCE   "G.983.2 section 7.3.49 VLAN tagging operation configuration data"
        ::= { zxGponRmL2Mgmt 18 }

    zxGponIPHostVLANTagOperConfigEntry OBJECT-TYPE
        SYNTAX      ZxGponIPHostVLANTagOperConfigEntry
        MAX-ACCESS  not-accessible
        STATUS      current
        DESCRIPTION
            "It is entry in the zxGponIPHostVLANTagOperConfigTable."
        INDEX   { zxGponOltIndex, zxGponONTIndex, zxGponIPHostConfigDataId }
        ::= { zxGponIPHostVLANTagOperConfigTable 1 }

    ZxGponIPHostVLANTagOperConfigEntry ::=
        SEQUENCE {
            zxGponIPHostVLANTagOperConfigUpTagOperMode           INTEGER,
            zxGponIPHostVLANTagOperConfigUpTagTCIVal             INTEGER,
            zxGponIPHostVLANTagOperConfigDownTagOperMode         INTEGER,
            zxGponIPHostVLANTagOperConfigEntryStatus             RowStatus
        }

    zxGponIPHostVLANTagOperConfigUpTagOperMode OBJECT-TYPE
        SYNTAX      INTEGER{
                    transparent(1),
                    overwrite(2),
                    add(3)
                    }
        MAX-ACCESS  read-write
        STATUS      current
        DESCRIPTION
        "This attribute selects how upstream VLAN tagging is sent.
        Valid values are:
        0x00 (upstream frame is sent 'as is,' regardless of whether or not the received frame is tagged)
        0x01 (The upstream frame is sent as tagged whether or not the received frame is tagged.  TCI, consisting of VID, CFI and user priority, is attached or overwritten by using the Upstream VLAN Tag TCI Value.).
        0x02 (The upstream frame is sent as tagged whether or not the received frame is tagged.  If the received frame is tagged, a second tag (Q-n-Q) is added to the frame. If the received frame is not tagged a tag is attached to the frame. TCI, consisting of VID, CFI and user priority, is attached or added by using the Upstream VLAN Tag TCI Value.).
       (1 byte)"
        REFERENCE   "G.983.2 section 7.3.49 VLAN tagging operation configuration data"
        ::= { zxGponIPHostVLANTagOperConfigEntry 1 }

    zxGponIPHostVLANTagOperConfigUpTagTCIVal OBJECT-TYPE
        SYNTAX      INTEGER
        MAX-ACCESS  read-write
        STATUS      current
        DESCRIPTION
        "This attribute indicates the TCI value for upstream VLAN tagging. It is used when the Upstream VLAN Tagging Operation Mode is 0x01. Any 2-byte value is acceptable.(2 bytes)"
        REFERENCE   "G.983.2 section 7.3.49 VLAN tagging operation configuration data"
        ::= { zxGponIPHostVLANTagOperConfigEntry 2 }

    zxGponIPHostVLANTagOperConfigDownTagOperMode OBJECT-TYPE
        SYNTAX      INTEGER{
                    transparent(1),
                    untag(2)
                    }
        MAX-ACCESS  read-write
        STATUS      current
        DESCRIPTION
        "This attribute selects whether or not downstream VLAN tagging is sent.
        Valid values are 0x00 (downstream frame is sent 'as is', regardless of whether or not the received frame is tagged)
        and 0x01 (The downstream frame is sent as untagged whether or not the received frame is tagged).(1 byte)"
        REFERENCE   "G.983.2 section 7.3.49 VLAN tagging operation configuration data"
        ::= { zxGponIPHostVLANTagOperConfigEntry 3 }

    zxGponIPHostVLANTagOperConfigEntryStatus OBJECT-TYPE
        SYNTAX      RowStatus
        MAX-ACCESS  read-write
        STATUS      current
        DESCRIPTION
        "This attribute selects whether or not downstream VLAN tagging is sent.
        Valid values are 0x00 (downstream frame is sent 'as is', regardless of whether or not the received frame is tagged)
        and 0x01 (The downstream frame is sent as untagged whether or not the received frame is tagged).(1 byte)"
        REFERENCE   "G.983.2 section 7.3.49 VLAN tagging operation configuration data"
        ::= { zxGponIPHostVLANTagOperConfigEntry 4 }

--G.984.4 9.3.13 Extended VLAN tagging operation configuration data
    zxGponExVLANTagConfigTable     OBJECT-TYPE
        SYNTAX      SEQUENCE OF ZxGponExVLANTagConfigEntry
        MAX-ACCESS  not-accessible
        STATUS      current
        DESCRIPTION
            "This managed entity organizes data associated with VLAN tagging.
            Regardless of its point of attachment, the specified tagging operations
            refer to the upstream direction. Instances of this managed entity are
            created and deleted by the OLT."
        REFERENCE   "G.984.4 9.3.13 Extended VLAN tagging operation configuration data"
        ::= { zxGponRmL2Mgmt 19 }

    zxGponExVLANTagConfigEntry OBJECT-TYPE
        SYNTAX      ZxGponExVLANTagConfigEntry
        MAX-ACCESS  not-accessible
        STATUS      current
        DESCRIPTION
            "It is entry in the zxGponExVLANTagConfigTable."
        INDEX   { zxGponOltIndex, zxGponONTIndex, zxGponExVlanIfType, zxGponExVlanIndex }
        ::= { zxGponExVLANTagConfigTable 1 }

    ZxGponExVLANTagConfigEntry ::=
        SEQUENCE {
            zxGponExVlanIfType                   INTEGER,
            zxGponExVlanIndex                    INTEGER,
            zxGponExVLANTagConfigInputTPID       INTEGER,
            zxGponExVLANTagConfigOutputTPID      INTEGER,
            zxGponExVLANTagConfigDownStreamMode  INTEGER,
            zxGponExVLANTagConfigEntryStatus     RowStatus,
            zxGponExVLANTagDscp2CosProfile       Integer32
        }

     zxGponExVlanIfType OBJECT-TYPE
        SYNTAX      INTEGER
        MAX-ACCESS  not-accessible
        STATUS      current
        DESCRIPTION
            "This attribute indicates the type of interface.
            1 eth uni bridge port
            2 flow
            3 IP host
            4 eth uni
            5 wifi
            6 veip"
        ::= { zxGponExVLANTagConfigEntry 1}

     zxGponExVlanIndex OBJECT-TYPE
        SYNTAX      INTEGER
        MAX-ACCESS  not-accessible
        STATUS      current
        DESCRIPTION
            "This attribute indicates the type of interface.
            For eth UNI:
            The third byte specifies the slot Id associated with this UNI;the forth byte
            specifies the port Id associated with this UNI.
            For flow:
            The forth byte specifies the flow Id.(4 bytes)
            For IPHostConfigDataId:
            The third and forth bytes provides a unique number for each instance of this managed entity.(4 bytes)"
        ::= { zxGponExVLANTagConfigEntry 2}

    zxGponExVLANTagConfigInputTPID     OBJECT-TYPE
        SYNTAX      INTEGER
        MAX-ACCESS  read-write
        STATUS      current
        DESCRIPTION
        "This attribute gives the special TPID value for operations
        on the input (filtering) side of the table. Typical values
        include 0x8a88 and 0x9100. (R, W) (mandatory) (2 bytes)."
        ::= { zxGponExVLANTagConfigEntry 3 }

    zxGponExVLANTagConfigOutputTPID     OBJECT-TYPE
        SYNTAX      INTEGER
        MAX-ACCESS  read-write
        STATUS      current
        DESCRIPTION
        "This attribute gives the special TPID value for operations
         on the output (tagging) side of the table. Typical values
         include 0x8a88 and 0x9100. (R, W) (mandatory) (2 bytes)."
        ::= { zxGponExVLANTagConfigEntry 4 }

    zxGponExVLANTagConfigDownStreamMode   OBJECT-TYPE
        SYNTAX      INTEGER{
                    inverseUpstream(1),
                    noOperation(2)
                    }
        MAX-ACCESS  read-write
        STATUS      current
        DESCRIPTION
        "Regardless of its association, the extended VLAN tagging
         operation configuration data ME pertains to upstream traffic.
         This attribute specifies the mode for downstream mapping. (R, W) (mandatory) (1 byte)"
        ::= { zxGponExVLANTagConfigEntry 5 }

    zxGponExVLANTagConfigEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponExVLANTagConfigEntry 6 }

    zxGponExVLANTagDscp2CosProfile OBJECT-TYPE
        SYNTAX      Integer32
        MAX-ACCESS  read-write
        STATUS      current
        DESCRIPTION
        "This attribute specifies DSCP to P-bits mapping profile ID."
        ::= { zxGponExVLANTagConfigEntry 7 }


   zxGponExVLANTableConfigTable     OBJECT-TYPE
        SYNTAX      SEQUENCE OF ZxGponExVLANTableConfigEntry
        MAX-ACCESS  not-accessible
        STATUS      current
        DESCRIPTION
            "This managed entity organizes data associated with VLAN tagging.
            Regardless of its point of attachment, the specified tagging operations
            refer to the upstream direction. Instances of this managed entity are
            created and deleted by the OLT."
        REFERENCE   "G.984.4 9.3.13 Extended VLAN tagging operation configuration data"
        ::= { zxGponRmL2Mgmt 20 }

   zxGponExVLANTableConfigEntry OBJECT-TYPE
        SYNTAX      ZxGponExVLANTableConfigEntry
        MAX-ACCESS  not-accessible
        STATUS      current
        DESCRIPTION
            "It is entry in the zxGponUniExVLANTableConfigTable."
        INDEX   { zxGponOltIndex, zxGponONTIndex, zxGponExVlanIfType, zxGponExVlanIndex, zxGponExVlANTableConfigFilterId }
        ::= { zxGponExVLANTableConfigTable 1 }

   ZxGponExVLANTableConfigEntry ::=
        SEQUENCE {
            zxGponExVlANTableConfigFilterId        INTEGER,
            zxGponExVlANTableConfigTreatId         INTEGER,
            zxGponExVLANTableConfigEntryStatus     RowStatus
        }

    zxGponExVlANTableConfigFilterId OBJECT-TYPE
        SYNTAX      INTEGER
        MAX-ACCESS  read-write
        STATUS      current
        DESCRIPTION
        "This attribute provides a unique index of filter for this ExVLAN table.
        (R, Set-by-create) (mandatory) (2 bytes)"
        ::= { zxGponExVLANTableConfigEntry 1 }

    zxGponExVlANTableConfigTreatId OBJECT-TYPE
        SYNTAX      INTEGER
        MAX-ACCESS  read-write
        STATUS      current
        DESCRIPTION
        "This attribute provides a unique index of treatment for this ExVLAN table.
        (R, Set-by-create) (mandatory) (2 bytes)"
        ::= { zxGponExVLANTableConfigEntry 2 }

    zxGponExVLANTableConfigEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponExVLANTableConfigEntry 3 }


    zxGponUNITPInfoTable    OBJECT-TYPE
        SYNTAX      SEQUENCE OF ZxGponUNITPInfoEntry
        MAX-ACCESS  not-accessible
        STATUS      current
        DESCRIPTION
            ""
        REFERENCE   ""
        ::= { zxGponRmL2Mgmt 21 }

    zxGponUNITPInfoEntry OBJECT-TYPE
        SYNTAX      ZxGponUNITPInfoEntry
        MAX-ACCESS  not-accessible
        STATUS      current
        DESCRIPTION
            "It is entry in the zxGponUNITPInfoTable."
        INDEX   { zxGponOltIndex, zxGponONTIndex, zxGponUNIIndex }
        ::= { zxGponUNITPInfoTable 1 }

    ZxGponUNITPInfoEntry ::=
        SEQUENCE {
            zxGponUNITPType                     INTEGER
        }

    zxGponUNITPType OBJECT-TYPE
        SYNTAX      INTEGER{
                    null(1),
                    iwtp(2),
                    mciwtp(3),
                    macbridge(4),
                    dot1p(5),
                    ces(6),
                    vbridge(7)
                    }
        MAX-ACCESS  read-only
        STATUS      current
        DESCRIPTION
        "This attribute indicates the TP type related with this UNI.
        null: no related services;
        iwtp: uni is directly connected with an iwtp;
        mciwtp: uni is directly connected with an multicast iwtp;
        macbridge: uni is connected with a bridge;
        dot1p: uni is connected with an iwtp by 802.1p mapping;
        ces: uni is connected with ces service;
        vbridge: uni is connected with a virtual bridge;
        "
        REFERENCE   ""
        ::= { zxGponUNITPInfoEntry 1 }


--The capability of the ONT(MAX supported bridge/uplink)
    zxGponOntBridgeCapabilityTable    OBJECT-TYPE
        SYNTAX      SEQUENCE OF ZxGponOntBridgeCapabilityEntry
        MAX-ACCESS  not-accessible
        STATUS      current
        DESCRIPTION
            ""
        REFERENCE   ""
        ::= { zxGponRmL2Mgmt 22 }

    zxGponOntBridgeCapabilityEntry OBJECT-TYPE
        SYNTAX      ZxGponOntBridgeCapabilityEntry
        MAX-ACCESS  not-accessible
        STATUS      current
        DESCRIPTION
            "It is entry in the zxGponOntBridgeCapabilityTable."
        INDEX   { zxGponOltIndex, zxGponONTIndex }
        ::= { zxGponOntBridgeCapabilityTable 1 }

    ZxGponOntBridgeCapabilityEntry ::=
        SEQUENCE {
            zxGponOntBridgeCapabilityMaxBridgeNum                     INTEGER,
            zxGponOntBridgeCapabilityMaxFlowNumPerBridge            INTEGER
        }

    zxGponOntBridgeCapabilityMaxBridgeNum OBJECT-TYPE
        SYNTAX      INTEGER
        MAX-ACCESS  read-only
        STATUS      current
        DESCRIPTION
        "This attribute indicates the maximum bridge group num supported on this ONT."
        REFERENCE   ""
        ::= { zxGponOntBridgeCapabilityEntry 1 }

    zxGponOntBridgeCapabilityMaxFlowNumPerBridge OBJECT-TYPE
        SYNTAX      INTEGER
        MAX-ACCESS  read-only
        STATUS      current
        DESCRIPTION
        "This attribute indicates the maximum flow num per bridge supported on this ONT."
        REFERENCE   ""
        ::= { zxGponOntBridgeCapabilityEntry 2 }


--Extended 802.1p mapper service profile
    zxGponFlowExDot1pMapServiceProfileTable    OBJECT-TYPE
        SYNTAX      SEQUENCE OF ZxGponFlowExDot1pMapServiceProfileEntry
        MAX-ACCESS  not-accessible
        STATUS      current
        DESCRIPTION
            "This managed entity is used to associate the priorities of 802.1P priority tagged
            frames of a certain flow with a specific connection."
        REFERENCE   ""
        ::= { zxGponRmL2Mgmt 23 }

    zxGponFlowExDot1pMapServiceProfileEntry OBJECT-TYPE
        SYNTAX      ZxGponFlowExDot1pMapServiceProfileEntry
        MAX-ACCESS  not-accessible
        STATUS      current
        DESCRIPTION
            "It is entry in the zxGponFlowExDot1pMapServiceProfileTable."
        INDEX   { zxGponOltIndex, zxGponONTIndex, zxGponFlowIndex }
        ::= { zxGponFlowExDot1pMapServiceProfileTable 1 }

    ZxGponFlowExDot1pMapServiceProfileEntry ::=
        SEQUENCE {
            zxGponFlowExDot1pMapServiceProfilePrio0QueueId          INTEGER,
            zxGponFlowExDot1pMapServiceProfilePrio1QueueId          INTEGER,
            zxGponFlowExDot1pMapServiceProfilePrio2QueueId          INTEGER,
            zxGponFlowExDot1pMapServiceProfilePrio3QueueId          INTEGER,
            zxGponFlowExDot1pMapServiceProfilePrio4QueueId          INTEGER,
            zxGponFlowExDot1pMapServiceProfilePrio5QueueId          INTEGER,
            zxGponFlowExDot1pMapServiceProfilePrio6QueueId          INTEGER,
            zxGponFlowExDot1pMapServiceProfilePrio7QueueId          INTEGER
        }

    zxGponFlowExDot1pMapServiceProfilePrio0QueueId OBJECT-TYPE
        SYNTAX      INTEGER
        MAX-ACCESS  read-write
        STATUS      current
        DESCRIPTION
        "This attribute represents the upstream queue id that is
        associated with P-Bit = 000 tagged frames. The value 0x0000 is a null pointer.(2 bytes)"
        REFERENCE   ""
        ::= { zxGponFlowExDot1pMapServiceProfileEntry 1 }

    zxGponFlowExDot1pMapServiceProfilePrio1QueueId OBJECT-TYPE
        SYNTAX      INTEGER
        MAX-ACCESS  read-write
        STATUS      current
        DESCRIPTION
        "This attribute represents the upstream queue id that is
        associated with P-Bit = 001 tagged frames. The value 0x0000 is a null pointer.(2 bytes)"
        REFERENCE   ""
        ::= { zxGponFlowExDot1pMapServiceProfileEntry 2 }

    zxGponFlowExDot1pMapServiceProfilePrio2QueueId OBJECT-TYPE
        SYNTAX      INTEGER
        MAX-ACCESS  read-write
        STATUS      current
        DESCRIPTION
        "This attribute represents the upstream queue id that is
        associated with P-Bit = 010 tagged frames. The value 0x0000 is a null pointer.(2 bytes)"
        REFERENCE   ""
        ::= { zxGponFlowExDot1pMapServiceProfileEntry 3 }

    zxGponFlowExDot1pMapServiceProfilePrio3QueueId OBJECT-TYPE
        SYNTAX      INTEGER
        MAX-ACCESS  read-write
        STATUS      current
        DESCRIPTION
        "This attribute represents the upstream queue id that is
        associated with P-Bit = 011 tagged frames. The value 0x0000 is a null pointer.(2 bytes)"
        REFERENCE   ""
        ::= { zxGponFlowExDot1pMapServiceProfileEntry 4 }

    zxGponFlowExDot1pMapServiceProfilePrio4QueueId OBJECT-TYPE
        SYNTAX      INTEGER
        MAX-ACCESS  read-write
        STATUS      current
        DESCRIPTION
        "This attribute represents the upstream queue id that is
        associated with P-Bit = 100 tagged frames. The value 0x0000 is a null pointer.(2 bytes)"
        REFERENCE   ""
        ::= { zxGponFlowExDot1pMapServiceProfileEntry 5 }

    zxGponFlowExDot1pMapServiceProfilePrio5QueueId OBJECT-TYPE
        SYNTAX      INTEGER
        MAX-ACCESS  read-write
        STATUS      current
        DESCRIPTION
        "This attribute represents the upstream queue id that is
        associated with P-Bit = 101 tagged frames. The value 0x0000 is a null pointer.(2 bytes)"
        REFERENCE   ""
        ::= { zxGponFlowExDot1pMapServiceProfileEntry 6 }

    zxGponFlowExDot1pMapServiceProfilePrio6QueueId OBJECT-TYPE
        SYNTAX      INTEGER
        MAX-ACCESS  read-write
        STATUS      current
        DESCRIPTION
        "This attribute represents the upstream queue id that is
        associated with P-Bit = 110 tagged frames. The value 0x0000 is a null pointer.(2 bytes)"
        REFERENCE   ""
        ::= { zxGponFlowExDot1pMapServiceProfileEntry 7 }

    zxGponFlowExDot1pMapServiceProfilePrio7QueueId OBJECT-TYPE
        SYNTAX      INTEGER
        MAX-ACCESS  read-write
        STATUS      current
        DESCRIPTION
        "This attribute represents the upstream queue id that is
        associated with P-Bit = 111 tagged frames. The value 0x0000 is a null pointer.(2 bytes)"
        REFERENCE   ""
        ::= { zxGponFlowExDot1pMapServiceProfileEntry 8 }

--Multicast Vlan Configuratio
    zxGponMCastVlanTable    OBJECT-TYPE
        SYNTAX      SEQUENCE OF ZxGponMCastVlanEntry
        MAX-ACCESS  not-accessible
        STATUS      current
        DESCRIPTION
            "This managed entity is used to configure the vlan of multicast."
        REFERENCE   ""
        ::= { zxGponRmL2Mgmt 24 }

    zxGponMCastVlanEntry OBJECT-TYPE
        SYNTAX      ZxGponMCastVlanEntry
        MAX-ACCESS  not-accessible
        STATUS      current
        DESCRIPTION
            "It is entry in the zxGponMCastVlanTable."
        INDEX   { zxGponOltIndex, zxGponONTIndex, zxGponMCastVlanId }
        ::= { zxGponMCastVlanTable 1 }

    ZxGponMCastVlanEntry ::=
        SEQUENCE {
            zxGponMCastVlanId                   INTEGER,
            zxGponMCastVlanEntryStatus          RowStatus
        }

    zxGponMCastVlanId OBJECT-TYPE
        SYNTAX      INTEGER(1..4094)
        MAX-ACCESS  not-accessible
        STATUS      current
        DESCRIPTION
        "This attribute represents the vlan id(1~4094) as the index."
        REFERENCE   ""
        ::= { zxGponMCastVlanEntry 1 }

    zxGponMCastVlanEntryStatus OBJECT-TYPE
        SYNTAX      RowStatus
        MAX-ACCESS  read-write
        STATUS      current
        DESCRIPTION
        "This attribute represents the operation of the entry."
        REFERENCE   ""
        ::= { zxGponMCastVlanEntry 2 }

--Multicast Address Configuratio
    zxGponMCastAddrTable    OBJECT-TYPE
        SYNTAX      SEQUENCE OF ZxGponMCastAddrEntry
        MAX-ACCESS  not-accessible
        STATUS      current
        DESCRIPTION
            "This managed entity is used to configure the address of multicast."
        REFERENCE   ""
        ::= { zxGponRmL2Mgmt 25 }

    zxGponMCastAddrEntry OBJECT-TYPE
        SYNTAX      ZxGponMCastAddrEntry
        MAX-ACCESS  not-accessible
        STATUS      current
        DESCRIPTION
            "It is entry in the zxGponMCastAddrTable."
        INDEX   { zxGponOltIndex, zxGponONTIndex, zxGponMCastAddr }
        ::= { zxGponMCastAddrTable 1 }

    ZxGponMCastAddrEntry ::=
        SEQUENCE {
            zxGponMCastAddr                   MacAddress,
            zxGponMCastAddrEntryStatus        RowStatus
        }

    zxGponMCastAddr OBJECT-TYPE
        SYNTAX      MacAddress
        MAX-ACCESS  not-accessible
        STATUS      current
        DESCRIPTION
        "This attribute represents the address(01:00:5e:00:00:00~01:00:5e:7f:ff:ff) as the index."
        REFERENCE   ""
        ::= { zxGponMCastAddrEntry 1 }

    zxGponMCastAddrEntryStatus OBJECT-TYPE
        SYNTAX      RowStatus
        MAX-ACCESS  read-write
        STATUS      current
        DESCRIPTION
        "This attribute represents the operation of the entry."
        REFERENCE   ""
        ::= { zxGponMCastAddrEntry 2 }

--Traffic scheduler-UNI
    zxGponTrafficSchedulerUNITable    OBJECT-TYPE
        SYNTAX      SEQUENCE OF ZxGponTrafficSchedulerUNIEntry
        MAX-ACCESS  not-accessible
        STATUS      current
        DESCRIPTION
            "This managed entity is used to configure the Traffic Scheduler of ETHUNI."
        REFERENCE   ""
        ::= { zxGponRmL2Mgmt 26 }

    zxGponTrafficSchedulerUNIEntry OBJECT-TYPE
        SYNTAX      ZxGponTrafficSchedulerUNIEntry
        MAX-ACCESS  not-accessible
        STATUS      current
        DESCRIPTION
            "It is entry in the zxGponTrafficSchedulerUNITable."
        INDEX   { zxGponOltIndex, zxGponONTIndex, zxGponUNIIndex }
        ::= { zxGponTrafficSchedulerUNITable 1 }

    ZxGponTrafficSchedulerUNIEntry ::=
        SEQUENCE {
            zxGponTrafficSchedulerUNIProfilePtr         INTEGER
        }

    zxGponTrafficSchedulerUNIProfilePtr OBJECT-TYPE
        SYNTAX      INTEGER
        MAX-ACCESS  read-write
        STATUS      current
        DESCRIPTION
        "This attribute refers to the Traffic Scheduler Profile related with this UNI."
        REFERENCE   ""
        ::= { zxGponTrafficSchedulerUNIEntry 1 }

--Y.1731 CFM
    zxGponCfmMepTable    OBJECT-TYPE
        SYNTAX      SEQUENCE OF ZxGponCfmMepEntry
        MAX-ACCESS  not-accessible
        STATUS      current
        DESCRIPTION
            "This managed entity is used to configure the Y.1731 CFM MEP."
        REFERENCE   ""
        ::= { zxGponRmL2Mgmt 27 }

    zxGponCfmMepEntry OBJECT-TYPE
        SYNTAX      ZxGponCfmMepEntry
        MAX-ACCESS  not-accessible
        STATUS      current
        DESCRIPTION
            "It is entry in the zxGponCfmMepTable."
        INDEX   { zxGponOltIndex, zxGponONTIndex, zxGponUNIIndex }
        ::= { zxGponCfmMepTable 1 }

    ZxGponCfmMepEntry ::=
        SEQUENCE {
            zxGponCfmMepMEPID                INTEGER,
            zxGponCfmMepMDName               OCTET STRING,
            zxGponCfmMepMDLevel              INTEGER,
            zxGponCfmMepMAName               OCTET STRING,
            zxGponCfmMepMACCMInterval        INTEGER,
            zxGponCfmMepMAAssociatedVLAN     OCTET STRING,
            zxGponCfmMepCCMEnable            TruthValue,
            zxGponCfmMepServerFuncEnable     TruthValue,
            zxGponCfmMepAISEnable            TruthValue,
            zxGponCfmMepDirection            INTEGER,
            zxGponCfmMepAdminState           INTEGER,
            zxGponCfmMepPriority             INTEGER,
            zxGponCfmMepPeerMEPID            INTEGER,
            zxGponCfmMepPeerMEPMAC           MacAddress,
            zxGponCfmMepEntryStatus          RowStatus
        }

    zxGponCfmMepMEPID OBJECT-TYPE
        SYNTAX      INTEGER(1..8191)
        MAX-ACCESS  read-write
        STATUS      current
        DESCRIPTION
        "This attribute specifies the MEP's own identity in the MA.
        For a given MA, the MEP ID must be unique throughout the network defined by the MD.
        The MEP ID is defined in the range 1..8191. The default value 0 indicates that no MEP ID is (yet) configured.
        (R, W, Set-by-create) (mandatory) (2 bytes)"
        REFERENCE   "G.984.4"
        ::= { zxGponCfmMepEntry 1 }

    zxGponCfmMepMDName OBJECT-TYPE
        SYNTAX      OCTET STRING(SIZE(1..13))
        MAX-ACCESS  read-write
        STATUS      current
        DESCRIPTION
        "This attribute specifies the name of MD which MEP belongs to."
        REFERENCE   "G.984.4"
        ::= { zxGponCfmMepEntry 2 }

    zxGponCfmMepMDLevel OBJECT-TYPE
        SYNTAX      INTEGER(0..7)
        MAX-ACCESS  read-write
        STATUS      current
        DESCRIPTION
        "This attribute ranges from 0..7 and specifies the maintenance level of this MD.
        Higher numbers have wider geographic scope."
        REFERENCE   "G.984.4"
        ::= { zxGponCfmMepEntry 3 }

    zxGponCfmMepMAName OBJECT-TYPE
        SYNTAX      OCTET STRING(SIZE(1..45))
        MAX-ACCESS  read-write
        STATUS      current
        DESCRIPTION
        "This attribute specifies the name of MA which MEP belongs to."
        REFERENCE   "G.984.4"
        ::= { zxGponCfmMepEntry 4 }

    zxGponCfmMepMACCMInterval OBJECT-TYPE
        SYNTAX      INTEGER{
                    disable(1),
                    t-3-33ms(2),
                    t-10ms(3),
                    t-100ms(4),
                    t-1s(5),
                    t-10s(6),
                    t-1min(7),
                    t-10min(8)
                    }
        MAX-ACCESS  read-write
        STATUS      current
        DESCRIPTION
        "If CCMs are enabled on a MEP, the CCM interval attribute specifies the rate at which they are generated.
        The MEP also expects to receive CCMs from each of the other MEPs in its CC database at this rate"
        REFERENCE   "G.984.4"
        ::= { zxGponCfmMepEntry 5 }

    zxGponCfmMepMAAssociatedVLAN OBJECT-TYPE
        SYNTAX      OCTET STRING(SIZE(24))
        MAX-ACCESS  read-write
        STATUS      current
        DESCRIPTION
        "This attribute is a list of up to 12 VLAN IDs with which this MA is associated.
        Once a set of VLANs is defined, the ONT should deny operations to other dot1ag maintenance associations
        or dot1ag default MD level entries that conflict with the set membership.
        The all-zeros value indicates that this MA is not associated with any VLANs.
        Assuming that the attribute is not 0, the first entry is understood to be the primary VLAN.
        Except forwarded LTMs, CFM messages emitted by maintenance points in this MA are tagged with the primary VLAN ID."
        REFERENCE   "G.984.4"
        ::= { zxGponCfmMepEntry 6 }

    zxGponCfmMepCCMEnable OBJECT-TYPE
        SYNTAX      TruthValue
        MAX-ACCESS  read-write
        STATUS      current
        DESCRIPTION
        "MEP generates continuity check messages, CCMs"
        REFERENCE   "G.984.4"
        ::= { zxGponCfmMepEntry 7 }

    zxGponCfmMepServerFuncEnable OBJECT-TYPE
        SYNTAX      TruthValue
        MAX-ACCESS  read-write
        STATUS      current
        DESCRIPTION
        "Enable Y.1731 server MEP function"
        REFERENCE   "G.984.4"
        ::= { zxGponCfmMepEntry 8 }

    zxGponCfmMepAISEnable OBJECT-TYPE
        SYNTAX      TruthValue
        MAX-ACCESS  read-write
        STATUS      current
        DESCRIPTION
        "Enable generation of Ethernet AIS"
        REFERENCE   "G.984.4"
        ::= { zxGponCfmMepEntry 9 }

    zxGponCfmMepDirection OBJECT-TYPE
        SYNTAX      INTEGER{
                    up(1),
                    down(2)
                    }
        MAX-ACCESS  read-write
        STATUS      current
        DESCRIPTION
        "An up MEP will face toward the core of the bridge.
        If more than one MEP exists on a given maintenance association and on a given bridge,
        all such MEPs must face the same direction."
        REFERENCE   "G.984.4"
        ::= { zxGponCfmMepEntry 10 }

    zxGponCfmMepAdminState OBJECT-TYPE
        SYNTAX      INTEGER{
                    unlock(1),
                    lock(2)
                    }
        MAX-ACCESS  read-write
        STATUS      current
        DESCRIPTION
        "This attribute locks (1) and unlocks (0) the functions performed by this managed entity.
        When the administrative state is set to lock, all functions are blocked, and alarms for
        this managed entity are no longer generated. Because spurious alarms may be generated during
        the process of configuring CFM across a network, the default value for this attribute is locked. "
        REFERENCE   "G.984.4"
        ::= { zxGponCfmMepEntry 11 }

    zxGponCfmMepPriority OBJECT-TYPE
        SYNTAX      INTEGER(0..7)
        MAX-ACCESS  read-write
        STATUS      current
        DESCRIPTION
        "By default, CCM and LTM frames are transmitted with the highest Ethernet priority available.
        Ranging from 0..7, this attribute permits these frames to be explicitly prioritized,
        which may be needed if flows are separated eg by 802.1p priority.
        The priority specified in this attribute is also used in LTR frames originated by this MEP. "
        REFERENCE   "G.984.4"
        ::= { zxGponCfmMepEntry 12 }

    zxGponCfmMepPeerMEPID OBJECT-TYPE
        SYNTAX      INTEGER(0..8191)
        MAX-ACCESS  read-write
        STATUS      current
        DESCRIPTION
        "Peer MEP ID."
        REFERENCE   "G.984.4"
        ::= { zxGponCfmMepEntry 13 }

    zxGponCfmMepPeerMEPMAC OBJECT-TYPE
        SYNTAX      MacAddress
        MAX-ACCESS  read-write
        STATUS      current
        DESCRIPTION
        "Peer MEP ID."
        REFERENCE   "G.984.4"
        ::= { zxGponCfmMepEntry 14 }

    zxGponCfmMepEntryStatus OBJECT-TYPE
        SYNTAX      RowStatus
        MAX-ACCESS  read-write
        STATUS      current
        DESCRIPTION
        ""
        REFERENCE   "G.984.4"
        ::= { zxGponCfmMepEntry 15 }

    zxGponBridgePortAddrListTable    OBJECT-TYPE
        SYNTAX      SEQUENCE OF ZxGponBridgePortAddrListEntry
        MAX-ACCESS  not-accessible
        STATUS      current
        DESCRIPTION
            ""
        REFERENCE   "G.984.4 MAC Bridge Port bridge table Data"
        ::= { zxGponRmL2Mgmt 28 }

    zxGponBridgePortAddrListEntry OBJECT-TYPE
        SYNTAX      ZxGponBridgePortAddrListEntry
        MAX-ACCESS  not-accessible
        STATUS      current
        DESCRIPTION
            "It is entry in the zxGponBridgePortAddrListTable."
        INDEX   { zxGponOltIndex, zxGponONTIndex, zxGponBridgePortType, zxGponBridgePortIndex, zxGponBridgePortAddrListIndex }
        ::= { zxGponBridgePortAddrListTable 1 }

    ZxGponBridgePortAddrListEntry ::=
        SEQUENCE {
            zxGponBridgePortAddrListIndex                 INTEGER,
            zxGponBridgePortAddrListTotalNum              INTEGER,
            zxGponBridgePortAddrListCurrentNum            INTEGER,
            zxGponBridgePortAddrListData                  OCTET STRING
        }

    zxGponBridgePortAddrListIndex OBJECT-TYPE
        SYNTAX      INTEGER
        MAX-ACCESS  not-accessible
        STATUS      current
        DESCRIPTION
        "Index for getnext."
        REFERENCE   "G.984.4 MAC Bridge Port bridge table Data"
        ::= { zxGponBridgePortAddrListEntry 1 }

    zxGponBridgePortAddrListTotalNum OBJECT-TYPE
        SYNTAX      INTEGER
        MAX-ACCESS  read-only
        STATUS      current
        DESCRIPTION
        "Total number of addresses entries related with this port."
        REFERENCE   "G.984.4 MAC Bridge Port bridge table Data"
        ::= { zxGponBridgePortAddrListEntry 2 }

    zxGponBridgePortAddrListCurrentNum OBJECT-TYPE
        SYNTAX      INTEGER
        MAX-ACCESS  read-only
        STATUS      current
        DESCRIPTION
        "The number of addresses entries by current getnext."
        REFERENCE   "G.984.4 MAC Bridge Port bridge table Data"
        ::= { zxGponBridgePortAddrListEntry 3 }

    zxGponBridgePortAddrListData OBJECT-TYPE
        SYNTAX      OCTET STRING(SIZE(32))
        MAX-ACCESS  read-only
        STATUS      current
        DESCRIPTION
        "This attribute identifies the MAC addresses learned by this bridge port.
         The first N*8 bytes is valid, N is determined by zxGponBridgePortAddrListCurrentNum.
         Each 8 bytes contain:
         - Information (2 bytes)
         - MAC address (6 bytes)
         The information bits are assigned as described below.
           Bit      Name              Setting
           1      Filter/forward    0: forward
                                1: filter
           2      Reserved            0
           3      Dynamic/static    0: this entry is statically assigned
                                1: this entry is dynamically learned
           4      Reserved            0
           16..5  Age                    Age in seconds (1..4095)
         "
        REFERENCE   "G.984.4 MAC Bridge Port bridge table Data"
        ::= { zxGponBridgePortAddrListEntry 4 }

    --IGMP Cfg
    zxGponUniIgmpCfgTable    OBJECT-TYPE
        SYNTAX      SEQUENCE OF ZxGponUniIgmpCfgEntry
        MAX-ACCESS  not-accessible
        STATUS      current
        DESCRIPTION
            "This managed entity organizes data associated with multicast
            management at subscriber ports of 802.1 bridges, including 802.1p
            mappers when the provisioning model is mapper-based rather than
            bridge-based.
            Instances of this managed entity are created and deleted by the
            OLT.
            The index 'zxGponUNIIndex' of this table supports
            Ethernet UNI, and VEIP."
        REFERENCE   "G.984.4 9.3.28 Multicast subscriber config info"
        ::= { zxGponRmL2Mgmt 29 }

    zxGponUniIgmpCfgEntry OBJECT-TYPE
        SYNTAX      ZxGponUniIgmpCfgEntry
        MAX-ACCESS  not-accessible
        STATUS      current
        DESCRIPTION
            "It is entry in the zxGponUNIIgmpCfgTable."
        INDEX   { zxGponOltIndex, zxGponONTIndex, zxGponUNIIndex }
        ::= { zxGponUniIgmpCfgTable 1 }

    ZxGponUniIgmpCfgEntry ::=
        SEQUENCE {
            zxGponUniIgmpProfileId               Integer32,
            zxGponUniIgmpMaxGroups               INTEGER,
            zxGponUniIgmpMaxBandwidth            Integer32,
            zxGponUniIgmpBandwidthEnforce        TruthValue,
            zxGponUniIgmpCfgRowStatus            RowStatus
        }

    zxGponUniIgmpProfileId OBJECT-TYPE
        SYNTAX      Integer32
        MAX-ACCESS  read-create
        STATUS      current
        DESCRIPTION
            "This attribute points to an instance of the multicast operations
            profile."
        ::= { zxGponUniIgmpCfgEntry 1 }

    zxGponUniIgmpMaxGroups OBJECT-TYPE
        SYNTAX      INTEGER(0..1000)
        MAX-ACCESS  read-create
        STATUS      current
        DESCRIPTION
            "This attribute specifies the maximum number of dynamic multicast
             groups that may be replicated to the client port at any one time.
             The default value 0 specifies that no administrative limit is to
             be imposed.
            "
        DEFVAL { 0 }
        ::= { zxGponUniIgmpCfgEntry 2 }

    zxGponUniIgmpMaxBandwidth OBJECT-TYPE
        SYNTAX      Integer32
        UNITS       "kbps"
        MAX-ACCESS  read-create
        STATUS      current
        DESCRIPTION
            "This attribute specifies the maximum imputed dynamic bandwidth,
             in kb per second, that may be delivered to the client port at
             any one time.
             The default value 0 specifies that no administrative limit is to
             be imposed. "
        DEFVAL { 0 }
        ::= { zxGponUniIgmpCfgEntry 3 }

    zxGponUniIgmpBandwidthEnforce OBJECT-TYPE
        SYNTAX      TruthValue
        MAX-ACCESS  read-create
        STATUS      current
        DESCRIPTION
            "The default value of this boolean attribute is false,
             and specifies that attempts to exceed the max multicast bandwidth
             be counted but honored. The value true specifies that such
             attempts be counted and denied."
        DEFVAL { false }
        ::= { zxGponUniIgmpCfgEntry 4 }

    zxGponUniIgmpCfgRowStatus OBJECT-TYPE
        SYNTAX      RowStatus
        MAX-ACCESS  read-create
        STATUS      current
        DESCRIPTION
            "This attribute provides the number of entries in the IGMP Config
            Table that are valid."
        REFERENCE   "G.984.4 9.3.28 Multicast subscriber config info"
        ::= { zxGponUniIgmpCfgEntry 31 }


    --Uni MVlan Cfg

    zxGponUniMVlanTagCfgTable    OBJECT-TYPE
        SYNTAX      SEQUENCE OF ZxGponUniMVlanTagCfgEntry
        MAX-ACCESS  not-accessible
        STATUS      current
        DESCRIPTION
            "This managed entity organizes data associated with multicast
            management at uni ports of onu."
        ::= { zxGponRmL2Mgmt 30 }

    zxGponUniMVlanTagCfgEntry OBJECT-TYPE
        SYNTAX      ZxGponUniMVlanTagCfgEntry
        MAX-ACCESS  not-accessible
        STATUS      current
        DESCRIPTION
            "It is entry in the zxGponUniMVlanTagCfgTable."
        INDEX   { zxGponOltIndex, zxGponONTIndex, zxGponUNIIndex }
        ::= { zxGponUniMVlanTagCfgTable 1 }

    ZxGponUniMVlanTagCfgEntry ::=
        SEQUENCE {
            zxGponUniMVlanTagMode            INTEGER
        }

    zxGponUniMVlanTagMode OBJECT-TYPE
        SYNTAX     INTEGER{
                   stripped(1),
                   notStripped(2),
                   translated(3)
                   }
        MAX-ACCESS  read-write
        STATUS      current
        DESCRIPTION
            "This attribute specifies the multicast VLAN tag mode."
        ::= { zxGponUniMVlanTagCfgEntry 1 }

    --Uni MVlan Translte

    zxAnGponUniMVlanTranslateTable  OBJECT-TYPE
            SYNTAX      SEQUENCE OF ZxAnGponUniMVlanTranslateEntry
            MAX-ACCESS  not-accessible
            STATUS      current
            DESCRIPTION
                "A table entry containing ONU UNI multicast VLAN
                    translation  information."
            ::= { zxGponRmL2Mgmt 33 }

    zxAnGponUniMVlanTranslateEntry  OBJECT-TYPE
            SYNTAX      ZxAnGponUniMVlanTranslateEntry
            MAX-ACCESS  not-accessible
            STATUS      current
            DESCRIPTION
                "GPON ONU multicast VLAN translation entry."
            INDEX    { zxGponOltIndex, zxGponONTIndex, zxGponUNIIndex,
                       zxAnGponUniMVlan }
            ::= {zxAnGponUniMVlanTranslateTable 1}

    ZxAnGponUniMVlanTranslateEntry ::=
            SEQUENCE {
                zxAnGponUniMVlan                   INTEGER,
                zxAnGponUniTranslatedMVlan            INTEGER,
                zxAnGponUniMVlanTransRowStatus     RowStatus
                }

    zxAnGponUniMVlan  OBJECT-TYPE
            SYNTAX      INTEGER(1..4094)
            MAX-ACCESS  not-accessible
            STATUS      current
            DESCRIPTION
                 "Multicast VLAN."
            ::= { zxAnGponUniMVlanTranslateEntry 1 }

    zxAnGponUniTranslatedMVlan  OBJECT-TYPE
            SYNTAX      INTEGER(1..4094)
            MAX-ACCESS  read-create
            STATUS      current
            DESCRIPTION
                 "Translated multicast VLAN."
            ::= { zxAnGponUniMVlanTranslateEntry 2 }

    zxAnGponUniMVlanTransRowStatus  OBJECT-TYPE
            SYNTAX      RowStatus
            MAX-ACCESS  read-create
            STATUS      current
            DESCRIPTION
                 "The row status of this entry."
            ::= { zxAnGponUniMVlanTranslateEntry 20 }


--IGMP Monitor
    zxGponUniIgmpMonitorTable    OBJECT-TYPE
        SYNTAX      SEQUENCE OF ZxGponUniIgmpMonitorEntry
        MAX-ACCESS  not-accessible
        STATUS      current
        DESCRIPTION
            "This managed entity provides the current status of each
            port with respect to its multicast subscriptions. It may
            be useful for status monitoring or debugging purposes.
            The status table includes all groups currently subscribed
            by the port, both dynamic and static.
            The index 'zxGponUNIIndex' of this table supports
            Ethernet UNI, and VEIP."
        REFERENCE   "G.984.4 9.3.29 Multicast subscriber monitor"
        ::= { zxGponRmL2Mgmt 31 }

    zxGponUniIgmpMonitorEntry OBJECT-TYPE
        SYNTAX      ZxGponUniIgmpMonitorEntry
        MAX-ACCESS  not-accessible
        STATUS      current
        DESCRIPTION
            "It is entry in the zxGponUniIgmpMonitorTable."
        INDEX   { zxGponOltIndex, zxGponONTIndex, zxGponUNIIndex }
        ::= { zxGponUniIgmpMonitorTable 1 }

    ZxGponUniIgmpMonitorEntry ::=
        SEQUENCE {
            zxGponUniIgmpMonitorCurrBw              Integer32,
            zxGponUniIgmpMonitorJoinCnt             Counter32,
            zxGponUniIgmpMonitorExceededCnt         Counter32,
            zxGponUniIgmpMonitorRowStatus           RowStatus
        }

    zxGponUniIgmpMonitorCurrBw OBJECT-TYPE
        SYNTAX      Integer32
        UNITS       "kbps"
        MAX-ACCESS  read-only
        STATUS      current
        DESCRIPTION
            "This attribute is the ONT's best effort estimate of the
            actual bandwidth currently being delivered over all dynamic
            multicast groups. "
        ::= { zxGponUniIgmpMonitorEntry 1 }

    zxGponUniIgmpMonitorJoinCnt OBJECT-TYPE
        SYNTAX      Counter32
        MAX-ACCESS  read-only
        STATUS      current
        DESCRIPTION
            "This attribute counts the number of times the corresponding
            subscriber sent a join message that was accepted. When full,
            the counter rolls over to 0."
        ::= { zxGponUniIgmpMonitorEntry 2 }

    zxGponUniIgmpMonitorExceededCnt OBJECT-TYPE
        SYNTAX      Counter32
        MAX-ACCESS  read-only
        STATUS      current
        DESCRIPTION
            "This attribute counts the number of join messages that did,
            or would have, exceeded the max multicast bandwidth, whether
            accepted or denied. When full, the counter rolls over to 0."
        ::= { zxGponUniIgmpMonitorEntry 3 }

    zxGponUniIgmpMonitorRowStatus OBJECT-TYPE
        SYNTAX      RowStatus
        MAX-ACCESS  read-create
        STATUS      current
        DESCRIPTION
            "rowstatus"
        ::= { zxGponUniIgmpMonitorEntry 31 }

--IGMP Monitor Dynamic Groups
    zxGponUniIgmpDynGroupTable    OBJECT-TYPE
        SYNTAX      SEQUENCE OF ZxGponUniIgmpDynGroupEntry
        MAX-ACCESS  not-accessible
        STATUS      current
        DESCRIPTION
            "This table lists the groups from the dynamic access control list
             that are currently being actively forwarded, along with the actual
             bandwidth of each.
             The index 'zxGponUNIIndex' of this table supports Ethernet UNI,
             and VEIP."
        REFERENCE   "G.984.4 9.3.29 Multicast subscriber monitor"
        ::= { zxGponRmL2Mgmt 32 }

    zxGponUniIgmpDynGroupEntry OBJECT-TYPE
        SYNTAX      ZxGponUniIgmpDynGroupEntry
        MAX-ACCESS  not-accessible
        STATUS      current
        DESCRIPTION
            "It is entry in the zxGponUniIgmpDynGroupTable."
        INDEX   { zxGponOltIndex, zxGponONTIndex, zxGponUNIIndex,
        zxGponUniIgmpDynGroupIndex }
        ::= { zxGponUniIgmpDynGroupTable 1 }

    ZxGponUniIgmpDynGroupEntry ::=
        SEQUENCE {
            zxGponUniIgmpDynGroupIndex           Integer32,
            zxGponUniIgmpDynGroupTotalNum        Integer32,
            zxGponUniIgmpDynGroupData            OCTET STRING
        }

    zxGponUniIgmpDynGroupIndex OBJECT-TYPE
        SYNTAX      Integer32
        MAX-ACCESS  not-accessible
        STATUS      current
        DESCRIPTION
            "Index of IGMP dynamic group."
        ::= { zxGponUniIgmpDynGroupEntry 1 }

    zxGponUniIgmpDynGroupTotalNum OBJECT-TYPE
        SYNTAX      Integer32
        MAX-ACCESS  read-only
        STATUS      current
        DESCRIPTION
            "Total number of group entries related with this port."
        ::= { zxGponUniIgmpDynGroupEntry 2 }

    zxGponUniIgmpDynGroupData OBJECT-TYPE
        SYNTAX      OCTET STRING(SIZE(24))
        MAX-ACCESS  read-only
        STATUS      current
        DESCRIPTION
            "This attribute identifies the dynamic group that is currently being
             actively forwarded.Each 24 bytes contain:
             - VLAN ID, 0 if not used (2 bytes)
             - Source IP address, 0.0.0.0 if not used (4 bytes)
             - Multicast destination IP address (4 bytes)
             - Best efforts actual bandwidth estimate, bytes per second(4 bytes)
             - Client (set-top box) IP address, that is, the IP address of the
               device currently joined (4 bytes)
             - Time since the most recent join of this client to the IP channel,
             in seconds (4 bytes).
             - Reserved (2 bytes)
            "
        ::= { zxGponUniIgmpDynGroupEntry 3 }

--Extend VLAN begin
   zxGponExtendedVlanMgmtObject    OBJECT IDENTIFIER ::= { zxGponRmL2Mgmt 100}

   --  Extended VLAN:zxGponVlanPortTable
    zxGponVlanPortTable OBJECT-TYPE
        SYNTAX      SEQUENCE OF ZxGponVlanPortEntry
        MAX-ACCESS  not-accessible
        STATUS      current
        DESCRIPTION
            "A table containing VLAN Port information for VLANs
            configured into the bridge by (local or network)
            management,  specifying the set of
            ports to which frames received on a VLAN for this FDB
            and containing a specific Group destination address are
            allowed to be forwarded."
        ::= { zxGponExtendedVlanMgmtObject 1 }

    zxGponVlanPortEntry OBJECT-TYPE
        SYNTAX      ZxGponVlanPortEntry
        MAX-ACCESS  not-accessible
        STATUS      current
        DESCRIPTION
            "Filtering information configured into the bridge by
            management, specifying the set of
            ports to which frames received on a VLAN and containing
            a specific Group destination address, are allowed to be
            forwarded.  "
        INDEX   { zxGponOltIndex, zxGponONTIndex, zxGponVlanPortType,zxGponVlanPortIndex }
        ::= { zxGponVlanPortTable 1 }

    ZxGponVlanPortEntry ::= SEQUENCE {
            zxGponVlanPortType                INTEGER,
            zxGponVlanPortIndex               INTEGER,
            zxGponVlanPortMode                INTEGER,
            zxGponVlanPortPvid                INTEGER,
            zxGponVlanPortDefaultPriority     INTEGER,
            zxGponVlanPortUntaggedVlanList    DisplayString,
            zxGponVlanPortTaggedVlanList      DisplayString
        }
    zxGponVlanPortType OBJECT-TYPE
        SYNTAX      INTEGER
             {
                 ethuni(1),
                 gemportUnicast(2),
                 gemportMulticast(3),
                 wifi(4),
                 veip(5),
                 wan(6)
             }
        MAX-ACCESS  not-accessible
        STATUS      current
        DESCRIPTION
            "This attribute indicates the type of port."
        ::= { zxGponVlanPortEntry 1 }

    zxGponVlanPortIndex OBJECT-TYPE
        SYNTAX      INTEGER
        MAX-ACCESS  not-accessible
        STATUS      current
        DESCRIPTION
            "This attribute indicates the port index.
            For ETH UNI:
            The third byte specifies the slot ID associated with this UNI;
            the forth byte specifies the port ID associated with this UNI.
            For GEM port unicast:
            The index specifies the GEM port Id.
            For GEM port multicast:
            The index specifies the multicast GEM port ID which should be 1.
            For WIFI:
            The third byte specifies the slot ID associated with this UNI;
            the forth byte specifies the port ID associated with this UNI.
            For VEIP:
            The index specifies the port ID associated with VEIP."
        ::= { zxGponVlanPortEntry 2 }

    zxGponVlanPortMode OBJECT-TYPE
        SYNTAX   INTEGER {
                 tag(1),
                 trunk(2),
                 hybrid(3),
                 transparent(4)
                 }
        MAX-ACCESS  read-write
        STATUS      current
        DESCRIPTION
            "the access mode of the port."
        ::= { zxGponVlanPortEntry 3 }

    zxGponVlanPortPvid OBJECT-TYPE
        SYNTAX      INTEGER(1..4094)
        MAX-ACCESS  read-write
        STATUS      current
        DESCRIPTION
            "the pvid of the port."
        ::= { zxGponVlanPortEntry 4 }

    zxGponVlanPortDefaultPriority OBJECT-TYPE
        SYNTAX      INTEGER(0..7)
        MAX-ACCESS  read-write
        STATUS      current
        DESCRIPTION
            "the default priority of the port."
        ::= { zxGponVlanPortEntry 5 }

    zxGponVlanPortUntaggedVlanList OBJECT-TYPE
            SYNTAX      DisplayString
            MAX-ACCESS  read-only
            STATUS      current
            DESCRIPTION
                "The Untagged vlan sequence to a Port."
            ::= { zxGponVlanPortEntry 6 }

    zxGponVlanPortTaggedVlanList OBJECT-TYPE
            SYNTAX     DisplayString
            MAX-ACCESS  read-only
            STATUS      current
            DESCRIPTION
               "The Tagged vlan sequence to a Port."
            ::= { zxGponVlanPortEntry 7 }

--  Extended VLAN:zxGponVlanPortConfVlanCmdTable
    zxGponVlanPortConfVlanCmdTable OBJECT-TYPE
        SYNTAX SEQUENCE OF ZxGponVlanPortConfVlanCmdEntry
        MAX-ACCESS      not-accessible
        STATUS          current
        DESCRIPTION
            "Operation command table for bridge port configuration like
            Vlan list.
            A single object such as pkg and channel will be added or removed to/from
            PkgIdList/ChanIdList through this table.
            "
         ::= { zxGponExtendedVlanMgmtObject 2 }

    zxGponVlanPortConfVlanCmdEntry  OBJECT-TYPE
        SYNTAX     ZxGponVlanPortConfVlanCmdEntry
        MAX-ACCESS not-accessible
        STATUS     current
        DESCRIPTION
            "A list of  entries of zxGponVlanPortConfVlanCmdTable."
        INDEX  { zxGponOltIndex, zxGponONTIndex, zxGponVlanPortType,zxGponVlanPortIndex }
         ::= { zxGponVlanPortConfVlanCmdTable 1 }

    ZxGponVlanPortConfVlanCmdEntry  ::= SEQUENCE {
        zxGponVlanPortConfVlanCmd      INTEGER,
        zxGponVlanPortConfVlanId       INTEGER
        }

    zxGponVlanPortConfVlanCmd OBJECT-TYPE
        SYNTAX INTEGER {
                    addTaggedVlan(1),
                    delTaggedVlan(2),
                    addUntaggedVlan(3),
                    delUntaggedVlan(4)
                    }
        MAX-ACCESS read-write
        STATUS current
        DESCRIPTION
            " The command to operate Vlan list of zxGponVlanPortConfTable.
            Each command is related to each meaming of zxGponVlanPortConfVlanObjName.
            "
         ::= { zxGponVlanPortConfVlanCmdEntry 1 }

    zxGponVlanPortConfVlanId OBJECT-TYPE
        SYNTAX INTEGER(1..4094)
        MAX-ACCESS read-write
        STATUS current
        DESCRIPTION
            " The value of object name in Vlan list,eg. pkgName,chanName
              Different command has different operated Vlan list,so this object
            has different meanings.please see the DESCRIPTION of zxGponVlanPortConfVlanListCmd.
            "
         ::= { zxGponVlanPortConfVlanCmdEntry 2 }

--  Extended VLAN:zxGponVlanTranslateTable
 zxGponVlanTranslateTable OBJECT-TYPE
        SYNTAX      SEQUENCE OF ZxGponVlanTranslateEntry
        MAX-ACCESS  not-accessible
        STATUS      current
        DESCRIPTION
            "A table containing VLAN translate information for VLANs
            configured into the bridge by (local or network)
            management."
        ::= { zxGponExtendedVlanMgmtObject 3 }

    zxGponVlanTranslateEntry OBJECT-TYPE
        SYNTAX      ZxGponVlanTranslateEntry
        MAX-ACCESS  not-accessible
        STATUS      current
        DESCRIPTION
            "VLAN Translate information for VLANs
            configured into the bridge by (local or network)
            management."
        INDEX   { zxGponOltIndex, zxGponONTIndex, zxGponVlanPortType,zxGponVlanPortIndex, zxGponVlanTranslateVlanId, zxGponVlanTranslatePriority}
        ::= { zxGponVlanTranslateTable 1 }

    ZxGponVlanTranslateEntry ::= SEQUENCE {
            zxGponVlanTranslateVlanId         INTEGER,
            zxGponVlanTranslatePriority       INTEGER,
            zxGponVlanTranslateCVlanId        INTEGER,
            zxGponVlanTranslateCVlanPriority  INTEGER,
            zxGponVlanTranslateSVlanId        INTEGER,
            zxGponVlanTranslateSVlanPriority  INTEGER,
            zxGponVlanTranslateRowStatus      RowStatus
        }

    zxGponVlanTranslateVlanId OBJECT-TYPE
        SYNTAX      INTEGER(1..4094)
        MAX-ACCESS  not-accessible
        STATUS      current
        DESCRIPTION
            "VlanId for Vlan translate."
        ::= { zxGponVlanTranslateEntry 1 }

    zxGponVlanTranslatePriority OBJECT-TYPE
        SYNTAX      INTEGER(0..8)
        MAX-ACCESS  not-accessible
        STATUS      current
        DESCRIPTION
            "Priority for Vlan translate,the scope of priority is from 0 to 8 and '8' indicates no configuration."
        ::= { zxGponVlanTranslateEntry 2 }

    zxGponVlanTranslateCVlanId OBJECT-TYPE
        SYNTAX      INTEGER (0..4094)
        MAX-ACCESS  read-write
        STATUS      current
        DESCRIPTION
            "Inner VLAN for Vlan translate,'0' indicates no translation."
        ::= { zxGponVlanTranslateEntry 3 }

    zxGponVlanTranslateCVlanPriority OBJECT-TYPE
        SYNTAX      INTEGER (0..8)
        MAX-ACCESS  read-write
        STATUS      current
        DESCRIPTION
            "Inner VLAN priority for Vlan translate,'8' indicates no translation."
        ::= { zxGponVlanTranslateEntry 4 }

    zxGponVlanTranslateSVlanId OBJECT-TYPE
        SYNTAX      INTEGER (0..4094)
        MAX-ACCESS  read-write
        STATUS      current
        DESCRIPTION
            "Outer VLAN for Vlan translate,'0' indicates no SVLAN."
        ::= { zxGponVlanTranslateEntry 5 }

    zxGponVlanTranslateSVlanPriority OBJECT-TYPE
        SYNTAX      INTEGER (0..8)
        MAX-ACCESS  read-write
        STATUS      current
        DESCRIPTION
            "Outer VLAN priority for Vlan translate,'8' indicates copy priority from inner VLAN priority."
        ::= { zxGponVlanTranslateEntry 6 }

    zxGponVlanTranslateRowStatus OBJECT-TYPE
        SYNTAX      RowStatus
        MAX-ACCESS  read-write
        STATUS      current
        DESCRIPTION
            "This object indicates the status of this entry."
        ::= { zxGponVlanTranslateEntry 7 }

--Extend VLAN end

--IP Host Config Data(section 7.3.98/G.983.2)
    zxGponIPHostConfigDataTable    OBJECT-TYPE
        SYNTAX      SEQUENCE OF ZxGponIPHostConfigDataEntry
        MAX-ACCESS  not-accessible
        STATUS      current
        DESCRIPTION
            "The IP Host Config Data contains the configuration for IP based services that are offered
            on the ONT.  This entity is conditionally required for ONTs that offer IP services from the
            ONT itself, and its presence allows additional features to be supported with the ONT.
            Instances of this managed entity are automatically created by the ONT after initialization
            if IP Host services are available.
            "
        REFERENCE   "G.983.2 section 7.3.98 IP Host Config Data"
        ::= { zxGponRmL3Mgmt 1 }

    zxGponIPHostConfigDataEntry OBJECT-TYPE
        SYNTAX      ZxGponIPHostConfigDataEntry
        MAX-ACCESS  not-accessible
        STATUS      current
        DESCRIPTION
            "It is entry in the zxGponIPHostConfigDataTable."
        INDEX   { zxGponOltIndex, zxGponONTIndex, zxGponIPHostConfigDataId }
        ::= { zxGponIPHostConfigDataTable 1 }

    ZxGponIPHostConfigDataEntry ::=
        SEQUENCE {
            zxGponIPHostConfigDataId                  INTEGER,
            zxGponIPHostConfigDataIPOptions           INTEGER,
            zxGponIPHostConfigDataMACAddress          MacAddress,
            zxGponIPHostConfigDataOntIdentifier       OCTET STRING,
            zxGponIPHostConfigDataIPAddress           IpAddress,
            zxGponIPHostConfigDataIPMask              IpAddress,
            zxGponIPHostConfigDataGateway             IpAddress,
            zxGponIPHostConfigDataPrimaryDNS          IpAddress,
            zxGponIPHostConfigDataSecondaryDNS        IpAddress,
            zxGponIPHostConfigDataCurrentAddress      IpAddress,
            zxGponIPHostConfigDataCurrentMask         IpAddress,
            zxGponIPHostConfigDataCurrentGateway      IpAddress,
            zxGponIPHostConfigDataCurrentPriDNS       IpAddress,
            zxGponIPHostConfigDataCurrentSecDNS       IpAddress,
            zxGponIPHostConfigDataDomainName          OCTET STRING,
            zxGponIPHostConfigDataHostName            OCTET STRING
        }

    zxGponIPHostConfigDataId OBJECT-TYPE
        SYNTAX      INTEGER
        MAX-ACCESS  read-only
        STATUS      current
        DESCRIPTION
        "This attribute provides a unique number for each instance of this managed entity.
        The ONT creates as many instances as there are independent IP stacks on the ONT.
        (1~n)"
        REFERENCE   "G.983.2 section 7.3.98 IP Host Config Data"
        ::= { zxGponIPHostConfigDataEntry 1 }

    zxGponIPHostConfigDataIPOptions OBJECT-TYPE
        SYNTAX      INTEGER
        MAX-ACCESS  read-write
        STATUS      current
        DESCRIPTION
        "This attribute is a bitfield that is used to enable or disable IP related options.
        A bit value of 1 enables the option and a bit value of 0 disables the option.
        The options are assigned as follows:
        0x1 = Enable DHCP
        0x2 = Respond to PINGs
        0x4 = Respond to TraceRoute messages.
        0x8 - 0x80 = Reserved for future use.
        (R, W) (mandatory) (1 byte)"
        REFERENCE   "G.983.2 section 7.3.98 IP Host Config Data"
        ::= { zxGponIPHostConfigDataEntry 2 }

    zxGponIPHostConfigDataMACAddress OBJECT-TYPE
        SYNTAX      MacAddress
        MAX-ACCESS  read-only
        STATUS      current
        DESCRIPTION
        "This attribute indicates the MAC address used by the IP Node (R) (mandatory) (6 bytes)"
        REFERENCE   "G.983.2 section 7.3.98 IP Host Config Data"
        ::= { zxGponIPHostConfigDataEntry 3 }

    zxGponIPHostConfigDataOntIdentifier OBJECT-TYPE
        SYNTAX      OCTET STRING(SIZE(0..25))
        MAX-ACCESS  read-write
        STATUS      current
        DESCRIPTION
        "A unique ONT identifier string. This string, if set is provided as part of the DHCP request
        to allow an alternative to MAC Address in retrieving the DHCP parameters of the specified ONT.
        The string may be up to 25 bytes long. If the string length is smaller than 25 bytes, it must
        be null terminated. Default value is 25 null bytes. (R, W) (mandatory) (25 bytes)
        "
        REFERENCE   "G.983.2 section 7.3.98 IP Host Config Data"
        ::= { zxGponIPHostConfigDataEntry 4 }

    zxGponIPHostConfigDataIPAddress OBJECT-TYPE
        SYNTAX      IpAddress
        MAX-ACCESS  read-write
        STATUS      current
        DESCRIPTION
        "Address used for all IP services hosted by the ONT, and has a default value of 0x0 [not set].
        If this value is set, it will override any values returned in DHCP. (R, W) (mandatory) (4 bytes)"
        REFERENCE   "G.983.2 section 7.3.98 IP Host Config Data"
        ::= { zxGponIPHostConfigDataEntry 5 }

    zxGponIPHostConfigDataIPMask OBJECT-TYPE
        SYNTAX      IpAddress
        MAX-ACCESS  read-write
        STATUS      current
        DESCRIPTION
        "Subnet mask for the IP services hosted by the ONT, and has a default value of 0x0 [not set].
        If this value is set, it will override any values returned in DHCP. (R, W) (mandatory) (4 bytes)"
        REFERENCE   "G.983.2 section 7.3.98 IP Host Config Data"
        ::= { zxGponIPHostConfigDataEntry 6 }

    zxGponIPHostConfigDataGateway OBJECT-TYPE
        SYNTAX      IpAddress
        MAX-ACCESS  read-write
        STATUS      current
        DESCRIPTION
        "Default Gateway Address used for all IP services hosted by the ONT, and has a default value of 0x0 [not set].
        If this value is set, it will override any values returned in DHCP. (R, W) (mandatory) (4 bytes)"
        REFERENCE   "G.983.2 section 7.3.98 IP Host Config Data"
        ::= { zxGponIPHostConfigDataEntry 7 }

    zxGponIPHostConfigDataPrimaryDNS OBJECT-TYPE
        SYNTAX      IpAddress
        MAX-ACCESS  read-write
        STATUS      current
        DESCRIPTION
        "Address used for the Primary DNS server for the IP service, and has a default value of 0x0 [not set].
        If this value is set, it will override any values returned in DHCP. (R, W) (mandatory) (4 bytes)"
        REFERENCE   "G.983.2 section 7.3.98 IP Host Config Data"
        ::= { zxGponIPHostConfigDataEntry 8 }

    zxGponIPHostConfigDataSecondaryDNS OBJECT-TYPE
        SYNTAX      IpAddress
        MAX-ACCESS  read-write
        STATUS      current
        DESCRIPTION
        "Address used for the Secondary DNS server for the IP service, and has a default value of 0x0 [not set].
        If this value is set, it will override any values returned in DHCP. (R, W) (mandatory) (4 bytes)"
        REFERENCE   "G.983.2 section 7.3.98 IP Host Config Data"
        ::= { zxGponIPHostConfigDataEntry 9 }

    zxGponIPHostConfigDataCurrentAddress OBJECT-TYPE
        SYNTAX      IpAddress
        MAX-ACCESS  read-only
        STATUS      current
        DESCRIPTION
        "Current address for the IP service hosted by the ONT.
        This attribute is updated by the ONT if a new address is assigned by DHCP. (R) (optional) (4 bytes)"
        REFERENCE   "G.983.2 section 7.3.98 IP Host Config Data"
        ::= { zxGponIPHostConfigDataEntry 10 }

    zxGponIPHostConfigDataCurrentMask OBJECT-TYPE
        SYNTAX      IpAddress
        MAX-ACCESS  read-only
        STATUS      current
        DESCRIPTION
        "Current subnet mask for the IP service.
        This attribute is updated by the ONT if a new mask is assigned by DHCP. (R) (optional) (4 bytes)"
        REFERENCE   "G.983.2 section 7.3.98 IP Host Config Data"
        ::= { zxGponIPHostConfigDataEntry 11 }

    zxGponIPHostConfigDataCurrentGateway OBJECT-TYPE
        SYNTAX      IpAddress
        MAX-ACCESS  read-only
        STATUS      current
        DESCRIPTION
        "Current default Gateway Address for the IP service.
        This attribute is updated by the ONT if a new gateway is assigned by DHCP. (R) (optional) (4 bytes)"
        REFERENCE   "G.983.2 section 7.3.98 IP Host Config Data"
        ::= { zxGponIPHostConfigDataEntry 12 }

    zxGponIPHostConfigDataCurrentPriDNS OBJECT-TYPE
        SYNTAX      IpAddress
        MAX-ACCESS  read-only
        STATUS      current
        DESCRIPTION
        "Current address used for the Primary DNS server for the IP service.
        This attribute is updated by the ONT if a new address is assigned by DHCP. (R) (optional) (4 bytes)"
        REFERENCE   "G.983.2 section 7.3.98 IP Host Config Data"
        ::= { zxGponIPHostConfigDataEntry 13 }

    zxGponIPHostConfigDataCurrentSecDNS OBJECT-TYPE
        SYNTAX      IpAddress
        MAX-ACCESS  read-only
        STATUS      current
        DESCRIPTION
        "Current address used for the Secondary DNS server for the IP service.
        This attribute is updated by the ONT if a new address is assigned by DHCP. (R) (optional) (4 bytes)"
        REFERENCE   "G.983.2 section 7.3.98 IP Host Config Data"
        ::= { zxGponIPHostConfigDataEntry 14 }

    zxGponIPHostConfigDataDomainName OBJECT-TYPE
        SYNTAX      OCTET STRING(SIZE(0..25))
        MAX-ACCESS  read-only
        STATUS      current
        DESCRIPTION
        "If domain name is indicated by DHCP, it is presented here. If domain name is not indicated,
        this attribute is set to an empty string.
        The string may be up to 25 bytes long. If the string length is smaller than 25 bytes,
        it must be null terminated.
        Default value is 25 null bytes. (R) (mandatory) (25 bytes)
        "
        REFERENCE   "G.983.2 section 7.3.98 IP Host Config Data"
        ::= { zxGponIPHostConfigDataEntry 15 }

    zxGponIPHostConfigDataHostName OBJECT-TYPE
        SYNTAX      OCTET STRING(SIZE(0..25))
        MAX-ACCESS  read-only
        STATUS      current
        DESCRIPTION
        "If host name is indicated by DHCP, it is presented here. If host name is not indicated,
        this attribute is set to an empty string.
        The string may be up to 25 bytes long. If the string length is smaller than 25 bytes,
        it must be null terminated.
        Default value is 25 null bytes. (R) (mandatory) (25 bytes)
        "
        REFERENCE   "G.983.2 section 7.3.98 IP Host Config Data"
        ::= { zxGponIPHostConfigDataEntry 16 }

--IP Host PPPoE Config Data
    zxGponPPPoEConfigDataTable    OBJECT-TYPE
        SYNTAX      SEQUENCE OF ZxGponPPPoEConfigDataEntry
        MAX-ACCESS  not-accessible
        STATUS      current
        DESCRIPTION
            "The Extend IP host config data configures IP based services in pppoe mode offered on the ONT. "
        REFERENCE   "Private ME"
        ::= { zxGponRmL3Mgmt 2 }

    zxGponPPPoEConfigDataEntry OBJECT-TYPE
        SYNTAX      ZxGponPPPoEConfigDataEntry
        MAX-ACCESS  not-accessible
        STATUS      current
        DESCRIPTION
            "It is entry in the zxGponPPPoEConfigDataTable."
        INDEX   { zxGponOltIndex, zxGponONTIndex, zxGponIPHostConfigDataId }
        ::= { zxGponPPPoEConfigDataTable 1 }

    ZxGponPPPoEConfigDataEntry ::=
        SEQUENCE {
            zxGponPPPoEConfigDataNATEnable            TruthValue,
            zxGponPPPoEConfigDataMode                 INTEGER,
            zxGponPPPoEConfigDataConnectTrigger       INTEGER,
            zxGponPPPoEConfigDataReleaseTimer         INTEGER,
            zxGponPPPoEConfigDataUsername             OCTET STRING,
            zxGponPPPoEConfigDataPassword             OCTET STRING,
            zxGponPPPoEConfigDataStatus               INTEGER,
            zxGponPPPoEConfigDataOnlineDuration       INTEGER,
            zxGponPPPoEConfigDataEntryStatus          RowStatus
        }

    zxGponPPPoEConfigDataNATEnable OBJECT-TYPE
        SYNTAX      TruthValue
        MAX-ACCESS  read-write
        STATUS      current
        DESCRIPTION
        "This Boolean attribute indicates whether NAT is enabled(true) or not (false),
        The default value is false."
        REFERENCE   ""
        ::= { zxGponPPPoEConfigDataEntry 1 }

    zxGponPPPoEConfigDataMode OBJECT-TYPE
        SYNTAX      INTEGER{
                    auto(1),
                    chap(2),
                    pap(3)
                    }
        MAX-ACCESS  read-write
        STATUS      current
        DESCRIPTION
        "This attribute specifies the PPPOE mode for the onu.
        Valid values include:
         1:AUTO;(default value)
         2:CHAP;(Challenge Handshake Authentication Protocol)
         3:PAP;(Password Authentication Protocol)
        "
        REFERENCE   ""
        ::= { zxGponPPPoEConfigDataEntry 2 }

    zxGponPPPoEConfigDataConnectTrigger OBJECT-TYPE
        SYNTAX      INTEGER{
                    always(1),
                    on-demand(2),
                    manual(3)
                    }
        MAX-ACCESS  read-write
        STATUS      current
        DESCRIPTION
        "This attribute specifies the connection trigger for the pppoe wan.
        Valid values include:
        1:Always(default value)
        2:On Demand
        3:Manual
        "
        REFERENCE   ""
        ::= { zxGponPPPoEConfigDataEntry 3 }

    zxGponPPPoEConfigDataReleaseTimer OBJECT-TYPE
        SYNTAX      INTEGER(0..65535)
        MAX-ACCESS  read-write
        STATUS      current
        DESCRIPTION
        "This attribute contains a release timer defined in seconds.
        The value 0 specifies that the ONT is to use its internal default.
        The default value of this attribute is 1200 seconds.
        "
        REFERENCE   ""
        ::= { zxGponPPPoEConfigDataEntry 4 }

    zxGponPPPoEConfigDataUsername OBJECT-TYPE
        SYNTAX      OCTET STRING(SIZE(1..25))
        MAX-ACCESS  read-write
        STATUS      current
        DESCRIPTION
        "This string attribute is the user name.
        If the string is shorter than 25 bytes,it must be null terminated.
        "
        REFERENCE   ""
        ::= { zxGponPPPoEConfigDataEntry 5 }

    zxGponPPPoEConfigDataPassword OBJECT-TYPE
        SYNTAX      OCTET STRING(SIZE(1..25))
        MAX-ACCESS  read-write
        STATUS      current
        DESCRIPTION
        "This string attribute is the password.
        If the string is shorter than 25 bytes,it must be null terminated.
        "
        REFERENCE   ""
        ::= { zxGponPPPoEConfigDataEntry 6 }

    zxGponPPPoEConfigDataStatus OBJECT-TYPE
        SYNTAX      INTEGER{
                    unconfigured(1),
                    connecting(2),
                    authenticating(3),
                    connected(4),
                    pending-disconnect(5),
                    disconnecting(6),
                    disconnected(7),
                    demand(8)
                    }
        MAX-ACCESS  read-only
        STATUS      current
        DESCRIPTION
        "Status of the pppoe wan."
        REFERENCE   ""
        ::= { zxGponPPPoEConfigDataEntry 7 }

    zxGponPPPoEConfigDataOnlineDuration OBJECT-TYPE
        SYNTAX      INTEGER
        MAX-ACCESS  read-only
        STATUS      current
        DESCRIPTION
        "This attribute reports the time in second that wan is online."
        REFERENCE   ""
        ::= { zxGponPPPoEConfigDataEntry 8 }

    zxGponPPPoEConfigDataEntryStatus OBJECT-TYPE
        SYNTAX      RowStatus
        MAX-ACCESS  read-write
        STATUS      current
        DESCRIPTION
        ""
        REFERENCE   ""
        ::= { zxGponPPPoEConfigDataEntry 9 }

--IP Static Route
    zxGponIpStaticRouteTable    OBJECT-TYPE
        SYNTAX      SEQUENCE OF ZxGponIpStaticRouteEntry
        MAX-ACCESS  not-accessible
        STATUS      current
        DESCRIPTION
            "This table contains information of ONU IP static routes
             configuration. This managed entity stores IP static routes."
        REFERENCE   "G.984.4 section 9.4.5 IP static routes"
        ::= { zxGponRmL3Mgmt 3 }

    zxGponIpStaticRouteEntry OBJECT-TYPE
        SYNTAX      ZxGponIpStaticRouteEntry
        MAX-ACCESS  not-accessible
        STATUS      current
        DESCRIPTION
            "It is entry in the zxGponIpStaticRouteTable."
        INDEX   { zxGponOltIndex, zxGponONTIndex,zxGponIpStaticRouteDestType,
                  zxGponIpStaticRouteDest, zxGponIpStaticRoutePfxLen }
        ::= { zxGponIpStaticRouteTable 1 }

    ZxGponIpStaticRouteEntry ::=
        SEQUENCE {
            zxGponIpStaticRouteDestType        InetAddressType,
            zxGponIpStaticRouteDest            InetAddress,
            zxGponIpStaticRoutePfxLen          InetAddressPrefixLength,
            zxGponIpStaticRouteNextHopType     InetAddressType,
            zxGponIpStaticRouteNextHop         InetAddress,
            zxGponIpStaticRouteOutputPort      Integer32,
            zxGponIpStaticRouteRowStatus       RowStatus
        }

   zxGponIpStaticRouteDestType OBJECT-TYPE
       SYNTAX     InetAddressType
       MAX-ACCESS not-accessible
       STATUS     current
       DESCRIPTION
           "The type of the zxGponIpStaticRouteDest address, as defined
            in the InetAddress MIB.
            Only those address types that may appear in an actual
            routing table are allowed as values of this object."
       REFERENCE "RFC 4001"
       ::= { zxGponIpStaticRouteEntry 1 }

    zxGponIpStaticRouteDest OBJECT-TYPE
        SYNTAX      InetAddress
        MAX-ACCESS  not-accessible
        STATUS      current
        DESCRIPTION
            "The destination IP address of this route.
             The type of this address is determined by the value of
             the zxGponIpStaticRouteDestType object.
             The values for the index objects zxGponIpStaticRouteDest and
             zxGponIpStaticRoutePfxLen must be consistent.  When the value
             of zxGponIpStaticRouteDest (excluding the zone index, if one
             is present) is x, then the bitwise logical-AND of x with the
             value of the mask formed from the corresponding index object
             zxGponIpStaticRoutePfxLen must be equal to x. If not, then the
             index pair is not consistent and an inconsistentName error must
             be returned on SET or CREATE requests.
             This field may be set to the default route address  0.0.0.0 ."
        REFERENCE   "G.984.4 section 9.4.5 IP static routes"
        ::= { zxGponIpStaticRouteEntry 2 }

    zxGponIpStaticRoutePfxLen OBJECT-TYPE
        SYNTAX      InetAddressPrefixLength
        MAX-ACCESS  not-accessible
        STATUS      current
        DESCRIPTION
            "Indicates the number of leading one bits that form the
             mask to be logical-ANDed with the destination address
             before being compared to the value in the
             zxGponIpStaticRouteDest field.
             The values for the index objects zxGponIpStaticRouteDest and
             zxGponIpStaticRoutePfxLen must be consistent.  When the value
             of zxGponIpStaticRouteDest (excluding the zone index, if one
             is present) is x, then the bitwise logical-AND of x with the
             value of the mask formed from the corresponding index object
             zxGponIpStaticRoutePfxLen must be equal to x.  If not, then
             the index pair is not consistent and an inconsistentName error
             must be returned on SET or CREATE requests."
        REFERENCE   "G.984.4 section 9.4.5 IP static routes"
        ::= { zxGponIpStaticRouteEntry 3 }

   zxGponIpStaticRouteNextHopType OBJECT-TYPE
       SYNTAX     InetAddressType
       MAX-ACCESS read-create
       STATUS     current
       DESCRIPTION
           "The type of the zxGponIpStaticRouteNextHopType address, as
            defined in the InetAddress MIB.
            Value should be set to unknown(0) for non-remote  routes.
            Only those address types that may appear in an actual
            routing table are allowed as values of this object."
       REFERENCE "RFC 4001"
       ::= { zxGponIpStaticRouteEntry 4 }

    zxGponIpStaticRouteNextHop OBJECT-TYPE
        SYNTAX      InetAddress
        MAX-ACCESS  read-create
        STATUS      current
        DESCRIPTION
            "On remote routes, the address of the next system route.
             For non-remote routes, a zero length string.
             The type of this address is determined by the value of the
             zxGponIpStaticRouteNextHopType object.
             This field is not used when the next hop is reached through an
             unnumbered link.
             For IPv4, the value is '255.255.255.255' when not used."
        REFERENCE   "G.984.4 section 9.4.5 IP static routes"
        ::= { zxGponIpStaticRouteEntry 5 }

    zxGponIpStaticRouteOutputPort OBJECT-TYPE
        SYNTAX      Integer32(1..255)
        MAX-ACCESS  read-create
        STATUS      current
        DESCRIPTION
            "The number of the IP port through which the next hop should be
             reached. This field is used when the next hop is reached through
             an unnumbered link and when a static route is set to support a
             fully meshed network. The value 0xFF indicates not used."
        REFERENCE   "G.984.4 section 9.4.5 IP static routes"
        ::= { zxGponIpStaticRouteEntry 6 }

    zxGponIpStaticRouteRowStatus  OBJECT-TYPE
        SYNTAX      RowStatus
        MAX-ACCESS  read-create
        STATUS      current
        DESCRIPTION
            "The status of this conceptual row.
             To create a row in this table, a manager must set this object to
             createAndGo(4). In particular, a newly created row cannot be
             created until the corresponding attributes from
             zxGponIpStaticRouteNextHopType to zxGponIpStaticRouteOutputPort
             have been set. To delete a row in this table, a manager must
             set this object to destroy(6)."
        ::= { zxGponIpStaticRouteEntry 50 }
--WAN IP Confuration
    zxGponRmWanIpConfTable    OBJECT-TYPE
        SYNTAX      SEQUENCE OF ZxGponRmWanIpConfEntry
        MAX-ACCESS  not-accessible
        STATUS      current
        DESCRIPTION
            "WAN IP configuration table."
        ::= { zxGponRmL3Mgmt 4 }

    zxGponRmWanIpConfEntry OBJECT-TYPE
        SYNTAX      ZxGponRmWanIpConfEntry
        MAX-ACCESS  not-accessible
        STATUS      current
        DESCRIPTION
            "WAN IP configuration entry.
            Entries in the zxGponRmWanIpConfTable are created and
            deleted using the zxGponRmWanIpConfRowStatus object."
        INDEX   { zxGponOltIndex, zxGponONTIndex, zxGponRmWanId }
        ::= { zxGponRmWanIpConfTable 1 }

    ZxGponRmWanIpConfEntry ::=
        SEQUENCE {
            zxGponRmWanId                 Integer32,
            zxGponRmWanIpMode             INTEGER,
            zxGponRmWanIpPrf              DisplayString,
            zxGponRmWanVlanPrf            DisplayString,
            zxGponRmWanHostId             Integer32,
            zxGponRmWanOnuIdentifier      DisplayString,
            zxGponRmWanIpAddrType         InetAddressType,
            zxGponRmWanIpAddr             InetAddress,
            zxGponRmWanIpAddrPfxLen       InetAddressPrefixLength,
            zxGponRmWanPppoeAuthMode      INTEGER,
            zxGponRmWanPppoeUserName      DisplayString,
            zxGponRmWanPppoePassword      DisplayString,
            zxGponRmWanCurrIpAddrType     InetAddressType,
            zxGponRmWanCurrIpAddr         InetAddress,
            zxGponRmWanCurrIpAddrPfxLen   InetAddressPrefixLength,
            zxGponRmWanCurrGatewayType    InetAddressType,
            zxGponRmWanCurrGateway        InetAddress,
            zxGponRmWanCurrPriDnsType     InetAddressType,
            zxGponRmWanCurrPriDns         InetAddress,
            zxGponRmWanCurrSecDnsType     InetAddressType,
            zxGponRmWanCurrSecDns         InetAddress,
            zxGponRmWanDomainName         DisplayString,
            zxGponRmWanHostName           DisplayString,
            zxGponRmWanMacAddr            MacAddress,
            zxGponRmWanRspPing            INTEGER,
            zxGponRmWanRspTraceRoute      INTEGER,
            zxGponRmWanIpConfRowStatus    RowStatus
        }

    zxGponRmWanId OBJECT-TYPE
        SYNTAX      Integer32(1..255)
        MAX-ACCESS  not-accessible
        STATUS      current
        DESCRIPTION
            "This attribute refers to the ID of WAN IP."
        ::= { zxGponRmWanIpConfEntry 1}

    zxGponRmWanIpMode OBJECT-TYPE
        SYNTAX      INTEGER{
                    static(1),
                    dhcp(2),
                    pppoe(3)
                    }
        MAX-ACCESS  read-create
        STATUS      current
        DESCRIPTION
            "IP address configuration mode."
        DEFVAL { static }
        ::= { zxGponRmWanIpConfEntry 2 }

    zxGponRmWanIpPrf OBJECT-TYPE
        SYNTAX      DisplayString(SIZE(0..64))
        MAX-ACCESS  read-create
        STATUS      current
        DESCRIPTION
            "This attribute refers to the name of table
            'zxGponVoipIpProfileTable'. If no profile name is indicated,
             this attribute is set to an null string."
        ::= { zxGponRmWanIpConfEntry 3 }

    zxGponRmWanVlanPrf OBJECT-TYPE
        SYNTAX      DisplayString(SIZE(1..64))
        MAX-ACCESS  read-create
        STATUS      current
        DESCRIPTION
            "This attribute refers to the name of table
            'zxGponVoipVlanProfileTable'."
        ::= { zxGponRmWanIpConfEntry 4 }

    zxGponRmWanHostId  OBJECT-TYPE
        SYNTAX      Integer32
        MAX-ACCESS  read-create
        STATUS      current
        DESCRIPTION
            "The ONU IP host ID, if this attribute is not specified,
            system will select an available IP host ID."
        ::= { zxGponRmWanIpConfEntry 5 }

    zxGponRmWanOnuIdentifier OBJECT-TYPE
        SYNTAX      DisplayString(SIZE(0..25))
        MAX-ACCESS  read-create
        STATUS      current
        DESCRIPTION
            "This attribute is related to 'zxGponRmWanIpMode'.
            This attribute is valid only when 'zxGponRmWanIpMode' is DHCP.
            A unique ONU identifier string. If set to a non-null value,
            this string is used instead of the MAC address in retrieving
            DHCP parameters. If the string is shorter than 25 characters,
            it must be null terminated. Its default value is null bytes."
        REFERENCE   "G.988 section 9.4.1 IP host config data"
        ::= { zxGponRmWanIpConfEntry 6 }

    zxGponRmWanIpAddrType     OBJECT-TYPE
        SYNTAX      InetAddressType
        MAX-ACCESS  read-create
        STATUS      current
        DESCRIPTION
            "The type of IP address denoted
             in zxGponRmWanIpAddr object."
        DEFVAL { ipv4 }
        ::= { zxGponRmWanIpConfEntry 7 }

    zxGponRmWanIpAddr     OBJECT-TYPE
        SYNTAX      InetAddress
        MAX-ACCESS  read-create
        STATUS      current
        DESCRIPTION
            "This attribute is related to 'zxGponRmWanIpMode'.
            This attribute is valid only when 'zxGponRmWanIpMode'
            is static."
        ::= { zxGponRmWanIpConfEntry 8 }

    zxGponRmWanIpAddrPfxLen     OBJECT-TYPE
        SYNTAX      InetAddressPrefixLength
        MAX-ACCESS  read-create
        STATUS      current
        DESCRIPTION
            "WAN IP address prefix length."
        ::= { zxGponRmWanIpConfEntry 9 }

    zxGponRmWanPppoeAuthMode OBJECT-TYPE
        SYNTAX      INTEGER{
                    auto(1),
                    chap(2),
                    pap(3)
                    }
        MAX-ACCESS  read-create
        STATUS      current
        DESCRIPTION
            "This attribute is related to 'zxGponRmWanIpMode'.
            This attribute is valid only when 'zxGponRmWanIpMode' is PPPoE."
        DEFVAL { auto }
        ::= { zxGponRmWanIpConfEntry 10 }

    zxGponRmWanPppoeUserName OBJECT-TYPE
        SYNTAX      DisplayString(SIZE(0..32))
        MAX-ACCESS  read-create
        STATUS      current
        DESCRIPTION
            "This attribute is related to 'zxGponRmWanIpMode'.
            This attribute is valid only when 'zxGponRmWanIpMode' is PPPoE."
        ::= { zxGponRmWanIpConfEntry 11 }

    zxGponRmWanPppoePassword OBJECT-TYPE
        SYNTAX      DisplayString(SIZE(0..32))
        MAX-ACCESS  read-create
        STATUS      current
        DESCRIPTION
            "This attribute is related to 'zxGponRmWanIpMode'.
            This attribute is valid only when 'zxGponRmWanIpMode' is PPPoE."
        ::= { zxGponRmWanIpConfEntry 12 }

    zxGponRmWanCurrIpAddrType     OBJECT-TYPE
        SYNTAX      InetAddressType
        MAX-ACCESS  read-only
        STATUS      current
        DESCRIPTION
            "The type of IP address denoted
             in 'zxGponRmWanCurrIpAddr' object."
        DEFVAL { ipv4 }
        ::= { zxGponRmWanIpConfEntry 13 }

    zxGponRmWanCurrIpAddr     OBJECT-TYPE
        SYNTAX      InetAddress
        MAX-ACCESS  read-only
        STATUS      current
        DESCRIPTION
            "The current IP address."
        ::= { zxGponRmWanIpConfEntry 14 }

    zxGponRmWanCurrIpAddrPfxLen     OBJECT-TYPE
        SYNTAX      InetAddressPrefixLength
        MAX-ACCESS  read-only
        STATUS      current
        DESCRIPTION
            "The current IP address prefix length."
        ::= { zxGponRmWanIpConfEntry 15 }

    zxGponRmWanCurrGatewayType     OBJECT-TYPE
        SYNTAX      InetAddressType
        MAX-ACCESS  read-only
        STATUS      current
        DESCRIPTION
            "The type of IP address denoted
             in 'zxGponRmWanCurrGateway' object."
        DEFVAL { ipv4 }
        ::= { zxGponRmWanIpConfEntry 16 }

    zxGponRmWanCurrGateway     OBJECT-TYPE
        SYNTAX      InetAddress
        MAX-ACCESS  read-only
        STATUS      current
        DESCRIPTION
            "The current gateway."
        ::= { zxGponRmWanIpConfEntry 17 }

    zxGponRmWanCurrPriDnsType     OBJECT-TYPE
        SYNTAX      InetAddressType
        MAX-ACCESS  read-only
        STATUS      current
        DESCRIPTION
            "The type of IP address denoted
             in 'zxGponRmWanCurrPriDns' object."
        DEFVAL { ipv4 }
        ::= { zxGponRmWanIpConfEntry 18 }

    zxGponRmWanCurrPriDns     OBJECT-TYPE
        SYNTAX      InetAddress
        MAX-ACCESS  read-only
        STATUS      current
        DESCRIPTION
            "The current primary DNS."
        ::= { zxGponRmWanIpConfEntry 19 }

    zxGponRmWanCurrSecDnsType     OBJECT-TYPE
        SYNTAX      InetAddressType
        MAX-ACCESS  read-only
        STATUS      current
        DESCRIPTION
            "The type of IP address denoted
             in zxGponRmWanCurrSecDns object."
        DEFVAL { ipv4 }
        ::= { zxGponRmWanIpConfEntry 20 }

    zxGponRmWanCurrSecDns     OBJECT-TYPE
        SYNTAX      InetAddress
        MAX-ACCESS  read-only
        STATUS      current
        DESCRIPTION
            "The current second DNS."
        ::= { zxGponRmWanIpConfEntry 21 }

    zxGponRmWanDomainName OBJECT-TYPE
        SYNTAX      DisplayString(SIZE(0..25))
        MAX-ACCESS  read-only
        STATUS      current
        DESCRIPTION
            "If DHCP indicates a domain name, it is presented here. If no
            domain name is indicated, this attribute is set to a null string.
            If the string is shorter than 25 bytes, it must be null
            terminated. The default value is 25 null bytes."
        REFERENCE   "G.988 section 9.4.1 IP host config data"
        ::= { zxGponRmWanIpConfEntry 22 }

    zxGponRmWanHostName OBJECT-TYPE
        SYNTAX      DisplayString(SIZE(0..25))
        MAX-ACCESS  read-only
        STATUS      current
        DESCRIPTION
            "If DHCP indicates a host name, it is presented here. If no host
            name is indicated, this attribute is set to a null string.If the
            string is shorter than 25 bytes, it must be null terminated.
            The default value is 25 null bytes."
        REFERENCE   "G.988 section 9.4.1 IP host config data"
        ::= { zxGponRmWanIpConfEntry 23 }

    zxGponRmWanMacAddr     OBJECT-TYPE
        SYNTAX      MacAddress
        MAX-ACCESS  read-only
        STATUS      current
        DESCRIPTION
            "This attribute indicates the MAC address used by the IP node."
        REFERENCE   "G.988 section 9.4.1 IP host config data"
        ::= { zxGponRmWanIpConfEntry 24 }

    zxGponRmWanRspPing OBJECT-TYPE
        SYNTAX      INTEGER{
                    enabled(1),
                    disabled(2)
                    }
        MAX-ACCESS  read-create
        STATUS      current
        DESCRIPTION
            "This attribute indicates whether respond to pings enabled."
        DEFVAL { disabled }
        ::= { zxGponRmWanIpConfEntry 25 }

    zxGponRmWanRspTraceRoute OBJECT-TYPE
        SYNTAX      INTEGER{
                    enabled(1),
                    disabled(2)
                    }
        MAX-ACCESS  read-create
        STATUS      current
        DESCRIPTION
            "This attribute indicates whether respond to trace route enabled."
        DEFVAL { disabled }
        ::= { zxGponRmWanIpConfEntry 26 }

    zxGponRmWanIpConfRowStatus OBJECT-TYPE
        SYNTAX      RowStatus
        MAX-ACCESS  read-create
        STATUS      current
        DESCRIPTION
            "The status of this conceptual row.

             To create a row in this table, a manager must
             set this object to createAndGo(4).

             To delete a row in this table, a manager must
             set this object to destroy(6).

             To query this object, always return 1. "
        ::= { zxGponRmWanIpConfEntry 50 }

--Voice management
--Physical path termination point POTS UNI
    zxGponPptpPOTSUNITable    OBJECT-TYPE
        SYNTAX      SEQUENCE OF ZxGponPptpPOTSUNIEntry
        MAX-ACCESS  not-accessible
        STATUS      current
        DESCRIPTION
            "This managed entity represents the point at the POTS UNI in the ONT where physical paths
            terminate and physical path level functions (e.g., analog telephony, facsimile function)
            are performed.
            One or more instances of this managed entity shall be contained in an instance of the
            ONTB-PON or a Circuit Pack managed entity classified as POTS type."
        REFERENCE   "G.983.2 section 7.3.26 Physical path termination point POTS UNI"
        ::= { zxGponRmVoiceMgmt 1 }

    zxGponPptpPOTSUNIEntry OBJECT-TYPE
        SYNTAX      ZxGponPptpPOTSUNIEntry
        MAX-ACCESS  not-accessible
        STATUS      current
        DESCRIPTION
            "It is entry in the zxGponPptpPOTSUNITable."
        INDEX   { zxGponOltIndex, zxGponONTIndex, zxGponUNIIndex }
        ::= { zxGponPptpPOTSUNITable 1 }

    ZxGponPptpPOTSUNIEntry ::=
        SEQUENCE {
            zxGponPptpPOTSUNIAdminState              INTEGER,
            zxGponPptpPOTSUNIIwVCCPtr                INTEGER,
            zxGponPptpPOTSUNIARC                     INTEGER,
            zxGponPptpPOTSUNIARCInterval             INTEGER,
            zxGponPptpPOTSUNIImpedance               INTEGER,
            zxGponPptpPOTSUNITxPath                  INTEGER,
            zxGponPptpPOTSUNIRxGain                  INTEGER,
            zxGponPptpPOTSUNITxGain                  INTEGER,
            zxGponPptpPOTSUNIOperState               INTEGER,
            zxGponPptpPOTSUNIHookState               INTEGER
        }

   zxGponPptpPOTSUNIAdminState OBJECT-TYPE
        SYNTAX      INTEGER{
                    unlock(1),
                    lock(2)
                    }
        MAX-ACCESS  read-write
        STATUS      current
        DESCRIPTION
        "This attribute is used to activate (unlock: value 0x00) and deactivate (lock: value 0x01)
        the functions performed by instances of this managed entity.(1 byte)"
        REFERENCE   "G.983.2 section 7.3.26 Physical path termination point POTS UNI"
        ::= { zxGponPptpPOTSUNIEntry 1 }

    zxGponPptpPOTSUNIIwVCCPtr OBJECT-TYPE
        SYNTAX      INTEGER
        MAX-ACCESS  read-only
        STATUS      current
        DESCRIPTION
        "This attribute provides a pointer to the instance of the Interworking VCC managed
        entity to which this instance is connected. The value 0x0000 is interpreted as a
        Null pointer.(2 bytes)"
        REFERENCE   "G.983.2 section 7.3.26 Physical path termination point POTS UNI"
        ::= { zxGponPptpPOTSUNIEntry 2 }

    zxGponPptpPOTSUNIARC OBJECT-TYPE
        SYNTAX      INTEGER
        MAX-ACCESS  read-write
        STATUS      current
        DESCRIPTION
        "This attribute is used to control alarm reporting from this managed entity. See I.1.8 for a complete description.(1 byte)"
        REFERENCE   "G.983.2 section 7.3.26 Physical path termination point POTS UNI"
        ::= { zxGponPptpPOTSUNIEntry 3 }

    zxGponPptpPOTSUNIARCInterval OBJECT-TYPE
        SYNTAX      INTEGER
        MAX-ACCESS  read-write
        STATUS      current
        DESCRIPTION
        "This attribute provides a provisionable length of time. See I.1.8 for a complete description.(1 byte)"
        REFERENCE   "G.983.2 section 7.3.26 Physical path termination point POTS UNI"
        ::= { zxGponPptpPOTSUNIEntry 4 }

    zxGponPptpPOTSUNIImpedance OBJECT-TYPE
        SYNTAX      INTEGER
        MAX-ACCESS  read-write
        STATUS      current
        DESCRIPTION
        "This attribute allows the impedance for the Physical Path Termination Point
        POTS UNI to be configured by the user.
        Valid values include 600 Ohm Impedance (value 0x00) and 900 Ohm Impedance (value 0x01).
        In addition, the following parameter sets from ETSI TS 101 270-1 (1999 10), Annex C,
        are valid:
        -    value 0x02: C1=150 nF, R1=750 Ohm, R2=270 Ohm;
        -    value 0x03: C1=115 nF, R1=820 Ohm, R2=220 Ohm;
        -    value 0x04: C1=230 nF, R1=1050 Ohm, R2=320 Ohm,
        where C1, R1, and R2 are related as shown below. Upon autonomous instantiation, the value 0x00 is used.
        (1 byte)"
        REFERENCE   "G.983.2 section 7.3.26 Physical path termination point POTS UNI"
        ::= { zxGponPptpPOTSUNIEntry 5 }

    zxGponPptpPOTSUNITxPath OBJECT-TYPE
        SYNTAX      INTEGER{
                    fulltimeOnHook(1),
                    partimeOnHook(2)
                    }
        MAX-ACCESS  read-write
        STATUS      current
        DESCRIPTION
        "This attribute allows for setting the Physical Path Termination Point POTS UNI
        to be put in either full-time or part-time on-hook transmission mode.
        Valid values include full time on-hook transmission (value 0x00) and part-time
        on-hook transmission (value 0x01) Upon autonomous instantiation, the value 0x00
        is used.(1 byte)"
        REFERENCE   "G.983.2 section 7.3.26 Physical path termination point POTS UNI"
        ::= { zxGponPptpPOTSUNIEntry 6 }

    zxGponPptpPOTSUNIRxGain OBJECT-TYPE
        SYNTAX      INTEGER
        MAX-ACCESS  read-write
        STATUS      current
        DESCRIPTION
        "This attribute provides a gain value for the received signal.
        Valid values are -12 dB to +6 dB in 0.1 dB increments.
        (value -120 to +60, 0 = 0 dB gain, -120 = -12.0 dB, etc.)
        Upon autonomous instantiation, the value 0x00 is used.(1 byte)"
        REFERENCE   "G.983.2 section 7.3.26 Physical path termination point POTS UNI"
        ::= { zxGponPptpPOTSUNIEntry 7 }

    zxGponPptpPOTSUNITxGain OBJECT-TYPE
        SYNTAX      INTEGER
        MAX-ACCESS  read-write
        STATUS      current
        DESCRIPTION
        "This attribute provides a gain value for the transmit signal.
        Valid values are -6 dB to +12 dB in 0.1 dB increments.
        (value -60 to +120, 0 = 0 dB gain, 60 = +6.0 dB, etc.).
        Upon autonomous instantiation, the value 0x00 is used.(1 byte)"
        REFERENCE   "G.983.2 section 7.3.26 Physical path termination point POTS UNI"
        ::= { zxGponPptpPOTSUNIEntry 8 }

    zxGponPptpPOTSUNIOperState OBJECT-TYPE
        SYNTAX      INTEGER{
                    enable(1),
                    disable(2)
                    }
        MAX-ACCESS  read-only
        STATUS      current
        DESCRIPTION
        "This attribute indicates whether or not this managed entity is capable of performing
        its task. The operational state reflects the perceived ability to receive or to generate
        a valid signal. Valid values are enabled (0x00) and disabled (0x01).(1 byte)"
        REFERENCE   "G.983.2 section 7.3.26 Physical path termination point POTS UNI"
        ::= { zxGponPptpPOTSUNIEntry 9 }

    zxGponPptpPOTSUNIHookState OBJECT-TYPE
        SYNTAX      INTEGER{
                    onHook(1),
                    offHook(2)
                    }
        MAX-ACCESS  read-only
        STATUS      current
        DESCRIPTION
        "This attribute indicates the state of the subscriber line: 0x00 = on hook, 0x01 = off hook.(1 byte)"
        REFERENCE   "G.983.2 section 7.3.26 Physical path termination point POTS UNI"
        ::= { zxGponPptpPOTSUNIEntry 10 }

--VoIP global configuration(VoIP Config Data section 7.3.101/G.983.2)
    zxGponVoIPConfigDataTable    OBJECT-TYPE
        SYNTAX      SEQUENCE OF ZxGponVoIPConfigDataEntry
        MAX-ACCESS  not-accessible
        STATUS      current
        DESCRIPTION
            "The VoIP Configuration Data defines the configuration for VoIP in the ONT.
            The OLT uses this ME to discover the VoIP signaling protocols and configuration
            methods supported by this ONT. The OLT then uses this ME to select the desired
            signaling protocol and configuration method. The entity is conditionally required
            for ONTs that offer VoIP services."
        REFERENCE   "G.983.2 section 7.3.101 VoIP Config Data"
        ::= { zxGponRmVoiceMgmt 2 }

    zxGponVoIPConfigDataEntry OBJECT-TYPE
        SYNTAX      ZxGponVoIPConfigDataEntry
        MAX-ACCESS  not-accessible
        STATUS      current
        DESCRIPTION
            "It is entry in the zxGponVoIPConfigDataTable."
        INDEX   { zxGponOltIndex, zxGponONTIndex }
        ::= { zxGponVoIPConfigDataTable 1 }

    ZxGponVoIPConfigDataEntry ::=
        SEQUENCE {
            zxGponVoIPConfigDataAvailableSignalProtocol      INTEGER,
            zxGponVoIPConfigDataSignalProtocolUsed           INTEGER,
            zxGponVoIPConfigDataAvailableConfigMethod        INTEGER,
            zxGponVoIPConfigDataConfigMethodUsed             INTEGER,
            zxGponVoIPConfigDataConfigAddress                OCTET STRING,
            zxGponVoIPOnuDomainName                          DisplayString,
            zxGponVoIPH248EquipName                          DisplayString,
            zxGponVoIPH248RegMode                            INTEGER,
            zxGponVoIPMgcRegMode                             INTEGER,
            zxGponVoIPLineName                               DisplayString,
            zxGponVoIPIpAllocMode                            INTEGER,
            zxGponVoIPCfgSvrValidateScheme                   INTEGER,
            zxGponVoIPCfgSvrUsername                         DisplayString,
            zxGponVoIPCfgSvrPassword                         DisplayString,
            zxGponVoIPCfgSvrRealm                            DisplayString,
            zxGponVoIPCfgSvrRetrieveFile                     TruthValue,
            zxGponVoIPCfgSvrRetrieveFileVer                  DisplayString,
            zxGponVoIPCfgStatus                              INTEGER
        }

    zxGponVoIPConfigDataAvailableSignalProtocol OBJECT-TYPE
        SYNTAX      INTEGER
        MAX-ACCESS  read-only
        STATUS      current
        DESCRIPTION
        "This attribute defines, using a bitmap, the VoIP Signaling Protocols supported in the
        ONT. Valid bitmap values are:
        0x00 = s, VoIP not supported
        0x01 = SIP
        0x02 = H.248
        0x04 = MGCP
        0xFF = NA
        (1 byte)"
        REFERENCE   "G.983.2 section 7.3.101 VoIP Config Data"
        ::= { zxGponVoIPConfigDataEntry 1 }

    zxGponVoIPConfigDataSignalProtocolUsed OBJECT-TYPE
        SYNTAX      INTEGER{
                    none(1),
                    sip(2),
                    h248(3),
                    mgcp(4)
                    }
        MAX-ACCESS  read-write
        STATUS      current
        DESCRIPTION
        "This attribute identifies the type of VoIP signaling protocol used for ONT.
        Only one type of protocol is allowed. Valid values are:
        0x00 = None
        0x01 = SIP
        0x02 = H.248
        0x03 = MGCP
        0xFF = Selected by Non-OMCI Management Interface
        (1 byte)"
        REFERENCE   "G.983.2 section 7.3.101 VoIP Config Data"
        ::= { zxGponVoIPConfigDataEntry 2 }

    zxGponVoIPConfigDataAvailableConfigMethod OBJECT-TYPE
        SYNTAX      INTEGER
        MAX-ACCESS  read-only
        STATUS      current
        DESCRIPTION
        "This attribute indicates, using a bitmap, the capabilities of the ONT with regard to VoIP service configuration:
        0x0001 indicates that the ONT is capable of using OMCI to configure its VoIP services.
        0x0002 indicates that the ONT is capable of working with configuration file retrieval to configure its VoIP services.
        0x0004 indicates that the ONT is capable of working with TR-69 to configure its VoIP services.
        0x0008 indicates that the ONT is capable of working with IETF sipping config framework to configure its VoIP services.
        Bits 5 - 24 are reserved for future use.
        Bits 25 - 32 are reserved for proprietary vendor configuration capability indications.
        Default value is 0x0001.(4 bytes)
        "
        REFERENCE   "G.983.2 section 7.3.101 VoIP Config Data"
        ::= { zxGponVoIPConfigDataEntry 3 }

    zxGponVoIPConfigDataConfigMethodUsed OBJECT-TYPE
        SYNTAX      INTEGER
        MAX-ACCESS  read-write
        STATUS      current
        DESCRIPTION
        "Indicates to the ONT, which method should be used to configure the VoIP Service of the ONT.
         0x00 the ONT default - do not configure.
         0x01 indicate use of OMCI for VoIP service configuration of the ONT.
         0x02 indicate use of configuration file retrieval for VoIP service configuration of the ONT.
         0x03 indicate use of TR-69 for VoIP service configuration of the ONT.
         0x04 indicate use of IETF sipping config framework for VoIP service configuration of the ONT.
         0x05 - 0xF0 are reserved for future use.
         0xF1 - 0xFF are reserved for proprietary vendor configuration methods.
         Default value is 0x00 (R, W) (mandatory) (1 bytes)
        "
        REFERENCE   "G.983.2 section 7.3.101 VoIP Config Data"
        ::= { zxGponVoIPConfigDataEntry 4 }

    zxGponVoIPConfigDataConfigAddress OBJECT-TYPE
        SYNTAX      OCTET STRING(SIZE(0..128))
        MAX-ACCESS  read-write
        STATUS      current
        DESCRIPTION
        "If this attribute is set to any value other than 0xFFFF, it points to a Network Address managed entity.
        In this case, the Network Address ME indicates the address of the server to contact using the method
        indicated in the VoIP Configuration Method Used attribute of the VoIP Service ME.
        If this attribute is set to 0xFFFF, an address is not defined by this attribute.
        However, the address may be defined by other methods such as deriving the address from the ONT Identifier
        attribute of the IP Host Config Data ME, and using a well-known URI schema.
        Default value is 0xFFFF (R, W) (mandatory) (2 bytes)
        Attention!! We hide the Network Address ME, using OCTET STRING instead!
        But now, it may be unused.
        "
        REFERENCE   "G.983.2 section 7.3.101 VoIP Config Data"
        ::= { zxGponVoIPConfigDataEntry 5 }

    zxGponVoIPOnuDomainName  OBJECT-TYPE
        SYNTAX      DisplayString (SIZE (0..128))
        MAX-ACCESS  read-write
        STATUS      current
        DESCRIPTION
            "ONU domain name is used to locate ONU by SS when the mode of MG
            registered to SS is using domain name."
        ::= { zxGponVoIPConfigDataEntry 6 }

    zxGponVoIPH248EquipName  OBJECT-TYPE
        SYNTAX      DisplayString (SIZE (0..25))
        MAX-ACCESS  read-write
        STATUS      current
        DESCRIPTION
            "ONU equipment name is used to locate ONU by SS when the mode of MG
            registered to SS is using equipment name."
        ::= { zxGponVoIPConfigDataEntry 7 }

    zxGponVoIPH248RegMode OBJECT-TYPE
        SYNTAX      INTEGER{
                    ipv4(1),
                    domainName(2),
                    equipmentName(3)
                    }
        MAX-ACCESS  read-write
        STATUS      current
        DESCRIPTION
            "This attribute specifies MID flag."
        DEFVAL {ipv4}
        ::= { zxGponVoIPConfigDataEntry 8 }

    zxGponVoIPMgcRegMode OBJECT-TYPE
        SYNTAX      INTEGER{
                    wildcard(1),
                    individual(2)
                    }
        MAX-ACCESS  read-write
        STATUS      current
        DESCRIPTION
            "This attribute specifies register mode."
        DEFVAL {wildcard}
        ::= { zxGponVoIPConfigDataEntry 9 }

    zxGponVoIPLineName  OBJECT-TYPE
        SYNTAX      DisplayString (SIZE (0..25))
        MAX-ACCESS  read-write
        STATUS      current
        DESCRIPTION
            "Line name sequence number.The default value is
            null(all zero bytes)"
        ::= { zxGponVoIPConfigDataEntry 10 }

    zxGponVoIPIpAllocMode OBJECT-TYPE
        SYNTAX      INTEGER{
                    singleIp(1),
                    dualIp(2),
                    multiIp(3)
                    }
        MAX-ACCESS  read-write
        STATUS      current
        DESCRIPTION
            "VoIP allocate mode."
        DEFVAL { singleIp }
        ::= { zxGponVoIPConfigDataEntry 11 }

    zxGponVoIPCfgSvrValidateScheme OBJECT-TYPE
        SYNTAX      INTEGER{
                    disable(1),
                    md5(2),
                    basic(3)
                    }
        MAX-ACCESS  read-write
        STATUS      current
        DESCRIPTION
            "User Validation Scheme."
        ::= { zxGponVoIPConfigDataEntry 12 }

    zxGponVoIPCfgSvrUsername  OBJECT-TYPE
        SYNTAX      DisplayString (SIZE (0..32))
        MAX-ACCESS  read-write
        STATUS      current
        DESCRIPTION
            "User name for validation."
        ::= { zxGponVoIPConfigDataEntry 13 }

    zxGponVoIPCfgSvrPassword  OBJECT-TYPE
        SYNTAX      DisplayString (SIZE (0..32))
        MAX-ACCESS  read-write
        STATUS      current
        DESCRIPTION
            "Password for validation."
        ::= { zxGponVoIPConfigDataEntry 14 }

    zxGponVoIPCfgSvrRealm  OBJECT-TYPE
        SYNTAX      DisplayString (SIZE (0..32))
        MAX-ACCESS  read-write
        STATUS      current
        DESCRIPTION
            "A string to be displayed to users so they know which user name
            and password to use.  This string should contain at least the name
            of the host performing the authentication and might additionally
            indicate the collection of users who might have access.  An example
            might be 'registered_users@gotham.news.com'.  The realm is a
            'quoted-string' as specified in section 2.2 of the HTTP/1.1
            specification."
        ::= { zxGponVoIPConfigDataEntry 15 }

    zxGponVoIPCfgSvrRetrieveFile  OBJECT-TYPE
        SYNTAX      TruthValue
        MAX-ACCESS  read-write
        STATUS      current
        DESCRIPTION
            "This attribute is an action. It will be set independently
            to notify ONU to retrieve file again."
        ::= { zxGponVoIPConfigDataEntry 16 }

    zxGponVoIPCfgSvrRetrieveFileVer  OBJECT-TYPE
        SYNTAX      DisplayString (SIZE (0..25))
        MAX-ACCESS  read-only
        STATUS      current
        DESCRIPTION
          "This attribute indicates the version of the latest retrieved file."
        ::= { zxGponVoIPConfigDataEntry 17 }

    zxGponVoIPCfgStatus  OBJECT-TYPE
        SYNTAX      INTEGER{
                    inactive(1),
                    active(2),
                    initializing(3),
                    fault(4)
                    }
        MAX-ACCESS  read-only
        STATUS      current
        DESCRIPTION
            "Indicates the status of the ONU VoIP service.
            Inactive: configuration retrieval has not been attempted
            Active: configuration was retrieved
            Initializing: configuration is now being retrieved
            Fault: configuration retrieval process failed"
        ::= { zxGponVoIPConfigDataEntry 18 }



--SIP Agent Config Data
    zxGponSIPAgentConfigDataTable    OBJECT-TYPE
        SYNTAX      SEQUENCE OF ZxGponSIPAgentConfigDataEntry
        MAX-ACCESS  not-accessible
        STATUS      current
        DESCRIPTION
            "One instance of this managed entity is related to a TCP/UDP Config Data object.
            This managed entity may be referenced by one or more SIP User Data managed entities."
        REFERENCE   "G.983.2 section 7.3.103 SIP Agent Config Data"
        ::= { zxGponRmVoiceMgmt 3 }

    zxGponSIPAgentConfigDataEntry OBJECT-TYPE
        SYNTAX      ZxGponSIPAgentConfigDataEntry
        MAX-ACCESS  not-accessible
        STATUS      current
        DESCRIPTION
            "It is entry in the zxGponSIPAgentConfigDataTable."
        INDEX   { zxGponOltIndex, zxGponONTIndex, zxGponSIPAgentConfigDataId }
        ::= { zxGponSIPAgentConfigDataTable 1 }

    ZxGponSIPAgentConfigDataEntry ::=
        SEQUENCE {
            zxGponSIPAgentConfigDataId                       INTEGER,
            zxGponSIPAgentConfigDataProxyServer              OCTET STRING,
            zxGponSIPAgentConfigDataOutboundProxy            OCTET STRING,
            zxGponSIPAgentConfigDataPrimaryDNS               IpAddress,
            zxGponSIPAgentConfigDataSecondaryDNS             IpAddress,
            zxGponSIPAgentConfigDataUDPTCPPort               INTEGER,
            zxGponSIPAgentConfigDataHostId                   INTEGER,
            zxGponSIPAgentConfigDataRegExpTime               INTEGER,
            zxGponSIPAgentConfigDataReRegStartTime           INTEGER,
            zxGponSIPAgentConfigDataHostPartURI              OCTET STRING,
            zxGponSIPAgentConfigDataSIPStatus                INTEGER,
            zxGponSIPAgentConfigDataRegServer                OCTET STRING,
            zxGponSIPAgentConfigDataValidatScheme            INTEGER,
            zxGponSIPAgentConfigDataRegUserName              OCTET STRING,
            zxGponSIPAgentConfigDataRegPassword              OCTET STRING,
            zxGponSIPAgentConfigDataRealm                    OCTET STRING,
            zxGponSIPAgentConfigDataSSVendor                 OCTET STRING,
            zxGponSIPAgentConfigDataEntryStatus              RowStatus
        }

    zxGponSIPAgentConfigDataId OBJECT-TYPE
        SYNTAX      INTEGER
        MAX-ACCESS  not-accessible
        STATUS      current
        DESCRIPTION
        "This attribute provides a unique number for each instance of this managed entity.
        (1~n)(R, Set-by-create) (mandatory) (2 bytes)"
        REFERENCE   "G.983.2 section 7.3.103 SIP Agent Config Data"
        ::= { zxGponSIPAgentConfigDataEntry 1 }

    zxGponSIPAgentConfigDataProxyServer OBJECT-TYPE
        SYNTAX      OCTET STRING(SIZE(0..128))
        MAX-ACCESS  read-write
        STATUS      current
        DESCRIPTION
        "This attribute provides a pointer to a LargeString ME  that contains the name (IP address or URI)
        of the SIP Proxy Server for SIP signaling messages. (R, W, Set-by-create) (mandatory) (2 bytes)"
        REFERENCE   "G.983.2 section 7.3.103 SIP Agent Config Data"
        ::= { zxGponSIPAgentConfigDataEntry 2 }

    zxGponSIPAgentConfigDataOutboundProxy OBJECT-TYPE
        SYNTAX      OCTET STRING(SIZE(0..128))
        MAX-ACCESS  read-write
        STATUS      current
        DESCRIPTION
        "This attribute provides a pointer to a LargeString ME that contains the name (IP address or URI)
        of the SIP outbound Proxy Server for SIP signaling messages.  (R, W, Set-by-create) (mandatory) (2 bytes)"
        REFERENCE   "G.983.2 section 7.3.103 SIP Agent Config Data"
        ::= { zxGponSIPAgentConfigDataEntry 3 }

    zxGponSIPAgentConfigDataPrimaryDNS OBJECT-TYPE
        SYNTAX      IpAddress
        MAX-ACCESS  read-write
        STATUS      current
        DESCRIPTION
        "This attribute defines the Primary SIP DNS IP Address.  If this value is zero, the Primary SIP DNS should not be used.
        Default value of 0.  (R, W, Set-by-create) (mandatory) (4 bytes)"
        REFERENCE   "G.983.2 section 7.3.103 SIP Agent Config Data"
        ::= { zxGponSIPAgentConfigDataEntry 4 }

    zxGponSIPAgentConfigDataSecondaryDNS OBJECT-TYPE
        SYNTAX      IpAddress
        MAX-ACCESS  read-write
        STATUS      current
        DESCRIPTION
        "This attribute defines the Secondary SIP DNS IP Address. If this value is zero, the Secondary SIP DNS should not be used.
        Default value of 0.  (R, W, Set-by-create) (mandatory) (4 bytes)"
        REFERENCE   "G.983.2 section 7.3.103 SIP Agent Config Data"
        ::= { zxGponSIPAgentConfigDataEntry 5 }

    zxGponSIPAgentConfigDataUDPTCPPort OBJECT-TYPE
        SYNTAX      INTEGER
        MAX-ACCESS  read-write
        STATUS      current
        DESCRIPTION
        "This attribute indicates the UDP/TCP port num.
        This attribute associates the SIP Agent with the TCP/UDP service to be used for communication with the SIP Server.
        Default value is 0xFFFF.  (R, W) (mandatory) (2 bytes)"
        REFERENCE   "G.983.2 section 7.3.103 SIP Agent Config Data"
        ::= { zxGponSIPAgentConfigDataEntry 6 }

    zxGponSIPAgentConfigDataHostId OBJECT-TYPE
        SYNTAX      INTEGER
        MAX-ACCESS  read-write
        STATUS      current
        DESCRIPTION
        "This attribute indicates the UDP/TCP port num.
        This attribute associates the SIP Agent with the TCP/UDP service to be used for communication with the SIP Server.
        Default value is 0xFFFF.  (R, W) (mandatory) (2 bytes)"
        REFERENCE   "G.983.2 section 7.3.103 SIP Agent Config Data"
        ::= { zxGponSIPAgentConfigDataEntry 7 }

    zxGponSIPAgentConfigDataRegExpTime OBJECT-TYPE
        SYNTAX      INTEGER
        MAX-ACCESS  read-write
        STATUS      current
        DESCRIPTION
        "This attribute defines the SIP Registration Expiration Time in seconds.  If this value is zero,
        the SIP Agent will not add an expiration time to the registration requests, and will not perform
        re-registration.
        The default value used at Create shall be 3600 seconds. (R, W) (mandatory) (4 bytes)"
        REFERENCE   "G.983.2 section 7.3.103 SIP Agent Config Data"
        ::= { zxGponSIPAgentConfigDataEntry 8 }

    zxGponSIPAgentConfigDataReRegStartTime OBJECT-TYPE
        SYNTAX      INTEGER
        MAX-ACCESS  read-write
        STATUS      current
        DESCRIPTION
        "This attribute provides the time in seconds prior to timeout that the SIP Agent should start
        the re-registration process.  The default value used at Create shall be 360 seconds. (R, W) (mandatory) (4 bytes)"
        REFERENCE   "G.983.2 section 7.3.103 SIP Agent Config Data"
        ::= { zxGponSIPAgentConfigDataEntry 9 }

    zxGponSIPAgentConfigDataHostPartURI OBJECT-TYPE
        SYNTAX      OCTET STRING(SIZE(0..128))
        MAX-ACCESS  read-write
        STATUS      current
        DESCRIPTION
        "This attribute provides a pointer to a LargeString ME that contains the host or domain part of
        the SIP Address of Record for users connected to this ONT. A 0xFFFF indicates the current address
        in the IP Host Config ME is used. Default value is 0xFFFF. (R, W, Set-by-create) (mandatory) (2 bytes)"
        REFERENCE   "G.983.2 section 7.3.103 SIP Agent Config Data"
        ::= { zxGponSIPAgentConfigDataEntry 10 }

    zxGponSIPAgentConfigDataSIPStatus OBJECT-TYPE
        SYNTAX      INTEGER{
                    ok-initial(1),
                    connected(2),
                    failed-icmpErr(3),
                    failed-malformedRsp(4),
                    failed-inadequateRsp(5),
                    failed-timeout(6)
                    }
        MAX-ACCESS  read-only
        STATUS      current
        DESCRIPTION
        "This attribute is used to show the current status of the SIP Agent.
        Values are as follows:
        0: ok/initial,
        1: Connected,
        2: Failed-ICMP Error,
        3: Failed-Malformed-response,
        4: Failed-Inadequate Info Response,
        5: Failed-Timeout.  (R) (mandatory) (1 byte)"
        REFERENCE   "G.983.2 section 7.3.103 SIP Agent Config Data"
        ::= { zxGponSIPAgentConfigDataEntry 11 }

    zxGponSIPAgentConfigDataRegServer OBJECT-TYPE
        SYNTAX      OCTET STRING(SIZE(0..128))
        MAX-ACCESS  read-write
        STATUS      current
        DESCRIPTION
        "This attribute provides a pointer to a Network Address ME that contains the name
        (IP address or resolved name) of the SIP Registrar Server for SIP signaling messages.
        Examples: '10.10.10.10' and 'proxy.voip.net'.
        Default value is 0xFFFF. (R, W, Set-by-create) (mandatory) (2 bytes)"
        REFERENCE   "G.983.2 section 7.3.103 SIP Agent Config Data"
        ::= { zxGponSIPAgentConfigDataEntry 12 }

    zxGponSIPAgentConfigDataValidatScheme OBJECT-TYPE
        SYNTAX      INTEGER{
                    disable(1),
                    md5(2),
                    basic(3)
                    }
        MAX-ACCESS  read-write
        STATUS      current
        DESCRIPTION
        ""
        REFERENCE   "G.983.2 section 7.3.103 SIP Agent Config Data"
        ::= { zxGponSIPAgentConfigDataEntry 13 }

    zxGponSIPAgentConfigDataRegUserName OBJECT-TYPE
        SYNTAX      OCTET STRING(SIZE(0..25))
        MAX-ACCESS  read-write
        STATUS      current
        DESCRIPTION
        ""
        REFERENCE   "G.983.2 section 7.3.103 SIP Agent Config Data"
        ::= { zxGponSIPAgentConfigDataEntry 14 }

    zxGponSIPAgentConfigDataRegPassword OBJECT-TYPE
        SYNTAX      OCTET STRING(SIZE(0..25))
        MAX-ACCESS  read-write
        STATUS      current
        DESCRIPTION
        ""
        REFERENCE   "G.983.2 section 7.3.103 SIP Agent Config Data"
        ::= { zxGponSIPAgentConfigDataEntry 15 }

    zxGponSIPAgentConfigDataRealm OBJECT-TYPE
        SYNTAX      OCTET STRING(SIZE(0..25))
        MAX-ACCESS  read-write
        STATUS      current
        DESCRIPTION
        ""
        REFERENCE   "G.983.2 section 7.3.103 SIP Agent Config Data"
        ::= { zxGponSIPAgentConfigDataEntry 16 }

    zxGponSIPAgentConfigDataSSVendor OBJECT-TYPE
        SYNTAX      OCTET STRING(SIZE(0..4))
        MAX-ACCESS  read-write
        STATUS      current
        DESCRIPTION
        " This attribute identifies the SIP Gateway softswitch vendor.
        The format is four ASCII coded alphabetic characters [A - Z] as defined in ANSI T1.220,
        All NULL characters indicates no particular vendor. (R,W, Set-by-create) (mandatory) (4 byte)"
        REFERENCE   "G.983.2 section 7.3.103 SIP Agent Config Data"
        ::= { zxGponSIPAgentConfigDataEntry 17 }

    zxGponSIPAgentConfigDataEntryStatus OBJECT-TYPE
        SYNTAX      RowStatus
        MAX-ACCESS  read-write
        STATUS      current
        DESCRIPTION
        " "
        REFERENCE   "G.983.2 section 7.3.103 SIP Agent Config Data"
        ::= { zxGponSIPAgentConfigDataEntry 18 }

--SIP User Data
    zxGponSIPUserDataTable    OBJECT-TYPE
        SYNTAX      SEQUENCE OF ZxGponSIPUserDataEntry
        MAX-ACCESS  not-accessible
        STATUS      current
        DESCRIPTION
            "An instance of this managed entity may be referenced by one VoIP Voice CTP managed entity."
        REFERENCE   "G.983.2 section 7.3.106 SIP User Data"
        ::= { zxGponRmVoiceMgmt 4 }

    zxGponSIPUserDataEntry OBJECT-TYPE
        SYNTAX      ZxGponSIPUserDataEntry
        MAX-ACCESS  not-accessible
        STATUS      current
        DESCRIPTION
            "It is entry in the zxGponSIPUserDataTable."
        INDEX   { zxGponOltIndex, zxGponONTIndex, zxGponUNIIndex }
        ::= { zxGponSIPUserDataTable 1 }

    ZxGponSIPUserDataEntry ::=
        SEQUENCE {
            zxGponSIPUserDataAgentId                  INTEGER,
            zxGponSIPUserDataUserPartAOR              OCTET STRING,
            zxGponSIPUserDataDisplayName              OCTET STRING,
            zxGponSIPUserDataUserName                 OCTET STRING,
            zxGponSIPUserDataPassword                 OCTET STRING,
            zxGponSIPUserDataVMailServerURI           OCTET STRING,
            zxGponSIPUserDataVMailValidateScheme      INTEGER,
            zxGponSIPUserDataVMailUserName            OCTET STRING,
            zxGponSIPUserDataVMailPassword            OCTET STRING,
            zxGponSIPUserDataVMailRealm               OCTET STRING,
            zxGponSIPUserDataVMailSubsciptExpTime     INTEGER,
            zxGponSIPUserDataNetworkDialPlanPtr       INTEGER,
            zxGponSIPUserDataServiceProfilePtr        INTEGER,
            zxGponSIPUserDataFeatureCodePtr           INTEGER,
            zxGponSIPUserDataReleaseTimer             INTEGER,
            zxGponSIPUserDataROHTimer                 INTEGER,
            zxGponSIPUserDataEntryStatus              RowStatus
        }

    zxGponSIPUserDataAgentId OBJECT-TYPE
        SYNTAX      INTEGER
        MAX-ACCESS  read-write
        STATUS      current
        DESCRIPTION
        "Points to the SIP Agent Config Data ME to be used for signaling.
        (R, W, Set-by-create) (mandatory) (2 bytes)"
        REFERENCE   "G.983.2 section 7.3.106 SIP User Data"
        ::= { zxGponSIPUserDataEntry 1 }

    zxGponSIPUserDataUserPartAOR OBJECT-TYPE
        SYNTAX      OCTET STRING(SIZE(0..128))
        MAX-ACCESS  read-write
        STATUS      current
        DESCRIPTION
        "This attribute provides a pointer to a LargeString ME that contains the user identification
        part of the Address of Record. This can take the form of  an alphanumeric string or the
        directory number used to reference the user in the network.  0xFFFF indicates that no user
        part AOR has been defined. (R, W, Set-by-create) (mandatory) (2 bytes)"
        REFERENCE   "G.983.2 section 7.3.106 SIP User Data"
        ::= { zxGponSIPUserDataEntry 2 }

    zxGponSIPUserDataDisplayName OBJECT-TYPE
        SYNTAX      OCTET STRING(SIZE(0..25))
        MAX-ACCESS  read-write
        STATUS      current
        DESCRIPTION
        "This attribute defines the Customer ID used for outgoing SIP messages display attribute in ASCII
        string format.   Default value shall be null (all zeros).  (R, W) (mandatory) (25 bytes)"
        REFERENCE   "G.983.2 section 7.3.106 SIP User Data"
        ::= { zxGponSIPUserDataEntry 3 }

    zxGponSIPUserDataUserName OBJECT-TYPE
        SYNTAX      OCTET STRING(SIZE(0..128))
        MAX-ACCESS  read-write
        STATUS      current
        DESCRIPTION
        "A pointer to an Authentication Security Method ME that contains a SIP user name and password used
        for authentication.  0xFFFF indicates no username/password. (R, W, Set-by-create) (mandatory) (2 bytes)"
        REFERENCE   "G.983.2 section 7.3.106 SIP User Data"
        ::= { zxGponSIPUserDataEntry 4 }

    zxGponSIPUserDataPassword OBJECT-TYPE
        SYNTAX      OCTET STRING(SIZE(0..25))
        MAX-ACCESS  read-write
        STATUS      current
        DESCRIPTION
        "A pointer to an Authentication Security Method ME that contains a SIP user name and password used
        for authentication.  0xFFFF indicates no username/password. (R, W, Set-by-create) (mandatory) (2 bytes)"
        REFERENCE   "G.983.2 section 7.3.106 SIP User Data"
        ::= { zxGponSIPUserDataEntry 5 }

    zxGponSIPUserDataVMailServerURI OBJECT-TYPE
        SYNTAX      OCTET STRING(SIZE(0..128))
        MAX-ACCESS  read-write
        STATUS      current
        DESCRIPTION
        "This attribute provides a pointer to a Network Address ME that contains the name (IP address or URI)
        of the SIP Voice Mail Server for SIP signaling messages.  A value of  0xFFFF indicates that no
        Voice Mail subscription is required. Default value is 0xFFFF. (R, W, Set by Create) (mandatory) (2 bytes)"
        REFERENCE   "G.983.2 section 7.3.106 SIP User Data"
        ::= { zxGponSIPUserDataEntry 6 }

    zxGponSIPUserDataVMailValidateScheme OBJECT-TYPE
        SYNTAX      INTEGER{
                    disable(1),
                    md5(2),
                    basic(3)
                    }
        MAX-ACCESS  read-write
        STATUS      current
        DESCRIPTION
        ""
        REFERENCE   "G.983.2 section 7.3.106 SIP User Data"
        ::= { zxGponSIPUserDataEntry 7 }

    zxGponSIPUserDataVMailUserName OBJECT-TYPE
        SYNTAX      OCTET STRING(SIZE(0..25))
        MAX-ACCESS  read-write
        STATUS      current
        DESCRIPTION
        ""
        REFERENCE   "G.983.2 section 7.3.106 SIP User Data"
        ::= { zxGponSIPUserDataEntry 8 }

    zxGponSIPUserDataVMailPassword OBJECT-TYPE
        SYNTAX      OCTET STRING(SIZE(0..25))
        MAX-ACCESS  read-write
        STATUS      current
        DESCRIPTION
        ""
        REFERENCE   "G.983.2 section 7.3.106 SIP User Data"
        ::= { zxGponSIPUserDataEntry 9 }

    zxGponSIPUserDataVMailRealm OBJECT-TYPE
        SYNTAX      OCTET STRING(SIZE(0..25))
        MAX-ACCESS  read-write
        STATUS      current
        DESCRIPTION
        ""
        REFERENCE   "G.983.2 section 7.3.106 SIP User Data"
        ::= { zxGponSIPUserDataEntry 10 }

    zxGponSIPUserDataVMailSubsciptExpTime OBJECT-TYPE
        SYNTAX      INTEGER
        MAX-ACCESS  read-write
        STATUS      current
        DESCRIPTION
        "This attribute defines the Voice Mail server subscription  Expiration Time in seconds.
        If this value is zero, the SIP Agent will use the implementation specific default for this ONT/ONU.
        The default value used at Create shall be 3600 seconds. (R, W, Set-by-create) (mandatory) (4 bytes)"
        REFERENCE   "G.983.2 section 7.3.106 SIP User Data"
        ::= { zxGponSIPUserDataEntry 11 }

    zxGponSIPUserDataNetworkDialPlanPtr OBJECT-TYPE
        SYNTAX      INTEGER
        MAX-ACCESS  read-write
        STATUS      current
        DESCRIPTION
        "Pointer to Network Dial Plan ME. A value of 0xFFFF indicates that no network dial plan is available.
        Default value is 0xFFFF. (R, W, Set-by-create) (mandatory) (2 bytes)"
        REFERENCE   "G.983.2 section 7.3.106 SIP User Data"
        ::= { zxGponSIPUserDataEntry 12 }

    zxGponSIPUserDataServiceProfilePtr OBJECT-TYPE
        SYNTAX      INTEGER
        MAX-ACCESS  read-write
        STATUS      current
        DESCRIPTION
        "Pointer to Application Services Profile ME. A value of 0xFFFF indicates that no Application
        Services Profile is available. Default value is 0xFFFF. (R, W, Set-by-create) (mandatory) (2 bytes)"
        REFERENCE   "G.983.2 section 7.3.106 SIP User Data"
        ::= { zxGponSIPUserDataEntry 13 }

    zxGponSIPUserDataFeatureCodePtr OBJECT-TYPE
        SYNTAX      INTEGER
        MAX-ACCESS  read-write
        STATUS      current
        DESCRIPTION
        "This attribute contains a pointer to the Feature Access Codes ME for this subscriber.
        A value of 0xFFFF indicates that no Feature Access Codes ME is available. Default value
        is 0xFFFF. (R, W, Set-by-create) (mandatory) (2 bytes)"
        REFERENCE   "G.983.2 section 7.3.106 SIP User Data"
        ::= { zxGponSIPUserDataEntry 14 }

    zxGponSIPUserDataReleaseTimer OBJECT-TYPE
        SYNTAX      INTEGER
        MAX-ACCESS  read-write
        STATUS      current
        DESCRIPTION
        "This attribute contains a release timer defined in seconds. 0x0 = Use internal default,
        Default value is 10 sec. (R, W) (optional)(1 byte)"
        REFERENCE   "G.983.2 section 7.3.106 SIP User Data"
        ::= { zxGponSIPUserDataEntry 15 }

    zxGponSIPUserDataROHTimer OBJECT-TYPE
        SYNTAX      INTEGER
        MAX-ACCESS  read-write
        STATUS      current
        DESCRIPTION
        "This attribute defines the length of time in seconds for the receiver off hook condition before
        ROH tone is applied. 0x0 = ROH is disabled. Default value is 15 seconds. (R,W) (optional) (1 byte)"
        REFERENCE   "G.983.2 section 7.3.106 SIP User Data"
        ::= { zxGponSIPUserDataEntry 16 }

    zxGponSIPUserDataEntryStatus OBJECT-TYPE
        SYNTAX      RowStatus
        MAX-ACCESS  read-write
        STATUS      current
        DESCRIPTION
        ""
        REFERENCE   "G.983.2 section 7.3.106 SIP User Data"
        ::= { zxGponSIPUserDataEntry 17 }

--VoIP Voice CTP
    zxGponVoIPVoiceCTPTable    OBJECT-TYPE
        SYNTAX      SEQUENCE OF ZxGponVoIPVoiceCTPEntry
        MAX-ACCESS  not-accessible
        STATUS      current
        DESCRIPTION
            "An instance of this managed entity refers to one PPTP POTS UNI managed entity, one VoIP Media Profile, and one SIP User Data managed entity or MGC Config Data ME."
        REFERENCE   "G.983.2 section 7.3.110 VoIP Voice CTP"
        ::= { zxGponRmVoiceMgmt 5 }

    zxGponVoIPVoiceCTPEntry OBJECT-TYPE
        SYNTAX      ZxGponVoIPVoiceCTPEntry
        MAX-ACCESS  not-accessible
        STATUS      current
        DESCRIPTION
            "It is entry in the zxGponVoIPVoiceCTPTable."
        INDEX   { zxGponOltIndex, zxGponONTIndex, zxGponUNIIndex }
        ::= { zxGponVoIPVoiceCTPTable 1 }

    ZxGponVoIPVoiceCTPEntry ::=
        SEQUENCE {
            zxGponVoIPVoiceCTPMediaProfilePtr         INTEGER,
            zxGponVoIPVoiceCTPSignalCode              INTEGER,
            zxGponVoIPVoiceCTPEntryStatus             RowStatus,
            zxGponVoIPVoiceCTPMGCId                   INTEGER
        }

    zxGponVoIPVoiceCTPMediaProfilePtr OBJECT-TYPE
        SYNTAX      INTEGER
        MAX-ACCESS  read-write
        STATUS      current
        DESCRIPTION
        "Pointer to VOIP Media Profile.  (R, W, Set-by-create) (mandatory) (2 bytes)"
        REFERENCE   "G.983.2 section 7.3.110 VoIP Voice CTP"
        ::= { zxGponVoIPVoiceCTPEntry 1 }

    zxGponVoIPVoiceCTPSignalCode OBJECT-TYPE
        SYNTAX      INTEGER{
                    loop-start(1),
                    ground-start(2),
                    loop-reverse-battery(3),
                    coin-first(4),
                    dial-tone-first(5),
                    multi-party(6)
                    }
        MAX-ACCESS  read-write
        STATUS      current
        DESCRIPTION
        "This attribute specifies whether 'loop start' (0x01), 'ground start' (0x02),
        'loop reverse battery' (0x03), 'coin first' (0x04), 'dial tone first' (0x05),
        or 'multi-party' (0x06) signaling is employed.  (R, Set-by-create) (mandatory) (1 byte)"
        REFERENCE   "G.983.2 section 7.3.110 VoIP Voice CTP"
        ::= { zxGponVoIPVoiceCTPEntry 2 }

    zxGponVoIPVoiceCTPEntryStatus OBJECT-TYPE
        SYNTAX      RowStatus
        MAX-ACCESS  read-write
        STATUS      current
        DESCRIPTION
        ""
        REFERENCE   "G.983.2 section 7.3.110 VoIP Voice CTP"
        ::= { zxGponVoIPVoiceCTPEntry 3 }

    zxGponVoIPVoiceCTPMGCId OBJECT-TYPE
        SYNTAX      INTEGER
        MAX-ACCESS  read-write
        STATUS      current
        DESCRIPTION
        "This attribute specifies the id of MGC related with POTS UNI.
        It's used when VoIP protocol is H.248."
        REFERENCE   "G.983.2 section 7.3.110 VoIP Voice CTP"
        ::= { zxGponVoIPVoiceCTPEntry 4 }

--VoIP line status
    zxGponVoIPLineStatusTable    OBJECT-TYPE
        SYNTAX      SEQUENCE OF ZxGponVoIPLineStatusEntry
        MAX-ACCESS  not-accessible
        STATUS      current
        DESCRIPTION
            "An instance of this managed entity is associated with a PPTP POTS UNI."
        REFERENCE   "G.984.4"
        ::= { zxGponRmVoiceMgmt 6 }

    zxGponVoIPLineStatusEntry OBJECT-TYPE
        SYNTAX      ZxGponVoIPLineStatusEntry
        MAX-ACCESS  not-accessible
        STATUS      current
        DESCRIPTION
            "It is entry in the zxGponVoIPLineStatusTable."
        INDEX   { zxGponOltIndex, zxGponONTIndex, zxGponUNIIndex }
        ::= { zxGponVoIPLineStatusTable 1 }

    ZxGponVoIPLineStatusEntry ::=
        SEQUENCE {
            zxGponVoIPLineStatusCodecUsed                 INTEGER,
            zxGponVoIPLineStatusVoiceServerStatus         INTEGER,
            zxGponVoIPLineStatusPortSessionType           INTEGER,
            zxGponVoIPLineStatusCall1PktPeriod            INTEGER,
            zxGponVoIPLineStatusCall2PktPeriod            INTEGER,
            zxGponVoIPLineStatusCall1DstAddr              OCTET STRING,
            zxGponVoIPLineStatusCall2DstAddr              OCTET STRING
        }

    zxGponVoIPLineStatusCodecUsed OBJECT-TYPE
        SYNTAX      INTEGER{
                    auto-select(1),
                    g711-a-law(2),
                    g711-mu-law(3),
                    g723(4),
                    g722-1(5),
                    g722-2(6),
                    g723-1(7),
                    g726(8),
                    g728(9),
                    g729-a(10),
                    g729-b(11),
                    g729-d(12),
                    g729-e(13),
                    melp(14)
                    }
        MAX-ACCESS  read-only
        STATUS      current
        DESCRIPTION
        "Reports the current codec used for a VoIP POTS port.(2 bytes)"
        REFERENCE   "G.984.4"
        ::= { zxGponVoIPLineStatusEntry 1 }

    zxGponVoIPLineStatusVoiceServerStatus OBJECT-TYPE
        SYNTAX      INTEGER{
                    initial(1),
                    registered(2),
                    insession(3),
                    fail-reg-icmp-err(4),
                    fail-reg-tcp-fail(5),
                    fail-reg-auth-fail(6),
                    fail-reg-timeout(7),
                    fail-reg-server-fail(8),
                    fail-invite-icmp-err(9),
                    fail-invite-tcp-fail(10),
                    fail-invite-auth-fail(11),
                    fail-invite-timeout(12),
                    fail-invite-server-fail(13),
                    port-not-config(14),
                    config-done(15)
                    }
        MAX-ACCESS  read-only
        STATUS      current
        DESCRIPTION
        "Status of the VoIP session for this POTS port(1 byte)"
        REFERENCE   "G.984.4"
        ::= { zxGponVoIPLineStatusEntry 2 }

    zxGponVoIPLineStatusPortSessionType OBJECT-TYPE
        SYNTAX      INTEGER{
                    idle(1),
                    two-way(2),
                    three-way(3),
                    fax(4),
                    telem(5),
                    conference(6)
                    }
        MAX-ACCESS  read-only
        STATUS      current
        DESCRIPTION
        "This attribute reports the current state of a VoIP POTS port session.(1 byte)"
        REFERENCE   "G.984.4"
        ::= { zxGponVoIPLineStatusEntry 3 }

    zxGponVoIPLineStatusCall1PktPeriod OBJECT-TYPE
        SYNTAX      INTEGER
        MAX-ACCESS  read-only
        STATUS      current
        DESCRIPTION
        "This attribute reports the packet period for the first call on the VoIP POTS port.
         The value is defined in milliseconds. (R) (mandatory) (2 bytes)"
        REFERENCE   "G.984.4"
        ::= { zxGponVoIPLineStatusEntry 4 }

    zxGponVoIPLineStatusCall2PktPeriod OBJECT-TYPE
        SYNTAX      INTEGER
        MAX-ACCESS  read-only
        STATUS      current
        DESCRIPTION
        "This attribute reports the packet period for the second call on the VoIP POTS port.
         The value is defined in milliseconds. (R) (mandatory) (2 bytes)"
        REFERENCE   "G.984.4"
        ::= { zxGponVoIPLineStatusEntry 5 }

    zxGponVoIPLineStatusCall1DstAddr OBJECT-TYPE
        SYNTAX      OCTET STRING(SIZE(0..25))
        MAX-ACCESS  read-only
        STATUS      current
        DESCRIPTION
        "This attribute reports the destination address for the first call on the VoIP POTS port.
         The value is an ASCII string. (R) (mandatory) (25 bytes)"
        REFERENCE   "G.984.4"
        ::= { zxGponVoIPLineStatusEntry 6 }

    zxGponVoIPLineStatusCall2DstAddr OBJECT-TYPE
        SYNTAX      OCTET STRING(SIZE(0..25))
        MAX-ACCESS  read-only
        STATUS      current
        DESCRIPTION
        "This attribute reports the destination address for the second call on the VoIP POTS port.
         The value is an ASCII string. (R) (mandatory) (25 bytes)"
        REFERENCE   "G.984.4"
        ::= { zxGponVoIPLineStatusEntry 7 }

--MGC Config Data
    zxGponMGCConfigDataTable    OBJECT-TYPE
        SYNTAX      SEQUENCE OF ZxGponMGCConfigDataEntry
        MAX-ACCESS  not-accessible
        STATUS      current
        DESCRIPTION
            "An instance of this managed entity may be associated with one or
             more VoIP voice CTP managed entities."
        REFERENCE   "G.984.4"
        ::= { zxGponRmVoiceMgmt 7 }

    zxGponMGCConfigDataEntry    OBJECT-TYPE
        SYNTAX      ZxGponMGCConfigDataEntry
        MAX-ACCESS  not-accessible
        STATUS      current
        DESCRIPTION
            "It is entry in the zxGponMGCConfigDataTable."
        INDEX   { zxGponOltIndex, zxGponONTIndex, zxGponMGCConfigDataId }
        ::= { zxGponMGCConfigDataTable 1 }

    ZxGponMGCConfigDataEntry ::=
        SEQUENCE {
            zxGponMGCConfigDataId                       INTEGER,
            zxGponMGCConfigDataPrimaryMGC               OCTET STRING,
            zxGponMGCConfigDataPrimaryValidateScheme    INTEGER,
            zxGponMGCConfigDataPrimaryUsername          OCTET STRING,
            zxGponMGCConfigDataPrimaryPassword          OCTET STRING,
            zxGponMGCConfigDataPrimaryRealm             OCTET STRING,
            zxGponMGCConfigDataSecondaryMGC             OCTET STRING,
            zxGponMGCConfigDataSecondaryValidateScheme  INTEGER,
            zxGponMGCConfigDataSecondaryUsername        OCTET STRING,
            zxGponMGCConfigDataSecondaryPassword        OCTET STRING,
            zxGponMGCConfigDataSecondaryRealm           OCTET STRING,
            zxGponMGCConfigDataTCPUDPPort               INTEGER,
            zxGponMGCConfigDataHostId                   INTEGER,
            zxGponMGCConfigDataVersion                  INTEGER,
            zxGponMGCConfigDataMessageFormat            INTEGER,
            zxGponMGCConfigDataMaxRetryTime             INTEGER,
            zxGponMGCConfigDataMaxRetryAttempts         INTEGER,
            zxGponMGCConfigDataServiceChangeDelay       INTEGER,
            zxGponMGCConfigDataTerminationIDbase        OCTET STRING,
            zxGponMGCConfigDataSSVendor                 OCTET STRING,
            zxGponMGCConfigDataEntryStatus              RowStatus
        }

    zxGponMGCConfigDataId   OBJECT-TYPE
        SYNTAX      INTEGER
        MAX-ACCESS  not-accessible
        STATUS      current
        DESCRIPTION
        "This attribute provides a unique number for each instance of this managed entity.
        (1~n)(R, Set-by-create) (mandatory) (2 bytes)"
        REFERENCE   "G.984.4 section 9.9.16    MGC config data"
        ::= { zxGponMGCConfigDataEntry 1 }

    zxGponMGCConfigDataPrimaryMGC    OBJECT-TYPE
        SYNTAX      OCTET STRING(SIZE(0..128))
        MAX-ACCESS  read-write
        STATUS      current
        DESCRIPTION
        "This attribute points to a network address ME that contains the name (IP address
        or resolved name) of the primary MGC that controls the signalling  messages. The
        port is optional and defaults to 2944 for text message formats and 2955 for binary
        message formats. (R, W, Set-by-create) (mandatory) (2 bytes)"
        REFERENCE   "G.984.4 section 9.9.16    MGC config data"
        ::= { zxGponMGCConfigDataEntry 2 }

    zxGponMGCConfigDataPrimaryValidateScheme OBJECT-TYPE
        SYNTAX      INTEGER{
                    disable(1),
                    md5(2),
                    basic(3)
                    }
        MAX-ACCESS  read-write
        STATUS      current
        DESCRIPTION
        ""
        REFERENCE   ""
        ::= { zxGponMGCConfigDataEntry 3 }

    zxGponMGCConfigDataPrimaryUsername    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 4 }

    zxGponMGCConfigDataPrimaryPassword    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 5 }

    zxGponMGCConfigDataPrimaryRealm    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 6 }

    zxGponMGCConfigDataSecondaryMGC    OBJECT-TYPE
        SYNTAX      OCTET STRING(SIZE(0..128))
        MAX-ACCESS  read-write
        STATUS      current
        DESCRIPTION
        "This attribute points to a network address ME that contains the name (IP address
        or resolved name) of the secondary or backup MGC that controls the signalling
        messages. The port is optional and defaults to 2944 for text message formats and
        2955 for binary message formats. (R, W, Set-by-create) (mandatory) (2 bytes)"
        REFERENCE   "G.984.4 section 9.9.16    MGC config data"
        ::= { zxGponMGCConfigDataEntry 7 }

    zxGponMGCConfigDataSecondaryValidateScheme OBJECT-TYPE
        SYNTAX      INTEGER{
                    disable(1),
                    md5(2),
                    basic(3)
                    }
        MAX-ACCESS  read-write
        STATUS      current
        DESCRIPTION
        ""
        REFERENCE   ""
        ::= { zxGponMGCConfigDataEntry 8 }

    zxGponMGCConfigDataSecondaryUsername    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 9 }

    zxGponMGCConfigDataSecondaryPassword    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 10 }

    zxGponMGCConfigDataSecondaryRealm    OBJECT-TYPE
        SYNTAX      OCTET STRING(SIZE(0..25))
        MAX-ACCESS  read-write
        STATUS      current
        DESCRIPTION
        ""
        REFERENCE   "G.984.4 section 9.9.16    MGC config data"
        ::= { zxGponMGCConfigDataEntry 11 }

    zxGponMGCConfigDataTCPUDPPort    OBJECT-TYPE
        SYNTAX      INTEGER
        MAX-ACCESS  read-write
        STATUS      current
        DESCRIPTION
        "This attribute specifies the port(1~65535) of TCP/UDP used for communication
        with the MGC. (R, W, Set-by-create) (mandatory) (2 bytes)"
        REFERENCE   "G.984.4 section 9.9.16    MGC config data"
        ::={ zxGponMGCConfigDataEntry 12 }

      zxGponMGCConfigDataHostId OBJECT-TYPE
        SYNTAX      INTEGER
        MAX-ACCESS  read-write
        STATUS      current
        DESCRIPTION
        ""
        REFERENCE   ""
        ::= { zxGponMGCConfigDataEntry 13 }

    zxGponMGCConfigDataVersion    OBJECT-TYPE
        SYNTAX      INTEGER
        MAX-ACCESS  read-write
        STATUS      current
        DESCRIPTION
        "This integer attribute reports the version(1~255) of the Megaco protocol in use.
        (R, W, Set-by-create) (mandatory) (1 byte)"
        REFERENCE   "G.984.4 section 9.9.16    MGC config data"
        ::={ zxGponMGCConfigDataEntry 14 }

    zxGponMGCConfigDataMessageFormat    OBJECT-TYPE
        SYNTAX      INTEGER{
                    text-long(1),
                    text-short(2),
                    binary(3)
                    }
        MAX-ACCESS  read-write
        STATUS      current
        DESCRIPTION
        "This attribute defines the message format. Valid values are:
        0    Text long
        1    Text short
        2    Binary
        The default value is 0. (R, W, Set-by-create) (mandatory) (1 byte)"
        REFERENCE   "G.984.4 section 9.9.16    MGC config data"
        ::={ zxGponMGCConfigDataEntry 15 }

    zxGponMGCConfigDataMaxRetryTime    OBJECT-TYPE
        SYNTAX      INTEGER
        MAX-ACCESS  read-write
        STATUS      current
        DESCRIPTION
        "This attribute specifies the maximum retry time for MGC transactions, in seconds.
        The default value 0 specifies vendor-specific implementation (R, W) (optional) (2 bytes)"
        REFERENCE   "G.984.4 section 9.9.16    MGC config data"
        ::={ zxGponMGCConfigDataEntry 16 }

    zxGponMGCConfigDataMaxRetryAttempts    OBJECT-TYPE
        SYNTAX      INTEGER
        MAX-ACCESS  read-write
        STATUS      current
        DESCRIPTION
        "This attribute specifies the maximum number of times a message is retransmitted
        to the MGC. The default value 0 specifies vendor-specific implementation
        (R, W, Set-by-create) (optional) (2 bytes)"
        REFERENCE   "G.984.4 section 9.9.16    MGC config data"
        ::={ zxGponMGCConfigDataEntry 17 }

    zxGponMGCConfigDataServiceChangeDelay    OBJECT-TYPE
        SYNTAX      INTEGER
        MAX-ACCESS  read-write
        STATUS      current
        DESCRIPTION
        "The attribute specifies the service status delay time for changes in line service
        status. This attribute is specified in seconds. The default value 0 specifies no
        delay. (R, W) (optional) (2 bytes)"
        REFERENCE   "G.984.4 section 9.9.16    MGC config data"
        ::={ zxGponMGCConfigDataEntry 18 }

    zxGponMGCConfigDataTerminationIDbase   OBJECT-TYPE
        SYNTAX      OCTET STRING (SIZE(0..25))
        MAX-ACCESS  read-write
        STATUS      current
        DESCRIPTION
        "The attribute specifies the base string for the H.248 physical termination id(s)
        for this ONT. This string is intended to uniquely identify an ONT. Vendor specific
        termination identifiers (i.e. port ids) are optionally added to this string to
        uniquely identify a termination on a specific ONT. (R, W) (optional) (25 bytes)"
        REFERENCE   "G.984.4 section 9.9.16    MGC config data"
        ::={ zxGponMGCConfigDataEntry 19 }

    zxGponMGCConfigDataSSVendor   OBJECT-TYPE
        SYNTAX      OCTET STRING (SIZE(0..4))
        MAX-ACCESS  read-write
        STATUS      current
        DESCRIPTION
        "This attribute identifies the gateway softswitch vendor.
         The format is four ASCII coded alphabetic characters [A..Z] as defined in ANSI T1.220.
         A value of four null characters indicates no particular vendor. (R, W, Set-by-create) (mandatory) (4 bytes)"
        REFERENCE   "G.984.4 section 9.9.16    MGC config data"
        ::={ zxGponMGCConfigDataEntry 20 }

    zxGponMGCConfigDataEntryStatus OBJECT-TYPE
        SYNTAX      RowStatus
        MAX-ACCESS  read-write
        STATUS      current
        DESCRIPTION
        "This attribute specifies the action of this entry."
        REFERENCE   "G.984.4 section 9.9.16    MGC config data"
        ::= { zxGponMGCConfigDataEntry 21 }
--SIP User
    zxGponSipUserTable    OBJECT-TYPE
        SYNTAX      SEQUENCE OF ZxGponSipUserEntry
        MAX-ACCESS  not-accessible
        STATUS      current
        DESCRIPTION
            "This table includes sip user configuration."
        ::= { zxGponRmVoiceMgmt 8 }

    zxGponSipUserEntry OBJECT-TYPE
        SYNTAX      ZxGponSipUserEntry
        MAX-ACCESS  not-accessible
        STATUS      current
        DESCRIPTION
            "It is entry in the zxGponSipUserTable."
        INDEX   { zxGponOltIndex, zxGponONTIndex, zxGponUNIIndex }
        ::= { zxGponSipUserTable 1 }

    ZxGponSipUserEntry ::=
        SEQUENCE {
            zxGponSipUserProfileId                             Integer32,
            zxGponSipUserPartAor                               OCTET STRING,
            zxGponSipUsername                                  OCTET STRING,
            zxGponSipUserPassword                              OCTET STRING,
            zxGponSipUserDisplayName                           OCTET STRING,
            zxGponSipUserVMailServerUri                        OCTET STRING,
            zxGponSipUserVMailValidScheme                      INTEGER,
            zxGponSipUserVMailUsername                         OCTET STRING,
            zxGponSipUserVMailPassword                         OCTET STRING,
            zxGponSipUserVMailRealm                            OCTET STRING,
            zxGponSipUserVMailSubsExpTime                      INTEGER,
            zxGponSipUserMediaProfile                          Integer32,
            zxGponSipUserVoiceCTPSignalCode                    INTEGER,
            zxGponSipUserRowStatus                             RowStatus
        }

    zxGponSipUserProfileId OBJECT-TYPE
        SYNTAX      Integer32
        MAX-ACCESS  read-create
        STATUS      current
        DESCRIPTION
        "This object indicates the profile ID."
        ::= { zxGponSipUserEntry 1 }

    zxGponSipUserPartAor OBJECT-TYPE
        SYNTAX      OCTET STRING(SIZE(0..128))
        MAX-ACCESS  read-create
        STATUS      current
        DESCRIPTION
        "This attribute points to a large string that contains the user
         identification part of the address of record. This can take the
         form of an alphanumeric string or the subscriber's directory
         number. The value 0xFFFF is a null pointer. (R, W, Set-by-create)
         (mandatory) (2 bytes)"
        REFERENCE   "G984.4 section 9.9.2"
        ::= { zxGponSipUserEntry 2 }

    zxGponSipUsername OBJECT-TYPE
        SYNTAX      OCTET STRING(SIZE(0..50))
        MAX-ACCESS  read-create
        STATUS      current
        DESCRIPTION
        "This string attribute is the user name."
        REFERENCE   "G984.4 section 9.12.4"
        ::= { zxGponSipUserEntry 3 }

    zxGponSipUserPassword OBJECT-TYPE
        SYNTAX      OCTET STRING(SIZE(0..25))
        MAX-ACCESS  read-create
        STATUS      current
        DESCRIPTION
        "This string attribute is the password. If the string is shorter than
         25 bytes, it must be null terminated. (R, W) (mandatory) (25 bytes)"
        REFERENCE   "G984.4 section 9.12.4"
        ::= { zxGponSipUserEntry 4 }

    zxGponSipUserDisplayName OBJECT-TYPE
        SYNTAX      OCTET STRING(SIZE(0..25))
        MAX-ACCESS  read-create
        STATUS      current
        DESCRIPTION
        "This attribute defines the Customer ID used for outgoing SIP
         messages display attribute in ASCII string format.Default value
         shall be null (all zeros).  (R, W) (mandatory) (25 bytes)"
        REFERENCE   "G984.4 section 9.9.2"
        ::= { zxGponSipUserEntry 5 }

    zxGponSipUserVMailServerUri OBJECT-TYPE
        SYNTAX      OCTET STRING(SIZE(0..128))
        MAX-ACCESS  read-create
        STATUS      current
        DESCRIPTION
        "This attribute provides a pointer to a Network Address ME that
         contains the name (IP address or URI) of the SIP Voice Mail
         Server for SIP signaling messages.  A value of  0xFFFF
         indicates that no Voice Mail subscription is required. Default
         value is 0xFFFF. (R, W, Set by Create) (mandatory) (2 bytes)"
        REFERENCE   "G.983.2 section 7.3.106 SIP User Data"
        ::= { zxGponSipUserEntry 6 }

    zxGponSipUserVMailValidScheme OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL {disable}
        ::= { zxGponSipUserEntry 7 }

    zxGponSipUserVMailUsername OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponSipUserEntry 8 }

    zxGponSipUserVMailPassword OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponSipUserEntry 9 }

    zxGponSipUserVMailRealm OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponSipUserEntry 10 }

    zxGponSipUserVMailSubsExpTime OBJECT-TYPE
        SYNTAX      INTEGER(0..2147483647)
        UNITS       "s"
        MAX-ACCESS  read-create
        STATUS      current
        DESCRIPTION
        "This attribute defines the Voice Mail server subscription
         Expiration Time in seconds. If this value is zero, the
         SIP Agent will use the implementation specific default for
         this ONT/ONU. The default value used at Create shall be
         3600 seconds. (R, W, Set-by-create) (mandatory) (4 bytes)"
        REFERENCE   "G984.4 section 9.9.2"
        DEFVAL {3600}
        ::= { zxGponSipUserEntry 11 }

    zxGponSipUserMediaProfile OBJECT-TYPE
        SYNTAX      Integer32
        MAX-ACCESS  read-create
        STATUS      current
        DESCRIPTION
            "This attribute refers to the name of table
            'zxGponVoIPMediaProfileTable'."
        ::= { zxGponSipUserEntry 12 }

    zxGponSipUserVoiceCTPSignalCode OBJECT-TYPE
        SYNTAX      INTEGER{
                    loop-start(1),
                    ground-start(2),
                    loop-reverse-battery(3),
                    coin-first(4),
                    dial-tone-first(5),
                    multi-party(6)
                    }
        MAX-ACCESS  read-create
        STATUS      current
        DESCRIPTION
            "This attribute specifies whether
            'loop start' (0x01),
            'ground start' (0x02),
            'loop reverse battery' (0x03),
            'coin first' (0x04),
            'dial tone first' (0x05),
            'multi-party' (0x06) signaling is employed.  (R, Set-by-create) (mandatory) (1 byte)"
        REFERENCE   "G.983.2 section 7.3.110 VoIP Voice CTP"
        ::= { zxGponSipUserEntry 13 }

    zxGponSipUserRowStatus OBJECT-TYPE
        SYNTAX      RowStatus
        MAX-ACCESS  read-create
        STATUS      current
        DESCRIPTION "The row status of this entry."
        ::= { zxGponSipUserEntry 30 }

--MGC User
    zxGponMgcUserTable    OBJECT-TYPE
        SYNTAX      SEQUENCE OF ZxGponMgcUserEntry
        MAX-ACCESS  not-accessible
        STATUS      current
        DESCRIPTION
            "This table includes mgc user configuration."
        REFERENCE   ""
        ::= { zxGponRmVoiceMgmt 9 }

    zxGponMgcUserEntry OBJECT-TYPE
        SYNTAX      ZxGponMgcUserEntry
        MAX-ACCESS  not-accessible
        STATUS      current
        DESCRIPTION
            "It is entry in the zxGponMGCTable."
        INDEX   { zxGponOltIndex, zxGponONTIndex, zxGponUNIIndex }
        ::= { zxGponMgcUserTable 1 }

    ZxGponMgcUserEntry ::=
        SEQUENCE {
            zxGponMgcUserProfileId                             Integer32,
            zxGponMgcUserMediaProfile                          Integer32,
            zxGponMgcUserVoiceCTPSignalCode                    INTEGER,
            zxGponMgcUserRowStatus                             RowStatus
        }

    zxGponMgcUserProfileId OBJECT-TYPE
        SYNTAX      Integer32
        MAX-ACCESS  read-create
        STATUS      current
        DESCRIPTION "This Object indicates the MGC Profile index."
        ::= { zxGponMgcUserEntry 1 }

    zxGponMgcUserMediaProfile OBJECT-TYPE
        SYNTAX      Integer32
        MAX-ACCESS  read-create
        STATUS      current
        DESCRIPTION
            "This attribute refers to the name of table
            'zxGponVoIPMediaProfileTable'."
        ::= { zxGponMgcUserEntry 2 }

    zxGponMgcUserVoiceCTPSignalCode OBJECT-TYPE
        SYNTAX      INTEGER{
                    loop-start(1),
                    ground-start(2),
                    loop-reverse-battery(3),
                    coin-first(4),
                    dial-tone-first(5),
                    multi-party(6)
                    }
        MAX-ACCESS  read-create
        STATUS      current
        DESCRIPTION
            "This attribute specifies whether
            'loop start' (0x01),
            'ground start' (0x02),
            'loop reverse battery' (0x03),
            'coin first' (0x04),
            'dial tone first' (0x05),
            'multi-party' (0x06) signaling is employed.  (R, Set-by-create) (mandatory) (1 byte)"
        REFERENCE   "G.983.2 section 7.3.110 VoIP Voice CTP"
        ::= { zxGponMgcUserEntry 3 }

    zxGponMgcUserRowStatus OBJECT-TYPE
        SYNTAX      RowStatus
        MAX-ACCESS  read-create
        STATUS      current
        DESCRIPTION "The row status of this entry."
        ::= { zxGponMgcUserEntry 30 }


    --POTS UNI Test
    zxGponPotsTestTable    OBJECT-TYPE
        SYNTAX      SEQUENCE OF ZxGponPotsTestEntry
        MAX-ACCESS  not-accessible
        STATUS      current
        DESCRIPTION
            "It is table for ONU UNI POTS test."
        REFERENCE   "G.984.4 "
        ::= { zxGponRmVoiceMgmt 10 }

    zxGponPotsTestEntry OBJECT-TYPE
        SYNTAX      ZxGponPotsTestEntry
        MAX-ACCESS  not-accessible
        STATUS      current
        DESCRIPTION
            "It is entry in the zxGponPotsTestTable."
        INDEX   { zxGponOltIndex, zxGponONTIndex, zxGponUNIIndex }
        ::= { zxGponPotsTestTable 1 }

    ZxGponPotsTestEntry ::=
        SEQUENCE {
            zxGponPotsTestMode              INTEGER,
            zxGponPotsTestItem              INTEGER,
            zxGponPotsTestAction            INTEGER
        }

    zxGponPotsTestMode OBJECT-TYPE
        SYNTAX      INTEGER{
                      normal(1),
                      force(2)
                    }
        MAX-ACCESS  read-write
        STATUS      current
        DESCRIPTION
            "The test mode are defined as described below
             normal(1) -- deny test if line busy
             force(2) -- forced mode
            "
        DEFVAL { normal }
        ::= { zxGponPotsTestEntry 1 }

    zxGponPotsTestItem OBJECT-TYPE
        SYNTAX      INTEGER{
                    allMltTests(1),
                    hazardousPotential(2),
                    foreignEmf(3),
                    resistiveFaults(4),
                    receiverOffHook(5),
                    ringer(6),
                    nt1DcSignatureTest(7),
                    selfTest(8),
                    dialToneMakeBreakTest(9),
                    lineCapacity(10),
                    battery(11),
                    loopCurrent(12),
                    ringVoltage(13),
                    outlineResistance(14),
                    outlineVoltage(15)
                    }
        MAX-ACCESS  read-write
        STATUS      current
        DESCRIPTION
            "POTS test item as described below
            allMltTests -- all MLT tests
            hazardousPotential -- hazardous potential
            foreignEmf -- foreign EMF
            resistiveFaults -- resistive faults
            receiverOffHook -- receiver off-hook
            ringer -- ring test
            nt1DcSignatureTest -- NT1 dc signature test
            selfTest -- self test
            dialToneMakeBreakTest -- dial tone make-break test
            lineCapacity -- outline capacity test
            battery -- feed voltage test
            loopCurrent -- loop current test
            ringVoltage -- ring voltage
            outlineResistance -- outline resistance test
            outlineVoltage -- outline voltage test
            "
        ::= { zxGponPotsTestEntry 2 }

    zxGponPotsTestAction OBJECT-TYPE
        SYNTAX      INTEGER{
                      start(1),
                      stop(2)
                    }
        MAX-ACCESS  read-write
        STATUS      current
        DESCRIPTION
            "The test action are defined as described below
               start -- start test
               stop -- stop test
             Before start action,need to ensure that zxGponPotsTestStatus
             is not in 'inProgress' state. "
        ::= { zxGponPotsTestEntry 3 }

    --POTS UNI Test Result
    zxGponPotsTestResultTable    OBJECT-TYPE
        SYNTAX      SEQUENCE OF ZxGponPotsTestResultEntry
        MAX-ACCESS  not-accessible
        STATUS      current
        DESCRIPTION
            "It is table for ONU UNI POTS test result."
        REFERENCE   "G.984.4 "
        ::= { zxGponRmVoiceMgmt 11 }

    zxGponPotsTestResultEntry OBJECT-TYPE
        SYNTAX      ZxGponPotsTestResultEntry
        MAX-ACCESS  not-accessible
        STATUS      current
        DESCRIPTION
            "It is entry in the zxGponPotsTestResultTable."
        INDEX   { zxGponOltIndex, zxGponONTIndex, zxGponUNIIndex }
        ::= { zxGponPotsTestResultTable 1 }

    ZxGponPotsTestResultEntry ::=
        SEQUENCE {
            zxGponPotsTestStatus       INTEGER,
            zxGponPotsTestResult       DisplayString
        }

    zxGponPotsTestStatus OBJECT-TYPE
        SYNTAX      INTEGER{
                    notStarted(1),
                    inProgress(2),
                    success(3),
                    failed(4)
                    }
        MAX-ACCESS  read-only
        STATUS      current
        DESCRIPTION
            "The status of POTS UNI test."
        ::= { zxGponPotsTestResultEntry 1 }

    zxGponPotsTestResult OBJECT-TYPE
        SYNTAX      DisplayString
        MAX-ACCESS  read-only
        STATUS      current
        DESCRIPTION
            "The result of POTS UNI Test which returns in text format."
        ::= { zxGponPotsTestResultEntry 2 }


    --VoIP IP Configuration
    zxGponOnuVoipIpConfigTable    OBJECT-TYPE
        SYNTAX      SEQUENCE OF ZxGponOnuVoipIpConfigEntry
        MAX-ACCESS  not-accessible
        STATUS      current
        DESCRIPTION
            "VoIP IP configuration table."
        ::= { zxGponRmVoiceMgmt 12 }

    zxGponOnuVoipIpConfigEntry OBJECT-TYPE
        SYNTAX      ZxGponOnuVoipIpConfigEntry
        MAX-ACCESS  not-accessible
        STATUS      current
        DESCRIPTION
            "VoIP IP configuration entry.
            Entries in the zxGponOnuVoipIpConfigTable are created and
            deleted using the zxGponOnuVoipIpConfigRowStatus object."
        INDEX   { zxGponOltIndex, zxGponONTIndex, zxGponOnuSlotId,
        zxGponOnuMediaIndex }
        ::= { zxGponOnuVoipIpConfigTable 1 }

    ZxGponOnuVoipIpConfigEntry ::=
        SEQUENCE {
            zxGponOnuSlotId                    Integer32,
            zxGponOnuMediaIndex                INTEGER,
            zxGponOnuVoipIpMode                INTEGER,
            zxGponOnuVoipIpProfile             DisplayString,
            zxGponOnuVoipVlanProfile           DisplayString,
            zxGponOnuVoipHostId                Integer32,
            zxGponOnuVoipOnuIdentifier         DisplayString,
            zxGponOnuVoipIpAddrType            InetAddressType,
            zxGponOnuVoipIpAddr                InetAddress,
            zxGponOnuVoipIpAddrPfxLen          InetAddressPrefixLength,
            zxGponOnuVoipPppoeMode             INTEGER,
            zxGponOnuVoipPppoeUserName         DisplayString,
            zxGponOnuVoipPppoePassWord         DisplayString,
            zxGponOnuVoipCurrentIpAddrType     InetAddressType,
            zxGponOnuVoipCurrentIpAddr         InetAddress,
            zxGponOnuVoipCurrentIpAddrPfxLen   InetAddressPrefixLength,
            zxGponOnuVoipCurrentGatewayType    InetAddressType,
            zxGponOnuVoipCurrentGateway        InetAddress,
            zxGponOnuVoipCurrentPriDnsType     InetAddressType,
            zxGponOnuVoipCurrentPriDns         InetAddress,
            zxGponOnuVoipCurrentSecDnsType     InetAddressType,
            zxGponOnuVoipCurrentSecDns         InetAddress,
            zxGponOnuVoipDomainName            DisplayString,
            zxGponOnuVoipHostName              DisplayString,
            zxGponOnuVoipMacAddress            MacAddress,
            zxGponOnuVoipResponsePing          TruthValue,
            zxGponOnuVoipResponseTraceRoute    TruthValue,
            zxGponOnuVoipIpConfigRowStatus     RowStatus
        }

    zxGponOnuSlotId OBJECT-TYPE
        SYNTAX      Integer32(0..16)
        MAX-ACCESS  not-accessible
        STATUS      current
        DESCRIPTION
            "This attribute indicates the index of slot in ONT.
            If slot ID is zero, it means the ONU is box-type,
            which can not plug card."
        ::= { zxGponOnuVoipIpConfigEntry 3}

    zxGponOnuMediaIndex OBJECT-TYPE
        SYNTAX      INTEGER{
                    signalandmedia(1),
                    media(2)
                    }
        MAX-ACCESS  not-accessible
        STATUS      current
        DESCRIPTION
            "This attribute indicates the whether the separation of media
             and signaling.If 'media' is configured,The media will use a
             separation IP address,otherwise media and signaling will share
             the same IP address."
        ::= { zxGponOnuVoipIpConfigEntry 4}

    zxGponOnuVoipIpMode OBJECT-TYPE
        SYNTAX      INTEGER{
                    static(1),
                    dhcp(2),
                    pppoe(3)
                    }
        MAX-ACCESS  read-create
        STATUS      current
        DESCRIPTION
            "IP address configuration mode."
        DEFVAL { static }
        ::= { zxGponOnuVoipIpConfigEntry 5 }

    zxGponOnuVoipIpProfile OBJECT-TYPE
        SYNTAX      DisplayString
        MAX-ACCESS  read-create
        STATUS      current
        DESCRIPTION
            "This attribute refers to the name of table
            'zxGponVoipIpProfileTable'.If no profile name is indicated,
             this attribute is set to a empty string."
        ::= { zxGponOnuVoipIpConfigEntry 6 }

    zxGponOnuVoipVlanProfile OBJECT-TYPE
        SYNTAX      DisplayString
        MAX-ACCESS  read-create
        STATUS      current
        DESCRIPTION
            "This attribute refers to the id of table
            'zxGponVoipVlanProfileTable'.If no profile name is indicated,
             this attribute is set to a null string."
        ::= { zxGponOnuVoipIpConfigEntry 7 }

    zxGponOnuVoipHostId  OBJECT-TYPE
        SYNTAX      Integer32
        MAX-ACCESS  read-create
        STATUS      current
        DESCRIPTION
            "The ONU IP host ID,if no specify this attribute,
            system will used a available IP host id."
        ::= { zxGponOnuVoipIpConfigEntry 8 }

    zxGponOnuVoipOnuIdentifier OBJECT-TYPE
        SYNTAX      DisplayString(SIZE(0..25))
        MAX-ACCESS  read-create
        STATUS      current
        DESCRIPTION
            "This attribute is relation to 'zxGponOnuVoipIpMode'.
            This attribute is valid only when 'zxGponOnuVoipIpMode' is dhcp.
            A unique ONU identifier string. If set to a non-null value,
            this string is used instead of the MAC address in retrieving
            DHCP parameters. If the string is shorter than 25 characters,
            it must be null terminated. Its default value is null bytes."
        REFERENCE   "G.988 section 9.4.1 IP host config data"
        ::= { zxGponOnuVoipIpConfigEntry 9 }

     zxGponOnuVoipIpAddrType     OBJECT-TYPE
        SYNTAX      InetAddressType
        MAX-ACCESS  read-create
        STATUS      current
        DESCRIPTION
            "The type of IP address denoted
             in zxGponOnuVoipIpAddr object."
        DEFVAL { ipv4 }
        ::= { zxGponOnuVoipIpConfigEntry 10 }

    zxGponOnuVoipIpAddr     OBJECT-TYPE
        SYNTAX      InetAddress
        MAX-ACCESS  read-create
        STATUS      current
        DESCRIPTION
            "This attribute is relation to 'zxGponOnuVoipIpMode'.
            This attribute is valid only when 'zxGponOnuVoipIpMode'
            is static."
        ::= { zxGponOnuVoipIpConfigEntry 11 }

    zxGponOnuVoipIpAddrPfxLen     OBJECT-TYPE
        SYNTAX      InetAddressPrefixLength
        MAX-ACCESS  read-create
        STATUS      current
        DESCRIPTION
            "VoIP IP address prefix length."
        ::= { zxGponOnuVoipIpConfigEntry 12 }

    zxGponOnuVoipPppoeMode OBJECT-TYPE
        SYNTAX      INTEGER{
                    auto(1),
                    chap(2),
                    pap(3)
                    }
        MAX-ACCESS  read-create
        STATUS      current
        DESCRIPTION
            "This attribute is relation to 'zxGponOnuVoipIpMode'.
            This attribute is valid only when 'zxGponOnuVoipIpMode' is pppoe."
        DEFVAL { auto }
        ::= { zxGponOnuVoipIpConfigEntry 13 }

    zxGponOnuVoipPppoeUserName OBJECT-TYPE
        SYNTAX      DisplayString(SIZE(0..32))
        MAX-ACCESS  read-create
        STATUS      current
        DESCRIPTION
            "This attribute is relation to 'zxGponOnuVoipIpMode'.
            This attribute is valid only when 'zxGponOnuVoipIpMode' is pppoe."
        ::= { zxGponOnuVoipIpConfigEntry 14 }

    zxGponOnuVoipPppoePassWord OBJECT-TYPE
        SYNTAX      DisplayString(SIZE(0..32))
        MAX-ACCESS  read-create
        STATUS      current
        DESCRIPTION
            "This attribute is relation to 'zxGponOnuVoipIpMode'.
            This attribute is valid only when 'zxGponOnuVoipIpMode' is pppoe."
        ::= { zxGponOnuVoipIpConfigEntry 15 }

     zxGponOnuVoipCurrentIpAddrType     OBJECT-TYPE
        SYNTAX      InetAddressType
        MAX-ACCESS  read-only
        STATUS      current
        DESCRIPTION
            "The type of IP address denoted
             in zxGponOnuVoipCurrentIpAddr object."
        DEFVAL { ipv4 }
        ::= { zxGponOnuVoipIpConfigEntry 16 }

    zxGponOnuVoipCurrentIpAddr     OBJECT-TYPE
        SYNTAX      InetAddress
        MAX-ACCESS  read-only
        STATUS      current
        DESCRIPTION
            "The current IP address."
        ::= { zxGponOnuVoipIpConfigEntry 17 }

    zxGponOnuVoipCurrentIpAddrPfxLen     OBJECT-TYPE
        SYNTAX      InetAddressPrefixLength
        MAX-ACCESS  read-only
        STATUS      current
        DESCRIPTION
            "The current IP address prefix length."
        ::= { zxGponOnuVoipIpConfigEntry 18 }

     zxGponOnuVoipCurrentGatewayType     OBJECT-TYPE
        SYNTAX      InetAddressType
        MAX-ACCESS  read-only
        STATUS      current
        DESCRIPTION
            "The type of IP address denoted
             in zxGponOnuVoipCurrentGateway object."
        DEFVAL { ipv4 }
        ::= { zxGponOnuVoipIpConfigEntry 19 }

    zxGponOnuVoipCurrentGateway     OBJECT-TYPE
        SYNTAX      InetAddress
        MAX-ACCESS  read-only
        STATUS      current
        DESCRIPTION
            "The current gateway."
        ::= { zxGponOnuVoipIpConfigEntry 20 }

     zxGponOnuVoipCurrentPriDnsType     OBJECT-TYPE
        SYNTAX      InetAddressType
        MAX-ACCESS  read-only
        STATUS      current
        DESCRIPTION
            "The type of IP address denoted
             in zxGponOnuVoipCurrentPriDns object."
        DEFVAL { ipv4 }
        ::= { zxGponOnuVoipIpConfigEntry 21 }

    zxGponOnuVoipCurrentPriDns     OBJECT-TYPE
        SYNTAX      InetAddress
        MAX-ACCESS  read-only
        STATUS      current
        DESCRIPTION
            "The current primary DNS."
        ::= { zxGponOnuVoipIpConfigEntry 22 }

     zxGponOnuVoipCurrentSecDnsType     OBJECT-TYPE
        SYNTAX      InetAddressType
        MAX-ACCESS  read-only
        STATUS      current
        DESCRIPTION
            "The type of IP address denoted
             in zxGponOnuVoipCurrentSecDns object."
        DEFVAL { ipv4 }
        ::= { zxGponOnuVoipIpConfigEntry 23 }

    zxGponOnuVoipCurrentSecDns     OBJECT-TYPE
        SYNTAX      InetAddress
        MAX-ACCESS  read-only
        STATUS      current
        DESCRIPTION
            "The current second DNS."
        ::= { zxGponOnuVoipIpConfigEntry 24 }

    zxGponOnuVoipDomainName OBJECT-TYPE
        SYNTAX      DisplayString(SIZE(0..25))
        MAX-ACCESS  read-only
        STATUS      current
        DESCRIPTION
            "If DHCP indicates a domain name, it is presented here. If no
            domain name is indicated, this attribute is set to a null string.
            If the string is shorter than 25 bytes, it must be null
            terminated. The default value is 25 null bytes."
        REFERENCE   "G.988 section 9.4.1 IP host config data"
        ::= { zxGponOnuVoipIpConfigEntry 25 }

    zxGponOnuVoipHostName OBJECT-TYPE
        SYNTAX      DisplayString(SIZE(0..25))
        MAX-ACCESS  read-only
        STATUS      current
        DESCRIPTION
            "If DHCP indicates a host name, it is presented here. If no host
            name is indicated, this attribute is set to a null string.If the
            string is shorter than 25 bytes, it must be null terminated.
            The default value is 25 null bytes."
        REFERENCE   "G.988 section 9.4.1 IP host config data"
        ::= { zxGponOnuVoipIpConfigEntry 26 }

    zxGponOnuVoipMacAddress     OBJECT-TYPE
        SYNTAX      MacAddress
        MAX-ACCESS  read-only
        STATUS      current
        DESCRIPTION
            "This attribute indicates the MAC address used by the IP node."
        REFERENCE   "G.988 section 9.4.1 IP host config data"
        ::= { zxGponOnuVoipIpConfigEntry 27 }

    zxGponOnuVoipResponsePing OBJECT-TYPE
        SYNTAX      TruthValue
        MAX-ACCESS  read-create
        STATUS      current
        DESCRIPTION
            "This attribute indicates whether respond to pings."
        DEFVAL { false }
        ::= { zxGponOnuVoipIpConfigEntry 28 }

    zxGponOnuVoipResponseTraceRoute OBJECT-TYPE
        SYNTAX      TruthValue
        MAX-ACCESS  read-create
        STATUS      current
        DESCRIPTION
            "This attribute indicates whether respond to trace route."
        DEFVAL { false }
        ::= { zxGponOnuVoipIpConfigEntry 29 }

    zxGponOnuVoipIpConfigRowStatus OBJECT-TYPE
        SYNTAX      RowStatus
        MAX-ACCESS  read-create
        STATUS      current
        DESCRIPTION
            "The status of this conceptual row.

             To create a row in this table, a manager must
             set this object to createAndGo(4).

             To delete a row in this table, a manager must
             set this object to destroy(6). "
        ::= { zxGponOnuVoipIpConfigEntry 50 }

--TDM management

--G.984.4 9.8.1    Physical path termination point CES UNI
    zxGponPptpCESUNITable    OBJECT-TYPE
        SYNTAX      SEQUENCE OF ZxGponPptpCESUNIEntry
        MAX-ACCESS  not-accessible
        STATUS      current
        DESCRIPTION
            "his managed entity represents the point at a CES UNI in the ONT where the
            physical path terminates and physical level functions are performed."
        REFERENCE   "G.984.4 9.8.1    Physical path termination point CES UNI"
        ::= { zxGponRmTDMMgmt 1 }

    zxGponPptpCESUNIEntry OBJECT-TYPE
        SYNTAX      ZxGponPptpCESUNIEntry
        MAX-ACCESS  not-accessible
        STATUS      current
        DESCRIPTION
            "It is entry in the zxGponPptpCESUNITable."
        INDEX   { zxGponOltIndex, zxGponONTIndex, zxGponUNIIndex }
        ::= { zxGponPptpCESUNITable 1 }

    ZxGponPptpCESUNIEntry ::=
        SEQUENCE {
            zxGponPptpCESUNIExpectedType              INTEGER,
            zxGponPptpCESUNISensedType                INTEGER,
            zxGponPptpCESUNILoopback                  INTEGER,
            zxGponPptpCESUNIAdminState                INTEGER,
            zxGponPptpCESUNIOperState                 INTEGER,
            zxGponPptpCESUNIDs1Framing                INTEGER,
            zxGponPptpCESUNIEncoding                  INTEGER,
            zxGponPptpCESUNILineLength                INTEGER,
            zxGponPptpCESUNIDs1Mode                   INTEGER,
            zxGponPptpCESUNIARC                       INTEGER,
            zxGponPptpCESUNIARCInterval               INTEGER,
            zxGponPptpCESUNILineType                  INTEGER
       }

   zxGponPptpCESUNIExpectedType OBJECT-TYPE
        SYNTAX      INTEGER
        MAX-ACCESS  read-write
        STATUS      current
        DESCRIPTION
        "The following coding is used for this attribute:
         0    Autosense
         1 to 254    One of the values from table 9.1.5-1/G.984.4 that is compatible with a CES circuit pack.(1 byte)"
        ::= { zxGponPptpCESUNIEntry 1 }

   zxGponPptpCESUNISensedType OBJECT-TYPE
        SYNTAX      INTEGER
        MAX-ACCESS  read-only
        STATUS      current
        DESCRIPTION
        "If the value of expected type is not 0, then the value of sensed type equals the value of
        expected type. If expected type = 0, then the value of sensed type is one of the compatible
        values from table 9.1.5-1/G.984.4.(1 byte)"
        ::= { zxGponPptpCESUNIEntry 2 }

   zxGponPptpCESUNILoopback OBJECT-TYPE
        SYNTAX      INTEGER{
                    noloop(1),
                    payloadloop(2),
                    lineloop(3),
                    opsloop1(4),
                    opsloop2(5),
                    opsloop3(6),
                    manualloop(7),
                    netloop(8),
                    smartjackloop(9),
                    netlooparmed(10)
                    }
        MAX-ACCESS  read-write
        STATUS      current
        DESCRIPTION
        " This attribute specifies and reports the loopback configuration of the physical interface.(1 byte)"
        ::= { zxGponPptpCESUNIEntry 3 }

   zxGponPptpCESUNIAdminState OBJECT-TYPE
        SYNTAX      INTEGER{
                    unlock(1),
                    lock(2)
                    }
        MAX-ACCESS  read-write
        STATUS      current
        DESCRIPTION
        "This attribute is used to activate (unlock: value 0x00) and deactivate (lock: value 0x01)
        the functions performed by instances of this managed entity.(1 byte)"
        ::= { zxGponPptpCESUNIEntry 4 }

    zxGponPptpCESUNIOperState OBJECT-TYPE
        SYNTAX      INTEGER{
                    enable(1),
                    disable(2)
                    }
        MAX-ACCESS  read-only
        STATUS      current
        DESCRIPTION
        "This attribute indicates whether or not this managed entity is capable of performing
        its task. The operational state reflects the perceived ability to receive or to generate
        a valid signal. Valid values are enabled (0x00) and disabled (0x01).(1 byte)"
        ::= { zxGponPptpCESUNIEntry 5 }

    zxGponPptpCESUNIDs1Framing OBJECT-TYPE
        SYNTAX      INTEGER{
                    extendsuper(1),
                    super(2),
                    unframe(3),
                    g704(4),
                    jtg704(5)
                    }
        MAX-ACCESS  read-write
        STATUS      current
        DESCRIPTION
        "This attribute specifies the DS1 framing structure.(1 byte)"
        ::= { zxGponPptpCESUNIEntry 6 }

    zxGponPptpCESUNIEncoding OBJECT-TYPE
        SYNTAX      INTEGER{
                    b8zs(1),
                    ami(2),
                    hdb3(3),
                    b3zs(4)
                    }
        MAX-ACCESS  read-write
        STATUS      current
        DESCRIPTION
        "This attribute specifies the line coding scheme.(1 byte)"
        ::= { zxGponPptpCESUNIEntry 7 }

    zxGponPptpCESUNILineLength OBJECT-TYPE
        SYNTAX      INTEGER
        MAX-ACCESS  read-write
        STATUS      current
        DESCRIPTION
        "This attribute specifies the length of the twisted pair cable from a DS1
        physical UNI to the DSX-1 cross-connect point or the length of co-axial
        cable from a DS3 physical UNI to the DSX-3 cross-connect point. Valid values
        are given in table 9.8.1-1/G.984.4..(1 byte)"
        ::= { zxGponPptpCESUNIEntry 8 }

    zxGponPptpCESUNIDs1Mode OBJECT-TYPE
        SYNTAX      INTEGER{
                    mode1(1),
                    mode2(2),
                    mode3(3),
                    mode4(4)
                    }
        MAX-ACCESS  read-write
        STATUS      current
        DESCRIPTION
        "This attribute specifies the mode of a DS1.(1 byte)"
        ::= { zxGponPptpCESUNIEntry 9 }

    zxGponPptpCESUNIARC OBJECT-TYPE
        SYNTAX      INTEGER
        MAX-ACCESS  read-write
        STATUS      current
        DESCRIPTION
        "This attribute is used to control alarm reporting from this managed entity. See clause I.1.8/G.984.4.(1 byte)"
        ::= { zxGponPptpCESUNIEntry 10 }

    zxGponPptpCESUNIARCInterval OBJECT-TYPE
        SYNTAX      INTEGER
        MAX-ACCESS  read-write
        STATUS      current
        DESCRIPTION
        "This attribute provides a provisionable length of time. See clause I.1.8/G.984.4.(1 byte)"
        ::= { zxGponPptpCESUNIEntry 11 }

    zxGponPptpCESUNILineType OBJECT-TYPE
        SYNTAX      INTEGER{
                    other(1),
                    ds3m23(2),
                    ds3syntran(3),
                    ds3cbitparity(4),
                    ds3clearchannel(5),
                    e3framed(6),
                    e3plcp(7)
                    }
        MAX-ACCESS  read-write
        STATUS      current
        DESCRIPTION
        "This attribute specifies the line type used in a DS3 or E3 application.(1 byte)"
        ::= { zxGponPptpCESUNIEntry 12 }

--G.984.4 9.8.5    Pseudowire termination point
--G.984.4 9.8.9    Ethernet flow termination point
    zxGponCESoETHConfigTable     OBJECT-TYPE
        SYNTAX      SEQUENCE OF ZxGponCESoETHConfigEntry
        MAX-ACCESS  not-accessible
        STATUS      current
        DESCRIPTION
            "The Ethernet flow termination point contains the attributes necessary
            to originate and terminate Ethernet frames in the ONT. It is appropriate
            when transporting pseudowire services via layer 2. Instances of this managed
            entity are created and deleted by the OLT."
        REFERENCE   "G.984.4 9.8.9    Ethernet flow termination point,9.8.5    Pseudowire termination point"
        ::= { zxGponRmTDMMgmt 2 }

    zxGponCESoETHConfigEntry OBJECT-TYPE
        SYNTAX      ZxGponCESoETHConfigEntry
        MAX-ACCESS  not-accessible
        STATUS      current
        DESCRIPTION
            "It is entry in the zxGponCESoETHConfigTable."
        INDEX   { zxGponOltIndex, zxGponONTIndex, zxGponUNIIndex }
        ::= { zxGponCESoETHConfigTable 1 }

    ZxGponCESoETHConfigEntry ::=
        SEQUENCE {
            zxGponCESoETHBridgeIndex             INTEGER,
            zxGponCESoETHTxPayloadECID           INTEGER,
            zxGponCESoETHTxSignallingECID        INTEGER,
            zxGponCESoETHExpPayloadECID          INTEGER,
            zxGponCESoETHExpSignallingECID       INTEGER,
            zxGponCESoETHRecvPayloadECID         INTEGER,
            zxGponCESoETHRecvSignallingECID      INTEGER,
            zxGponCESoETHTagPolicy               INTEGER,
            zxGponCESoETHVlanTagVal              INTEGER,
            zxGponCESoETHSrcMac                  MacAddress,
            zxGponCESoETHDstMac                  MacAddress,
            zxGponCESoETHLoopback                INTEGER,
            zxGponCESoETHEntryStatus             RowStatus
        }

     zxGponCESoETHBridgeIndex OBJECT-TYPE
        SYNTAX      INTEGER
        MAX-ACCESS  read-write
        STATUS      current
        DESCRIPTION
            "This attribute indicates the index of MAC bridge in ONT, from 1 to M.
            The first byte specifies the slot Id associated with this MAC bridge;
            the second byte specifies the bridge group Id associated with this MAC bridge.(2 bytes)"
        ::= { zxGponCESoETHConfigEntry 1}

     zxGponCESoETHTxPayloadECID OBJECT-TYPE
        SYNTAX      INTEGER
        MAX-ACCESS  read-write
        STATUS      current
        DESCRIPTION
            "reference to Transmit circuit ID in G.984.4 9.8.5    Pseudowire termination point,
            This attribute is a pair of ECID (Ethernet circuit ID)values that the ONT transmits
            in the direction from the TDM termination toward the packet-switched network.
            This is the first value which is used for the payload ECID.(4 bytes)."
        ::= { zxGponCESoETHConfigEntry 2}

    zxGponCESoETHTxSignallingECID     OBJECT-TYPE
        SYNTAX      INTEGER
        MAX-ACCESS  read-write
        STATUS      current
        DESCRIPTION
        "reference to Transmit circuit ID in G.984.4 9.8.5    Pseudowire termination point,
        this is the second which is required only if signalling is to be carried in a distinct channel.
        If signalling is not present, or is carried in the same channel as the payload,
        the second ECID should be set to 0.(4 bytes)."
        ::= { zxGponCESoETHConfigEntry 3}

    zxGponCESoETHExpPayloadECID     OBJECT-TYPE
        SYNTAX      INTEGER
        MAX-ACCESS  read-write
        STATUS      current
        DESCRIPTION
            "reference to Expected circuit ID in G.984.4 9.8.5    Pseudowire termination point,
            This attribute is a pair of ECID (Ethernet circuit ID) values that the ONT can
            expect in the direction from the packet-switched network toward the TDM termination.
            This is the first value which is used for the payload ECID.(4 bytes)."
        ::= { zxGponCESoETHConfigEntry 4}

    zxGponCESoETHExpSignallingECID     OBJECT-TYPE
        SYNTAX      INTEGER
        MAX-ACCESS  read-write
        STATUS      current
        DESCRIPTION
            "reference to Expected circuit ID in G.984.4 9.8.5    Pseudowire termination point,
            This attribute is a pair of ECID (Ethernet circuit ID) values that the ONT can
            expect in the direction from the packet-switched network toward the TDM termination.
            This is the second which is used for the optional separate signalling ECID. In both cases,
            default value 0 indicates that no ECID checking is expected..(4 bytes)."
        ::= { zxGponCESoETHConfigEntry 5}

    zxGponCESoETHRecvPayloadECID     OBJECT-TYPE
        SYNTAX      INTEGER
        MAX-ACCESS  read-only
        STATUS      current
        DESCRIPTION
            "reference to Received circuit ID in G.984.4 9.8.5    Pseudowire termination point,
            This attribute is a pair of ECID (Ethernet circuit ID) values that the ONT can
            expect in the direction from the packet-switched network toward the TDM termination.
            This is the first value which is used for the payload ECID.(4 bytes)."
        ::= { zxGponCESoETHConfigEntry 6}

    zxGponCESoETHRecvSignallingECID     OBJECT-TYPE
        SYNTAX      INTEGER
        MAX-ACCESS  read-only
        STATUS      current
        DESCRIPTION
            "reference to Received circuit ID in G.984.4 9.8.5    Pseudowire termination point,
            This attribute is a pair of ECID (Ethernet circuit ID) values that the ONT can
            expect in the direction from the packet-switched network toward the TDM termination.
            This is the second which is used for the optional separate signalling ECID. In both cases,
            the default value 0 indicates that no ECID checking is expected.(4 bytes)."
        ::= { zxGponCESoETHConfigEntry 7}

    zxGponCESoETHTagPolicy     OBJECT-TYPE
        SYNTAX      INTEGER{
                    untag(1),
                    tag(2)
                    }
        MAX-ACCESS  read-write
        STATUS      current
        DESCRIPTION
        "This attribute specifies the tagging policy to be applied to upstream Ethernet frames.(1 byte)"
        ::= { zxGponCESoETHConfigEntry 8 }

    zxGponCESoETHVlanTagVal     OBJECT-TYPE
        SYNTAX      INTEGER
        MAX-ACCESS  read-write
        STATUS      current
        DESCRIPTION
        "If the tag policy calls for tagging of upstream Ethernet frames, this attribute specifies the tag
        control information, which includes the VLAN tag, P bits and CFI bit. (R, W) (optional) (2 bytes)"
        ::= { zxGponCESoETHConfigEntry 9 }

    zxGponCESoETHSrcMac     OBJECT-TYPE
        SYNTAX      MacAddress
        MAX-ACCESS  read-only
        STATUS      current
        DESCRIPTION
        "This attribute specifies the near-end MAC address. It is established by non-OMCI means (eg factory
        programmed into ONT flash memory) and included here for information only.(R)(mandatory) (6 bytes)"
        ::= { zxGponCESoETHConfigEntry 10 }

    zxGponCESoETHDstMac     OBJECT-TYPE
        SYNTAX      MacAddress
        MAX-ACCESS  read-write
        STATUS      current
        DESCRIPTION
        "This attribute specifies the MAC address of the destination Ethernet frames.
        (R, W, Set-by-create) (mandatory) (6 bytes)"
        ::= { zxGponCESoETHConfigEntry 11 }

    zxGponCESoETHLoopback     OBJECT-TYPE
        SYNTAX      INTEGER{
                    noloopback(1),
                    loopback(2)
                    }
        MAX-ACCESS  read-write
        STATUS      current
        DESCRIPTION
        "This attribute sets the loopback configuration:
        0    No loopback
        1    Loopback of downstream traffic at MAC client(R, W) (mandatory) (1 byte)"
        ::= { zxGponCESoETHConfigEntry 12 }


    zxGponCESoETHEntryStatus OBJECT-TYPE
        SYNTAX      RowStatus
        MAX-ACCESS  read-write
        STATUS      current
        DESCRIPTION
        "This attribute specifies the action of this entry."
        REFERENCE   "G.984.4 9.8.9    Ethernet flow termination point"
        ::= { zxGponCESoETHConfigEntry 20 }

    zxGponCESoIPConfigTable     OBJECT-TYPE
        SYNTAX      SEQUENCE OF ZxGponCESoIPConfigEntry
        MAX-ACCESS  not-accessible
        STATUS      current
        DESCRIPTION
            "The pseudowire termination point supports packetized (rather than TDM) G-PON
             transport of TDM services, transported either directly over Ethernet or over UDP/IP.
             Instances of this managed entity are created and deleted by the OLT.This table is
             the config of transported over UDP/IP"
        REFERENCE   "G.984.4 9.8.5    Pseudowire termination point"
        ::= { zxGponRmTDMMgmt 3 }

    zxGponCESoIPConfigEntry OBJECT-TYPE
        SYNTAX      ZxGponCESoIPConfigEntry
        MAX-ACCESS  not-accessible
        STATUS      current
        DESCRIPTION
            "It is entry in the zxGponCESoIPConfigTable."
        INDEX   { zxGponOltIndex, zxGponONTIndex, zxGponUNIIndex }
        ::= { zxGponCESoIPConfigTable 1 }

    ZxGponCESoIPConfigEntry ::=
        SEQUENCE {
            zxGponCESoIPNearEndIp            INTEGER,
            zxGponCESoIPHostId               INTEGER,
            zxGponCESoIPFarEndIp             OCTET STRING,
            zxGponCESoIPEntryStatus          RowStatus
        }

    zxGponCESoIPNearEndIp     OBJECT-TYPE
        SYNTAX      INTEGER
        MAX-ACCESS  read-write
        STATUS      current
        DESCRIPTION
        "When the pseudowire service is transported via IP, this attribute points to
        an instance of the TCP/UDP config data managed entity. The default value 0 is
        applicable if the pseudowire is not transported via IP. (R, W, Set-by-create)
        (mandatory for IP transport) (2 bytes)"
        ::= { zxGponCESoIPConfigEntry 1 }

    zxGponCESoIPHostId     OBJECT-TYPE
        SYNTAX      INTEGER
        MAX-ACCESS  read-write
        STATUS      current
        DESCRIPTION
        "(2 bytes)"
        ::= { zxGponCESoIPConfigEntry 2 }

     zxGponCESoIPFarEndIp     OBJECT-TYPE
        SYNTAX      OCTET STRING
        MAX-ACCESS  read-write
        STATUS      current
        DESCRIPTION
        "When the pseudowire service is transported via IP, this attribute points to a large
         string managed entity that contains the URI of the far-end termination point(2 bytes)"
        ::= { zxGponCESoIPConfigEntry 3 }

    zxGponCESoIPEntryStatus OBJECT-TYPE
        SYNTAX      RowStatus
        MAX-ACCESS  read-write
        STATUS      current
        DESCRIPTION
        "This attribute specifies the action of this entry."
        REFERENCE   ""
        ::= { zxGponCESoIPConfigEntry 10 }

--create pw TDM
    zxGponPwTDMConfigTable     OBJECT-TYPE
        SYNTAX      SEQUENCE OF ZxGponPwTDMConfigEntry
        MAX-ACCESS  not-accessible
        STATUS      current
        DESCRIPTION
            ""
        REFERENCE   "G.984.4 9.8.5    Pseudowire termination point"
        ::= { zxGponRmTDMMgmt 4 }

    zxGponPwTDMConfigEntry OBJECT-TYPE
        SYNTAX      ZxGponPwTDMConfigEntry
        MAX-ACCESS  not-accessible
        STATUS      current
        DESCRIPTION
            "It is entry in the zxGponPwTDMConfigTable."
        INDEX   { zxGponOltIndex, zxGponONTIndex, zxGponUNIIndex }
        ::= { zxGponPwTDMConfigTable 1 }

    ZxGponPwTDMConfigEntry ::=
        SEQUENCE {
            zxGponPwTDMPayloadSize          INTEGER,
            zxGponPwTDMPayloadDelay         INTEGER,
            zxGponPwTDMTimingMode           INTEGER,
            zxGponPwTDMProfile              INTEGER,
            zxGponPwTDMTransport            INTEGER
        }

    zxGponPwTDMPayloadSize     OBJECT-TYPE
        SYNTAX      INTEGER
        MAX-ACCESS  read-write
        STATUS      current
        DESCRIPTION
        "Number of payload bytes per packet. Valid only if service type =
        unstructured or unstructured octet-aligned. Valid choices depend on the TDM
        service, but must include the following. Other choices are at the vendor's discretion.
                DS1    192
                DS1    200, required only if unstructured octet aligned service is supported
              E1    256
        DS3    1024
        E3    1024   (R, W, Set-by-create) (mandatory for unstructured service) (2 bytes)"
        ::= { zxGponPwTDMConfigEntry 1 }

    zxGponPwTDMPayloadDelay     OBJECT-TYPE
        SYNTAX      INTEGER
        MAX-ACCESS  read-write
        STATUS      current
        DESCRIPTION
        "Number of 125 microsecond frames to be encapsulated in each pseudowire packet.
        Valid only if service type = structured. The minimum set of choices for various
        TDM services is listed below, and is affected by the possible presence of in-band
        signalling. Other choices are at the vendor's discretion.
                NxDS0, no signalling, N = 1    64 (8 ms) required,
        40 (5 ms) desired
        NxDS0, no signalling, N = 2..4    32 (4 ms)
        NxDS0, no signalling, N > 4    8 (1 ms)
        NxDS0 with DS1 CAS    24 (3 ms)
        NxDS0 with E1 CAS    16 (2 ms)  (R, W, Set-by-create) (mandatory for structured service) (1 byte)"
        ::= { zxGponPwTDMConfigEntry 2 }

     zxGponPwTDMTimingMode     OBJECT-TYPE
        SYNTAX      INTEGER{
                    network(1),
                    differential(2),
                    adaptive(3),
                    loop(4)
                    }
        MAX-ACCESS  read-write
        STATUS      current
        DESCRIPTION
        "This attribute selects the timing mode of the TDM service. If RTP is used, this attribute must
        be set to be consistent with the value of the RTP time stamp mode attribute in the RTP parameters
        managed entity at the far end.
        0    Network timing (default)
                1    Differential timing
                2    Adaptive timing
                3    Loop timing: local TDM transmit clock derived from local TDM receive stream(R, W) (mandatory) (1 byte)"
        ::= { zxGponPwTDMConfigEntry 3 }

     zxGponPwTDMProfile     OBJECT-TYPE
        SYNTAX      INTEGER
        MAX-ACCESS  read-write
        STATUS      current
        DESCRIPTION
        "This attribute points to an instance of the pseudowire maintenance profile managed entity. If the
        pointer has its default value 0, the ONT's internal defaults apply. (R, W) (optional) (2 bytes)"
        ::= { zxGponPwTDMConfigEntry 4 }

     zxGponPwTDMTransport     OBJECT-TYPE
        SYNTAX      INTEGER{
                    ethernet(1),
                    ip(2)
                    }
        MAX-ACCESS  read-write
        STATUS      current
        DESCRIPTION
        "Underlying transport:
           0    Ethernet, MEF8
           1    UDP/IP
        (R, W, Set-by-create) (mandatory) (1 byte)"
        ::= { zxGponPwTDMConfigEntry 5 }

--create pw optional
    zxGponPwOptionalConfigTable     OBJECT-TYPE
        SYNTAX      SEQUENCE OF ZxGponPwOptionalConfigEntry
        MAX-ACCESS  not-accessible
        STATUS      current
        DESCRIPTION
            ""
        REFERENCE   "G.984.4 9.8.5    Pseudowire termination point"
        ::= { zxGponRmTDMMgmt 5 }

    zxGponPwOptionalConfigEntry OBJECT-TYPE
        SYNTAX      ZxGponPwOptionalConfigEntry
        MAX-ACCESS  not-accessible
        STATUS      current
        DESCRIPTION
            "It is entry in the zxGponPwTDMConfigTable."
        INDEX   { zxGponOltIndex, zxGponONTIndex, zxGponUNIIndex }
        ::= { zxGponPwOptionalConfigTable 1 }

    ZxGponPwOptionalConfigEntry ::=
        SEQUENCE {
            zxGponPwOptionalServiceType          INTEGER,
            zxGponPwOptionalSignalling           INTEGER,
            zxGponPwOptionalARC                  INTEGER,
            zxGponPwOptionalARCInterval          INTEGER
        }

    zxGponPwOptionalServiceType     OBJECT-TYPE
        SYNTAX      INTEGER{
                    basicUnstructured(1),
                    octetAlignedUnstructured(2),
                    structured(3)
                    }
        MAX-ACCESS  read-write
        STATUS      current
        DESCRIPTION
        "This attribute specifies the basic service type, either a transparent bit
         pipe or an encapsulation that recognizes the underlying structure of the payload.
         0    Basic unstructured (also known as structure agnostic)
         1    Octet aligned unstructured, structure agnostic. Applicable only to DS1, a mode
            in which each frame of 193 bits is encapsulated in 25 bytes with 7 padding bits.
         2    Structured (structure-locked)(R, W, Set-by-create) (mandatory) (1 byte)"
        ::= { zxGponPwOptionalConfigEntry 1 }

    zxGponPwOptionalSignalling     OBJECT-TYPE
        SYNTAX      INTEGER{
                    noSignalling(1),
                    casSame(2),
                    casSeparate(3)
                    }
        MAX-ACCESS  read-write
        STATUS      current
        DESCRIPTION
        "0    No signalling visible at this layer
         1    CAS, to be carried in the same packet stream as the payload
         2    CAS, to be carried in a separate signalling channel
         (R, W, Set-by-create) (mandatory for structured service type) (1 byte)"
        ::= { zxGponPwOptionalConfigEntry 2 }

     zxGponPwOptionalARC     OBJECT-TYPE
        SYNTAX      INTEGER
        MAX-ACCESS  read-write
        STATUS      current
        DESCRIPTION
        "See clause I.1.8/G.984.4. (R, W) (optional) (1 byte)"
        ::= { zxGponPwOptionalConfigEntry 3 }

     zxGponPwOptionalARCInterval     OBJECT-TYPE
        SYNTAX      INTEGER
        MAX-ACCESS  read-write
        STATUS      current
        DESCRIPTION
        "See clause I.1.8/G.984.4. (R, W) (optional) (1 byte)"
        ::= { zxGponPwOptionalConfigEntry 4 }

--G.984.4 9.8.6    RTP pseudowire parameters
      zxGponPwRTPConfigTable     OBJECT-TYPE
        SYNTAX      SEQUENCE OF ZxGponPwRTPConfigEntry
        MAX-ACCESS  not-accessible
        STATUS      current
        DESCRIPTION
            "The pseudowire termination point supports packetized (rather than TDM) G-PON
             transport of TDM services, transported either directly over Ethernet or over UDP/IP.
             Instances of this managed entity are created and deleted by the OLT.This table is
             the config of transported over UDP/IP"
        REFERENCE   "G.984.4 9.8.6    RTP pseudowire parameters"
        ::= { zxGponRmTDMMgmt 6 }

    zxGponPwRTPConfigEntry OBJECT-TYPE
        SYNTAX      ZxGponPwRTPConfigEntry
        MAX-ACCESS  not-accessible
        STATUS      current
        DESCRIPTION
            "It is entry in the zxGponPwRTPConfigTable."
        INDEX   { zxGponOltIndex, zxGponONTIndex, zxGponUNIIndex }
        ::= { zxGponPwRTPConfigTable 1 }

    ZxGponPwRTPConfigEntry ::=
        SEQUENCE {
            zxGponPwRTPTsMode                       INTEGER,
            zxGponPwRTPPayloadPTYPE                 INTEGER,
            zxGponPwRTPSignallingPTYPE              INTEGER,
            zxGponPwRTPExpPayloadPTYPE              INTEGER,
            zxGponPwRTPExpSignallingPTYPE           INTEGER,
            zxGponPwRTPPayloadSSRC                  INTEGER,
            zxGponPwRTPSignallingSSRC               INTEGER,
            zxGponPwRTPExpPayloadSSRC               INTEGER,
            zxGponPwRTPExpSignallingSSRC            INTEGER,
            zxGponPwRTPClockReference               INTEGER,
            zxGponPwRTPEntryStatus                  RowStatus
        }

    zxGponPwRTPTsMode     OBJECT-TYPE
        SYNTAX      INTEGER{
                    unknown(1),
                    absolute(2),
                    differential(3)
                    }
        MAX-ACCESS  read-write
        STATUS      current
        DESCRIPTION
            "This attribute determines the mode in which RTP timestamps are generated in the TDM to PSN direction.
            0    Unknown or not applicable (default)
            1    Absolute. Timestamps are based on the timing of the incoming TDM signal.
            2    Differential. Timestamps are based on the ONT's reference clock, which is understood to be
                             stratum-traceable along with the reference clock at the far end.
            (R, W, Set-by-create) (mandatory) (1 byte)"
        ::= { zxGponPwRTPConfigEntry 1}

    zxGponPwRTPPayloadPTYPE     OBJECT-TYPE
        SYNTAX      INTEGER
        MAX-ACCESS  read-write
        STATUS      current
        DESCRIPTION
            "PTYPE specifies the RTP payload type in the TDM to PSN direction. It comprises two values.
            The first is for the payload channel, the second, for the optional separate signalling channel.
            Assignable PTYPEs lie in the dynamic range 96..127. If signalling is not transported in its own channel,
            the second value should be set to 0. (R, W, Set-by-create) (mandatory) (1 bytes)"
        ::= { zxGponPwRTPConfigEntry 2}

    zxGponPwRTPSignallingPTYPE     OBJECT-TYPE
        SYNTAX      INTEGER
        MAX-ACCESS  read-write
        STATUS      current
        DESCRIPTION
            "PTYPE specifies the RTP payload type in the TDM to PSN direction. It comprises two values.
            The first is for the payload channel, the second, for the optional separate signalling channel.
            Assignable PTYPEs lie in the dynamic range 96..127. If signalling is not transported in its own channel,
            the second value should be set to 0. (R, W, Set-by-create) (mandatory) (1 bytes)"
        ::= { zxGponPwRTPConfigEntry 3}

    zxGponPwRTPExpPayloadPTYPE     OBJECT-TYPE
        SYNTAX      INTEGER
        MAX-ACCESS  read-write
        STATUS      current
        DESCRIPTION
            "Expected PTYPE specifies the RTP payload type in the PSN to TDM direction. The received payload type
            may be used to detect malformed packets. It comprises two values. The first is for the payload channel,
            the second, for the optional separate signalling channel. To disable either or both of the check functions,
            set the corresponding value to its default value 0. (R, W, Set-by-create) (optional) (1 bytes)"
        ::= { zxGponPwRTPConfigEntry 4}

    zxGponPwRTPExpSignallingPTYPE     OBJECT-TYPE
        SYNTAX      INTEGER
        MAX-ACCESS  read-write
        STATUS      current
        DESCRIPTION
            "Expected PTYPE specifies the RTP payload type in the PSN to TDM direction. The received payload type
            may be used to detect malformed packets. It comprises two values. The first is for the payload channel,
            the second, for the optional separate signalling channel. To disable either or both of the check functions,
            set the corresponding value to its default value 0. (R, W, Set-by-create) (optional) (1 bytes)"
        ::= { zxGponPwRTPConfigEntry 5}

    zxGponPwRTPPayloadSSRC     OBJECT-TYPE
        SYNTAX      INTEGER
        MAX-ACCESS  read-write
        STATUS      current
        DESCRIPTION
            "SSRC specifies the RTP synchronization source in the TDM to PSN direction. It comprises two values. The first
            is for the payload channel, the second, for the optional separate signalling channel. If signalling is not
            transported in its own channel, the second value should be set to 0. (R, W, Set-by-create) (mandatory) (4 bytes)"
        ::= { zxGponPwRTPConfigEntry 6}

    zxGponPwRTPSignallingSSRC     OBJECT-TYPE
        SYNTAX      INTEGER
        MAX-ACCESS  read-write
        STATUS      current
        DESCRIPTION
            "SSRC specifies the RTP synchronization source in the TDM to PSN direction. It comprises two values. The first
            is for the payload channel, the second, for the optional separate signalling channel. If signalling is not
            transported in its own channel, the second value should be set to 0. (R, W, Set-by-create) (mandatory) (4 bytes)"
        ::= { zxGponPwRTPConfigEntry 7}

    zxGponPwRTPExpPayloadSSRC     OBJECT-TYPE
        SYNTAX      INTEGER
        MAX-ACCESS  read-write
        STATUS      current
        DESCRIPTION
            "Expected SSRC specifies the RTP synchronization source in the PSN to TDM direction. The received SSRC may be used
            to detect misconnection (stray packets). It comprises two values. The first is for the payload channel, the second,
            for the optional separate signalling channel. To disable either or both of the check functions, set the corresponding
            value to its default value 0. (R, W, Set-by-create) (optional) (8 bytes)"
        ::= { zxGponPwRTPConfigEntry 8}

    zxGponPwRTPExpSignallingSSRC     OBJECT-TYPE
        SYNTAX      INTEGER
        MAX-ACCESS  read-write
        STATUS      current
        DESCRIPTION
            "Expected SSRC specifies the RTP synchronization source in the PSN to TDM direction. The received SSRC may be used
            to detect misconnection (stray packets). It comprises two values. The first is for the payload channel, the second,
            for the optional separate signalling channel. To disable either or both of the check functions, set the corresponding
            value to its default value 0. (R, W, Set-by-create) (optional) (8 bytes)"
        ::= { zxGponPwRTPConfigEntry 9}

    zxGponPwRTPClockReference     OBJECT-TYPE
        SYNTAX      INTEGER
        MAX-ACCESS  read-write
        STATUS      current
        DESCRIPTION
            "This attribute specifies the frequency of the common timing reference, in multiples of 8 kHz.
             The default value is 1 (8 kHz). (R, W, Set-by-create) (mandatory) (2 bytes)"
        ::= { zxGponPwRTPConfigEntry 10}

    zxGponPwRTPEntryStatus OBJECT-TYPE
        SYNTAX      RowStatus
        MAX-ACCESS  read-write
        STATUS      current
        DESCRIPTION
        "This attribute specifies the action of this entry."
        REFERENCE   ""
        ::= { zxGponPwRTPConfigEntry 20 }


--Misc management
--PPTP Video UNI
    zxGponPptpVideoUNITable    OBJECT-TYPE
        SYNTAX      SEQUENCE OF ZxGponPptpVideoUNIEntry
        MAX-ACCESS  not-accessible
        STATUS      current
        DESCRIPTION
            "This managed entity represents the point at the video UNI in the ONT where physical paths terminate
            and physical path level functions are performed.
            One or more instances of this managed entity shall be contained in an instance of a Circuit Pack
            managed entity classified as Video type."
        REFERENCE   "G.983.2 section 7.3.52 Physical path termination point video UNI"
        ::= { zxGponRmMiscMgmt 1 }

    zxGponPptpVideoUNIEntry OBJECT-TYPE
        SYNTAX      ZxGponPptpVideoUNIEntry
        MAX-ACCESS  not-accessible
        STATUS      current
        DESCRIPTION
            "It is entry in the zxGponPptpVideoUNITable."
        INDEX   { zxGponOltIndex, zxGponONTIndex, zxGponUNIIndex }
        ::= { zxGponPptpVideoUNITable 1 }

    ZxGponPptpVideoUNIEntry ::=
        SEQUENCE {
            zxGponPptpVideoUNIAdminState              INTEGER,
            zxGponPptpVideoUNIOperState               INTEGER,
            zxGponPptpVideoUNIARC                     INTEGER,
            zxGponPptpVideoUNIARCInterval             INTEGER,
            zxGponPptpVideoUNIPowerControl            INTEGER
        }

    zxGponPptpVideoUNIAdminState OBJECT-TYPE
        SYNTAX      INTEGER{
                    unlock(1),
                    lock(2)
                    }
        MAX-ACCESS  read-write
        STATUS      current
        DESCRIPTION
        "This attribute is used to activate (unlock: value 0x00) and deactivate (lock: value 0x01)
        the functions performed by instances of this managed entity.(1 byte)"
        REFERENCE   "G.983.2 section 7.3.52 Physical path termination point video UNI"
        ::= { zxGponPptpVideoUNIEntry 1 }

    zxGponPptpVideoUNIOperState OBJECT-TYPE
        SYNTAX      INTEGER{
                    enable(1),
                    disable(2)
                    }
        MAX-ACCESS  read-only
        STATUS      current
        DESCRIPTION
        "This attribute indicates whether or not this managed entity is capable of performing
        its task. The operational state reflects the perceived ability to receive or to generate
        a valid signal. Valid values are enabled (0x00) and disabled (0x01).(1 byte)"
        REFERENCE   "G.983.2 section 7.3.52 Physical path termination point video UNI"
        ::= { zxGponPptpVideoUNIEntry 2 }

    zxGponPptpVideoUNIARC OBJECT-TYPE
        SYNTAX      INTEGER
        MAX-ACCESS  read-write
        STATUS      current
        DESCRIPTION
        "This attribute is used to control alarm reporting from this managed entity.
        See I.1.8 for a complete description.(1 byte)"
        REFERENCE   "G.983.2 section 7.3.52 Physical path termination point video UNI"
        ::= { zxGponPptpVideoUNIEntry 3 }

    zxGponPptpVideoUNIARCInterval OBJECT-TYPE
        SYNTAX      INTEGER
        MAX-ACCESS  read-write
        STATUS      current
        DESCRIPTION
        "This attribute provides a provisionable length of time. See I.1.8 for a complete description.(1 byte)"
        REFERENCE   "G.983.2 section 7.3.52 Physical path termination point video UNI"
        ::= { zxGponPptpVideoUNIEntry 4 }

    zxGponPptpVideoUNIPowerControl OBJECT-TYPE
        SYNTAX      INTEGER{
                    controlDisable(1),
                    controlEnable(2)
                    }
        MAX-ACCESS  read-write
        STATUS      current
        DESCRIPTION
        "This attribute controls whether power is provided to an external equipment over the
        Ethernet PPTP. Value 0x01 enables power over Ethernet.
        The default value 0x00 disables power feed.(1 byte)"
        REFERENCE   "G.983.2 section 7.3.52 Physical path termination point video UNI"
        ::= { zxGponPptpVideoUNIEntry 5 }


--PPTP Video ANI
    zxGponPptpVideoAniTable    OBJECT-TYPE
      SYNTAX      SEQUENCE OF ZxGponPptpVideoAniEntry
      MAX-ACCESS  not-accessible
      STATUS      current
      DESCRIPTION
            "This managed entity represents an RF video ANI in the ONU,
            where physical paths terminate and physical path level
            functions are performed. An instance of this managed entity
            is associated with each instance of a real or preprovisioned
            video ANI port."
      REFERENCE "G.988 section 9.13.2 Physical path termination point video ANI"
      ::= { zxGponRmMiscMgmt 3 }

    zxGponPptpVideoAniEntry OBJECT-TYPE
        SYNTAX      ZxGponPptpVideoAniEntry
        MAX-ACCESS  not-accessible
        STATUS      current
        DESCRIPTION
            "It is entry in the zxGponPptpVideoAniTable."
        INDEX   { zxGponOltIndex, zxGponONTIndex }
        ::= { zxGponPptpVideoAniTable 1 }

    ZxGponPptpVideoAniEntry ::=
        SEQUENCE {
            zxGponVideoAniAdminState                    INTEGER,
            zxGponVideoAniOperState                     INTEGER,
            zxGponVideoAniArc                           INTEGER,
            zxGponVideoAniArcInterval                   Integer32,
            zxGponVideoAniFreqRangeLow                  INTEGER,
            zxGponVideoAniFreqRangeHigh                 INTEGER,
            zxGponVideoAniSignalCapability              INTEGER,
            zxGponVideoAniOpticalSignalLevel            Integer32,
            zxGponVideoAniPilotSignalLevel              Integer32,
            zxGponVideoAniSignalLevelMin                Integer32,
            zxGponVideoAniSignalLevelMax                Integer32,
            zxGponVideoAniPilotFrequency                Unsigned32,
            zxGponVideoAniAgcMode                       INTEGER,
            zxGponVideoAniAgcValue                      Integer32,
            zxGponVideoAniLowerOpticalThresh            Integer32,
            zxGponVideoAniUpperOpticalThresh            Integer32
        }

    zxGponVideoAniAdminState OBJECT-TYPE
      SYNTAX      INTEGER{
                    unlocked(1),
                    locked(2)
                    }
      MAX-ACCESS  read-write
      STATUS      current
      DESCRIPTION
        "This attribute is used to activate (unlock: value 0x00) and
        deactivate (lock: value 0x01) the functions performed by
        instances of this managed entity.(1 byte)"
      REFERENCE "G.988 section 9.13.2 Physical path termination point video ANI"
      ::= { zxGponPptpVideoAniEntry 1 }

    zxGponVideoAniOperState OBJECT-TYPE
      SYNTAX      INTEGER{
                    enabled(1),
                    disabled(2)
                    }
      MAX-ACCESS  read-only
      STATUS      current
      DESCRIPTION
          "This attribute indicates whether or not this managed entity is
          capable of performing its task. The operational state reflects
          the perceived ability to receive or to generate a valid signal.
          Valid values are enabled (0x00) and disabled (0x01).(1 byte)"
      REFERENCE "G.988 section 9.13.2 Physical path termination point video ANI"
      ::= { zxGponPptpVideoAniEntry 2 }

    zxGponVideoAniArc OBJECT-TYPE
      SYNTAX      INTEGER{
                    enabled(1),
                    disabled(2)
                    }
      MAX-ACCESS  read-write
      STATUS      current
      DESCRIPTION
          "This attribute is used to control alarm reporting from
          this managed entity.
          See A.1.4.3 for a complete description.(1 byte)"
      REFERENCE "G.988 section 9.13.2 Physical path termination point video ANI"
      DEFVAL {disabled}
      ::= { zxGponPptpVideoAniEntry 3 }

    zxGponVideoAniArcInterval OBJECT-TYPE
      SYNTAX      Integer32(0..255)
      UNITS        "min"
      MAX-ACCESS  read-write
      STATUS      current
      DESCRIPTION
        "This attribute provides a provisionable length of time.
        The special value 255 means that the timer never expires.
        See A.1.4.3 for a complete description.(1 byte)"
      REFERENCE "G.988 section 9.13.2 Physical path termination point video ANI"
      DEFVAL {0}
      ::= { zxGponPptpVideoAniEntry 4 }

    zxGponVideoAniFreqRangeLow OBJECT-TYPE
      SYNTAX INTEGER{
                    noLowBand(1),
                    from50to550(2),
                    from50to750(3),
                    from50to870(4)
                    }
      MAX-ACCESS  read-only
      STATUS      current
      DESCRIPTION
        "This attribute indicates the lower of the two possible frequency
        ranges supported.
        Different frequency ranges are indicated by code points:
            noLowBand(1): No low band
            from50to550(2): 50..550 MHz
            from50to750(3): 50..750 MHz
            from50to870(4): 50..870 MHz
            5..255 Reserved"
      REFERENCE "G.988 section 9.13.2 Physical path termination point video ANI"
      ::= { zxGponPptpVideoAniEntry 5 }

    zxGponVideoAniFreqRangeHigh OBJECT-TYPE
      SYNTAX      INTEGER{
                    noHighBand(1),
                    from550to750(2),
                    from550to870(3),
                    from950to2050(4),
                    from2150to3250(5),
                    from950to3250(6)
                    }
      MAX-ACCESS  read-only
      STATUS      current
      DESCRIPTION
        "This attribute indicates the higher of the two frequency
        ranges supported.
        Different frequency ranges are indicated by code points:
            noHighBand(1): No high band
            from550to750(2): 550..750 MHz
            from550to870(3): 550..870 MHz
            from950to2050(4): 950..2050 MHz
            from2150to3250(5): 2150..3250 MHz
            from950to3250(6): 950..3250 MHz
            7..255 Reserved"
      REFERENCE "G.988 section 9.13.2 Physical path termination point video ANI"
      ::= { zxGponPptpVideoAniEntry 6 }

    zxGponVideoAniSignalCapability OBJECT-TYPE
      SYNTAX    INTEGER{
                    noCapability(1),
                    total(2),
                    fixed(3),
                    totalAndFixed(4),
                    variable(5),
                    totalAndVariable(6),
                    broadband(7),
                    totalAndBroadband(8)
                   }
      MAX-ACCESS  read-only
      STATUS      current
      DESCRIPTION
        "This attribute indicates the capability of the ONU to measure
        the video signal level.
        Capabilities are indicated by code points:
            noCapability(1): No signal level measurement capability
            total(2): Total optical power level
            fixed(3): Fixed frequency pilot tone power level
            totalAndFixed(4): Total optical power level and fixed
                              frequency pilot tone power level
            variable(5): Variable frequency pilot tone power level
            totalAndVariable(6): Total optical power level
                                 and variable frequency pilot tone power level
            broadband(7): Broadband RF power level
            totalAndBroadband(8): Total optical power level
                                  and broadband RF power level
            9..255 Reserved"
      REFERENCE "G.988 section 9.13.2 Physical path termination point video ANI"
      ::= { zxGponPptpVideoAniEntry 7 }

    zxGponVideoAniOpticalSignalLevel OBJECT-TYPE
      SYNTAX      Integer32
      UNITS        "dBuW"
      MAX-ACCESS  read-only
      STATUS      current
      DESCRIPTION
        "This attribute is an unsigned integer that returns
        the current measurement of the total optical signal level.
          If signal capability = 1, 3, 5 or 7, this attribute is undefined.
          If signal capability =2, 4, 6 or 8, this attribute describes the total
                optical power that is generating photocurrent on the receiver."
      REFERENCE "G.988 section 9.13.2 Physical path termination point video ANI"
      ::= { zxGponPptpVideoAniEntry 8 }

    zxGponVideoAniPilotSignalLevel OBJECT-TYPE
     SYNTAX      Integer32
     UNITS        "dBuV"
     MAX-ACCESS  read-only
     STATUS      current
     DESCRIPTION
        "This attribute indicates the current measurement
        of the pilot signal level or broadband RF level.
            If signal capability = 1 or 2, then this attribute is undefined.
            If signal capability = 3, 4, 5 or 6,
                this attribute reports the pilot signal level at
                the output of the video UNI.
            If signal capability = 7 or 8,
                this attribute reports the total RF power level at
                the output of the video UNI."
     REFERENCE "G.988 section 9.13.2 Physical path termination point video ANI"
     ::= { zxGponPptpVideoAniEntry 9 }

    zxGponVideoAniSignalLevelMin OBJECT-TYPE
      SYNTAX      Integer32
      UNITS        "dBuW"
      MAX-ACCESS  read-only
      STATUS      current
      DESCRIPTION
        "This attribute indicates the minimum optical RF power per channel
        that results in a CNR of 47 dBc for a channel of 4.5 MHz bandwidth
        at a receive optical power of -5 dBm."
      REFERENCE "G.988 section 9.13.2 Physical path termination point video ANI"
      ::= { zxGponPptpVideoAniEntry 10 }

    zxGponVideoAniSignalLevelMax OBJECT-TYPE
      SYNTAX      Integer32
      UNITS        "dBuW"
      MAX-ACCESS  read-only
      STATUS      current
      DESCRIPTION
        "This attribute indicates the maximum optical RF power per channel
        that results in a CTB of -57 dBc for an 80-channel ensemble of carriers
        at a per-channel optical modulation index of 3.5%."
      REFERENCE "G.988 section 9.13.2 Physical path termination point video ANI"
      ::= { zxGponPptpVideoAniEntry 11 }

    zxGponVideoAniPilotFrequency OBJECT-TYPE
      SYNTAX      Unsigned32(0..4294967295)
      UNITS        "Hz"
      MAX-ACCESS  read-write
      STATUS      current
      DESCRIPTION
        "This attribute specifies the frequency of the pilot channel receiver.
        The unit of this attribute is Hz.
        If signal capability = 1, 2, 7 or 8, this attribute is undefined.
        If signal capability = 3 or 4, this attribute is functionally read only.
        If signal capability = 5 or 6, this attribute is read-write."
      REFERENCE "G.988 section 9.13.2 Physical path termination point video ANI"
      ::= { zxGponPptpVideoAniEntry 12 }

    zxGponVideoAniAgcMode OBJECT-TYPE
      SYNTAX      INTEGER{
                    no(1),
                    broadband(2),
                    optical(3)
                    }
      MAX-ACCESS  read-write
      STATUS      current
      DESCRIPTION
        "This attribute allows the discovery and configuration of
        the ONU's AGC capabilities. The attribute contains a code point
        for several AGC types.
         The ONU displays the currently used AGC mode.
         The OLT can discover new modes via the set command;
         the ONU denies attempts to set an unsupported mode.
         The code points are:
            no(1): No AGC
            broadband(2): Broadband RF AGC
            optical(3): Optical AGC
            4..255 Reserved"
      REFERENCE "G.988 section 9.13.2 Physical path termination point video ANI"
      ::= { zxGponPptpVideoAniEntry 13 }

    zxGponVideoAniAgcValue OBJECT-TYPE
      SYNTAX      Integer32(-128..127)
      UNITS        "0.1 dB"
      MAX-ACCESS  read-write
      STATUS      current
      DESCRIPTION
        "This attribute indicates the measurement offset that the ONU should
        use in AGC. The attribute has a step size of 0.1 dB, represented as
        a signed integer."
      REFERENCE "G.988 section 9.13.2 Physical path termination point video ANI"
      ::= { zxGponPptpVideoAniEntry 14 }

    zxGponVideoAniLowerOpticalThresh OBJECT-TYPE
      SYNTAX      Integer32(-120..60)
      UNITS       "0.1 dBm"
      MAX-ACCESS  read-write
      STATUS      current
      DESCRIPTION
        "This attribute specifies the optical level used to declare
        the video OOR low alarm.
        Valid values are -12 to +6 dBm in 0.1 dB increments, represented as
        a 2s complement integer.
        (Coding -120 to +60, where 0x00 = 0dBm, 0x88 = -12.0 dBm, etc.)
        Upon ME instantiation, the ONU sets this attribute to 0xA1 (-9.5 dBm)."
      REFERENCE "G.988 section 9.13.2 Physical path termination point video ANI"
      ::= { zxGponPptpVideoAniEntry 15 }

    zxGponVideoAniUpperOpticalThresh OBJECT-TYPE
     SYNTAX      Integer32(-120..60)
     UNITS       "0.1 dBm"
     MAX-ACCESS  read-write
     STATUS      current
     DESCRIPTION
        "This attribute specifies the optical level used to declare
        the video OOR high alarm.
        Valid values are -12 to +6 dBm in 0.1 dB increments, represented as
        a 2s complement integer.
        (Coding -120 to +60, 0x00 = 0 dBm, 0x88 = -12.0 dBm, etc.)
        Upon ME instantiation, the ONU sets this attribute to 0x19 (+2.5 dBm)."
     REFERENCE "G.988 section 9.13.2 Physical path termination point video ANI"
     ::= { zxGponPptpVideoAniEntry 16 }

--profile management
--filter rule for extended vlan
    zxGponFilterRuleTable    OBJECT-TYPE
        SYNTAX      SEQUENCE OF ZxGponFilterRuleEntry
        MAX-ACCESS  not-accessible
        STATUS      current
        DESCRIPTION
            "This managed entity organizes data associated with VLAN tagging.
            Regardless of its point of attachment, the specified tagging operations
            refer to the upstream direction. Instances of this managed entity are
            created and deleted by the OLT."
        REFERENCE   "G.984.4 9.3.13 Extended VLAN tagging operation configuration data"
        ::= { zxGponRmProfileMgmt 1 }

    zxGponFilterRuleEntry OBJECT-TYPE
        SYNTAX      ZxGponFilterRuleEntry
        MAX-ACCESS  not-accessible
        STATUS      current
        DESCRIPTION
            "It is entry in the zxGponFilterRuleEntry."
        INDEX   {zxGponFilterRuleId}
        ::= { zxGponFilterRuleTable 1 }

    ZxGponFilterRuleEntry ::=
        SEQUENCE {
            zxGponFilterRuleId              INTEGER,
            zxGponFilterRuleName            OCTET STRING,
            zxGponFilterRuleTagNum          INTEGER,
            zxGponFilterRuleEthType         INTEGER,
            zxGponFilterRuleInnerPrio       INTEGER,
            zxGponFilterRuleInnerVID        INTEGER,
            zxGponFilterRuleInnerTPID       INTEGER,
            zxGponFilterRuleOuterPrio       INTEGER,
            zxGponFilterRuleOuterVID        INTEGER,
            zxGponFilterRuleOuterTPID       INTEGER,
            zxGponFilterRuleRefCnt          INTEGER,
            zxGponFilterRuleEntryStatus     RowStatus,
            zxGponFilterRuleFlowClassType   INTEGER,
            zxGponFilterRuleFlowClassData   OCTET STRING
        }

    zxGponFilterRuleId OBJECT-TYPE
        SYNTAX      INTEGER
        MAX-ACCESS  not-accessible
        STATUS      current
        DESCRIPTION
        "This attribute provides a unique number for each instance of this managed entity.
        (R, Set-by-create) (mandatory) (4 bytes)"
        ::= { zxGponFilterRuleEntry 1 }

    zxGponFilterRuleName OBJECT-TYPE
        SYNTAX      OCTET STRING(SIZE(1..63))
        MAX-ACCESS  read-write
        STATUS      current
        DESCRIPTION
        "This attribute provides a unique name for each instance of this managed entity.
        (R, Set-by-create) (mandatory) (2 bytes)"
        ::= { zxGponFilterRuleEntry 2 }

    zxGponFilterRuleTagNum  OBJECT-TYPE
        SYNTAX      INTEGER
        MAX-ACCESS  read-write
        STATUS      current
        DESCRIPTION
        "This attribute provides the number of tag.
        (R, Set-by-create) (mandatory) (2 bytes)"
        ::= { zxGponFilterRuleEntry 3 }

    zxGponFilterRuleEthType     OBJECT-TYPE
        SYNTAX      INTEGER{
                    notFilter(1),
                    ipoe(2),
                    pppoe(3),
                    arp(4),
                    tcp(7),
                    udp(8),
                    icmpV6(9),
                    icmpV4(10),
                    ipv6oe(11),
                    dhcp(12),
                    igmp(13),
                    sip(14),
                    pwe3(15),
                    macCtrl(16)
                    }
        MAX-ACCESS  read-write
        STATUS      current
        DESCRIPTION
        "The Ethertype value on which to filter received frames,
         as listed below. Note: This filter is recommended for
         use on untagged frames or frames with only priority.
         The Ethertype value on which to filter received frames,
             as listed below.
             1 Do not filter on Ethertype.
             2 Ethertype = 0x0800 (filter IPoE frames)
             3 Ethertype = 0x8863 or 0x8864 (filter PPPoE frames)
             4 Ethertype = 0x0806 (filter ARP frames)
             7  TCP
             8  UDP
             9  ICMPv6
             10 ICMPv4
             11 IPv6oE
             12 DHCP.
             13 IGMP.
             14 SIP.
             15 PWE3 = 0X8847.
             16 MAC Control = 0x8808
             Note: This filter is recommended for
             use on untagged frames or frames with only priority."
        ::= { zxGponFilterRuleEntry 4 }

    zxGponFilterRuleInnerPrio     OBJECT-TYPE
        SYNTAX      INTEGER
        MAX-ACCESS  read-write
        STATUS      current
        DESCRIPTION
        "Filter received frames on this priority value(0-7).Do not filter on inner priority(8).
        This is the default filter when no other one-tag rule applies(14).This entry is a no-tag
        rule; ignore all other filter fields(15).(4 bits)"
        ::= { zxGponFilterRuleEntry 5 }

    zxGponFilterRuleInnerVID     OBJECT-TYPE
        SYNTAX      INTEGER
        MAX-ACCESS  read-write
        STATUS      current
        DESCRIPTION
        "Filter received frames on this VID value(0-4094).Do not filter on the inner VID(4096).(13 bits)"
        ::= { zxGponFilterRuleEntry 6 }

    zxGponFilterRuleInnerTPID   OBJECT-TYPE
        SYNTAX      INTEGER{
                    notFilter(1),
                    defaultTPID(5),
                    ignoreDE(6),
                    zeroDE(7),
                    oneDE(8)
                    }
        MAX-ACCESS  read-write
        STATUS      current
        DESCRIPTION
        "Filter Inner TPID/DE: (3 bits)"
        ::= { zxGponFilterRuleEntry 7 }

    zxGponFilterRuleOuterPrio     OBJECT-TYPE
        SYNTAX      INTEGER
        MAX-ACCESS  read-write
        STATUS      current
        DESCRIPTION
        "Filter received frames on this priority value(0-7).Do not filter on outer priority.(8).
        This is the default filter when no other two-tag rule applies(14).This entry is not a
        double-tag rule; ignore all other outer tag filter fields(15).(4 bits)"
        ::= { zxGponFilterRuleEntry 8 }

    zxGponFilterRuleOuterVID     OBJECT-TYPE
        SYNTAX      INTEGER
        MAX-ACCESS  read-write
        STATUS      current
        DESCRIPTION
        "Filter received frames on this VID value(0-4094).Do not filter on the outer VID(4096).(13 bits)"
        ::= { zxGponFilterRuleEntry 9 }

    zxGponFilterRuleOuterTPID   OBJECT-TYPE
        SYNTAX      INTEGER{
                    notFilter(1),
                    defaultTPID(5),
                    ignoreDE(6),
                    zeroDE(7),
                    oneDE(8)
                    }
        MAX-ACCESS  read-write
        STATUS      current
        DESCRIPTION
        "Filter outer TPID/DE: (3 bits)"
        ::= { zxGponFilterRuleEntry 10 }

    zxGponFilterRuleRefCnt OBJECT-TYPE
        SYNTAX      INTEGER
        MAX-ACCESS  read-only
        STATUS      current
        DESCRIPTION
        "Forbidden to delete table entry if not equal zero."
        ::= { zxGponFilterRuleEntry 11 }

    zxGponFilterRuleEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponFilterRuleEntry 12 }

    zxGponFilterRuleFlowClassType OBJECT-TYPE
        SYNTAX      INTEGER{
                    notCare(1),
                    srcIpv4(2),
                    dstIpv4(3),
                    srcMac(4),
                    dstMac(5),
                    srcL4Port(6),
                    dstL4Port(7)
                    }
        MAX-ACCESS  read-write
        STATUS      current
        DESCRIPTION
            "This attribute specifies the flow classification data type of
              this entry, 'notCare' means that data will not be filtered by
              specified data type, 'zxGponFilterRuleFilterData' is not used
              in such a case."
        ::= { zxGponFilterRuleEntry 13 }

    zxGponFilterRuleFlowClassData OBJECT-TYPE
        SYNTAX      OCTET STRING(SIZE(6))
        MAX-ACCESS  read-write
        STATUS      current
        DESCRIPTION
        "This attribute specifies the filter data contend of this entry.
        If FilterDataType is ip, this attribute indicates the ip address
          using the first 4 bytes;
        If FilterDataType is mac, this attribute indicates the mac address
          using the total 6 bytes;
        If FilterDataType is L4 port, this attribute indicates the L4 port
          using the first 2 bytes(0..65535);"
        ::= { zxGponFilterRuleEntry 14 }


--treatment rule for extended vlan
    zxGponTreatmentRuleTable    OBJECT-TYPE
        SYNTAX      SEQUENCE OF ZxGponTreatmentRuleEntry
        MAX-ACCESS  not-accessible
        STATUS      current
        DESCRIPTION
            "This managed entity organizes data associated with VLAN tagging.
            Regardless of its point of attachment, the specified tagging operations
            refer to the upstream direction. Instances of this managed entity are
            created and deleted by the OLT."
        REFERENCE   "G.984.4 9.3.13 Extended VLAN tagging operation configuration data"
        ::= { zxGponRmProfileMgmt 2 }

    zxGponTreatmentRuleEntry OBJECT-TYPE
        SYNTAX      ZxGponTreatmentRuleEntry
        MAX-ACCESS  not-accessible
        STATUS      current
        DESCRIPTION
            "It is entry in the zxGponTreatmentRuleEntry."
        INDEX   {zxGponTreatmentRuleId }
        ::= { zxGponTreatmentRuleTable 1 }

    ZxGponTreatmentRuleEntry ::=
        SEQUENCE {
            zxGponTreatmentRuleId              INTEGER,
            zxGponTreatmentRuleName            OCTET STRING,
            zxGponTreatmentRuleTagsRemove      INTEGER,
            zxGponTreatmentRuleAddInnerTag     TruthValue,
            zxGponTreatmentRuleAddOuterTag     TruthValue,
            zxGponTreatmentRuleInnerPrio       INTEGER,
            zxGponTreatmentRuleInnerPrioInsert INTEGER,
            zxGponTreatmentRuleInnerVID        INTEGER,
            zxGponTreatmentRuleInnerVIDInsert  INTEGER,
            zxGponTreatmentRuleInnerTPID       INTEGER,
            zxGponTreatmentRuleOuterPrio       INTEGER,
            zxGponTreatmentRuleOuterPrioInsert INTEGER,
            zxGponTreatmentRuleOuterVID        INTEGER,
            zxGponTreatmentRuleOuterVIDInsert  INTEGER,
            zxGponTreatmentRuleOuterTPID       INTEGER,
            zxGponTreatmentRuleRefCnt          INTEGER,
            zxGponTreatmentRuleEntryStatus     RowStatus
        }

    zxGponTreatmentRuleId OBJECT-TYPE
        SYNTAX      INTEGER
        MAX-ACCESS  not-accessible
        STATUS      current
        DESCRIPTION
        "This attribute provides a unique number for each instance of this managed entity.
        (R, Set-by-create) (mandatory) (4 bytes)"
        ::= { zxGponTreatmentRuleEntry 1 }

    zxGponTreatmentRuleName OBJECT-TYPE
        SYNTAX      OCTET STRING(SIZE(1..63))
        MAX-ACCESS  read-write
        STATUS      current
        DESCRIPTION
        "This attribute provides a unique name for each instance of this managed entity.
        (R, Set-by-create) (mandatory) (2 bytes)"
        ::= { zxGponTreatmentRuleEntry 2 }

    zxGponTreatmentRuleTagsRemove OBJECT-TYPE
        SYNTAX      INTEGER
        MAX-ACCESS  read-write
        STATUS      current
        DESCRIPTION
        "This attribute provides the number of tags to remove(0~2).(R, Set-by-create) (mandatory) (2 bytes)"
        ::= { zxGponTreatmentRuleEntry 3 }

    zxGponTreatmentRuleAddInnerTag OBJECT-TYPE
        SYNTAX      TruthValue
        MAX-ACCESS  read-write
        STATUS      current
        DESCRIPTION
        "This Boolean attribute indicates whether or not a add inner tag is
        enabled. The value TRUE means enabled.(1 byte)"
        ::= { zxGponTreatmentRuleEntry 4 }

    zxGponTreatmentRuleAddOuterTag OBJECT-TYPE
        SYNTAX      TruthValue
        MAX-ACCESS  read-write
        STATUS      current
        DESCRIPTION
        "This Boolean attribute indicates whether or not a add outer tag is
        enabled. The value TRUE means enabled.(1 byte)"
        ::= { zxGponTreatmentRuleEntry 5 }

    zxGponTreatmentRuleInnerPrio  OBJECT-TYPE
        SYNTAX      INTEGER{
                    insert(1),
                    copyInner(2),
                    copyOuter(3)
                    }
        MAX-ACCESS  read-write
        STATUS      current
        DESCRIPTION
        "Treatment priority: (4 bits)"
        ::= { zxGponTreatmentRuleEntry 6 }

    zxGponTreatmentRuleInnerPrioInsert  OBJECT-TYPE
        SYNTAX      INTEGER
        MAX-ACCESS  read-write
        STATUS      current
        DESCRIPTION
        "Use this value as the priority to insert in the inner VLAN tag. (0-7)(4 bits)"
        ::= { zxGponTreatmentRuleEntry 7 }

    zxGponTreatmentRuleInnerVID     OBJECT-TYPE
        SYNTAX      INTEGER{
                    insert(1),
                    copyInner(2),
                    copyOuter(3)
                    }
        MAX-ACCESS  read-write
        STATUS      current
        DESCRIPTION
        "Treatment VID: (13 bits)"
        ::= { zxGponTreatmentRuleEntry 8 }

    zxGponTreatmentRuleInnerVIDInsert     OBJECT-TYPE
        SYNTAX      INTEGER
        MAX-ACCESS  read-write
        STATUS      current
        DESCRIPTION
        "Use this value as the VID in the inner VLAN tag. (0-4094)(13 bits)"
        ::= { zxGponTreatmentRuleEntry 9 }

    zxGponTreatmentRuleInnerTPID     OBJECT-TYPE
        SYNTAX      INTEGER{
                    mode0(1),
                    mode1(2),
                    mode2(3),
                    mode3(4),
                    mode4(5),
                    mode5(6),
                    mode6(7),
                    mode7(8)
                    }
        MAX-ACCESS  read-write
        STATUS      current
        DESCRIPTION
        "Treatment inner TPID/DE: (3 bits)
         000    Copy TPID (and DE, if present) from inner tag of received frame
         001    Copy TPID (and DE, if present) from outer tag of received frame
         010    Set TPID = output TPID attribute value, copy DE bit from inner tag of received frame
         011    Set TPID = output TPID, copy DE from outer tag of received frame
         100    Set TPID = 0x8100
         101    Reserved
         110    Set TPID = output TPID, DE=0
         111    Set TPID = output TPID, DE=1"
        ::= { zxGponTreatmentRuleEntry 10 }

    zxGponTreatmentRuleOuterPrio     OBJECT-TYPE
        SYNTAX      INTEGER{
                    insert(1),
                    copyInner(2),
                    copyOuter(3),
                    dscp(4)
                    }
        MAX-ACCESS  read-write
        STATUS      current
        DESCRIPTION
        "Treatment priority: (4 bits)"
        ::= { zxGponTreatmentRuleEntry 11 }

    zxGponTreatmentRuleOuterPrioInsert     OBJECT-TYPE
        SYNTAX      INTEGER
        MAX-ACCESS  read-write
        STATUS      current
        DESCRIPTION
        "Use this value as the priority to insert in the outer VLAN tag. (0-7)(4 bits)"
        ::= { zxGponTreatmentRuleEntry 12 }

    zxGponTreatmentRuleOuterVID     OBJECT-TYPE
        SYNTAX      INTEGER{
                    insert(1),
                    copyInner(2),
                    copyOuter(3)
                    }
        MAX-ACCESS  read-write
        STATUS      current
        DESCRIPTION
        "Treatment VID: (13 bits)"
        ::= { zxGponTreatmentRuleEntry 13 }

    zxGponTreatmentRuleOuterVIDInsert     OBJECT-TYPE
        SYNTAX      INTEGER
        MAX-ACCESS  read-write
        STATUS      current
        DESCRIPTION
        "Use this value as the VID in the outer VLAN tag. (0-4094)(13 bits)"
        ::= { zxGponTreatmentRuleEntry 14 }

    zxGponTreatmentRuleOuterTPID     OBJECT-TYPE
        SYNTAX      INTEGER{
                    mode0(1),
                    mode1(2),
                    mode2(3),
                    mode3(4),
                    mode4(5),
                    mode5(6),
                    mode6(7),
                    mode7(8)
                    }
        MAX-ACCESS  read-write
        STATUS      current
        DESCRIPTION
        "Treatment outer TPID/DE: (3 bits)
         000    Copy TPID (and DE, if present) from inner tag of received frame
         001    Copy TPID (and DE, if present) from outer tag of received frame
         010    Set TPID = output TPID attribute value, copy DE bit from inner tag of received frame
         011    Set TPID = output TPID, copy DE from outer tag of received frame
         100    Set TPID = 0x8100
         101    Reserved
         110    Set TPID = output TPID, DE=0
         111    Set TPID = output TPID, DE=1"
        ::= { zxGponTreatmentRuleEntry 15}

    zxGponTreatmentRuleRefCnt OBJECT-TYPE
        SYNTAX      INTEGER
        MAX-ACCESS  read-only
        STATUS      current
        DESCRIPTION
        "Forbidden to delete table entry if not equal zero."
        ::= { zxGponTreatmentRuleEntry 16 }

    zxGponTreatmentRuleEntryStatus OBJECT-TYPE
        SYNTAX      RowStatus
        MAX-ACCESS  read-write
        STATUS      current
        DESCRIPTION
        "This attribute specifies the action of this entry."
        REFERENCE   "G.984.4 9.3.13 Extended VLAN tagging operation configuration data"
        ::= { zxGponTreatmentRuleEntry 17 }

--VoIP Media Profile
    zxGponVoIPMediaProfileTable    OBJECT-TYPE
        SYNTAX      SEQUENCE OF ZxGponVoIPMediaProfileEntry
        MAX-ACCESS  not-accessible
        STATUS      current
        DESCRIPTION
            "An instance of this managed entity may be referenced by one or more VoIP Voice CTP managed entities."
        REFERENCE   "G.983.2 section 7.3.107 VoIP Media Profile"
        ::= { zxGponRmProfileMgmt 3 }

    zxGponVoIPMediaProfileEntry OBJECT-TYPE
        SYNTAX      ZxGponVoIPMediaProfileEntry
        MAX-ACCESS  not-accessible
        STATUS      current
        DESCRIPTION
            "It is entry in the zxGponVoIPMediaProfileTable."
        INDEX   { zxGponVoIPMediaProfileId }
        ::= { zxGponVoIPMediaProfileTable 1 }

    ZxGponVoIPMediaProfileEntry ::=
        SEQUENCE {
            zxGponVoIPMediaProfileId                                        INTEGER,
            zxGponVoIPMediaProfileName                                      OCTET STRING,
            zxGponVoIPMediaProfileFaxMode                                   INTEGER,
            zxGponVoIPMediaProfileFirstCodecSelection                       INTEGER,
            zxGponVoIPMediaProfileFirstPacketPeriodSelection                INTEGER,
            zxGponVoIPMediaProfileFirstSilenceSelection                     INTEGER,
            zxGponVoIPMediaProfileSecondCodecSelection                      INTEGER,
            zxGponVoIPMediaProfileSecondPacketPeriodSelection               INTEGER,
            zxGponVoIPMediaProfileSecondSilenceSelection                    INTEGER,
            zxGponVoIPMediaProfileThirdCodecSelection                       INTEGER,
            zxGponVoIPMediaProfileThirdPacketPeriodSelection                INTEGER,
            zxGponVoIPMediaProfileThirdSilenceSelection                     INTEGER,
            zxGponVoIPMediaProfileFourthCodecSelection                      INTEGER,
            zxGponVoIPMediaProfileFourthPacketPeriodSelection               INTEGER,
            zxGponVoIPMediaProfileFourthSilenceSelection                    INTEGER,
            zxGponVoIPMediaProfileOOBDTMF                                   INTEGER,
            zxGponVoiceServiceProfileAALAnnouncementType                    INTEGER,
            zxGponVoiceServiceProfileAALJitterTarget                        INTEGER,
            zxGponVoiceServiceProfileAALJitterBufMax                        INTEGER,
            zxGponVoiceServiceProfileAALEchoCancelInd                       TruthValue,
            zxGponVoiceServiceProfileAALPSTNVariant                         INTEGER,
            zxGponRTPProfileLocalPortMin                                    INTEGER,
            zxGponRTPProfileLocalPortMax                                    INTEGER,
            zxGponRTPProfileDSCPMark                                        INTEGER,
            zxGponRTPProfilePiggybackEvents                                 INTEGER,
            zxGponRTPProfileToneEvents                                      INTEGER,
            zxGponRTPProfileDTMFEvents                                      INTEGER,
            zxGponRTPProfileCASEvents                                       INTEGER,
            zxGponVoIPMediaProfileRefCnt                                    INTEGER,
            zxGponVoIPMediaProfileEntryStatus                               RowStatus
        }

    zxGponVoIPMediaProfileId OBJECT-TYPE
        SYNTAX      INTEGER
        MAX-ACCESS  not-accessible
        STATUS      current
        DESCRIPTION
        "This attribute provides a unique number for each instance of this managed entity.
        (R, Set-by-create) (mandatory) (2 bytes)"
        REFERENCE   "G.983.2 section 7.3.107 VoIP Media Profile"
        ::= { zxGponVoIPMediaProfileEntry 1 }

    zxGponVoIPMediaProfileName OBJECT-TYPE
        SYNTAX      OCTET STRING(SIZE(1..63))
        MAX-ACCESS  read-write
        STATUS      current
        DESCRIPTION
        "This attribute provides a unique number for each instance of this managed entity.
        (R, Set-by-create) (mandatory) (2 bytes)"
        REFERENCE   "G.983.2 section 7.3.107 VoIP Media Profile"
        ::= { zxGponVoIPMediaProfileEntry 2 }

    zxGponVoIPMediaProfileFaxMode OBJECT-TYPE
        SYNTAX      INTEGER{
                    passthru(1),
                    itu-t38(2)
                    }
        MAX-ACCESS  read-write
        STATUS      current
        DESCRIPTION
        "Selects the fax mode, values are 0 - passthru, 1 - ITU-T T.38.
        Default value is 0 (R, W, Set-by-create) (mandatory) (1 byte)"
        REFERENCE   "G.983.2 section 7.3.107 VoIP Media Profile"
        ::= { zxGponVoIPMediaProfileEntry 3 }

    zxGponVoIPMediaProfileFirstCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection  as defined by RFC 3551.  Default Value is 0-PCMU. (R,  W, Set-by-create) (mandatory) (1 byte)"
        REFERENCE   "G.983.2 section 7.3.107 VoIP Media Profile"
        ::= { zxGponVoIPMediaProfileEntry 4 }

    zxGponVoIPMediaProfileFirstPacketPeriodSelection OBJECT-TYPE
        SYNTAX      INTEGER
        MAX-ACCESS  read-write
        STATUS      current
        DESCRIPTION
        "This attribute selects the Packet Period Selection interval in milliseconds.  Default value is 10. Valid values are 10 - 30 ms. (R, W, Set-by-create) (mandatory) (1 byte)"
        REFERENCE   "G.983.2 section 7.3.107 VoIP Media Profile"
        ::= { zxGponVoIPMediaProfileEntry 5 }

    zxGponVoIPMediaProfileFirstSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 6 }

    zxGponVoIPMediaProfileSecondCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection as defined by RFC 3551. Default Value is 0-PCMU. (R, W, Set-by-create) (mandatory) (1 byte)"
        REFERENCE   "G.983.2 section 7.3.107 VoIP Media Profile"
        ::= { zxGponVoIPMediaProfileEntry 7 }

    zxGponVoIPMediaProfileSecondPacketPeriodSelection OBJECT-TYPE
        SYNTAX      INTEGER
        MAX-ACCESS  read-write
        STATUS      current
        DESCRIPTION
        "This attribute selects the Packet Period Selection interval in milliseconds.  Default value is 10. Valid values are 10 - 30 ms. (R, W, Set-by-create) (mandatory) (1 byte)"
        REFERENCE   "G.983.2 section 7.3.107 VoIP Media Profile"
        ::= { zxGponVoIPMediaProfileEntry 8 }

    zxGponVoIPMediaProfileSecondSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 9 }

    zxGponVoIPMediaProfileThirdCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection as defined by RFC 3551. Default Value is 0-PCMU. (R, W, Set-by-create) (mandatory) (1 byte)"
        REFERENCE   "G.983.2 section 7.3.107 VoIP Media Profile"
        ::= { zxGponVoIPMediaProfileEntry 10 }

    zxGponVoIPMediaProfileThirdPacketPeriodSelection OBJECT-TYPE
        SYNTAX      INTEGER
        MAX-ACCESS  read-write
        STATUS      current
        DESCRIPTION
        "This attribute selects the Packet Period Selection interval in milliseconds.  Default value is 10. Valid values are 10 - 30 ms. (R,  W, Set-by-create) (mandatory) (1 byte)"
        REFERENCE   "G.983.2 section 7.3.107 VoIP Media Profile"
        ::= { zxGponVoIPMediaProfileEntry 11 }

    zxGponVoIPMediaProfileThirdSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 12 }

    zxGponVoIPMediaProfileFourthCodecSelection OBJECT-TYPE
        SYNTAX      INTEGER{
                    pcmu(1),
                    gsm(4),
                    g723(5),
                    dvi4-rate8khz(6),
                    dvi4-rate16khz(7),
                    lpc(8),
                    pcma(9),
                    g722(10),
                    l16-2channel(11),
                    l16-1channel(12),
                    qcelp(13),
                    cn(14),
                    mpa(15),
                    g728(16),
                    dvi4-rate11khz(17),
                    dvi4-rate22khz(18),
                    g729(19)
                    }
        MAX-ACCESS  read-write
        STATUS      current
        DESCRIPTION
        "Specifies the codec selection as defined by RFC 3551. Default Value is 0-PCMU. (R, W, Set-by-create) (mandatory) (1 byte)"
        REFERENCE   "G.983.2 section 7.3.107 VoIP Media Profile"
        ::= { zxGponVoIPMediaProfileEntry 13 }

    zxGponVoIPMediaProfileFourthPacketPeriodSelection OBJECT-TYPE
        SYNTAX      INTEGER
        MAX-ACCESS  read-write
        STATUS      current
        DESCRIPTION
        "This attribute selects the Packet Period Selection interval in milliseconds.  Default value is 10. Valid values are 10 - 30 ms. (R, W, Set-by-create) (mandatory) (1 byte)"
        REFERENCE   "G.983.2 section 7.3.107 VoIP Media Profile"
        ::= { zxGponVoIPMediaProfileEntry 14 }

    zxGponVoIPMediaProfileFourthSilenceSelection OBJECT-TYPE
        SYNTAX      INTEGER{
                    off(1),
                    on(2)
                    }
        MAX-ACCESS  read-write
        STATUS      current
        DESCRIPTION
        "This attribute indicates whether silence suppression is on or off.  Valid values are 0 = off and 1 = on.  (R, Set-by-create) (mandatory) (1 byte)"
        REFERENCE   "G.983.2 section 7.3.107 VoIP Media Profile"
        ::= { zxGponVoIPMediaProfileEntry 15 }

    zxGponVoIPMediaProfileOOBDTMF OBJECT-TYPE
        SYNTAX      INTEGER{
                    disable(1),
                    enable(2)
                    }
        MAX-ACCESS  read-write
        STATUS      current
        DESCRIPTION
        "This attribute defines the Out-of-band DMTF Enable. When enabled (value = 1) , DTMF tones are carried out of band via RTP or the associated signaling protocol. When disabled (value = 0), DTMF tones are carried in the PCM. Default value of 1. (R, W, Set-by-create) (mandatory) (1 byte)"
        REFERENCE   "G.983.2 section 7.3.107 VoIP Media Profile"
        ::= { zxGponVoIPMediaProfileEntry 16 }

    zxGponVoiceServiceProfileAALAnnouncementType OBJECT-TYPE
        SYNTAX      INTEGER{
                    silence(1),
                    reorderTone(2),
                    fastBusy(3),
                    voiceAnnounce(4),
                    na(5)
                    }
        MAX-ACCESS  read-write
        STATUS      current
        DESCRIPTION
        "This attribute provides the announcement to the customer going off-hook when no call has been attempted."
        REFERENCE   "G.983.2 section 7.3.24 Voice service profile AAL"
        ::= { zxGponVoIPMediaProfileEntry 17 }

    zxGponVoiceServiceProfileAALJitterTarget OBJECT-TYPE
        SYNTAX      INTEGER
        MAX-ACCESS  read-write
        STATUS      current
        DESCRIPTION
        "This attribute provides the target value of the jitter buffer. The system will try to maintain the jitter buffer at the target value.
        Units are in milliseconds. (R, W, Set-by-create) (mandatory for AAL2) (2 bytes)"
        REFERENCE   "G.983.2 section 7.3.24 Voice service profile AAL"
        ::= { zxGponVoIPMediaProfileEntry 18 }

    zxGponVoiceServiceProfileAALJitterBufMax OBJECT-TYPE
        SYNTAX      INTEGER
        MAX-ACCESS  read-write
        STATUS      current
        DESCRIPTION
        "This attribute provides the maximum depth of the jitter buffer associated with this service.
        Units are in milliseconds. (R, W, Set-by-create) (mandatory for AAL 2) (2 bytes)"
        REFERENCE   "G.983.2 section 7.3.24 Voice service profile AAL"
        ::= { zxGponVoIPMediaProfileEntry 19 }

    zxGponVoiceServiceProfileAALEchoCancelInd OBJECT-TYPE
        SYNTAX      TruthValue
        MAX-ACCESS  read-write
        STATUS      current
        DESCRIPTION
        "This Boolean attribute indicates whether echo cancellation is on or off,
        where the value TRUE implies that it is on. (R, Set-by-create) (mandatory) (1 byte)"
        REFERENCE   "G.983.2 section 7.3.24 Voice service profile AAL"
        ::= { zxGponVoIPMediaProfileEntry 20 }

    zxGponVoiceServiceProfileAALPSTNVariant OBJECT-TYPE
        SYNTAX      INTEGER
        MAX-ACCESS  read-write
        STATUS      current
        DESCRIPTION
        "This attribute controls which variant of POTS signalling shall be used on the associated UNIs.
        The value used is equal to the 'country code'. (R, Set-by-Create) (optional) (2 bytes)"
        REFERENCE   "G.983.2 section 7.3.24 Voice service profile AAL"
        ::= { zxGponVoIPMediaProfileEntry 21 }

    zxGponRTPProfileLocalPortMin OBJECT-TYPE
        SYNTAX      INTEGER
        MAX-ACCESS  read-write
        STATUS      current
        DESCRIPTION
        "This attribute defines the base RTP port that should be used for voice traffic.
        Default is 50000 (R, W, Set-by-create) (mandatory) (2 bytes)"
        REFERENCE   "G.983.2 section 7.3.108 RTP Profile Data"
        ::= { zxGponVoIPMediaProfileEntry 22 }

    zxGponRTPProfileLocalPortMax OBJECT-TYPE
        SYNTAX      INTEGER
        MAX-ACCESS  read-write
        STATUS      current
        DESCRIPTION
        "This attribute defines the top end range RTP port used for voice traffic.
        Default must be greater than LocalPortMin but is determined by vendor application. (R, W, Set-by-create) (optional) (2 bytes)"
        REFERENCE   "G.983.2 section 7.3.108 RTP Profile Data"
        ::= { zxGponVoIPMediaProfileEntry 23 }

    zxGponRTPProfileDSCPMark OBJECT-TYPE
        SYNTAX      INTEGER
        MAX-ACCESS  read-write
        STATUS      current
        DESCRIPTION
        "Diffserv code point to be used for outgoing RTP packets for this profile.
        Default value is Expedited Forwarding (EF) = 0x2E (0b00101110).  (R, W, Set-by-create) (mandatory) (1 byte)"
        REFERENCE   "G.983.2 section 7.3.108 RTP Profile Data"
        ::= { zxGponVoIPMediaProfileEntry 24 }

    zxGponRTPProfilePiggybackEvents OBJECT-TYPE
        SYNTAX      INTEGER{
                    disable(1),
                    enable(2)
                    }
        MAX-ACCESS  read-write
        STATUS      current
        DESCRIPTION
        "Enables or disables RTP piggyback events. 0x0 = Disabled. 0x1 = Enabled.
        Default value is Disabled (0x0).  (R, W, Set-by-create) (mandatory) (1 byte)"
        REFERENCE   "G.983.2 section 7.3.108 RTP Profile Data"
        ::= { zxGponVoIPMediaProfileEntry 25 }

    zxGponRTPProfileToneEvents OBJECT-TYPE
        SYNTAX      INTEGER{
                    disable(1),
                    enable(2)
                    }
        MAX-ACCESS  read-write
        STATUS      current
        DESCRIPTION
        "Enables or disables handling of tones via RTP Tone Events per RFC2833. 0x0 = Disabled. 0x1 = Enabled.
        Default value is Disabled (0x0).  (R, W, Set-by-create) (mandatory) (1 byte)"
        REFERENCE   "G.983.2 section 7.3.108 RTP Profile Data"
        ::= { zxGponVoIPMediaProfileEntry 26 }

    zxGponRTPProfileDTMFEvents OBJECT-TYPE
        SYNTAX      INTEGER{
                    disable(1),
                    enable(2)
                    }
        MAX-ACCESS  read-write
        STATUS      current
        DESCRIPTION
        "Enables or disables handling of DTMF via RTP DTMF Events per RFC2833.
        This attribute is ignored unless the OOB DTMF attribute in the VoIP Media Profile ME is set to enabled. 0x0 = Disabled. 0x1 = Enabled.
        Default value is Disabled (0x0).  (R, W, Set-by-create) (mandatory) (1 byte)"
        REFERENCE   "G.983.2 section 7.3.108 RTP Profile Data"
        ::= { zxGponVoIPMediaProfileEntry 27 }

    zxGponRTPProfileCASEvents OBJECT-TYPE
        SYNTAX      INTEGER{
                    disable(1),
                    enable(2)
                    }
        MAX-ACCESS  read-write
        STATUS      current
        DESCRIPTION
        "Enables or disables handling of CAS via RTP CAS Events per RFC2833. 0x0 = Disabled. 0x1 = Enabled.
        Default value is Disabled (0x0).  (R, W, Set-by-create) (mandatory) (1 byte)"
        REFERENCE   "G.983.2 section 7.3.108 RTP Profile Data"
        ::= { zxGponVoIPMediaProfileEntry 28 }

    zxGponVoIPMediaProfileRefCnt OBJECT-TYPE
        SYNTAX      INTEGER
        MAX-ACCESS  read-only
        STATUS      current
        DESCRIPTION
        "Forbidden to modify table entry if not equal zero."
        REFERENCE   "G.983.2 section 7.3.108 RTP Profile Data"
        ::= { zxGponVoIPMediaProfileEntry 29 }

    zxGponVoIPMediaProfileEntryStatus OBJECT-TYPE
        SYNTAX      RowStatus
        MAX-ACCESS  read-write
        STATUS      current
        DESCRIPTION
        ""
        REFERENCE   "G.983.2 section 7.3.107 VoIP Media Profile"
        ::= { zxGponVoIPMediaProfileEntry 30 }

--Network Dial Plan Table
    zxGponNetworkDialPlanTable    OBJECT-TYPE
        SYNTAX      SEQUENCE OF ZxGponNetworkDialPlanEntry
        MAX-ACCESS  not-accessible
        STATUS      current
        DESCRIPTION
            "An instance of this managed entity may be associated with one or more instances of the SIP User Data managed entity."
        REFERENCE   "G.983.2 section 7.3.112 Network Dial Plan Table"
        ::= { zxGponRmProfileMgmt 4 }

    zxGponNetworkDialPlanEntry OBJECT-TYPE
        SYNTAX      ZxGponNetworkDialPlanEntry
        MAX-ACCESS  not-accessible
        STATUS      current
        DESCRIPTION
            "It is entry in the zxGponNetworkDialPlanTable."
        INDEX   { zxGponNetworkDialPlanId }
        ::= { zxGponNetworkDialPlanTable 1 }

    ZxGponNetworkDialPlanEntry ::=
        SEQUENCE {
            zxGponNetworkDialPlanId                        INTEGER,
            zxGponNetworkDialPlanName                      OCTET STRING,
            zxGponNetworkDialPlanTableMaxSize              INTEGER,
            zxGponNetworkDialPlanCriticalDialTimeout       INTEGER,
            zxGponNetworkDialPlanParticalDialTimeout       INTEGER,
            zxGponNetworkDialPlanFormat                    INTEGER,
            zxGponNetworkDialPlanRefCnt                    INTEGER,
            zxGponNetworkDialPlanEntryStatus               RowStatus
        }

    zxGponNetworkDialPlanId OBJECT-TYPE
        SYNTAX      INTEGER
        MAX-ACCESS  not-accessible
        STATUS      current
        DESCRIPTION
        "This attribute provides a unique number for each instance of this managed entity.  (R, Set-by-create) (mandatory) (2 bytes)"
        REFERENCE   "G.983.2 section 7.3.112 Network Dial Plan Table"
        ::= { zxGponNetworkDialPlanEntry 1 }

    zxGponNetworkDialPlanName OBJECT-TYPE
        SYNTAX      OCTET STRING(SIZE(1..63))
        MAX-ACCESS  read-write
        STATUS      current
        DESCRIPTION
        "This attribute indicates the name of the dial plan table."
        REFERENCE   "G.983.2 section 7.3.112 Network Dial Plan Table"
        ::= { zxGponNetworkDialPlanEntry 2 }

    zxGponNetworkDialPlanTableMaxSize OBJECT-TYPE
        SYNTAX      INTEGER
        MAX-ACCESS  read-write
        STATUS      current
        DESCRIPTION
        "    This attribute indicates the maximum number of dial plans that can be stored in the dial
        plan table.  (R, Set-by-create) (mandatory) (2 bytes)"
        REFERENCE   "G.983.2 section 7.3.112 Network Dial Plan Table"
        ::= { zxGponNetworkDialPlanEntry 3 }

    zxGponNetworkDialPlanCriticalDialTimeout OBJECT-TYPE
        SYNTAX      INTEGER
        MAX-ACCESS  read-write
        STATUS      current
        DESCRIPTION
        "This attribute defines the critical dial timeout for digit map processing in milliseconds.
        Default value is 4000ms.  (R, W, Set-by-create) (mandatory) (2 bytes)"
        REFERENCE   "G.983.2 section 7.3.112 Network Dial Plan Table"
        ::= { zxGponNetworkDialPlanEntry 4 }

    zxGponNetworkDialPlanParticalDialTimeout OBJECT-TYPE
        SYNTAX      INTEGER
        MAX-ACCESS  read-write
        STATUS      current
        DESCRIPTION
        "This attribute defines the partial dial timeout for digit map processing in milliseconds.
        Default value is 16000ms.  (R, W, Set-by-create) (mandatory) (2 bytes)"
        REFERENCE   "G.983.2 section 7.3.112 Network Dial Plan Table"
        ::= { zxGponNetworkDialPlanEntry 5 }

    zxGponNetworkDialPlanFormat OBJECT-TYPE
        SYNTAX      INTEGER{
                    not-defined(1),
                    h248(2),
                    nsc(3),
                    vendor-specific(4)
                    }
        MAX-ACCESS  read-write
        STATUS      current
        DESCRIPTION
        "This attribute define the dial plan format standard that is supported in the ONT for VoIP.
        Valid values include 0 = not defined,  1 = H.248 format with specific plan (table entries define
        the dialing plan) 2=NSC format, 3=Vendor specific format.  Default is 1.  (R, W, Set-by-create) (mandatory) (1 bytes)"
        REFERENCE   "G.983.2 section 7.3.112 Network Dial Plan Table"
        ::= { zxGponNetworkDialPlanEntry 6 }

    zxGponNetworkDialPlanRefCnt OBJECT-TYPE
        SYNTAX      INTEGER
        MAX-ACCESS  read-only
        STATUS      current
        DESCRIPTION
        "Forbidden to modify if not equal zero"
        REFERENCE   "G.983.2 section 7.3.112 Network Dial Plan Table"
        ::= { zxGponNetworkDialPlanEntry 7 }

    zxGponNetworkDialPlanEntryStatus OBJECT-TYPE
        SYNTAX      RowStatus
        MAX-ACCESS  read-write
        STATUS      current
        DESCRIPTION
        ""
        REFERENCE   "G.983.2 section 7.3.112 Network Dial Plan Table"
        ::= { zxGponNetworkDialPlanEntry 8 }

--Network Dial Plan Table Operation
    zxGponNetworkDialPlanOperationTable    OBJECT-TYPE
        SYNTAX      SEQUENCE OF ZxGponNetworkDialPlanOperationEntry
        MAX-ACCESS  not-accessible
        STATUS      current
        DESCRIPTION
            "An instance of this managed entity may be associated with one or more instances of the SIP User Data managed entity.
            Here, the operations of Dial Plan Table are defined."
        REFERENCE   "G.983.2 section 7.3.112 Network Dial Plan Table"
        ::= { zxGponRmProfileMgmt 5 }

    zxGponNetworkDialPlanOperationEntry OBJECT-TYPE
        SYNTAX      ZxGponNetworkDialPlanOperationEntry
        MAX-ACCESS  not-accessible
        STATUS      current
        DESCRIPTION
            "It is entry in the zxGponNetworkDialPlanOperationTable."
        INDEX   { zxGponNetworkDialPlanId, zxGponNetworkDialPlanOperationTableId }
        ::= { zxGponNetworkDialPlanOperationTable 1 }

    ZxGponNetworkDialPlanOperationEntry ::=
        SEQUENCE {
            zxGponNetworkDialPlanOperationTableId                   INTEGER,
            zxGponNetworkDialPlanOperationToken                     OCTET STRING,
            zxGponNetworkDialPlanOperationEntryStatus               RowStatus
        }

    zxGponNetworkDialPlanOperationTableId OBJECT-TYPE
        SYNTAX      INTEGER
        MAX-ACCESS  not-accessible
        STATUS      current
        DESCRIPTION
        "A unique identifier of a dial plan within the dial plan table (1 byte);"
        REFERENCE   "G.983.2 section 7.3.112 Network Dial Plan Table"
        ::= { zxGponNetworkDialPlanOperationEntry 1 }

    zxGponNetworkDialPlanOperationToken OBJECT-TYPE
        SYNTAX      OCTET STRING(SIZE(1..28))
        MAX-ACCESS  read-write
        STATUS      current
        DESCRIPTION
        "Token used by the VoIP service to process dial plans.  This ASCII string is typically
        delimited by ':'.  (R, W) (conditionally required) (28 bytes)"
        REFERENCE   "G.983.2 section 7.3.112 Network Dial Plan Table"
        ::= { zxGponNetworkDialPlanOperationEntry 2 }

    zxGponNetworkDialPlanOperationEntryStatus OBJECT-TYPE
        SYNTAX      RowStatus
        MAX-ACCESS  read-write
        STATUS      current
        DESCRIPTION
        ""
        REFERENCE   "G.983.2 section 7.3.112 Network Dial Plan Table"
        ::= { zxGponNetworkDialPlanOperationEntry 3 }

--G.984.4 9.8.7    Pseudowire maintenance profile
    zxGponPwProfileTable    OBJECT-TYPE
        SYNTAX      SEQUENCE OF ZxGponPwProfileEntry
        MAX-ACCESS  not-accessible
        STATUS      current
        DESCRIPTION
            "The pseudowire maintenance profile permits the configuration of pseudowire
            service exception handling. It is created and deleted by the OLT."
        REFERENCE   "G.984.4 9.8.7    Pseudowire maintenance profile"
        ::= { zxGponRmProfileMgmt 6 }

    zxGponPwProfileEntry OBJECT-TYPE
        SYNTAX      ZxGponPwProfileEntry
        MAX-ACCESS  not-accessible
        STATUS      current
        DESCRIPTION
            "It is entry in the zxGponPwProfileTable."
        INDEX   {zxGponPwProfileId }
        ::= { zxGponPwProfileTable 1 }

    ZxGponPwProfileEntry ::=
        SEQUENCE {
            zxGponPwProfileId                     INTEGER,
            zxGponPwProfileName                   OCTET STRING,
            zxGponPwProfileJtrBfrMaxDepth         INTEGER,
            zxGponPwProfileJtrBfrDesireDepth      INTEGER,
            zxGponPwProfileFillPolicy             INTEGER,
            zxGponPwProfileMisconnectPacketDeclr  INTEGER,
            zxGponPwProfileMisconnectPacketClr    INTEGER,
            zxGponPwProfileLossPacketDeclr        INTEGER,
            zxGponPwProfileLossPacketClr          INTEGER,
            zxGponPwProfileBfrDeclr               INTEGER,
            zxGponPwProfileBfrClr                 INTEGER,
            zxGponPwProfileMalformedPacketDeclr   INTEGER,
            zxGponPwProfileMalformedPacketClr     INTEGER,
            zxGponPwProfileRbitTxset              INTEGER,
            zxGponPwProfileRbitTxClr              INTEGER,
            zxGponPwProfileRbitRecieve            INTEGER,
            zxGponPwProfileLbitRecieve            INTEGER,
            zxGponPwProfileSesThreshold           INTEGER,
            zxGponPwProfileRefCnt                 INTEGER,
            zxGponPwProfileEntryStatus            RowStatus
        }

    zxGponPwProfileId OBJECT-TYPE
        SYNTAX      INTEGER
        MAX-ACCESS  not-accessible
        STATUS      current
        DESCRIPTION
        "This attribute provides a unique number for each instance of this managed entity.
        (R, Set-by-create) (mandatory) (2 bytes)"
        ::= { zxGponPwProfileEntry 1 }

    zxGponPwProfileName OBJECT-TYPE
        SYNTAX      OCTET STRING(SIZE(1..63))
        MAX-ACCESS  read-write
        STATUS      current
        DESCRIPTION
        "This attribute provides a unique name for each instance of this managed entity.
        (R, Set-by-create) (mandatory) (2 bytes)"
        ::= { zxGponPwProfileEntry 2 }

    zxGponPwProfileJtrBfrMaxDepth OBJECT-TYPE
        SYNTAX      INTEGER
        MAX-ACCESS  read-write
        STATUS      current
        DESCRIPTION
        "This attribute specifies the desired maximum depth of the playout buffer in the
        PSN to TDM direction. The value is expressed as a multiple of the 125 us frame rate.
        The default value 0 selects the ONT's internal policy. (R, W, Set-by-create) (optional) (2 bytes)"
        ::= { zxGponPwProfileEntry 3 }

    zxGponPwProfileJtrBfrDesireDepth OBJECT-TYPE
        SYNTAX      INTEGER
        MAX-ACCESS  read-write
        STATUS      current
        DESCRIPTION
        "This attribute specifies the desired nominal fill depth of the playout buffer in the PSN to TDM
        direction. The value is expressed as a multiple of the 125 us frame rate. The default value 0 selects
        the ONT's internal policy. (R, W, Set-by-create) (optional) (2 bytes)"
        ::= { zxGponPwProfileEntry 4 }

    zxGponPwProfileFillPolicy OBJECT-TYPE
        SYNTAX      INTEGER
        MAX-ACCESS  read-write
        STATUS      current
        DESCRIPTION
        "TThis attribute defines the payload bit pattern to be applied toward the TDM service if no payload
        packet is available to play out. The default value 0 specifies that the ONT apply its internal policy.
        0    ONT default, vendor-specific (recommended: AIS for unstructured service, all 1s for structured service)
        1    Play out AIS according to the service definition (for example, DS3 AIS)
        2    Play out all 1s
        3    Play out all 0s
        4    Repeat the previous data
        5    Play out DS1 idle (ANSI T1.403-1999 appendix C)
        6..15    Reserved for future standardization
        16..255    Vendor-specific, not to be standardized.(R, W, Set-by-create) (optional) (1 byte)"
        ::= { zxGponPwProfileEntry 5 }

    zxGponPwProfileMisconnectPacketDeclr  OBJECT-TYPE
        SYNTAX      INTEGER
        MAX-ACCESS  read-write
        STATUS      current
        DESCRIPTION
        "The alarm declaration policy attribute defines the anomaly rate that causes the corresponding alarm
        to be declared. It is an integer percentage between 1..100. If this density of anomalies occurs during
        the alarm onset soak interval, the alarm is declared. The default value 0 selects the ONT's internal policy.
        (R, W, Set-by-create) (optional) (1 byte)"
        ::= { zxGponPwProfileEntry 6 }

    zxGponPwProfileMisconnectPacketClr  OBJECT-TYPE
        SYNTAX      INTEGER
        MAX-ACCESS  read-write
        STATUS      current
        DESCRIPTION
        "The alarm clear policy attribute defines the anomaly rate that causes the corresponding alarm to be
        cleared. It is an integer percentage between 0..99. If no more than this density of anomalies occurs
        during the alarm clear soak interval, the alarm is cleared. The default value 255 selects the ONT's
        internal policy. (R, W, Set-by-create) (optional) (1 byte)"
        ::= { zxGponPwProfileEntry 7 }

    zxGponPwProfileLossPacketDeclr     OBJECT-TYPE
        SYNTAX      INTEGER
        MAX-ACCESS  read-write
        STATUS      current
        DESCRIPTION
        "(R, W, Set-by-create) (optional) (1 byte)"
        ::= { zxGponPwProfileEntry 8 }

    zxGponPwProfileLossPacketClr     OBJECT-TYPE
        SYNTAX      INTEGER
        MAX-ACCESS  read-write
        STATUS      current
        DESCRIPTION
        "(R, W, Set-by-create) (optional) (1 byte)"
        ::= { zxGponPwProfileEntry 9 }

    zxGponPwProfileBfrDeclr     OBJECT-TYPE
        SYNTAX      INTEGER
        MAX-ACCESS  read-write
        STATUS      current
        DESCRIPTION
        "(R, W, Set-by-create) (optional) (1 byte)"
        ::= { zxGponPwProfileEntry 10 }

    zxGponPwProfileBfrClr     OBJECT-TYPE
        SYNTAX      INTEGER
        MAX-ACCESS  read-write
        STATUS      current
        DESCRIPTION
        "(R, W, Set-by-create) (optional) (1 byte)"
        ::= { zxGponPwProfileEntry 11 }

    zxGponPwProfileMalformedPacketDeclr     OBJECT-TYPE
        SYNTAX      INTEGER
        MAX-ACCESS  read-write
        STATUS      current
        DESCRIPTION
        "(R, W, Set-by-create) (optional) (1 byte)"
        ::= { zxGponPwProfileEntry 12 }

    zxGponPwProfileMalformedPacketClr     OBJECT-TYPE
        SYNTAX      INTEGER
        MAX-ACCESS  read-write
        STATUS      current
        DESCRIPTION
        "(R, W, Set-by-create) (optional) (1 byte)"
        ::= { zxGponPwProfileEntry 13}

    zxGponPwProfileRbitTxset OBJECT-TYPE
        SYNTAX      INTEGER
        MAX-ACCESS  read-write
        STATUS      current
        DESCRIPTION
        "This attribute defines the number of consecutive lost packets that causes
        the transmitted R bit to be set in the TDM to PSN direction, indicating lost
        packets to the far end. The default value 0 selects the ONT's internal policy.
        (R, W, Set-by-create) (optional) (1 byte)"
        ::= { zxGponPwProfileEntry 14 }

    zxGponPwProfileRbitTxClr OBJECT-TYPE
        SYNTAX      INTEGER
        MAX-ACCESS  read-write
        STATUS      current
        DESCRIPTION
        "This attribute defines the number of consecutive valid packets that causes the
        transmitted R bit to be cleared in the TDM to PSN direction, removing the remote
        failure indication to the far end. The default value 0 selects the ONT's internal
        policy. (R, W, Set-by-create) (optional) (1 byte)"
        ::= { zxGponPwProfileEntry 15 }

    zxGponPwProfileRbitRecieve OBJECT-TYPE
        SYNTAX      INTEGER{
                    doNothing(1),
                    playOutSrvSpecialCode(2),
                    sendChannelIdle(3)
                    }
        MAX-ACCESS  read-write
        STATUS      current
        DESCRIPTION
        "This attribute defines the action toward the Nx64 TDM interface when remote
        failure is indicated on packets received from the PSN (either R bit set or M = 0b10
        while the L bit is cleared).
        0    Do nothing (default)
        1    Play out service-specific RAI/REI/RDI code
        2    Send channel idle signalling and idle channel payload to all DS0s comprising the service
        (R, W, Set-by-create) (optional) (1 byte)"
        ::= { zxGponPwProfileEntry 16 }

    zxGponPwProfileLbitRecieve OBJECT-TYPE
        SYNTAX      INTEGER{
                    playOutAIS(1),
                    repeatLast(2),
                    sendChannelIdle(3)
                    }
        MAX-ACCESS  read-write
        STATUS      current
        DESCRIPTION
        "This attribute defines the action toward the TDM interface when far end TDM failure
        is indicated on packets received from the PSN (L bit set).
        0    Play out service-specific AIS (default)
        1    Repeat last received packet
        2    Send channel idle signalling and idle channel payload to all DS0s comprising the service
        (R, W, Set-by-create) (optional) (1 byte)"
        ::= { zxGponPwProfileEntry 17 }

    zxGponPwProfileSesThreshold OBJECT-TYPE
        SYNTAX      INTEGER
        MAX-ACCESS  read-write
        STATUS      current
        DESCRIPTION
        "Number of lost, malformed or otherwise unusable packets expected in the PSN to TDM
        direction within a one-second interval that causes a severely errored second to be counted.
        Stray packets do not count toward a severely errored second, nor do packets whose L bit is
        set at the far end. The default value is 3. (R, W, Set-by-create) (optional) (2 bytes)"
        ::= { zxGponPwProfileEntry 18 }

    zxGponPwProfileRefCnt OBJECT-TYPE
        SYNTAX      INTEGER
        MAX-ACCESS  read-only
        STATUS      current
        DESCRIPTION
        "Forbidden to delete table entry if not equal zero."
        ::= { zxGponPwProfileEntry 19 }

    zxGponPwProfileEntryStatus OBJECT-TYPE
        SYNTAX      RowStatus
        MAX-ACCESS  read-write
        STATUS      current
        DESCRIPTION
        "This attribute specifies the action of this entry."
        ::= { zxGponPwProfileEntry 30 }

--VoIP Application Service Profile
--not implemented yet!
    zxGponVoipAppServiceProfileTable    OBJECT-TYPE
        SYNTAX      SEQUENCE OF ZxGponVoipAppServiceProfileEntry
        MAX-ACCESS  not-accessible
        STATUS      current
        DESCRIPTION
            "An instance of this managed entity is referenced by the SIP User Data ME."
        REFERENCE   "G.983.2 section 7.3.113 VoIP Application Service Profile"
        ::= { zxGponRmProfileMgmt 7 }

    zxGponVoipAppServiceProfileEntry OBJECT-TYPE
        SYNTAX      ZxGponVoipAppServiceProfileEntry
        MAX-ACCESS  not-accessible
        STATUS      current
        DESCRIPTION
            "It is entry in the zxGponVoipAppServiceProfileTable."
        INDEX   { zxGponVoipAppServiceProfileName }
        ::= { zxGponVoipAppServiceProfileTable 1 }

    ZxGponVoipAppServiceProfileEntry ::=
        SEQUENCE {
            zxGponVoipAppServiceProfileName                       DisplayString,
            zxGponVoipAppServiceProfileCIDFeature                 INTEGER,
            zxGponVoipAppServiceProfileCallWaitingFeature         INTEGER,
            zxGponVoipAppServiceProfileCallProgressFeature        INTEGER,
            zxGponVoipAppServiceProfileCallPresentationFeature    INTEGER,
            zxGponVoipAppServiceProfileDirectConnectFeature       INTEGER,
            zxGponVoipAppServiceProfileDirectConnectURI           OCTET STRING,
            zxGponVoipAppDcUriAuthMode                            INTEGER,
            zxGponVoipAppDcUriUsername                            OCTET STRING,
            zxGponVoipAppDcUriPassword                            OCTET STRING,
            zxGponVoipAppDcUriRealm                               OCTET STRING,
            zxGponVoipAppServiceProfileBridgeLineAgentURI         OCTET STRING,
            zxGponVoipAppBlaUriAuthMode                           INTEGER,
            zxGponVoipAppBlaUriUsername                           OCTET STRING,
            zxGponVoipAppBlaUriPassword                           OCTET STRING,
            zxGponVoipAppBlaUriRealm                              OCTET STRING,
            zxGponVoipAppServiceProfileConferenceFactoryURI       OCTET STRING,
            zxGponVoipAppCcUriAuthMode                            INTEGER,
            zxGponVoipAppCcUriUsername                            OCTET STRING,
            zxGponVoipAppCcUriPassword                            OCTET STRING,
            zxGponVoipAppCcUriRealm                               OCTET STRING,
            zxGponVoipAppServiceProfileEntryStatus                RowStatus
        }

    zxGponVoipAppServiceProfileName OBJECT-TYPE
        SYNTAX      DisplayString(SIZE(1..32))
        MAX-ACCESS  not-accessible
        STATUS      current
        DESCRIPTION
        "The profile name of VoIP application service."
        REFERENCE   "G.983.2 section 7.3.113 VoIP application service profile"
        ::= { zxGponVoipAppServiceProfileEntry 1 }

    zxGponVoipAppServiceProfileCIDFeature OBJECT-TYPE
        SYNTAX      INTEGER
        MAX-ACCESS  read-create
        STATUS      current
        DESCRIPTION
        "This attribute contains a bitmap of caller ID features. Bit clear is
        disabled  and bit set is enabled. The bit position values are:
        0x01 Calling Number
        0x02 Calling Name
        0x04 CID blocking (both number and name)
        0x08 CID number- Permanent presentation status for number (0 = Public, 1 = Private)
        0x10 CID name - Permanent presentation status for name (0 = Public, 1 = Private)
        0x20 Anonymous CID blocking (ACR)
        0x40 - 0x80 not used
        The default value shall be disabled (0).  (R, W, Set-by-create) (mandatory) (1 byte)
        "
        REFERENCE   "G.983.2 section 7.3.113 VoIP Application Service Profile"
        ::= { zxGponVoipAppServiceProfileEntry 2 }

    zxGponVoipAppServiceProfileCallWaitingFeature OBJECT-TYPE
        SYNTAX      INTEGER
        MAX-ACCESS  read-create
        STATUS      current
        DESCRIPTION
        "This attribute contains a bitmap of caller waiting features. Bit clear is disabled
        and bit set is enabled. The bit position values are:
        0x01 call waiting
        0x02 Caller ID Announcement
        0x04 - 0x80 not used
        The default value shall be disabled (0).  (R, W, Set-by-create) (mandatory) (1 byte)
        "
        REFERENCE   "G.983.2 section 7.3.113 VoIP Application Service Profile"
        ::= { zxGponVoipAppServiceProfileEntry 3 }

     zxGponVoipAppServiceProfileCallProgressFeature OBJECT-TYPE
        SYNTAX      INTEGER
        MAX-ACCESS  read-create
        STATUS      current
        DESCRIPTION
        "This attribute contains a bitmap of call processing features. Bit clear is disabled
        and bit set is enabled. The bit position values are:
        0x0001 3way
        0x0002 call transfer
        0x0004 call hold
        0x0008 call park
        0x0010 do not disturb
        0x0020 Flash on Emergency Service call. (Flash is to be processed during an Emergency Service call)
        0x0040 Emergency Service originating hold (determines if a call clearing is to be performed on an on-hook during an Emergency Service call)
        0x0080 6way
        0x0100 - 0x8000 not used
        The default value shall be disabled (0).  (R, W, Set-by-create) (mandatory) (2 bytes)
        "
        REFERENCE   "G.983.2 section 7.3.113 VoIP Application Service Profile"
        ::= { zxGponVoipAppServiceProfileEntry 4 }

    zxGponVoipAppServiceProfileCallPresentationFeature OBJECT-TYPE
        SYNTAX      INTEGER
        MAX-ACCESS  read-create
        STATUS      current
        DESCRIPTION
        "This attribute contains a bitmap of call presentation features. Bit clear is disabled
        and bit set is enabled. The bit position values are:
        0x0001 Message Waiting Indication Splash Ring
        0x0002 Message Waiting Indication Special Dial tone
        0x0004 Message Waiting Indication Visual Indication
        0x0008 Call Forwarding Indication
        0x0010 - 0x8000 not used
        The default value shall be disabled (0).  (R, W, Set-by-create) (mandatory) (2 bytes)
        "
        REFERENCE   "G.983.2 section 7.3.113 VoIP Application Service Profile"
        ::= { zxGponVoipAppServiceProfileEntry 5 }

    zxGponVoipAppServiceProfileDirectConnectFeature OBJECT-TYPE
        SYNTAX      INTEGER
        MAX-ACCESS  read-create
        STATUS      current
        DESCRIPTION
        "This attribute contains a bitmap of characteristics associated with the direct connect
        feature. Bit clear is disabled and bit set is enabled. The bit position values are:
        0x01 direct connect feature enabled
        0x02 dial tone feature delay option
        The default value shall be disabled (0).  (R, W, Set-by-create) (mandatory) (1 byte)
        "
        REFERENCE   "G.983.2 section 7.3.113 VoIP Application Service Profile"
        ::= { zxGponVoipAppServiceProfileEntry 6 }

    zxGponVoipAppServiceProfileDirectConnectURI OBJECT-TYPE
        SYNTAX      OCTET STRING(SIZE(0..128))
        MAX-ACCESS  read-create
        STATUS      current
        DESCRIPTION
        "This attribute points to a Network Address managed entity.
        If this attribute is set to 0xFFFF, no URI is defined.
        If this attribute is set to any other value, it should point to a Network Address managed entity. Network Address ME indicates the URI of the Direct Connect.
        Default value is 0xFFFF. (R, W, Set-by-create) (mandatory) (2 bytes)
        "
        REFERENCE   "G.983.2 section 7.3.113 VoIP Application Service Profile"
        ::= { zxGponVoipAppServiceProfileEntry 7 }

    zxGponVoipAppDcUriAuthMode OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL { disable }
        ::= { zxGponVoipAppServiceProfileEntry 8 }

    zxGponVoipAppDcUriUsername OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponVoipAppServiceProfileEntry 9 }

    zxGponVoipAppDcUriPassword OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponVoipAppServiceProfileEntry 10 }

    zxGponVoipAppDcUriRealm OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponVoipAppServiceProfileEntry 11 }

    zxGponVoipAppServiceProfileBridgeLineAgentURI OBJECT-TYPE
        SYNTAX      OCTET STRING(SIZE(0..128))
        MAX-ACCESS  read-create
        STATUS      current
        DESCRIPTION
        "This attribute points to a Network Address managed entity.
        If this attribute is set to 0xFFFF, no URI is defined.
        If this attribute is set to any other value, it should point to a Network Address
        managed entity. Network Address ME indicates the URI of the Bridged Line Agent.
        Default value is 0xFFFF. (R, W, Set-by-create) (mandatory) (2 bytes)
        "
        REFERENCE   "G.983.2 section 7.3.113 VoIP Application Service Profile"
        ::= { zxGponVoipAppServiceProfileEntry 12 }

    zxGponVoipAppBlaUriAuthMode OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL { disable }
        ::= { zxGponVoipAppServiceProfileEntry 13 }

    zxGponVoipAppBlaUriUsername OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponVoipAppServiceProfileEntry 14 }

    zxGponVoipAppBlaUriPassword OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponVoipAppServiceProfileEntry 15 }

    zxGponVoipAppBlaUriRealm OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponVoipAppServiceProfileEntry 16 }

    zxGponVoipAppServiceProfileConferenceFactoryURI OBJECT-TYPE
        SYNTAX      OCTET STRING(SIZE(0..375))
        MAX-ACCESS  read-create
        STATUS      current
        DESCRIPTION
        "This attribute points to a Network Address managed entity.
        If this attribute is set to 0xFFFF, no URI is defined.
        If this attribute is set to any other value, it should point to a Network Address
        managed entity. Network Address ME indicates the URI of the Conference Factory.
        Default value is 0xFFFF. (R, W, Set-by-create) (mandatory) (2 bytes)
        "
        REFERENCE   "G.983.2 section 7.3.113 VoIP Application Service Profile"
        ::= { zxGponVoipAppServiceProfileEntry 17 }

    zxGponVoipAppCcUriAuthMode OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL { disable }
        ::= { zxGponVoipAppServiceProfileEntry 18 }

    zxGponVoipAppCcUriUsername OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponVoipAppServiceProfileEntry 19 }

    zxGponVoipAppCcUriPassword OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponVoipAppServiceProfileEntry 20 }

    zxGponVoipAppCcUriRealm OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponVoipAppServiceProfileEntry 21 }

    zxGponVoipAppServiceProfileEntryStatus OBJECT-TYPE
        SYNTAX      RowStatus
        MAX-ACCESS  read-create
        STATUS      current
        DESCRIPTION
        ""
        REFERENCE   "G.983.2 section 7.3.113 VoIP Application Service Profile"
        ::= { zxGponVoipAppServiceProfileEntry 50 }

--VoIP Feature Access Codes
--not implemented yet!
    zxGponVoipFeatureAccessCodeTable    OBJECT-TYPE
        SYNTAX      SEQUENCE OF ZxGponVoipFeatureAccessCodeEntry
        MAX-ACCESS  not-accessible
        STATUS      current
        DESCRIPTION
            "An instance of this managed entity is referenced by the SIP User
            Data ME. Each access code is a string of characters from the set
            {0..9, *, #}, with trailing nulls in any unused bytes."
        REFERENCE   "G.983.2 section 7.3.115 VoIP Feature Access Codes"
        ::= { zxGponRmProfileMgmt 8 }

    zxGponVoipFeatureAccessCodeEntry OBJECT-TYPE
        SYNTAX      ZxGponVoipFeatureAccessCodeEntry
        MAX-ACCESS  not-accessible
        STATUS      current
        DESCRIPTION
            "It is entry in the zxGponVoipFeatureAccessCodeTable."
        INDEX   { zxGponFeatureAccessCodePrfName }
        ::= { zxGponVoipFeatureAccessCodeTable 1 }

    ZxGponVoipFeatureAccessCodeEntry ::=
        SEQUENCE {
            zxGponFeatureAccessCodePrfName                        DisplayString,
            zxGponVoipFeatureAccessCodeCancelCallWaiting          OCTET STRING,
            zxGponVoipFeatureAccessCodeCallHold                   OCTET STRING,
            zxGponVoipFeatureAccessCodeCallPark                   OCTET STRING,
            zxGponVoipFeatureAccessCodeCIDSActivate               OCTET STRING,
            zxGponVoipFeatureAccessCodeCIDSDeactivate             OCTET STRING,
            zxGponVoipFeatureAccessCodeDoNotDisturbActivation     OCTET STRING,
            zxGponVoipFeatureAccessCodeDoNotDisturbDeactivation   OCTET STRING,
            zxGponVoipFeatureAccessCodeDoNotDisturbPINChange      OCTET STRING,
            zxGponVoipFeatureAccessCodeEmergencyServiceNumber     OCTET STRING,
            zxGponVoipFeatureAccessCodeIntercomService            OCTET STRING,
            zxGponVoipFacUnattendedCallTrans                      OCTET STRING,
            zxGponVoipFacAttendedCallTrans                        OCTET STRING,
            zxGponVoipFeatureAccessCodeEntryStatus                RowStatus
        }

    zxGponFeatureAccessCodePrfName OBJECT-TYPE
        SYNTAX      DisplayString(SIZE(1..32))
        MAX-ACCESS  not-accessible
        STATUS      current
        DESCRIPTION
        "The profile name of VoIP feature access codes."
        REFERENCE   "G.983.2 section 7.3.115 VoIP feature access codes"
        ::= { zxGponVoipFeatureAccessCodeEntry 1 }

    zxGponVoipFeatureAccessCodeCancelCallWaiting OBJECT-TYPE
        SYNTAX      OCTET STRING(SIZE(5))
        MAX-ACCESS  read-create
        STATUS      current
        DESCRIPTION
        "This attribute defines the feature access code for cancel call waiting.
        (R, W) (optional) (5 bytes)"
        REFERENCE   "G.983.2 section 7.3.115 VoIP Feature Access Codes"
        ::= { zxGponVoipFeatureAccessCodeEntry 2 }

    zxGponVoipFeatureAccessCodeCallHold OBJECT-TYPE
        SYNTAX      OCTET STRING(SIZE(5))
        MAX-ACCESS  read-create
        STATUS      current
        DESCRIPTION
        "This attribute defines the feature access code for call hold.
        (R, W) (optional) (5 bytes)"
        REFERENCE   "G.983.2 section 7.3.115 VoIP Feature Access Codes"
        ::= { zxGponVoipFeatureAccessCodeEntry 3 }

    zxGponVoipFeatureAccessCodeCallPark OBJECT-TYPE
        SYNTAX      OCTET STRING(SIZE(5))
        MAX-ACCESS  read-create
        STATUS      current
        DESCRIPTION
        "This attribute defines the feature access code for call park.
        (R, W) (optional) (5 bytes)"
        REFERENCE   "G.983.2 section 7.3.115 VoIP Feature Access Codes"
        ::= { zxGponVoipFeatureAccessCodeEntry 4 }

    zxGponVoipFeatureAccessCodeCIDSActivate OBJECT-TYPE
        SYNTAX      OCTET STRING(SIZE(5))
        MAX-ACCESS  read-create
        STATUS      current
        DESCRIPTION
        "This attribute defines the feature access code for CIDS activate.
        (R, W) (optional) (5 bytes)"
        REFERENCE   "G.983.2 section 7.3.115 VoIP Feature Access Codes"
        ::= { zxGponVoipFeatureAccessCodeEntry 5 }

    zxGponVoipFeatureAccessCodeCIDSDeactivate OBJECT-TYPE
        SYNTAX      OCTET STRING(SIZE(5))
        MAX-ACCESS  read-create
        STATUS      current
        DESCRIPTION
        "This attribute defines the feature access code for CIDS deactivate.
        (R, W) (optional) (5 bytes)"
        REFERENCE   "G.983.2 section 7.3.115 VoIP Feature Access Codes"
        ::= { zxGponVoipFeatureAccessCodeEntry 6 }

    zxGponVoipFeatureAccessCodeDoNotDisturbActivation OBJECT-TYPE
        SYNTAX      OCTET STRING(SIZE(5))
        MAX-ACCESS  read-create
        STATUS      current
        DESCRIPTION
        "This attribute defines the feature access code to activate do not
        disturb. (R, W) (optional) (5 bytes)"
        REFERENCE   "G.983.2 section 7.3.115 VoIP Feature Access Codes"
        ::= { zxGponVoipFeatureAccessCodeEntry 7 }

    zxGponVoipFeatureAccessCodeDoNotDisturbDeactivation OBJECT-TYPE
        SYNTAX      OCTET STRING(SIZE(5))
        MAX-ACCESS  read-create
        STATUS      current
        DESCRIPTION
        "This attribute defines the feature access code to deactivate do not
        disturb. (R, W) (optional) (5 bytes)"
        REFERENCE   "G.983.2 section 7.3.115 VoIP Feature Access Codes"
        ::= { zxGponVoipFeatureAccessCodeEntry 8 }

    zxGponVoipFeatureAccessCodeDoNotDisturbPINChange OBJECT-TYPE
        SYNTAX      OCTET STRING(SIZE(5))
        MAX-ACCESS  read-create
        STATUS      current
        DESCRIPTION
        "This attribute defines the feature access code for do not disturb.
        (R, W) (optional) (5 bytes)"
        REFERENCE   "G.983.2 section 7.3.115 VoIP Feature Access Codes"
        ::= { zxGponVoipFeatureAccessCodeEntry 9 }

    zxGponVoipFeatureAccessCodeEmergencyServiceNumber OBJECT-TYPE
        SYNTAX      OCTET STRING(SIZE(5))
        MAX-ACCESS  read-create
        STATUS      current
        DESCRIPTION
        " This attribute defines the emergency service number. Example: 911.
        (R, W) (optional) (5 bytes)"
        REFERENCE   "G.983.2 section 7.3.115 VoIP Feature Access Codes"
        ::= { zxGponVoipFeatureAccessCodeEntry 10 }

    zxGponVoipFeatureAccessCodeIntercomService OBJECT-TYPE
        SYNTAX      OCTET STRING(SIZE(5))
        MAX-ACCESS  read-create
        STATUS      current
        DESCRIPTION
        "This attribute defines the feature access code for in home intercom
        service. (R, W) (optional) (5 bytes)"
        REFERENCE   "G.983.2 section 7.3.115 VoIP Feature Access Codes"
        ::= { zxGponVoipFeatureAccessCodeEntry 11 }

    zxGponVoipFacUnattendedCallTrans OBJECT-TYPE
        SYNTAX      OCTET STRING(SIZE(5))
        MAX-ACCESS  read-create
        STATUS      current
        DESCRIPTION
        "This attribute defines the feature access code for unattended call
        trans. (R, W) (optional) (5 bytes)"
        REFERENCE   "G.983.2 section 7.3.115 VoIP Feature Access Codes"
        ::= { zxGponVoipFeatureAccessCodeEntry 12 }

    zxGponVoipFacAttendedCallTrans OBJECT-TYPE
        SYNTAX      OCTET STRING(SIZE(5))
        MAX-ACCESS  read-create
        STATUS      current
        DESCRIPTION
        "This attribute defines the feature access code for attended call
        trans. (R, W) (optional) (5 bytes)"
        REFERENCE   "G.983.2 section 7.3.115 VoIP Feature Access Codes"
        ::= { zxGponVoipFeatureAccessCodeEntry 13 }

    zxGponVoipFeatureAccessCodeEntryStatus OBJECT-TYPE
        SYNTAX      RowStatus
        MAX-ACCESS  read-create
        STATUS      current
        DESCRIPTION
        ""
        REFERENCE   "G.983.2 section 7.3.115 VoIP Feature Access Codes"
        ::= { zxGponVoipFeatureAccessCodeEntry 50 }

--Traffic Scheduler Profile
    zxGponTrafficSchedulerProfileTable    OBJECT-TYPE
        SYNTAX      SEQUENCE OF ZxGponTrafficSchedulerProfileEntry
        MAX-ACCESS  not-accessible
        STATUS      current
        DESCRIPTION
            "An instance of this managed entity is referenced by the TrafficSchedulerUNI."
        REFERENCE   "Private ME"
        ::= { zxGponRmProfileMgmt 9 }

    zxGponTrafficSchedulerProfileEntry OBJECT-TYPE
        SYNTAX      ZxGponTrafficSchedulerProfileEntry
        MAX-ACCESS  not-accessible
        STATUS      current
        DESCRIPTION
            "It is entry in the zxGponTrafficSchedulerProfileTable."
        INDEX   { zxGponTrafficSchedulerProfileId }
        ::= { zxGponTrafficSchedulerProfileTable 1 }

    ZxGponTrafficSchedulerProfileEntry ::=
        SEQUENCE {
            zxGponTrafficSchedulerProfileId                         INTEGER,
            zxGponTrafficSchedulerProfileName                       OCTET STRING,
            zxGponTrafficSchedulerProfileMode                       INTEGER,
            zxGponTrafficSchedulerProfileQueueMap                   OCTET STRING,
            zxGponTrafficSchedulerProfileQueueWeight                OCTET STRING,
            zxGponTrafficSchedulerProfileRefCnt                     INTEGER,
            zxGponTrafficSchedulerProfileEntryStatus                RowStatus
        }

    zxGponTrafficSchedulerProfileId OBJECT-TYPE
        SYNTAX      INTEGER
        MAX-ACCESS  not-accessible
        STATUS      current
        DESCRIPTION
        "Profile index."
        REFERENCE   ""
        ::= { zxGponTrafficSchedulerProfileEntry 1 }

    zxGponTrafficSchedulerProfileName OBJECT-TYPE
        SYNTAX      OCTET STRING(SIZE(1..63))
        MAX-ACCESS  read-write
        STATUS      current
        DESCRIPTION
        ""
        REFERENCE   ""
        ::= { zxGponTrafficSchedulerProfileEntry 2 }

    zxGponTrafficSchedulerProfileMode OBJECT-TYPE
        SYNTAX      INTEGER{
                    sp(1),
                    wrr(2),
                    spwrr(3),
                    default(4)
                    }
        MAX-ACCESS  read-write
        STATUS      current
        DESCRIPTION
        "This attribute defines the schedule mode.
        'default(4)' means using the default mode of ONT.
        "
        REFERENCE   ""
        ::= { zxGponTrafficSchedulerProfileEntry 3 }

    zxGponTrafficSchedulerProfileQueueMap OBJECT-TYPE
        SYNTAX      OCTET STRING(SIZE(8))
        MAX-ACCESS  read-write
        STATUS      current
        DESCRIPTION
        "This attribute defines the queue map of 802.1p prioriry.
        Each byte stands for the queue id(0~7).
        Default as:
        802.1p priority            cos queue id
        0                          0
        1                          0
        2                          1
        3                          1
        4                          2
        5                          2
        6                          3
        7                          3
        "
        REFERENCE   ""
        ::= { zxGponTrafficSchedulerProfileEntry 4 }

    zxGponTrafficSchedulerProfileQueueWeight OBJECT-TYPE
        SYNTAX      OCTET STRING(SIZE(8))
        MAX-ACCESS  read-write
        STATUS      current
        DESCRIPTION
        "This attribute defines the queue weight.
        Each byte stands for the weight(0~15) of queue.
        "
        REFERENCE   ""
        ::= { zxGponTrafficSchedulerProfileEntry 5 }

    zxGponTrafficSchedulerProfileRefCnt OBJECT-TYPE
        SYNTAX      INTEGER
        MAX-ACCESS  read-write
        STATUS      current
        DESCRIPTION
        "This attribute defines the reference count of this profile.
        If the reference is nonzero, this profile cannot be deleted or modified."
        REFERENCE   ""
        ::= { zxGponTrafficSchedulerProfileEntry 6 }

    zxGponTrafficSchedulerProfileEntryStatus OBJECT-TYPE
        SYNTAX      RowStatus
        MAX-ACCESS  read-write
        STATUS      current
        DESCRIPTION
        ""
        REFERENCE   ""
        ::= { zxGponTrafficSchedulerProfileEntry 7 }

   --IGMP Profile
   zxGponIgmpProfileTable    OBJECT-TYPE
        SYNTAX      SEQUENCE OF ZxGponIgmpProfileEntry
        MAX-ACCESS  not-accessible
        STATUS      current
        DESCRIPTION
            "This managed entity organizes data associated with IGMP profile."
        REFERENCE   "G.984.4 9.3.27 Multicast operations profile"
        ::= { zxGponRmProfileMgmt 10 }

    zxGponIgmpProfileEntry OBJECT-TYPE
        SYNTAX      ZxGponIgmpProfileEntry
        MAX-ACCESS  not-accessible
        STATUS      current
        DESCRIPTION
            "It is entry in the zxGponIgmpProfileEntry."
        INDEX   {zxGponIgmpProfileId}
        ::= { zxGponIgmpProfileTable 1 }

    ZxGponIgmpProfileEntry ::=
        SEQUENCE {
            zxGponIgmpProfileId                 Integer32,
            zxGponIgmpProfileName               OCTET STRING,
            zxGponIgmpVersion                   INTEGER,
            zxGponIgmpWorkMode                  INTEGER,
            zxGponIgmpFastLeaveEnable           TruthValue,
            zxGponIgmpUpstreamTagMode           INTEGER,
            zxGponIgmpUpstreamVlanTag           INTEGER,
            zxGponIgmpUpstreamPriority          INTEGER,
            zxGponIgmpUpstreamMaxRate           Integer32,
            zxGponIgmpRobustness                INTEGER,
            zxGponIgmpProxyAddressType          InetAddressType,
            zxGponIgmpProxyIpAddress            InetAddress,
            zxGponIgmpQueryInterval             Integer32,
            zxGponIgmpQueryMaxRspTime           Integer32,
            zxGponIgmpLastMembQueryInterval     Integer32,
            zxGponIgmpUnauthJoinFwdEnable       TruthValue,
            zxGponIptvDynamicPackageIdNames      DisplayString,
            zxGponIptvStaticPackageIdNames       DisplayString,
            zxGponIgmpRefCnt                    Integer32,
            zxGponIgmpRowStatus                 RowStatus
        }

    zxGponIgmpProfileId OBJECT-TYPE
        SYNTAX      Integer32
        MAX-ACCESS  not-accessible
        STATUS      current
        DESCRIPTION
            "This attribute provides a unique number for each instance of this
             managed entity. "
        ::= { zxGponIgmpProfileEntry 1 }

    zxGponIgmpProfileName OBJECT-TYPE
        SYNTAX      OCTET STRING(SIZE(1..64))
        MAX-ACCESS  read-create
        STATUS      current
        DESCRIPTION
            "This attribute specifies the version of IGMP to be supported."
        ::= { zxGponIgmpProfileEntry 2 }

    zxGponIgmpVersion OBJECT-TYPE
        SYNTAX      INTEGER{
                    v1(1),
                    v2(2),
                    v3(3)
                    }
        MAX-ACCESS  read-create
        STATUS      current
        DESCRIPTION
            "This attribute specifies the version of IGMP to be supported."
        ::= { zxGponIgmpProfileEntry 3 }

    zxGponIgmpWorkMode  OBJECT-TYPE
        SYNTAX      INTEGER{
                    snooping(1),
                    spr(2),
                    proxy(3)
                    }
        MAX-ACCESS  read-create
        STATUS      current
        DESCRIPTION
            "This attribute enables an IGMP function.
            The default value 1 specifies transparent IGMP snooping only.
            The value 2 specifies snooping with proxy reporting (SPR);
            the value 3 specifies IGMP proxy."
        DEFVAL { snooping }
        ::= { zxGponIgmpProfileEntry 4 }

    zxGponIgmpFastLeaveEnable     OBJECT-TYPE
        SYNTAX      TruthValue
        MAX-ACCESS  read-create
        STATUS      current
        DESCRIPTION
            "This attribute enables the fast leave function.
             The default value false disables fast leave;
             true enables immediate leave."
        DEFVAL { false }
        ::= { zxGponIgmpProfileEntry 5 }

    zxGponIgmpUpstreamTagMode     OBJECT-TYPE
        SYNTAX      INTEGER{
                    transparent(1),
                    addTag(2),
                    replaceVidAndPrio(3),
                    replaceVid(4)
                    }
        MAX-ACCESS  read-create
        STATUS      current
        DESCRIPTION
            "This attribute controls the upstream IGMP TCI attribute."
        ::= { zxGponIgmpProfileEntry 6 }

    zxGponIgmpUpstreamVlanTag     OBJECT-TYPE
        SYNTAX      INTEGER(0..4094)
        MAX-ACCESS  read-create
        STATUS      current
        DESCRIPTION
            "Under control of the upstream IGMP tag control attribute,
             the attribute defines a VLAN ID to add to upstream IGMP
             messages.While zxGponIgmpUpstreamTagMode is 'transparent'
             the value is 0."
        ::= { zxGponIgmpProfileEntry 7 }

     zxGponIgmpUpstreamPriority     OBJECT-TYPE
        SYNTAX      INTEGER(0..7)
        MAX-ACCESS  read-create
        STATUS      current
        DESCRIPTION
            "Under control of the upstream IGMP tag control attribute,
             the attribute defines a priority to add to upstream IGMP
             messages."
        ::= { zxGponIgmpProfileEntry 8 }

    zxGponIgmpUpstreamMaxRate   OBJECT-TYPE
        SYNTAX      Integer32
        UNITS        "pps"
        MAX-ACCESS  read-create
        STATUS      current
        DESCRIPTION
            "This attribute limits the maximum rate of upstream IGMP traffic.
             The default value 0 imposes no rate limit on this traffic"
        DEFVAL { 0 }
        ::= { zxGponIgmpProfileEntry 9 }

    zxGponIgmpRobustness     OBJECT-TYPE
        SYNTAX      INTEGER(0..255)
        MAX-ACCESS  read-create
        STATUS      current
        DESCRIPTION
            "This attribute allows tuning for possible packet loss in the
             network.
             default value 0 causes the ONT to follow the IETF recommendation
             to copy the robustness value from query messages originating
             further upstream."
        DEFVAL { 0 }
        ::= { zxGponIgmpProfileEntry 10 }

    zxGponIgmpProxyAddressType OBJECT-TYPE
        SYNTAX       InetAddressType
        MAX-ACCESS   read-create
        STATUS       current
        DESCRIPTION
            "This attribute specifies the IP address typr to be used by a
             proxy querier."
        DEFVAL { ipv4 }
        ::= { zxGponIgmpProfileEntry 11 }

    zxGponIgmpProxyIpAddress     OBJECT-TYPE
        SYNTAX      InetAddress
        MAX-ACCESS  read-create
        STATUS      current
        DESCRIPTION
            "This attribute specifies the IP address to be used by a proxy
             querier.
             Although it is not a legitimate IP address, the default value
             0.0.0.0 is legal in this case (see RFC 4541)."
        ::= { zxGponIgmpProfileEntry 12 }

    zxGponIgmpQueryInterval   OBJECT-TYPE
        SYNTAX      Integer32
        UNITS       "s"
        MAX-ACCESS  read-create
        STATUS      current
        DESCRIPTION
            "This attribute specifies the interval between general queries in
             seconds.
             The default is 125 seconds."
        DEFVAL { 125 }
        ::= { zxGponIgmpProfileEntry 13 }

    zxGponIgmpQueryMaxRspTime OBJECT-TYPE
        SYNTAX      Integer32
        UNITS       "0.1s"
        MAX-ACCESS  read-create
        STATUS      current
        DESCRIPTION
            "This attribute is the max response time added by the proxy
             into general query messages directed to UNIs.
             It is expressed in tenths of seconds, with a default of 100
             (10 seconds)."
        DEFVAL { 100 }
        ::= { zxGponIgmpProfileEntry 14 }

    zxGponIgmpLastMembQueryInterval OBJECT-TYPE
        SYNTAX      Integer32
        UNITS       "0.1s"
        MAX-ACCESS  read-create
        STATUS      current
        DESCRIPTION
            "This attribute specifies the max response time inserted
            into group-specific queries sent to UNIs in response to group
            leave messages.
            It is also the repetition rate of [robustness] transmissions of
            the query.It is specified in tenths of seconds, with a default
            of 10 (1 second)."
        DEFVAL { 10 }
        ::= { zxGponIgmpProfileEntry 15 }

    zxGponIgmpUnauthJoinFwdEnable OBJECT-TYPE
        SYNTAX      TruthValue
        MAX-ACCESS  read-create
        STATUS      current
        DESCRIPTION
            "This object attribute specifies the ONT's behaviour when it
            receives an IGMP join request for a group that is not authorized
            in the dynamic addess control list table, or an IGMPv3 membership
            report for groups, none of which are authorized in the dynamic
            ACL.
            The default value false specifies that the ONT silently discard
            the IGMP request;
            the value true specifies that the ONT forward the request
            upstream.
            The ONT does not attempt to honour the request for the
            unauthorized group(s) in either case."
        DEFVAL { false }
        ::= { zxGponIgmpProfileEntry 16 }

    zxGponIptvDynamicPackageIdNames OBJECT-TYPE
        SYNTAX      DisplayString
        MAX-ACCESS  read-create
        STATUS      current
        DESCRIPTION
            "This attribute specifies the IPTV dynamic package name list,
             such as 'AA,BB,CC,,,FF,,'."
        ::= { zxGponIgmpProfileEntry 17 }

    zxGponIptvStaticPackageIdNames OBJECT-TYPE
        SYNTAX      DisplayString
        MAX-ACCESS  read-create
        STATUS      current
        DESCRIPTION
            "This attribute specifies the IPTV Static name list,
             such as 'AA'."
        ::= { zxGponIgmpProfileEntry 18 }

    zxGponIgmpRefCnt OBJECT-TYPE
        SYNTAX      Integer32
        MAX-ACCESS  read-only
        STATUS      current
        DESCRIPTION
            "Forbidden to delete table entry if not equal zero."
        ::= { zxGponIgmpProfileEntry 19 }

    zxGponIgmpRowStatus OBJECT-TYPE
        SYNTAX      RowStatus
        MAX-ACCESS  read-create
        STATUS      current
        DESCRIPTION
            "This attribute specifies the action of this entry."
        REFERENCE   "G.984.4 9.3.27 Multicast operations profile"
        ::= { zxGponIgmpProfileEntry 50 }

--SIP Profile
    zxGponSipProfileTable    OBJECT-TYPE
        SYNTAX      SEQUENCE OF ZxGponSipProfileEntry
        MAX-ACCESS  not-accessible
        STATUS      current
        DESCRIPTION
            "This table includes sip profile configuration."
        ::= { zxGponRmProfileMgmt 11 }

    zxGponSipProfileEntry OBJECT-TYPE
        SYNTAX      ZxGponSipProfileEntry
        MAX-ACCESS  not-accessible
        STATUS      current
        DESCRIPTION
            "It is entry in the zxGponSipProfileTable."
        INDEX   { zxGponSipProfileId }
        ::= { zxGponSipProfileTable 1 }

    ZxGponSipProfileEntry ::=
        SEQUENCE {
            zxGponSipProfileId                                 Integer32,
            zxGponSipProfileName                               OCTET STRING,
            zxGponSipProxyServerAddress                        OCTET STRING,
            zxGponSipOutboundProxyAddress                      OCTET STRING,
            zxGponSipPrimaryDns                                IpAddress,
            zxGponSipSecondaryDns                              IpAddress,
            zxGponSipUdpPort                                   INTEGER,
            zxGponSipIpHostId                                  INTEGER,
            zxGponSipRegExpTime                                INTEGER,
            zxGponSipReregHeadStartTime                        INTEGER,
            zxGponSipHostPartUri                               OCTET STRING,
            zxGponSipRegServer                                 OCTET STRING,
            zxGponSipValidationScheme                          INTEGER,
            zxGponSipRegUsername                               OCTET STRING,
            zxGponSipRegPassword                               OCTET STRING,
            zxGponSipRealm                                     OCTET STRING,
            zxGponSipSsVendor                                  OCTET STRING,
            zxGponSipNetworkDialPlanPtr                        Integer32,
            zxGponSipReleaseTimer                              INTEGER,
            zxGponSipRohTimer                                  INTEGER,
            zxGponSipTosDscpOption                             INTEGER,
            zxGponSipTosDscpValue                              Integer32,
            zxGponSipMediaUdpPort                              Integer32,
            zxGponSipMediaTosDscpOption                        INTEGER,
            zxGponSipMediaTosDscpValue                         Integer32,
            zxGponSipLinkTestEnable                            INTEGER,
            zxGponSipLinkTestInterval                          Integer32,
            zxGponSipRefCnt                                    Integer32,
            zxGponSipRowStatus                                 RowStatus,
            zxGponVoipAppServicePrf                            DisplayString,
            zxGponVoipFeatureAccessCodePrf                     DisplayString
        }

    zxGponSipProfileId OBJECT-TYPE
        SYNTAX      Integer32
        MAX-ACCESS  not-accessible
        STATUS      current
        DESCRIPTION "This object indicates the profile ID."
        ::= { zxGponSipProfileEntry 1 }

    zxGponSipProfileName OBJECT-TYPE
        SYNTAX      OCTET STRING(SIZE(1..64))
        MAX-ACCESS  read-create
        STATUS      current
        DESCRIPTION "This object indicates the profile name."
        ::= { zxGponSipProfileEntry 2 }

    zxGponSipProxyServerAddress OBJECT-TYPE
        SYNTAX      OCTET STRING(SIZE(0..128))
        MAX-ACCESS  read-create
        STATUS      current
        DESCRIPTION
        "This attribute points to a large string ME that contains
         the name (IP address or URI) of the SIP proxy server for
         SIP signalling messages. (R, W, Set-by-create)
         (mandatory) (2 bytes)"
        REFERENCE   "G984.4 section 9.9.3 "
        ::= { zxGponSipProfileEntry 3 }

    zxGponSipOutboundProxyAddress OBJECT-TYPE
        SYNTAX      OCTET STRING(SIZE(0..128))
        MAX-ACCESS  read-create
        STATUS      current
        DESCRIPTION
        "This attribute points to a large string ME that contains the name
         (IP address or URI) of the outbound proxy server for SIP signalling
         messages. An outbound SIP proxy may or may not be required within
         a given network. If an outbound SIP proxy is used, the outbound
         proxy address pointer attribute must be set to point to a valid
         large string ME. If an outbound SIP proxy is not used, the outbound
         proxy address pointer attribute must be set to a null pointer.
         (R, W, Set by create) (mandatory) (2 bytes)"
        REFERENCE   "G984.4 section 9.9.3"
        ::= { zxGponSipProfileEntry 4 }

    zxGponSipPrimaryDns OBJECT-TYPE
        SYNTAX      IpAddress
        MAX-ACCESS  read-create
        STATUS      current
        DESCRIPTION
        "This attribute specifies the primary SIP DNS IP address.
         If this value is 0, no primary SIP DNS is defined.
         The default value is 0. (R, W, Set-by-create)
         (mandatory) (4 bytes)"
        REFERENCE   "G984.4 section 9.9.3"
        DEFVAL {0.0.0.0}
        ::= { zxGponSipProfileEntry 5 }

    zxGponSipSecondaryDns OBJECT-TYPE
        SYNTAX      IpAddress
        MAX-ACCESS  read-create
        STATUS      current
        DESCRIPTION
        "This attribute specifies the secondary SIP DNS IP address.
         If this value is 0, no secondary SIP DNS is defined.
         The default value is 0. (R, W, Set-by-create)
         (mandatory) (4 bytes)"
        REFERENCE   "G984.4 section 9.9.3"
        DEFVAL {0.0.0.0}
        ::= { zxGponSipProfileEntry 6 }

    zxGponSipUdpPort OBJECT-TYPE
        SYNTAX      INTEGER(1..65535)
        MAX-ACCESS  read-create
        STATUS      current
        DESCRIPTION
        "This attribute specifies the port number that offers the UDP
         service. (R, W, Set-by-create) (mandatory) (2 bytes)"
        REFERENCE   "G984.4 section 9.4.14"
        DEFVAL {5060}
        ::= { zxGponSipProfileEntry 7 }

    zxGponSipIpHostId OBJECT-TYPE
        SYNTAX      INTEGER(1..255)
        MAX-ACCESS  read-create
        STATUS      current
        DESCRIPTION
        "This attribute points to the IP host config data ME associated
         with this TCP/UDP data. Any number of ports and protocols may
         be associated with an IP host. (R, W, Set-by-create)
         (mandatory) (2 bytes).
         This value comes from 'IP Host Config Data' table."
        REFERENCE   "G984.4 section 9.4.14"
        DEFVAL {1}
        ::= { zxGponSipProfileEntry 8 }

    zxGponSipRegExpTime OBJECT-TYPE
        SYNTAX      INTEGER(0..2147483647)
        UNITS        "s"
        MAX-ACCESS  read-create
        STATUS      current
        DESCRIPTION
        "This attribute defines the SIP Registration Expiration Time in
         seconds. If this value is zero, the SIP Agent will not add an
         expiration time to the registration requests, and will not
         perform re-registration. The default value used at Create shall
         be 3600 seconds. (R, W) (mandatory) (4 bytes)"
        REFERENCE   "G.984.4 section 9.9.3"
        DEFVAL {3600}
        ::= { zxGponSipProfileEntry 9 }

    zxGponSipReregHeadStartTime OBJECT-TYPE
        SYNTAX      INTEGER(0..2147483647)
        UNITS        "s"
        MAX-ACCESS  read-create
        STATUS      current
        DESCRIPTION
        "This attribute provides the time in seconds prior to timeout that the
        SIP Agent should start the re-registration process.  The default value
        used at Create shall be 360 seconds. (R, W) (mandatory) (4 bytes)"
        REFERENCE   "G.984.4 section 9.9.3"
        DEFVAL {360}
        ::= { zxGponSipProfileEntry 10 }

    zxGponSipHostPartUri OBJECT-TYPE
        SYNTAX      OCTET STRING(SIZE(0..128))
        MAX-ACCESS  read-create
        STATUS      current
        DESCRIPTION
        "This attribute provides a pointer to a LargeString ME that contains
         the host or domain part of the SIP Address of Record for users
         connected to this ONT. A 0xFFFF indicates the current address
         in the IP Host Config ME is used. Default value is 0xFFFF.
         (R, W, Set-by-create) (mandatory) (2 bytes)"
        REFERENCE   "G.984.4 section 9.9.3"
        ::= { zxGponSipProfileEntry 11 }

    zxGponSipRegServer OBJECT-TYPE
        SYNTAX      OCTET STRING(SIZE(0..128))
        MAX-ACCESS  read-create
        STATUS      current
        DESCRIPTION
        "This attribute provides a pointer to a Network Address ME that
         contains the name (IP address or resolved name) of the SIP
         Registrar Server for SIP signaling messages.
         Examples: '10.10.10.10' and 'proxy.voip.net'.
         Default value is 0xFFFF. (R, W, Set-by-create) (mandatory) (2 bytes)"
        REFERENCE   "G.984.4 section 9.9.3"
        ::= { zxGponSipProfileEntry 12 }

    zxGponSipValidationScheme OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL { disable }
        ::= { zxGponSipProfileEntry 13 }

    zxGponSipRegUsername OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponSipProfileEntry 14 }

    zxGponSipRegPassword OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponSipProfileEntry 15 }

    zxGponSipRealm OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponSipProfileEntry 16 }

    zxGponSipSsVendor OBJECT-TYPE
        SYNTAX      OCTET STRING(SIZE(0..4))
        MAX-ACCESS  read-create
        STATUS      current
        DESCRIPTION
        "This attribute identifies the SIP Gateway softswitch vendor.
         The format is four ASCII coded alphabetic characters [A - Z]
         as defined in ANSI T1.220, All NULL characters indicates no
         particular vendor. (R,W, Set-by-create) (mandatory) (4 byte)"
        REFERENCE   "G.984.4 section 9.9.3"
        ::= { zxGponSipProfileEntry 17 }

    zxGponSipNetworkDialPlanPtr OBJECT-TYPE
        SYNTAX      Integer32
        MAX-ACCESS  read-create
        STATUS      current
        DESCRIPTION
        "Pointer to Network Dial Plan ME. A value of 0xFFFF indicates that no
         network dial plan is available. Default value is 0xFFFF.
         (R, W, Set-by-create) (mandatory) (2 bytes)"
        REFERENCE   "G.984.4 section 9.9.3"
        DEFVAL {0}
        ::= { zxGponSipProfileEntry 18 }

    zxGponSipReleaseTimer OBJECT-TYPE
        SYNTAX      INTEGER(0..255)
        UNITS       "s"
        MAX-ACCESS  read-create
        STATUS      current
        DESCRIPTION
        "This attribute contains a release timer defined in seconds.
         0x0 = Use internal default, Default value is 10 sec. (R, W)
         (optional)(1 byte)"
        REFERENCE   "G.984.4 section 9.9.3"
        DEFVAL {10}
        ::= { zxGponSipProfileEntry 19 }

    zxGponSipRohTimer OBJECT-TYPE
        SYNTAX      INTEGER(0..255)
        UNITS       "s"
        MAX-ACCESS  read-create
        STATUS      current
        DESCRIPTION
        "This attribute defines the length of time in seconds for the
         receiver off hook condition before ROH tone is applied.
         0x0 = ROH is disabled. Default value is 15 seconds.
         (R,W) (optional) (1 byte)"
        REFERENCE   "G.983.2 section 7.3.106 Sip User Data"
        DEFVAL {15}
        ::= { zxGponSipProfileEntry 20 }

    zxGponSipTosDscpOption  OBJECT-TYPE
        SYNTAX      INTEGER
        {
            tos(1),
            dscp(2)
        }
        MAX-ACCESS  read-create
        STATUS      current
        DESCRIPTION
            "The mode of QoS tag.
            1:tos
            2:dscp"
        ::= { zxGponSipProfileEntry 21 }

    zxGponSipTosDscpValue  OBJECT-TYPE
        SYNTAX      Integer32(0..63)
        MAX-ACCESS  read-create
        STATUS      current
        DESCRIPTION
            "This attribute assocites with 'zxGponSipTosDscpOption'.
            Tos values: 0~7; Dscp values: 0~63."
        ::= { zxGponSipProfileEntry 22 }


    zxGponSipMediaUdpPort OBJECT-TYPE
        SYNTAX      Integer32(1..65535)
        MAX-ACCESS  read-create
        STATUS      current
        DESCRIPTION
            "This attribute specifies the port number that offers the UDP
             service. (R, W, Set-by-create) (mandatory) (2 bytes)"
        REFERENCE   "G984.4 section 9.4.14"
        DEFVAL {5060}
        ::= { zxGponSipProfileEntry 23 }

    zxGponSipMediaTosDscpOption  OBJECT-TYPE
        SYNTAX      INTEGER
        {
            tos(1),
            dscp(2)
        }
        MAX-ACCESS  read-create
        STATUS      current
        DESCRIPTION
            "The mode of QoS tag.
            1:tos
            2:dscp"
        ::= { zxGponSipProfileEntry 24 }

    zxGponSipMediaTosDscpValue  OBJECT-TYPE
        SYNTAX      Integer32(0..63)
        MAX-ACCESS  read-create
        STATUS      current
        DESCRIPTION
            "This attribute assocites with 'zxGponSipMediaTosDscpOption'.
            Tos values: 0~7; Dscp values: 0~63."
        ::= { zxGponSipProfileEntry 25 }

    zxGponSipLinkTestEnable  OBJECT-TYPE
        SYNTAX      INTEGER
        {
            disabled(1),
            enabled(2)
        }
        MAX-ACCESS  read-create
        STATUS      current
        DESCRIPTION
            "Heart beat message type."
        DEFVAL {disabled}
        ::= { zxGponSipProfileEntry 26 }

    zxGponSipLinkTestInterval  OBJECT-TYPE
        SYNTAX      Integer32(10000..600000)
        UNITS       "s"
        MAX-ACCESS  read-create
        STATUS      current
        DESCRIPTION
            "This attribute specifies Link Test Interval in seconds.
            Value 0 (not set). The default value is 20 seconds."
        DEFVAL {20}
        ::= { zxGponSipProfileEntry 27 }

    zxGponSipRefCnt OBJECT-TYPE
        SYNTAX      Integer32
        MAX-ACCESS  read-only
        STATUS      current
        DESCRIPTION
            "Forbidden to delete table entry if not equal zero."
        ::= { zxGponSipProfileEntry 29 }

    zxGponSipRowStatus OBJECT-TYPE
        SYNTAX      RowStatus
        MAX-ACCESS  read-create
        STATUS      current
        DESCRIPTION
            "The row status of this entry."
        ::= { zxGponSipProfileEntry 30 }

    zxGponVoipAppServicePrf  OBJECT-TYPE
        SYNTAX       DisplayString(SIZE(0..32))
        MAX-ACCESS  read-create
        STATUS      current
        DESCRIPTION
            "This attribute refers to the name of table
             '.zxGponVoipAppServiceProfileTable'."
        ::= { zxGponSipProfileEntry 40 }

    zxGponVoipFeatureAccessCodePrf  OBJECT-TYPE
        SYNTAX       DisplayString(SIZE(0..32))
        MAX-ACCESS  read-create
        STATUS      current
        DESCRIPTION
            "This attribute refers to the name of table
             'zxGponVoipFeatureAccessCodeTable'."
        ::= { zxGponSipProfileEntry 41 }


--MGC Profile
    zxGponMgcProfileTable    OBJECT-TYPE
        SYNTAX      SEQUENCE OF ZxGponMgcProfileEntry
        MAX-ACCESS  not-accessible
        STATUS      current
        DESCRIPTION
            "This table includes mgc profile configuration."
        ::= { zxGponRmProfileMgmt 12 }

    zxGponMgcProfileEntry OBJECT-TYPE
        SYNTAX      ZxGponMgcProfileEntry
        MAX-ACCESS  not-accessible
        STATUS      current
        DESCRIPTION
            "It is entry in the zxGponMgcProfileTable."
        INDEX   { zxGponMgcProfileId }
        ::= { zxGponMgcProfileTable 1 }

    ZxGponMgcProfileEntry ::=
        SEQUENCE {
            zxGponMgcProfileId                                 Integer32,
            zxGponMgcProfileName                               OCTET STRING,
            zxGponMgcPrimaryServer                             OCTET STRING,
            zxGponMgcPrimaryValidScheme                        INTEGER,
            zxGponMgcPrimaryUsername                           OCTET STRING,
            zxGponMgcPrimaryPassword                           OCTET STRING,
            zxGponMgcPrimaryRealm                              OCTET STRING,
            zxGponMgcSecondaryServer                           OCTET STRING,
            zxGponMgcSecondaryValidScheme                      INTEGER,
            zxGponMgcSecondaryUsername                         OCTET STRING,
            zxGponMgcSecondaryPassword                         OCTET STRING,
            zxGponMgcSecondaryRealm                            OCTET STRING,
            zxGponMgcMessageFormat                             INTEGER,
            zxGponMgcUdpPort                                   INTEGER,
            zxGponMgcIpHostId                                  INTEGER,
            zxGponMgcVersion                                   INTEGER,
            zxGponMgcMaxRetryTime                              INTEGER,
            zxGponMgcMaxRetryAttempts                          INTEGER,
            zxGponMgcServiceChangeDelay                        INTEGER,
            zxGponMgcSsVendor                                  OCTET STRING,
            zxGponMgcTidPrefix                                 DisplayString,
            zxGponMgcUserTidAssignPolicy                       INTEGER,
            zxGponMgcUserTidPrefix                             DisplayString,
            zxGponMgcUserTidPostfixLen                         INTEGER,
            zxGponMgcUserTidPostfixStartNum                    INTEGER,
            zxGponMgcRtpTidAssignPolicy                        INTEGER,
            zxGponMgcRtpTidPrefix                              DisplayString,
            zxGponMgcRtpTidPostfixLen                          INTEGER,
            zxGponMgcRtpTidPostfixStartNum                     INTEGER,
            zxGponMgcTosDscpOption                             INTEGER,
            zxGponMgcTosDscpValue                              INTEGER,
            zxGponMgcMediaUdpPort                              INTEGER,
            zxGponMgcMediaTosDscpOption                        INTEGER,
            zxGponMgcMediaTosDscpValue                         INTEGER,
            zxGponMgcHeartBeatMsgType                          INTEGER,
            zxGponMgcHeartBeatInterval                         Integer32,
            zxGponMgcRtpLinkDetection                          INTEGER,
            zxGponMgcNumShortestMatch                          INTEGER,
            zxGponMgcDigitMapLongTimer                         INTEGER,
            zxGponMgcDigitMapShortTimer                        INTEGER,
            zxGponMgcDigitMapStartTimer                        INTEGER,
            zxGponMgcMinReregTimer                             Integer32,
            zxGponMgcMaxReregTimer                             Integer32,
            zxGponMgcRegMsgRetranTimer                         Integer32,
            zxGponMgcTotalRetranTime                           Integer32,
            zxGponMgcPassiveHeartBeatEnable                    INTEGER,
            zxGponMgcMinAvalancheTimer                         Integer32,
            zxGponMgcMaxAvalancheTimer                         Integer32,
            zxGponMgcRefCnt                                    Integer32,
            zxGponMgcRowStatus                                 RowStatus
        }

    zxGponMgcProfileId OBJECT-TYPE
        SYNTAX      Integer32
        MAX-ACCESS  not-accessible
        STATUS      current
        DESCRIPTION "This object indicates the profile ID."
        ::= { zxGponMgcProfileEntry 1 }

    zxGponMgcProfileName OBJECT-TYPE
        SYNTAX      OCTET STRING(SIZE(1..64))
        MAX-ACCESS  read-create
        STATUS      current
        DESCRIPTION "This object indicates the profile name."
        ::= { zxGponMgcProfileEntry 2 }

    zxGponMgcPrimaryServer    OBJECT-TYPE
        SYNTAX      OCTET STRING(SIZE(0..128))
        MAX-ACCESS  read-create
        STATUS      current
        DESCRIPTION
        "This attribute points to a network address ME that contains the name
         (IP address or resolved name) of the primary MGC that controls the
         signalling  messages.  (R, W, Set-by-create) (mandatory) (2 bytes)"
        REFERENCE   "G.984.4 section 9.9.16     MGC config data"
        ::= { zxGponMgcProfileEntry 3 }

    zxGponMgcPrimaryValidScheme OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL {disable}
        ::= { zxGponMgcProfileEntry 4 }

    zxGponMgcPrimaryUsername    OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponMgcProfileEntry 5 }

    zxGponMgcPrimaryPassword    OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponMgcProfileEntry 6 }

    zxGponMgcPrimaryRealm    OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponMgcProfileEntry 7 }

    zxGponMgcSecondaryServer    OBJECT-TYPE
        SYNTAX      OCTET STRING(SIZE(0..128))
        MAX-ACCESS  read-create
        STATUS      current
        DESCRIPTION
        "This attribute points to a network address ME that contains the name
         (IP address or resolved name) of the secondary or backup MGC that
         controls the signalling  messages.  (R, W, Set-by-create)
         (mandatory) (2 bytes)"
        REFERENCE   "G.984.4 section 9.9.16     MGC config data"
        ::= { zxGponMgcProfileEntry 8 }

    zxGponMgcSecondaryValidScheme OBJECT-TYPE
        SYNTAX      INTEGER{
                    disable(1),
                    md5(2),
                    basic(3)
                    }
        MAX-ACCESS  read-create
        STATUS      current
        DESCRIPTION
        "This attribute specifies the validation scheme used when the ONT
         validates a challenge. Validation schemes are defined as follows:
         1  Validation disabled.
         2  Validate using MD5 digest authentication as defined in
            [IETF RFC 2069] (recommended).
         3  Validate using basic authentication as defined in
            [IETF RFC 2617].(R, W) (mandatory) (1 byte)"
        REFERENCE   "G.984.4 section 9.12.4"
        DEFVAL {disable}
        ::= { zxGponMgcProfileEntry 9 }

    zxGponMgcSecondaryUsername    OBJECT-TYPE
        SYNTAX      OCTET STRING(SIZE(0..25))
        MAX-ACCESS  read-create
        STATUS      current
        DESCRIPTION
        "This string attribute is the user name. If the string is shorter
         than 25 bytes, it must be null terminated (Note). (R, W)
         (mandatory) (25 bytes)"
        REFERENCE   "G.984.4 section 9.12.4"
        ::= { zxGponMgcProfileEntry 10 }

    zxGponMgcSecondaryPassword    OBJECT-TYPE
        SYNTAX      OCTET STRING(SIZE(0..25))
        MAX-ACCESS  read-create
        STATUS      current
        DESCRIPTION
        "This string attribute is the password. If the string is shorter
         than 25 bytes, it must be null terminated. (R, W)
         (mandatory) (25 bytes)"
        REFERENCE   "G.984.4 section 9.12.4"
        ::= { zxGponMgcProfileEntry 11 }

    zxGponMgcSecondaryRealm    OBJECT-TYPE
        SYNTAX      OCTET STRING(SIZE(0..25))
        MAX-ACCESS  read-create
        STATUS      current
        DESCRIPTION
        "This string attribute specifies the realm used in digest
         authentication. If the string is shorter than 25 bytes,
         it must be null terminated. (R, W) (mandatory) (25 bytes)"
        REFERENCE   "G.984.4 section 9.12.4"
        ::= { zxGponMgcProfileEntry 12 }

    zxGponMgcMessageFormat OBJECT-TYPE
        SYNTAX      INTEGER{
                    textLong(1),
                    textShort(2),
                    binary(3)
                    }
        MAX-ACCESS  read-create
        STATUS      current
        DESCRIPTION
        "This attribute defines the message format. Valid values are:
         1 Text long
         2 Text short
         3 Binary
         The default value is 0. (R, W, Set-by-create) (mandatory) (1 byte)"
        REFERENCE   "G984.4 section 9.4.14"
        DEFVAL { textLong}
        ::= { zxGponMgcProfileEntry 13 }

    zxGponMgcUdpPort OBJECT-TYPE
        SYNTAX      INTEGER(1..65535)
        MAX-ACCESS  read-create
        STATUS      current
        DESCRIPTION
        "This attribute specifies the port number that offers the TCP/UDP
         service. (R, W, Set-by-create) (mandatory) (2 bytes)
         The port is optional and defaults to 2944 for text message formats
         and 2955 for binary message formats. (R, W, Set by create)
         (mandatory) (2 bytes)"
        REFERENCE   "G984.4 section 9.4.14"
        ::= { zxGponMgcProfileEntry 14 }

    zxGponMgcIpHostId OBJECT-TYPE
        SYNTAX      INTEGER(1..255)
        MAX-ACCESS  read-create
        STATUS      current
        DESCRIPTION
        "This attribute points to the IP host config data ME associated
         with this TCP/UDP data. Any number of ports and protocols may
         be associated with an IP host. (R, W, Set-by-create)
         (mandatory) (2 bytes).
         This value come from 'IP Host Config Data' table.
         This attribute is deprecated."
        REFERENCE   "G984.4 section 9.4.14"
        DEFVAL {1}
        ::= { zxGponMgcProfileEntry 15 }

    zxGponMgcVersion OBJECT-TYPE
        SYNTAX      INTEGER(1..255)
        MAX-ACCESS  read-create
        STATUS      current
        DESCRIPTION
        "This integer attribute reports the version of the Megaco protocol
         in use. (R, W, Set-by-create) (mandatory) (1 byte)"
        REFERENCE   "G984.4 section 9.4.14"
        ::= { zxGponMgcProfileEntry 16 }

    zxGponMgcMaxRetryTime OBJECT-TYPE
        SYNTAX      INTEGER(0..65535)
        UNITS       "s"
        MAX-ACCESS  read-create
        STATUS      current
        DESCRIPTION
        "This attribute specifies the maximum retry time for MGC transactions,
         in seconds. The default value 0 specifies vendor-specific
         implementation (R, W) (optional) (2 bytes)"
        REFERENCE   "G984.4 section 9.4.14"
        DEFVAL {0}
        ::= { zxGponMgcProfileEntry 17 }

    zxGponMgcMaxRetryAttempts OBJECT-TYPE
        SYNTAX      INTEGER(0..65535)
        MAX-ACCESS  read-create
        STATUS      current
        DESCRIPTION
        "This attribute specifies the maximum number of times a message
         is retransmitted to the MGC. The default value 0 specifies
         vendor-specific implementation. (R, W, Set-by-create) (optional)
         (2 bytes)"
        REFERENCE   "G984.4 section 9.4.14"
        DEFVAL {0}
        ::= { zxGponMgcProfileEntry 18 }

    zxGponMgcServiceChangeDelay OBJECT-TYPE
        SYNTAX      INTEGER(0..65535)
        UNITS       "s"
        MAX-ACCESS  read-create
        STATUS      current
        DESCRIPTION
        "The attribute specifies the service status delay time for changes
         in line service status. This attribute is specified in seconds.
         The default value 0 specifies no delay. (R, W) (optional) (2 bytes)"
        REFERENCE   "G984.4 section 9.4.14"
        DEFVAL {0}
        ::= { zxGponMgcProfileEntry 19 }

    zxGponMgcSsVendor   OBJECT-TYPE
        SYNTAX      OCTET STRING (SIZE(0..4))
        MAX-ACCESS  read-create
        STATUS      current
        DESCRIPTION
        "This attribute identifies the gateway softswitch vendor. The format
        is four ASCII coded alphabetic characters [A..Z] as defined in
        [ATIS 0322000]. A value of four null characters indicates no particular
        vendor. (R, W, Set-by-create) (mandatory) (4 bytes)"
        REFERENCE   "G984.4 section 9.4.14"
        ::={ zxGponMgcProfileEntry 20 }

    zxGponMgcTidPrefix   OBJECT-TYPE
        SYNTAX      DisplayString (SIZE (0..25))
        MAX-ACCESS  read-create
        STATUS      current
        DESCRIPTION
        "The attribute specifies the base string for the H.248 physical
         termination id(s)for this ONT. This string is intended to
         uniquely identify an ONT.  Vendor specific termination
         identifiers (i.e. port ids) are optionally added to this string
         to uniquely identify a termination on a specific ONT.
         (R, W) (optional) (25 bytes)"
        REFERENCE   "G.984.4 section 9.9.16 MGC config data"
        ::= { zxGponMgcProfileEntry 21 }

    zxGponMgcUserTidAssignPolicy  OBJECT-TYPE
        SYNTAX      INTEGER
        {
            default(1),
            specified(2)
        }
        MAX-ACCESS  read-create
        STATUS      current
        DESCRIPTION
            "Default value '1' indicates User TID is assigned by ONT.
             The value '2' indicates that User TID is produced
             by the config data."
        DEFVAL {default}
        ::= { zxGponMgcProfileEntry 22 }

    zxGponMgcUserTidPrefix  OBJECT-TYPE
        SYNTAX      DisplayString (SIZE (0..128))
        MAX-ACCESS  read-create
        STATUS      current
        DESCRIPTION
            "User TID Prefix."
        ::= { zxGponMgcProfileEntry 23 }

    zxGponMgcUserTidPostfixLen  OBJECT-TYPE
        SYNTAX      INTEGER(0..7)
        MAX-ACCESS  read-create
        STATUS      current
        DESCRIPTION
            "Length of User TID Postfix"
        ::= { zxGponMgcProfileEntry 24 }

    zxGponMgcUserTidPostfixStartNum  OBJECT-TYPE
        SYNTAX      INTEGER(0..9)
        MAX-ACCESS  read-create
        STATUS      current
        DESCRIPTION
            "Start Number of User TID Postfix."
        DEFVAL {0}
        ::= { zxGponMgcProfileEntry 25 }

    zxGponMgcRtpTidAssignPolicy  OBJECT-TYPE
        SYNTAX      INTEGER
        {
            default(1),
            specified(2)
        }
        MAX-ACCESS  read-create
        STATUS      current
        DESCRIPTION
            "Default value '1' indicates RTP TID is assigned by ONT.
             The value '2' indicates that RTP TID is produced
             by the config data."
        DEFVAL {default}
        ::= { zxGponMgcProfileEntry 26 }

    zxGponMgcRtpTidPrefix  OBJECT-TYPE
        SYNTAX      DisplayString (SIZE (1..8))
        MAX-ACCESS  read-create
        STATUS      current
        DESCRIPTION
            "RTP TID Prefix."
        ::= { zxGponMgcProfileEntry 27 }

    zxGponMgcRtpTidPostfixLen  OBJECT-TYPE
        SYNTAX      INTEGER(0..7)
        MAX-ACCESS  read-create
        STATUS      current
        DESCRIPTION
            "Length of RTP TID Postfix."
        ::= { zxGponMgcProfileEntry 28 }

    zxGponMgcRtpTidPostfixStartNum  OBJECT-TYPE
        SYNTAX      INTEGER(0..9)
        MAX-ACCESS  read-create
        STATUS      current
        DESCRIPTION
            "Start number of RTP TID Postfix."
        DEFVAL {0}
        ::= { zxGponMgcProfileEntry 29 }

   zxGponMgcTosDscpOption  OBJECT-TYPE
        SYNTAX      INTEGER
        {
            tos(1),
            dscp(2)
        }
        MAX-ACCESS  read-create
        STATUS      current
        DESCRIPTION
            "The mode of QoS tag.
            1:tos
            2:dscp"
        ::= { zxGponMgcProfileEntry 30 }

    zxGponMgcTosDscpValue  OBJECT-TYPE
        SYNTAX      INTEGER(0..63)
        MAX-ACCESS  read-create
        STATUS      current
        DESCRIPTION
            "This attribute assocites with 'zxGponMgcTosDscpOption'.
            Tos values: 0~7; Dscp values: 0~63."
        ::= { zxGponMgcProfileEntry 31 }

    zxGponMgcMediaUdpPort OBJECT-TYPE
        SYNTAX      INTEGER(1..65535)
        MAX-ACCESS  read-create
        STATUS      current
        DESCRIPTION
            "This attribute specifies the port number that offers the TCP/UDP
            service. (R, W, Set-by-create) (mandatory) (2 bytes)
            The port is optional and defaults to 2944 for text message formats
            and 2955 for binary message formats. (R, W, Set by create)
            (mandatory) (2 bytes)"
        REFERENCE   "G984.4 section 9.4.14"
        ::= { zxGponMgcProfileEntry 32 }

    zxGponMgcMediaTosDscpOption  OBJECT-TYPE
        SYNTAX      INTEGER
        {
            tos(1),
            dscp(2)
        }
        MAX-ACCESS  read-create
        STATUS      current
        DESCRIPTION
            "The mode of QoS tag.
            1:tos
            2:dscp"
        ::= { zxGponMgcProfileEntry 33 }

    zxGponMgcMediaTosDscpValue  OBJECT-TYPE
        SYNTAX      INTEGER(0..63)
        MAX-ACCESS  read-create
        STATUS      current
        DESCRIPTION
            "This attribute assocites with 'zxGponMgcMediaTosDscpOption'.
            Tos values: 0~7; Dscp values: 0~63."
        ::= { zxGponMgcProfileEntry 34 }

    zxGponMgcHeartBeatMsgType  OBJECT-TYPE
        SYNTAX      INTEGER
        {
            disabled(1),
            servicechange(2),
            notify(3)
        }
        MAX-ACCESS  read-create
        STATUS      current
        DESCRIPTION
            "Heart beat message type."
        DEFVAL { servicechange }
        ::= { zxGponMgcProfileEntry 35 }

    zxGponMgcHeartBeatInterval  OBJECT-TYPE
        SYNTAX      Integer32(10000..86400000)
        UNITS       "Milliseconds"
        MAX-ACCESS  read-create
        STATUS      current
        DESCRIPTION
            "This attribute defines the heart beat interval in milliseconds.
            The default value is 60000 ms."
        DEFVAL { 60000 }
        ::= { zxGponMgcProfileEntry 36 }

    zxGponMgcRtpLinkDetection  OBJECT-TYPE
        SYNTAX      INTEGER
        {
            enabled(1),
            disabled(2)
        }
        MAX-ACCESS  read-create
        STATUS      current
        DESCRIPTION
            "RTP link detection flag."
        DEFVAL { disabled }
        ::= { zxGponMgcProfileEntry 37 }

    zxGponMgcNumShortestMatch  OBJECT-TYPE
        SYNTAX      INTEGER
        {
            enabled(1),
            disabled(2)
        }
        MAX-ACCESS  read-create
        STATUS      current
        DESCRIPTION
            "Number shortest match flag."
        DEFVAL { disabled }
        ::= { zxGponMgcProfileEntry 38 }

    zxGponMgcDigitMapLongTimer  OBJECT-TYPE
        SYNTAX      INTEGER(2000..60000)
        UNITS       "ms"
        MAX-ACCESS  read-create
        STATUS      current
        DESCRIPTION
            "This attribute defines the DigitMap Long Timer for digit map
            processing in milliseconds. Valid values: 2000~60000.
            The default value is 20000 ms."
        DEFVAL { 20000 }
        ::= { zxGponMgcProfileEntry 39 }

    zxGponMgcDigitMapShortTimer  OBJECT-TYPE
        SYNTAX      INTEGER(2000..60000)
        UNITS       "ms"
        MAX-ACCESS  read-create
        STATUS      current
        DESCRIPTION
            "This attribute defines the DigitMap Short Timer for digit map
            processing in milliseconds.
            Valid values: 2000~60000 .The default value is 5000ms"
       DEFVAL { 5000 }
        ::= { zxGponMgcProfileEntry 40 }

    zxGponMgcDigitMapStartTimer  OBJECT-TYPE
        SYNTAX      INTEGER(2000..60000)
        UNITS       "ms"
        MAX-ACCESS  read-create
        STATUS      current
        DESCRIPTION
            "This attribute defines the DigitMap Start Timer for digit map
             processing in milliseconds.
            Valid values: 2000~60000 .The default value is 10000 ms."
        DEFVAL { 10000 }
        ::= { zxGponMgcProfileEntry 41 }

    zxGponMgcMinReregTimer  OBJECT-TYPE
        SYNTAX      Integer32(0..500000)
        UNITS       "ms"
        MAX-ACCESS  read-create
        STATUS      current
        DESCRIPTION
            "This attribute defines the ReReg Timer Min in milliseconds.
            Valid values: 0~500000 .The default value is 60000 ms."
        DEFVAL { 60000 }
        ::= { zxGponMgcProfileEntry 42 }

    zxGponMgcMaxReregTimer  OBJECT-TYPE
        SYNTAX      Integer32(0..500000)
        UNITS       "ms"
        MAX-ACCESS  read-create
        STATUS      current
        DESCRIPTION
            "This attribute defines the ReReg Timer Max in milliseconds.
            Valid values: 0~500000 .The default value is 120000 ms."
        DEFVAL { 120000 }
        ::= { zxGponMgcProfileEntry 43 }

    zxGponMgcRegMsgRetranTimer  OBJECT-TYPE
        SYNTAX      Integer32(100..50000)
        UNITS       "ms"
        MAX-ACCESS  read-create
        STATUS      current
        DESCRIPTION
            "This attribute defines the RegMsg Retran Timer in milliseconds.
            Valid values: 100~50000 .The default value is 2000 ms"
        DEFVAL { 2000 }
        ::= { zxGponMgcProfileEntry 44 }

    zxGponMgcTotalRetranTime  OBJECT-TYPE
        SYNTAX      Integer32(100..50000)
        UNITS       "ms"
        MAX-ACCESS  read-create
        STATUS      current
        DESCRIPTION
            "This attribute defines the Total Retran Time in milliseconds.
            Valid values: 100~500000 .The default value is 10000 ms."
        DEFVAL { 10000 }
        ::= { zxGponMgcProfileEntry 45 }

    zxGponMgcPassiveHeartBeatEnable  OBJECT-TYPE
        SYNTAX      INTEGER
        {
            enabled(1),
            disabled(2)
        }
        MAX-ACCESS  read-create
        STATUS      current
        DESCRIPTION
            "This attribute defines the MGC passive heart beat enable.
            The default value is disabled."
        DEFVAL { disabled }
        ::= { zxGponMgcProfileEntry 46 }

     zxGponMgcMinAvalancheTimer  OBJECT-TYPE
        SYNTAX      Integer32(0..500000)
        UNITS       "ms"
        MAX-ACCESS  read-create
        STATUS      current
        DESCRIPTION
            "This attribute defines the avalanche timer minimum in milliseconds.
            Valid values: 0~500000. The default value is 10000 ms."
        DEFVAL { 10000 }
        ::= { zxGponMgcProfileEntry 47 }

    zxGponMgcMaxAvalancheTimer  OBJECT-TYPE
        SYNTAX      Integer32(0..500000)
        UNITS       "ms"
        MAX-ACCESS  read-create
        STATUS      current
        DESCRIPTION
            "This attribute defines the avalanche timer maximum in milliseconds.
            Valid values: 0~500000 .The default value is 60000 ms."
        DEFVAL { 60000 }
        ::= { zxGponMgcProfileEntry 48 }

    zxGponMgcRefCnt OBJECT-TYPE
        SYNTAX      Integer32
        MAX-ACCESS  read-only
        STATUS      current
        DESCRIPTION
            "Forbidden to delete table entry if not equal zero."
        ::= { zxGponMgcProfileEntry 49 }

    zxGponMgcRowStatus OBJECT-TYPE
        SYNTAX      RowStatus
        MAX-ACCESS  read-create
        STATUS      current
        DESCRIPTION
            "The row status of this entry."
        ::= { zxGponMgcProfileEntry 50 }

-- DSCP to COS Profile
    zxGponDscp2CosProfileTable    OBJECT-TYPE
        SYNTAX      SEQUENCE OF ZxGponDscp2CosProfileEntry
        MAX-ACCESS  not-accessible
        STATUS      current
        DESCRIPTION
            "This attribute specifies the profile that mapping from DSCP
             to P-bits."
        REFERENCE   "G.984.4 9.3.13 Extended VLAN tagging operation
             configuration data"
        ::= {zxGponRmProfileMgmt  13}

    zxGponDscp2CosProfileEntry OBJECT-TYPE
        SYNTAX      ZxGponDscp2CosProfileEntry
        MAX-ACCESS  not-accessible
        STATUS      current
        DESCRIPTION
            "It is entry in the zxGponDscp2CosProfileEntry."
        INDEX   {zxGponDscp2CosProfileId }
        ::= { zxGponDscp2CosProfileTable 1 }

    ZxGponDscp2CosProfileEntry ::=
        SEQUENCE {
            zxGponDscp2CosProfileId              Integer32,
            zxGponDscp2CosProfileName            DisplayString,
            zxGponDscp2CosMapping                OCTET STRING,
            zxGponDscp2CosProfileRefCnt          Integer32,
            zxGponDscp2CosProfileEntryStatus     RowStatus
        }

    zxGponDscp2CosProfileId OBJECT-TYPE
        SYNTAX      Integer32
        MAX-ACCESS  not-accessible
        STATUS      current
        DESCRIPTION
        "This attribute provides a unique number for each instance of
         this managed entity."
        ::= { zxGponDscp2CosProfileEntry 1 }

    zxGponDscp2CosProfileName OBJECT-TYPE
        SYNTAX      DisplayString(SIZE(1..63))
        MAX-ACCESS  read-create
        STATUS      current
        DESCRIPTION
        "This attribute provides a unique name for each instance of
         this managed entity. "
        ::= { zxGponDscp2CosProfileEntry 2}

    zxGponDscp2CosMapping OBJECT-TYPE
        SYNTAX      OCTET STRING(SIZE(1..24))
        MAX-ACCESS  read-create
        STATUS      current
        DESCRIPTION
        "This attribute specifies mapping from DSCP to P-bits.
         The attribute can be considered a bit string sequence of
         64 3-bit groups. The 64 sequence entries represent the
         possible values of the 6-bit DSCP field. Each 3-bit group
         specifies the P-bit value to which the associated DSCP
         value should be mapped."
        REFERENCE   "G.984.4 9.3.13 Extended VLAN tagging operation
           configuration data"
        ::= { zxGponDscp2CosProfileEntry 3 }

    zxGponDscp2CosProfileRefCnt OBJECT-TYPE
        SYNTAX      Integer32
        MAX-ACCESS  read-only
        STATUS      current
        DESCRIPTION
        "Forbidden to delete table entry if not equal zero."
        ::= { zxGponDscp2CosProfileEntry 4 }

    zxGponDscp2CosProfileEntryStatus OBJECT-TYPE
        SYNTAX      RowStatus
        MAX-ACCESS  read-create
        STATUS      current
        DESCRIPTION
        "This attribute specifies the action of this entry."
        REFERENCE   "G.984.4 9.3.13 Extended VLAN tagging operation
           configuration data."
        ::= { zxGponDscp2CosProfileEntry 10 }

-- VoIP IP Profile
    zxGponVoipIpProfileTable    OBJECT-TYPE
        SYNTAX      SEQUENCE OF ZxGponVoipIpProfileEntry
        MAX-ACCESS  not-accessible
        STATUS      current
        DESCRIPTION
            "VoIP IP profile table. "
        ::= {zxGponRmProfileMgmt  14}

    zxGponVoipIpProfileEntry OBJECT-TYPE
        SYNTAX      ZxGponVoipIpProfileEntry
        MAX-ACCESS  not-accessible
        STATUS      current
        DESCRIPTION
            "VoIP IP profile  entry.
            Entries in the zxGponVoipIpProfileTable are created and
            deleted using the zxGponVoipVlanProfileRowStatus object."
        INDEX   {zxGponVoipIpProfileName }
        ::= { zxGponVoipIpProfileTable 1 }

    ZxGponVoipIpProfileEntry ::=
        SEQUENCE {
            zxGponVoipIpProfileName              DisplayString,
            zxGponVoipIpProfileGatewayType       InetAddressType,
            zxGponVoipIpProfileGateway           InetAddress,
            zxGponVoipIpProfilePriDnsType        InetAddressType,
            zxGponVoipIpProfilePriDns            InetAddress,
            zxGponVoipIpProfileSecDnsType        InetAddressType,
            zxGponVoipIpProfileSecDns            InetAddress,
            zxGponVoipIpProfileRefCnt            Integer32,
            zxGponVoipIpProfileRowStatus         RowStatus
        }

    zxGponVoipIpProfileName OBJECT-TYPE
        SYNTAX      DisplayString(SIZE(1..64))
        MAX-ACCESS  not-accessible
        STATUS      current
        DESCRIPTION
            "The profile name is a display string. It is an index of
             this table."
        ::= { zxGponVoipIpProfileEntry 1 }

    zxGponVoipIpProfileGatewayType OBJECT-TYPE
        SYNTAX      InetAddressType
        MAX-ACCESS  read-create
        STATUS      current
        DESCRIPTION
           "The type of IP address denoted
            in zxGponVoipIpProfileGateway object."
        DEFVAL { ipv4 }
        ::= { zxGponVoipIpProfileEntry 2 }

    zxGponVoipIpProfileGateway OBJECT-TYPE
        SYNTAX      InetAddress
        MAX-ACCESS  read-create
        STATUS      current
        DESCRIPTION
           "The default gateway address used for IP host services,
           this attribute has default value 0 (not set). If this
           value is set, it overrides any values returned in DHCP.

           The address type (InetAddressType) that relates to
           this object is specified by the corresponding value
           of zxGponVoipIpProfileGatewayType."
        DEFVAL { ''H }
        ::= { zxGponVoipIpProfileEntry 3 }

    zxGponVoipIpProfilePriDnsType OBJECT-TYPE
        SYNTAX      InetAddressType
        MAX-ACCESS  read-create
        STATUS      current
        DESCRIPTION
           "The type of IP address denoted
            in zxGponVoipIpProfilePriDns object."
        DEFVAL { ipv4 }
        ::= { zxGponVoipIpProfileEntry 4 }

    zxGponVoipIpProfilePriDns OBJECT-TYPE
        SYNTAX      InetAddress
        MAX-ACCESS  read-create
        STATUS      current
        DESCRIPTION
           "The address of the primary DNS server, this attribute has
            default value 0 (not set). If this value is set, it overrides
            any values returned in DHCP.

           The address type (InetAddressType) that relates to
           this object is specified by the corresponding value
           of zxGponVoipIpProfilePriDnsType."
        DEFVAL { ''H }
        ::= { zxGponVoipIpProfileEntry 5 }

    zxGponVoipIpProfileSecDnsType OBJECT-TYPE
        SYNTAX      InetAddressType
        MAX-ACCESS  read-create
        STATUS      current
        DESCRIPTION
           "The type of IP address denoted
            in zxGponVoipIpProfileSecDns object."
        DEFVAL { ipv4 }
        ::= { zxGponVoipIpProfileEntry 6 }

    zxGponVoipIpProfileSecDns OBJECT-TYPE
        SYNTAX      InetAddress
        MAX-ACCESS  read-create
        STATUS      current
        DESCRIPTION
           "The address of the secondary DNS server, this attribute has
           default value 0 (not set). If this value is set, it overrides
           any values returned in DHCP.

           The address type (InetAddressType) that relates to
           this object is specified by the corresponding value
           of zxGponVoipIpProfileSecDnsType."
        DEFVAL { ''H }
        ::= { zxGponVoipIpProfileEntry 7 }

    zxGponVoipIpProfileRefCnt OBJECT-TYPE
        SYNTAX      Integer32
        MAX-ACCESS  read-only
        STATUS      current
        DESCRIPTION
            "Forbidden to delete table entry if not equal zero."
        ::= { zxGponVoipIpProfileEntry 30 }

    zxGponVoipIpProfileRowStatus OBJECT-TYPE
        SYNTAX      RowStatus
        MAX-ACCESS  read-create
        STATUS      current
        DESCRIPTION
            "The status of this conceptual row.

             To create a row in this table, a manager must
             set this object to createAndGo(4).

             To delete a row in this table, a manager must
             set this object to destroy(6). "
        ::= { zxGponVoipIpProfileEntry 31 }

-- VoIP VLAN Profile
    zxGponVoipVlanProfileTable    OBJECT-TYPE
        SYNTAX      SEQUENCE OF ZxGponVoipVlanProfileEntry
        MAX-ACCESS  not-accessible
        STATUS      current
        DESCRIPTION
            "VoIP VLAN Profile table."
        ::= {zxGponRmProfileMgmt  15}

    zxGponVoipVlanProfileEntry OBJECT-TYPE
        SYNTAX      ZxGponVoipVlanProfileEntry
        MAX-ACCESS  not-accessible
        STATUS      current
        DESCRIPTION
            "VoIP VLAN Profile entry.
            Entries in the zxGponVoipVlanProfileTable are created and
            deleted using the zxGponVoipVlanProfileRowStatus object."
        INDEX   {zxGponVoipVlanProfileName }
        ::= { zxGponVoipVlanProfileTable 1 }

    ZxGponVoipVlanProfileEntry ::=
        SEQUENCE {
            zxGponVoipVlanProfileName            DisplayString,
            zxGponVoipVlanProfileTagMode         INTEGER,
            zxGponVoipVlanProfileCVlanId         Integer32,
            zxGponVoipVlanProfileCVlanPri        Integer32,
            zxGponVoipVlanProfileSVlanId         Integer32,
            zxGponVoipVlanProfileRefCnt          Integer32,
            zxGponVoipVlanProfileRowStatus       RowStatus
        }

    zxGponVoipVlanProfileName OBJECT-TYPE
        SYNTAX      DisplayString(SIZE(1..64))
        MAX-ACCESS  not-accessible
        STATUS      current
        DESCRIPTION "This object indicates the profile name."
        ::= { zxGponVoipVlanProfileEntry 1 }

    zxGponVoipVlanProfileTagMode OBJECT-TYPE
        SYNTAX   INTEGER {
                 tag(1),
                 vlanStacking(2)
                 }
        MAX-ACCESS  read-create
        STATUS      current
        DESCRIPTION
            "VLAN tag mode. If mode is tag, zxGponVoipVlanProfileSVlanId
            need not be configuration. If mode is vlanStacking,
            zxGponVoipVlanProfileSVlanId should be configuration."
        ::= { zxGponVoipVlanProfileEntry 2 }

    zxGponVoipVlanProfileCVlanId OBJECT-TYPE
        SYNTAX      Integer32(1..4094)
        MAX-ACCESS  read-create
        STATUS      current
        DESCRIPTION
            "CVLAN tag ID."
        ::= { zxGponVoipVlanProfileEntry 3 }

    zxGponVoipVlanProfileCVlanPri OBJECT-TYPE
        SYNTAX      Integer32(0..7)
        MAX-ACCESS  read-create
        STATUS      current
        DESCRIPTION
            "CVLAN tag priority."
        ::= { zxGponVoipVlanProfileEntry 4 }

    zxGponVoipVlanProfileSVlanId OBJECT-TYPE
        SYNTAX      Integer32(0..4094)
        MAX-ACCESS  read-create
        STATUS      current
        DESCRIPTION
            "SVLAN tag ID.The zero means invalid value."
        ::= { zxGponVoipVlanProfileEntry 5 }

    zxGponVoipVlanProfileRefCnt OBJECT-TYPE
        SYNTAX      Integer32
        MAX-ACCESS  read-only
        STATUS      current
        DESCRIPTION
            "Forbidden to delete table entry if not equal zero."
        ::= { zxGponVoipVlanProfileEntry 30 }

    zxGponVoipVlanProfileRowStatus OBJECT-TYPE
        SYNTAX      RowStatus
        MAX-ACCESS  read-create
        STATUS      current
        DESCRIPTION
            "The status of this conceptual row.

             To create a row in this table, a manager must
             set this object to createAndGo(4).

             To delete a row in this table, a manager must
             set this object to destroy(6). "
        ::= { zxGponVoipVlanProfileEntry 50 }

-- Traffic Profile
    zxGponRmTrafficPrfTable    OBJECT-TYPE
        SYNTAX      SEQUENCE OF ZxGponRmTrafficPrfEntry
        MAX-ACCESS  not-accessible
        STATUS      current
        DESCRIPTION
            "This table contains information of ONU traffic profile
              configuration.
            The traffic descriptor allows for traffic management.
            A priority controlled ONT can point from a MAC bridge port
            configuration data ME to a GEM traffic descriptor in order
            to implement traffic management (marking, policing).
            A rate controlled ONT can point to a GEM traffic descriptor
            from either a MAC bridge port configuration data ME or
            GEM port network CTP to implement traffic
            management."
        REFERENCE   "G.988/9.2.12       Traffic Descriptor"
        ::= { zxGponRmProfileMgmt 16 }

    zxGponRmTrafficPrfEntry OBJECT-TYPE
        SYNTAX     ZxGponRmTrafficPrfEntry
        MAX-ACCESS  not-accessible
        STATUS      current
        DESCRIPTION
            "It is an entry in the zxGponRmTrafficPrfTable."
        INDEX   { zxGponRmTrafficPrfName  }
        ::= { zxGponRmTrafficPrfTable 1 }

    ZxGponRmTrafficPrfEntry ::=
        SEQUENCE {
            zxGponRmTrafficPrfName                       DisplayString,
            zxGponRmTrafficPrfCir                        Integer32,
            zxGponRmTrafficPrfPir                        Integer32,
            zxGponRmTrafficPrfCbs                        Integer32,
            zxGponRmTrafficPrfPbs                        Integer32,
            zxGponRmTrafficPrfColourMode                 INTEGER,
            zxGponRmTrafficPrfInColourMark               INTEGER,
            zxGponRmTrafficPrfOutColourMark              INTEGER,
            zxGponRmTrafficPrfMeterType                  INTEGER,
            zxGponRmTrafficPrfRefCnt                     Integer32,
            zxGponRmTrafficPrfRowStatus                  RowStatus
        }

    zxGponRmTrafficPrfName OBJECT-TYPE
        SYNTAX      DisplayString(SIZE(1..64))
        MAX-ACCESS  not-accessible
        STATUS      current
        DESCRIPTION
            "Traffic profile name."
        ::= { zxGponRmTrafficPrfEntry 1 }

    zxGponRmTrafficPrfCir OBJECT-TYPE
        SYNTAX      Integer32(0..10000000)
        UNITS       "kbps"
        MAX-ACCESS  read-create
        STATUS      current
        DESCRIPTION
            "This attribute specifies committed information rate."
        REFERENCE   "G.988.9.2.12 traffic descriptor"
        DEFVAL    { 0 }
        ::= { zxGponRmTrafficPrfEntry 2 }

    zxGponRmTrafficPrfPir OBJECT-TYPE
        SYNTAX      Integer32(0..10000000)
        UNITS       "kbps"
        MAX-ACCESS  read-create
        STATUS      current
        DESCRIPTION
            "This attribute specifies peak information rate.
             The value 0 accepts the ONU's factory policy."
        REFERENCE   "G.988.9.2.12 traffic descriptor"
        DEFVAL    { 0 }
        ::= { zxGponRmTrafficPrfEntry 3 }

    zxGponRmTrafficPrfCbs OBJECT-TYPE
        SYNTAX      Integer32(0..1023000)
        UNITS       "bytes"
        MAX-ACCESS  read-create
        STATUS      current
        DESCRIPTION
            "This attribute specifies committed block size, in bytes. "
        REFERENCE   "G.988.9.2.12 traffic descriptor"
        DEFVAL    { 0 }
        ::= { zxGponRmTrafficPrfEntry 4 }

    zxGponRmTrafficPrfPbs OBJECT-TYPE
        SYNTAX      Integer32(0..1023000)
        UNITS       "bytes"
        MAX-ACCESS  read-create
        STATUS      current
        DESCRIPTION
            "This attribute specifies peak block size, in bytes.
             The value 0 accepts the ONU's factory policy."
        REFERENCE   "G.988.9.2.12 traffic descriptor"
        DEFVAL    { 0 }
        ::= { zxGponRmTrafficPrfEntry 5 }

    zxGponRmTrafficPrfColourMode OBJECT-TYPE
        SYNTAX      INTEGER{
                    colourBlind(1),
                    colourAware(2)
                    }
        MAX-ACCESS  read-create
        STATUS      current
        DESCRIPTION
            "This attribute specifies whether the colour marking algorithm
             considers pre-existing marking on ingress packets (colour-aware)
             or ignores it (colour-blind). If colour-aware, packets can only
             be demoted (from green to yellow or red, or from yellow to red). "
        REFERENCE   "G.988.9.2.12 traffic descriptor"
        DEFVAL    { colourBlind }
        ::= { zxGponRmTrafficPrfEntry 6 }

    zxGponRmTrafficPrfInColourMark OBJECT-TYPE
        SYNTAX      INTEGER{
                    noMarking(1),
                    dei(2),
                    pcp8p0d(3),
                    pcp7p1d(4),
                    pcp6p2d(5),
                    pcp5p3d(6),
                    dscpAfClass(7)
                    }
        MAX-ACCESS  read-create
        STATUS      current
        DESCRIPTION
            "This attribute is meaningful in colour-aware mode.
             It specifies how the pre-existing drop precedence is
             marked on ingress packets. For DEI and PCP marking,
             a drop eligible indicator is equivalent to yellow colour,
             otherwise the colour is green. For DSCP AF marking,
             the lowest drop precedence is equivalent to green,
             otherwise the colour is yellow."
        REFERENCE   "G.988.9.2.12 traffic descriptor"
        DEFVAL    { noMarking }
        ::= { zxGponRmTrafficPrfEntry 7 }

    zxGponRmTrafficPrfOutColourMark OBJECT-TYPE
        SYNTAX      INTEGER{
                    noMarking(1),
                    internalMarking(2),
                    dei(3),
                    pcp8p0d(4),
                    pcp7p1d(5),
                    pcp6p2d(6),
                    pcp5p3d(7),
                    dscpAfClass(8)
                    }
        MAX-ACCESS  read-create
        STATUS      current
        DESCRIPTION
            "This attribute specifies how drop precedence is to be
             marked by the ONT on egress packets. If set to internal
             marking only, the externally visible packet contents are
             not modified, but the packet is identified in a vendor-specific
             local way that indicates its colour to the priority queue-G ME.
             It is possible for the egress marking to differ from the ingress
             marking; for example ingress PCP marking could be translated to
             DEI egress marking."
        REFERENCE   "G.988.9.2.12 traffic descriptor"
        DEFVAL    { noMarking }
        ::= { zxGponRmTrafficPrfEntry 8 }

    zxGponRmTrafficPrfMeterType OBJECT-TYPE
        SYNTAX      INTEGER{
                    notSpecified(1),
                    rfc4115(2),
                    rfc2698(3)
                    }
        MAX-ACCESS  read-create
        STATUS      current
        DESCRIPTION
            "This attribute specifies the algorithm used to determine the
             colour of the packet. "
        REFERENCE   "G.988.9.2.12 traffic descriptor"
        DEFVAL    { notSpecified }
        ::= { zxGponRmTrafficPrfEntry 9 }

    zxGponRmTrafficPrfRefCnt OBJECT-TYPE
        SYNTAX      Integer32
        MAX-ACCESS  read-only
        STATUS      current
        DESCRIPTION
            "This attribute indicates the reference count of profile."
        ::= { zxGponRmTrafficPrfEntry 10 }

    zxGponRmTrafficPrfRowStatus OBJECT-TYPE
        SYNTAX      RowStatus
        MAX-ACCESS  read-create
        STATUS      current
        DESCRIPTION
            "The status of this conceptual row.
             To create a row in this table, a manager must
             set this object to createAndGo(4).
             In particular, a newly created row cannot be created
             until the corresponding attributes from zxGponRmTrafficPrfCir
             to zxGponRmTrafficPrfMeterType have been set.
             To delete a row in this table, a manager must
             set this object to destroy(6)."
        ::= { zxGponRmTrafficPrfEntry 50 }

--OMCI Trap Info MIB

    zxGponOnuOMCITrapInfoTable    OBJECT-TYPE
        SYNTAX      SEQUENCE OF ZxGponOnuOMCITrapInfoEntry
        MAX-ACCESS  not-accessible
        STATUS      current
        DESCRIPTION
            ""
        REFERENCE   ""
        ::= { zxGponOmciTrapsInfo 1 }

    zxGponOnuOMCITrapInfoEntry OBJECT-TYPE
        SYNTAX      ZxGponOnuOMCITrapInfoEntry
        MAX-ACCESS  not-accessible
        STATUS      current
        DESCRIPTION
            ""
        INDEX   { ifIndex, zxGponOnuOMCITrapSubType, zxGponOnuOMCITrapPosition }
        ::= { zxGponOnuOMCITrapInfoTable 1 }

    ZxGponOnuOMCITrapInfoEntry ::=
        SEQUENCE {
            zxGponOnuOMCITrapSubType                       INTEGER,
            zxGponOnuOMCITrapPosition                      INTEGER,
            zxGponOnuOMCITrapStatus                        INTEGER
        }

    zxGponOnuOMCITrapSubType OBJECT-TYPE
        SYNTAX      INTEGER
        MAX-ACCESS  read-only
        STATUS      current
        DESCRIPTION
        "This attribute indicates the sub-type of an OMCI trap:
        1:      uni-LANLos,
        2:      ethUniPm-FCSErrs,
        3:      ethUniPm-ExecessCollisionCnt,
        4:      ethUniPm-LateCollisionCnt,
        5:      ethUniPm-FrameTooLongs,
        6:      ethUniPm-RxBufOverflows,
        7:      ethUniPm-TxBufOverflows,
        8:      ethUniPm-SingleCollisionCnt,
        9:      ethUniPm-MultiCollisionCnt,
        10:     ethUniPm-SQECnt,
        11:     ethUniPm-DeferredTxCnt,
        12:     ethUniPm-InternalMACTxErrCnt,
        13:     ethUniPm-CarrierSenseErrCnt,
        14:     ethUniPm-AlignErrCnt,
        15:     ethUniPm-InternalMACRxErrCnt,
        16:     galEthPm-DiscardedFrames,
        17:     gemPortPm-LostPkts,
        18:     gemPortPm-MisinsertedPkts,
        19:     gemPortPm-ImpairedBlocks,
        147:    SIPUA-register auth,
        148:    SIPUA-register timeout,
        149:    SIPUA-register fail
        "
        REFERENCE   ""
        ::= { zxGponOnuOMCITrapInfoEntry 1 }

    zxGponOnuOMCITrapPosition OBJECT-TYPE
        SYNTAX      INTEGER
        MAX-ACCESS  read-only
        STATUS      current
        DESCRIPTION
        "This attribute indicates the position of the OMCI trap.
        According to the sub-type, it may be the UNI index or the GEM port of the ONU."
        REFERENCE   ""
        ::= { zxGponOnuOMCITrapInfoEntry 2 }

    zxGponOnuOMCITrapStatus OBJECT-TYPE
        SYNTAX      INTEGER{
                    alarm(1),
                    restore(2)
                    }
        MAX-ACCESS  read-only
        STATUS      current
        DESCRIPTION
        "This attribute indicates the trap status."
        REFERENCE   ""
        ::= { zxGponOnuOMCITrapInfoEntry 3 }

--OMCI Trap MIB

    zxGponOnuOMCITrap        NOTIFICATION-TYPE
        OBJECTS {
            ifIndex,
            zxGponOnuOMCITrapSubType,
            zxGponOnuOMCITrapPosition,
            zxGponOnuOMCITrapStatus,
            zxGponOntDevMgmtName,
            zxGponOntDevMgmtTypeName,
            zxGponOntDevMgmtDescription,
            zxGponOnuRegistrationInfo
        }
        STATUS  current
        DESCRIPTION
            ""
        ::={zxGponOmciTraps 1}


--OMCI statistics
    zxGponOmciEthStatsTable    OBJECT-TYPE
        SYNTAX      SEQUENCE OF ZxGponOmciEthStatsEntry
        MAX-ACCESS  not-accessible
        STATUS      current
        DESCRIPTION
            ""
        REFERENCE   "G.984.4 Ethernet performance monitoring history data
                     Ethernet performance monitoring history data 2
                     Ethernet performance monitoring history data 3"
        ::= { zxGponOmciStatistics 1 }

    zxGponOmciEthStatsEntry OBJECT-TYPE
        SYNTAX      ZxGponOmciEthStatsEntry
        MAX-ACCESS  not-accessible
        STATUS      current
        DESCRIPTION
            "It is entry in the zxGponOmciEthStatsTable."
        INDEX   { zxGponOltIndex, zxGponONTIndex, zxGponUNIIndex }
        ::= { zxGponOmciEthStatsTable 1 }

    ZxGponOmciEthStatsEntry ::=
        SEQUENCE {
            zxGponOmciEthStatsIntervalEndTime              INTEGER,
            zxGponOmciEthStatsThresDataId                  INTEGER,
            zxGponOmciEthStatsFCSErrors                    Unsigned32,
            zxGponOmciEthStatsExcessiveCollisionCnt        Unsigned32,
            zxGponOmciEthStatsLateCollisionCnt             Unsigned32,
            zxGponOmciEthStatsFrameTooLongs                Unsigned32,
            zxGponOmciEthStatsRxBufOverflows               Unsigned32,
            zxGponOmciEthStatsTxBufOverflows               Unsigned32,
            zxGponOmciEthStatsSingleCollisionCnt           Unsigned32,
            zxGponOmciEthStatsMultipleCollisionCnt         Unsigned32,
            zxGponOmciEthStatsSQECnt                       Unsigned32,
            zxGponOmciEthStatsDeferredTxCnt                Unsigned32,
            zxGponOmciEthStatsInternalMACTxErrCnt          Unsigned32,
            zxGponOmciEthStatsCarrierSenseErrCnt           Unsigned32,
            zxGponOmciEthStatsAlignmentErrCnt              Unsigned32,
            zxGponOmciEthStatsInternalMACRxErrCnt          Unsigned32,
            zxGponOmciEthStatsEntryStatus                  RowStatus,
            zxGponOmciEthStatsPPPoEFilteredCnt             Unsigned32,
            zxGponOmciEthStatsDropEvents                   Unsigned32,
            zxGponOmciEthStatsRxOctets                     Unsigned32,
            zxGponOmciEthStatsRxPkts                       Unsigned32,
            zxGponOmciEthStatsRxBroadcastPkts              Unsigned32,
            zxGponOmciEthStatsRxMulticastPkts              Unsigned32,
            zxGponOmciEthStatsRxUndersizePkts              Unsigned32,
            zxGponOmciEthStatsRxFragments                  Unsigned32,
            zxGponOmciEthStatsRxJabbers                    Unsigned32,
            zxGponOmciEthStatsRx64OctetsPkts               Unsigned32,
            zxGponOmciEthStatsRx65To127OctetsPkts          Unsigned32,
            zxGponOmciEthStatsRx128To255OctetsPkts         Unsigned32,
            zxGponOmciEthStatsRx256To511OctetsPkts         Unsigned32,
            zxGponOmciEthStatsRx512To1023OctetsPkts        Unsigned32,
            zxGponOmciEthStatsRx1024To1518OctetsPkts       Unsigned32
        }

    zxGponOmciEthStatsIntervalEndTime OBJECT-TYPE
        SYNTAX      INTEGER
        MAX-ACCESS  read-only
        STATUS      current
        DESCRIPTION
        ""
        REFERENCE   "G.984.4"
        ::= { zxGponOmciEthStatsEntry 1 }

    zxGponOmciEthStatsThresDataId OBJECT-TYPE
        SYNTAX      INTEGER
        MAX-ACCESS  read-write
        STATUS      current
        DESCRIPTION
        ""
        REFERENCE   "G.984.4"
        ::= { zxGponOmciEthStatsEntry 2 }

    zxGponOmciEthStatsFCSErrors OBJECT-TYPE
        SYNTAX      Unsigned32
        MAX-ACCESS  read-only
        STATUS      current
        DESCRIPTION
        ""
        REFERENCE   "G.984.4 Ethernet performance monitoring history data"
        ::= { zxGponOmciEthStatsEntry 3 }

    zxGponOmciEthStatsExcessiveCollisionCnt OBJECT-TYPE
        SYNTAX      Unsigned32
        MAX-ACCESS  read-only
        STATUS      current
        DESCRIPTION
        ""
        REFERENCE   "G.984.4 Ethernet performance monitoring history data"
        ::= { zxGponOmciEthStatsEntry 4 }

    zxGponOmciEthStatsLateCollisionCnt OBJECT-TYPE
        SYNTAX      Unsigned32
        MAX-ACCESS  read-only
        STATUS      current
        DESCRIPTION
        ""
        REFERENCE   "G.984.4 Ethernet performance monitoring history data"
        ::= { zxGponOmciEthStatsEntry 5 }

    zxGponOmciEthStatsFrameTooLongs OBJECT-TYPE
        SYNTAX      Unsigned32
        MAX-ACCESS  read-only
        STATUS      current
        DESCRIPTION
        ""
        REFERENCE   "G.984.4 Ethernet performance monitoring history data"
        ::= { zxGponOmciEthStatsEntry 6 }

    zxGponOmciEthStatsRxBufOverflows OBJECT-TYPE
        SYNTAX      Unsigned32
        MAX-ACCESS  read-only
        STATUS      current
        DESCRIPTION
        ""
        REFERENCE   "G.984.4 Ethernet performance monitoring history data"
        ::= { zxGponOmciEthStatsEntry 7 }

    zxGponOmciEthStatsTxBufOverflows OBJECT-TYPE
        SYNTAX      Unsigned32
        MAX-ACCESS  read-only
        STATUS      current
        DESCRIPTION
        ""
        REFERENCE   "G.984.4 Ethernet performance monitoring history data"
        ::= { zxGponOmciEthStatsEntry 8 }

    zxGponOmciEthStatsSingleCollisionCnt OBJECT-TYPE
        SYNTAX      Unsigned32
        MAX-ACCESS  read-only
        STATUS      current
        DESCRIPTION
        ""
        REFERENCE   "G.984.4 Ethernet performance monitoring history data"
        ::= { zxGponOmciEthStatsEntry 9 }

    zxGponOmciEthStatsMultipleCollisionCnt OBJECT-TYPE
        SYNTAX      Unsigned32
        MAX-ACCESS  read-only
        STATUS      current
        DESCRIPTION
        ""
        REFERENCE   "G.984.4 Ethernet performance monitoring history data"
        ::= { zxGponOmciEthStatsEntry 10 }

    zxGponOmciEthStatsSQECnt OBJECT-TYPE
        SYNTAX      Unsigned32
        MAX-ACCESS  read-only
        STATUS      current
        DESCRIPTION
        ""
        REFERENCE   "G.984.4 Ethernet performance monitoring history data"
        ::= { zxGponOmciEthStatsEntry 11 }

    zxGponOmciEthStatsDeferredTxCnt OBJECT-TYPE
        SYNTAX      Unsigned32
        MAX-ACCESS  read-only
        STATUS      current
        DESCRIPTION
        ""
        REFERENCE   "G.984.4 Ethernet performance monitoring history data"
        ::= { zxGponOmciEthStatsEntry 12 }

    zxGponOmciEthStatsInternalMACTxErrCnt OBJECT-TYPE
        SYNTAX      Unsigned32
        MAX-ACCESS  read-only
        STATUS      current
        DESCRIPTION
        ""
        REFERENCE   "G.984.4 Ethernet performance monitoring history data"
        ::= { zxGponOmciEthStatsEntry 13 }

    zxGponOmciEthStatsCarrierSenseErrCnt OBJECT-TYPE
        SYNTAX      Unsigned32
        MAX-ACCESS  read-only
        STATUS      current
        DESCRIPTION
        ""
        REFERENCE   "G.984.4 Ethernet performance monitoring history data"
        ::= { zxGponOmciEthStatsEntry 14 }

    zxGponOmciEthStatsAlignmentErrCnt OBJECT-TYPE
        SYNTAX      Unsigned32
        MAX-ACCESS  read-only
        STATUS      current
        DESCRIPTION
        ""
        REFERENCE   "G.984.4 Ethernet performance monitoring history data"
        ::= { zxGponOmciEthStatsEntry 15 }

    zxGponOmciEthStatsInternalMACRxErrCnt OBJECT-TYPE
        SYNTAX      Unsigned32
        MAX-ACCESS  read-only
        STATUS      current
        DESCRIPTION
        ""
        REFERENCE   "G.984.4 Ethernet performance monitoring history data"
        ::= { zxGponOmciEthStatsEntry 16 }

    zxGponOmciEthStatsEntryStatus OBJECT-TYPE
        SYNTAX      RowStatus
        MAX-ACCESS  read-write
        STATUS      current
        DESCRIPTION
        "This attribute specifies the action of this entry."
        REFERENCE   "G.984.4"
        ::= { zxGponOmciEthStatsEntry 17 }

    zxGponOmciEthStatsPPPoEFilteredCnt OBJECT-TYPE
        SYNTAX      Unsigned32
        MAX-ACCESS  read-only
        STATUS      current
        DESCRIPTION
        ""
        REFERENCE   "G.984.4 Ethernet performance monitoring history data 2"
        ::= { zxGponOmciEthStatsEntry 18 }

    zxGponOmciEthStatsDropEvents OBJECT-TYPE
        SYNTAX      Unsigned32
        MAX-ACCESS  read-only
        STATUS      current
        DESCRIPTION
        ""
        REFERENCE   "G.984.4 Ethernet performance monitoring history data 3"
        ::= { zxGponOmciEthStatsEntry 19 }

    zxGponOmciEthStatsRxOctets OBJECT-TYPE
        SYNTAX      Unsigned32
        MAX-ACCESS  read-only
        STATUS      current
        DESCRIPTION
        ""
        REFERENCE   "G.984.4"
        ::= { zxGponOmciEthStatsEntry 20 }

    zxGponOmciEthStatsRxPkts OBJECT-TYPE
        SYNTAX      Unsigned32
        MAX-ACCESS  read-only
        STATUS      current
        DESCRIPTION
        ""
        REFERENCE   "G.984.4 Ethernet performance monitoring history data 3"
        ::= { zxGponOmciEthStatsEntry 21 }

    zxGponOmciEthStatsRxBroadcastPkts OBJECT-TYPE
        SYNTAX      Unsigned32
        MAX-ACCESS  read-only
        STATUS      current
        DESCRIPTION
        ""
        REFERENCE   "G.984.4 Ethernet performance monitoring history data 3"
        ::= { zxGponOmciEthStatsEntry 22 }

    zxGponOmciEthStatsRxMulticastPkts OBJECT-TYPE
        SYNTAX      Unsigned32
        MAX-ACCESS  read-only
        STATUS      current
        DESCRIPTION
        ""
        REFERENCE   "G.984.4 Ethernet performance monitoring history data 3"
        ::= { zxGponOmciEthStatsEntry 23 }

    zxGponOmciEthStatsRxUndersizePkts OBJECT-TYPE
        SYNTAX      Unsigned32
        MAX-ACCESS  read-only
        STATUS      current
        DESCRIPTION
        ""
        REFERENCE   "G.984.4 Ethernet performance monitoring history data 3"
        ::= { zxGponOmciEthStatsEntry 24 }

    zxGponOmciEthStatsRxFragments OBJECT-TYPE
        SYNTAX      Unsigned32
        MAX-ACCESS  read-only
        STATUS      current
        DESCRIPTION
        ""
        REFERENCE   "G.984.4 Ethernet performance monitoring history data 3"
        ::= { zxGponOmciEthStatsEntry 25 }

    zxGponOmciEthStatsRxJabbers OBJECT-TYPE
        SYNTAX      Unsigned32
        MAX-ACCESS  read-only
        STATUS      current
        DESCRIPTION
        ""
        REFERENCE   "G.984.4 Ethernet performance monitoring history data 3"
        ::= { zxGponOmciEthStatsEntry 26 }

    zxGponOmciEthStatsRx64OctetsPkts OBJECT-TYPE
        SYNTAX      Unsigned32
        MAX-ACCESS  read-only
        STATUS      current
        DESCRIPTION
        ""
        REFERENCE   "G.984.4 Ethernet performance monitoring history data 3"
        ::= { zxGponOmciEthStatsEntry 27 }

    zxGponOmciEthStatsRx65To127OctetsPkts OBJECT-TYPE
        SYNTAX      Unsigned32
        MAX-ACCESS  read-only
        STATUS      current
        DESCRIPTION
        ""
        REFERENCE   "G.984.4 Ethernet performance monitoring history data 3"
        ::= { zxGponOmciEthStatsEntry 28 }

    zxGponOmciEthStatsRx128To255OctetsPkts OBJECT-TYPE
        SYNTAX      Unsigned32
        MAX-ACCESS  read-only
        STATUS      current
        DESCRIPTION
        ""
        REFERENCE   "G.984.4 Ethernet performance monitoring history data 3"
        ::= { zxGponOmciEthStatsEntry 29 }

    zxGponOmciEthStatsRx256To511OctetsPkts OBJECT-TYPE
        SYNTAX      Unsigned32
        MAX-ACCESS  read-only
        STATUS      current
        DESCRIPTION
        ""
        REFERENCE   "G.984.4 Ethernet performance monitoring history data 3"
        ::= { zxGponOmciEthStatsEntry 30 }

    zxGponOmciEthStatsRx512To1023OctetsPkts OBJECT-TYPE
        SYNTAX      Unsigned32
        MAX-ACCESS  read-only
        STATUS      current
        DESCRIPTION
        ""
        REFERENCE   "G.984.4 Ethernet performance monitoring history data 3"
        ::= { zxGponOmciEthStatsEntry 31 }

    zxGponOmciEthStatsRx1024To1518OctetsPkts OBJECT-TYPE
        SYNTAX      Unsigned32
        MAX-ACCESS  read-only
        STATUS      current
        DESCRIPTION
        ""
        REFERENCE   "G.984.4 Ethernet performance monitoring history data 3"
        ::= { zxGponOmciEthStatsEntry 32 }


    zxGponOmciGEMStatsTable    OBJECT-TYPE
        SYNTAX      SEQUENCE OF ZxGponOmciGEMStatsEntry
        MAX-ACCESS  not-accessible
        STATUS      current
        DESCRIPTION
            ""
        REFERENCE   "G.984.4 & G.983.2"
        ::= { zxGponOmciStatistics 2 }

    zxGponOmciGEMStatsEntry OBJECT-TYPE
        SYNTAX      ZxGponOmciGEMStatsEntry
        MAX-ACCESS  not-accessible
        STATUS      current
        DESCRIPTION
            "It is entry in the zxGponOmciGEMStatsTable."
        INDEX   { zxGponOltIndex, zxGponONTIndex, zxGponGemPortIndex }
        ::= { zxGponOmciGEMStatsTable 1 }

    ZxGponOmciGEMStatsEntry ::=
        SEQUENCE {
            zxGponOmciGEMStatsIntervalEndTime               INTEGER,
            zxGponOmciGEMStatsThresDataId                   INTEGER,
            zxGponOmciGEMStatsLostPkts                      Unsigned32,
            zxGponOmciGEMStatsMisInsertedPkts               Unsigned32,
            zxGponOmciGEMStatsRxPkts                        Counter64,
            zxGponOmciGEMStatsRxBlocks                      Counter64,
            zxGponOmciGEMStatsTxBlocks                      Counter64,
            zxGponOmciGEMStatsImpairedBlocks                Unsigned32,
            zxGponOmciGEMStatsEntryStatus                   RowStatus
        }

    zxGponOmciGEMStatsIntervalEndTime OBJECT-TYPE
        SYNTAX      INTEGER
        MAX-ACCESS  read-only
        STATUS      current
        DESCRIPTION
        ""
        REFERENCE   "G.984.4 & G.983.2"
        ::= { zxGponOmciGEMStatsEntry 1 }

    zxGponOmciGEMStatsThresDataId OBJECT-TYPE
        SYNTAX      INTEGER
        MAX-ACCESS  read-write
        STATUS      current
        DESCRIPTION
        ""
        REFERENCE   "G.984.4 & G.983.2"
        ::= { zxGponOmciGEMStatsEntry 2 }

    zxGponOmciGEMStatsLostPkts OBJECT-TYPE
        SYNTAX      Unsigned32
        MAX-ACCESS  read-only
        STATUS      current
        DESCRIPTION
        ""
        REFERENCE   "G.984.4 & G.983.2"
        ::= { zxGponOmciGEMStatsEntry 3 }

    zxGponOmciGEMStatsMisInsertedPkts OBJECT-TYPE
        SYNTAX      Unsigned32
        MAX-ACCESS  read-only
        STATUS      current
        DESCRIPTION
        ""
        REFERENCE   "G.984.4 & G.983.2"
        ::= { zxGponOmciGEMStatsEntry 4 }

    zxGponOmciGEMStatsRxPkts OBJECT-TYPE
        SYNTAX      Counter64
        MAX-ACCESS  read-only
        STATUS      current
        DESCRIPTION
        ""
        REFERENCE   "G.984.4 & G.983.2"
        ::= { zxGponOmciGEMStatsEntry 6 }

    zxGponOmciGEMStatsRxBlocks OBJECT-TYPE
        SYNTAX      Counter64
        MAX-ACCESS  read-only
        STATUS      current
        DESCRIPTION
        ""
        REFERENCE   "G.984.4 & G.983.2"
        ::= { zxGponOmciGEMStatsEntry 7 }

    zxGponOmciGEMStatsTxBlocks OBJECT-TYPE
        SYNTAX      Counter64
        MAX-ACCESS  read-only
        STATUS      current
        DESCRIPTION
        ""
        REFERENCE   "G.984.4 & G.983.2"
        ::= { zxGponOmciGEMStatsEntry 8 }

    zxGponOmciGEMStatsImpairedBlocks OBJECT-TYPE
        SYNTAX      Unsigned32
        MAX-ACCESS  read-only
        STATUS      current
        DESCRIPTION
        ""
        REFERENCE   "G.984.4 & G.983.2"
        ::= { zxGponOmciGEMStatsEntry 9 }

    zxGponOmciGEMStatsEntryStatus OBJECT-TYPE
        SYNTAX      RowStatus
        MAX-ACCESS  read-write
        STATUS      current
        DESCRIPTION
        "This attribute specifies the action of this interworking."
        REFERENCE   "G.984.4 & G.983.2"
        ::= { zxGponOmciGEMStatsEntry 10 }

    zxGponOmciGALEthStatsTable    OBJECT-TYPE
        SYNTAX      SEQUENCE OF ZxGponOmciGALEthStatsEntry
        MAX-ACCESS  not-accessible
        STATUS      current
        DESCRIPTION
            ""
        REFERENCE   "G.984.4 & G.983.2"
        ::= { zxGponOmciStatistics 3 }

    zxGponOmciGALEthStatsEntry OBJECT-TYPE
        SYNTAX      ZxGponOmciGALEthStatsEntry
        MAX-ACCESS  not-accessible
        STATUS      current
        DESCRIPTION
            "It is entry in the zxGponOmciGALEthStatsTable."
        INDEX   { zxGponOltIndex, zxGponONTIndex, zxGponGemPortIndex }
        ::= { zxGponOmciGALEthStatsTable 1 }

    ZxGponOmciGALEthStatsEntry ::=
        SEQUENCE {
            zxGponOmciGALEthStatsIntervalEndTime               INTEGER,
            zxGponOmciGALEthStatsThresDataId                   INTEGER,
            zxGponOmciGALEthStatsDiscardedFrames               Unsigned32,
            zxGponOmciGALEthStatsEntryStatus                   RowStatus
        }

    zxGponOmciGALEthStatsIntervalEndTime OBJECT-TYPE
        SYNTAX      INTEGER
        MAX-ACCESS  read-only
        STATUS      current
        DESCRIPTION
        ""
        REFERENCE   "G.984.4 & G.983.2"
        ::= { zxGponOmciGALEthStatsEntry 1 }

    zxGponOmciGALEthStatsThresDataId OBJECT-TYPE
        SYNTAX      INTEGER
        MAX-ACCESS  read-write
        STATUS      current
        DESCRIPTION
        ""
        REFERENCE   "G.984.4 & G.983.2"
        ::= { zxGponOmciGALEthStatsEntry 2 }

    zxGponOmciGALEthStatsDiscardedFrames OBJECT-TYPE
        SYNTAX      Unsigned32
        MAX-ACCESS  read-only
        STATUS      current
        DESCRIPTION
        ""
        REFERENCE   "G.984.4 & G.983.2"
        ::= { zxGponOmciGALEthStatsEntry 3 }

    zxGponOmciGALEthStatsEntryStatus OBJECT-TYPE
        SYNTAX      RowStatus
        MAX-ACCESS  read-write
        STATUS      current
        DESCRIPTION
        ""
        REFERENCE   "G.984.4 & G.983.2"
        ::= { zxGponOmciGALEthStatsEntry 4 }

    zxGponOmciBridgeStatsTable    OBJECT-TYPE
        SYNTAX      SEQUENCE OF ZxGponOmciBridgeStatsEntry
        MAX-ACCESS  not-accessible
        STATUS      current
        DESCRIPTION
            ""
        REFERENCE   "G.984.4 & G.983.2"
        ::= { zxGponOmciStatistics 4 }

    zxGponOmciBridgeStatsEntry OBJECT-TYPE
        SYNTAX      ZxGponOmciBridgeStatsEntry
        MAX-ACCESS  not-accessible
        STATUS      current
        DESCRIPTION
            "It is entry in the zxGponOmciBridgeStatsTable."
        INDEX   { zxGponOltIndex, zxGponONTIndex, zxGponSwitchIndex }
        ::= { zxGponOmciBridgeStatsTable 1 }

    ZxGponOmciBridgeStatsEntry ::=
        SEQUENCE {
            zxGponOmciBridgeStatsIntervalEndTime               INTEGER,
            zxGponOmciBridgeStatsThresDataId                   INTEGER,
            zxGponOmciBridgeStatsLearnEntryDiscardFrames       Unsigned32,
            zxGponOmciBridgeStatsEntryStatus                   RowStatus
        }

    zxGponOmciBridgeStatsIntervalEndTime OBJECT-TYPE
        SYNTAX      INTEGER
        MAX-ACCESS  read-only
        STATUS      current
        DESCRIPTION
        ""
        REFERENCE   "G.984.4 & G.983.2"
        ::= { zxGponOmciBridgeStatsEntry 1 }

    zxGponOmciBridgeStatsThresDataId OBJECT-TYPE
        SYNTAX      INTEGER
        MAX-ACCESS  read-write
        STATUS      current
        DESCRIPTION
        ""
        REFERENCE   "G.984.4 & G.983.2"
        ::= { zxGponOmciBridgeStatsEntry 2 }

    zxGponOmciBridgeStatsLearnEntryDiscardFrames OBJECT-TYPE
        SYNTAX      Unsigned32
        MAX-ACCESS  read-only
        STATUS      current
        DESCRIPTION
        ""
        REFERENCE   "G.984.4 & G.983.2"
        ::= { zxGponOmciBridgeStatsEntry 3 }

    zxGponOmciBridgeStatsEntryStatus OBJECT-TYPE
        SYNTAX      RowStatus
        MAX-ACCESS  read-write
        STATUS      current
        DESCRIPTION
        ""
        REFERENCE   "G.984.4 & G.983.2"
        ::= { zxGponOmciBridgeStatsEntry 4 }


    zxGponOmciUNIBridgePortStatsTable    OBJECT-TYPE
        SYNTAX      SEQUENCE OF ZxGponOmciUNIBridgePortStatsEntry
        MAX-ACCESS  not-accessible
        STATUS      current
        DESCRIPTION
            ""
        REFERENCE   "G.984.4 & G.983.2"
        ::= { zxGponOmciStatistics 5 }

    zxGponOmciUNIBridgePortStatsEntry OBJECT-TYPE
        SYNTAX      ZxGponOmciUNIBridgePortStatsEntry
        MAX-ACCESS  not-accessible
        STATUS      current
        DESCRIPTION
            "It is entry in the zxGponOmciUNIBridgePortStatsTable."
        INDEX   { zxGponOltIndex, zxGponONTIndex, zxGponUNIIndex }
        ::= { zxGponOmciUNIBridgePortStatsTable 1 }

    ZxGponOmciUNIBridgePortStatsEntry ::=
        SEQUENCE {
            zxGponOmciUNIBridgePortStatsIntervalEndTime               INTEGER,
            zxGponOmciUNIBridgePortStatsThresDataId                   INTEGER,
            zxGponOmciUNIBridgePortStatsForwardFrameCnt               Unsigned32,
            zxGponOmciUNIBridgePortStatsDelayExceedDiscardCnt         Unsigned32,
            zxGponOmciUNIBridgePortStatsMTUExceedDiscardCnt           Unsigned32,
            zxGponOmciUNIBridgePortStatsRxFrameCnt                    Unsigned32,
            zxGponOmciUNIBridgePortStatsRxDiscardCnt                  Unsigned32,
            zxGponOmciUNIBridgePortStatsEntryStatus                   RowStatus
        }

    zxGponOmciUNIBridgePortStatsIntervalEndTime OBJECT-TYPE
        SYNTAX      INTEGER
        MAX-ACCESS  read-only
        STATUS      current
        DESCRIPTION
        ""
        REFERENCE   "G.984.4 & G.983.2"
        ::= { zxGponOmciUNIBridgePortStatsEntry 1 }

    zxGponOmciUNIBridgePortStatsThresDataId OBJECT-TYPE
        SYNTAX      INTEGER
        MAX-ACCESS  read-write
        STATUS      current
        DESCRIPTION
        ""
        REFERENCE   "G.984.4 & G.983.2"
        ::= { zxGponOmciUNIBridgePortStatsEntry 2 }

    zxGponOmciUNIBridgePortStatsForwardFrameCnt OBJECT-TYPE
        SYNTAX      Unsigned32
        MAX-ACCESS  read-only
        STATUS      current
        DESCRIPTION
        ""
        REFERENCE   "G.984.4 & G.983.2"
        ::= { zxGponOmciUNIBridgePortStatsEntry 3 }

    zxGponOmciUNIBridgePortStatsDelayExceedDiscardCnt OBJECT-TYPE
        SYNTAX      Unsigned32
        MAX-ACCESS  read-only
        STATUS      current
        DESCRIPTION
        ""
        REFERENCE   "G.984.4 & G.983.2"
        ::= { zxGponOmciUNIBridgePortStatsEntry 4 }

    zxGponOmciUNIBridgePortStatsMTUExceedDiscardCnt OBJECT-TYPE
        SYNTAX      Unsigned32
        MAX-ACCESS  read-only
        STATUS      current
        DESCRIPTION
        ""
        REFERENCE   "G.984.4 & G.983.2"
        ::= { zxGponOmciUNIBridgePortStatsEntry 5 }

    zxGponOmciUNIBridgePortStatsRxFrameCnt OBJECT-TYPE
        SYNTAX      Unsigned32
        MAX-ACCESS  read-only
        STATUS      current
        DESCRIPTION
        ""
        REFERENCE   "G.984.4 & G.983.2"
        ::= { zxGponOmciUNIBridgePortStatsEntry 6 }

    zxGponOmciUNIBridgePortStatsRxDiscardCnt OBJECT-TYPE
        SYNTAX      Unsigned32
        MAX-ACCESS  read-only
        STATUS      current
        DESCRIPTION
        ""
        REFERENCE   "G.984.4 & G.983.2"
        ::= { zxGponOmciUNIBridgePortStatsEntry 7 }

    zxGponOmciUNIBridgePortStatsEntryStatus OBJECT-TYPE
        SYNTAX      RowStatus
        MAX-ACCESS  read-write
        STATUS      current
        DESCRIPTION
        ""
        REFERENCE   "G.984.4 & G.983.2"
        ::= { zxGponOmciUNIBridgePortStatsEntry 8 }

    zxGponOmciFlowBridgePortStatsTable    OBJECT-TYPE
        SYNTAX      SEQUENCE OF ZxGponOmciFlowBridgePortStatsEntry
        MAX-ACCESS  not-accessible
        STATUS      current
        DESCRIPTION
            ""
        REFERENCE   "G.984.4 & G.983.2"
        ::= { zxGponOmciStatistics 6 }

    zxGponOmciFlowBridgePortStatsEntry OBJECT-TYPE
        SYNTAX      ZxGponOmciFlowBridgePortStatsEntry
        MAX-ACCESS  not-accessible
        STATUS      current
        DESCRIPTION
            "It is entry in the zxGponOmciFlowBridgePortStatsTable."
        INDEX   { zxGponOltIndex, zxGponONTIndex, zxGponFlowIndex }
        ::= { zxGponOmciFlowBridgePortStatsTable 1 }

    ZxGponOmciFlowBridgePortStatsEntry ::=
        SEQUENCE {
            zxGponOmciFlowBridgePortStatsIntervalEndTime               INTEGER,
            zxGponOmciFlowBridgePortStatsThresDataId                   INTEGER,
            zxGponOmciFlowBridgePortStatsForwardFrameCnt               Unsigned32,
            zxGponOmciFlowBridgePortStatsDelayExceedDiscardCnt         Unsigned32,
            zxGponOmciFlowBridgePortStatsMTUExceedDiscardCnt           Unsigned32,
            zxGponOmciFlowBridgePortStatsRxFrameCnt                    Unsigned32,
            zxGponOmciFlowBridgePortStatsRxDiscardCnt                  Unsigned32,
            zxGponOmciFlowBridgePortStatsEntryStatus                   RowStatus
        }

    zxGponOmciFlowBridgePortStatsIntervalEndTime OBJECT-TYPE
        SYNTAX      INTEGER
        MAX-ACCESS  read-only
        STATUS      current
        DESCRIPTION
        ""
        REFERENCE   "G.984.4 & G.983.2"
        ::= { zxGponOmciFlowBridgePortStatsEntry 1 }

    zxGponOmciFlowBridgePortStatsThresDataId OBJECT-TYPE
        SYNTAX      INTEGER
        MAX-ACCESS  read-write
        STATUS      current
        DESCRIPTION
        ""
        REFERENCE   "G.984.4 & G.983.2"
        ::= { zxGponOmciFlowBridgePortStatsEntry 2 }

    zxGponOmciFlowBridgePortStatsForwardFrameCnt OBJECT-TYPE
        SYNTAX      Unsigned32
        MAX-ACCESS  read-only
        STATUS      current
        DESCRIPTION
        ""
        REFERENCE   "G.984.4 & G.983.2"
        ::= { zxGponOmciFlowBridgePortStatsEntry 3 }

    zxGponOmciFlowBridgePortStatsDelayExceedDiscardCnt OBJECT-TYPE
        SYNTAX      Unsigned32
        MAX-ACCESS  read-only
        STATUS      current
        DESCRIPTION
        ""
        REFERENCE   "G.984.4 & G.983.2"
        ::= { zxGponOmciFlowBridgePortStatsEntry 4 }

    zxGponOmciFlowBridgePortStatsMTUExceedDiscardCnt OBJECT-TYPE
        SYNTAX      Unsigned32
        MAX-ACCESS  read-only
        STATUS      current
        DESCRIPTION
        ""
        REFERENCE   "G.984.4 & G.983.2"
        ::= { zxGponOmciFlowBridgePortStatsEntry 5 }

    zxGponOmciFlowBridgePortStatsRxFrameCnt OBJECT-TYPE
        SYNTAX      Unsigned32
        MAX-ACCESS  read-only
        STATUS      current
        DESCRIPTION
        ""
        REFERENCE   "G.984.4 & G.983.2"
        ::= { zxGponOmciFlowBridgePortStatsEntry 6 }

    zxGponOmciFlowBridgePortStatsRxDiscardCnt OBJECT-TYPE
        SYNTAX      Unsigned32
        MAX-ACCESS  read-only
        STATUS      current
        DESCRIPTION
        ""
        REFERENCE   "G.984.4 & G.983.2"
        ::= { zxGponOmciFlowBridgePortStatsEntry 7 }

    zxGponOmciFlowBridgePortStatsEntryStatus OBJECT-TYPE
        SYNTAX      RowStatus
        MAX-ACCESS  read-write
        STATUS      current
        DESCRIPTION
        ""
        REFERENCE   "G.984.4 & G.983.2"
        ::= { zxGponOmciFlowBridgePortStatsEntry 8 }

--IP Host Performance Monitoring History Data
    zxGponOmciIPHostStatsTable    OBJECT-TYPE
        SYNTAX      SEQUENCE OF ZxGponOmciIPHostStatsEntry
        MAX-ACCESS  not-accessible
        STATUS      current
        DESCRIPTION
            ""
        REFERENCE   "G.984.4 & G.983.2"
        ::= { zxGponOmciStatistics 7 }

    zxGponOmciIPHostStatsEntry OBJECT-TYPE
        SYNTAX      ZxGponOmciIPHostStatsEntry
        MAX-ACCESS  not-accessible
        STATUS      current
        DESCRIPTION
            "It is entry in the zxGponOmciIPHostStatsTable."
        INDEX   { zxGponOltIndex, zxGponONTIndex, zxGponIPHostConfigDataId }
        ::= { zxGponOmciIPHostStatsTable 1 }

    ZxGponOmciIPHostStatsEntry ::=
        SEQUENCE {
            zxGponOmciIPHostStatsIntervalEndTime              INTEGER,
            zxGponOmciIPHostStatsThresDataId                  INTEGER,
            zxGponOmciIPHostStatsICMPErrors                   Unsigned32,
            zxGponOmciIPHostStatsDNSErrors                    Unsigned32,
            zxGponOmciIPHostStatsEntryStatus                  RowStatus,
            zxGponOmciIpHostStatsRxPkts                       Unsigned32,
            zxGponOmciIpHostStatsTxPkts                       Unsigned32,
            zxGponOmciIpHostStatsRxOctets                     Unsigned32,
            zxGponOmciIpHostStatsTxOctets                     Unsigned32
        }

    zxGponOmciIPHostStatsIntervalEndTime OBJECT-TYPE
        SYNTAX      INTEGER
        MAX-ACCESS  read-only
        STATUS      current
        DESCRIPTION
        ""
        REFERENCE   "G.984.4 & G.983.2"
        ::= { zxGponOmciIPHostStatsEntry 1 }

    zxGponOmciIPHostStatsThresDataId OBJECT-TYPE
        SYNTAX      INTEGER
        MAX-ACCESS  read-write
        STATUS      current
        DESCRIPTION
        ""
        REFERENCE   "G.984.4 & G.983.2"
        ::= { zxGponOmciIPHostStatsEntry 2 }

    zxGponOmciIPHostStatsICMPErrors OBJECT-TYPE
        SYNTAX      Unsigned32
        MAX-ACCESS  read-only
        STATUS      current
        DESCRIPTION
        ""
        REFERENCE   "G.984.4 & G.983.2"
        ::= { zxGponOmciIPHostStatsEntry 3 }

    zxGponOmciIPHostStatsDNSErrors OBJECT-TYPE
        SYNTAX      Unsigned32
        MAX-ACCESS  read-only
        STATUS      current
        DESCRIPTION
        ""
        REFERENCE   "G.984.4 & G.983.2"
        ::= { zxGponOmciIPHostStatsEntry 4 }

    zxGponOmciIPHostStatsEntryStatus OBJECT-TYPE
        SYNTAX      RowStatus
        MAX-ACCESS  read-write
        STATUS      current
        DESCRIPTION
        "This attribute specifies the action of this entry."
        REFERENCE   "G.984.4 & G.983.2"
        ::= { zxGponOmciIPHostStatsEntry 5 }

    zxGponOmciIpHostStatsRxPkts OBJECT-TYPE
        SYNTAX      Unsigned32
        MAX-ACCESS  read-only
        STATUS      current
        DESCRIPTION
        "This attribute counts packets received."
        ::= { zxGponOmciIPHostStatsEntry 6 }

    zxGponOmciIpHostStatsTxPkts OBJECT-TYPE
        SYNTAX      Unsigned32
        MAX-ACCESS  read-only
        STATUS      current
        DESCRIPTION
        "This attribute counts packets transmitted."
        ::= { zxGponOmciIPHostStatsEntry 7 }

    zxGponOmciIpHostStatsRxOctets OBJECT-TYPE
        SYNTAX      Unsigned32
        MAX-ACCESS  read-only
        STATUS      current
        DESCRIPTION
        "This attribute counts octets received."
        ::= { zxGponOmciIPHostStatsEntry 8 }

    zxGponOmciIpHostStatsTxOctets OBJECT-TYPE
        SYNTAX      Unsigned32
        MAX-ACCESS  read-only
        STATUS      current
        DESCRIPTION
        "This attribute counts octets transmitted."
        ::= { zxGponOmciIPHostStatsEntry 9 }

--Call Control PM History Data
    zxGponOmciCallCtrlStatsTable    OBJECT-TYPE
        SYNTAX      SEQUENCE OF ZxGponOmciCallCtrlStatsEntry
        MAX-ACCESS  not-accessible
        STATUS      current
        DESCRIPTION
            ""
        REFERENCE   "G.984.4 & G.983.2"
        ::= { zxGponOmciStatistics 8 }

    zxGponOmciCallCtrlStatsEntry OBJECT-TYPE
        SYNTAX      ZxGponOmciCallCtrlStatsEntry
        MAX-ACCESS  not-accessible
        STATUS      current
        DESCRIPTION
            "It is entry in the zxGponOmciCallCtrlStatsTable."
        INDEX   { zxGponOltIndex, zxGponONTIndex, zxGponUNIIndex }
        ::= { zxGponOmciCallCtrlStatsTable 1 }

    ZxGponOmciCallCtrlStatsEntry ::=
        SEQUENCE {
            zxGponOmciCallCtrlStatsIntervalEndTime              INTEGER,
            zxGponOmciCallCtrlStatsThresDataId                  INTEGER,
            zxGponOmciCallCtrlStatsCallSetupFailures            Unsigned32,
            zxGponOmciCallCtrlStatsCallSetupTimer               Unsigned32,
            zxGponOmciCallCtrlStatsCallTerminateFailures        Unsigned32,
            zxGponOmciCallCtrlStatsAnalogPortReleases           Unsigned32,
            zxGponOmciCallCtrlStatsAnalogPortOffHookTimer       Unsigned32,
            zxGponOmciCallCtrlStatsEntryStatus                  RowStatus
        }

    zxGponOmciCallCtrlStatsIntervalEndTime OBJECT-TYPE
        SYNTAX      INTEGER
        MAX-ACCESS  read-only
        STATUS      current
        DESCRIPTION
        ""
        REFERENCE   "G.984.4 & G.983.2"
        ::= { zxGponOmciCallCtrlStatsEntry 1 }

    zxGponOmciCallCtrlStatsThresDataId OBJECT-TYPE
        SYNTAX      INTEGER
        MAX-ACCESS  read-write
        STATUS      current
        DESCRIPTION
        ""
        REFERENCE   "G.984.4 & G.983.2"
        ::= { zxGponOmciCallCtrlStatsEntry 2 }

    zxGponOmciCallCtrlStatsCallSetupFailures OBJECT-TYPE
        SYNTAX      Unsigned32
        MAX-ACCESS  read-only
        STATUS      current
        DESCRIPTION
        ""
        REFERENCE   "G.984.4 & G.983.2"
        ::= { zxGponOmciCallCtrlStatsEntry 3 }

    zxGponOmciCallCtrlStatsCallSetupTimer OBJECT-TYPE
        SYNTAX      Unsigned32
        MAX-ACCESS  read-only
        STATUS      current
        DESCRIPTION
        ""
        REFERENCE   "G.984.4 & G.983.2"
        ::= { zxGponOmciCallCtrlStatsEntry 4 }

    zxGponOmciCallCtrlStatsCallTerminateFailures OBJECT-TYPE
        SYNTAX      Unsigned32
        MAX-ACCESS  read-only
        STATUS      current
        DESCRIPTION
        ""
        REFERENCE   "G.984.4 & G.983.2"
        ::= { zxGponOmciCallCtrlStatsEntry 5 }

    zxGponOmciCallCtrlStatsAnalogPortReleases OBJECT-TYPE
        SYNTAX      Unsigned32
        MAX-ACCESS  read-only
        STATUS      current
        DESCRIPTION
        ""
        REFERENCE   "G.984.4 & G.983.2"
        ::= { zxGponOmciCallCtrlStatsEntry 6 }

    zxGponOmciCallCtrlStatsAnalogPortOffHookTimer OBJECT-TYPE
        SYNTAX      Unsigned32
        MAX-ACCESS  read-only
        STATUS      current
        DESCRIPTION
        ""
        REFERENCE   "G.984.4 & G.983.2"
        ::= { zxGponOmciCallCtrlStatsEntry 7 }

    zxGponOmciCallCtrlStatsEntryStatus OBJECT-TYPE
        SYNTAX      RowStatus
        MAX-ACCESS  read-write
        STATUS      current
        DESCRIPTION
        "This attribute specifies the action of this entry."
        REFERENCE   "G.984.4 & G.983.2"
        ::= { zxGponOmciCallCtrlStatsEntry 8 }

--RTP Monitoring Data
    zxGponOmciRTPStatsTable    OBJECT-TYPE
        SYNTAX      SEQUENCE OF ZxGponOmciRTPStatsEntry
        MAX-ACCESS  not-accessible
        STATUS      current
        DESCRIPTION
            ""
        REFERENCE   "G.984.4 & G.983.2"
        ::= { zxGponOmciStatistics 9 }

    zxGponOmciRTPStatsEntry OBJECT-TYPE
        SYNTAX      ZxGponOmciRTPStatsEntry
        MAX-ACCESS  not-accessible
        STATUS      current
        DESCRIPTION
            "It is entry in the zxGponOmciRTPStatsTable."
        INDEX   { zxGponOltIndex, zxGponONTIndex, zxGponUNIIndex }
        ::= { zxGponOmciRTPStatsTable 1 }

    ZxGponOmciRTPStatsEntry ::=
        SEQUENCE {
            zxGponOmciRTPStatsIntervalEndTime              INTEGER,
            zxGponOmciRTPStatsThresDataId                  INTEGER,
            zxGponOmciRTPStatsRTPErrors                    Unsigned32,
            zxGponOmciRTPStatsPktLoss                      Unsigned32,
            zxGponOmciRTPStatsMaxJitter                    Unsigned32,
            zxGponOmciRTPStatsMaxTimeBtwRTPPkts            Unsigned32,
            zxGponOmciRTPStatsBufUnderflows                Unsigned32,
            zxGponOmciRTPStatsBufOverflows                 Unsigned32,
            zxGponOmciRTPStatsEntryStatus                  RowStatus
        }

    zxGponOmciRTPStatsIntervalEndTime OBJECT-TYPE
        SYNTAX      INTEGER
        MAX-ACCESS  read-only
        STATUS      current
        DESCRIPTION
        ""
        REFERENCE   "G.984.4 & G.983.2"
        ::= { zxGponOmciRTPStatsEntry 1 }

    zxGponOmciRTPStatsThresDataId OBJECT-TYPE
        SYNTAX      INTEGER
        MAX-ACCESS  read-write
        STATUS      current
        DESCRIPTION
        ""
        REFERENCE   "G.984.4 & G.983.2"
        ::= { zxGponOmciRTPStatsEntry 2 }

    zxGponOmciRTPStatsRTPErrors OBJECT-TYPE
        SYNTAX      Unsigned32
        MAX-ACCESS  read-only
        STATUS      current
        DESCRIPTION
        ""
        REFERENCE   "G.984.4 & G.983.2"
        ::= { zxGponOmciRTPStatsEntry 3 }

    zxGponOmciRTPStatsPktLoss OBJECT-TYPE
        SYNTAX      Unsigned32
        MAX-ACCESS  read-only
        STATUS      current
        DESCRIPTION
        ""
        REFERENCE   "G.984.4 & G.983.2"
        ::= { zxGponOmciRTPStatsEntry 4 }

    zxGponOmciRTPStatsMaxJitter OBJECT-TYPE
        SYNTAX      Unsigned32
        MAX-ACCESS  read-only
        STATUS      current
        DESCRIPTION
        ""
        REFERENCE   "G.984.4 & G.983.2"
        ::= { zxGponOmciRTPStatsEntry 5 }

    zxGponOmciRTPStatsMaxTimeBtwRTPPkts OBJECT-TYPE
        SYNTAX      Unsigned32
        MAX-ACCESS  read-only
        STATUS      current
        DESCRIPTION
        ""
        REFERENCE   "G.984.4 & G.983.2"
        ::= { zxGponOmciRTPStatsEntry 6 }

    zxGponOmciRTPStatsBufUnderflows OBJECT-TYPE
        SYNTAX      Unsigned32
        MAX-ACCESS  read-only
        STATUS      current
        DESCRIPTION
        ""
        REFERENCE   "G.984.4 & G.983.2"
        ::= { zxGponOmciRTPStatsEntry 7 }

    zxGponOmciRTPStatsBufOverflows OBJECT-TYPE
        SYNTAX      Unsigned32
        MAX-ACCESS  read-only
        STATUS      current
        DESCRIPTION
        ""
        REFERENCE   "G.984.4 & G.983.2"
        ::= { zxGponOmciRTPStatsEntry 8 }

    zxGponOmciRTPStatsEntryStatus OBJECT-TYPE
        SYNTAX      RowStatus
        MAX-ACCESS  read-write
        STATUS      current
        DESCRIPTION
        "This attribute specifies the action of this entry."
        REFERENCE   "G.984.4 & G.983.2"
        ::= { zxGponOmciRTPStatsEntry 9 }

--SIP Call Initiation Performance Monitoring History Data
    zxGponOmciSIPCallInitStatsTable    OBJECT-TYPE
        SYNTAX      SEQUENCE OF ZxGponOmciSIPCallInitStatsEntry
        MAX-ACCESS  not-accessible
        STATUS      current
        DESCRIPTION
            ""
        REFERENCE   "G.984.4 & G.983.2"
        ::= { zxGponOmciStatistics 10 }

    zxGponOmciSIPCallInitStatsEntry OBJECT-TYPE
        SYNTAX      ZxGponOmciSIPCallInitStatsEntry
        MAX-ACCESS  not-accessible
        STATUS      current
        DESCRIPTION
            "It is entry in the zxGponOmciSIPCallInitStatsTable."
        INDEX   { zxGponOltIndex, zxGponONTIndex, zxGponSIPAgentConfigDataId }
        ::= { zxGponOmciSIPCallInitStatsTable 1 }

    ZxGponOmciSIPCallInitStatsEntry ::=
        SEQUENCE {
            zxGponOmciSIPCallInitStatsIntervalEndTime              INTEGER,
            zxGponOmciSIPCallInitStatsThresDataId                  INTEGER,
            zxGponOmciSIPCallInitStatsConnectFailures              Unsigned32,
            zxGponOmciSIPCallInitStatsValidateFailures             Unsigned32,
            zxGponOmciSIPCallInitStatsTimeoutCounter               Unsigned32,
            zxGponOmciSIPCallInitStatsRxFailures                   Unsigned32,
            zxGponOmciSIPCallInitStatsAuthFailures                 Unsigned32,
            zxGponOmciSIPCallInitStatsEntryStatus                  RowStatus
        }

    zxGponOmciSIPCallInitStatsIntervalEndTime OBJECT-TYPE
        SYNTAX      INTEGER
        MAX-ACCESS  read-only
        STATUS      current
        DESCRIPTION
        ""
        REFERENCE   "G.984.4 & G.983.2"
        ::= { zxGponOmciSIPCallInitStatsEntry 1 }

    zxGponOmciSIPCallInitStatsThresDataId OBJECT-TYPE
        SYNTAX      INTEGER
        MAX-ACCESS  read-write
        STATUS      current
        DESCRIPTION
        ""
        REFERENCE   "G.984.4 & G.983.2"
        ::= { zxGponOmciSIPCallInitStatsEntry 2 }

    zxGponOmciSIPCallInitStatsConnectFailures OBJECT-TYPE
        SYNTAX      Unsigned32
        MAX-ACCESS  read-only
        STATUS      current
        DESCRIPTION
        ""
        REFERENCE   "G.984.4 & G.983.2"
        ::= { zxGponOmciSIPCallInitStatsEntry 3 }

    zxGponOmciSIPCallInitStatsValidateFailures OBJECT-TYPE
        SYNTAX      Unsigned32
        MAX-ACCESS  read-only
        STATUS      current
        DESCRIPTION
        ""
        REFERENCE   "G.984.4 & G.983.2"
        ::= { zxGponOmciSIPCallInitStatsEntry 4 }

    zxGponOmciSIPCallInitStatsTimeoutCounter OBJECT-TYPE
        SYNTAX      Unsigned32
        MAX-ACCESS  read-only
        STATUS      current
        DESCRIPTION
        ""
        REFERENCE   "G.984.4 & G.983.2"
        ::= { zxGponOmciSIPCallInitStatsEntry 5 }

    zxGponOmciSIPCallInitStatsRxFailures OBJECT-TYPE
        SYNTAX      Unsigned32
        MAX-ACCESS  read-only
        STATUS      current
        DESCRIPTION
        ""
        REFERENCE   "G.984.4 & G.983.2"
        ::= { zxGponOmciSIPCallInitStatsEntry 6 }

    zxGponOmciSIPCallInitStatsAuthFailures OBJECT-TYPE
        SYNTAX      Unsigned32
        MAX-ACCESS  read-only
        STATUS      current
        DESCRIPTION
        ""
        REFERENCE   "G.984.4 & G.983.2"
        ::= { zxGponOmciSIPCallInitStatsEntry 7 }

    zxGponOmciSIPCallInitStatsEntryStatus OBJECT-TYPE
        SYNTAX      RowStatus
        MAX-ACCESS  read-write
        STATUS      current
        DESCRIPTION
        "This attribute specifies the action of this entry."
        REFERENCE   "G.984.4 & G.983.2"
        ::= { zxGponOmciSIPCallInitStatsEntry 8 }

--SIP Agent Monitoring History Data
    zxGponOmciSIPAgentStatsTable    OBJECT-TYPE
        SYNTAX      SEQUENCE OF ZxGponOmciSIPAgentStatsEntry
        MAX-ACCESS  not-accessible
        STATUS      current
        DESCRIPTION
            ""
        REFERENCE   "G.984.4 & G.983.2"
        ::= { zxGponOmciStatistics 11 }

    zxGponOmciSIPAgentStatsEntry OBJECT-TYPE
        SYNTAX      ZxGponOmciSIPAgentStatsEntry
        MAX-ACCESS  not-accessible
        STATUS      current
        DESCRIPTION
            "It is entry in the zxGponOmciSIPAgentStatsTable."
        INDEX   { zxGponOltIndex, zxGponONTIndex, zxGponSIPAgentConfigDataId }
        ::= { zxGponOmciSIPAgentStatsTable 1 }

    ZxGponOmciSIPAgentStatsEntry ::=
        SEQUENCE {
            zxGponOmciSIPAgentStatsIntervalEndTime              INTEGER,
            zxGponOmciSIPAgentStatsThresDataId                  INTEGER,
            zxGponOmciSIPAgentStatsTransactions                 Unsigned32,
            zxGponOmciSIPAgentStatsRxInviteReqs                 Unsigned32,
            zxGponOmciSIPAgentStatsRxInviteRetrans              Unsigned32,
            zxGponOmciSIPAgentStatsRxNonInviteReqs              Unsigned32,
            zxGponOmciSIPAgentStatsRxNonInviteRetrans           Unsigned32,
            zxGponOmciSIPAgentStatsRxResponses                  Unsigned32,
            zxGponOmciSIPAgentStatsRxResponseRetrans            Unsigned32,
            zxGponOmciSIPAgentStatsTxInviteReqs                 Unsigned32,
            zxGponOmciSIPAgentStatsTxInviteRetrans              Unsigned32,
            zxGponOmciSIPAgentStatsTxNonInviteReqs              Unsigned32,
            zxGponOmciSIPAgentStatsTxNonInviteRetrans           Unsigned32,
            zxGponOmciSIPAgentStatsTxResponses                  Unsigned32,
            zxGponOmciSIPAgentStatsTxResponseRetrans            Unsigned32,
            zxGponOmciSIPAgentStatsEntryStatus                  RowStatus
        }

    zxGponOmciSIPAgentStatsIntervalEndTime OBJECT-TYPE
        SYNTAX      INTEGER
        MAX-ACCESS  read-only
        STATUS      current
        DESCRIPTION
        ""
        REFERENCE   "G.984.4 & G.983.2"
        ::= { zxGponOmciSIPAgentStatsEntry 1 }

    zxGponOmciSIPAgentStatsThresDataId OBJECT-TYPE
        SYNTAX      INTEGER
        MAX-ACCESS  read-write
        STATUS      current
        DESCRIPTION
        ""
        REFERENCE   "G.984.4 & G.983.2"
        ::= { zxGponOmciSIPAgentStatsEntry 2 }

    zxGponOmciSIPAgentStatsTransactions OBJECT-TYPE
        SYNTAX      Unsigned32
        MAX-ACCESS  read-only
        STATUS      current
        DESCRIPTION
        ""
        REFERENCE   "G.984.4 & G.983.2"
        ::= { zxGponOmciSIPAgentStatsEntry 3 }

    zxGponOmciSIPAgentStatsRxInviteReqs OBJECT-TYPE
        SYNTAX      Unsigned32
        MAX-ACCESS  read-only
        STATUS      current
        DESCRIPTION
        ""
        REFERENCE   "G.984.4 & G.983.2"
        ::= { zxGponOmciSIPAgentStatsEntry 4 }

    zxGponOmciSIPAgentStatsRxInviteRetrans OBJECT-TYPE
        SYNTAX      Unsigned32
        MAX-ACCESS  read-only
        STATUS      current
        DESCRIPTION
        ""
        REFERENCE   "G.984.4 & G.983.2"
        ::= { zxGponOmciSIPAgentStatsEntry 5 }

    zxGponOmciSIPAgentStatsRxNonInviteReqs OBJECT-TYPE
        SYNTAX      Unsigned32
        MAX-ACCESS  read-only
        STATUS      current
        DESCRIPTION
        ""
        REFERENCE   "G.984.4 & G.983.2"
        ::= { zxGponOmciSIPAgentStatsEntry 6 }

    zxGponOmciSIPAgentStatsRxNonInviteRetrans OBJECT-TYPE
        SYNTAX      Unsigned32
        MAX-ACCESS  read-only
        STATUS      current
        DESCRIPTION
        ""
        REFERENCE   "G.984.4 & G.983.2"
        ::= { zxGponOmciSIPAgentStatsEntry 7 }

    zxGponOmciSIPAgentStatsRxResponses OBJECT-TYPE
        SYNTAX      Unsigned32
        MAX-ACCESS  read-only
        STATUS      current
        DESCRIPTION
        ""
        REFERENCE   "G.984.4 & G.983.2"
        ::= { zxGponOmciSIPAgentStatsEntry 8 }

    zxGponOmciSIPAgentStatsRxResponseRetrans OBJECT-TYPE
        SYNTAX      Unsigned32
        MAX-ACCESS  read-only
        STATUS      current
        DESCRIPTION
        ""
        REFERENCE   "G.984.4 & G.983.2"
        ::= { zxGponOmciSIPAgentStatsEntry 9 }

    zxGponOmciSIPAgentStatsTxInviteReqs OBJECT-TYPE
        SYNTAX      Unsigned32
        MAX-ACCESS  read-only
        STATUS      current
        DESCRIPTION
        ""
        REFERENCE   "G.984.4 & G.983.2"
        ::= { zxGponOmciSIPAgentStatsEntry 10 }

    zxGponOmciSIPAgentStatsTxInviteRetrans OBJECT-TYPE
        SYNTAX      Unsigned32
        MAX-ACCESS  read-only
        STATUS      current
        DESCRIPTION
        ""
        REFERENCE   "G.984.4 & G.983.2"
        ::= { zxGponOmciSIPAgentStatsEntry 11 }

    zxGponOmciSIPAgentStatsTxNonInviteReqs OBJECT-TYPE
        SYNTAX      Unsigned32
        MAX-ACCESS  read-only
        STATUS      current
        DESCRIPTION
        ""
        REFERENCE   "G.984.4 & G.983.2"
        ::= { zxGponOmciSIPAgentStatsEntry 12 }

    zxGponOmciSIPAgentStatsTxNonInviteRetrans OBJECT-TYPE
        SYNTAX      Unsigned32
        MAX-ACCESS  read-only
        STATUS      current
        DESCRIPTION
        ""
        REFERENCE   "G.984.4 & G.983.2"
        ::= { zxGponOmciSIPAgentStatsEntry 13 }

    zxGponOmciSIPAgentStatsTxResponses OBJECT-TYPE
        SYNTAX      Unsigned32
        MAX-ACCESS  read-only
        STATUS      current
        DESCRIPTION
        ""
        REFERENCE   "G.984.4 & G.983.2"
        ::= { zxGponOmciSIPAgentStatsEntry 14 }

    zxGponOmciSIPAgentStatsTxResponseRetrans OBJECT-TYPE
        SYNTAX      Unsigned32
        MAX-ACCESS  read-only
        STATUS      current
        DESCRIPTION
        ""
        REFERENCE   "G.984.4 & G.983.2"
        ::= { zxGponOmciSIPAgentStatsEntry 15 }

    zxGponOmciSIPAgentStatsEntryStatus OBJECT-TYPE
        SYNTAX      RowStatus
        MAX-ACCESS  read-write
        STATUS      current
        DESCRIPTION
        "This attribute specifies the action of this entry."
        REFERENCE   "G.984.4 & G.983.2"
        ::= { zxGponOmciSIPAgentStatsEntry 16 }

--MGC performance monitoring history data
    zxGponOmciMGCStatsTable    OBJECT-TYPE
        SYNTAX      SEQUENCE OF ZxGponOmciMGCStatsEntry
        MAX-ACCESS  not-accessible
        STATUS      current
        DESCRIPTION
            "An instance of this managed entity is associated with an instance of the
            MGC config data or MGC config portal ME."
        REFERENCE   "G.984.4"
        ::= { zxGponOmciStatistics 12 }

    zxGponOmciMGCStatsEntry    OBJECT-TYPE
        SYNTAX      ZxGponOmciMGCStatsEntry
        MAX-ACCESS  not-accessible
        STATUS      current
        DESCRIPTION
            "It is entry in the zxGponOmciMGCStatsTable."
        INDEX   { zxGponOltIndex, zxGponONTIndex, zxGponMGCConfigDataId }
        ::= { zxGponOmciMGCStatsTable 1 }

    ZxGponOmciMGCStatsEntry ::=
        SEQUENCE {
            zxGponOmciMGCStatsIntervalEndTime         INTEGER,
            zxGponOmciMGCStatsThresholdDataId         INTEGER,
            zxGponOmciMGCStatsRecvMsg                 INTEGER,
            zxGponOmciMGCStatsRecvOctets              INTEGER,
            zxGponOmciMGCStatsSendMsg                 INTEGER,
            zxGponOmciMGCStatsSendOctets              INTEGER,
            zxGponOmciMGCStatsProtocolErrors          INTEGER,
            zxGponOmciMGCStatsTransLosses             INTEGER,
            zxGponOmciMGCStatsLastEvent               INTEGER,
            zxGponOmciMGCStatsLastEventTime           INTEGER,
            zxGponOmciMGCStatsLastResetTime           INTEGER,
            zxGponOmciMGCStatsEntryStatus             RowStatus
        }

    zxGponOmciMGCStatsIntervalEndTime   OBJECT-TYPE
        SYNTAX      INTEGER
        MAX-ACCESS  read-only
        STATUS      current
        DESCRIPTION
        "This attribute identifies the most recently finished 15-minute interval. (R) (mandatory) (1 byte)"
        REFERENCE   "G.984.4 section    9.9.17    MGC performance monitoring history data"
        ::= { zxGponOmciMGCStatsEntry 1 }

    zxGponOmciMGCStatsThresholdDataId   OBJECT-TYPE
        SYNTAX      INTEGER
        MAX-ACCESS  read-write
        STATUS      current
        DESCRIPTION
        "This attribute points to an instance of the threshold data  managed entity
        that contains PM threshold values."
        REFERENCE   "G.984.4 section    9.9.17    MGC performance monitoring history data"
        ::= { zxGponOmciMGCStatsEntry 2 }

    zxGponOmciMGCStatsRecvMsg   OBJECT-TYPE
        SYNTAX      INTEGER
        MAX-ACCESS  read-only
        STATUS      current
        DESCRIPTION
        "This attribute counts the number of received Megaco messages on this association,
        as defined by H.341. (R) (mandatory) (4 bytes)"
        REFERENCE   "G.984.4 section    9.9.17    MGC performance monitoring history data"
        ::= { zxGponOmciMGCStatsEntry 3 }

    zxGponOmciMGCStatsRecvOctets   OBJECT-TYPE
        SYNTAX      INTEGER
        MAX-ACCESS  read-only
        STATUS      current
        DESCRIPTION
        "This attribute counts the total number of octets received on this association,
        as defined by H.341. (R) (mandatory) (4 bytes)"
        REFERENCE   "G.984.4 section    9.9.17    MGC performance monitoring history data"
        ::= { zxGponOmciMGCStatsEntry 4 }

    zxGponOmciMGCStatsSendMsg   OBJECT-TYPE
        SYNTAX      INTEGER
        MAX-ACCESS  read-only
        STATUS      current
        DESCRIPTION
        "This attribute counts the total number of Megaco messages sent over this association,
        as defined by H.341. (R) (mandatory) (4 bytes)"
        REFERENCE   "G.984.4 section    9.9.17    MGC performance monitoring history data"
        ::= { zxGponOmciMGCStatsEntry 5 }

    zxGponOmciMGCStatsSendOctets   OBJECT-TYPE
        SYNTAX      INTEGER
        MAX-ACCESS  read-only
        STATUS      current
        DESCRIPTION
        "This attribute counts the total number of octets sent over this association,
        as defined by H.341. (R) (mandatory) (4 bytes)"
        REFERENCE   "G.984.4 section    9.9.17    MGC performance monitoring history data"
        ::= { zxGponOmciMGCStatsEntry 6 }

    zxGponOmciMGCStatsProtocolErrors   OBJECT-TYPE
        SYNTAX      INTEGER
        MAX-ACCESS  read-only
        STATUS      current
        DESCRIPTION
        "This attribute counts the total number of errors detected on this association,
        as defined by H.341. This includes:syntax errors detected in a given received message,
          outgoing transactions that failed for protocol reasons.(R) (mandatory) (4 bytes)"
        REFERENCE   "G.984.4 section    9.9.17    MGC performance monitoring history data"
        ::= { zxGponOmciMGCStatsEntry 7 }

    zxGponOmciMGCStatsTransLosses   OBJECT-TYPE
        SYNTAX      INTEGER
        MAX-ACCESS  read-only
        STATUS      current
        DESCRIPTION
        "This attribute counts the total number of transport losses (for example, socket problems)
        detected on this association. A link loss is defined as loss of communication with the
        remote entity due to hardware/transient problems, or problems in related software.
        (R) (mandatory) (4 bytes)"
        REFERENCE   "G.984.4 section    9.9.17    MGC performance monitoring history data"
        ::= { zxGponOmciMGCStatsEntry 8 }

    zxGponOmciMGCStatsLastEvent   OBJECT-TYPE
        SYNTAX      INTEGER{
                    no-event(1),
                    link-up(2),
                    link-down(3),
                    persistent-error(4),
                    local-shutdown(5),
                    failover-down(6)
                    }
        MAX-ACCESS  read-only
        STATUS      current
        DESCRIPTION
        "This attribute reports the last event detected on this association.
        This includes events such as the link failing or being set up."
        REFERENCE   "G.984.4 section    9.9.17    MGC performance monitoring history data"
        ::= { zxGponOmciMGCStatsEntry 9 }

    zxGponOmciMGCStatsLastEventTime   OBJECT-TYPE
        SYNTAX      INTEGER
        MAX-ACCESS  read-only
        STATUS      current
        DESCRIPTION
        "This attribute reports the time in seconds since the last event on
        this association was detected, as defined by H.341. (R) (mandatory) (4 bytes)"
        REFERENCE   "G.984.4 section    9.9.17    MGC performance monitoring history data"
        ::= { zxGponOmciMGCStatsEntry 10 }

    zxGponOmciMGCStatsLastResetTime   OBJECT-TYPE
        SYNTAX      INTEGER
        MAX-ACCESS  read-only
        STATUS      current
        DESCRIPTION
        "This attribute reports the time in seconds since these statistics were last reset,
        as defined by H.341. Under normal circumstances, a get action on this attribute would
        return 900 seconds to indicate a completed 15-minute interval. (R) (mandatory) (4 bytes)"
        REFERENCE   "G.984.4 section    9.9.17    MGC performance monitoring history data"
        ::= { zxGponOmciMGCStatsEntry 11 }

    zxGponOmciMGCStatsEntryStatus OBJECT-TYPE
        SYNTAX      RowStatus
        MAX-ACCESS  read-write
        STATUS      current
        DESCRIPTION
        "This attribute specifies the action of this entry."
        REFERENCE   "G.984.4 section    9.9.17    MGC performance monitoring history data"
        ::= { zxGponOmciMGCStatsEntry 12 }


--CES performance monitoring history data
    zxGponOmciCESStatsTable    OBJECT-TYPE
        SYNTAX      SEQUENCE OF ZxGponOmciCESStatsEntry
        MAX-ACCESS  not-accessible
        STATUS      current
        DESCRIPTION
            "Performance monitoring history data of Physical path termination point CES UNI."
        REFERENCE
           "G.984.4, CES physical interface performance monitoring history data,
        Pseudowire performance monitoring history data"
        ::= { zxGponOmciStatistics 13 }

    zxGponOmciCESStatsEntry    OBJECT-TYPE
        SYNTAX      ZxGponOmciCESStatsEntry
        MAX-ACCESS  not-accessible
        STATUS      current
        DESCRIPTION
            "It is entry in the zxGponOmciCESStatsTable."
        INDEX   { zxGponOltIndex, zxGponONTIndex, zxGponUNIIndex }
        ::= { zxGponOmciCESStatsTable 1 }

    ZxGponOmciCESStatsEntry ::=
        SEQUENCE {
            zxGponOmciCESStatsIntervalEndTime               INTEGER,
            zxGponOmciCESStatsThresholdDataId               INTEGER,
            zxGponOmciCESStatsDownPkts                      Unsigned32,
            zxGponOmciCESStatsUpPkts                        Unsigned32,
            zxGponOmciCESStatsDownMissingPkts               Unsigned32,
            zxGponOmciCESStatsDownReorderedPkts             Unsigned32,
            zxGponOmciCESStatsDownMisorderedPkts            Unsigned32,
            zxGponOmciCESStatsDownBufUnderrunOrOverrunPkts  Unsigned32,
            zxGponOmciCESStatsDownMalformedPkts             Unsigned32,
            zxGponOmciCESStatsDownStrayPkts                 Unsigned32,
            zxGponOmciCESStatsDownRemotePktLoss             Unsigned32,
            zxGponOmciCESStatsUpTDMLbitPkts                 Unsigned32,
            zxGponOmciCESStatsDownErrSeconds                Unsigned32,
            zxGponOmciCESStatsDownSeverelyErrSeconds        Unsigned32,
            zxGponOmciCESStatsDownUnavailableSeconds        Unsigned32,
--            zxGponOmciCESStatsUpErrSeconds                  Unsigned32,
--            zxGponOmciCESStatsUpSeverelyErrSeconds          Unsigned32,
--            zxGponOmciCESStatsUpBurstErrSeconds             Unsigned32,
--            zxGponOmciCESStatsUpUnavailableSeconds          Unsigned32,
--            zxGponOmciCESStatsUpControlledSlipSeconds       Unsigned32,
            zxGponOmciCESStatsEntryStatus                   RowStatus
        }

    zxGponOmciCESStatsIntervalEndTime   OBJECT-TYPE
        SYNTAX      INTEGER
        MAX-ACCESS  read-only
        STATUS      current
        DESCRIPTION
        ""
        REFERENCE   "G.984.4, Pseudowire performance monitoring history data"
        ::= { zxGponOmciCESStatsEntry 1 }

    zxGponOmciCESStatsThresholdDataId   OBJECT-TYPE
        SYNTAX      INTEGER
        MAX-ACCESS  read-write
        STATUS      current
        DESCRIPTION
        ""
        REFERENCE   "G.984.4, Pseudowire performance monitoring history data"
        ::= { zxGponOmciCESStatsEntry 2 }

    zxGponOmciCESStatsDownPkts   OBJECT-TYPE
        SYNTAX      Unsigned32
        MAX-ACCESS  read-only
        STATUS      current
        DESCRIPTION
        ""
        REFERENCE   "G.984.4, Pseudowire performance monitoring history data"
        ::= { zxGponOmciCESStatsEntry 3 }

    zxGponOmciCESStatsUpPkts   OBJECT-TYPE
        SYNTAX      Unsigned32
        MAX-ACCESS  read-only
        STATUS      current
        DESCRIPTION
        ""
        REFERENCE   "G.984.4, Pseudowire performance monitoring history data"
        ::= { zxGponOmciCESStatsEntry 4 }

    zxGponOmciCESStatsDownMissingPkts   OBJECT-TYPE
        SYNTAX      Unsigned32
        MAX-ACCESS  read-only
        STATUS      current
        DESCRIPTION
        ""
        REFERENCE   "G.984.4, Pseudowire performance monitoring history data"
        ::= { zxGponOmciCESStatsEntry 5 }

    zxGponOmciCESStatsDownReorderedPkts   OBJECT-TYPE
        SYNTAX      Unsigned32
        MAX-ACCESS  read-only
        STATUS      current
        DESCRIPTION
        ""
        REFERENCE   "G.984.4, Pseudowire performance monitoring history data"
        ::= { zxGponOmciCESStatsEntry 6 }

    zxGponOmciCESStatsDownMisorderedPkts   OBJECT-TYPE
        SYNTAX      Unsigned32
        MAX-ACCESS  read-only
        STATUS      current
        DESCRIPTION
        ""
        REFERENCE   "G.984.4, Pseudowire performance monitoring history data"
        ::= { zxGponOmciCESStatsEntry 7 }

    zxGponOmciCESStatsDownBufUnderrunOrOverrunPkts   OBJECT-TYPE
        SYNTAX      Unsigned32
        MAX-ACCESS  read-only
        STATUS      current
        DESCRIPTION
        ""
        REFERENCE   "G.984.4, Pseudowire performance monitoring history data"
        ::= { zxGponOmciCESStatsEntry 8 }

    zxGponOmciCESStatsDownMalformedPkts   OBJECT-TYPE
        SYNTAX      Unsigned32
        MAX-ACCESS  read-only
        STATUS      current
        DESCRIPTION
        ""
        REFERENCE   "G.984.4, Pseudowire performance monitoring history data"
        ::= { zxGponOmciCESStatsEntry 9 }

    zxGponOmciCESStatsDownStrayPkts   OBJECT-TYPE
        SYNTAX      Unsigned32
        MAX-ACCESS  read-only
        STATUS      current
        DESCRIPTION
        ""
        REFERENCE   "G.984.4, Pseudowire performance monitoring history data"
        ::= { zxGponOmciCESStatsEntry 10 }

    zxGponOmciCESStatsDownRemotePktLoss   OBJECT-TYPE
        SYNTAX      Unsigned32
        MAX-ACCESS  read-only
        STATUS      current
        DESCRIPTION
        ""
        REFERENCE   "G.984.4, Pseudowire performance monitoring history data"
        ::= { zxGponOmciCESStatsEntry 11 }

    zxGponOmciCESStatsUpTDMLbitPkts   OBJECT-TYPE
        SYNTAX      Unsigned32
        MAX-ACCESS  read-only
        STATUS      current
        DESCRIPTION
        ""
        REFERENCE   "G.984.4, Pseudowire performance monitoring history data"
        ::= { zxGponOmciCESStatsEntry 12 }

    zxGponOmciCESStatsDownErrSeconds   OBJECT-TYPE
        SYNTAX      Unsigned32
        MAX-ACCESS  read-only
        STATUS      current
        DESCRIPTION
        ""
        REFERENCE   "G.984.4, Pseudowire performance monitoring history data"
        ::= { zxGponOmciCESStatsEntry 13 }

    zxGponOmciCESStatsDownSeverelyErrSeconds   OBJECT-TYPE
        SYNTAX      Unsigned32
        MAX-ACCESS  read-only
        STATUS      current
        DESCRIPTION
        ""
        REFERENCE   "G.984.4, Pseudowire performance monitoring history data"
        ::= { zxGponOmciCESStatsEntry 14 }

    zxGponOmciCESStatsDownUnavailableSeconds   OBJECT-TYPE
        SYNTAX      Unsigned32
        MAX-ACCESS  read-only
        STATUS      current
        DESCRIPTION
        ""
        REFERENCE   "G.984.4, Pseudowire performance monitoring history data"
        ::= { zxGponOmciCESStatsEntry 15 }

--    zxGponOmciCESStatsUpErrSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 16 }
--
--    zxGponOmciCESStatsUpSeverelyErrSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 17 }
--
--    zxGponOmciCESStatsUpBurstErrSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 18 }
--
--    zxGponOmciCESStatsUpUnavailableSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 19 }
--
--    zxGponOmciCESStatsUpControlledSlipSeconds   OBJECT-TYPE
--        SYNTAX      Unsigned32
--        MAX-ACCESS  read-only
--        STATUS      current
--        DESCRIPTION
--        ""
--        REFERENCE   "G.984.4, CES physical interface performance monitoring history data"
--        ::= { zxGponOmciCESStatsEntry 20 }

    zxGponOmciCESStatsEntryStatus OBJECT-TYPE
        SYNTAX      RowStatus
        MAX-ACCESS  read-write
        STATUS      current
        DESCRIPTION
        ""
        REFERENCE   "G.984.4"
        ::= { zxGponOmciCESStatsEntry 25 }


--Private Eth Statistics
    zxGponOmciPrivateEthStatsTable    OBJECT-TYPE
        SYNTAX      SEQUENCE OF ZxGponOmciPrivateEthStatsEntry
        MAX-ACCESS  not-accessible
        STATUS      current
        DESCRIPTION
            ""
        REFERENCE   "Vender specific Ethernet performance
                     Ethernet performance monitoring history data 4"
        ::= { zxGponOmciStatistics 14 }

    zxGponOmciPrivateEthStatsEntry OBJECT-TYPE
        SYNTAX      ZxGponOmciPrivateEthStatsEntry
        MAX-ACCESS  not-accessible
        STATUS      current
        DESCRIPTION
            "It is entry in the zxGponOmciPrivateEthStatsTable."
        INDEX   { zxGponOltIndex, zxGponONTIndex, zxGponUNIIndex }
        ::= { zxGponOmciPrivateEthStatsTable 1 }

    ZxGponOmciPrivateEthStatsEntry ::=
        SEQUENCE {
            zxGponOmciPrivateEthStatsIntervalEndTime  INTEGER,
            zxGponOmciPrivateEthStatsThresDataId      INTEGER,
            zxGponOmciPrivateEthStatsRxBroadcast      Unsigned32,
            zxGponOmciPrivateEthStatsRxUnicast        Unsigned32,
            zxGponOmciPrivateEthStatsRxMulticast      Unsigned32,
            zxGponOmciPrivateEthStatsRxDiscarded      Unsigned32,
            zxGponOmciPrivateEthStatsTxBroadcast      Unsigned32,
            zxGponOmciPrivateEthStatsTxUnicast        Unsigned32,
            zxGponOmciPrivateEthStatsTxMulticast      Unsigned32,
            zxGponOmciPrivateEthStatsTxDiscarded      Unsigned32,
            zxGponOmciPrvtEthTxPauseFrms              Unsigned32,
            zxGponOmciPrvtEthRxPauseFrms              Unsigned32,
            zxGponOmciPrvtEthTxErrOctets              Unsigned32,
            zxGponOmciPrvtEthRxErrOctets              Unsigned32,
            zxGponOmciPrivateEthStatsEntryStatus      RowStatus,
            zxGponPrvtEthTxFrms                       Unsigned32,
            zxGponPrvtEthTxUnicastFrms                Unsigned32,
            zxGponPrvtEthTxMulticastFrms              Unsigned32,
            zxGponPrvtEthTxCollisions                 Unsigned32,
            zxGponPrvtEthRxFrms                       Unsigned32,
            zxGponPrvtEthRxFcsErrors                  Unsigned32,
            zxGponPrvtEthRxUnicastFrms                Unsigned32,
            zxGponPrvtEthRxMulticastFrms              Unsigned32,
            zxGponPrvtEthRxUndersizeFrms              Unsigned32
        }

    zxGponOmciPrivateEthStatsIntervalEndTime OBJECT-TYPE
        SYNTAX      INTEGER
        MAX-ACCESS  read-only
        STATUS      current
        DESCRIPTION
        ""
        REFERENCE   "G.984.4"
        ::= { zxGponOmciPrivateEthStatsEntry 1 }

    zxGponOmciPrivateEthStatsThresDataId OBJECT-TYPE
        SYNTAX      INTEGER
        MAX-ACCESS  read-write
        STATUS      current
        DESCRIPTION
        ""
        REFERENCE   "G.984.4"
        ::= { zxGponOmciPrivateEthStatsEntry 2 }

    zxGponOmciPrivateEthStatsRxBroadcast OBJECT-TYPE
        SYNTAX      Unsigned32
        MAX-ACCESS  read-only
        STATUS      current
        DESCRIPTION
        ""
        REFERENCE   "G.984.4 Ethernet performance monitoring history data"
        ::= { zxGponOmciPrivateEthStatsEntry 3 }

    zxGponOmciPrivateEthStatsRxUnicast OBJECT-TYPE
        SYNTAX      Unsigned32
        MAX-ACCESS  read-only
        STATUS      current
        DESCRIPTION
        ""
        REFERENCE   "G.984.4 Ethernet performance monitoring history data"
        ::= { zxGponOmciPrivateEthStatsEntry 4 }

    zxGponOmciPrivateEthStatsRxMulticast OBJECT-TYPE
        SYNTAX      Unsigned32
        MAX-ACCESS  read-only
        STATUS      current
        DESCRIPTION
        ""
        REFERENCE   "G.984.4 Ethernet performance monitoring history data"
        ::= { zxGponOmciPrivateEthStatsEntry 5 }

    zxGponOmciPrivateEthStatsRxDiscarded OBJECT-TYPE
        SYNTAX      Unsigned32
        MAX-ACCESS  read-only
        STATUS      current
        DESCRIPTION
        ""
        REFERENCE   "G.984.4 Ethernet performance monitoring history data"
        ::= { zxGponOmciPrivateEthStatsEntry 6 }

    zxGponOmciPrivateEthStatsTxBroadcast OBJECT-TYPE
        SYNTAX      Unsigned32
        MAX-ACCESS  read-only
        STATUS      current
        DESCRIPTION
        ""
        REFERENCE   "G.984.4 Ethernet performance monitoring history data"
        ::= { zxGponOmciPrivateEthStatsEntry 7 }

    zxGponOmciPrivateEthStatsTxUnicast OBJECT-TYPE
        SYNTAX      Unsigned32
        MAX-ACCESS  read-only
        STATUS      current
        DESCRIPTION
        ""
        REFERENCE   "G.984.4 Ethernet performance monitoring history data"
        ::= { zxGponOmciPrivateEthStatsEntry 8 }

    zxGponOmciPrivateEthStatsTxMulticast OBJECT-TYPE
        SYNTAX      Unsigned32
        MAX-ACCESS  read-only
        STATUS      current
        DESCRIPTION
        ""
        REFERENCE   "G.984.4 Ethernet performance monitoring history data"
        ::= { zxGponOmciPrivateEthStatsEntry 9 }

    zxGponOmciPrivateEthStatsTxDiscarded OBJECT-TYPE
        SYNTAX      Unsigned32
        MAX-ACCESS  read-only
        STATUS      current
        DESCRIPTION
        ""
        REFERENCE   "G.984.4 Ethernet performance monitoring history data"
        ::= { zxGponOmciPrivateEthStatsEntry 10 }

    zxGponOmciPrvtEthTxPauseFrms OBJECT-TYPE
        SYNTAX      Unsigned32
        MAX-ACCESS  read-only
        STATUS      current
        DESCRIPTION
        "The total number of pause frames sent on the interface."
        REFERENCE   "G.984.4 Ethernet performance monitoring history data"
        ::= { zxGponOmciPrivateEthStatsEntry 11 }

    zxGponOmciPrvtEthRxPauseFrms OBJECT-TYPE
        SYNTAX      Unsigned32
        MAX-ACCESS  read-only
        STATUS      current
        DESCRIPTION
        "The total number of pause frames received on the interface."
        REFERENCE   "G.984.4 Ethernet performance monitoring history data"
        ::= { zxGponOmciPrivateEthStatsEntry 12 }

    zxGponOmciPrvtEthTxErrOctets OBJECT-TYPE
        SYNTAX      Unsigned32
        MAX-ACCESS  read-only
        STATUS      current
        DESCRIPTION
        "The total number of errored octets sent on the interface."
        REFERENCE   "G.984.4 Ethernet performance monitoring history data"
        ::= { zxGponOmciPrivateEthStatsEntry 13 }

    zxGponOmciPrvtEthRxErrOctets OBJECT-TYPE
        SYNTAX      Unsigned32
        MAX-ACCESS  read-only
        STATUS      current
        DESCRIPTION
        "The total number of errored octets received on the interface."
        REFERENCE   "G.984.4 Ethernet performance monitoring history data"
        ::= { zxGponOmciPrivateEthStatsEntry 14 }

    zxGponOmciPrivateEthStatsEntryStatus OBJECT-TYPE
        SYNTAX      RowStatus
        MAX-ACCESS  read-write
        STATUS      current
        DESCRIPTION
        "This attribute specifies the action of this entry."
        REFERENCE   "G.984.4"
        ::= { zxGponOmciPrivateEthStatsEntry 20 }


    zxGponPrvtEthTxFrms OBJECT-TYPE
        SYNTAX      Unsigned32
        MAX-ACCESS  read-only
        STATUS      current
        DESCRIPTION
        "The total number of frames sent on the interface."
        REFERENCE   "Private ME: Ethernet performance monitoring history data5"
        ::= { zxGponOmciPrivateEthStatsEntry 21 }

    zxGponPrvtEthTxUnicastFrms OBJECT-TYPE
        SYNTAX      Unsigned32
        MAX-ACCESS  read-only
        STATUS      current
        DESCRIPTION
        "The total number of unicast frames sent on the interface."
        REFERENCE   "Private ME: Ethernet performance monitoring history data5"
        ::= { zxGponOmciPrivateEthStatsEntry 22 }

    zxGponPrvtEthTxMulticastFrms OBJECT-TYPE
        SYNTAX      Unsigned32
        MAX-ACCESS  read-only
        STATUS      current
        DESCRIPTION
        "The total number of multicast frames sent on the interface."
        REFERENCE   "Private ME: Ethernet performance monitoring history data5"
        ::= { zxGponOmciPrivateEthStatsEntry 23 }

    zxGponPrvtEthTxCollisions OBJECT-TYPE
        SYNTAX      Unsigned32
        MAX-ACCESS  read-only
        STATUS      current
        DESCRIPTION
        "The best estimate of the total number of collisions on this Ethernet
        segment."
        REFERENCE   "Private ME: Ethernet performance monitoring history data5"
        ::= { zxGponOmciPrivateEthStatsEntry 24 }

    zxGponPrvtEthRxFrms OBJECT-TYPE
        SYNTAX      Unsigned32
        MAX-ACCESS  read-only
        STATUS      current
        DESCRIPTION
        "The total number of frames received on the interface."
        REFERENCE   "Private ME: Ethernet performance monitoring history data5"
        ::= { zxGponOmciPrivateEthStatsEntry 25 }

    zxGponPrvtEthRxFcsErrors OBJECT-TYPE
        SYNTAX      Unsigned32
        MAX-ACCESS  read-only
        STATUS      current
        DESCRIPTION
        "The total number of FCS errors received on the interface."
        REFERENCE   "Private ME: Ethernet performance monitoring history data5"
        ::= { zxGponOmciPrivateEthStatsEntry 26 }

    zxGponPrvtEthRxUnicastFrms OBJECT-TYPE
        SYNTAX      Unsigned32
        MAX-ACCESS  read-only
        STATUS      current
        DESCRIPTION
        "The total number of unicast frames received on the interface."
        REFERENCE   "Private ME: Ethernet performance monitoring history data5"
        ::= { zxGponOmciPrivateEthStatsEntry 27 }

    zxGponPrvtEthRxMulticastFrms OBJECT-TYPE
        SYNTAX      Unsigned32
        MAX-ACCESS  read-only
        STATUS      current
        DESCRIPTION
        "The total number of multicast frames received on the interface."
        REFERENCE   "Private ME: Ethernet performance monitoring history data5"
        ::= { zxGponOmciPrivateEthStatsEntry 28 }

    zxGponPrvtEthRxUndersizeFrms OBJECT-TYPE
        SYNTAX      Unsigned32
        MAX-ACCESS  read-only
        STATUS      current
        DESCRIPTION
        "The total number of undersize frames received on the interface."
        REFERENCE   "Private ME: Ethernet performance monitoring history data5"
        ::= { zxGponOmciPrivateEthStatsEntry 29 }

--Private ME (OAM functions for Performance Monitoring data)
    zxGponOmciCfmMepStatsTable    OBJECT-TYPE
        SYNTAX      SEQUENCE OF ZxGponOmciCfmMepStatsEntry
        MAX-ACCESS  not-accessible
        STATUS      current
        DESCRIPTION
            ""
        REFERENCE   "Private ME"
        ::= { zxGponOmciStatistics 15 }

    zxGponOmciCfmMepStatsEntry OBJECT-TYPE
        SYNTAX      ZxGponOmciCfmMepStatsEntry
        MAX-ACCESS  not-accessible
        STATUS      current
        DESCRIPTION
            "It is entry in the zxGponOmciCfmMepStatsTable."
        INDEX   { zxGponOltIndex, zxGponONTIndex, zxGponOmciCfmMepStatsMonitorOption, zxGponUNIIndex }
        ::= { zxGponOmciCfmMepStatsTable 1 }

    ZxGponOmciCfmMepStatsEntry ::=
        SEQUENCE {
            zxGponOmciCfmMepStatsMonitorOption               INTEGER,
            zxGponOmciCfmMepStatsIntervalTime                INTEGER,
            zxGponOmciCfmMepStatsMonitorTimes                INTEGER,
            zxGponOmciCfmMepStatsEthLMRatio                  Unsigned32,
            zxGponOmciCfmMepStatsEthDMDelayInSec             Unsigned32,
            zxGponOmciCfmMepStatsEthDMDelayInNanoSec         Unsigned32,
            zxGponOmciCfmMepStatsEthDMJitterInSec            Unsigned32,
            zxGponOmciCfmMepStatsEthDMJitterInNanoSec        Unsigned32,
            zxGponOmciCfmMepStatsInBWUtilization             Unsigned32,
            zxGponOmciCfmMepStatsOutBWUtilization            Unsigned32,
            zxGponOmciCfmMepStatsEntryStatus                 RowStatus
        }

    zxGponOmciCfmMepStatsMonitorOption OBJECT-TYPE
        SYNTAX      INTEGER{
                    single-end-lm(1),
                    dual-end-lm(2),
                    one-way-dm(3),
                    two-way-dm(4)
                    }
        MAX-ACCESS  not-accessible
        STATUS      current
        DESCRIPTION
        ""
        REFERENCE   ""
        ::= { zxGponOmciCfmMepStatsEntry 1 }

    zxGponOmciCfmMepStatsIntervalTime OBJECT-TYPE
        SYNTAX      INTEGER
        MAX-ACCESS  read-write
        STATUS      current
        DESCRIPTION
        "Monitoring interval time in unit of 100ms."
        REFERENCE   ""
        ::= { zxGponOmciCfmMepStatsEntry 2 }

    zxGponOmciCfmMepStatsMonitorTimes OBJECT-TYPE
        SYNTAX      INTEGER
        MAX-ACCESS  read-write
        STATUS      current
        DESCRIPTION
        ""
        REFERENCE   ""
        ::= { zxGponOmciCfmMepStatsEntry 3 }

    zxGponOmciCfmMepStatsEthLMRatio OBJECT-TYPE
        SYNTAX      Unsigned32
        MAX-ACCESS  read-only
        STATUS      current
        DESCRIPTION
        "The percent of loss, in unit of 0.01 percent."
        REFERENCE   ""
        ::= { zxGponOmciCfmMepStatsEntry 4 }

    zxGponOmciCfmMepStatsEthDMDelayInSec OBJECT-TYPE
        SYNTAX      Unsigned32
        MAX-ACCESS  read-only
        STATUS      current
        DESCRIPTION
        ""
        REFERENCE   ""
        ::= { zxGponOmciCfmMepStatsEntry 5 }

    zxGponOmciCfmMepStatsEthDMDelayInNanoSec OBJECT-TYPE
        SYNTAX      Unsigned32
        MAX-ACCESS  read-only
        STATUS      current
        DESCRIPTION
        ""
        REFERENCE   ""
        ::= { zxGponOmciCfmMepStatsEntry 6 }

    zxGponOmciCfmMepStatsEthDMJitterInSec OBJECT-TYPE
        SYNTAX      Unsigned32
        MAX-ACCESS  read-only
        STATUS      current
        DESCRIPTION
        ""
        REFERENCE   ""
        ::= { zxGponOmciCfmMepStatsEntry 7 }

    zxGponOmciCfmMepStatsEthDMJitterInNanoSec OBJECT-TYPE
        SYNTAX      Unsigned32
        MAX-ACCESS  read-only
        STATUS      current
        DESCRIPTION
        ""
        REFERENCE   ""
        ::= { zxGponOmciCfmMepStatsEntry 8 }

    zxGponOmciCfmMepStatsInBWUtilization OBJECT-TYPE
        SYNTAX      Unsigned32
        MAX-ACCESS  read-only
        STATUS      current
        DESCRIPTION
        "The percent of utilization of inbound bandwidth, in unit of 0.01 percent."
        REFERENCE   ""
        ::= { zxGponOmciCfmMepStatsEntry 9 }

    zxGponOmciCfmMepStatsOutBWUtilization OBJECT-TYPE
        SYNTAX      Unsigned32
        MAX-ACCESS  read-only
        STATUS      current
        DESCRIPTION
        "The percent of utilization of outbound bandwidth, in unit of 0.01 percent."
        REFERENCE   ""
        ::= { zxGponOmciCfmMepStatsEntry 10 }

    zxGponOmciCfmMepStatsEntryStatus OBJECT-TYPE
        SYNTAX      RowStatus
        MAX-ACCESS  read-write
        STATUS      current
        DESCRIPTION
        ""
        REFERENCE   ""
        ::= { zxGponOmciCfmMepStatsEntry 11 }

--9.3.30    Ethernet frame performance monitoring history data upstream
    zxGponOmciEthStatsUpTable    OBJECT-TYPE
        SYNTAX      SEQUENCE OF ZxGponOmciEthStatsUpEntry
        MAX-ACCESS  not-accessible
        STATUS      current
        DESCRIPTION
            ""
        REFERENCE   "9.3.30    Ethernet frame performance monitoring history data upstream"
        ::= { zxGponOmciStatistics 16 }

    zxGponOmciEthStatsUpEntry OBJECT-TYPE
        SYNTAX      ZxGponOmciEthStatsUpEntry
        MAX-ACCESS  not-accessible
        STATUS      current
        DESCRIPTION
            "It is entry in the zxGponOmciEthStatsUpTable."
        INDEX   { zxGponOltIndex, zxGponONTIndex, zxGponUNIIndex }
        ::= { zxGponOmciEthStatsUpTable 1 }

    ZxGponOmciEthStatsUpEntry ::=
        SEQUENCE {
            zxGponOmciEthStatsUpIntervalEndTime              INTEGER,
            zxGponOmciEthStatsUpThresDataId                  INTEGER,
            zxGponOmciEthStatsUpDropEvents                   Unsigned32,
            zxGponOmciEthStatsUpOctets                       Unsigned32,
            zxGponOmciEthStatsUpPkts                         Unsigned32,
            zxGponOmciEthStatsUpBroadcastPkts                Unsigned32,
            zxGponOmciEthStatsUpMulticastPkts                Unsigned32,
            zxGponOmciEthStatsUpCRCErrPkts                   Unsigned32,
            zxGponOmciEthStatsUpUndersizePkts                Unsigned32,
            zxGponOmciEthStatsUpOversizePkts                 Unsigned32,
            zxGponOmciEthStatsUp64OctetsPkts                 Unsigned32,
            zxGponOmciEthStatsUp65To127OctetsPkts            Unsigned32,
            zxGponOmciEthStatsUp128To255OctetsPkts           Unsigned32,
            zxGponOmciEthStatsUp256To511OctetsPkts           Unsigned32,
            zxGponOmciEthStatsUp512To1023OctetsPkts          Unsigned32,
            zxGponOmciEthStatsUp1024To1518OctetsPkts         Unsigned32,
            zxGponOmciEthStatsUpEntryStatus                  RowStatus

        }

    zxGponOmciEthStatsUpIntervalEndTime OBJECT-TYPE
        SYNTAX      INTEGER
        MAX-ACCESS  read-only
        STATUS      current
        DESCRIPTION
        ""
        REFERENCE   "G.984.4"
        ::= { zxGponOmciEthStatsUpEntry 1 }

    zxGponOmciEthStatsUpThresDataId OBJECT-TYPE
        SYNTAX      INTEGER
        MAX-ACCESS  read-write
        STATUS      current
        DESCRIPTION
        ""
        REFERENCE   "G.984.4"
        ::= { zxGponOmciEthStatsUpEntry 2 }

    zxGponOmciEthStatsUpDropEvents OBJECT-TYPE
        SYNTAX      Unsigned32
        MAX-ACCESS  read-only
        STATUS      current
        DESCRIPTION
        ""
        REFERENCE   ""
        ::= { zxGponOmciEthStatsUpEntry 3 }

    zxGponOmciEthStatsUpOctets OBJECT-TYPE
        SYNTAX      Unsigned32
        MAX-ACCESS  read-only
        STATUS      current
        DESCRIPTION
        ""
        REFERENCE   ""
        ::= { zxGponOmciEthStatsUpEntry 4 }

    zxGponOmciEthStatsUpPkts OBJECT-TYPE
        SYNTAX      Unsigned32
        MAX-ACCESS  read-only
        STATUS      current
        DESCRIPTION
        ""
        REFERENCE   ""
        ::= { zxGponOmciEthStatsUpEntry 5 }

    zxGponOmciEthStatsUpBroadcastPkts OBJECT-TYPE
        SYNTAX      Unsigned32
        MAX-ACCESS  read-only
        STATUS      current
        DESCRIPTION
        ""
        REFERENCE   ""
        ::= { zxGponOmciEthStatsUpEntry 6 }

    zxGponOmciEthStatsUpMulticastPkts OBJECT-TYPE
        SYNTAX      Unsigned32
        MAX-ACCESS  read-only
        STATUS      current
        DESCRIPTION
        ""
        REFERENCE   ""
        ::= { zxGponOmciEthStatsUpEntry 7 }

    zxGponOmciEthStatsUpCRCErrPkts OBJECT-TYPE
        SYNTAX      Unsigned32
        MAX-ACCESS  read-only
        STATUS      current
        DESCRIPTION
        ""
        REFERENCE   ""
        ::= { zxGponOmciEthStatsUpEntry 8 }

    zxGponOmciEthStatsUpUndersizePkts OBJECT-TYPE
        SYNTAX      Unsigned32
        MAX-ACCESS  read-only
        STATUS      current
        DESCRIPTION
        ""
        REFERENCE   ""
        ::= { zxGponOmciEthStatsUpEntry 9 }

    zxGponOmciEthStatsUpOversizePkts OBJECT-TYPE
        SYNTAX      Unsigned32
        MAX-ACCESS  read-only
        STATUS      current
        DESCRIPTION
        ""
        REFERENCE   ""
        ::= { zxGponOmciEthStatsUpEntry 10 }

    zxGponOmciEthStatsUp64OctetsPkts OBJECT-TYPE
        SYNTAX      Unsigned32
        MAX-ACCESS  read-only
        STATUS      current
        DESCRIPTION
        ""
        REFERENCE   ""
        ::= { zxGponOmciEthStatsUpEntry 11 }

    zxGponOmciEthStatsUp65To127OctetsPkts OBJECT-TYPE
        SYNTAX      Unsigned32
        MAX-ACCESS  read-only
        STATUS      current
        DESCRIPTION
        ""
        REFERENCE   ""
        ::= { zxGponOmciEthStatsUpEntry 12 }

    zxGponOmciEthStatsUp128To255OctetsPkts OBJECT-TYPE
        SYNTAX      Unsigned32
        MAX-ACCESS  read-only
        STATUS      current
        DESCRIPTION
        ""
        REFERENCE   ""
        ::= { zxGponOmciEthStatsUpEntry 13 }

    zxGponOmciEthStatsUp256To511OctetsPkts OBJECT-TYPE
        SYNTAX      Unsigned32
        MAX-ACCESS  read-only
        STATUS      current
        DESCRIPTION
        ""
        REFERENCE   ""
        ::= { zxGponOmciEthStatsUpEntry 14 }

    zxGponOmciEthStatsUp512To1023OctetsPkts OBJECT-TYPE
        SYNTAX      Unsigned32
        MAX-ACCESS  read-only
        STATUS      current
        DESCRIPTION
        ""
        REFERENCE   ""
        ::= { zxGponOmciEthStatsUpEntry 15 }

    zxGponOmciEthStatsUp1024To1518OctetsPkts OBJECT-TYPE
        SYNTAX      Unsigned32
        MAX-ACCESS  read-only
        STATUS      current
        DESCRIPTION
        ""
        REFERENCE   ""
        ::= { zxGponOmciEthStatsUpEntry 16 }

    zxGponOmciEthStatsUpEntryStatus OBJECT-TYPE
        SYNTAX      RowStatus
        MAX-ACCESS  read-write
        STATUS      current
        DESCRIPTION
        ""
        REFERENCE   ""
        ::= { zxGponOmciEthStatsUpEntry 30 }

--9.3.30    Ethernet frame performance monitoring history data downstream
    zxGponOmciEthStatsDownTable    OBJECT-TYPE
        SYNTAX      SEQUENCE OF ZxGponOmciEthStatsDownEntry
        MAX-ACCESS  not-accessible
        STATUS      current
        DESCRIPTION
            ""
        REFERENCE   "9.3.31    Ethernet frame performance monitoring history data downstream"
        ::= { zxGponOmciStatistics 17 }

    zxGponOmciEthStatsDownEntry OBJECT-TYPE
        SYNTAX      ZxGponOmciEthStatsDownEntry
        MAX-ACCESS  not-accessible
        STATUS      current
        DESCRIPTION
            "It is entry in the zxGponOmciEthStatsDownTable."
        INDEX   { zxGponOltIndex, zxGponONTIndex, zxGponUNIIndex }
        ::= { zxGponOmciEthStatsDownTable 1 }

    ZxGponOmciEthStatsDownEntry ::=
        SEQUENCE {
            zxGponOmciEthStatsDownIntervalEndTime              INTEGER,
            zxGponOmciEthStatsDownThresDataId                  INTEGER,
            zxGponOmciEthStatsDownDropEvents                   Unsigned32,
            zxGponOmciEthStatsDownOctets                       Unsigned32,
            zxGponOmciEthStatsDownPkts                         Unsigned32,
            zxGponOmciEthStatsDownBroadcastPkts                Unsigned32,
            zxGponOmciEthStatsDownMulticastPkts                Unsigned32,
            zxGponOmciEthStatsDownCRCErrPkts                   Unsigned32,
            zxGponOmciEthStatsDownUndersizePkts                Unsigned32,
            zxGponOmciEthStatsDownOversizePkts                 Unsigned32,
            zxGponOmciEthStatsDown64OctetsPkts                 Unsigned32,
            zxGponOmciEthStatsDown65To127OctetsPkts            Unsigned32,
            zxGponOmciEthStatsDown128To255OctetsPkts           Unsigned32,
            zxGponOmciEthStatsDown256To511OctetsPkts           Unsigned32,
            zxGponOmciEthStatsDown512To1023OctetsPkts          Unsigned32,
            zxGponOmciEthStatsDown1024To1518OctetsPkts         Unsigned32,
            zxGponOmciEthStatsDownEntryStatus                  RowStatus

        }

    zxGponOmciEthStatsDownIntervalEndTime OBJECT-TYPE
        SYNTAX      INTEGER
        MAX-ACCESS  read-only
        STATUS      current
        DESCRIPTION
        ""
        REFERENCE   "G.984.4"
        ::= { zxGponOmciEthStatsDownEntry 1 }

    zxGponOmciEthStatsDownThresDataId OBJECT-TYPE
        SYNTAX      INTEGER
        MAX-ACCESS  read-write
        STATUS      current
        DESCRIPTION
        ""
        REFERENCE   "G.984.4"
        ::= { zxGponOmciEthStatsDownEntry 2 }

    zxGponOmciEthStatsDownDropEvents OBJECT-TYPE
        SYNTAX      Unsigned32
        MAX-ACCESS  read-only
        STATUS      current
        DESCRIPTION
        ""
        REFERENCE   ""
        ::= { zxGponOmciEthStatsDownEntry 3 }

    zxGponOmciEthStatsDownOctets OBJECT-TYPE
        SYNTAX      Unsigned32
        MAX-ACCESS  read-only
        STATUS      current
        DESCRIPTION
        ""
        REFERENCE   ""
        ::= { zxGponOmciEthStatsDownEntry 4 }

    zxGponOmciEthStatsDownPkts OBJECT-TYPE
        SYNTAX      Unsigned32
        MAX-ACCESS  read-only
        STATUS      current
        DESCRIPTION
        ""
        REFERENCE   ""
        ::= { zxGponOmciEthStatsDownEntry 5 }

    zxGponOmciEthStatsDownBroadcastPkts OBJECT-TYPE
        SYNTAX      Unsigned32
        MAX-ACCESS  read-only
        STATUS      current
        DESCRIPTION
        ""
        REFERENCE   ""
        ::= { zxGponOmciEthStatsDownEntry 6 }

    zxGponOmciEthStatsDownMulticastPkts OBJECT-TYPE
        SYNTAX      Unsigned32
        MAX-ACCESS  read-only
        STATUS      current
        DESCRIPTION
        ""
        REFERENCE   ""
        ::= { zxGponOmciEthStatsDownEntry 7 }

    zxGponOmciEthStatsDownCRCErrPkts OBJECT-TYPE
        SYNTAX      Unsigned32
        MAX-ACCESS  read-only
        STATUS      current
        DESCRIPTION
        ""
        REFERENCE   ""
        ::= { zxGponOmciEthStatsDownEntry 8 }

    zxGponOmciEthStatsDownUndersizePkts OBJECT-TYPE
        SYNTAX      Unsigned32
        MAX-ACCESS  read-only
        STATUS      current
        DESCRIPTION
        ""
        REFERENCE   ""
        ::= { zxGponOmciEthStatsDownEntry 9 }

    zxGponOmciEthStatsDownOversizePkts OBJECT-TYPE
        SYNTAX      Unsigned32
        MAX-ACCESS  read-only
        STATUS      current
        DESCRIPTION
        ""
        REFERENCE   ""
        ::= { zxGponOmciEthStatsDownEntry 10 }

    zxGponOmciEthStatsDown64OctetsPkts OBJECT-TYPE
        SYNTAX      Unsigned32
        MAX-ACCESS  read-only
        STATUS      current
        DESCRIPTION
        ""
        REFERENCE   ""
        ::= { zxGponOmciEthStatsDownEntry 11 }

    zxGponOmciEthStatsDown65To127OctetsPkts OBJECT-TYPE
        SYNTAX      Unsigned32
        MAX-ACCESS  read-only
        STATUS      current
        DESCRIPTION
        ""
        REFERENCE   ""
        ::= { zxGponOmciEthStatsDownEntry 12 }

    zxGponOmciEthStatsDown128To255OctetsPkts OBJECT-TYPE
        SYNTAX      Unsigned32
        MAX-ACCESS  read-only
        STATUS      current
        DESCRIPTION
        ""
        REFERENCE   ""
        ::= { zxGponOmciEthStatsDownEntry 13 }

    zxGponOmciEthStatsDown256To511OctetsPkts OBJECT-TYPE
        SYNTAX      Unsigned32
        MAX-ACCESS  read-only
        STATUS      current
        DESCRIPTION
        ""
        REFERENCE   ""
        ::= { zxGponOmciEthStatsDownEntry 14 }

    zxGponOmciEthStatsDown512To1023OctetsPkts OBJECT-TYPE
        SYNTAX      Unsigned32
        MAX-ACCESS  read-only
        STATUS      current
        DESCRIPTION
        ""
        REFERENCE   ""
        ::= { zxGponOmciEthStatsDownEntry 15 }

    zxGponOmciEthStatsDown1024To1518OctetsPkts OBJECT-TYPE
        SYNTAX      Unsigned32
        MAX-ACCESS  read-only
        STATUS      current
        DESCRIPTION
        ""
        REFERENCE   ""
        ::= { zxGponOmciEthStatsDownEntry 16 }

    zxGponOmciEthStatsDownEntryStatus OBJECT-TYPE
        SYNTAX      RowStatus
        MAX-ACCESS  read-write
        STATUS      current
        DESCRIPTION
        ""
        REFERENCE   ""
        ::= { zxGponOmciEthStatsDownEntry 30 }


--FEC Current Statics G984.4_9.2.11
    zxGponOmciFecCurrStatsTable    OBJECT-TYPE
        SYNTAX      SEQUENCE OF ZxGponOmciFecCurrStatsEntry
        MAX-ACCESS  not-accessible
        STATUS      current
        DESCRIPTION
            "FEC performance monitoring current data"
        REFERENCE   "9.2.11  FEC performance monitoring history data."
        ::= { zxGponOmciStatistics 18 }

    zxGponOmciFecCurrStatsEntry OBJECT-TYPE
        SYNTAX      ZxGponOmciFecCurrStatsEntry
        MAX-ACCESS  not-accessible
        STATUS      current
        DESCRIPTION
            "It is entry in the zxGponOmciFecCurrStatsTable."
        INDEX   { zxGponOltIndex, zxGponONTIndex }
        ::= { zxGponOmciFecCurrStatsTable 1 }

    ZxGponOmciFecCurrStatsEntry ::=
        SEQUENCE {
            zxGponOmciFecCurrIntvlEndTime              INTEGER,
            zxGponOmciFecCurrThresDataId               INTEGER,
            zxGponOmciFecCurrCrctBytes                 Unsigned32,
            zxGponOmciFecCurrCrctCodeWords             Unsigned32,
            zxGponOmciFecCurrUcrctCodeWords            Unsigned32,
            zxGponOmciFecCurrTotalCodeWords            Unsigned32,
            zxGponOmciFecCurrFecSeconds                Unsigned32,
            zxGponOmciFecCurrEntryStatus               RowStatus
        }

    zxGponOmciFecCurrIntvlEndTime OBJECT-TYPE
        SYNTAX      INTEGER(0..255)
        MAX-ACCESS  read-only
        STATUS      current
        DESCRIPTION
        "This attribute identifies the most recently finished 15-minute
        interval."
        REFERENCE   "G.984.4"
        ::= { zxGponOmciFecCurrStatsEntry 1 }

    zxGponOmciFecCurrThresDataId OBJECT-TYPE
        SYNTAX      INTEGER(0..65535)
        MAX-ACCESS  read-create
        STATUS      current
        DESCRIPTION
        "This attribute points to an instance of the threshold data 1 managed
         entity that contains PM threshold values. Since no threshold value
         attribute number exceeds 7, a threshold data 2 ME is optional."
        REFERENCE   "G.984.4"
        ::= { zxGponOmciFecCurrStatsEntry 2 }

    zxGponOmciFecCurrCrctBytes OBJECT-TYPE
        SYNTAX      Unsigned32
        MAX-ACCESS  read-only
        STATUS      current
        DESCRIPTION
        "This attribute counts the number of bytes that were corrected by the
        FEC function."
        REFERENCE   "G.984.4"
        ::= { zxGponOmciFecCurrStatsEntry 3 }

    zxGponOmciFecCurrCrctCodeWords OBJECT-TYPE
        SYNTAX      Unsigned32
        MAX-ACCESS  read-only
        STATUS      current
        DESCRIPTION
        "This attribute counts the code words that were corrected by the FEC
         function."
        REFERENCE   "G.984.4"
        ::= { zxGponOmciFecCurrStatsEntry 4 }

    zxGponOmciFecCurrUcrctCodeWords OBJECT-TYPE
        SYNTAX      Unsigned32
        MAX-ACCESS  read-only
        STATUS      current
        DESCRIPTION
        "This attribute counts the code words that were not corrected by
         the FEC function."
        REFERENCE   "G.984.4"
        ::= { zxGponOmciFecCurrStatsEntry 5 }

    zxGponOmciFecCurrTotalCodeWords OBJECT-TYPE
        SYNTAX      Unsigned32
        MAX-ACCESS  read-only
        STATUS      current
        DESCRIPTION
        "This attribute counts the total received code words."
        REFERENCE   "G.984.4"
        ::= { zxGponOmciFecCurrStatsEntry 6 }

    zxGponOmciFecCurrFecSeconds OBJECT-TYPE
        SYNTAX      Unsigned32
        MAX-ACCESS  read-only
        STATUS      current
        DESCRIPTION
        "This attribute counts seconds during which there was a forward error
         correction anomaly."
        REFERENCE   "G.984.4"
        ::= { zxGponOmciFecCurrStatsEntry 7 }

    zxGponOmciFecCurrEntryStatus OBJECT-TYPE
        SYNTAX      RowStatus
        MAX-ACCESS  read-create
        STATUS      current
        DESCRIPTION
        "The row status of this entry.The zxGponOmciFecCurrThresDataId need to
        be configured when add a row to the entry. When add or delete rows in
        zxGponOmciFecCurrStatsTable,The corresponding entry in
        zxGponOmciFecHisStatsTable synchronization also be added or deleted."
        ::= { zxGponOmciFecCurrStatsEntry 30 }

--zxGponOmciMcastVlanStatsTable
    zxGponOmciMcastVlanStatsTable    OBJECT-TYPE
        SYNTAX      SEQUENCE OF ZxGponOmciMcastVlanStatsEntry
        MAX-ACCESS  not-accessible
        STATUS      current
        DESCRIPTION
            "GPON ONT multicast performance monitoring current data."
        ::= { zxGponOmciStatistics 19 }

    zxGponOmciMcastVlanStatsEntry OBJECT-TYPE
        SYNTAX      ZxGponOmciMcastVlanStatsEntry
        MAX-ACCESS  not-accessible
        STATUS      current
        DESCRIPTION
            "It is entry in the zxGponOmciMcastVlanStatsTable."
        INDEX   { zxGponOltIndex, zxGponONTIndex,zxGponUNIIndex,zxGponMCastVlanId }
        ::= { zxGponOmciMcastVlanStatsTable 1 }

    ZxGponOmciMcastVlanStatsEntry ::=
        SEQUENCE {
            zxGponMcastIntervalEndTime         INTEGER,
            zxGponMcastThresDataId             INTEGER,
            zxGponMcastTxJoins                 Counter32,
            zxGponMcastRxJoins                 Counter32,
            zxGponMcastSuccJoins                Counter32,
            zxGponMcastUnsuccJoins              Counter32,
            zxGponMcastTxLeave                 Counter32,
            zxGponMcastRxLeave                 Counter32,
            zxGponMcastTxGenQuery              Counter32,
            zxGponMcastRxGenQuery              Counter32,
            zxGponMcastTxGroupSpeQuery         Counter32,
            zxGponMcastRxGroupSpeQuery         Counter32,
            zxGponMcastRxInvalidIgmp           Counter32,
            zxGponMcastMonitoringStatus        RowStatus
        }

    zxGponMcastIntervalEndTime OBJECT-TYPE
        SYNTAX      INTEGER(0..255)
        MAX-ACCESS  read-only
        STATUS      current
        DESCRIPTION
        "This attribute identifies the most recently finished 15-minute
        interval."
        ::= { zxGponOmciMcastVlanStatsEntry 1 }

    zxGponMcastThresDataId OBJECT-TYPE
        SYNTAX      INTEGER(0..65535)
        MAX-ACCESS  read-only
        STATUS      current
        DESCRIPTION
        "This attribute points to an instance of the threshold data 1 managed
         entity that contains PM threshold values. Since no threshold value
         attribute number exceeds 7, a threshold data 2 ME is optional."
        ::= { zxGponOmciMcastVlanStatsEntry 2 }

    zxGponMcastTxJoins OBJECT-TYPE
        SYNTAX      Counter32
        MAX-ACCESS  read-only
        STATUS      current
        DESCRIPTION
        "This attribute counts the total number of transmit joins message."
        ::= { zxGponOmciMcastVlanStatsEntry 3 }

    zxGponMcastRxJoins OBJECT-TYPE
        SYNTAX      Counter32
        MAX-ACCESS  read-only
        STATUS      current
        DESCRIPTION
        "This attribute counts the total number of received joins message."
        ::= { zxGponOmciMcastVlanStatsEntry 4 }

    zxGponMcastSuccJoins OBJECT-TYPE
        SYNTAX      Counter32
        MAX-ACCESS  read-only
        STATUS      current
        DESCRIPTION
        "This attribute counts the total number of successful joins message."
        ::= { zxGponOmciMcastVlanStatsEntry 5 }

    zxGponMcastUnsuccJoins OBJECT-TYPE
        SYNTAX      Counter32
        MAX-ACCESS  read-only
        STATUS      current
        DESCRIPTION
        "This attribute counts the total number of unsuccessful joins message."
        ::= { zxGponOmciMcastVlanStatsEntry 6 }

    zxGponMcastTxLeave OBJECT-TYPE
        SYNTAX      Counter32
        MAX-ACCESS  read-only
        STATUS      current
        DESCRIPTION
        "This attribute counts the total number of transmitted leave message."
        ::= { zxGponOmciMcastVlanStatsEntry 7 }

    zxGponMcastRxLeave OBJECT-TYPE
        SYNTAX      Counter32
        MAX-ACCESS  read-only
        STATUS      current
        DESCRIPTION
        "This attribute counts the total number of received leave message."
        ::= { zxGponOmciMcastVlanStatsEntry 8 }

    zxGponMcastTxGenQuery OBJECT-TYPE
        SYNTAX      Counter32
        MAX-ACCESS  read-only
        STATUS      current
        DESCRIPTION
        "This attribute counts the total number of tranmsmitted general
        query message."
        ::= { zxGponOmciMcastVlanStatsEntry 9 }

    zxGponMcastRxGenQuery OBJECT-TYPE
        SYNTAX      Counter32
        MAX-ACCESS  read-only
        STATUS      current
        DESCRIPTION
        "This attribute counts the total number of received general
        query message."
        ::= { zxGponOmciMcastVlanStatsEntry 10 }

    zxGponMcastTxGroupSpeQuery OBJECT-TYPE
        SYNTAX      Counter32
        MAX-ACCESS  read-only
        STATUS      current
        DESCRIPTION
        "This attribute counts the total number of tranmsmitted special
        query message."
        ::= { zxGponOmciMcastVlanStatsEntry 11 }

    zxGponMcastRxGroupSpeQuery OBJECT-TYPE
        SYNTAX      Counter32
        MAX-ACCESS  read-only
        STATUS      current
        DESCRIPTION
        "This attribute counts the total number of received special
        query message."
        ::= { zxGponOmciMcastVlanStatsEntry 12 }

    zxGponMcastRxInvalidIgmp OBJECT-TYPE
        SYNTAX      Counter32
        MAX-ACCESS  read-only
        STATUS      current
        DESCRIPTION
        "This attribute counts the total number of received invalid
        IGMP message."
        ::= { zxGponOmciMcastVlanStatsEntry 13 }

    zxGponMcastMonitoringStatus OBJECT-TYPE
        SYNTAX      RowStatus
        MAX-ACCESS  read-create
        STATUS      current
        DESCRIPTION
        "This attribute specifies the action of this entry."
        ::= { zxGponOmciMcastVlanStatsEntry 30 }

--zxGponOmciVlanEthStatsTable
    zxGponOmciVlanEthStatsTable    OBJECT-TYPE
        SYNTAX      SEQUENCE OF ZxGponOmciVlanEthStatsEntry
        MAX-ACCESS  not-accessible
        STATUS      current
        DESCRIPTION
            "GPON ONT Ethernet UNI VLAN Monitoring Table."
        ::= { zxGponOmciStatistics 20 }

    zxGponOmciVlanEthStatsEntry OBJECT-TYPE
        SYNTAX      ZxGponOmciVlanEthStatsEntry
        MAX-ACCESS  not-accessible
        STATUS      current
        DESCRIPTION
            "It is entry in the zxGponVlanEthMonitoringTable."
        INDEX   { zxGponOltIndex, zxGponONTIndex,zxGponUNIIndex,zxGponVlanId }
        ::= { zxGponOmciVlanEthStatsTable 1 }

    ZxGponOmciVlanEthStatsEntry ::=
        SEQUENCE {
            zxGponVlanId                           INTEGER,
            zxGponVlanEthIntervalEndTime           INTEGER,
            zxGponVlanEthThresDataId               INTEGER,
            zxGponVlanEthRxFrms                    Counter32,
            zxGponVlanEthRxOctets                  Counter32,
            zxGponVlanEthDcdInboundFrms            Counter32,
            zxGponVlanEthFwdOutboundFrms           Counter32,
            zxGponVlanEthDcdLackBuffersFrms        Counter32,
            zxGponVlanEthDcdTransDelayFrms         Counter32,
            zxGponVlanEthDcdOnErrorFrms            Counter32,
            zxGponVlanEthDcdByFilteringFrms        Counter32,
            zxGponOmciVlanEthStatsStatus           RowStatus
        }

    zxGponVlanId OBJECT-TYPE
        SYNTAX      INTEGER(1..4095)
        MAX-ACCESS  not-accessible
        STATUS      current
        DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
        ::= { zxGponOmciVlanEthStatsEntry 1 }


    zxGponVlanEthIntervalEndTime OBJECT-TYPE
        SYNTAX      INTEGER(0..255)
        MAX-ACCESS  read-only
        STATUS      current
        DESCRIPTION
        "This attribute identifies the most recently finished 15-minute
        interval."
        ::= { zxGponOmciVlanEthStatsEntry 2 }

    zxGponVlanEthThresDataId OBJECT-TYPE
        SYNTAX      INTEGER(0..65535)
        MAX-ACCESS  read-only
        STATUS      current
        DESCRIPTION
        "This attribute points to an instance of the threshold data 1 managed
         entity that contains PM threshold values. Since no threshold value
         attribute number exceeds 7, a threshold data 2 ME is optional."
        ::= { zxGponOmciVlanEthStatsEntry 3 }

    zxGponVlanEthRxFrms OBJECT-TYPE
        SYNTAX      Counter32
        MAX-ACCESS  read-only
        STATUS      current
        DESCRIPTION
        "This attribute counts the total received frames."
        ::= { zxGponOmciVlanEthStatsEntry 4 }

    zxGponVlanEthRxOctets OBJECT-TYPE
        SYNTAX      Counter32
        MAX-ACCESS  read-only
        STATUS      current
        DESCRIPTION
        "This attribute counts the total received octets."
        ::= { zxGponOmciVlanEthStatsEntry 5 }

    zxGponVlanEthDcdInboundFrms OBJECT-TYPE
        SYNTAX      Counter32
        MAX-ACCESS  read-only
        STATUS      current
        DESCRIPTION
        "This attribute counts the total discard inbound frames."
        ::= { zxGponOmciVlanEthStatsEntry 6 }

    zxGponVlanEthFwdOutboundFrms OBJECT-TYPE
        SYNTAX      Counter32
        MAX-ACCESS  read-only
        STATUS      current
        DESCRIPTION
        "This attribute counts the total forward outbound frames."
        ::= { zxGponOmciVlanEthStatsEntry 7 }

    zxGponVlanEthDcdLackBuffersFrms OBJECT-TYPE
        SYNTAX      Counter32
        MAX-ACCESS  read-only
        STATUS      current
        DESCRIPTION
        "This attribute counts the total discard frames because
        of lacking buffers."
        ::= { zxGponOmciVlanEthStatsEntry 8 }

    zxGponVlanEthDcdTransDelayFrms OBJECT-TYPE
        SYNTAX      Counter32
        MAX-ACCESS  read-only
        STATUS      current
        DESCRIPTION
        "This attribute counts the total discard frames because
        of transmission delay."
        ::= { zxGponOmciVlanEthStatsEntry 9 }

    zxGponVlanEthDcdOnErrorFrms OBJECT-TYPE
        SYNTAX      Counter32
        MAX-ACCESS  read-only
        STATUS      current
        DESCRIPTION
        "This attribute counts the total discard frames on errors."
        ::= { zxGponOmciVlanEthStatsEntry 10 }

    zxGponVlanEthDcdByFilteringFrms OBJECT-TYPE
        SYNTAX      Counter32
        MAX-ACCESS  read-only
        STATUS      current
        DESCRIPTION
        "This attribute counts the total discard frames on ingress
        filtering."
        ::= { zxGponOmciVlanEthStatsEntry 11 }

    zxGponOmciVlanEthStatsStatus OBJECT-TYPE
        SYNTAX      RowStatus
        MAX-ACCESS  read-create
        STATUS      current
        DESCRIPTION
        "This attribute specifies the action of this entry."
        ::= { zxGponOmciVlanEthStatsEntry 30 }

--OMCI history statistics
    zxGponOmciEthHisStatsTable    OBJECT-TYPE
        SYNTAX      SEQUENCE OF ZxGponOmciEthHisStatsEntry
        MAX-ACCESS  not-accessible
        STATUS      current
        DESCRIPTION
            ""
        REFERENCE   "G.984.4 Ethernet performance monitoring history data
                     Ethernet performance monitoring history data 2
                     Ethernet performance monitoring history data 3"
        ::= { zxGponOmciStatistics 21 }

    zxGponOmciEthHisStatsEntry OBJECT-TYPE
        SYNTAX      ZxGponOmciEthHisStatsEntry
        MAX-ACCESS  not-accessible
        STATUS      current
        DESCRIPTION
            "It is entry in the zxGponOmciEthHisStatsTable."
        INDEX   { zxGponOltIndex, zxGponONTIndex, zxGponUNIIndex }
        ::= { zxGponOmciEthHisStatsTable 1 }

    ZxGponOmciEthHisStatsEntry ::=
        SEQUENCE {
            zxGponOmciEthHisStatsIntervalEndTime              INTEGER,
            zxGponOmciEthHisStatsThresDataId                  INTEGER,
            zxGponOmciEthHisStatsFCSErrors                    Unsigned32,
            zxGponOmciEthHisStatsExcessiveCollisionCnt        Unsigned32,
            zxGponOmciEthHisStatsLateCollisionCnt             Unsigned32,
            zxGponOmciEthHisStatsFrameTooLongs                Unsigned32,
            zxGponOmciEthHisStatsRxBufOverflows               Unsigned32,
            zxGponOmciEthHisStatsTxBufOverflows               Unsigned32,
            zxGponOmciEthHisStatsSingleCollisionCnt           Unsigned32,
            zxGponOmciEthHisStatsMultipleCollisionCnt         Unsigned32,
            zxGponOmciEthHisStatsSQECnt                       Unsigned32,
            zxGponOmciEthHisStatsDeferredTxCnt                Unsigned32,
            zxGponOmciEthHisStatsInternalMACTxErrCnt          Unsigned32,
            zxGponOmciEthHisStatsCarrierSenseErrCnt           Unsigned32,
            zxGponOmciEthHisStatsAlignmentErrCnt              Unsigned32,
            zxGponOmciEthHisStatsInternalMACRxErrCnt          Unsigned32,
            zxGponOmciEthHisStatsEntryStatus                  RowStatus,
            zxGponOmciEthHisStatsPPPoEFilteredCnt             Unsigned32,
            zxGponOmciEthHisStatsDropEvents                   Unsigned32,
            zxGponOmciEthHisStatsRxOctets                     Unsigned32,
            zxGponOmciEthHisStatsRxPkts                       Unsigned32,
            zxGponOmciEthHisStatsRxBroadcastPkts              Unsigned32,
            zxGponOmciEthHisStatsRxMulticastPkts              Unsigned32,
            zxGponOmciEthHisStatsRxUndersizePkts              Unsigned32,
            zxGponOmciEthHisStatsRxFragments                  Unsigned32,
            zxGponOmciEthHisStatsRxJabbers                    Unsigned32,
            zxGponOmciEthHisStatsRx64OctetsPkts               Unsigned32,
            zxGponOmciEthHisStatsRx65To127OctetsPkts          Unsigned32,
            zxGponOmciEthHisStatsRx128To255OctetsPkts         Unsigned32,
            zxGponOmciEthHisStatsRx256To511OctetsPkts         Unsigned32,
            zxGponOmciEthHisStatsRx512To1023OctetsPkts        Unsigned32,
            zxGponOmciEthHisStatsRx1024To1518OctetsPkts       Unsigned32
        }

    zxGponOmciEthHisStatsIntervalEndTime OBJECT-TYPE
        SYNTAX      INTEGER
        MAX-ACCESS  read-only
        STATUS      current
        DESCRIPTION
        ""
        REFERENCE   "G.984.4"
        ::= { zxGponOmciEthHisStatsEntry 1 }

    zxGponOmciEthHisStatsThresDataId OBJECT-TYPE
        SYNTAX      INTEGER
        MAX-ACCESS  read-only
        STATUS      current
        DESCRIPTION
        ""
        REFERENCE   "G.984.4"
        ::= { zxGponOmciEthHisStatsEntry 2 }

    zxGponOmciEthHisStatsFCSErrors OBJECT-TYPE
        SYNTAX      Unsigned32
        MAX-ACCESS  read-only
        STATUS      current
        DESCRIPTION
        ""
        REFERENCE   "G.984.4 Ethernet performance monitoring history data"
        ::= { zxGponOmciEthHisStatsEntry 3 }

    zxGponOmciEthHisStatsExcessiveCollisionCnt OBJECT-TYPE
        SYNTAX      Unsigned32
        MAX-ACCESS  read-only
        STATUS      current
        DESCRIPTION
        ""
        REFERENCE   "G.984.4 Ethernet performance monitoring history data"
        ::= { zxGponOmciEthHisStatsEntry 4 }

    zxGponOmciEthHisStatsLateCollisionCnt OBJECT-TYPE
        SYNTAX      Unsigned32
        MAX-ACCESS  read-only
        STATUS      current
        DESCRIPTION
        ""
        REFERENCE   "G.984.4 Ethernet performance monitoring history data"
        ::= { zxGponOmciEthHisStatsEntry 5 }

    zxGponOmciEthHisStatsFrameTooLongs OBJECT-TYPE
        SYNTAX      Unsigned32
        MAX-ACCESS  read-only
        STATUS      current
        DESCRIPTION
        ""
        REFERENCE   "G.984.4 Ethernet performance monitoring history data"
        ::= { zxGponOmciEthHisStatsEntry 6 }

    zxGponOmciEthHisStatsRxBufOverflows OBJECT-TYPE
        SYNTAX      Unsigned32
        MAX-ACCESS  read-only
        STATUS      current
        DESCRIPTION
        ""
        REFERENCE   "G.984.4 Ethernet performance monitoring history data"
        ::= { zxGponOmciEthHisStatsEntry 7 }

    zxGponOmciEthHisStatsTxBufOverflows OBJECT-TYPE
        SYNTAX      Unsigned32
        MAX-ACCESS  read-only
        STATUS      current
        DESCRIPTION
        ""
        REFERENCE   "G.984.4 Ethernet performance monitoring history data"
        ::= { zxGponOmciEthHisStatsEntry 8 }

    zxGponOmciEthHisStatsSingleCollisionCnt OBJECT-TYPE
        SYNTAX      Unsigned32
        MAX-ACCESS  read-only
        STATUS      current
        DESCRIPTION
        ""
        REFERENCE   "G.984.4 Ethernet performance monitoring history data"
        ::= { zxGponOmciEthHisStatsEntry 9 }

    zxGponOmciEthHisStatsMultipleCollisionCnt OBJECT-TYPE
        SYNTAX      Unsigned32
        MAX-ACCESS  read-only
        STATUS      current
        DESCRIPTION
        ""
        REFERENCE   "G.984.4 Ethernet performance monitoring history data"
        ::= { zxGponOmciEthHisStatsEntry 10 }

    zxGponOmciEthHisStatsSQECnt OBJECT-TYPE
        SYNTAX      Unsigned32
        MAX-ACCESS  read-only
        STATUS      current
        DESCRIPTION
        ""
        REFERENCE   "G.984.4 Ethernet performance monitoring history data"
        ::= { zxGponOmciEthHisStatsEntry 11 }

    zxGponOmciEthHisStatsDeferredTxCnt OBJECT-TYPE
        SYNTAX      Unsigned32
        MAX-ACCESS  read-only
        STATUS      current
        DESCRIPTION
        ""
        REFERENCE   "G.984.4 Ethernet performance monitoring history data"
        ::= { zxGponOmciEthHisStatsEntry 12 }

    zxGponOmciEthHisStatsInternalMACTxErrCnt OBJECT-TYPE
        SYNTAX      Unsigned32
        MAX-ACCESS  read-only
        STATUS      current
        DESCRIPTION
        ""
        REFERENCE   "G.984.4 Ethernet performance monitoring history data"
        ::= { zxGponOmciEthHisStatsEntry 13 }

    zxGponOmciEthHisStatsCarrierSenseErrCnt OBJECT-TYPE
        SYNTAX      Unsigned32
        MAX-ACCESS  read-only
        STATUS      current
        DESCRIPTION
        ""
        REFERENCE   "G.984.4 Ethernet performance monitoring history data"
        ::= { zxGponOmciEthHisStatsEntry 14 }

    zxGponOmciEthHisStatsAlignmentErrCnt OBJECT-TYPE
        SYNTAX      Unsigned32
        MAX-ACCESS  read-only
        STATUS      current
        DESCRIPTION
        ""
        REFERENCE   "G.984.4 Ethernet performance monitoring history data"
        ::= { zxGponOmciEthHisStatsEntry 15 }

    zxGponOmciEthHisStatsInternalMACRxErrCnt OBJECT-TYPE
        SYNTAX      Unsigned32
        MAX-ACCESS  read-only
        STATUS      current
        DESCRIPTION
        ""
        REFERENCE   "G.984.4 Ethernet performance monitoring history data"
        ::= { zxGponOmciEthHisStatsEntry 16 }

    zxGponOmciEthHisStatsEntryStatus OBJECT-TYPE
        SYNTAX      RowStatus
        MAX-ACCESS  read-only
        STATUS      current
        DESCRIPTION
        "This attribute specifies the action of this entry."
        REFERENCE   "G.984.4"
        ::= { zxGponOmciEthHisStatsEntry 17 }

    zxGponOmciEthHisStatsPPPoEFilteredCnt OBJECT-TYPE
        SYNTAX      Unsigned32
        MAX-ACCESS  read-only
        STATUS      current
        DESCRIPTION
        ""
        REFERENCE   "G.984.4 Ethernet performance monitoring history data 2"
        ::= { zxGponOmciEthHisStatsEntry 18 }

    zxGponOmciEthHisStatsDropEvents OBJECT-TYPE
        SYNTAX      Unsigned32
        MAX-ACCESS  read-only
        STATUS      current
        DESCRIPTION
        ""
        REFERENCE   "G.984.4 Ethernet performance monitoring history data 3"
        ::= { zxGponOmciEthHisStatsEntry 19 }

    zxGponOmciEthHisStatsRxOctets OBJECT-TYPE
        SYNTAX      Unsigned32
        MAX-ACCESS  read-only
        STATUS      current
        DESCRIPTION
        ""
        REFERENCE   "G.984.4"
        ::= { zxGponOmciEthHisStatsEntry 20 }

    zxGponOmciEthHisStatsRxPkts OBJECT-TYPE
        SYNTAX      Unsigned32
        MAX-ACCESS  read-only
        STATUS      current
        DESCRIPTION
        ""
        REFERENCE   "G.984.4 Ethernet performance monitoring history data 3"
        ::= { zxGponOmciEthHisStatsEntry 21 }

    zxGponOmciEthHisStatsRxBroadcastPkts OBJECT-TYPE
        SYNTAX      Unsigned32
        MAX-ACCESS  read-only
        STATUS      current
        DESCRIPTION
        ""
        REFERENCE   "G.984.4 Ethernet performance monitoring history data 3"
        ::= { zxGponOmciEthHisStatsEntry 22 }

    zxGponOmciEthHisStatsRxMulticastPkts OBJECT-TYPE
        SYNTAX      Unsigned32
        MAX-ACCESS  read-only
        STATUS      current
        DESCRIPTION
        ""
        REFERENCE   "G.984.4 Ethernet performance monitoring history data 3"
        ::= { zxGponOmciEthHisStatsEntry 23 }

    zxGponOmciEthHisStatsRxUndersizePkts OBJECT-TYPE
        SYNTAX      Unsigned32
        MAX-ACCESS  read-only
        STATUS      current
        DESCRIPTION
        ""
        REFERENCE   "G.984.4 Ethernet performance monitoring history data 3"
        ::= { zxGponOmciEthHisStatsEntry 24 }

    zxGponOmciEthHisStatsRxFragments OBJECT-TYPE
        SYNTAX      Unsigned32
        MAX-ACCESS  read-only
        STATUS      current
        DESCRIPTION
        ""
        REFERENCE   "G.984.4 Ethernet performance monitoring history data 3"
        ::= { zxGponOmciEthHisStatsEntry 25 }

    zxGponOmciEthHisStatsRxJabbers OBJECT-TYPE
        SYNTAX      Unsigned32
        MAX-ACCESS  read-only
        STATUS      current
        DESCRIPTION
        ""
        REFERENCE   "G.984.4 Ethernet performance monitoring history data 3"
        ::= { zxGponOmciEthHisStatsEntry 26 }

    zxGponOmciEthHisStatsRx64OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 27 }

    zxGponOmciEthHisStatsRx65To127OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 28 }

    zxGponOmciEthHisStatsRx128To255OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 29 }

    zxGponOmciEthHisStatsRx256To511OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 30 }

    zxGponOmciEthHisStatsRx512To1023OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 31 }

    zxGponOmciEthHisStatsRx1024To1518OctetsPkts OBJECT-TYPE
        SYNTAX      Unsigned32
        MAX-ACCESS  read-only
        STATUS      current
        DESCRIPTION
        ""
        REFERENCE   "G.984.4 Ethernet performance monitoring history data 3"
        ::= { zxGponOmciEthHisStatsEntry 32 }

--GEM history data
    zxGponOmciGEMHisStatsTable    OBJECT-TYPE
        SYNTAX      SEQUENCE OF ZxGponOmciGEMHisStatsEntry
        MAX-ACCESS  not-accessible
        STATUS      current
        DESCRIPTION
            ""
        REFERENCE   "G.984.4 & G.983.2"
        ::= { zxGponOmciStatistics 22 }

    zxGponOmciGEMHisStatsEntry OBJECT-TYPE
        SYNTAX      ZxGponOmciGEMHisStatsEntry
        MAX-ACCESS  not-accessible
        STATUS      current
        DESCRIPTION
            "It is entry in the zxGponOmciGEMHisStatsTable."
        INDEX   { zxGponOltIndex, zxGponONTIndex, zxGponGemPortIndex }
        ::= { zxGponOmciGEMHisStatsTable 1 }

    ZxGponOmciGEMHisStatsEntry ::=
        SEQUENCE {
            zxGponOmciGEMHisStatsIntervalEndTime               INTEGER,
            zxGponOmciGEMHisStatsThresDataId                   INTEGER,
            zxGponOmciGEMHisStatsLostPkts                      Unsigned32,
            zxGponOmciGEMHisStatsMisInsertedPkts               Unsigned32,
            zxGponOmciGEMHisStatsRxPkts                        Counter64,
            zxGponOmciGEMHisStatsRxBlocks                      Counter64,
            zxGponOmciGEMHisStatsTxBlocks                      Counter64,
            zxGponOmciGEMHisStatsImpairedBlocks                Unsigned32,
            zxGponOmciGEMHisStatsEntryStatus                   RowStatus
        }

    zxGponOmciGEMHisStatsIntervalEndTime OBJECT-TYPE
        SYNTAX      INTEGER
        MAX-ACCESS  read-only
        STATUS      current
        DESCRIPTION
        ""
        REFERENCE   "G.984.4 & G.983.2"
        ::= { zxGponOmciGEMHisStatsEntry 1 }

    zxGponOmciGEMHisStatsThresDataId OBJECT-TYPE
        SYNTAX      INTEGER
        MAX-ACCESS  read-only
        STATUS      current
        DESCRIPTION
        ""
        REFERENCE   "G.984.4 & G.983.2"
        ::= { zxGponOmciGEMHisStatsEntry 2 }

    zxGponOmciGEMHisStatsLostPkts OBJECT-TYPE
        SYNTAX      Unsigned32
        MAX-ACCESS  read-only
        STATUS      current
        DESCRIPTION
        ""
        REFERENCE   "G.984.4 & G.983.2"
        ::= { zxGponOmciGEMHisStatsEntry 3 }

    zxGponOmciGEMHisStatsMisInsertedPkts OBJECT-TYPE
        SYNTAX      Unsigned32
        MAX-ACCESS  read-only
        STATUS      current
        DESCRIPTION
        ""
        REFERENCE   "G.984.4 & G.983.2"
        ::= { zxGponOmciGEMHisStatsEntry 4 }

    zxGponOmciGEMHisStatsRxPkts OBJECT-TYPE
        SYNTAX      Counter64
        MAX-ACCESS  read-only
        STATUS      current
        DESCRIPTION
        ""
        REFERENCE   "G.984.4 & G.983.2"
        ::= { zxGponOmciGEMHisStatsEntry 6 }

    zxGponOmciGEMHisStatsRxBlocks OBJECT-TYPE
        SYNTAX      Counter64
        MAX-ACCESS  read-only
        STATUS      current
        DESCRIPTION
        ""
        REFERENCE   "G.984.4 & G.983.2"
        ::= { zxGponOmciGEMHisStatsEntry 7 }

    zxGponOmciGEMHisStatsTxBlocks OBJECT-TYPE
        SYNTAX      Counter64
        MAX-ACCESS  read-only
        STATUS      current
        DESCRIPTION
        ""
        REFERENCE   "G.984.4 & G.983.2"
        ::= { zxGponOmciGEMHisStatsEntry 8 }

    zxGponOmciGEMHisStatsImpairedBlocks OBJECT-TYPE
        SYNTAX      Unsigned32
        MAX-ACCESS  read-only
        STATUS      current
        DESCRIPTION
        ""
        REFERENCE   "G.984.4 & G.983.2"
        ::= { zxGponOmciGEMHisStatsEntry 9 }

    zxGponOmciGEMHisStatsEntryStatus OBJECT-TYPE
        SYNTAX      RowStatus
        MAX-ACCESS  read-only
        STATUS      current
        DESCRIPTION
        "This attribute specifies the action of this interworking."
        REFERENCE   "G.984.4 & G.983.2"
        ::= { zxGponOmciGEMHisStatsEntry 10 }

--UNI bridge port history statistics
    zxGponOmciUNIBridgePortHisStatsTable    OBJECT-TYPE
        SYNTAX      SEQUENCE OF ZxGponOmciUNIBridgePortHisStatsEntry
        MAX-ACCESS  not-accessible
        STATUS      current
        DESCRIPTION
            ""
        REFERENCE   "G.984.4 & G.983.2"
        ::= { zxGponOmciStatistics 23 }

    zxGponOmciUNIBridgePortHisStatsEntry OBJECT-TYPE
        SYNTAX      ZxGponOmciUNIBridgePortHisStatsEntry
        MAX-ACCESS  not-accessible
        STATUS      current
        DESCRIPTION
            "It is entry in the zxGponOmciUNIBridgePortHisStatsTable."
        INDEX   { zxGponOltIndex, zxGponONTIndex, zxGponUNIIndex }
        ::= { zxGponOmciUNIBridgePortHisStatsTable 1 }

    ZxGponOmciUNIBridgePortHisStatsEntry ::=
        SEQUENCE {
            zxGponOmciUNIBridgePortHisStatsIntervalEndTime               INTEGER,
            zxGponOmciUNIBridgePortHisStatsThresDataId                   INTEGER,
            zxGponOmciUNIBridgePortHisStatsForwardFrameCnt               Unsigned32,
            zxGponOmciUNIBridgePortHisStatsDelayExceedDiscardCnt         Unsigned32,
            zxGponOmciUNIBridgePortHisStatsMTUExceedDiscardCnt           Unsigned32,
            zxGponOmciUNIBridgePortHisStatsRxFrameCnt                    Unsigned32,
            zxGponOmciUNIBridgePortHisStatsRxDiscardCnt                  Unsigned32,
            zxGponOmciUNIBridgePortHisStatsEntryStatus                   RowStatus
        }

    zxGponOmciUNIBridgePortHisStatsIntervalEndTime OBJECT-TYPE
        SYNTAX      INTEGER
        MAX-ACCESS  read-only
        STATUS      current
        DESCRIPTION
        ""
        REFERENCE   "G.984.4 & G.983.2"
        ::= { zxGponOmciUNIBridgePortHisStatsEntry 1 }

    zxGponOmciUNIBridgePortHisStatsThresDataId OBJECT-TYPE
        SYNTAX      INTEGER
        MAX-ACCESS  read-only
        STATUS      current
        DESCRIPTION
        ""
        REFERENCE   "G.984.4 & G.983.2"
        ::= { zxGponOmciUNIBridgePortHisStatsEntry 2 }

    zxGponOmciUNIBridgePortHisStatsForwardFrameCnt OBJECT-TYPE
        SYNTAX      Unsigned32
        MAX-ACCESS  read-only
        STATUS      current
        DESCRIPTION
        ""
        REFERENCE   "G.984.4 & G.983.2"
        ::= { zxGponOmciUNIBridgePortHisStatsEntry 3 }

    zxGponOmciUNIBridgePortHisStatsDelayExceedDiscardCnt OBJECT-TYPE
        SYNTAX      Unsigned32
        MAX-ACCESS  read-only
        STATUS      current
        DESCRIPTION
        ""
        REFERENCE   "G.984.4 & G.983.2"
        ::= { zxGponOmciUNIBridgePortHisStatsEntry 4 }

    zxGponOmciUNIBridgePortHisStatsMTUExceedDiscardCnt OBJECT-TYPE
        SYNTAX      Unsigned32
        MAX-ACCESS  read-only
        STATUS      current
        DESCRIPTION
        ""
        REFERENCE   "G.984.4 & G.983.2"
        ::= { zxGponOmciUNIBridgePortHisStatsEntry 5 }

    zxGponOmciUNIBridgePortHisStatsRxFrameCnt OBJECT-TYPE
        SYNTAX      Unsigned32
        MAX-ACCESS  read-only
        STATUS      current
        DESCRIPTION
        ""
        REFERENCE   "G.984.4 & G.983.2"
        ::= { zxGponOmciUNIBridgePortHisStatsEntry 6 }

    zxGponOmciUNIBridgePortHisStatsRxDiscardCnt OBJECT-TYPE
        SYNTAX      Unsigned32
        MAX-ACCESS  read-only
        STATUS      current
        DESCRIPTION
        ""
        REFERENCE   "G.984.4 & G.983.2"
        ::= { zxGponOmciUNIBridgePortHisStatsEntry 7 }

    zxGponOmciUNIBridgePortHisStatsEntryStatus OBJECT-TYPE
        SYNTAX      RowStatus
        MAX-ACCESS  read-only
        STATUS      current
        DESCRIPTION
        ""
        REFERENCE   "G.984.4 & G.983.2"
        ::= { zxGponOmciUNIBridgePortHisStatsEntry 8 }

--Flow bridge port history statistics
    zxGponOmciFlowBridgePortHisStatsTable    OBJECT-TYPE
        SYNTAX      SEQUENCE OF ZxGponOmciFlowBridgePortHisStatsEntry
        MAX-ACCESS  not-accessible
        STATUS      current
        DESCRIPTION
            ""
        REFERENCE   "G.984.4 & G.983.2"
        ::= { zxGponOmciStatistics 24 }

    zxGponOmciFlowBridgePortHisStatsEntry OBJECT-TYPE
        SYNTAX      ZxGponOmciFlowBridgePortHisStatsEntry
        MAX-ACCESS  not-accessible
        STATUS      current
        DESCRIPTION
            "It is entry in the zxGponOmciFlowBridgePortHisStatsTable."
        INDEX   { zxGponOltIndex, zxGponONTIndex, zxGponFlowIndex }
        ::= { zxGponOmciFlowBridgePortHisStatsTable 1 }

    ZxGponOmciFlowBridgePortHisStatsEntry ::=
        SEQUENCE {
            zxGponOmciFlowBridgePortHisStatsIntervalEndTime               INTEGER,
            zxGponOmciFlowBridgePortHisStatsThresDataId                   INTEGER,
            zxGponOmciFlowBridgePortHisStatsForwardFrameCnt               Unsigned32,
            zxGponOmciFlowBridgePortHisStatsDelayExceedDiscardCnt         Unsigned32,
            zxGponOmciFlowBridgePortHisStatsMTUExceedDiscardCnt           Unsigned32,
            zxGponOmciFlowBridgePortHisStatsRxFrameCnt                    Unsigned32,
            zxGponOmciFlowBridgePortHisStatsRxDiscardCnt                  Unsigned32,
            zxGponOmciFlowBridgePortHisStatsEntryStatus                   RowStatus
        }

    zxGponOmciFlowBridgePortHisStatsIntervalEndTime OBJECT-TYPE
        SYNTAX      INTEGER
        MAX-ACCESS  read-only
        STATUS      current
        DESCRIPTION
        ""
        REFERENCE   "G.984.4 & G.983.2"
        ::= { zxGponOmciFlowBridgePortHisStatsEntry 1 }

    zxGponOmciFlowBridgePortHisStatsThresDataId OBJECT-TYPE
        SYNTAX      INTEGER
        MAX-ACCESS  read-only
        STATUS      current
        DESCRIPTION
        ""
        REFERENCE   "G.984.4 & G.983.2"
        ::= { zxGponOmciFlowBridgePortHisStatsEntry 2 }

    zxGponOmciFlowBridgePortHisStatsForwardFrameCnt OBJECT-TYPE
        SYNTAX      Unsigned32
        MAX-ACCESS  read-only
        STATUS      current
        DESCRIPTION
        ""
        REFERENCE   "G.984.4 & G.983.2"
        ::= { zxGponOmciFlowBridgePortHisStatsEntry 3 }

    zxGponOmciFlowBridgePortHisStatsDelayExceedDiscardCnt OBJECT-TYPE
        SYNTAX      Unsigned32
        MAX-ACCESS  read-only
        STATUS      current
        DESCRIPTION
        ""
        REFERENCE   "G.984.4 & G.983.2"
        ::= { zxGponOmciFlowBridgePortHisStatsEntry 4 }

    zxGponOmciFlowBridgePortHisStatsMTUExceedDiscardCnt OBJECT-TYPE
        SYNTAX      Unsigned32
        MAX-ACCESS  read-only
        STATUS      current
        DESCRIPTION
        ""
        REFERENCE   "G.984.4 & G.983.2"
        ::= { zxGponOmciFlowBridgePortHisStatsEntry 5 }

    zxGponOmciFlowBridgePortHisStatsRxFrameCnt OBJECT-TYPE
        SYNTAX      Unsigned32
        MAX-ACCESS  read-only
        STATUS      current
        DESCRIPTION
        ""
        REFERENCE   "G.984.4 & G.983.2"
        ::= { zxGponOmciFlowBridgePortHisStatsEntry 6 }

    zxGponOmciFlowBridgePortHisStatsRxDiscardCnt OBJECT-TYPE
        SYNTAX      Unsigned32
        MAX-ACCESS  read-only
        STATUS      current
        DESCRIPTION
        ""
        REFERENCE   "G.984.4 & G.983.2"
        ::= { zxGponOmciFlowBridgePortHisStatsEntry 7 }

    zxGponOmciFlowBridgePortHisStatsEntryStatus OBJECT-TYPE
        SYNTAX      RowStatus
        MAX-ACCESS  read-only
        STATUS      current
        DESCRIPTION
        ""
        REFERENCE   "G.984.4 & G.983.2"
        ::= { zxGponOmciFlowBridgePortHisStatsEntry 8 }

--History statistics
    zxGponOmciEthHisStatsUpTable    OBJECT-TYPE
        SYNTAX      SEQUENCE OF ZxGponOmciEthHisStatsUpEntry
        MAX-ACCESS  not-accessible
        STATUS      current
        DESCRIPTION
            ""
        REFERENCE   "9.3.30    Ethernet frame performance monitoring history data upstream"
        ::= { zxGponOmciStatistics 26 }

    zxGponOmciEthHisStatsUpEntry OBJECT-TYPE
        SYNTAX      ZxGponOmciEthHisStatsUpEntry
        MAX-ACCESS  not-accessible
        STATUS      current
        DESCRIPTION
            "It is entry in the zxGponOmciEthHisStatsUpTable."
        INDEX   { zxGponOltIndex, zxGponONTIndex, zxGponUNIIndex }
        ::= { zxGponOmciEthHisStatsUpTable 1 }

    ZxGponOmciEthHisStatsUpEntry ::=
        SEQUENCE {
            zxGponOmciEthHisStatsUpIntervalEndTime              INTEGER,
            zxGponOmciEthHisStatsUpThresDataId                  INTEGER,
            zxGponOmciEthHisStatsUpDropEvents                   Unsigned32,
            zxGponOmciEthHisStatsUpOctets                       Unsigned32,
            zxGponOmciEthHisStatsUpPkts                         Unsigned32,
            zxGponOmciEthHisStatsUpBroadcastPkts                Unsigned32,
            zxGponOmciEthHisStatsUpMulticastPkts                Unsigned32,
            zxGponOmciEthHisStatsUpCRCErrPkts                   Unsigned32,
            zxGponOmciEthHisStatsUpUndersizePkts                Unsigned32,
            zxGponOmciEthHisStatsUpOversizePkts                 Unsigned32,
            zxGponOmciEthHisStatsUp64OctetsPkts                 Unsigned32,
            zxGponOmciEthHisStatsUp65To127OctetsPkts            Unsigned32,
            zxGponOmciEthHisStatsUp128To255OctetsPkts           Unsigned32,
            zxGponOmciEthHisStatsUp256To511OctetsPkts           Unsigned32,
            zxGponOmciEthHisStatsUp512To1023OctetsPkts          Unsigned32,
            zxGponOmciEthHisStatsUp1024To1518OctetsPkts         Unsigned32,
            zxGponOmciEthHisStatsUpEntryStatus                  RowStatus

        }

    zxGponOmciEthHisStatsUpIntervalEndTime OBJECT-TYPE
        SYNTAX      INTEGER
        MAX-ACCESS  read-only
        STATUS      current
        DESCRIPTION
        ""
        REFERENCE   "G.984.4"
        ::= { zxGponOmciEthHisStatsUpEntry 1 }

    zxGponOmciEthHisStatsUpThresDataId OBJECT-TYPE
        SYNTAX      INTEGER
        MAX-ACCESS  read-only
        STATUS      current
        DESCRIPTION
        ""
        REFERENCE   "G.984.4"
        ::= { zxGponOmciEthHisStatsUpEntry 2 }

    zxGponOmciEthHisStatsUpDropEvents OBJECT-TYPE
        SYNTAX      Unsigned32
        MAX-ACCESS  read-only
        STATUS      current
        DESCRIPTION
        ""
        REFERENCE   ""
        ::= { zxGponOmciEthHisStatsUpEntry 3 }

    zxGponOmciEthHisStatsUpOctets OBJECT-TYPE
        SYNTAX      Unsigned32
        MAX-ACCESS  read-only
        STATUS      current
        DESCRIPTION
        ""
        REFERENCE   ""
        ::= { zxGponOmciEthHisStatsUpEntry 4 }

    zxGponOmciEthHisStatsUpPkts OBJECT-TYPE
        SYNTAX      Unsigned32
        MAX-ACCESS  read-only
        STATUS      current
        DESCRIPTION
        ""
        REFERENCE   ""
        ::= { zxGponOmciEthHisStatsUpEntry 5 }

    zxGponOmciEthHisStatsUpBroadcastPkts OBJECT-TYPE
        SYNTAX      Unsigned32
        MAX-ACCESS  read-only
        STATUS      current
        DESCRIPTION
        ""
        REFERENCE   ""
        ::= { zxGponOmciEthHisStatsUpEntry 6 }

    zxGponOmciEthHisStatsUpMulticastPkts OBJECT-TYPE
        SYNTAX      Unsigned32
        MAX-ACCESS  read-only
        STATUS      current
        DESCRIPTION
        ""
        REFERENCE   ""
        ::= { zxGponOmciEthHisStatsUpEntry 7 }

    zxGponOmciEthHisStatsUpCRCErrPkts OBJECT-TYPE
        SYNTAX      Unsigned32
        MAX-ACCESS  read-only
        STATUS      current
        DESCRIPTION
        ""
        REFERENCE   ""
        ::= { zxGponOmciEthHisStatsUpEntry 8 }

    zxGponOmciEthHisStatsUpUndersizePkts OBJECT-TYPE
        SYNTAX      Unsigned32
        MAX-ACCESS  read-only
        STATUS      current
        DESCRIPTION
        ""
        REFERENCE   ""
        ::= { zxGponOmciEthHisStatsUpEntry 9 }

    zxGponOmciEthHisStatsUpOversizePkts OBJECT-TYPE
        SYNTAX      Unsigned32
        MAX-ACCESS  read-only
        STATUS      current
        DESCRIPTION
        ""
        REFERENCE   ""
        ::= { zxGponOmciEthHisStatsUpEntry 10 }

    zxGponOmciEthHisStatsUp64OctetsPkts OBJECT-TYPE
        SYNTAX      Unsigned32
        MAX-ACCESS  read-only
        STATUS      current
        DESCRIPTION
        ""
        REFERENCE   ""
        ::= { zxGponOmciEthHisStatsUpEntry 11 }

    zxGponOmciEthHisStatsUp65To127OctetsPkts OBJECT-TYPE
        SYNTAX      Unsigned32
        MAX-ACCESS  read-only
        STATUS      current
        DESCRIPTION
        ""
        REFERENCE   ""
        ::= { zxGponOmciEthHisStatsUpEntry 12 }

    zxGponOmciEthHisStatsUp128To255OctetsPkts OBJECT-TYPE
        SYNTAX      Unsigned32
        MAX-ACCESS  read-only
        STATUS      current
        DESCRIPTION
        ""
        REFERENCE   ""
        ::= { zxGponOmciEthHisStatsUpEntry 13 }

    zxGponOmciEthHisStatsUp256To511OctetsPkts OBJECT-TYPE
        SYNTAX      Unsigned32
        MAX-ACCESS  read-only
        STATUS      current
        DESCRIPTION
        ""
        REFERENCE   ""
        ::= { zxGponOmciEthHisStatsUpEntry 14 }

    zxGponOmciEthHisStatsUp512To1023OctetsPkts OBJECT-TYPE
        SYNTAX      Unsigned32
        MAX-ACCESS  read-only
        STATUS      current
        DESCRIPTION
        ""
        REFERENCE   ""
        ::= { zxGponOmciEthHisStatsUpEntry 15 }

    zxGponOmciEthHisStatsUp1024To1518OctetsPkts OBJECT-TYPE
        SYNTAX      Unsigned32
        MAX-ACCESS  read-only
        STATUS      current
        DESCRIPTION
        ""
        REFERENCE   ""
        ::= { zxGponOmciEthHisStatsUpEntry 16 }

    zxGponOmciEthHisStatsUpEntryStatus OBJECT-TYPE
        SYNTAX      RowStatus
        MAX-ACCESS  read-only
        STATUS      current
        DESCRIPTION
        ""
        REFERENCE   ""
        ::= { zxGponOmciEthHisStatsUpEntry 30 }

--9.3.30    Ethernet frame performance monitoring history data downstream
    zxGponOmciEthHisStatsDownTable    OBJECT-TYPE
        SYNTAX      SEQUENCE OF ZxGponOmciEthHisStatsDownEntry
        MAX-ACCESS  not-accessible
        STATUS      current
        DESCRIPTION
            ""
        REFERENCE   "9.3.31    Ethernet frame performance monitoring history data downstream"
        ::= { zxGponOmciStatistics 27 }

    zxGponOmciEthHisStatsDownEntry OBJECT-TYPE
        SYNTAX      ZxGponOmciEthHisStatsDownEntry
        MAX-ACCESS  not-accessible
        STATUS      current
        DESCRIPTION
            "It is entry in the zxGponOmciEthHisStatsDownTable."
        INDEX   { zxGponOltIndex, zxGponONTIndex, zxGponUNIIndex }
        ::= { zxGponOmciEthHisStatsDownTable 1 }

    ZxGponOmciEthHisStatsDownEntry ::=
        SEQUENCE {
            zxGponOmciEthHisStatsDownIntervalEndTime              INTEGER,
            zxGponOmciEthHisStatsDownThresDataId                  INTEGER,
            zxGponOmciEthHisStatsDownDropEvents                   Unsigned32,
            zxGponOmciEthHisStatsDownOctets                       Unsigned32,
            zxGponOmciEthHisStatsDownPkts                         Unsigned32,
            zxGponOmciEthHisStatsDownBroadcastPkts                Unsigned32,
            zxGponOmciEthHisStatsDownMulticastPkts                Unsigned32,
            zxGponOmciEthHisStatsDownCRCErrPkts                   Unsigned32,
            zxGponOmciEthHisStatsDownUndersizePkts                Unsigned32,
            zxGponOmciEthHisStatsDownOversizePkts                 Unsigned32,
            zxGponOmciEthHisStatsDown64OctetsPkts                 Unsigned32,
            zxGponOmciEthHisStatsDown65To127OctetsPkts            Unsigned32,
            zxGponOmciEthHisStatsDown128To255OctetsPkts           Unsigned32,
            zxGponOmciEthHisStatsDown256To511OctetsPkts           Unsigned32,
            zxGponOmciEthHisStatsDown512To1023OctetsPkts          Unsigned32,
            zxGponOmciEthHisStatsDown1024To1518OctetsPkts         Unsigned32,
            zxGponOmciEthHisStatsDownEntryStatus                  RowStatus

        }

    zxGponOmciEthHisStatsDownIntervalEndTime OBJECT-TYPE
        SYNTAX      INTEGER
        MAX-ACCESS  read-only
        STATUS      current
        DESCRIPTION
        ""
        REFERENCE   "G.984.4"
        ::= { zxGponOmciEthHisStatsDownEntry 1 }

    zxGponOmciEthHisStatsDownThresDataId OBJECT-TYPE
        SYNTAX      INTEGER
        MAX-ACCESS  read-only
        STATUS      current
        DESCRIPTION
        ""
        REFERENCE   "G.984.4"
        ::= { zxGponOmciEthHisStatsDownEntry 2 }

    zxGponOmciEthHisStatsDownDropEvents OBJECT-TYPE
        SYNTAX      Unsigned32
        MAX-ACCESS  read-only
        STATUS      current
        DESCRIPTION
        ""
        REFERENCE   ""
        ::= { zxGponOmciEthHisStatsDownEntry 3 }

    zxGponOmciEthHisStatsDownOctets OBJECT-TYPE
        SYNTAX      Unsigned32
        MAX-ACCESS  read-only
        STATUS      current
        DESCRIPTION
        ""
        REFERENCE   ""
        ::= { zxGponOmciEthHisStatsDownEntry 4 }

    zxGponOmciEthHisStatsDownPkts OBJECT-TYPE
        SYNTAX      Unsigned32
        MAX-ACCESS  read-only
        STATUS      current
        DESCRIPTION
        ""
        REFERENCE   ""
        ::= { zxGponOmciEthHisStatsDownEntry 5 }

    zxGponOmciEthHisStatsDownBroadcastPkts OBJECT-TYPE
        SYNTAX      Unsigned32
        MAX-ACCESS  read-only
        STATUS      current
        DESCRIPTION
        ""
        REFERENCE   ""
        ::= { zxGponOmciEthHisStatsDownEntry 6 }

    zxGponOmciEthHisStatsDownMulticastPkts OBJECT-TYPE
        SYNTAX      Unsigned32
        MAX-ACCESS  read-only
        STATUS      current
        DESCRIPTION
        ""
        REFERENCE   ""
        ::= { zxGponOmciEthHisStatsDownEntry 7 }

    zxGponOmciEthHisStatsDownCRCErrPkts OBJECT-TYPE
        SYNTAX      Unsigned32
        MAX-ACCESS  read-only
        STATUS      current
        DESCRIPTION
        ""
        REFERENCE   ""
        ::= { zxGponOmciEthHisStatsDownEntry 8 }

    zxGponOmciEthHisStatsDownUndersizePkts OBJECT-TYPE
        SYNTAX      Unsigned32
        MAX-ACCESS  read-only
        STATUS      current
        DESCRIPTION
        ""
        REFERENCE   ""
        ::= { zxGponOmciEthHisStatsDownEntry 9 }

    zxGponOmciEthHisStatsDownOversizePkts OBJECT-TYPE
        SYNTAX      Unsigned32
        MAX-ACCESS  read-only
        STATUS      current
        DESCRIPTION
        ""
        REFERENCE   ""
        ::= { zxGponOmciEthHisStatsDownEntry 10 }

    zxGponOmciEthHisStatsDown64OctetsPkts OBJECT-TYPE
        SYNTAX      Unsigned32
        MAX-ACCESS  read-only
        STATUS      current
        DESCRIPTION
        ""
        REFERENCE   ""
        ::= { zxGponOmciEthHisStatsDownEntry 11 }

    zxGponOmciEthHisStatsDown65To127OctetsPkts OBJECT-TYPE
        SYNTAX      Unsigned32
        MAX-ACCESS  read-only
        STATUS      current
        DESCRIPTION
        ""
        REFERENCE   ""
        ::= { zxGponOmciEthHisStatsDownEntry 12 }

    zxGponOmciEthHisStatsDown128To255OctetsPkts OBJECT-TYPE
        SYNTAX      Unsigned32
        MAX-ACCESS  read-only
        STATUS      current
        DESCRIPTION
        ""
        REFERENCE   ""
        ::= { zxGponOmciEthHisStatsDownEntry 13 }

    zxGponOmciEthHisStatsDown256To511OctetsPkts OBJECT-TYPE
        SYNTAX      Unsigned32
        MAX-ACCESS  read-only
        STATUS      current
        DESCRIPTION
        ""
        REFERENCE   ""
        ::= { zxGponOmciEthHisStatsDownEntry 14 }

    zxGponOmciEthHisStatsDown512To1023OctetsPkts OBJECT-TYPE
        SYNTAX      Unsigned32
        MAX-ACCESS  read-only
        STATUS      current
        DESCRIPTION
        ""
        REFERENCE   ""
        ::= { zxGponOmciEthHisStatsDownEntry 15 }

    zxGponOmciEthHisStatsDown1024To1518OctetsPkts OBJECT-TYPE
        SYNTAX      Unsigned32
        MAX-ACCESS  read-only
        STATUS      current
        DESCRIPTION
        ""
        REFERENCE   ""
        ::= { zxGponOmciEthHisStatsDownEntry 16 }

    zxGponOmciEthHisStatsDownEntryStatus OBJECT-TYPE
        SYNTAX      RowStatus
        MAX-ACCESS  read-only
        STATUS      current
        DESCRIPTION
        ""
        REFERENCE   ""
        ::= { zxGponOmciEthHisStatsDownEntry 30 }

--FEC History Statics G984.4_9.2.11
    zxGponOmciFecHisStatsTable    OBJECT-TYPE
        SYNTAX      SEQUENCE OF ZxGponOmciFecHisStatsEntry
        MAX-ACCESS  not-accessible
        STATUS      current
        DESCRIPTION
            "FEC performance monitoring history data."
        REFERENCE   "9.2.11  FEC performance monitoring history data."
        ::= { zxGponOmciStatistics 28 }

    zxGponOmciFecHisStatsEntry OBJECT-TYPE
        SYNTAX      ZxGponOmciFecHisStatsEntry
        MAX-ACCESS  not-accessible
        STATUS      current
        DESCRIPTION
            "It is entry in the zxGponOmciFecHisStatsTable."
        INDEX   { zxGponOltIndex, zxGponONTIndex }
        ::= { zxGponOmciFecHisStatsTable 1 }

    ZxGponOmciFecHisStatsEntry ::=
        SEQUENCE {
            zxGponOmciFecHisIntvlEndTime              INTEGER,
            zxGponOmciFecHisThresDataId               INTEGER,
            zxGponOmciFecHisCrctBytes                 Unsigned32,
            zxGponOmciFecHisCrctCodeWords             Unsigned32,
            zxGponOmciFecHisUcrctCodeWords            Unsigned32,
            zxGponOmciFecHisTotalCodeWords            Unsigned32,
            zxGponOmciFecHisFecSeconds                Unsigned32
        }

    zxGponOmciFecHisIntvlEndTime OBJECT-TYPE
        SYNTAX      INTEGER(0..255)
        MAX-ACCESS  read-only
        STATUS      current
        DESCRIPTION
        "This attribute identifies the most recently finished 15-minute
        interval."
        REFERENCE   "G.984.4"
        ::= { zxGponOmciFecHisStatsEntry 1 }

    zxGponOmciFecHisThresDataId OBJECT-TYPE
        SYNTAX      INTEGER(0..65535)
        MAX-ACCESS  read-only
        STATUS      current
        DESCRIPTION
        "This attribute points to an instance of the threshold data 1 managed
         entity that contains PM threshold values. Since no threshold value
         attribute number exceeds 7, a threshold data 2 ME is optional."
        REFERENCE   "G.984.4"
        ::= { zxGponOmciFecHisStatsEntry 2 }

    zxGponOmciFecHisCrctBytes OBJECT-TYPE
        SYNTAX      Unsigned32
        MAX-ACCESS  read-only
        STATUS      current
        DESCRIPTION
        "This attribute counts the number of bytes that were corrected by the
        FEC function."
        REFERENCE   "G.984.4"
        ::= { zxGponOmciFecHisStatsEntry 3 }

    zxGponOmciFecHisCrctCodeWords OBJECT-TYPE
        SYNTAX      Unsigned32
        MAX-ACCESS  read-only
        STATUS      current
        DESCRIPTION
        "This attribute counts the code words that were corrected by the FEC
         function."
        REFERENCE   "G.984.4"
        ::= { zxGponOmciFecHisStatsEntry 4 }

    zxGponOmciFecHisUcrctCodeWords OBJECT-TYPE
        SYNTAX      Unsigned32
        MAX-ACCESS  read-only
        STATUS      current
        DESCRIPTION
        "This attribute counts the code words that were not corrected by
         the FEC function."
        REFERENCE   "G.984.4"
        ::= { zxGponOmciFecHisStatsEntry 5 }

    zxGponOmciFecHisTotalCodeWords OBJECT-TYPE
        SYNTAX      Unsigned32
        MAX-ACCESS  read-only
        STATUS      current
        DESCRIPTION
        "This attribute counts the total received code words."
        REFERENCE   "G.984.4"
        ::= { zxGponOmciFecHisStatsEntry 6 }

    zxGponOmciFecHisFecSeconds OBJECT-TYPE
        SYNTAX      Unsigned32
        MAX-ACCESS  read-only
        STATUS      current
        DESCRIPTION
        "This attribute counts seconds during which there was a forward error
         correction anomaly."
        REFERENCE   "G.984.4"
        ::= { zxGponOmciFecHisStatsEntry 7 }

--CES history data
    zxGponOmciCESHisStatsTable    OBJECT-TYPE
        SYNTAX      SEQUENCE OF ZxGponOmciCESHisStatsEntry
        MAX-ACCESS  not-accessible
        STATUS      current
        DESCRIPTION
            "Performance monitoring history data of Physical path termination point CES UNI."
        REFERENCE
           "G.984.4, CES physical interface performance monitoring history data,
        Pseudowire performance monitoring history data"
        ::= { zxGponOmciStatistics 31 }

    zxGponOmciCESHisStatsEntry    OBJECT-TYPE
        SYNTAX      ZxGponOmciCESHisStatsEntry
        MAX-ACCESS  not-accessible
        STATUS      current
        DESCRIPTION
            "It is entry in the zxGponOmciCESStatsTable."
        INDEX   { zxGponOltIndex, zxGponONTIndex, zxGponUNIIndex }
        ::= { zxGponOmciCESHisStatsTable 1 }

    ZxGponOmciCESHisStatsEntry ::=
        SEQUENCE {
            zxGponOmciCESHisStatsIntervalEndTime               INTEGER,
            zxGponOmciCESHisStatsThresholdDataId               INTEGER,
            zxGponOmciCESHisStatsDownPkts                      Unsigned32,
            zxGponOmciCESHisStatsUpPkts                        Unsigned32,
            zxGponOmciCESHisStatsDownMissingPkts               Unsigned32,
            zxGponOmciCESHisStatsDownReorderedPkts             Unsigned32,
            zxGponOmciCESHisStatsDownMisorderedPkts            Unsigned32,
            zxGponOmciCESHisStatsDownBufUnderrunOrOverrunPkts  Unsigned32,
            zxGponOmciCESHisStatsDownMalformedPkts             Unsigned32,
            zxGponOmciCESHisStatsDownStrayPkts                 Unsigned32,
            zxGponOmciCESHisStatsDownRemotePktLoss             Unsigned32,
            zxGponOmciCESHisStatsUpTDMLbitPkts                 Unsigned32,
            zxGponOmciCESHisStatsDownErrSeconds                Unsigned32,
            zxGponOmciCESHisStatsDownSeverelyErrSeconds        Unsigned32,
            zxGponOmciCESHisStatsDownUnavailableSeconds        Unsigned32,
--            zxGponOmciCESHisStatsUpErrSeconds                  Unsigned32,
--            zxGponOmciCESHisStatsUpSeverelyErrSeconds          Unsigned32,
--            zxGponOmciCESHisStatsUpBurstErrSeconds             Unsigned32,
--            zxGponOmciCESHisStatsUpUnavailableSeconds          Unsigned32,
--            zxGponOmciCESHisStatsUpControlledSlipSeconds       Unsigned32,
            zxGponOmciCESHisStatsEntryStatus                   RowStatus
        }

    zxGponOmciCESHisStatsIntervalEndTime   OBJECT-TYPE
        SYNTAX      INTEGER
        MAX-ACCESS  read-only
        STATUS      current
        DESCRIPTION
        ""
        REFERENCE   "G.984.4, Pseudowire performance monitoring history data"
        ::= { zxGponOmciCESHisStatsEntry 1 }

    zxGponOmciCESHisStatsThresholdDataId   OBJECT-TYPE
        SYNTAX      INTEGER
        MAX-ACCESS  read-only
        STATUS      current
        DESCRIPTION
        ""
        REFERENCE   "G.984.4, Pseudowire performance monitoring history data"
        ::= { zxGponOmciCESHisStatsEntry 2 }

    zxGponOmciCESHisStatsDownPkts   OBJECT-TYPE
        SYNTAX      Unsigned32
        MAX-ACCESS  read-only
        STATUS      current
        DESCRIPTION
        ""
        REFERENCE   "G.984.4, Pseudowire performance monitoring history data"
        ::= { zxGponOmciCESHisStatsEntry 3 }

    zxGponOmciCESHisStatsUpPkts   OBJECT-TYPE
        SYNTAX      Unsigned32
        MAX-ACCESS  read-only
        STATUS      current
        DESCRIPTION
        ""
        REFERENCE   "G.984.4, Pseudowire performance monitoring history data"
        ::= { zxGponOmciCESHisStatsEntry 4 }

    zxGponOmciCESHisStatsDownMissingPkts   OBJECT-TYPE
        SYNTAX      Unsigned32
        MAX-ACCESS  read-only
        STATUS      current
        DESCRIPTION
        ""
        REFERENCE   "G.984.4, Pseudowire performance monitoring history data"
        ::= { zxGponOmciCESHisStatsEntry 5 }

    zxGponOmciCESHisStatsDownReorderedPkts   OBJECT-TYPE
        SYNTAX      Unsigned32
        MAX-ACCESS  read-only
        STATUS      current
        DESCRIPTION
        ""
        REFERENCE   "G.984.4, Pseudowire performance monitoring history data"
        ::= { zxGponOmciCESHisStatsEntry 6 }

    zxGponOmciCESHisStatsDownMisorderedPkts   OBJECT-TYPE
        SYNTAX      Unsigned32
        MAX-ACCESS  read-only
        STATUS      current
        DESCRIPTION
        ""
        REFERENCE   "G.984.4, Pseudowire performance monitoring history data"
        ::= { zxGponOmciCESHisStatsEntry 7 }

    zxGponOmciCESHisStatsDownBufUnderrunOrOverrunPkts   OBJECT-TYPE
        SYNTAX      Unsigned32
        MAX-ACCESS  read-only
        STATUS      current
        DESCRIPTION
        ""
        REFERENCE   "G.984.4, Pseudowire performance monitoring history data"
        ::= { zxGponOmciCESHisStatsEntry 8 }

    zxGponOmciCESHisStatsDownMalformedPkts   OBJECT-TYPE
        SYNTAX      Unsigned32
        MAX-ACCESS  read-only
        STATUS      current
        DESCRIPTION
        ""
        REFERENCE   "G.984.4, Pseudowire performance monitoring history data"
        ::= { zxGponOmciCESHisStatsEntry 9 }

    zxGponOmciCESHisStatsDownStrayPkts   OBJECT-TYPE
        SYNTAX      Unsigned32
        MAX-ACCESS  read-only
        STATUS      current
        DESCRIPTION
        ""
        REFERENCE   "G.984.4, Pseudowire performance monitoring history data"
        ::= { zxGponOmciCESHisStatsEntry 10 }

    zxGponOmciCESHisStatsDownRemotePktLoss   OBJECT-TYPE
        SYNTAX      Unsigned32
        MAX-ACCESS  read-only
        STATUS      current
        DESCRIPTION
        ""
        REFERENCE   "G.984.4, Pseudowire performance monitoring history data"
        ::= { zxGponOmciCESHisStatsEntry 11 }

    zxGponOmciCESHisStatsUpTDMLbitPkts   OBJECT-TYPE
        SYNTAX      Unsigned32
        MAX-ACCESS  read-only
        STATUS      current
        DESCRIPTION
        ""
        REFERENCE   "G.984.4, Pseudowire performance monitoring history data"
        ::= { zxGponOmciCESHisStatsEntry 12 }

    zxGponOmciCESHisStatsDownErrSeconds   OBJECT-TYPE
        SYNTAX      Unsigned32
        MAX-ACCESS  read-only
        STATUS      current
        DESCRIPTION
        ""
        REFERENCE   "G.984.4, Pseudowire performance monitoring history data"
        ::= { zxGponOmciCESHisStatsEntry 13 }

    zxGponOmciCESHisStatsDownSeverelyErrSeconds   OBJECT-TYPE
        SYNTAX      Unsigned32
        MAX-ACCESS  read-only
        STATUS      current
        DESCRIPTION
        ""
        REFERENCE   "G.984.4, Pseudowire performance monitoring history data"
        ::= { zxGponOmciCESHisStatsEntry 14 }

    zxGponOmciCESHisStatsDownUnavailableSeconds   OBJECT-TYPE
        SYNTAX      Unsigned32
        MAX-ACCESS  read-only
        STATUS      current
        DESCRIPTION
        ""
        REFERENCE   "G.984.4, Pseudowire performance monitoring history data"
        ::= { zxGponOmciCESHisStatsEntry 15 }

--    zxGponOmciCESHisStatsUpErrSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 16 }
--
--    zxGponOmciCESHisStatsUpSeverelyErrSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 17 }
--
--    zxGponOmciCESHisStatsUpBurstErrSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 18 }
--
--    zxGponOmciCESHisStatsUpUnavailableSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 19 }
--
--    zxGponOmciCESHisStatsUpControlledSlipSeconds   OBJECT-TYPE
--        SYNTAX      Unsigned32
--        MAX-ACCESS  read-only
--        STATUS      current
--        DESCRIPTION
--        ""
--        REFERENCE   "G.984.4, CES physical interface performance monitoring history data"
--        ::= { zxGponOmciCESHisStatsEntry 20 }

    zxGponOmciCESHisStatsEntryStatus OBJECT-TYPE
        SYNTAX      RowStatus
        MAX-ACCESS  read-only
        STATUS      current
        DESCRIPTION
        ""
        REFERENCE   "G.984.4"
        ::= { zxGponOmciCESHisStatsEntry 25 }


--Private Eth History Statistics
    zxGponOmciPrivateEthHisStatsTable    OBJECT-TYPE
        SYNTAX      SEQUENCE OF ZxGponOmciPrivateEthHisStatsEntry
        MAX-ACCESS  not-accessible
        STATUS      current
        DESCRIPTION
            ""
        REFERENCE   "Vender specific Ethernet performance
                     Ethernet performance monitoring history data 4"
        ::= { zxGponOmciStatistics 41 }

    zxGponOmciPrivateEthHisStatsEntry OBJECT-TYPE
        SYNTAX      ZxGponOmciPrivateEthHisStatsEntry
        MAX-ACCESS  not-accessible
        STATUS      current
        DESCRIPTION
            "It is entry in the zxGponOmciPrivateEthHisStatsTable."
        INDEX   { zxGponOltIndex, zxGponONTIndex, zxGponUNIIndex }
        ::= { zxGponOmciPrivateEthHisStatsTable 1 }

    ZxGponOmciPrivateEthHisStatsEntry ::=
        SEQUENCE {
            zxGponOmciPrivateEthHisStatsIntervalEndTime  INTEGER,
            zxGponOmciPrivateEthHisStatsThresDataId      INTEGER,
            zxGponOmciPrivateEthHisStatsRxBroadcast      Unsigned32,
            zxGponOmciPrivateEthHisStatsRxUnicast        Unsigned32,
            zxGponOmciPrivateEthHisStatsRxMulticast      Unsigned32,
            zxGponOmciPrivateEthHisStatsRxDiscarded      Unsigned32,
            zxGponOmciPrivateEthHisStatsTxBroadcast      Unsigned32,
            zxGponOmciPrivateEthHisStatsTxUnicast        Unsigned32,
            zxGponOmciPrivateEthHisStatsTxMulticast      Unsigned32,
            zxGponOmciPrivateEthHisStatsTxDiscarded      Unsigned32,
            zxGponOmciPrivateEthHisStatsTxPauseFrames    Unsigned32,
            zxGponOmciPrivateEthHisStatsRxPauseFrames    Unsigned32,
            zxGponOmciPrivateEthHisStatsTxErroredOctets  Unsigned32,
            zxGponOmciPrivateEthHisStatsRxErroredOctets  Unsigned32,
            zxGponOmciPrivateEthHisStatsEntryStatus      RowStatus
        }

    zxGponOmciPrivateEthHisStatsIntervalEndTime OBJECT-TYPE
        SYNTAX      INTEGER
        MAX-ACCESS  read-only
        STATUS      current
        DESCRIPTION
        ""
        REFERENCE   "G.984.4"
        ::= { zxGponOmciPrivateEthHisStatsEntry 1 }

    zxGponOmciPrivateEthHisStatsThresDataId OBJECT-TYPE
        SYNTAX      INTEGER
        MAX-ACCESS  read-only
        STATUS      current
        DESCRIPTION
        ""
        REFERENCE   "G.984.4"
        ::= { zxGponOmciPrivateEthHisStatsEntry 2 }

    zxGponOmciPrivateEthHisStatsRxBroadcast OBJECT-TYPE
        SYNTAX      Unsigned32
        MAX-ACCESS  read-only
        STATUS      current
        DESCRIPTION
        ""
        REFERENCE   "G.984.4 Ethernet performance monitoring history data"
        ::= { zxGponOmciPrivateEthHisStatsEntry 3 }

    zxGponOmciPrivateEthHisStatsRxUnicast OBJECT-TYPE
        SYNTAX      Unsigned32
        MAX-ACCESS  read-only
        STATUS      current
        DESCRIPTION
        ""
        REFERENCE   "G.984.4 Ethernet performance monitoring history data"
        ::= { zxGponOmciPrivateEthHisStatsEntry 4 }

    zxGponOmciPrivateEthHisStatsRxMulticast OBJECT-TYPE
        SYNTAX      Unsigned32
        MAX-ACCESS  read-only
        STATUS      current
        DESCRIPTION
        ""
        REFERENCE   "G.984.4 Ethernet performance monitoring history data"
        ::= { zxGponOmciPrivateEthHisStatsEntry 5 }

    zxGponOmciPrivateEthHisStatsRxDiscarded OBJECT-TYPE
        SYNTAX      Unsigned32
        MAX-ACCESS  read-only
        STATUS      current
        DESCRIPTION
        ""
        REFERENCE   "G.984.4 Ethernet performance monitoring history data"
        ::= { zxGponOmciPrivateEthHisStatsEntry 6 }

    zxGponOmciPrivateEthHisStatsTxBroadcast OBJECT-TYPE
        SYNTAX      Unsigned32
        MAX-ACCESS  read-only
        STATUS      current
        DESCRIPTION
        ""
        REFERENCE   "G.984.4 Ethernet performance monitoring history data"
        ::= { zxGponOmciPrivateEthHisStatsEntry 7 }

    zxGponOmciPrivateEthHisStatsTxUnicast OBJECT-TYPE
        SYNTAX      Unsigned32
        MAX-ACCESS  read-only
        STATUS      current
        DESCRIPTION
        ""
        REFERENCE   "G.984.4 Ethernet performance monitoring history data"
        ::= { zxGponOmciPrivateEthHisStatsEntry 8 }

    zxGponOmciPrivateEthHisStatsTxMulticast OBJECT-TYPE
        SYNTAX      Unsigned32
        MAX-ACCESS  read-only
        STATUS      current
        DESCRIPTION
        ""
        REFERENCE   "G.984.4 Ethernet performance monitoring history data"
        ::= { zxGponOmciPrivateEthHisStatsEntry 9 }

    zxGponOmciPrivateEthHisStatsTxDiscarded OBJECT-TYPE
        SYNTAX      Unsigned32
        MAX-ACCESS  read-only
        STATUS      current
        DESCRIPTION
        ""
        REFERENCE   "G.984.4 Ethernet performance monitoring history data"
        ::= { zxGponOmciPrivateEthHisStatsEntry 10 }

    zxGponOmciPrivateEthHisStatsTxPauseFrames OBJECT-TYPE
        SYNTAX      Unsigned32
        MAX-ACCESS  read-only
        STATUS      current
        DESCRIPTION
        ""
        REFERENCE   "G.984.4 Ethernet performance monitoring history data"
        ::= { zxGponOmciPrivateEthHisStatsEntry 11 }

    zxGponOmciPrivateEthHisStatsRxPauseFrames OBJECT-TYPE
        SYNTAX      Unsigned32
        MAX-ACCESS  read-only
        STATUS      current
        DESCRIPTION
        ""
        REFERENCE   "G.984.4 Ethernet performance monitoring history data"
        ::= { zxGponOmciPrivateEthHisStatsEntry 12 }

    zxGponOmciPrivateEthHisStatsTxErroredOctets OBJECT-TYPE
        SYNTAX      Unsigned32
        MAX-ACCESS  read-only
        STATUS      current
        DESCRIPTION
        ""
        REFERENCE   "G.984.4 Ethernet performance monitoring history data"
        ::= { zxGponOmciPrivateEthHisStatsEntry 13 }

    zxGponOmciPrivateEthHisStatsRxErroredOctets OBJECT-TYPE
        SYNTAX      Unsigned32
        MAX-ACCESS  read-only
        STATUS      current
        DESCRIPTION
        ""
        REFERENCE   "G.984.4 Ethernet performance monitoring history data"
        ::= { zxGponOmciPrivateEthHisStatsEntry 14 }

    zxGponOmciPrivateEthHisStatsEntryStatus OBJECT-TYPE
        SYNTAX      RowStatus
        MAX-ACCESS  read-only
        STATUS      current
        DESCRIPTION
        "This attribute specifies the action of this entry."
        REFERENCE   "G.984.4"
        ::= { zxGponOmciPrivateEthHisStatsEntry 20 }


    zxGponOmciStatsThresholdTable    OBJECT-TYPE
        SYNTAX      SEQUENCE OF ZxGponOmciStatsThresholdEntry
        MAX-ACCESS  not-accessible
        STATUS      current
        DESCRIPTION
            ""
        REFERENCE   "G.984.4 Performance monitoring history data"
        ::= { zxGponOmciStatistics 51 }

    zxGponOmciStatsThresholdEntry OBJECT-TYPE
        SYNTAX      ZxGponOmciStatsThresholdEntry
        MAX-ACCESS  not-accessible
        STATUS      current
        DESCRIPTION
            "It is entry in the zxGponOmciStatsThresholdEntry."
        INDEX   {zxGponOmciStatsThresholdType, zxGponOmciStatsThresholdId}
        ::= { zxGponOmciStatsThresholdTable 1 }

    ZxGponOmciStatsThresholdEntry ::=
        SEQUENCE {
            zxGponOmciStatsThresholdType                  INTEGER,
            zxGponOmciStatsThresholdId                    INTEGER,
            zxGponOmciStatsThresholdName                  OCTET STRING,
            zxGponOmciStatsThresValue1                    Unsigned32,
            zxGponOmciStatsThresValue2                    Unsigned32,
            zxGponOmciStatsThresValue3                    Unsigned32,
            zxGponOmciStatsThresValue4                    Unsigned32,
            zxGponOmciStatsThresValue5                    Unsigned32,
            zxGponOmciStatsThresValue6                    Unsigned32,
            zxGponOmciStatsThresValue7                    Unsigned32,
            zxGponOmciStatsThresValue8                    Unsigned32,
            zxGponOmciStatsThresValue9                    Unsigned32,
            zxGponOmciStatsThresValue10                   Unsigned32,
            zxGponOmciStatsThresValue11                   Unsigned32,
            zxGponOmciStatsThresValue12                   Unsigned32,
            zxGponOmciStatsThresValue13                   Unsigned32,
            zxGponOmciStatsThresValue14                   Unsigned32,
            zxGponOmciStatsThresValue15                   Unsigned32,
            zxGponOmciStatsThresValue16                   Unsigned32,
            zxGponOmciStatsThresValue17                   Unsigned32,
            zxGponOmciStatsThresValue18                   Unsigned32,
            zxGponOmciStatsThresValue19                   Unsigned32,
            zxGponOmciStatsThresValue20                   Unsigned32,
            zxGponOmciStatsThresRefCnt                    INTEGER,
            zxGponOmciStatsThresEntryStatus               RowStatus
        }
     zxGponOmciStatsThresholdType OBJECT-TYPE
        SYNTAX      INTEGER
        MAX-ACCESS  not-accessible
        STATUS      current
        DESCRIPTION
            "This attribute indicates the type of OMCI statistics threshold data.
            1 eth
            2 ces
            3 gem port
            4 bridge port

            For eth, there are 19 threshold data as follows:
               fcs-err value1
               excessive-collision value2
               late-collision value3
               too-long value4
               rx-buf-overflow value5
               tx-buf-overflow value6
               single-collision value7
               multi-collisions value8
               sqe value9
               deferred-tx value10
               internal-mac-tx-err value11
               internal-mac-rx-err value12
               carrier-sense-err value13
               alignment-err value14
               pppoe-filtered value15
               drop-events value16
               undersize value17
               fragments value18
               jabbers value19
            For ces, there are 10 threshold data as follows:
               down-missing value1
               down-reordered value2
               down-misordered value3
               down-buffer-underrun-overrun value4
               down-malformed value5
               down-stray value6
               down-remote-loss value7
               down-es value8
               down-ses value9
               down-uas value10
            For gem port, there are 3 threshold data as follows:
               lost-packets value1
               misinserted-packets value2
               impaired-blocks value3
            For bridge port, there are 3 threshold data as follows:
               delay-exceeded-discard value1
               mtu-exceeded-discard value2
               received-and-discarded value3"
        ::= { zxGponOmciStatsThresholdEntry 1}

    zxGponOmciStatsThresholdId OBJECT-TYPE
        SYNTAX      INTEGER
        MAX-ACCESS  not-accessible
        STATUS      current
        DESCRIPTION
        "This attribute provides a unique number for each instance of this managed entity.
        (R, Set-by-create) (mandatory) (4 bytes)"
        ::= { zxGponOmciStatsThresholdEntry 2 }

    zxGponOmciStatsThresholdName OBJECT-TYPE
        SYNTAX      OCTET STRING(SIZE(1..63))
        MAX-ACCESS  read-write
        STATUS      current
        DESCRIPTION
        "This attribute provides a unique name for each instance of this managed entity.
        (R, Set-by-create) (mandatory) (2 bytes)"
        ::= { zxGponOmciStatsThresholdEntry 3 }

    zxGponOmciStatsThresValue1 OBJECT-TYPE
        SYNTAX      Unsigned32
        MAX-ACCESS  read-write
        STATUS      current
        DESCRIPTION
        ""
        REFERENCE   "Threshold data value"
        ::= { zxGponOmciStatsThresholdEntry 4 }

    zxGponOmciStatsThresValue2 OBJECT-TYPE
        SYNTAX      Unsigned32
        MAX-ACCESS  read-write
        STATUS      current
        DESCRIPTION
        ""
        REFERENCE   "Threshold data value"
        ::= { zxGponOmciStatsThresholdEntry 5 }

    zxGponOmciStatsThresValue3 OBJECT-TYPE
        SYNTAX      Unsigned32
        MAX-ACCESS  read-write
        STATUS      current
        DESCRIPTION
        ""
        REFERENCE   "Threshold data value"
        ::= { zxGponOmciStatsThresholdEntry 6 }

    zxGponOmciStatsThresValue4 OBJECT-TYPE
        SYNTAX      Unsigned32
        MAX-ACCESS  read-write
        STATUS      current
        DESCRIPTION
        ""
        REFERENCE   "Threshold data value"
        ::= { zxGponOmciStatsThresholdEntry 7 }

    zxGponOmciStatsThresValue5 OBJECT-TYPE
        SYNTAX      Unsigned32
        MAX-ACCESS  read-write
        STATUS      current
        DESCRIPTION
        ""
        REFERENCE   "Threshold data value"
        ::= { zxGponOmciStatsThresholdEntry 8 }

    zxGponOmciStatsThresValue6 OBJECT-TYPE
        SYNTAX      Unsigned32
        MAX-ACCESS  read-write
        STATUS      current
        DESCRIPTION
        ""
        REFERENCE   "Threshold data value"
        ::= { zxGponOmciStatsThresholdEntry 9 }

    zxGponOmciStatsThresValue7 OBJECT-TYPE
        SYNTAX      Unsigned32
        MAX-ACCESS  read-write
        STATUS      current
        DESCRIPTION
        ""
        REFERENCE   "Threshold data value"
        ::= { zxGponOmciStatsThresholdEntry 10 }

    zxGponOmciStatsThresValue8 OBJECT-TYPE
        SYNTAX      Unsigned32
        MAX-ACCESS  read-write
        STATUS      current
        DESCRIPTION
        ""
        REFERENCE   "Threshold data value"
        ::= { zxGponOmciStatsThresholdEntry 11 }

    zxGponOmciStatsThresValue9 OBJECT-TYPE
        SYNTAX      Unsigned32
        MAX-ACCESS  read-write
        STATUS      current
        DESCRIPTION
        ""
        REFERENCE   "Threshold data value"
        ::= { zxGponOmciStatsThresholdEntry 12 }

    zxGponOmciStatsThresValue10 OBJECT-TYPE
        SYNTAX      Unsigned32
        MAX-ACCESS  read-write
        STATUS      current
        DESCRIPTION
        ""
        REFERENCE   "Threshold data value"
        ::= { zxGponOmciStatsThresholdEntry 13 }

    zxGponOmciStatsThresValue11 OBJECT-TYPE
        SYNTAX      Unsigned32
        MAX-ACCESS  read-write
        STATUS      current
        DESCRIPTION
        ""
        REFERENCE   "Threshold data value"
        ::= { zxGponOmciStatsThresholdEntry 14 }

    zxGponOmciStatsThresValue12 OBJECT-TYPE
        SYNTAX      Unsigned32
        MAX-ACCESS  read-write
        STATUS      current
        DESCRIPTION
        ""
        REFERENCE   "Threshold data value"
        ::= { zxGponOmciStatsThresholdEntry 15 }

    zxGponOmciStatsThresValue13 OBJECT-TYPE
        SYNTAX      Unsigned32
        MAX-ACCESS  read-write
        STATUS      current
        DESCRIPTION
        ""
        REFERENCE   "Threshold data value"
        ::= { zxGponOmciStatsThresholdEntry 16 }

    zxGponOmciStatsThresValue14 OBJECT-TYPE
        SYNTAX      Unsigned32
        MAX-ACCESS  read-write
        STATUS      current
        DESCRIPTION
        ""
        REFERENCE   "Threshold data value"
        ::= { zxGponOmciStatsThresholdEntry 17 }

    zxGponOmciStatsThresValue15 OBJECT-TYPE
        SYNTAX      Unsigned32
        MAX-ACCESS  read-write
        STATUS      current
        DESCRIPTION
        ""
        REFERENCE   "Threshold data value"
        ::= { zxGponOmciStatsThresholdEntry 18 }

    zxGponOmciStatsThresValue16 OBJECT-TYPE
        SYNTAX      Unsigned32
        MAX-ACCESS  read-write
        STATUS      current
        DESCRIPTION
        ""
        REFERENCE   "Threshold data value"
        ::= { zxGponOmciStatsThresholdEntry 19 }

    zxGponOmciStatsThresValue17 OBJECT-TYPE
        SYNTAX      Unsigned32
        MAX-ACCESS  read-write
        STATUS      current
        DESCRIPTION
        ""
        REFERENCE   "Threshold data value"
        ::= { zxGponOmciStatsThresholdEntry 20 }

    zxGponOmciStatsThresValue18 OBJECT-TYPE
        SYNTAX      Unsigned32
        MAX-ACCESS  read-write
        STATUS      current
        DESCRIPTION
        ""
        REFERENCE   "Threshold data value"
        ::= { zxGponOmciStatsThresholdEntry 21 }

    zxGponOmciStatsThresValue19 OBJECT-TYPE
        SYNTAX      Unsigned32
        MAX-ACCESS  read-write
        STATUS      current
        DESCRIPTION
        ""
        REFERENCE   "Threshold data value"
        ::= { zxGponOmciStatsThresholdEntry 22 }

    zxGponOmciStatsThresValue20 OBJECT-TYPE
        SYNTAX      Unsigned32
        MAX-ACCESS  read-write
        STATUS      current
        DESCRIPTION
        ""
        REFERENCE   "Threshold data value"
        ::= { zxGponOmciStatsThresholdEntry 23 }


    zxGponOmciStatsThresRefCnt OBJECT-TYPE
        SYNTAX      INTEGER
        MAX-ACCESS  read-only
        STATUS      current
        DESCRIPTION
        "Forbidden to delete table entry if not equal zero."
        ::= { zxGponOmciStatsThresholdEntry 24 }

    zxGponOmciStatsThresEntryStatus OBJECT-TYPE
        SYNTAX      RowStatus
        MAX-ACCESS  read-write
        STATUS      current
        DESCRIPTION
        "This attribute specifies the action of this entry."
        REFERENCE   "G.984.4"
        ::= { zxGponOmciStatsThresholdEntry 30 }

--------------------------------------------------------------------------
-- zxGponRmUniVoipSrvC15MPerfTable
--------------------------------------------------------------------------
    zxGponRmUniVoipSrvC15MPerfTable    OBJECT-TYPE
        SYNTAX      SEQUENCE OF ZxGponRmUniVoipSrvC15MPerfEntry
        MAX-ACCESS  not-accessible
        STATUS      current
        DESCRIPTION
            "The current 15 minutes performance data table related to
            the VoIP service of POTS UNI."
        REFERENCE   "Private ME"
        ::= { zxGponOmciStatistics 104 }

    zxGponRmUniVoipSrvC15MPerfEntry OBJECT-TYPE
        SYNTAX      ZxGponRmUniVoipSrvC15MPerfEntry
        MAX-ACCESS  not-accessible
        STATUS      current
        DESCRIPTION
            "It is entry in the zxGponRmUniVoipSrvC15MPerfTable."
        INDEX   { zxGponOltIndex, zxGponONTIndex, zxGponUNIIndex }
        ::= { zxGponRmUniVoipSrvC15MPerfTable 1 }

    ZxGponRmUniVoipSrvC15MPerfEntry ::=
        SEQUENCE {
            zxGponUniVoipPerfThreshPrfId               Integer32,
            zxGponUniVoipC15MTxRtpPkts                 Counter32,
            zxGponUniVoipC15MRxRtpPkts                 Counter32,
            zxGponUniVoipC15MAverageDelay              Integer32,
            zxGponUniVoipC15MAverageJitter             Integer32,
            zxGponUniVoipC15MPktLossRatio              Integer32,
            zxGponUniVoipC15MTxMediaDataRate           Gauge32,
            zxGponUniVoipC15MRxMediaDataRate           Gauge32,
            zxGponUniVoipC15MCurCallDuration           Unsigned32,
            zxGponUniVoipC15MTotCallDuration           Unsigned32,
            zxGponUniVoipC15MCallTimes                 Unsigned32,
            zxGponUniVoipPerfRowStatus                 RowStatus
        }

    zxGponUniVoipPerfThreshPrfId OBJECT-TYPE
        SYNTAX      Integer32
        MAX-ACCESS  read-create
        STATUS      current
        DESCRIPTION
            "This attribute is the ID of profile used by threshold
            configuration. According to 'zxGponOmciStatsThresholdId'
            in 'zxGponOmciStatsThresholdTable'. This attribute is not
            supported now."
        REFERENCE   "Private ME"
        ::= { zxGponRmUniVoipSrvC15MPerfEntry 1 }

    zxGponUniVoipC15MTxRtpPkts OBJECT-TYPE
        SYNTAX      Counter32
        MAX-ACCESS  read-only
        STATUS      current
        DESCRIPTION
            "This attribute identifies the total number of transmitted RTP
            packets."
        REFERENCE   "Private ME"
        ::= { zxGponRmUniVoipSrvC15MPerfEntry 2 }

    zxGponUniVoipC15MRxRtpPkts OBJECT-TYPE
        SYNTAX      Counter32
        MAX-ACCESS  read-only
        STATUS      current
        DESCRIPTION
            "This attribute identifies the total number of received RTP
            packets."
        REFERENCE   "Private ME"
        ::= { zxGponRmUniVoipSrvC15MPerfEntry 3 }

    zxGponUniVoipC15MAverageDelay OBJECT-TYPE
        SYNTAX      Integer32(0..65535)
        UNITS       "Milliseconds"
        MAX-ACCESS  read-only
        STATUS      current
        DESCRIPTION
            "This attribute identifies average delay in milliseconds."
        REFERENCE   "Private ME"
        ::= { zxGponRmUniVoipSrvC15MPerfEntry 4 }

    zxGponUniVoipC15MAverageJitter OBJECT-TYPE
        SYNTAX      Integer32(0..65535)
        UNITS       "Milliseconds"
        MAX-ACCESS  read-only
        STATUS      current
        DESCRIPTION
            "This attribute identifies average jitter in milliseconds."
        REFERENCE   "Private ME"
        ::= { zxGponRmUniVoipSrvC15MPerfEntry 5 }

    zxGponUniVoipC15MPktLossRatio OBJECT-TYPE
        SYNTAX      Integer32(0..100)
        UNITS       "percent"
        MAX-ACCESS  read-only
        STATUS      current
        DESCRIPTION
            "This attribute identifies the percent of packets loss."
        REFERENCE   "Private ME"
        ::= { zxGponRmUniVoipSrvC15MPerfEntry 6 }

    zxGponUniVoipC15MTxMediaDataRate OBJECT-TYPE
        SYNTAX      Gauge32
        UNITS       "kbps"
        MAX-ACCESS  read-only
        STATUS      current
        DESCRIPTION
            "This attribute identifies transmitted rate of media data."
        REFERENCE   "Private ME"
        ::= { zxGponRmUniVoipSrvC15MPerfEntry 7 }

    zxGponUniVoipC15MRxMediaDataRate OBJECT-TYPE
        SYNTAX      Gauge32
        UNITS       "kbps"
        MAX-ACCESS  read-only
        STATUS      current
        DESCRIPTION
            "This attribute identifies received rate of media data."
        REFERENCE   "Private ME"
        ::= { zxGponRmUniVoipSrvC15MPerfEntry 8 }

    zxGponUniVoipC15MCurCallDuration OBJECT-TYPE
        SYNTAX      Unsigned32
        UNITS       "Seconds"
        MAX-ACCESS  read-only
        STATUS      current
        DESCRIPTION
            "This attribute identifies the duration of current call in
            seconds."
        REFERENCE   "Private ME"
        ::= { zxGponRmUniVoipSrvC15MPerfEntry 9 }

    zxGponUniVoipC15MTotCallDuration OBJECT-TYPE
        SYNTAX      Unsigned32
        UNITS       "Seconds"
        MAX-ACCESS  read-only
        STATUS      current
        DESCRIPTION
            "This attribute identifies the duration of total calls in
            seconds."
        REFERENCE   "Private ME"
        ::= { zxGponRmUniVoipSrvC15MPerfEntry 10 }

    zxGponUniVoipC15MCallTimes OBJECT-TYPE
        SYNTAX      Unsigned32
        MAX-ACCESS  read-only
        STATUS      current
        DESCRIPTION
            "This attribute identifies the total number of call times."
        REFERENCE   "Private ME"
        ::= { zxGponRmUniVoipSrvC15MPerfEntry 11 }

    zxGponUniVoipPerfRowStatus OBJECT-TYPE
        SYNTAX      RowStatus
        MAX-ACCESS  read-create
        STATUS      current
        DESCRIPTION
            "The status of this conceptual row.

             The supported actions of this conceptual row only include:
             'createAndGo' and 'destroy'.

             To create a row in this table, a manager must
             set this object to createAndGo(4).

             To delete a row in this table, a manager must
             set this object to destroy(6).

             To query this object, always return 1."
        REFERENCE   "Private ME"
        ::= { zxGponRmUniVoipSrvC15MPerfEntry 50 }

--------------------------------------------------------------------------
-- zxGponRmUniVoipSrvH15MPerfTable
--------------------------------------------------------------------------
    zxGponRmUniVoipSrvH15MPerfTable    OBJECT-TYPE
        SYNTAX      SEQUENCE OF ZxGponRmUniVoipSrvH15MPerfEntry
        MAX-ACCESS  not-accessible
        STATUS      current
        DESCRIPTION
            "The 15 minutes interval performance data table related to
             the VoIP service of POTS UNI."
        REFERENCE   "Private ME"
        ::= { zxGponOmciStatistics 105 }

    zxGponRmUniVoipSrvH15MPerfEntry OBJECT-TYPE
        SYNTAX      ZxGponRmUniVoipSrvH15MPerfEntry
        MAX-ACCESS  not-accessible
        STATUS      current
        DESCRIPTION
            "It is entry in the zxGponRmUniVoipSrvH15MPerfTable."
        INDEX   { zxGponOltIndex, zxGponONTIndex, zxGponUNIIndex }
        ::= { zxGponRmUniVoipSrvH15MPerfTable 1 }

    ZxGponRmUniVoipSrvH15MPerfEntry ::=
        SEQUENCE {
            zxGponUniVoipH15MIntvEndTime             Integer32,
            zxGponUniVoipH15MTxRtpPkts               Counter32,
            zxGponUniVoipH15MRxRtpPkts               Counter32,
            zxGponUniVoipH15MAverageDelay            Integer32,
            zxGponUniVoipH15MAverageJitter           Integer32,
            zxGponUniVoipH15MPktLossRatio            Integer32,
            zxGponUniVoipH15MTxMediaDataRate         Gauge32,
            zxGponUniVoipH15MRxMediaDataRate         Gauge32,
            zxGponUniVoipH15MCurCallDuration         Unsigned32,
            zxGponUniVoipH15MTotCallDuration         Unsigned32,
            zxGponUniVoipH15MCallTimes               Unsigned32
        }

    zxGponUniVoipH15MIntvEndTime OBJECT-TYPE
        SYNTAX      Integer32(0..255)
        MAX-ACCESS  read-only
        STATUS      current
        DESCRIPTION
            "This attribute identifies the most recently finished 15-minute
            interval."
        REFERENCE   "Private ME"
        ::= { zxGponRmUniVoipSrvH15MPerfEntry 1 }

    zxGponUniVoipH15MTxRtpPkts OBJECT-TYPE
        SYNTAX      Counter32
        MAX-ACCESS  read-only
        STATUS      current
        DESCRIPTION
            "This attribute identifies the total number of transmitted RTP
            packets."
        REFERENCE   "Private ME"
        ::= { zxGponRmUniVoipSrvH15MPerfEntry 2 }

    zxGponUniVoipH15MRxRtpPkts OBJECT-TYPE
        SYNTAX      Counter32
        MAX-ACCESS  read-only
        STATUS      current
        DESCRIPTION
            "This attribute identifies the total number of received RTP
            packets."
        REFERENCE   "Private ME"
        ::= { zxGponRmUniVoipSrvH15MPerfEntry 3 }

    zxGponUniVoipH15MAverageDelay OBJECT-TYPE
        SYNTAX      Integer32(0..65535)
        UNITS       "Milliseconds"
        MAX-ACCESS  read-only
        STATUS      current
        DESCRIPTION
            "This attribute identifies average delay in milliseconds."
        REFERENCE   "Private ME"
        ::= { zxGponRmUniVoipSrvH15MPerfEntry 4 }

    zxGponUniVoipH15MAverageJitter OBJECT-TYPE
        SYNTAX      Integer32(0..65535)
        UNITS       "Milliseconds"
        MAX-ACCESS  read-only
        STATUS      current
        DESCRIPTION
            "This attribute identifies average jitter in milliseconds."
        REFERENCE   "Private ME"
        ::= { zxGponRmUniVoipSrvH15MPerfEntry 5 }

    zxGponUniVoipH15MPktLossRatio OBJECT-TYPE
        SYNTAX      Integer32(0..100)
        UNITS       "percent"
        MAX-ACCESS  read-only
        STATUS      current
        DESCRIPTION
            "This attribute identifies the percent of packets loss."
        REFERENCE   "Private ME"
        ::= { zxGponRmUniVoipSrvH15MPerfEntry 6 }

    zxGponUniVoipH15MTxMediaDataRate OBJECT-TYPE
        SYNTAX      Gauge32
        UNITS       "kbps"
        MAX-ACCESS  read-only
        STATUS      current
        DESCRIPTION
            "This attribute identifies transmitted rate of media data."
        REFERENCE   "Private ME"
        ::= { zxGponRmUniVoipSrvH15MPerfEntry 7 }

    zxGponUniVoipH15MRxMediaDataRate OBJECT-TYPE
        SYNTAX      Gauge32
        UNITS       "kbps"
        MAX-ACCESS  read-only
        STATUS      current
        DESCRIPTION
            "This attribute identifies received rate of media data."
        REFERENCE   "Private ME"
        ::= { zxGponRmUniVoipSrvH15MPerfEntry 8 }

    zxGponUniVoipH15MCurCallDuration OBJECT-TYPE
        SYNTAX      Unsigned32
        UNITS       "Seconds"
        MAX-ACCESS  read-only
        STATUS      current
        DESCRIPTION
            "This attribute identifies the duration of current call in
            seconds."
        REFERENCE   "Private ME"
        ::= { zxGponRmUniVoipSrvH15MPerfEntry 9 }

    zxGponUniVoipH15MTotCallDuration OBJECT-TYPE
        SYNTAX      Unsigned32
        UNITS       "Seconds"
        MAX-ACCESS  read-only
        STATUS      current
        DESCRIPTION
            "This attribute identifies the duration of total calls in
            seconds."
        REFERENCE   "Private ME"
        ::= { zxGponRmUniVoipSrvH15MPerfEntry 10 }

    zxGponUniVoipH15MCallTimes OBJECT-TYPE
        SYNTAX      Unsigned32
        MAX-ACCESS  read-only
        STATUS      current
        DESCRIPTION
            "This attribute identifies the total number of call times."
        REFERENCE   "Private ME"
        ::= { zxGponRmUniVoipSrvH15MPerfEntry 11 }

--------------------------------------------------------------------------
-- zxGponRmOnuVoipSrvC15MPerfTable
--------------------------------------------------------------------------
    zxGponRmOnuVoipSrvC15MPerfTable    OBJECT-TYPE
        SYNTAX      SEQUENCE OF ZxGponRmOnuVoipSrvC15MPerfEntry
        MAX-ACCESS  not-accessible
        STATUS      current
        DESCRIPTION
            "The current 15 minutes performance data table related to
            the VoIP service of ONU."
        REFERENCE   "Private ME"
        ::= { zxGponOmciStatistics 106 }

    zxGponRmOnuVoipSrvC15MPerfEntry OBJECT-TYPE
        SYNTAX      ZxGponRmOnuVoipSrvC15MPerfEntry
        MAX-ACCESS  not-accessible
        STATUS      current
        DESCRIPTION
            "It is entry in the zxGponRmOnuVoipSrvC15MPerfTable."
        INDEX   { zxGponOltIndex, zxGponONTIndex}
        ::= { zxGponRmOnuVoipSrvC15MPerfTable 1 }

    ZxGponRmOnuVoipSrvC15MPerfEntry ::=
        SEQUENCE {
            zxGponOnuVoipPerfThreshPrfId           Integer32,
            zxGponOnuVoipC15MTxSignalMsg           Counter32,
            zxGponOnuVoipC15MRxSignalMsg           Counter32,
            zxGponOnuVoipC15MReTxSignalMsg         Counter32,
            zxGponOnuVoipC15MLossSignalMsg         Counter32,
            zxGponOnuVoipC15MErrSignalMsg          Counter32,
            zxGponOnuVoipC15MUnknowSignalMsg       Counter32,
            zxGponOnuVoipPerfRowStatus             RowStatus
        }

    zxGponOnuVoipPerfThreshPrfId OBJECT-TYPE
        SYNTAX      Integer32
        MAX-ACCESS  read-create
        STATUS      current
        DESCRIPTION
            "This attribute is the ID of profile used by threshold
            configuration. According to 'zxGponOmciStatsThresholdId'
            in 'zxGponOmciStatsThresholdTable'. This attribute is not
            supported now."
        REFERENCE   "Private ME"
        ::= { zxGponRmOnuVoipSrvC15MPerfEntry 1 }

    zxGponOnuVoipC15MTxSignalMsg OBJECT-TYPE
        SYNTAX      Counter32
        MAX-ACCESS  read-only
        STATUS      current
        DESCRIPTION
            "This attribute identifies the total number of transmitted
            signalling messages."
        REFERENCE   "Private ME"
        ::= { zxGponRmOnuVoipSrvC15MPerfEntry 2 }

    zxGponOnuVoipC15MRxSignalMsg OBJECT-TYPE
        SYNTAX      Counter32
        MAX-ACCESS  read-only
        STATUS      current
        DESCRIPTION
            "This attribute identifies the total number of received signalling
            messages."
        REFERENCE   "Private ME"
        ::= { zxGponRmOnuVoipSrvC15MPerfEntry 3 }

    zxGponOnuVoipC15MReTxSignalMsg OBJECT-TYPE
        SYNTAX      Counter32
        MAX-ACCESS  read-only
        STATUS      current
        DESCRIPTION
            "This attribute identifies the number of retransmitted signalling
            messages."
        REFERENCE   "Private ME"
        ::= { zxGponRmOnuVoipSrvC15MPerfEntry 4 }

    zxGponOnuVoipC15MLossSignalMsg OBJECT-TYPE
        SYNTAX      Counter32
        MAX-ACCESS  read-only
        STATUS      current
        DESCRIPTION
            "This attribute identifies the total number of lost signalling
            messages."
        REFERENCE   "Private ME"
        ::= { zxGponRmOnuVoipSrvC15MPerfEntry 5 }

    zxGponOnuVoipC15MErrSignalMsg OBJECT-TYPE
        SYNTAX      Counter32
        MAX-ACCESS  read-only
        STATUS      current
        DESCRIPTION
            "This attribute identifies the total number of errored signalling
            messages."
        REFERENCE   "Private ME"
        ::= { zxGponRmOnuVoipSrvC15MPerfEntry 6 }

    zxGponOnuVoipC15MUnknowSignalMsg OBJECT-TYPE
        SYNTAX      Counter32
        MAX-ACCESS  read-only
        STATUS      current
        DESCRIPTION
            "This attribute identifies the total number of unknown signalling
            messages."
        REFERENCE   "Private ME"
        ::= { zxGponRmOnuVoipSrvC15MPerfEntry 7 }

    zxGponOnuVoipPerfRowStatus OBJECT-TYPE
        SYNTAX      RowStatus
        MAX-ACCESS  read-create
        STATUS      current
        DESCRIPTION
            "The status of this conceptual row.

             The supported actions of this conceptual row only include:
             'createAndGo' and 'destroy'.

             To create a row in this table, a manager must
             set this object to createAndGo(4).

             To delete a row in this table, a manager must
             set this object to destroy(6).

             To query this object, always return 1."
        REFERENCE   "Private ME"
        ::= { zxGponRmOnuVoipSrvC15MPerfEntry 50 }

--------------------------------------------------------------------------
-- zxGponRmOnuVoipSrvH15MPerfTable
--------------------------------------------------------------------------
    zxGponRmOnuVoipSrvH15MPerfTable    OBJECT-TYPE
        SYNTAX      SEQUENCE OF ZxGponRmOnuVoipSrvH15MPerfEntry
        MAX-ACCESS  not-accessible
        STATUS      current
        DESCRIPTION
            "Performance monitoring data related to the VoIP service of ONU."
        REFERENCE   "Private ME"
        ::= { zxGponOmciStatistics 107 }

    zxGponRmOnuVoipSrvH15MPerfEntry OBJECT-TYPE
        SYNTAX      ZxGponRmOnuVoipSrvH15MPerfEntry
        MAX-ACCESS  not-accessible
        STATUS      current
        DESCRIPTION
            "It is entry in the zxGponRmOnuVoipSrvH15MPerfTable."
        INDEX   { zxGponOltIndex, zxGponONTIndex}
        ::= { zxGponRmOnuVoipSrvH15MPerfTable 1 }

    ZxGponRmOnuVoipSrvH15MPerfEntry ::=
        SEQUENCE {
            zxGponOnuVoipH15MIntvEndTime            Integer32,
            zxGponOnuVoipH15MTxSignalMsg            Counter32,
            zxGponOnuVoipH15MRxSignalMsg            Counter32,
            zxGponOnuVoipH15MReTxSignalMsg          Counter32,
            zxGponOnuVoipH15MLossSignalMsg          Counter32,
            zxGponOnuVoipH15MErrSignalMsg           Counter32,
            zxGponOnuVoipH15MUnknowSignalMsg        Counter32
        }

    zxGponOnuVoipH15MIntvEndTime OBJECT-TYPE
        SYNTAX      Integer32(0..255)
        MAX-ACCESS  read-only
        STATUS      current
        DESCRIPTION
            "This attribute identifies the most recently finished 15-minute
            interval."
        REFERENCE   "Private ME"
        ::= { zxGponRmOnuVoipSrvH15MPerfEntry 1 }

    zxGponOnuVoipH15MTxSignalMsg OBJECT-TYPE
        SYNTAX      Counter32
        MAX-ACCESS  read-only
        STATUS      current
        DESCRIPTION
            "This attribute identifies the total number of transmitted
            signalling messages."
        REFERENCE   "Private ME"
        ::= { zxGponRmOnuVoipSrvH15MPerfEntry 2 }

    zxGponOnuVoipH15MRxSignalMsg OBJECT-TYPE
        SYNTAX      Counter32
        MAX-ACCESS  read-only
        STATUS      current
        DESCRIPTION
            "This attribute identifies the total number of received signalling
            messages."
        REFERENCE   "Private ME"
        ::= { zxGponRmOnuVoipSrvH15MPerfEntry 3 }

    zxGponOnuVoipH15MReTxSignalMsg OBJECT-TYPE
        SYNTAX      Counter32
        MAX-ACCESS  read-only
        STATUS      current
        DESCRIPTION
            "This attribute identifies the number of retransmitted signalling
            messages."
        REFERENCE   "Private ME"
        ::= { zxGponRmOnuVoipSrvH15MPerfEntry 4 }

    zxGponOnuVoipH15MLossSignalMsg OBJECT-TYPE
        SYNTAX      Counter32
        MAX-ACCESS  read-only
        STATUS      current
        DESCRIPTION
            "This attribute identifies the total number of lost signalling
            messages."
        REFERENCE   "Private ME"
        ::= { zxGponRmOnuVoipSrvH15MPerfEntry 5 }

    zxGponOnuVoipH15MErrSignalMsg OBJECT-TYPE
        SYNTAX      Counter32
        MAX-ACCESS  read-only
        STATUS      current
        DESCRIPTION
            "This attribute identifies the total number of errored signalling
            messages."
        REFERENCE   "Private ME"
        ::= { zxGponRmOnuVoipSrvH15MPerfEntry 6 }

    zxGponOnuVoipH15MUnknowSignalMsg OBJECT-TYPE
        SYNTAX      Counter32
        MAX-ACCESS  read-only
        STATUS      current
        DESCRIPTION
            "This attribute identifies the total number of unknown signalling
            messages."
        REFERENCE   "Private ME"
        ::= { zxGponRmOnuVoipSrvH15MPerfEntry 7 }

--Service
    zxGponServiceTable    OBJECT-TYPE
        SYNTAX      SEQUENCE OF ZxGponServiceEntry
        MAX-ACCESS  not-accessible
        STATUS      current
        DESCRIPTION
            ""
        REFERENCE   "G.984.4 & G.983.2"
        ::= { zxGponRmServiceMgmt 1 }

    zxGponServiceEntry OBJECT-TYPE
        SYNTAX      ZxGponServiceEntry
        MAX-ACCESS  not-accessible
        STATUS      current
        DESCRIPTION
            "It is entry in the zxGponServiceTable."
        INDEX   { zxGponOltIndex, zxGponONTIndex, zxGponServiceIndex }
        ::= { zxGponServiceTable 1 }

    ZxGponServiceEntry ::=
        SEQUENCE {
            zxGponServiceName                         OCTET STRING,
            zxGponServiceType                         INTEGER,
            zxGponServiceIfId                         INTEGER,
            zxGponServiceGemPort                      INTEGER,
            zxGponServiceMapType                      INTEGER,
            zxGponServiceMapCos                       INTEGER,
            zxGponServiceMapVlan                      OCTET STRING,
            zxGponServiceMVlan                        INTEGER,
            zxGponServiceEntryStatus                  RowStatus
        }

    zxGponServiceName OBJECT-TYPE
        SYNTAX      OCTET STRING(SIZE(1..32))
        MAX-ACCESS  read-write
        STATUS      current
        DESCRIPTION
            "The white space can't be included in the name."
        REFERENCE   "G.984.4 & G.983.2"
        ::= { zxGponServiceEntry 1 }

    zxGponServiceType OBJECT-TYPE
        SYNTAX      INTEGER{
                    internet(1),
                    iptv(2),
                    voip(3),
                    internet-iptv(4),
                    hybrid(5)
                    }
        MAX-ACCESS  read-write
        STATUS      current
        DESCRIPTION
        ""
        REFERENCE   "G.984.4 & G.983.2"
        ::= { zxGponServiceEntry 2 }

    zxGponServiceIfId OBJECT-TYPE
        SYNTAX      INTEGER
        MAX-ACCESS  read-write
        STATUS      current
        DESCRIPTION
        "4bytes value contains:type(MSB 2bytes)/ifId(LSB 2bytes).
        type   means
        -------------
        2      iphost"
        REFERENCE   "G.984.4 & G.983.2"
        ::= { zxGponServiceEntry 3 }

    zxGponServiceGemPort OBJECT-TYPE
        SYNTAX      INTEGER
        MAX-ACCESS  read-write
        STATUS      current
        DESCRIPTION
        ""
        REFERENCE   "G.984.4 & G.983.2"
        ::= { zxGponServiceEntry 4 }

    zxGponServiceMapType OBJECT-TYPE
        SYNTAX      INTEGER{
                    cos(1),
                    vlan(2),
                    cos-vlan(3),
                    transparent(4),
                    untag(5)
                    }
        MAX-ACCESS  read-write
        STATUS      current
        DESCRIPTION
        ""
        REFERENCE   "G.984.4 & G.983.2"
        ::= { zxGponServiceEntry 5 }

    zxGponServiceMapCos OBJECT-TYPE
        SYNTAX      INTEGER
        MAX-ACCESS  read-write
        STATUS      current
        DESCRIPTION
        "1 byte value stands for the list of 802.1p priority.
        MSB stands for priority 7, LSB stands for priority 0.
        "
        REFERENCE   "G.984.4 & G.983.2"
        ::= { zxGponServiceEntry 6 }

    zxGponServiceMapVlan OBJECT-TYPE
        SYNTAX      OCTET STRING(SIZE(24))
        MAX-ACCESS  read-write
        STATUS      current
        DESCRIPTION
        "Each 2 bytes stand for the vlan id related with this service.
        The first N*2 bytes are valid, until vlan id=0."
        REFERENCE   "G.984.4 & G.983.2"
        ::= { zxGponServiceEntry 7 }
    zxGponServiceMVlan OBJECT-TYPE
        SYNTAX      INTEGER
        MAX-ACCESS  read-write
        STATUS      current
        DESCRIPTION
        ""
        REFERENCE   "G.984.4 & G.983.2"
        ::= { zxGponServiceEntry 8 }

    zxGponServiceEntryStatus OBJECT-TYPE
        SYNTAX      RowStatus
        MAX-ACCESS  read-write
        STATUS      current
        DESCRIPTION
        ""
        REFERENCE   "G.984.4 & G.983.2"
        ::= { zxGponServiceEntry 30 }

--------------------------------------------------------------------------
-- 22. zxGponRmFirewallMgmt
-- 22.1 zxGponOnuIpFilterTable
--------------------------------------------------------------------------

    zxGponOnuIpFilterTable    OBJECT-TYPE
        SYNTAX      SEQUENCE OF ZxGponOnuIpFilterEntry
        MAX-ACCESS  not-accessible
        STATUS      current
        DESCRIPTION
        "Gpon onu ip filter table."
        ::= { zxGponRmFirewallMgmt 1 }

    zxGponOnuIpFilterEntry OBJECT-TYPE
        SYNTAX      ZxGponOnuIpFilterEntry
        MAX-ACCESS  not-accessible
        STATUS      current
        DESCRIPTION
            "It is entry in the zxGponOnuIpFilterTable."
        INDEX   { zxGponOltIndex, zxGponONTIndex, zxGponOnuIpFilterIndex }
        ::= { zxGponOnuIpFilterTable 1 }

    ZxGponOnuIpFilterEntry ::=
        SEQUENCE {
            zxGponOnuIpFilterIndex                       INTEGER,
            zxGponOnuIpFilterState                       INTEGER,
            zxGponOnuIpFilterMode                        INTEGER,
            zxGponOnuIpFilterProtocol                    INTEGER,
            zxGponOnuIpFilterStartSrcIpType              InetAddressType,
            zxGponOnuIpFilterStartSrcIpAddr              InetAddress,
            zxGponOnuIpFilterEndSrcIpType                InetAddressType,
            zxGponOnuIpFilterEndSrcIpAddr                InetAddress,
            zxGponOnuIpFilterStartDestIpType             InetAddressType,
            zxGponOnuIpFilterStartDestIpAddr             InetAddress,
            zxGponOnuIpFilterEndDestIpType               InetAddressType,
            zxGponOnuIpFilterEndDestIpAddr               InetAddress,
            zxGponOnuIpFilterStartSrcPort                INTEGER,
            zxGponOnuIpFilterEndSrcPort                  INTEGER,
            zxGponOnuIpFilterStartDestPort               INTEGER,
            zxGponOnuIpFilterEndDestPort                 INTEGER,
            zxGponOnuIpFilterIngressIfType               INTEGER,
            zxGponOnuIpFilterIngressIfId                 INTEGER,
            zxGponOnuIpFilterEgressIfType                INTEGER,
            zxGponOnuIpFilterEgressIfId                  INTEGER,
            zxGponOnuIpFilterEntryStatus                 RowStatus
        }

    zxGponOnuIpFilterIndex OBJECT-TYPE
        SYNTAX      INTEGER(1..255)
        MAX-ACCESS  not-accessible
        STATUS      current
        DESCRIPTION
        "Gpon onu ip filter index "
        ::= { zxGponOnuIpFilterEntry 1 }

    zxGponOnuIpFilterState OBJECT-TYPE
        SYNTAX      INTEGER{
                    disable(1),
                    enable(2)
                    }
        MAX-ACCESS  read-create
        STATUS      current
        DESCRIPTION
        "Gpon onu ip filter state"
        DEFVAL {disable}
        ::= { zxGponOnuIpFilterEntry 2 }

    zxGponOnuIpFilterMode OBJECT-TYPE
        SYNTAX      INTEGER{
                    discard(1),
                    permit(2)
                    }
        MAX-ACCESS  read-create
        STATUS      current
        DESCRIPTION
        "Gpon onu ip filter mode."
        DEFVAL {discard}
        ::= { zxGponOnuIpFilterEntry 3 }

    zxGponOnuIpFilterProtocol OBJECT-TYPE
        SYNTAX      INTEGER{
                    all(1),
                    tcp(2),
                    udp(3),
                    tcpudp(4),
                    icmp(5)
                    }
        MAX-ACCESS  read-create
        STATUS      current
        DESCRIPTION
        "Gpon onu ip filter protocol."
        DEFVAL {tcp}
        ::= { zxGponOnuIpFilterEntry 4 }

    zxGponOnuIpFilterStartSrcIpType OBJECT-TYPE
        SYNTAX       InetAddressType
        MAX-ACCESS   read-create
        STATUS       current
        DESCRIPTION
            "Gpon onu ip filter start source ip type."
        DEFVAL { ipv4 }
        ::= { zxGponOnuIpFilterEntry 5 }

    zxGponOnuIpFilterStartSrcIpAddr OBJECT-TYPE
        SYNTAX      InetAddress
        MAX-ACCESS  read-create
        STATUS      current
        DESCRIPTION
        "Gpon onu ip filter start source ip.The configuration
        of zxGponOnuIpFilterStartSrcIpAddr is optional."
        ::= { zxGponOnuIpFilterEntry 6 }

    zxGponOnuIpFilterEndSrcIpType OBJECT-TYPE
        SYNTAX       InetAddressType
        MAX-ACCESS   read-create
        STATUS       current
        DESCRIPTION
            "Gpon onu ip filter end source ip address type"
        DEFVAL { ipv4 }
        ::= { zxGponOnuIpFilterEntry 7 }

    zxGponOnuIpFilterEndSrcIpAddr OBJECT-TYPE
        SYNTAX      InetAddress
        MAX-ACCESS  read-create
        STATUS      current
        DESCRIPTION
        "Gpon onu ip filter end source ip address.When
        zxGponOnuIpFilterStartSrcIpAddr is not configured,
        zxGponOnuIpFilterEndSrcIpAddr can not be configured."
        ::= { zxGponOnuIpFilterEntry 8 }

    zxGponOnuIpFilterStartDestIpType OBJECT-TYPE
        SYNTAX       InetAddressType
        MAX-ACCESS   read-create
        STATUS       current
        DESCRIPTION
            "Gpon onu ip filter start destination ip type."
        DEFVAL { ipv4 }
        ::= { zxGponOnuIpFilterEntry 9 }

    zxGponOnuIpFilterStartDestIpAddr OBJECT-TYPE
        SYNTAX      InetAddress
        MAX-ACCESS  read-create
        STATUS      current
        DESCRIPTION
        "Gpon onu ip filter start destination ip.The configuration
        of zxGponOnuIpFilterStartDestIpAddr is optional."
        ::= { zxGponOnuIpFilterEntry 10 }

    zxGponOnuIpFilterEndDestIpType OBJECT-TYPE
        SYNTAX       InetAddressType
        MAX-ACCESS   read-create
        STATUS       current
        DESCRIPTION
            "Gpon onu ip filter end destination ip type.."
        DEFVAL { ipv4 }
        ::= { zxGponOnuIpFilterEntry 11 }

    zxGponOnuIpFilterEndDestIpAddr OBJECT-TYPE
        SYNTAX      InetAddress
        MAX-ACCESS  read-create
        STATUS      current
        DESCRIPTION
        "Gpon onu ip filter end destination ip address.When
        zxGponOnuIpFilterStartDestIpAddr is not configured,
        zxGponOnuIpFilterEndDestIpAddr can not be configured."
        ::= { zxGponOnuIpFilterEntry 12 }

    zxGponOnuIpFilterStartSrcPort OBJECT-TYPE
        SYNTAX      INTEGER(1..65535)
        MAX-ACCESS  read-create
        STATUS      current
        DESCRIPTION
        "Gpon onu ip filter start source port.The configuration
        of zxGponOnuIpFilterStartSrcPort is optional."
        ::= { zxGponOnuIpFilterEntry 13 }

    zxGponOnuIpFilterEndSrcPort OBJECT-TYPE
        SYNTAX      INTEGER(1..65535)
        MAX-ACCESS  read-create
        STATUS      current
        DESCRIPTION
        "Gpon onu ip filter end source port.The configuration
        of zxGponOnuIpFilterEndSrcPort is optional.When
        zxGponOnuIpFilterStartSrcPort is not configured,
        zxGponOnuIpFilterEndSrcPort can not be configured."
        ::= { zxGponOnuIpFilterEntry 14 }

    zxGponOnuIpFilterStartDestPort OBJECT-TYPE
        SYNTAX      INTEGER(1..65535)
        MAX-ACCESS  read-create
        STATUS      current
        DESCRIPTION
        "Gpon onu ip filter start dest port.The configuration
        of zxGponOnuIpFilterEndSrcPort is optional."
        ::= { zxGponOnuIpFilterEntry 15 }

    zxGponOnuIpFilterEndDestPort OBJECT-TYPE
        SYNTAX      INTEGER(1..65535)
        MAX-ACCESS  read-create
        STATUS      current
        DESCRIPTION
        "Gpon onu ip filter end dest port.The configuration
        of zxGponOnuIpFilterEndSrcPort is optional.When
        zxGponOnuIpFilterStartDestPort is not configured,
        zxGponOnuIpFilterEndDestPort can not be configured."
        ::= { zxGponOnuIpFilterEntry 16 }

    zxGponOnuIpFilterIngressIfType OBJECT-TYPE
        SYNTAX      INTEGER{
                    none(1),
                    lan(2),
                    iphost(3),
                    ethuni(4)
                    }
        MAX-ACCESS  read-create
        STATUS      current
        DESCRIPTION
        "Gpon onu ip filter ingress type.The configuration
        of zxGponOnuIpFilterIngressIfType is optional."
        ::= { zxGponOnuIpFilterEntry 17 }

    zxGponOnuIpFilterIngressIfId OBJECT-TYPE
        SYNTAX      INTEGER(1..65535)
        MAX-ACCESS  read-create
        STATUS      current
        DESCRIPTION
        "The interface id which is related with this interface.
         It can be the IfId of lan,ethuni or iphost, according to the
         zxGponOnuIpFilterIngressType.
         The format as below:
         type      1st byte  2nd byte  3rd byte              4th byte
         none/lan  reserved  reserved  reserved              reserved
         iphost    reserved  reserved  reserved              iphost index(1~255)
         ethuni    reserved  reserved  slot of ethuni(0~255) ethuni index(1~255)
         (4 bytes)

         The configuration
        of zxGponOnuIpFilterIngressIfId is optional."
        ::= { zxGponOnuIpFilterEntry 18 }

    zxGponOnuIpFilterEgressIfType OBJECT-TYPE
        SYNTAX      INTEGER{
                    none(1),
                    lan(2),
                    iphost(3),
                    ethuni(4)
                    }
        MAX-ACCESS  read-create
        STATUS      current
        DESCRIPTION
        "Gpon onu ip filter egress type.The configuration
        of zxGponOnuIpFilterEgressIfType is optional."
        ::= { zxGponOnuIpFilterEntry 19 }

    zxGponOnuIpFilterEgressIfId OBJECT-TYPE
        SYNTAX      INTEGER(1..65535)
        MAX-ACCESS  read-create
        STATUS      current
        DESCRIPTION
        "The interface id which is related with this interface.
         It can be the IfId of lan,ethuni or iphost, according to the
         zxGponOnuIpFilterEgressType.
         The format as below:
         type      1st byte  2nd byte  3rd byte              4th byte
         none/lan  reserved  reserved  reserved              reserved
         iphost    reserved  reserved  reserved              iphost index(1~255)
         ethuni    reserved  reserved  slot of ethuni(0~255) ethuni index(1~255)
         (4 bytes)
         The configuration
        of zxGponOnuIpFilterEgressIfId is optional."
        ::= { zxGponOnuIpFilterEntry 20 }

    zxGponOnuIpFilterEntryStatus OBJECT-TYPE
        SYNTAX      RowStatus
        MAX-ACCESS  read-create
        STATUS      current
        DESCRIPTION
        "Entry status of zxGponOnuIpFilterTable."
        ::= { zxGponOnuIpFilterEntry 50 }

--------------------------------------------------------------------------
-- 22.2 zxGponPortForwardTable
--------------------------------------------------------------------------

    zxGponPortForwardTable    OBJECT-TYPE
        SYNTAX      SEQUENCE OF ZxGponPortForwardEntry
        MAX-ACCESS  not-accessible
        STATUS      current
        DESCRIPTION
            "This table configure wan to lan port foward rules."
        ::= { zxGponRmFirewallMgmt 2 }

    zxGponPortForwardEntry OBJECT-TYPE
        SYNTAX      ZxGponPortForwardEntry
        MAX-ACCESS  not-accessible
        STATUS      current
        DESCRIPTION
            "Gpon port forward table entry."
        INDEX   { zxGponOltIndex, zxGponONTIndex, zxGponPortForwardIndex }
        ::= { zxGponPortForwardTable 1 }

    ZxGponPortForwardEntry ::=
        SEQUENCE {
            zxGponPortForwardIndex                    INTEGER,
            zxGponPortForwardState                    INTEGER,
            zxGponPortForwardProtocol                 INTEGER,
            zxGponPortForwardMappingType              INTEGER,
            zxGponPortForwardIpHostId                 INTEGER,
            zxGponPortForwardLanHostIpType            InetAddressType,
            zxGponPortForwardLanHostIp                IpAddress,
            zxGponPortForwardLanHostMac               MacAddress,
            zxGponPortForwardLanStartPort             INTEGER,
            zxGponPortForwardLanEndPort               INTEGER,
            zxGponPortForwardWanStartPort             INTEGER,
            zxGponPortForwardWanEndPort               INTEGER,
            zxGponPortForwardWanStartIpType           InetAddressType,
            zxGponPortForwardWanStartIp               IpAddress,
            zxGponPortForwardWanEndIpType             InetAddressType,
            zxGponPortForwardWanEndIp                 IpAddress,
            zxGponPortForwardEntryStatus              RowStatus
        }

    zxGponPortForwardIndex OBJECT-TYPE
        SYNTAX      INTEGER(1..255)
        MAX-ACCESS  not-accessible
        STATUS      current
        DESCRIPTION
        "Gpon port forward index."
        ::= { zxGponPortForwardEntry 1 }

    zxGponPortForwardState OBJECT-TYPE
        SYNTAX      INTEGER{
                    disable(1),
                    enable(2)
                    }
        MAX-ACCESS  read-create
        STATUS      current
        DESCRIPTION
        "Disable or enable forward rule."
        DEFVAL {disable}
        ::= { zxGponPortForwardEntry 2 }

    zxGponPortForwardProtocol OBJECT-TYPE
        SYNTAX      INTEGER{
                    tcp(1),
                    udp(2),
                    tcpudp(3)
                    }
        MAX-ACCESS  read-create
        STATUS      current
        DESCRIPTION
        "Gpon port forward protocol type."
        DEFVAL {tcp}
        ::= { zxGponPortForwardEntry 3 }

    zxGponPortForwardMappingType OBJECT-TYPE
        SYNTAX      INTEGER{
                    ip(1),
                    mac(2)
                    }
        MAX-ACCESS  read-create
        STATUS      current
        DESCRIPTION
        "Gpon port forward mapping type."
        ::= { zxGponPortForwardEntry 4 }

    zxGponPortForwardIpHostId OBJECT-TYPE
        SYNTAX      INTEGER(1..255)
        MAX-ACCESS  read-create
        STATUS      current
        DESCRIPTION
        "Gpon port forward IpHost Id. "
        ::= { zxGponPortForwardEntry 5 }

    zxGponPortForwardLanHostIpType OBJECT-TYPE
        SYNTAX       InetAddressType
        MAX-ACCESS   read-create
        STATUS       current
        DESCRIPTION
            "This attribute specifies the LAN HostIp ip address type."
        DEFVAL { ipv4 }
        ::= { zxGponPortForwardEntry 6 }

    zxGponPortForwardLanHostIp OBJECT-TYPE
        SYNTAX      IpAddress
        MAX-ACCESS  read-create
        STATUS      current
        DESCRIPTION
        "Gpon port forward LAN host ip."
        ::= { zxGponPortForwardEntry 7 }

    zxGponPortForwardLanHostMac OBJECT-TYPE
        SYNTAX      MacAddress
        MAX-ACCESS  read-create
        STATUS      current
        DESCRIPTION
        "Gpon port forward LAN host MAC address."
        ::= { zxGponPortForwardEntry 8 }

    zxGponPortForwardLanStartPort OBJECT-TYPE
        SYNTAX      INTEGER(1..65535)
        MAX-ACCESS  read-create
        STATUS      current
        DESCRIPTION
        "Gpon port forward LAN start port."
        ::= { zxGponPortForwardEntry 9 }

    zxGponPortForwardLanEndPort OBJECT-TYPE
        SYNTAX      INTEGER(1..65535)
        MAX-ACCESS  read-create
        STATUS      current
        DESCRIPTION
        "Gpon port forward LAN end port."
        ::= { zxGponPortForwardEntry 10 }

    zxGponPortForwardWanStartPort OBJECT-TYPE
        SYNTAX      INTEGER(1..65535)
        MAX-ACCESS  read-create
        STATUS      current
        DESCRIPTION
        "Gpon port forward WAN start port."
        ::= { zxGponPortForwardEntry 11 }

    zxGponPortForwardWanEndPort OBJECT-TYPE
        SYNTAX      INTEGER(1..65535)
        MAX-ACCESS  read-create
        STATUS      current
        DESCRIPTION
        "Gpon port forward WAN end port."
        ::= { zxGponPortForwardEntry 12 }

    zxGponPortForwardWanStartIpType OBJECT-TYPE
        SYNTAX       InetAddressType
        MAX-ACCESS   read-create
        STATUS       current
        DESCRIPTION
            "Gpon port forward wan start ip address type."
        DEFVAL { ipv4 }
        ::= { zxGponPortForwardEntry 13 }

    zxGponPortForwardWanStartIp OBJECT-TYPE
        SYNTAX      IpAddress
        MAX-ACCESS  read-create
        STATUS      current
        DESCRIPTION
        "Gpon port forward WAN start ip address."
        ::= { zxGponPortForwardEntry 14 }

    zxGponPortForwardWanEndIpType OBJECT-TYPE
        SYNTAX       InetAddressType
        MAX-ACCESS   read-create
        STATUS       current
        DESCRIPTION
        "Gpon port forward wan end ip address type."
        DEFVAL { ipv4 }
        ::= { zxGponPortForwardEntry 15 }

    zxGponPortForwardWanEndIp OBJECT-TYPE
        SYNTAX      IpAddress
        MAX-ACCESS  read-create
        STATUS      current
        DESCRIPTION
        "Gpon port forward wan end ip address."
        ::= { zxGponPortForwardEntry 16 }

    zxGponPortForwardEntryStatus OBJECT-TYPE
        SYNTAX      RowStatus
        MAX-ACCESS  read-create
        STATUS      current
        DESCRIPTION
        "The row status of this entry."
        ::= { zxGponPortForwardEntry 40 }
--------------------------------------------------------------------------
-- 23. zxGponRmSecurityMgmt
-- 23.1 zxGponOnuSecCtrlTable
--------------------------------------------------------------------------
    zxGponOnuSecCtrlTable    OBJECT-TYPE
        SYNTAX      SEQUENCE OF ZxGponOnuSecCtrlEntry
        MAX-ACCESS  not-accessible
        STATUS      current
        DESCRIPTION
            "This table includes ONU  security information. "
        ::= { zxGponRmSecurityMgmt 1 }

    zxGponOnuSecCtrlEntry OBJECT-TYPE
        SYNTAX      ZxGponOnuSecCtrlEntry
        MAX-ACCESS  not-accessible
        STATUS      current
        DESCRIPTION
            "An entry in zxGponOnuSecCtrlTable."
        INDEX   { zxGponOltIndex, zxGponONTIndex }
        ::= { zxGponOnuSecCtrlTable 1 }
    ZxGponOnuSecCtrlEntry ::=
        SEQUENCE {
            zxGponOnuSecCtrlEnhancedEnable        INTEGER,
            zxGponOnuSecCtrlEnhancedPsk           OCTET STRING
        }
    zxGponOnuSecCtrlEnhancedEnable OBJECT-TYPE
        SYNTAX      INTEGER{
            enable(1),
            disable(2)
        }
        MAX-ACCESS  read-write
        STATUS      current
        DESCRIPTION
            "Enable or disable the ONU enhanced security control function."
        DEFVAL    { disable }
        ::=  {  zxGponOnuSecCtrlEntry  1 }
    zxGponOnuSecCtrlEnhancedPsk OBJECT-TYPE
        SYNTAX      OCTET STRING(SIZE(32))
        MAX-ACCESS  read-write
        STATUS      current
        DESCRIPTION
            "A PSK of 128 bits simplifies the application of security
             algorithms based on AES-128 (e.g. AES-CMAC-128).
             A PSK is associated with a particular ONU and is stored
             at that ONU and at the operator infrastructure."
        ::= { zxGponOnuSecCtrlEntry 2 }


--------------------------------------------------------------------------
-- 24. zxGponRmQosMgmt
-- 24.1 zxGponUniTrafficTreatTable
--------------------------------------------------------------------------
    zxGponUniTrafficTreatTable    OBJECT-TYPE
        SYNTAX      SEQUENCE OF ZxGponUniTrafficTreatEntry
        MAX-ACCESS  not-accessible
        STATUS      current
        DESCRIPTION
            "This table includes ONU UNI traffic treat information. "
        ::= { zxGponRmQosMgmt 1 }

    zxGponUniTrafficTreatEntry OBJECT-TYPE
        SYNTAX      ZxGponUniTrafficTreatEntry
        MAX-ACCESS  not-accessible
        STATUS      current
        DESCRIPTION
            "An entry in zxGponUniTrafficTreatTable."
        INDEX   { zxGponOltIndex, zxGponONTIndex, zxGponUNIIndex,
                  zxGponUniTrafficVlan,
                  zxGponUniTrafficPrio, zxGponUniTrafficEthernetType }
        ::= { zxGponUniTrafficTreatTable 1 }

    ZxGponUniTrafficTreatEntry ::=
        SEQUENCE {
            zxGponUniTrafficVlan                        Integer32,
            zxGponUniTrafficPrio                        Integer32,
            zxGponUniTrafficEthernetType                INTEGER,
            zxGponUniTrafficCir                         Integer32,
            zxGponUniTrafficTreatMode                   INTEGER,
            zxGponUniTrafficLowerPrioRemark             Integer32,
            zxGponUniTrafficUpperPrioRemark             Integer32,
            zxGponUniTrafficRowStatus                   RowStatus
        }

    zxGponUniTrafficVlan OBJECT-TYPE
        SYNTAX      Integer32(0..4096)
        MAX-ACCESS  not-accessible
        STATUS      current
        DESCRIPTION
            "The traffic VLAN, value 4096 means VLAN is not cared.
             VLAN 0 is a UNTAG message with  priority."
        DEFVAL { 4096 }
        ::= { zxGponUniTrafficTreatEntry 1 }

    zxGponUniTrafficPrio OBJECT-TYPE
        SYNTAX      Integer32(0..8)
        MAX-ACCESS  not-accessible
        STATUS      current
        DESCRIPTION
            "The traffic priority, value 8 means priority is not cared."
        DEFVAL { 8 }
        ::= { zxGponUniTrafficTreatEntry 2 }

    zxGponUniTrafficEthernetType OBJECT-TYPE
        SYNTAX      INTEGER{
                    any(1),
                    ipoe(2),
                    pppoe(3),
                    arp(4)
                    }
        MAX-ACCESS  not-accessible
        STATUS      current
        DESCRIPTION
            "The traffic Ethernet type."
        DEFVAL { any }
        ::= { zxGponUniTrafficTreatEntry 3 }

    zxGponUniTrafficCir OBJECT-TYPE
        SYNTAX      Integer32(0..4294967295)
        UNITS       "kbps"
        MAX-ACCESS  read-create
        STATUS      current
        DESCRIPTION
            "The committed information rate."
        ::= { zxGponUniTrafficTreatEntry 4 }

    zxGponUniTrafficTreatMode OBJECT-TYPE
        SYNTAX      INTEGER{
                    rateLimit(1),
                    prioRemark(2)
                    }
        MAX-ACCESS  read-create
        STATUS      current
        DESCRIPTION
            "The traffic treat mode.
             When the value is rateLimit indicates rate
             limit to traffic, the value is prioRemark
             indicates remarking priority."
        DEFVAL { rateLimit }
        ::= { zxGponUniTrafficTreatEntry 5 }

    zxGponUniTrafficLowerPrioRemark OBJECT-TYPE
        SYNTAX      Integer32(0..7)
        MAX-ACCESS  read-create
        STATUS      current
        DESCRIPTION
            "Remark the priority when traffic rate is lower
             than zxGponUniTrafficCir. This object is valid
             when zxGponUniTrafficTreatMode is prioRemark(2)."
        ::= { zxGponUniTrafficTreatEntry 6 }

    zxGponUniTrafficUpperPrioRemark OBJECT-TYPE
        SYNTAX      Integer32(0..7)
        MAX-ACCESS  read-create
        STATUS      current
        DESCRIPTION
            "Remark the priority when traffic rate is upper
             than zxGponUniTrafficCir. This object is valid
             when zxGponUniTrafficTreatMode is prioRemark(2)."
        ::= { zxGponUniTrafficTreatEntry 7 }

    zxGponUniTrafficRowStatus OBJECT-TYPE
        SYNTAX      RowStatus
        MAX-ACCESS  read-create
        STATUS      current
        DESCRIPTION
            "The row status of this entry."
        ::= { zxGponUniTrafficTreatEntry 8 }
--------------------------------------------------------------------------
-- 24. zxGponRmQosMgmt
-- 24.2 zxGponGemPortQosTable
--------------------------------------------------------------------------
    zxGponGemPortQosTable    OBJECT-TYPE
        SYNTAX      SEQUENCE OF ZxGponGemPortQosEntry
        MAX-ACCESS  not-accessible
        STATUS      current
        DESCRIPTION
            "This table contains information of ONU GEM port QoS configuration.
             One entry in this table reflects a configuration table defined by
             a manager which can be used to configure the ONU GEM port QoS.
             If the GEM port mapping mode is cos careless, the following 8
             UsPrioToTcontQueues must be set with the same value at the same
             time when changing the upstream queue."
        REFERENCE   "G.984.4/9.11.1 & 9.11.3
                     Traffic management/Priority queue-G
                     & GEM traffic descriptor"
        ::= { zxGponRmQosMgmt 2 }

    zxGponGemPortQosEntry OBJECT-TYPE
        SYNTAX      ZxGponGemPortQosEntry
        MAX-ACCESS  not-accessible
        STATUS      current
        DESCRIPTION
            "An entry in zxGponGemPortQosTable."
        INDEX   { zxGponOltIndex, zxGponONTIndex, zxGponGemPortIndex }
        ::= { zxGponGemPortQosTable 1 }

    ZxGponGemPortQosEntry ::=
        SEQUENCE {
            zxGponGemPortUsTrafficProfile        DisplayString,
            zxGponGemPortDsTrafficProfile        DisplayString,
            zxGponGemPortUsPrio0ToTcontQueue     Integer32,
            zxGponGemPortUsPrio1ToTcontQueue     Integer32,
            zxGponGemPortUsPrio2ToTcontQueue     Integer32,
            zxGponGemPortUsPrio3ToTcontQueue     Integer32,
            zxGponGemPortUsPrio4ToTcontQueue     Integer32,
            zxGponGemPortUsPrio5ToTcontQueue     Integer32,
            zxGponGemPortUsPrio6ToTcontQueue     Integer32,
            zxGponGemPortUsPrio7ToTcontQueue     Integer32,
            zxGponGemPortDsUniId                 Integer32,
            zxGponGemPortDsToUniQueue            Integer32
        }

    zxGponGemPortUsTrafficProfile OBJECT-TYPE
        SYNTAX      DisplayString(SIZE(0..64))
        MAX-ACCESS  read-write
        STATUS      current
        DESCRIPTION
            "This attribute points to the instance of the GEM traffic
             descriptor managed entity that contains the upstream
             traffic parameters used for this GEM port network CTP ME.
             It indicates no rate limiting when the length of value is 0."

        REFERENCE   "G.984.4 9.2.3 GEM port network CTP"
        ::= { zxGponGemPortQosEntry 1 }

    zxGponGemPortDsTrafficProfile OBJECT-TYPE
        SYNTAX      DisplayString(SIZE(0..64))
        MAX-ACCESS  read-write
        STATUS      current
        DESCRIPTION
            "This attribute points to the instance of the traffic descriptor
             managed entity that contains the downstream traffic parameters
             for this GEM port network CTP.
             It indicates no rate limiting when the length of value is 0."
        REFERENCE   "G.984.4 9.2.3 GEM port network CTP"
        ::= { zxGponGemPortQosEntry 2 }

    zxGponGemPortUsPrio0ToTcontQueue OBJECT-TYPE
        SYNTAX      Integer32(0..7)
        MAX-ACCESS  read-write
        STATUS      current
        DESCRIPTION
            "This attribute points to the instance of the priority queue-G
             used for this GEM port with priority 0 in the upstream direction."
        REFERENCE   "G.984.4 9.2.3 GEM port network CTP"
        ::= { zxGponGemPortQosEntry 3 }

    zxGponGemPortUsPrio1ToTcontQueue OBJECT-TYPE
        SYNTAX      Integer32(0..7)
        MAX-ACCESS  read-write
        STATUS      current
        DESCRIPTION
            "This attribute points to the instance of the priority queue-G used
             for this GEM port with priority 1 in the upstream direction."
        REFERENCE   "G.984.4 9.2.3 GEM port network CTP"
        ::= { zxGponGemPortQosEntry 4 }

    zxGponGemPortUsPrio2ToTcontQueue OBJECT-TYPE
        SYNTAX      Integer32(0..7)
        MAX-ACCESS  read-write
        STATUS      current
        DESCRIPTION
            "This attribute points to the instance of the priority queue-G used
             for this GEM port with priority 2 in the upstream direction."
        REFERENCE   "G.984.4 9.2.3 GEM port network CTP"
        ::= { zxGponGemPortQosEntry 5 }

    zxGponGemPortUsPrio3ToTcontQueue OBJECT-TYPE
        SYNTAX      Integer32(0..7)
        MAX-ACCESS  read-write
        STATUS      current
        DESCRIPTION
            "This attribute points to the instance of the priority queue-G used
             for  this GEM port with priority 3 in the upstream direction."
        REFERENCE   "G.984.4 9.2.3 GEM port network CTP"
        ::= { zxGponGemPortQosEntry 6 }

    zxGponGemPortUsPrio4ToTcontQueue OBJECT-TYPE
        SYNTAX      Integer32(0..7)
        MAX-ACCESS  read-write
        STATUS      current
        DESCRIPTION
            "This attribute points to the instance of the priority queue-G used
             for this GEM port with priority 4 in the upstream direction."
        REFERENCE   "G.984.4 9.2.3 GEM port network CTP"
        ::= { zxGponGemPortQosEntry 7 }

    zxGponGemPortUsPrio5ToTcontQueue OBJECT-TYPE
        SYNTAX      Integer32(0..7)
        MAX-ACCESS  read-write
        STATUS      current
        DESCRIPTION
            "This attribute points to the instance of the priority queue-G used
             for this GEM port with priority 5 in the upstream direction."
        REFERENCE   "G.984.4 9.2.3 GEM port network CTP"
        ::= { zxGponGemPortQosEntry 8 }

    zxGponGemPortUsPrio6ToTcontQueue OBJECT-TYPE
        SYNTAX      Integer32(0..7)
        MAX-ACCESS  read-write
        STATUS      current
        DESCRIPTION
            "This attribute points to the instance of the priority queue-G used
             for this GEM port with priority 6 in the upstream direction."
        REFERENCE   "G.984.4 9.2.3 GEM port network CTP"
        ::= { zxGponGemPortQosEntry 9 }

    zxGponGemPortUsPrio7ToTcontQueue OBJECT-TYPE
        SYNTAX      Integer32(0..7)
        MAX-ACCESS  read-write
        STATUS      current
        DESCRIPTION
            "This attribute points to the instance of the priority queue-G used
             for this GEM port with priority 7 in the upstream direction."
        REFERENCE   "G.984.4 9.2.3 GEM port network CTP"
        ::= { zxGponGemPortQosEntry 10 }

    zxGponGemPortDsUniId OBJECT-TYPE
        SYNTAX      Integer32
        MAX-ACCESS  read-write
        STATUS      current
        DESCRIPTION
            "This attribute points to an Ethernet UNI where the physical path
             terminates and Ethernet physical level functions are performed. "
        REFERENCE   "G.984.4 9.2.3 GEM port network CTP"
        ::= { zxGponGemPortQosEntry 11 }

    zxGponGemPortDsToUniQueue OBJECT-TYPE
        SYNTAX      Integer32(0..7)
        MAX-ACCESS  read-write
        STATUS      current
        DESCRIPTION
            "This attribute points to the instance of the priority queue-G used
             for  this GEM port network CTP in the downstream direction."
        REFERENCE   "G.984.4 Traffic management"
        ::= { zxGponGemPortQosEntry 12 }
--------------------------------------------------------------------------
-- 25. zxGponRmVeipMgmt
-- 25.1 zxGponVeipTable
--------------------------------------------------------------------------

    zxGponVeipTable   OBJECT-TYPE
        SYNTAX      SEQUENCE OF ZxGponVeipEntry
        MAX-ACCESS  not-accessible
        STATUS      current
        DESCRIPTION
            "zxGponVeipTable table.
             This managed entity represents the data plane hand-off point in
             an ONU to a separate (non-OMCI) management domain.
             The virtual Ethernet interface point is managed by OMCI,
             and is potentially known to the non-OMCI management domain.
             One or more Ethernet traffic flows are present at this boundary."
        REFERENCE   "G.988 9.5.5 virtual Ethernet interface point"
        ::= { zxGponRmVeipMgmt 2 }

    zxGponVeipEntry   OBJECT-TYPE
        SYNTAX      ZxGponVeipEntry
        MAX-ACCESS  not-accessible
        STATUS      current
        DESCRIPTION
            "zxGponVeipEntry entry.
             GPON VEIP configuration entry."
        INDEX   { zxGponOltIndex, zxGponONTIndex, zxGponVeipIndex }
        ::= { zxGponVeipTable 1 }

    ZxGponVeipEntry ::= SEQUENCE {
        zxGponVeipIndex                           Integer32,
        zxGponVeipAdminStatus                     INTEGER,
        zxGponVeipOperStatus                      INTEGER,
        zxGponVeipInterDomainName                 DisplayString,
        zxGponVeipIsPortAssigned                  TruthValue,
        zxGponVeipProtocolType                    INTEGER,
        zxGponVeipAssignedPort                    Integer32,
        zxGponVeipHostId                          Integer32,
        zxGponVeipIanaAssignedPort                Integer32
        }

    zxGponVeipIndex  OBJECT-TYPE
        SYNTAX      Integer32(1..255)
        MAX-ACCESS  not-accessible
        STATUS      current
        DESCRIPTION
            "This attribute uniquely identifies each instance
             of this managed entity.
             To facilitate easy discovery,
             the ONU should assign IDs in the sequence 1, 2, ....
             The values 0 and 0xFFFF are reserved and not used now."
        ::= { zxGponVeipEntry 1 }

    zxGponVeipAdminStatus    OBJECT-TYPE
        SYNTAX      INTEGER {
            unlocked(1),
            locked(2)
        }
        MAX-ACCESS  read-write
        STATUS      current
        DESCRIPTION
            "This attribute locks and unlocks the functions performed by
             this managed entity."
        DEFVAL  { unlocked }
        ::= {zxGponVeipEntry 2 }

    zxGponVeipOperStatus    OBJECT-TYPE
        SYNTAX      INTEGER {
            enabled(1),
            disabled(2)
        }
        MAX-ACCESS  read-only
        STATUS      current
        DESCRIPTION
            "This attribute indicates whether or not the managed entity
             is capable of performing its function.
             Valid values are enabled and disabled."
        ::= {zxGponVeipEntry 3 }

    zxGponVeipInterDomainName    OBJECT-TYPE
        SYNTAX      DisplayString  ( SIZE ( 0 .. 25  ) )
        MAX-ACCESS  read-write
        STATUS      current
        DESCRIPTION
            "This attribute is a character string that provides an optional way
             to identify the virtual Ethernet interface point
             to a non-OMCI management domain.
             The interface may also be identified by its managed entity ID,
             IANA assigned port and possibly other ways.
             If the vendor offers no information in this attribute,
             it should be set to a sequence of null bytes."
        ::= { zxGponVeipEntry 4 }

    zxGponVeipIsPortAssigned OBJECT-TYPE
        SYNTAX      TruthValue
        MAX-ACCESS  read-write
        STATUS      current
        DESCRIPTION
            "This attribute points to an instance of the TCP/UDP config data
             managed entity, which provides for OMCI management of
             the non-OMCI management domain's IP connectivity.
             This attribute specifies whether to assign tcp or udp port
             for IP connectivity."
        DEFVAL     { true }
        ::= { zxGponVeipEntry 5 }

    zxGponVeipProtocolType    OBJECT-TYPE
        SYNTAX      INTEGER {
            tcp(1),
            udp(2)
        }
        MAX-ACCESS  read-write
        STATUS      current
        DESCRIPTION
            "This attribute points to an instance of the TCP/UDP config data
             managed entity, which provides for OMCI management of
             the non-OMCI management domain's IP connectivity.
             This attribute specifies the protocol used in IP connectivity."
        DEFVAL  { udp }
        ::= {zxGponVeipEntry 6 }

    zxGponVeipAssignedPort  OBJECT-TYPE
        SYNTAX      Integer32(0..65535)
        MAX-ACCESS  read-write
        STATUS      current
        DESCRIPTION
            "This attribute points to an instance of the TCP/UDP config data
             managed entity, which provides for OMCI management of
             the non-OMCI management domain's IP connectivity.
             This attribute specifies the assigned tcp or udp port
             for IP connectivity when zxGponVeipIsTcpOrUdpPortAssigned is true."
        ::= { zxGponVeipEntry 7 }

    zxGponVeipHostId  OBJECT-TYPE
        SYNTAX      Integer32(1..255)
        MAX-ACCESS  read-write
        STATUS      current
        DESCRIPTION
            "This attribute points to an instance of the TCP/UDP config data
             managed entity, which provides for OMCI management of
             the non-OMCI management domain's IP connectivity
             when zxGponVeipIsTcpOrUdpPortAssigned is true.
             This attribute specifies the host ID for IP connectivity."
        ::= { zxGponVeipEntry 8 }

    zxGponVeipIanaAssignedPort    OBJECT-TYPE
        SYNTAX      Integer32(0..65535)
        MAX-ACCESS  read-only
        STATUS      current
        DESCRIPTION
            "This attribute contains the TCP or UDP port value
             as assigned by IANA for the management protocol associated
             with this virtual Ethernet interface.
             This attribute is to be regarded as a hint,
             not as a requirement that management communications use this port;
             the actual port and protocol are specified
             in the associated TCP/UDP config data managed entity.
             If no port has been assigned, or if the management protocol
             is free to be chosen at run-time,
             this attribute should be set to 0xFFFF."
        DEFVAL  { 65535 }
        ::= {zxGponVeipEntry 9 }

--------------------------------------------------------------------------
-- 26. zxGponRmTr069Mgmt
-- 26.1 zxGponTr069AcsTable
--------------------------------------------------------------------------

    zxGponTr069AcsTable   OBJECT-TYPE
        SYNTAX      SEQUENCE OF ZxGponTr069AcsEntry
        MAX-ACCESS  not-accessible
        STATUS      current
        DESCRIPTION
            "zxGponTr069AcsTable table.
             If functions within the ONU are managed by [BBF TR-69],
             this ME allows OMCI configuration of the ACS URL
             and related authentication information for an ACS connection
             initiated by the ONU.
             TR-69 supports other means to discover its ACS,
             so not all TR-69-compatible ONUs necessarily support this ME.
             Further, even if the ONU does support this ME,
             some operators may choose not to use it."
        REFERENCE   "G.988 9.12.16 TR-069 management server"
        ::= { zxGponRmTr069Mgmt 2 }

    zxGponTr069AcsEntry   OBJECT-TYPE
        SYNTAX      ZxGponTr069AcsEntry
        MAX-ACCESS  not-accessible
        STATUS      current
        DESCRIPTION
            "zxGponTr069AcsEntry entry.
             GPON Tr069 management server configuration entry."
        INDEX   { zxGponOltIndex, zxGponONTIndex, zxGponVeipIndex }
        ::= { zxGponTr069AcsTable 1 }

    ZxGponTr069AcsEntry ::= SEQUENCE {
        zxGponTr069AcsAdminStatus              INTEGER,
        zxGponTr069AcsUri                      DisplayString,
        zxGponTr069AcsValidationScheme         INTEGER,
        zxGponTr069AcsUsername                 DisplayString,
        zxGponTr069AcsPassword                 DisplayString,
        zxGponTr069AcsRealm                    DisplayString,
        zxGponTr069AssociatedTag               Integer32
        }

    zxGponTr069AcsAdminStatus    OBJECT-TYPE
        SYNTAX      INTEGER {
            unlocked(1),
            locked(2)
        }
        MAX-ACCESS  read-write
        STATUS      current
        DESCRIPTION
            "This attribute locks and unlocks the functions performed
             by this managed entity. When the administrative state is locked,
             the functions of this ME are disabled.
             TR-69 connectivity to an ACS may be possible through means
             that do not depend on this ME.
             The default value of this attribute is locked."
        DEFVAL  { locked }
        ::= {zxGponTr069AcsEntry 1 }

    zxGponTr069AcsUri OBJECT-TYPE
        SYNTAX       DisplayString  ( SIZE ( 0 .. 128  ) )
        MAX-ACCESS   read-write
        STATUS       current
        DESCRIPTION
            "This attribute points to the large string ME that contains
             the network address.
             It may contain a fully qualified domain name,
             URI or IP address. The URI may also contain a port identifier,
             eg x.y.z.com:5060.
             A null pointer indicates that no network address is defined."
        ::= { zxGponTr069AcsEntry 2 }

    zxGponTr069AcsValidationScheme    OBJECT-TYPE
        SYNTAX      INTEGER {
            disabled(1),
            md5(2),
            basic(3)
        }
        MAX-ACCESS  read-write
        STATUS      current
        DESCRIPTION
            "This attribute specifies the validation scheme used when the ONT
             validates a challenge. Validation schemes are defined as follows:
             1  Validation disabled.
             2  Validate using MD5 digest authentication as defined in
                [IETF RFC 2069].
             3  Validate using basic authentication as defined in
                [IETF RFC 2617]."
        DEFVAL  { disabled }
        ::= {zxGponTr069AcsEntry 3 }

    zxGponTr069AcsUsername    OBJECT-TYPE
        SYNTAX      DisplayString  ( SIZE ( 0 .. 25  ) )
        MAX-ACCESS  read-write
        STATUS      current
        DESCRIPTION
            "This string attribute is the user name. If the string is shorter
             than 25 bytes, it must be null terminated (Note)."
        REFERENCE   "G.984.4 section 9.12.4"
        ::= {zxGponTr069AcsEntry 4 }

    zxGponTr069AcsPassword    OBJECT-TYPE
        SYNTAX      DisplayString  ( SIZE ( 0 .. 25  ) )
        MAX-ACCESS  read-write
        STATUS      current
        DESCRIPTION
            "This string attribute is the password. If the string is shorter
             than 25 bytes, it must be null terminated."
        REFERENCE   "G.984.4 section 9.12.4"
        ::= {zxGponTr069AcsEntry 5 }

    zxGponTr069AcsRealm    OBJECT-TYPE
        SYNTAX      DisplayString  ( SIZE ( 0 .. 25  ) )
        MAX-ACCESS  read-write
        STATUS      current
        DESCRIPTION
            "This string attribute specifies the realm used in md5 digest
             authentication. If the string is shorter than 25 bytes,
             it must be null terminated."
        ::= {zxGponTr069AcsEntry 6 }

    zxGponTr069AssociatedTag    OBJECT-TYPE
        SYNTAX      Integer32(0..65535)
        MAX-ACCESS  read-write
        STATUS      current
        DESCRIPTION
            "This attribute is a TCI value for TR-69 management traffic
             passing through the virtual ethernet interface point.
             A TCI, comprising user priority, CFI and VID,
             is represented by 2 bytes.
             the first 3 bits represent priority.
             the last 12 bits represent VID.
             eg: priority(3 bits)| reserved(1 bits) |VID(12bits).
             The value 0xFFFF specifies that TR-69 management traffic
             passes through the virtual ethernet interface point
             with neither a VLAN nor a priority tag."
        ::= {zxGponTr069AcsEntry 7 }
--------------------------------------------------------------------------
-- 27. zxGponRmTestMgmt
-- 27.1 zxGponIpHostTestTable
-- 27.2 zxGponPingResultTable
--------------------------------------------------------------------------
--IP And Trace Ping Test
    zxGponIpHostTestTable   OBJECT-TYPE
        SYNTAX      SEQUENCE OF ZxGponIpHostTestEntry
        MAX-ACCESS  not-accessible
        STATUS      current
        DESCRIPTION
            "The test action for IP host config data entity class,
             including ping and traceroute."
        REFERENCE   "section A.3.21.2/G.988"
        ::= { zxGponRmTestMgmt 2 }
    zxGponIpHostTestEntry   OBJECT-TYPE
        SYNTAX      ZxGponIpHostTestEntry
        MAX-ACCESS  not-accessible
        STATUS      current
        DESCRIPTION
            "It is the entry of zxGponIpHostTestTable."
        INDEX   { zxGponOltIndex, zxGponONTIndex, zxGponIPHostConfigDataId }
        ::= { zxGponIpHostTestTable 1 }

    ZxGponIpHostTestEntry ::= SEQUENCE {
            zxGponIpHostTestAction          INTEGER,
            zxGponIpHostTestIpAddressType   InetAddressType,
            zxGponIpHostTestIpAddress       InetAddress
        }
    zxGponIpHostTestAction    OBJECT-TYPE
        SYNTAX      INTEGER {
            ping(1),
            traceRoute(2)
        }
        MAX-ACCESS  read-write
        STATUS      current
        DESCRIPTION
            "This attribute specifies the test action.
             It includes ping test and trace route test.
            "
        ::= {zxGponIpHostTestEntry 1 }
    zxGponIpHostTestIpAddressType OBJECT-TYPE
       SYNTAX       InetAddressType
       MAX-ACCESS   read-write
       STATUS       current
       DESCRIPTION
           "This objects indicates the type of IP address stored
            in the corresponding zxGponIpHostTestIpAddress object."
       DEFVAL { ipv4 }
       ::= { zxGponIpHostTestEntry 2 }
    zxGponIpHostTestIpAddress OBJECT-TYPE
       SYNTAX      InetAddress
       MAX-ACCESS  read-write
       STATUS      current
       DESCRIPTION
            "This attribute specifies the IP address of target."
       ::= { zxGponIpHostTestEntry 3 }
--IP host Ping Test result
    zxGponPingResultTable   OBJECT-TYPE
        SYNTAX      SEQUENCE OF ZxGponPingResultEntry
        MAX-ACCESS  not-accessible
        STATUS      current
        DESCRIPTION
            "Test result for IP host config data entity class,
             including ping and trace route."
        REFERENCE   "section A.3.39.4/G.988"
        ::= { zxGponRmTestMgmt 3 }
    zxGponPingResultEntry   OBJECT-TYPE
        SYNTAX      ZxGponPingResultEntry
        MAX-ACCESS  not-accessible
        STATUS      current
        DESCRIPTION
            "It is the entry of the zxGponPingResultTable."
        INDEX   { zxGponOltIndex, zxGponONTIndex, zxGponIPHostConfigDataId }
        ::= { zxGponPingResultTable 1 }

    ZxGponPingResultEntry ::= SEQUENCE {
            zxGponPingResultStatus                     INTEGER,
            zxGponPingResultSentProbes                 Integer32,
            zxGponPingResultProbeResponses             Integer32,
            zxGponPingResultMaxRtt                     Integer32,
            zxGponPingResultMinRtt                     Integer32,
            zxGponPingResultAverageRtt                 Integer32
        }
    zxGponPingResultStatus    OBJECT-TYPE
        SYNTAX      INTEGER {
            notStarted(1),
            inProgress(2),
            finished(3),
            failed(4)
        }
        MAX-ACCESS  read-only
        STATUS      current
        DESCRIPTION
            "This attribute specifies the status of Ping test.
             notStarted:The test is not started, and the result is unavailable.
             inProgress:The test is in progress, and the result is unavailable.
             finished:The test is in finished, and the result is available.
             failed:The test is failed,and the result is unavailable."
        ::= {zxGponPingResultEntry 1 }
    zxGponPingResultSentProbes OBJECT-TYPE
        SYNTAX      Integer32
        UNITS       "probes"
        MAX-ACCESS  read-only
        STATUS      current
        DESCRIPTION
            "The value of this object reflects the number of probes sent.
             The value of this object must be reported as 0 when no probes
             have been sent."
        ::= { zxGponPingResultEntry 2 }

    zxGponPingResultProbeResponses OBJECT-TYPE
        SYNTAX      Integer32
        UNITS       "responses"
        MAX-ACCESS  read-only
        STATUS      current
        DESCRIPTION
            "Number of responses received. The value of this object MUST be
             reported as 0 when no probe responses have been received."
        ::= { zxGponPingResultEntry 3 }
    zxGponPingResultMaxRtt OBJECT-TYPE
        SYNTAX      Integer32
        UNITS       "ms"
        MAX-ACCESS  read-only
        STATUS      current
        DESCRIPTION
            "The maximum ping round-trip-time (RTT) received. A value
             of 0 for this object implies that no RTT has been received."
        ::= { zxGponPingResultEntry 4 }
    zxGponPingResultMinRtt OBJECT-TYPE
        SYNTAX      Integer32
        UNITS       "ms"
        MAX-ACCESS  read-only
        STATUS      current
        DESCRIPTION
            "The minimum ping round-trip-time (RTT) received. A value
             of 0 for this object implies that no RTT has been received."
        ::= { zxGponPingResultEntry 5 }

    zxGponPingResultAverageRtt OBJECT-TYPE
        SYNTAX      Integer32
        UNITS       "ms"
        MAX-ACCESS  read-only
        STATUS      current
        DESCRIPTION
            "The average ping round-trip-time (RTT) received. A value
             of 0 for this object implies that no RTT has been received."
        ::= { zxGponPingResultEntry 6 }
--------------------------------------------------------------------------
-- 28. zxGponRmWanMgmt
-- 28.1 zxGponRmWanConfTable(WAN configuration data)
--------------------------------------------------------------------------
    zxGponRmWanConfTable    OBJECT-TYPE
        SYNTAX      SEQUENCE OF ZxGponRmWanConfEntry
        MAX-ACCESS  not-accessible
        STATUS      current
        DESCRIPTION
            "WAN configuration data table."
        REFERENCE   "Private ME: WAN configuration data"
        ::= { zxGponRmWanMgmt 2 }

    zxGponRmWanConfEntry OBJECT-TYPE
        SYNTAX      ZxGponRmWanConfEntry
        MAX-ACCESS  not-accessible
        STATUS      current
        DESCRIPTION
            "WAN configuration data entry.
            Entries in the zxGponRmWanConfTable are created and
            deleted using the zxGponRmWanConfRowStatus object."
        INDEX   { zxGponOltIndex, zxGponONTIndex, zxGponRmWanIndex }
        ::= { zxGponRmWanConfTable 1 }

    ZxGponRmWanConfEntry ::=
        SEQUENCE {
            zxGponRmWanIndex              Integer32,
            zxGponRmWanServiceType        BITS,
            zxGponRmWanAssociatedIpHostId Integer32,
            zxGponRmWanAssociatedEthUni   OCTET STRING,
            zxGponRmWanAssociatedSsid     OCTET STRING,
            zxGponRmWanMVid               Integer32,
            zxGponRmWanMtu                Integer32,
            zxGponRmWanOnlineDuration     Integer32,
            zxGponRmWanConfRowStatus      RowStatus
        }

    zxGponRmWanIndex   OBJECT-TYPE
        SYNTAX      Integer32(1..255)
        MAX-ACCESS  not-accessible
        STATUS      current
        DESCRIPTION
            "This attribute refers to the index of WAN."
        REFERENCE   "Private ME: WAN configuration data"
        ::= { zxGponRmWanConfEntry 1}

    zxGponRmWanServiceType OBJECT-TYPE
        SYNTAX      BITS{
                    internet(0),
                    tr069(1),
                    voip(2),
                    other(3)
                    }
        MAX-ACCESS  read-create
        STATUS      current
        DESCRIPTION
            "This attribute contains a bitmap of service type.
            1 indicates the service is transported over WAN.
            The bit position values are:
            bit0:Internet
            bit1:TR069 management
            bit2:VoIP
            bit3:other( current only IPTV)
            bit4~bit7:Reserved
            This attribute is mandatory."
        REFERENCE   "Private ME: WAN configuration data"
        ::= { zxGponRmWanConfEntry 2 }

    zxGponRmWanAssociatedIpHostId  OBJECT-TYPE
        SYNTAX      Integer32(0..255)
        MAX-ACCESS  read-create
        STATUS      current
        DESCRIPTION
            "The IP host WAN associated with.
            This attribute is related to 'zxGponRmWanServiceType'.
            This attribute is optional when 'zxGponRmWanServiceType' supports
            internet service.
            0 means not associated with IP host."
        REFERENCE   "Private ME: WAN configuration data"
        DEFVAL { 0 }
        ::= { zxGponRmWanConfEntry 3 }

    zxGponRmWanAssociatedEthUni OBJECT-TYPE
         SYNTAX     OCTET STRING(SIZE(2))
        MAX-ACCESS  read-create
        STATUS      current
        DESCRIPTION
            "This attribute contains a bitmap of Ethernet UNI associated
            with WAN.
            A bit value of 1 indicates the service of the Ethernet UNI
            is transported over WAN, and the default bit value is 0.
            The bit position values are:
            bit0:Ethernet UNI 1
            bit1:Ethernet UNI 2
            ...
            bit15:Ethernet UNI 16"
        REFERENCE   "Private ME: WAN configuration data"
        DEFVAL { '0000000000000000'H }
        ::= { zxGponRmWanConfEntry 4 }

    zxGponRmWanAssociatedSsid OBJECT-TYPE
         SYNTAX     OCTET STRING(SIZE(2))
        MAX-ACCESS  read-create
        STATUS      current
        DESCRIPTION
            "This attribute contains a bitmap of SSID associated
            with WAN.
            A bit value of 1 indicates the SSID service is transported over WAN,
            and the default bit value is 0.
            The bit position values are:
            bit0:SSID 1
            bit1:SSID 2
            ...
            bit15:SSID 16"
        REFERENCE   "Private ME: WAN configuration data"
        DEFVAL { 0 }
        ::= { zxGponRmWanConfEntry 5 }

    zxGponRmWanMVid     OBJECT-TYPE
        SYNTAX      Integer32(1..4094|65535)
        MAX-ACCESS  read-create
        STATUS      current
        DESCRIPTION
            "This attribute specifies the multicast VLAN associated with this
             WAN config data.
             This attribute is related to 'zxGponRmWanServiceType'.
             This attribute is valid only when 'zxGponRmWanServiceType' supports
             other service.
             And a value of 65535 indicates invalid or no need to take effect."
        REFERENCE   "Private ME: WAN configuration data"
        DEFVAL { 65535 }
        ::= { zxGponRmWanConfEntry 6 }

    zxGponRmWanMtu  OBJECT-TYPE
        SYNTAX      Integer32(64..2000|0)
        UNITS       "Bytes"
        MAX-ACCESS  read-create
        STATUS      current
        DESCRIPTION
            "This attribute specifies the MTU value.
             A value of 0 indicates ONU's internal default."
        REFERENCE   "Private ME: WAN configuration data"
        DEFVAL { 0 }
        ::= { zxGponRmWanConfEntry 7 }

    zxGponRmWanOnlineDuration     OBJECT-TYPE
        SYNTAX      Integer32
        UNITS       "Seconds"
        MAX-ACCESS  read-only
        STATUS      current
        DESCRIPTION
            "This attribute reports the time in second that this WAN is online."
        REFERENCE   "Private ME: WAN configuration data"
        ::= { zxGponRmWanConfEntry 8 }

    zxGponRmWanConfRowStatus OBJECT-TYPE
        SYNTAX      RowStatus
        MAX-ACCESS  read-create
        STATUS      current
        DESCRIPTION
            "The status of this conceptual row.

             To create a row in this table, a manager must
             set this object to createAndGo(4).

             To delete a row in this table, a manager must
             set this object to destroy(6).

             To query this object, always return 1. "
        ::= { zxGponRmWanConfEntry 50 }
--------------------------------------------------------------------------
-- 28.2 zxAnGponRmOnuWanConfTable(ONU WAN Control)
--------------------------------------------------------------------------
    zxAnGponRmOnuWanConfTable    OBJECT-TYPE
        SYNTAX      SEQUENCE OF ZxAnGponRmOnuWanConfEntry
        MAX-ACCESS  not-accessible
        STATUS      current
        DESCRIPTION
            "WAN global control table of ONU."
        REFERENCE   "Private ME"
        ::= { zxGponRmWanMgmt 3 }

    zxAnGponRmOnuWanConfEntry OBJECT-TYPE
        SYNTAX      ZxAnGponRmOnuWanConfEntry
        MAX-ACCESS  not-accessible
        STATUS      current
        DESCRIPTION
            "It is entry in the zxAnGponRmOnuWanConfTable."
        INDEX   { zxGponOltIndex, zxGponONTIndex }
        ::= { zxAnGponRmOnuWanConfTable 1 }

     ZxAnGponRmOnuWanConfEntry ::=
        SEQUENCE {
            zxAnGponRmOnuWanMaxUserNum   Integer32
        }

     zxAnGponRmOnuWanMaxUserNum OBJECT-TYPE
        SYNTAX      Integer32(0..255)
        MAX-ACCESS  read-write
        STATUS      current
        DESCRIPTION
            "This attribute identifies the maximum user number of WAN.
             The value 254 means the ONU's internal policy.
             The value 255 means no limit."
        REFERENCE   "Private ME"
        DEFVAL { 254 }
        ::= { zxAnGponRmOnuWanConfEntry 1 }

END
