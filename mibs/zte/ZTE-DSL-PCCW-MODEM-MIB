ZTE-DSL-PCCW-MODEM-MIB DEFINITIONS ::= BEGIN

    IMPORTS
        MODULE-IDENTITY, OBJECT-TYPE, NOTIFICATION-TYPE,
        Integer32, Counter64,TimeTicks,Counter32                    FROM SNMPv2-SMI

        DisplayString, TruthValue,
        MacAddress				FROM SNMPv2-TC

        MODULE-COMPLIANCE, OBJECT-GROUP         FROM SNMPv2-CONF
        ifIndex                                 FROM IF-MIB
        zxDsl                                   FROM ZTE-DSL-MIB;

    PortList ::= TEXTUAL-CONVENTION
        STATUS      current
        DESCRIPTION
            "Each octet within this value specifies a set of eight
            ports, with the first octet specifying ports 1 through
            8, the second octet specifying ports 9 through 16, etc.
            Within each octet, the most significant bit represents
            the lowest numbered port, and the least significant bit
            represents the highest numbered port.  Thus, each port
            of the bridge is represented by a single bit within the
            value of this object.  If that bit has a value of '1'
            then that port is included in the set of ports; the port
            is not included if its bit has a value of '0'."
        SYNTAX      OCTET STRING

    zxpccwModem MODULE-IDENTITY
        LAST-UPDATED    "0603060000Z"  -- March 06, 2006
        ORGANIZATION    "ZTE, Inc."
        CONTACT-INFO    "ZTE"

        DESCRIPTION     "ZTE Enterprise MIB definition."

        REVISION        "0603060000Z"  -- March 06, 2006
        DESCRIPTION     "Initial MIB creation."

        ::= { zxDsl 27 }

    zxpccwModemFWInfo            OBJECT IDENTIFIER ::= {zxpccwModem 1}
    zxpccwModemFWDownLoad            OBJECT IDENTIFIER ::= {zxpccwModem 2}


   	zxpccwModemFWInfoTable	OBJECT-TYPE
		SYNTAX		SEQUENCE  OF  zxpccwModemFWInfoEntry
		MAX-ACCESS	not-accessible
		STATUS		current
		DESCRIPTION	"The modem info table."
		::=  { zxpccwModemFWInfo  1 }

	zxpccwModemFWInfoEntry	OBJECT-TYPE
		SYNTAX		zxpccwModemFWInfoEntry
		MAX-ACCESS	not-accessible
		STATUS		current
		DESCRIPTION	""
		INDEX		{  ifIndex  }
		::=  { zxpccwModemFWInfoTable 1 }

	zxpccwModemFWInfoEntry  ::=  SEQUENCE {
		zxpccwCpeVendId  DisplayString,
		zxpccwCpeModel   DisplayString,
		zxpccwCpeFirmwareVersion  DisplayString
		}
	zxpccwCpeVendId	OBJECT-TYPE
		SYNTAX			DisplayString (SIZE(0..64))
		MAX-ACCESS		read-only
		STATUS			current
		DESCRIPTION		"The identifier of modem vender."
		::=  {  zxpccwModemFWInfoEntry  1  }
	zxpccwCpeModel	OBJECT-TYPE
		SYNTAX			DisplayString (SIZE(0..32))
		MAX-ACCESS		read-only
		STATUS			current
		DESCRIPTION		"The model of modem."
		::=  {  zxpccwModemFWInfoEntry  2  }
	zxpccwCpeFirmwareVersion	OBJECT-TYPE
		SYNTAX			DisplayString (SIZE(0..16))
		MAX-ACCESS		read-only
		STATUS			current
		DESCRIPTION		"The firmware vesion of modem."
		::=  {  zxpccwModemFWInfoEntry  3  }


   	zxpccwModemFWLoadRstTable	OBJECT-TYPE
		SYNTAX		SEQUENCE  OF  zxpccwModemFWLoadRstEntry
		MAX-ACCESS	not-accessible
		STATUS		current
		DESCRIPTION	"The results of loading firmware table."
		::=  { zxpccwModemFWInfo  2 }

	zxpccwModemFWLoadRstEntry	OBJECT-TYPE
		SYNTAX		zxpccwModemFWLoadRstEntry
		MAX-ACCESS	not-accessible
		STATUS		current
		DESCRIPTION	""
		INDEX		{  ifIndex  }
		::=  { zxpccwModemFWLoadRstTable 1 }

	zxpccwModemFWLoadRstEntry  ::=  SEQUENCE {
		zxpccwCpeTftpOperStatus  INTEGER
		}

	zxpccwCpeTftpOperStatus	OBJECT-TYPE
		SYNTAX			INTEGER
		MAX-ACCESS		read-only
		STATUS			current
		DESCRIPTION		"notStarted(1) - download has not yet started
                   inProgress(2) - download has not yet finished
                   success(3) - download has finished successfully
                   errorTftpSessionDown (4) - tftp session download
                   errorSysAuthFail (5) - modem password file put fail
                   erroSysFirmFail(6) - modem firmware file put fail
                   errorRebootFail(7)-modem reboot fail
                   errorPortLinkDown(8)– port link down
                   errorFault(9) - download has fault condition on device."
		::=  {  zxpccwModemFWLoadRstEntry  1  }

	zxpccwCpeTftpPortlist	OBJECT-TYPE
		SYNTAX			PortList
		MAX-ACCESS		read-write
		STATUS			current
		DESCRIPTION		"portlist in which to download fw"
		::=  {  zxpccwModemFWDownLoad  1  }

	zxpccwCpeVerAndPswdFileServerIP	OBJECT-TYPE
		SYNTAX			IpAddress
		MAX-ACCESS		read-write
		STATUS			current
		DESCRIPTION		"ftp server ip address"
		::=  {  zxpccwModemFWDownLoad  2  }

	zxpccwFtpUser	OBJECT-TYPE
		SYNTAX			DisplayString (SIZE(0..127))
		MAX-ACCESS		read-write
		STATUS			current
		DESCRIPTION		"ftp user name"
		::=  {  zxpccwModemFWDownLoad  3  }

	zxpccwFtpPswd	OBJECT-TYPE
		SYNTAX			DisplayString (SIZE(0..127))
		MAX-ACCESS		read-write
		STATUS			current
		DESCRIPTION		"ftp password"
		::=  {  zxpccwModemFWDownLoad  4  }

	zxpccwCpeFirmwareFileName	OBJECT-TYPE
		SYNTAX			DisplayString (SIZE(0..255))
		MAX-ACCESS		read-write
		STATUS			current
		DESCRIPTION		"fw file name in the ftp"
		::=  {  zxpccwModemFWDownLoad  5  }

	zxpccwCpePasswordFileName	OBJECT-TYPE
		SYNTAX			DisplayString (SIZE(0..255))
		MAX-ACCESS		read-write
		STATUS			current
		DESCRIPTION		"passowrd file name in the ftp"
		::=  {  zxpccwModemFWDownLoad  6  }

	zxpccwCpeRebootFileName	OBJECT-TYPE
		SYNTAX			DisplayString (SIZE(0..255))
		MAX-ACCESS		read-write
		STATUS			current
		DESCRIPTION		"reboot file name in the ftp"
		::=  {  zxpccwModemFWDownLoad  7  }

	zxpccwFirmwareFileNameToCpe	OBJECT-TYPE
		SYNTAX			DisplayString (SIZE(0..255))
		MAX-ACCESS		read-write
		STATUS			current
		DESCRIPTION		"fw file name save in the modem"
		::=  {  zxpccwModemFWDownLoad  8  }

	zxpccwPasswordFileNameToCpe	OBJECT-TYPE
		SYNTAX			DisplayString (SIZE(0..255))
		MAX-ACCESS		read-write
		STATUS			current
		DESCRIPTION		"passowrd file name saved in the modem"
		::=  {  zxpccwModemFWDownLoad  9  }

	zxpccwRebootFileNameToCpe	OBJECT-TYPE
		SYNTAX			DisplayString (SIZE(0..255))
		MAX-ACCESS		read-write
		STATUS			current
		DESCRIPTION		"reboot file name saved in the modem"
		::=  {  zxpccwModemFWDownLoad  10  }

	zxpccwCpeTftpAdminStatus	OBJECT-TYPE
		SYNTAX			INTEGER
		MAX-ACCESS		read-write
		STATUS			current
		DESCRIPTION		"download action
                  1 : ftp command from CLI
                  2 : ftp command from NMS."
		::=  {  zxpccwModemFWDownLoad  11  }

	zxpccwCpeTftpFinishPortlist	OBJECT-TYPE
		SYNTAX			PortList
		MAX-ACCESS		read-only
		STATUS			current
		DESCRIPTION		"Download fw fininsh/not in each port"
		::=  {  zxpccwModemFWDownLoad  12  }

	zxpccwCpeTftpResultPortlist	OBJECT-TYPE
		SYNTAX			PortList
		MAX-ACCESS		read-only
		STATUS			current
		DESCRIPTION		"Download fw success/fail in each port"
		::=  {  zxpccwModemFWDownLoad  13 }

	zxpccwCpeFtpOperStatus	OBJECT-TYPE
		SYNTAX			INTEGER
		MAX-ACCESS		read-only
		STATUS			current
		DESCRIPTION		"notStarted(1)           -- ftp has not yet started;
                   inProgress(2)           -- ftp has not yet finished;
                   success(3)              -- ftp has finished successfully;
                   fail(4)            -- ftp fail
                   lost command(5) – ftp command from NMS been lost."
		::=  {  zxpccwModemFWDownLoad  14  }

	zxpccwCpeMptResult	OBJECT-TYPE
		SYNTAX			INTEGER
		MAX-ACCESS		read-only
		STATUS			current
		DESCRIPTION		"success(1)-- success;
                   paraError(2)--input parameter error;
                   createFileError(3)--Create file in ramdisk error;
                   inProgressError(4)--Last downloading not over;
                   downToCscError(5)--Down version  to csc error;
                   delFileError(6)--Delete file in ramdisk error."
		::=  {  zxpccwModemFWDownLoad  15  }

    zxpccwCpeActualModel	OBJECT-TYPE
		SYNTAX			DisplayString (SIZE(0..32))
		MAX-ACCESS		read-write
		STATUS			current
		DESCRIPTION		"The actual model of modem."
		::=  {  zxpccwModemFWDownLoad  16  }

    zxpccwCpeActualFirmwareVersion	OBJECT-TYPE
		SYNTAX			DisplayString (SIZE(0..16))
		MAX-ACCESS		read-write
		STATUS			current
		DESCRIPTION		"The actual firmware vesion of modem."
		::=  {  zxpccwModemFWDownLoad  17  }
END
