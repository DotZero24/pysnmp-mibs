-- *****************************************************************
-- File Name : ZXR10-IF-MIB.mib
-- Date      : 2008-04-02
-- Author    : zhongyan ZTE Nms dept.
--
-- Copyright (c) 1985-2008 by ZTE Corp.
-- All rights reserved.
-- *****************************************************************
ZXR10-IF-MIB DEFINITIONS ::= BEGIN
  IMPORTS
          OBJECT-TYPE, Integer32                          FROM SNMPv2-SMI
          DisplayString, RowStatus, TEXTUAL-CONVENTION    FROM SNMPv2-TC
          zxr10interfaces                                 FROM ZXR10-SMI;

-------------------------------------------------------------------------------
-- Textual conventions
-------------------------------------------------------------------------------
    ListStatus ::= TEXTUAL-CONVENTION
        STATUS  current
        DESCRIPTION
            ""
        SYNTAX  INTEGER
        {
            disable(0),
            enable(1)
        }

    CipPriorityValue ::= TEXTUAL-CONVENTION
        STATUS  current
        DESCRIPTION
            ""
        SYNTAX  INTEGER
        {
            disable(0),
            enable(1)
        }

------------------------------------------------------------------------------
-- 1.zxr10 Uni Table
------------------------------------------------------------------------------
    zxr10UniTable OBJECT-TYPE
        SYNTAX      SEQUENCE OF Zxr10UniEntry
        MAX-ACCESS  not-accessible
        STATUS      current
        DESCRIPTION
            "A list of uni interface information."
        ::= { zxr10interfaces 4 }

    zxr10UniEntry OBJECT-TYPE
        SYNTAX      Zxr10UniEntry
        MAX-ACCESS  not-accessible
        STATUS      current
        DESCRIPTION
            "An entry to uni interface table."
        INDEX  { zxr10UniId }
        ::= { zxr10UniTable 1 }

    Zxr10UniEntry ::= SEQUENCE {
        zxr10UniId          Integer32,
        zxr10UniName        DisplayString,
        zxr10UniDesciption  DisplayString,
        zxr10UniBindIfName  DisplayString,
        zxr10UniBindIfIndex Integer32,
        zxr10UniLstStatus   ListStatus,
        zxr10UniRowStatus   RowStatus
        }

    zxr10UniId  OBJECT-TYPE
        SYNTAX      Integer32
        MAX-ACCESS  not-accessible
        STATUS      current
        DESCRIPTION
            ""
        ::= { zxr10UniEntry 1 }

    zxr10UniName  OBJECT-TYPE
        SYNTAX      DisplayString
        MAX-ACCESS  read-only
        STATUS      current
        DESCRIPTION
            ""
        ::= { zxr10UniEntry 2 }

    zxr10UniDesciption  OBJECT-TYPE
        SYNTAX      DisplayString
        MAX-ACCESS  read-write
        STATUS      current
        DESCRIPTION
            ""
        ::= { zxr10UniEntry 3 }

    zxr10UniBindIfName  OBJECT-TYPE
        SYNTAX      DisplayString
        MAX-ACCESS  read-write
        STATUS      current
        DESCRIPTION
            ""
        ::= { zxr10UniEntry 4 }

    zxr10UniBindIfIndex  OBJECT-TYPE
        SYNTAX      Integer32
        MAX-ACCESS  read-only
        STATUS      current
        DESCRIPTION
            ""
        ::= { zxr10UniEntry 5 }

    zxr10UniLstStatus  OBJECT-TYPE
        SYNTAX      ListStatus
        MAX-ACCESS  read-write
        STATUS      current
        DESCRIPTION
            ""
        ::= { zxr10UniEntry 6 }

    zxr10UniRowStatus OBJECT-TYPE
        SYNTAX      RowStatus
        MAX-ACCESS  read-write
        STATUS      current
        DESCRIPTION
            ""
        ::= { zxr10UniEntry 7 }

------------------------------------------------------------------------------
-- 2.zxr10 Cip Table
------------------------------------------------------------------------------
    zxr10CipTable  OBJECT-TYPE
        SYNTAX      SEQUENCE OF Zxr10CipEntry
        MAX-ACCESS  not-accessible
        STATUS      current
        DESCRIPTION
            "A list of cip interface information."
        ::= { zxr10interfaces 5 }

    zxr10CipEntry  OBJECT-TYPE
        SYNTAX      Zxr10CipEntry
        MAX-ACCESS  not-accessible
        STATUS      current
        DESCRIPTION
            "An entry to cip interface table."
        INDEX  { zxr10CipId }
        ::= { zxr10CipTable 1 }

    Zxr10CipEntry ::= SEQUENCE {
        zxr10CipId              Integer32,
        zxr10CipName            DisplayString,
        zxr10CipDesciption      DisplayString,
        zxr10CipType            Integer32,
        zxr10CipBindName        DisplayString,
        zxr10CipBindIdOrIfIndex Integer32,
        zxr10CipAdminStatus     INTEGER,
        zxr10CipPhyStatus       INTEGER,
        zxr10CipProStatus       INTEGER,
        zxr10CipDetectStatus    INTEGER,
        zxr10CipRowStatus       RowStatus,
        zxr10CipServiceIndex    Integer32,
        zxr10CipPriority        CipPriorityValue,
        zxr10CipStackId         Integer32,
        zxr10CipQingTerminal    Integer32,
        zxr10CipStructure       INTEGER,
        zxr10CipIdleCode        Integer32,
        zxr10CipVcType          INTEGER,
        zxr10CipAu3             Integer32,
        zxr10CipAu4             Integer32,
        zxr10CipTug2            Integer32,
        zxr10CipTug3            Integer32,
        zxr10CipVcId            Integer32,
        zxr10CipTimeslots       DisplayString,
        zxr10CipClassMapName    DisplayString,
        zxr10CipBindVpnStatus   INTEGER
        }

    zxr10CipId  OBJECT-TYPE
        SYNTAX      Integer32
        MAX-ACCESS  not-accessible
        STATUS      current
        DESCRIPTION
            ""
        ::= { zxr10CipEntry 1 }

    zxr10CipName  OBJECT-TYPE
        SYNTAX      DisplayString
        MAX-ACCESS  read-only
        STATUS      current
        DESCRIPTION
            ""
        ::= { zxr10CipEntry 2 }

    zxr10CipDesciption  OBJECT-TYPE
        SYNTAX      DisplayString
        MAX-ACCESS  read-write
        STATUS      current
        DESCRIPTION
            ""
        ::= { zxr10CipEntry 3 }

    zxr10CipType  OBJECT-TYPE
        SYNTAX      Integer32
        MAX-ACCESS  read-write
        STATUS      current
        DESCRIPTION
            ""
        ::= { zxr10CipEntry 4 }

    zxr10CipBindName  OBJECT-TYPE
        SYNTAX      DisplayString
        MAX-ACCESS  read-write
        STATUS      current
        DESCRIPTION
            ""
        ::= { zxr10CipEntry 5 }

    zxr10CipBindIdOrIfIndex  OBJECT-TYPE
        SYNTAX      Integer32
        MAX-ACCESS  read-only
        STATUS      current
        DESCRIPTION
            ""
        ::= { zxr10CipEntry 6 }

    zxr10CipAdminStatus OBJECT-TYPE
        SYNTAX      INTEGER{up(0),down(1)}
        MAX-ACCESS  read-create
        STATUS      current
        DESCRIPTION
            ""
        ::= { zxr10CipEntry 7 }

    zxr10CipPhyStatus  OBJECT-TYPE
        SYNTAX      INTEGER{up(0),down(1)}
        MAX-ACCESS  read-only
        STATUS      current
        DESCRIPTION
            ""
        ::= { zxr10CipEntry 8 }

    zxr10CipProStatus  OBJECT-TYPE
        SYNTAX      INTEGER{up(0),down(1)}
        MAX-ACCESS  read-only
        STATUS      current
        DESCRIPTION
            ""
        ::= { zxr10CipEntry 9 }

    zxr10CipDetectStatus OBJECT-TYPE
        SYNTAX      INTEGER{ok(0),sf(1),sd(2)}
        MAX-ACCESS  read-only
        STATUS      current
        DESCRIPTION
            ""
        ::= { zxr10CipEntry 10 }

    zxr10CipRowStatus  OBJECT-TYPE
        SYNTAX      RowStatus
        MAX-ACCESS  read-create
        STATUS      current
        DESCRIPTION
            ""
        ::= { zxr10CipEntry 11 }

    zxr10CipServiceIndex  OBJECT-TYPE
        SYNTAX      Integer32
        MAX-ACCESS  read-only
        STATUS      current
        DESCRIPTION
            ""
        ::= { zxr10CipEntry 12 }

    zxr10CipPriority  OBJECT-TYPE
        SYNTAX      CipPriorityValue
        MAX-ACCESS  read-write
        STATUS      current
        DESCRIPTION
            ""
        ::= { zxr10CipEntry 13 }

    zxr10CipStackId  OBJECT-TYPE
        SYNTAX      Integer32
        MAX-ACCESS  read-only
        STATUS      current
        DESCRIPTION
            ""
        ::= { zxr10CipEntry 14 }

    zxr10CipQingTerminal  OBJECT-TYPE
        SYNTAX      Integer32
        MAX-ACCESS  read-only
        STATUS      current
        DESCRIPTION
            ""
        ::= { zxr10CipEntry 15}

    zxr10CipStructure  OBJECT-TYPE
        SYNTAX      INTEGER{agnostic(0),aware(1)}
        MAX-ACCESS  read-write
        STATUS      current
        DESCRIPTION
            ""
        ::= { zxr10CipEntry 16}

    zxr10CipIdleCode  OBJECT-TYPE
        SYNTAX      Integer32
        MAX-ACCESS  read-write
        STATUS      current
        DESCRIPTION
            ""
        ::= { zxr10CipEntry 17}

    zxr10CipVcType  OBJECT-TYPE
        SYNTAX      INTEGER{e1(0),t1(1)}
        MAX-ACCESS  read-write
        STATUS      current
        DESCRIPTION
            ""
        ::= { zxr10CipEntry 18}

    zxr10CipAu3  OBJECT-TYPE
        SYNTAX      Integer32
        MAX-ACCESS  read-write
        STATUS      current
        DESCRIPTION
            ""
        ::= { zxr10CipEntry 19}

    zxr10CipAu4  OBJECT-TYPE
        SYNTAX      Integer32
        MAX-ACCESS  read-write
        STATUS      current
        DESCRIPTION
            ""
        ::= { zxr10CipEntry 20}

    zxr10CipTug2     OBJECT-TYPE
        SYNTAX      Integer32
        MAX-ACCESS  read-write
        STATUS      current
        DESCRIPTION
            ""
        ::= { zxr10CipEntry 21}

    zxr10CipTug3     OBJECT-TYPE
        SYNTAX      Integer32
        MAX-ACCESS  read-write
        STATUS      current
        DESCRIPTION
            ""
        ::= { zxr10CipEntry 22}

    zxr10CipVcId    OBJECT-TYPE
        SYNTAX      Integer32
        MAX-ACCESS  read-write
        STATUS      current
        DESCRIPTION
            ""
        ::= { zxr10CipEntry 23}

    zxr10CipTimeslots    OBJECT-TYPE
        SYNTAX      DisplayString
        MAX-ACCESS  read-write
        STATUS      current
        DESCRIPTION
            ""
        ::= { zxr10CipEntry 24}

    zxr10CipClassMapName    OBJECT-TYPE
        SYNTAX      DisplayString
        MAX-ACCESS  read-create
        STATUS      current
        DESCRIPTION
            ""
        ::= { zxr10CipEntry 25}

    zxr10CipBindVpnStatus OBJECT-TYPE
        SYNTAX      INTEGER
        {
            no(1),
            yes(2)
        }
        MAX-ACCESS  read-only
        STATUS      current
        DESCRIPTION
            "It indicates whether AC has been bound to VPN or not,
            no by default."
        DEFVAL {no}
        ::= { zxr10CipEntry 26}

------------------------------------------------------------------------------
-- 3.zxr10 Ces Table
------------------------------------------------------------------------------
    zxr10CesTable  OBJECT-TYPE
        SYNTAX  SEQUENCE OF Zxr10CesEntry
        MAX-ACCESS  not-accessible
        STATUS  current
        DESCRIPTION
            "A list of ces interface information."
        ::= { zxr10interfaces 6 }

    zxr10CesEntry  OBJECT-TYPE
        SYNTAX  Zxr10CesEntry
        MAX-ACCESS  not-accessible
        STATUS  current
        DESCRIPTION
            "An entry to ces interface table."
        INDEX  { zxr10CesId }
        ::= { zxr10CesTable 1 }

    Zxr10CesEntry ::= SEQUENCE {
        zxr10CesId            Integer32,
        zxr10CesName          DisplayString,
        zxr10CesDesciption    DisplayString,
        zxr10CesE1Name        DisplayString,
        zxr10CesE1IfIndex     Integer32,
        zxr10CesAal1          Integer32,
        zxr10CesRowStatus     RowStatus,
        zxr10CesServiceIndex  Integer32
        }

    zxr10CesId  OBJECT-TYPE
        SYNTAX   Integer32
        MAX-ACCESS  not-accessible
        STATUS  current
        DESCRIPTION
            ""
        ::= { zxr10CesEntry 1 }

    zxr10CesName  OBJECT-TYPE
        SYNTAX   DisplayString
        MAX-ACCESS  read-only
        STATUS  current
        DESCRIPTION
            ""
        ::= { zxr10CesEntry 2 }

    zxr10CesDesciption  OBJECT-TYPE
        SYNTAX   DisplayString
        MAX-ACCESS  read-write
        STATUS  current
        DESCRIPTION
            ""
        ::= { zxr10CesEntry 3 }

    zxr10CesE1Name  OBJECT-TYPE
        SYNTAX   DisplayString
        MAX-ACCESS  read-write
        STATUS  current
        DESCRIPTION
            ""
        ::= { zxr10CesEntry 4 }

    zxr10CesE1IfIndex  OBJECT-TYPE
        SYNTAX   Integer32
        MAX-ACCESS  read-write
        STATUS  current
        DESCRIPTION
            ""
        ::= { zxr10CesEntry 5 }

    zxr10CesAal1  OBJECT-TYPE
        SYNTAX   Integer32
        MAX-ACCESS  read-write
        STATUS  current
        DESCRIPTION
            ""
        ::= { zxr10CesEntry 6 }

    zxr10CesRowStatus  OBJECT-TYPE
        SYNTAX   RowStatus
        MAX-ACCESS  read-write
        STATUS  current
        DESCRIPTION
            ""
        ::= { zxr10CesEntry 7 }

    zxr10CesServiceIndex  OBJECT-TYPE
        SYNTAX   Integer32
        MAX-ACCESS  read-only
        STATUS  current
        DESCRIPTION
            ""
        ::= { zxr10CesEntry 8 }
END
