ZXPW-TDM-EXT-MIB DEFINITIONS ::= BEGIN

IMPORTS
  MODULE-IDENTITY, OBJECT-TYPE,
  Integer32, Unsigned32
     FROM SNMPv2-SMI

  TEXTUAL-CONVENTION
     FROM SNMPv2-TC

  DisplayString
     FROM RFC1213-MIB

  zxPwIndex
     FROM ZXPW-STD-MIB

  zxPwCTDM
      FROM ZTE-MASTER-MIB

  IANAPwTypeTC
     FROM ZX-PWE3-MIB
  ;

-- The TDM Extended MIB

    zxPwTDMExtMIB MODULE-IDENTITY
        LAST-UPDATED "200812090000Z"  -- Dec 9, 2008
        ORGANIZATION    "Zhongxing Telcom Co. Ltd."
        CONTACT-INFO    "Zhongxing Telcom Co. Ltd.
                         E-mail: info@mail.zte.com.cn
                         http  : www.zte.com.cn or www.zhongxing.com"

        DESCRIPTION
            "This MIB contains managed object definitions for
             encapsulating TDM (NxDS0) as pseudo-wires over
             packet-switching networks (PSN).

             This MIB supplements the ZXPW-STD-MIB as in: Zelig, D.,
             Nadeau,T. 'Pseudo Wire (PW) Management Information Base'.
             The ZXPW-STD-MIB contains structures and MIB associations
             generic to Pseudo-Wire (PW) emulation. PW-specific
             MIBs (such as this) contain config and stats for specific
             PW types.
            "
        ::= { zxPwCTDM 11 }

-- Local Textual conventions
    PwTDMCfgIndex ::= TEXTUAL-CONVENTION
        STATUS      current
        DESCRIPTION
           "Index into any of the relevant pwCXXXCfgTable."
        SYNTAX      Unsigned32

-- Notifications
-- pwTDMExtNotifications OBJECT IDENTIFIER ::= { pwTDMExtMIB 0 }

-- Tables, Scalars
zxPwTDMExtObjects       OBJECT IDENTIFIER ::= { zxPwTDMExtMIB 1 }

-- Conformance
-- pwCTDMExtConformance   OBJECT IDENTIFIER ::= { pwTDMExtMIB 2 }

-- TDM Extended Card table
    zxPwTDMExtCardTable  OBJECT-TYPE
        SYNTAX      SEQUENCE OF ZxPwTDMExtCardEntry
        MAX-ACCESS  not-accessible
        STATUS      current
        DESCRIPTION
             "This table provides one row for each CES Card."
        ::= {zxPwTDMExtObjects 1}

    zxPwTDMExtCardEntry  OBJECT-TYPE
        SYNTAX      ZxPwTDMExtCardEntry
        MAX-ACCESS  not-accessible
        STATUS      current
        DESCRIPTION
            "CES Card information entry"
        INDEX    { zxPwTDMExtRack,zxPwTDMExtShelf,zxPwTDMExtSlot  }
        ::= {zxPwTDMExtCardTable 1}

    ZxPwTDMExtCardEntry ::=
        SEQUENCE {
            zxPwTDMExtRack                  Integer32,
            zxPwTDMExtShelf                 Integer32,
            zxPwTDMExtSlot                  Integer32,
            zxPwTDMExtTDMType               INTEGER,
            zxPwTDMExtTransmitClockSource   INTEGER,
            zxPwTDMExtPrimaryClock          INTEGER,
            zxPwTDMExtSecondaryClock        INTEGER,
            zxPwTDMExtPwType                IANAPwTypeTC,
            zxPwTDMExtReferenceClockSource  INTEGER,
            zxPwTDMExtServiceClockSource    INTEGER,
            zxPwTDMExtServiceClockE1No      Integer32
        }

    zxPwTDMExtRack  OBJECT-TYPE
        SYNTAX      Integer32
        MAX-ACCESS  not-accessible
        STATUS      current
        DESCRIPTION
             "Rack number."
        ::= { zxPwTDMExtCardEntry 1 }

    zxPwTDMExtShelf  OBJECT-TYPE
        SYNTAX      Integer32
        MAX-ACCESS  not-accessible
        STATUS      current
        DESCRIPTION
             "Shelf number."
        ::= { zxPwTDMExtCardEntry 2 }

    zxPwTDMExtSlot  OBJECT-TYPE
        SYNTAX      Integer32
        MAX-ACCESS  not-accessible
        STATUS      current
        DESCRIPTION
             "Slot number."
        ::= { zxPwTDMExtCardEntry 3 }

    zxPwTDMExtTDMType OBJECT-TYPE
        SYNTAX       INTEGER
        {
            udt(1),
            sdtMaster(2),
            sdtSlave(3),
            unconfigured (9)
        }
        MAX-ACCESS    read-write
        STATUS        current
        DESCRIPTION
            "This variable indicates the TDM type of the card."
        REFERENCE
            "Used by MAP"
        ::= { zxPwTDMExtCardEntry 4 }

    zxPwTDMExtTransmitClockSource OBJECT-TYPE
        SYNTAX      INTEGER
        {
            loopTiming(1),
            localTiming(2),
            throughTiming(3),
            adaptive(4),
            enhancedAdaptive (5),
            differential(6),
            lineTiming(7),
            wanderOptimalAdaptive(8)
        }
        MAX-ACCESS  read-write
        STATUS      current
        DESCRIPTION
            "'loopTiming' indicates that the recovered receive clock is used as
             the transmit clock.

             'localTiming' indicates that a local clock source is used or when
             an external clock is attached to the box containing the interface.

             'throughTiming' indicates that recovered receive clock from another
             interface is used as the transmit clock.

             'adaptive' indicates that the clock is recovered based on the data
             flow and not based on the physical layer.

             'differential' indicates that recovered clock by using the
             information if packet and common reference clock.

             'enhanced-adaptive' are customed values.

             'lineTiming' indicates that recovered clock from E1/T1 Interface.

             'wanderOptimalAdaptive' indicate an alogrithm that is different
             from 'adaptive'. This alogrithm optimizes the wander of clock, but
             needs more time to recover the clock."
        ::= { zxPwTDMExtCardEntry 5 }

    zxPwTDMExtPrimaryClock OBJECT-TYPE
        SYNTAX      INTEGER (1..8)
        MAX-ACCESS  read-write
        STATUS      current
        DESCRIPTION
            "Primary clock source position."
        DEFVAL { 1 }
        ::= { zxPwTDMExtCardEntry 6 }

    zxPwTDMExtSecondaryClock OBJECT-TYPE
        SYNTAX      INTEGER (1..8)
        MAX-ACCESS  read-write
        STATUS      current
        DESCRIPTION
            "Secondary clock source position."
        DEFVAL { 2 }
        ::= { zxPwTDMExtCardEntry 7 }

    zxPwTDMExtPwType OBJECT-TYPE
        SYNTAX      IANAPwTypeTC
        MAX-ACCESS  read-write
        STATUS      current
        DESCRIPTION
            "Indicates the PW type (i.e. the carried service).
             Used by F829 Ne."
        ::= { zxPwTDMExtCardEntry 8 }

    zxPwTDMExtReferenceClockSource OBJECT-TYPE
        SYNTAX      INTEGER
        {
            packet(1),
            line(2)
        }
        MAX-ACCESS  read-write
        STATUS      current
        DESCRIPTION
            "The reference clock source type.
             packet(1) -- Getting the reference clock source from network side
                          packet.
             line(2)   -- Getting the reference clock source from user side
                          line.
            "
        DEFVAL  { packet }
        ::= { zxPwTDMExtCardEntry 9 }

    zxPwTDMExtServiceClockSource OBJECT-TYPE
        SYNTAX      INTEGER
        {
            internalClock(1),
            e1Clock(2)
        }
        MAX-ACCESS  read-write
        STATUS      current
        DESCRIPTION
            "The service clock source type.
             internalClock(1) -- Getting the clock source from internal.
             e1Clock(2)       -- Getting the clock source from E1 interface.
            "
        REFERENCE
            "Used by 9806 serial DSLAM"
        ::= { zxPwTDMExtCardEntry 10 }

    zxPwTDMExtServiceClockE1No OBJECT-TYPE
        SYNTAX      Integer32
        MAX-ACCESS  read-write
        STATUS      current
        DESCRIPTION
            "The E1 port number. It will be valid when
             zxPwTDMExtServiceClockSource is set to e1Clock(2).
            "
        REFERENCE
            "Used by 9806 serial DSLAM"
        ::= { zxPwTDMExtCardEntry 11 }

-- End of TDM Extended Card table

-- TDM PW Extended table

    zxPwTDMExtTable OBJECT-TYPE
        SYNTAX        SEQUENCE OF ZxPwTDMExtEntry
        MAX-ACCESS    not-accessible
        STATUS        current
        DESCRIPTION
            "This table contains basic information including ifIndex,
             and pointers to entries in the relevant TDM config
             tables for this TDM PW."
        ::= { zxPwTDMExtObjects 2 }

    zxPwTDMExtEntry OBJECT-TYPE
        SYNTAX        ZxPwTDMExtEntry
        MAX-ACCESS    not-accessible
        STATUS        current
        DESCRIPTION
            "This table is indexed by the same index that was
             created for the associated entry in the PW Table
             (in the ZXPW-STD-MIB).
             - The zxPwIndex."
        INDEX  { zxPwIndex }
        ::= { zxPwTDMExtTable 1 }

    ZxPwTDMExtEntry ::= SEQUENCE {
         zxPwTDMExtHWNo                  Integer32,
         zxPwTDMExtTSList                DisplayString,
         zxPwExtGenTDMCfgIndex           PwTDMCfgIndex,
         zxPwTDMExtFramesPerPacket       INTEGER
    }

    zxPwTDMExtHWNo OBJECT-TYPE
        SYNTAX     Integer32
        MAX-ACCESS    read-write
        STATUS        current
        DESCRIPTION
            "The parameter represents the HW number related with this PW.
             Only used in SDT type."
        REFERENCE
            "Used by MAP"
        ::= { zxPwTDMExtEntry 1 }

    zxPwTDMExtTSList OBJECT-TYPE
        SYNTAX      DisplayString
        MAX-ACCESS  read-write
        STATUS      current
        DESCRIPTION
            "The 64k time slots related with this PW.Only used in SDT type.
            For example: 1-6,8,20-25"
        REFERENCE
            "Used by MAP"
        ::= { zxPwTDMExtEntry 2 }

    zxPwExtGenTDMCfgIndex OBJECT-TYPE
        SYNTAX        PwTDMCfgIndex
        MAX-ACCESS    read-write
        STATUS        current
        DESCRIPTION
            "Index to the generic parameters in the TDM configuration
             table that appears in this MIB module. It is likely that
             multiple TDM PWs of the same characteristic will share
             a single TDM Cfg entry."
        REFERENCE
            "Used by MAP"
        ::= { zxPwTDMExtEntry 3 }

    zxPwTDMExtFramesPerPacket OBJECT-TYPE
        SYNTAX      INTEGER(1..20)
        MAX-ACCESS  read-write
        STATUS      current
        DESCRIPTION
            "The number of the trunk frames per packet."
        DEFVAL { 1 }
        ::= { zxPwTDMExtEntry 4 }

-- End of TDM PW table


END
