-------------------------------------------------------------------------------
-- File Name : ZTE-AN-IEEE1588-MIB.mib
-- Date      : 2011-01-26
-- Author    : ZTE Shanghai NMS Dept.
--
-- ZTE CPE Version MIB for Access Node.
--
-------------------------------------------------------------------------------

ZTE-AN-IEEE1588-MIB DEFINITIONS ::= BEGIN

IMPORTS
    MODULE-IDENTITY, OBJECT-TYPE, NOTIFICATION-TYPE,
    IpAddress, TimeTicks, Integer32, Counter32,
    Gauge32, Counter64                              FROM SNMPv2-SMI
    RowStatus, TruthValue, DisplayString,
    TEXTUAL-CONVENTION                              FROM SNMPv2-TC
    SnmpAdminString                                 FROM SNMP-FRAMEWORK-MIB
    InetAddress,InetAddressType                     FROM INET-ADDRESS-MIB
    zxAn                                            FROM ZTE-AN-TC-MIB;

zxAnIeee1588Mib MODULE-IDENTITY
    LAST-UPDATED "201101261500Z"
    ORGANIZATION "ZTE Corporation"
    CONTACT-INFO "zhangzhikun
                  Mail: zhang.zhikun@zte.com.cn
                  Tel : 021-68895557"
    DESCRIPTION  "The MIB module for the management of IEEE1588 ."
    ::= {zxAn 66}

-------------------------------------------------------------------------------
-- Following management objects are defined.
-- 1. PTP Management : zxAnPtpTable
-- 2. PTP Management : zxAnPtpRemoteSrcTable
-- 3. Synchronization Time Management: zxAnSyncTime1ppsSrcTable
-- 4. Synchronization Time Management: zxAnSyncTimeTodSrcTable
-- 5. Synchronization Time Management: zxAnSyncTimeOutputPortTable
-------------------------------------------------------------------------------
zxAnPtpMgmt             OBJECT IDENTIFIER ::= {zxAnIeee1588Mib 1}
zxAnSyncTimeClkSrcMgmt  OBJECT IDENTIFIER ::= {zxAnIeee1588Mib 2}
-------------------------------------------------------------------------------
-- 1. PTP Management : zxAnPtpTable
-------------------------------------------------------------------------------
    zxAnPtpTable   OBJECT-TYPE
        SYNTAX      SEQUENCE  OF  ZxAnPtpEntry
        MAX-ACCESS  not-accessible
        STATUS      current
        DESCRIPTION "This table includes PTP configuration information in NE
                    equipment."
        ::=  { zxAnPtpMgmt 2 }

    zxAnPtpEntry   OBJECT-TYPE
        SYNTAX      ZxAnPtpEntry
        MAX-ACCESS  not-accessible
        STATUS      current
        DESCRIPTION "An entry in zxAnPtpTable."
        INDEX   {zxAnPtpRack,zxAnPtpShelf,
                zxAnPtpSlot,zxAnPtpId}
        ::=  { zxAnPtpTable 1 }

    ZxAnPtpEntry  ::=  SEQUENCE {
        zxAnPtpRack                      Integer32,
        zxAnPtpShelf                     Integer32,
        zxAnPtpSlot                      Integer32,
        zxAnPtpId                        Integer32,
        zxAnPtpClockType                 INTEGER,
        zxAnPtpSlaveOnly                 TruthValue,
        zxAnPtpDomainNumber              Integer32,
        zxAnPtpProtocolIpAddrType        InetAddressType,
        zxAnPtpProtocolIpAddress         InetAddress,
        zxAnPtpEthWorkMode               INTEGER,
        zxAnPtpPacketsMode               INTEGER,
        zxAnPtpTwoStepFlag               TruthValue,
        zxAnPtpSendPacketsRate           Integer32,
        zxAnPtpClockStatus               INTEGER,
        zxAnPtpUtcTime                   DisplayString,
        zxAnPtpRowStatus                 RowStatus
        }

    zxAnPtpRack  OBJECT-TYPE
        SYNTAX      Integer32
        MAX-ACCESS  not-accessible
        STATUS      current
        DESCRIPTION
            "This object indicates the rack number."
        ::= { zxAnPtpEntry 1 }

    zxAnPtpShelf  OBJECT-TYPE
        SYNTAX      Integer32
        MAX-ACCESS  not-accessible
        STATUS      current
        DESCRIPTION
            "This object indicates the shelf number."
        ::= { zxAnPtpEntry 2 }

    zxAnPtpSlot  OBJECT-TYPE
        SYNTAX      Integer32
        MAX-ACCESS  not-accessible
        STATUS      current
        DESCRIPTION
            "This object indicates the slot number."
        ::= { zxAnPtpEntry 3 }

    zxAnPtpId  OBJECT-TYPE
        SYNTAX      Integer32(1..4)
        MAX-ACCESS  not-accessible
        STATUS      current
        DESCRIPTION
            "The PTP node ID."
        ::= { zxAnPtpEntry 4 }

    zxAnPtpClockType OBJECT-TYPE
        SYNTAX        INTEGER
        {
            ordinary(1),
            boundary(2)
        }
        MAX-ACCESS    read-create
        STATUS        current
        DESCRIPTION
            "The value of clock type shall indicate the type of PTP node
             as defined in table 42 of IEEE1588-2008."
        REFERENCE
            "Clause 15.5.3.1.2.1 of IEEE1588-2008"
        DEFVAL { ordinary }
        ::= { zxAnPtpEntry 5 }

    zxAnPtpSlaveOnly OBJECT-TYPE
        SYNTAX         TruthValue
        MAX-ACCESS     read-create
        STATUS         current
        DESCRIPTION
            "The value of defaultDS.slaveOnly shall be TRUE if the clock
             is a slave-only clock; see 9.2.2.
             The value shall be FALSE if the clock is a non-slave-only
             clock;
             see 9.2.3 of IEEE1588-2008."
        REFERENCE
            "Clause 8.2.1.4.4, IEEE1588-2008"
        DEFVAL { true }
        ::= { zxAnPtpEntry 6 }

    zxAnPtpDomainNumber OBJECT-TYPE
        SYNTAX         Integer32(0..255)
        MAX-ACCESS     read-create
        STATUS  current
        DESCRIPTION
            "The value of defaultDS.domainNumber is the domain attribute
            (see 7.1 of IEEE1588-2008) of the local clock.
             Value 0 indicates the default domain."
        REFERENCE
            "Clause 8.2.1.4.3, IEEE1588-2008"
        DEFVAL { 0 }
        ::= { zxAnPtpEntry 7 }

    zxAnPtpProtocolIpAddrType OBJECT-TYPE
        SYNTAX      InetAddressType
        MAX-ACCESS  read-create
        STATUS      current
        DESCRIPTION
            "This object indicates the type of IP address denoted
            in zxAnPtpProtocolIpAddress object."
        DEFVAL { ipv4 }
        ::= { zxAnPtpEntry 8 }

    zxAnPtpProtocolIpAddress OBJECT-TYPE
        SYNTAX         InetAddress
        MAX-ACCESS     read-create
        STATUS         current
        DESCRIPTION
            "The value of protocolAddress shall be the protocol address
            of the port indicated by the targetPortIdentity. "
        REFERENCE
            "Clause 15.5.3.1.2.5 of IEEE1588-2008"
        ::= { zxAnPtpEntry 9 }

    zxAnPtpEthWorkMode OBJECT-TYPE
        SYNTAX        INTEGER
        {
            syncE(1),
            notSyncE(2)
        }
        MAX-ACCESS    read-create
        STATUS        current
        DESCRIPTION
            "The PTP node ethernet work mode."
        DEFVAL { syncE }
        ::= { zxAnPtpEntry 10 }

    zxAnPtpPacketsMode OBJECT-TYPE
        SYNTAX        INTEGER
        {
            unicast(1),
            multicast(2),
            broadcast(3)
        }
        MAX-ACCESS    read-create
        STATUS        current
        DESCRIPTION
            "The PTP node packets mode."
        DEFVAL { multicast }
        ::= { zxAnPtpEntry 11 }

    zxAnPtpTwoStepFlag OBJECT-TYPE
        SYNTAX        TruthValue
        MAX-ACCESS    read-create
        STATUS        current
        DESCRIPTION
            "The value of defaultDS.twoStepFlag shall be TRUE
             if the clock is a two-step clock;
              otherwise, the value shall be FALSE."
        REFERENCE
            "Clause 8.2.1.2.1, IEEE1588-2008"
        DEFVAL { false }
        ::= { zxAnPtpEntry 12 }

    zxAnPtpSendPacketsRate  OBJECT-TYPE
        SYNTAX      Integer32(1..512)
        UNITS       "pps"
        MAX-ACCESS  read-create
        STATUS      current
        DESCRIPTION
            "The sending packets rate of PTP node.
             The value should be 2^n, such as 1, 2, 4, 8, 16
                      and so on."
        ::= { zxAnPtpEntry 13 }

    zxAnPtpClockStatus OBJECT-TYPE
        SYNTAX  INTEGER
          {
            freeRun(1),
            holdover(2),
            acquisition(3),
            locked(4)
          }
        MAX-ACCESS read-only
        STATUS  current
        DESCRIPTION
            "State of the clock servo loop."
        ::= { zxAnPtpEntry 14 }

    zxAnPtpUtcTime  OBJECT-TYPE
        SYNTAX          DisplayString  ( SIZE ( 1 .. 19 ) )
        MAX-ACCESS      read-only
        STATUS          current
        DESCRIPTION     "The UTC time of PTP node. The format is
                        yyyy-mm-dd HH:MM:SS.For example,  2001-01-01 02:22:33."
        ::=  {  zxAnPtpEntry  15  }

    zxAnPtpRowStatus OBJECT-TYPE
        SYNTAX      RowStatus
        MAX-ACCESS  read-create
        STATUS      current
        DESCRIPTION
            "The row status of this entry."
        ::= { zxAnPtpEntry 50 }
-------------------------------------------------------------------------------
-- 2. PTP Management : zxAnPtpRemoteSrcTable
-------------------------------------------------------------------------------
    zxAnPtpRemoteSrcTable   OBJECT-TYPE
        SYNTAX      SEQUENCE  OF  ZxAnPtpRemoteSrcEntry
        MAX-ACCESS  not-accessible
        STATUS      current
        DESCRIPTION "This table includes PTP source configuration information
                     in NE equipment."
        ::=  { zxAnPtpMgmt 3 }

    zxAnPtpRemoteSrcEntry   OBJECT-TYPE
        SYNTAX      ZxAnPtpRemoteSrcEntry
        MAX-ACCESS  not-accessible
        STATUS      current
        DESCRIPTION "An entry in zxAnPtpRemoteSrcTable."
        INDEX   {zxAnPtpRack,zxAnPtpShelf,
                zxAnPtpSlot,zxAnPtpId,
                zxAnPtpRemoteSrcIpAddrType,zxAnPtpRemoteSrcIpAddress}
        ::=  { zxAnPtpRemoteSrcTable 1 }

    ZxAnPtpRemoteSrcEntry  ::=  SEQUENCE {
        zxAnPtpRemoteSrcIpAddrType          InetAddressType,
        zxAnPtpRemoteSrcIpAddress           InetAddress,
        zxAnPtpRemoteSrcDomainNumber        Integer32,
        zxAnPtpRemoteSrcPathDelayAdjust     Integer32,
        zxAnPtpRemoteSrcWorkStatus          INTEGER,
        zxAnPtpRemoteSrcRowStatus           RowStatus
        }

    zxAnPtpRemoteSrcIpAddrType OBJECT-TYPE
        SYNTAX      InetAddressType
        MAX-ACCESS  not-accessible
        STATUS      current
        DESCRIPTION
            "This object indicates the type of IP address denoted
             in zxAnPtpRemoteSrcIpAddress object."
        DEFVAL { ipv4 }
        ::= { zxAnPtpRemoteSrcEntry 1 }

    zxAnPtpRemoteSrcIpAddress OBJECT-TYPE
        SYNTAX         InetAddress
        MAX-ACCESS     not-accessible
        STATUS         current
        DESCRIPTION
            "The PTP source IP address."
        ::= { zxAnPtpRemoteSrcEntry 2 }

    zxAnPtpRemoteSrcDomainNumber OBJECT-TYPE
        SYNTAX         Integer32(0..255)
        MAX-ACCESS     read-create
        STATUS  current
        DESCRIPTION
            "The value of defaultDS.domainNumber is the domain attribute
             (see 7.1 of IEEE1588-2008) of the local clock.
              Value 0 indicates the default domain."
        REFERENCE
         "Clause 8.2.1.4.3, IEEE1588-2008"
        DEFVAL { 0 }
        ::= { zxAnPtpRemoteSrcEntry 3 }

    zxAnPtpRemoteSrcPathDelayAdjust OBJECT-TYPE
        SYNTAX          Integer32(-1000000..1000000)
        UNITS           "ns"
        MAX-ACCESS   read-create
        STATUS       current
        DESCRIPTION
            "The value of currentDS.meanPathDelay is an
             implementation-specific representation of the
             current value of the mean propagation time between
             a master and slave clock as computed by the slave."
        REFERENCE
         "Clause 8.2.2.4, IEEE1588-2008"
        ::= { zxAnPtpRemoteSrcEntry 4 }

    zxAnPtpRemoteSrcWorkStatus      OBJECT-TYPE
        SYNTAX          INTEGER
        {
             none(1),
             active(2),
             standby(3)
        }
        MAX-ACCESS      read-only
        STATUS          current
        DESCRIPTION
            "The remote PTP source work status,
             active(2) indicates PTP source is active,
             standby(3) indicates PTP source is standby source,
             none(1) indicates PTP source is invalid."
        ::=  {  zxAnPtpRemoteSrcEntry  5  }

    zxAnPtpRemoteSrcRowStatus OBJECT-TYPE
        SYNTAX      RowStatus
        MAX-ACCESS  read-create
        STATUS      current
        DESCRIPTION
            "The row status of this entry."
        ::= { zxAnPtpRemoteSrcEntry 50 }

-------------------------------------------------------------------------------
-- 3. Synchronization Time Management: zxAnSyncTime1ppsSrcTable
-------------------------------------------------------------------------------

    zxAnSyncTime1ppsSrcTable   OBJECT-TYPE
        SYNTAX      SEQUENCE  OF  ZxAnSyncTime1ppsSrcEntry
        MAX-ACCESS  not-accessible
        STATUS      current
        DESCRIPTION "This table includes 1PPS source information in NE
                    equipment."
        ::=  { zxAnSyncTimeClkSrcMgmt 3 }

    zxAnSyncTime1ppsSrcEntry   OBJECT-TYPE
        SYNTAX      ZxAnSyncTime1ppsSrcEntry
        MAX-ACCESS  not-accessible
        STATUS      current
        DESCRIPTION "An entry in zxAnSyncTime1ppsSrcTable."
        INDEX   {zxAnSyncTime1ppsSrcRack,zxAnSyncTime1ppsSrcShelf,
                zxAnSyncTime1ppsSrcSlot,zxAnSyncTime1ppsSrcId}
        ::=  { zxAnSyncTime1ppsSrcTable 1 }

    ZxAnSyncTime1ppsSrcEntry  ::=  SEQUENCE {
        zxAnSyncTime1ppsSrcRack                Integer32,
        zxAnSyncTime1ppsSrcShelf               Integer32,
        zxAnSyncTime1ppsSrcSlot                Integer32,
        zxAnSyncTime1ppsSrcId                  Integer32,
        zxAnSyncTime1ppsSrcSignalType          INTEGER,
        zxAnSyncTime1ppsSrcPriority            Integer32,
        zxAnSyncTime1ppsSrcPortType            INTEGER,
        zxAnSyncTime1ppsSrcPort                Integer32,
        zxAnSyncTime1ppsSrcWorkStatus          INTEGER,
        zxAnSyncTime1ppsSrcValidStatus          INTEGER,
        zxAnSyncTime1ppsSrcPortStatus          INTEGER,
        zxAnSyncTime1ppsSrcRowStatus           RowStatus
        }

   zxAnSyncTime1ppsSrcRack  OBJECT-TYPE
        SYNTAX      Integer32
        MAX-ACCESS  not-accessible
        STATUS      current
        DESCRIPTION
            "This object indicates the rack number."
        ::= { zxAnSyncTime1ppsSrcEntry 1 }

    zxAnSyncTime1ppsSrcShelf  OBJECT-TYPE
        SYNTAX      Integer32
        MAX-ACCESS  not-accessible
        STATUS      current
        DESCRIPTION
            "This object indicates the shelf number."
        ::= { zxAnSyncTime1ppsSrcEntry 2 }

    zxAnSyncTime1ppsSrcSlot  OBJECT-TYPE
        SYNTAX      Integer32
        MAX-ACCESS  not-accessible
        STATUS      current
        DESCRIPTION
            "This object indicates the slot number."
        ::= { zxAnSyncTime1ppsSrcEntry 3 }

    zxAnSyncTime1ppsSrcId  OBJECT-TYPE
        SYNTAX      Integer32(1..4)
        MAX-ACCESS  not-accessible
        STATUS      current
        DESCRIPTION
            "The ID of 1PPS signal source."
        ::= { zxAnSyncTime1ppsSrcEntry 4 }

    zxAnSyncTime1ppsSrcSignalType      OBJECT-TYPE
        SYNTAX          INTEGER
        {
             ptp(1),
             onepps(2)
        }
        MAX-ACCESS      read-create
        STATUS          current
        DESCRIPTION     "The type of 1PPS signal source."
        ::=  {  zxAnSyncTime1ppsSrcEntry  5  }

    zxAnSyncTime1ppsSrcPriority  OBJECT-TYPE
        SYNTAX      Integer32(1..255)
        MAX-ACCESS  read-create
        STATUS      current
        DESCRIPTION
            "The priority of 1PPS signal source, value 1 is the
              highest priority."
        ::= { zxAnSyncTime1ppsSrcEntry 6 }

    zxAnSyncTime1ppsSrcPortType      OBJECT-TYPE
        SYNTAX          INTEGER
        {
             typeTtl(1),
             type422(2)
        }
        MAX-ACCESS      read-create
        STATUS          current
        DESCRIPTION     "The 1PPS signal source port type.
                         It is valid only for the 'onepps' signal type."
        ::=  {  zxAnSyncTime1ppsSrcEntry  7  }

    zxAnSyncTime1ppsSrcPort  OBJECT-TYPE
        SYNTAX      Integer32(1..4)
        MAX-ACCESS  read-create
        STATUS      current
        DESCRIPTION
            "The physical port number.
             It is valid only for the 'onepps' signal type.
            "
        ::= { zxAnSyncTime1ppsSrcEntry 8 }

    zxAnSyncTime1ppsSrcWorkStatus      OBJECT-TYPE
        SYNTAX          INTEGER
        {
             none(1),
             active(2),
             standby(3)
        }
        MAX-ACCESS      read-only
        STATUS          current
        DESCRIPTION
             "The 1PPS signal source work status,
             active(2) indicates PTP source is active,
             standby(3) indicates PTP source is standby source,
             none(1) indicates PTP source is invalid."
        ::=  {  zxAnSyncTime1ppsSrcEntry  9  }

    zxAnSyncTime1ppsSrcValidStatus      OBJECT-TYPE
        SYNTAX          INTEGER
        {
             valid(1),
             invalid(2)
        }
        MAX-ACCESS      read-only
        STATUS          current
        DESCRIPTION
            "The 1PPS singnal source work status.
             When  the value is invalid,
             then zxAnSyncTime1ppsSrcWorkStatus is none."
        ::=  {  zxAnSyncTime1ppsSrcEntry  10  }

    zxAnSyncTime1ppsSrcPortStatus      OBJECT-TYPE
        SYNTAX          INTEGER
        {
             none(1),
             normal(2),
             signalLos(3)
        }
        MAX-ACCESS      read-only
        STATUS          current
        DESCRIPTION
             "The 1PPS signal source port status.
              It is valid only for the 'onepps' signal type.
              If zxAnSyncTime1ppsSrcSignalType is 'ptp',
              then the value is none.
              When the value is none or signalLos, then
              zxAnSyncTime1ppsSrcValidStatus is invalid. "
        ::=  {  zxAnSyncTime1ppsSrcEntry  11  }

    zxAnSyncTime1ppsSrcRowStatus OBJECT-TYPE
        SYNTAX      RowStatus
        MAX-ACCESS  read-create
        STATUS      current
        DESCRIPTION
            "The row status of this entry."
        ::= { zxAnSyncTime1ppsSrcEntry 30 }

-------------------------------------------------------------------------------
-- 4. Synchronization Time Management: zxAnSyncTimeTodSrcTable
-------------------------------------------------------------------------------

   zxAnSyncTimeTodSrcTable   OBJECT-TYPE
        SYNTAX      SEQUENCE  OF  ZxAnSyncTimeTodSrcEntry
        MAX-ACCESS  not-accessible
        STATUS      current
        DESCRIPTION "This table includes TOD source information in NE
                    equipment."
        ::=  { zxAnSyncTimeClkSrcMgmt 4 }

    zxAnSyncTimeTodSrcEntry   OBJECT-TYPE
        SYNTAX      ZxAnSyncTimeTodSrcEntry
        MAX-ACCESS  not-accessible
        STATUS      current
        DESCRIPTION "An entry in zxAnSyncTimeTodSrcTable."
        INDEX   {zxAnSyncTimeTodSrcRack,zxAnSyncTimeTodSrcShelf,
                zxAnSyncTimeTodSrcSlot,zxAnSyncTimeTodSrcPort}
        ::=  { zxAnSyncTimeTodSrcTable 1 }

    ZxAnSyncTimeTodSrcEntry  ::=  SEQUENCE {
        zxAnSyncTimeTodSrcRack                Integer32,
        zxAnSyncTimeTodSrcShelf               Integer32,
        zxAnSyncTimeTodSrcSlot                Integer32,
        zxAnSyncTimeTodSrcPort                Integer32,
        zxAnSyncTimeTodSrcSignalType          INTEGER,
        zxAnSyncTimeTodSrcYearAdjust          Integer32,
        zxAnSyncTimeTodSrcPortStatus          INTEGER,
        zxAnSyncTimeTodSrcRowStatus           RowStatus
        }

    zxAnSyncTimeTodSrcRack  OBJECT-TYPE
        SYNTAX      Integer32
        MAX-ACCESS  not-accessible
        STATUS      current
        DESCRIPTION
            "This object indicates the rack number."
        ::= { zxAnSyncTimeTodSrcEntry 1 }

    zxAnSyncTimeTodSrcShelf  OBJECT-TYPE
        SYNTAX      Integer32
        MAX-ACCESS  not-accessible
        STATUS      current
        DESCRIPTION
            "This object indicates the shelf number."
        ::= { zxAnSyncTimeTodSrcEntry 2 }

    zxAnSyncTimeTodSrcSlot  OBJECT-TYPE
        SYNTAX      Integer32
        MAX-ACCESS  not-accessible
        STATUS      current
        DESCRIPTION
            "This object indicates the slot number."
        ::= { zxAnSyncTimeTodSrcEntry 3 }

    zxAnSyncTimeTodSrcPort  OBJECT-TYPE
        SYNTAX      Integer32
        MAX-ACCESS  not-accessible
        STATUS      current
        DESCRIPTION
            "This object indicates the port number."
        ::= { zxAnSyncTimeTodSrcEntry 4 }

    zxAnSyncTimeTodSrcSignalType      OBJECT-TYPE
        SYNTAX          INTEGER
        {
             gps(1),
             chinaMobile(2),
             chinaUnicom(3),
             chinaTelecom(4)
        }
        MAX-ACCESS      read-create
        STATUS          current
        DESCRIPTION     "The signal type of TOD signal source."
        ::=  {  zxAnSyncTimeTodSrcEntry  5  }

    zxAnSyncTimeTodSrcYearAdjust      OBJECT-TYPE
        SYNTAX          Integer32(0..2050)
        UNITS           "year"
        MAX-ACCESS      read-create
        STATUS          current
        DESCRIPTION     "The year adjustment value of TOD signal source.
                         It is valid only for the 'gps' signal type."
        DEFVAL          { 0 }
        ::=  {  zxAnSyncTimeTodSrcEntry  6  }

    zxAnSyncTimeTodSrcPortStatus      OBJECT-TYPE
        SYNTAX          INTEGER
        {
             none(1),
             normal(2),
             signalLos(3)
        }
        MAX-ACCESS      read-only
        STATUS          current
        DESCRIPTION     "The TOD signal source port status."
        ::=  {  zxAnSyncTimeTodSrcEntry  7  }

    zxAnSyncTimeTodSrcRowStatus OBJECT-TYPE
        SYNTAX      RowStatus
        MAX-ACCESS  read-create
        STATUS      current
        DESCRIPTION
            "The row status of this entry."
        ::= { zxAnSyncTimeTodSrcEntry 30 }

-------------------------------------------------------------------------------
-- 5. Synchronization Time Management: zxAnSyncTimeOutputPortTable
-------------------------------------------------------------------------------

   zxAnSyncTimeOutputPortTable   OBJECT-TYPE
        SYNTAX      SEQUENCE  OF  ZxAnSyncTimeOutputPortEntry
        MAX-ACCESS  not-accessible
        STATUS      current
        DESCRIPTION "This table includes 1PPS and TOD signal output ports
                      information in NE equipment."
        ::=  { zxAnSyncTimeClkSrcMgmt 5 }

    zxAnSyncTimeOutputPortEntry   OBJECT-TYPE
        SYNTAX      ZxAnSyncTimeOutputPortEntry
        MAX-ACCESS  not-accessible
        STATUS      current
        DESCRIPTION "An entry in zxAnSyncTimeOutputPortTable."
        INDEX   {zxAnSyncTimeOutputRack,zxAnSyncTimeOutputShelf,
                zxAnSyncTimeOutputSlot,zxAnSyncTimeOutputPort}
        ::=  { zxAnSyncTimeOutputPortTable 1 }

    ZxAnSyncTimeOutputPortEntry  ::=  SEQUENCE {
        zxAnSyncTimeOutputRack                Integer32,
        zxAnSyncTimeOutputShelf               Integer32,
        zxAnSyncTimeOutputSlot                Integer32,
        zxAnSyncTimeOutputPort                Integer32,
        zxAnSyncTimeOutputPortEnable          INTEGER,
        zxAnSyncTimeOutputPortPhaseAdjus      Integer32,
        zxAnSyncTimeOutputPortRowStatus       RowStatus
        }

    zxAnSyncTimeOutputRack  OBJECT-TYPE
        SYNTAX      Integer32
        MAX-ACCESS  not-accessible
        STATUS      current
        DESCRIPTION
            "This object indicates the rack number."
        ::= { zxAnSyncTimeOutputPortEntry 1 }

    zxAnSyncTimeOutputShelf  OBJECT-TYPE
        SYNTAX      Integer32
        MAX-ACCESS  not-accessible
        STATUS      current
        DESCRIPTION
            "This object indicates the shelf number."
        ::= { zxAnSyncTimeOutputPortEntry 2 }

    zxAnSyncTimeOutputSlot  OBJECT-TYPE
        SYNTAX      Integer32
        MAX-ACCESS  not-accessible
        STATUS      current
        DESCRIPTION
            "This object indicates the slot number."
        ::= { zxAnSyncTimeOutputPortEntry 3 }

    zxAnSyncTimeOutputPort  OBJECT-TYPE
        SYNTAX      Integer32
        MAX-ACCESS  not-accessible
        STATUS      current
        DESCRIPTION
            "This object indicates the  port number."
        ::= { zxAnSyncTimeOutputPortEntry 4 }

    zxAnSyncTimeOutputPortEnable      OBJECT-TYPE
        SYNTAX          INTEGER
        {
              enable(1),
              disable(2)
        }
        MAX-ACCESS      read-create
        STATUS          current
        DESCRIPTION     "Enables or disables the output port of
                         1PPS and TOD signal."
        DEFVAL { enable }
        ::=  {  zxAnSyncTimeOutputPortEntry  5  }

    zxAnSyncTimeOutputPortPhaseAdjus      OBJECT-TYPE
        SYNTAX          Integer32(-1000000..1000000)
        UNITS           "ns"
        MAX-ACCESS      read-create
        STATUS          current
        DESCRIPTION     "The phase adjustment value.
                         It is valid only for the 1PPS signal."
        DEFVAL { 0 }
        ::=  {  zxAnSyncTimeOutputPortEntry  6  }

    zxAnSyncTimeOutputPortRowStatus OBJECT-TYPE
        SYNTAX      RowStatus
        MAX-ACCESS  read-create
        STATUS      current
        DESCRIPTION
            "The row status of this entry."
        ::= { zxAnSyncTimeOutputPortEntry 30 }

END
