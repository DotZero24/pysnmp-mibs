--------------------------------------------------------------------------------
-- File Name : ZTE-AN-PORTLOCATING-NDP-MIB.mib
-- Date      : 2011-03-01
-- Author    : ZTE Shanghai Nms dept.

--
-- Zte NDP Port Locating Management Mib for Access Node
--
--
--------------------------------------------------------------------------------
ZTE-AN-PORTLOCATING-NDP-MIB    DEFINITIONS ::= BEGIN

IMPORTS
    MODULE-IDENTITY, OBJECT-TYPE, Integer32     FROM SNMPv2-SMI
    TruthValue                                  FROM SNMPv2-TC
    zxAnPortLocatingMib                         FROM ZTE-AN-PORT-LOCATING-MIB
    zxAn                                        FROM ZTE-AN-TC-MIB;

zxAnPortLocatingNdpMib MODULE-IDENTITY
    LAST-UPDATED "201103011730Z"
    ORGANIZATION "ZTE Corporation"
    CONTACT-INFO "ZTE NMS dept.
                 Mail: wang.bingyu@zte.com.cn
                 Tel : 021-68896259"
    DESCRIPTION  "The MIB module for the management of NDP port locating."
    ::= {zxAnPortLocatingMib 45}
--------------------------------------------------------------------------------
-- Following management objects are defined.
-- 1. Global Objects
-- 2. NDP Port Locating Table
--------------------------------------------------------------------------------

zxAnPortLocatingNdpGlobal OBJECT IDENTIFIER ::=  {  zxAnPortLocatingNdpMib  1  }

--------------------------------------------------------------------------------
-- 1. Global Objects
--------------------------------------------------------------------------------
    zxAnNdpLioEnable OBJECT-TYPE
        SYNTAX      INTEGER
            {
                enable(1),
                disable(2)
            }
        MAX-ACCESS  read-write
        STATUS      current
        DESCRIPTION
        "Enable or disable the NDP port location function."
        DEFVAL { disable }
        ::= { zxAnPortLocatingNdpGlobal 1 }

--------------------------------------------------------------------------------
-- 2. NDP Port Locating Table
--------------------------------------------------------------------------------

    zxAnPortLocatingNdpTable OBJECT-TYPE
        SYNTAX             SEQUENCE OF ZxAnPortLocatingNdpEntry
        MAX-ACCESS         not-accessible
        STATUS             current
        DESCRIPTION
        "NDP port locating table."
        ::= { zxAnPortLocatingNdpMib 2 }

    zxAnPortLocatingNdpEntry OBJECT-TYPE
        SYNTAX             ZxAnPortLocatingNdpEntry
        MAX-ACCESS         not-accessible
        STATUS             current
        DESCRIPTION
        "NDP port locating entry."
        INDEX   { zxAnPortLocatingNdpRack, zxAnPortLocatingNdpShelf,
                  zxAnPortLocatingNdpSlot, zxAnPortLocatingNdpPort,
                  zxAnPortLocatingNdpOnu,  zxAnPortLocatingNdpIfType,
                  zxAnPortLocatingNdpLogicalId }
        ::= { zxAnPortLocatingNdpTable 1 }

    ZxAnPortLocatingNdpEntry ::= SEQUENCE {
        zxAnPortLocatingNdpRack          Integer32,
        zxAnPortLocatingNdpShelf         Integer32,
        zxAnPortLocatingNdpSlot          Integer32,
        zxAnPortLocatingNdpPort          Integer32,
        zxAnPortLocatingNdpOnu           Integer32,
        zxAnPortLocatingNdpIfType        INTEGER,
        zxAnPortLocatingNdpLogicalId     OBJECT IDENTIFIER,
        zxAnNdpLioIfConfEnable      INTEGER,
        zxAnNdpLioIfConfTrust       TruthValue,
        zxAnNdpLioIfConfPolicy      INTEGER
        }

    zxAnPortLocatingNdpRack    OBJECT-TYPE
        SYNTAX      Integer32
        MAX-ACCESS  not-accessible
        STATUS      current
        DESCRIPTION
            "Rack No. of the interface."
        ::= { zxAnPortLocatingNdpEntry 1 }

    zxAnPortLocatingNdpShelf   OBJECT-TYPE
        SYNTAX      Integer32
        MAX-ACCESS  not-accessible
        STATUS      current
        DESCRIPTION
            "Shelf No. of the interface."
        ::= { zxAnPortLocatingNdpEntry 2 }

    zxAnPortLocatingNdpSlot    OBJECT-TYPE
        SYNTAX      Integer32
        MAX-ACCESS  not-accessible
        STATUS      current
        DESCRIPTION
            "Slot No. of the interface."
        ::= { zxAnPortLocatingNdpEntry 3 }

    zxAnPortLocatingNdpPort    OBJECT-TYPE
        SYNTAX      Integer32
        MAX-ACCESS  not-accessible
        STATUS      current
        DESCRIPTION
            "Physical port No. of the interface."
        ::= { zxAnPortLocatingNdpEntry 4 }

    zxAnPortLocatingNdpOnu     OBJECT-TYPE
        SYNTAX      Integer32
        MAX-ACCESS  not-accessible
        STATUS      current
        DESCRIPTION
            "ONU No. of the interface.
             It is valid only if zxAnPortLocatingNdpIfType is 'portVPort' ,
             otherwise, its value is 0."
        ::= { zxAnPortLocatingNdpEntry 5 }

    zxAnPortLocatingNdpIfType  OBJECT-TYPE
        SYNTAX      INTEGER {
            bridgePort(2),
            ponVPort(4)
        }
        MAX-ACCESS  not-accessible
        STATUS      current
        DESCRIPTION
            "Type of the interface."
        ::= { zxAnPortLocatingNdpEntry 6 }

    zxAnPortLocatingNdpLogicalId OBJECT-TYPE
        SYNTAX      OBJECT IDENTIFIER
        MAX-ACCESS  not-accessible
        STATUS      current
        DESCRIPTION
            "Logic index of the interface.
            If zxAnPortLocatingNdpIfType is 'bridgePort', this object
            indicates 'pvc', such as oid '1' indicates 'PVC1'.
            If zxAnPortLocatingNdpIfType is 'ponVPort', this object
            indicates 'ponVPort', such as oid '1' indicates 'PortVPort1'."
        ::= { zxAnPortLocatingNdpEntry 7 }

    zxAnNdpLioIfConfEnable OBJECT-TYPE
        SYNTAX      INTEGER  {
                enable(1),
                disable(2)
            }
        MAX-ACCESS  read-write
        STATUS      current
        DESCRIPTION
            "Enable or disable the NDP port location of the interface."
        DEFVAL { disable }
        ::= { zxAnPortLocatingNdpEntry 8 }

    zxAnNdpLioIfConfTrust OBJECT-TYPE
        SYNTAX      TruthValue
        MAX-ACCESS  read-write
        STATUS      current
        DESCRIPTION
            "NDP port locating trust flag."
        DEFVAL { false }
        ::= { zxAnPortLocatingNdpEntry 9 }

    zxAnNdpLioIfConfPolicy OBJECT-TYPE
        SYNTAX      INTEGER {
                keep(1),
                replace(2),
                discard(3),
                add(4)
            }
        MAX-ACCESS  read-write
        STATUS      current
        DESCRIPTION
            "NDP port locating trust policy.
            if zxAnPortLocatingNdpIfTrust is trust, keep and replace is valid.
            if zxAnPortLocatingNdpIfTrust is false, discard and add is valid."
        DEFVAL { add }
        ::= { zxAnPortLocatingNdpEntry 10 }

END
