ZTE-DSL-UAPS-MIB  DEFINITIONS ::= BEGIN
  IMPORTS
    TEXTUAL-CONVENTION, DisplayString,MacAddress,TruthValue   FROM SNMPv2-TC
    MODULE-IDENTITY, OBJECT-TYPE, enterprises, Integer32      FROM SNMPv2-SMI
    ifIndex                                                   FROM IF-MIB;


  zxDslUapsMib  MODULE-IDENTITY
    LAST-UPDATED  "200701311000Z"
    ORGANIZATION  "ZTE Corporation"
    CONTACT-INFO  "suchunshan
                  Mail: suchunshan@zte.com.cn
                  Tel : 021-68896292"
    DESCRIPTION   "This MIB defines zte dsl uaps function modules' managed objects."
    ::=  {  zxDsl 33  }

    zte       OBJECT IDENTIFIER ::= { enterprises 3902 }
    zxDsl     OBJECT IDENTIFIER ::= { zte 1004 }


    zxDslUapsObjects    OBJECT IDENTIFIER ::= { zxDslUapsMib 1 }
    zxDslUapsTraps      OBJECT IDENTIFIER ::= { zxDslUapsMib 2 }


--------------------------------------------------------------------------------
-- Following objects are defined.
-- 1.Uaps Table
-- 2.Trap
-- 3.
--------------------------------------------------------------------------------




------------------------------------------------------------------------------
-- 1.Uaps
------------------------------------------------------------------------------


    zxDslUapsPortMode OBJECT-TYPE
        SYNTAX      INTEGER
            {
                uaps(1),
                trunk(2),
                uplink(3)
            }
        MAX-ACCESS  read-write
        STATUS      current
        DESCRIPTION
            "Port working mode."
          ::= { zxDslUapsObjects 1}


    zxDslUapsPrimaryPort OBJECT-TYPE
        SYNTAX      INTEGER
        MAX-ACCESS  read-write
        STATUS      current
        DESCRIPTION
            "The primary UAPS port.It is 1 or 2 in ZXDSL9806H.
            It is used in all port working mode but trunk(2).
            "
          ::= { zxDslUapsObjects 2}


    zxDslUapsAutoFailbackEnable OBJECT-TYPE
        SYNTAX      INTEGER
        MAX-ACCESS  read-write
        STATUS      current
        DESCRIPTION
            "Enable/disable recovery to the UAPS primary port automatically
            when the primary port is normal again."
          ::= { zxDslUapsObjects 3}


    zxDslUapsProtectionTime OBJECT-TYPE
        SYNTAX      INTEGER (10..900)
        UNITS       "second"
        MAX-ACCESS  read-write
        STATUS      current
        DESCRIPTION
            "The protection time of UAPS.When the fail time of port is larger
            than it,the UAPS module should failover to the secondary port.
            It is only used in uaps mode.
            "
          ::= { zxDslUapsObjects 4}



    zxDslUapsForceSwap OBJECT-TYPE
        SYNTAX      INTEGER
        MAX-ACCESS  read-write
        STATUS      current
        DESCRIPTION
            "Force to swap the primary and secondary port."
          ::= { zxDslUapsObjects 5}



    zxDslUapsPortWorkingStatus OBJECT-TYPE
        SYNTAX      INTEGER
        {
            primaryPortInWorking(1),
            secondaryPortInWorking(2)
        }
        MAX-ACCESS  read-only
        STATUS      current
        DESCRIPTION
            "It indicates which port is in working state."
          ::= { zxDslUapsObjects 6}


    zxDslUapsPortOperStatus OBJECT-TYPE
        SYNTAX      BITS
        {
            primaryPort(0),
            secondaryPort(1)
        }
        MAX-ACCESS  read-only
        STATUS      current
        DESCRIPTION
            "It indicates the operational status of ports.
            The bit value 0 means down and 1 means up.
            "
          ::= { zxDslUapsObjects 7}



    zxDslUapsIsInPrtctTime OBJECT-TYPE
        SYNTAX      TruthValue
        MAX-ACCESS  read-only
        STATUS      current
        DESCRIPTION
            "It indicates if the UAPS is in protect time status. "
          ::= { zxDslUapsObjects 8}



    zxDslUapsSwapRequestStatus OBJECT-TYPE
        SYNTAX      INTEGER
        {
            existRequest(1),
            noRequest(2)
        }
        MAX-ACCESS  read-only
        STATUS      current
        DESCRIPTION
            "It indicates if there is a swap request in memory. "
          ::= { zxDslUapsObjects 9}


    zxDslUapsSwapReason OBJECT-TYPE
        SYNTAX      BITS
        {
            failback(0),  -- primary port is recovery
            failover(1),  -- primary port is in fault
            forceSwap(2)
        }
        MAX-ACCESS  read-only
        STATUS      current
        DESCRIPTION
            "It indicates the reason of swap.
            NOTE:
               BIT 0 is just the MSB of this variable and is NOT the LSB.
            "
          ::= { zxDslUapsObjects 10}




------------------------------------------------------------------------------
-- 2.Trap
------------------------------------------------------------------------------


    zxDslUapsSwappedTrap NOTIFICATION-TYPE
        OBJECTS {
                    zxDslUapsPortWorkingStatus,
                    zxDslUapsPortOperStatus,
                    zxDslUapsSwapReason
                }
        STATUS             current
        DESCRIPTION
           "It indicates the primary and seconday port of UAPS module has swapped."
       ::= { zxDslUapsTraps 1 }


END
