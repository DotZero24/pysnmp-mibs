--  ******************************************************
--  $Id: zxr10poe.mib 12 2008-12-05  Caosl $
--
--  zxr10poe.mib: ZXR10 POE MIB file
--
--  August. 2008, Cao shuling
--
--  Copyright(c) 2008 by ZTE Corporaton
--  All rights reservered
--
--
--  ******************************************************

ZXR10-POE-MIB DEFINITIONS ::= BEGIN

IMPORTS
	--MODULE-IDENTITY,
	OBJECT-TYPE, Integer32
		FROM SNMPv2-SMI
	enterprises
        FROM SNMPv2-SMI;

    zte OBJECT IDENTIFIER ::= { enterprises 3902 }
    zxr10 OBJECT IDENTIFIER ::= { zte 3 }

    zxr10POE OBJECT IDENTIFIER ::= { zxr10 319 }

    --The follow part defined some data types which will be used in this acl mib file later
    DisplayString ::= OCTET STRING
    --  This data type is used to model textual information taken
    --  from the NVT ASCII character set.  By convention, objects
    --  with this syntax are declared as having
    --  SIZE (0..255)

   -- PSE Objects

	pseTable OBJECT-TYPE
		SYNTAX      SEQUENCE OF PseEntry
		MAX-ACCESS  not-accessible
		STATUS      current
		DESCRIPTION
	       "A table of objects that display and control attributes
		     of the main power source in a PSE  device.  Ethernet
		     switches are one example of boxes that would support
		     these objects.
		     Values of all read-write objects in this table are
		     persistent at restart/reboot."
       ::= { zxr10POE 1 }

   pseEntry OBJECT-TYPE
       SYNTAX      PseEntry
       MAX-ACCESS  not-accessible
       STATUS      current
       DESCRIPTION
           "A set of objects that display and control the Main
		      power of a PSE."
       INDEX    { pseGroupIndex }
       ::= { pseTable 1 }

   PseEntry ::= SEQUENCE {
       pseGroupIndex
          Integer32,
       overTemperatureAutoRecovery
          INTEGER,
       psePeakPower
          DisplayString,
       psePeakPowerTime
          DisplayString,
       pseCurrentTemperature
          DisplayString,
       pseFirmwareVersion
          DisplayString,
       pseCriticalPower
          DisplayString
       }

     pseGroupIndex OBJECT-TYPE
       SYNTAX      Integer32 (1..2147483647)
       MAX-ACCESS  not-accessible
       STATUS      current
       DESCRIPTION
           "This variable uniquely identifies the group
            containing the port to which a power Ethernet PSE is
            connected.  Group means box in the stack, module in a
            rack and the value 1 MUST be used for non-modular devices.
            Furthermore, the same value MUST be used in this variable,
            pethMainPseGroupIndex, and pethNotificationControlGroupIndex
            to refer to a given box in a stack or module in the rack."
       ::= { pseEntry 1 }

	overTemperatureAutoRecovery OBJECT-TYPE
		SYNTAX  INTEGER{disable(0),enable(1)}
		MAX-ACCESS read-write
		STATUS current
		DESCRIPTION
	        "disable (0) An group which can not provide the overtemperature auto-recovery functions.
	         enable(1) An group which can provide the overtemperature auto-recovery functions."
		::= { pseEntry 2 }

     psePeakPower OBJECT-TYPE
	    SYNTAX DisplayString
	    UNITS      "Watts"
	    MAX-ACCESS read-only
	    STATUS current
	    DESCRIPTION
	        "Poe peak-power."
	    ::= { pseEntry 3 }

    psePeakPowerTime OBJECT-TYPE
	    SYNTAX  DisplayString
	    MAX-ACCESS read-only
	    STATUS current
	    DESCRIPTION
	        "peak-power time."
	   	::= { pseEntry 4 }

     pseCurrentTemperature OBJECT-TYPE
		SYNTAX  DisplayString
		MAX-ACCESS read-only
		STATUS current
		DESCRIPTION
	        "Poe current temperature."
		::= { pseEntry 5 }

     pseFirmwareVersion OBJECT-TYPE
		SYNTAX DisplayString
		MAX-ACCESS read-only
	    STATUS current
	    DESCRIPTION
	        "Poe firmware version."
	    ::= { pseEntry 6 }

	 pseCriticalPower OBJECT-TYPE
	    SYNTAX DisplayString
	    UNITS      "Watts"
	    MAX-ACCESS read-only
	    STATUS current
	    DESCRIPTION
	        "Poe critical-power."
	    ::= { pseEntry 7 }


-- PORT Objects
	portTable OBJECT-TYPE
		SYNTAX      SEQUENCE OF PortEntry
		MAX-ACCESS  not-accessible
		STATUS      current
		DESCRIPTION
		    "A table of objects that display and control the power
	        characteristics of power Ethernet ports on a Power Source
	        Entity (PSE) device.  This group will be implemented in
	        managed power Ethernet switches and mid-span devices.
	        Values of all read-write objects in this table are
	        persistent at restart/reboot."
		::= { zxr10POE 2 }

	portEntry OBJECT-TYPE
		SYNTAX      PortEntry
		MAX-ACCESS  not-accessible
		STATUS      current
		DESCRIPTION
		     "A set of objects that display and control the power
           characteristics of a power Ethernet PSE port. "
		INDEX    { portEntryGroupIndex,portEntryPortIndex }
		::= { portTable 1 }

	PortEntry ::= SEQUENCE {
       portEntryGroupIndex
           Integer32,
       portEntryPortIndex
          Integer32,
       interfaceCurrentPower
           DisplayString ,
       interfaceAvgPower
           DisplayString,
       interfacePeakPower
           DisplayString,
       interfacepeakPowerTime
           DisplayString,
       enhancedMode
           INTEGER,
       pdMaxPower
           INTEGER
   }
	  portEntryGroupIndex OBJECT-TYPE
		SYNTAX       Integer32 (1..2147483647)
		MAX-ACCESS  not-accessible
		STATUS      current
		DESCRIPTION
		    "This variable uniquely identifies the group to which
		    power Ethernet PSE is connected.  Group means (box in
		    the stack, module in a rack) and the value 1 MUST be
		    used for non-modular devices.  Furthermore, the same
		    value MUST be used in this variable, pethPsePortGroupIndex,
		    and pethNotificationControlGroupIndex to refer to a
		    given box in a stack or module in a rack."
		::= { portEntry 1 }

	portEntryPortIndex OBJECT-TYPE
       SYNTAX      Integer32 (1..2147483647)
       MAX-ACCESS  not-accessible
       STATUS      current
       DESCRIPTION
           "This variable uniquely identifies the power Ethernet PSE
            port within group pethPsePortGroupIndex to which the
            power Ethernet PSE entry is connected."
       ::= { portEntry 2 }


    interfaceCurrentPower OBJECT-TYPE
       SYNTAX      DisplayString
       UNITS      "Watts"
       MAX-ACCESS  read-only
       STATUS      current
       DESCRIPTION
			"The current power of the PSE port expressed in Watts."
       ::= { portEntry 3 }

	interfaceAvgPower OBJECT-TYPE
		SYNTAX   DisplayString
		UNITS      "Watts"
		MAX-ACCESS  read-only
		STATUS      current
		DESCRIPTION
		        "The average power of the PSE port expressed in Watts."
		::= { portEntry 4 }

	interfacePeakPower OBJECT-TYPE
       SYNTAX      DisplayString
       UNITS      "Watts"
       MAX-ACCESS  read-only
       STATUS      current
       DESCRIPTION
               "The peak power of the PSE port expressed in Watts."
       ::= { portEntry 5 }

	interfacepeakPowerTime OBJECT-TYPE
       SYNTAX      DisplayString
       MAX-ACCESS  read-only
       STATUS      current
       DESCRIPTION
               "The interface peak Power Time."
       ::= { portEntry 6 }

     enhancedMode  OBJECT-TYPE
        SYNTAX   INTEGER{enable(0),disable(1)}
        MAX-ACCESS  read-write
        STATUS      current
        DESCRIPTION
               "enable (0) An interface which can provide the enhanced mode.
	         disable(1) An interface which can not provide the enhanced mode."
       ::= { portEntry 7 }

       pdMaxPower  OBJECT-TYPE
       SYNTAX   INTEGER { fifteen-point-four(0),
                          four(1),
                         seven(2),
                         eighteen(3),
                         twenty-seven(4),
                         thirty(5)
                         }
        MAX-ACCESS  read-write
        STATUS      current
        DESCRIPTION
               "The max poe pd power:
			   15.4(0)      15.4W
			   4.0(1),      4.0W
			   7.0(2),      7.0W
			   ext.18(3),   18W
			   ext.27(4),   27W
			   ext.30(5)    30W  "
       ::= { portEntry 8 }

   END
