ZTE-AN-DHCP-RELAY-MIB DEFINITIONS ::= BEGIN

IMPORTS
      OBJECT-TYPE, MODULE-IDENTITY, IpAddress                 FROM SNMPv2-SMI
    RowStatus, MacAddress, DisplayString                    FROM SNMPv2-TC
    zxAn, ZxAnIfindex                                       FROM ZTE-AN-TC-MIB;

    zxAnDhcpRelayMIB MODULE-IDENTITY
    LAST-UPDATED "200612080000Z"
    ORGANIZATION "zte Telcom Co. Ltd."
    CONTACT-INFO
        "E-mail: shen.yuyang@zte.com.cn,
         E-mail: suchunshan@zte.com.cn"
    DESCRIPTION
        "The MIB module is for configuration of DHCP relay
         feature."
    ::= { zxAn 53 }

    zxAnDhcpRelayMIBNotifs
        OBJECT IDENTIFIER ::= { zxAnDhcpRelayMIB 0 }
    zxAnDhcpRelayMIBObjects
        OBJECT IDENTIFIER ::= { zxAnDhcpRelayMIB 1 }

    zxAnDrGlobal
        OBJECT IDENTIFIER ::= { zxAnDhcpRelayMIBObjects 1 }
    zxAnDrOption60
        OBJECT IDENTIFIER ::= { zxAnDhcpRelayMIBObjects 2 }
    zxAnDrVlanInterface
        OBJECT IDENTIFIER ::= { zxAnDhcpRelayMIBObjects 3 }
    zxAnDrShowUsers
        OBJECT IDENTIFIER ::= { zxAnDhcpRelayMIBObjects 4 }

-- the global group

    zxAnDrDatabaseOper OBJECT-TYPE
        SYNTAX      INTEGER
            {
                read(1),
                write(2)
            }
        MAX-ACCESS  read-write
        STATUS      current
        DESCRIPTION
        "read = 1, write = 2"
        ::= { zxAnDrGlobal 1 }

    zxAnDrServMaxRetryTimes OBJECT-TYPE
        SYNTAX      INTEGER(5..1000)
        MAX-ACCESS  read-write
        STATUS      current
        DESCRIPTION
        "set dhcp relay agent max retry times"
        DEFVAL { 10 }
        ::= { zxAnDrGlobal 2 }

    zxAnDrUpdateArp OBJECT-TYPE
        SYNTAX      INTEGER
            {
                enable(1),
                disable(2)
            }
        MAX-ACCESS  read-write
        STATUS      current
        DESCRIPTION
        "enable = 1, disable = 2"
        DEFVAL { disable }
        ::= { zxAnDrGlobal 3 }

    zxAnDrProxyLeaseTime OBJECT-TYPE
        SYNTAX      INTEGER(60..18000)
        UNITS       "seconds"
        MAX-ACCESS  read-write
        STATUS      current
        DESCRIPTION
        "set proxy short lease time"
        DEFVAL { 60 }
        ::= { zxAnDrGlobal 4 }

    zxAnDrForwardMode OBJECT-TYPE
        SYNTAX      INTEGER {
            allSimultaneously(1),
            roundRobin(2)
            }
        MAX-ACCESS  read-write
        STATUS      current
        DESCRIPTION
            "allSimultaneously(1) : DHCP relay forwards DHCP message to
             all DHCP servers simultaneously.
             roundRobin(2): DHCP relay forwards DHCP message to
             DHCP server in a round-robin manner.
            "
        DEFVAL { roundRobin }
        ::= { zxAnDrGlobal 5 }

    zxAnDrCos OBJECT-TYPE
        SYNTAX      Integer32(0..7|255)
        MAX-ACCESS  read-write
        STATUS      current
        DESCRIPTION
            "Modify CoS of DHCP relay packets.
             For example, if the value is 6, when receiving
             a DHCP message from DHCP client which CoS value is 3,
             DHCP relay forwards the message with CoS 6 to DHCP server.
             255 means DHCP relay does not modify DHCP message CoS."
        DEFVAL { 255 }
        ::= { zxAnDrGlobal 6 }
-- the option60 group

    zxAnDrOption60Table OBJECT-TYPE
        SYNTAX      SEQUENCE OF ZxAnDrOption60Entry
        MAX-ACCESS  not-accessible
        STATUS      current
        DESCRIPTION
        " dhcp option60 map table. "
        ::= { zxAnDrOption60 1 }

    zxAnDrOption60Entry OBJECT-TYPE
        SYNTAX      ZxAnDrOption60Entry
        MAX-ACCESS  not-accessible
        STATUS      current
        DESCRIPTION
        " dhcp snooping bind entry. "
        INDEX { zxAnDrOption60Str,zxAnDrOption60Srv }
        ::= { zxAnDrOption60Table 1 }

    ZxAnDrOption60Entry ::= SEQUENCE {
        zxAnDrOption60Str    DisplayString,
        zxAnDrOption60Srv    IpAddress,
        zxAnDrOption60Frd    INTEGER,
        zxAnDrOption60Row    RowStatus
        }

    zxAnDrOption60Str OBJECT-TYPE
      SYNTAX      DisplayString(SIZE (1..50))
      MAX-ACCESS  not-accessible
      STATUS      current
      DESCRIPTION
          "this is option60 string."
      REFERENCE "Used by MAP"
      ::= { zxAnDrOption60Entry 1 }

    zxAnDrOption60Srv OBJECT-TYPE
      SYNTAX      IpAddress
      MAX-ACCESS  not-accessible
      STATUS      current
      DESCRIPTION
          "this is option60 string map server."
      REFERENCE "Used by MAP"
      ::= { zxAnDrOption60Entry 2 }

    zxAnDrOption60Frd OBJECT-TYPE
      SYNTAX      INTEGER
              {
                  smart(0),
                  standard(1),
                  security(2)
              }
      MAX-ACCESS  read-create
      STATUS      current
      DESCRIPTION
          "this is option60 string map server."
      DEFVAL { smart }
      ::= { zxAnDrOption60Entry 3 }

    zxAnDrOption60Row OBJECT-TYPE
      SYNTAX      RowStatus
      MAX-ACCESS  read-create
      STATUS      current
      DESCRIPTION
          "only support createAndGo and destroy."
      REFERENCE "Used by MAP"
      ::= { zxAnDrOption60Entry 4 }

-- the vlan interface group

    zxAnDrVlanIntTable OBJECT-TYPE
        SYNTAX      SEQUENCE OF ZxAnDrVlanIntEntry
        MAX-ACCESS  not-accessible
        STATUS      current
        DESCRIPTION
        " dhcp vlan interface relay table. "
        ::= { zxAnDrVlanInterface 1 }

    zxAnDrVlanIntEntry OBJECT-TYPE
        SYNTAX      ZxAnDrVlanIntEntry
        MAX-ACCESS  not-accessible
        STATUS      current
        DESCRIPTION
        " dhcp vlan interface relay entry. "
        INDEX { zxAnDrIntIndex }
        ::= { zxAnDrVlanIntTable 1 }

    ZxAnDrVlanIntEntry ::= SEQUENCE {
        zxAnDrIntIndex        ZxAnIfindex,
        zxAnDrOption60Oper    INTEGER,
        zxAnDrAgentIp         IpAddress
        }

    zxAnDrIntIndex OBJECT-TYPE
      SYNTAX      ZxAnIfindex
      MAX-ACCESS  not-accessible
      STATUS      current
      DESCRIPTION
          "set the vlan interface."
      REFERENCE "Used by MAP"
      ::= { zxAnDrVlanIntEntry 1 }

    zxAnDrOption60Oper OBJECT-TYPE
      SYNTAX      INTEGER
            {
                enable(1),
                disable(2)
            }
      MAX-ACCESS  read-write
      STATUS      current
      DESCRIPTION
          "set the vlan interface use option60 select server enable."
      REFERENCE "Used by MAP"
      DEFVAL { disable }

      ::= { zxAnDrVlanIntEntry 2 }

    zxAnDrAgentIp OBJECT-TYPE
      SYNTAX      IpAddress
      MAX-ACCESS  read-write
      STATUS      current
      DESCRIPTION
          "set dhcp relay agent ip."
      REFERENCE "Used by MAP"
      ::= { zxAnDrVlanIntEntry 3 }

-- the vlan interface group server table

    zxAnDrVlanIntServTable OBJECT-TYPE
        SYNTAX      SEQUENCE OF ZxAnDrVlanIntServEntry
        MAX-ACCESS  not-accessible
        STATUS      current
        DESCRIPTION
        " dhcp vlan interface relay server table. "
        ::= { zxAnDrVlanInterface 2 }

    zxAnDrVlanIntServEntry OBJECT-TYPE
        SYNTAX      ZxAnDrVlanIntServEntry
        MAX-ACCESS  not-accessible
        STATUS      current
        DESCRIPTION
        " dhcp vlan interface relay server entry. "
        INDEX { zxAnDrIntIndex,zxAnDrVlanIntServIp }
        ::= { zxAnDrVlanIntServTable 1 }

    ZxAnDrVlanIntServEntry ::= SEQUENCE {
        zxAnDrVlanIntServIp     IpAddress,
        zxAnDrVlanIntServFrd    INTEGER,
        zxAnDrVlanIntServRow    RowStatus
        }

    zxAnDrVlanIntServIp OBJECT-TYPE
      SYNTAX      IpAddress
      MAX-ACCESS  not-accessible
      STATUS      current
      DESCRIPTION
          "set dhcp relay server ip."
      REFERENCE "Used by MAP"
      ::= { zxAnDrVlanIntServEntry 1 }

    zxAnDrVlanIntServFrd OBJECT-TYPE
      SYNTAX      INTEGER
              {
                  smart(0),
                  standard(1),
                  security(2)
              }
      MAX-ACCESS  read-create
      STATUS      current
      DESCRIPTION
          "set dhcp relay forward mode."
      DEFVAL { smart }
      ::= { zxAnDrVlanIntServEntry 2 }

    zxAnDrVlanIntServRow OBJECT-TYPE
      SYNTAX      RowStatus
      MAX-ACCESS  read-create
      STATUS      current
      DESCRIPTION
          "only support createAndGo and destroy."
      REFERENCE "Used by MAP"
      ::= { zxAnDrVlanIntServEntry 3 }

-- the show users group

    zxAnDrUserViewTable OBJECT-TYPE
        SYNTAX      SEQUENCE OF ZxAnDrUserViewEntry
        MAX-ACCESS  not-accessible
        STATUS      current
        DESCRIPTION
        "show dhcp relay users by interface. "
        ::= { zxAnDrShowUsers 1 }

    zxAnDrUserViewEntry OBJECT-TYPE
        SYNTAX      ZxAnDrUserViewEntry
        MAX-ACCESS  not-accessible
        STATUS      current
        DESCRIPTION
        "show dhcp relay users entry. "
        INDEX { zxAnDrIntIndex,
                zxAnDrUserViewMac }
        ::= { zxAnDrUserViewTable 1 }

    ZxAnDrUserViewEntry ::= SEQUENCE {
        zxAnDrUserViewMac           MacAddress,
        zxAnDrUserViewIp            IpAddress,
        zxAnDrUserViewState         DisplayString,
        zxAnDrUserViewTime          DisplayString }

    zxAnDrUserViewMac OBJECT-TYPE
        SYNTAX      MacAddress
        MAX-ACCESS  not-accessible
        STATUS      current
        DESCRIPTION
        ""
        ::= { zxAnDrUserViewEntry 1 }

    zxAnDrUserViewIp OBJECT-TYPE
        SYNTAX      IpAddress
        MAX-ACCESS  read-only
        STATUS      current
        DESCRIPTION
        ""
        ::= { zxAnDrUserViewEntry 2 }

    zxAnDrUserViewState OBJECT-TYPE
        SYNTAX      DisplayString (SIZE (0..9))
        MAX-ACCESS  read-only
        STATUS      current
        DESCRIPTION
        ""
        ::= { zxAnDrUserViewEntry 3 }

    zxAnDrUserViewTime OBJECT-TYPE
        SYNTAX      DisplayString (SIZE (0..50))
        MAX-ACCESS  read-only
        STATUS      current
        DESCRIPTION
        ""
        ::= { zxAnDrUserViewEntry 4 }

END
