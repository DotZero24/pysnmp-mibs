--
-- Zte Dsl Line Ext Mib
--
--

ZTE-DSL-LINE-EXT-MIB DEFINITIONS ::= BEGIN
    IMPORTS
        MODULE-IDENTITY, OBJECT-TYPE,
        TimeTicks,Counter32, Gauge32    FROM SNMPv2-SMI
        MODULE-COMPLIANCE, OBJECT-GROUP FROM SNMPv2-CONF
        SnmpAdminString                 FROM SNMP-FRAMEWORK-MIB
        ifIndex                         FROM IF-MIB
        adslLineConfProfileName,
        adslLineConfProfileEntry,adslLineAlarmConfProfileEntry
                                        FROM ADSL-LINE-MIB
        RowStatus                       FROM SNMPv2-TC
        enterprises                     FROM RFC1155-SMI;


-- ZTE Dsl line ext MIB objects

    zxAdslExtMib MODULE-IDENTITY
            LAST-UPDATED "200404081300Z"
            ORGANIZATION "zte dsl product line"
            CONTACT-INFO
                " su chunshan
                  Mail: suchunshan@zte.com.cn
                  Tel : 021-68896292,68896251"
            DESCRIPTION
                "This mib defines extended dsl line mo (managed object ) for adsl2,
                 adsl+ and dsl loop test.

                 Naming Conventions:
                 Atuc -- (ATUC) modem at near (Central) end of line
                 Atur -- (ATUR) modem at Remote end of line "
    ::= {zxDsl 4}


    zte OBJECT IDENTIFIER ::= { enterprises 3902 }
    zxDsl OBJECT IDENTIFIER ::= { zte 1004 }


    zxAdslExtMibObjects OBJECT IDENTIFIER ::= { zxAdslExtMib 1 }


--  Is support adsl2+

    zxAdslIsSupportAdsl2Plus  OBJECT-TYPE
            SYNTAX      INTEGER {
                support   (1),
                noSupport (2)
                }
            MAX-ACCESS  read-only
            STATUS      current
            DESCRIPTION
                "A flag is to indicate whether this device is support Adsl2Plus management."
            ::= {zxAdslExtMibObjects 11 }


--  Is support dsl connection rate threshold

    zxAdslIsSupportAdslRateThresh  OBJECT-TYPE
            SYNTAX      INTEGER {
                Support   (1),
                noSupport (2)
                }
            MAX-ACCESS  read-only
            STATUS      current
            DESCRIPTION
                "A flag is to indicate whether this device is support dsl
                connection rate threshold management."
            ::= {zxAdslExtMibObjects 14 }



--  Adsl Line Extended Table

    zxAdslLineTable  OBJECT-TYPE
            SYNTAX      SEQUENCE OF ZxAdslLineEntry
            MAX-ACCESS  not-accessible
            STATUS      current
            DESCRIPTION
                "Adsl line additional information table."
            ::= {zxAdslExtMibObjects 1}


    zxAdslLineEntry  OBJECT-TYPE
            SYNTAX      ZxAdslLineEntry
            MAX-ACCESS  not-accessible
            STATUS      current
            DESCRIPTION
                "Adsl line additional information entry"
            INDEX    { ifIndex }
            ::= {zxAdslLineTable 1}


    ZxAdslLineEntry ::=
            SEQUENCE {
                zxAdslLinePMConfPMSF         INTEGER,
                zxAdslLinePMState            INTEGER,
                zxAdslLineDMTTrellis         INTEGER,
                zxAdslLineTxAtmCells         Counter32,
                zxAdslLineRxAtmCells         Counter32,
                zxAdslLineIdleCells          Counter32,
                zxAdslLineTxDataRate         Gauge32,
                zxAdslLineRxDataRate         Gauge32
                }

    zxAdslLinePMConfPMSF  OBJECT-TYPE
        SYNTAX      INTEGER {
            l0_FullOn   (1),
            l2_LowPower (3),
            l3_Idle     (4)
            }
        MAX-ACCESS  read-create
        STATUS      current
        DESCRIPTION
            "This configuration parameter defines the line states to be forced by
            the near-end ATU on this line. It is coded as an integer value with
            following definition:
                L0_FullOn   Force the line to transition from the L3 idle state
                            to the L0 full-on state. This transition requires
                            the (short) initialization procedures. After
                            reaching the L0 state, the line may transition into
                            or exit from the L2 low power state (if L2 state is
                            enabled). If the L0 state is not reached (after a
                            vendor discretionary number of retries and/or within
                            a vendor discretionary timeout), then an
                            Initialization Failure occurs. Whenever the line is
                            in the L3 state, attemps shall be made to transition
                            to the L0 state until it is forced into another
                            state through this configuration parameter.
                L2_LowPower Force the line to transition from L0 full on to L2
                            low power state. This transition requires the entry
                            into L2 mode. This is a out-of-service test value
                            for triggering the L2 mode.
                L3_Idle     Force the line to transition from the L0 full-on or
                            L2 low power state to the L3 idle state. This
                            transition requires the (orderly) shutdown procedure.
                            After reaching the L3 state, the line shall remain
                            in the L3 idle state until it is forced into another
                            state through this configuration parameter.

                Forced line state transitions require the line to enter or exit
                from the L3 idle state. These transitions are not restricted by
                the Line state enabling parameter value.

                NOTE - Supported for ADSL2/ADSL2plus ONLY.
                       This configuration parameter maps to the AdminStatus of
                the line, which is part of the GeneralInformationGroup object
                group specified in RFC 2233, and may not need to be duplicated
                in the ADSL MIB. See also RFC2662. The Administrative Status of
                the line is UP when the line is forced to the L0 state and is
                DOWN when the line is forced to the L3 state."

        REFERENCE "Section 7.3.1.1.3 Power management state forced (PMSF),
                   G.997.1 (05/2003) "
        DEFVAL { 1 }
        ::= { zxAdslLineEntry 1 }



    zxAdslLinePMState  OBJECT-TYPE
        SYNTAX      INTEGER {
            l0_FullOn   (1),
            l1_LowPower (2),
            l2_LowPower (3),
            l3_Idle     (4)
            }
        MAX-ACCESS  read-only
        STATUS      current
        DESCRIPTION
            "The Line has four possible power management states, numbered 0 to 3
            and corresponding to respectively:

                L0 - Synchronized - This Line state (L0) is when the Line has
                     full transmission (i.e. showtime).

                L1 - Power Down Data transmission - This line state (L1) is when
                     there is transmission on the line but the net data rate is
                     reduced (e.g. only for OAM and higher layer connection and
                     session control). This state applies to G.992.2 only.

                L2 - Power Down Data transmission - This line state (L2) is when
                     there is transmission on the line but the net data rate is
                     reduced (e.g. only for OAM and higher layer connection and
                     session control). This state applies to G.992.3 and G.992.4 only.

                L3 - No power - This Line state (L3) is when there is No Power
                     transmitted on the line at all.

            NOTE -  This parameter maps to the OperStatus of the line, which is
                    part of the GeneralInformationGroup object group specified
                    in RFC 2233, and may not need to be duplicated in the ADSL MIB.
                    See also RFC2662 and RFC3440. The Operational Status of the
                    line is UP in the L0, L1 or L2 state (i.e., during showtime)
                    and is DOWN in the L3 state (e.g., during (short)
                    initialization and loop diagnostics mode). "

        REFERENCE "Section 7.5.1.2  Line power management state  5.4 Profiles,
                   G.997.1 (05/2003) "
        ::= { zxAdslLineEntry 2 }

    zxAdslLineDMTTrellis  OBJECT-TYPE
            SYNTAX      INTEGER {
                unknown(0),
                on     (1),   -- Trellis coding enabled
                off    (2)    -- Trellis coding disabled
                }
            MAX-ACCESS  read-only
            STATUS      deprecated
            DESCRIPTION
                "Parameter that indicates whether trellis coding has been enabled or
                disabled.Trellis coding should always be enabled for its clear
                performancen advantage.Trellis coding is mandatory for ADSL/ADSL2plus."
            ::= { zxAdslLineEntry 3 }

    zxAdslLineTxAtmCells  OBJECT-TYPE
            SYNTAX      Counter32
            MAX-ACCESS  read-only
            STATUS      current
            DESCRIPTION
                 "Transmitted ATM cell counter.This is a count of total data cells
                 only transmitted  by ATU-C."
            ::= { zxAdslLineEntry 4 }


    zxAdslLineRxAtmCells  OBJECT-TYPE
            SYNTAX      Counter32
            MAX-ACCESS  read-only
            STATUS      current
            DESCRIPTION
                 "Received ATM cell counter.This is a count of total data cells
                 only received by ATU-C."
            ::= { zxAdslLineEntry 5 }

    zxAdslLineIdleCells  OBJECT-TYPE
            SYNTAX      Counter32
            MAX-ACCESS  read-only
            STATUS      current
            DESCRIPTION
                 "Number of idle cells transmitted/recieved by ATU-C."
            ::= { zxAdslLineEntry 6 }

    zxAdslLineTxDataRate  OBJECT-TYPE
            SYNTAX      Gauge32
            UNITS       "kbps"
            MAX-ACCESS  read-only
            STATUS      current
            DESCRIPTION
                 "Transmitted net data rate on this line."
            ::= { zxAdslLineEntry 7 }

    zxAdslLineRxDataRate  OBJECT-TYPE
            SYNTAX      Gauge32
            UNITS       "kbps"
            MAX-ACCESS  read-only
            STATUS      current
            DESCRIPTION
                 "Recieved net data rate on this line."
            ::= { zxAdslLineEntry 8 }




--  Adsl Line Config Profile Extended Table

    zxAdslLineConfProfileExtTable  OBJECT-TYPE
            SYNTAX      SEQUENCE OF ZxAdslLineConfProfileExtEntry
            MAX-ACCESS  not-accessible
            STATUS      current
            DESCRIPTION
                "Adsl line config profile extended information table."
            ::= {zxAdslExtMibObjects 2}


    zxAdslLineConfProfileExtEntry  OBJECT-TYPE
            SYNTAX      ZxAdslLineConfProfileExtEntry
            MAX-ACCESS  not-accessible
            STATUS      current
            DESCRIPTION
               "An entry extends the adslLineConfProfileEntry defined in
               [RFC2662]. Each entry corresponds to an ADSL line profile."

            AUGMENTS    { adslLineConfProfileEntry }
            ::= {zxAdslLineConfProfileExtTable 1}


    ZxAdslLineConfProfileExtEntry ::=
            SEQUENCE {
                zxAdslLineDMTConfTrellis         INTEGER,
                zxAdslAtucConfMaxBitsPerBin      INTEGER,
                zxAdslAtucConfTxStartBin         INTEGER,
                zxAdslAtucConfTxEndBin           INTEGER,
                zxAdslAtucConfRxStartBin         INTEGER,
                zxAdslAtucConfRxEndBin           INTEGER,
                zxAdslAtucConfUseCustomBins      INTEGER,
--                zxAdslAtucConfBinUsage           OCTET STRING,
                zxAdslAtucConfDnBitSwap          INTEGER,
                zxAdslAtucConfUpBitSwap          INTEGER,
                zxAdslAtucConfREADSL2Enable      INTEGER,
                zxAdslAtucConfPsdMaskType        INTEGER,
                zxAdslAtucConfPMMode             BITS,
                zxAdslAtucConfPML0Time           INTEGER,
                zxAdslAtucConfPML2Time           INTEGER,
                zxAdslAtucConfPML2ATPR           INTEGER,
                zxAdslAtucConfPML2Rate           INTEGER,
                zxAdsl2ConfMinProtectionDs       INTEGER,
                zxAdsl2ConfMinProtectionUs       INTEGER
                }


    zxAdslLineDMTConfTrellis  OBJECT-TYPE
            SYNTAX      INTEGER {
                on     (1),   -- Enable Trellis coding
                off    (2)    -- Disable Trellis coding
                }
            MAX-ACCESS  read-create
            STATUS      deprecated
            DESCRIPTION
                "Parameter that enable or disable trellis coding. Trellis coding
                should always be enabled for its clear performancen advantage.
                Trellis coding is mandatory for ADSL/ADSL2plus.
                The value on(1) is default for all Annexes and ADSL2/ADSL2plus."
            ::= { zxAdslLineConfProfileExtEntry 1 }

    zxAdslAtucConfMaxBitsPerBin  OBJECT-TYPE
            SYNTAX      INTEGER (0..15)
            MAX-ACCESS  read-create
            STATUS      current
            DESCRIPTION
                "Specifies maximum Rx number of bits per bin."
            DEFVAL { 15 }
            ::= { zxAdslLineConfProfileExtEntry 2 }

    zxAdslAtucConfTxStartBin  OBJECT-TYPE
            SYNTAX      INTEGER
            MAX-ACCESS  read-create
            STATUS      current
            DESCRIPTION
                "Specifies lowest bin number allowed for Tx signal.
                 Different line coding type has different default value.
                    0x20 (default for Annex A only)
                    0x20 (default for ADSL2/ADSL2plus)
                    0x06 (default for Annex A if G.Span and/or G.Span Plus are also defined)
                    0x40 (default for Annex B)
                    0x06 (default for Annex C/C.x)
                    0x06 (default for G.Span)
                    0x06 (default for G.Span Plus)"
            ::= { zxAdslLineConfProfileExtEntry 3 }

    zxAdslAtucConfTxEndBin  OBJECT-TYPE
            SYNTAX      INTEGER(0..512)
            MAX-ACCESS  read-create
            STATUS      current
            DESCRIPTION
                "Specifies highest bin number allowed for Tx signal.
                 Default = 0x3ff (default for all Annexes and ADSL2/ADSL2plus)"
            ::= { zxAdslLineConfProfileExtEntry 4 }



    zxAdslAtucConfRxStartBin  OBJECT-TYPE
            SYNTAX      INTEGER
            MAX-ACCESS  read-create
            STATUS      current
            DESCRIPTION
                "Specifies lowest bin number allowed for Rx signal.
                 Different line coding type has different default value.
                    0x06 (default for Annex A)
                    0x01 (default for Annex B)
                    0x06 (default for Annex C/C.x)
                    0x06 (default for G.Span/ADSL+)
                    0x06 (default for G.Span Plus)
                    0x06 (default for ADSL2/ADLS2plus) "
            ::= { zxAdslLineConfProfileExtEntry 5 }



    zxAdslAtucConfRxEndBin  OBJECT-TYPE
            SYNTAX      INTEGER(0..512)
            MAX-ACCESS  read-create
            STATUS      current
            DESCRIPTION
                "Specifies highest bin number allowed for Rx signal.
                Default = 0x3f (default for all Annexes and ADSL2/ADLS2plus)"
            ::= { zxAdslLineConfProfileExtEntry 6 }


    zxAdslAtucConfUseCustomBins  OBJECT-TYPE
            SYNTAX      INTEGER {
                enable(1),  -- enable use custom Bins
                disable(2)  -- disable use custom Bins
                }
            MAX-ACCESS  read-create
            STATUS      current
            DESCRIPTION
                "Enable or disable custom bin selection for upstream/downstream
                transmission. This parameter is used in conjunction with the
                adslAtucDMTConfFreqBins and
                adslAturDMTConfFreqBins[ADSL-DMT-LINE-MIB] parameter."
            DEFVAL { 2 }
            ::= { zxAdslLineConfProfileExtEntry 7 }



--    zxAdslAtucConfBinUsage  OBJECT-TYPE
--            SYNTAX      OCTET STRING(SIZE (64))
--            MAX-ACCESS  read-create
--            STATUS      current
--            DESCRIPTION
--                "Customer selected value (default value is all 1 that is 0x1ff)
--                64-byte parameter that allows the user to select which of the
--                bins will be enabled for upstream and downstream transmission
--                when using non-overlapped (FDM) mode. A 1 in bit position
--                indicates usage of corresponding bin,whereas a 0 disables usage
--                of corresponding bin.  "
--            ::= { zxAdslLineConfProfileExtEntry 6 }


    zxAdslAtucConfDnBitSwap  OBJECT-TYPE
            SYNTAX      INTEGER {
                enable(1),
                disable(2)
                }
            MAX-ACCESS  read-create
            STATUS      current
            DESCRIPTION
                "enables/disables downstream bit swapping.
                 Different line coding type has different default value.
                     disable(2)  (default for ADSL2/ADLS2plus, Annex B, Annex C
                                 C.x, G.Span/ADSL+ and G.Span Plus)
                     enable(1)   (default for Annex A) "
            ::= { zxAdslLineConfProfileExtEntry 8 }

    zxAdslAtucConfUpBitSwap  OBJECT-TYPE
            SYNTAX      INTEGER {
                enable(1),
                disable(2)
                }
            MAX-ACCESS  read-create
            STATUS      current
            DESCRIPTION
                "enables/disables upstream bit swapping.
                 Different line coding type has different default value.
                     disable(2)  (default for ADSL2/ADLS2plus, Annex B, Annex C
                                 C.x, G.Span/ADSL+ and G.Span Plus)
                     enable(1)   (default for Annex A) "
            ::= { zxAdslLineConfProfileExtEntry 9 }


    zxAdslAtucConfREADSL2Enable  OBJECT-TYPE
            SYNTAX      INTEGER {
                enable(1),
                disable(2)
                }
            MAX-ACCESS  read-create
            STATUS      deprecated
            DESCRIPTION
                "Defines whether downstream READSL2 operation should be forced
                by the ATU-C."

            REFERENCE "Section 6.10.1 on page 66,Annex L ITU G.992.3"
            DEFVAL { 2 }
            ::= { zxAdslLineConfProfileExtEntry 10 }



    zxAdslAtucConfPsdMaskType  OBJECT-TYPE
            SYNTAX      INTEGER
            MAX-ACCESS  read-create
            STATUS      current
            DESCRIPTION
                " It is supported by G.Span. Dsl card team will provide files
                about it in details."
            ::= { zxAdslLineConfProfileExtEntry 11 }

    zxAdslAtucConfPMMode  OBJECT-TYPE
            SYNTAX      BITS {
                idle (0),
                lowPower(1)
                }
            MAX-ACCESS  read-create
            STATUS      current
            DESCRIPTION
                " This configuration parameter defines the line states the ATU-C
                may autonomously transition to on this line. It is coded in a
                bit map representation (0 if not allowed, 1 if allowed) with
                following definition:
                    Bit 0   L3 state (Idle state)
                    Bit 1   L1/L2 state (Low power state)."

            REFERENCE "Section 7.3.1.1.4 ITU G.997.1(05/2003) "
            ::= { zxAdslLineConfProfileExtEntry 12 }

    zxAdslAtucConfPML0Time  OBJECT-TYPE
            SYNTAX      INTEGER (0..255)
            UNITS       "seconds"
            MAX-ACCESS  read-create
            STATUS      current
            DESCRIPTION
                " PM configuration parameter,related to the L2 low power state.
                This parameter represents the minimum time between an exit from
                the L2 state and the next entry into the L2 state. "

            REFERENCE "Section 7.3.1.1.5 ITU G.997.1(05/2003) "
            ::= { zxAdslLineConfProfileExtEntry 13 }

    zxAdslAtucConfPML2Time  OBJECT-TYPE
            SYNTAX      INTEGER (0..255)
            UNITS       "seconds"
            MAX-ACCESS  read-create
            STATUS      current
            DESCRIPTION
                " PM configuration parameter,related to the L2 low power state.
                This parameter represents the minimum time between an entry into
                the L2 state and the first Power Trim in the L2 state and between
                two consecutive Power Trims in the L2 State."

            REFERENCE "Section 7.3.1.1.6 ITU G.997.1(05/2003) "
            ::= { zxAdslLineConfProfileExtEntry 14 }



    zxAdslAtucConfPML2ATPR  OBJECT-TYPE
            SYNTAX      INTEGER (0..31)
            UNITS       "dB"
            MAX-ACCESS  read-create
            STATUS      current
            DESCRIPTION
                " PM configuration parameter,related to the L2 low power state.
                This parameter represents the Maximum Aggregate Transmit Power
                Reduction (in dB) that can be performed through a single Power
                Trim in the L2 state. It ranges from 0 dB to 31 dB."

            REFERENCE "Section 7.3.1.1.3 ITU G.997.1(05/2003) "
            ::= { zxAdslLineConfProfileExtEntry 15 }


    zxAdslAtucConfPML2Rate  OBJECT-TYPE
            SYNTAX      INTEGER (256..1024)
            UNITS       "kbps"
            MAX-ACCESS  read-create
            STATUS      current
            DESCRIPTION
                " PM configuration parameter,related to the L2 low power state.
                This parameter specifies the minimum net data rate during the
                low power state (L2)."

            REFERENCE "Section 7.3.2.1.5 ITU G.997.1(05/2003) "
            ::= { zxAdslLineConfProfileExtEntry 16 }

    zxAdsl2ConfMinProtectionDs  OBJECT-TYPE
            SYNTAX      INTEGER
                {
                 noProtection (1),
                 halfSymbol (2),
                 singleSymbol (3),
                 twoSymbols (4),
                 fourSymbols (5),
                 eightSymbols (6),
                 sixteenSymbols (7)
                 }
            UNITS       "symbols"
            MAX-ACCESS  read-create
            STATUS      current
            DESCRIPTION
             "Minimum Impulse Noise Protection on Downstream direction.  The
              minimum impulse noise protection for the bearer channel,
              expressed in symbols.  The parameter can take the following
              values: noProtection (i.e., INP not required), halfSymbol
              (i.e., INP length is 1/2 symbol) and 1-16 symbols in steps
              of 1 symbol."
            REFERENCE    "ITU-T G.997.1, paragraph 7.3.2.3"
            DEFVAL       { noProtection }
            ::= { zxAdslLineConfProfileExtEntry 20 }

   zxAdsl2ConfMinProtectionUs  OBJECT-TYPE
            SYNTAX      INTEGER
                {
                 noProtection (1),
                 halfSymbol (2),
                 singleSymbol (3),
                 twoSymbols (4),
                 fourSymbols (5),
                 eightSymbols (6),
                 sixteenSymbols (7)
                 }
            UNITS       "symbols"
            MAX-ACCESS  read-create
            STATUS      current
            DESCRIPTION
             "  Minimum Impulse Noise Protection on Upstream direction.  The
                minimum impulse noise protection for the bearer channel,
                expressed in symbols. "
            REFERENCE    "ITU-T G.997.1, paragraph 7.3.2.3"
            DEFVAL       { noProtection }
            ::= { zxAdslLineConfProfileExtEntry 21 }

-- Atuc Physical Table

    zxAdslAtucPhysTable  OBJECT-TYPE
            SYNTAX      SEQUENCE OF ZxAdslAtucPhysEntry
            MAX-ACCESS  not-accessible
            STATUS      current
            DESCRIPTION
                 "This table provides one row for each ATUC
                 Each row contains the Physical Layer Parameters
                 table for that ATUC. ADSL physical interfaces are
                 those ifEntries where ifType is equal to adsl(94)."
            ::= {zxAdslExtMibObjects 3}


    zxAdslAtucPhysEntry  OBJECT-TYPE
            SYNTAX      ZxAdslAtucPhysEntry
            MAX-ACCESS  not-accessible
            STATUS      current
            DESCRIPTION
                "Adsl physical layer line actuals information entry"
            INDEX    { ifIndex }
            ::= {zxAdslAtucPhysTable 1}


    ZxAdslAtucPhysEntry ::=
            SEQUENCE {
                zxAdslAtucPrevSnrMgn          INTEGER,
                zxAdslAtucPrevAtn             Gauge32,
                zxAdslAtucPrevAttainableRate  Gauge32,
                zxAdslAtucChipVersion         SnmpAdminString
                }

    zxAdslAtucPrevSnrMgn  OBJECT-TYPE
            SYNTAX      INTEGER (-640..640)
            UNITS       "tenth dB"
            MAX-ACCESS  read-only
            STATUS      current
            DESCRIPTION
                 "The adslAtucCurrSnrMgn at the time of the last linkup event."
            ::= { zxAdslAtucPhysEntry 1 }


    zxAdslAtucPrevAtn  OBJECT-TYPE
            SYNTAX      Gauge32(0..630)
            UNITS       "tenth dB"
            MAX-ACCESS  read-only
            STATUS      current
            DESCRIPTION
                 "The adslAtucCurrAtn at the time of the last linkup event."
            ::= { zxAdslAtucPhysEntry 2 }

    zxAdslAtucPrevAttainableRate  OBJECT-TYPE
            SYNTAX      Gauge32
            UNITS       "kbps"
            MAX-ACCESS  read-only
            STATUS      current
            DESCRIPTION
                 "The adslAtucCurrAttainableRate at the time of the last linkup event."
            ::= { zxAdslAtucPhysEntry 3 }

    zxAdslAtucChipVersion  OBJECT-TYPE
            SYNTAX      SnmpAdminString (SIZE (0..32))
            MAX-ACCESS  read-only
            STATUS      deprecated
            DESCRIPTION
                 "The atuc chip version number."
            ::= { zxAdslAtucPhysEntry 4 }




-- Atur Physical Table

    zxAdslAturPhysTable  OBJECT-TYPE
            SYNTAX      SEQUENCE OF ZxAdslAturPhysEntry
            MAX-ACCESS  not-accessible
            STATUS      current
            DESCRIPTION
                 "This table provides one row for each ATUR
                 Each row contains the Physical Layer Parameters
                 table for that ATUR. ADSL physical interfaces are
                 those ifEntries where ifType is equal to adsl(94)."
            ::= {zxAdslExtMibObjects 4}


    zxAdslAturPhysEntry  OBJECT-TYPE
            SYNTAX      ZxAdslAturPhysEntry
            MAX-ACCESS  not-accessible
            STATUS      current
            DESCRIPTION
                "Adsl physical layer line actuals information entry"
            INDEX    { ifIndex }
            ::= {zxAdslAturPhysTable 1}


    ZxAdslAturPhysEntry ::=
            SEQUENCE {
                zxAdslAturPrevSnrMgn          INTEGER,
                zxAdslAturPrevAtn             Gauge32,
                zxAdslAturPrevAttainableRate  Gauge32
                }

    zxAdslAturPrevSnrMgn  OBJECT-TYPE
            SYNTAX      INTEGER (-640..640)
            UNITS       "tenth dB"
            MAX-ACCESS  read-only
            STATUS      current
            DESCRIPTION
                 "The adslAturCurrSnrMgn at the time of the last linkup event."
            ::= { zxAdslAturPhysEntry 1 }


    zxAdslAturPrevAtn  OBJECT-TYPE
            SYNTAX      Gauge32(0..630)
            UNITS       "tenth dB"
            MAX-ACCESS  read-only
            STATUS      current
            DESCRIPTION
                 "The adslAturCurrAtn at the time of the last linkup event."
            ::= { zxAdslAturPhysEntry 2 }

    zxAdslAturPrevAttainableRate  OBJECT-TYPE
            SYNTAX      Gauge32
            UNITS       "kbps"
            MAX-ACCESS  read-only
            STATUS      current
            DESCRIPTION
                 "The adslAturCurrAttainableRate at the time of the last linkup event."
            ::= { zxAdslAturPhysEntry 3 }





-- Atuc Channel Table

    zxAdslAtucChanTable  OBJECT-TYPE
            SYNTAX      SEQUENCE OF ZxAdslAtucChanEntry
            MAX-ACCESS  not-accessible
            STATUS      current
            DESCRIPTION
                 "This table provides one row for each Atuc channel.
                 ADSL channel interfaces are those ifEntries
                 where ifType is equal to adslInterleave(124)
                 or adslFast(125)."
            ::= {zxAdslExtMibObjects 5}


    zxAdslAtucChanEntry  OBJECT-TYPE
            SYNTAX      ZxAdslAtucChanEntry
            MAX-ACCESS  not-accessible
            STATUS      current
            DESCRIPTION
                "Adsl channel layer line actuals information entry"
            INDEX    { ifIndex }
            ::= {zxAdslAtucChanTable 1}


    ZxAdslAtucChanEntry ::=
            SEQUENCE {
                zxAdslAtucChanRsSymbols       INTEGER,
                zxAdslAtucChanRsDepth         INTEGER,
                zxAdslAtucChanRsRedundancy    INTEGER
                }

    zxAdslAtucChanRsSymbols  OBJECT-TYPE
            SYNTAX      INTEGER
            MAX-ACCESS  read-only
            STATUS      current
            DESCRIPTION
                 "The number of DMT symbols per ReedSolomon code word (S) in
                 the upstream direction.
                    Note that S is not restricted to interleaved mode only.
                 This parameter is calculated differently for G.992.3 and
                 G.992.5."
            ::= { zxAdslAtucChanEntry 1 }


    zxAdslAtucChanRsDepth  OBJECT-TYPE
            SYNTAX      INTEGER
            MAX-ACCESS  read-only
            STATUS      current
            DESCRIPTION
                 "This parameter indicates interleaving depth (D) in the upstream
                  direction.
                     Note that D is not restricted to interleaved mode only.
                  Even in fast mode, D is a valid constant value and is equal to 1."
            ::= { zxAdslAtucChanEntry 2 }

    zxAdslAtucChanRsRedundancy  OBJECT-TYPE
            SYNTAX      INTEGER
            MAX-ACCESS  read-only
            STATUS      current
            DESCRIPTION
                 "The number of redundant bytes (R) per Reed-Solomon code in the
                  upstream direction. "
            ::= { zxAdslAtucChanEntry 3 }





-- Atur Channel Table

    zxAdslAturChanTable  OBJECT-TYPE
            SYNTAX      SEQUENCE OF ZxAdslAturChanEntry
            MAX-ACCESS  not-accessible
            STATUS      current
            DESCRIPTION
                 "This table provides one row for each ATUR channel.
                 ADSL channel interfaces are those ifEntries
                 where ifType is equal to adslInterleave(124)
                 or adslFast(125)."
            ::= {zxAdslExtMibObjects 6}


    zxAdslAturChanEntry  OBJECT-TYPE
            SYNTAX      ZxAdslAturChanEntry
            MAX-ACCESS  not-accessible
            STATUS      current
            DESCRIPTION
                "Adsl channel layer line actuals information entry"
            INDEX    { ifIndex }
            ::= {zxAdslAturChanTable 1}


    ZxAdslAturChanEntry ::=
            SEQUENCE {
                zxAdslAturChanRsSymbols       INTEGER,
                zxAdslAturChanRsDepth         INTEGER,
                zxAdslAturChanRsRedundancy    INTEGER
                }

    zxAdslAturChanRsSymbols  OBJECT-TYPE
            SYNTAX      INTEGER
            MAX-ACCESS  read-only
            STATUS      current
            DESCRIPTION
                 "The number of DMT symbols per ReedSolomon code word (S) in
                 the upstream direction.
                    Note that S is not restricted to interleaved mode only.
                    This parameter is calculated differently for G.992.3 and
                 G.992.5."
            ::= { zxAdslAturChanEntry 1 }


    zxAdslAturChanRsDepth  OBJECT-TYPE
            SYNTAX      INTEGER
            MAX-ACCESS  read-only
            STATUS      current
            DESCRIPTION
                 "This parameter indicates interleaving depth (D) in the upstream
                  direction.
                     Note that D is not restricted to interleaved mode only.
                  Even in fast mode, D is a valid constant value and is equal to 1."
            ::= { zxAdslAturChanEntry 2 }

    zxAdslAturChanRsRedundancy  OBJECT-TYPE
            SYNTAX      INTEGER
            MAX-ACCESS  read-only
            STATUS      current
            DESCRIPTION
                 "The number of redundant bytes (R) per Reed-Solomon code in the
                  upstream direction. "
            ::= { zxAdslAturChanEntry 3 }



-- Atuc Channel Performance Data Table

    zxAdslAtucChanPerfTable  OBJECT-TYPE
            SYNTAX      SEQUENCE OF ZxAdslAtucChanPerfEntry
            MAX-ACCESS  not-accessible
            STATUS      current
            DESCRIPTION
                 "This table provides one row for each Atuc channel.
                 ADSL channel interfaces are those ifEntries
                 where ifType is equal to adslInterleave(124)
                 or adslFast(125)."
            ::= {zxAdslExtMibObjects 7}


    zxAdslAtucChanPerfEntry  OBJECT-TYPE
            SYNTAX      ZxAdslAtucChanPerfEntry
            MAX-ACCESS  not-accessible
            STATUS      current
            DESCRIPTION
                "DMT channel layer line actuals information entry"
            INDEX    { ifIndex }
            ::= {zxAdslAtucChanPerfTable 1}


    ZxAdslAtucChanPerfEntry ::=
            SEQUENCE {
                zxAdslAtucChanPerfNcd           Counter32,
                zxAdslAtucChanPerfOcd           Counter32,
                zxAdslAtucChanPerfHec           Counter32,
                zxAdslAtucChanPerfCurr15Ncd     Counter32,
                zxAdslAtucChanPerfCurr15Ocd     Counter32,
                zxAdslAtucChanPerfCurr15Hec     Counter32,
                zxAdslAtucChanPerfCurr1DayNcd   Counter32,
                zxAdslAtucChanPerfCurr1DayOcd   Counter32,
                zxAdslAtucChanPerfCurr1DayHec   Counter32,
                zxAdslAtucChanPerfPrev1DayNcd   Counter32,
                zxAdslAtucChanPerfPrev1DayOcd   Counter32,
                zxAdslAtucChanPerfPrev1DayHec   Counter32
                }

    zxAdslAtucChanPerfNcd  OBJECT-TYPE
            SYNTAX      Counter32
            MAX-ACCESS  read-only
            STATUS      current
            DESCRIPTION
                 "Count of no cell delineation (ncd) on this channel."
            ::= { zxAdslAtucChanPerfEntry 1 }

    zxAdslAtucChanPerfOcd  OBJECT-TYPE
            SYNTAX      Counter32
            MAX-ACCESS  read-only
            STATUS      current
            DESCRIPTION
                 "Count of out of cell delineation (ocd) on this channel."
            ::= { zxAdslAtucChanPerfEntry 2 }

    zxAdslAtucChanPerfHec  OBJECT-TYPE
            SYNTAX      Counter32
            MAX-ACCESS  read-only
            STATUS      current
            DESCRIPTION
                 "Header error check counter (hec) on this channel."
            ::= { zxAdslAtucChanPerfEntry 3 }

    zxAdslAtucChanPerfCurr15Ncd  OBJECT-TYPE
            SYNTAX      Counter32
            MAX-ACCESS  read-only
            STATUS      current
            DESCRIPTION
                 "Count of no cell delineation (ncd) on this channel within
                 the current 15 minute time interval."
            ::= { zxAdslAtucChanPerfEntry 4 }


    zxAdslAtucChanPerfCurr15Ocd  OBJECT-TYPE
            SYNTAX      Counter32
            MAX-ACCESS  read-only
            STATUS      current
            DESCRIPTION
                 "Count of out of cell delineation (ocd) on this channel  within
                  the current 15 minute time interval."
            ::= { zxAdslAtucChanPerfEntry 5 }

    zxAdslAtucChanPerfCurr15Hec  OBJECT-TYPE
            SYNTAX      Counter32
            MAX-ACCESS  read-only
            STATUS      current
            DESCRIPTION
                 "Header error check counter (hec) on this channel within the
                 current 15 minute time interval."
            ::= { zxAdslAtucChanPerfEntry 6 }


    zxAdslAtucChanPerfCurr1DayNcd  OBJECT-TYPE
            SYNTAX      Counter32
            MAX-ACCESS  read-only
            STATUS      current
            DESCRIPTION
                 "Count of no cell delineation (ncd) on this channel within
                 the current 1 day interval."
            ::= { zxAdslAtucChanPerfEntry 7 }


    zxAdslAtucChanPerfCurr1DayOcd  OBJECT-TYPE
            SYNTAX      Counter32
            MAX-ACCESS  read-only
            STATUS      current
            DESCRIPTION
                 "Count of out of cell delineation (ocd) on this channel  within
                  the current 1 day interval."
            ::= { zxAdslAtucChanPerfEntry 8 }

    zxAdslAtucChanPerfCurr1DayHec  OBJECT-TYPE
            SYNTAX      Counter32
            MAX-ACCESS  read-only
            STATUS      current
            DESCRIPTION
                 "Header error check counter (hec) on this channel within the
                 current 1 day interval"
            ::= { zxAdslAtucChanPerfEntry 9 }

    zxAdslAtucChanPerfPrev1DayNcd  OBJECT-TYPE
            SYNTAX      Counter32
            MAX-ACCESS  read-only
            STATUS      current
            DESCRIPTION
                 "Count of no cell delineation (ncd) on this channel within
                  the most recent previous 1-day period."
            ::= { zxAdslAtucChanPerfEntry 10 }


    zxAdslAtucChanPerfPrev1DayOcd  OBJECT-TYPE
            SYNTAX      Counter32
            MAX-ACCESS  read-only
            STATUS      current
            DESCRIPTION
                 "Count of out of cell delineation (ocd) on this channel  within
                   the most recent previous 1-day period."
            ::= { zxAdslAtucChanPerfEntry 11 }

    zxAdslAtucChanPerfPrev1DayHec  OBJECT-TYPE
            SYNTAX      Counter32
            MAX-ACCESS  read-only
            STATUS      current
            DESCRIPTION
                 "Header error check counter (hec) on this channel within the most
                  recent previous 1-day period."
            ::= { zxAdslAtucChanPerfEntry 12 }




-- Atur Channel Performance Data Table

    zxAdslAturChanPerfTable  OBJECT-TYPE
            SYNTAX      SEQUENCE OF ZxAdslAturChanPerfEntry
            MAX-ACCESS  not-accessible
            STATUS      current
            DESCRIPTION
                 "This table provides one row for each Atur channel.
                 ADSL channel interfaces are those ifEntries
                 where ifType is equal to adslInterleave(124)
                 or adslFast(125)."
            ::= {zxAdslExtMibObjects 8}


    zxAdslAturChanPerfEntry  OBJECT-TYPE
            SYNTAX      ZxAdslAturChanPerfEntry
            MAX-ACCESS  not-accessible
            STATUS      current
            DESCRIPTION
                "DMT channel layer line actuals information entry"
            INDEX    { ifIndex }
            ::= {zxAdslAturChanPerfTable 1}


    ZxAdslAturChanPerfEntry ::=
            SEQUENCE {
                zxAdslAturChanPerfNcd           Counter32,
                zxAdslAturChanPerfHec           Counter32,
                zxAdslAturChanPerfCurr15Ncd     Counter32,
                zxAdslAturChanPerfCurr15Hec     Counter32,
                zxAdslAturChanPerfCurr1DayNcd   Counter32,
                zxAdslAturChanPerfCurr1DayHec   Counter32,
                zxAdslAturChanPerfPrev1DayNcd   Counter32,
                zxAdslAturChanPerfPrev1DayHec   Counter32
                }

    zxAdslAturChanPerfNcd  OBJECT-TYPE
            SYNTAX      Counter32
            MAX-ACCESS  read-only
            STATUS      current
            DESCRIPTION
                 "Count of no cell delineation (ncd) on this channel."
            ::= { zxAdslAturChanPerfEntry 1 }

    zxAdslAturChanPerfHec  OBJECT-TYPE
            SYNTAX      Counter32
            MAX-ACCESS  read-only
            STATUS      current
            DESCRIPTION
                 "Header error check counter (hec) on this channel."
            ::= { zxAdslAturChanPerfEntry 2 }

    zxAdslAturChanPerfCurr15Ncd  OBJECT-TYPE
            SYNTAX      Counter32
            MAX-ACCESS  read-only
            STATUS      current
            DESCRIPTION
                 "Count of no cell delineation (ncd) on this channel within
                 the current 15 minute time interval."
            ::= { zxAdslAturChanPerfEntry 3 }


    zxAdslAturChanPerfCurr15Hec  OBJECT-TYPE
            SYNTAX      Counter32
            MAX-ACCESS  read-only
            STATUS      current
            DESCRIPTION
                 "Header error check counter (hec) on this channel within the
                 current 15 minute time interval"
            ::= { zxAdslAturChanPerfEntry 4 }


    zxAdslAturChanPerfCurr1DayNcd  OBJECT-TYPE
            SYNTAX      Counter32
            MAX-ACCESS  read-only
            STATUS      current
            DESCRIPTION
                 "Count of no cell delineation (ncd) on this channel within
                 the current 1 day interval."
            ::= { zxAdslAturChanPerfEntry 5 }


    zxAdslAturChanPerfCurr1DayHec  OBJECT-TYPE
            SYNTAX      Counter32
            MAX-ACCESS  read-only
            STATUS      current
            DESCRIPTION
                 "Header error check counter (hec) on this channel within the
                 current 1 day interval"
            ::= { zxAdslAturChanPerfEntry 6 }

    zxAdslAturChanPerfPrev1DayNcd  OBJECT-TYPE
            SYNTAX      Counter32
            MAX-ACCESS  read-only
            STATUS      current
            DESCRIPTION
                 "Count of no cell delineation (ncd) on this channel within
                  the most recent previous 1-day period."
            ::= { zxAdslAturChanPerfEntry 7 }


    zxAdslAturChanPerfPrev1DayHec  OBJECT-TYPE
            SYNTAX      Counter32
            MAX-ACCESS  read-only
            STATUS      current
            DESCRIPTION
                 "Header error check counter (hec) on this channel within the most
                  recent previous 1-day period."
            ::= { zxAdslAturChanPerfEntry 8 }



-- Dsl Loop Test Table

    zxDslLoopTestTable  OBJECT-TYPE
            SYNTAX      SEQUENCE OF ZxDslLoopTestEntry
            MAX-ACCESS  not-accessible
            STATUS      current
            DESCRIPTION
                 "This table provides one row for each DSL line tesing."
            ::= {zxAdslExtMibObjects 9}


    zxDslLoopTestEntry  OBJECT-TYPE
            SYNTAX      ZxDslLoopTestEntry
            MAX-ACCESS  not-accessible
            STATUS      current
            DESCRIPTION
                "DSL line tesing information entry"
            INDEX    { zxDslLoopTestPort }
            ::= {zxDslLoopTestTable 1}


    ZxDslLoopTestEntry ::=
            SEQUENCE {
                zxDslLoopTestPort               INTEGER,
                zxDslLoopTestType               INTEGER,
                zxDslLoopTestOperStatus         INTEGER,
                zxDslLoopTestResult             INTEGER,
                zxDslLoopTestConfParam1         INTEGER,
                zxDslLoopTestConfParam2         INTEGER,
                zxDslLoopTestConfParam3         INTEGER,
                zxDslLoopTestConfParam4         INTEGER,
                zxDslLoopTestConfParam5         INTEGER,
                zxDslLoopTestResultParam1       INTEGER,
                zxDslLoopTestResultParam2       INTEGER,
                zxDslLoopTestResultParam3       INTEGER,
                zxDslLoopTestResultParam4       INTEGER,
                zxDslLoopTestResultParam5       INTEGER,
                zxDslLoopTestRowStatus          RowStatus
                }

    zxDslLoopTestPort  OBJECT-TYPE
            SYNTAX      INTEGER
            MAX-ACCESS  not-accessible
            STATUS      current
            DESCRIPTION
                 "Dsl port number.It should be equal to ifIndex in DSL layer."
            ::= { zxDslLoopTestEntry 1 }

    zxDslLoopTestType  OBJECT-TYPE
            SYNTAX      INTEGER {
                noOper(0),  -- No operation
                cancle(1),  -- Cancle this test
                utopia(2),  -- Utopia loopback test
                afe(3),     -- AFE loopback test
                hybrid(4),  -- Hybrid loopback test
                atuc_OAM(5),-- ATUC data path loopback test,such as ATM OAM loopback.
                atur_OAM(6) -- ATUR data path loopback test,such as ATM OAM loopback.
                }
            MAX-ACCESS  read-create
            STATUS      current
            DESCRIPTION
                 "This is loop test action expected."
            ::= { zxDslLoopTestEntry 2 }


    zxDslLoopTestOperStatus  OBJECT-TYPE
            SYNTAX      INTEGER {
                neverExcute(0),   -- Never excute test
                excuting(1),      -- Excuting test now
                excuted(2),       -- Test has been excuted
                faliedToCommit(3) -- Falied to commit test command to DSL card.
                }
            MAX-ACCESS  read-only
            STATUS      current
            DESCRIPTION
                 "This is loop test operational status.

                  Note: if zxDslLoopTestOperStatus equal to Excuting(1),
                  ifOperStaus should be tesing(3). "
            ::= { zxDslLoopTestEntry 3 }


    zxDslLoopTestResult  OBJECT-TYPE
            SYNTAX      INTEGER {
                NoResult(0),
                Success(1),
                GeneralFailed(2), -- Test failed but no detailed reason.
                NoSupport(3),     -- Current DSL card doesn't support this test.
                Unkown(4),        -- Unkown the test result.
                NoSuchPort(5),    -- No this port on dsl card
                LoopBackFailed(6),-- Loop back failed on dsl card
                PortNotActive(7), -- Some test can't be excuted when port is not actived.
                PortInTesting(8), -- Port in testing and can't excute the new test
                PortInService(9), -- Port in service and can't excute the test
                PortFailures(10), -- Port has failures and can't excute the test
                CardFailures(11), -- Dsl card has failures and can't excute the test
                NoPvcFound(12),   -- No PVC found on the test port or VPI/VCI is not 8/81 while test type is ATUR-OAM
                UnknownTestType(13) -- The test type is not UTOPIA,AFE,HYBRID,ATUC-OAM or ATUR-OAM
            }
            MAX-ACCESS  read-only
            STATUS      current
            DESCRIPTION
                 "This is loop test result and includes reasons for test failures."
            ::= { zxDslLoopTestEntry 4 }


    zxDslLoopTestConfParam1  OBJECT-TYPE
            SYNTAX      INTEGER
            MAX-ACCESS  read-create
            STATUS      current
            DESCRIPTION
                 "Configuration param for some looptest.Its definition may be deferent
                 according to the zxDslLoopTestType value and device type.

                 For DSL8220v2.x:
                    zxDslLoopTestType          zxDslLoopTestConfParam1
                    --------------------------------------------------
                    UTOPIA(2)                  OAM cells number
                    AFE(3)                     OAM cells number
                    HYBRID(4)                  OAM cells number
                    ATUC_OAM(5)                OAM cells number
                    ATUR_OAM(6)                OAM cells number

                  "
             ::= { zxDslLoopTestEntry 5 }

    zxDslLoopTestConfParam2  OBJECT-TYPE
            SYNTAX      INTEGER
            MAX-ACCESS  read-create
            STATUS      current
            DESCRIPTION
                 "Configuration param for some looptest.Its definition may be deferent
                 according to the zxDslLoopTestType value and device type.
                 No looptest uses this param now."
             ::= { zxDslLoopTestEntry 6 }

    zxDslLoopTestConfParam3  OBJECT-TYPE
            SYNTAX      INTEGER
            MAX-ACCESS  read-create
            STATUS      current
            DESCRIPTION
                 "Configuration param for some looptest.Its definition may be deferent
                 according to the zxDslLoopTestType value and device type.
                 No looptest uses this param now."
             ::= { zxDslLoopTestEntry 7 }

    zxDslLoopTestConfParam4  OBJECT-TYPE
            SYNTAX      INTEGER
            MAX-ACCESS  read-create
            STATUS      current
            DESCRIPTION
                 "Configuration param for some looptest.Its definition may be deferent
                 according to the zxDslLoopTestType value and device type.
                 No looptest uses this param now."
             ::= { zxDslLoopTestEntry 8 }

    zxDslLoopTestConfParam5  OBJECT-TYPE
            SYNTAX      INTEGER
            MAX-ACCESS  read-create
            STATUS      current
            DESCRIPTION
                 "Configuration param for some looptest.Its definition may be deferent
                 according to the zxDslLoopTestType value and device type.
                 No looptest uses this param now."
             ::= { zxDslLoopTestEntry 9 }


    zxDslLoopTestResultParam1  OBJECT-TYPE
            SYNTAX      INTEGER
            MAX-ACCESS  read-only
            STATUS      current
            DESCRIPTION
                 "Loop test result param for some looptest.Its definition may be deferent
                 according to the zxDslLoopTestType value and device type.

                 For DSL8220v2.x:
                    zxDslLoopTestType          zxDslLoopTestConfParam1
                    --------------------------------------------------
                    ATUR_OAM(6)                Recieved OAM cells number

                 "
             ::= { zxDslLoopTestEntry 10 }

    zxDslLoopTestResultParam2  OBJECT-TYPE
            SYNTAX      INTEGER
            MAX-ACCESS  read-only
            STATUS      current
            DESCRIPTION
                 "Loop test result param for some looptest.Its definition may be deferent
                 according to the zxDslLoopTestType value and device type.
                 No looptest uses this param now."

             ::= { zxDslLoopTestEntry 11 }

    zxDslLoopTestResultParam3  OBJECT-TYPE
            SYNTAX      INTEGER
            MAX-ACCESS  read-only
            STATUS      current
            DESCRIPTION
                 "Loop test result param for some looptest.Its definition may be deferent
                 according to the zxDslLoopTestType value and device type.
                 No looptest uses this param now."
             ::= { zxDslLoopTestEntry 12 }

    zxDslLoopTestResultParam4  OBJECT-TYPE
            SYNTAX      INTEGER
            MAX-ACCESS  read-only
            STATUS      current
            DESCRIPTION
                 "Loop test result param for some looptest.Its definition may be deferent
                 according to the zxDslLoopTestType value and device type.
                 No looptest uses this param now."
             ::= { zxDslLoopTestEntry 13 }

    zxDslLoopTestResultParam5  OBJECT-TYPE
            SYNTAX      INTEGER
            MAX-ACCESS  read-only
            STATUS      current
            DESCRIPTION
                 "Loop test result param for some looptest.Its definition may be deferent
                 according to the zxDslLoopTestType value and device type.
                 No looptest uses this param now."
             ::= { zxDslLoopTestEntry 14 }


    zxDslLoopTestRowStatus  OBJECT-TYPE
            SYNTAX      RowStatus
            MAX-ACCESS  read-create
            STATUS      current
            DESCRIPTION
                 "Loop test table RowStatus . "
             ::= { zxDslLoopTestEntry 15 }





--  Adsl Line Alarm Profile Extended Table


    zxAdslLineAlarmConfProfileExtTable  OBJECT-TYPE
            SYNTAX      SEQUENCE OF ZxAdslLineAlarmConfProfileExtEntry
            MAX-ACCESS  not-accessible
            STATUS      current
            DESCRIPTION
                "Adsl line alarm config profile extended information table.
            The cycle of thresholds monitoring shoul be less than 5 minutes."
            ::= {zxAdslExtMibObjects 20}


    zxAdslLineAlarmConfProfileExtEntry  OBJECT-TYPE
            SYNTAX      ZxAdslLineAlarmConfProfileExtEntry
            MAX-ACCESS  not-accessible
            STATUS      current
            DESCRIPTION
               "An entry extends the adslLineAlarmConfProfileEntry defined in
               [RFC2662]. Each entry corresponds to an ADSL line alarm profile."

            AUGMENTS    { adslLineAlarmConfProfileEntry }
            ::= {zxAdslLineAlarmConfProfileExtTable 1}


    ZxAdslLineAlarmConfProfileExtEntry ::=
            SEQUENCE {
                zxAdslAtucConnRateTolerance          INTEGER,
                zxAdslAturConnRateTolerance          INTEGER,
                zxAdslThreshAtucConnRate             INTEGER,
                zxAdslThreshAturConnRate             INTEGER,
                zxAdslThreshAtucBandwidthUtil        INTEGER,
                zxAdslThreshAturBandwidthUtil        INTEGER,
                zxAdslThreshAtucPacketLossRate       INTEGER,
                zxAdslThreshAturPacketLossRate       INTEGER,
                zxAdslThreshAtucBlockErrorRate       INTEGER,
                zxAdslThreshAturBlockErrorRate       INTEGER,
                zxAdslThreshReservedMetric1          INTEGER,
                zxAdslThreshReservedMetric2          INTEGER,
                zxAdslThreshReservedMetric3          INTEGER
                }


    zxAdslAtucConnRateTolerance  OBJECT-TYPE
            SYNTAX      INTEGER(0..100)
            UNITS       "%"
            MAX-ACCESS  read-create
            STATUS      current
            DESCRIPTION
                " Tolerance between configured adslAtucChanConfInterleaveMaxTxRate and
                actual adslAtucChanCurrTxRate.

                Calculation:

                           100*(adslAtucChanConfInterleaveMaxTxRate - adslAtucChanCurrTxRate)
                Difference =-------------------------------------------------------------------
                                          adslAtucChanConfInterleaveMaxTxRate

                If Difference  is larger than zxAdslAtucConnRateTolerance,
                zxAdslAtucConnRateOverThreshTrap trap will be sent.

                  A value of `0' will disable the trap. "

            DEFVAL { 0 }
            ::= { zxAdslLineAlarmConfProfileExtEntry 1 }



    zxAdslAturConnRateTolerance  OBJECT-TYPE
            SYNTAX      INTEGER(0..100)
            UNITS       "%"
            MAX-ACCESS  read-create
            STATUS      current
            DESCRIPTION
                " Tolerance between configured adslAturChanConfInterleaveMaxTxRate and
                actual adslAturChanCurrTxRate.

                Calculation:

                           100*(adslAturChanConfInterleaveMaxTxRate - adslAturChanCurrTxRate)
                Difference =-------------------------------------------------------------------
                                          adslAturChanConfInterleaveMaxTxRate


                If Difference  is larger than zxAdslAturConnRateTolerance,
                zxAdslAturConnRateOverThreshTrap trap will be sent.

                  A value of `0' will disable the trap. "

            DEFVAL { 0 }
            ::= { zxAdslLineAlarmConfProfileExtEntry 2 }



    zxAdslThreshAtucConnRate  OBJECT-TYPE
            SYNTAX      INTEGER
            UNITS       "kbps"
            MAX-ACCESS  read-create
            STATUS      current
            DESCRIPTION
                "   Threshold of Atuc connection rate.
                    If adslAtucChanCurrTxRate  is lower than zxAdslThreshAtucConnRate,
                zxAdslAtucConnRateOverThreshTrap trap will be sent.
                    A value of `0' will disable the trap. "

            DEFVAL { 0 }
            ::= { zxAdslLineAlarmConfProfileExtEntry 3 }



    zxAdslThreshAturConnRate  OBJECT-TYPE
            SYNTAX      INTEGER
            UNITS       "kbps"
            MAX-ACCESS  read-create
            STATUS      current
            DESCRIPTION
                "   Threshold of Atur connection rate.
                    If adslAturChanCurrTxRate  is lower than zxAdslThreshAturConnRate,
                zxAdslAturConnRateOverThreshTrap trap will be sent.
                    A value of `0' will disable the trap. "

            DEFVAL { 0 }
            ::= { zxAdslLineAlarmConfProfileExtEntry 4 }


    zxAdslThreshAtucBandwidthUtil  OBJECT-TYPE
            SYNTAX      INTEGER(0..100)
            UNITS       "%"
            MAX-ACCESS  read-create
            STATUS      current
            DESCRIPTION
                "  Threshold of Atuc bandwidth utilization.

                Calculation:

                                                 Delta(ifOutOctets)*8*1024*100
                    Atuc Utilization = ----------------------------------------------------
                                       (time interval)*adslAtucChanConfInterleaveMaxTxRate

                where:
                    Delta(ifOutOctets):  difference of ifOutOctets in two polling cycles
                                        of collecting the ifOutOctets.
                                        Unit is bytes.

                    (time interval)  :  the polling cycles.
                                        Unit is seconds.

                    adslAtucChanConfInterleaveMaxTxRate: configured atuc Tx rate.
                                        Unit is kbps.


                or
                                                 zxAdslLineTxDataRate*100
                    Atuc Utilization = ----------------------------------------------------
                                              adslAtucChanConfInterleaveMaxTxRate

                    zxAdslLineTxDataRate               : actual atuc Tx rate.      Unit is kbps.
                    adslAtucChanConfInterleaveMaxTxRate: configured atuc Tx rate.  Unit is kbps.



                If Utilization is larger than zxAdslThreshAtucBandwidthUtil,
                zxAdslAtucBandwidthUtilOverThreshTrap trap will be sent.

                  A value of `0' will disable the trap. "

            DEFVAL { 0 }
            ::= { zxAdslLineAlarmConfProfileExtEntry 5 }


    zxAdslThreshAturBandwidthUtil  OBJECT-TYPE
            SYNTAX      INTEGER(0..100)
            UNITS       "%"
            MAX-ACCESS  read-create
            STATUS      current
            DESCRIPTION
                "  Threshold of Atur bandwidth utilization.

                Calculation:

                                                 Delta(ifInOctets)*8*1024*100
                    Atur Utilization = ----------------------------------------------------
                                       (time interval)*adslAturChanConfInterleaveMaxTxRate

                where:
                    Delta(ifInOctets):  difference of ifInOctets in two poll cycles
                                        of collecting the ifInOctets.
                                        Unit is bytes.

                    (time interval)  :  the poll cycles.
                                        Unit is seconds.

                    adslAturChanConfInterleaveMaxTxRate: configured atur Tx rate.
                                        Unit is kbps.

                or
                                                 zxAdslLineRxDataRate*100
                    Atur Utilization = ----------------------------------------------------
                                              adslAturChanConfInterleaveMaxTxRate

                    zxAdslLineRxDataRate               : actual atuc Rx rate.      Unit is kbps.
                    adslAturChanConfInterleaveMaxTxRate: configured atur Tx rate.  Unit is kbps.

                If Utilization is larger than zxAdslThreshAturBandwidthUtil,
                zxAdslAturBandwidthUtilOverThreshTrap trap will be sent.

                  A value of `0' will disable the trap. "

            DEFVAL { 0 }
            ::= { zxAdslLineAlarmConfProfileExtEntry 6 }


    zxAdslThreshAtucPacketLossRate  OBJECT-TYPE
            SYNTAX      INTEGER(0..100)
            UNITS       "%"
            MAX-ACCESS  read-create
            STATUS      current
            DESCRIPTION
                "  The percentage of lost packets to total packets received on
                the Atuc interface.

                Calculation:
                                                      ifOutDiscards*100
                  Atuc PacketLossRate = ---------------------------------------------------
                                        ifOutUcastPkts+ifOutMulticastPkts+ifOutBroadcastPkts


                If this threshold is across, zxAdslAtucPacketLossRateOverThreshTrap trap will be sent.
                   A value of `0' will disable the trap. "

            DEFVAL { 0 }
            ::= { zxAdslLineAlarmConfProfileExtEntry 7 }


    zxAdslThreshAturPacketLossRate  OBJECT-TYPE
            SYNTAX      INTEGER(0..100)
            UNITS       "%"
            MAX-ACCESS  read-create
            STATUS      current
            DESCRIPTION
                "  The percentage of lost packets  to total packets received on
                the Atur interface.

                Calculation:
                                                      ifInDiscards*100
                  Atur PacketLossRate = ---------------------------------------------------
                                        ifInUcastPkts+ifInMulticastPkts+ifInBroadcastPkts


                If this threshold is across, zxAdslAturPacketLossRateOverThreshTrap trap will be sent.
                   A value of `0' will disable the trap. "

            DEFVAL { 0 }
            ::= { zxAdslLineAlarmConfProfileExtEntry 8 }



    zxAdslThreshAtucBlockErrorRate  OBJECT-TYPE
            SYNTAX      INTEGER(0..100)
            UNITS       "%"
            MAX-ACCESS  read-create
            STATUS      current
            DESCRIPTION
                "  The percentage of adslAtucChanUncorrectBlks to
                adslAtucChanReceivedBlks on the Atuc interface.
                If this threshold is across, zxAdslAtucBlockErrorRateOverThreshTrap
                trap will be sent.
                   A value of `0' will disable the trap.   "

            DEFVAL { 0 }
            ::= { zxAdslLineAlarmConfProfileExtEntry 9 }


    zxAdslThreshAturBlockErrorRate  OBJECT-TYPE
            SYNTAX      INTEGER(0..100)
            UNITS       "%"
            MAX-ACCESS  read-create
            STATUS      current
            DESCRIPTION
                "  The percentage of adslAturChanUncorrectBlks to
                adslAturChanReceivedBlks on the Atur interface.
                If this threshold is across, zxAdslAturBlockErrorRateOverThreshTrap
                trap will be sent.
                   A value of `0' will disable the trap. "

            DEFVAL { 0 }
            ::= { zxAdslLineAlarmConfProfileExtEntry 10 }


    zxAdslThreshReservedMetric1  OBJECT-TYPE
            SYNTAX      INTEGER(0..100)
            UNITS       ""
            MAX-ACCESS  read-create
            STATUS      current
            DESCRIPTION
                "  reserved threshold.
                   A value of `0' will disable the trap. "

            DEFVAL { 0 }
            ::= { zxAdslLineAlarmConfProfileExtEntry 11 }


    zxAdslThreshReservedMetric2  OBJECT-TYPE
            SYNTAX      INTEGER(0..100)
            UNITS       ""
            MAX-ACCESS  read-create
            STATUS      current
            DESCRIPTION
                "  reserved threshold.
                   A value of `0' will disable the trap. "

            DEFVAL { 0 }
            ::= { zxAdslLineAlarmConfProfileExtEntry 12 }

    zxAdslThreshReservedMetric3  OBJECT-TYPE
            SYNTAX      INTEGER(0..100)
            UNITS       ""
            MAX-ACCESS  read-create
            STATUS      current
            DESCRIPTION
                "  reserved threshold.
                   A value of `0' will disable the trap. "

            DEFVAL { 0 }
            ::= { zxAdslLineAlarmConfProfileExtEntry 13 }






--  trap definitions

    zxAdslExtTraps OBJECT IDENTIFIER ::= { zxAdslExtMib 2 }


    zxAdslAtuxConnRateOverThreshTrap      NOTIFICATION-TYPE
            OBJECTS { adslAtucChanConfInterleaveMaxTxRate,
                      adslAtucChanCurrTxRate  }
            STATUS  current
            DESCRIPTION
                "zxAdslAtucConnRateTolerance threshold or zxAdslThreshAtucConnRate reached."
            ::= { zxAdslExtTraps 1 }


    zxAdslAtuxConnRateUnderThreshTrap      NOTIFICATION-TYPE
            OBJECTS { adslAtucChanConfInterleaveMaxTxRate,
                      adslAtucChanCurrTxRate  }
            STATUS  current
            DESCRIPTION
                " AtucConnRate Difference is below threshold of zxAdslAtucConnRateTolerance.
                 Or adslAtucChanCurrTxRate is below threshold of zxAdslThreshAtucConnRate. "
            ::= { zxAdslExtTraps 2 }


    zxAdslAtucBandwidthUtilOverThreshTrap      NOTIFICATION-TYPE
            OBJECTS { adslAtucChanConfInterleaveMaxTxRate,
                      zxAdslLineTxDataRate }
            STATUS  current
            DESCRIPTION
                "zxAdslThreshAtucBandwidthUtil threshold reached."
            ::= { zxAdslExtTraps 5 }


    zxAdslAtucBandwidthUtilUnderThreshTrap      NOTIFICATION-TYPE
            OBJECTS { adslAtucChanConfInterleaveMaxTxRate,
                      zxAdslLineTxDataRate }
            STATUS  current
            DESCRIPTION
                "Atuc BandwidthUtil  is below threshold of zxAdslThreshAtucBandwidthUtil."
            ::= { zxAdslExtTraps 6 }


    zxAdslAturBandwidthUtilOverThreshTrap      NOTIFICATION-TYPE
            OBJECTS { adslAturChanConfInterleaveMaxTxRate,
                      zxAdslLineRxDataRate }
            STATUS  current
            DESCRIPTION
                "zxAdslThreshAturBandwidthUtil threshold reached."
            ::= { zxAdslExtTraps 7 }


    zxAdslAturBandwidthUtilUnderThreshTrap      NOTIFICATION-TYPE
            OBJECTS { adslAturChanConfInterleaveMaxTxRate,
                      zxAdslLineRxDataRate }
            STATUS  current
            DESCRIPTION
                "Atur BandwidthUtil  is below threshold of zxAdslThreshAturBandwidthUtil."
            ::= { zxAdslExtTraps 8 }



    zxAdslAtucPacketLossRateOverThreshTrap      NOTIFICATION-TYPE
            OBJECTS { ifOutDiscards, ifOutUcastPkts,
                      ifOutMulticastPkts, ifOutBroadcastPkts
                       }
            STATUS  current
            DESCRIPTION
                "zxAdslThreshAtucPacketLossRate threshold reached."
            ::= { zxAdslExtTraps 9 }

    zxAdslAtucPacketLossRateUnderThreshTrap      NOTIFICATION-TYPE
            OBJECTS { ifOutDiscards, ifOutUcastPkts,
                      ifOutMulticastPkts, ifOutBroadcastPkts
                       }
            STATUS  current
            DESCRIPTION
                "Atuc PacketLossRate is below  threshold of zxAdslThreshAtucPacketLossRate."
            ::= { zxAdslExtTraps 10 }



    zxAdslAturPacketLossRateOverThreshTrap      NOTIFICATION-TYPE
            OBJECTS { ifInDiscards, ifInUcastPkts,
                      ifInMulticastPkts, ifInBroadcastPkts
                       }
            STATUS  current
            DESCRIPTION
                "zxAdslThreshAturPacketLossRate threshold reached."
            ::= { zxAdslExtTraps 11 }



    zxAdslAturPacketLossRateUnderThreshTrap      NOTIFICATION-TYPE
            OBJECTS { ifInDiscards, ifInUcastPkts,
                      ifInMulticastPkts, ifInBroadcastPkts
                       }
            STATUS  current
            DESCRIPTION
                "Atur PacketLossRate is below  threshold of zxAdslThreshAturPacketLossRate."
            ::= { zxAdslExtTraps 12 }


    zxAdslAtucBlockErrorRateOverThreshTrap      NOTIFICATION-TYPE
            OBJECTS { adslAtucChanUncorrectBlks,
                      adslAtucChanReceivedBlks }
            STATUS  current
            DESCRIPTION
                "zxAdslThreshAtucBlockErrorRate threshold reached."
            ::= { zxAdslExtTraps 13 }


    zxAdslAtucBlockErrorRateUnderThreshTrap      NOTIFICATION-TYPE
            OBJECTS { adslAtucChanUncorrectBlks,
                      adslAtucChanReceivedBlks }
            STATUS  current
            DESCRIPTION
                " Atuc BlockErrorRate is below  threshold of zxAdslThreshAtucBlockErrorRate."
            ::= { zxAdslExtTraps 14 }

    zxAdslAturBlockErrorRateOverThreshTrap      NOTIFICATION-TYPE
            OBJECTS { adslAturChanUncorrectBlks,
                      adslAturChanReceivedBlks }
            STATUS  current
            DESCRIPTION
                "zxAdslThreshAturBlockErrorRate threshold reached."
            ::= { zxAdslExtTraps 15 }

    zxAdslAturBlockErrorRateUnderThreshTrap      NOTIFICATION-TYPE
            OBJECTS { adslAturChanUncorrectBlks,
                      adslAturChanReceivedBlks }
            STATUS  current
            DESCRIPTION
                "Atur BlockErrorRate  is below threshold of zxAdslThreshAturBlockErrorRate."
            ::= { zxAdslExtTraps 16 }


END
