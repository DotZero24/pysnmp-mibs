--------------------------------------------------------------------------
-- File Name : ZTE-AN-SYNCE-MIB.mib
-- Date      : 2010-07-28
-- Author    : ZTE Nms dept.

--
-- Zte Ethernet Synchronization Mib for Access Node
--
--------------------------------------------------------------------------

ZTE-AN-SYNCE-MIB    DEFINITIONS ::= BEGIN

    IMPORTS
        MODULE-IDENTITY                  FROM SNMPv2-SMI
        zxAn,ZxAnIfindex                 FROM ZTE-AN-TC-MIB;


    zxAnSyncEMib        MODULE-IDENTITY
        LAST-UPDATED    "201007281600Z"
        ORGANIZATION    "ZTE Corporation"
        CONTACT-INFO    "ZTE NMS dept.
                        Li Xiaochun  68896452"
        DESCRIPTION     "This MIB defines description of ZTE Ethernet
                        Synchronization objects."
        ::=  { zxAn 65 }

    zxAnSyncEObjects    OBJECT IDENTIFIER ::=  {  zxAnSyncEMib  1  }

    zxAnSyncETrapObjects    OBJECT IDENTIFIER    ::=  {  zxAnSyncEMib  2  }

--------------------------------------------------------------------------------
-- Following objects are defined.

-- 1. Global Configuration
-- 2. SyncE NNI Port Table
-- Trap Objects
--------------------------------------------------------------------------------


--------------------------------------------------------------------------------
-- 1. Global Configuration
--------------------------------------------------------------------------------

    zxAnSyncEGlobalObjects  OBJECT IDENTIFIER    ::=  {  zxAnSyncEObjects  1  }

    zxAnSyncEClockSourceType OBJECT-TYPE
       SYNTAX               INTEGER
          {
              localClock    (1),
              gps1pps       (2),
              pon8k         (3),
              clockRecovery (4)
          }
       MAX-ACCESS       read-write
       STATUS           current
       DESCRIPTION      "Specifies the source of the transmit clock.
              localClock: indicates that a local clock source is used.
              gps1pps:indicates that an external clock source GPS 1PPS is used.
              pon8k:  indicates that an external clock source
                      1/8th of a sec at 8k sample rate (125ms) is used.
              clockRecovery :indicates that recovered receive clock from another
                             interface is used as the transmit clock."
       ::=  {  zxAnSyncEGlobalObjects  1  }

    zxAnSyncEClockRecoveryPort OBJECT-TYPE
       SYNTAX               ZxAnIfindex
       MAX-ACCESS           read-write
       STATUS               current
       DESCRIPTION          "Specifies the port where the clock is recovered and
                            used as the transmit clock. this value must be set
                            when zxAnSyncEClockSourceType is clockRecovery,
                            meanwhile, the clock mode for this port must be in
                            the slave mode."
       ::=  {  zxAnSyncEGlobalObjects  2  }

    zxAnSyncEUniPortSyncEnable OBJECT-TYPE
       SYNTAX                  INTEGER
          {
              enable  (1),
              disable (2)
          }
       MAX-ACCESS       read-write
       STATUS           current
       DESCRIPTION      "Enable/disable SyncE on all the UNI ports."
       DEFVAL { disable }
       ::=  {  zxAnSyncEGlobalObjects  3  }

    zxAnSyncEClockSourceStatus OBJECT-TYPE
       SYNTAX                 INTEGER
          {
              valid    (1),
              invalid  (2)
          }
       MAX-ACCESS       read-only
       STATUS           current
       DESCRIPTION      "The network clock source status.
                         'valid' indicates the selected network clock source is
                         valid, 'invalid' indicates the selected network clock
                         source is invalid due to clock frequency offset
                         exceeded limit or other factors."
       ::=  {  zxAnSyncEGlobalObjects  4  }

   zxAnSyncEClockOperationStatus OBJECT-TYPE
       SYNTAX           INTEGER
          {
              freerunPhaselockedNormal(1),
              holdover(2),
              locked(4),
              prelocked2LostPhase(5),
              prelocked(6),
              lostPhase(7),
              freerun2PhaselockedAbnormal(11),
              directPass(14),
              destroyFreerunOrHoldover(21),
              acquiring(22),
              unknown(255)
          }
       MAX-ACCESS       read-only
       STATUS           current
       DESCRIPTION      "Operation status of the clock.
                         'freerunPhaselockedNormal' indicates the freerun mode
                         conforms to the
                         freerun mode defined above. It is essentially a
                         temporary mode until a valid source is available.
                         'holdover' indicates the holdover mode conforms to the
                         holdover mode defined above. The holdover memory is no
                         longer updated by the incoming reference clock.
                         'locked' indicates a steady state mode, entered when
                         holdover memory is acquired.
                         'prelocked2LostPhase' indicates pre-locked2 status, the
                         clock try to pre-locked in lost Phase status.
                         'prelocked' indicates pre-locked status.
                         'lostPhase' indicates lost Phase status.
                         'freerun2PhaselockedAbnormal' indicates free-running2
                         status, the phase-locked loop is abnormal.
                         'directPass' indicates direct pass status.
                         'destroyFreerunOrHoldover' indicates destroy freerun or
                         holdover status.
                         'acquiring' indicates a temporary mode when coming from
                         freerun, to acquire holdover memory.
                         'unknown' indicates the clock operation status is
                         unknown."
       ::=  {  zxAnSyncEGlobalObjects  5  }

--------------------------------------------------------------------------------
-- 2. SyncE NNI Port Table
--------------------------------------------------------------------------------
    zxAnSyncENniPortTable OBJECT-TYPE
        SYNTAX       SEQUENCE OF ZxAnSyncENniPortEntry
        MAX-ACCESS   not-accessible
        STATUS       current
        DESCRIPTION  "The SyncE NNI Port Table."
        ::= { zxAnSyncEObjects 2 }

    zxAnSyncENniPortEntry OBJECT-TYPE
        SYNTAX       ZxAnSyncENniPortEntry
        MAX-ACCESS   not-accessible
        STATUS       current
        DESCRIPTION  "The SyncE NNI Port Entry"
        INDEX { zxAnSyncENniPortIndex }
        ::= { zxAnSyncENniPortTable 1 }

    ZxAnSyncENniPortEntry ::= SEQUENCE {
        zxAnSyncENniPortIndex               ZxAnIfindex,
        zxAnSyncENniPortSyncEnable          INTEGER,
        zxAnSyncENniPortClockMode           INTEGER
    }

    zxAnSyncENniPortIndex OBJECT-TYPE
        SYNTAX       ZxAnIfindex
        MAX-ACCESS   not-accessible
        STATUS       current
        DESCRIPTION  "An index for a NNI port."
        ::= { zxAnSyncENniPortEntry 1 }

    zxAnSyncENniPortSyncEnable OBJECT-TYPE
       SYNTAX                  INTEGER
          {
              enable  (1),
              disable (2)
          }
       MAX-ACCESS       read-write
       STATUS           current
       DESCRIPTION      "Enable/disable SyncE on specific NNI port."
       DEFVAL { disable }
       ::=  {  zxAnSyncENniPortEntry  2 }

    zxAnSyncENniPortClockMode OBJECT-TYPE
        SYNTAX       INTEGER
        {
            master (1),
            slave  (2)
        }
        MAX-ACCESS   read-write
        STATUS       current
        DESCRIPTION  "The clock mode of NNI port. This value must be set to
                     slave when the NNI port is used for clock recovery."
        ::= { zxAnSyncENniPortEntry 3 }

--------------------------------------------------------------------------------
-- Trap Objects
--------------------------------------------------------------------------------

END
