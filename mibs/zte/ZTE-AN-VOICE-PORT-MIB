--------------------------------------------------------------------------------
-- File Name : ZTE-AN-VOICE-PORT-MIB.mib
-- Date      : 2010-08-24
-- Author    : ZTE NMS Dept.
--
-- ZTE Voice Port MIB for Access Node
--
--------------------------------------------------------------------------------

ZTE-AN-VOICE-PORT-MIB DEFINITIONS ::= BEGIN

IMPORTS
        MODULE-IDENTITY, NOTIFICATION-TYPE, OBJECT-TYPE, enterprises,
        IpAddress, Counter32, Integer32, Counter64, Unsigned32, Gauge32
                            FROM SNMPv2-SMI
        TEXTUAL-CONVENTION, MacAddress, DateAndTime, RowStatus, DisplayString,
        TruthValue          FROM SNMPv2-TC
        InetAddressType, InetAddress         FROM INET-ADDRESS-MIB;

zxAnVoicePortMib MODULE-IDENTITY
    LAST-UPDATED "201008241400Z"
    ORGANIZATION "ZTE Corporation"
    CONTACT-INFO "Fuhua
                  Mail: fu.hua@zte.com.cn
                  Tel : 021-68896250"
    DESCRIPTION   "The MIB module for the management of voice ports."
::= { zxAn 5200 }

--------------------------------------------------------------------------------
-- Following objects are defined.
-- 1. a200SlcTable
-- 2. zxAnVoicePortGlobalObjects
-- 3. PSTN Port Electrical Characteristics Table
--------------------------------------------------------------------------------
zte OBJECT IDENTIFIER ::= { enterprises 3902 }
zxAn OBJECT IDENTIFIER ::= { zte 1015 }
zxAnVoiceMgmt       OBJECT IDENTIFIER ::= {zxAnVoicePortMib 3}
zxAnVoicePortConfig OBJECT IDENTIFIER ::= {zxAnVoiceMgmt 3}

--------------------------------------------------------------------------------
-- 1. a200SlcTable
--------------------------------------------------------------------------------

    a200SlcTable OBJECT-TYPE
        SYNTAX      SEQUENCE OF A200SlcEntry
        MAX-ACCESS  not-accessible
        STATUS      current
        DESCRIPTION
            "\u7528\u6237\u7535\u8def\u8868\uff0c\u63cf\u8ff0\u7528\u6237
             \u7535\u8def\u7684\u72b6\u6001\uff0c\u53ca\u7535\u8def\u529f
             \u80fd\u914d\u7f6e"
        ::= { zxAnVoicePortConfig 1 }

    a200SlcEntry OBJECT-TYPE
        SYNTAX      A200SlcEntry
        MAX-ACCESS  not-accessible
        STATUS      current
        DESCRIPTION
            "describe colunms and index in slc table"
        INDEX { a200slcrackno, a200slcshelfno, a200slcslotno, a200slcindex}
        ::= { a200SlcTable 1 }

    A200SlcEntry ::= SEQUENCE {
        a200slcrackno                       Integer32,
        a200slcshelfno                      Integer32,
        a200slcslotno                       Integer32,
        a200slcindex                        Integer32,
        a200slcpkg                          Integer32,
        a200slcstatus                       Integer32,
        a200slcdftevent                     INTEGER,
        a200slcusermode                     INTEGER,
        a200slcFaxMode                      INTEGER,
        a200slcQovsId                       INTEGER,
        a200slcCIDType                      INTEGER,
        a200slcImType                       INTEGER,
        a200slcecenable                     INTEGER,
        a200slcuserclass                    INTEGER,
        a200slcPktToPcmGain                 INTEGER,
        a200slcPcmToPktGain                 INTEGER,
        a200slcphonenum                     DisplayString,
        a200slcoperNum                      INTEGER,
        a200slcblockoper                    INTEGER,
        a200slcunblockoper                  INTEGER,
        a200slcmonitorflag                  INTEGER,
        a200slcmonitoreerack                INTEGER,
        a200slcmonitoreeshelf               INTEGER,
        a200slcmonitoreeslot                INTEGER,
        a200slcmonitoreeindex               INTEGER,
        a200slcDialMode                     INTEGER,
        a200slcFeedCurrent                  INTEGER,
        a200slcHighImpedanceOper            INTEGER,
        a200slcNoneHighImpedanceOper        INTEGER,
        zxAnSlcDelayDialMode                INTEGER,
        zxAnSlcDdiTrapEnable                INTEGER,
        zxAnSlcSemiPerConnSrcIpAddr         IpAddress,
        zxAnSlcSemiPerConnSrcPort           Integer32,
        zxAnSlcSemiPerConnDstIpAddr         IpAddress,
        zxAnSlcSemiPerConnDstPort           Integer32,
        zxAnSlcSemiPerConnSdpProfileId      Integer32,
        zxAnSlcSemiPerConnSdpInformation    DisplayString
        }

    a200slcrackno  OBJECT-TYPE
        SYNTAX      Integer32
        MAX-ACCESS  not-accessible
        STATUS      current
        DESCRIPTION
            "\u7535\u8def\u5e8f\u53f7"
        ::= { a200SlcEntry 1 }

    a200slcshelfno  OBJECT-TYPE
        SYNTAX      Integer32
        MAX-ACCESS  not-accessible
        STATUS      current
        DESCRIPTION
            "\u7535\u8def\u5e8f\u53f7"
        ::= { a200SlcEntry 2 }

    a200slcslotno  OBJECT-TYPE
        SYNTAX      Integer32
        MAX-ACCESS  not-accessible
        STATUS      current
        DESCRIPTION
            "\u7535\u8def\u5e8f\u53f7"
        ::= { a200SlcEntry 3 }

    a200slcindex  OBJECT-TYPE
        SYNTAX      Integer32
        MAX-ACCESS  not-accessible
        STATUS      current
        DESCRIPTION
            "\u7535\u8def\u5e8f\u53f7"
        ::= { a200SlcEntry 4 }

    a200slcpkg    OBJECT-TYPE
        SYNTAX      Integer32
        MAX-ACCESS  read-write
        STATUS      current
        DESCRIPTION
            "\u7535\u8def\u652f\u6301\u7684\u5305\u7c7b\u578b\uff0c\u6309\u4f4d
              \u53d6\u503c"
        ::= { a200SlcEntry 5 }

    a200slcstatus   OBJECT-TYPE
        SYNTAX      Integer32
        MAX-ACCESS  read-only
        STATUS      current
        DESCRIPTION
            "\u7535\u8def\u72b6\u6001\uff0c\u6309\u4f4d\u53d6\u503c"
        ::= { a200SlcEntry 6 }

    a200slcdftevent  OBJECT-TYPE
        SYNTAX      INTEGER(0..127)
        MAX-ACCESS  read-write
        STATUS      current
        DESCRIPTION
            "\u7535\u8def\u7f3a\u7701\u68c0\u6d4b\u4e8b\u4ef6\u7c7b\u578b
            \uff0c\u6309\u4f4d\u53d6\u503c"
        ::= { a200SlcEntry 7 }

    a200slcusermode   OBJECT-TYPE
        SYNTAX      INTEGER {
            usermodeIdle(0),
            usermodeH248(1),
            usermodeZteUni(2),
            usermodeV5(3),
            usermodeZ(4),
            usermodeMgcp(5),
            usermodeZteSni(6),
            usermodeV5Isdn(7),
            usermodeV5Ddn(8),
            usermodeSip(9)
            }
        MAX-ACCESS  read-only
        STATUS      current
        DESCRIPTION ""
        ::= { a200SlcEntry 8 }

    a200slcFaxMode   OBJECT-TYPE
        SYNTAX      INTEGER {
            faxT30(0),
            faxT38(1),
            faxRTP(2),
            faxFastModem(3),
            faxFastFax(4),
            noSwitch(5),
            selfSwitch(6),
            faxV34(13)
            }
        MAX-ACCESS  read-write
        STATUS      current
        DESCRIPTION ""
        ::= { a200SlcEntry 9 }

    a200slcQovsId   OBJECT-TYPE
        SYNTAX      INTEGER(0..5)
        MAX-ACCESS  read-write
        STATUS      current
        DESCRIPTION ""
        ::= { a200SlcEntry 10 }

    a200slcCIDType   OBJECT-TYPE
        SYNTAX      INTEGER {
            dtmf(1),
            fskBell202(2),
            mf(3),
            fskV23(4)
            }
        MAX-ACCESS  read-write
        STATUS      current
        DESCRIPTION ""
        DEFVAL{ fskBell202 }
        ::= { a200SlcEntry 11 }

    a200slcImType   OBJECT-TYPE
        SYNTAX      INTEGER {
            normal(0),
            bt3(3),
            etsi(4),
            bt5(5),
            ohm600(6)
            }
        MAX-ACCESS  read-write
        STATUS      current
        DESCRIPTION ""
        ::= { a200SlcEntry 12 }

    a200slcecenable   OBJECT-TYPE
        SYNTAX      INTEGER {
            enable(1),
            disable(2),
            default(0)
            }
        MAX-ACCESS  read-write
        STATUS      current
        DESCRIPTION ""
        ::= { a200SlcEntry 14 }

    a200slcuserclass   OBJECT-TYPE
        SYNTAX      INTEGER{normal(0),vip(1)}
        MAX-ACCESS  read-write
        STATUS      current
        DESCRIPTION ""
        ::= { a200SlcEntry 15 }

    a200slcPktToPcmGain  OBJECT-TYPE
        SYNTAX      INTEGER(-20..20)
        MAX-ACCESS  read-write
        STATUS      current
        DESCRIPTION ""
        ::= { a200SlcEntry 16 }

    a200slcPcmToPktGain  OBJECT-TYPE
        SYNTAX      INTEGER(-20..20)
        MAX-ACCESS  read-write
        STATUS      current
        DESCRIPTION ""
        ::= { a200SlcEntry 17 }

    a200slcphonenum   OBJECT-TYPE
        SYNTAX      DisplayString(SIZE(0..32))
        MAX-ACCESS  read-write
        STATUS      current
        DESCRIPTION ""
        ::= { a200SlcEntry 18 }

    a200slcoperNum   OBJECT-TYPE
        SYNTAX      INTEGER(1..192)
        MAX-ACCESS  read-write
        STATUS      current
        DESCRIPTION
            "end of the circuit No., should be larger or equal to msagSlcBegin"
        ::= { a200SlcEntry 19 }

    a200slcblockoper   OBJECT-TYPE
        SYNTAX      INTEGER(1)
        MAX-ACCESS  read-write
        STATUS      current
        DESCRIPTION
            "block slc"
        ::= { a200SlcEntry 20 }

    a200slcunblockoper   OBJECT-TYPE
        SYNTAX      INTEGER(1)
        MAX-ACCESS  read-write
        STATUS      current
        DESCRIPTION
            "unblock slc"
        ::= { a200SlcEntry 21 }

    a200slcmonitorflag  OBJECT-TYPE
        SYNTAX      INTEGER(1..2)
        MAX-ACCESS  read-write
        STATUS      current
        DESCRIPTION ""
        ::= { a200SlcEntry 22 }

    a200slcmonitoreerack  OBJECT-TYPE
        SYNTAX      INTEGER(0..3)
        MAX-ACCESS  read-write
        STATUS      current
        DESCRIPTION ""
        ::= { a200SlcEntry 23 }

    a200slcmonitoreeshelf  OBJECT-TYPE
        SYNTAX      INTEGER(0..4)
        MAX-ACCESS  read-write
        STATUS      current
        DESCRIPTION ""
        ::= { a200SlcEntry 24 }

    a200slcmonitoreeslot  OBJECT-TYPE
        SYNTAX      INTEGER(0..17)
        MAX-ACCESS  read-write
        STATUS      current
        DESCRIPTION ""
        ::= { a200SlcEntry 25 }

    a200slcmonitoreeindex  OBJECT-TYPE
        SYNTAX      INTEGER(0..31)
        MAX-ACCESS  read-write
        STATUS      current
        DESCRIPTION ""
        ::= { a200SlcEntry 26 }

    a200slcDialMode     OBJECT-TYPE
        SYNTAX      INTEGER {
            dtmf(0),
            pulse(1)
            }
        MAX-ACCESS  read-write
        STATUS      current
        DESCRIPTION
            "DDI number send mode"
        ::= { a200SlcEntry 27 }

    a200slcFeedCurrent     OBJECT-TYPE
        SYNTAX      INTEGER {
            curr25mA(1),
            curr32mA(2),
            curr40mA(3),
            curr16mA(4),
            curr20mA(5),
            curr30mA(6),
            curr35mA(7),
            curr45mA(8),
            curr50mA(9),
            curr55mA(10)
            }
        UNITS       "mA"
        MAX-ACCESS  read-write
        STATUS      current
        DESCRIPTION
            "Feed current"
        ::= { a200SlcEntry 28 }

    a200slcHighImpedanceOper   OBJECT-TYPE
        SYNTAX      INTEGER(1)
        MAX-ACCESS  read-write
        STATUS      current
        DESCRIPTION
            "Set subscriber circuit to high-impedance status."
        ::= { a200SlcEntry 29 }

    a200slcNoneHighImpedanceOper   OBJECT-TYPE
        SYNTAX      INTEGER(1)
        MAX-ACCESS  read-write
        STATUS      current
        DESCRIPTION
            "Set subscriber circuit to none high-impedance status."
        ::= { a200SlcEntry 30 }

    zxAnSlcDelayDialMode     OBJECT-TYPE
        SYNTAX      INTEGER{
            noDelay(1),
            delay(2)
            }
        MAX-ACCESS  read-write
        STATUS      current
        DESCRIPTION    "Delay dial mode.
            noDelay(1): No delay,dial is send to PBX immediately;
            delay(2):   Delay until receives signal from PBX.
            "
        DEFVAL{ noDelay }
        ::={a200SlcEntry 31}

    zxAnSlcDdiTrapEnable OBJECT-TYPE
        SYNTAX          INTEGER  {
            enabled(1),
            disabled(2)
        }
        MAX-ACCESS      read-write
        STATUS          current
        DESCRIPTION
            "Enables or disables DDI port trap."
        DEFVAL { disabled }
        ::= { a200SlcEntry 32 }

    zxAnSlcSemiPerConnSrcIpAddr OBJECT-TYPE
        SYNTAX      IpAddress
        MAX-ACCESS  read-write
        STATUS      current
        DESCRIPTION "The source IP address of semi permanent connection.
                     The default value 0.0.0.0 means not configured."
        DEFVAL      { '00000000'h }
        ::= { a200SlcEntry 33 }

    zxAnSlcSemiPerConnSrcPort   OBJECT-TYPE
        SYNTAX      Integer32(0 | 20480..21503)
        MAX-ACCESS  read-write
        STATUS      current
        DESCRIPTION "The source port semi permanent connection.
                    The default value 0 means not configured."
        DEFVAL      { 0 }
        ::= { a200SlcEntry 34 }

    zxAnSlcSemiPerConnDstIpAddr OBJECT-TYPE
        SYNTAX      IpAddress
        MAX-ACCESS  read-write
        STATUS      current
        DESCRIPTION "The destination IP address of semi permanent connection.
                    The default value 0.0.0.0 means not configured."
        DEFVAL      { '00000000'h }
        ::= { a200SlcEntry 35 }

    zxAnSlcSemiPerConnDstPort   OBJECT-TYPE
        SYNTAX      Integer32(0..65535)
        MAX-ACCESS  read-write
        STATUS      current
        DESCRIPTION "The destination port of semi permanent connection.
                    The default value 0 means not configured."
        DEFVAL      { 0 }
        ::= { a200SlcEntry 36 }

    zxAnSlcSemiPerConnSdpProfileId   OBJECT-TYPE
        SYNTAX      Integer32(0..4)
        MAX-ACCESS  read-write
        STATUS      current
        DESCRIPTION "SDP profile ID. The default value 0 means not configured."
         DEFVAL     { 0 }
        ::= { a200SlcEntry 37 }

    zxAnSlcSemiPerConnSdpInformation  OBJECT-TYPE
        SYNTAX      DisplayString(SIZE(0..255))
        MAX-ACCESS  read-only
        STATUS      current
        DESCRIPTION "SDP information."
        ::= { a200SlcEntry 38 }

--------------------------------------------------------------------------------
-- 2. zxAnVoicePortGlobalObjects
--------------------------------------------------------------------------------

    zxAnVoicePortGlobalObjects OBJECT IDENTIFIER ::= {zxAnVoicePortConfig 1400}

    zxAnVoicePortMgmtCapabilities OBJECT-TYPE
        SYNTAX      BITS {
            nbPlatform(0),
            delayDialMode(1)
            }
        MAX-ACCESS  read-only
        STATUS      current
        DESCRIPTION
            "The voice port management capabilities of this equipment.
            The bit value 1 means the function represented by this bit is
            supported by this equipment.
            bit 1: value 1 means support narrowband platform.
            bit 2: value 1 means support zxAnSlcDelayDialMode.
            NOTE: No recommended to display it in NMS."
        ::= { zxAnVoicePortGlobalObjects 1 }

    zxAnPstnPortECharGlobalObjects OBJECT IDENTIFIER ::= {
        zxAnVoicePortGlobalObjects 51 }

    zxAnPstnPortGlbPcmLaw  OBJECT-TYPE
        SYNTAX      INTEGER {
            aLaw(1),
            muLaw(2)
        }
        MAX-ACCESS  read-write
        STATUS      current
        DESCRIPTION
            "PCM law."
        DEFVAL { aLaw }
        ::= { zxAnPstnPortECharGlobalObjects 1 }

    zxAnPstnPortGlbRingVoltage  OBJECT-TYPE
         SYNTAX      INTEGER {
            volt50V(1),
            volt75V(2),
            volt90V(3)
        }
        MAX-ACCESS  read-write
        STATUS      current
        DESCRIPTION
            "Ring voltage."
        DEFVAL { volt75V }
        ::= { zxAnPstnPortECharGlobalObjects 2 }

    zxAnPstnPortGlbRingFrequency   OBJECT-TYPE
         SYNTAX      INTEGER {
            freq16Hz(1),
            freq25Hz(2),
            freq50Hz(3)
        }
        MAX-ACCESS  read-write
        STATUS      current
        DESCRIPTION
            "Ring frequency."
        DEFVAL { freq25Hz }
        ::= { zxAnPstnPortECharGlobalObjects 3 }

    zxAnPstnPolarityRevPulseEnable   OBJECT-TYPE
         SYNTAX      INTEGER {
            enable(1),
            disable(2)
        }
        MAX-ACCESS  read-write
        STATUS      current
        DESCRIPTION
            "Polarity reversing pulse enable."
        DEFVAL { enable }
        ::= { zxAnPstnPortECharGlobalObjects 4 }

    zxAnPstnPolarityRevPulseWidth   OBJECT-TYPE
        SYNTAX      Integer32(20..1270)
        UNITS       "milli-seconds"
        MAX-ACCESS  read-write
        STATUS      current
        DESCRIPTION
            "Polarity reversing pulse width."
        DEFVAL { 1000 }
        ::= { zxAnPstnPortECharGlobalObjects 5 }

    zxAnPstnPolarityRevMode   OBJECT-TYPE
         SYNTAX      INTEGER {
            hard(1),
            soft(2)
        }
        MAX-ACCESS  read-write
        STATUS      current
        DESCRIPTION
            "Polarity reversing mode."
        DEFVAL { hard }
        ::= { zxAnPstnPortECharGlobalObjects 6 }

    zxAnPstnMinDialPulseBreakTime   OBJECT-TYPE
        SYNTAX      Integer32(20..200)
        UNITS       "milli-seconds"
        MAX-ACCESS  read-write
        STATUS      current
        DESCRIPTION
            "Minimum dialed pulse break time."
        DEFVAL { 20 }
        ::= { zxAnPstnPortECharGlobalObjects 7 }

    zxAnPstnMaxDialPulseBreakTime   OBJECT-TYPE
        SYNTAX      Integer32(20..200)
        UNITS       "milli-seconds"
        MAX-ACCESS  read-write
        STATUS      current
        DESCRIPTION
            "Maximum dialed pulse break time."
        DEFVAL { 80 }
        ::= { zxAnPstnPortECharGlobalObjects 8 }

    zxAnPstnMinDialPulseMakeTime   OBJECT-TYPE
        SYNTAX      Integer32(20..200)
        UNITS       "milli-seconds"
        MAX-ACCESS  read-write
        STATUS      current
        DESCRIPTION
            "Minimum dialed pulse make time."
        DEFVAL { 20 }
        ::= { zxAnPstnPortECharGlobalObjects 9 }

    zxAnPstnMaxDialPulseMakeTime   OBJECT-TYPE
        SYNTAX      Integer32(20..200)
        UNITS       "milli-seconds"
        MAX-ACCESS  read-write
        STATUS      current
        DESCRIPTION
            "Maximum dialed pulse make time."
        DEFVAL { 90 }
        ::= { zxAnPstnPortECharGlobalObjects 10 }

    zxAnPstnMinDialPulseInterdigit   OBJECT-TYPE
        SYNTAX      Integer32(20..500)
        UNITS       "milli-seconds"
        MAX-ACCESS  read-write
        STATUS      current
        DESCRIPTION
            "Minimum dialed pulse interdigit time."
        DEFVAL { 250 }
        ::= { zxAnPstnPortECharGlobalObjects 11 }

    zxAnPstnPortGlbKcType  OBJECT-TYPE
        SYNTAX      INTEGER {
            type16kc(1),
            type12kc(2)
        }
        MAX-ACCESS  read-write
        STATUS      current
        DESCRIPTION
            "KC type."
        DEFVAL { type16kc }
        ::= { zxAnPstnPortECharGlobalObjects 12 }

    zxAnPstnPortGlbKcVoltage  OBJECT-TYPE
        SYNTAX      INTEGER {
            volt1V(1),
            volt1point5V(2),
            volt2V(3),
            volt2point5V(4)
        }
        MAX-ACCESS  read-write
        STATUS      current
        DESCRIPTION
            "KC voltage.
            volt1V means 1.0V.
            volt1point5V means 1.5V.
            volt2V means 2.0V.
            volt2point5V means 2.5V."
        DEFVAL { volt2point5V }
        ::= { zxAnPstnPortECharGlobalObjects 13 }

    zxAnPstnPortGlbKcPulseWidth  OBJECT-TYPE
        SYNTAX      Integer32(0..65535)
        UNITS       "milli-seconds"
        MAX-ACCESS  read-write
        STATUS      current
        DESCRIPTION
            "KC pulse width."
        DEFVAL { 200 }
        ::= { zxAnPstnPortECharGlobalObjects 14 }

    zxAnPstnPortGlbKcPulseInterval  OBJECT-TYPE
        SYNTAX      Integer32(0..65535)
        UNITS       "milli-seconds"
        MAX-ACCESS  read-write
        STATUS      current
        DESCRIPTION
            "KC pulse interval."
        DEFVAL { 100 }
        ::= { zxAnPstnPortECharGlobalObjects 15 }

    zxAnPstnHookFlashMinTime  OBJECT-TYPE
        SYNTAX       Integer32(50..1500)
        UNITS        "milli-seconds"
        MAX-ACCESS   read-write
        STATUS       current
        DESCRIPTION
            "The minimal time of hook flash."
        DEFVAL { 90 }
        ::= {zxAnPstnPortECharGlobalObjects 16}

    zxAnPstnHookFlashMaxTime  OBJECT-TYPE
        SYNTAX       Integer32(50..1500)
        UNITS        "milli-seconds"
        MAX-ACCESS   read-write
        STATUS       current
        DESCRIPTION
            "The maximal time of hook flash."
        DEFVAL { 470 }
        ::= {zxAnPstnPortECharGlobalObjects 17}

--------------------------------------------------------------------------------
-- 3. PSTN Port Electrical Characteristics Table
--------------------------------------------------------------------------------

    zxAnPstnPortECharTable OBJECT-TYPE
        SYNTAX      SEQUENCE OF ZxAnPstnPortECharEntry
        MAX-ACCESS  not-accessible
        STATUS      current
        DESCRIPTION
            "PSTN port electrical characteristics table."
        ::= { zxAnVoicePortConfig 1401 }

    zxAnPstnPortECharEntry OBJECT-TYPE
        SYNTAX      ZxAnPstnPortECharEntry
        MAX-ACCESS  not-accessible
        STATUS      current
        DESCRIPTION
            "PSTN port electrical characteristics entry."
        INDEX { zxAnPstnPortECharRack, zxAnPstnPortECharShelf,
                zxAnPstnPortECharSlot, zxAnPstnPortECharPort}
        ::= { zxAnPstnPortECharTable 1 }

    ZxAnPstnPortECharEntry ::= SEQUENCE {
        zxAnPstnPortECharRack               Integer32,
        zxAnPstnPortECharShelf              Integer32,
        zxAnPstnPortECharSlot               Integer32,
        zxAnPstnPortECharPort               Integer32,
        zxAnPstnPortECharOperNum            Integer32,
        zxAnPstnPortFeedVoltage             INTEGER,
        zxAnPstnPortFeedCurrent             INTEGER,
        zxAnPstnPortImpedanceType           INTEGER,
        zxAnPstnPortAdGain                  INTEGER,
        zxAnPstnPortDaGain                  INTEGER
    }

    zxAnPstnPortECharRack  OBJECT-TYPE
        SYNTAX      Integer32
        MAX-ACCESS  not-accessible
        STATUS      current
        DESCRIPTION
            "Rack of PSTN port."
        ::= { zxAnPstnPortECharEntry 1 }

    zxAnPstnPortECharShelf  OBJECT-TYPE
        SYNTAX      Integer32
        MAX-ACCESS  not-accessible
        STATUS      current
        DESCRIPTION
            "Shelf of PSTN port."
        ::= { zxAnPstnPortECharEntry 2 }

    zxAnPstnPortECharSlot  OBJECT-TYPE
        SYNTAX      Integer32
        MAX-ACCESS  not-accessible
        STATUS      current
        DESCRIPTION
            "Slot of PSTN port."
        ::= { zxAnPstnPortECharEntry 3 }

    zxAnPstnPortECharPort  OBJECT-TYPE
        SYNTAX      Integer32
        MAX-ACCESS  not-accessible
        STATUS      current
        DESCRIPTION
            "Port number of PSTN port."
        ::= { zxAnPstnPortECharEntry 4 }

    zxAnPstnPortECharOperNum   OBJECT-TYPE
        SYNTAX      Integer32
        MAX-ACCESS  read-write
        STATUS      current
        DESCRIPTION
            "Batch operation number. zxAnPstnPortECharPort means the start port
            number in batch operation."
        ::= { zxAnPstnPortECharEntry 5 }

    zxAnPstnPortFeedVoltage  OBJECT-TYPE
        SYNTAX      INTEGER {
            volt48v(1),
            volt75v(2)
        }
        MAX-ACCESS  read-write
        STATUS      current
        DESCRIPTION
            "Feed voltage."
        DEFVAL { volt48v }
        ::= { zxAnPstnPortECharEntry 6 }

    zxAnPstnPortFeedCurrent   OBJECT-TYPE
        SYNTAX      INTEGER {
            curr25mA(1),
            curr32mA(2),
            curr40mA(3),
            curr16mA(4),
            curr20mA(5),
            curr30mA(6),
            curr35mA(7),
            curr45mA(8)
        }
        MAX-ACCESS  read-write
        STATUS      current
        DESCRIPTION
            "Feed current."
        DEFVAL { curr20mA }
        ::= { zxAnPstnPortECharEntry 7 }

    zxAnPstnPortImpedanceType  OBJECT-TYPE
        SYNTAX      INTEGER {
            normal(1),
            im600ohm(2),
            hkBt3(3),
            hkBt5(4),
            etsi(5),
            russia(6)
        }
        MAX-ACCESS  read-write
        STATUS      current
        DESCRIPTION
            "Impedance type."
        DEFVAL { im600ohm }
        ::= { zxAnPstnPortECharEntry 8 }

    zxAnPstnPortAdGain  OBJECT-TYPE
        SYNTAX      INTEGER {
            gain0dB(1),
            gainNeg1dB(2),
            gainNeg2dB(3),
            gainNeg3dB(4),
            gainNeg4dB(5),
            gainNeg5dB(6),
            gainNeg6dB(7),
            gainNeg7dB(8),
            gain1dB(9),
            gain2dB(10),
            gain3dB(11)
        }
        MAX-ACCESS  read-write
        STATUS      current
        DESCRIPTION
            "Gain of converting the analog signals to digital signals."
        DEFVAL { gain0dB }
        ::= { zxAnPstnPortECharEntry 9 }

    zxAnPstnPortDaGain  OBJECT-TYPE
        SYNTAX      INTEGER {
            gain0dB(1),
            gainNeg3point5dB(2),
            gainNeg4dB(3),
            gainNeg5dB(4),
            gainNeg6dB(5),
            gainNeg7dB(6),
            gainNeg8dB(7),
            gainNeg9dB(8),
            gainNeg10dB(9)
        }
        MAX-ACCESS  read-write
        STATUS      current
        DESCRIPTION
            "Gain of converting the digital signals to analog signals.
            gain0dB(1): 0dB
            gainNeg3point5dB(2): -3.5dB
            gainNeg4dB(3): -4dB
            gainNeg5dB(4): -5dB
            gainNeg6dB(5): -6dB
            gainNeg7dB(6): -7dB
            gainNeg8dB(7): -8dB
            gainNeg9dB(8): -9dB
            gainNeg10dB(9): -10dB"
        DEFVAL { gainNeg3point5dB }
        ::= { zxAnPstnPortECharEntry 10 }

END
