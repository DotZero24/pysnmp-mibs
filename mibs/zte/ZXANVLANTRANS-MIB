-- *****************************************************************
-- ZTE XPON VLAN TRANSLATE MIB
--
-- 08-09-2007
--
-- Copyright(c) 2008 ZTE Corporation
-- All rights reserved.
-- *****************************************************************

ZXANVLANTRANS-MIB DEFINITIONS ::= BEGIN
    IMPORTS
        enterprises                      FROM RFC1155-SMI
        Integer32                        FROM SNMPv2-SMI
        VlanId                           FROM ZTE-AN-TC-MIB
        RowStatus                        FROM SNMPv2-TC
        MODULE-IDENTITY                  FROM SNMPv2-SMI
        OBJECT-TYPE                      FROM SNMPv2-SMI
        NOTIFICATION-TYPE                FROM SNMPv2-SMI
        zxAnPonMib                       FROM ZTE-MASTER-MIB;

zxAnVlanTrans        MODULE-IDENTITY
    LAST-UPDATED "200806100000Z"  -- Jun 10, 2008"
    ORGANIZATION "ZTE Corp."
    CONTACT-INFO
        "ZTE GPON Working Group:
        http://www.zte.com.cn
        e-mail:
        ouyang.haiming@zte.com.cn
        "
    DESCRIPTION
        ""
    ::= { zxAnPonMib 10 }


zxAnVlanTransRuleTable OBJECT-TYPE
    SYNTAX     SEQUENCE OF ZxAnVlanTransRuleEntry
    MAX-ACCESS not-accessible
    STATUS     current
    DESCRIPTION
        " "
    ::= { zxAnVlanTrans 1 }

zxAnVlanTransRuleEntry OBJECT-TYPE
    SYNTAX      ZxAnVlanTransRuleEntry
    MAX-ACCESS  not-accessible
    STATUS      current
    DESCRIPTION
            ""
    INDEX   { zxAnPonOnuId, zxAnOnuPortId, zxAnVlanTransOriginalCvlan }
    ::= { zxAnVlanTransRuleTable 1 }

ZxAnVlanTransRuleEntry ::=
    SEQUENCE {
            zxAnPonOnuId                                                                  Integer32,
            zxAnOnuPortId                                 Integer32,
        zxAnVlanTransOriginalCvlan                    VlanId,
        zxAnVlanTransNewCvlan                         VlanId,
        zxAnVlanTransBroadcast                        INTEGER,
        zxAnVlanTransMode                             INTEGER,
        zxAnVlanTransEntryStatus                      RowStatus
    }

zxAnPonOnuId OBJECT-TYPE
    SYNTAX      Integer32
    MAX-ACCESS  not-accessible
    STATUS      current
    DESCRIPTION
        "  |-------------+-----------|---------|---------|------------|----------|
           |InterfaceType| Shelf No. | Slot No.| Pon No. |   Onu No.  | Reserved |
           |  3 (4bits)  | (4bits)   | (5bits) | (3bits) |   (8bits)  | (8bits)  |
           +-------------+-----------+---------+---------+------------+----------+"
    REFERENCE   ""
    ::= { zxAnVlanTransRuleEntry 1}

zxAnOnuPortId OBJECT-TYPE
    SYNTAX      Integer32
    MAX-ACCESS  not-accessible
    STATUS      current
    DESCRIPTION
        "FE port NO. in ONU. "
    REFERENCE   ""
    ::= { zxAnVlanTransRuleEntry 2}


zxAnVlanTransOriginalCvlan OBJECT-TYPE
    SYNTAX      VlanId
    MAX-ACCESS  not-accessible
    STATUS      current
    DESCRIPTION
        ""
    REFERENCE   ""
    ::= { zxAnVlanTransRuleEntry 3}

zxAnVlanTransNewCvlan OBJECT-TYPE
    SYNTAX      VlanId
    MAX-ACCESS  read-write
    STATUS      current
    DESCRIPTION
        ""
    REFERENCE   ""
    ::= { zxAnVlanTransRuleEntry 4}

zxAnVlanTransBroadcast OBJECT-TYPE
    SYNTAX      INTEGER{
                                disable(0),
                                enable(1)
                            }
    MAX-ACCESS  read-write
    STATUS      current
    DESCRIPTION
        ""
    REFERENCE   ""
    ::= { zxAnVlanTransRuleEntry 5}

zxAnVlanTransMode OBJECT-TYPE
    SYNTAX      INTEGER
                {
                   oneToOne(1),
                   nToOne(2)
                }
    MAX-ACCESS  read-write
    STATUS      current
    DESCRIPTION
        "The translate mode."
    DEFVAL  { oneToOne }
    ::= { zxAnVlanTransRuleEntry 6}


zxAnVlanTransEntryStatus OBJECT-TYPE
    SYNTAX      RowStatus
    MAX-ACCESS  read-write
    STATUS      current
    DESCRIPTION
        ""
    REFERENCE   ""
    ::= { zxAnVlanTransRuleEntry 10 }


zxAnVlanTransGlobalTable    OBJECT-TYPE
    SYNTAX      SEQUENCE OF ZxAnVlanTransGlobalEntry
    MAX-ACCESS  not-accessible
    STATUS      current
    DESCRIPTION
        ""
    REFERENCE   ""
    ::= { zxAnVlanTrans 2 }

zxAnVlanTransGlobalEntry OBJECT-TYPE
    SYNTAX      ZxAnVlanTransGlobalEntry
    MAX-ACCESS  not-accessible
    STATUS      current
    DESCRIPTION
        ""
    INDEX   {zxAnPonOnuId }
    ::= { zxAnVlanTransGlobalTable 1 }

ZxAnVlanTransGlobalEntry ::=
    SEQUENCE {
        zxAnVlanTransSvlanBase                       VlanId
    }

zxAnVlanTransSvlanBase OBJECT-TYPE
    SYNTAX      VlanId
    MAX-ACCESS  read-write
    STATUS      current
    DESCRIPTION
        "MDU svlan base, this attribute is optional."
    REFERENCE   ""
    ::= { zxAnVlanTransGlobalEntry 1 }

END
