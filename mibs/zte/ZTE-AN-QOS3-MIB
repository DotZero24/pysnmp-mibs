-------------------------------------------------------------------------------
-- File Name : ZTE-AN-QOS3-MIB.mib
-- Date      : 2010-10-28
-- Author    : ZTE NMS Dept.
--
-- ZTE QoS MIB for Access Node
--
--
-------------------------------------------------------------------------------
    ZTE-AN-QOS3-MIB    DEFINITIONS ::= BEGIN
        IMPORTS
            RowStatus                                   FROM SNMPv2-TC
            MODULE-IDENTITY,OBJECT-TYPE,Integer32       FROM SNMPv2-SMI
            zxAn                                        FROM ZTE-AN-TC-MIB
            DisplayString                               FROM RFC1213-MIB;

    zxAnQosMib    MODULE-IDENTITY
        LAST-UPDATED   "201010281326Z"
        ORGANIZATION   "ZTE Corporation"
        CONTACT-INFO   "ZTE NMS dept.
                        Mail: majian@zte.com.cn
                        Tel: 68896270."
        DESCRIPTION    "This MIB defines ZTE Access Node QoS managed objects.
                        This MIB will replace ZTE-AN-QOSII-MIB.mib."
        ::=  {  zxAn  21  }

    zxAnQos3Objects        OBJECT IDENTIFIER   ::=  { zxAnQosMib 4 }
    zxAnQos3GlobalObjects  OBJECT IDENTIFIER   ::=  { zxAnQos3Objects 1 }
    zxAnQos3MappingProfile OBJECT IDENTIFIER   ::=  { zxAnQos3Objects 2 }
    zxAnQos3PortConfig     OBJECT IDENTIFIER   ::=  { zxAnQos3Objects 3 }
    zxAnQos3VPortConfig    OBJECT IDENTIFIER   ::=  { zxAnQos3Objects 4 }
    zxAnQos3Queue          OBJECT IDENTIFIER   ::=  { zxAnQos3Objects 5 }
    zxAnQos3Traffic        OBJECT IDENTIFIER   ::=  { zxAnQos3Objects 6 }
------------------------------------------------------------------------------
-- Following objects are defined.
-- 1.zxAnQos3GlobalObjects
-- 2.zxAnQos3CosRemarkProfileTable
-- 3.zxAnQos3DscpRemarkProfileTable
-- 4.zxAnQos3Dscp2CosProfileTable
-- 5.zxAnQos3Dscp2DropProfileTable
-- 6.zxAnQos3PortConfigTable
-- 7.zxAnQos3VPortConfigTable
-- 8.zxAnQos3QueueBlockProfileTable
-- 9.zxAnQos3QueueMapProfileTable
-- 10.zxAnQos3PortQueueConfigTable
-- 11.zxAnQos3TrafficProfileTable
-- 12.zxAnQos3TrafficConfigTable
-- 13.zxAnQos3RemainingBwTable
-- 14.zxAnQos3MplsTc2CosProfileTable
-- 15.zxAnQos3Cos2MplsTcProfileTable
-- 16.zxAnQos3AtmTrafficProfileTable

------------------------------------------------------------------------------
-- 1.zxAnQos3GlobalObjects
------------------------------------------------------------------------------

    zxAnQos3MgmtCapabilities  OBJECT-TYPE
        SYNTAX      BITS    {
            supportQos3(0),
            supportTrafficPrfType(1),
            supportPvc2Queue(2),
            supportTrafficColorMode(3)
        }
        MAX-ACCESS  read-only
        STATUS      current
        DESCRIPTION
            "The QoS management capabilities of this equipment.
             The bit value 1 means the function represented by this bit is
             supported by this equipment.
             NOTE: No recommended to display it in NMS.

             supportQos3(0) - Support QoS 3
             supportTrafficPrfType(1) - Support zxAnQosTrafficIfConfPrfType in
                                        zxAnQos3TrafficConfigTable,
                                        zxAnQosTrafficPrfCirCosRemark  and
                                        zxAnQosTrafficPrfPirCosRemark in
                                        zxAnQos3TrafficProfileTable.
             supportPvc2Queue(2) -      Support zxAnQosPvc2Queue in
                                        zxAnQos3QueueMapProfileTable.
             supportTrafficColorMode(3) - support zxAnQosTrafficPrfColorMode in
                                        zxAnQos3TrafficProfileTable.
            "
        ::= { zxAnQos3GlobalObjects 1 }

    zxAnQos3QueueGlobalObjects OBJECT IDENTIFIER
    ::=  { zxAnQos3GlobalObjects 2 }

    zxAnQosEthCosToQueue  OBJECT-TYPE
        SYNTAX      OCTET STRING(SIZE (8))
        MAX-ACCESS  read-write
        STATUS      current
        DESCRIPTION
            "The queue that each CoS value has been assigned to, global
             parameter, only effect on ethernet interace. For example, the value
             '00 01 02 03 04 05 06 07' means queue 0 is assigned to CoS priority
             0,...,queue 7 is assigned to CoS priority 7. Number of ethernet
             queues is fixed to 8."
        ::= { zxAnQos3QueueGlobalObjects 1 }

------------------------------------------------------------------------------
-- 2.zxAnQos3CosRemarkProfileTable
------------------------------------------------------------------------------
    zxAnQos3CosRemarkProfileTable  OBJECT-TYPE
        SYNTAX      SEQUENCE  OF  ZxAnQos3CosRemarkProfileEntry
        MAX-ACCESS  not-accessible
        STATUS      current
        DESCRIPTION
            "This table contains CoS remark information.
             One entry in this table reflects a profile defined which can be
             used to configure an interface."
        ::= { zxAnQos3MappingProfile 1 }

    zxAnQos3CosRemarkProfileEntry  OBJECT-TYPE
        SYNTAX      ZxAnQos3CosRemarkProfileEntry
        MAX-ACCESS  not-accessible
        STATUS      current
        DESCRIPTION
            "An entry in zxAnQos3CosRemarkProfileTable."
        INDEX { zxAnQosCosToCosPrfName }
        ::= { zxAnQos3CosRemarkProfileTable 1 }

    ZxAnQos3CosRemarkProfileEntry  ::=
        SEQUENCE {
            zxAnQosCosToCosPrfName   DisplayString,
            zxAnQosCosToCos      OCTET STRING,
            zxAnQosCosToCosPrfRowStatus     RowStatus
        }

    zxAnQosCosToCosPrfName OBJECT-TYPE
        SYNTAX      DisplayString(SIZE(1..32))
        MAX-ACCESS  not-accessible
        STATUS      current
        DESCRIPTION
            "The profile name is a display string. It is an index of
             this table."
        ::= { zxAnQos3CosRemarkProfileEntry 1 }

    zxAnQosCosToCos    OBJECT-TYPE
        SYNTAX      OCTET STRING(SIZE (8))
        MAX-ACCESS  read-create
        STATUS      current
        DESCRIPTION
            "The CoS priority remark value.
             For example, the value '00 01 02 03 04 05 06 07' means CoS
             priority 0 is remarked to CoS priority 0,...,CoS priority 7 is
             remarked to CoS priority 7. The range of CoS priority is 0-7."
        ::= { zxAnQos3CosRemarkProfileEntry 2 }

    zxAnQosCosToCosPrfRowStatus  OBJECT-TYPE
        SYNTAX      RowStatus
        MAX-ACCESS  read-create
        STATUS      current
        DESCRIPTION
            "This object is used to create a new row or to modify or
             delete an existing row in this table."
        ::= { zxAnQos3CosRemarkProfileEntry 20 }

------------------------------------------------------------------------------
-- 3.zxAnQos3DscpRemarkProfileTable
------------------------------------------------------------------------------
    zxAnQos3DscpRemarkProfileTable  OBJECT-TYPE
        SYNTAX      SEQUENCE  OF  ZxAnQos3DscpRemarkProfileEntry
        MAX-ACCESS  not-accessible
        STATUS      current
        DESCRIPTION
            "This table contains DSCP remark information.
             One entry in this table reflects a profile defined which can be
             used to configure an interface."
        ::= { zxAnQos3MappingProfile 2 }

    zxAnQos3DscpRemarkProfileEntry  OBJECT-TYPE
        SYNTAX      ZxAnQos3DscpRemarkProfileEntry
        MAX-ACCESS  not-accessible
        STATUS      current
        DESCRIPTION
            "An entry in zxAnQos3DscpRemarkProfileTable."
        INDEX { zxAnQosDscpToDscpPrfName }
        ::= { zxAnQos3DscpRemarkProfileTable 1 }

    ZxAnQos3DscpRemarkProfileEntry  ::=
        SEQUENCE {
            zxAnQosDscpToDscpPrfName        DisplayString,
            zxAnQosDscpToDscp               OCTET STRING,
            zxAnQosDscpToDscpPrfRowStatus     RowStatus
        }

    zxAnQosDscpToDscpPrfName OBJECT-TYPE
        SYNTAX      DisplayString(SIZE(1..32))
        MAX-ACCESS  not-accessible
        STATUS      current
        DESCRIPTION
            "The profile name is a display string. It is an index of
             this table."
        ::= { zxAnQos3DscpRemarkProfileEntry 1 }

    zxAnQosDscpToDscp    OBJECT-TYPE
        SYNTAX      OCTET STRING(SIZE (64))
        MAX-ACCESS  read-create
        STATUS      current
        DESCRIPTION
            "The DSCP priority remark value.
             For example, the value '00 01 ...3F' means DSCP priority 0 is
             remarked to DSCP priority 0,...,DSCP priority 63 is remarked to
             DSCP priority 63. The range of DSCP priority is 0-63."
        ::= { zxAnQos3DscpRemarkProfileEntry 2 }

    zxAnQosDscpToDscpPrfRowStatus  OBJECT-TYPE
        SYNTAX      RowStatus
        MAX-ACCESS  read-create
        STATUS      current
        DESCRIPTION
            "This object is used to create a new row or to modify or
             delete an existing row in this table."
        ::= { zxAnQos3DscpRemarkProfileEntry 20 }

-------------------------------------------------------------------------------
-- 4.zxAnQos3Dscp2CosProfileTable
-------------------------------------------------------------------------------
    zxAnQos3Dscp2CosProfileTable OBJECT-TYPE
        SYNTAX      SEQUENCE OF ZxAnQos3Dscp2CosProfileEntry
        MAX-ACCESS  not-accessible
        STATUS      current
        DESCRIPTION
            "This table contains DSCP to CoS mapping information.
             One entry in this table reflects a profile defined which can be
             used to configure an interface."
        ::= { zxAnQos3MappingProfile 3 }

    zxAnQos3Dscp2CosProfileEntry OBJECT-TYPE
        SYNTAX      ZxAnQos3Dscp2CosProfileEntry
        MAX-ACCESS  not-accessible
        STATUS      current
        DESCRIPTION
            "An entry for zxAnQos3Dscp2CosProfileTable."
        INDEX { zxAnQosDscpToCosPrfName }
        ::= { zxAnQos3Dscp2CosProfileTable 1 }

    ZxAnQos3Dscp2CosProfileEntry  ::=
        SEQUENCE {
            zxAnQosDscpToCosPrfName       DisplayString,
            zxAnQosDscpToCos              OCTET STRING,
            zxAnQosDscpToCosPrfRowStatus  RowStatus
        }

    zxAnQosDscpToCosPrfName OBJECT-TYPE
        SYNTAX      DisplayString(SIZE(1..32))
        MAX-ACCESS  not-accessible
        STATUS      current
        DESCRIPTION
            "The profile name is a display string. It is an index of
             this table."
        ::= { zxAnQos3Dscp2CosProfileEntry 1 }

    zxAnQosDscpToCos    OBJECT-TYPE
        SYNTAX      OCTET STRING(SIZE (64))
        MAX-ACCESS  read-create
        STATUS      current
        DESCRIPTION
            "The DSCP mapping CoS priority value.
             For example, the value '00 01...07' means DSCP priority 0 is
             mapping to CoS priority 0,...,DSCP priority 63 is mapping to CoS
             priority 7. The range of CoS priority is 0-7."
        ::= { zxAnQos3Dscp2CosProfileEntry 2 }

    zxAnQosDscpToCosPrfRowStatus  OBJECT-TYPE
        SYNTAX      RowStatus
        MAX-ACCESS  read-create
        STATUS      current
        DESCRIPTION
            "This object is used to create a new row or to modify or
             delete an existing row in this table."
        ::= { zxAnQos3Dscp2CosProfileEntry 20 }

-------------------------------------------------------------------------------
-- 5.zxAnQos3Dscp2DropProfileTable
-------------------------------------------------------------------------------
    zxAnQos3Dscp2DropProfileTable OBJECT-TYPE
        SYNTAX      SEQUENCE OF ZxAnQos3Dscp2DropProfileEntry
        MAX-ACCESS  not-accessible
        STATUS      current
        DESCRIPTION
            "This table contains DSCP to drop precedence mapping information.
             One entry in this table reflects a profile defined which can be
             used to configure an interface."
        ::= { zxAnQos3MappingProfile 4 }

    zxAnQos3Dscp2DropProfileEntry OBJECT-TYPE
        SYNTAX      ZxAnQos3Dscp2DropProfileEntry
        MAX-ACCESS  not-accessible
        STATUS      current
        DESCRIPTION
            "An entry for zxAnQos3Dscp2DropProfileTable."
        INDEX { zxAnQosDscpToDropPrecedePrfName }
        ::= { zxAnQos3Dscp2DropProfileTable 1 }

    ZxAnQos3Dscp2DropProfileEntry  ::=
        SEQUENCE {
            zxAnQosDscpToDropPrecedePrfName    DisplayString,
            zxAnQosDscpToDropPrecedence        OCTET STRING,
            zxAnQosDscpToDropPrePrfRowStatus   RowStatus
        }

    zxAnQosDscpToDropPrecedePrfName OBJECT-TYPE
        SYNTAX      DisplayString(SIZE(1..32))
        MAX-ACCESS  not-accessible
        STATUS      current
        DESCRIPTION
            "The profile name is a display string. It is an index of
             this table."
        ::= { zxAnQos3Dscp2DropProfileEntry 1 }

    zxAnQosDscpToDropPrecedence    OBJECT-TYPE
        SYNTAX      OCTET STRING(SIZE (64))
        MAX-ACCESS  read-create
        STATUS      current
        DESCRIPTION
            "The DSCP mapping drop precedence value.
             For example, '00 01 02...02' means DSCP priority 0 is
             mapping to drop precedence 0,...,DSCP priority 63
             is mapping to drop precedence 2. The range of drop
             precedence is 0-2."
        ::= { zxAnQos3Dscp2DropProfileEntry 2 }

    zxAnQosDscpToDropPrePrfRowStatus  OBJECT-TYPE
        SYNTAX      RowStatus
        MAX-ACCESS  read-create
        STATUS      current
        DESCRIPTION
            "This object is used to create a new row or to modify or
             delete an existing row in this table."
        ::= { zxAnQos3Dscp2DropProfileEntry 20 }

--------------------------------------------------------------------------------
-- 14.zxAnQos3MplsTc2CosProfileTable
--------------------------------------------------------------------------------
    zxAnQos3MplsTc2CosProfileTable OBJECT-TYPE
        SYNTAX      SEQUENCE OF ZxAnQos3MplsTc2CosProfileEntry
        MAX-ACCESS  not-accessible
        STATUS      current
        DESCRIPTION
            "This table contains MPLS TC value to CoS priority mapping
             information. One entry in this table reflects a profile defined
             which can be used to configure an interface."
        ::= { zxAnQos3MappingProfile 5 }

    zxAnQos3MplsTc2CosProfileEntry OBJECT-TYPE
        SYNTAX      ZxAnQos3MplsTc2CosProfileEntry
        MAX-ACCESS  not-accessible
        STATUS      current
        DESCRIPTION
            "An entry for zxAnQos3MplsTc2CosProfileTable."
        INDEX { zxAnQosMplsTcToCosPrfName }
        ::= { zxAnQos3MplsTc2CosProfileTable 1 }

    ZxAnQos3MplsTc2CosProfileEntry  ::=
        SEQUENCE {
            zxAnQosMplsTcToCosPrfName        DisplayString,
            zxAnQosMplsTcToCos               OCTET STRING,
            zxAnQosMplsTcToCosPrfRowStatus   RowStatus
        }

    zxAnQosMplsTcToCosPrfName OBJECT-TYPE
        SYNTAX      DisplayString(SIZE(1..32))
        MAX-ACCESS  not-accessible
        STATUS      current
        DESCRIPTION
            "The profile name is a display string. It is an index of
             this table."
        ::= { zxAnQos3MplsTc2CosProfileEntry 1 }

    zxAnQosMplsTcToCos OBJECT-TYPE
        SYNTAX      OCTET STRING(SIZE (8))
        MAX-ACCESS  read-create
        STATUS      current
        DESCRIPTION
            "The MPLS TC value mapping CoS priority value.
             For example, '00 01 02 03 04 05 06 07' means TC 0 is mapping to
             CoS priority 0,...,TC 7 is mapping to CoS priority 7.
             The range of MPLS TC value and CoS priority are 0-7."
        ::= { zxAnQos3MplsTc2CosProfileEntry 2 }

    zxAnQosMplsTcToCosPrfRowStatus OBJECT-TYPE
        SYNTAX      RowStatus
        MAX-ACCESS  read-create
        STATUS      current
        DESCRIPTION
            "This object is used to create a new row or to modify or
             delete an existing row in this table."
        ::= { zxAnQos3MplsTc2CosProfileEntry 20 }

--------------------------------------------------------------------------------
-- 15.zxAnQos3Cos2MplsTcProfileTable
--------------------------------------------------------------------------------
    zxAnQos3Cos2MplsTcProfileTable OBJECT-TYPE
        SYNTAX      SEQUENCE OF ZxAnQos3Cos2MplsTcProfileEntry
        MAX-ACCESS  not-accessible
        STATUS      current
        DESCRIPTION
            "This table contains CoS priority to MPLS TC value mapping
             information. One entry in this table reflects a profile defined
             which can be used to configure an interface."
        ::= { zxAnQos3MappingProfile 6 }

    zxAnQos3Cos2MplsTcProfileEntry OBJECT-TYPE
        SYNTAX      ZxAnQos3Cos2MplsTcProfileEntry
        MAX-ACCESS  not-accessible
        STATUS      current
        DESCRIPTION
            "An entry for zxAnQos3Cos2MplsTcProfileTable."
        INDEX { zxAnQosCosToMplsTcPrfName }
        ::= { zxAnQos3Cos2MplsTcProfileTable 1 }

    ZxAnQos3Cos2MplsTcProfileEntry  ::=
        SEQUENCE {
            zxAnQosCosToMplsTcPrfName        DisplayString,
            zxAnQosCosToMplsTc               OCTET STRING,
            zxAnQosCosToMplsTcPrfRowStatus   RowStatus
        }

    zxAnQosCosToMplsTcPrfName OBJECT-TYPE
        SYNTAX      DisplayString(SIZE(1..32))
        MAX-ACCESS  not-accessible
        STATUS      current
        DESCRIPTION
            "The profile name is a display string. It is an index of
             this table."
        ::= { zxAnQos3Cos2MplsTcProfileEntry 1 }

    zxAnQosCosToMplsTc OBJECT-TYPE
        SYNTAX      OCTET STRING(SIZE (8))
        MAX-ACCESS  read-create
        STATUS      current
        DESCRIPTION
            "The CoS priority mapping MPLS TC value.
             For example, '00 01 02 03 04 05 06 07' means CoS priority 0 is
             mapping to TC value 0,...,CoS priority 7 is mapping to TC value 7.
             The range of CoS priority and TC value are 0-7."
        ::= { zxAnQos3Cos2MplsTcProfileEntry 2 }

    zxAnQosCosToMplsTcPrfRowStatus OBJECT-TYPE
        SYNTAX      RowStatus
        MAX-ACCESS  read-create
        STATUS      current
        DESCRIPTION
            "This object is used to create a new row or to modify or
             delete an existing row in this table."
        ::= { zxAnQos3Cos2MplsTcProfileEntry 20 }
--------------------------------------------------------------------------------
-- 6.zxAnQos3PortConfigTable
--------------------------------------------------------------------------------

    zxAnQos3PortConfigTable  OBJECT-TYPE
        SYNTAX      SEQUENCE  OF  ZxAnQos3PortConfigEntry
        MAX-ACCESS  not-accessible
        STATUS      current
        DESCRIPTION
            "This table contains QoS configuration parameters for physical
             interface."
        ::= { zxAnQos3PortConfig 1 }

    zxAnQos3PortConfigEntry  OBJECT-TYPE
        SYNTAX      ZxAnQos3PortConfigEntry
        MAX-ACCESS  not-accessible
        STATUS      current
        DESCRIPTION
            "An entry in zxAnQosPortConfigTable."
        INDEX { zxAnQos3Rack, zxAnQos3Shelf,
                zxAnQos3Slot, zxAnQos3Port,
                zxAnQos3Onu, zxAnQos3VCircuitType,
                zxAnQos3LogicalId }
        ::= { zxAnQos3PortConfigTable 1 }

    ZxAnQos3PortConfigEntry  ::=
        SEQUENCE {
            zxAnQos3Rack                     Integer32,
            zxAnQos3Shelf                    Integer32,
            zxAnQos3Slot                     Integer32,
            zxAnQos3Port                     Integer32,
            zxAnQos3Onu                      Integer32,
            zxAnQos3VCircuitType             INTEGER,
            zxAnQos3LogicalId                OBJECT IDENTIFIER,
            zxAnQosIfRateLimit               Integer32,
            zxAnQosIfBucketSize              Integer32,
            zxAnQosIfTrustMode               INTEGER,
            zxAnQosIfDefaultCos              INTEGER,
            zxAnQosIfDscpToCosPrf            DisplayString,
            zxAnQosIfDscpToDropPrecedencePrf DisplayString,
            zxAnQosIfDscpToDscpPrf           DisplayString,
            zxAnQosIfIngressRateLimit        Integer32,
            zxAnQosIfIngressBucketSize       Integer32
        }

    zxAnQos3Rack  OBJECT-TYPE
        SYNTAX      Integer32
        MAX-ACCESS  not-accessible
        STATUS      current
        DESCRIPTION
            "Rack number of the port."
        ::= { zxAnQos3PortConfigEntry 1 }

    zxAnQos3Shelf  OBJECT-TYPE
        SYNTAX      Integer32
        MAX-ACCESS  not-accessible
        STATUS      current
        DESCRIPTION
            "Shelf number of the port."
        ::= { zxAnQos3PortConfigEntry 2 }

    zxAnQos3Slot  OBJECT-TYPE
        SYNTAX      Integer32
        MAX-ACCESS  not-accessible
        STATUS      current
        DESCRIPTION
            "Slot number of the port."
        ::= { zxAnQos3PortConfigEntry 3 }

    zxAnQos3Port  OBJECT-TYPE
        SYNTAX      Integer32
        MAX-ACCESS  not-accessible
        STATUS      current
        DESCRIPTION
            "The port number."
        ::= { zxAnQos3PortConfigEntry 4 }

    zxAnQos3Onu  OBJECT-TYPE
        SYNTAX      Integer32
        MAX-ACCESS  not-accessible
        STATUS      current
        DESCRIPTION
             "The ONU number. It is 0 in DSL port."
        ::= { zxAnQos3PortConfigEntry 5 }

    zxAnQos3VCircuitType  OBJECT-TYPE
        SYNTAX      INTEGER
        {
            physicalPort(1),
            bridgePort(2),
            eponOnu(3),
            gpon(4),
            servicePort(11),
            vlan(12),
            queue(13)
        }
        MAX-ACCESS  not-accessible
        STATUS      current
        DESCRIPTION
            "Virtual circuit type."
        ::= { zxAnQos3PortConfigEntry 6 }

    zxAnQos3LogicalId OBJECT-TYPE
        SYNTAX      OBJECT IDENTIFIER
        MAX-ACCESS  not-accessible
        STATUS      current
        DESCRIPTION
            "Logic index of the interface.

            If zxAnQos3VCircuitType is 'physicalPort', its value is 0.

            If zxAnQos3VCircuitType is 'bridgePort', this object
            indicates 'pvc', such as oid '1' indicates 'PVC1'.

            If zxAnQos3VCircuitType is 'gpon', this object
            indicates 'ponVPort', such as oid '1' indicates 'VPort1'.

            If zxAnQos3VCircuitType is 'vlan', this object indicates
            'vlanId | svlanId.cvlanId', such as oid '1' indicates 'VLANID1',
            oid '1.2' indicates 'SVLANID1.CVLANID2'.

            If zxAnQos3VCircuitType is 'queue', this object indicates
            'queueId', such as oid '1' indicates 'QUEUE 1'.
            "
        ::= { zxAnQos3PortConfigEntry 7 }

    zxAnQosIfRateLimit  OBJECT-TYPE
        SYNTAX      Integer32(0|64..10000000)
        UNITS       "kbps"
        MAX-ACCESS  read-write
        STATUS      current
        DESCRIPTION
            "The rate-limit of interface's shaping,
             0 is not limit."
        DEFVAL { 0 }
        ::= { zxAnQos3PortConfigEntry 8 }

    zxAnQosIfBucketSize OBJECT-TYPE
        SYNTAX      Integer32(0|4..16000)
        UNITS       "kbytes"
        MAX-ACCESS  read-write
        STATUS      current
        DESCRIPTION
            "The bucket-size of interface's shaping,
             0 is not shaping."
        DEFVAL { 0 }
        ::= { zxAnQos3PortConfigEntry 9 }

    zxAnQosIfTrustMode OBJECT-TYPE
        SYNTAX      INTEGER
        {
            cos(1),
            dscp(2)
        }
        MAX-ACCESS  read-write
        STATUS      current
        DESCRIPTION
            "Trust mode."
        DEFVAL { cos }
        ::= { zxAnQos3PortConfigEntry 10 }

    zxAnQosIfDefaultCos OBJECT-TYPE
        SYNTAX      INTEGER(0..7)
        MAX-ACCESS  read-write
        STATUS      current
        DESCRIPTION
            "Default CoS value.
             This object is valid only when zxAnQosIfTrustMode is set to
             cos."
        DEFVAL { 0 }
        ::= { zxAnQos3PortConfigEntry 11 }

    zxAnQosIfDscpToCosPrf OBJECT-TYPE
        SYNTAX      DisplayString(SIZE(1..32))
        MAX-ACCESS  read-write
        STATUS      current
        DESCRIPTION
            "The value of this object is the name of the referenced profile in
             the zxAnQos3Dscp2CosProfileTable which applies on this
             interface.
             This object is valid only when zxAnQosIfTrustMode is set to
             dscp."
        ::= { zxAnQos3PortConfigEntry 12 }

    zxAnQosIfDscpToDropPrecedencePrf OBJECT-TYPE
        SYNTAX      DisplayString(SIZE(0..32))
        MAX-ACCESS  read-write
        STATUS      current
        DESCRIPTION
            "The value of this object is the name of the referenced profile in
             the zxAnQos3Dscp2DropProfileTable which applies on this
             interface.
             This object is valid only when zxAnQosIfTrustMode is set to
             dscp."
        ::= { zxAnQos3PortConfigEntry 13 }

    zxAnQosIfDscpToDscpPrf OBJECT-TYPE
        SYNTAX      DisplayString(SIZE(0..32))
        MAX-ACCESS  read-write
        STATUS      current
        DESCRIPTION
            "The value of this object is the name of the referenced profile in
             the zxAnQos3DscpRemarkProfileTable which applies on this
             interface.
             This object is valid only when zxAnQosIfTrustMode is set to
             dscp."
        ::= { zxAnQos3PortConfigEntry 14 }

    zxAnQosIfIngressRateLimit  OBJECT-TYPE
        SYNTAX      Integer32(0|64..10000000)
        UNITS       "kbps"
        MAX-ACCESS  read-write
        STATUS      current
        DESCRIPTION
            "Ingress rate limit.
             zxAnQosIfIngressRateLimit is mandatory with
             zxAnQosIfIngressBucketSize.
             0 means no limit."
        DEFVAL  { 0 }
        ::= { zxAnQos3PortConfigEntry 15 }

    zxAnQosIfIngressBucketSize OBJECT-TYPE
        SYNTAX      Integer32(0|4..16000)
        UNITS       "kbytes"
        MAX-ACCESS  read-write
        STATUS      current
        DESCRIPTION
            "Ingress bucket size.
             zxAnQosIfIngressBucketSize is mandatory with
             zxAnQosIfIngressRateLimit.
             0 means no shaping."
        DEFVAL  { 0 }
        ::= { zxAnQos3PortConfigEntry 16 }

-------------------------------------------------------------------------------
-- 7.zxAnQos3VPortConfigTable
-------------------------------------------------------------------------------
    zxAnQos3VPortConfigTable  OBJECT-TYPE
        SYNTAX      SEQUENCE  OF  ZxAnQos3VPortConfigEntry
        MAX-ACCESS  not-accessible
        STATUS      current
        DESCRIPTION
            "This table contains QoS configuration parameters for virtual
             circuit."
        ::= { zxAnQos3VPortConfig 1 }

    zxAnQos3VPortConfigEntry  OBJECT-TYPE
        SYNTAX      ZxAnQos3VPortConfigEntry
        MAX-ACCESS  not-accessible
        STATUS      current
        DESCRIPTION
            "An entry in zxAnQos3VPortConfigTable."
        INDEX { zxAnQos3Rack, zxAnQos3Shelf,
                zxAnQos3Slot, zxAnQos3Port,
                zxAnQos3Onu, zxAnQos3VCircuitType,
                zxAnQos3LogicalId}
        ::= { zxAnQos3VPortConfigTable 1 }

    ZxAnQos3VPortConfigEntry  ::=
        SEQUENCE {
            zxAnQosIfCosFilter               INTEGER,
            zxAnQos3IngressCosMarkMode       INTEGER,
            zxAnQos3IngressInnerCosMarkMode  INTEGER,
            zxAnQos3EgressCosMarkMode        INTEGER,
            zxAnQos3IngressDefaultCos        INTEGER,
            zxAnQos3IngressDefaultInnerCos   INTEGER,
            zxAnQosIfDefaultEgressCos        INTEGER,
            zxAnQosIfCosToCosPrf             DisplayString,
            zxAnQosIfCtagCosToCosPrf         DisplayString,
            zxAnQosIfEgressCosToCosPrf       DisplayString,
            zxAnQos3IngressDscp2CosPrf       DisplayString,
            zxAnQos3IngressDscp2InnerCosPrf  DisplayString,
            zxAnQosIfEgressDscpToCosPrf      DisplayString
        }

    zxAnQosIfCosFilter OBJECT-TYPE
        SYNTAX      INTEGER
        {
            enable(1),
            disable(2),
            notSupport(255)
        }
        MAX-ACCESS  read-write
        STATUS      current
        DESCRIPTION
            "Enable or disable CoS filter."
        DEFVAL { disable }
        ::= { zxAnQos3VPortConfigEntry 1 }

    zxAnQos3IngressCosMarkMode OBJECT-TYPE
        SYNTAX      INTEGER
        {
            trust(1),
            override(2),
            cosRemark(3),
            dscpToCos(4),
            notSupport(255)
        }
        MAX-ACCESS  read-write
        STATUS      current
        DESCRIPTION
            "CoS mark mode, ingress direction.
             trust(1)     -- Trust the CoS priority and not to change it.
             override(2)  -- Override the CoS priority with
                             zxAnQos3IngressDefaultCos.
             cosRemark(3) -- Remark the CoS priority with
                             zxAnQosIfCosToCosPrf.
             dscpToCos(4)  -- Remark the CoS priority with
                             zxAnQos3IngressDscp2CosPrf."
        DEFVAL { trust }
        ::= { zxAnQos3VPortConfigEntry 2 }

    zxAnQos3IngressInnerCosMarkMode OBJECT-TYPE
        SYNTAX      INTEGER
        {
            trust(1),
            override(2),
            cosRemark(3),
            dscpToCos(4),
            notSupport(255)
        }
        MAX-ACCESS  read-write
        STATUS      current
        DESCRIPTION
            "Inner CoS mark mode, ingress direction.
             trust(1)    -- Trust the CoS priority and not to change it.
             override(2) -- Override the CoS priority with
                            zxAnQos3IngressDefaultInnerCos.
             cosRemark(3)-- Remark the CoS priority with
                            zxAnQosIfCtagCosToCosPrf.
             dscpToCos(4) -- Remark the CoS priority with
                            zxAnQos3IngressDscp2InnerCosPrf."
        DEFVAL { trust }
        ::= { zxAnQos3VPortConfigEntry 3 }

    zxAnQos3EgressCosMarkMode OBJECT-TYPE
        SYNTAX      INTEGER
        {
            trust(1),
            override(2),
            cosRemark(3),
            dscpToCos(4),
            notSupport(255)
        }
        MAX-ACCESS  read-write
        STATUS      current
        DESCRIPTION
            "CoS mark mode, Egress direction.
             trust(1)     -- Trust the CoS priority and not to change it.
             override(2)  -- Override the CoS priority with
                             zxAnQos3EgressDefaultCos.
             cosRemark(3) -- Remark the CoS priority with
                             zxAnQosIfEgressCosToCosPrf.
             dscpToCos(4)  -- Remark the inner CoS priority with
                             zxAnQosIfEgressDscpToCosPrf."
        DEFVAL { trust }
        ::= { zxAnQos3VPortConfigEntry 4 }

    zxAnQos3IngressDefaultCos  OBJECT-TYPE
        SYNTAX      INTEGER(0..7|255)
        MAX-ACCESS  read-write
        STATUS      current
        DESCRIPTION
            "Ingress default CoS value.
             255 means not support."
        DEFVAL { 0 }
        ::= { zxAnQos3VPortConfigEntry 5 }

    zxAnQos3IngressDefaultInnerCos OBJECT-TYPE
        SYNTAX      INTEGER(0..7|255)
        MAX-ACCESS  read-write
        STATUS      current
        DESCRIPTION
            "Ingress default inner CoS value.
             255 means not support."
        DEFVAL { 0 }
        ::= { zxAnQos3VPortConfigEntry 6 }

    zxAnQosIfDefaultEgressCos  OBJECT-TYPE
        SYNTAX      INTEGER(0..7|255)
        MAX-ACCESS  read-write
        STATUS      current
        DESCRIPTION
            "Egress default CoS vlaue.
             255 means not support."
        DEFVAL { 0 }
        ::= { zxAnQos3VPortConfigEntry 7 }

    zxAnQosIfCosToCosPrf OBJECT-TYPE
        SYNTAX      DisplayString(SIZE(0..32))
        MAX-ACCESS  read-write
        STATUS      current
        DESCRIPTION
            "The value of this object is the name of the referenced profile in
             the zxAnQos3CosRemarkProfileTable which applies on this
             interface.
             A zero-length means not support."
        ::= { zxAnQos3VPortConfigEntry 8 }

    zxAnQosIfCtagCosToCosPrf OBJECT-TYPE
        SYNTAX      DisplayString(SIZE(0..32))
        MAX-ACCESS  read-write
        STATUS      current
        DESCRIPTION
            "The value of this object is the name of the referenced profile in
             the zxAnQos3CosRemarkProfileTable which applies on this
             interface..
             A zero-length means not support."
        ::= { zxAnQos3VPortConfigEntry 9 }

    zxAnQosIfEgressCosToCosPrf OBJECT-TYPE
        SYNTAX      DisplayString(SIZE(0..32))
        MAX-ACCESS  read-write
        STATUS      current
        DESCRIPTION
            "The value of this object is the name of the referenced profile in
             the zxAnQos3CosRemarkProfileTable which applies on this
             interface.
             A zero-length means not support."
        ::= { zxAnQos3VPortConfigEntry 10 }

    zxAnQos3IngressDscp2CosPrf OBJECT-TYPE
        SYNTAX      DisplayString(SIZE(0..32))
        MAX-ACCESS  read-write
        STATUS      current
        DESCRIPTION
            "The value of this object is the name of the referenced profile in
             the zxAnQos3Dscp2CosProfileTable which applies on this
             interface.
             A zero-length means not support."
        ::= { zxAnQos3VPortConfigEntry 11 }

    zxAnQos3IngressDscp2InnerCosPrf OBJECT-TYPE
        SYNTAX      DisplayString(SIZE(0..32))
        MAX-ACCESS  read-write
        STATUS      current
        DESCRIPTION
            "The value of this object is the name of the referenced profile in
             the zxAnQos3Dscp2CosProfileTable which applies on this
             interface.
             A zero-length means not support."
        ::= { zxAnQos3VPortConfigEntry 12 }

    zxAnQosIfEgressDscpToCosPrf OBJECT-TYPE
        SYNTAX      DisplayString(SIZE(0..32))
        MAX-ACCESS  read-write
        STATUS      current
        DESCRIPTION
            "The value of this object is the name of the referenced profile in
             the zxAnQos3Dscp2CosProfileTable which applies on this
             interface.
             A zero-length means not support."
        ::= { zxAnQos3VPortConfigEntry 13 }

------------------------------------------------------------------------------
-- 8.zxAnQos3QueueBlockProfileTable
------------------------------------------------------------------------------
    zxAnQos3QueueBlockProfileTable  OBJECT-TYPE
        SYNTAX      SEQUENCE  OF  ZxAnQos3QueueBlockProfileEntry
        MAX-ACCESS  not-accessible
        STATUS      current
        DESCRIPTION
            "This table contains configuration parameters for queue.
             One entry in this table reflects a profile defined which can be
             used to configure an interface."
        ::= { zxAnQos3Queue 1 }

    zxAnQos3QueueBlockProfileEntry  OBJECT-TYPE
        SYNTAX      ZxAnQos3QueueBlockProfileEntry
        MAX-ACCESS  not-accessible
        STATUS      current
        DESCRIPTION
            "An entry in zxAnQos3QueueBlockProfileTable."
        INDEX { zxAnQosQueueBlockPrfName }
        ::= { zxAnQos3QueueBlockProfileTable 1 }

    ZxAnQos3QueueBlockProfileEntry  ::=
        SEQUENCE {
            zxAnQosQueueBlockPrfName          DisplayString,
            zxAnQosQueueBlockQNumber          INTEGER,
            zxAnQosQueueWeight                OCTET STRING,
            zxAnQosQueueDepth                 OCTET STRING,
            zxAnQosQueueBlockRowStatus        RowStatus
        }

    zxAnQosQueueBlockPrfName  OBJECT-TYPE
        SYNTAX      DisplayString(SIZE(1..32))
        MAX-ACCESS  not-accessible
        STATUS      current
        DESCRIPTION
            "The profile name is a display string. It is an index of this
            table."
        ::= { zxAnQos3QueueBlockProfileEntry 1 }

    zxAnQosQueueBlockQNumber OBJECT-TYPE
        SYNTAX      INTEGER
        {
            two(2),
            four(4),
            eight(8)
        }
        MAX-ACCESS  read-create
        STATUS      current
        DESCRIPTION
            "The number of queues."
        DEFVAL { eight }
        ::= { zxAnQos3QueueBlockProfileEntry 2 }

    zxAnQosQueueWeight OBJECT-TYPE
        SYNTAX      OCTET STRING(SIZE (8))
        MAX-ACCESS  read-create
        STATUS      current
        DESCRIPTION
            "The weight of queues.
             For example, the value '01 02 04 06 02 02 02 02' means that
             weight of queue 0 is 1,...,weight of queue 7 is 2.
             The range of each weight is 0 to 63.
             Default value of weight is 0.
             The invalid weight of queues must be set to 255.
             Queue's number is associated with zxAnQosQueueBlockQNumber."
        ::= { zxAnQos3QueueBlockProfileEntry 3 }

    zxAnQosQueueDepth     OBJECT-TYPE
         SYNTAX      OCTET STRING(SIZE (8))
         MAX-ACCESS  read-create
         STATUS      current
         DESCRIPTION
             "The depth of queues.
              For example, the value '01 02 04 06 02 02 02 02' means depth of
              queue 0 is 1,...,depth of queue 7 is 2.
              The range of each depth is 0 to 63.
              Unit of depth is 2kbytes.
              Default value of depth is 2.
              The invalid depth of queues must be set to 255.
              Queue's number is associated with zxAnQosQueueBlockQNumber."
        ::= { zxAnQos3QueueBlockProfileEntry 4 }

    zxAnQosQueueBlockRowStatus  OBJECT-TYPE
        SYNTAX      RowStatus
        MAX-ACCESS  read-create
        STATUS      current
        DESCRIPTION
            "This object is used to create a new row or to modify or
             delete an existing row in this table."
        ::= { zxAnQos3QueueBlockProfileEntry 20 }

------------------------------------------------------------------------------
-- 9.zxAnQos3QueueMapProfileTable
------------------------------------------------------------------------------
    zxAnQos3QueueMapProfileTable  OBJECT-TYPE
        SYNTAX      SEQUENCE  OF  ZxAnQos3QueueMapProfileEntry
        MAX-ACCESS  not-accessible
        STATUS      current
        DESCRIPTION
            "This table contains configuration parameters for enqueue profile.
             One entry in this table reflects a profile defined which can be
             used to configure an interface."
        ::= { zxAnQos3Queue 2 }

    zxAnQos3QueueMapProfileEntry  OBJECT-TYPE
        SYNTAX      ZxAnQos3QueueMapProfileEntry
        MAX-ACCESS  not-accessible
        STATUS      current
        DESCRIPTION
            "An entry in zxAnQos3QueueMapProfileTable."
        INDEX { zxAnQosQueueMapPrfName }
        ::= { zxAnQos3QueueMapProfileTable 1 }

    ZxAnQos3QueueMapProfileEntry  ::=
        SEQUENCE {
            zxAnQosQueueMapPrfName      DisplayString,
            zxAnQosQueueMapQNumber      INTEGER,
            zxAnQosQueueMapMode         INTEGER,
            zxAnQosCosToQueue           OCTET STRING,
            zxAnQosPvc2Queue            OCTET STRING,
            zxAnQosQueueMapRowStatus    RowStatus
        }

    zxAnQosQueueMapPrfName  OBJECT-TYPE
        SYNTAX      DisplayString(SIZE(1..32))
        MAX-ACCESS  not-accessible
        STATUS      current
        DESCRIPTION
            "The profile name is a display string. It is an index of
             this table."
        ::= { zxAnQos3QueueMapProfileEntry 1 }

    zxAnQosQueueMapQNumber OBJECT-TYPE
        SYNTAX      INTEGER
        {
            two(2),
            four(4),
            eight(8)
        }
        MAX-ACCESS  read-create
        STATUS      current
        DESCRIPTION
            "The number of queues."
        DEFVAL { eight }
        ::= { zxAnQos3QueueMapProfileEntry 2 }

    zxAnQosQueueMapMode OBJECT-TYPE
        SYNTAX      INTEGER
        {
            cos(1),
            servicePort(2),
            gemPort(3),
            pvc(4)
        }
        MAX-ACCESS  read-create
        STATUS      current
        DESCRIPTION
            "Queue mapping mode."
        DEFVAL { cos }
        ::= { zxAnQos3QueueMapProfileEntry 3 }

    zxAnQosCosToQueue OBJECT-TYPE
        SYNTAX      OCTET STRING(SIZE (8))
        MAX-ACCESS  read-create
        STATUS      current
        DESCRIPTION
            "The queue that each CoS value has been assigned to.
             For example, the value '00 01 02 03 04 05 06 07' means queue 0
             is assigned to CoS priority 0,...,queue 7 is assigned to CoS
             priority 7.
             Number of queues is associated with zxAnQosQueueMapQNumber."
        ::= { zxAnQos3QueueMapProfileEntry 4 }

    zxAnQosPvc2Queue OBJECT-TYPE
        SYNTAX      OCTET STRING(SIZE (8))
        MAX-ACCESS  read-create
        STATUS      current
        DESCRIPTION
            "The queue that each PVC value has been assigned to.
             For example, the value '00 01 02 03 04 05 06 07' means PVC 1
             is assigned to queue 0,...,PVC 8 is assigned to queue 7.
             Number of queues is associated with zxAnQosQueueMapQNumber.
             The object is valid only when zxAnQosQueueMapMode is pvc(4)."
        ::= { zxAnQos3QueueMapProfileEntry 5 }

    zxAnQosQueueMapRowStatus  OBJECT-TYPE
        SYNTAX      RowStatus
        MAX-ACCESS  read-create
        STATUS      current
        DESCRIPTION
            "This object is used to create a new row or to modify or
             delete an existing row in this table."
        ::= { zxAnQos3QueueMapProfileEntry 20 }

-------------------------------------------------------------------------------
-- 10.zxAnQos3PortQueueConfigTable
-------------------------------------------------------------------------------
    zxAnQos3PortQueueConfigTable  OBJECT-TYPE
        SYNTAX      SEQUENCE  OF  ZxAnQos3PortQueueConfigEntry
        MAX-ACCESS  not-accessible
        STATUS      current
        DESCRIPTION
            "This table contains interface queue configuration. It is used
             for physical interface."
        ::= { zxAnQos3Queue 3 }

    zxAnQos3PortQueueConfigEntry  OBJECT-TYPE
        SYNTAX      ZxAnQos3PortQueueConfigEntry
        MAX-ACCESS  not-accessible
        STATUS      current
        DESCRIPTION
            "An entry in zxAnQos3PortQueueConfigTable."
        INDEX {zxAnQos3Rack, zxAnQos3Shelf,
               zxAnQos3Slot, zxAnQos3Port,
               zxAnQos3Onu, zxAnQos3VCircuitType,
               zxAnQos3LogicalId }
        ::= { zxAnQos3PortQueueConfigTable 1 }

    ZxAnQos3PortQueueConfigEntry  ::=
        SEQUENCE {
            zxAnQosIfQueueBlockPrf       DisplayString,
            zxAnQosIfQueueMapPrf         DisplayString
        }

    zxAnQosIfQueueBlockPrf OBJECT-TYPE
        SYNTAX      DisplayString(SIZE(0..32))
        MAX-ACCESS  read-write
        STATUS      current
        DESCRIPTION
            "This object configures queue profile for this interface.
             The value of this object is the name of the referenced profile in
             the zxAnQos3QueueBlockProfileTable."
        ::= { zxAnQos3PortQueueConfigEntry 1 }

    zxAnQosIfQueueMapPrf OBJECT-TYPE
        SYNTAX      DisplayString(SIZE(0..32))
        MAX-ACCESS  read-write
        STATUS      current
        DESCRIPTION
            "This object configures enqueue profile for this interface.
             The value of this object is the name of the referenced profile in
             the zxAnQos3QueueMapProfileTable. Notice that if the interface type
             is Ethernet, configure zxAnQosEthCosToQueue instead of this object
             ."
        ::= { zxAnQos3PortQueueConfigEntry 2 }

------------------------------------------------------------------------------
-- 11.zxAnQos3TrafficProfileTable
------------------------------------------------------------------------------
    zxAnQos3TrafficProfileTable OBJECT-TYPE
        SYNTAX      SEQUENCE OF ZxAnQos3TrafficProfileEntry
        MAX-ACCESS  not-accessible
        STATUS      current
        DESCRIPTION
            "This table contains information about traffic control.
             An entry in this table reflects a profile defined which can be
             used to configure an interface."
        ::= { zxAnQos3Traffic 1 }

    zxAnQos3TrafficProfileEntry OBJECT-TYPE
        SYNTAX      ZxAnQos3TrafficProfileEntry
        MAX-ACCESS  not-accessible
        STATUS      current
        DESCRIPTION
            "An entry in zxAnQos3TrafficProfileTable."
        INDEX { zxAnQosTrafficPrfName }
        ::= { zxAnQos3TrafficProfileTable 1 }

    ZxAnQos3TrafficProfileEntry ::= SEQUENCE {
        zxAnQosTrafficPrfName          DisplayString,
        zxAnQosTrafficPrfCir           Integer32,
        zxAnQosTrafficPrfCbs           Integer32,
        zxAnQosTrafficPrfPir           Integer32,
        zxAnQosTrafficPrfPbs           Integer32,
        zxAnQosTrafficPrfDiscardMode   INTEGER,
        zxAnQosTrafficPrfCirCosRemark  Integer32,
        zxAnQosTrafficPrfPirCosRemark  Integer32,
        zxAnQosTrafficPrfColorMode     INTEGER,
        zxAnQosTrafficPrfRowStatus     RowStatus
    }

    zxAnQosTrafficPrfName  OBJECT-TYPE
        SYNTAX      DisplayString(SIZE(1..32))
        MAX-ACCESS  not-accessible
        STATUS      current
        DESCRIPTION
            "Traffic profile name which applies to an interface."
        ::= { zxAnQos3TrafficProfileEntry 1 }

    zxAnQosTrafficPrfCir OBJECT-TYPE
        SYNTAX      Integer32(0..10000000)
        UNITS       "kbps"
        MAX-ACCESS  read-create
        STATUS      current
        DESCRIPTION
            "Committed Information Rate(CIR) in kbps."
        ::= { zxAnQos3TrafficProfileEntry 2 }

    zxAnQosTrafficPrfCbs OBJECT-TYPE
        SYNTAX      Integer32(0..1023)
        UNITS       "kbytes"
        MAX-ACCESS  read-create
        STATUS      current
        DESCRIPTION
            "Committed Burst Rate(CBS) in kbytes."
        ::= { zxAnQos3TrafficProfileEntry 3 }

    zxAnQosTrafficPrfPir OBJECT-TYPE
        SYNTAX      Integer32(0..10000000)
        UNITS       "kbps"
        MAX-ACCESS  read-create
        STATUS      current
        DESCRIPTION
            "Peak Information Rate(PIR) in kbps."
        ::= { zxAnQos3TrafficProfileEntry 4 }

    zxAnQosTrafficPrfPbs OBJECT-TYPE
        SYNTAX      Integer32(0..1023)
        UNITS       "kbytes"
        MAX-ACCESS  read-create
        STATUS      current
        DESCRIPTION
            "Peak Burst Rate(PBS) in kbyte."
        ::= { zxAnQos3TrafficProfileEntry 5 }

    zxAnQosTrafficPrfDiscardMode OBJECT-TYPE
        SYNTAX      INTEGER
        {
            noDistinction(1),
            lowPriorityFirst(2)
        }
        MAX-ACCESS  read-create
        STATUS      current
        DESCRIPTION
            "The discard mode is used when the traffic exceeds the limit.
             noDistinction(1)    -- discard extra flow equally.
             lowPriorityFirst(2) -- discard low priority first."
        ::= { zxAnQos3TrafficProfileEntry 6 }

    zxAnQosTrafficPrfCirCosRemark OBJECT-TYPE
        SYNTAX      Integer32(0..7|255)
        MAX-ACCESS  read-create
        STATUS      current
        DESCRIPTION
            "CIR CoS priority remark value.
             '0xFF' indicates no config."
        DEFVAL { 0 }
        ::= { zxAnQos3TrafficProfileEntry 7 }

    zxAnQosTrafficPrfPirCosRemark OBJECT-TYPE
        SYNTAX      Integer32(0..7|255)
        MAX-ACCESS  read-create
        STATUS      current
        DESCRIPTION
            "PIR CoS priority remark value.
             '0xFF' indicates no config."
        DEFVAL { 0 }
        ::= { zxAnQos3TrafficProfileEntry 8 }

    zxAnQosTrafficPrfColorMode OBJECT-TYPE
        SYNTAX      INTEGER
        {
            colorAware(1),
            colorBlind(2)
        }
        MAX-ACCESS  read-create
        STATUS      current
        DESCRIPTION
            "Color mode is used to determine how to classify the traffic
             according the color flag that the traffic carries.
             colorAware(1) -- the color already associated with each service
                              frame is taken into account.
             colorBlind(2) -- the color already associated with each service
                              frame is ignored."
        DEFVAL { colorBlind }
        ::= { zxAnQos3TrafficProfileEntry 9 }

    zxAnQosTrafficPrfRowStatus OBJECT-TYPE
        SYNTAX      RowStatus
        MAX-ACCESS  read-create
        STATUS      current
        DESCRIPTION
            "This object is used to create a new row or modify or
             delete an existing row in this table."
        ::= { zxAnQos3TrafficProfileEntry 20 }

--------------------------------------------------------------------------------
-- 12.zxAnQos3TrafficConfigTable
--------------------------------------------------------------------------------
    zxAnQos3TrafficConfigTable  OBJECT-TYPE
        SYNTAX      SEQUENCE  OF  ZxAnQos3TrafficConfigEntry
        MAX-ACCESS  not-accessible
        STATUS      current
        DESCRIPTION
            "This table contains interface QoS traffic configuration."
        ::=  { zxAnQos3Traffic  2 }

    zxAnQos3TrafficConfigEntry  OBJECT-TYPE
        SYNTAX      ZxAnQos3TrafficConfigEntry
        MAX-ACCESS  not-accessible
        STATUS      current
        DESCRIPTION
            "An entry in zxAnQos3TrafficConfigTable."
        INDEX { zxAnQos3Rack, zxAnQos3Shelf,
                zxAnQos3Slot, zxAnQos3Port,
                zxAnQos3Onu, zxAnQos3VCircuitType,
                zxAnQos3LogicalId, zxAnQosTrafficIfVlanDirection}
        ::= { zxAnQos3TrafficConfigTable 1 }

    ZxAnQos3TrafficConfigEntry  ::=
        SEQUENCE {
            zxAnQosTrafficIfVlanDirection   INTEGER,
            zxAnQosTrafficIfConfPrf         DisplayString,
            zxAnQosTrafficIfConfPrfType     INTEGER,
            zxAnQosTrafficIfRowStatus       RowStatus
        }

    zxAnQosTrafficIfVlanDirection OBJECT-TYPE
        SYNTAX      INTEGER
        {
            ingress(1),
            egress(2)
        }
        MAX-ACCESS  not-accessible
        STATUS      current
        DESCRIPTION
            "Egress direction or ingress direction on an interface."
        ::= { zxAnQos3TrafficConfigEntry 1 }

    zxAnQosTrafficIfConfPrf OBJECT-TYPE
        SYNTAX      DisplayString(SIZE(1..32))
        MAX-ACCESS  read-create
        STATUS      current
        DESCRIPTION
            "This object configures traffic profile of ingress or egress
             direction. The value of this object is the name of the referenced
             profile in the zxAnQos3TrafficProfileTable."
        ::= { zxAnQos3TrafficConfigEntry 2 }

    zxAnQosTrafficIfConfPrfType OBJECT-TYPE
        SYNTAX      INTEGER
        {
            ip(1),
            atm(2)
        }
        MAX-ACCESS  read-create
        STATUS      current
        DESCRIPTION
            "The value is defined as traffic profile type.
             ip(1)  -- IP type.
             atm(2) -- ATM type."
        DEFVAL {ip}
        ::= { zxAnQos3TrafficConfigEntry 3 }

    zxAnQosTrafficIfRowStatus  OBJECT-TYPE
        SYNTAX      RowStatus
        MAX-ACCESS  read-create
        STATUS      current
        DESCRIPTION
            "This object is used to create a new row or modify or
             delete an existing row in this table."
        ::=  { zxAnQos3TrafficConfigEntry  20 }

------------------------------------------------------------------------------
-- 16.zxAnQos3AtmTrafficProfileTable
------------------------------------------------------------------------------
    zxAnQos3AtmTrafficProfileTable OBJECT-TYPE
        SYNTAX      SEQUENCE OF ZxAnQos3AtmTrafficProfileEntry
        MAX-ACCESS  not-accessible
        STATUS      current
        DESCRIPTION
            "This table contains information about ATM traffic control.
             An entry in this table reflects a profile defined which can be
             used to configure a dsl PVC interface only, but can not be used to
             configure other interface."
        ::= { zxAnQos3Traffic 3 }

    zxAnQos3AtmTrafficProfileEntry OBJECT-TYPE
        SYNTAX      ZxAnQos3AtmTrafficProfileEntry
        MAX-ACCESS  not-accessible
        STATUS      current
        DESCRIPTION
            "An entry in zxAnQos3AtmTrafficProfileTable."
        INDEX { zxAnQosAtmTrafficPrfName }
        ::= { zxAnQos3AtmTrafficProfileTable 1 }

    ZxAnQos3AtmTrafficProfileEntry ::= SEQUENCE {
        zxAnQosAtmTrafficPrfName           DisplayString,
        zxAnQosAtmTrafficPrfType           INTEGER,
        zxAnQosAtmTrafficPrfPcr            Integer32,
        zxAnQosAtmTrafficPrfPcrCosRemark   Integer32,
        zxAnQosAtmTrafficPrfMcr            Integer32,
        zxAnQosAtmTrafficPrfMcrCosRemark   Integer32,
        zxAnQosAtmTrafficPrfScr            Integer32,
        zxAnQosAtmTrafficPrfScrCosRemark   Integer32,
        zxAnQosAtmTrafficPrfDiscardMode    INTEGER,
        zxAnQosAtmTrafficPrfRowStatus      RowStatus
    }

    zxAnQosAtmTrafficPrfName  OBJECT-TYPE
        SYNTAX      DisplayString(SIZE(1..32))
        MAX-ACCESS  not-accessible
        STATUS      current
        DESCRIPTION
            "Traffic profile name which applies to an interface."
        ::= { zxAnQos3AtmTrafficProfileEntry 1 }

    zxAnQosAtmTrafficPrfType OBJECT-TYPE
        SYNTAX      INTEGER
        {
            atmCbr(1),
            atmUbr(2),
            atmVbr(3)
        }
        MAX-ACCESS  read-create
        STATUS      current
        DESCRIPTION
            "The value is defined as ATM sub-type.
             atmCbr(1) -- ATM CBR type.
             atmUbr(2) -- ATM UBR type.
             atmVbr(3) -- ATM VBR type."
        ::= { zxAnQos3AtmTrafficProfileEntry 2 }

    zxAnQosAtmTrafficPrfPcr OBJECT-TYPE
        SYNTAX      Integer32(0..20480)
        UNITS       "kbps"
        MAX-ACCESS  read-create
        STATUS      current
        DESCRIPTION
            "Peak cell rate(PCR) in kbps."
        ::= { zxAnQos3AtmTrafficProfileEntry 3 }

   zxAnQosAtmTrafficPrfPcrCosRemark OBJECT-TYPE
        SYNTAX      Integer32(0..7|255)
        MAX-ACCESS  read-create
        STATUS      current
        DESCRIPTION
            "PCR CoS priority remark value.
             '0xFF' indicates no config."
        ::= { zxAnQos3AtmTrafficProfileEntry 4 }

    zxAnQosAtmTrafficPrfMcr OBJECT-TYPE
        SYNTAX      Integer32(0..20480)
        UNITS       "kbps"
        MAX-ACCESS  read-create
        STATUS      current
        DESCRIPTION
            "Minimum cell rate(MCR) in kbps."
        ::= { zxAnQos3AtmTrafficProfileEntry 5 }

    zxAnQosAtmTrafficPrfMcrCosRemark OBJECT-TYPE
        SYNTAX      Integer32(0..7|255)
        MAX-ACCESS  read-create
        STATUS      current
        DESCRIPTION
            "MCR CoS priority remark value.
             '0xFF' indicates no config."
        ::= { zxAnQos3AtmTrafficProfileEntry 6 }

    zxAnQosAtmTrafficPrfScr OBJECT-TYPE
        SYNTAX      Integer32(0..20480)
        UNITS       "kbps"
        MAX-ACCESS  read-create
        STATUS      current
        DESCRIPTION
            "Sustainable cell rate(SCR) in kbps."
        ::= { zxAnQos3AtmTrafficProfileEntry 7 }

    zxAnQosAtmTrafficPrfScrCosRemark OBJECT-TYPE
        SYNTAX      Integer32(0..7|255)
        MAX-ACCESS  read-create
        STATUS      current
        DESCRIPTION
            "SCR CoS priority remark value.
             '0xFF' indicates no config."
        ::= { zxAnQos3AtmTrafficProfileEntry 8 }

    zxAnQosAtmTrafficPrfDiscardMode OBJECT-TYPE
        SYNTAX      INTEGER
        {
            noDistinction(1),
            lowPriorityFirst(2)
        }
        MAX-ACCESS  read-create
        STATUS      current
        DESCRIPTION
            "The discard mode is used when the traffic exceeds the limit.
             noDistinction(1)    -- discard extra flow equally.
             lowPriorityFirst(2) -- discard low priority first."
        ::= { zxAnQos3AtmTrafficProfileEntry 9 }

    zxAnQosAtmTrafficPrfRowStatus OBJECT-TYPE
        SYNTAX      RowStatus
        MAX-ACCESS  read-create
        STATUS      current
        DESCRIPTION
            "This object is used to create a new row or modify or
             delete an existing row in this table."
        ::= { zxAnQos3AtmTrafficProfileEntry 20 }

--------------------------------------------------------------------------------
-- 13.zxAnQos3RemainingBwTable
--------------------------------------------------------------------------------
    zxAnQos3RemainingBwTable  OBJECT-TYPE
        SYNTAX      SEQUENCE  OF  ZxAnQos3RemainingBwEntry
        MAX-ACCESS  not-accessible
        STATUS      current
        DESCRIPTION
            "This table contains information about interface's bandwidth.
             It is used for physical ports."
        REFERENCE
            "Only Used by AG."
        ::=  { zxAnQos3Traffic  24 }

    zxAnQos3RemainingBwEntry  OBJECT-TYPE
        SYNTAX      ZxAnQos3RemainingBwEntry
        MAX-ACCESS  not-accessible
        STATUS      current
        DESCRIPTION
            "An entry in zxAnQos3RemainingBwTable."
        INDEX { zxAnQos3Rack, zxAnQos3Shelf,
                zxAnQos3Slot, zxAnQos3Port,
                zxAnQos3Onu, zxAnQos3VCircuitType,
                zxAnQos3LogicalId}
        ::= { zxAnQos3RemainingBwTable 1 }

    ZxAnQos3RemainingBwEntry  ::=
        SEQUENCE {
            zxAnQosTrafficTotalBandwidth      Integer32,
            zxAnQosTrafficRemainingBandwidth  Integer32
        }

    zxAnQosTrafficTotalBandwidth  OBJECT-TYPE
        SYNTAX      Integer32
        UNITS       "kbps"
        MAX-ACCESS  read-only
        STATUS      current
        DESCRIPTION
            "Total bandwidth of the interface."
        ::= { zxAnQos3RemainingBwEntry 1 }

    zxAnQosTrafficRemainingBandwidth  OBJECT-TYPE
        SYNTAX      Integer32
        UNITS       "kbps"
        MAX-ACCESS  read-only
        STATUS      current
        DESCRIPTION
            "Remaining bandwidth of the interface."
        ::= { zxAnQos3RemainingBwEntry 2 }
END
