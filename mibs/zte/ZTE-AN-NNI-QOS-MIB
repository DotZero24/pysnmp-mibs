--------------------------------------------------------------------------------
-- File Name : ZTE-AN-NNI-QOS-MIB.mib
-- Date      : 2008-01-18
-- Author    : ZTE Nms dept.

--
-- Zte NNI Qos Mib for Access Node
--
--
--------------------------------------------------------------------------------


ZTE-AN-NNI-QOS-MIB    DEFINITIONS ::= BEGIN
    IMPORTS
        RowStatus                         FROM SNMPv2-TC
        MODULE-IDENTITY, OBJECT-TYPE      FROM SNMPv2-SMI
        Integer32                         FROM SNMPv2-SMI
        Unsigned32                        FROM SNMPv2-SMI
        ifIndex                           FROM IF-MIB
        ZxAnIfindex                       FROM ZTE-AN-TC-MIB
        zxAn                              FROM ZTE-AN-TC-MIB;


    zxAnNniQosMib    MODULE-IDENTITY
        LAST-UPDATED    "200801191102Z"
        ORGANIZATION    "ZTE Corporation"
        CONTACT-INFO    "Su Chunshan
                        Mail: suchunshan@zte.com.cn
                        Tel : 021-68896292"
        DESCRIPTION     "This MIB defines zte Access Node managed objects."
        ::=  {  zxAn  22  }

    zxAnNniQosObjects           OBJECT IDENTIFIER   ::=  { zxAnNniQosMib 1 }
    zxAnNniQosTrapObjects       OBJECT IDENTIFIER   ::=  { zxAnNniQosMib 2 }

    zxAnNniQosGlobalObjects     OBJECT IDENTIFIER   ::=  { zxAnNniQosObjects 1 }

--------------------------------------------------------------------------------
-- Following objects are defined.
-- 1.Global configuration cos 2 Shape
-- 2.Shape schedular Table
--------------------------------------------------------------------------------

--------------------------------------------------------------------------------
-- 1.Global configuration cos 2 Shape
--------------------------------------------------------------------------------
    zxAnNniQosCos2Queue OBJECT-TYPE
        SYNTAX      OCTET STRING(SIZE (8))
        MAX-ACCESS  read-write
        STATUS      current
        DESCRIPTION
        ""
        ::= { zxAnNniQosGlobalObjects 1 }


--------------------------------------------------------------------------------
-- 2.Traffic Class (DSCP) to COS Priority Mapping Table
--------------------------------------------------------------------------------
      zxAnNniQosQueueSchedTable    OBJECT-TYPE
            SYNTAX        SEQUENCE  OF  ZxAnNniQosQueueSchedEntry
            MAX-ACCESS    not-accessible
            STATUS        current
            DESCRIPTION    ""
            ::=  { zxAnNniQosObjects  2 }

      zxAnNniQosQueueSchedEntry    OBJECT-TYPE
            SYNTAX        ZxAnNniQosQueueSchedEntry
            MAX-ACCESS    not-accessible
            STATUS        current
            DESCRIPTION    ""
            INDEX        {  ifIndex  }
            ::=  { zxAnNniQosQueueSchedTable 1 }

      ZxAnNniQosQueueSchedEntry  ::=  SEQUENCE
          {
            zxAnNniQosQueueSchedAlgorithm       INTEGER,
            zxAnNniQosQueueSchedWeight          OCTET STRING,
            zxAnNniQosQueueSchedMinRate         OBJECT IDENTIFIER,
            zxAnNniQosQueueSchedMaxRate         OBJECT IDENTIFIER,
            zxAnNniQosQueueSchedRowStatus       RowStatus
          }


      zxAnNniQosQueueSchedAlgorithm    OBJECT-TYPE
            SYNTAX        INTEGER
                  {
                    sp(1),      -- Strict Priority
                    wrr(2),     -- Weighted Round Robin (WRR)
                    fq(3)       -- Fair Queue
                  }
            MAX-ACCESS    read-create
            STATUS        current
            DESCRIPTION        ""
            ::=  {  zxAnNniQosQueueSchedEntry  1  }

      zxAnNniQosQueueSchedWeight    OBJECT-TYPE
            SYNTAX        OCTET STRING(SIZE (8))
            MAX-ACCESS    read-create
            STATUS        current
            DESCRIPTION        ""
            ::=  {  zxAnNniQosQueueSchedEntry  2  }

    zxAnNniQosQueueSchedMinRate     OBJECT-TYPE
        SYNTAX      OBJECT IDENTIFIER
        MAX-ACCESS  read-create
        STATUS      current
        DESCRIPTION
            "The integer sequence of queue's minrate.The size of
            sequence is 8 and it presents min rate for 8 queques.
            For example,the value {100.200.300.400.
            500.600.700.800} means queue1's min rate
            is both 100kbps,....,
            The range of each rate is 0 to 1000000.
            The unit is kbps."
        ::=  {  zxAnNniQosQueueSchedEntry  3  }

    zxAnNniQosQueueSchedMaxRate     OBJECT-TYPE
        SYNTAX      OBJECT IDENTIFIER
        MAX-ACCESS  read-create
        STATUS      current
        DESCRIPTION
            "The integer sequence of queue's max rate.The size of
            sequence is 8 and it presents max rate for 8 queques.
            For example,the value {100.200.300.400.
            500.600.700.800} means queue1's max rate
            is both 100kbps,....,
            The range of each rate is 0 to 1000000.
            The unit is kbps."
        ::=  {  zxAnNniQosQueueSchedEntry  4 }

      zxAnNniQosQueueSchedRowStatus    OBJECT-TYPE
            SYNTAX        RowStatus
            MAX-ACCESS    read-create
            STATUS        current
            DESCRIPTION        ""
            ::=  {  zxAnNniQosQueueSchedEntry  10  }

-------------------
      zxAnNniQosAclBindTable    OBJECT-TYPE
            SYNTAX        SEQUENCE  OF  ZxAnNniQosAclBindEntry
            MAX-ACCESS    not-accessible
            STATUS        current
            DESCRIPTION    ""
            ::=  { zxAnNniQosObjects  3 }

      zxAnNniQosAclBindEntry    OBJECT-TYPE
            SYNTAX        ZxAnNniQosAclBindEntry
            MAX-ACCESS    not-accessible
            STATUS        current
            DESCRIPTION    ""
            INDEX        {  ifIndex  }
            ::=  { zxAnNniQosAclBindTable 1 }

      ZxAnNniQosAclBindEntry  ::=  SEQUENCE
          {
            zxAnNniQosAclIndex              INTEGER,
            zxAnNniQosAclBindDir            INTEGER,
            zxAnNniQosAclBindRowStatus      RowStatus
          }


      zxAnNniQosAclIndex    OBJECT-TYPE
            SYNTAX        INTEGER(1..349)
            MAX-ACCESS    read-create
            STATUS        current
            DESCRIPTION        ""
            ::=  {  zxAnNniQosAclBindEntry  1  }

      zxAnNniQosAclBindDir    OBJECT-TYPE
            SYNTAX        INTEGER
              {
                in(1),
                out(2)
              }
            MAX-ACCESS    read-create
            STATUS        current
            DESCRIPTION        ""
            ::=  {  zxAnNniQosAclBindEntry  2  }

      zxAnNniQosAclBindRowStatus    OBJECT-TYPE
            SYNTAX        RowStatus
             MAX-ACCESS    read-create
            STATUS        current
            DESCRIPTION        ""
            ::=  {  zxAnNniQosAclBindEntry  10  }

--deprecated
      zxAnNniQosShapeTable    OBJECT-TYPE
            SYNTAX        SEQUENCE  OF  ZxAnNniQosShapeEntry
            MAX-ACCESS    not-accessible
            STATUS        current
            DESCRIPTION    "deprecated"
            ::=  { zxAnNniQosObjects  4 }

      zxAnNniQosShapeEntry    OBJECT-TYPE
            SYNTAX        ZxAnNniQosShapeEntry
            MAX-ACCESS    not-accessible
            STATUS        current
            DESCRIPTION    "deprecated"
            INDEX        {  ifIndex  }
            ::=  { zxAnNniQosShapeTable 1 }

      ZxAnNniQosShapeEntry  ::=  SEQUENCE
          {
            zxAnNniQosShapeRate         Integer32,
            zxAnNniQosShapeBurstSize    Integer32,
            zxAnNniQosShapeDir          INTEGER,
            zxAnNniQosShapeRowStatus    RowStatus
          }

      zxAnNniQosShapeRate    OBJECT-TYPE
            SYNTAX        Integer32
            MAX-ACCESS    read-create
            STATUS        current
            DESCRIPTION        "deprecated"
            ::=  {  zxAnNniQosShapeEntry  1  }

      zxAnNniQosShapeBurstSize    OBJECT-TYPE
            SYNTAX        Integer32
            MAX-ACCESS    read-create
            STATUS        current
            DESCRIPTION        "deprecated"
            ::=  {  zxAnNniQosShapeEntry  2  }

      zxAnNniQosShapeDir    OBJECT-TYPE
            SYNTAX        INTEGER{
                    in(1),
                    out(2)
                  }
            MAX-ACCESS    read-create
            STATUS        current
            DESCRIPTION        "deprecated"
            ::=  {  zxAnNniQosShapeEntry  3  }

      zxAnNniQosShapeRowStatus    OBJECT-TYPE
            SYNTAX        RowStatus
            MAX-ACCESS    read-create
            STATUS        current
            DESCRIPTION        "deprecated"
            ::=  {  zxAnNniQosShapeEntry  10  }



--
      zxAnNniQosShapeConfTable    OBJECT-TYPE
            SYNTAX        SEQUENCE  OF  ZxAnNniQosShapeConfEntry
            MAX-ACCESS    not-accessible
            STATUS        current
            DESCRIPTION    ""
            ::=  { zxAnNniQosObjects  5 }

      zxAnNniQosShapeConfEntry    OBJECT-TYPE
            SYNTAX        ZxAnNniQosShapeConfEntry
            MAX-ACCESS    not-accessible
            STATUS        current
            DESCRIPTION    ""
            INDEX        {  ifIndex, zxAnNniQosShapeConfDir  }
            ::=  { zxAnNniQosShapeConfTable 1 }

      ZxAnNniQosShapeConfEntry  ::=  SEQUENCE
          {
            zxAnNniQosShapeConfDir          INTEGER,
            zxAnNniQosShapeConfRate         Integer32,
            zxAnNniQosShapeConfBurstSize    Integer32,
            zxAnNniQosShapeConfRowStatus    RowStatus
          }

      zxAnNniQosShapeConfDir    OBJECT-TYPE
            SYNTAX        INTEGER{
                    in(1),
                    out(2)
                  }
            MAX-ACCESS    not-accessible
            STATUS        current
            DESCRIPTION        ""
            ::=  {  zxAnNniQosShapeConfEntry  1  }

      zxAnNniQosShapeConfRate    OBJECT-TYPE
            SYNTAX        Integer32
            MAX-ACCESS    read-create
            STATUS        current
            DESCRIPTION        ""
            ::=  {  zxAnNniQosShapeConfEntry  2  }

      zxAnNniQosShapeConfBurstSize    OBJECT-TYPE
            SYNTAX        Integer32
            MAX-ACCESS    read-create
            STATUS        current
            DESCRIPTION        ""
            ::=  {  zxAnNniQosShapeConfEntry  3  }

      zxAnNniQosShapeConfRowStatus    OBJECT-TYPE
            SYNTAX        RowStatus
            MAX-ACCESS    read-create
            STATUS        current
            DESCRIPTION        ""
            ::=  {  zxAnNniQosShapeConfEntry  10  }

------
      zxAnNniQosTrustTable    OBJECT-TYPE
            SYNTAX        SEQUENCE  OF  ZxAnNniQosTrustEntry
            MAX-ACCESS    not-accessible
            STATUS        current
            DESCRIPTION    ""
            ::=  { zxAnNniQosObjects  6 }

      zxAnNniQosTrustEntry    OBJECT-TYPE
            SYNTAX        ZxAnNniQosTrustEntry
            MAX-ACCESS    not-accessible
            STATUS        current
            DESCRIPTION    ""
            INDEX        {  ifIndex  }
            ::=  { zxAnNniQosTrustTable 1 }

      ZxAnNniQosTrustEntry  ::=  SEQUENCE
          {
            zxAnNniQosTrustDscp          INTEGER,
            zxAnNniQosTrustCos         INTEGER
          }

      zxAnNniQosTrustDscp    OBJECT-TYPE
            SYNTAX        INTEGER{
                    enable(1),
                    disable(2)
                  }
            MAX-ACCESS    read-create
            STATUS        current
            DESCRIPTION        ""
            ::=  {  zxAnNniQosTrustEntry  1  }

      zxAnNniQosTrustCos    OBJECT-TYPE
            SYNTAX        INTEGER{
                    enable(1),
                    disable(2)
                  }
            MAX-ACCESS    read-create
            STATUS        current
            DESCRIPTION        ""
            ::=  {  zxAnNniQosTrustEntry  2  }
--------------
      zxAnNniQosConformDscpTable    OBJECT-TYPE
            SYNTAX        SEQUENCE  OF  ZxAnNniQosConformDscpEntry
            MAX-ACCESS    not-accessible
            STATUS        current
            DESCRIPTION    ""
            ::=  { zxAnNniQosObjects  7 }

      zxAnNniQosConformDscpEntry    OBJECT-TYPE
            SYNTAX        ZxAnNniQosConformDscpEntry
            MAX-ACCESS    not-accessible
            STATUS        current
            DESCRIPTION    ""
            INDEX        {  zxAnNniQosConformDscpDscp  }
            ::=  { zxAnNniQosConformDscpTable 1 }

      ZxAnNniQosConformDscpEntry  ::=  SEQUENCE
          {
          zxAnNniQosConformDscpDscp  INTEGER,
            zxAnNniQosConformDscpNewDscp          INTEGER,
            zxAnNniQosConformDscpNewCos         INTEGER,
            zxAnNniQosConformDscpNewDp         INTEGER ,
            zxAnNniQosConformDscpRowStatus       RowStatus
          }

      zxAnNniQosConformDscpDscp    OBJECT-TYPE
            SYNTAX        INTEGER(0..63)
            MAX-ACCESS    not-accessible
            STATUS        current
            DESCRIPTION        ""
            ::=  {  zxAnNniQosConformDscpEntry  1  }

      zxAnNniQosConformDscpNewDscp    OBJECT-TYPE
            SYNTAX        INTEGER(0..63)
            MAX-ACCESS    read-create
            STATUS        current
            DESCRIPTION        ""
            ::=  {  zxAnNniQosConformDscpEntry  2  }

      zxAnNniQosConformDscpNewCos    OBJECT-TYPE
            SYNTAX        INTEGER(0..7)
            MAX-ACCESS    read-create
            STATUS        current
            DESCRIPTION        ""
            ::=  {  zxAnNniQosConformDscpEntry  3  }

      zxAnNniQosConformDscpNewDp    OBJECT-TYPE
            SYNTAX        INTEGER(0..2)
            MAX-ACCESS    read-create
            STATUS        current
            DESCRIPTION        ""
            ::=  {  zxAnNniQosConformDscpEntry  4  }

      zxAnNniQosConformDscpRowStatus    OBJECT-TYPE
            SYNTAX        RowStatus
            MAX-ACCESS    read-create
            STATUS        current
            DESCRIPTION        ""
            ::=  {  zxAnNniQosConformDscpEntry  10  }
------
    zxAnNniQosCos2Drop OBJECT-TYPE
        SYNTAX      OCTET STRING(SIZE (8))
        MAX-ACCESS  read-write
        STATUS      current
        DESCRIPTION
        ""
        ::= { zxAnNniQosGlobalObjects 8 }

     zxAnNniQosTrustMode  OBJECT-TYPE
        SYNTAX      INTEGER
        {
            untrust(1),
            trustcosonly(2),
            trustdscponly(3),
            notsupport(255)
        }
        MAX-ACCESS  read-write
        STATUS      current
        DESCRIPTION
            "Goobal Trust Mode."
        DEFVAL      { untrust }
        ::= { zxAnNniQosGlobalObjects 9 }

END
