ZTE-DSL-SSH-MIB DEFINITIONS ::= BEGIN
IMPORTS
    OBJECT-TYPE, MODULE-IDENTITY, enterprises    FROM SNMPv2-SMI;

zxDslSshMib   MODULE-IDENTITY
        LAST-UPDATED    "0706090000Z"
        ORGANIZATION    "Zhongxing Telcom Co. Ltd."
        CONTACT-INFO    "E-mail: suchunshan@zte.com.cn"
        DESCRIPTION     "SSH Control MIB definition."
        ::= { zxDsl 35 }


zte OBJECT IDENTIFIER ::= { enterprises 3902 }
zxDsl OBJECT IDENTIFIER ::= { zte 1004 }


zxDslSshglobal      OBJECT IDENTIFIER ::= { zxDslSshMib 1 }

zxDslSshGlobalState OBJECT-TYPE
    SYNTAX      INTEGER
    {
            enable(1),
            disable(2)
    }
    MAX-ACCESS  read-write
    STATUS      current
    DESCRIPTION
    "ssh global status"
    DEFVAL { disable }
    ::= { zxDslSshglobal 1 }

zxDslSshAuthMode OBJECT-TYPE
    SYNTAX      INTEGER
        {
            local(1),
            radius(2)
      }
    MAX-ACCESS  read-write
    STATUS      current
    DESCRIPTION
    "ssh authentication mode"
    DEFVAL { local }
    ::= { zxDslSshglobal 2 }

zxDslSshAuthType OBJECT-TYPE
    SYNTAX      INTEGER
        {
            pap(1),
            chap(2)
      }
    MAX-ACCESS  read-write
    STATUS      current
    DESCRIPTION
    "ssh authentication type"
    DEFVAL { chap }
    ::= { zxDslSshglobal 3 }

zxDslSshGenKey OBJECT-TYPE
    SYNTAX      INTEGER
        {
            value(1)
      }
    MAX-ACCESS  read-write
    STATUS      current
    DESCRIPTION
    "set value 1, then the switch gen a key for ssh"
    ::= { zxDslSshglobal 4 }

zxDslSshServOnly OBJECT-TYPE
    SYNTAX      INTEGER
        {
            enable(1),
            disable(2)
      }
    MAX-ACCESS  read-write
    STATUS      current
    DESCRIPTION
    "when ssy server only, then disable telnet access"
    DEFVAL { disable }
    ::= { zxDslSshglobal 5 }

zxDslSshVersion OBJECT-TYPE
    SYNTAX      INTEGER
        {
            sshv1(1),
            sshv2(2)
      }
    MAX-ACCESS  read-write
    STATUS      current
    DESCRIPTION
    "ssh version select"
    DEFVAL { sshv1 }
    ::= { zxDslSshglobal 6 }

END
