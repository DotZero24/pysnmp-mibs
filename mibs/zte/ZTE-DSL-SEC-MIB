-- File Name : ZTE-DSL-SEC-MIB.mib
-- Date      : Mon Oct 17 14:13:24 GMT+08:00 2005
-- Author    : ZTE Nms dept.

--
-- Zte Dsl SYS-CTRL Mib
--
--

ZTE-DSL-SEC-MIB	DEFINITIONS ::= BEGIN
	IMPORTS
	        zxDsl
			FROM ZTE-DSL-MIB
		RowStatus, DisplayString
			FROM SNMPv2-TC
		DisplayString, ifIndex
			FROM RFC1213-MIB
		MODULE-IDENTITY, OBJECT-TYPE, NOTIFICATION-TYPE, IpAddress, TimeTicks, Counter32, Gauge32, Integer32, Unsigned32
			FROM SNMPv2-SMI
		SnmpAdminString
			FROM SNMP-FRAMEWORK-MIB;

	zxDslSysSecMib	MODULE-IDENTITY
		LAST-UPDATED	"200404151500Z"
		ORGANIZATION	"ZTE Corporation"
		CONTACT-INFO	"ma ke
                  Mail: zte@zte.com.cn
                  Tel : 021-68896477"
		DESCRIPTION		"This MIB defines zte dsl managed objects."
		::=  {  zxDsl  36  }


    zxDslSysSecObjects     OBJECT IDENTIFIER ::= {zxDslSysSecMib 1}
    zxDslSysSecTrapObjects OBJECT IDENTIFIER ::= {zxDslSysSecMib 2}


    zxDslCrftTerminalEnable OBJECT-TYPE
       SYNTAX             INTEGER
          {
              enable  ( 1 ),
              disable ( 2 )
          }
       MAX-ACCESS       read-write
       STATUS           current
       DESCRIPTION      "Enable/disable craft terminal interface."
       DEFVAL { enable }
       ::=  {  zxDslSysSecObjects  1  }



    zxDslCliSecurityLevel OBJECT-TYPE
       SYNTAX             INTEGER
          {
              guest  (1), -- read only and ordinary informatin only
              administrator (2) -- read and write advanced informatin
          }
       MAX-ACCESS       read-write
       STATUS           current
       DESCRIPTION      "Security level of CLI."
       DEFVAL { administrator }
       ::=  {  zxDslSysSecObjects  2  }



    zxDslCrftTerminalLogonStatus OBJECT-TYPE
       SYNTAX             INTEGER
          {
              logon  ( 1 ),
              logout ( 2 )
          }
       MAX-ACCESS       read-only
       STATUS           current
       DESCRIPTION      "The using status of craft terminal interface."
       ::=  {  zxDslSysSecObjects  3  }



    zxDslSysLatestLogonCrftTerminalType OBJECT-TYPE
       SYNTAX             INTEGER
          {
              rs232SerialInterface( 1 ),
              outbandMgmtInterface( 2 )
          }
       MAX-ACCESS       read-only
       STATUS           current
       DESCRIPTION      "The type of the craft terminal interface lastest logon."
       ::=  {  zxDslSysSecObjects  4  }


    zxDslCliLogonWelcomeMessage OBJECT-TYPE
       SYNTAX      DisplayString (SIZE(1..400))
       MAX-ACCESS       read-write
       STATUS           current
       DESCRIPTION      "The welcome message of the terminal interface logon."
       ::=  {  zxDslSysSecObjects  5  }


    zxDslCliLogonOvertimeMin OBJECT-TYPE
       SYNTAX      Integer32 (1..60)
       MAX-ACCESS       read-write
       STATUS           current
       DESCRIPTION      "The overtime in minutes of the terminal interface logon."
       ::=  {  zxDslSysSecObjects  6  }

    zxDslIllegalLoginUserName   OBJECT-TYPE
        SYNTAX          DisplayString  ( SIZE ( 0 .. 15  ) )
        MAX-ACCESS      read-only
        STATUS          current
        DESCRIPTION     "User name of illegal login attemp."
        ::=  {  zxDslSysSecObjects  7 }

    zxDslIllegalLoginType   OBJECT-TYPE
        SYNTAX             INTEGER
          {
              console(1),
              telnet(2),
              ssh(3)
          }
        MAX-ACCESS      read-only
        STATUS          current
        DESCRIPTION     "The type of illegal login attemp."
        ::=  {  zxDslSysSecObjects  8  }

    zxDslIllegalLoginIP   OBJECT-TYPE
        SYNTAX             IpAddress
        MAX-ACCESS      read-only
        STATUS          current
        DESCRIPTION     "The IP address of illegal login attemp."
        ::=  {  zxDslSysSecObjects  9  }

    zxDslCrftTerminLogonTrap      NOTIFICATION-TYPE
        OBJECTS { zxDslSysLatestLogonCrftTerminalType  }
            STATUS  current
            DESCRIPTION
                " User has logon equipment through the craft terminal interface."
            ::= { zxDslSysSecTrapObjects 1 }


    zxDslCrftTerminLogoutTrap      NOTIFICATION-TYPE
        OBJECTS { zxDslSysLatestLogonCrftTerminalType  }
            STATUS  current
            DESCRIPTION
                " User has logout equipment from the craft terminal interface."
            ::= { zxDslSysSecTrapObjects 2 }

    zxDslIllegalLoginTrap      NOTIFICATION-TYPE
        OBJECTS { zxDslIllegalLoginUserName, zxDslIllegalLoginType,zxDslIllegalLoginIP }
            STATUS  current
            DESCRIPTION
                "This alarm indicates that an illegal login attemp happend."
            ::= { zxDslSysSecTrapObjects 3 }

END
