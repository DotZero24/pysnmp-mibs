ZXR10-X25-II-MIB DEFINITIONS ::= BEGIN

   IMPORTS
       MODULE-IDENTITY, OBJECT-TYPE, Counter32, Gauge32,
       Integer32, TimeTicks, Counter64,
       NOTIFICATION-TYPE,
       enterprises,Unsigned32          FROM SNMPv2-SMI

       RowStatus
                                        FROM SNMPv2-TC
       mgmt, NetworkAddress, IpAddress, Counter, Gauge
                         FROM RFC1155-SMI
      --         Counter, TimeTicks     FROM RFC1155-SMI
      -- IpAddress,DisplayString, mib-2   FROM RFC1213-MIB
      --            OBJECT-TYPE            FROM RFC-1212
                  TRAP-TYPE              FROM RFC-1215;

   zte OBJECT IDENTIFIER ::= { enterprises 3902 }
   zxr10 OBJECT IDENTIFIER ::= { zte 3}

   zxr10X25MIBII OBJECT IDENTIFIER ::= { zxr10 4001}

   DisplayString ::= OCTET STRING

   UShort	::=  TEXTUAL-CONVENTION
	STATUS		current
	DESCRIPTION
		"The 16-bit unsigned short integer."
	SYNTAX		INTEGER (0..65535)

UChar	::= TEXTUAL-CONVENTION
	STATUS		current
	DESCRIPTION
		"The 8-bit unsigned integer."
	SYNTAX	INTEGER (0..255)

UCHAR	::= TEXTUAL-CONVENTION
	STATUS		current
	DESCRIPTION
		"The 8-bit unsigned integer."
	SYNTAX	INTEGER (0..255)

X25Address	::= TEXTUAL-CONVENTION
	STATUS		current
	DESCRIPTION
		"The X.25 Address."
	SYNTAX	OCTET STRING(SIZE(8))

zxr10X25II				OBJECT IDENTIFIER	::= { zxr10X25MIBII 1}




-- struct_x25_pvc_config_table

zxr10X25PVCTable	OBJECT-TYPE
	SYNTAX		SEQUENCE OF Zxr10X25PVCEntry
	MAX-ACCESS	not-accessible
	STATUS		current
	DESCRIPTION
		"A list of Definition of PVC-Table entries."
	::= { zxr10X25II 4}

zxr10X25PVCEntry	OBJECT-TYPE
	SYNTAX		Zxr10X25PVCEntry
	MAX-ACCESS	not-accessible
	STATUS		current
	DESCRIPTION
		"An entry in the table."
	INDEX {
		zxr10X25PVCNo

		}
	::= { zxr10X25PVCTable 1}

Zxr10X25PVCEntry ::=
	SEQUENCE {
		zxr10X25PVCRowStatus				RowStatus,
		zxr10X25PVCNo						UShort,
        zxr10X25PVCStartLcn                 UShort,
        zxr10X25PVCNextLcn                  UShort,
        zxr10X25PVCStartPortName            DisplayString,
        zxr10X25PVCNextPortName             DisplayString,
        zxr10X25PVCStartPortIfIndex         Unsigned32,
        zxr10X25PVCNextPortIfIndex          Unsigned32

	}

zxr10X25PVCRowStatus	OBJECT-TYPE
	SYNTAX		RowStatus
	MAX-ACCESS	read-create
	STATUS		current
	DESCRIPTION
		"."
	::= { zxr10X25PVCEntry 1}

zxr10X25PVCNo	OBJECT-TYPE
	SYNTAX		UShort
	MAX-ACCESS	read-only
	STATUS		current
	DESCRIPTION
		" PVC index number (1-255)"
	::= { zxr10X25PVCEntry 2}

zxr10X25PVCStartLcn	OBJECT-TYPE
	SYNTAX		UShort
	MAX-ACCESS	read-create
	STATUS		current
	DESCRIPTION
		"in interface lcn(1-255)"
	::= { zxr10X25PVCEntry 3}

zxr10X25PVCNextLcn	OBJECT-TYPE
	SYNTAX		UShort
	MAX-ACCESS	read-create
	STATUS		current
	DESCRIPTION
		"out interface lcn(1-255)"
	::= { zxr10X25PVCEntry 4}

zxr10X25PVCStartPortName	OBJECT-TYPE
	SYNTAX		DisplayString(SIZE(0..32))
	MAX-ACCESS	read-only
	STATUS		current
	DESCRIPTION
		"in interface name"
	::= { zxr10X25PVCEntry 5}

zxr10X25PVCNextPortName	OBJECT-TYPE
	SYNTAX		DisplayString(SIZE(0..32))
	MAX-ACCESS	read-only
	STATUS		current
	DESCRIPTION
		"out interface name"
	::= { zxr10X25PVCEntry 6}

zxr10X25PVCStartPortIfIndex	OBJECT-TYPE
	SYNTAX		Unsigned32
	MAX-ACCESS	read-create
	STATUS		current
	DESCRIPTION
		"in index number"
	::= { zxr10X25PVCEntry 7}

zxr10X25PVCNextPortIfIndex	OBJECT-TYPE
	SYNTAX		Unsigned32
	MAX-ACCESS	read-create
	STATUS		current
	DESCRIPTION
		"out index number"
	::= { zxr10X25PVCEntry 8}


zxr10X25OperTable	OBJECT-TYPE
	SYNTAX		SEQUENCE OF Zxr10X25OperEntry
	MAX-ACCESS	not-accessible
	STATUS		current
	DESCRIPTION
		"A list of Definition of Oper-Table entries."
	::= { zxr10X25II 6}

zxr10X25OperEntry	OBJECT-TYPE
	SYNTAX		Zxr10X25OperEntry
	MAX-ACCESS	not-accessible
	STATUS		current
	DESCRIPTION
		"An entry in the table."
	INDEX { zxr10X25OperIfIndex }
	::= { zxr10X25OperTable 1}

Zxr10X25OperEntry ::=
	SEQUENCE {
		zxr10X25OperStatus				    INTEGER,
		zxr10X25OperIfIndex					Unsigned32,
		zxr10X25OperLapbMode				UCHAR,
		zxr10X25OperLapbPSSize			    UShort,
		zxr10X25OperLapbWinSize			    UShort,
		zxr10X25OperLapbRetranCount 	    UShort,
		zxr10X25OperLapbTimeoutT1  			UShort,
		zxr10X25OperLapbTimeoutT2  			UShort,
		zxr10X25OperLapbTimeoutT3  			UShort,
		zxr10X25OperLapbPktMaxVC       		UShort,
		zxr10X25OperLapbPktT20          	UShort,
		zxr10X25OperLapbPktT21          	UShort,
		zxr10X25OperLapbPktT22          	UShort,
		zxr10X25OperLapbPktT23          	UShort,
		zxr10X25OperLapbPktWinSize  		UShort,
	    zxr10X25OperLapbPktPSize    		UShort,
        zxr10X25OperLapbPktSvcIdleTime	    UShort,
		zxr10X25OperLapbDteDce 			    UCHAR,
		zxr10X25OperLapbUserOrTrunk 	    UCHAR,
	    zxr10X25OperIfName					DisplayString,
	    zxr10X25OperLabpStatus              UCHAR,
	    zxr10X25OperInterfaceType           UCHAR
	}

zxr10X25OperStatus	OBJECT-TYPE
	SYNTAX		INTEGER{active(1),modify(4),resetDefault(6),encapFrx25(7),encapX25(8),noencap(9),enable(10),noenable(11)}
	MAX-ACCESS	read-create
	STATUS		current
	DESCRIPTION
		"."
	::= { zxr10X25OperEntry 1}

zxr10X25OperIfIndex	OBJECT-TYPE
	SYNTAX		Unsigned32
	MAX-ACCESS	read-only
	STATUS		current
	DESCRIPTION
		"interface index number"
	::= { zxr10X25OperEntry 2}



zxr10X25OperLapbMode	OBJECT-TYPE
	SYNTAX		UCHAR
	MAX-ACCESS	read-create
	STATUS		current
	DESCRIPTION
		"configure LAPB moudle｛8 | 128},8 or 128"
	::= { zxr10X25OperEntry 3}



zxr10X25OperLapbPSSize	OBJECT-TYPE
	SYNTAX		UShort
	MAX-ACCESS	read-create
	STATUS		current
	DESCRIPTION
		"configure lapb packet size:136\264\520\1032.default:1032"
	::= { zxr10X25OperEntry 4}

zxr10X25OperLapbWinSize	OBJECT-TYPE
	SYNTAX		UShort
	MAX-ACCESS	read-create
	STATUS		current
	DESCRIPTION
		"configure lapb window size:0~999.default:7"
	::= { zxr10X25OperEntry 5}

zxr10X25OperLapbRetranCount	OBJECT-TYPE
	SYNTAX		UShort
	MAX-ACCESS	read-create
	STATUS		current
	DESCRIPTION
		" configure  lapb retransfer count:0~999.default:3"
	::= { zxr10X25OperEntry 6}

zxr10X25OperLapbTimeoutT1	OBJECT-TYPE
	SYNTAX		UShort
	MAX-ACCESS	read-create
	STATUS		current
	DESCRIPTION
		" configure send timer T1:0~999.default:15"
	::= { zxr10X25OperEntry 7}

zxr10X25OperLapbTimeoutT2	OBJECT-TYPE
	SYNTAX		UShort
	MAX-ACCESS	read-create
	STATUS		current
	DESCRIPTION
		"configure receive timer T2:0~999.default:9"
	::= { zxr10X25OperEntry 8}

zxr10X25OperLapbTimeoutT3	OBJECT-TYPE
	SYNTAX		UShort
	MAX-ACCESS	read-create
	STATUS		current
	DESCRIPTION
		"configue channel spare T3:0~999.default:20"
	::= { zxr10X25OperEntry 9}

zxr10X25OperLapbPktMaxVC	OBJECT-TYPE
	SYNTAX		UShort
	MAX-ACCESS	read-create
	STATUS		current
	DESCRIPTION
		"configure max virtual connect:0~999.default:200"
	::= { zxr10X25OperEntry 10}

zxr10X25OperLapbPktT20	OBJECT-TYPE
	SYNTAX		UShort
	MAX-ACCESS	read-create
	STATUS		current
	DESCRIPTION
		"configure restart timer(T20):0~999.default:5"
	::= { zxr10X25OperEntry 11}

zxr10X25OperLapbPktT21	OBJECT-TYPE
	SYNTAX		UShort
	MAX-ACCESS	read-create
	STATUS		current
	DESCRIPTION
		" configure call timer (T21):0~999.default:60"
	::= { zxr10X25OperEntry 12}

zxr10X25OperLapbPktT22	OBJECT-TYPE
	SYNTAX		UShort
	MAX-ACCESS	read-create
	STATUS		current
	DESCRIPTION
		" configure reset timer (T22):0~999.default:60"
	::= { zxr10X25OperEntry 13}

zxr10X25OperLapbPktT23	OBJECT-TYPE
	SYNTAX		UShort
	MAX-ACCESS	read-create
	STATUS		current
	DESCRIPTION
		"configure registration timer(T23):0~999.default:60"
	::= { zxr10X25OperEntry 14}

zxr10X25OperLapbPktWinSize	OBJECT-TYPE
	SYNTAX		UShort
	MAX-ACCESS	read-create
	STATUS		current
	DESCRIPTION
		"configure packet window Size:0~999.default:7"
	::= { zxr10X25OperEntry 15}

zxr10X25OperLapbPktPSize	OBJECT-TYPE
	SYNTAX		UShort
	MAX-ACCESS	read-create
	STATUS		current
	DESCRIPTION
		"configure packet length:128\256\512\1024.default:1024"
	::= { zxr10X25OperEntry 16}

zxr10X25OperLapbPktSvcIdleTime	OBJECT-TYPE
	SYNTAX		UShort
	MAX-ACCESS	read-create
	STATUS		current
	DESCRIPTION
		" configure SVC spare timer:0~999.default:7"
	::= { zxr10X25OperEntry 17}

zxr10X25OperLapbDteDce	OBJECT-TYPE
	SYNTAX		UCHAR
	MAX-ACCESS	read-create
	STATUS		current
	DESCRIPTION
		" configure lapb mode(dte/dce) 0:DTE;1:DCE"
	::= { zxr10X25OperEntry 18}

zxr10X25OperLapbUserOrTrunk	OBJECT-TYPE
	SYNTAX		UCHAR
	MAX-ACCESS	read-create
	STATUS		current
	DESCRIPTION
		" configure Interface as user or trunk 0:user;1:trunk"
	::= { zxr10X25OperEntry 19}


zxr10X25OperIfName	OBJECT-TYPE
	SYNTAX		DisplayString(SIZE(0..32))
	MAX-ACCESS	read-only
	STATUS		current
	DESCRIPTION
		"interface name"
	::= { zxr10X25OperEntry 20}

zxr10X25OperLabpStatus	OBJECT-TYPE
	SYNTAX		UCHAR
	MAX-ACCESS	read-only
	STATUS		current
	DESCRIPTION
		"lapb status"
	::= { zxr10X25OperEntry 21}

zxr10X25OperInterfaceType	OBJECT-TYPE
	SYNTAX		UCHAR
	MAX-ACCESS	read-only
	STATUS		current
	DESCRIPTION
		"interface encapsulation type,0:x.25;1:x.25 over frame;2:frame"
	::= { zxr10X25OperEntry 22}

---SVC Table

zxr10X25SVCTable	OBJECT-TYPE
	SYNTAX		SEQUENCE OF Zxr10X25SVCEntry
	MAX-ACCESS	not-accessible
	STATUS		current
	DESCRIPTION
		"A list of Definition of SVC-Table entries."
	::= { zxr10X25II 7}

zxr10X25SVCEntry	OBJECT-TYPE
	SYNTAX		Zxr10X25SVCEntry
	MAX-ACCESS	not-accessible
	STATUS		current
	DESCRIPTION
		"An entry in the table."
	INDEX {
		zxr10X25SVCNo

		}
	::= { zxr10X25SVCTable 1}

Zxr10X25SVCEntry ::=
	SEQUENCE {
		zxr10X25SVCNo						UShort,
        zxr10X25SVCStartLcn                 UShort,
        zxr10X25SVCNextLcn                  UShort,
        zxr10X25SVCStartPortName            DisplayString,
        zxr10X25SVCNextPortName             DisplayString,
        zxr10X25SVCStartPortIfIndex         Unsigned32,
        zxr10X25SVCNextPortIfIndex          Unsigned32

	}



zxr10X25SVCNo	OBJECT-TYPE
	SYNTAX		UShort
	MAX-ACCESS	read-only
	STATUS		current
	DESCRIPTION
		" SVC index number (1-1024)"
	::= { zxr10X25SVCEntry 1}

zxr10X25SVCStartLcn	OBJECT-TYPE
	SYNTAX		UShort
	MAX-ACCESS	read-only
	STATUS		current
	DESCRIPTION
		"in interface lcn(1-255)"
	::= { zxr10X25SVCEntry 2}

zxr10X25SVCNextLcn	OBJECT-TYPE
	SYNTAX		UShort
	MAX-ACCESS	read-only
	STATUS		current
	DESCRIPTION
		"out interface lcn(1-255)"
	::= { zxr10X25SVCEntry 3}

zxr10X25SVCStartPortName	OBJECT-TYPE
	SYNTAX		DisplayString(SIZE(0..32))
	MAX-ACCESS	read-only
	STATUS		current
	DESCRIPTION
		"in interface name"
	::= { zxr10X25SVCEntry 4}

zxr10X25SVCNextPortName	OBJECT-TYPE
	SYNTAX		DisplayString(SIZE(0..32))
	MAX-ACCESS	read-only
	STATUS		current
	DESCRIPTION
		"out interface name"
	::= { zxr10X25SVCEntry 5}

zxr10X25SVCStartPortIfIndex	OBJECT-TYPE
	SYNTAX		Unsigned32
	MAX-ACCESS	read-only
	STATUS		current
	DESCRIPTION
		"in index number"
	::= { zxr10X25SVCEntry 6}

zxr10X25SVCNextPortIfIndex	OBJECT-TYPE
	SYNTAX		Unsigned32
	MAX-ACCESS	read-only
	STATUS		current
	DESCRIPTION
		"out index number"
	::= { zxr10X25SVCEntry 7}

--Statistcs
zxr10X25LapbFlowTable	OBJECT-TYPE
	SYNTAX		SEQUENCE OF Zxr10X25LapbFlowEntry
	MAX-ACCESS	not-accessible
	STATUS		current
	DESCRIPTION
		"A list of Definition of Table entries."
	::= { zxr10X25II 8}

zxr10X25LapbFlowEntry	OBJECT-TYPE
	SYNTAX		Zxr10X25LapbFlowEntry
	MAX-ACCESS	not-accessible
	STATUS		current
	DESCRIPTION
		"An entry in the table."
	INDEX   {
		        zxr10X25LapbStatIfIndex
    		}
	::= { zxr10X25LapbFlowTable 1}

Zxr10X25LapbFlowEntry ::=
	SEQUENCE {
        zxr10X25LapbFlowBusyDefers       Unsigned32,
        zxr10X25LapbFlowRejOutPkts       Unsigned32,
        zxr10X25LapbFlowRejInPkts        Unsigned32,
        zxr10X25LapbFlowT1Timeouts       Unsigned32,
        zxr10X25LapbFlowRROutPkts        Unsigned32,
        zxr10X25LapbFlowRRInPkts         Unsigned32,
        zxr10X25LapbFlowRNROutPkts       Unsigned32,
        zxr10X25LapbFlowRNRInPkts        Unsigned32,
        zxr10X25LapbFlowIOutPkts         Unsigned32,
        zxr10X25LapbFlowIInPkts          Unsigned32,
        zxr10X25LapbFlowDMOutPkts        Unsigned32,
        zxr10X25LapbFlowDMInPkts         Unsigned32,
        zxr10X25LapbFlowSABOutPkts       Unsigned32,
        zxr10X25LapbFlowSABInPkts        Unsigned32,
        zxr10X25LapbFlowUAOutPkts        Unsigned32,
        zxr10X25LapbFlowUAInPkts         Unsigned32,
        zxr10X25LapbFlowDISCOutPkts      Unsigned32,
        zxr10X25LapbFlowDISCInPkts       Unsigned32,
        zxr10X25LapbFlowFRMROutPkts      Unsigned32,
        zxr10X25LapbFlowFRMRInPkts       Unsigned32,
        zxr10X25LapbFlowOutPkts          Unsigned32,
        zxr10X25LapbFlowInPkts           Unsigned32,
        zxr10X25LapbFlowStateChanges     Unsigned32,
        zxr10X25LapbStatIfIndex          Unsigned32
	}

zxr10X25LapbFlowBusyDefers	OBJECT-TYPE
	SYNTAX		Unsigned32
	MAX-ACCESS	read-create
	STATUS		current
	DESCRIPTION
		""
	::= { zxr10X25LapbFlowEntry 1}

zxr10X25LapbFlowRejOutPkts	OBJECT-TYPE
	SYNTAX		Unsigned32
	MAX-ACCESS	read-create
	STATUS		current
	DESCRIPTION
		""
	::= { zxr10X25LapbFlowEntry 2}

zxr10X25LapbFlowRejInPkts	OBJECT-TYPE
	SYNTAX		Unsigned32
	MAX-ACCESS	read-create
	STATUS		current
	DESCRIPTION
		""
	::= { zxr10X25LapbFlowEntry 3}

zxr10X25LapbFlowT1Timeouts	OBJECT-TYPE
	SYNTAX		Unsigned32
	MAX-ACCESS	read-create
	STATUS		current
	DESCRIPTION
		""
	::= { zxr10X25LapbFlowEntry 4}

zxr10X25LapbFlowRROutPkts	OBJECT-TYPE
	SYNTAX		Unsigned32
	MAX-ACCESS	read-create
	STATUS		current
	DESCRIPTION
		""
	::= { zxr10X25LapbFlowEntry 5}

zxr10X25LapbFlowRRInPkts	OBJECT-TYPE
	SYNTAX		Unsigned32
	MAX-ACCESS	read-create
	STATUS		current
	DESCRIPTION
		""
	::= { zxr10X25LapbFlowEntry 6}

zxr10X25LapbFlowRNROutPkts	OBJECT-TYPE
	SYNTAX		Unsigned32
	MAX-ACCESS	read-create
	STATUS		current
	DESCRIPTION
		""
	::= { zxr10X25LapbFlowEntry 7}

zxr10X25LapbFlowRNRInPkts	OBJECT-TYPE
	SYNTAX		Unsigned32
	MAX-ACCESS	read-create
	STATUS		current
	DESCRIPTION
		""
	::= { zxr10X25LapbFlowEntry 8}

zxr10X25LapbFlowIOutPkts	OBJECT-TYPE
	SYNTAX		Unsigned32
	MAX-ACCESS	read-create
	STATUS		current
	DESCRIPTION
		""
	::= { zxr10X25LapbFlowEntry 9}

zxr10X25LapbFlowIInPkts	OBJECT-TYPE
	SYNTAX		Unsigned32
	MAX-ACCESS	read-create
	STATUS		current
	DESCRIPTION
		""
	::= { zxr10X25LapbFlowEntry 10}

zxr10X25LapbFlowDMOutPkts	OBJECT-TYPE
	SYNTAX		Unsigned32
	MAX-ACCESS	read-create
	STATUS		current
	DESCRIPTION
		""
	::= { zxr10X25LapbFlowEntry 11}

zxr10X25LapbFlowDMInPkts	OBJECT-TYPE
	SYNTAX		Unsigned32
	MAX-ACCESS	read-create
	STATUS		current
	DESCRIPTION
		""
	::= { zxr10X25LapbFlowEntry 12}

zxr10X25LapbFlowSABOutPkts	OBJECT-TYPE
	SYNTAX		Unsigned32
	MAX-ACCESS	read-create
	STATUS		current
	DESCRIPTION
		""
	::= { zxr10X25LapbFlowEntry 13}

zxr10X25LapbFlowSABInPkts	OBJECT-TYPE
	SYNTAX		Unsigned32
	MAX-ACCESS	read-create
	STATUS		current
	DESCRIPTION
		""
	::= { zxr10X25LapbFlowEntry 14}

zxr10X25LapbFlowUAOutPkts	OBJECT-TYPE
	SYNTAX		Unsigned32
	MAX-ACCESS	read-create
	STATUS		current
	DESCRIPTION
		""
	::= { zxr10X25LapbFlowEntry 15}

zxr10X25LapbFlowUAInPkts	OBJECT-TYPE
	SYNTAX		Unsigned32
	MAX-ACCESS	read-create
	STATUS		current
	DESCRIPTION
		""
	::= { zxr10X25LapbFlowEntry 16}

zxr10X25LapbFlowDISCOutPkts	OBJECT-TYPE
	SYNTAX		Unsigned32
	MAX-ACCESS	read-create
	STATUS		current
	DESCRIPTION
		""
	::= { zxr10X25LapbFlowEntry 17}

zxr10X25LapbFlowDISCInPkts	OBJECT-TYPE
	SYNTAX		Unsigned32
	MAX-ACCESS	read-create
	STATUS		current
	DESCRIPTION
		""
	::= { zxr10X25LapbFlowEntry 18}

zxr10X25LapbFlowFRMROutPkts	OBJECT-TYPE
	SYNTAX		Unsigned32
	MAX-ACCESS	read-create
	STATUS		current
	DESCRIPTION
		""
	::= { zxr10X25LapbFlowEntry 19}

zxr10X25LapbFlowFRMRInPkts	OBJECT-TYPE
	SYNTAX		Unsigned32
	MAX-ACCESS	read-create
	STATUS		current
	DESCRIPTION
		""
	::= { zxr10X25LapbFlowEntry 20}

zxr10X25LapbFlowOutPkts	OBJECT-TYPE
	SYNTAX		Unsigned32
	MAX-ACCESS	read-create
	STATUS		current
	DESCRIPTION
		""
	::= { zxr10X25LapbFlowEntry 21}

zxr10X25LapbFlowInPkts	OBJECT-TYPE
	SYNTAX		Unsigned32
	MAX-ACCESS	read-create
	STATUS		current
	DESCRIPTION
		""
	::= { zxr10X25LapbFlowEntry 22}

zxr10X25LapbFlowStateChanges	OBJECT-TYPE
	SYNTAX		Unsigned32
	MAX-ACCESS	read-create
	STATUS		current
	DESCRIPTION
		""
	::= { zxr10X25LapbFlowEntry 23}

zxr10X25LapbStatIfIndex	OBJECT-TYPE
	SYNTAX		Unsigned32
	MAX-ACCESS	read-create
	STATUS		current
	DESCRIPTION
		""
	::= { zxr10X25LapbFlowEntry 24}

-- X.25 statistics table

zxr10X25StatTable	OBJECT-TYPE
	SYNTAX		SEQUENCE OF Zxr10X25StatEntry
	MAX-ACCESS	not-accessible
	STATUS		current
	DESCRIPTION
		"A list of Definition of Table entries."
	::= { zxr10X25II 9}

zxr10X25StatEntry	OBJECT-TYPE
	SYNTAX		Zxr10X25StatEntry
	MAX-ACCESS	not-accessible
	STATUS		current
	DESCRIPTION
		"An entry in the table."
	INDEX   {
		        zxr10X25StatLapbIndex
    		}
	::= { zxr10X25StatTable 1}

Zxr10X25StatEntry ::=
	SEQUENCE {

        zxr10X25StatLapbIndex                             Unsigned32,
        zxr10StatRecvX25CALLREQUESTCnt                    Unsigned32,
        zxr10StatRecvX25CALLACCEPTEDCnt                   Unsigned32,
        zxr10StatRecvX25CLEARREQUESTCnt                   Unsigned32,
        zxr10StatRecvX25CLEARCONFIRMATIONCnt              Unsigned32,
        zxr10StatRecvX25DATACnt                           Unsigned32,
        zxr10StatRecvX25INTERRUPTCnt                      Unsigned32,
        zxr10StatRecvX25INTERRUPTCONFIRMATIONCnt          Unsigned32,
        zxr10StatRecvX25RRCnt                             Unsigned32,
        zxr10StatRecvX25RNRCnt                            Unsigned32,
        zxr10StatRecvX25REJCnt                            Unsigned32,
        zxr10StatRecvX25RESETREQUESTCnt                   Unsigned32,
        zxr10StatRecvX25RESETCONFIRMATIONCnt              Unsigned32,
        zxr10StatRecvX25REGISTRATIONREQUESTCnt            Unsigned32,
        zxr10StatRecvX25REGISTRATIONCONFIRMATIONCnt       Unsigned32,
        zxr10StatRecvX25RESTARTREQUESTCnt                 Unsigned32,
        zxr10StatRecvX25RESTARTCONFIRMATIONCnt            Unsigned32,
        zxr10StatRecvX25DIAGNOSTICCnt                     Unsigned32,
        zxr10StatRecvX25ILLEGALCnt                        Unsigned32,
        zxr10StatRecvX25TotalDataSize                     Unsigned32,
        zxr10StatSendX25CALLREQUESTCnt                    Unsigned32,
        zxr10StatSendX25CALLACCEPTEDCnt                   Unsigned32,
        zxr10StatSendX25CLEARREQUESTCnt                   Unsigned32,
        zxr10StatSendX25CLEARCONFIRMATIONCnt              Unsigned32,
        zxr10StatSendX25DATACnt                           Unsigned32,
        zxr10StatSendX25INTERRUPTCnt                      Unsigned32,
        zxr10StatSendX25INTERRUPTCONFIRMATIONCnt          Unsigned32,
        zxr10StatSendX25RRCnt                             Unsigned32,
        zxr10StatSendX25RNRCnt                            Unsigned32,
        zxr10StatSendX25REJCnt                            Unsigned32,
        zxr10StatSendX25RESETREQUESTCnt                   Unsigned32,
        zxr10StatSendX25RESETCONFIRMATIONCnt              Unsigned32,
        zxr10StatSendX25REGISTRATIONREQUESTCnt            Unsigned32,
        zxr10StatSendX25REGISTRATIONCONFIRMATIONCnt       Unsigned32,
        zxr10StatSendX25RESTARTREQUESTCnt                 Unsigned32,
        zxr10StatSendX25RESTARTCONFIRMATIONCnt            Unsigned32,
        zxr10StatSendX25DIAGNOSTICCnt                     Unsigned32,
        zxr10StatSendX25ILLEGALCnt                        Unsigned32,
        zxr10StatSendX25TotalDataSize                     Unsigned32

	}

zxr10X25StatLapbIndex	OBJECT-TYPE
	SYNTAX		Unsigned32
	MAX-ACCESS	read-only
	STATUS		current
	DESCRIPTION
		""
	::= { zxr10X25StatEntry 1}

zxr10StatRecvX25CALLREQUESTCnt	OBJECT-TYPE
	SYNTAX		Unsigned32
	MAX-ACCESS	read-only
	STATUS		current
	DESCRIPTION
		""
	::= { zxr10X25StatEntry 2}

zxr10StatRecvX25CALLACCEPTEDCnt	OBJECT-TYPE
	SYNTAX		Unsigned32
	MAX-ACCESS	read-only
	STATUS		current
	DESCRIPTION
		""
	::= { zxr10X25StatEntry 3}

zxr10StatRecvX25CLEARREQUESTCnt	OBJECT-TYPE
	SYNTAX		Unsigned32
	MAX-ACCESS	read-only
	STATUS		current
	DESCRIPTION
		""
	::= { zxr10X25StatEntry 4}

zxr10StatRecvX25CLEARCONFIRMATIONCnt	OBJECT-TYPE
	SYNTAX		Unsigned32
	MAX-ACCESS	read-only
	STATUS		current
	DESCRIPTION
		""
	::= { zxr10X25StatEntry 5}

zxr10StatRecvX25DATACnt	OBJECT-TYPE
	SYNTAX		Unsigned32
	MAX-ACCESS	read-only
	STATUS		current
	DESCRIPTION
		""
	::= { zxr10X25StatEntry 6}

zxr10StatRecvX25INTERRUPTCnt	OBJECT-TYPE
	SYNTAX		Unsigned32
	MAX-ACCESS	read-only
	STATUS		current
	DESCRIPTION
		""
	::= { zxr10X25StatEntry 7}

zxr10StatRecvX25INTERRUPTCONFIRMATIONCnt	OBJECT-TYPE
	SYNTAX		Unsigned32
	MAX-ACCESS	read-only
	STATUS		current
	DESCRIPTION
		""
	::= { zxr10X25StatEntry 8}


zxr10StatRecvX25RRCnt	OBJECT-TYPE
	SYNTAX		Unsigned32
	MAX-ACCESS	read-only
	STATUS		current
	DESCRIPTION
		""
	::= { zxr10X25StatEntry 9}

zxr10StatRecvX25RNRCnt	OBJECT-TYPE
	SYNTAX		Unsigned32
	MAX-ACCESS	read-only
	STATUS		current
	DESCRIPTION
		""
	::= { zxr10X25StatEntry 10}

zxr10StatRecvX25REJCnt	OBJECT-TYPE
	SYNTAX		Unsigned32
	MAX-ACCESS	read-only
	STATUS		current
	DESCRIPTION
		""
	::= { zxr10X25StatEntry 11}

zxr10StatRecvX25RESETREQUESTCnt	OBJECT-TYPE
	SYNTAX		Unsigned32
	MAX-ACCESS	read-only
	STATUS		current
	DESCRIPTION
		""
	::= { zxr10X25StatEntry 12}

zxr10StatRecvX25RESETCONFIRMATIONCnt    OBJECT-TYPE
	SYNTAX		Unsigned32
	MAX-ACCESS	read-only
	STATUS		current
	DESCRIPTION
		""
	::= { zxr10X25StatEntry 13}

zxr10StatRecvX25REGISTRATIONREQUESTCnt  OBJECT-TYPE
	SYNTAX		Unsigned32
	MAX-ACCESS	read-only
	STATUS		current
	DESCRIPTION
		""
	::= { zxr10X25StatEntry 14}

zxr10StatRecvX25REGISTRATIONCONFIRMATIONCnt  OBJECT-TYPE
	SYNTAX		Unsigned32
	MAX-ACCESS	read-only
	STATUS		current
	DESCRIPTION
		""
	::= { zxr10X25StatEntry 15}

zxr10StatRecvX25RESTARTREQUESTCnt           OBJECT-TYPE
	SYNTAX		Unsigned32
	MAX-ACCESS	read-only
	STATUS		current
	DESCRIPTION
		""
	::= { zxr10X25StatEntry 16}

zxr10StatRecvX25RESTARTCONFIRMATIONCnt      OBJECT-TYPE
	SYNTAX		Unsigned32
	MAX-ACCESS	read-only
	STATUS		current
	DESCRIPTION
		""
	::= { zxr10X25StatEntry 17}

zxr10StatRecvX25DIAGNOSTICCnt               OBJECT-TYPE
	SYNTAX		Unsigned32
	MAX-ACCESS	read-only
	STATUS		current
	DESCRIPTION
		""
	::= { zxr10X25StatEntry 18}

zxr10StatRecvX25ILLEGALCnt                  OBJECT-TYPE
	SYNTAX		Unsigned32
	MAX-ACCESS	read-only
	STATUS		current
	DESCRIPTION
		""
	::= { zxr10X25StatEntry 19}

zxr10StatRecvX25TotalDataSize                  OBJECT-TYPE
	SYNTAX		Unsigned32
	MAX-ACCESS	read-only
	STATUS		current
	DESCRIPTION
		""
	::= { zxr10X25StatEntry 20}

zxr10StatSendX25CALLREQUESTCnt       OBJECT-TYPE
	SYNTAX		Unsigned32
	MAX-ACCESS	read-only
	STATUS		current
	DESCRIPTION
		""
	::= { zxr10X25StatEntry 21}

zxr10StatSendX25CALLACCEPTEDCnt             OBJECT-TYPE
	SYNTAX		Unsigned32
	MAX-ACCESS	read-only
	STATUS		current
	DESCRIPTION
		""
	::= { zxr10X25StatEntry 22}

zxr10StatSendX25CLEARREQUESTCnt             OBJECT-TYPE
	SYNTAX		Unsigned32
	MAX-ACCESS	read-only
	STATUS		current
	DESCRIPTION
		""
	::= { zxr10X25StatEntry 23}

zxr10StatSendX25CLEARCONFIRMATIONCnt        OBJECT-TYPE
	SYNTAX		Unsigned32
	MAX-ACCESS	read-only
	STATUS		current
	DESCRIPTION
		""
	::= { zxr10X25StatEntry 24}

zxr10StatSendX25DATACnt                     OBJECT-TYPE
	SYNTAX		Unsigned32
	MAX-ACCESS	read-only
	STATUS		current
	DESCRIPTION
		""
	::= { zxr10X25StatEntry 25}

zxr10StatSendX25INTERRUPTCnt                OBJECT-TYPE
	SYNTAX		Unsigned32
	MAX-ACCESS	read-only
	STATUS		current
	DESCRIPTION
		""
	::= { zxr10X25StatEntry 26}

zxr10StatSendX25INTERRUPTCONFIRMATIONCnt    OBJECT-TYPE
	SYNTAX		Unsigned32
	MAX-ACCESS	read-only
	STATUS		current
	DESCRIPTION
		""
	::= { zxr10X25StatEntry 27}

zxr10StatSendX25RRCnt                       OBJECT-TYPE
	SYNTAX		Unsigned32
	MAX-ACCESS	read-only
	STATUS		current
	DESCRIPTION
		""
	::= { zxr10X25StatEntry 28}

zxr10StatSendX25RNRCnt                      OBJECT-TYPE
	SYNTAX		Unsigned32
	MAX-ACCESS	read-only
	STATUS		current
	DESCRIPTION
		""
	::= { zxr10X25StatEntry 29}

zxr10StatSendX25REJCnt                      OBJECT-TYPE
	SYNTAX		Unsigned32
	MAX-ACCESS	read-only
	STATUS		current
	DESCRIPTION
		""
	::= { zxr10X25StatEntry 30}

zxr10StatSendX25RESETREQUESTCnt             OBJECT-TYPE
	SYNTAX		Unsigned32
	MAX-ACCESS	read-only
	STATUS		current
	DESCRIPTION
		""
	::= { zxr10X25StatEntry 31}

zxr10StatSendX25RESETCONFIRMATIONCnt        OBJECT-TYPE
	SYNTAX		Unsigned32
	MAX-ACCESS	read-only
	STATUS		current
	DESCRIPTION
		""
	::= { zxr10X25StatEntry 32}

zxr10StatSendX25REGISTRATIONREQUESTCnt      OBJECT-TYPE
	SYNTAX		Unsigned32
	MAX-ACCESS	read-only
	STATUS		current
	DESCRIPTION
		""
	::= { zxr10X25StatEntry 33}

zxr10StatSendX25REGISTRATIONCONFIRMATIONCnt     OBJECT-TYPE
	SYNTAX		Unsigned32
	MAX-ACCESS	read-only
	STATUS		current
	DESCRIPTION
		""
	::= { zxr10X25StatEntry 34}

zxr10StatSendX25RESTARTREQUESTCnt           OBJECT-TYPE
	SYNTAX		Unsigned32
	MAX-ACCESS	read-only
	STATUS		current
	DESCRIPTION
		""
	::= { zxr10X25StatEntry 35}

zxr10StatSendX25RESTARTCONFIRMATIONCnt      OBJECT-TYPE
	SYNTAX		Unsigned32
	MAX-ACCESS	read-only
	STATUS		current
	DESCRIPTION
		""
	::= { zxr10X25StatEntry 36}

zxr10StatSendX25DIAGNOSTICCnt               OBJECT-TYPE
	SYNTAX		Unsigned32
	MAX-ACCESS	read-only
	STATUS		current
	DESCRIPTION
		""
	::= { zxr10X25StatEntry 37}

zxr10StatSendX25ILLEGALCnt                  OBJECT-TYPE
	SYNTAX		Unsigned32
	MAX-ACCESS	read-only
	STATUS		current
	DESCRIPTION
		""
	::= { zxr10X25StatEntry 38}

zxr10StatSendX25TotalDataSize                  OBJECT-TYPE
	SYNTAX		Unsigned32
	MAX-ACCESS	read-only
	STATUS		current
	DESCRIPTION
		""
	::= { zxr10X25StatEntry 39}

zxr10X25UserAddrTable	OBJECT-TYPE
	SYNTAX		SEQUENCE OF Zxr10X25UserAddrEntry
	MAX-ACCESS	not-accessible
	STATUS		current
	DESCRIPTION
		"A list of Definition of Table entries."
	::= { zxr10X25II 10}

zxr10X25UserAddrEntry	OBJECT-TYPE
	SYNTAX		Zxr10X25UserAddrEntry
	MAX-ACCESS	not-accessible
	STATUS		current
	DESCRIPTION
		"An entry in the table."
	INDEX   {
		        zxr10X25UserIfIndex
    		}
	::= { zxr10X25UserAddrTable 1}

Zxr10X25UserAddrEntry ::=
	SEQUENCE {
		zxr10X25UserX121Address			    DisplayString,
		zxr10X25UserIfIndex				    Unsigned32,
		zxr10X25UserIfName				    DisplayString,
        zxr10X25UserQoS                     INTEGER,
        zxr10X25UserRowStatus               RowStatus
	}

zxr10X25UserX121Address      OBJECT-TYPE
	SYNTAX		DisplayString(SIZE(5))
	MAX-ACCESS	read-create
	STATUS		current
	DESCRIPTION
		""
	::= { zxr10X25UserAddrEntry 1}

zxr10X25UserIfIndex      OBJECT-TYPE
	SYNTAX		Unsigned32
	MAX-ACCESS	read-create
	STATUS		current
	DESCRIPTION
		""
	::= { zxr10X25UserAddrEntry 2}

zxr10X25UserIfName      OBJECT-TYPE
	SYNTAX		DisplayString(SIZE(1..32))
	MAX-ACCESS	read-create
	STATUS		current
	DESCRIPTION
		""
	::= { zxr10X25UserAddrEntry 3}

zxr10X25UserQoS      OBJECT-TYPE
	SYNTAX		INTEGER{high(1),medium(2),low(3)}
	MAX-ACCESS	read-create
	STATUS		current
	DESCRIPTION
		""
	::= { zxr10X25UserAddrEntry 4}

zxr10X25UserRowStatus      OBJECT-TYPE
	SYNTAX		RowStatus
	MAX-ACCESS	read-create
	STATUS		current
	DESCRIPTION
		""
	::= { zxr10X25UserAddrEntry 5}


zxr10X25TrunkTable	OBJECT-TYPE
	SYNTAX		SEQUENCE OF Zxr10X25TrunkEntry
	MAX-ACCESS	not-accessible
	STATUS		current
	DESCRIPTION
		"A list of Definition of Table entries."
	::= { zxr10X25II 11}

zxr10X25TrunkEntry	OBJECT-TYPE
	SYNTAX		Zxr10X25TrunkEntry
	MAX-ACCESS	not-accessible
	STATUS		current
	DESCRIPTION
		"An entry in the table."
	INDEX   {
		        zxr10X25TrunkIfIndex,
		        zxr10X25TrunkX121Address
    		}
	::= { zxr10X25TrunkTable 1}

Zxr10X25TrunkEntry ::=
	SEQUENCE {
		zxr10X25TrunkX121Address			DisplayString,
		zxr10X25TrunkIfName				    DisplayString,
        zxr10X25TrunkQoS                    INTEGER,
        zxr10X25TrunkRowStatus              RowStatus,
        zxr10X25TrunkIfIndex                Unsigned32
	}

zxr10X25TrunkX121Address      OBJECT-TYPE
	SYNTAX		DisplayString(SIZE(1..10))
	MAX-ACCESS	read-create
	STATUS		current
	DESCRIPTION
		""
	::= { zxr10X25TrunkEntry 1}

zxr10X25TrunkIfName      OBJECT-TYPE
	SYNTAX		DisplayString(SIZE(1..32))
	MAX-ACCESS	read-only
	STATUS		current
	DESCRIPTION
		""
	::= { zxr10X25TrunkEntry 2}

zxr10X25TrunkQoS      OBJECT-TYPE
	SYNTAX		INTEGER{first-select-trunk(1),second-select-trunk(2),third-select-trunk(3)}
	MAX-ACCESS	read-create
	STATUS		current
	DESCRIPTION
		""
	::= { zxr10X25TrunkEntry 3}

zxr10X25TrunkRowStatus      OBJECT-TYPE
	SYNTAX		RowStatus
	MAX-ACCESS	read-create
	STATUS		current
	DESCRIPTION
		""
	::= { zxr10X25TrunkEntry 4}

zxr10X25TrunkIfIndex      OBJECT-TYPE
	SYNTAX		Unsigned32
	MAX-ACCESS	read-only
	STATUS		current
	DESCRIPTION
		""
	::= { zxr10X25TrunkEntry 5}

zxr10X25StationAddress OBJECT-TYPE
    SYNTAX  DisplayString(SIZE(5))
    MAX-ACCESS  read-create
    STATUS  current
    DESCRIPTION
    ""
    ::= { zxr10X25II 12 }

zxr10X25DefaultTrunk OBJECT-TYPE
    SYNTAX  DisplayString(SIZE(1..32))
    MAX-ACCESS  read-create
    STATUS  current
    DESCRIPTION
    ""
    ::= { zxr10X25II 13 }

END
