ZTE-AN-PORT-LOCATING-MIB DEFINITIONS ::= BEGIN
IMPORTS
    OBJECT-TYPE, MODULE-IDENTITY, Integer32        FROM SNMPv2-SMI
    DisplayString, RowStatus, TruthValue,TEXTUAL-CONVENTION
                                                   FROM SNMPv2-TC
    ZxAnIfindex, zxAn                              FROM ZTE-AN-TC-MIB;


    zxAnPortLocatingMib   MODULE-IDENTITY
         LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."
        ::= { zxAn 32 }

--------------------------------------------------------------------------------
-- TEXTUAL-CONVENTION
--------------------------------------------------------------------------------
    ZxAnAccessLoopTagType ::= TEXTUAL-CONVENTION
        STATUS      current
        DESCRIPTION
            "A set of access loop characteristics defined in TR-101 about DSL
            line, each bit refers to a suboption:
            Bit 00 : Suboption81, actual data rate upstream.
            Bit 01 : Suboption82, actual data rate downstream.
            Bit 02 : Suboption83, minimum data rate upstream.
            Bit 03 : Suboption84, minimum data rate downstream.
            Bit 04 : Suboption85, attainable data rate upstream.
            Bit 05 : Suboption86, attainable data rate downstream.
            Bit 06 : Suboption87, maximum data rate upstream.
            Bit 07 : Suboption88, maximum data rate downstream.
            Bit 08 : Suboption89, minimum data rate upstream in low power state.
            Bit 09 : Suboption8A, minimum data rate downstream in low power
            state.
            Bit 10 : Suboption8B, maximum interleaving delay upstream.
            Bit 11 : Suboption8C, actual interleaving delay upstream.
            Bit 12 : Suboption8D, maximum interleaving delay downstream.
            Bit 13 : Suboption8E, actual interleaving delay downstream."
        SYNTAX      BITS {
            suboption81(0),
            suboption82(1),
            suboption83(2),
            suboption84(3),
            suboption85(4),
            suboption86(5),
            suboption87(6),
            suboption88(7),
            suboption89(8),
            suboption8A(9),
            suboption8B(10),
            suboption8C(11),
            suboption8D(12),
            suboption8E(13)
        }


    zxAnPortIdAccessNodeName OBJECT-TYPE
        SYNTAX      DisplayString  ( SIZE ( 1 .. 64  ) )
        MAX-ACCESS  read-write
        STATUS      current
        DESCRIPTION
            "Access node name."
        ::= { zxAnPortLocatingMib 1 }



    zxAnPortIdAccessNodeIdType OBJECT-TYPE
        SYNTAX      INTEGER
             {
                inbandMac(1),
                hostname(2)
            }
        MAX-ACCESS  read-write
        STATUS      current
        DESCRIPTION
            "Access Node Identifier type.  1: inband-mac, 2: hostname"
        DEFVAL { inbandMac }
        ::= { zxAnPortLocatingMib 2 }


    zxAnPortIdRack OBJECT-TYPE
        SYNTAX      Integer32
        MAX-ACCESS  read-write
        STATUS      current
        DESCRIPTION
            "Rack of this NE used in port locating application."
        ::= { zxAnPortLocatingMib 3 }


    zxAnPortIdShelf OBJECT-TYPE
        SYNTAX      Integer32
        MAX-ACCESS  read-write
        STATUS      current
        DESCRIPTION
            "Frame of this NE used in port locating application."
        ::= { zxAnPortLocatingMib 4 }

    zxAnPortLocatingCircuitIdSyntaxEnable OBJECT-TYPE
        SYNTAX      INTEGER
            {
                enable(1),
                disable(2)
            }
        MAX-ACCESS  read-write
        STATUS      current
        DESCRIPTION
        "Port locating Circuit ID Syntax enable switch."
        DEFVAL { disable }
        ::= { zxAnPortLocatingMib 5 }

   zxAnPortLocatingAccessLoopEncapsulationEnable OBJECT-TYPE
        SYNTAX      INTEGER
            {
                enable(1),
                disable(2)
            }
        MAX-ACCESS  read-write
        STATUS      current
        DESCRIPTION
        "Port access loop encapsulation enable."
        DEFVAL { disable }
        ::= { zxAnPortLocatingMib 6 }

    zxAnPortIdAccessNodeSlaveId OBJECT-TYPE
        SYNTAX      DisplayString  ( SIZE ( 1 .. 50  ) )
        MAX-ACCESS  read-write
        STATUS      current
        DESCRIPTION
        "This field is designed for Deutsche Telekom.
        By using the DHCP relay agent function the device
        must be able to create the CID and the RID as described
        in BBF TR-101 and TR-156.The CID contains Access-Node-Identifier.
        Access-Node-Identifier which is required by Deutsche Telekom
        consists of two IDs:Access-Node-ID1 and Access-Node-ID2.
        This field indicates Access-Node-ID2."
        DEFVAL { "" }
        ::= { zxAnPortLocatingMib 7 }

    zxAnPortIdDhcpV4AccessLoopChar OBJECT-TYPE
        SYNTAX      ZxAnAccessLoopTagType
        MAX-ACCESS  read-write
        STATUS      current
        DESCRIPTION
            "Access loop characteristics of DHCP packet.
            The bit value 1 means the suboption represented by this
            bit is supported. It used only by DHCP."
        ::= { zxAnPortLocatingMib 8 }

    zxAnPortIdPppoeAccessLoopChar OBJECT-TYPE
        SYNTAX      ZxAnAccessLoopTagType
        MAX-ACCESS  read-write
        STATUS      current
        DESCRIPTION
            "Access loop characteristics of PPPoE packet.
            The bit value 1 means the suboption represented by this
            bit is supported. It used by PPPoE."
        ::= { zxAnPortLocatingMib 9 }

--------------------------------------------------------------------------------
-- Following objects are defined.
-- 1.zxAnPortLocatingTable
-- 2.zxAnPortLocatingCircuitIdSyntaxTable
--------------------------------------------------------------------------------




------------------------------------------------------------------------------
-- 1.zxAnPortLocatingTable
------------------------------------------------------------------------------

    zxAnPortLocatingTable OBJECT-TYPE
        SYNTAX      SEQUENCE OF ZxAnPortLocatingEntry
        MAX-ACCESS  not-accessible
        STATUS      current
        DESCRIPTION
        "port Locating table"
        ::= { zxAnPortLocatingMib 20 }

    zxAnPortLocatingEntry OBJECT-TYPE
        SYNTAX      ZxAnPortLocatingEntry
        MAX-ACCESS  not-accessible
        STATUS      current
        DESCRIPTION
        " port Locating entry. "
        INDEX { zxAnPortLocatingIndex }
        ::= { zxAnPortLocatingTable 1 }

    ZxAnPortLocatingEntry ::= SEQUENCE {
        zxAnPortLocatingIndex                       ZxAnIfindex,
        zxAnPortIdIfConfFormat                      INTEGER,
        zxAnPortIdIfConfRidEnable                   INTEGER,
        zxAnPortIdIfConfRid                         DisplayString,
        zxAnPortLocatingIfaceAccessLoopCharEnable   INTEGER,
        zxAnPortIdIfConfUserDefinedCid              DisplayString,
        zxAnPortIdIfConfFormatProfile               DisplayString,
        zxAnPortIdIfConfRidFormatProfile            DisplayString
        }

    zxAnPortLocatingIndex     OBJECT-TYPE
        SYNTAX             ZxAnIfindex
        MAX-ACCESS         not-accessible
        STATUS          current
        DESCRIPTION
            "The ifindex of the port location."
        ::= { zxAnPortLocatingEntry 1 }

    zxAnPortIdIfConfFormat OBJECT-TYPE
        SYNTAX      INTEGER
              {
                chinaTel(1),
                dslForum(2),
                chinaNet(3),
                turkeyTel(4),
                koreaTel(5),
                telecomItalia(6),
                singTel(7),
                flexibleSyntax(8),
                franceTel(9),
                deutscheTel(10),
                silknet(11),
                vodafone(12),
                bhartiAirtel(13),
                formatProfile(255)
            }
        MAX-ACCESS  read-write
        STATUS      current
        DESCRIPTION
        "Format of port locating."
        DEFVAL { chinaTel }
        ::= { zxAnPortLocatingEntry 2 }

    zxAnPortIdIfConfRidEnable OBJECT-TYPE
        SYNTAX      INTEGER
            {
                enable(1),
                disable(2)
            }
        MAX-ACCESS  read-write
        STATUS      current
        DESCRIPTION
        "enable = 1, disable = 2"
        DEFVAL { disable }
        ::= { zxAnPortLocatingEntry 3 }

    zxAnPortIdIfConfRid OBJECT-TYPE
        SYNTAX      DisplayString (SIZE (0..64))
        MAX-ACCESS  read-write
        STATUS      current
        DESCRIPTION
        ""
        ::= { zxAnPortLocatingEntry 4 }

    zxAnPortLocatingIfaceAccessLoopCharEnable OBJECT-TYPE
        SYNTAX      INTEGER
            {
                enable(1),
                disable(2)
            }
        MAX-ACCESS  read-write
        STATUS      current
        DESCRIPTION
        "Access Loop Characteristics enable switch."
        DEFVAL { disable }
        ::= { zxAnPortLocatingEntry 5 }

   zxAnPortIdIfConfUserDefinedCid OBJECT-TYPE
        SYNTAX      DisplayString (SIZE (0..64))
        MAX-ACCESS  read-write
        STATUS      current
        DESCRIPTION
        ""
        ::= { zxAnPortLocatingEntry 6 }

    zxAnPortIdIfConfFormatProfile OBJECT-TYPE
        SYNTAX      DisplayString (SIZE (1..32))
        MAX-ACCESS  read-write
        STATUS      current
        DESCRIPTION
        "Format profile of port identification."
        ::= { zxAnPortLocatingEntry 7 }

    zxAnPortIdIfConfRidFormatProfile OBJECT-TYPE
        SYNTAX      DisplayString (SIZE (1..32))
        MAX-ACCESS  read-write
        STATUS      current
        DESCRIPTION
        "Format profile of remote ID."
        ::= { zxAnPortLocatingEntry 8 }
------------------------------------------------------------------------------
-- 2.zxAnPortLocatingCircuitIdSyntaxTable
------------------------------------------------------------------------------

    zxAnPortLocatingCircuitIdSyntaxTable OBJECT-TYPE
        SYNTAX      SEQUENCE OF ZxAnPortLocatingCircuitIdSyntaxEntry
        MAX-ACCESS  not-accessible
        STATUS      current
        DESCRIPTION
        "Port locating Circuit ID Syntax table."
        ::= { zxAnPortLocatingMib 22 }

    zxAnPortLocatingCircuitIdSyntaxEntry OBJECT-TYPE
        SYNTAX      ZxAnPortLocatingCircuitIdSyntaxEntry
        MAX-ACCESS  not-accessible
        STATUS      current
        DESCRIPTION
        "Port locating Circuit ID Syntax entry. "
        INDEX { zxAnPortLocatingCircuitIdSyntaxIndex, zxAnPortLocatingCircuitIdComponentIndex }
        ::= { zxAnPortLocatingCircuitIdSyntaxTable 1 }

    ZxAnPortLocatingCircuitIdSyntaxEntry ::= SEQUENCE {
        zxAnPortLocatingCircuitIdSyntaxIndex        Integer32,
        zxAnPortLocatingCircuitIdComponentIndex     Integer32,
        zxAnPortLocatingCircuitIdComponentType      INTEGER,
        zxAnPortLocatingCircuitIdComponentId        Integer32,
        zxAnPortLocatingCircuitIdComponentWidth     Integer32,
        zxAnPortLocatingCidComponentStr             DisplayString,
        zxAnPortLocatingCircuitIdComponentRowStatus RowStatus
        }

    zxAnPortLocatingCircuitIdSyntaxIndex     OBJECT-TYPE
        SYNTAX         Integer32
        MAX-ACCESS     not-accessible
        STATUS      current
        DESCRIPTION
        "A first key that identifies the Circuit ID Syntax."
        REFERENCE   "TR-141 Section 6.16"
        ::= { zxAnPortLocatingCircuitIdSyntaxEntry 1 }

    zxAnPortLocatingCircuitIdComponentIndex     OBJECT-TYPE
        SYNTAX         Integer32
        MAX-ACCESS     not-accessible
        STATUS      current
        DESCRIPTION
        "A second key that identifies a component in the Circuit ID Syntax."
        REFERENCE   "TR-141 Section 6.16"
        ::= { zxAnPortLocatingCircuitIdSyntaxEntry 2 }


    zxAnPortLocatingCircuitIdComponentType OBJECT-TYPE
        SYNTAX      INTEGER
              {
                standardVar(1),
                extendedVar(2),
                separator(3),
                userDefinedString(4)
              }
        MAX-ACCESS  read-create
        STATUS      current
        DESCRIPTION
        "An attribute that identifies the type of this component. The following
            types are possible:
            standardVar - A TR-101 based variable(1: access node id, 2: chassis,
                          3: rack, 4: frame, 5: slot, 6: sub-slot, 7: port,
                          8: vpi, 9: vci, 10: q-vid, 11: ethernet-priority)
            extendedVar - A proprietary variable(1: onu id, 2: gemPort,
                          3: cvlan, 4: svlan)
            separator - A delimiter or constant string(1: #, 2: ., 3: ,, 4: ;,
                        5: /, 6: space, 7: :)
            userDefinedString - Information configured by the network operator.
                                when the value is userDefinedString(4), the
                                zxAnPortLocatingCidComponentStr is valid, the
                                zxAnPortLocatingCircuitIdComponentId is invalid
                                and the recommandation is 0."
        REFERENCE   "TR-141 Section 6.16"
        DEFVAL { standardVar }
               ::= { zxAnPortLocatingCircuitIdSyntaxEntry 3 }

    zxAnPortLocatingCircuitIdComponentId OBJECT-TYPE
        SYNTAX         Integer32
        MAX-ACCESS  read-create
        STATUS      current
        DESCRIPTION
        "A unique and content sensitive identifier for the specific definition of this component. The following identifiers are expected:
            A row number in table 2 of TR-101 (R-126).
            An index into a proprietary managed entity that specifies possible proprietary variables.
            An index into a proprietary managed entity that specifies possible delimiters and constant character strings."
        REFERENCE   "TR-141 Section 6.16"
        ::= { zxAnPortLocatingCircuitIdSyntaxEntry 4 }

    zxAnPortLocatingCircuitIdComponentWidth OBJECT-TYPE
        SYNTAX      Integer32
        MAX-ACCESS  read-create
        STATUS      current
        DESCRIPTION
        "The width of the port locating Circuit ID Syntax component.If the
        length of component is less than the width then fill zero in front of
        the component.The width has no effect on
        zxAnPortLocatingCidComponentStr."
        ::= { zxAnPortLocatingCircuitIdSyntaxEntry 5 }

    zxAnPortLocatingCidComponentStr  OBJECT-TYPE
        SYNTAX      DisplayString (SIZE (0..50))
        MAX-ACCESS  read-create
        STATUS      current
        DESCRIPTION
        "Information configured by the network operator.The recommandation of
        default value is ''.When the value of
        zxAnPortLocatingCircuitIdComponentType is userDefinedString(4),
        this variable is valid."
        ::= { zxAnPortLocatingCircuitIdSyntaxEntry 6 }

    zxAnPortLocatingCircuitIdComponentRowStatus  OBJECT-TYPE
        SYNTAX      RowStatus
        MAX-ACCESS  read-create
        STATUS      current
        DESCRIPTION
        "The row status of this entry."
        ::= { zxAnPortLocatingCircuitIdSyntaxEntry 20 }

------------------------------------------------------------------------------
-- .zxAnPortLocatingVlan test for c300
------------------------------------------------------------------------------
     zxAnVlanPortLocatingObjects        OBJECT IDENTIFIER  ::= { zxAnPortLocatingMib 25 }


     zxAnVlanPortLocatingEnable OBJECT-TYPE
        SYNTAX      TruthValue
        MAX-ACCESS  read-write
        STATUS      current
        DESCRIPTION
             "Enable or disable VLAN port locating.1-truth,2-false."
        DEFVAL { 2 }
        ::= { zxAnVlanPortLocatingObjects 1 }


     zxAnVlanPortLocatingTable OBJECT-TYPE
        SYNTAX      SEQUENCE OF ZxAnVlanPortLocatingEntry
        MAX-ACCESS  not-accessible
        STATUS      current
        DESCRIPTION
        "VLAN Port locating table.When zxAnVlanPortLocatingEnable equal 'truth',this table is effective."
        ::= { zxAnVlanPortLocatingObjects 2 }

    zxAnVlanPortLocatingEntry OBJECT-TYPE
        SYNTAX      ZxAnVlanPortLocatingEntry
        MAX-ACCESS  not-accessible
        STATUS      current
        DESCRIPTION
        ""
        INDEX { zxAnPortLocatingVlan}
        ::= { zxAnVlanPortLocatingTable 1 }

    ZxAnVlanPortLocatingEntry ::= SEQUENCE {
        zxAnPortLocatingVlan        Integer32,
        zxAnPortLocatingVlanRowStatus RowStatus
        }

    zxAnPortLocatingVlan     OBJECT-TYPE
        SYNTAX         Integer32
        MAX-ACCESS     not-accessible
        STATUS      current
        DESCRIPTION
        "A  key that identifies the vlan port location."
        ::= { zxAnVlanPortLocatingEntry 1 }

    zxAnPortLocatingVlanRowStatus  OBJECT-TYPE
        SYNTAX      RowStatus
        MAX-ACCESS  read-create
        STATUS      current
        DESCRIPTION
        "The row status of this entry."
        ::= { zxAnVlanPortLocatingEntry 20 }


END
