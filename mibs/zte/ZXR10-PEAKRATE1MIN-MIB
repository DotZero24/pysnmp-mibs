--  ******************************************************
--  $Id: zxr10poe.mib 12 2008-12-05  Caosl $
--
--  zxr10poe.mib: ZXR10 POE MIB file
--
--  August. 2008, Cao shuling
--
--  Copyright(c) 2008 by ZTE Corporaton
--  All rights reservered
--
--
--  ******************************************************

ZXR10-PEAKRATE1MIN-MIB DEFINITIONS ::= BEGIN

IMPORTS
	--MODULE-IDENTITY,
	  TimeTicks
    FROM RFC1155-SMI
	OBJECT-TYPE, Integer32, Counter64
		FROM SNMPv2-SMI
	enterprises
        FROM SNMPv2-SMI;

    zte OBJECT IDENTIFIER ::= { enterprises 3902 }
    zxr10 OBJECT IDENTIFIER ::= { zte 3 }
    zxr10switch OBJECT IDENTIFIER ::= { zxr10 102}
    zxr10Peakrate1Min OBJECT IDENTIFIER ::= { zxr10switch 31 }

    --The follow part defined some data types which will be used in this acl mib file later
    DisplayString ::= OCTET STRING
    --  This data type is used to model textual information taken
    --  from the NVT ASCII character set.  By convention, objects
    --  with this syntax are declared as having
    --  SIZE (0..255)


-- PORT Objects
	portPeakrateTable OBJECT-TYPE
		SYNTAX      SEQUENCE OF PortPeakrateEntry
		MAX-ACCESS  not-accessible
		STATUS      current
		DESCRIPTION
		    "A table of objects that display the 1min peak rate
		    statistics information. This group will be implemented in
	        managed Ethernet switches devices."
		::= { zxr10Peakrate1Min 1 }

	portPeakrateEntry OBJECT-TYPE
		SYNTAX      PortPeakrateEntry
		MAX-ACCESS  not-accessible
		STATUS      current
		DESCRIPTION
		     "A set of objects that display the statistics information of the port. "
		INDEX    { portIfOutIndex }
		::= { portPeakrateTable 1 }

	PortPeakrateEntry ::= SEQUENCE {
       portIfOutIndex
           INTEGER,
       portPeakrateEnable
           INTEGER,
       portInUnicastPktsPeak
           Counter64,
       portInUnicastTime
           OCTET STRING,
       portInMulticastPktsPeak
           Counter64,
       portInMulticastTime
           OCTET STRING,
       portInBroadcastPktsPeak
           Counter64,
       portInBroadcastTime
           OCTET STRING,
       portInTotalErrPktsPeak
           Counter64,
       portInTotalErrTime
           OCTET STRING,
       portOutUnicastPktsPeak
           Counter64,
       portOutUnicastTime
           OCTET STRING,
       portOutMulticastPktsPeak
           Counter64,
       portOutMulticastTime
           OCTET STRING,
       portOutBroadcastPktsPeak
           Counter64,
       portOutBroadcastTime
           OCTET STRING,
       portOutTotalErrPktsPeak
           Counter64,
       portOutTotalErrTime
           OCTET STRING,
       portClearPeakPkts
           INTEGER
   }
	  portIfOutIndex OBJECT-TYPE
		SYNTAX       INTEGER (1..2147483647)
		MAX-ACCESS  read-only
		STATUS      current
		DESCRIPTION
		    "A unique value for each interface.  Its value
                      ranges between 1 and the value of ifNumber.  The
                      value for each interface must remain constant at
                      least from one re-initialization of the entity's
                      network management system to the next re-initialization."
		::= { portPeakrateEntry 1 }

    portPeakrateEnable OBJECT-TYPE
       SYNTAX      INTEGER { enable ( 1 ) , disable ( 2 ) }
       MAX-ACCESS  read-write
       STATUS      current
       DESCRIPTION
			"The state of the port`s peak rate statistic function."
       ::= { portPeakrateEntry 2 }

	portInUnicastPktsPeak OBJECT-TYPE
		SYNTAX   Counter64
		UNITS      "ppm"
		MAX-ACCESS  read-only
		STATUS      current
		DESCRIPTION
		        "The unicast packet peak rate of the port IN direction in ppm(packets per minute)."
		::= { portPeakrateEntry 3 }

	portInUnicastTime OBJECT-TYPE
		SYNTAX   OCTET STRING
		MAX-ACCESS  read-only
		STATUS      current
		DESCRIPTION
		        "The unicast packet peak rate time(YYYYMMDD-hh:mm:ss,such as 20090622-09:30:20) of the port IN direction."
		::= { portPeakrateEntry 4 }

	portInMulticastPktsPeak OBJECT-TYPE
		SYNTAX   Counter64
		UNITS      "ppm"
		MAX-ACCESS  read-only
		STATUS      current
		DESCRIPTION
		        "The multicast packet peak rate of the port IN direction in ppm(packets per minute)."
		::= { portPeakrateEntry 5 }

	portInMulticastTime OBJECT-TYPE
		SYNTAX   OCTET STRING
		MAX-ACCESS  read-only
		STATUS      current
		DESCRIPTION
		        "The multicast packet peak rate time(YYYYMMDD-hh:mm:ss,such as 20090622-09:30:20) of the port IN direction ."
		::= { portPeakrateEntry 6 }

	portInBroadcastPktsPeak OBJECT-TYPE
		SYNTAX   Counter64
		UNITS      "ppm"
		MAX-ACCESS  read-only
		STATUS      current
		DESCRIPTION
		        "The broadcast packet peak rate of the port IN direction in ppm(packets per minute)."
		::= { portPeakrateEntry 7 }

	portInBroadcastTime OBJECT-TYPE
		SYNTAX   OCTET STRING
		MAX-ACCESS  read-only
		STATUS      current
		DESCRIPTION
		        "The broadcast packet peak rate time(YYYYMMDD-hh:mm:ss,such as 20090622-09:30:20) of the port IN direction."
		::= { portPeakrateEntry 8 }

    portInTotalErrPktsPeak OBJECT-TYPE
		SYNTAX   Counter64
		UNITS      "ppm"
		MAX-ACCESS  read-only
		STATUS      current
		DESCRIPTION
		        "The total error packet peak rate of the port IN direction in ppm(packets per minute)."
		::= { portPeakrateEntry 9 }

	portInTotalErrTime OBJECT-TYPE
		SYNTAX   OCTET STRING
		MAX-ACCESS  read-only
		STATUS      current
		DESCRIPTION
		        "The total error packet peak rate time(YYYYMMDD-hh:mm:ss,such as 20090622-09:30:20) of the port IN direction ."
		::= { portPeakrateEntry 10 }

    portOutUnicastPktsPeak OBJECT-TYPE
		SYNTAX   Counter64
		UNITS      "ppm"
		MAX-ACCESS  read-only
		STATUS      current
		DESCRIPTION
		        "The unicast packet peak rate of the port OUT direction in ppm(packets per minute)."
		::= { portPeakrateEntry 11 }

	portOutUnicastTime OBJECT-TYPE
		SYNTAX   OCTET STRING
		MAX-ACCESS  read-only
		STATUS      current
		DESCRIPTION
		        "The unicast packet peak rate time(YYYYMMDD-hh:mm:ss,such as 20090622-09:30:20) of the port OUT direction."
		::= { portPeakrateEntry 12 }

	portOutMulticastPktsPeak OBJECT-TYPE
		SYNTAX   Counter64
		UNITS      "ppm"
		MAX-ACCESS  read-only
		STATUS      current
		DESCRIPTION
		        "The multicast packet peak rate of the port OUT direction in ppm(packets per minute)."
		::= { portPeakrateEntry 13 }

	portOutMulticastTime OBJECT-TYPE
		SYNTAX   OCTET STRING
		MAX-ACCESS  read-only
		STATUS      current
		DESCRIPTION
		        "The multicast packet peak rate time(YYYYMMDD-hh:mm:ss,such as 20090622-09:30:20) of the port OUT direction."
		::= { portPeakrateEntry 14 }

	portOutBroadcastPktsPeak OBJECT-TYPE
		SYNTAX   Counter64
		UNITS      "ppm"
		MAX-ACCESS  read-only
		STATUS      current
		DESCRIPTION
		        "The broadcast packet peak rate of the port OUT direction in ppm(packets per minute)."
		::= { portPeakrateEntry 15 }

	portOutBroadcastTime OBJECT-TYPE
		SYNTAX   OCTET STRING
		MAX-ACCESS  read-only
		STATUS      current
		DESCRIPTION
		        "The broadcast packet peak rate time(YYYYMMDD-hh:mm:ss,such as 20090622-09:30:20) of the port OUT direction."
		::= { portPeakrateEntry 16 }

    portOutTotalErrPktsPeak OBJECT-TYPE
		SYNTAX   Counter64
		UNITS      "ppm"
		MAX-ACCESS  read-only
		STATUS      current
		DESCRIPTION
		        "The total error packet peak rate of the port OUT direction in ppm(packets per minute)."
		::= { portPeakrateEntry 17 }

	portOutTotalErrTime OBJECT-TYPE
		SYNTAX   OCTET STRING
		MAX-ACCESS  read-only
		STATUS      current
		DESCRIPTION
		        "The total error packet peak rate time(YYYYMMDD-hh:mm:ss,such as 20090622-09:30:20) of the port OUT direction."
		::= { portPeakrateEntry 18 }

    portClearPeakPkts OBJECT-TYPE
		SYNTAX			INTEGER { clear ( 0 ) }
		MAX-ACCESS		read-write
		STATUS			current
		DESCRIPTION		"Clear peak statistics of the whole ports which are enable."
		::=  {  portPeakrateEntry  19  }

   END
