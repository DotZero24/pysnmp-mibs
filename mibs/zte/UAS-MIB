UAS-MIB DEFINITIONS ::= BEGIN
IMPORTS
        MODULE-IDENTITY, OBJECT-TYPE,
        Counter32,Integer32,TimeTicks,
        IpAddress, enterprises                    FROM SNMPv2-SMI
        DisplayString,PhysAddress                 FROM SNMPv2-TC;



    zxUasMib  MODULE-IDENTITY
    LAST-UPDATED "200503081500Z"
    ORGANIZATION "ZTE Co."
    CONTACT-INFO ""
    DESCRIPTION
        "This mib defines management information objects for uas"
    ::= { zxUas 1 }

    zte                          OBJECT IDENTIFIER ::= { enterprises 3902 }
    zxUas                        OBJECT IDENTIFIER ::= { zte 1006 }


    zxUasMibObjects              OBJECT IDENTIFIER ::= { zxUasMib 1 }
    zxUasTraps                   OBJECT IDENTIFIER ::= { zxUasMib 2 }

    zxUasSystemGroup             OBJECT IDENTIFIER ::= { zxUasMibObjects 1 }
    zxUasServiceMgmtGroup        OBJECT IDENTIFIER ::= { zxUasMibObjects 2 }
    zxUasStaticsGroup            OBJECT IDENTIFIER ::= { zxUasMibObjects 3 }



    -- statics mib
    zxUasPppStatics              OBJECT IDENTIFIER ::= { zxUasStaticsGroup 1 }
    -- zxUasAaaStatics
    -- zxSecurityStatics

    -- trap mib

    -- system mgmt

    -- service mgmt


---IP pool mib

    zxUasInterfaceIPPoolTable  OBJECT-TYPE
        SYNTAX      SEQUENCE OF ZxUasInterfaceIPPoolEntry
        MAX-ACCESS  not-accessible
        STATUS      current
        DESCRIPTION
            "This table contains IP Pool entry"
        ::= { zxUasServiceMgmtGroup 1 }

    zxUasInterfaceIPPoolEntry  OBJECT-TYPE
        SYNTAX      ZxUasInterfaceIPPoolEntry
        MAX-ACCESS  not-accessible
        STATUS      current
        DESCRIPTION
            "This list contains IP Pool parameters
             and is indexed by zxUasIPPoolName"
        INDEX  { zxUasIPPoolName,
                 zxUasIPPoolVirtualRouteField,
                 zxUasIPPoolInterfaceName,
                 zxUasIPPoolID,
                 zxUasIPPoolStartIPAddr,
                 zxUasIPPoolEndIPAddr
                 }
        ::= { zxUasInterfaceIPPoolTable  1}

    ZxUasInterfaceIPPoolEntry  ::= SEQUENCE  {
        zxUasIPPoolName                 DisplayString,
        zxUasIPPoolVirtualRouteField    DisplayString,
        zxUasIPPoolInterfaceName        DisplayString,
        zxUasIPPoolID                   INTEGER,
        zxUasIPPoolStartIPAddr          IpAddress,
        zxUasIPPoolEndIPAddr            IpAddress,
        zxUasIPPoolFreeIPNum            INTEGER,
        zxUasIPPoolUsedIPNum            INTEGER,
        zxUasIPPoolUnavailableIPNum     INTEGER,
        zxUasIPPoolBindToDomainFlag     INTEGER
        }

    zxUasIPPoolName  OBJECT-TYPE
        SYNTAX      DisplayString(SIZE(0..31))
        MAX-ACCESS  read-only
        STATUS      current
        DESCRIPTION
            "IP Pool name."
        ::= { zxUasInterfaceIPPoolEntry 1 }

    zxUasIPPoolVirtualRouteField  OBJECT-TYPE
        SYNTAX      DisplayString(SIZE(0..15))
        MAX-ACCESS  read-only
        STATUS      current
        DESCRIPTION
            "IP pool virtual route field name."
        ::= { zxUasInterfaceIPPoolEntry 2 }

    zxUasIPPoolInterfaceName  OBJECT-TYPE
        SYNTAX      DisplayString(SIZE(0..31))
        MAX-ACCESS  read-only
        STATUS      current
        DESCRIPTION
            "VBUI global port."
        ::= { zxUasInterfaceIPPoolEntry 3 }

    zxUasIPPoolID  OBJECT-TYPE
        SYNTAX      INTEGER
        MAX-ACCESS  read-only
        STATUS      current
        DESCRIPTION
            "IP Pool ID."
        ::= { zxUasInterfaceIPPoolEntry 4 }

    zxUasIPPoolStartIPAddr  OBJECT-TYPE
        SYNTAX      IpAddress
        MAX-ACCESS  read-only
        STATUS      current
        DESCRIPTION
            "start IP address."
        ::= { zxUasInterfaceIPPoolEntry 5 }

    zxUasIPPoolEndIPAddr  OBJECT-TYPE
        SYNTAX      IpAddress
        MAX-ACCESS  read-only
        STATUS      current
        DESCRIPTION
            "end IP Address."
        ::= { zxUasInterfaceIPPoolEntry 6 }

    zxUasIPPoolFreeIPNum  OBJECT-TYPE
        SYNTAX      INTEGER(0..256)
        MAX-ACCESS  read-only
        STATUS      current
        DESCRIPTION
            "free IP Num."
        ::= { zxUasInterfaceIPPoolEntry 7 }

    zxUasIPPoolUsedIPNum  OBJECT-TYPE
        SYNTAX      INTEGER(0..256)
        MAX-ACCESS  read-only
        STATUS      current
        DESCRIPTION
            "used IP Num."
        ::= { zxUasInterfaceIPPoolEntry 8 }

    zxUasIPPoolUnavailableIPNum  OBJECT-TYPE
        SYNTAX      INTEGER(0..256)
        MAX-ACCESS  read-only
        STATUS      current
        DESCRIPTION
            "unavailable IP Num."
        ::= { zxUasInterfaceIPPoolEntry 9 }

    zxUasIPPoolBindToDomainFlag  OBJECT-TYPE
        SYNTAX      INTEGER{
            unreserved(1),
            reserved(2)
            }
        MAX-ACCESS  read-only
        STATUS      current
        DESCRIPTION
            "this flag is used for binding to domain."
        ::= { zxUasInterfaceIPPoolEntry 10 }

--- active subscriber mib

    zxUasActiveSubscriberTable  OBJECT-TYPE
        SYNTAX      SEQUENCE OF ZxUasActiveSubscriberEntry
        MAX-ACCESS  not-accessible
        STATUS      current
        DESCRIPTION
            "This table contains active subscriber entry"
        ::= { zxUasServiceMgmtGroup 2 }

    zxUasActiveSubscriberEntry  OBJECT-TYPE
        SYNTAX      ZxUasActiveSubscriberEntry
        MAX-ACCESS  not-accessible
        STATUS      current
        DESCRIPTION
            "This list contains active subscriber parameters
             and is indexed by zxUasActiveSubscriberIndex "
        INDEX { zxUasActiveSubscriberVirtualRouteField,
                zxUasActiveSubscriberIPAddr,
                zxUasActiveSubscriberType,
                zxUasActiveSubscriberPPPID
                }
        ::= { zxUasActiveSubscriberTable 1 }

    ZxUasActiveSubscriberEntry ::= SEQUENCE {
        zxUasActiveSubscriberVirtualRouteField  DisplayString,
        zxUasActiveSubscriberIPAddr             IpAddress,
        zxUasActiveSubscriberType               INTEGER,
        zxUasActiveSubscriberPPPID              Integer32,
        zxUasActiveSubscriberName               DisplayString,
        zxUasActiveSubscriberInterfaceName      DisplayString,
        zxUasActiveSubscriberDoaminID           Integer32,
        zxUasActiveSubscriberSlot               Integer32,
        zxUasActiveSubscriberPort               Integer32,
        zxUasActiveSubscriberVlanId             Integer32,
        zxUasActiveSubscriberVpi                Integer32,
        zxUasActiveSubscriberVci                Integer32,
        zxUasActiveSubscriberMACAddr            PhysAddress,
        zxUasActiveSubscriberUpOctets           Counter32,
        zxUasActiveSubscriberUpGigaOctets       Counter32,
        zxUasActiveSubscriberDownOctets         Counter32,
        zxUasActiveSubscriberDownGigaOctets     Counter32,
        zxUasActiveDhcpSubscriberAuthFlag       Integer32,
        zxUasActiveSubscriberUpTime             TimeTicks
        }

    zxUasActiveSubscriberVirtualRouteField  OBJECT-TYPE
        SYNTAX      DisplayString(SIZE(0..15))
        MAX-ACCESS  read-only
        STATUS      current
        DESCRIPTION
            "active subscriber virtual route field name."
        ::= { zxUasActiveSubscriberEntry 1 }

    zxUasActiveSubscriberIPAddr  OBJECT-TYPE
        SYNTAX      IpAddress
        MAX-ACCESS  read-only
        STATUS      current
        DESCRIPTION
            "active subscriber IP address."
        ::= { zxUasActiveSubscriberEntry 2 }

    zxUasActiveSubscriberType  OBJECT-TYPE
        SYNTAX      INTEGER{
            ppp(1),
            ipdhcp(2),
            remotedhcp(3),
            ipdhcprelay(4),
            iphost(5),
            remotehost(6),
            vpn(7),
            brg(8)
            }
        MAX-ACCESS  read-only
        STATUS      current
        DESCRIPTION
            "active subscriber type."
        ::= { zxUasActiveSubscriberEntry 3 }

    zxUasActiveSubscriberPPPID  OBJECT-TYPE
        SYNTAX      Integer32
        MAX-ACCESS  read-only
        STATUS      current
        DESCRIPTION
            "PPP active subscriber ID."
        ::= { zxUasActiveSubscriberEntry 4 }

    zxUasActiveSubscriberName  OBJECT-TYPE
        SYNTAX      DisplayString(SIZE(0..63))
        MAX-ACCESS  read-only
        STATUS      current
        DESCRIPTION
            "active subscriber name."
        ::= { zxUasActiveSubscriberEntry 5 }

    zxUasActiveSubscriberInterfaceName  OBJECT-TYPE
        SYNTAX      DisplayString(SIZE(0..31))
        MAX-ACCESS  read-only
        STATUS      current
        DESCRIPTION
            "active subscriber VBUI global port."
        ::= { zxUasActiveSubscriberEntry 6 }

    zxUasActiveSubscriberDoaminID  OBJECT-TYPE
        SYNTAX      Integer32
        MAX-ACCESS  read-only
        STATUS      current
        DESCRIPTION
            "active subscriber domain ID."
        ::= { zxUasActiveSubscriberEntry 7 }

    zxUasActiveSubscriberSlot  OBJECT-TYPE
        SYNTAX      Integer32
        MAX-ACCESS  read-only
        STATUS      current
        DESCRIPTION
            "active subscriber slot."
        ::= { zxUasActiveSubscriberEntry 8 }

    zxUasActiveSubscriberPort  OBJECT-TYPE
        SYNTAX      Integer32
        MAX-ACCESS  read-only
        STATUS      current
        DESCRIPTION
            "active subscriber port."
        ::= { zxUasActiveSubscriberEntry 9 }

    zxUasActiveSubscriberVlanId  OBJECT-TYPE
        SYNTAX      Integer32
        MAX-ACCESS  read-only
        STATUS      current
        DESCRIPTION
            "active subscriber VlanId."
        ::= { zxUasActiveSubscriberEntry 10 }

    zxUasActiveSubscriberVpi  OBJECT-TYPE
        SYNTAX      Integer32
        MAX-ACCESS  read-only
        STATUS      current
        DESCRIPTION
            "active subscriber vpi value."
        ::= { zxUasActiveSubscriberEntry 11 }

    zxUasActiveSubscriberVci  OBJECT-TYPE
        SYNTAX      Integer32
        MAX-ACCESS  read-only
        STATUS      current
        DESCRIPTION
            "active subscriber vci value."
        ::= { zxUasActiveSubscriberEntry 12 }

    zxUasActiveSubscriberMACAddr  OBJECT-TYPE
        SYNTAX      PhysAddress
        MAX-ACCESS  read-only
        STATUS      current
        DESCRIPTION
            "active subscriber host MAC address."
        ::= { zxUasActiveSubscriberEntry 13 }

    zxUasActiveSubscriberUpOctets  OBJECT-TYPE
        SYNTAX      Counter32
        MAX-ACCESS  read-only
        STATUS      current
        DESCRIPTION
            "active subscriber up flow."
        ::= { zxUasActiveSubscriberEntry 14 }

    zxUasActiveSubscriberUpGigaOctets  OBJECT-TYPE
        SYNTAX      Counter32
        MAX-ACCESS  read-only
        STATUS      current
        DESCRIPTION
            "active subscriber up flow extend."
        ::= { zxUasActiveSubscriberEntry 15 }

    zxUasActiveSubscriberDownOctets  OBJECT-TYPE
        SYNTAX      Counter32
        MAX-ACCESS  read-only
        STATUS      current
        DESCRIPTION
            "active subscriber down flow."
        ::= { zxUasActiveSubscriberEntry 16 }

    zxUasActiveSubscriberDownGigaOctets  OBJECT-TYPE
        SYNTAX      Counter32
        MAX-ACCESS  read-only
        STATUS      current
        DESCRIPTION
            "active subscriber down flow extend."
        ::= { zxUasActiveSubscriberEntry 17 }

    zxUasActiveDhcpSubscriberAuthFlag  OBJECT-TYPE
        SYNTAX      Integer32
        MAX-ACCESS  read-only
        STATUS      current
        DESCRIPTION
            "DHCP subscriber authentication status."
        ::= { zxUasActiveSubscriberEntry 18 }

    zxUasActiveSubscriberUpTime  OBJECT-TYPE
        SYNTAX      TimeTicks
        MAX-ACCESS  read-only
        STATUS      current
        DESCRIPTION
            "active subscriber create time."
        ::= { zxUasActiveSubscriberEntry 19 }

    zxUasTail  OBJECT-TYPE
        SYNTAX     INTEGER{
               true(1),
               false(0)
               }
        MAX-ACCESS  not-accessible
        STATUS      current
        DESCRIPTION
            " null node"
        ::= { zxUasServiceMgmtGroup 3 }

-- statics
--- ppp statics mib
---
    zxUasPppCallCount  OBJECT-TYPE
        SYNTAX      Counter32
        MAX-ACCESS  read-only
        STATUS      current
        DESCRIPTION
            "ppp calling counts."
        ::= { zxUasPppStatics 1 }

    zxUasPppCallFailedCount  OBJECT-TYPE
        SYNTAX      Counter32
        MAX-ACCESS  read-only
        STATUS      current
        DESCRIPTION
            "ppp calling failed counts."
        ::= { zxUasPppStatics 2 }

    zxUasPppLinkBreakFailedCount  OBJECT-TYPE
        SYNTAX      Counter32
        MAX-ACCESS  read-only
        STATUS      current
        DESCRIPTION
            "ppp linkbreak failed counts."
        ::= { zxUasPppStatics 3 }

    zxUasPppAbnormalCloseCount  OBJECT-TYPE
        SYNTAX      Counter32
        MAX-ACCESS  read-only
        STATUS      current
        DESCRIPTION
            "abnormal close counts."
        ::= { zxUasPppStatics 4 }


--- active subscriber statics mib

    zxUasActiveSubscriberStaticsTable  OBJECT-TYPE
        SYNTAX      SEQUENCE OF ZxUasActiveSubscriberStaticsEntry
        MAX-ACCESS  not-accessible
        STATUS      current
        DESCRIPTION
            "This table contains active subscriber statics Entry"
        ::= { zxUasStaticsGroup 2 }

    zxUasActiveSubscriberStaticsEntry  OBJECT-TYPE
        SYNTAX      ZxUasActiveSubscriberStaticsEntry
        MAX-ACCESS  not-accessible
        STATUS      current
        DESCRIPTION
            "This list contains active subscriber statics
             parameters and is indexed by zxUasActiveSubscriberType"
        INDEX { zxUasActiveSubscriberType }
        ::= { zxUasActiveSubscriberStaticsTable 1 }

    ZxUasActiveSubscriberStaticsEntry ::= SEQUENCE {
        zxUasActiveSubscriberNum        Integer32
        }

    zxUasActiveSubscriberNum  OBJECT-TYPE
        SYNTAX      Integer32
        MAX-ACCESS  read-only
        STATUS      current
        DESCRIPTION
            "ppp users num,iphost users num,dhcp users num and vpn users num."
        ::= { zxUasActiveSubscriberStaticsEntry 1 }

	zxUasMaxSubscriberOnlineCount  OBJECT-TYPE
        SYNTAX      Integer32
        MAX-ACCESS  read-only
        STATUS      current
        DESCRIPTION
            "The subscriber peak online in the history"
        ::= { zxUasStaticsGroup 3 }

	zxUasMaxSubscriberOnlineClear  OBJECT-TYPE
        SYNTAX      INTEGER{normal(0),
        clear(1)
        }
        MAX-ACCESS  read-write
        STATUS      current
        DESCRIPTION
            "Clear subscriber peak online in the history"
        ::= { zxUasStaticsGroup 4 }

        zxUasMaxSubscriberOnlineTime  OBJECT-TYPE
        SYNTAX      DisplayString(SIZE(0..31))
        MAX-ACCESS  read-only
        STATUS      current
        DESCRIPTION
            "The time which the max subscriber occured."
        ::= { zxUasStaticsGroup 5 }

-- trap

END
