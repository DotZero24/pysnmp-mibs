--------------------------------------------------------------------------
-- File Name : ZTE-AN-SYS-MIB.mib
-- Date      : 2010-01-25
-- Author    : ZTE Nms dept.

--
-- Zte System Mgmt Mib for Access Node
--
--
--------------------------------------------------------------------------


ZTE-AN-PETH-MIB    DEFINITIONS ::= BEGIN

    IMPORTS
        TruthValue, DisplayString                   FROM SNMPv2-TC
        enterprises, MODULE-IDENTITY, Integer32, NOTIFICATION-TYPE
                                                    FROM SNMPv2-SMI
        zxAn                                        FROM ZTE-AN-TC-MIB
        ifIndex                                     FROM RFC1213-MIB;

    zxAnPethMib    MODULE-IDENTITY
        LAST-UPDATED    "201001251500Z"
        ORGANIZATION    "ZTE Corporation"
        CONTACT-INFO    "ZTE NMS dept.
                         She Yunsheng  68896270"
        DESCRIPTION        "This MIB defines Description of zte power ethernet managed objects."
        ::=  {  zxAn  300  }

    zxAnPethObjects    OBJECT IDENTIFIER
        ::=  {  zxAnPethMib  1  }

    zxAnPethTrapObjects    OBJECT IDENTIFIER
        ::=  {  zxAnPethMib  2  }

--------------------------------------------------------------------------------
-- Following objects are defined.
-- 1.Global Configuration
-- 2.PSE Port Information
-- 3.PSE Card Information
-- 4.PDE Port Information
-- 5.Trap Objects
--------------------------------------------------------------------------------


--------------------------------------------------------------------------------
-- 1.Global Configuration
--------------------------------------------------------------------------------

    zxAnPethGlobalObjects    OBJECT IDENTIFIER
        ::=  {  zxAnPethObjects  1  }

    zxAnPethPsePmMode OBJECT-TYPE
        SYNTAX      INTEGER
        {
            none ( 1 ) ,
            staticPowerWithPriority ( 2 ) ,
            dynamicPowerWithPriority ( 3 ) ,
            staticPowerWithoutPriority ( 4 ) ,
            dynamicPowerWithoutPriority ( 5 )
        }
        MAX-ACCESS  read-write
        STATUS      current
        DESCRIPTION
            "The power management mode. Possible values are:
             none (1) - Power management is not performed by default,
                        The user must power-up the port manually.
             staticPowerWithPriority    (2)- Power is budgeted staticly base
                                             on the priority.
             dynamicPowerWithPriority   (3)- Power is budgeted base on the load
                                             and priority.
             staticPowerWithoutPriority (4)- Same as staticPowerWithPriority
                                             except the priority
             dynamicPowerWithoutPriority(5)- Same as dynamicPowerWithPriority
                                             except the priority."
        ::= { zxAnPethGlobalObjects 1}

    zxAnPethPseActualCurrent OBJECT-TYPE
        SYNTAX      Integer32
        UNITS       "mA"
        MAX-ACCESS  read-only
        STATUS      current
        DESCRIPTION
            "The actual momentary current."
        ::= { zxAnPethGlobalObjects 2 }

    zxAnPethPseActualVoltage OBJECT-TYPE
        SYNTAX      Integer32
        UNITS       "0.1V"
        MAX-ACCESS  read-only
        STATUS      current
        DESCRIPTION
            "The actual momentary input line voltage."
        ::= { zxAnPethGlobalObjects 3 }

    zxAnPethPseChipTemp OBJECT-TYPE
        SYNTAX      Integer32
        UNITS       "centigrade"
        MAX-ACCESS  read-only
        STATUS      current
        DESCRIPTION
            "The temperature of the PSE chip."
        ::= { zxAnPethGlobalObjects 4 }

    zxAnPethPseChipTempAlmThresh OBJECT-TYPE
        SYNTAX      Integer32(10..250)
        UNITS       "centigrade"
        MAX-ACCESS  read-write
        STATUS      current
        DESCRIPTION
            "The temperature alarm threshold of the PSE chip."
        DEFVAL  { 120 }
        ::= { zxAnPethGlobalObjects 5 }

    zxAnPethPseChipTempTrapEnable OBJECT-TYPE
        SYNTAX      INTEGER
        {
            enabled(1),
            disabled(2)
        }
        MAX-ACCESS  read-write
        STATUS      current
        DESCRIPTION
            "Enable/disable the zxAnPethPseChipHighTempAlm and
             zxAnPethPseChipHighTempClr."
        ::= { zxAnPethGlobalObjects 6 }

    zxAnPethPseOutVoltageUpperThresh OBJECT-TYPE
        SYNTAX      Integer32(0|440..585)
        UNITS       "0.1V"
        MAX-ACCESS  read-write
        STATUS      current
        DESCRIPTION
            "The upper threshold of PSE output volts.
             The alarm should be generated when zxAnPethPseActualVoltage
             exceeds this threshold.
             zxAnPethPseOutVoltageUpperThresh must be larger than
             zxAnPethPseOutVoltageLowerThresh.
             If it is 0, no alarm reported to manager."
        ::= { zxAnPethGlobalObjects 7 }

    zxAnPethPseOutVoltageLowerThresh OBJECT-TYPE
        SYNTAX      Integer32(0|440..585)
        UNITS       "0.1V"
        MAX-ACCESS  read-write
        STATUS      current
        DESCRIPTION
            "The lower threshold of PSE output volts.
             The alarm should be generated when zxAnPethPseActualVoltage is
             lower than this threshold.
             zxAnPethPseOutVoltageLowerThresh must be less than
             zxAnPethPseOutVoltageUpperThresh.
             If it is 0, no alarm reported to manager."
        ::= { zxAnPethGlobalObjects 8 }

    zxAnPethPseFirmwareVersion OBJECT-TYPE
        SYNTAX      DisplayString(SIZE(1..32))
        MAX-ACCESS  read-only
        STATUS      current
        DESCRIPTION
            "The PSE firmware version."
        ::= { zxAnPethGlobalObjects 9 }

    zxAnPethMainPsePowerLimit OBJECT-TYPE
        SYNTAX      Integer32(1..65535)
        UNITS       "0.1Watts"
        MAX-ACCESS  read-write
        STATUS      current
        DESCRIPTION
            "The power threshhold of PSE output."
        ::= { zxAnPethGlobalObjects 10 }

    zxAnPethMainPsePowerUsageThresh OBJECT-TYPE
        SYNTAX      Integer32(0..65535)
        UNITS       "0.1Watts"
        MAX-ACCESS  read-write
        STATUS      current
        DESCRIPTION
            "The PSE power usage threshold.

             When pethMainPseConsumptionPower is larger than
             zxAnPethMainPsePowerUsageThresh, pethMainPowerUsageOnNotification
             will be sent.

             Value 0 means that pethMainPowerUsageOnNotification is disabled.

             Note: zxAnPethMainPsePowerUsageThresh must be less than
             zxAnPethMainPsePowerLimit."
        ::= { zxAnPethGlobalObjects 11 }

--------------------------------------------------------------------------------
-- 2.PSE Port Information
--------------------------------------------------------------------------------

    zxAnPethPsePortTable OBJECT-TYPE
        SYNTAX SEQUENCE OF ZxAnPethPsePortEntry
        MAX-ACCESS not-accessible
        STATUS current
        DESCRIPTION
            "Peth Port Table"
        ::= { zxAnPethObjects 2 }

    zxAnPethPsePortEntry OBJECT-TYPE
        SYNTAX ZxAnPethPsePortEntry
        MAX-ACCESS not-accessible
        STATUS current
        DESCRIPTION
            "Peth Port Entry"
        INDEX { ifIndex }
        ::= { zxAnPethPsePortTable 1 }

    ZxAnPethPsePortEntry ::= SEQUENCE {
        zxAnPethPsePortForcePowerEnable  INTEGER,
        zxAnPethPsePortActualVoltage     Integer32,
        zxAnPethPsePortActualCurrent     Integer32,
        zxAnPethPsePortActualPower       Integer32,
        zxAnPethPsePortMaxPower          INTEGER,
        zxAnPethPsePortDetectionType     INTEGER,
        zxAnPethPsePortWorkMode          INTEGER,
        zxAnPethPsePortReset             INTEGER,
        zxAnPethPsePortOperStatus        INTEGER,
        zxAnPethPsePortDetailInfo        DisplayString,
        zxAnPethPsePortTrapEnable        INTEGER
    }

    zxAnPethPsePortForcePowerEnable OBJECT-TYPE
        SYNTAX INTEGER
        {
            enabled  ( 1 ) ,
            disabled ( 2 )
        }
        MAX-ACCESS read-write
        STATUS current
        DESCRIPTION
            "Enable/disable force power on this interface.
            and force power on the specified port without detection."
        ::= { zxAnPethPsePortEntry 1 }

    zxAnPethPsePortActualVoltage OBJECT-TYPE
        SYNTAX  Integer32
        UNITS   "0.1V"
        MAX-ACCESS read-only
        STATUS current
        DESCRIPTION
            "The actual voltage of this port."
        ::= { zxAnPethPsePortEntry 2 }

    zxAnPethPsePortActualCurrent  OBJECT-TYPE
        SYNTAX  Integer32
        UNITS   "mA"
        MAX-ACCESS read-only
        STATUS current
        DESCRIPTION
            "The actual current of this port."
        ::= { zxAnPethPsePortEntry 3 }

    zxAnPethPsePortActualPower OBJECT-TYPE
        SYNTAX  Integer32
        UNITS   "0.1W"
        MAX-ACCESS read-only
        STATUS current
        DESCRIPTION
            "The actual power of this port."
        ::= { zxAnPethPsePortEntry 4 }

    zxAnPethPsePortMaxPower OBJECT-TYPE
        SYNTAX     INTEGER(0..300)
        UNITS      "0.1W"
        MAX-ACCESS read-write
        STATUS     current
        DESCRIPTION
            "The maximum power of this port."
        ::= { zxAnPethPsePortEntry 5 }

    zxAnPethPsePortDetectionType OBJECT-TYPE
        SYNTAX INTEGER
        {
            noDetection     (1),
            legacyOnly      (2),
            fourPointOnly   (3),
            fourPointLegacy (4),
            twoPointOnly    (5),
            twoPointLegacy  (6)
        }
        MAX-ACCESS read-write
        STATUS current
        DESCRIPTION
            "Describes the detection type of the port PD detection.
            NoDetection indicates force power on the port without detection,
            LegacyOnly indicates legacy detection only,
            FourPointOnly indicates IEEE 802.3af 4-Point Detection only,
            FourPointLegacy indicates IEEE 802.3af 4-Point followed by Legacy,
            TwoPointOnly indicates IEEE 802.3af 2-Point Detection only,
            TwoPointLegacy indicates IEEE 802.3af 2-Point followed by Legacy."
        ::= { zxAnPethPsePortEntry 6 }

    zxAnPethPsePortWorkMode  OBJECT-TYPE
        SYNTAX      INTEGER
        {
            ieee8023af(1),
            ieee8023at(2)
        }
        MAX-ACCESS  read-only
        STATUS      current
        DESCRIPTION
            "PSE port working mode."
        ::= { zxAnPethPsePortEntry 7 }

    zxAnPethPsePortReset  OBJECT-TYPE
        SYNTAX      INTEGER
        {
            reset(1)
        }
        MAX-ACCESS  read-write
        STATUS      current
        DESCRIPTION
            "Reset port."
        ::= { zxAnPethPsePortEntry 8 }

    zxAnPethPsePortOperStatus  OBJECT-TYPE
        SYNTAX      INTEGER
        {
            up(1),
            down(2)
        }
        MAX-ACCESS  read-only
        STATUS      current
        DESCRIPTION
            "PSE port operational status."
        ::= { zxAnPethPsePortEntry 9 }

    zxAnPethPsePortDetailInfo  OBJECT-TYPE
        SYNTAX      DisplayString(SIZE (0..64))
        MAX-ACCESS  read-only
        STATUS      current
        DESCRIPTION
            "PSE port detail information.
             When zxAnPethPsePortOperStatus is 'down', this object will be show
             the detail information of port."
        ::= { zxAnPethPsePortEntry 10 }

    zxAnPethPsePortTrapEnable  OBJECT-TYPE
        SYNTAX      INTEGER
        {
            enabled(1),
            disabled(2)
        }
        MAX-ACCESS  read-write
        STATUS      current
        DESCRIPTION
            "Enable/disable the zxAnPethPsePortStatusUp and
             zxAnPethPsePortStatusDown."
        ::= { zxAnPethPsePortEntry 11 }

--------------------------------------------------------------------------------
-- 3.PSE Card Information
--------------------------------------------------------------------------------

    zxAnPethPseCardTable OBJECT-TYPE
        SYNTAX SEQUENCE OF ZxAnPethPseCardEntry
        MAX-ACCESS not-accessible
        STATUS current
        DESCRIPTION
            "Peth Card Table"
        ::= { zxAnPethObjects 3 }

    zxAnPethPseCardEntry OBJECT-TYPE
        SYNTAX ZxAnPethPseCardEntry
        MAX-ACCESS not-accessible
        STATUS current
        DESCRIPTION
            "Peth Card Entry"
        INDEX
            {
                zxAnPethPseRack,
                zxAnPethPseShelf,
                zxAnPethPseSlot
            }
        ::= { zxAnPethPseCardTable 1 }

    ZxAnPethPseCardEntry ::= SEQUENCE {
        zxAnPethPseRack            Integer32,
        zxAnPethPseShelf           Integer32,
        zxAnPethPseSlot            Integer32,
        zxAnPethPseCardSupportPoe  TruthValue
    }

    zxAnPethPseRack  OBJECT-TYPE
        SYNTAX          Integer32
        MAX-ACCESS      not-accessible
        STATUS          current
        DESCRIPTION
            "Rack No."
        ::=  {  zxAnPethPseCardEntry  1  }

    zxAnPethPseShelf  OBJECT-TYPE
        SYNTAX          Integer32
        MAX-ACCESS      not-accessible
        STATUS          current
        DESCRIPTION
            "Shelf No."
        ::=  {  zxAnPethPseCardEntry  2  }

    zxAnPethPseSlot  OBJECT-TYPE
        SYNTAX          Integer32
        MAX-ACCESS      not-accessible
        STATUS          current
        DESCRIPTION
            "Card No."
        ::=  {  zxAnPethPseCardEntry  3  }

    zxAnPethPseCardSupportPoe OBJECT-TYPE
        SYNTAX      TruthValue
        MAX-ACCESS  read-only
        STATUS      current
        DESCRIPTION
            "This variable indicates whether the card supports PoE management."
        ::= { zxAnPethPseCardEntry 4 }

--------------------------------------------------------------------------------
-- 4.PDE Port Information
--------------------------------------------------------------------------------
    zxAnPethPdePortTable OBJECT-TYPE
        SYNTAX      SEQUENCE OF ZxAnPethPdePortEntry
        MAX-ACCESS  not-accessible
        STATUS      current
        DESCRIPTION
            "PDE(Power Device Equipment) port information."
        ::= { zxAnPethObjects 4 }

    zxAnPethPdePortEntry OBJECT-TYPE
        SYNTAX      ZxAnPethPdePortEntry
        MAX-ACCESS  not-accessible
        STATUS      current
        DESCRIPTION
            "PDE port entry."
        INDEX { ifIndex }
        ::= { zxAnPethPdePortTable 1 }

    ZxAnPethPdePortEntry ::= SEQUENCE {
        zxAnPethPdePortAutoCheckEnable     INTEGER,
        zxAnPethPdePortPowerSupplyStatus   INTEGER
    }

    zxAnPethPdePortAutoCheckEnable  OBJECT-TYPE
        SYNTAX      INTEGER{
            enabled(1),
            disabled(2)
        }
        MAX-ACCESS  read-write
        STATUS      current
        DESCRIPTION
            "Enable/disable to check port power status automatically."
        DEFVAL { disabled }
        ::= { zxAnPethPdePortEntry 1 }

    zxAnPethPdePortPowerSupplyStatus  OBJECT-TYPE
        SYNTAX      INTEGER{
            unknown(1),
            on(2),
            off(3)
        }
        MAX-ACCESS  read-only
        STATUS      current
        DESCRIPTION
            "The port power status."
        ::= { zxAnPethPdePortEntry 2 }

--------------------------------------------------------------------------------
--------------------------------------------------------------------------------
-- 5.Trap Objects
--------------------------------------------------------------------------------

    zxAnPethPseChipHighTempAlm NOTIFICATION-TYPE
        OBJECTS
        {
            zxAnPethPseChipTemp,
            zxAnPethPseChipTempAlmThresh
        }
        STATUS             current
        DESCRIPTION
            "The PSE chip temperature has exceeded normal operating temperature
             zxAnPethPseChipTempAlmThresh.
             The zxAnPethPseChipTemp object identifies the current status."
        ::= { zxAnPethTrapObjects 1 }

    zxAnPethPseChipHighTempClr NOTIFICATION-TYPE
        OBJECTS
        {
            zxAnPethPseChipTemp,
            zxAnPethPseChipTempAlmThresh
        }
        STATUS             current
        DESCRIPTION
            "The PSE chip temperature has returned to normal operating
             temperature zxAnPethPseChipTempAlmThresh.
             The zxAnPethPseChipTemp object identifies the current status."
        ::= { zxAnPethTrapObjects 2 }

    zxAnPethPsePortStatusUp      NOTIFICATION-TYPE
        OBJECTS
        {
            zxAnPethPsePortOperStatus,
            zxAnPethPsePortOperStatusDetail
        }
        STATUS  current
        DESCRIPTION
            "A zxAnPethPsePortStatusUp is sent when zxAnPethPsePortOperStatus
             changes to up."
        ::= { zxAnPethTrapObjects 3 }

    zxAnPethPsePortStatusDown      NOTIFICATION-TYPE
        OBJECTS
        {
            zxAnPethPsePortOperStatus,
            zxAnPethPsePortOperStatusDetail
        }
        STATUS  current
        DESCRIPTION
            "A zxAnPethPsePortStatusDown is sent when zxAnPethPsePortOperStatus
             changes to down."
        ::= { zxAnPethTrapObjects 4 }

    zxAnPethPseOverVoltageAlm  NOTIFICATION-TYPE
        OBJECTS
        {
            zxAnPethPseActualVoltage,
            zxAnPethPseVoltageUpperThresh
        }
        STATUS  current
        DESCRIPTION
            "It indicates that the PSE voltage is over-voltage."
        ::= { zxAnPethTrapObjects 5 }

    zxAnPethPseOverVoltageClr  NOTIFICATION-TYPE
        OBJECTS
        {
            zxAnPethPseActualVoltage,
            zxAnPethPseVoltageUpperThresh
        }
        STATUS  current
        DESCRIPTION
            "It indicates that the over-voltage fault is cleared."
        ::= { zxAnPethTrapObjects 6 }

    zxAnPethPseUnderVoltageAlm  NOTIFICATION-TYPE
        OBJECTS
        {
            zxAnPethPseActualVoltage,
            zxAnPethPseVoltageLowerThresh
        }
        STATUS  current
        DESCRIPTION
            "It indicates that the PSE voltage is under-voltage."
        ::= { zxAnPethTrapObjects 7 }

    zxAnPethPseUnderVoltageClr   NOTIFICATION-TYPE
        OBJECTS
        {
            zxAnPethPseActualVoltage,
            zxAnPethPseVoltageLowerThresh
        }
        STATUS  current
        DESCRIPTION
            "It indicates that the under-voltage fault is cleared."
        ::= { zxAnPethTrapObjects 8 }

    zxAnPethPdePortPowerOffAlm NOTIFICATION-TYPE
        OBJECTS
        {
            zxAnPethPdePortPowerSupplyStatus
        }
        STATUS  current
        DESCRIPTION
            "A zxAnPethPdePortPowerOffAlm is sent when
             zxAnPethPdePortPowerStatus is off(2)."
        ::= { zxAnPethTrapObjects 9 }

    zxAnPethPdePortPowerOffClr NOTIFICATION-TYPE
        OBJECTS
        {
            zxAnPethPdePortPowerSupplyStatus
        }
        STATUS  current
        DESCRIPTION
            "A zxAnPethPdePortPowerOffClr is sent when
             zxAnPethPdePortPowerOffAlm is cleared."
        ::= { zxAnPethTrapObjects 10 }
END
