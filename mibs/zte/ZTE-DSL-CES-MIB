ZTE-DSL-CES-MIB DEFINITIONS ::= BEGIN
IMPORTS
        MODULE-IDENTITY, OBJECT-TYPE,NOTIFICATION-TYPE      FROM SNMPv2-SMI
        RowStatus                                           FROM SNMPv2-TC
        atmfCESCbrIndex,atmfCESConfEntry,atmfCESStatsEntry  FROM ATMF-CES
        entPhysicalIndex  FROM ENTITY-MIB
        zxDsl             FROM ZTE-DSL-MIB;


zxAdslCesMib MODULE-IDENTITY
    LAST-UPDATED "200404151500Z"
    ORGANIZATION "ZTE Corporation"
    CONTACT-INFO ""
    DESCRIPTION  "This MIB defines zte dsl CES(Circuit Emulation Service)
                    managed objects. "
    ::= {zxDsl 5}


zxDslCesObjects     OBJECT IDENTIFIER ::= {zxAdslCesMib 1}
zxDslCesTrapObjects OBJECT IDENTIFIER ::= {zxAdslCesMib 2}



-- CES BasicInformation Table

zxDslCesBasicInfoTable  OBJECT-TYPE
    SYNTAX SEQUENCE OF zxDslCesBasicInfoEntry
    MAX-ACCESS      not-accessible
    STATUS          current
    DESCRIPTION
        "CES Basic infomation Table"
    ::= { zxDslCesObjects 1 }

zxDslCesBasicInfoEntry  OBJECT-TYPE
    SYNTAX      zxDslCesBasicInfoEntry
    MAX-ACCESS  not-accessible
    STATUS      current
    DESCRIPTION
        "entry in zxDslCesBasicInfo table"
    INDEX   {  entPhysicalIndex  }
    ::= { zxDslCesBasicInfoTable 1 }

zxDslCesBasicInfoEntry ::= SEQUENCE {
    zxDslCesBasicInfoCbrClockMode   INTEGER,
    zxDslCesBasicInfoCbrTimingVpi   INTEGER,
    zxDslCesBasicInfoCbrTimingVci   INTEGER,
    zxDslCesBasicInfoCbrAlarmSwitch INTEGER,
    zxDslCesAlarmInfo               INTEGER,
    zxDslCesBasicInfoRowStatus      RowStatus
    }

zxDslCesBasicInfoCbrClockMode OBJECT-TYPE
    SYNTAX INTEGER {
        synchronous(1),
        srts(2),
        adaptive(3)
    }
    MAX-ACCESS read-create
    STATUS current
    DESCRIPTION
        "Define if DSx/Ex service clocking mode. This maps into
        transmit clock source of CBR interface.
        For structured modes this value, if present, must be set to
        synchronous(1)."
    DEFVAL { synchronous }
    ::= { zxDslCesBasicInfoEntry 1 }

zxDslCesBasicInfoCbrTimingVpi OBJECT-TYPE
    SYNTAX INTEGER
    MAX-ACCESS read-create
    STATUS current
    DESCRIPTION
        "timer VPI"
    ::= { zxDslCesBasicInfoEntry 2 }

zxDslCesBasicInfoCbrTimingVci OBJECT-TYPE
    SYNTAX INTEGER
    MAX-ACCESS read-create
    STATUS current
    DESCRIPTION
        "timer VCI"
    ::= { zxDslCesBasicInfoEntry 3 }

zxDslCesBasicInfoCbrAlarmSwitch OBJECT-TYPE
    SYNTAX INTEGER {
        enable(1),
        disable(0)
    }
    MAX-ACCESS read-create
    STATUS current
    DESCRIPTION
        "Alarm switch,if set to disable(2),alarm will be not notified."
    DEFVAL { disable }
    ::= { zxDslCesBasicInfoEntry 4 }

zxDslCesAlarmInfo OBJECT-TYPE
    SYNTAX INTEGER
    MAX-ACCESS read-create
    STATUS current
    DESCRIPTION
        "AlarmInfo is defined for CES trap."
    ::= { zxDslCesBasicInfoEntry 5 }


zxDslCesBasicInfoRowStatus OBJECT-TYPE
    SYNTAX RowStatus
    MAX-ACCESS read-create
    STATUS current
    DESCRIPTION
        "This variable is defined for CES agent table operation."
    ::= { zxDslCesBasicInfoEntry 6 }



-- CES Configuration Table

zxDslCesConfTable OBJECT-TYPE
    SYNTAX SEQUENCE OF zxDslCesConfEntry
    MAX-ACCESS not-accessible
    STATUS current
    DESCRIPTION
        "The CES configuration table used to manage interworking
        between CBR interfaces or channels and ATM Virtual Channel
        Links (VCLs). The reverse mapping is shown in the
        atmfCESMappingTable."
    ::= { zxDslCesObjects 2 }

zxDslCesConfEntry OBJECT-TYPE
    SYNTAX zxDslCesConfEntry
    MAX-ACCESS not-accessible
    STATUS current
    DESCRIPTION
        "An entry in the CES configuration table. There is one
        entry in the table per CES entity, mapping one CBR
        interface, channel, or bundle to an ATM VCL.
        Creation of a row in this table with a non-zero
        atmfCESAtmIndex causes a corresponding entry in the
        atmVclTable of the ATM-MIB (RFC1695) to be created."
    AUGMENTS { atmfCESConfEntry }
    ::= { zxDslCesConfTable 1 }

zxDslCesConfEntry ::= SEQUENCE {
    zxDslCesConfCbrLine         INTEGER,
    zxDslCesConfTSMapBitmap     OCTET STRING (SIZE (8)),
    zxDslCesConfCbrVpi          INTEGER,
    zxDslCesConfCbrVci          INTEGER,
    zxDslCesConfLineDirection   INTEGER,
    zxDslCesConfAALType         INTEGER,
    zxDslCesConfPvcBinding      INTEGER,
    zxDslCesConfRowStatus       RowStatus
     }

zxDslCesConfCbrLine OBJECT-TYPE
    SYNTAX INTEGER (0..15)
    MAX-ACCESS read-create
    STATUS current
    DESCRIPTION
        "port no. on STUCB card"
    ::= { zxDslCesConfEntry 1 }

zxDslCesConfTSMapBitmap OBJECT-TYPE
    -- SYNTAX PortList
    SYNTAX OCTET STRING (SIZE (8))
    MAX-ACCESS read-create
    STATUS current
    DESCRIPTION
        "each bit represents one time slot"
    ::= { zxDslCesConfEntry 2 }

zxDslCesConfCbrVpi OBJECT-TYPE
    SYNTAX INTEGER
    MAX-ACCESS read-create
    STATUS current
    DESCRIPTION
        "VPI of CES_PVC on STUCB card."
    ::= { zxDslCesConfEntry 3 }

zxDslCesConfCbrVci OBJECT-TYPE
    SYNTAX INTEGER
    MAX-ACCESS read-create
    STATUS current
    DESCRIPTION
        "VCI of CES_PVC on STUCB card."
    ::= { zxDslCesConfEntry 4 }

zxDslCesConfLineDirection OBJECT-TYPE
    SYNTAX INTEGER {
        double(0),
        rx(1),
        tx(2)
    }
    MAX-ACCESS read-create
    STATUS current
    DESCRIPTION
        "Line Direction"
    ::= { zxDslCesConfEntry 5 }

zxDslCesConfAALType OBJECT-TYPE
    SYNTAX INTEGER{
        AAL1(0),
        AAL5(1),
        CBRAAL0(2)
    }
    MAX-ACCESS read-create
    STATUS current
    DESCRIPTION
        "AAL Type"
    ::= { zxDslCesConfEntry 6 }

zxDslCesConfPvcBinding OBJECT-TYPE
    SYNTAX INTEGER {
        no(0),
        yes(1)
    }
    MAX-ACCESS read-create
    STATUS current
    DESCRIPTION
        "Pvc Binding"
    ::= { zxDslCesConfEntry 7 }


zxDslCesConfRowStatus OBJECT-TYPE
    SYNTAX INTEGER {
        passive(0),
        active(1)
        }
    MAX-ACCESS read-create
    STATUS current
    DESCRIPTION
        "This variable is defined for CES agent table operation."
    ::= { zxDslCesConfEntry 8 }



-- CES Trap definition

zxDslCesAlarmDataFifoOverrun NOTIFICATION-TYPE
    OBJECTS {
        zxdslcesbasicinfomodules
        }
    STATUS  current
    DESCRIPTION
        "Zi90500DataFifoOverrun"
    ::= { zxDslCesTrapObjects 1 }

zxDslCesAlarmEventSdlError NOTIFICATION-TYPE
    OBJECTS {
        zxdslcesbasicinfomodule
        }
    STATUS  current
    DESCRIPTION
        "Zi90500EventSdlError"
    ::= { zxDslCesTrapObjects 2 }


zxDslCesAlarmRxSarWriteOverrun NOTIFICATION-TYPE
    OBJECTS {
        zxdslcesbasicinfomodule
        }
    STATUS  current
    DESCRIPTION
        "Zi90500RxSarWriteOverrun"
    ::= { zxDslCesTrapObjects 3 }


zxDslCesAlarmRxSarWriteUnderrun NOTIFICATION-TYPE
    OBJECTS {
        zxdslcesbasicinfomodule
        }
    STATUS  current
    DESCRIPTION
        "Zi90500RxSarWriteUnderrun"
    ::= { zxDslCesTrapObjects 4 }

zxDslCesAlarmPointerOutRange NOTIFICATION-TYPE
    OBJECTS {
        zxdslcesbasicinfomodule
        }
    STATUS  current
    DESCRIPTION
        "Zi90500PointerOutRange"
    ::= { zxDslCesTrapObjects 5 }

zxDslCesAlarmPoniterParityError NOTIFICATION-TYPE
    OBJECTS {
        zxdslcesbasicinfomodule
        }
    STATUS  current
    DESCRIPTION
        "Zi90500PoniterParityError"
    ::= { zxDslCesTrapObjects 6 }

zxDslCesAlarmAAL1SeqNumError NOTIFICATION-TYPE
    OBJECTS {
        zxdslcesbasicinfomodule
        }
    STATUS  current
    DESCRIPTION
        "Zi90500AAL1SeqNumError"
    ::= { zxDslCesTrapObjects 7 }

zxDslCesAlarmAAL1CRCError NOTIFICATION-TYPE
    OBJECTS {
        zxdslcesbasicinfomodule
        }
    STATUS  current
    DESCRIPTION
        "Zi90500AAL1CRCError"
    ::= { zxDslCesTrapObjects 8 }

zxDslCesAlarmAAL1ParityError NOTIFICATION-TYPE
    OBJECTS {
        zxdslcesbasicinfomodule
        }
    STATUS  current
    DESCRIPTION
        "Zi90500AAL1ParityError"
    ::= { zxDslCesTrapObjects 9 }

zxDslCesAlarmUTOPIAFifoOverrun NOTIFICATION-TYPE
    OBJECTS {
        zxdslcesbasicinfomodule
        }
    STATUS  current
    DESCRIPTION
        "Zi90500UTOPIAFifoOverrun"
    ::= { zxDslCesTrapObjects 10 }

zxDslCesAlarmDataCellFifoOverrun NOTIFICATION-TYPE
    OBJECTS {
        zxdslcesbasicinfomodule
        }
    STATUS  current
    DESCRIPTION
        "Zi90500DataCellFifoOverrun"
    ::= { zxDslCesTrapObjects 11 }

zxDslCesAlarmTDMReadUnderrun NOTIFICATION-TYPE
    OBJECTS {
        zxdslcesbasicinfomodule
        }
    STATUS  current
    DESCRIPTION
        "Zi90500TDMReadUnderrun"
    ::= { zxDslCesTrapObjects 12 }

zxDslCesAlarmTDMOutBandwidth NOTIFICATION-TYPE
    OBJECTS {
        zxdslcesbasicinfomodule
        }
    STATUS  current
    DESCRIPTION
        "Zi90500TDMOutBandwidth"
    ::= { zxDslCesTrapObjects 13 }

zxDslCesAlarmTDMClockAbsent NOTIFICATION-TYPE
    OBJECTS {
        zxdslcesbasicinfomodule
        }
    STATUS  current
    DESCRIPTION
        "Zi90500TDMClockAbsent"
    ::= { zxDslCesTrapObjects 14 }


END
