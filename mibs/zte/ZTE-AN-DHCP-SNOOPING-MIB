ZTE-AN-DHCP-SNOOPING-MIB DEFINITIONS ::= BEGIN
IMPORTS
    OBJECT-TYPE, MODULE-IDENTITY, IpAddress, Counter32, Counter64,
    Gauge32, Integer32                           FROM SNMPv2-SMI
    MacAddress, DisplayString,RowStatus          FROM SNMPv2-TC
    InetAddress,InetAddressType,InetAddressPrefixLength
                                                 FROM INET-ADDRESS-MIB
    zxAn, ZxAnIfindex, VlanId                    FROM ZTE-AN-TC-MIB;

    zxAnDhcpSnoopingMib   MODULE-IDENTITY
         LAST-UPDATED    "0612060000Z"  -- july. 23, 2005
        ORGANIZATION    "zte Telcom Co. Ltd."
        CONTACT-INFO    "E-mail: shen.yuyang@zte.com.cn,
                         E-mail: suchunshan@zte.com.cn"
        DESCRIPTION     "This MIB defines DHCP Snooping managed objects for
                         Access Node."
        ::= { zxAn 51 }

    zxAnDhcpSnoopingMIBNotifs
        OBJECT IDENTIFIER ::= { zxAnDhcpSnoopingMib 0 }
    zxAnDhcpSnoopingMIBObjects
        OBJECT IDENTIFIER ::= { zxAnDhcpSnoopingMib 1 }

    zxAnDsGlobal
        OBJECT IDENTIFIER ::= { zxAnDhcpSnoopingMIBObjects 1 }
    zxAnDsVlan
        OBJECT IDENTIFIER ::= { zxAnDhcpSnoopingMIBObjects 2 }
    zxAnDsBinds
        OBJECT IDENTIFIER ::= { zxAnDhcpSnoopingMIBObjects 3 }
    zxAnDsInterface
        OBJECT IDENTIFIER ::= { zxAnDhcpSnoopingMIBObjects 4 }
    zxAnDsShow
        OBJECT IDENTIFIER ::= { zxAnDhcpSnoopingMIBObjects 5 }
    zxAnDsUserInterface
        OBJECT IDENTIFIER ::= { zxAnDhcpSnoopingMIBObjects 6 }
    zxAnDsv6Show
        OBJECT IDENTIFIER ::= { zxAnDhcpSnoopingMIBObjects 7 }
    zxAnDsStat
        OBJECT IDENTIFIER ::= { zxAnDhcpSnoopingMIBObjects 8 }

-- the global group

    zxAnDsGlobalEnable OBJECT-TYPE
        SYNTAX      INTEGER
            {
                enable(1),
                disable(2)
            }
        MAX-ACCESS  read-write
        STATUS      current
        DESCRIPTION
        "enable = 1, disable = 2"
        DEFVAL { disable }
        ::= { zxAnDsGlobal 1 }

    zxAnDsv6GlobalEnable OBJECT-TYPE
        SYNTAX      INTEGER
            {
                enable(1),
                disable(2)
            }
        MAX-ACCESS  read-write
        STATUS      current
        DESCRIPTION
        "DHCPv6 Snooping global status."
        DEFVAL { disable }
        ::= { zxAnDsGlobal 2 }

-- the vlan group

    zxAnDsVlanTable OBJECT-TYPE
        SYNTAX      SEQUENCE OF ZxAnDsVlanEntry
        MAX-ACCESS  not-accessible
        STATUS      current
        DESCRIPTION
        "DHCP Snooping VLAN table."
        ::= { zxAnDsVlan 1 }

    zxAnDsVlanEntry OBJECT-TYPE
        SYNTAX      ZxAnDsVlanEntry
        MAX-ACCESS  not-accessible
        STATUS      current
        DESCRIPTION
        "DHCP Snooping VLAN entry."
        INDEX { zxAnDsVlanIndex }
        ::= { zxAnDsVlanTable 1 }

    ZxAnDsVlanEntry ::= SEQUENCE {
        zxAnDsVlanIndex      VlanId,
        zxAnDsVlanEnable     INTEGER,
        zxAnDsv6VlanEnable   INTEGER
        }

    zxAnDsVlanIndex OBJECT-TYPE
        SYNTAX      VlanId
        MAX-ACCESS  not-accessible
        STATUS      current
        DESCRIPTION
        "This object indicates the VLAN number on which DHCP Snooping
         feature is configured."
    ::= { zxAnDsVlanEntry 1 }

    zxAnDsVlanEnable OBJECT-TYPE
        SYNTAX      INTEGER
            {
                enable(1),
                disable(2)
            }
        MAX-ACCESS  read-write
        STATUS      current
        DESCRIPTION
        "This object indicates whether DHCP Snooping is enabled in
         this VLAN.
         If this object is set to 'enable', DHCP Snooping is enabled.
         If this object is set to 'disable', DHCP Snooping is disabled."
    DEFVAL { disable }
    ::= { zxAnDsVlanEntry 2 }

    zxAnDsv6VlanEnable OBJECT-TYPE
        SYNTAX      INTEGER
            {
                enable(1),
                disable(2)
            }
        MAX-ACCESS  read-write
        STATUS      current
        DESCRIPTION
        "DHCPv6 Snooping enabled in this vlan."
        DEFVAL { disable }
    ::= { zxAnDsVlanEntry 3 }

-- the interface group

    zxAnDsInterfaceTable OBJECT-TYPE
        SYNTAX      SEQUENCE OF ZxAnDsInterfaceEntry
        MAX-ACCESS  not-accessible
        STATUS      current
        DESCRIPTION
        "A table provides the DHCP snooping port type set."
        ::= { zxAnDsInterface 1 }

    zxAnDsInterfaceEntry OBJECT-TYPE
        SYNTAX      ZxAnDsInterfaceEntry
        MAX-ACCESS  not-accessible
        STATUS      current
        DESCRIPTION
        "A row instance of port type set."
        INDEX { zxAnDsInterfaceIndex }
        ::= { zxAnDsInterfaceTable 1 }

    ZxAnDsInterfaceEntry ::= SEQUENCE {
      zxAnDsInterfaceIndex    ZxAnIfindex,
        zxAnDsInterfaceType     INTEGER,
        zxAnDsv6InterfaceType   INTEGER
        }

    zxAnDsInterfaceIndex OBJECT-TYPE
        SYNTAX      ZxAnIfindex
        MAX-ACCESS  not-accessible
        STATUS      current
        DESCRIPTION
        "physical interface, like gei_x"
        ::= { zxAnDsInterfaceEntry 1 }

    zxAnDsInterfaceType OBJECT-TYPE
        SYNTAX    INTEGER
            {
                trust(1),
                untrust(2)
            }
        MAX-ACCESS  read-write
        STATUS      current
        DESCRIPTION
        "when the physical interface connected to dhcp server,
      then it must be set trust"
        DEFVAL { untrust }
        ::= { zxAnDsInterfaceEntry 2 }

    zxAnDsv6InterfaceType OBJECT-TYPE
        SYNTAX    INTEGER
            {
                trust(1),
                untrust(2)
            }
        MAX-ACCESS  read-write
        STATUS      current
        DESCRIPTION
        "when the physical interface connected to dhcpv6 server,
         then it must be set trust"
        DEFVAL { untrust }
        ::= { zxAnDsInterfaceEntry 3 }

-- the show group

    zxAnDsPortBindViewTable OBJECT-TYPE
        SYNTAX      SEQUENCE OF ZxAnDsPortBindViewEntry
        MAX-ACCESS  not-accessible
        STATUS      current
        DESCRIPTION
        "show dhcp snooping bind table by port. "
        ::= { zxAnDsShow 1 }

    zxAnDsPortBindViewEntry OBJECT-TYPE
        SYNTAX      ZxAnDsPortBindViewEntry
        MAX-ACCESS  not-accessible
        STATUS      current
        DESCRIPTION
        "View dhcp snooping bind entry. "
        INDEX { zxAnDsInterfaceIndex,
                zxAnDsPortBindViewMac,
                zxAnDsPortBindViewVlan }
        ::= { zxAnDsPortBindViewTable 1 }

    ZxAnDsPortBindViewEntry ::= SEQUENCE {
        zxAnDsPortBindViewMac            MacAddress,
        zxAnDsPortBindViewVlan           INTEGER,
        zxAnDsPortBindViewIp             IpAddress,
        zxAnDsPortBindViewType           INTEGER,
        zxAnDsPortBindViewTime           DisplayString,
        zxAnDsPortBindViewSvlan          INTEGER,
        zxAnDsPortBindViewRowStatus      RowStatus
        }

    zxAnDsPortBindViewMac OBJECT-TYPE
        SYNTAX      MacAddress
        MAX-ACCESS  not-accessible
        STATUS      current
        DESCRIPTION
        "MAC address for DHCP snooping."
        ::= { zxAnDsPortBindViewEntry 1 }

    zxAnDsPortBindViewVlan OBJECT-TYPE
        SYNTAX      INTEGER(0..4096)
        MAX-ACCESS  not-accessible
        STATUS      current
        DESCRIPTION
         "It indicates the static configuration for binding snooping
              when the value is '0'."
        ::= { zxAnDsPortBindViewEntry 2 }

    zxAnDsPortBindViewIp OBJECT-TYPE
        SYNTAX      IpAddress
        MAX-ACCESS  read-create
        STATUS      current
        DESCRIPTION
        "IP address for DHCP snooping."
        ::= { zxAnDsPortBindViewEntry 3 }

    zxAnDsPortBindViewType OBJECT-TYPE
        SYNTAX      INTEGER
              {
                dynamic(0),
                static(1)
            }
        MAX-ACCESS  read-only
        STATUS      current
        DESCRIPTION
        "DHCP snooping binding type."
        ::= { zxAnDsPortBindViewEntry 4 }

    zxAnDsPortBindViewTime OBJECT-TYPE
        SYNTAX      DisplayString (SIZE (0..19))
        MAX-ACCESS  read-create
        STATUS      current
        DESCRIPTION
        "The lease time.The format is
              yyyy-mm-dd HH:MM:SS.For example,  2001-01-01 02:22:33."
        ::= { zxAnDsPortBindViewEntry 5 }

    zxAnDsPortBindViewSvlan OBJECT-TYPE
        SYNTAX      INTEGER(0..4096)
        MAX-ACCESS  read-only
        STATUS      current
        DESCRIPTION
         "SVLAN"
        ::= { zxAnDsPortBindViewEntry 6 }

    zxAnDsPortBindViewRowStatus OBJECT-TYPE
        SYNTAX      RowStatus
        MAX-ACCESS  read-create
        STATUS      current
        DESCRIPTION
            "This object indicates the status of this entry."
        ::= { zxAnDsPortBindViewEntry 20 }

    zxAnDsShowGlobalObjects OBJECT IDENTIFIER  ::= { zxAnDsShow 50 }

    zxAnDsPortBindOnlineUserNum  OBJECT-TYPE
        SYNTAX      INTEGER(0..32768)
        MAX-ACCESS  read-only
        STATUS      current
        DESCRIPTION
            "The number of online user which are bound in DHCP snooping."
        ::= {zxAnDsShowGlobalObjects 1}

-- dhcpv6 show group

    zxAnDsv6PortBindViewTable OBJECT-TYPE
        SYNTAX      SEQUENCE OF ZxAnDsv6PortBindViewEntry
        MAX-ACCESS  not-accessible
        STATUS      current
        DESCRIPTION
        "Show dhcpv6 snooping bind table by port. "
        ::= { zxAnDsv6Show 1 }

    zxAnDsv6PortBindViewEntry OBJECT-TYPE
        SYNTAX      ZxAnDsv6PortBindViewEntry
        MAX-ACCESS  not-accessible
        STATUS      current
        DESCRIPTION
        "View dhcpv6 snooping bind entry. "
        INDEX { zxAnDsInterfaceIndex,
                zxAnDsv6PortBindViewMac,
                zxAnDsv6PortBindViewVlan }
        ::= { zxAnDsv6PortBindViewTable 1 }

    ZxAnDsv6PortBindViewEntry ::= SEQUENCE {
        zxAnDsv6PortBindViewMac            MacAddress,
        zxAnDsv6PortBindViewVlan           INTEGER,
        zxAnDsv6PortBindViewIp             InetAddress,
        zxAnDsv6PortBindViewType           INTEGER,
        zxAnDsv6PortBindViewTime           DisplayString,
        zxAnDsv6PortBindViewIpPfxLen       InetAddressPrefixLength,
        zxAnDsv6PortBindViewSvlan          INTEGER,
        zxAnDsv6PortBindViewRowStatus      RowStatus
        }


    zxAnDsv6PortBindViewMac OBJECT-TYPE
        SYNTAX      MacAddress
        MAX-ACCESS  not-accessible
        STATUS      current
        DESCRIPTION
        "Mac address."
        ::= { zxAnDsv6PortBindViewEntry 1 }

    zxAnDsv6PortBindViewVlan OBJECT-TYPE
        SYNTAX      INTEGER(0..4096)
        MAX-ACCESS  not-accessible
        STATUS      current
        DESCRIPTION
        "It indicates the static configuration for binding snooping
              when the value is '0'."
        ::= { zxAnDsv6PortBindViewEntry 2 }

    zxAnDsv6PortBindViewIp OBJECT-TYPE
        SYNTAX      InetAddress
        MAX-ACCESS  read-create
        STATUS      current
        DESCRIPTION
        "Alocated IP address of a DHCP client host."
        ::= { zxAnDsv6PortBindViewEntry 3 }

    zxAnDsv6PortBindViewType OBJECT-TYPE
        SYNTAX      INTEGER
              {
                dynamic(0),
                static(1)
            }
        MAX-ACCESS  read-only
        STATUS      current
        DESCRIPTION
        "The type of a DHCP client's binding."
        ::= { zxAnDsv6PortBindViewEntry 4 }

    zxAnDsv6PortBindViewTime OBJECT-TYPE
        SYNTAX      DisplayString (SIZE (0..19))
        MAX-ACCESS  read-create
        STATUS      current
        DESCRIPTION
        "Lease time of a DHCP client's binding.The format is
              yyyy-mm-dd HH:MM:SS.For example,  2001-01-01 02:22:33."
        ::= { zxAnDsv6PortBindViewEntry 5 }

     zxAnDsv6PortBindViewIpPfxLen OBJECT-TYPE
        SYNTAX      InetAddressPrefixLength
        MAX-ACCESS  read-create
        STATUS      current
        DESCRIPTION
        "The ipv6 prefix length."
        ::= { zxAnDsv6PortBindViewEntry 6 }

    zxAnDsv6PortBindViewSvlan OBJECT-TYPE
        SYNTAX      INTEGER(0..4096)
        MAX-ACCESS  read-only
        STATUS      current
        DESCRIPTION
         "SVLAN"
        ::= { zxAnDsv6PortBindViewEntry 7 }

    zxAnDsv6PortBindViewRowStatus OBJECT-TYPE
        SYNTAX      RowStatus
        MAX-ACCESS  read-create
        STATUS      current
        DESCRIPTION
            "This object indicates the status of this entry."
        ::= { zxAnDsv6PortBindViewEntry 20 }

-- the user interface group

    zxAnDsUserInterfaceTable OBJECT-TYPE
        SYNTAX      SEQUENCE OF ZxAnDsUserInterfaceEntry
        MAX-ACCESS  not-accessible
        STATUS      current
        DESCRIPTION
        "A table provides the DHCP snooping user interface set."
        ::= { zxAnDsUserInterface 1 }

    zxAnDsUserInterfaceEntry OBJECT-TYPE
        SYNTAX      ZxAnDsUserInterfaceEntry
        MAX-ACCESS  not-accessible
        STATUS      current
        DESCRIPTION
        "A row instance of user interface set."
        INDEX { zxAnDsUserInterfaceIndex }
        ::= { zxAnDsUserInterfaceTable 1 }

    ZxAnDsUserInterfaceEntry ::= SEQUENCE {
      zxAnDsUserInterfaceIndex    ZxAnIfindex,
        zxAnDsUserInterfaceQuota    Integer32,
        zxAnDsv6UserInterfaceQuota  Integer32
        }

    zxAnDsUserInterfaceIndex OBJECT-TYPE
        SYNTAX      ZxAnIfindex
        MAX-ACCESS  not-accessible
        STATUS      current
        DESCRIPTION
        "user interface, like adsl_x"
        ::= { zxAnDsUserInterfaceEntry 1 }

    zxAnDsUserInterfaceQuota OBJECT-TYPE
        SYNTAX      Integer32(0..255)
        MAX-ACCESS  read-write
        STATUS      current
        DESCRIPTION
        "set the user interface max dhcp session number. when the value is 0,
       that means no limit in the user interface."
        DEFVAL { 0 }
        ::= { zxAnDsUserInterfaceEntry 2 }

    zxAnDsv6UserInterfaceQuota OBJECT-TYPE
        SYNTAX      Integer32(0..255)
        MAX-ACCESS  read-write
        STATUS      current
        DESCRIPTION
        "set the user interface max dhcpv6 session number. when the value is 0,
         that means no limit in the user interface."
        DEFVAL { 0 }
        ::= { zxAnDsUserInterfaceEntry 3 }

-------------------------------------------------------------------------------
-- 10. zxAnDsVPortStatisticsTable
-------------------------------------------------------------------------------
    zxAnDhcpSnoopingIfStatTable OBJECT-TYPE
        SYNTAX      SEQUENCE OF ZxAnDhcpSnoopingIfStatEntry
        MAX-ACCESS  not-accessible
        STATUS      current
        DESCRIPTION
            "DHCP snooping statistics table."
        ::= { zxAnDsStat 1 }

    zxAnDhcpSnoopingIfStatEntry OBJECT-TYPE
        SYNTAX      ZxAnDhcpSnoopingIfStatEntry
        MAX-ACCESS  not-accessible
        STATUS      current
        DESCRIPTION
            "DHCP snooping statistics entry."
        INDEX { zxAnDsIfStatRack, zxAnDsIfStatShelf,
                zxAnDsIfStatSlot, zxAnDsIfStatPort,
                zxAnDsIfStatOnu, zxAnDsIfStatIfType,
                zxAnDsIfStatLogicalId }
        ::= {zxAnDhcpSnoopingIfStatTable 1 }

    ZxAnDhcpSnoopingIfStatEntry ::= SEQUENCE {
        zxAnDsIfStatRack            Integer32,
        zxAnDsIfStatShelf           Integer32,
        zxAnDsIfStatSlot            Integer32,
        zxAnDsIfStatPort            Integer32,
        zxAnDsIfStatOnu             Integer32,
        zxAnDsIfStatIfType          INTEGER,
        zxAnDsIfStatLogicalId       OBJECT IDENTIFIER,
        zxAnDsIfStatDiscoverPackets Counter32,
        zxAnDsIfStatOfferPackets    Counter32,
        zxAnDsIfStatRequestPackets  Counter32,
        zxAnDsIfStatAckPackets      Counter32,
        zxAnDsIfStatNackPackets     Counter32,
        zxAnDsIfStatReleasePackets  Counter32,
        zxAnDsIfStatDeclinePackets  Counter32,
        zxAnDsIfStatInformPackets   Counter32
        }

    zxAnDsIfStatRack  OBJECT-TYPE
        SYNTAX      Integer32
        MAX-ACCESS  not-accessible
        STATUS      current
        DESCRIPTION
            "This object indicates the rack number."
        ::= { zxAnDhcpSnoopingIfStatEntry 1 }

    zxAnDsIfStatShelf  OBJECT-TYPE
        SYNTAX      Integer32
        MAX-ACCESS  not-accessible
        STATUS      current
        DESCRIPTION
            "This object indicates the shelf number."
        ::= { zxAnDhcpSnoopingIfStatEntry 2 }

    zxAnDsIfStatSlot  OBJECT-TYPE
        SYNTAX      Integer32
        MAX-ACCESS  not-accessible
        STATUS      current
        DESCRIPTION
            "This object indicates the slot number."
        ::= { zxAnDhcpSnoopingIfStatEntry 3 }

    zxAnDsIfStatPort  OBJECT-TYPE
        SYNTAX      Integer32
        MAX-ACCESS  not-accessible
        STATUS      current
        DESCRIPTION
            "This object indicates the physical port number."
        ::= { zxAnDhcpSnoopingIfStatEntry 4 }

    zxAnDsIfStatOnu  OBJECT-TYPE
        SYNTAX      Integer32
        MAX-ACCESS  not-accessible
        STATUS      current
        DESCRIPTION
          "When zxAnDsIfStatIfType are 'ponOnu' or 'ponVPort' or
             'servicePort' this object indicates 'onu ID'.
           When zxAnDsIfStatIfType are 'physicalPort' or 'bridgePort'
              its value is '0'."
        ::= { zxAnDhcpSnoopingIfStatEntry 5 }

    zxAnDsIfStatIfType  OBJECT-TYPE
        SYNTAX      INTEGER
        {
            physicalPort(1),
            bridgePort(2),
            ponOnu(3),
            ponVPort(4),
            servicePort(11),
            vlan(12)
        }
        MAX-ACCESS  not-accessible
        STATUS      current
        DESCRIPTION
            "This object indicates the type of port."
        ::= { zxAnDhcpSnoopingIfStatEntry 6 }

    zxAnDsIfStatLogicalId OBJECT-TYPE
        SYNTAX      OBJECT IDENTIFIER
        MAX-ACCESS  not-accessible
        STATUS      current
        DESCRIPTION
         "This value is an oid which indicats the logical index.
          When zxAnDsIfStatIfType is 'physicalPort' its value is '0'.
          When zxAnDsIfStatIfType is 'bridgePort' this object includes
            {pvc} , such as oid {1} indicates  pvc1 .
          When zxAnDsIfStatIfType is 'ponOnu' its value is '0'.
          When zxAnDsIfStatIfType is 'ponVPort' this object includes
            {gemport/llid} , such as oid {1} indicates  ponVPort1 .
          When zxAnDsIfStatIfType is 'servicePort' this object includes
            {serviceportID} , such as oid {1} indicates  serviceportID1 ."
        ::= { zxAnDhcpSnoopingIfStatEntry 7 }

    zxAnDsIfStatDiscoverPackets  OBJECT-TYPE
        SYNTAX      Counter32
        MAX-ACCESS  read-only
        STATUS      current
        DESCRIPTION
            "The number of DHCP discover packets received."
        ::= { zxAnDhcpSnoopingIfStatEntry 8 }

    zxAnDsIfStatOfferPackets  OBJECT-TYPE
        SYNTAX      Counter32
        MAX-ACCESS  read-only
        STATUS      current
        DESCRIPTION
            "The number of DHCP offer packets received."
        ::= { zxAnDhcpSnoopingIfStatEntry 9 }

    zxAnDsIfStatRequestPackets  OBJECT-TYPE
        SYNTAX      Counter32
        MAX-ACCESS  read-only
        STATUS      current
        DESCRIPTION
            "The number of DHCP request packets received."
        ::= { zxAnDhcpSnoopingIfStatEntry 10 }

    zxAnDsIfStatAckPackets  OBJECT-TYPE
        SYNTAX      Counter32
        MAX-ACCESS  read-only
        STATUS      current
        DESCRIPTION
            "The number of DHCP ack packets received."
        ::= { zxAnDhcpSnoopingIfStatEntry 11 }

    zxAnDsIfStatNackPackets  OBJECT-TYPE
        SYNTAX      Counter32
        MAX-ACCESS  read-only
        STATUS      current
        DESCRIPTION
            "The number of DHCP nack packets received."
        ::= { zxAnDhcpSnoopingIfStatEntry 12 }

    zxAnDsIfStatReleasePackets  OBJECT-TYPE
        SYNTAX      Counter32
        MAX-ACCESS  read-only
        STATUS      current
        DESCRIPTION
            "The number of DHCP release packets received."
        ::= { zxAnDhcpSnoopingIfStatEntry 13 }

    zxAnDsIfStatDeclinePackets  OBJECT-TYPE
        SYNTAX      Counter32
        MAX-ACCESS  read-only
        STATUS      current
        DESCRIPTION
            "The number of DHCP decline packets received."
        ::= { zxAnDhcpSnoopingIfStatEntry 14 }

    zxAnDsIfStatInformPackets  OBJECT-TYPE
        SYNTAX      Counter32
        MAX-ACCESS  read-only
        STATUS      current
        DESCRIPTION
            "The number of DHCP inform packets received."
        ::= { zxAnDhcpSnoopingIfStatEntry 15 }
END
