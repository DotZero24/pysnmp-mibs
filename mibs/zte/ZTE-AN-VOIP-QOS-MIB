ZTE-AN-VOIP-QOS-MIB DEFINITIONS ::= BEGIN

  IMPORTS
      MODULE-IDENTITY         FROM SNMPv2-SMI
      NOTIFICATION-TYPE       FROM SNMPv2-SMI
      OBJECT-TYPE             FROM SNMPv2-SMI
      enterprises             FROM SNMPv2-SMI
      Counter32               FROM SNMPv2-SMI
      Integer32               FROM SNMPv2-SMI
      Counter64               FROM SNMPv2-SMI
      Unsigned32              FROM SNMPv2-SMI
      Gauge32                 FROM SNMPv2-SMI
      IpAddress               FROM SNMPv2-SMI
      TEXTUAL-CONVENTION      FROM SNMPv2-TC
      RowStatus               FROM SNMPv2-TC
      DisplayString           FROM SNMPv2-TC
      TruthValue              FROM SNMPv2-TC;

    zxAnVoipQosMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."

    ::= { zxAn 5200 }

    zte OBJECT IDENTIFIER ::= { enterprises 3902 }
    zxAn OBJECT IDENTIFIER ::= { zte 1015 }
    msagmajorVersion OBJECT IDENTIFIER ::= { zxAnVoipQosMib 3 }

-- MODULE DESCRIPTION END
--------------------------------------------------------

msagVoipQovs OBJECT IDENTIFIER ::= { msagmajorVersion 7 }

    msagVoipQovsParaSetTable OBJECT-TYPE
        SYNTAX      SEQUENCE OF MsagVoipQovsParaSetEntry
        MAX-ACCESS  not-accessible
        STATUS      current
        DESCRIPTION ""
        ::= { msagVoipQovs 1 }

   msagVoipQovsParaSetEntry OBJECT-TYPE
        SYNTAX      MsagVoipQovsParaSetEntry
        MAX-ACCESS  not-accessible
        STATUS      current
        DESCRIPTION ""
        INDEX { msagVoipQovsParaIndex}
        ::= { msagVoipQovsParaSetTable 1 }

    MsagVoipQovsParaSetEntry  ::= SEQUENCE {
        msagVoipQovsParaIndex          INTEGER,
        msagVoipQovsParaTimer          INTEGER,
        msagVoipQovsParaDelayThresh    INTEGER,
        msagVoipQovsParaLossThresh     INTEGER,
        msagVoipQovsParaJitterThresh   INTEGER
      }

    msagVoipQovsParaIndex    OBJECT-TYPE
        SYNTAX          INTEGER (1)
        MAX-ACCESS      not-accessible
        STATUS          current
        DESCRIPTION     ""
        ::= { msagVoipQovsParaSetEntry 1 }

    msagVoipQovsParaTimer    OBJECT-TYPE
        SYNTAX          INTEGER (1..10)
        MAX-ACCESS      read-write
        STATUS          current
        DESCRIPTION     "second"
        ::= { msagVoipQovsParaSetEntry 2 }

    msagVoipQovsParaDelayThresh    OBJECT-TYPE
        SYNTAX          INTEGER (1..100)
        MAX-ACCESS      read-write
        STATUS          current
        DESCRIPTION     ""
        ::= { msagVoipQovsParaSetEntry 3 }

    msagVoipQovsParaLossThresh    OBJECT-TYPE
        SYNTAX          INTEGER (1..100)
        MAX-ACCESS      read-write
        STATUS          current
        DESCRIPTION     ""
        ::= { msagVoipQovsParaSetEntry 4 }

    msagVoipQovsParaJitterThresh    OBJECT-TYPE
        SYNTAX          INTEGER (1..100)
        MAX-ACCESS      read-write
        STATUS          current
        DESCRIPTION     ""
        ::= { msagVoipQovsParaSetEntry 5 }


    msagVoipQovsCommandTable OBJECT-TYPE
        SYNTAX      SEQUENCE OF MsagVoipQovsCommandEntry
        MAX-ACCESS  not-accessible
        STATUS      current
        DESCRIPTION ""
        ::= { msagVoipQovs 2 }

    msagVoipQovsCommandEntry OBJECT-TYPE
        SYNTAX      MsagVoipQovsCommandEntry
        MAX-ACCESS  not-accessible
        STATUS      current
        DESCRIPTION ""
        INDEX {
             msagVoipQovsCmdRackno,
             msagVoipQovsCmdShelfno,
             msagVoipQovsCmdSlotno,
             msagVoipQovsCmdIndex}
        ::= { msagVoipQovsCommandTable 1 }

    MsagVoipQovsCommandEntry  ::= SEQUENCE {
        msagVoipQovsCmdRackno    INTEGER,
        msagVoipQovsCmdShelfno   INTEGER,
        msagVoipQovsCmdSlotno    INTEGER,
        msagVoipQovsCmdIndex     INTEGER,
        msagVoipQovsCmdno        INTEGER
    }

    msagVoipQovsCmdRackno    OBJECT-TYPE
        SYNTAX          INTEGER (1..3)
        MAX-ACCESS      not-accessible
        STATUS          current
        DESCRIPTION     ""
        ::= { msagVoipQovsCommandEntry 1 }

    msagVoipQovsCmdShelfno    OBJECT-TYPE
        SYNTAX          INTEGER (1..5)
        MAX-ACCESS      not-accessible
        STATUS          current
        DESCRIPTION     ""
        ::= { msagVoipQovsCommandEntry 2 }

    msagVoipQovsCmdSlotno    OBJECT-TYPE
        SYNTAX          INTEGER (1..23)
        MAX-ACCESS      not-accessible
        STATUS          current
        DESCRIPTION     ""
        ::= { msagVoipQovsCommandEntry 3 }

    msagVoipQovsCmdIndex    OBJECT-TYPE
        SYNTAX          INTEGER (1..23)
        MAX-ACCESS      not-accessible
        STATUS          current
        DESCRIPTION     ""
        ::= { msagVoipQovsCommandEntry 4 }

    msagVoipQovsCmdno OBJECT-TYPE
         SYNTAX          INTEGER{cmdStart(1),cmdEnd(2)}
         MAX-ACCESS      read-write
         STATUS          current
         DESCRIPTION     ""
         ::= { msagVoipQovsCommandEntry 5 }

    msagVoipQovsResultTable OBJECT-TYPE
        SYNTAX      SEQUENCE OF MsagVoipQovsResultEntry
        MAX-ACCESS  not-accessible
        STATUS      current
        DESCRIPTION ""
        ::= { msagVoipQovs 3 }

    msagVoipQovsResultEntry OBJECT-TYPE
        SYNTAX      MsagVoipQovsResultEntry
        MAX-ACCESS  not-accessible
        STATUS      current
        DESCRIPTION ""
        INDEX {
             msagVoipQRRackno,
             msagVoipQRShelfno,
             msagVoipQRSlotno,
             msagVoipQRIndex}
        ::= { msagVoipQovsResultTable 1 }

    MsagVoipQovsResultEntry  ::= SEQUENCE {
        msagVoipQRRackno        INTEGER,
        msagVoipQRShelfno       INTEGER,
        msagVoipQRSlotno        INTEGER,
        msagVoipQRIndex         INTEGER,
        msagVoipQRDelay         INTEGER,
        msagVoipQRLoss          INTEGER,
        msagVoipQRJitter        INTEGER,
        msagVoipQRSrcPort       Integer32,
        msagVoipQRDestPort      Integer32,
        msagVoipQRSrcIPAddr     IpAddress,
        msagVoipQRTime          Integer32,
        msagVoipQRMos           Integer32,
        msagVoipQRLossRate      Integer32,
        msagVoipQRsignalLev     Integer32,
        msagVoipQRnoiseLev      Integer32,
        msagVoipQRRERL          Integer32,
        msagVoipQRBurstDuration Integer32,
        msagVoipQRgapDuration   Integer32,
        msagVoipQRBurstDensity  Integer32,
        msagVoipQRGapDensity    Integer32
    }

    msagVoipQRRackno    OBJECT-TYPE
        SYNTAX          INTEGER (1..3)
        MAX-ACCESS      not-accessible
        STATUS          current
        DESCRIPTION     ""
        ::= { msagVoipQovsResultEntry 1 }

    msagVoipQRShelfno    OBJECT-TYPE
        SYNTAX          INTEGER (1..5)
        MAX-ACCESS      not-accessible
        STATUS          current
        DESCRIPTION     ""
        ::= { msagVoipQovsResultEntry 2 }

    msagVoipQRSlotno    OBJECT-TYPE
        SYNTAX          INTEGER (1..23)
        MAX-ACCESS      not-accessible
        STATUS          current
        DESCRIPTION     ""
        ::= { msagVoipQovsResultEntry 3 }

    msagVoipQRIndex    OBJECT-TYPE
        SYNTAX          INTEGER (1..23)
        MAX-ACCESS      not-accessible
        STATUS          current
        DESCRIPTION     ""
        ::= { msagVoipQovsResultEntry 4 }

    msagVoipQRDelay OBJECT-TYPE
         SYNTAX          INTEGER(1..100)
         MAX-ACCESS      read-only
         STATUS          current
         DESCRIPTION     ""
         ::= { msagVoipQovsResultEntry 5 }

    msagVoipQRLoss OBJECT-TYPE
         SYNTAX          INTEGER(1..100)
         MAX-ACCESS      read-only
         STATUS          current
         DESCRIPTION     ""
         ::= { msagVoipQovsResultEntry 6 }

    msagVoipQRJitter OBJECT-TYPE
         SYNTAX          INTEGER(1..100)
         MAX-ACCESS      read-only
         STATUS          current
         DESCRIPTION     ""
         ::= { msagVoipQovsResultEntry 7 }

    msagVoipQRSrcPort OBJECT-TYPE
         SYNTAX          Integer32
         MAX-ACCESS      read-only
         STATUS          current
         DESCRIPTION     ""
         ::= { msagVoipQovsResultEntry 8 }

    msagVoipQRDestPort OBJECT-TYPE
         SYNTAX          Integer32
         MAX-ACCESS      read-only
         STATUS          current
         DESCRIPTION     ""
         ::= { msagVoipQovsResultEntry 9 }

    msagVoipQRSrcIPAddr  OBJECT-TYPE
         SYNTAX          IpAddress
         MAX-ACCESS      read-only
         STATUS          current
         DESCRIPTION     ""
         ::= { msagVoipQovsResultEntry 10 }

    msagVoipQRTime     OBJECT-TYPE
         SYNTAX          Integer32
         MAX-ACCESS      read-only
         STATUS          current
         DESCRIPTION     ""
         ::= { msagVoipQovsResultEntry 11 }

    msagVoipQRMos     OBJECT-TYPE
         SYNTAX          Integer32
         MAX-ACCESS      read-only
         STATUS          current
         DESCRIPTION     ""
         ::= { msagVoipQovsResultEntry 12 }

   msagVoipQRLossRate     OBJECT-TYPE
         SYNTAX          Integer32
         MAX-ACCESS      read-only
         STATUS          current
         DESCRIPTION     ""
         ::= { msagVoipQovsResultEntry 13 }

   msagVoipQRsignalLev     OBJECT-TYPE
         SYNTAX          Integer32
         MAX-ACCESS      read-only
         STATUS          current
         DESCRIPTION     ""
         ::= { msagVoipQovsResultEntry 14 }

   msagVoipQRnoiseLev     OBJECT-TYPE
         SYNTAX          Integer32
         MAX-ACCESS      read-only
         STATUS          current
         DESCRIPTION     ""
         ::= { msagVoipQovsResultEntry 15 }

   msagVoipQRRERL     OBJECT-TYPE
         SYNTAX          Integer32
         MAX-ACCESS      read-only
         STATUS          current
         DESCRIPTION     ""
         ::= { msagVoipQovsResultEntry 16 }

   msagVoipQRBurstDuration     OBJECT-TYPE
         SYNTAX          Integer32
         MAX-ACCESS      read-only
         STATUS          current
         DESCRIPTION     ""
         ::= { msagVoipQovsResultEntry 17 }

   msagVoipQRgapDuration     OBJECT-TYPE
         SYNTAX          Integer32
         MAX-ACCESS      read-only
         STATUS          current
         DESCRIPTION     ""
         ::= { msagVoipQovsResultEntry 18 }

   msagVoipQRBurstDensity     OBJECT-TYPE
         SYNTAX          Integer32
         MAX-ACCESS      read-only
         STATUS          current
         DESCRIPTION     ""
         ::= { msagVoipQovsResultEntry 19 }

   msagVoipQRGapDensity     OBJECT-TYPE
         SYNTAX          Integer32
         MAX-ACCESS      read-only
         STATUS          current
         DESCRIPTION     ""
         ::= { msagVoipQovsResultEntry 20 }

   msagNarrowGetNext     OBJECT-TYPE
         SYNTAX          Integer32
         MAX-ACCESS      read-only
         STATUS          current
         DESCRIPTION     ""
         ::= { msagVoipQovs 10 }

  ------------------------------------------------------------
END
