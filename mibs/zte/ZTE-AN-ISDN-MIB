ZTE-AN-ISDN-MIB DEFINITIONS ::= BEGIN

  IMPORTS
      MODULE-IDENTITY         FROM SNMPv2-SMI
      NOTIFICATION-TYPE       FROM SNMPv2-SMI
      OBJECT-TYPE             FROM SNMPv2-SMI
      enterprises             FROM SNMPv2-SMI
      Counter32               FROM SNMPv2-SMI
      Integer32               FROM SNMPv2-SMI
      Counter64               FROM SNMPv2-SMI
      Unsigned32              FROM SNMPv2-SMI
      Gauge32                 FROM SNMPv2-SMI
      IpAddress               FROM SNMPv2-SMI
      TEXTUAL-CONVENTION      FROM SNMPv2-TC
      RowStatus               FROM SNMPv2-TC
      DisplayString           FROM SNMPv2-TC
      TruthValue              FROM SNMPv2-TC;

    zxAnISDNMib MODULE-IDENTITY
        LAST-UPDATED    "0608140000Z"  -- july. 23, 2005
        ORGANIZATION    "zte Telcom Co. Ltd."
        CONTACT-INFO    "E-mail: shen.yuyang@zte.com.cn,
                         E-mail: suchunshan@zte.com.cn"
        DESCRIPTION     "This MIB defines PortLocating managed objects for Access Node."

    ::= { zxAn 5200 }

    zte OBJECT IDENTIFIER ::= { enterprises 3902 }
    zxAn OBJECT IDENTIFIER ::= { zte 1015 }

    msagmajorVersion OBJECT IDENTIFIER ::= { zxAnISDNMib 3 }

-- MODULE DESCRIPTION END
--------------------------------------------------------

    msagISDNService     OBJECT IDENTIFIER ::= { msagmajorVersion 4 }
    zxAnIsdnBertMgmtGroup    OBJECT IDENTIFIER ::= { msagISDNService 11 }

    isdnAppServerTable OBJECT-TYPE
      SYNTAX    SEQUENCE OF IsdnAppServerEntry
      MAX-ACCESS not-accessible
      STATUS     current
      DESCRIPTION ""
      ::={msagISDNService 1}

    isdnAppServerEntry OBJECT-TYPE
      SYNTAX    IsdnAppServerEntry
      MAX-ACCESS not-accessible
      STATUS     current
      DESCRIPTION ""
      INDEX {isdnAppServerID}
      ::={isdnAppServerTable 1}

     IsdnAppServerEntry ::=
        SEQUENCE{
          isdnAppServerID        INTEGER,
          isdnAppServerProtocol  INTEGER,
          isdnAppServerMode      INTEGER,
          isdnAppServerModeEval  INTEGER,
          isdnAppServerStatus    INTEGER,
          isdnAppServerRowStatus RowStatus
      }

    isdnAppServerID OBJECT-TYPE
      SYNTAX      INTEGER(1..128)
      MAX-ACCESS  not-accessible
      STATUS      current
      DESCRIPTION ""
      ::= { isdnAppServerEntry 1 }

    isdnAppServerProtocol    OBJECT-TYPE
      SYNTAX      INTEGER{tpM3UA(1),tpM2UA(2),tpM2PA(3),tpSUA(4),tpIUA(5),tpV5UA(6)}
      MAX-ACCESS  read-create
      STATUS      current
      DESCRIPTION ""
      ::= { isdnAppServerEntry 2 }

    isdnAppServerMode    OBJECT-TYPE
      SYNTAX      INTEGER{masterSlave(1),share(2),broadcast(3)}
      MAX-ACCESS  read-create
      STATUS      current
      DESCRIPTION ""
      ::= { isdnAppServerEntry 3 }

    isdnAppServerModeEval    OBJECT-TYPE
      SYNTAX      INTEGER(0..255)
      MAX-ACCESS  read-create
      STATUS      current
      DESCRIPTION ""
      ::= { isdnAppServerEntry 4 }

    isdnAppServerStatus    OBJECT-TYPE
      SYNTAX      INTEGER{down(0),inactive(1),active(2),pending(4)}
      MAX-ACCESS  read-create
      STATUS      current
      DESCRIPTION ""
      ::= { isdnAppServerEntry 5 }

    isdnAppServerRowStatus    OBJECT-TYPE
      SYNTAX      RowStatus
      MAX-ACCESS  read-create
      STATUS      current
      DESCRIPTION ""
      ::= { isdnAppServerEntry 6 }

    isdnAppServerProcTable OBJECT-TYPE
      SYNTAX    SEQUENCE OF IsdnAppServerProcEntry
      MAX-ACCESS not-accessible
      STATUS     current
      DESCRIPTION "(ASP)"
      ::={msagISDNService 2}

    isdnAppServerProcEntry OBJECT-TYPE
      SYNTAX    IsdnAppServerProcEntry
      MAX-ACCESS not-accessible
      STATUS     current
      DESCRIPTION ""
      INDEX {isdnASPID}
      ::={isdnAppServerProcTable 1}

    IsdnAppServerProcEntry ::=
        SEQUENCE{
          isdnASPID          INTEGER,
          isdnASPDestPort    INTEGER,
          isdnASPLoclPort    INTEGER,
          isdnASPSctpID      Integer32,
          isdnASPUpProto     INTEGER,
          isdnASPDownProto   INTEGER,
          isdnASPDestIP      IpAddress,
          isdnASPInStream    INTEGER,
          isdnASPOutStream   INTEGER,
          isdnASPStat        INTEGER,
          isdnASPModule      Integer32,
          isdnASPClieOrServ  INTEGER,
          isdnASPRowStatus   RowStatus
      }

    isdnASPID    OBJECT-TYPE
      SYNTAX      INTEGER(1..128)
      MAX-ACCESS  not-accessible
      STATUS      current
      DESCRIPTION ""
      ::= { isdnAppServerProcEntry 1 }

    isdnASPDestPort    OBJECT-TYPE
      SYNTAX      INTEGER (0..65535)
      MAX-ACCESS  read-create
      STATUS      current
      DESCRIPTION ""
      ::= { isdnAppServerProcEntry 2 }

    isdnASPLoclPort    OBJECT-TYPE
      SYNTAX      INTEGER (0..65535)
      MAX-ACCESS  read-create
      STATUS      current
      DESCRIPTION ""
      ::= { isdnAppServerProcEntry 3 }

    isdnASPSctpID    OBJECT-TYPE
      SYNTAX      Integer32
      MAX-ACCESS  read-only
      STATUS      current
      DESCRIPTION ""
      ::= { isdnAppServerProcEntry 4 }

    isdnASPUpProto    OBJECT-TYPE
      SYNTAX      INTEGER {iua(5)}
      MAX-ACCESS  read-only
      STATUS      current
      DESCRIPTION ""
      ::= { isdnAppServerProcEntry 5 }

    isdnASPDownProto    OBJECT-TYPE
      SYNTAX      INTEGER {udp(1),ip(2)}
      MAX-ACCESS  read-create
      STATUS      current
      DESCRIPTION ""
      ::= { isdnAppServerProcEntry 6 }

    isdnASPDestIP    OBJECT-TYPE
      SYNTAX      IpAddress
      MAX-ACCESS  read-create
      STATUS      current
      DESCRIPTION ""
      ::= { isdnAppServerProcEntry 7 }

    isdnASPInStream    OBJECT-TYPE
      SYNTAX      INTEGER(0..16)
      MAX-ACCESS  read-create
      STATUS      current
      DESCRIPTION ""
      ::= { isdnAppServerProcEntry 8 }

   isdnASPOutStream    OBJECT-TYPE
     SYNTAX      INTEGER(0..16)
     MAX-ACCESS  read-create
     STATUS      current
     DESCRIPTION ""
     ::= { isdnAppServerProcEntry 9 }

   isdnASPStat    OBJECT-TYPE
     SYNTAX      INTEGER{
            aspLost(0),
            aspDown(1),
            aspInactive(2),
            aspActive(4),
            aspStandby(8),
            aspManual(64),
            aspCongest(128)
        }
     MAX-ACCESS  read-only
     STATUS      current
     DESCRIPTION ""
     ::= { isdnAppServerProcEntry 10 }

   isdnASPModule    OBJECT-TYPE
     SYNTAX      Integer32
     MAX-ACCESS  read-only
     STATUS      current
     DESCRIPTION ""
     ::= { isdnAppServerProcEntry 11 }

   isdnASPClieOrServ    OBJECT-TYPE
     SYNTAX      INTEGER{client(1),server(2)}
     MAX-ACCESS  read-only
     STATUS      current
     DESCRIPTION ""
     ::= { isdnAppServerProcEntry 12 }

   isdnASPRowStatus    OBJECT-TYPE
     SYNTAX      RowStatus
     MAX-ACCESS  read-create
     STATUS      current
     DESCRIPTION ""
     ::= { isdnAppServerProcEntry 14 }

   isdnASASPRelationTable OBJECT-TYPE
     SYNTAX    SEQUENCE OF IsdnASASPRelationEntry
     MAX-ACCESS not-accessible
     STATUS     current
     DESCRIPTION "ASASP"
     ::={msagISDNService 3}

  isdnASASPRelationEntry OBJECT-TYPE
    SYNTAX    IsdnASASPRelationEntry
    MAX-ACCESS not-accessible
    STATUS     current
    DESCRIPTION ""
    INDEX {isdnAARASPID,isdnAARASID}
    ::={isdnASASPRelationTable 1}

  IsdnASASPRelationEntry ::=
        SEQUENCE{
          isdnAARASPID       INTEGER,
          isdnAARASID        INTEGER,
          isdnAARQueue       INTEGER,
          isdnAARRowStatus   RowStatus
      }

    isdnAARASPID    OBJECT-TYPE
      SYNTAX      INTEGER(1..128)
      MAX-ACCESS  not-accessible
      STATUS      current
      DESCRIPTION ""
      ::= { isdnASASPRelationEntry 1 }

    isdnAARASID     OBJECT-TYPE
      SYNTAX      INTEGER(1..128)
      MAX-ACCESS  not-accessible
      STATUS      current
      DESCRIPTION ""
      ::= { isdnASASPRelationEntry 2 }

    isdnAARQueue    OBJECT-TYPE
      SYNTAX      INTEGER{aspInit(0),aspDown(1),aspUp(2),aspActive(4)}
      MAX-ACCESS  read-only
      STATUS      current
      DESCRIPTION ""
      ::= { isdnASASPRelationEntry 3 }

    isdnAARRowStatus OBJECT-TYPE
      SYNTAX      RowStatus
      MAX-ACCESS  read-create
      STATUS      current
      DESCRIPTION ""
      ::= { isdnASASPRelationEntry 4 }

    isdnDLinkTable OBJECT-TYPE
      SYNTAX    SEQUENCE OF IsdnDLinkEntry
      MAX-ACCESS not-accessible
      STATUS     current
      DESCRIPTION "30B+D"
      ::={msagISDNService 4}

    isdnDLinkEntry OBJECT-TYPE
      SYNTAX    IsdnDLinkEntry
      MAX-ACCESS not-accessible
      STATUS     current
      DESCRIPTION ""
      INDEX {isdnDLinkRack,isdnDLinkShelf,isdnDLinkSlot,
      isdnDLinkPCMNo,isdnDLinkLinkIdx}
      ::={isdnDLinkTable 1}

  IsdnDLinkEntry ::=
        SEQUENCE{
          isdnDLinkRack       Integer32,
          isdnDLinkShelf      Integer32,
          isdnDLinkSlot       Integer32,
          isdnDLinkPCMNo      INTEGER,
          isdnDLinkLinkIdx    INTEGER,
          isdnDLinkIfID       INTEGER,
          isdnDLinkLinkID     INTEGER,
          isdnDLinkLinkInfo   INTEGER,
          isdnDLinkASID       INTEGER,
          isdnDLinkNumber     INTEGER,
          isdnDLinkProtocol   INTEGER,
          isdnDLinkStatus     Integer32,
          isdnDLinkRowStatus  RowStatus
      }


   isdnDLinkRack    OBJECT-TYPE
     SYNTAX      Integer32
     MAX-ACCESS  not-accessible
     STATUS      current
     DESCRIPTION ""
     ::= { isdnDLinkEntry 1 }

   isdnDLinkShelf   OBJECT-TYPE
     SYNTAX      Integer32
     MAX-ACCESS  not-accessible
     STATUS      current
     DESCRIPTION ""
     ::= { isdnDLinkEntry 2 }

   isdnDLinkSlot    OBJECT-TYPE
     SYNTAX      Integer32
     MAX-ACCESS  not-accessible
     STATUS      current
     DESCRIPTION ""
     ::= { isdnDLinkEntry 3 }

   isdnDLinkPCMNo   OBJECT-TYPE
     SYNTAX      INTEGER(1..8)
     MAX-ACCESS  not-accessible
     STATUS      current
     DESCRIPTION ""
     ::= { isdnDLinkEntry 4 }

   isdnDLinkLinkIdx OBJECT-TYPE
     SYNTAX      INTEGER(0..31)
     MAX-ACCESS  not-accessible
     STATUS      current
     DESCRIPTION ""
     ::= { isdnDLinkEntry 5 }

   isdnDLinkIfID    OBJECT-TYPE
     SYNTAX      INTEGER(1..65535)
     MAX-ACCESS  read-create
     STATUS      current
     DESCRIPTION ""
     ::= { isdnDLinkEntry 6 }

   isdnDLinkLinkID  OBJECT-TYPE
     SYNTAX      INTEGER(1..512)
     MAX-ACCESS  read-create
     STATUS      current
     DESCRIPTION ""
     ::= { isdnDLinkEntry 7 }

   isdnDLinkLinkInfo  OBJECT-TYPE
     SYNTAX      INTEGER{networkSide(0),subscriberSide(1)}
     MAX-ACCESS  read-create
     STATUS      current
     DESCRIPTION ""
     ::= { isdnDLinkEntry 8 }

   isdnDLinkASID    OBJECT-TYPE
     SYNTAX      INTEGER(1..128)
     MAX-ACCESS  read-create
     STATUS      current
     DESCRIPTION ""
     ::= { isdnDLinkEntry 9 }

   isdnDLinkNumber  OBJECT-TYPE
     SYNTAX      INTEGER(1..8)
     MAX-ACCESS  read-create
     STATUS      current
     DESCRIPTION ""
     ::= { isdnDLinkEntry 10 }

   isdnDLinkProtocol  OBJECT-TYPE
     SYNTAX      INTEGER{ptl2BplusD(1),ptl30BplusD(2),ptl23BplusD(3)}
     MAX-ACCESS  read-only
     STATUS      current
     DESCRIPTION ""
     ::= { isdnDLinkEntry 11 }

   isdnDLinkStatus  OBJECT-TYPE
     SYNTAX      Integer32
     MAX-ACCESS  read-only
     STATUS      current
     DESCRIPTION ""
     ::= { isdnDLinkEntry 12 }

   isdnDLinkRowStatus     OBJECT-TYPE
     SYNTAX      RowStatus
     MAX-ACCESS  read-create
     STATUS      current
     DESCRIPTION ""
     ::= { isdnDLinkEntry 13 }


--loopback table begin
   loopbackTable OBJECT-TYPE
       SYNTAX      SEQUENCE OF LoopbackEntry
       MAX-ACCESS  not-accessible
       STATUS      current
       DESCRIPTION "Loopback table"
       ::={msagISDNService 6}

   loopbackEntry OBJECT-TYPE
       SYNTAX    LoopbackEntry
       MAX-ACCESS  not-accessible
       STATUS      current
       DESCRIPTION "Loopback table entry"
       INDEX { loopbackrack,loopbackshelf,loopbackslot,loopbackportno}
       ::={loopbackTable 1}

   LoopbackEntry ::=
       SEQUENCE{
       loopbackrack       Integer32,
       loopbackshelf      Integer32,
       loopbackslot       Integer32,
       loopbackportno     Integer32,
       loopbacklooptype   INTEGER
   }

   loopbackrack  OBJECT-TYPE
       SYNTAX      Integer32
       MAX-ACCESS  not-accessible
       STATUS      current
       DESCRIPTION "Rack number of the port."
       ::={loopbackEntry 1}

   loopbackshelf  OBJECT-TYPE
       SYNTAX      Integer32
       MAX-ACCESS  not-accessible
       STATUS      current
       DESCRIPTION "Shelf number of the port."
       ::={loopbackEntry 2}

   loopbackslot  OBJECT-TYPE
       SYNTAX      Integer32
       MAX-ACCESS  not-accessible
       STATUS      current
       DESCRIPTION "Slot number of the port."
       ::={loopbackEntry 3}

   loopbackportno  OBJECT-TYPE
       SYNTAX      Integer32
       MAX-ACCESS  not-accessible
       STATUS      current
       DESCRIPTION "Port number."
       ::={loopbackEntry 4}

   loopbacklooptype  OBJECT-TYPE
       SYNTAX      INTEGER
           {
               localLoopback(1),
               remoteLineLoopback(2),
               noLoopback(3)
           }
       MAX-ACCESS  read-write
       STATUS      current
       DESCRIPTION
           "Port loopback status.
            localLoopback(1)      - Set port to local loopback status.
            remoteLineLoopback(2) - Set port to remote loopback status.
            noLoopback(3)         - Change port from loopback status to normal
                                    status.
           "
       ::={loopbackEntry 5}

--end of ddn loopback table


--msagIsdnCapability table begin

    msagIsdnCapabilityTable OBJECT-TYPE
        SYNTAX      SEQUENCE OF MsagIsdnCapabilityEntry
        MAX-ACCESS  not-accessible
        STATUS      current
        DESCRIPTION ""
        ::= { msagISDNService 7 }

    msagIsdnCapabilityEntry OBJECT-TYPE
        SYNTAX      MsagIsdnCapabilityEntry
        MAX-ACCESS  not-accessible
        STATUS      current
        DESCRIPTION ""
        INDEX { isdnkrack,isdnshelf,isdnslot,isdnportno}
        ::={msagIsdnCapabilityTable 1}

    MsagIsdnCapabilityEntry ::= SEQUENCE {
        isdnkrack                       INTEGER,
        isdnshelf                       INTEGER,
        isdnslot                        INTEGER,
        isdnportno                      INTEGER,
        isdnLossOfSignal                Unsigned32,
        isdnLossOfPower                 Unsigned32,
        isdnLossOfFrame                 Unsigned32,
        isdnClear                       INTEGER
    }

    isdnkrack  OBJECT-TYPE
        SYNTAX    INTEGER(1..3)
        MAX-ACCESS  not-accessible
        STATUS      current
        DESCRIPTION ""
        ::={msagIsdnCapabilityEntry 1}

    isdnshelf       OBJECT-TYPE
        SYNTAX    INTEGER(1..5)
        MAX-ACCESS  not-accessible
        STATUS      current
        DESCRIPTION ""
        ::={msagIsdnCapabilityEntry 2}

    isdnslot  OBJECT-TYPE
        SYNTAX    INTEGER(1..23)
        MAX-ACCESS  not-accessible
        STATUS      current
        DESCRIPTION ""
        ::={msagIsdnCapabilityEntry 3}

    isdnportno  OBJECT-TYPE
        SYNTAX    INTEGER(1..8)
        MAX-ACCESS  not-accessible
        STATUS      current
        DESCRIPTION ""
        ::={msagIsdnCapabilityEntry 4}

    isdnLossOfSignal  OBJECT-TYPE
        SYNTAX      Unsigned32(0..4294967295)
        MAX-ACCESS  read-only
        STATUS      current
        DESCRIPTION ""
        ::={msagIsdnCapabilityEntry 20}

    isdnLossOfPower  OBJECT-TYPE
        SYNTAX      Unsigned32(0..4294967295)
        MAX-ACCESS  read-only
        STATUS      current
        DESCRIPTION ""
        ::={msagIsdnCapabilityEntry 21}

    isdnLossOfFrame  OBJECT-TYPE
        SYNTAX      Unsigned32(0..4294967295)
        MAX-ACCESS  read-only
        STATUS      current
        DESCRIPTION ""
        ::={msagIsdnCapabilityEntry 22}

    isdnClear          OBJECT-TYPE
        SYNTAX      INTEGER(1)
        MAX-ACCESS  read-write
        STATUS      current
        DESCRIPTION ""
        ::={msagIsdnCapabilityEntry 23}

--end of msagIsdnCapability table

--zxAnIsdnPortActiveStatusTable table begin

   zxAnIsdnPortActiveStatusTable OBJECT-TYPE
       SYNTAX      SEQUENCE OF ZxAnIsdnPortActiveStatusEntry
       MAX-ACCESS  not-accessible
       STATUS      current
       DESCRIPTION
           "ISDN port active status table."
       ::={msagISDNService 8}

   zxAnIsdnPortActiveStatusEntry OBJECT-TYPE
       SYNTAX      ZxAnIsdnPortActiveStatusEntry
       MAX-ACCESS  not-accessible
       STATUS      current
       DESCRIPTION
           "ISDN port active status table entry."
       INDEX
           {
               zxAnIsdnPortRack,
               zxAnIsdnPortShelf,
               zxAnIsdnPortSlot,
               zxAnIsdnPortNo
           }
       ::={zxAnIsdnPortActiveStatusTable 1}

   ZxAnIsdnPortActiveStatusEntry ::=
       SEQUENCE{
       zxAnIsdnPortRack            Integer32,
       zxAnIsdnPortShelf           Integer32,
       zxAnIsdnPortSlot            Integer32,
       zxAnIsdnPortNo              Integer32,
       zxAnIsdnPortL1ActiveStatus  INTEGER,
       zxAnIsdnPortL2ActiveStatus  INTEGER
   }

   zxAnIsdnPortRack  OBJECT-TYPE
       SYNTAX      Integer32
       MAX-ACCESS  not-accessible
       STATUS      current
       DESCRIPTION
           "Rack number of the port."
       ::={zxAnIsdnPortActiveStatusEntry 1}

   zxAnIsdnPortShelf  OBJECT-TYPE
       SYNTAX      Integer32
       MAX-ACCESS  not-accessible
       STATUS      current
       DESCRIPTION
           "Shelf number of the port."
       ::={zxAnIsdnPortActiveStatusEntry 2}

   zxAnIsdnPortSlot  OBJECT-TYPE
       SYNTAX      Integer32
       MAX-ACCESS  not-accessible
       STATUS      current
       DESCRIPTION
           "Slot number of the port."
       ::={zxAnIsdnPortActiveStatusEntry 3}

   zxAnIsdnPortNo  OBJECT-TYPE
       SYNTAX      Integer32
       MAX-ACCESS  not-accessible
       STATUS      current
       DESCRIPTION
           "Port number."
       ::={zxAnIsdnPortActiveStatusEntry 4}

   zxAnIsdnPortL1ActiveStatus  OBJECT-TYPE
       SYNTAX      INTEGER
           {
               keepActive(0),
               notKeepActive(1)
           }
       MAX-ACCESS  read-write
       STATUS      current
       DESCRIPTION
           "U-interface physical layer(Layer 1) active status.
            This object could be configured base on D-link.
           "
       ::={zxAnIsdnPortActiveStatusEntry 5}

   zxAnIsdnPortL2ActiveStatus  OBJECT-TYPE
       SYNTAX      INTEGER
           {
               keepActive(1),
               notKeepActive(2)
           }
       MAX-ACCESS  read-write
       STATUS      current
       DESCRIPTION
           "U-interface data link layer(Layer 2) active status.
            This object could be configured base on D-link.
           "
       ::={zxAnIsdnPortActiveStatusEntry 6}

--end of msagIsdnCapability table

--zxAnIsdnUIfCfgTable begin

   zxAnIsdnUIfCfgTable OBJECT-TYPE
       SYNTAX      SEQUENCE OF ZxAnIsdnUIfCfgEntry
       MAX-ACCESS  not-accessible
       STATUS      current
       DESCRIPTION
           "ISDN U-interface configuration table."
       ::={msagISDNService 9}

   zxAnIsdnUIfCfgEntry OBJECT-TYPE
       SYNTAX      ZxAnIsdnUIfCfgEntry
       MAX-ACCESS  not-accessible
       STATUS      current
       DESCRIPTION
           "ISDN U-interface configuration table entry."
       INDEX { zxAnIsdnUIfRack,zxAnIsdnUIfShelf,zxAnIsdnUIfSlot,zxAnIsdnUIfNo}
       ::={zxAnIsdnUIfCfgTable 1}

   ZxAnIsdnUIfCfgEntry ::=
       SEQUENCE{
       zxAnIsdnUIfRack                    Integer32,
       zxAnIsdnUIfShelf                   Integer32,
       zxAnIsdnUIfSlot                    Integer32,
       zxAnIsdnUIfNo                      Integer32,
       zxAnIsdnUIfRemotePowerFeedEnable   INTEGER,
       zxAnIsdnUIfTrapEnable              INTEGER,
       zxAnIsdnUIfActiveStatus            INTEGER,
       zxAnIsdnUIfSoftReset               INTEGER,
       zxAnIsdnUIfAbnormalReason          INTEGER
   }

   zxAnIsdnUIfRack  OBJECT-TYPE
       SYNTAX       Integer32
       MAX-ACCESS   not-accessible
       STATUS       current
       DESCRIPTION
           "Rack number of the port."
       ::={zxAnIsdnUIfCfgEntry 1}

   zxAnIsdnUIfShelf  OBJECT-TYPE
       SYNTAX       Integer32
       MAX-ACCESS   not-accessible
       STATUS       current
       DESCRIPTION
           "Shelf number of the port."
       ::={zxAnIsdnUIfCfgEntry 2}

   zxAnIsdnUIfSlot  OBJECT-TYPE
       SYNTAX       Integer32
       MAX-ACCESS   not-accessible
       STATUS       current
       DESCRIPTION
           "Slot number of the port."
       ::={zxAnIsdnUIfCfgEntry 3}

   zxAnIsdnUIfNo  OBJECT-TYPE
       SYNTAX       Integer32
       MAX-ACCESS   not-accessible
       STATUS       current
       DESCRIPTION
           "The port number."
       ::={zxAnIsdnUIfCfgEntry 4}

   zxAnIsdnUIfRemotePowerFeedEnable  OBJECT-TYPE
       SYNTAX       INTEGER
           {
               enable(1),
               disable(2)
           }
       MAX-ACCESS   read-write
       STATUS       current
       DESCRIPTION
           "U-interface remote power feeding status."
       DEFVAL  {  disable  }
       ::={zxAnIsdnUIfCfgEntry 5}

   zxAnIsdnUIfTrapEnable  OBJECT-TYPE
       SYNTAX       INTEGER
           {
               enable(1),
               disable(2)
           }
       MAX-ACCESS   read-write
       STATUS       current
       DESCRIPTION
           "Trap control of U-interface.
            enable(1)  - Enable the trap of U-interface.
            disable(2) - Disable the trap of U-interface.
           "
       DEFVAL  {  disable  }
       ::={zxAnIsdnUIfCfgEntry 6}

   zxAnIsdnUIfActiveStatus  OBJECT-TYPE
       SYNTAX       INTEGER
           {
               active(1),
               inactive(2)
           }
       MAX-ACCESS   read-only
       STATUS       current
       DESCRIPTION
           "The active status of U-interface."
       DEFVAL  {  inactive  }
       ::={zxAnIsdnUIfCfgEntry 7}

   zxAnIsdnUIfSoftReset  OBJECT-TYPE
       SYNTAX       INTEGER
           {
               reset(1)
           }
       MAX-ACCESS   read-write
       STATUS       current
       DESCRIPTION
           "Soft reset the U interface when it is set to 1.
           When get this variable,always return 1."
       ::={zxAnIsdnUIfCfgEntry 8}

   zxAnIsdnUIfAbnormalReason  OBJECT-TYPE
       SYNTAX       INTEGER
            {
                errorIndication2(1),            -- Error Indication 2
                errorIndication3(2),            -- Error Indication 3
                lossOfSignalLevel(3),           -- Loss of Signal Level
                reSyncIndication(4),            -- Re-synchronization indication after a LOF
                frameJump(5),                   -- Frame Jump
                uIfActivationIndication(6),     -- U-Interface Activation Indication
                uIfdeactivationIndication(7),   -- U-Interface Deactivation Indication
                other(255)                      -- Other
            }
       MAX-ACCESS   read-only
       STATUS       current
       DESCRIPTION
           "The abnormal reason of the U-interface."
       ::={zxAnIsdnUIfCfgEntry 9}

--end of zxAnIsdnUIfCfgTable

--zxAnIsdnSIfCfgTable begin

   zxAnIsdnSIfCfgTable OBJECT-TYPE
       SYNTAX      SEQUENCE OF ZxAnIsdnSIfCfgEntry
       MAX-ACCESS  not-accessible
       STATUS      current
       DESCRIPTION
           "ISDN S-interface configuration table."
       ::={msagISDNService 10}

   zxAnIsdnSIfCfgEntry OBJECT-TYPE
       SYNTAX      ZxAnIsdnSIfCfgEntry
       MAX-ACCESS  not-accessible
       STATUS      current
       DESCRIPTION
           "ISDN S-interface configuration table entry."
       INDEX { zxAnIsdnSIfRack,zxAnIsdnSIfShelf,zxAnIsdnSIfSlot,zxAnIsdnSIfNo}
       ::={zxAnIsdnSIfCfgTable 1}

   ZxAnIsdnSIfCfgEntry ::=
       SEQUENCE{
       zxAnIsdnSIfRack                    Integer32,
       zxAnIsdnSIfShelf                   Integer32,
       zxAnIsdnSIfSlot                    Integer32,
       zxAnIsdnSIfNo                      Integer32,
       zxAnIsdnSIfTrapEnable              INTEGER,
       zxAnIsdnSIfSyncStatus              INTEGER,
       zxAnIsdnSIfAbnormalReason          INTEGER
   }

   zxAnIsdnSIfRack  OBJECT-TYPE
       SYNTAX       Integer32
       MAX-ACCESS   not-accessible
       STATUS       current
       DESCRIPTION
           "Rack number of the port."
       ::={zxAnIsdnSIfCfgEntry 1}

   zxAnIsdnSIfShelf  OBJECT-TYPE
       SYNTAX       Integer32
       MAX-ACCESS   not-accessible
       STATUS       current
       DESCRIPTION
           "Shelf number of the port."
       ::={zxAnIsdnSIfCfgEntry 2}

   zxAnIsdnSIfSlot  OBJECT-TYPE
       SYNTAX       Integer32
       MAX-ACCESS   not-accessible
       STATUS       current
       DESCRIPTION
           "Slot number of the port."
       ::={zxAnIsdnSIfCfgEntry 3}

   zxAnIsdnSIfNo  OBJECT-TYPE
       SYNTAX       Integer32
       MAX-ACCESS   not-accessible
       STATUS       current
       DESCRIPTION
           "The port number."
       ::={zxAnIsdnSIfCfgEntry 4}

   zxAnIsdnSIfTrapEnable  OBJECT-TYPE
       SYNTAX       INTEGER
           {
               enable(1),
               disable(2)
           }
       MAX-ACCESS   read-write
       STATUS       current
       DESCRIPTION
           "Trap control of S-interface.
            enable(1)  - Enable the S interface Trap.
            disable(2) - Disable the S interface trap.
           "
       DEFVAL  {  disable  }
       ::={zxAnIsdnSIfCfgEntry 5}

   zxAnIsdnSIfSyncStatus  OBJECT-TYPE
       SYNTAX       INTEGER
           {
               synchronized(1),
               unsynchronized(2)
           }
       MAX-ACCESS   read-only
       STATUS       current
       DESCRIPTION
           "The synchronized status  of S-interface."
       DEFVAL  {  unsynchronized  }
       ::={zxAnIsdnSIfCfgEntry 6}

   zxAnIsdnSIfAbnormalReason  OBJECT-TYPE
        SYNTAX    INTEGER
            {
                errorIndication2(1),            -- Error Indication 2
                errorIndication3(2),            -- Error Indication 3
                lossOfSignalLevel(3),           -- Loss of Signal Level
                reSyncIndication(4),            -- Re-synchronization indication after a LOF
                frameJump(5),                   -- Frame Jump
                uIfActivationIndication(6),     -- U-Interface Activation Indication
                uIfdeactivationIndication(7),   -- U-Interface Deactivation Indication
                other(255)                      -- Other
            }
       MAX-ACCESS   read-only
       STATUS       current
       DESCRIPTION
           "The abnormal reason of the S-interface."
       ::={zxAnIsdnSIfCfgEntry 7}

--end of zxAnIsdnSIfCfgTable

--------------------------------------------------------------------------------
-- zxAnIsdnBertConfTable
--------------------------------------------------------------------------------
    zxAnIsdnBertConfTable OBJECT-TYPE
        SYNTAX      SEQUENCE OF ZxAnIsdnBertConfEntry
        MAX-ACCESS  not-accessible
        STATUS      current
        DESCRIPTION
            "The BERT function configuration table"
        ::={zxAnIsdnBertMgmtGroup 1}

    zxAnIsdnBertConfEntry OBJECT-TYPE
        SYNTAX       ZxAnIsdnBertConfEntry
        MAX-ACCESS   not-accessible
        STATUS       current
        DESCRIPTION
            "An entry in the BERT function configuration table."
        INDEX
            {
                zxAnIsdnBertConfRack,
                zxAnIsdnBertConfShelf,
                zxAnIsdnBertConfSlot,
                zxAnIsdnBertConfCircuit
            }
        ::={zxAnIsdnBertConfTable 1}

    ZxAnIsdnBertConfEntry ::=
        SEQUENCE{
            zxAnIsdnBertConfRack           Integer32,
            zxAnIsdnBertConfShelf          Integer32,
            zxAnIsdnBertConfSlot           Integer32,
            zxAnIsdnBertConfCircuit        Integer32,
            zxAnIsdnBertAction             INTEGER,
            zxAnIsdnBertLoopbackPosition   INTEGER,
            zxAnIsdnBertThresholdLevel     INTEGER,
            zxAnIsdnBertMeasurePrecision   INTEGER,
            zxAnIsdnBertForceTest          TruthValue,
            zxAnIsdnBertStartDateAndTime   DisplayString,
            zxAnIsdnBertOperStatus         INTEGER,
            zxAnIsdnBertResult             INTEGER,
            zxAnIsdnBertRowStatus          RowStatus
    }

    zxAnIsdnBertConfRack  OBJECT-TYPE
        SYNTAX       Integer32
        MAX-ACCESS   not-accessible
        STATUS       current
        DESCRIPTION  "Rack of ISDN BERT"
        ::={zxAnIsdnBertConfEntry 1}

    zxAnIsdnBertConfShelf  OBJECT-TYPE
        SYNTAX      Integer32
        MAX-ACCESS  not-accessible
        STATUS      current
        DESCRIPTION  "Shelf of ISDN BERT"
        ::={zxAnIsdnBertConfEntry 2}

    zxAnIsdnBertConfSlot  OBJECT-TYPE
        SYNTAX       Integer32
        MAX-ACCESS   not-accessible
        STATUS       current
        DESCRIPTION  "Slot of ISDN BERT"
        ::={zxAnIsdnBertConfEntry 3}

    zxAnIsdnBertConfCircuit  OBJECT-TYPE
        SYNTAX      Integer32
        MAX-ACCESS  not-accessible
        STATUS      current
        DESCRIPTION  "Port of ISDN BERT"
        ::={zxAnIsdnBertConfEntry 4}

    zxAnIsdnBertAction  OBJECT-TYPE
        SYNTAX      INTEGER
           {
               start(1),
               stop(2)
           }
        MAX-ACCESS  read-create
        STATUS      current
        DESCRIPTION
            "The action type of ISDN BERT function."
        ::={zxAnIsdnBertConfEntry 5}

    zxAnIsdnBertLoopbackPosition  OBJECT-TYPE
        SYNTAX      INTEGER
            {
                local(1),
                nt(2),
                teTa(3)
            }
        MAX-ACCESS  read-create
        STATUS      current
        DESCRIPTION
            "The loopback position.
            local(1):Loopback at ISDN circuit of ISDN card.
            nt(2):Loopback at NT  of customer side.
            teTa(3):Loopback at TE/TA of customer side."
        DEFVAL      {local}
        ::={zxAnIsdnBertConfEntry 6}

    zxAnIsdnBertThresholdLevel  OBJECT-TYPE
        SYNTAX      INTEGER
            {
                tenENegtive3(3),
                tenENegtive4(4),
                tenENegtive5(5),
                tenENegtive6(6)
            }
        MAX-ACCESS  read-create
        STATUS      current
        DESCRIPTION
            "The BERT threshold level.
            tenENegtive3(3):10 ^ -3
            tenENegtive4(4):10 ^ -4
            tenENegtive5(5):10 ^ -5
            tenENegtive6(6):10 ^ -6"
        DEFVAL      {tenENegtive3}
        ::={zxAnIsdnBertConfEntry 7}

     zxAnIsdnBertMeasurePrecision     OBJECT-TYPE
        SYNTAX      INTEGER
            {
                neg30To45(1),
                neg22To30(2),
                neg17To20(3),
                neg12To14(4)
            }
        MAX-ACCESS  read-create
        STATUS      current
        DESCRIPTION
            "The measure precision of BERT.
            neg30To45(1):-30% to +45%
            neg22To30(2):-22% to +30%
            neg17To20(3):-17% to +20%
            neg12To14(4):-12% to +14%"
        DEFVAL     {neg30To45}
        ::={zxAnIsdnBertConfEntry 8}

    zxAnIsdnBertForceTest     OBJECT-TYPE
        SYNTAX      TruthValue
        MAX-ACCESS  read-create
        STATUS      current
        DESCRIPTION
            "Whether or not to test if the circuit is not in idle status."
        DEFVAL     {false}
        ::={zxAnIsdnBertConfEntry 9}

    zxAnIsdnBertStartDateAndTime  OBJECT-TYPE
        SYNTAX      DisplayString(SIZE(1..32))
        MAX-ACCESS  read-only
        STATUS      current
        DESCRIPTION
            "The date and time when the last BERT testing is started."
        ::={zxAnIsdnBertConfEntry 10}

    zxAnIsdnBertOperStatus  OBJECT-TYPE
        SYNTAX      INTEGER
           {
               notStarted(1),
               inProgress(2),
               success(3),
               failed(4)
           }
        MAX-ACCESS  read-only
        STATUS      current
        DESCRIPTION
            "The operation status of ISDN BERT."
        DEFVAL      {notStarted}
        ::={zxAnIsdnBertConfEntry 11}

    zxAnIsdnBertResult  OBJECT-TYPE
        SYNTAX      INTEGER
           {
               noResult(1),
               pass(2),
               notPass(3),
               failed(4)
           }
        MAX-ACCESS  read-only
        STATUS      current
        DESCRIPTION
            "The result of ISDN BERT.
            zxAnIsdnBertResult will be noResult(1) when zxAnIsdnBertOperStatus
            is notStarted(1) or inProgress(2).
            zxAnIsdnBertResult will be pass(2) or notPass(3) when
            zxAnIsdnBertOperStatus is success(3).
            zxAnIsdnBertResult will be failed(4) when zxAnIsdnBertOperStatus is
            failed(4)."
        DEFVAL      {noResult}
        ::={zxAnIsdnBertConfEntry 12}

    zxAnIsdnBertRowStatus OBJECT-TYPE
        SYNTAX      RowStatus
        MAX-ACCESS  read-create
        STATUS      current
        DESCRIPTION
           "The status of this conceptual row.  This object is used for
            creating or deleting an entry from this table.
            To create a row in this table, a manager must set this
            object to either createAndGo(4).
            An entry can be deleted by setting this object to destroy(6)."
        ::= {zxAnIsdnBertConfEntry 20}

--------------------------------------------------------------------------------
-- zxAnIsdnBertStatsTable
--------------------------------------------------------------------------------
    zxAnIsdnBertStatsTable OBJECT-TYPE
        SYNTAX      SEQUENCE OF ZxAnIsdnBertStatsEntry
        MAX-ACCESS  not-accessible
        STATUS      current
        DESCRIPTION
            "The BERT function statistic table"
        ::={zxAnIsdnBertMgmtGroup 2}

    zxAnIsdnBertStatsEntry OBJECT-TYPE
        SYNTAX       ZxAnIsdnBertStatsEntry
        MAX-ACCESS   not-accessible
        STATUS       current
        DESCRIPTION
            "An entry in the BERT function statistic table."
            INDEX
                {
                    zxAnIsdnBertStatsRack,
                    zxAnIsdnBertStatsShelf,
                    zxAnIsdnBertStatsSlot,
                    zxAnIsdnBertStatsCircuit
                }
        ::={zxAnIsdnBertStatsTable 1}

    ZxAnIsdnBertStatsEntry ::=
        SEQUENCE{
            zxAnIsdnBertStatsRack          Integer32,
            zxAnIsdnBertStatsShelf         Integer32,
            zxAnIsdnBertStatsSlot          Integer32,
            zxAnIsdnBertStatsCircuit       Integer32,
            zxAnIsdnBertTimeElapsed        Integer32,
            zxAnIsdnBertTxTotalBits        Counter64,
            zxAnIsdnBertRxTotalBits        Counter64,
            zxAnIsdnBertRxErrorBits        Counter32,
            zxAnIsdnBertRxBitErrorRatio    Unsigned32
    }

    zxAnIsdnBertStatsRack  OBJECT-TYPE
        SYNTAX       Integer32
        MAX-ACCESS   not-accessible
        STATUS       current
        DESCRIPTION  "Rack of ISDN BERT"
        ::={zxAnIsdnBertStatsEntry 1}

    zxAnIsdnBertStatsShelf  OBJECT-TYPE
        SYNTAX      Integer32
        MAX-ACCESS  not-accessible
        STATUS      current
        DESCRIPTION  "Shelf of ISDN BERT"
        ::={zxAnIsdnBertStatsEntry 2}

    zxAnIsdnBertStatsSlot  OBJECT-TYPE
        SYNTAX       Integer32
        MAX-ACCESS   not-accessible
        STATUS       current
        DESCRIPTION  "Slot of ISDN BERT"
        ::={zxAnIsdnBertStatsEntry 3}

    zxAnIsdnBertStatsCircuit  OBJECT-TYPE
        SYNTAX      Integer32
        MAX-ACCESS  not-accessible
        STATUS      current
        DESCRIPTION  "Port of ISDN BERT"
        ::={zxAnIsdnBertStatsEntry 4}

    zxAnIsdnBertTimeElapsed  OBJECT-TYPE
        SYNTAX      Integer32
        UNITS       "10ms"
        MAX-ACCESS  read-only
        STATUS      current
        DESCRIPTION  "The elapsed time in the BERT."
        ::={zxAnIsdnBertStatsEntry 5}

    zxAnIsdnBertTxTotalBits  OBJECT-TYPE
        SYNTAX      Counter64
        MAX-ACCESS  read-only
        STATUS      current
        DESCRIPTION  "The total number of bits be sent in the BERT."
        ::={zxAnIsdnBertStatsEntry 6}

    zxAnIsdnBertRxTotalBits  OBJECT-TYPE
        SYNTAX      Counter64
        MAX-ACCESS  read-only
        STATUS      current
        DESCRIPTION  "The total number of bits be received in the BERT."
        ::={zxAnIsdnBertStatsEntry 7}

    zxAnIsdnBertRxErrorBits  OBJECT-TYPE
        SYNTAX      Counter32
        MAX-ACCESS  read-only
        STATUS      current
        DESCRIPTION  "The number of errored bits to be received in the BERT."
        ::={zxAnIsdnBertStatsEntry 8}

    zxAnIsdnBertRxBitErrorRatio  OBJECT-TYPE
        SYNTAX      Unsigned32(0..100)
        UNITS       "percents"
        MAX-ACCESS  read-only
        STATUS      current
        DESCRIPTION  "The ratio of received bit errors in the BERT."
        ::={zxAnIsdnBertStatsEntry 9}


    zxAnIsdnTrunkTerminationIdTable OBJECT-TYPE
        SYNTAX        SEQUENCE OF ZxAnIsdnTrunkTerminationIdEntry
        MAX-ACCESS    not-accessible
        STATUS        current
        DESCRIPTION   "The trunk TerminationId table"
        ::={msagISDNService 12}

    zxAnIsdnTrunkTerminationIdEntry OBJECT-TYPE
        SYNTAX        ZxAnIsdnTrunkTerminationIdEntry
        MAX-ACCESS    not-accessible
        STATUS        current
        DESCRIPTION   "The trunk TerminationId entry."
        INDEX         { zxAnIsdnTrunkTidRack, zxAnIsdnTrunkTidShelf,
                        zxAnIsdnTrunkTidSlot, zxAnIsdnTrunkTidDsx1LinkNo,
                        zxAnIsdnTrunkTidDsx1TsNo}
        ::={zxAnIsdnTrunkTerminationIdTable 1}

    ZxAnIsdnTrunkTerminationIdEntry ::=
       SEQUENCE{
           zxAnIsdnTrunkTidRack                 Integer32,
           zxAnIsdnTrunkTidShelf                Integer32,
           zxAnIsdnTrunkTidSlot                 Integer32,
           zxAnIsdnTrunkTidDsx1LinkNo           Integer32,
           zxAnIsdnTrunkTidDsx1TsNo             Integer32,
           zxAnIsdnTrunkTidPrefix               DisplayString,
           zxAnIsdnTrunkTidType                 INTEGER,
           zxAnIsdnTrunkTidOperNum              Integer32,
           zxAnIsdnTrunkTidDigitBeginNo         Integer32,
           zxAnIsdnTrunkTidDigitLength          Integer32,
           zxAnIsdnTrunkTidMgId                 Integer32,
           zxAnIsdnTrunkTerminationId           DisplayString,
           zxAnIsdnTrunkTidRowStatus            RowStatus
      }


    zxAnIsdnTrunkTidRack  OBJECT-TYPE
      SYNTAX        Integer32
      MAX-ACCESS    not-accessible
      STATUS        current
      DESCRIPTION   "This object indicates the rack number."
      ::={zxAnIsdnTrunkTerminationIdEntry 1}

    zxAnIsdnTrunkTidShelf   OBJECT-TYPE
      SYNTAX        Integer32
      MAX-ACCESS    not-accessible
      STATUS        current
      DESCRIPTION   "This object indicates the shelf number."
      ::={zxAnIsdnTrunkTerminationIdEntry 2}


    zxAnIsdnTrunkTidSlot   OBJECT-TYPE
      SYNTAX        Integer32
      MAX-ACCESS    not-accessible
      STATUS        current
      DESCRIPTION   "This object indicates the slot number."
      ::={zxAnIsdnTrunkTerminationIdEntry 3}

    zxAnIsdnTrunkTidDsx1LinkNo   OBJECT-TYPE
      SYNTAX        Integer32(1..16)
      MAX-ACCESS    not-accessible
      STATUS        current
      DESCRIPTION   "This object indicates the E1/T1 number."
      ::={zxAnIsdnTrunkTerminationIdEntry 4}

    zxAnIsdnTrunkTidDsx1TsNo   OBJECT-TYPE
      SYNTAX        Integer32(1..32)
      MAX-ACCESS    not-accessible
      STATUS        current
      DESCRIPTION   " The begin TS number of trunk terminationID."
      ::={zxAnIsdnTrunkTerminationIdEntry 5}

    zxAnIsdnTrunkTidPrefix   OBJECT-TYPE
      SYNTAX        DisplayString(SIZE(1..64))
      MAX-ACCESS    read-create
      STATUS        current
      DESCRIPTION   "The termination ID's prefix.
            The termination ID's total length(prefix and digit) is 64."
      ::={zxAnIsdnTrunkTerminationIdEntry 6}

    zxAnIsdnTrunkTidType   OBJECT-TYPE
      SYNTAX        INTEGER
      {
         type1(1),
         type2(2),
         type3(3)
       }
      MAX-ACCESS    read-create
      STATUS        current
      DESCRIPTION "
        type1: USER00100100000-USER00100100031,
        type2: USER0-USER31
        type3: User000-USER031 "
      ::={zxAnIsdnTrunkTerminationIdEntry 7}

    zxAnIsdnTrunkTidOperNum    OBJECT-TYPE
      SYNTAX        Integer32(1..30)
      MAX-ACCESS    read-create
      STATUS        current
      DESCRIPTION   "Batch operation number."
      ::={zxAnIsdnTrunkTerminationIdEntry 8}

    zxAnIsdnTrunkTidDigitBeginNo   OBJECT-TYPE
      SYNTAX        Integer32(0..65535)
      MAX-ACCESS    read-create
      STATUS        current
      DESCRIPTION   "When zxAnIsdnTrunkTidType is type2 or type3,
                     zxAnIsdnTrunkTidBeginNo can be used"
      ::={zxAnIsdnTrunkTerminationIdEntry 9}

    zxAnIsdnTrunkTidDigitLength   OBJECT-TYPE
      SYNTAX        Integer32(2..64)
      MAX-ACCESS    read-create
      STATUS        current
      DESCRIPTION   "The termination ID's digit length.
         when zxAnIsdnTrunkTidType is type3,
         zxAnIsdnTrunkTidDigitBeginNo can be used"
      ::={zxAnIsdnTrunkTerminationIdEntry 10}

    zxAnIsdnTrunkTidMgId   OBJECT-TYPE
      SYNTAX        Integer32(1..255)
      MAX-ACCESS    read-create
      STATUS        current
      DESCRIPTION   "This object indicates the MG ID."
      ::={zxAnIsdnTrunkTerminationIdEntry 11}

    zxAnIsdnTrunkTerminationId   OBJECT-TYPE
      SYNTAX        DisplayString(SIZE(0..64))
      MAX-ACCESS    read-only
      STATUS        current
      DESCRIPTION   "The termination ID."
      ::={zxAnIsdnTrunkTerminationIdEntry 12}

    zxAnIsdnTrunkTidRowStatus   OBJECT-TYPE
      SYNTAX        RowStatus
      MAX-ACCESS    read-create
      STATUS        current
      DESCRIPTION   "The row status of this entry."
      ::={zxAnIsdnTrunkTerminationIdEntry 50}

--------------------------------------------------------------------------------
--E1 Trunk Table
--------------------------------------------------------------------------------

    zxAnIsdnTrunkTable OBJECT-TYPE
        SYNTAX      SEQUENCE OF ZxAnIsdnTrunkEntry
        MAX-ACCESS  not-accessible
        STATUS      current
        DESCRIPTION
            "E1 trunk table.
            Trunk means ISDN(30B+D)."
        ::={msagISDNService 13}

    zxAnIsdnTrunkEntry OBJECT-TYPE
        SYNTAX      ZxAnIsdnTrunkEntry
        MAX-ACCESS  not-accessible
        STATUS      current
        DESCRIPTION
            "E1 trunk entry."
        INDEX { zxAnIsdnTrunkRack, zxAnIsdnTrunkShelf, zxAnIsdnTrunkSlot,
                zxAnIsdnTrunkDsx1LinkNo, zxAnIsdnTrunkDsx1TsNo }
        ::={zxAnIsdnTrunkTable 1}

    ZxAnIsdnTrunkEntry ::= SEQUENCE {
            zxAnIsdnTrunkRack       Integer32,
            zxAnIsdnTrunkShelf      Integer32,
            zxAnIsdnTrunkSlot       Integer32,
            zxAnIsdnTrunkDsx1LinkNo Integer32,
            zxAnIsdnTrunkDsx1TsNo   Integer32,
            zxAnIsdnTrunkStatus     BITS
        }

    zxAnIsdnTrunkRack    OBJECT-TYPE
        SYNTAX       Integer32
        MAX-ACCESS   not-accessible
        STATUS       current
        DESCRIPTION
            "Rack number of trunk user."
        ::= { zxAnIsdnTrunkEntry 1 }

    zxAnIsdnTrunkShelf   OBJECT-TYPE
        SYNTAX       Integer32
        MAX-ACCESS   not-accessible
        STATUS       current
        DESCRIPTION
            "Shelf number of trunk user."
        ::= { zxAnIsdnTrunkEntry 2 }

    zxAnIsdnTrunkSlot    OBJECT-TYPE
        SYNTAX       Integer32
        MAX-ACCESS   not-accessible
        STATUS       current
        DESCRIPTION
            "Slot number of trunk user."
        ::= { zxAnIsdnTrunkEntry 3 }

    zxAnIsdnTrunkDsx1LinkNo    OBJECT-TYPE
        SYNTAX       Integer32
        MAX-ACCESS   not-accessible
        STATUS       current
        DESCRIPTION
            "E1 link number of trunk user."
        ::= { zxAnIsdnTrunkEntry 4 }

    zxAnIsdnTrunkDsx1TsNo    OBJECT-TYPE
        SYNTAX      Integer32
        MAX-ACCESS  not-accessible
        STATUS      current
        DESCRIPTION
            "Time slot number of trunk user."
        ::= { zxAnIsdnTrunkEntry 5 }

    zxAnIsdnTrunkStatus     OBJECT-TYPE
        SYNTAX      BITS {
            idle(0),
            commOff(1),
            powerOff(2),
            fault(3),
            manualBlock(4),
            seizure(5),
            spc(6)
        }
        MAX-ACCESS  read-only
        STATUS      current
        DESCRIPTION
            "Status of trunk user.
            idle(0):        value 1 means idle status,
            commOff(1):     value 1 means communication break off,
            powerOff(2):    value 1 means power off,
            fault(3):       value 1 means fault,
            manualBlock(4): value 1 means block manually,
            seizure(5):     value 1 means this time slot is seizured by user,
            spc(Signaling Point Code)(6): value 1 means this
                                 time slot is used by signaling.
            "
         ::= { zxAnIsdnTrunkEntry 6 }

--------------------------------------------------------------------------------
--zxAnIsdnCallStatsTable
--------------------------------------------------------------------------------

    zxAnIsdnCallStatsTable OBJECT-TYPE
        SYNTAX      SEQUENCE OF ZxAnIsdnCallStatsEntry
        MAX-ACCESS  not-accessible
        STATUS      current
        DESCRIPTION
            "ISDN call statistics table."
        ::= { msagISDNService 14 }

    zxAnIsdnCallStatsEntry OBJECT-TYPE
        SYNTAX      ZxAnIsdnCallStatsEntry
        MAX-ACCESS  not-accessible
        STATUS      current
        DESCRIPTION
            "ISDN call statistics entry."
        INDEX { zxAnIsdnCallStatsRack,zxAnIsdnCallStatsShelf,
                zxAnIsdnCallStatsSlot,zxAnIsdnCallStatsPort}
        ::={zxAnIsdnCallStatsTable 1}

    ZxAnIsdnCallStatsEntry ::= SEQUENCE {
        zxAnIsdnCallStatsRack           Integer32,
        zxAnIsdnCallStatsShelf          Integer32,
        zxAnIsdnCallStatsSlot           Integer32,
        zxAnIsdnCallStatsPort           Integer32,
        zxAnIsdnSuccessIncomingCalls    Counter32,
        zxAnIsdnFailedIncomingCalls     Counter32,
        zxAnIsdnSuccessOutgoingCalls    Counter32,
        zxAnIsdnFailedOutgoingCalls     Counter32,
        zxAnIsdnActiveIncomingCalls     Counter32,
        zxAnIsdnActiveOutgoingCalls     Counter32
    }

    zxAnIsdnCallStatsRack  OBJECT-TYPE
        SYNTAX      Integer32
        MAX-ACCESS  not-accessible
        STATUS      current
        DESCRIPTION
            "Rack of ISDN port."
        ::={zxAnIsdnCallStatsEntry 1}

    zxAnIsdnCallStatsShelf       OBJECT-TYPE
        SYNTAX      Integer32
        MAX-ACCESS  not-accessible
        STATUS      current
        DESCRIPTION
            "Shelf of ISDN port."
        ::={zxAnIsdnCallStatsEntry 2}

    zxAnIsdnCallStatsSlot  OBJECT-TYPE
        SYNTAX      Integer32
        MAX-ACCESS  not-accessible
        STATUS      current
        DESCRIPTION
            "Slot of ISDN port."
        ::={zxAnIsdnCallStatsEntry 3}

    zxAnIsdnCallStatsPort  OBJECT-TYPE
        SYNTAX      Integer32
        MAX-ACCESS  not-accessible
        STATUS      current
        DESCRIPTION
            "2B+D:port no. of the card. 30B+D:E1 link no. of the card."
        ::={zxAnIsdnCallStatsEntry 4}

    zxAnIsdnSuccessIncomingCalls   OBJECT-TYPE
        SYNTAX      Counter32
        MAX-ACCESS  read-only
        STATUS      current
        DESCRIPTION
            "Count of the successful session incomming calls."
        ::= { zxAnIsdnCallStatsEntry 5}

    zxAnIsdnFailedIncomingCalls   OBJECT-TYPE
        SYNTAX      Counter32
        MAX-ACCESS  read-only
        STATUS      current
        DESCRIPTION
            "Count of the unsuccessful session incomming calls."
        ::= { zxAnIsdnCallStatsEntry 6 }

    zxAnIsdnSuccessOutgoingCalls   OBJECT-TYPE
        SYNTAX      Counter32
        MAX-ACCESS  read-only
        STATUS      current
        DESCRIPTION
            "Count of the successful session outgoing calls."
        ::= { zxAnIsdnCallStatsEntry 7 }

    zxAnIsdnFailedOutgoingCalls   OBJECT-TYPE
        SYNTAX      Counter32
        MAX-ACCESS  read-only
        STATUS      current
        DESCRIPTION
            "Count of the unsuccessful session outgoing calls."
        ::= { zxAnIsdnCallStatsEntry 8 }

    zxAnIsdnActiveIncomingCalls   OBJECT-TYPE
        SYNTAX      Counter32
        MAX-ACCESS  read-only
        STATUS      current
        DESCRIPTION
            "Current count of the session incomming calls."
        ::= { zxAnIsdnCallStatsEntry 9 }

    zxAnIsdnActiveOutgoingCalls   OBJECT-TYPE
        SYNTAX      Counter32
        MAX-ACCESS  read-only
        STATUS      current
        DESCRIPTION
            "Current count of the session outgoing calls."
        ::= { zxAnIsdnCallStatsEntry 10 }

--------------------------------------------------------------------------------
--zxAnIsdnRemotePowerSupplyTable
--------------------------------------------------------------------------------

    zxAnIsdnRemotePowerSupplyTable OBJECT-TYPE
        SYNTAX      SEQUENCE OF ZxAnIsdnRemotePowerSupplyEntry
        MAX-ACCESS  not-accessible
        STATUS      current
        DESCRIPTION
            "ISDN remote power supply configuration table."
        ::={msagISDNService 15}

    zxAnIsdnRemotePowerSupplyEntry OBJECT-TYPE
        SYNTAX      ZxAnIsdnRemotePowerSupplyEntry
        MAX-ACCESS  not-accessible
        STATUS      current
        DESCRIPTION
            "ISDN remote power supply configuration entry."
        INDEX { zxAnIsdnRemotePowerSupplyRack,zxAnIsdnRemotePowerSupplyShelf,
                zxAnIsdnRemotePowerSupplySlot}
       ::={zxAnIsdnRemotePowerSupplyTable 1}

    ZxAnIsdnRemotePowerSupplyEntry ::= SEQUENCE {
        zxAnIsdnRemotePowerSupplyRack           Integer32,
        zxAnIsdnRemotePowerSupplyShelf          Integer32,
        zxAnIsdnRemotePowerSupplySlot           Integer32,
        zxAnIsdnRemotePowerSupplyEnable         INTEGER
        }

    zxAnIsdnRemotePowerSupplyRack  OBJECT-TYPE
        SYNTAX       Integer32
        MAX-ACCESS   not-accessible
        STATUS       current
        DESCRIPTION
            "Rack number."
        ::={zxAnIsdnRemotePowerSupplyEntry 1}

    zxAnIsdnRemotePowerSupplyShelf  OBJECT-TYPE
        SYNTAX       Integer32
        MAX-ACCESS   not-accessible
        STATUS       current
        DESCRIPTION
            "Shelf number."
        ::={zxAnIsdnRemotePowerSupplyEntry 2}

    zxAnIsdnRemotePowerSupplySlot  OBJECT-TYPE
        SYNTAX       Integer32
        MAX-ACCESS   not-accessible
        STATUS       current
        DESCRIPTION
            "Slot number."
        ::={zxAnIsdnRemotePowerSupplyEntry 3}

    zxAnIsdnRemotePowerSupplyEnable  OBJECT-TYPE
        SYNTAX       INTEGER
           {
               enabled(1),
               disabled(2)
           }
        MAX-ACCESS   read-write
        STATUS       current
        DESCRIPTION
            "Enables and disables ISDN remote power supply."
        DEFVAL  { enabled }
        ::={zxAnIsdnRemotePowerSupplyEntry 4}

--------------------------------------------------------------------------------
--zxAnIsdnTrapObjects
--------------------------------------------------------------------------------

    zxAnIsdnTrapObjects OBJECT IDENTIFIER ::= { msagISDNService 100 }

    zxAnIsdnSInterfaceUnsyncAlm NOTIFICATION-TYPE
        OBJECTS { zxAnIsdnSIfSyncStatus }
        STATUS  current
        DESCRIPTION
            "A zxAnIsdnSInterfaceUnsyncAlm is sent when the agent has
            detected that the S-interface is unsynchronized."
       ::= { zxAnIsdnTrapObjects 1 }

    zxAnIsdnSInterfaceUnsyncClr NOTIFICATION-TYPE
        OBJECTS { zxAnIsdnSIfSyncStatus }
        STATUS  current
        DESCRIPTION
            "A zxAnIsdnSInterfaceUnsyncClr is sent when the agent has
            detected that the S-interface is synchronized."
       ::= { zxAnIsdnTrapObjects 2 }

    zxAnIsdnUInterfaceAbnormal NOTIFICATION-TYPE
        OBJECTS { zxAnIsdnUIfAbnormalReason }
        STATUS  current
        DESCRIPTION
            "A zxAnIsdnUInterfaceAbnormal is sent when the agent has
            detected that the U-interface is abnormal."
       ::= { zxAnIsdnTrapObjects 3 }

    zxAnIsdnSInterfaceAbnormal NOTIFICATION-TYPE
        OBJECTS { zxAnIsdnSIfAbnormalReason }
        STATUS  current
        DESCRIPTION
            "A zxAnIsdnSInterfaceAbnormal is sent when the agent has
            detected that the S-interface is abnormal."
       ::= { zxAnIsdnTrapObjects 4 }

END
