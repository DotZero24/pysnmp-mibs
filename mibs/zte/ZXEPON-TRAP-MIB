-- *****************************************************************
-- ZTE EPON PERFORMANCE MIB
--
-- 03-06-2007
--
-- Copyright(c) 2007 ZTE Corporation
-- All rights reserved.
-- *****************************************************************

ZXEPON-TRAP-MIB DEFINITIONS ::= BEGIN
    IMPORTS
        ifIndex,DisplayString                                FROM RFC1213-MIB
        MODULE-IDENTITY, OBJECT-TYPE, NOTIFICATION-TYPE      FROM SNMPv2-SMI
        zxAnEponMib                                          FROM ZTE-MASTER-MIB
        onuOnlineForwardAction,onuRegisterLoid  FROM ZXEPON-SERVICE-PRIVATE-MIB;


zxAnEponTrap        MODULE-IDENTITY
    LAST-UPDATED "200704040000Z"
    ORGANIZATION    "Zhongxing Telcom Co. Ltd."
    CONTACT-INFO    "Zhongxing Telcom Co. Ltd.
                     E-mail: info@mail.zte.com.cn
                     http  : www.zte.com.cn or www.zhongxing.com"

    DESCRIPTION
         ""
    ::= { zxAnEponMib 10 }

    zxAnEponTrapOlt   OBJECT IDENTIFIER ::= { zxAnEponTrap 1}
    zxAnEponTrapBindVar   OBJECT IDENTIFIER ::= { zxAnEponTrap 2}
    zxAnEponTrapEvent   OBJECT IDENTIFIER ::= { zxAnEponTrap 3}
    zxAnEponTrapOnu     OBJECT IDENTIFIER ::= { zxAnEponTrap 4}
--zxAnEponTrapOlt

    zxAnEponOnuBerOverThreshold        NOTIFICATION-TYPE
        OBJECTS {
                ifIndex, zxAnEponTrapEventString,zxAnEponTrapOnuType,zxAnEponTrapOltPortName,zxAnEponTrapOnuDesc
                }
        STATUS  current
        DESCRIPTION
            ""
        ::={zxAnEponTrapOlt 1}

    zxAnEponOnuBerOverThresholdRestore        NOTIFICATION-TYPE
        OBJECTS {
                ifIndex, zxAnEponTrapEventString,zxAnEponTrapOnuType,zxAnEponTrapOltPortName,zxAnEponTrapOnuDesc
                }
        STATUS  current
        DESCRIPTION
            ""
        ::={zxAnEponTrapOlt 2}

    zxAnEponDeviceOltPortBerState        NOTIFICATION-TYPE
        OBJECTS {
                ifIndex,zxAnEponTrapOltPortName
                }
        STATUS  current
        DESCRIPTION
            ""
        ::={zxAnEponTrapOlt 11}

    zxAnEponDeviceOltPortBerStateRestore        NOTIFICATION-TYPE
        OBJECTS {
                ifIndex,zxAnEponTrapOltPortName
                }
        STATUS  current
        DESCRIPTION
            ""
        ::={zxAnEponTrapOlt 12}

    zxAnEponPonLOS        NOTIFICATION-TYPE
        OBJECTS {
                ifIndex,zxAnEponTrapPonLosReason,zxAnEponTrapOltPortName
                }
        STATUS  current
        DESCRIPTION
            ""
        ::={zxAnEponTrapOlt 13}

    zxAnEponPonLOSRestore        NOTIFICATION-TYPE
        OBJECTS {
                ifIndex,zxAnEponTrapPonLosReason,zxAnEponTrapOltPortName
                }
        STATUS  current
        DESCRIPTION
            ""
        ::={zxAnEponTrapOlt 14}

    zxAnEponOnuOffLine        NOTIFICATION-TYPE
        OBJECTS {
                ifIndex,zxAnEponTrapOnuOffLineReason,zxAnEponTrapOnuType,zxAnEponTrapOltPortName,zxAnEponTrapOnuDesc,zxAnEponTrapDid
                }
        STATUS  current
        DESCRIPTION
            ""
        ::={zxAnEponTrapOlt 15}

    zxAnEponOnuOffLineRestore        NOTIFICATION-TYPE
        OBJECTS {
                ifIndex,zxAnEponTrapOnuOffLineReason,zxAnEponTrapOnuType,zxAnEponTrapOltPortName,zxAnEponTrapOnuDesc,zxAnEponTrapDid
                }
        STATUS  current
        DESCRIPTION
            ""
        ::={zxAnEponTrapOlt 16}

    zxAnEponOnuErroredSymbolPeriodEvent        NOTIFICATION-TYPE
        OBJECTS {
                ifIndex,zxAnEponTrapOnuType,zxAnEponTrapOltPortName,zxAnEponTrapOnuDesc
                }
        STATUS  current
        DESCRIPTION
            ""
        ::={zxAnEponTrapOlt 17}

    zxAnEponOnuErroredSymbolPeriodEventRestore        NOTIFICATION-TYPE
        OBJECTS {
                ifIndex,zxAnEponTrapOnuType,zxAnEponTrapOltPortName,zxAnEponTrapOnuDesc
                }
        STATUS  current
        DESCRIPTION
            ""
        ::={zxAnEponTrapOlt 18}


    zxAnEponOnuErroredFrameEvent        NOTIFICATION-TYPE
        OBJECTS {
                ifIndex,zxAnEponTrapOnuType,zxAnEponTrapOltPortName,zxAnEponTrapOnuDesc
                }
        STATUS  current
        DESCRIPTION
            ""
        ::={zxAnEponTrapOlt 19}

    zxAnEponOnuErroredFrameEventRestore        NOTIFICATION-TYPE
        OBJECTS {
                ifIndex,zxAnEponTrapOnuType,zxAnEponTrapOltPortName,zxAnEponTrapOnuDesc
                }
        STATUS  current
        DESCRIPTION
            ""
        ::={zxAnEponTrapOlt 20}


    zxAnEponOnuErroredFramePeriodEvent        NOTIFICATION-TYPE
        OBJECTS {
                ifIndex,zxAnEponTrapOnuType,zxAnEponTrapOltPortName,zxAnEponTrapOnuDesc
                }
        STATUS  current
        DESCRIPTION
            ""
        ::={zxAnEponTrapOlt 21}

    zxAnEponOnuErroredFramePeriodEventRestore        NOTIFICATION-TYPE
        OBJECTS {
                ifIndex,zxAnEponTrapOnuType,zxAnEponTrapOltPortName,zxAnEponTrapOnuDesc
                }
        STATUS  current
        DESCRIPTION
            ""
        ::={zxAnEponTrapOlt 22}

    zxAnEponOnuErroredFrameSecondsSummaryEvent        NOTIFICATION-TYPE
        OBJECTS {
                ifIndex,zxAnEponTrapOnuType,zxAnEponTrapOltPortName,zxAnEponTrapOnuDesc
                }
        STATUS  current
        DESCRIPTION
            ""
        ::={zxAnEponTrapOlt 23}

    zxAnEponOnuErroredFrameSecondsSummaryEventRestore        NOTIFICATION-TYPE
        OBJECTS {
                ifIndex,zxAnEponTrapOnuType,zxAnEponTrapOltPortName,zxAnEponTrapOnuDesc
                }
        STATUS  current
        DESCRIPTION
            ""
        ::={zxAnEponTrapOlt 24}

    zxAnEponOnuUplinkBitError        NOTIFICATION-TYPE
        OBJECTS {
                ifIndex,zxAnEponTrapOnuType,zxAnEponTrapOltPortName,zxAnEponTrapOnuDesc
                }
        STATUS  current
        DESCRIPTION
            ""
        ::={zxAnEponTrapOlt 25}

    zxAnEponOnuUplinkBitErrorRestore        NOTIFICATION-TYPE
        OBJECTS {
                ifIndex,zxAnEponTrapOnuType,zxAnEponTrapOltPortName,zxAnEponTrapOnuDesc
                }
        STATUS  current
        DESCRIPTION
            ""
        ::={zxAnEponTrapOlt 26}

    zxAnEponOnuUplinkFrameError        NOTIFICATION-TYPE
        OBJECTS {
                ifIndex,zxAnEponTrapOnuType,zxAnEponTrapOltPortName,zxAnEponTrapOnuDesc
                }
        STATUS  current
        DESCRIPTION
            ""
        ::={zxAnEponTrapOlt 27}

    zxAnEponOnuUplinkFrameErrorRestore        NOTIFICATION-TYPE
        OBJECTS {
                ifIndex,zxAnEponTrapOnuType,zxAnEponTrapOltPortName,zxAnEponTrapOnuDesc
                }
        STATUS  current
        DESCRIPTION
            ""
        ::={zxAnEponTrapOlt 28}

    zxAnEponOnuAuthSuccMsg        NOTIFICATION-TYPE
        OBJECTS {
                ifIndex,zxAnEponTrapOnuType,zxAnEponTrapOltPortName,
                zxAnEponTrapOnuDesc,onuOnlineForwardAction,
                zxAnEponOnuActualSpeedType
                }
        STATUS  current
        DESCRIPTION
            "ONU authentication success message."
        ::={zxAnEponTrapOlt 29}

    zxAnEponPonOpticalTransceiverLos        NOTIFICATION-TYPE
        OBJECTS {
                ifIndex,zxAnEponTrapOltPortName
                }
        STATUS  current
        DESCRIPTION
            "OLT PON Port Optical Modules LOS."
        ::={zxAnEponTrapOlt 30}

    zxAnEponPonOpticalTransceiverLosRestore      NOTIFICATION-TYPE
        OBJECTS {
                ifIndex,zxAnEponTrapOltPortName
                }
        STATUS  current
        DESCRIPTION
            "OLT PON Port Optical Modules LOS restore."
        ::={zxAnEponTrapOlt 31}

    zxAnEponLoidConflict NOTIFICATION-TYPE
        OBJECTS {   ifIndex,onuRegisterLoid,zxAnEponTrapMac,zxAnEponOnuIfIndex }
        STATUS             current
        DESCRIPTION
           "The LOID conflict trap that is generated when unauthorized ONU
             reports an LOID that has been binded by other registered ONU.
             The first ifIndex indicates the PON port of unauthorized ONU.
             The zxAnEponTrapMac indicates the MAC of unauthorized ONU.
             zxAnEponOnuIfIndex indicates the authorized ONU whih the
             same LOID.
             "
       ::= { zxAnEponTrapOlt 32 }

--zxAnEponTrapBindVar

    zxAnEponTrapDid OBJECT-TYPE
        SYNTAX      OCTET STRING(SIZE (0..255))
        MAX-ACCESS  read-only
        STATUS      current
        DESCRIPTION
                ""
        ::= { zxAnEponTrapBindVar 1 }

    zxAnEponTrapMac OBJECT-TYPE
        SYNTAX      OCTET STRING(SIZE (0..255))
        MAX-ACCESS  read-only
        STATUS      current
        DESCRIPTION
                ""
        ::= { zxAnEponTrapBindVar 2 }

    zxAnEponTrapIp OBJECT-TYPE
        SYNTAX      OCTET STRING(SIZE (0..255))
        MAX-ACCESS  read-only
        STATUS      current
        DESCRIPTION
                ""
        ::= { zxAnEponTrapBindVar 3 }

    zxAnEponTrapMask OBJECT-TYPE
        SYNTAX      OCTET STRING(SIZE (0..255))
        MAX-ACCESS  read-only
        STATUS      current
        DESCRIPTION
                ""
        ::= { zxAnEponTrapBindVar 4 }

    zxAnEponTrapOnuType OBJECT-TYPE
        SYNTAX      OCTET STRING(SIZE (0..255))
        MAX-ACCESS  read-only
        STATUS      current
        DESCRIPTION
                ""
        ::= { zxAnEponTrapBindVar 5 }

    zxAnEponTrapOnuName OBJECT-TYPE
        SYNTAX      OCTET STRING(SIZE (0..255))
        MAX-ACCESS  read-only
        STATUS      current
        DESCRIPTION
                ""
        ::= { zxAnEponTrapBindVar 6 }

    zxAnEponTrapPonLosReason OBJECT-TYPE
        SYNTAX      INTEGER
                        {
                        fiberBroken(1),
                        otherReasons(2),
                        allOnuDyingGasp(3),
                        allOnuNeverOnline(4)
                        }
        MAX-ACCESS  read-only
        STATUS      current
        DESCRIPTION
                "OLT LOS Reason
                 fiberBroken:trunk or branch fiber is broken.
                 allOnuDyingGasp:all ONUs under the PON port are
                                 power off.
                 allOnuNeverOnline:all ONUs under the PON port are
                                   never online.
                 otherReasons:other reasons."
        ::= { zxAnEponTrapBindVar 7 }

    zxAnEponTrapOnuOffLineReason OBJECT-TYPE
        SYNTAX      INTEGER
                        {
                        subtrunkfibrebreak(1),
                        onupoweroff(2)
                        }
        MAX-ACCESS  read-only
        STATUS      current
        DESCRIPTION
                ""
        ::= { zxAnEponTrapBindVar 8 }

    zxAnEponTrapOltPortName OBJECT-TYPE
        SYNTAX      OCTET STRING(SIZE (0..255))
        MAX-ACCESS  read-only
        STATUS      current
        DESCRIPTION
                ""
        ::= { zxAnEponTrapBindVar 9 }

    zxAnEponTrapOnuModel OBJECT-TYPE
        SYNTAX      OCTET STRING(SIZE (0..255))
        MAX-ACCESS  read-only
        STATUS      current
        DESCRIPTION
                ""
        ::= { zxAnEponTrapBindVar 10 }

    zxAnEponTrapOnuDesc OBJECT-TYPE
        SYNTAX      OCTET STRING(SIZE (0..255))
        MAX-ACCESS  read-only
        STATUS      current
        DESCRIPTION
                ""
        ::= { zxAnEponTrapBindVar 11 }

    zxAnEponTrapTime OBJECT-TYPE
        SYNTAX      OCTET STRING(SIZE (0..255))
        MAX-ACCESS  read-only
        STATUS      current
        DESCRIPTION
                ""
        ::= { zxAnEponTrapBindVar 12 }

    zxAnEponRogueOnuIdList OBJECT-TYPE
        SYNTAX      OBJECT IDENTIFIER
        MAX-ACCESS  read-only
        STATUS      current
        DESCRIPTION
                "The rogue ONU id list, that has been authenticated."
        ::= { zxAnEponTrapBindVar 13 }

    zxAnEponHighProbabilityRogueOnuIdList OBJECT-TYPE
        SYNTAX      OBJECT IDENTIFIER
        MAX-ACCESS  read-only
        STATUS      current
        DESCRIPTION
                "The high possibility rogue ONU id list, that has been authenticated."
        ::= { zxAnEponTrapBindVar 14 }

    zxAnEponLowProbabilityRogueOnuIdList OBJECT-TYPE
        SYNTAX      OBJECT IDENTIFIER
        MAX-ACCESS  read-only
        STATUS      current
        DESCRIPTION
                "The low possibility rogue ONU id list, that has been authenticated."
        ::= { zxAnEponTrapBindVar 15 }

    zxAnEponRogueUnauthOnuList OBJECT-TYPE
        SYNTAX      OCTET STRING(SIZE (0..768))
        MAX-ACCESS  read-only
        STATUS      current
        DESCRIPTION
                "The rogue ONU MAC list, that has been unauthenticated."
        ::= { zxAnEponTrapBindVar 16 }

    zxAnEponHighPossibilityRogueUnauthOnuList OBJECT-TYPE
        SYNTAX      OCTET STRING(SIZE (0..768))
        MAX-ACCESS  read-only
        STATUS      current
        DESCRIPTION
                "The high possibility rogue ONU MAC list, that has been unauthenticated."
        ::= { zxAnEponTrapBindVar 17 }

    zxAnEponLowPossibilityRogueUnauthOnuList OBJECT-TYPE
        SYNTAX      OCTET STRING(SIZE (0..768))
        MAX-ACCESS  read-only
        STATUS      current
        DESCRIPTION
                "The low possibility rogue ONU MAC list, that has been unauthenticated."
        ::= { zxAnEponTrapBindVar 18 }

    zxAnEponOnuActualSpeedType OBJECT-TYPE
        SYNTAX      INTEGER {
                    upDownstream1G(1),
                    upDownstream10G(2),
                    upstream1GAndDownstream10G(3)
                    }
        MAX-ACCESS  read-only
        STATUS      current
        DESCRIPTION
                "The actual speed type of ONU."
        ::= { zxAnEponTrapBindVar 19 }

    zxAnEponOnuConfigSpeedType OBJECT-TYPE
        SYNTAX      INTEGER {
                    upDownstream1G(1),
                    upDownstream10G(2),
                    upstream1GAndDownstream10G(3)
                    }
        MAX-ACCESS  read-only
        STATUS      current
        DESCRIPTION
                "The config speed type of ONU."
        ::= { zxAnEponTrapBindVar 20 }

    zxAnEponOnuIfIndex OBJECT-TYPE
         SYNTAX      INTEGER
         MAX-ACCESS  read-only
         STATUS      current
         DESCRIPTION
              "A unique value for each interface.  Its value
               ranges between 1 and the value of ifNumber.  The
               value for each interface must remain constant at
               least from one re-initialization of the entity's
               network management system to the next re-
                     initialization."
         ::= { zxAnEponTrapBindVar 21 }

--zxAnEponTrapEvent

    zxAnEponTrapEventString OBJECT-TYPE
        SYNTAX      OCTET STRING(SIZE (0..256))
        MAX-ACCESS  read-only
        STATUS      current
        DESCRIPTION
                ""
        ::= { zxAnEponTrapEvent 1 }


    zxAnEponTrapEventOltReset        NOTIFICATION-TYPE
        OBJECTS {
                ifIndex,zxAnEponTrapOltPortName
                }
        STATUS  current
        DESCRIPTION
            ""
        ::={zxAnEponTrapEvent 2}

    zxAnEponTrapEventOnuOffline        NOTIFICATION-TYPE
        OBJECTS {
                ifIndex
                }
        STATUS  current
        DESCRIPTION
            ""
        ::={zxAnEponTrapEvent 3}

    zxAnEponTrapEventOnuOnline        NOTIFICATION-TYPE
        OBJECTS {
                ifIndex
                }
        STATUS  current
        DESCRIPTION
            ""
        ::={zxAnEponTrapEvent 4}

    zxAnEponTrapEventExtendedOamDiscoveryFail        NOTIFICATION-TYPE
        OBJECTS {
                ifIndex,zxAnEponTrapOltPortName,zxAnEponTrapOnuDesc
                }
        STATUS  current
        DESCRIPTION
            ""
        ::={zxAnEponTrapEvent 5}

    zxAnEponTrapEventLocalOnuConfigureFail        NOTIFICATION-TYPE
        OBJECTS {
                ifIndex,zxAnEponTrapOnuType,zxAnEponTrapOltPortName,zxAnEponTrapOnuDesc
                }
        STATUS  current
        DESCRIPTION
            ""
        ::={zxAnEponTrapEvent 6}

    zxAnEponTrapEventUnkownOnuOffline        NOTIFICATION-TYPE
        OBJECTS {
                ifIndex,zxAnEponTrapEventString,zxAnEponTrapOnuType,zxAnEponTrapOltPortName,zxAnEponTrapDid
                }
        STATUS  current
        DESCRIPTION
            ""
        ::={zxAnEponTrapEvent 7}

    zxAnEponTrapEventDenyUnkownOnuRegister        NOTIFICATION-TYPE
        OBJECTS {
                ifIndex,zxAnEponTrapEventString,zxAnEponTrapOnuType,zxAnEponTrapOltPortName,zxAnEponTrapDid
                }
        STATUS  current
        DESCRIPTION
            ""
        ::={zxAnEponTrapEvent 8}

    zxAnEponTrapEventUnkownOnuOnline        NOTIFICATION-TYPE
        OBJECTS {
                ifIndex,zxAnEponTrapEventString,zxAnEponTrapOnuType,zxAnEponTrapOltPortName,zxAnEponTrapDid
                }
        STATUS  current
        DESCRIPTION
            ""
        ::={zxAnEponTrapEvent 9}

    zxAnEponTrapEventRemoteOnuConfigureFail        NOTIFICATION-TYPE
        OBJECTS {
                ifIndex,zxAnEponTrapEventString
                }
        STATUS  current
        DESCRIPTION
            ""
        ::={zxAnEponTrapEvent 10}

    zxAnEponTrapEventTransparent        NOTIFICATION-TYPE
        OBJECTS {
                ifIndex,zxAnEponTrapEventString,zxAnEponTrapOnuType,zxAnEponTrapOltPortName,zxAnEponTrapOnuDesc
                }
        STATUS  current
        DESCRIPTION
            ""
        ::={zxAnEponTrapEvent 11}

    zxAnEponTrapEventOnuDyingGasp        NOTIFICATION-TYPE
        OBJECTS {
                ifIndex,zxAnEponTrapOnuType,zxAnEponTrapOltPortName,zxAnEponTrapOnuDesc
                }
        STATUS  current
        DESCRIPTION
            ""
        ::={zxAnEponTrapEvent 12}

    zxAnEponTrapEventOnuAutoConfigRequest        NOTIFICATION-TYPE
        OBJECTS {
                ifIndex,zxAnEponTrapDid,zxAnEponTrapMac,zxAnEponTrapIp,
                zxAnEponTrapMask,zxAnEponTrapOnuType,zxAnEponTrapOnuDesc
                }
        STATUS  current
        DESCRIPTION
            ""
        ::={zxAnEponTrapEvent 13}

    zxAnEponTrapEventOnuIpNotAutoConfig        NOTIFICATION-TYPE
        OBJECTS {
                ifIndex,zxAnEponTrapEventString
                }
        STATUS  current
        DESCRIPTION
            ""
        ::={zxAnEponTrapEvent 14}

    zxAnEponTrapEventOnuPowerOff        NOTIFICATION-TYPE
        OBJECTS {
                ifIndex,zxAnEponTrapOltPortName,zxAnEponTrapOnuType, zxAnEponTrapOnuDesc,zxAnEponTrapDid
                }
        STATUS  current
        DESCRIPTION
            ""
        ::={zxAnEponTrapEvent 15}

    zxAnEponTrapEventOnuPowerOffRestore        NOTIFICATION-TYPE
        OBJECTS {
                ifIndex,zxAnEponTrapOltPortName,zxAnEponTrapOnuType, zxAnEponTrapOnuDesc,zxAnEponTrapDid
                }
        STATUS  current
        DESCRIPTION
            ""
        ::={zxAnEponTrapEvent 16}

    zxAnEponTrapEventOnuUnauthenticate        NOTIFICATION-TYPE
        OBJECTS {
                ifIndex,zxAnEponTrapDid,zxAnEponTrapMac,zxAnEponTrapOnuType, zxAnEponTrapTime
                }
        STATUS  current
        DESCRIPTION
            ""
        ::={zxAnEponTrapEvent 17}

    zxAnEponTrapEventOnuConstantOptical        NOTIFICATION-TYPE
        OBJECTS {
                ifIndex,zxAnEponTrapOltPortName,zxAnEponTrapOnuType,
                 zxAnEponTrapOnuDesc,zxAnEponRogueOnuIdList,zxAnEponHighProbabilityRogueOnuIdList,zxAnEponLowProbabilityRogueOnuIdList,
                 zxAnEponRogueUnauthOnuList,zxAnEponHighPossibilityRogueUnauthOnuList,zxAnEponLowPossibilityRogueUnauthOnuList
                }
        STATUS  current
        DESCRIPTION
            ""
        ::={zxAnEponTrapEvent 18}

    zxAnEponTrapEventOnuConstantOpticalRestore        NOTIFICATION-TYPE
        OBJECTS {
                ifIndex,zxAnEponTrapOltPortName,zxAnEponTrapOnuType,
                 zxAnEponTrapOnuDesc,zxAnEponRogueOnuIdList,zxAnEponHighProbabilityRogueOnuIdList,zxAnEponLowProbabilityRogueOnuIdList,
                 zxAnEponRogueUnauthOnuList,zxAnEponHighPossibilityRogueUnauthOnuList,zxAnEponLowPossibilityRogueUnauthOnuList
                }
        STATUS  current
        DESCRIPTION
            ""
        ::={zxAnEponTrapEvent 19}


    zxAnEponTrapEventPonResetFailed        NOTIFICATION-TYPE
        OBJECTS {
                ifIndex,zxAnEponTrapOltPortName
                }
        STATUS  current
        DESCRIPTION
            "it indicate OLT PON MAC reset failed"
        ::={zxAnEponTrapEvent 20}

    zxAnEponOnuSpeedTypeMismatchTrap     NOTIFICATION-TYPE
        OBJECTS {
                ifIndex,zxAnEponTrapMac,zxAnEponTrapOnuType,zxAnEponTrapTime,
                zxAnEponOnuActualSpeedType,zxAnEponOnuConfigSpeedType,zxAnEponTrapDid
                }
        STATUS  current
        DESCRIPTION
            "EPON ONU actual speed type and config speed type mismatch."
        ::={zxAnEponTrapEvent 21}


--zxAnEponOnuTrap begin

    zxAnEponOnuTrapInfo     OBJECT IDENTIFIER ::= { zxAnEponTrapOnu 1}
    zxAnEponOnuBaseTrap     OBJECT IDENTIFIER ::= { zxAnEponTrapOnu 2}
    zxAnEponOnuPonIfTrap    OBJECT IDENTIFIER ::= { zxAnEponTrapOnu 3}
    zxAnEponOnuCardTrap     OBJECT IDENTIFIER ::= { zxAnEponTrapOnu 4}
    zxAnEponOnuPortTrap     OBJECT IDENTIFIER ::= { zxAnEponTrapOnu 5}


    zxAnEponOnuOamObjType   OBJECT-TYPE
        SYNTAX      INTEGER
        MAX-ACCESS  read-only
        STATUS      current
        DESCRIPTION
                ""
        ::= { zxAnEponOnuTrapInfo  1}

    zxAnEponOnuOamInstanceNum  OBJECT-TYPE
        SYNTAX      INTEGER
        MAX-ACCESS  read-only
        STATUS      current
        DESCRIPTION
                ""
        ::= { zxAnEponOnuTrapInfo  2}

    zxAnEponOnuOamAlarmId  OBJECT-TYPE
        SYNTAX      INTEGER
        MAX-ACCESS  read-only
        STATUS      current
        DESCRIPTION
                ""
        ::= { zxAnEponOnuTrapInfo  3}

    zxAnEponOnuOamTimeStamp  OBJECT-TYPE
        SYNTAX      INTEGER
        MAX-ACCESS  read-only
        STATUS      current
        DESCRIPTION
                ""
        ::= { zxAnEponOnuTrapInfo  4}

    zxAnEponOnuOamAlarmState  OBJECT-TYPE
        SYNTAX      INTEGER
        MAX-ACCESS  read-only
        STATUS      current
        DESCRIPTION
                ""
        ::= { zxAnEponOnuTrapInfo  5}

    zxAnEponOnuOamAlarmInfo  OBJECT-TYPE
        SYNTAX      DisplayString (SIZE (0..128))
        MAX-ACCESS  read-only
        STATUS      current
        DESCRIPTION
                ""
        ::= { zxAnEponOnuTrapInfo  6}

    zxAnEponOnuActionResult     OBJECT-TYPE
        SYNTAX          INTEGER
            {
             success(1),
             fail(2)
            }
        MAX-ACCESS  read-only
        STATUS          current
        DESCRIPTION     "This MIB is defined for onu action(reset,recovery) result"
        ::=  {  zxAnEponOnuTrapInfo  7 }

     zxAnEponOnuLuminousEmissionStatus     OBJECT-TYPE
        SYNTAX          INTEGER
            {
             on(1),
             off(2)
            }
        MAX-ACCESS  read-only
        STATUS          current
        DESCRIPTION     "This MIB is defined for onu action(reset,recovery) result"
        ::=  {  zxAnEponOnuTrapInfo  8 }

    zxAnEponOnuDataChannelLinkStatus     OBJECT-TYPE
        SYNTAX          INTEGER
            {
             on(1),
             off(2)
            }
        MAX-ACCESS  read-only
        STATUS          current
        DESCRIPTION     "This MIB is defined for onu action(reset,recovery) result"
        ::=  {  zxAnEponOnuTrapInfo  9 }

     zxAnEponOnuFirmwareVersionUpdateStatus     OBJECT-TYPE
        SYNTAX          INTEGER
            {
             notstart(1),
             updatefailed(2),
             downloading(3),
             writingimage(4),
             updatefinished(5)
            }
        MAX-ACCESS  read-only
        STATUS          current
        DESCRIPTION     "This MIB is defined for onu action(reset,recovery) result"
        ::=  {  zxAnEponOnuTrapInfo  10 }

      zxAnEponOnuFirmwareVersionUpdateFailedReason     OBJECT-TYPE
        SYNTAX          INTEGER
            {
              none(1),
              downloaderror(2),
              downloadtimeout(3),
              onureturnerror(4),
              userabort(5),
              onuoffline(6)
            }
        MAX-ACCESS  read-only
        STATUS          current
        DESCRIPTION     "This MIB is defined for onu action(reset,recovery) result"
        ::=  {  zxAnEponOnuTrapInfo  11 }

    zxAnEponOnuOamV21Message        NOTIFICATION-TYPE
        OBJECTS {
                ifIndex, zxAnEponOnuOamObjType, zxAnEponOnuOamInstanceNum,zxAnEponOnuOamAlarmId,zxAnEponOnuOamTimeStamp,zxAnEponOnuOamAlarmState,zxAnEponOnuOamAlarmInfo
                }
        STATUS  current
        DESCRIPTION
            "CTC ONU OAM Message v2.1"
        ::={zxAnEponOnuTrapInfo 101}


    zxAnEponOnuEquipmentAlm        NOTIFICATION-TYPE
        OBJECTS {
                ifIndex, zxAnEponOnuOamTimeStamp, zxAnEponOnuOamAlarmInfo
                }
        STATUS  current
        DESCRIPTION
            "A functional failure on an internal interface"
        ::={zxAnEponOnuBaseTrap 1}

    zxAnEponOnuEquipmentRestore        NOTIFICATION-TYPE
        OBJECTS {
                ifIndex,zxAnEponOnuOamTimeStamp, zxAnEponOnuOamAlarmInfo
                }
        STATUS  current
        DESCRIPTION
            ""
        ::={zxAnEponOnuBaseTrap 2}

    zxAnEponOnuPowerAlm        NOTIFICATION-TYPE
        OBJECTS {
                ifIndex,zxAnEponOnuOamTimeStamp, zxAnEponOnuOamAlarmInfo
                }
        STATUS  current
        DESCRIPTION
            "ONU Power Alarm"
        ::={zxAnEponOnuBaseTrap 3}

    zxAnEponOnuPowerRestore        NOTIFICATION-TYPE
        OBJECTS {
                ifIndex,zxAnEponOnuOamTimeStamp, zxAnEponOnuOamAlarmInfo
                }
        STATUS  current
        DESCRIPTION
            ""
        ::={zxAnEponOnuBaseTrap 4}

    zxAnEponOnuButteryMissingAlm        NOTIFICATION-TYPE
        OBJECTS {
                ifIndex,zxAnEponOnuOamTimeStamp
                }
        STATUS  current
        DESCRIPTION
            "ONU Battery is provisioned but missing"
        ::={zxAnEponOnuBaseTrap 5}

    zxAnEponOnuButteryMissingRestore        NOTIFICATION-TYPE
        OBJECTS {
                ifIndex,zxAnEponOnuOamTimeStamp
                }
        STATUS  current
        DESCRIPTION
            ""
        ::={zxAnEponOnuBaseTrap 6}

    zxAnEponOnuButteryFailureAlm        NOTIFICATION-TYPE
        OBJECTS {
                ifIndex,zxAnEponOnuOamTimeStamp
                }
        STATUS  current
        DESCRIPTION
            "ONU Battery is provisioned and present but cannot recharge"
        ::={zxAnEponOnuBaseTrap 7}

    zxAnEponOnuButteryFailureRestore        NOTIFICATION-TYPE
        OBJECTS {
                ifIndex,zxAnEponOnuOamTimeStamp
                }
        STATUS  current
        DESCRIPTION
            ""
        ::={zxAnEponOnuBaseTrap 8}

    zxAnEponOnuButteryVoltLowAlm        NOTIFICATION-TYPE
        OBJECTS {
                ifIndex,zxAnEponOnuOamTimeStamp,zxAnEponOnuOamAlarmInfo
                }
        STATUS  current
        DESCRIPTION
            "ONU Battery is provisioned and present but its voltage is too low"
        ::={zxAnEponOnuBaseTrap 9}

    zxAnEponOnuButteryVoltLowRestore        NOTIFICATION-TYPE
        OBJECTS {
                ifIndex,zxAnEponOnuOamTimeStamp,zxAnEponOnuOamAlarmInfo
                }
        STATUS  current
        DESCRIPTION
            ""
        ::={zxAnEponOnuBaseTrap 10}

    zxAnEponOnuPhysicalIntrusionAlm        NOTIFICATION-TYPE
        OBJECTS {
                ifIndex,zxAnEponOnuOamTimeStamp
                }
        STATUS  current
        DESCRIPTION
            "Applies if the ONU is supported with detection such as door or box open"
        ::={zxAnEponOnuBaseTrap 11}

    zxAnEponOnuPhysicalIntrusionRestore        NOTIFICATION-TYPE
        OBJECTS {
                ifIndex,zxAnEponOnuOamTimeStamp
                }
        STATUS  current
        DESCRIPTION
            ""
        ::={zxAnEponOnuBaseTrap 12}

    zxAnEponOnuSelfTestFailureAlm        NOTIFICATION-TYPE
        OBJECTS {
                ifIndex,zxAnEponOnuOamTimeStamp, zxAnEponOnuOamAlarmInfo
                }
        STATUS  current
        DESCRIPTION
            "ONU Self-Test Failure"
        ::={zxAnEponOnuBaseTrap 13}

    zxAnEponOnuSelfTestFailureRestore        NOTIFICATION-TYPE
        OBJECTS {
                ifIndex,zxAnEponOnuOamTimeStamp,zxAnEponOnuOamAlarmInfo
                }
        STATUS  current
        DESCRIPTION
            ""
        ::={zxAnEponOnuBaseTrap 14}

    zxAnEponOnuTempHighAlm        NOTIFICATION-TYPE
        OBJECTS {
                ifIndex,zxAnEponOnuOamTimeStamp, zxAnEponOnuOamAlarmInfo
                }
        STATUS  current
        DESCRIPTION
            "ONU Temperature  over Threshold"
        ::={zxAnEponOnuBaseTrap 15}

    zxAnEponOnuTempHighAlmRestore        NOTIFICATION-TYPE
        OBJECTS {
                ifIndex,zxAnEponOnuOamTimeStamp, zxAnEponOnuOamAlarmInfo
                }
        STATUS  current
        DESCRIPTION
            ""
        ::={zxAnEponOnuBaseTrap 16}

    zxAnEponOnuTempLowAlm        NOTIFICATION-TYPE
        OBJECTS {
                ifIndex,zxAnEponOnuOamTimeStamp, zxAnEponOnuOamAlarmInfo
                }
        STATUS  current
        DESCRIPTION
            "ONU Temperature  over Threshold"
        ::={zxAnEponOnuBaseTrap 17}

    zxAnEponOnuTempLowAlmRestore        NOTIFICATION-TYPE
        OBJECTS {
                ifIndex,zxAnEponOnuOamTimeStamp, zxAnEponOnuOamAlarmInfo
                }
        STATUS  current
        DESCRIPTION
            ""
        ::={zxAnEponOnuBaseTrap 18}

    zxAnEponOnuIADConnectionFailureAlm        NOTIFICATION-TYPE
        OBJECTS {
                ifIndex,zxAnEponOnuOamTimeStamp, zxAnEponOnuOamAlarmInfo
                }
        STATUS  current
        DESCRIPTION
            "Failure of Connection between inner IAD and SS platform, such as Lose of SS, no keep alive packets, etc"
        ::={zxAnEponOnuBaseTrap 19}

    zxAnEponOnuIADConnectionFailureRestore        NOTIFICATION-TYPE
        OBJECTS {
                ifIndex,zxAnEponOnuOamTimeStamp, zxAnEponOnuOamAlarmInfo
                }
        STATUS  current
        DESCRIPTION
            ""
        ::={zxAnEponOnuBaseTrap 20}

    zxAnEponOnuPonSwitchAlm        NOTIFICATION-TYPE
        OBJECTS {
                ifIndex,zxAnEponOnuOamTimeStamp, zxAnEponOnuOamAlarmInfo
                }
        STATUS  current
        DESCRIPTION
            "ONU failure of the working fiber pathway
            "
        ::={zxAnEponOnuBaseTrap 21}

    zxAnEponOnuPonSwitchRestore        NOTIFICATION-TYPE
        OBJECTS {
                ifIndex,zxAnEponOnuOamTimeStamp, zxAnEponOnuOamAlarmInfo
                }
        STATUS  current
        DESCRIPTION
            ""
        ::={zxAnEponOnuBaseTrap 22}

    zxAnEponOnuResetNotification        NOTIFICATION-TYPE
        OBJECTS {
                ifIndex,zxAnEponOnuActionResult
                }
        STATUS  current
        DESCRIPTION
            "ONU Reset
            "
        ::={zxAnEponOnuBaseTrap 23}

    zxAnEponOnuRecoveryNotification        NOTIFICATION-TYPE
        OBJECTS {
                ifIndex,zxAnEponOnuActionResult
                }
        STATUS  current
        DESCRIPTION
            "ONU Recovery
            "
        ::={zxAnEponOnuBaseTrap 24}

     zxAnEponOnuDataChannelTurnOffNotification        NOTIFICATION-TYPE
        OBJECTS {
                ifIndex,zxAnEponOnuActionResult,zxAnEponOnuDataChannelLinkStatus
                }
        STATUS  current
        DESCRIPTION
            "ONU Data Channel Turn Off
            "
        ::={zxAnEponOnuBaseTrap 25}

          zxAnEponOnuLuminousEmissionOffNotification        NOTIFICATION-TYPE
        OBJECTS {
                ifIndex,zxAnEponOnuActionResult,zxAnEponOnuLuminousEmissionStatus
                }
        STATUS  current
        DESCRIPTION
            "ONU Recovery
            "
        ::={zxAnEponOnuBaseTrap 26}

      zxAnEponOnuFirmwareVersionUpdateNotification        NOTIFICATION-TYPE
        OBJECTS {
                ifIndex,zxAnEponOnuVersionUpdateStatus
                }
        STATUS  current
        DESCRIPTION
            "ONU Recovery
            "
        ::={zxAnEponOnuBaseTrap 27}

      zxAnEponOnuFirmwareVersionUpdateFailedNotification     NOTIFICATION-TYPE
        OBJECTS {
                ifIndex,zxAnEponOnuVersionUpdateFailedReason
                }
        STATUS  current
        DESCRIPTION
            "ONU Recovery
            "
        ::={zxAnEponOnuBaseTrap 28}

      zxAnEponOnuPowerSwitchAlm        NOTIFICATION-TYPE
        OBJECTS {
                ifIndex,zxAnEponOnuOamAlarmInfo,zxAnEponOnuOamTimeStamp
                }
        STATUS  current
        DESCRIPTION
            "A zxAnEponOnuPowerSwitchAlm trap is sent when the ONU power
            has been switched to standby power."
        ::={zxAnEponOnuBaseTrap 29}

    zxAnEponOnuPowerSwitchRestore        NOTIFICATION-TYPE
        OBJECTS {
                ifIndex,zxAnEponOnuOamAlarmInfo,zxAnEponOnuOamTimeStamp
                }
        STATUS  current
        DESCRIPTION
            "A zxAnEponOnuPowerSwitchRestore trap is sent when the ONU power
            has been switched to AC mains power."
        ::={zxAnEponOnuBaseTrap 30}



 --Pon if alarm
    zxAnEponOnuPonRxPowerHighAlm        NOTIFICATION-TYPE
        OBJECTS {
                ifIndex,zxAnEponOnuOamInstanceNum, zxAnEponOnuOamTimeStamp, zxAnEponOnuOamAlarmInfo
                }
        STATUS  current
        DESCRIPTION
            "ONU RX Optical Power over Threshold"
        ::={zxAnEponOnuPonIfTrap 1}

    zxAnEponOnuPonRxPowerHighAlmRestore        NOTIFICATION-TYPE
        OBJECTS {
                ifIndex, zxAnEponOnuOamInstanceNum,zxAnEponOnuOamTimeStamp,zxAnEponOnuOamAlarmInfo
                }
        STATUS  current
        DESCRIPTION
            ""
        ::={zxAnEponOnuPonIfTrap 2}

    zxAnEponOnuPonRxPowerLowAlm        NOTIFICATION-TYPE
        OBJECTS {
                ifIndex,zxAnEponOnuOamInstanceNum, zxAnEponOnuOamTimeStamp, zxAnEponOnuOamAlarmInfo
                }
        STATUS  current
        DESCRIPTION
            "ONU RX Optical Power Lower Than Threshold"
        ::={zxAnEponOnuPonIfTrap 3}

    zxAnEponOnuPonRxPowerLowAlmRestore        NOTIFICATION-TYPE
        OBJECTS {
                ifIndex, zxAnEponOnuOamInstanceNum,zxAnEponOnuOamTimeStamp,zxAnEponOnuOamAlarmInfo
                }
        STATUS  current
        DESCRIPTION
            ""
        ::={zxAnEponOnuPonIfTrap 4}

    zxAnEponOnuPonTxPowerHighAlm        NOTIFICATION-TYPE
        OBJECTS {
                ifIndex,zxAnEponOnuOamInstanceNum, zxAnEponOnuOamTimeStamp, zxAnEponOnuOamAlarmInfo
                }
        STATUS  current
        DESCRIPTION
            "ONU TX Optical Power over Threshold"
        ::={zxAnEponOnuPonIfTrap 5}

    zxAnEponOnuPonTxPowerHighAlmRestore        NOTIFICATION-TYPE
        OBJECTS {
                ifIndex, zxAnEponOnuOamInstanceNum,zxAnEponOnuOamTimeStamp,zxAnEponOnuOamAlarmInfo
                }
        STATUS  current
        DESCRIPTION
            ""
        ::={zxAnEponOnuPonIfTrap 6}

    zxAnEponOnuPonTxPowerLowAlm        NOTIFICATION-TYPE
        OBJECTS {
                ifIndex,zxAnEponOnuOamInstanceNum, zxAnEponOnuOamTimeStamp, zxAnEponOnuOamAlarmInfo
                }
        STATUS  current
        DESCRIPTION
            "ONU RX Optical Power Lower Than Threshold"
        ::={zxAnEponOnuPonIfTrap 7}

    zxAnEponOnuPonTxPowerLowAlmRestore        NOTIFICATION-TYPE
        OBJECTS {
                ifIndex, zxAnEponOnuOamInstanceNum,zxAnEponOnuOamTimeStamp,zxAnEponOnuOamAlarmInfo
                }
        STATUS  current
        DESCRIPTION
            ""
        ::={zxAnEponOnuPonIfTrap 8}

    zxAnEponOnuPonTxBiasHighAlm        NOTIFICATION-TYPE
        OBJECTS {
                ifIndex,zxAnEponOnuOamInstanceNum, zxAnEponOnuOamTimeStamp, zxAnEponOnuOamAlarmInfo
                }
        STATUS  current
        DESCRIPTION
            "ONU Bias Current over Threshold"
        ::={zxAnEponOnuPonIfTrap 9}

    zxAnEponOnuPonTxBiasHighAlmRestore        NOTIFICATION-TYPE
        OBJECTS {
                ifIndex, zxAnEponOnuOamInstanceNum, zxAnEponOnuOamTimeStamp,zxAnEponOnuOamAlarmInfo
                }
        STATUS  current
        DESCRIPTION
            ""
        ::={zxAnEponOnuPonIfTrap 10}

    zxAnEponOnuPonTxBiasLowAlm        NOTIFICATION-TYPE
        OBJECTS {
                ifIndex,zxAnEponOnuOamInstanceNum, zxAnEponOnuOamTimeStamp, zxAnEponOnuOamAlarmInfo
                }
        STATUS  current
        DESCRIPTION
            "ONU Bias Current Lower Than Threshold"
        ::={zxAnEponOnuPonIfTrap 11}

    zxAnEponOnuPonTxBiasLowAlmRestore        NOTIFICATION-TYPE
        OBJECTS {
                ifIndex, zxAnEponOnuOamInstanceNum, zxAnEponOnuOamTimeStamp,zxAnEponOnuOamAlarmInfo
                }
        STATUS  current
        DESCRIPTION
            ""
        ::={zxAnEponOnuPonIfTrap 12}

    zxAnEponPonOnuVccHighAlm        NOTIFICATION-TYPE
        OBJECTS {
                ifIndex,zxAnEponOnuOamInstanceNum,zxAnEponOnuOamTimeStamp, zxAnEponOnuOamAlarmInfo
                }
        STATUS  current
        DESCRIPTION
            "ONU Supply Voltage over Threshold"
        ::={zxAnEponOnuPonIfTrap 13}

    zxAnEponPonOnuVccHighAlmRestore        NOTIFICATION-TYPE
        OBJECTS {
                ifIndex, zxAnEponOnuOamInstanceNum, zxAnEponOnuOamTimeStamp,zxAnEponOnuOamAlarmInfo
                }
        STATUS  current
        DESCRIPTION
            ""
        ::={zxAnEponOnuPonIfTrap 14}

    zxAnEponPonOnuVccLowAlm        NOTIFICATION-TYPE
        OBJECTS {
                ifIndex,zxAnEponOnuOamInstanceNum,zxAnEponOnuOamTimeStamp, zxAnEponOnuOamAlarmInfo
                }
        STATUS  current
        DESCRIPTION
            "ONU Supply Voltage Lower Than Threshold"
        ::={zxAnEponOnuPonIfTrap 15}

    zxAnEponPonOnuVccLowAlmRestore        NOTIFICATION-TYPE
        OBJECTS {
                ifIndex, zxAnEponOnuOamInstanceNum, zxAnEponOnuOamTimeStamp,zxAnEponOnuOamAlarmInfo
                }
        STATUS  current
        DESCRIPTION
            ""
        ::={zxAnEponOnuPonIfTrap 16}

    zxAnEponOnuPonTempHighAlm        NOTIFICATION-TYPE
        OBJECTS {
                ifIndex,zxAnEponOnuOamInstanceNum,zxAnEponOnuOamTimeStamp, zxAnEponOnuOamAlarmInfo
                }
        STATUS  current
        DESCRIPTION
            ""
        ::={zxAnEponOnuPonIfTrap 17}

    zxAnEponOnuPonTempHighAlmRestore        NOTIFICATION-TYPE
        OBJECTS {
                ifIndex, zxAnEponOnuOamInstanceNum, zxAnEponOnuOamTimeStamp,zxAnEponOnuOamAlarmInfo
                }
        STATUS  current
        DESCRIPTION
            ""
        ::={zxAnEponOnuPonIfTrap 18}

    zxAnEponOnuPonTempLowAlm        NOTIFICATION-TYPE
        OBJECTS {
                ifIndex,zxAnEponOnuOamInstanceNum,zxAnEponOnuOamTimeStamp, zxAnEponOnuOamAlarmInfo
                }
        STATUS  current
        DESCRIPTION
            ""
        ::={zxAnEponOnuPonIfTrap 19}

    zxAnEponOnuPonTempLowAlmRestore        NOTIFICATION-TYPE
        OBJECTS {
                ifIndex, zxAnEponOnuOamInstanceNum, zxAnEponOnuOamTimeStamp,zxAnEponOnuOamAlarmInfo
                }
        STATUS  current
        DESCRIPTION
            ""
        ::={zxAnEponOnuPonIfTrap 20}

--end pon if alarm
--Card alarm
    zxAnEponOnuCardAlm        NOTIFICATION-TYPE
        OBJECTS {
                ifIndex, zxAnEponOnuOamInstanceNum,zxAnEponOnuOamTimeStamp, zxAnEponOnuOamAlarmInfo
                }
        STATUS  current
        DESCRIPTION
            "A functional failure on an user interface card"
        ::={zxAnEponOnuCardTrap 1}

    zxAnEponOnuCardRestore        NOTIFICATION-TYPE
        OBJECTS {
                ifIndex, zxAnEponOnuOamInstanceNum,zxAnEponOnuOamTimeStamp, zxAnEponOnuOamAlarmInfo
                }
        STATUS  current
        DESCRIPTION
            ""
        ::={zxAnEponOnuCardTrap 2}

    zxAnEponOnuCardTestFailureAlm        NOTIFICATION-TYPE
        OBJECTS {
                ifIndex, zxAnEponOnuOamInstanceNum,zxAnEponOnuOamTimeStamp, zxAnEponOnuOamAlarmInfo
                }
        STATUS  current
        DESCRIPTION
            "ONU card self-test failure"
        ::={zxAnEponOnuCardTrap 3}

    zxAnEponOnuCardTestFailureRestore        NOTIFICATION-TYPE
        OBJECTS {
                ifIndex, zxAnEponOnuOamInstanceNum,zxAnEponOnuOamTimeStamp, zxAnEponOnuOamAlarmInfo
                }
        STATUS  current
        DESCRIPTION
            ""
        ::={zxAnEponOnuCardTrap 4}

--end card alarm
--Port alarm
    zxAnEponOnuEthAutoNegFailureAlm        NOTIFICATION-TYPE
        OBJECTS {
                ifIndex, zxAnEponOnuOamInstanceNum,zxAnEponOnuOamTimeStamp
                }
        STATUS  current
        DESCRIPTION
            "ONU Ethernet Port Auto-negotiation Failure"
        ::={zxAnEponOnuPortTrap 1}

    zxAnEponOnuEthAutoNegFailureRestore        NOTIFICATION-TYPE
        OBJECTS {
                ifIndex,zxAnEponOnuOamInstanceNum,zxAnEponOnuOamTimeStamp
                }
        STATUS  current
        DESCRIPTION
            ""
        ::={zxAnEponOnuPortTrap 2}

    zxAnEponOnuEthLOSAlm        NOTIFICATION-TYPE
        OBJECTS {
                ifIndex, zxAnEponOnuOamInstanceNum,zxAnEponOnuOamTimeStamp
                }
        STATUS  current
        DESCRIPTION
            "ONU Ethernet Port LOS(Loss of Signal)"
        ::={zxAnEponOnuPortTrap 3}

    zxAnEponOnuEthLOSRestore        NOTIFICATION-TYPE
        OBJECTS {
                ifIndex,zxAnEponOnuOamInstanceNum,zxAnEponOnuOamTimeStamp
                }
        STATUS  current
        DESCRIPTION
            ""
        ::={zxAnEponOnuPortTrap 4}

    zxAnEponOnuEthFailureAlm        NOTIFICATION-TYPE
        OBJECTS {
                ifIndex, zxAnEponOnuOamInstanceNum,zxAnEponOnuOamTimeStamp
                }
        STATUS  current
        DESCRIPTION
            "ONU Ethernet port failure"
        ::={zxAnEponOnuPortTrap 5}

    zxAnEponOnuEthFailureRestore        NOTIFICATION-TYPE
        OBJECTS {
                ifIndex,zxAnEponOnuOamInstanceNum,zxAnEponOnuOamTimeStamp
                }
        STATUS  current
        DESCRIPTION
            ""
        ::={zxAnEponOnuPortTrap 6}

    zxAnEponOnuEthLoopbackAlm        NOTIFICATION-TYPE
        OBJECTS {
                ifIndex, zxAnEponOnuOamInstanceNum,zxAnEponOnuOamTimeStamp
                ,zxAnEponOnuOamAlarmInfo
                }
        STATUS  current
        DESCRIPTION
            "This trap will be sent to managemet system when ONU Ethernet
             port loopback was happened .
             The format  of zxAnEponOnuOamAlarmInfo  as following:
                '1' means inner loopback
                '2' means outer loopback .
             "
        ::={zxAnEponOnuPortTrap 7}

    zxAnEponOnuEthLoopbackRestore        NOTIFICATION-TYPE
        OBJECTS {
                ifIndex,zxAnEponOnuOamInstanceNum,zxAnEponOnuOamTimeStamp
                ,zxAnEponOnuOamAlarmInfo
                }
        STATUS  current
        DESCRIPTION
            "The trap of zxAnEponOnuEthLoopbackAlm restore."
        ::={zxAnEponOnuPortTrap 8}

    zxAnEponOnuEthCongestionAlm        NOTIFICATION-TYPE
        OBJECTS {
                ifIndex, zxAnEponOnuOamInstanceNum,zxAnEponOnuOamTimeStamp
                }
        STATUS  current
        DESCRIPTION
            "ONU Ethernet Port Congestion"
        ::={zxAnEponOnuPortTrap 9}

    zxAnEponOnuEthCongestionRestore        NOTIFICATION-TYPE
        OBJECTS {
                ifIndex,zxAnEponOnuOamInstanceNum,zxAnEponOnuOamTimeStamp
                }
        STATUS  current
        DESCRIPTION
            ""
        ::={zxAnEponOnuPortTrap 10}

    zxAnEponOnuPOTSFailureAlm        NOTIFICATION-TYPE
        OBJECTS {
                ifIndex, zxAnEponOnuOamInstanceNum,zxAnEponOnuOamTimeStamp,zxAnEponOnuOamAlarmInfo
                }
        STATUS  current
        DESCRIPTION
            "ONU POTS Port Failure"
        ::={zxAnEponOnuPortTrap 11}

    zxAnEponOnuPOTSFailureRestore        NOTIFICATION-TYPE
        OBJECTS {
                ifIndex,zxAnEponOnuOamInstanceNum,zxAnEponOnuOamTimeStamp, zxAnEponOnuOamAlarmInfo
                }
        STATUS  current
        DESCRIPTION
            ""
        ::={zxAnEponOnuPortTrap 12}

    zxAnEponOnuE1FailureAlm        NOTIFICATION-TYPE
        OBJECTS {
                ifIndex, zxAnEponOnuOamInstanceNum,zxAnEponOnuOamTimeStamp,zxAnEponOnuOamAlarmInfo
                }
        STATUS  current
        DESCRIPTION
            "ONU E1 Port Failure"
        ::={zxAnEponOnuPortTrap 13}

    zxAnEponOnuE1FailureRestore        NOTIFICATION-TYPE
        OBJECTS {
                ifIndex,zxAnEponOnuOamInstanceNum,zxAnEponOnuOamTimeStamp, zxAnEponOnuOamAlarmInfo
                }
        STATUS  current
        DESCRIPTION
            ""
        ::={zxAnEponOnuPortTrap 14}

    zxAnEponOnuE1TimingLockAlm        NOTIFICATION-TYPE
        OBJECTS {
                ifIndex, zxAnEponOnuOamInstanceNum,zxAnEponOnuOamTimeStamp
                }
        STATUS  current
        DESCRIPTION
            "ONU E1 Timing Unlock"
        ::={zxAnEponOnuPortTrap 15}

    zxAnEponOnuE1TimingLockRestore        NOTIFICATION-TYPE
        OBJECTS {
                ifIndex,zxAnEponOnuOamInstanceNum,zxAnEponOnuOamTimeStamp
                }
        STATUS  current
        DESCRIPTION
            ""
        ::={zxAnEponOnuPortTrap 16}

    zxAnEponOnuE1LosAlm        NOTIFICATION-TYPE
        OBJECTS {
                ifIndex, zxAnEponOnuOamInstanceNum,zxAnEponOnuOamTimeStamp
                }
        STATUS  current
        DESCRIPTION
            "ONU E1 Port LOS(Loss of Signal)"
        ::={zxAnEponOnuPortTrap 17}

    zxAnEponOnuE1LosRestore        NOTIFICATION-TYPE
        OBJECTS {
                ifIndex,zxAnEponOnuOamInstanceNum,zxAnEponOnuOamTimeStamp
                }
        STATUS  current
        DESCRIPTION
            ""
        ::={zxAnEponOnuPortTrap 18}



--end port alarm

--zxAnEponOnuTrap end

END
