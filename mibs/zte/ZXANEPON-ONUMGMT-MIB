-- *****************************************************************
-- ZTE EPONC200 REMOTE MANAGEMENT ONU PORT MIB
--
-- 20-7-2005
--
-- Copyright(c) 2005 ZTE Corporation
-- All rights reserved.
-- *****************************************************************
--

ZXANEPON-ONUMGMT-MIB DEFINITIONS ::= BEGIN
    IMPORTS
        DisplayString                    FROM RFC1213-MIB
        RowStatus                        FROM SNMPv2-TC
        TruthValue                       FROM SNMPv2-TC
        Unsigned32                       FROM SNMPv2-SMI
        Integer32                        FROM SNMPv2-SMI
        MacAddress                       FROM SNMPv2-TC
        IpAddress                        FROM SNMPv2-SMI
        MODULE-IDENTITY                  FROM SNMPv2-SMI
        OBJECT-TYPE                      FROM SNMPv2-SMI
        Counter64                        FROM SNMPv2-SMI
        zxAnEponMib                      FROM ZTE-MASTER-MIB;

    zxAnEponOnuRemoteMgmt MODULE-IDENTITY
        LAST-UPDATED "200702280000Z"  -- Feb 28, 2007"
        ORGANIZATION "ZTE Corp."
        CONTACT-INFO
            "ZTE GPON Working Group:
            http://www.zte.com.cn
            e-mail:
            hu.dan@zte.com.cn
            "
        DESCRIPTION
            "the remote management and control of ONU"
        ::= { zxAnEponMib 1 }

        zxAnEponOnuExtendedAttrMgmt                OBJECT IDENTIFIER ::= { zxAnEponOnuRemoteMgmt 1}
        zxAnEponOnuExtendedActionMgmt              OBJECT IDENTIFIER ::= { zxAnEponOnuRemoteMgmt 2}
        zxAnEponOnuStdAttrMgmt                     OBJECT IDENTIFIER ::= { zxAnEponOnuRemoteMgmt 3}
        zxAnEponOnuStdActionMgmt                   OBJECT IDENTIFIER ::= { zxAnEponOnuRemoteMgmt 4}
        zxAnEponOnuDbaAttrMgmt                     OBJECT IDENTIFIER ::= { zxAnEponOnuRemoteMgmt 5}
        zxAnEponOnuProfileMgmt                     OBJECT IDENTIFIER ::= { zxAnEponOnuRemoteMgmt 6}
        zxAnEponOnuPfmncStatis                     OBJECT IDENTIFIER ::= { zxAnEponOnuRemoteMgmt 7}
        zxAnPtpExtOamMgmt                           OBJECT IDENTIFIER ::= { zxAnEponOnuRemoteMgmt 8}

        zxAnEponOnuCustomMgmt                      OBJECT IDENTIFIER ::= { zxAnEponOnuRemoteMgmt 101}


--------------------------------------------------------------------------------
-- Following objects are defined.
-- 1.35 EPON ONU VOIP remote profile management(OAM)
-- 1.35.1 Voip Ip profile table index next
-- 1.35.2 Voip Ip profile table
-- 1.35.3 Voip VLAN profile table index next
-- 1.35.4 Voip VLAN profile table
-- 1.35.5 Voip H.248 protocol profile table index next
-- 1.35.6 Voip H.248 protocol profile table
-- 1.35.7 Voip MGCP protocol profile table index next
-- 1.35.8 Voip MGCP protocol profile table
-- 1.35.9 Voip SIP protocol profile table index next
-- 1.35.10 Voip SIP protocol profile table
-- 1.35.11 Voip Fax protocol profile table index next
-- 1.35.12 Voip Fax protocol profile table

-- 1.36 EPON ONU VOIP remote management(OAM)
-- 1.36.1 Voip ip parameter management table
-- 1.36.2 Voip PPPoE parameter management table
-- 1.36.3 Voip meida gateway domain name table
-- 1.36.4 Voip H.248/MGCP user TID config table
-- 1.36.5 Voip H.248/MGCP rtp TID config table
-- 1.36.6 Voip SIP user info table
-- 1.36.7 Voip card basic info table
-- 1.36.8 Voip H248/MGCP user tid info table
-- 1.36.9 Voip H248/MGCP rtp tid info table
-- 1.36.10 Voip module status table
-- 1.36.11 Voip user interface status table
-- 1.36.12 Voip profile apply table
-- 1.36.13 Voip SIP attribute table
-- 1.36.14 Voip SIP attribute table
-- 1.36.15 Voip present call number table
-- 1.36.16 Voip timer config table
-- 1.36.17 Voip Statistics Table
-- 1.36.18 Voip Other Config Table

-- 1.37 Onu capability extended table
-- 1.38 Onu interface table
-- 1.39 MDU/MTU card operation table
-- 1.40 EPON MDU SNMP parameter management(OAM)
-- 1.40.1 MDU SNMP parameter table
-- 1.40.2 MDU SNMP trap server table
-- 1.41 ONU multicast VLAN switch table
-- 1.42 ONU port loop detect table
-- 1.43 ONU LLID queue table
-- 1.44 ONU PON attribute table
-- 1.45 EPON ONU SLA management(OAM)
-- 1.45.1 zxAnEponOnuSlaProfileIdxNext
-- 1.45.2 zxAnEponOnuSlaProfileTable
-- 1.45.3 ONU service queue table
-- 1.45.4 ONU SLA profile apply table
-- 1.46 ONU optical protection holdover table
-- 1.48 EPON ONU alarm management(OAM)
-- 1.48.1 ONU alarm control table
-- 1.48.2 ONU PON alarm control table
-- 1.48.3 ONU UNI alarm control table
-- 1.49 EPON ONU version management(OAM)
-- 1.49.1 ONU version table
-- 1.49.2 ONU version update table
-- 1.49.3 ONU version update status table
-- 1.49.4 ONU version action table
-- 1.53 EPON ONU WAN management(OAM)
-- 1.53.2 zxAnEponRmWanPrfTable
-- 1.53.3 zxAnEponRmOnuWanConfTable
--------------------------------------------------------------------------------

------------------------------------------------------------------------------
--  1.zxAnEponOnuExtendedAttrMgmt
------------------------------------------------------------------------------

    zxAnEponOnuSnTable OBJECT-TYPE
        SYNTAX       SEQUENCE OF ZxAnEponOnuSnEntry
        MAX-ACCESS   not-accessible
        STATUS       current
        DESCRIPTION
          "ONU SN table."
          ::= { zxAnEponOnuExtendedAttrMgmt 1 }

    zxAnEponOnuSnEntry OBJECT-TYPE
        SYNTAX      ZxAnEponOnuSnEntry
        MAX-ACCESS  not-accessible
        STATUS      current
        DESCRIPTION " "
        INDEX   { zxAnEponOnuIfIndex }
        ::= { zxAnEponOnuSnTable 1 }

    ZxAnEponOnuSnEntry ::=
        SEQUENCE {
                zxAnEponOnuIfIndex                 INTEGER,
                zxAnEponOnuVendorId                OCTET STRING,
                zxAnEponOnuModel                   OCTET STRING,
                zxAnEponOnuMacAddr                 MacAddress,
                zxAnEponOnuHardwareVersion         OCTET STRING,
                zxAnEponOnuSoftwareVersion         OCTET STRING,
                zxAnEponOnuExtendedModel           OCTET STRING
                }

    zxAnEponOnuIfIndex OBJECT-TYPE
        SYNTAX      INTEGER
        MAX-ACCESS  not-accessible
        STATUS      current
        DESCRIPTION
            "The 4 bytes index includes:
            interface type(bit31~28);shelfId(bit27~24);slotId(bit23~19);oltId(bit18~16);onu(bit15~bit8);reserved(bit7~bit0)"
        ::= { zxAnEponOnuSnEntry 1}

    zxAnEponOnuVendorId OBJECT-TYPE
        SYNTAX      OCTET STRING(SIZE(4))
        MAX-ACCESS  read-only
        STATUS      current
        DESCRIPTION
                "The code set for the Vendor_ID is specified in
                ANSI T1.220. The 4 characters are mapped in the
                4-byte field by taking each ASCII/ANSI character
                code and concatenating them."
        ::= { zxAnEponOnuSnEntry 2}

    zxAnEponOnuModel OBJECT-TYPE
        SYNTAX      OCTET STRING(SIZE(4))
        MAX-ACCESS  read-only
        STATUS      current
        DESCRIPTION
                "Vendor specific ONU model."
        ::= { zxAnEponOnuSnEntry 3}

    zxAnEponOnuMacAddr OBJECT-TYPE
        SYNTAX      MacAddress
        MAX-ACCESS  read-only
        STATUS      current
        DESCRIPTION
                "The ONU MAC address."
        ::= { zxAnEponOnuSnEntry 4}

    zxAnEponOnuHardwareVersion OBJECT-TYPE
        SYNTAX      OCTET STRING(SIZE(8))
        MAX-ACCESS  read-only
        STATUS      current
        DESCRIPTION
                "The ONU hardware version."
        ::= { zxAnEponOnuSnEntry 5}

    zxAnEponOnuSoftwareVersion OBJECT-TYPE
        SYNTAX      OCTET STRING(SIZE(16))
        MAX-ACCESS  read-only
        STATUS      current
        DESCRIPTION
                "The ONU software version."
        ::= { zxAnEponOnuSnEntry 6}
    zxAnEponOnuExtendedModel  OBJECT-TYPE
        SYNTAX      OCTET STRING(SIZE(16))
        MAX-ACCESS  read-only
        STATUS      current
        DESCRIPTION
            "The extended ONU model. "
        ::= { zxAnEponOnuSnEntry 7}

    zxAnEponOnuFirmwareVerTable OBJECT-TYPE
        SYNTAX       SEQUENCE OF ZxAnEponOnuFirmwareVerEntry
        MAX-ACCESS   not-accessible
        STATUS       current
        DESCRIPTION
          "ONU firmware version table."
          ::= { zxAnEponOnuExtendedAttrMgmt 2 }

    zxAnEponOnuFirmwareVerEntry OBJECT-TYPE
        SYNTAX      ZxAnEponOnuFirmwareVerEntry
        MAX-ACCESS  not-accessible
        STATUS      current
        DESCRIPTION ""
        INDEX   { zxAnEponOnuIfIndex}
        ::= { zxAnEponOnuFirmwareVerTable 1 }

    ZxAnEponOnuFirmwareVerEntry ::=
        SEQUENCE {
                zxAnEponOnuFirmwareVer             OCTET STRING
                }

    zxAnEponOnuFirmwareVer OBJECT-TYPE
        SYNTAX      OCTET STRING(SIZE(16))
        MAX-ACCESS  read-only
        STATUS      current
        DESCRIPTION
                "ONU firmware version."
        ::= { zxAnEponOnuFirmwareVerEntry 1}

    zxAnEponOnuChipsetIdTable OBJECT-TYPE
        SYNTAX       SEQUENCE OF ZxAnEponOnuChipsetIdEntry
        MAX-ACCESS   not-accessible
        STATUS       current
        DESCRIPTION
          "ONU SN table."
          ::= { zxAnEponOnuExtendedAttrMgmt 3 }

    zxAnEponOnuChipsetIdEntry OBJECT-TYPE
        SYNTAX      ZxAnEponOnuChipsetIdEntry
        MAX-ACCESS  not-accessible
        STATUS      current
        DESCRIPTION " "
        INDEX   { zxAnEponOnuIfIndex}
        ::= { zxAnEponOnuChipsetIdTable 1 }

    ZxAnEponOnuChipsetIdEntry ::=
        SEQUENCE {
                zxAnEponOnuChipVendorId                OCTET STRING,
                zxAnEponOnuChipModel                   OCTET STRING,
                zxAnEponOnuChipRevision                INTEGER,
                zxAnEponOnuChipDate                    OCTET STRING
                }

    zxAnEponOnuChipVendorId OBJECT-TYPE
        SYNTAX      OCTET STRING(SIZE(2))
        MAX-ACCESS  read-only
        STATUS      current
        DESCRIPTION
                "ONU chipset Vendor ID."
        ::= { zxAnEponOnuChipsetIdEntry 1}

    zxAnEponOnuChipModel OBJECT-TYPE
        SYNTAX      OCTET STRING(SIZE(2))
        MAX-ACCESS  read-only
        STATUS      current
        DESCRIPTION
                "Vendor specific chipset model."
        ::= { zxAnEponOnuChipsetIdEntry 2}

    zxAnEponOnuChipRevision OBJECT-TYPE
        SYNTAX      INTEGER
        MAX-ACCESS  read-only
        STATUS      current
        DESCRIPTION
                "The chipset revision."
        ::= { zxAnEponOnuChipsetIdEntry 3}

    zxAnEponOnuChipDate OBJECT-TYPE
        SYNTAX      OCTET STRING(SIZE(3))
        MAX-ACCESS  read-only
        STATUS      current
        DESCRIPTION
                "The time that chipset was designed.Format YY/MM/DD"
        ::= { zxAnEponOnuChipsetIdEntry 4}

    zxAnEponOnuCapabilityTable OBJECT-TYPE
        SYNTAX       SEQUENCE OF ZxAnEponOnuCapabilityEntry
        MAX-ACCESS   not-accessible
        STATUS       current
        DESCRIPTION
          "ONU SN table."
          ::= { zxAnEponOnuExtendedAttrMgmt 4 }

    zxAnEponOnuCapabilityEntry OBJECT-TYPE
        SYNTAX      ZxAnEponOnuCapabilityEntry
        MAX-ACCESS  not-accessible
        STATUS      current
        DESCRIPTION "An entry in the zxAnEponOnuCapabilityTable."
        INDEX   { zxAnEponOnuIfIndex}
        ::= { zxAnEponOnuCapabilityTable 1 }

    ZxAnEponOnuCapabilityEntry ::=
        SEQUENCE {
                zxAnEponOnuServiceSupported           BITS,
                zxAnEponOnuGePortNumber               INTEGER,
                zxAnEponOnuGePortBitmap               OCTET STRING,
                zxAnEponOnuFePortNumber               INTEGER,
                zxAnEponOnuFePortBitmap               OCTET STRING,
                zxAnEponOnuPotsPortNumber             INTEGER,
                zxAnEponOnuE1PortNumber               INTEGER,
                zxAnEponOnuUsQueueNumber              INTEGER,
                zxAnEponOnuUsPortMaxQueueNumber       INTEGER,
                zxAnEponOnuDsQueueNumber              INTEGER,
                zxAnEponOnuDsPortMaxQueueNumber       INTEGER,
                zxAnEponOnuBatteryBackup              TruthValue
                }

      zxAnEponOnuServiceSupported OBJECT-TYPE
        SYNTAX      BITS{
                      gePortSupport (0),
                      fePortSupport(1),
                      voipSupport(2),
                      e1Support(3),
                      onuOffLine(4)
                    }
        MAX-ACCESS  read-only
        STATUS      current
        DESCRIPTION
                "The service type surpoted on the ONU."
        ::= { zxAnEponOnuCapabilityEntry 1}

      zxAnEponOnuGePortNumber OBJECT-TYPE
        SYNTAX      INTEGER(0..255)
        MAX-ACCESS  read-only
        STATUS      current
        DESCRIPTION
                "The number of GE port surpoted on the ONU."
        ::= { zxAnEponOnuCapabilityEntry 2}

      zxAnEponOnuGePortBitmap OBJECT-TYPE
        SYNTAX      OCTET STRING(SIZE(8))
        MAX-ACCESS  read-only
        STATUS      current
        DESCRIPTION
                "if bitX is equal to 1, ONU Xth port is GE port.Total octes is 8."
        ::= { zxAnEponOnuCapabilityEntry 3}

      zxAnEponOnuFePortNumber OBJECT-TYPE
        SYNTAX      INTEGER(0..255)
        MAX-ACCESS  read-only
        STATUS      current
        DESCRIPTION
                "The number of FE port surpoted on the ONU."
        ::= { zxAnEponOnuCapabilityEntry 4}

      zxAnEponOnuFePortBitmap OBJECT-TYPE
        SYNTAX      OCTET STRING(SIZE(8))
        MAX-ACCESS  read-only
        STATUS      current
        DESCRIPTION
                "if bitX is equal to 1, ONU Xth port is FE port.Total octes is 8."
        ::= { zxAnEponOnuCapabilityEntry 5}

      zxAnEponOnuPotsPortNumber OBJECT-TYPE
        SYNTAX      INTEGER(0..255)
        MAX-ACCESS  read-only
        STATUS      current
        DESCRIPTION
                "The number of POTS port surpoted on the ONU."
        ::= { zxAnEponOnuCapabilityEntry 6}

      zxAnEponOnuE1PortNumber OBJECT-TYPE
        SYNTAX      INTEGER(0..255)
        MAX-ACCESS  read-only
        STATUS      current
        DESCRIPTION
                "The number of E1 port surpoted on the ONU."
        ::= { zxAnEponOnuCapabilityEntry 7}

      zxAnEponOnuUsQueueNumber OBJECT-TYPE
        SYNTAX      INTEGER(0..255)
        MAX-ACCESS  read-only
        STATUS      current
        DESCRIPTION
                "The number of upstream queues."
        ::= { zxAnEponOnuCapabilityEntry 8}

      zxAnEponOnuUsPortMaxQueueNumber OBJECT-TYPE
        SYNTAX      INTEGER(0..255)
        MAX-ACCESS  read-only
        STATUS      current
        DESCRIPTION
                "Maximum queues per port upstream."
        ::= { zxAnEponOnuCapabilityEntry 9}

      zxAnEponOnuDsQueueNumber OBJECT-TYPE
        SYNTAX      INTEGER(0..255)
        MAX-ACCESS  read-only
        STATUS      current
        DESCRIPTION
                "The number of downstream queues."
        ::= { zxAnEponOnuCapabilityEntry 10}

      zxAnEponOnuDsPortMaxQueueNumber OBJECT-TYPE
        SYNTAX      INTEGER(0..255)
        MAX-ACCESS  read-only
        STATUS      current
        DESCRIPTION
                "Maximum queues per port downstream."
        ::= { zxAnEponOnuCapabilityEntry 11}

      zxAnEponOnuBatteryBackup OBJECT-TYPE
        SYNTAX      TruthValue
        MAX-ACCESS  read-only
        STATUS      current
        DESCRIPTION
                ""
        ::= { zxAnEponOnuCapabilityEntry 12}

      zxAnEponOnuEthLinkStateTable OBJECT-TYPE
        SYNTAX       SEQUENCE OF ZxAnEponOnuEthLinkStateEntry
        MAX-ACCESS   not-accessible
        STATUS       current
        DESCRIPTION
          "ONU Eth link state object table."
          ::= { zxAnEponOnuExtendedAttrMgmt 5 }

    zxAnEponOnuEthLinkStateEntry OBJECT-TYPE
        SYNTAX      ZxAnEponOnuEthLinkStateEntry
        MAX-ACCESS  not-accessible
        STATUS      current
        DESCRIPTION ""
        INDEX       { zxAnEponOnuIfIndex,zxAnEponOnuPortId}
        ::= { zxAnEponOnuEthLinkStateTable 1 }

    ZxAnEponOnuEthLinkStateEntry ::=
        SEQUENCE {
                    zxAnEponOnuPortId                 INTEGER,
                    zxAnEponOnuEthPortLinkState       INTEGER
                }

    zxAnEponOnuPortId OBJECT-TYPE
        SYNTAX      INTEGER
        MAX-ACCESS  not-accessible
        STATUS      current
        DESCRIPTION
                "ONU PON port or ethernet port identifier."
        ::= { zxAnEponOnuEthLinkStateEntry 1}

    zxAnEponOnuEthPortLinkState OBJECT-TYPE
        SYNTAX     INTEGER{
                          down(1),
                          up(2)}
        MAX-ACCESS  read-only
        STATUS      current
        DESCRIPTION
                ""
        ::= { zxAnEponOnuEthLinkStateEntry 2}

    zxAnEponOnuEthPortPauseTable OBJECT-TYPE
        SYNTAX       SEQUENCE OF ZxAnEponOnuEthPortPauseEntry
        MAX-ACCESS   not-accessible
        STATUS       current
        DESCRIPTION
          "ONU Ethernet port pause function table."
          ::= { zxAnEponOnuExtendedAttrMgmt 6 }

    zxAnEponOnuEthPortPauseEntry OBJECT-TYPE
        SYNTAX      ZxAnEponOnuEthPortPauseEntry
        MAX-ACCESS  not-accessible
        STATUS      current
        DESCRIPTION " "
        INDEX       { zxAnEponOnuIfIndex,zxAnEponOnuPortId}
        ::= { zxAnEponOnuEthPortPauseTable 1 }

    ZxAnEponOnuEthPortPauseEntry ::=
        SEQUENCE {
                zxAnEponOnuPortBackPressure       INTEGER
                }

    zxAnEponOnuPortBackPressure OBJECT-TYPE
        SYNTAX      INTEGER{
                      deactive(1),
                      active(2)
                    }
        MAX-ACCESS  read-write
        STATUS      current
        DESCRIPTION
                " "
        ::= { zxAnEponOnuEthPortPauseEntry 1}

    zxAnEponOnuEthPortPolicingTable OBJECT-TYPE
        SYNTAX       SEQUENCE OF ZxAnEponOnuEthPortPolicingEntry
        MAX-ACCESS   not-accessible
        STATUS       current
        DESCRIPTION
          "ONU Ethernet port policing function table."
          ::= { zxAnEponOnuExtendedAttrMgmt 7 }

    zxAnEponOnuEthPortPolicingEntry OBJECT-TYPE
        SYNTAX      ZxAnEponOnuEthPortPolicingEntry
        MAX-ACCESS  not-accessible
        STATUS      current
        DESCRIPTION " "
        INDEX       { zxAnEponOnuIfIndex,zxAnEponOnuPortId}
        ::= { zxAnEponOnuEthPortPolicingTable 1 }

    ZxAnEponOnuEthPortPolicingEntry ::=
        SEQUENCE {
                zxAnEponOnuPortPolicing                         INTEGER,
                zxAnEponOnuPortPolicingCir                      INTEGER,
                zxAnEponOnuPortPolicingBucketDepth              INTEGER,
                zxAnEponOnuPortPolicingExtraBurstSize           INTEGER,
                zxAnEponOnuPortPolicingDownStream                INTEGER,
                zxAnEponOnuPortPolicingCirDownStream             INTEGER,
                zxAnEponOnuPortPolicingBucketDepthDownStream     INTEGER,
                zxAnEponOnuPortPolicingExtraBurstSizeDownStream  INTEGER
                }

    zxAnEponOnuPortPolicing OBJECT-TYPE
        SYNTAX      INTEGER{
                      deactive(1),
                      active(2)
                    }
        MAX-ACCESS  read-write
        STATUS      current
        DESCRIPTION
                ""
        DEFVAL { deactive }
        ::= { zxAnEponOnuEthPortPolicingEntry 1}

    zxAnEponOnuPortPolicingCir OBJECT-TYPE
        SYNTAX      INTEGER(0..16777215)
        MAX-ACCESS  read-write
        STATUS      current
        DESCRIPTION
                "This parameter indicates the committed Information
                 Rate of the port. The parameter presents the rate in
                 Kbps."
        ::= { zxAnEponOnuEthPortPolicingEntry 2}

    zxAnEponOnuPortPolicingBucketDepth OBJECT-TYPE
        SYNTAX      INTEGER(1522..16777215)
        MAX-ACCESS  read-write
        STATUS      current
        DESCRIPTION
                "This parameter identifies the depth of this token
                  bucket to tolerant the certain burst. The unit of CBS is
                  byte"
        ::= { zxAnEponOnuEthPortPolicingEntry 3}

    zxAnEponOnuPortPolicingExtraBurstSize OBJECT-TYPE
        SYNTAX      INTEGER(0..1522)
        MAX-ACCESS  read-write
        STATUS      current
        DESCRIPTION
                "This parameter identifies the extra token to permet
                the forwarding engine to finish the packet being sent
                when the CBS is exhausted. Here the Unit of EBS
                token is byte"
        ::= { zxAnEponOnuEthPortPolicingEntry 4}


      zxAnEponOnuPortPolicingDownStream OBJECT-TYPE
        SYNTAX      INTEGER{
                                  notavailable(0),
                      deactive(1),
                      active(2)
                    }
        MAX-ACCESS  read-write
        STATUS      current
        DESCRIPTION
                ""
        DEFVAL { deactive }
        ::= { zxAnEponOnuEthPortPolicingEntry 5}

    zxAnEponOnuPortPolicingCirDownStream OBJECT-TYPE
        SYNTAX      INTEGER(0..16777215)
        MAX-ACCESS  read-write
        STATUS      current
        DESCRIPTION
                "This parameter indicates the committed Information
                 Rate of the port. The parameter presents the rate in
                 Kbps."
        ::= { zxAnEponOnuEthPortPolicingEntry 6}

    zxAnEponOnuPortPolicingBucketDepthDownStream OBJECT-TYPE
        SYNTAX      INTEGER(1522..16777215)
        MAX-ACCESS  read-write
        STATUS      current
        DESCRIPTION
                "This parameter identifies the depth of this token
                  bucket to tolerant the certain burst. The unit of CBS is
                  byte"
        ::= { zxAnEponOnuEthPortPolicingEntry 7}

    zxAnEponOnuPortPolicingExtraBurstSizeDownStream OBJECT-TYPE
        SYNTAX      INTEGER(0..1522)
        MAX-ACCESS  read-write
        STATUS      current
        DESCRIPTION
                "This parameter identifies the extra token to permet
                the forwarding engine to finish the packet being sent
                when the CBS is exhausted. Here the Unit of EBS
                token is byte"
        ::= { zxAnEponOnuEthPortPolicingEntry 8}




    zxAnEponOnuVoipPortTable OBJECT-TYPE
        SYNTAX       SEQUENCE OF ZxAnEponOnuVoipPortEntry
        MAX-ACCESS   not-accessible
        STATUS       current
        DESCRIPTION
          "ONU VOIP port function table."
          ::= { zxAnEponOnuExtendedAttrMgmt 8 }

    zxAnEponOnuVoipPortEntry OBJECT-TYPE
        SYNTAX      ZxAnEponOnuVoipPortEntry
        MAX-ACCESS  not-accessible
        STATUS      current
        DESCRIPTION " "
        INDEX       { zxAnEponOnuIfIndex,zxAnEponOnuPortId}
        ::= { zxAnEponOnuVoipPortTable 1 }

    ZxAnEponOnuVoipPortEntry ::=
        SEQUENCE {
                zxAnEponOnuVoipPortEnable                INTEGER
                }

    zxAnEponOnuVoipPortEnable OBJECT-TYPE
        SYNTAX      INTEGER{
                      disable(1),
                      enable(2)
                    }
        MAX-ACCESS  read-write
        STATUS      current
        DESCRIPTION
                ""
        DEFVAL { disable }
        ::= { zxAnEponOnuVoipPortEntry 1}

   zxAnEponOnuE1PortTable OBJECT-TYPE
        SYNTAX       SEQUENCE OF ZxAnEponOnuE1PortEntry
        MAX-ACCESS   not-accessible
        STATUS       current
        DESCRIPTION
          "ONU VOIP port function table."
          ::= { zxAnEponOnuExtendedAttrMgmt 9 }

    zxAnEponOnuE1PortEntry OBJECT-TYPE
        SYNTAX      ZxAnEponOnuE1PortEntry
        MAX-ACCESS  not-accessible
        STATUS      current
        DESCRIPTION "An entry in the zxAnEponOnuE1PortTable."
        INDEX       { zxAnEponOnuIfIndex,zxAnEponOnuPortId}
        ::= { zxAnEponOnuE1PortTable 1 }

    ZxAnEponOnuE1PortEntry ::=
        SEQUENCE {
                zxAnEponOnuE1PortEnable                INTEGER
                }

    zxAnEponOnuE1PortEnable OBJECT-TYPE
        SYNTAX      INTEGER{
                      disable(1),
                      enable(2)
                    }
        MAX-ACCESS  read-write
        STATUS      current
        DESCRIPTION
                ""
        DEFVAL { disable }
        ::= { zxAnEponOnuE1PortEntry 1}

    zxAnEponOnuVlanCfgMgmt  OBJECT IDENTIFIER ::= { zxAnEponOnuExtendedAttrMgmt 10}

    zxAnEponOnuVlanCfgTable OBJECT-TYPE
        SYNTAX       SEQUENCE OF ZxAnEponOnuVlanCfgEntry
        MAX-ACCESS   not-accessible
        STATUS       current
        DESCRIPTION
          ""
          ::= { zxAnEponOnuVlanCfgMgmt 1 }

     zxAnEponOnuVlanCfgEntry OBJECT-TYPE
        SYNTAX      ZxAnEponOnuVlanCfgEntry
        MAX-ACCESS  not-accessible
        STATUS      current
        DESCRIPTION ""
        INDEX       { zxAnEponOnuIfIndex,zxAnEponOnuPortId}
        ::= { zxAnEponOnuVlanCfgTable 1 }

    ZxAnEponOnuVlanCfgEntry ::=
        SEQUENCE {
                      zxAnEponOnuVlanMode           INTEGER,
                      zxAnEponOnuVlanCfgState       INTEGER
                }

    zxAnEponOnuVlanMode OBJECT-TYPE
        SYNTAX      INTEGER{
                    transparent(1),
                    tag(2),
                    translation(3),
                    trunk(4),
                    hybrid(5),
                    aggregation(6)
                    }
        MAX-ACCESS  read-write
        STATUS      current
        DESCRIPTION
                "VLAN handling mode."
        DEFVAL  {transparent}
        ::= { zxAnEponOnuVlanCfgEntry 1}

    zxAnEponOnuVlanCfgState OBJECT-TYPE
        SYNTAX      INTEGER{
                    not-finish(1),
                    finish(2)
                    }
        MAX-ACCESS  read-write
        STATUS      current
        DESCRIPTION
                "when mode is set with value of tag or translation
                and the related configuration is not completed,
                the state must set with not_finish(1).Otherwise the state set with finish(2)."
        DEFVAL  {not-finish}
        ::= { zxAnEponOnuVlanCfgEntry 2}


    zxAnEponOnuVlanTagTable OBJECT-TYPE
        SYNTAX       SEQUENCE OF ZxAnEponOnuVlanTagEntry
        MAX-ACCESS   not-accessible
        STATUS       current
        DESCRIPTION
          "This table is needed by tag and translation handling mode"
          ::= { zxAnEponOnuVlanCfgMgmt 2 }

    zxAnEponOnuVlanTagEntry OBJECT-TYPE
        SYNTAX      ZxAnEponOnuVlanTagEntry
        MAX-ACCESS  not-accessible
        STATUS      current
        DESCRIPTION "An entry in the zxAnEponOnuVlanTable."
        INDEX       { zxAnEponOnuIfIndex,zxAnEponOnuPortId}
        ::= { zxAnEponOnuVlanTagTable 1 }

    ZxAnEponOnuVlanTagEntry ::=
        SEQUENCE {
                zxAnEponOnuVlanTagVid                  INTEGER,
                zxAnEponOnuVlanTagTpid                 INTEGER,
                zxAnEponOnuVlanTagCfi                  INTEGER,
                zxAnEponOnuVlanPriority                INTEGER
            }

    zxAnEponOnuVlanTagVid OBJECT-TYPE
        SYNTAX      INTEGER(0..4094)
        MAX-ACCESS  read-write
        STATUS      current
        DESCRIPTION
                "This attribute used as default vlan tag attribute in translation handling mode
                 "
        ::= { zxAnEponOnuVlanTagEntry 1}

    zxAnEponOnuVlanTagTpid OBJECT-TYPE
        SYNTAX      INTEGER
        MAX-ACCESS  read-write
        STATUS      current
        DESCRIPTION
                "This attribute used as default vlan tag attribute in translation handling mode
                 "
       ::= { zxAnEponOnuVlanTagEntry 2}

    zxAnEponOnuVlanTagCfi OBJECT-TYPE
        SYNTAX      INTEGER(0..1)
        MAX-ACCESS  read-write
        STATUS      current
        DESCRIPTION
                "This attribute used as default vlan tag attribute in translation handling mode
                 "
      ::= { zxAnEponOnuVlanTagEntry 3}

    zxAnEponOnuVlanPriority OBJECT-TYPE
        SYNTAX      INTEGER(0..7)
        MAX-ACCESS  read-write
        STATUS      current
        DESCRIPTION
                "This attribute used as default vlan tag attribute in translation handling mode
                 "
       ::= { zxAnEponOnuVlanTagEntry 4}

    zxAnEponOnuVlanTranslationTable OBJECT-TYPE
        SYNTAX       SEQUENCE OF ZxAnEponOnuVlanTranslationEntry
        MAX-ACCESS   not-accessible
        STATUS       current
        DESCRIPTION
          "This table is needed by translation handling mode"
          ::= { zxAnEponOnuVlanCfgMgmt 3 }

    zxAnEponOnuVlanTranslationEntry OBJECT-TYPE
        SYNTAX      ZxAnEponOnuVlanTranslationEntry
        MAX-ACCESS  not-accessible
        STATUS      current
        DESCRIPTION "An entry in the zxAnEponOnuVlanTable."
        INDEX       { zxAnEponOnuIfIndex, zxAnEponOnuPortId, zxAnEponOnuVlanTransModeEntryId}
        ::= { zxAnEponOnuVlanTranslationTable 1 }

    ZxAnEponOnuVlanTranslationEntry ::=
        SEQUENCE {
                zxAnEponOnuVlanTransModeEntryId             INTEGER,
                zxAnEponOnuVlanTransOriginalTag             Unsigned32,
                zxAnEponOnuVlanTransNewTag                  Unsigned32,
                zxAnEponOnuVlanTransModeRowStatus           RowStatus
            }

    zxAnEponOnuVlanTransModeEntryId OBJECT-TYPE
        SYNTAX      INTEGER
        MAX-ACCESS  not-accessible
        STATUS      current
        DESCRIPTION
                ""
        ::= { zxAnEponOnuVlanTranslationEntry 1}

    zxAnEponOnuVlanTransOriginalTag OBJECT-TYPE
        SYNTAX      Unsigned32
        MAX-ACCESS  read-write
        STATUS      current
        DESCRIPTION
                "This attribute only applied to Translation handling mode,
                 other handling mode is invalid."
        ::= { zxAnEponOnuVlanTranslationEntry 2}

    zxAnEponOnuVlanTransNewTag OBJECT-TYPE
        SYNTAX      Unsigned32
        MAX-ACCESS  read-write
        STATUS      current
        DESCRIPTION
                "This attribute only applied to Translation handling mode,
                 other handling mode is invalid."
        ::= { zxAnEponOnuVlanTranslationEntry 3}

     zxAnEponOnuVlanTransModeRowStatus OBJECT-TYPE
        SYNTAX      RowStatus
        MAX-ACCESS  read-write
        STATUS      current
        DESCRIPTION
            "The control that allows creation and deletion of entries. Deleting can be done
             when the entry SHOULD NOT be used by any other entry."
        ::= { zxAnEponOnuVlanTranslationEntry 4}

    zxAnEponOnuVlanTrunkTable OBJECT-TYPE
        SYNTAX       SEQUENCE OF ZxAnEponOnuVlanTrunkEntry
        MAX-ACCESS   not-accessible
        STATUS       current
        DESCRIPTION
          "This table is needed by trunk handling mode"
          ::= { zxAnEponOnuVlanCfgMgmt 4 }

    zxAnEponOnuVlanTrunkEntry OBJECT-TYPE
        SYNTAX      ZxAnEponOnuVlanTrunkEntry
        MAX-ACCESS  not-accessible
        STATUS      current
        DESCRIPTION "An entry in the zxAnEponOnuVlanTable."
        INDEX       { zxAnEponOnuIfIndex, zxAnEponOnuPortId}
        ::= { zxAnEponOnuVlanTrunkTable 1 }

    ZxAnEponOnuVlanTrunkEntry ::=
        SEQUENCE {
                zxAnEponOnuVlanTrunkModeVlan             OCTET STRING
            }

    zxAnEponOnuVlanTrunkModeVlan OBJECT-TYPE
        SYNTAX      OCTET STRING
        MAX-ACCESS  read-write
        STATUS      current
        DESCRIPTION
                "vlan-id list"
        ::= { zxAnEponOnuVlanTrunkEntry 1}

    zxAnEponOnuVlanAggregationTable  OBJECT-TYPE
            SYNTAX      SEQUENCE OF ZxAnEponOnuVlanAggregationEntry
            MAX-ACCESS  not-accessible
            STATUS      current
            DESCRIPTION
                "EPON remote management ONU VLAN aggregation table."
            ::= {zxAnEponOnuVlanCfgMgmt 5}

    zxAnEponOnuVlanAggregationEntry  OBJECT-TYPE
            SYNTAX      ZxAnEponOnuVlanAggregationEntry
            MAX-ACCESS  not-accessible
            STATUS      current
            DESCRIPTION
                "EPON remote management ONU VLAN aggregation entry."
            INDEX    { zxAnEponOnuIfIndex,zxAnEponOnuPortId,zxAnEponOnuVlanAggGrpId }
            ::= {zxAnEponOnuVlanAggregationTable 1}

    ZxAnEponOnuVlanAggregationEntry ::=
            SEQUENCE {
                zxAnEponOnuVlanAggGrpId         INTEGER,
                zxAnEponOnuVlamAggSrcVlanList   DisplayString,
                zxAnEponOnuVlanAggDestVlan      INTEGER,
                zxAnEponOnuVlanAggRowStatus     RowStatus
                }

    zxAnEponOnuVlanAggGrpId OBJECT-TYPE
            SYNTAX      INTEGER(1..3)
            MAX-ACCESS  read-create
            STATUS      current
            DESCRIPTION
                    ""
            ::= { zxAnEponOnuVlanAggregationEntry 1 }

    zxAnEponOnuVlamAggSrcVlanList  OBJECT-TYPE
            SYNTAX      DisplayString
            MAX-ACCESS  read-create
            STATUS      current
            DESCRIPTION
                 "Source VLAN list. Example: 2,5,9-16"
            ::= { zxAnEponOnuVlanAggregationEntry 2 }

    zxAnEponOnuVlanAggDestVlan  OBJECT-TYPE
            SYNTAX      INTEGER(1..4094)
            MAX-ACCESS  read-create
            STATUS      current
            DESCRIPTION
                 "Destination VLAN."
            ::= { zxAnEponOnuVlanAggregationEntry 3 }

    zxAnEponOnuVlanAggRowStatus  OBJECT-TYPE
            SYNTAX      RowStatus
            MAX-ACCESS  read-create
            STATUS      current
            DESCRIPTION
                 "ONU VLAN aggregation table RowStatus.
                 Set it CreateAndWait(5) if not all the group is created.
                 set it Active(1) when all the group is created."
            ::= { zxAnEponOnuVlanAggregationEntry 10 }

    zxAnEponOnuClassMarkingAttrMgmt            OBJECT IDENTIFIER ::= { zxAnEponOnuExtendedAttrMgmt 11}

    zxAnEponOnuClassMarkingConditionTable OBJECT-TYPE
        SYNTAX       SEQUENCE OF ZxAnEponOnuClassMarkingConditionEntry
        MAX-ACCESS   not-accessible
        STATUS       current
        DESCRIPTION
          "ONU classification and marking managed object table."
          ::= { zxAnEponOnuClassMarkingAttrMgmt 1 }

    zxAnEponOnuClassMarkingConditionEntry OBJECT-TYPE
        SYNTAX      ZxAnEponOnuClassMarkingConditionEntry
        MAX-ACCESS  not-accessible
        STATUS      current
        DESCRIPTION "An entry in the zxAnEponOnuClassMarkingConditionTable."
        INDEX       { zxAnEponOnuIfIndex, zxAnEponOnuClassMarkingConditionId}
        ::= { zxAnEponOnuClassMarkingConditionTable 1 }

    ZxAnEponOnuClassMarkingConditionEntry ::=
        SEQUENCE {
                zxAnEponOnuClassMarkingConditionId      INTEGER,
                zxAnEponOnuClassMarkingConditionName    OCTET STRING,
                zxAnEponOnuClassMarkingField            INTEGER,
                zxAnEponOnuClassMarkingMatchValue       OCTET STRING,
                zxAnEponOnuClassMarkingOperator         INTEGER,
                zxAnEponOnuClassMarkingConditionRefCnt  INTEGER,
                zxAnEponOnuClassMarkingConditionRowStatus  RowStatus
                }

    zxAnEponOnuClassMarkingConditionId OBJECT-TYPE
        SYNTAX      INTEGER
        MAX-ACCESS  not-accessible
        STATUS      current
        DESCRIPTION
                ""
        ::= { zxAnEponOnuClassMarkingConditionEntry 1}

    zxAnEponOnuClassMarkingConditionName OBJECT-TYPE
        SYNTAX     OCTET STRING(SIZE(0..32))
        MAX-ACCESS  read-write
        STATUS      current
        DESCRIPTION
                ""
        ::= { zxAnEponOnuClassMarkingConditionEntry 2}

    zxAnEponOnuClassMarkingField OBJECT-TYPE
        SYNTAX     INTEGER{
                                     da(1),
                                     sa(2),
                                     priority(3),
                                     vlan(4),
                                     ethType(5),
                                     destIp(6),
                                     srcIp(7),
                                     ipProtType(8),
                                     ipV4(9),
                                     ipV6(10),
                                     l4SrcPort(11),
                                     l4DestPort(12),
                                     linkIndex(13),
                                     ipPrecedence(14)
                    }
        MAX-ACCESS  read-write
        STATUS      current
        DESCRIPTION
                ""
        ::= { zxAnEponOnuClassMarkingConditionEntry 3}

    zxAnEponOnuClassMarkingMatchValue OBJECT-TYPE
        SYNTAX     OCTET STRING(SIZE(6))
        MAX-ACCESS  read-write
        STATUS      current
        DESCRIPTION
                ""
        ::= { zxAnEponOnuClassMarkingConditionEntry 4}

    zxAnEponOnuClassMarkingOperator OBJECT-TYPE
        SYNTAX     INTEGER{
                                        never-match(1),
                                        equal(2),
                                        not-equal(3),
                                        less-and-equal(4),
                                        greater-and-equal(5),
                                        exist(6),
                                        not-exist(7),
                                        always-match(8)
                  }
        MAX-ACCESS  read-write
        STATUS      current
        DESCRIPTION
                ""
        ::= { zxAnEponOnuClassMarkingConditionEntry 5}

    zxAnEponOnuClassMarkingConditionRefCnt OBJECT-TYPE
        SYNTAX      INTEGER
        MAX-ACCESS  read-only
        STATUS      current
        DESCRIPTION
            "Indicate the reference count of this instance."
        ::= { zxAnEponOnuClassMarkingConditionEntry 6}

    zxAnEponOnuClassMarkingConditionRowStatus OBJECT-TYPE
        SYNTAX      RowStatus
        MAX-ACCESS  read-write
        STATUS      current
        DESCRIPTION
            "The control that allows creation and deletion of entries. Deleting can be done
             when the entry SHOULD NOT be used by any other entry."
        ::= { zxAnEponOnuClassMarkingConditionEntry 7}

    zxAnEponOnuClassMarkingRuleTable OBJECT-TYPE
        SYNTAX       SEQUENCE OF ZxAnEponOnuClassMarkingRuleEntry
        MAX-ACCESS   not-accessible
        STATUS       current
        DESCRIPTION
          "ONU classification and marking managed object table."
          ::= { zxAnEponOnuClassMarkingAttrMgmt 2 }

    zxAnEponOnuClassMarkingRuleEntry OBJECT-TYPE
        SYNTAX      ZxAnEponOnuClassMarkingRuleEntry
        MAX-ACCESS  not-accessible
        STATUS      current
        DESCRIPTION "An entry in the zxAnEponOnuClassMarkingRuleTable."
        INDEX       { zxAnEponOnuIfIndex, zxAnEponOnuClassMarkingRuleId}
        ::= { zxAnEponOnuClassMarkingRuleTable 1 }

    ZxAnEponOnuClassMarkingRuleEntry ::=
        SEQUENCE {
                zxAnEponOnuClassMarkingRuleId          INTEGER,
                zxAnEponOnuClassMarkingRuleName        OCTET STRING,
                zxAnEponOnuClassMarkingQueue           INTEGER,
                zxAnEponOnuClassMarkingPriority        INTEGER,
                zxAnEponOnuClassMarkingRuleRefCnt      INTEGER,
                zxAnEponOnuClassMarkingRuleRowStatus   RowStatus
                }

    zxAnEponOnuClassMarkingRuleId OBJECT-TYPE
        SYNTAX      INTEGER
        MAX-ACCESS  not-accessible
        STATUS      current
        DESCRIPTION
                " "
        ::= { zxAnEponOnuClassMarkingRuleEntry 1}

    zxAnEponOnuClassMarkingRuleName OBJECT-TYPE
        SYNTAX     OCTET STRING(SIZE(0..32))
        MAX-ACCESS  read-write
        STATUS      current
        DESCRIPTION
                ""
        ::= { zxAnEponOnuClassMarkingRuleEntry 2}

    zxAnEponOnuClassMarkingQueue OBJECT-TYPE
        SYNTAX     INTEGER
        MAX-ACCESS  read-write
        STATUS      current
        DESCRIPTION
                ""
        ::= { zxAnEponOnuClassMarkingRuleEntry 3}

    zxAnEponOnuClassMarkingPriority OBJECT-TYPE
        SYNTAX     INTEGER(0..7)
        MAX-ACCESS  read-write
        STATUS      current
        DESCRIPTION
                ""
        ::= { zxAnEponOnuClassMarkingRuleEntry 4}

    zxAnEponOnuClassMarkingRuleRefCnt OBJECT-TYPE
        SYNTAX      INTEGER
        MAX-ACCESS  read-only
        STATUS      current
        DESCRIPTION
            "Indicate the reference count of this instance."
        ::= { zxAnEponOnuClassMarkingRuleEntry 5}

    zxAnEponOnuClassMarkingRuleRowStatus OBJECT-TYPE
        SYNTAX      RowStatus
        MAX-ACCESS  read-write
        STATUS      current
        DESCRIPTION
            "The control that allows creation and deletion of entries. Deleting can be done
             when the entry SHOULD NOT be used by any other entry."
        ::= { zxAnEponOnuClassMarkingRuleEntry 6}

    zxAnEponOnuClassMarkingTable OBJECT-TYPE
        SYNTAX       SEQUENCE OF ZxAnEponOnuClassMarkingEntry
        MAX-ACCESS   not-accessible
        STATUS       current
        DESCRIPTION
          "ONU classification and marking managed object table."
          ::= { zxAnEponOnuClassMarkingAttrMgmt 3 }

    zxAnEponOnuClassMarkingEntry OBJECT-TYPE
        SYNTAX      ZxAnEponOnuClassMarkingEntry
        MAX-ACCESS  not-accessible
        STATUS      current
        DESCRIPTION "An entry in the zxAnEponOnuClassMarkingTable."
        INDEX       { zxAnEponOnuIfIndex, zxAnEponOnuPortId, zxAnEponOnuClassMarkingRulePrecedence}
        ::= { zxAnEponOnuClassMarkingTable 1 }

    ZxAnEponOnuClassMarkingEntry ::=
        SEQUENCE {
                zxAnEponOnuClassMarkingRulePrecedence     INTEGER,
                zxAnEponOnuClassMarkingRuleIndex          INTEGER,
                zxAnEponOnuClassMarkingRuleConditionList  OCTET STRING,
                zxAnEponOnuClassMarkingRowStatus          RowStatus,
                zxAnEponOnuClassMarkingRulePriority       INTEGER,
                zxAnEponOnuClassMarkingRuleDirection      INTEGER,
                zxAnEponOnuClassMarkingRuleType           INTEGER
                }

    zxAnEponOnuClassMarkingRulePrecedence OBJECT-TYPE
        SYNTAX     INTEGER
        MAX-ACCESS  not-accessible
        STATUS      current
        DESCRIPTION
                ""
        ::= { zxAnEponOnuClassMarkingEntry 1}

    zxAnEponOnuClassMarkingRuleIndex OBJECT-TYPE
        SYNTAX     INTEGER
        MAX-ACCESS  read-write
        STATUS      current
        DESCRIPTION
                ""
        ::= { zxAnEponOnuClassMarkingEntry 2}

    zxAnEponOnuClassMarkingRuleConditionList OBJECT-TYPE
        SYNTAX      OCTET STRING
        MAX-ACCESS  read-write
        STATUS      current
        DESCRIPTION
                ""
        ::= { zxAnEponOnuClassMarkingEntry 3}

    zxAnEponOnuClassMarkingRowStatus OBJECT-TYPE
        SYNTAX      RowStatus
        MAX-ACCESS  read-write
        STATUS      current
        DESCRIPTION
            "The control that allows creation and deletion of entries. Deleting can be done
             when the entry SHOULD NOT be used by any other entry."
        ::= { zxAnEponOnuClassMarkingEntry 4}

    zxAnEponOnuClassMarkingRulePriority OBJECT-TYPE
        SYNTAX     INTEGER
        MAX-ACCESS  read-write
        STATUS      current
        DESCRIPTION
                ""
        ::= { zxAnEponOnuClassMarkingEntry 5}

    zxAnEponOnuClassMarkingRuleDirection OBJECT-TYPE
        SYNTAX     INTEGER{
                    downstream(1),
                    upstream(2)}
        MAX-ACCESS  read-write
        STATUS      current
        DESCRIPTION
                ""
        ::= { zxAnEponOnuClassMarkingEntry 6}

    zxAnEponOnuClassMarkingRuleType OBJECT-TYPE
        SYNTAX     INTEGER{
                    classification(1),
                    filter(2)}
        MAX-ACCESS  read-write
        STATUS      current
        DESCRIPTION
                ""
        ::= { zxAnEponOnuClassMarkingEntry 7}


    zxAnEponOnuClassMarkingClearTable OBJECT-TYPE
        SYNTAX       SEQUENCE OF ZxAnEponOnuClassMarkingClearEntry
        MAX-ACCESS   not-accessible
        STATUS       current
        DESCRIPTION
          "."
          ::= { zxAnEponOnuClassMarkingAttrMgmt 4 }

    zxAnEponOnuClassMarkingClearEntry OBJECT-TYPE
        SYNTAX      ZxAnEponOnuClassMarkingClearEntry
        MAX-ACCESS  not-accessible
        STATUS      current
        DESCRIPTION ""
        INDEX       { zxAnEponOnuIfIndex }
        ::= { zxAnEponOnuClassMarkingClearTable 1 }

    ZxAnEponOnuClassMarkingClearEntry ::=
        SEQUENCE {
                zxAnEponOnuClassMarkingClear       INTEGER
                }

    zxAnEponOnuClassMarkingClear OBJECT-TYPE
        SYNTAX     INTEGER
        MAX-ACCESS  read-write
        STATUS      current
        DESCRIPTION
                ""
        ::= { zxAnEponOnuClassMarkingClearEntry 1}


    zxAnEponOnuClassMarkingCompatibilityTable OBJECT-TYPE
        SYNTAX       SEQUENCE OF ZxAnEponOnuClassMarkingCompatibilityEntry
        MAX-ACCESS   not-accessible
        STATUS       current
        DESCRIPTION
          "."
          ::= { zxAnEponOnuClassMarkingAttrMgmt 101 }

    zxAnEponOnuClassMarkingCompatibilityEntry OBJECT-TYPE
        SYNTAX      ZxAnEponOnuClassMarkingCompatibilityEntry
        MAX-ACCESS  not-accessible
        STATUS      current
        DESCRIPTION ""
        INDEX       { zxAnEponOnuIfIndex, zxAnEponOnuPortId}
        ::= { zxAnEponOnuClassMarkingCompatibilityTable 1 }

    ZxAnEponOnuClassMarkingCompatibilityEntry ::=
        SEQUENCE {
                zxAnEponOnuClassMarkingRulePriorityFlag       INTEGER,
                zxAnEponOnuClassMarkingRuleDirectionFlag      INTEGER,
                zxAnEponOnuClassMarkingRuleTypeFlag           INTEGER
                }

    zxAnEponOnuClassMarkingRulePriorityFlag OBJECT-TYPE
        SYNTAX     INTEGER{
                    enable(1),
                    disable(2)}
        MAX-ACCESS  read-only
        STATUS      current
        DESCRIPTION
                ""
        ::= { zxAnEponOnuClassMarkingCompatibilityEntry 1}

    zxAnEponOnuClassMarkingRuleDirectionFlag OBJECT-TYPE
        SYNTAX     INTEGER{
                    enable(1),
                    disable(2)}
        MAX-ACCESS  read-only
        STATUS      current
        DESCRIPTION
                ""
        ::= { zxAnEponOnuClassMarkingCompatibilityEntry 2}

    zxAnEponOnuClassMarkingRuleTypeFlag OBJECT-TYPE
        SYNTAX     INTEGER{
                    enable(1),
                    disable(2)}
        MAX-ACCESS  read-only
        STATUS      current
        DESCRIPTION
                ""
        ::= { zxAnEponOnuClassMarkingCompatibilityEntry 3}


    zxAnEponOnuMulticastVlanTable OBJECT-TYPE
        SYNTAX       SEQUENCE OF ZxAnEponOnuMulticastVlanEntry
        MAX-ACCESS   not-accessible
        STATUS       current
        DESCRIPTION
          "ONU VOIP port function table."
          ::= { zxAnEponOnuExtendedAttrMgmt 12 }

    zxAnEponOnuMulticastVlanEntry OBJECT-TYPE
        SYNTAX      ZxAnEponOnuMulticastVlanEntry
        MAX-ACCESS  not-accessible
        STATUS      current
        DESCRIPTION " "
        INDEX       { zxAnEponOnuIfIndex,zxAnEponOnuPortId}
        ::= { zxAnEponOnuMulticastVlanTable 1 }

    ZxAnEponOnuMulticastVlanEntry ::=
        SEQUENCE {
                zxAnEponOnuMulticastVlanAction         INTEGER,
                zxAnEponOnuMulticastVlanList           OCTET STRING
                }
    zxAnEponOnuMulticastVlanAction OBJECT-TYPE
        SYNTAX      INTEGER{
                    delete(0),
                    add(1),
                    clear(2)}
        MAX-ACCESS  read-write
        STATUS      current
        DESCRIPTION
                ""
        ::= { zxAnEponOnuMulticastVlanEntry 1}

    zxAnEponOnuMulticastVlanList OBJECT-TYPE
        SYNTAX      OCTET STRING
        MAX-ACCESS  read-write
        STATUS      current
        DESCRIPTION
                ""
        ::= { zxAnEponOnuMulticastVlanEntry 2}

    zxAnEponOnuMulticastTagCfgTable OBJECT-TYPE
        SYNTAX       SEQUENCE OF ZxAnEponOnuMulticastTagCfgEntry
        MAX-ACCESS   not-accessible
        STATUS       current
        DESCRIPTION
          " "
          ::= { zxAnEponOnuExtendedAttrMgmt 13 }

    zxAnEponOnuMulticastTagCfgEntry OBJECT-TYPE
        SYNTAX      ZxAnEponOnuMulticastTagCfgEntry
        MAX-ACCESS  not-accessible
        STATUS      current
        DESCRIPTION ""
        INDEX       { zxAnEponOnuIfIndex,zxAnEponOnuPortId}
        ::= { zxAnEponOnuMulticastTagCfgTable 1 }

    ZxAnEponOnuMulticastTagCfgEntry ::=
        SEQUENCE {
                zxAnEponOnuMulticastTagStripe            INTEGER
                }

    zxAnEponOnuMulticastTagStripe OBJECT-TYPE
        SYNTAX     INTEGER{
                   not-striped(1),
                   striped(2),
                   tagSwitch(3)
                    }
        MAX-ACCESS  read-write
        STATUS      current
        DESCRIPTION
                ""
        ::= { zxAnEponOnuMulticastTagCfgEntry 1}

    zxAnEponOnuMulticastSwitchTable OBJECT-TYPE
        SYNTAX       SEQUENCE OF ZxAnEponOnuMulticastSwitchEntry
        MAX-ACCESS   not-accessible
        STATUS       current
        DESCRIPTION
          "ONU Eth link state object table."
          ::= { zxAnEponOnuExtendedAttrMgmt 14 }

    zxAnEponOnuMulticastSwitchEntry OBJECT-TYPE
        SYNTAX      ZxAnEponOnuMulticastSwitchEntry
        MAX-ACCESS  not-accessible
        STATUS      current
        DESCRIPTION "An entry in the zxAnEponOnuMulticastCfgTable."
        INDEX   { zxAnEponOnuIfIndex }
        ::= { zxAnEponOnuMulticastSwitchTable 1 }

    ZxAnEponOnuMulticastSwitchEntry ::=
        SEQUENCE {
                zxAnEponOnuMulticastSwitchAttr            INTEGER
                }

    zxAnEponOnuMulticastSwitchAttr OBJECT-TYPE
        SYNTAX     INTEGER{
                   igmpsnooping(1),
                   ctrl-multicast(2)}
        MAX-ACCESS  read-write
        STATUS      current
        DESCRIPTION
                ""
        ::= { zxAnEponOnuMulticastSwitchEntry 1}

    zxAnEponOnuMulticastControlMgmt  OBJECT IDENTIFIER ::= { zxAnEponOnuExtendedAttrMgmt 15}

    zxAnEponOnuMulticastControlClearTable OBJECT-TYPE
        SYNTAX       SEQUENCE OF ZxAnEponOnuMulticastControlClearEntry
        MAX-ACCESS   not-accessible
        STATUS       current
        DESCRIPTION
          " "
          ::= { zxAnEponOnuMulticastControlMgmt 1 }

    zxAnEponOnuMulticastControlClearEntry OBJECT-TYPE
        SYNTAX      ZxAnEponOnuMulticastControlClearEntry
        MAX-ACCESS  not-accessible
        STATUS      current
        DESCRIPTION ""
        INDEX   { zxAnEponOnuIfIndex}
        ::= { zxAnEponOnuMulticastControlClearTable 1 }

    ZxAnEponOnuMulticastControlClearEntry ::=
        SEQUENCE {
                zxAnEponOnuMcstCtrlClear            INTEGER
                }

    zxAnEponOnuMcstCtrlClear OBJECT-TYPE
        SYNTAX      INTEGER
        MAX-ACCESS  read-write
        STATUS      current
        DESCRIPTION
                ""
        ::= { zxAnEponOnuMulticastControlClearEntry 1}

    zxAnEponOnuMulticastControlTable OBJECT-TYPE
        SYNTAX       SEQUENCE OF ZxAnEponOnuMulticastControlEntry
        MAX-ACCESS   not-accessible
        STATUS       current
        DESCRIPTION
          "ONU multicast control entry function table."
          ::= { zxAnEponOnuMulticastControlMgmt 2 }

    zxAnEponOnuMulticastControlEntry OBJECT-TYPE
        SYNTAX      ZxAnEponOnuMulticastControlEntry
        MAX-ACCESS  not-accessible
        STATUS      current
        DESCRIPTION ""
        INDEX       { zxAnEponOnuIfIndex, zxAnEponOnuMcstCtrlEntryIndex }
        ::= { zxAnEponOnuMulticastControlTable 1 }

    ZxAnEponOnuMulticastControlEntry ::=
        SEQUENCE {
                zxAnEponOnuMcstCtrlEntryIndex              INTEGER,
                zxAnEponOnuMcstCtrlAction                  INTEGER,
                zxAnEponOnuMcstCtrlType                    INTEGER,
                zxAnEponOnuMcstCtrlUserId                  INTEGER,
                zxAnEponOnuMcstCtrlGda                     MacAddress,
                zxAnEponOnuMcstCtrlMvlan                   INTEGER,
                zxAnEponOnuMcstCtrlGdaIp                   IpAddress
                }

    zxAnEponOnuMcstCtrlEntryIndex OBJECT-TYPE
        SYNTAX      INTEGER
        MAX-ACCESS  not-accessible
        STATUS      current
        DESCRIPTION
                ""
        ::= { zxAnEponOnuMulticastControlEntry 1}

    zxAnEponOnuMcstCtrlAction OBJECT-TYPE
        SYNTAX      INTEGER{
                        delete(1),
                        add(2)
                    }
        MAX-ACCESS  read-write
        STATUS      current
        DESCRIPTION
                ""
        ::= { zxAnEponOnuMulticastControlEntry 2}

    zxAnEponOnuMcstCtrlType OBJECT-TYPE
        SYNTAX      INTEGER{
                      gda(1),
                      gda-and-vlan(2),
                      gda-and-sa(3),
                      gip-and-vlan(4)
                    }
        MAX-ACCESS  read-write
        STATUS      current
        DESCRIPTION
                ""
        ::= { zxAnEponOnuMulticastControlEntry 3}

    zxAnEponOnuMcstCtrlUserId OBJECT-TYPE
        SYNTAX      INTEGER(1..4094)
        MAX-ACCESS  read-write
        STATUS      current
        DESCRIPTION
                "The unicast vlan(CVlan)"
        ::= { zxAnEponOnuMulticastControlEntry 4}

    zxAnEponOnuMcstCtrlGda OBJECT-TYPE
        SYNTAX      MacAddress
        MAX-ACCESS  read-write
        STATUS      current
        DESCRIPTION
                "The group destination MAC address"
        ::= { zxAnEponOnuMulticastControlEntry 5}

    zxAnEponOnuMcstCtrlMvlan OBJECT-TYPE
        SYNTAX      INTEGER(1..4094)
        MAX-ACCESS  read-write
        STATUS      current
        DESCRIPTION
                "Multicast vlan."
        ::= { zxAnEponOnuMulticastControlEntry 6}

    zxAnEponOnuMcstCtrlGdaIp OBJECT-TYPE
        SYNTAX      IpAddress
        MAX-ACCESS  read-write
        STATUS      current
        DESCRIPTION
                "Multicast gda ipaddress."
        ::= { zxAnEponOnuMulticastControlEntry 7}


    zxAnEponOnuMaxGroupNumTable OBJECT-TYPE
        SYNTAX       SEQUENCE OF ZxAnEponOnuMaxGroupNumEntry
        MAX-ACCESS   not-accessible
        STATUS       current
        DESCRIPTION
          "Supported maximum multicast group number table."
          ::= { zxAnEponOnuExtendedAttrMgmt 16 }

    zxAnEponOnuMaxGroupNumEntry OBJECT-TYPE
        SYNTAX      ZxAnEponOnuMaxGroupNumEntry
        MAX-ACCESS  not-accessible
        STATUS      current
        DESCRIPTION ""
        INDEX       { zxAnEponOnuIfIndex,zxAnEponOnuPortId}
        ::= { zxAnEponOnuMaxGroupNumTable 1 }

    ZxAnEponOnuMaxGroupNumEntry ::=
        SEQUENCE {
                zxAnEponOnuMaxGroupNum                    INTEGER
                }

    zxAnEponOnuMaxGroupNum OBJECT-TYPE
        SYNTAX      INTEGER(0..255)
        MAX-ACCESS  read-write
        STATUS      current
        DESCRIPTION
                "Supported maximum multicast group number."
        ::= { zxAnEponOnuMaxGroupNumEntry 1}



--  Comment: Created by PSK time:2007-06-13

 zxAnEponOnuAlarmCtrlTable OBJECT-TYPE
        SYNTAX       SEQUENCE OF ZxAnEponOnuAlarmCtrlEntry
        MAX-ACCESS   not-accessible
        STATUS       current
        DESCRIPTION
          "Enable or Disable the ONU Alarm."
          ::= { zxAnEponOnuExtendedAttrMgmt 17 }

  zxAnEponOnuAlarmCtrlEntry OBJECT-TYPE
        SYNTAX      ZxAnEponOnuAlarmCtrlEntry
        MAX-ACCESS  not-accessible
        STATUS      current
        DESCRIPTION ""
        INDEX       { zxAnEponOnuIfIndex}
        ::= { zxAnEponOnuAlarmCtrlTable 1 }

    ZxAnEponOnuAlarmCtrlEntry ::=
        SEQUENCE {
                zxAnEponOnuAlarmCtr                  INTEGER
                }

    zxAnEponOnuAlarmCtr OBJECT-TYPE
        SYNTAX      INTEGER{
                      disable(1),
                      enable(2)
                    }
        MAX-ACCESS  read-write
        STATUS      current
        DESCRIPTION
                "Enable or Disable the ONU Alarm."
        DEFVAL { enable }
        ::= { zxAnEponOnuAlarmCtrlEntry 1}


    zxAnEponOnuMACNumTable OBJECT-TYPE
        SYNTAX       SEQUENCE OF ZxAnEponOnuMACNumEntry
        MAX-ACCESS   not-accessible
        STATUS       current
        DESCRIPTION
          "Supported onu ethernet-Port MAC number table."
          ::= { zxAnEponOnuExtendedAttrMgmt 18 }

    zxAnEponOnuMACNumEntry OBJECT-TYPE
        SYNTAX      ZxAnEponOnuMACNumEntry
        MAX-ACCESS  not-accessible
        STATUS      current
        DESCRIPTION ""
        INDEX       { zxAnEponOnuIfIndex,zxAnEponOnuPortId}
        ::= { zxAnEponOnuMACNumTable 1 }

    ZxAnEponOnuMACNumEntry ::=
        SEQUENCE {
                zxAnEponOnuMACNum                     INTEGER,
                zxAnEponOnuUniLearnedMacs             Integer32
                }

    zxAnEponOnuMACNum OBJECT-TYPE
        SYNTAX      INTEGER(0..65535)
        MAX-ACCESS  read-write
        STATUS      current
        DESCRIPTION
                "Supported onu ethernet-Port MAC number table."
        DEFVAL { 65535 }
        ::= { zxAnEponOnuMACNumEntry 1}

    zxAnEponOnuUniLearnedMacs  OBJECT-TYPE
        SYNTAX      Integer32
        MAX-ACCESS  read-only
        STATUS      current
        DESCRIPTION
             "EPON ONU UNI learned MAC addresses."
        DEFVAL { 0 }
        ::= { zxAnEponOnuMACNumEntry 2 }


   zxAnEponOnuMACAgingTimeTable OBJECT-TYPE
        SYNTAX       SEQUENCE OF ZxAnEponOnuMACAgingTimeEntry
        MAX-ACCESS   not-accessible
        STATUS       current
        DESCRIPTION
          "ONU MAC Aging time table."
          ::= { zxAnEponOnuExtendedAttrMgmt 19 }

    zxAnEponOnuMACAgingTimeEntry OBJECT-TYPE
        SYNTAX      ZxAnEponOnuMACAgingTimeEntry
        MAX-ACCESS  not-accessible
        STATUS      current
        DESCRIPTION "An entry in the zxAnEponOnuMACAgingTimeTable."
        INDEX   { zxAnEponOnuIfIndex}
        ::= { zxAnEponOnuMACAgingTimeTable 1 }

    ZxAnEponOnuMACAgingTimeEntry ::=
        SEQUENCE {
                zxAnEponOnuMACAgingTimeAttr INTEGER
                }

     zxAnEponOnuMACAgingTimeAttr OBJECT-TYPE
        SYNTAX      INTEGER(15..86400)
        MAX-ACCESS  read-write
        STATUS      current
        DESCRIPTION
                "Aging time: seconds."
        DEFVAL { 300 }
        ::= { zxAnEponOnuMACAgingTimeEntry 1}

-- filter MAC Address
  zxAnEponOnuFilterMACTable OBJECT-TYPE
        SYNTAX       SEQUENCE OF ZxAnEponOnuFilterMACEntry
        MAX-ACCESS   not-accessible
        STATUS       current
        DESCRIPTION
          "ONU Ethernet Port Filter MAC Table."
          ::= { zxAnEponOnuExtendedAttrMgmt 20 }

    zxAnEponOnuFilterMACEntry OBJECT-TYPE
        SYNTAX      ZxAnEponOnuFilterMACEntry
        MAX-ACCESS  not-accessible
        STATUS      current
        DESCRIPTION " "
        INDEX       { zxAnEponOnuIfIndex,zxAnEponOnuPortId, zxAnEponOnuFilterMAC, zxEponFilterVlan}
        ::= { zxAnEponOnuFilterMACTable 1 }

    ZxAnEponOnuFilterMACEntry ::=
        SEQUENCE {
                zxAnEponOnuFilterMAC           MacAddress,
                zxEponFilterVlan          INTEGER,
                          zxAnEponOnuFilterMACEntryStatus             RowStatus
                }

    zxAnEponOnuFilterMAC   OBJECT-TYPE
        SYNTAX      MacAddress
        MAX-ACCESS  not-accessible
        STATUS      current
        DESCRIPTION
                ""
        ::= { zxAnEponOnuFilterMACEntry 1 }
    zxEponFilterVlan  OBJECT-TYPE
        SYNTAX      INTEGER(1..4094)
        MAX-ACCESS  not-accessible
        STATUS      current
        DESCRIPTION
                ""
        ::= { zxAnEponOnuFilterMACEntry 2 }

    zxAnEponOnuFilterMACEntryStatus OBJECT-TYPE
        SYNTAX      RowStatus
        MAX-ACCESS  read-write
        STATUS      current
        DESCRIPTION
                ""
        ::= { zxAnEponOnuFilterMACEntry 3 }


-- Bind MAC Address
     zxAnEponOnuBindMACTable OBJECT-TYPE
        SYNTAX       SEQUENCE OF ZxAnEponOnuBindMACEntry
        MAX-ACCESS   not-accessible
        STATUS       current
        DESCRIPTION
          "ONU Ethernet Port Binded MAC Table."
          ::= { zxAnEponOnuExtendedAttrMgmt 21 }

    zxAnEponOnuBindMACEntry OBJECT-TYPE
        SYNTAX      ZxAnEponOnuBindMACEntry
        MAX-ACCESS  not-accessible
        STATUS      current
        DESCRIPTION " "
        INDEX       { zxAnEponOnuIfIndex, zxAnEponOnuPortId, zxAnEponOnuBindMAC, zxEponBindVlan }
        ::= { zxAnEponOnuBindMACTable 1 }

    ZxAnEponOnuBindMACEntry ::=
        SEQUENCE {
                zxAnEponOnuBindMAC           MacAddress,
                zxEponBindVlan    INTEGER,
                          zxAnEponOnuBindMACEntryStatus             RowStatus
                }

    zxAnEponOnuBindMAC OBJECT-TYPE
        SYNTAX      MacAddress
        MAX-ACCESS  not-accessible
        STATUS      current
        DESCRIPTION
                ""
        ::= { zxAnEponOnuBindMACEntry 1}
    zxEponBindVlan  OBJECT-TYPE
        SYNTAX      INTEGER(1..4094)
        MAX-ACCESS  not-accessible
        STATUS      current
        DESCRIPTION
                ""
        ::= { zxAnEponOnuBindMACEntry 2 }

    zxAnEponOnuBindMACEntryStatus OBJECT-TYPE
        SYNTAX      RowStatus
        MAX-ACCESS  read-write
        STATUS      current
        DESCRIPTION
                ""
        ::= { zxAnEponOnuBindMACEntry 3 }

-- Static MAC Address
  zxAnEponOnuStaticMACTable OBJECT-TYPE
        SYNTAX       SEQUENCE OF ZxAnEponOnuStaticMACEntry
        MAX-ACCESS   not-accessible
        STATUS       current
        DESCRIPTION
          "ONU Ethernet Port Static MAC Table."
          ::= { zxAnEponOnuExtendedAttrMgmt 22 }

    zxAnEponOnuStaticMACEntry OBJECT-TYPE
        SYNTAX      ZxAnEponOnuStaticMACEntry
        MAX-ACCESS  not-accessible
        STATUS      current
        DESCRIPTION " "
        INDEX       { zxAnEponOnuIfIndex,zxAnEponOnuPortId, zxAnEponOnuStaticMAC, zxEponStaticVlan}
        ::= { zxAnEponOnuStaticMACTable 1 }

    ZxAnEponOnuStaticMACEntry ::=
        SEQUENCE {
                zxAnEponOnuStaticMAC           MacAddress,
                zxEponStaticVlan          INTEGER,
                            zxAnEponOnuStaicMACEntryStatus RowStatus
                }

    zxAnEponOnuStaticMAC OBJECT-TYPE
        SYNTAX      MacAddress
        MAX-ACCESS  not-accessible
        STATUS      current
        DESCRIPTION
                ""
        ::= { zxAnEponOnuStaticMACEntry 1}

    zxEponStaticVlan  OBJECT-TYPE
        SYNTAX      INTEGER(1..4094)
        MAX-ACCESS  not-accessible
        STATUS      current
        DESCRIPTION
                ""
        ::= { zxAnEponOnuStaticMACEntry 2 }

    zxAnEponOnuStaicMACEntryStatus OBJECT-TYPE
        SYNTAX      RowStatus
        MAX-ACCESS  read-write
        STATUS      current
        DESCRIPTION
                ""
        ::= { zxAnEponOnuStaticMACEntry 3 }


 -- MAC Address Clear  Action

 zxAnEponOnuMACAddressClearTable OBJECT-TYPE
        SYNTAX       SEQUENCE OF ZxAnEponOnuMACAddressClearEntry
        MAX-ACCESS   not-accessible
        STATUS       current
        DESCRIPTION
          "Clear Ethernet Port MAC Address Table(filter, bind or static)"
          ::= { zxAnEponOnuExtendedAttrMgmt 23 }

    zxAnEponOnuMACAddressClearEntry OBJECT-TYPE
        SYNTAX      ZxAnEponOnuMACAddressClearEntry
        MAX-ACCESS  not-accessible
        STATUS      current
        DESCRIPTION " "
        INDEX       { zxAnEponOnuIfIndex,zxAnEponOnuPortId }
        ::= { zxAnEponOnuMACAddressClearTable 1 }

    ZxAnEponOnuMACAddressClearEntry ::=
        SEQUENCE {
                zxAnEponOnuMACAddressType           INTEGER
                }

   zxAnEponOnuMACAddressType OBJECT-TYPE
        SYNTAX      INTEGER{
                    filter(1),
                    bind(2),
                    static(3)}
        MAX-ACCESS  read-write
        STATUS      current
        DESCRIPTION
                ""
        ::= { zxAnEponOnuMACAddressClearEntry 1 }



  zxAnEponOnuManagerIPTable OBJECT-TYPE
        SYNTAX       SEQUENCE OF ZxAnEponOnuManagerIPTableEntry
        MAX-ACCESS   not-accessible
        STATUS       current
        DESCRIPTION
          "Onu's Manage IP Information."
          ::= { zxAnEponOnuExtendedAttrMgmt 24 }

  zxAnEponOnuManagerIPTableEntry OBJECT-TYPE
        SYNTAX      ZxAnEponOnuManagerIPTableEntry
        MAX-ACCESS  not-accessible
        STATUS      current
        DESCRIPTION ""
        INDEX       { zxAnEponOnuIfIndex}
        ::= { zxAnEponOnuManagerIPTable 1 }

    ZxAnEponOnuManagerIPTableEntry ::=
        SEQUENCE {
            zxEponOnuIPAddress          IpAddress,
            zxEponOnuIPMask             IpAddress,
            zxEponMangementPriority     INTEGER,
            zxEponMangementVlan         INTEGER,
            zxEponManagementHostIP      IpAddress,
            zxEponManagementHostMask    IpAddress,
            zxEponManagementGateway     IpAddress,
            zxEponOnuIPConfigureStatus  INTEGER,
            zxEponMangementSVlan        INTEGER
                }

    zxEponOnuIPAddress OBJECT-TYPE
        SYNTAX      IpAddress
        MAX-ACCESS  read-write
        STATUS      current
        DESCRIPTION
        ""
        ::= { zxAnEponOnuManagerIPTableEntry 1 }

    zxEponOnuIPMask  OBJECT-TYPE
        SYNTAX      IpAddress
        MAX-ACCESS  read-write
        STATUS      current
        DESCRIPTION
        ""
        ::= { zxAnEponOnuManagerIPTableEntry 2 }

    zxEponMangementPriority   OBJECT-TYPE
        SYNTAX      INTEGER(0..7)
        MAX-ACCESS  read-write
        STATUS      current
        DESCRIPTION
                ""
        ::= { zxAnEponOnuManagerIPTableEntry 3 }

    zxEponMangementVlan  OBJECT-TYPE
        SYNTAX      INTEGER(1..4094)
        MAX-ACCESS  read-write
        STATUS      current
        DESCRIPTION
                ""
        ::= { zxAnEponOnuManagerIPTableEntry 4}

    zxEponManagementHostIP OBJECT-TYPE
        SYNTAX      IpAddress
        MAX-ACCESS  read-write
        STATUS      current
        DESCRIPTION
        ""
        ::= { zxAnEponOnuManagerIPTableEntry 5 }

    zxEponManagementHostMask  OBJECT-TYPE
        SYNTAX      IpAddress
        MAX-ACCESS  read-write
        STATUS      current
        DESCRIPTION
        ""
        ::= { zxAnEponOnuManagerIPTableEntry 6 }

   zxEponManagementGateway  OBJECT-TYPE
        SYNTAX      IpAddress
        MAX-ACCESS  read-write
        STATUS      current
        DESCRIPTION
        ""
        ::= { zxAnEponOnuManagerIPTableEntry 7 }

    zxEponOnuIPConfigureStatus  OBJECT-TYPE
        SYNTAX       INTEGER{
                      disable(1),
                      enable(2)
                    }
        MAX-ACCESS  read-write
        STATUS      current
        DESCRIPTION
                ""
        ::= { zxAnEponOnuManagerIPTableEntry 8}

    zxEponMangementSVlan  OBJECT-TYPE
        SYNTAX      INTEGER(0..4094)
        MAX-ACCESS  read-write
        STATUS      current
        DESCRIPTION
                ""
        ::= { zxAnEponOnuManagerIPTableEntry 9}

     zxAnEponOnuIsolationCtrlTable OBJECT-TYPE
        SYNTAX       SEQUENCE OF ZxAnEponOnuIsolationCtrlEntry
        MAX-ACCESS   not-accessible
        STATUS       current
        DESCRIPTION
          "Enable or Disable the ONU Port Isolation."
          ::= { zxAnEponOnuExtendedAttrMgmt 25 }

    zxAnEponOnuIsolationCtrlEntry OBJECT-TYPE
        SYNTAX      ZxAnEponOnuIsolationCtrlEntry
        MAX-ACCESS  not-accessible
        STATUS      current
        DESCRIPTION ""
        INDEX       { zxAnEponOnuIfIndex}
        ::= { zxAnEponOnuIsolationCtrlTable 1 }

    ZxAnEponOnuIsolationCtrlEntry ::=
        SEQUENCE {
                zxAnEponOnuIsolationCtr                  INTEGER
                }

    zxAnEponOnuIsolationCtr  OBJECT-TYPE
        SYNTAX      INTEGER{
                      disable(1),
                      enable(2)
                    }
        MAX-ACCESS  read-write
        STATUS      current
        DESCRIPTION
                "Enable or Disable the ONU Port Isolation."
        DEFVAL { enable }
        ::= { zxAnEponOnuIsolationCtrlEntry 1}

  zxAnEponRmFastLeaveAbiTable OBJECT-TYPE
        SYNTAX       SEQUENCE OF ZxAnEponRmFastLeaveAbiEntry
        MAX-ACCESS   not-accessible
        STATUS       current
        DESCRIPTION
          "onu rm fastLeave object table."
          ::= { zxAnEponOnuExtendedAttrMgmt 26 }

    zxAnEponRmFastLeaveAbiEntry OBJECT-TYPE
            SYNTAX      ZxAnEponRmFastLeaveAbiEntry
        MAX-ACCESS  not-accessible
        STATUS      current
        DESCRIPTION ""
        INDEX       { zxAnEponOnuIfIndex }
        ::= { zxAnEponRmFastLeaveAbiTable 1 }

    ZxAnEponRmFastLeaveAbiEntry ::=
        SEQUENCE {
               fastleaveabi    INTEGER
                }

    fastleaveabi  OBJECT-TYPE
        SYNTAX      INTEGER
        MAX-ACCESS  read-only
        STATUS      current
        DESCRIPTION
                "bitmap: 0xff: not gain
         0x01: snooping: fast-leave
         0x02: snooping: not-fast-leave
         0x04: control-multicast: fast-leave
         0x08: control-multicast: not -fast-leave"
        ::= { zxAnEponRmFastLeaveAbiEntry 1}

  eponRmFastLeaveAdminStateTable OBJECT-TYPE
        SYNTAX       SEQUENCE OF EponRmFastLeaveAdminStateEntry
        MAX-ACCESS   not-accessible
        STATUS       current
        DESCRIPTION
          "onu rm fastLeave adminstate object table."
          ::= { zxAnEponOnuExtendedAttrMgmt 27 }

    eponRmFastLeaveAdminStateEntry OBJECT-TYPE
        SYNTAX      EponRmFastLeaveAdminStateEntry
        MAX-ACCESS  not-accessible
        STATUS      current
        DESCRIPTION ""
        INDEX       { zxAnEponOnuIfIndex }
        ::= { eponRmFastLeaveAdminStateTable 1 }

    EponRmFastLeaveAdminStateEntry ::=
        SEQUENCE {
               getState    INTEGER
                }

        getState  OBJECT-TYPE
        SYNTAX      INTEGER{
                                          noResult(0),
                      disable(1),
                      enable(2)
                    }
        MAX-ACCESS  read-write
        STATUS      current
        DESCRIPTION
                "e_eponrm_noResult=0,
                 e_eponrm_disabled=1,
         e_eponrm_enabled=2"
        ::= { eponRmFastLeaveAdminStateEntry 1}

  eponIpGlobalTable OBJECT-TYPE
        SYNTAX       SEQUENCE OF EponIpGlobalEntry
        MAX-ACCESS   not-accessible
        STATUS       current
        DESCRIPTION
          "onu rm fastLeave adminstate object table."
          ::= { zxAnEponOnuExtendedAttrMgmt 28 }

    eponIpGlobalEntry OBJECT-TYPE
        SYNTAX      EponIpGlobalEntry
        MAX-ACCESS  not-accessible
        STATUS      current
        DESCRIPTION ""
        INDEX       { zxAnEponOnuIfIndex, zxAnEponOnuVioceCardIndex}
        ::= { eponIpGlobalTable 1 }

    EponIpGlobalEntry ::=
        SEQUENCE {
                           zxAnEponOnuVioceCardIndex    INTEGER,
               zxAnEponOnuVoiceIpMngIpRelation    INTEGER,
                           zxAnEponOnuVoiceIpMode    INTEGER,
                           zxAnEponOnuVoiceIpAddress    IpAddress,
                           zxAnEponOnuVoiceDnsServer    IpAddress,
                           zxAnEponOnuVoiceIpMask    IpAddress,
                           zxAnEponOnuVoiceGateway   IpAddress,
                           zxAnEponOnuVoicePPPoEMode    INTEGER,
                           zxAnEponOnuVoicePPPoEUserName   DisplayString,
                           zxAnEponOnuVoicePPPoEPassword    DisplayString,
                           zxAnEponOnuVoiceTaggedFlag    INTEGER,
                           zxAnEponOnuVoiceDataVlan    INTEGER,
                           zxAnEponOnuVoiceDataPriority   INTEGER,
                           zxAnEponOnuVoiceDhcpLeaseTime   INTEGER,
                           zxAnEponOnuVoicePPPoEStatus   INTEGER
                           }
                zxAnEponOnuVioceCardIndex  OBJECT-TYPE
        SYNTAX      INTEGER
        MAX-ACCESS  not-accessible
        STATUS      current
        DESCRIPTION
                " Onu Vioce Card Index"
        ::= { eponIpGlobalEntry 1}

                zxAnEponOnuVoiceIpMngIpRelation  OBJECT-TYPE
        SYNTAX      INTEGER{
                                          standalone(1),
                      useVOIPIP(2)
                    }
        MAX-ACCESS  read-write
        STATUS      current
        DESCRIPTION
                " Onu Voice Ip Mng Ip Relation"
        ::= { eponIpGlobalEntry 2}

                zxAnEponOnuVoiceIpMode  OBJECT-TYPE
        SYNTAX      INTEGER{
                                          static(1),
                      dhcp(2),
                      pppoe(3)
                    }
        MAX-ACCESS  read-write
        STATUS      current
        DESCRIPTION
                " Onu Voice Ip Mode 0:static; 1:dhcp;2:PPPOE"
        ::= { eponIpGlobalEntry 3}

                zxAnEponOnuVoiceIpAddress  OBJECT-TYPE
        SYNTAX      IpAddress
        MAX-ACCESS  read-write
        STATUS      current
        DESCRIPTION
                " Onu Voice Ip Address"
        ::= { eponIpGlobalEntry 4}

                zxAnEponOnuVoiceDnsServer  OBJECT-TYPE
        SYNTAX      IpAddress
        MAX-ACCESS  read-write
        STATUS      current
        DESCRIPTION
                " Onu Voice Dns Server"
        ::= { eponIpGlobalEntry 5}

                zxAnEponOnuVoiceIpMask  OBJECT-TYPE
        SYNTAX      IpAddress
        MAX-ACCESS  read-write
        STATUS      current
        DESCRIPTION
                " Onu Voice Ip Mask"
        ::= { eponIpGlobalEntry 6}

                zxAnEponOnuVoiceGateway  OBJECT-TYPE
        SYNTAX      IpAddress
        MAX-ACCESS  read-write
        STATUS      current
        DESCRIPTION
                " Onu Voice Gateway"
        ::= { eponIpGlobalEntry 7}

                zxAnEponOnuVoicePPPoEMode  OBJECT-TYPE
        SYNTAX      INTEGER{
                                          auto(1),
                      chap(2),
                      pap(3)
                    }
        MAX-ACCESS  read-write
        STATUS      current
        DESCRIPTION
                "1:AUTO;2:CHAP;3:PAP"
        ::= { eponIpGlobalEntry 8}

                zxAnEponOnuVoicePPPoEUserName  OBJECT-TYPE
        SYNTAX      DisplayString
        MAX-ACCESS  read-write
        STATUS      current
        DESCRIPTION
                " Onu Voice PPPoE UserName"
        ::= { eponIpGlobalEntry 9}

                zxAnEponOnuVoicePPPoEPassword  OBJECT-TYPE
        SYNTAX      DisplayString
        MAX-ACCESS  read-write
        STATUS      current
        DESCRIPTION
                " Onu Voice PPPoE Password"
        ::= { eponIpGlobalEntry 10}

                zxAnEponOnuVoiceTaggedFlag  OBJECT-TYPE
        SYNTAX      INTEGER{
                      enable(1),
                      disable(2)
                    }
        MAX-ACCESS  read-write
        STATUS      current
        DESCRIPTION
                " Onu Voice Tagged Flag"
        ::= { eponIpGlobalEntry 11}

                zxAnEponOnuVoiceDataVlan  OBJECT-TYPE
        SYNTAX      INTEGER
        MAX-ACCESS  read-write
        STATUS      current
        DESCRIPTION
                " Onu Voice Data Vlan"
        ::= { eponIpGlobalEntry 12}

                zxAnEponOnuVoiceDataPriority  OBJECT-TYPE
        SYNTAX      INTEGER{
                                          pri0(1),
                      pri1(2),
                      pri2(3),
                                          pri3(4),
                      pri4(5),
                      pri5(6),
                                          pri6(7),
                      pri7(8)
                    }
        MAX-ACCESS  read-write
        STATUS      current
        DESCRIPTION
                " Onu Voice Data Priority"
        ::= { eponIpGlobalEntry 13}

                zxAnEponOnuVoiceDhcpLeaseTime  OBJECT-TYPE
        SYNTAX      INTEGER
        MAX-ACCESS  read-only
        STATUS      current
        DESCRIPTION
                " Onu Voice Dhcp Lease Time"
        ::= { eponIpGlobalEntry 14}

                zxAnEponOnuVoicePPPoEStatus  OBJECT-TYPE
        SYNTAX      INTEGER{
                      dhcping(1),
                                          dhcpfinish(2),
                      pppoeing(3),
                                          pppoefinish(4)
                    }
        MAX-ACCESS  read-only
        STATUS      current
        DESCRIPTION
                " Onu Voice PPPoE Status"
        ::= { eponIpGlobalEntry 15}

    epon0pticalTransceiverDiagnosisTable OBJECT-TYPE
        SYNTAX       SEQUENCE OF Epon0pticalTransceiverDiagnosisEntry
        MAX-ACCESS   not-accessible
        STATUS       current
        DESCRIPTION
          "epon 0pticalTransceiverDiagnosis object table."
          ::= { zxAnEponOnuExtendedAttrMgmt 29 }

    epon0pticalTransceiverDiagnosisEntry OBJECT-TYPE
        SYNTAX      Epon0pticalTransceiverDiagnosisEntry
        MAX-ACCESS  not-accessible
        STATUS      current
        DESCRIPTION ""
        INDEX       { zxAnEponOnuIfIndex}
        ::= { epon0pticalTransceiverDiagnosisTable 1 }

    Epon0pticalTransceiverDiagnosisEntry ::=
        SEQUENCE {
                           zxAnEponOnuTransTemperature    DisplayString,
               zxAnEponOnuSupplyVoltage    DisplayString,
                           zxAnEponOnuTxBiasCurrent    DisplayString,
                           zxAnEponOnuTxPower    DisplayString,
                           zxAnEponOnuRxPower    DisplayString
                           }
        zxAnEponOnuTransTemperature  OBJECT-TYPE
        SYNTAX      DisplayString
        MAX-ACCESS  read-only
        STATUS      current
        DESCRIPTION
                " Epon Onu TransTemperature value"
        ::= { epon0pticalTransceiverDiagnosisEntry 1}

        zxAnEponOnuSupplyVoltage  OBJECT-TYPE
        SYNTAX      DisplayString
        MAX-ACCESS  read-only
        STATUS      current
        DESCRIPTION
                " Epon Onu SupplyVoltage value"
        ::= { epon0pticalTransceiverDiagnosisEntry 2}

        zxAnEponOnuTxBiasCurrent  OBJECT-TYPE
        SYNTAX      DisplayString
        MAX-ACCESS  read-only
        STATUS      current
        DESCRIPTION
                " Epon Onu TxBias Current value"
        ::= { epon0pticalTransceiverDiagnosisEntry 3}

        zxAnEponOnuTxPower  OBJECT-TYPE
        SYNTAX      DisplayString
        MAX-ACCESS  read-only
        STATUS      current
        DESCRIPTION
                " Epon Onu TxPower value"
        ::= { epon0pticalTransceiverDiagnosisEntry 4}

        zxAnEponOnuRxPower  OBJECT-TYPE
        SYNTAX      DisplayString
        MAX-ACCESS  read-only
        STATUS      current
        DESCRIPTION
                " Epon Onu RxPower value"
        ::= { epon0pticalTransceiverDiagnosisEntry 5}

    eponRmOnuTransAlarmCfgTable OBJECT-TYPE
        SYNTAX       SEQUENCE OF EponRmOnuTransAlarmCfgTableEntry
        MAX-ACCESS   not-accessible
        STATUS       current
        DESCRIPTION
          "Epon Rm Onu TransAlarmCfg object table."
          ::= { zxAnEponOnuExtendedAttrMgmt 30}

    eponRmOnuTransAlarmCfgTableEntry OBJECT-TYPE
        SYNTAX      EponRmOnuTransAlarmCfgTableEntry
        MAX-ACCESS  not-accessible
        STATUS      current
        DESCRIPTION ""
        INDEX       { zxAnEponOnuIfIndex}
        ::= { eponRmOnuTransAlarmCfgTable 1 }

    EponRmOnuTransAlarmCfgTableEntry ::=
        SEQUENCE {
                           zxAnEponOnuTrans    INTEGER
                           }
        zxAnEponOnuTrans  OBJECT-TYPE
        SYNTAX      INTEGER{
                      disable(1),
                      enable(2)
                    }
        MAX-ACCESS  read-write
        STATUS      current
        DESCRIPTION
                "Enable or Disable the Epon Rm ONU TransAlarmCfg."
        DEFVAL { enable }
        ::= { eponRmOnuTransAlarmCfgTableEntry 1}

    eponRmOnuTransAlarmThresholdTable OBJECT-TYPE
        SYNTAX       SEQUENCE OF EponRmOnuTransAlarmThresholdEntry
        MAX-ACCESS   not-accessible
        STATUS       current
        DESCRIPTION
          "Epon Rm Onu Trans Alarm Threshold object table."
          ::= { zxAnEponOnuExtendedAttrMgmt 31 }

    eponRmOnuTransAlarmThresholdEntry OBJECT-TYPE
        SYNTAX      EponRmOnuTransAlarmThresholdEntry
        MAX-ACCESS  not-accessible
        STATUS      current
        DESCRIPTION ""
        INDEX       { zxAnEponOnuIfIndex }
        ::= { eponRmOnuTransAlarmThresholdTable 1 }

    EponRmOnuTransAlarmThresholdEntry ::=
        SEQUENCE {
                           zxAnEponOnuTempHighAlarm    DisplayString,
               zxAnEponOnuTempLowAlarm     DisplayString,
                           zxAnEponOnuTempHighWarning  DisplayString,
                           zxAnEponOnuTempLowwarning    DisplayString,
                           zxAnEponOnuVoltageHighAlarm    DisplayString,
               zxAnEponOnuVoltageLowAlarm     DisplayString,
                           zxAnEponOnuVoltageHighWarning  DisplayString,
                           zxAnEponOnuVoltageLowWarning    DisplayString,
                           zxAnEponOnuBiasHighAlarm   DisplayString,
                           zxAnEponOnuBiasLowAlarm    DisplayString,
               zxAnEponOnuBiasHighWarning     DisplayString,
                           zxAnEponOnuBiasLowWarning  DisplayString,
                           zxAnEponOnuTxPowerHighAlarm    DisplayString,
                           zxAnEponOnuTxPowerLowAlarm    DisplayString,
               zxAnEponOnuTxPowerHighWarning     DisplayString,
                           zxAnEponOnuTxPowerLowWarning  DisplayString,
                           zxAnEponOnuRxPowerHighAlarm    DisplayString,
                           zxAnEponOnuRxPowerLowAlarm   DisplayString,
                           zxAnEponOnuRxPowerHighWarning    DisplayString,
                           zxAnEponOnuRxPowerLowWarning   DisplayString
                           }
        zxAnEponOnuTempHighAlarm  OBJECT-TYPE
        SYNTAX      DisplayString
        MAX-ACCESS  read-write
        STATUS      current
        DESCRIPTION
                " Epon Onu Temp High Alarm value"
        ::= { eponRmOnuTransAlarmThresholdEntry 1}

        zxAnEponOnuTempLowAlarm  OBJECT-TYPE
        SYNTAX      DisplayString
        MAX-ACCESS  read-write
        STATUS      current
        DESCRIPTION
                " Epon Onu Temp Low Alarm value"
        ::= { eponRmOnuTransAlarmThresholdEntry 2}

        zxAnEponOnuTempHighWarning  OBJECT-TYPE
        SYNTAX      DisplayString
        MAX-ACCESS  read-write
        STATUS      current
        DESCRIPTION
                " Epon Onu Temp High Warning value"
        ::= { eponRmOnuTransAlarmThresholdEntry 3}

        zxAnEponOnuTempLowwarning  OBJECT-TYPE
        SYNTAX      DisplayString
        MAX-ACCESS  read-write
        STATUS      current
        DESCRIPTION
                " Epon Onu Temp Low warning value"
        ::= { eponRmOnuTransAlarmThresholdEntry 4}

        zxAnEponOnuVoltageHighAlarm  OBJECT-TYPE
        SYNTAX      DisplayString
        MAX-ACCESS  read-write
        STATUS      current
        DESCRIPTION
                " Epon Onu Voltage High Alarm value"
        ::= { eponRmOnuTransAlarmThresholdEntry 5}

        zxAnEponOnuVoltageLowAlarm  OBJECT-TYPE
        SYNTAX      DisplayString
        MAX-ACCESS  read-write
        STATUS      current
        DESCRIPTION
                " Epon Onu Voltage Low Alarm value"
        ::= { eponRmOnuTransAlarmThresholdEntry 6}

        zxAnEponOnuVoltageHighWarning  OBJECT-TYPE
        SYNTAX      DisplayString
        MAX-ACCESS  read-write
        STATUS      current
        DESCRIPTION
                " Epon Onu Voltage High Warning value"
        ::= { eponRmOnuTransAlarmThresholdEntry 7}

        zxAnEponOnuVoltageLowWarning  OBJECT-TYPE
        SYNTAX      DisplayString
        MAX-ACCESS  read-write
        STATUS      current
        DESCRIPTION
                " Epon Onu Voltage Low Warning value"
        ::= { eponRmOnuTransAlarmThresholdEntry 8}

        zxAnEponOnuBiasHighAlarm  OBJECT-TYPE
        SYNTAX      DisplayString
        MAX-ACCESS  read-write
        STATUS      current
        DESCRIPTION
                " Epon Onu Bias High Alarm value"
        ::= { eponRmOnuTransAlarmThresholdEntry 9}

        zxAnEponOnuBiasLowAlarm  OBJECT-TYPE
        SYNTAX      DisplayString
        MAX-ACCESS  read-write
        STATUS      current
        DESCRIPTION
                " Epon Onu Bias Low Alarm value"
        ::= { eponRmOnuTransAlarmThresholdEntry 10}

        zxAnEponOnuBiasHighWarning  OBJECT-TYPE
        SYNTAX      DisplayString
        MAX-ACCESS  read-write
        STATUS      current
        DESCRIPTION
                " Epon Onu Bias High Warning value"
        ::= { eponRmOnuTransAlarmThresholdEntry 11}

        zxAnEponOnuBiasLowWarning  OBJECT-TYPE
        SYNTAX      DisplayString
        MAX-ACCESS  read-write
        STATUS      current
        DESCRIPTION
                " Epon Onu Bias Low Warning value"
        ::= { eponRmOnuTransAlarmThresholdEntry 12}

        zxAnEponOnuTxPowerHighAlarm  OBJECT-TYPE
        SYNTAX      DisplayString
        MAX-ACCESS  read-write
        STATUS      current
        DESCRIPTION
                " Epon Onu TxPower High Alarm value"
        ::= { eponRmOnuTransAlarmThresholdEntry 13}

        zxAnEponOnuTxPowerLowAlarm  OBJECT-TYPE
        SYNTAX      DisplayString
        MAX-ACCESS  read-write
        STATUS      current
        DESCRIPTION
                " Epon Onu TxPower Low Alarm value"
        ::= { eponRmOnuTransAlarmThresholdEntry 14}

        zxAnEponOnuTxPowerHighWarning  OBJECT-TYPE
        SYNTAX      DisplayString
        MAX-ACCESS  read-write
        STATUS      current
        DESCRIPTION
                " Epon Onu TxPower High Warning value"
        ::= { eponRmOnuTransAlarmThresholdEntry 15}

        zxAnEponOnuTxPowerLowWarning  OBJECT-TYPE
        SYNTAX      DisplayString
        MAX-ACCESS  read-write
        STATUS      current
        DESCRIPTION
                " Epon Onu TxPower Low Warning value"
        ::= { eponRmOnuTransAlarmThresholdEntry 16}

        zxAnEponOnuRxPowerHighAlarm  OBJECT-TYPE
        SYNTAX      DisplayString
        MAX-ACCESS  read-write
        STATUS      current
        DESCRIPTION
                " Epon Onu RxPower High Alarm value"
        ::= { eponRmOnuTransAlarmThresholdEntry 17}

        zxAnEponOnuRxPowerLowAlarm  OBJECT-TYPE
        SYNTAX      DisplayString
        MAX-ACCESS  read-write
        STATUS      current
        DESCRIPTION
                " Epon Onu  RxPower Low Alarm value"
        ::= { eponRmOnuTransAlarmThresholdEntry 18}

        zxAnEponOnuRxPowerHighWarning  OBJECT-TYPE
        SYNTAX      DisplayString
        MAX-ACCESS  read-write
        STATUS      current
        DESCRIPTION
                " Epon Onu  RxPower High Warning value"
        ::= { eponRmOnuTransAlarmThresholdEntry 19}

        zxAnEponOnuRxPowerLowWarning  OBJECT-TYPE
        SYNTAX      DisplayString
        MAX-ACCESS  read-write
        STATUS      current
        DESCRIPTION
                " Epon Onu RxPower Low Warning value"
        ::= { eponRmOnuTransAlarmThresholdEntry 20}

    zxEponUniProfileAdmin                OBJECT IDENTIFIER ::= { zxAnEponOnuExtendedAttrMgmt 32}

    zxEponUniProfileTable  OBJECT-TYPE
        SYNTAX         SEQUENCE OF ZxEponUniProfileEntry
        MAX-ACCESS     not-accessible
        STATUS         current
        DESCRIPTION
            "EPON UNI port limit profile table"
        ::= { zxEponUniProfileAdmin 1 }

    zxEponUniProfileEntry OBJECT-TYPE
            SYNTAX         ZxEponUniProfileEntry
            MAX-ACCESS     not-accessible
            STATUS         current
            DESCRIPTION
            "EPON UNI port limit profile entry"
            INDEX    {uniProfileIndex }
            ::= { zxEponUniProfileTable 1}

    ZxEponUniProfileEntry ::=
        SEQUENCE {
                uniProfileIndex        INTEGER,
                                uniProfileName         DisplayString,
                uniProfileUpCir          Integer32,
                uniProfileUpCbs          Integer32,
                                uniProfileUpEbs          Integer32,
                uniProfileDownCir          Integer32,
                uniProfileDownCbs          Integer32,
                                uniProfileDownEbs          Integer32,
                                uniProfileRowStatus    RowStatus
                 }

   uniProfileIndex   OBJECT-TYPE
        SYNTAX       INTEGER
        MAX-ACCESS   not-accessible
        STATUS       current
        DESCRIPTION
            "This parameter indicates the committed Information
                 Rate of the port. The parameter presents the rate in
                 Kbps."
        ::= { zxEponUniProfileEntry 1 }

    uniProfileName   OBJECT-TYPE
        SYNTAX      DisplayString(SIZE(1..31))
        MAX-ACCESS  read-write
        STATUS      current
        DESCRIPTION
            "This object identifies a row in this table."
          ::= { zxEponUniProfileEntry 2 }

   uniProfileUpCir   OBJECT-TYPE
        SYNTAX       Integer32(0..16777215)
        MAX-ACCESS   read-write
        STATUS       current
        DESCRIPTION
            "This parameter indicates the committed Information
                 Rate of the port. The parameter presents the rate in
                 Kbps."
        ::= { zxEponUniProfileEntry 3 }

   uniProfileUpCbs   OBJECT-TYPE
        SYNTAX       Integer32(1522..16777215)
        MAX-ACCESS   read-write
        STATUS       current
        DESCRIPTION
            "This parameter identifies the depth of this token
                  bucket to tolerant the certain burst. The unit of CBS is
                  byte"
        ::= { zxEponUniProfileEntry 4 }

   uniProfileUpEbs    OBJECT-TYPE
        SYNTAX       Integer32(0..1522)
        MAX-ACCESS   read-write
        STATUS       current
        DESCRIPTION
            "This parameter identifies the extra token to permet
                the forwarding engine to finish the packet being sent
                when the CBS is exhausted. Here the Unit of EBS
                token is byte"
        ::= { zxEponUniProfileEntry 5 }

   uniProfileDownCir   OBJECT-TYPE
        SYNTAX       Integer32(0..16777215)
        MAX-ACCESS   read-write
        STATUS       current
        DESCRIPTION
            "This parameter indicates the committed Information
                 Rate of the port. The parameter presents the rate in
                 Kbps."
        ::= { zxEponUniProfileEntry 6 }

   uniProfileDownCbs   OBJECT-TYPE
        SYNTAX       Integer32(1522..16777215)
        MAX-ACCESS   read-write
        STATUS       current
        DESCRIPTION
            "This parameter identifies the depth of this token
                  bucket to tolerant the certain burst. The unit of CBS is
                  byte"
        ::= { zxEponUniProfileEntry 7 }

   uniProfileDownEbs    OBJECT-TYPE
        SYNTAX       Integer32(0..1522)
        MAX-ACCESS   read-write
        STATUS       current
        DESCRIPTION
            "This parameter identifies the extra token to permet
                the forwarding engine to finish the packet being sent
                when the CBS is exhausted. Here the Unit of EBS
                token is byte"
        ::= { zxEponUniProfileEntry 8 }

   uniProfileRowStatus        OBJECT-TYPE
        SYNTAX      RowStatus
        MAX-ACCESS  read-create
        STATUS      current
        DESCRIPTION
            "EPON uni port limit RowStatus "
        ::= { zxEponUniProfileEntry  9 }

    uniProfileNextIndex     OBJECT-TYPE
        SYNTAX      INTEGER
        MAX-ACCESS  read-only
        STATUS      current
        DESCRIPTION
            "Next available index of profile table "
        ::= { zxEponUniProfileAdmin 2 }

    zxEponUniLimitCfgTable  OBJECT-TYPE
        SYNTAX         SEQUENCE OF ZxEponUniLimitCfgEntry
        MAX-ACCESS     not-accessible
        STATUS         current
        DESCRIPTION
            "EPON onu bandwidth profile config table"
        ::= { zxAnEponOnuExtendedAttrMgmt 34 }

    zxEponUniLimitCfgEntry OBJECT-TYPE
            SYNTAX         ZxEponUniLimitCfgEntry
            MAX-ACCESS     not-accessible
            STATUS         current
            DESCRIPTION
            "EPON uni limit profile config entry"
            INDEX    { zxAnEponOnuIfIndex,zxAnEponOnuPortId }
            ::= { zxEponUniLimitCfgTable 1}

    ZxEponUniLimitCfgEntry ::=
        SEQUENCE {
                                uniCfgLimitProfileIndex             INTEGER
                 }

    uniCfgLimitProfileIndex    OBJECT-TYPE
        SYNTAX      INTEGER(0..256)
        MAX-ACCESS  read-write
        STATUS      current
        DESCRIPTION
            "uni up limit profile name, 0 for no profile."
          ::= { zxEponUniLimitCfgEntry 1 }

------------------------------------------------------------------------------
-- 1.35 EPON ONU VOIP remote profile management(OAM)
------------------------------------------------------------------------------

    zxAnEponRmVoipProfileMgmt  OBJECT IDENTIFIER ::= { zxAnEponOnuExtendedAttrMgmt 35}


--------------------------------------------------------------------------------
-- 1.35.1 Voip Ip profile table index next
--------------------------------------------------------------------------------
    zxAnEponRmVoipIpProfileIdxNext OBJECT-TYPE
                SYNTAX      INTEGER
                MAX-ACCESS  read-only
                STATUS      current
                DESCRIPTION
                "Use this value as index to create an entry of zxAnEponRmVoipIpProfileTable"
                ::= { zxAnEponRmVoipProfileMgmt 1 }

--------------------------------------------------------------------------------
-- 1.35.2 Voip Ip profile table
--------------------------------------------------------------------------------
    zxAnEponRmVoipIpProfileTable  OBJECT-TYPE
            SYNTAX      SEQUENCE OF ZxAnEponRmVoipIpProfileEntry
            MAX-ACCESS  not-accessible
            STATUS      current
            DESCRIPTION
                "EPON remote management voip IP profile table."
            ::= {zxAnEponRmVoipProfileMgmt 2}

    zxAnEponRmVoipIpProfileEntry  OBJECT-TYPE
            SYNTAX      ZxAnEponRmVoipIpProfileEntry
            MAX-ACCESS  not-accessible
            STATUS      current
            DESCRIPTION
               "EPON remote management voip IP profile entry."
            INDEX    {zxAnEponRmVoipIpProfileIdx }
            ::= {zxAnEponRmVoipIpProfileTable 1}

    ZxAnEponRmVoipIpProfileEntry ::=
            SEQUENCE {
                zxAnEponRmVoipIpProfileIdx          INTEGER,
                                zxAnEponRmVoipIpProfileName         DisplayString,
                                zxAnEponRmVoipIpMngIpRelation       INTEGER,
                zxAnEponRmVoipIpMode                INTEGER,
                zxAnEponRmVoipIpDefaultGateWay      IpAddress,
                                zxAnEponRmVoipIpPrimaryDNSServerIp  IpAddress,
                zxAnEponRmVoipIpPPPoEMode           INTEGER,
                zxAnEponRmVoipIpRowStatus           RowStatus
                }

    zxAnEponRmVoipIpProfileIdx  OBJECT-TYPE
            SYNTAX      INTEGER
            MAX-ACCESS  not-accessible
            STATUS      current
            DESCRIPTION
                 "EPON remote management voip IP profile index."
            ::= { zxAnEponRmVoipIpProfileEntry 1 }

    zxAnEponRmVoipIpProfileName  OBJECT-TYPE
            SYNTAX      DisplayString ( SIZE(1..32) )
            MAX-ACCESS  read-create
            STATUS      current
            DESCRIPTION
                 "EPON remote management voip IP profile name."
            ::= { zxAnEponRmVoipIpProfileEntry 2 }

    zxAnEponRmVoipIpMngIpRelation  OBJECT-TYPE
            SYNTAX      INTEGER {
                independent(1),
                shared(2)
                }
            MAX-ACCESS  read-create
            STATUS      current
            DESCRIPTION
                 "The relationship between Voip ipaddress and manangement ipaddress."
            DEFVAL { independent }
            ::= { zxAnEponRmVoipIpProfileEntry 3 }

    zxAnEponRmVoipIpMode  OBJECT-TYPE
            SYNTAX      INTEGER {
                static(1),
                dhcp(2),
                pppoe(3)
                }
            MAX-ACCESS  read-create
            STATUS      current
            DESCRIPTION
                 "The Ip mode of this voip card."
            DEFVAL { dhcp }
            ::= { zxAnEponRmVoipIpProfileEntry 4 }

    zxAnEponRmVoipIpDefaultGateWay  OBJECT-TYPE
            SYNTAX      IpAddress
            MAX-ACCESS  read-create
            STATUS      current
            DESCRIPTION
                 "If the IP mode is static, the default gateway should be configed."
            ::= { zxAnEponRmVoipIpProfileEntry 5 }

    zxAnEponRmVoipIpPrimaryDNSServerIp  OBJECT-TYPE
            SYNTAX      IpAddress
            MAX-ACCESS  read-create
            STATUS      current
            DESCRIPTION
                 "If the IP mode is static, the primary dns server should be configed."
            ::= { zxAnEponRmVoipIpProfileEntry 6 }

    zxAnEponRmVoipIpPPPoEMode  OBJECT-TYPE
            SYNTAX      INTEGER {
                auto(1),
                chap(2),
                pap(3)
                }
            MAX-ACCESS  read-create
            STATUS      current
            DESCRIPTION
                 "If the IP mode is PPPoE, the mode of PPPoE should be configed.
                  chap-Challenge Handshake Authentication Protocol;
                  pap-Password Authentication Protocol;"
            DEFVAL { auto }
            ::= { zxAnEponRmVoipIpProfileEntry 7 }

    zxAnEponRmVoipIpRowStatus  OBJECT-TYPE
            SYNTAX      RowStatus
            MAX-ACCESS  read-create
            STATUS      current
            DESCRIPTION
                 "Ip profile table RowStatus. "
            ::= { zxAnEponRmVoipIpProfileEntry 30 }

--------------------------------------------------------------------------------
-- 1.35.3 Voip VLAN profile table index next
--------------------------------------------------------------------------------
    zxAnEponRmVoipVlanProfileIdxNext OBJECT-TYPE
                SYNTAX      INTEGER
                MAX-ACCESS  read-only
                STATUS      current
                DESCRIPTION
                "Use this value as index to create an entry of zxAnEponRmVoipVlanProfileTable"
                ::= { zxAnEponRmVoipProfileMgmt 3 }

--------------------------------------------------------------------------------
-- 1.35.4 Voip VLAN profile table
--------------------------------------------------------------------------------
    zxAnEponRmVoipVlanProfileTable  OBJECT-TYPE
            SYNTAX      SEQUENCE OF ZxAnEponRmVoipVlanProfileEntry
            MAX-ACCESS  not-accessible
            STATUS      current
            DESCRIPTION
                "EPON remote management voip VLAN profile table."
            ::= {zxAnEponRmVoipProfileMgmt 4}

    zxAnEponRmVoipVlanProfileEntry  OBJECT-TYPE
            SYNTAX      ZxAnEponRmVoipVlanProfileEntry
            MAX-ACCESS  not-accessible
            STATUS      current
            DESCRIPTION
               "EPON remote management voip VLAN profile entry."
            INDEX    {zxAnEponRmVoipVlanProfileIdx }
            ::= {zxAnEponRmVoipVlanProfileTable 1}

    ZxAnEponRmVoipVlanProfileEntry ::=
            SEQUENCE {
                zxAnEponRmVoipVlanProfileIdx        INTEGER,
                zxAnEponRmVoipVlanProfileName       DisplayString,
                zxAnEponRmVoipVlanTagMode           INTEGER,
                zxAnEponRmVoipVlanTagCVlan          INTEGER,
                zxAnEponRmVoipVlanTagPriority       INTEGER,
                                zxAnEponRmVoipVlanTagSVlan          INTEGER,
                zxAnEponRmVoipVlanRowStatus         RowStatus
                }

    zxAnEponRmVoipVlanProfileIdx  OBJECT-TYPE
            SYNTAX      INTEGER
            MAX-ACCESS  not-accessible
            STATUS      current
            DESCRIPTION
                 "EPON remote management voip VLAN profile index."
            ::= { zxAnEponRmVoipVlanProfileEntry 1 }

    zxAnEponRmVoipVlanProfileName  OBJECT-TYPE
            SYNTAX      DisplayString ( SIZE(1..32) )
            MAX-ACCESS  read-create
            STATUS      current
            DESCRIPTION
                 "EPON remote management voip VLAN profile name."
            ::= { zxAnEponRmVoipVlanProfileEntry 2 }

    zxAnEponRmVoipVlanTagMode  OBJECT-TYPE
            SYNTAX      INTEGER {
                transparent(1),
                tag(2),
                vlanStacking(3)
                }
            MAX-ACCESS  read-create
            STATUS      current
            DESCRIPTION
                 "Vlan tag mode.
                  If mode is transparent, the other parameters is no use;
                  If mode is tag, CVLAN should be configed;
                  If mode is vlanStacking, all parameters should be configed."
            DEFVAL { tag }
            ::= { zxAnEponRmVoipVlanProfileEntry 3 }

    zxAnEponRmVoipVlanTagCVlan  OBJECT-TYPE
            SYNTAX      INTEGER(1..4094)
            MAX-ACCESS  read-create
            STATUS      current
            DESCRIPTION
                 "VLAN tag CVLAN."
            DEFVAL { 2 }
            ::= { zxAnEponRmVoipVlanProfileEntry 4 }

    zxAnEponRmVoipVlanTagPriority  OBJECT-TYPE
            SYNTAX      INTEGER(0..7)
            MAX-ACCESS  read-create
            STATUS      current
            DESCRIPTION
                 "VLAN tag priority."
            DEFVAL { 7 }
            ::= { zxAnEponRmVoipVlanProfileEntry 5 }

    zxAnEponRmVoipVlanTagSVlan  OBJECT-TYPE
            SYNTAX      INTEGER(1..4094)
            MAX-ACCESS  read-create
            STATUS      current
            DESCRIPTION
                 "VLAN tag SVLAN."
            ::= { zxAnEponRmVoipVlanProfileEntry 6 }

    zxAnEponRmVoipVlanRowStatus  OBJECT-TYPE
            SYNTAX      RowStatus
            MAX-ACCESS  read-create
            STATUS      current
            DESCRIPTION
                 "Vlan profile table RowStatus. "
            ::= { zxAnEponRmVoipVlanProfileEntry 30 }

--------------------------------------------------------------------------------
-- 1.35.5 Voip H.248 protocol profile table index next
--------------------------------------------------------------------------------
    zxAnEponRmVoipH248ProfileIdxNext OBJECT-TYPE
                SYNTAX      INTEGER
                MAX-ACCESS  read-only
                STATUS      current
                DESCRIPTION
                "Use this value as index to create an entry of zxAnEponRmVoipH248ProfileTable"
                ::= { zxAnEponRmVoipProfileMgmt 5 }

--------------------------------------------------------------------------------
-- 1.35.6 Voip H.248 protocol profile table
--------------------------------------------------------------------------------
    zxAnEponRmVoipH248ProfileTable  OBJECT-TYPE
            SYNTAX      SEQUENCE OF ZxAnEponRmVoipH248ProfileEntry
            MAX-ACCESS  not-accessible
            STATUS      current
            DESCRIPTION
                "EPON remote management H.248 protocol profile table."
            ::= {zxAnEponRmVoipProfileMgmt 6}

    zxAnEponRmVoipH248ProfileEntry  OBJECT-TYPE
            SYNTAX      ZxAnEponRmVoipH248ProfileEntry
            MAX-ACCESS  not-accessible
            STATUS      current
            DESCRIPTION
               "EPON remote management voip H.248 protocol profile entry."
            INDEX    {zxAnEponRmVoipH248ProfileIdx }
            ::= {zxAnEponRmVoipH248ProfileTable 1}

    ZxAnEponRmVoipH248ProfileEntry ::=
            SEQUENCE {
                zxAnEponRmVoipH248ProfileIdx        INTEGER,
                zxAnEponRmVoipH248ProfileName       DisplayString,
                zxAnEponRmVoipH248RegServerIp       IpAddress,
                zxAnEponRmVoipH248RegServerPort     INTEGER,
                zxAnEponRmVoipH248BackRegServerIp   IpAddress,
                zxAnEponRmVoipH248BackRegServerPort INTEGER,
                zxAnEponRmVoipH248RtpLinkKeptFlag   INTEGER,
                zxAnEponRmVoipH248OnuHeartbeatMode  INTEGER,
                zxAnEponRmVoipH248OnuHeartbeatCycle INTEGER,
                zxAnEponRmVoipH248OnuHeartbeatCount INTEGER,
                zxAnEponRmVoipH248MgRegMode         INTEGER,
                zxAnEponRmVoipH248MgPort            INTEGER,
                zxAnEponRmVoipH248RowStatus         RowStatus
                }

    zxAnEponRmVoipH248ProfileIdx  OBJECT-TYPE
            SYNTAX      INTEGER
            MAX-ACCESS  not-accessible
            STATUS      current
            DESCRIPTION
                 "EPON remote management voip H.248 protocol profile index."
            ::= { zxAnEponRmVoipH248ProfileEntry 1 }

    zxAnEponRmVoipH248ProfileName  OBJECT-TYPE
            SYNTAX      DisplayString ( SIZE(1..32) )
            MAX-ACCESS  read-create
            STATUS      current
            DESCRIPTION
                 "EPON remote management voip H248 profile name."
            ::= { zxAnEponRmVoipH248ProfileEntry 2 }

    zxAnEponRmVoipH248RegServerIp  OBJECT-TYPE
            SYNTAX      IpAddress
            MAX-ACCESS  read-create
            STATUS      current
            DESCRIPTION
                 "Register Server Ip."
            ::= { zxAnEponRmVoipH248ProfileEntry 3 }

    zxAnEponRmVoipH248RegServerPort  OBJECT-TYPE
            SYNTAX      INTEGER(1001..65535)
            MAX-ACCESS  read-create
            STATUS      current
            DESCRIPTION
                 "Register Server port."
            DEFVAL { 2944 }
            ::= { zxAnEponRmVoipH248ProfileEntry 4 }

    zxAnEponRmVoipH248BackRegServerIp  OBJECT-TYPE
            SYNTAX      IpAddress
            MAX-ACCESS  read-create
            STATUS      current
            DESCRIPTION
                 "Backup register Server Ip."
            ::= { zxAnEponRmVoipH248ProfileEntry 5 }

    zxAnEponRmVoipH248BackRegServerPort  OBJECT-TYPE
            SYNTAX      INTEGER(1001..65535)
            MAX-ACCESS  read-create
            STATUS      current
            DESCRIPTION
                 "Backup register Server port."
            DEFVAL { 2944 }
            ::= { zxAnEponRmVoipH248ProfileEntry 6 }

    zxAnEponRmVoipH248RtpLinkKeptFlag  OBJECT-TYPE
            SYNTAX      INTEGER {
                off(1),
                on(2)
                }
            MAX-ACCESS  read-create
            STATUS      current
            DESCRIPTION
                 "RTP link kept flag."
            DEFVAL { off }
            ::= { zxAnEponRmVoipH248ProfileEntry 7 }

    zxAnEponRmVoipH248OnuHeartbeatMode  OBJECT-TYPE
            SYNTAX      INTEGER {
                none(1),
                h248ServiceChange(2),
                h248Ctc(3)
                }
            MAX-ACCESS  read-create
            STATUS      current
            DESCRIPTION
                 "Heart beat mode.
                  None-Heart beat is closed;
                  h248ServiceChange-H.248 service change format;
                  h248Ctc-China telecom standard IT/ITO notify format."
            DEFVAL { h248Ctc }
            ::= { zxAnEponRmVoipH248ProfileEntry 8 }

    zxAnEponRmVoipH248OnuHeartbeatCycle  OBJECT-TYPE
            SYNTAX      INTEGER(10..65535)
            UNITS       "Seconds"
            MAX-ACCESS  read-create
            STATUS      current
            DESCRIPTION
                 "The cycle time of heart beat."
            DEFVAL { 60 }
            ::= { zxAnEponRmVoipH248ProfileEntry 9 }

    zxAnEponRmVoipH248OnuHeartbeatCount  OBJECT-TYPE
            SYNTAX      INTEGER(1..3)
            MAX-ACCESS  read-create
            STATUS      current
            DESCRIPTION
                 "The count of heart beat, UNIT:count."
            DEFVAL { 3 }
            ::= { zxAnEponRmVoipH248ProfileEntry 10 }

    zxAnEponRmVoipH248MgRegMode  OBJECT-TYPE
            SYNTAX      INTEGER {
                domainName(1),
                ip(2),
                deviceName(3)
                }
            MAX-ACCESS  read-create
            STATUS      current
            DESCRIPTION
                 "Media gate register mode.
                  domainName-Use domain name;
                  ip-Use IP address;
                  deviceName-Use device name."
            DEFVAL { domainName }
            ::= { zxAnEponRmVoipH248ProfileEntry 11 }

    zxAnEponRmVoipH248MgPort  OBJECT-TYPE
            SYNTAX      INTEGER(1001..65535)
            MAX-ACCESS  read-create
            STATUS      current
            DESCRIPTION
                 "Meida gate port."
            DEFVAL { 2944 }
            ::= { zxAnEponRmVoipH248ProfileEntry 12 }

    zxAnEponRmVoipH248RowStatus  OBJECT-TYPE
            SYNTAX      RowStatus
            MAX-ACCESS  read-create
            STATUS      current
            DESCRIPTION
                 "H.248 protocol profile table RowStatus. "
            ::= { zxAnEponRmVoipH248ProfileEntry 30 }

--------------------------------------------------------------------------------
-- 1.35.7 Voip MGCP protocol profile table index next
--------------------------------------------------------------------------------
    zxAnEponRmVoipMgcpProfileIdxNext OBJECT-TYPE
                SYNTAX      INTEGER
                MAX-ACCESS  read-only
                STATUS      current
                DESCRIPTION
                "Use this value as index to create an entry of zxAnEponRmVoipMgcpProfileTable"
                ::= { zxAnEponRmVoipProfileMgmt 7 }

--------------------------------------------------------------------------------
-- 1.35.8 Voip MGCP protocol profile table
--------------------------------------------------------------------------------
    zxAnEponRmVoipMgcpProfileTable  OBJECT-TYPE
            SYNTAX      SEQUENCE OF ZxAnEponRmVoipMgcpProfileEntry
            MAX-ACCESS  not-accessible
            STATUS      current
            DESCRIPTION
                "EPON remote management MGCP protocol profile table."
            ::= {zxAnEponRmVoipProfileMgmt 8}

    zxAnEponRmVoipMgcpProfileEntry  OBJECT-TYPE
            SYNTAX      ZxAnEponRmVoipMgcpProfileEntry
            MAX-ACCESS  not-accessible
            STATUS      current
            DESCRIPTION
               "EPON remote management voip MGCP protocol profile entry."
            INDEX    {zxAnEponRmVoipMgcpProfileIdx }
            ::= {zxAnEponRmVoipMgcpProfileTable 1}

    ZxAnEponRmVoipMgcpProfileEntry ::=
            SEQUENCE {
                zxAnEponRmVoipMgcpProfileIdx        INTEGER,
                zxAnEponRmVoipMgcpProfileName       DisplayString,
                                zxAnEponRmVoipMgcpRegServerIp       IpAddress,
                zxAnEponRmVoipMgcpRegServerPort     INTEGER,
                zxAnEponRmVoipMgcpBackRegServerIp   IpAddress,
                                zxAnEponRmVoipMgcpBackRegServerPort INTEGER,
                                zxAnEponRmVoipMgcpOnuHeartbeatMode  INTEGER,
                                zxAnEponRmVoipMgcpOnuHeartbeatCycle INTEGER,
                                zxAnEponRmVoipMgcpOnuHeartbeatCount INTEGER,
                                zxAnEponRmVoipMgcpMgRegMode         INTEGER,
                                zxAnEponRmVoipMgcpMgPort            INTEGER,
                zxAnEponRmVoipMgcpRowStatus         RowStatus
                }

    zxAnEponRmVoipMgcpProfileIdx  OBJECT-TYPE
            SYNTAX      INTEGER
            MAX-ACCESS  not-accessible
            STATUS      current
            DESCRIPTION
                 "EPON remote management voip MGCP protocol profile index."
            ::= { zxAnEponRmVoipMgcpProfileEntry 1 }

    zxAnEponRmVoipMgcpProfileName  OBJECT-TYPE
            SYNTAX      DisplayString ( SIZE(1..32) )
            MAX-ACCESS  read-create
            STATUS      current
            DESCRIPTION
                 "EPON remote management voip MGCP profile name."
            ::= { zxAnEponRmVoipMgcpProfileEntry 2 }

    zxAnEponRmVoipMgcpRegServerIp  OBJECT-TYPE
            SYNTAX      IpAddress
            MAX-ACCESS  read-create
            STATUS      current
            DESCRIPTION
                 "Register Server Ip."
            ::= { zxAnEponRmVoipMgcpProfileEntry 3 }

    zxAnEponRmVoipMgcpRegServerPort  OBJECT-TYPE
            SYNTAX      INTEGER(1001..65535)
            MAX-ACCESS  read-create
            STATUS      current
            DESCRIPTION
                 "Register Server port."
            DEFVAL { 2727 }
            ::= { zxAnEponRmVoipMgcpProfileEntry 4 }

    zxAnEponRmVoipMgcpBackRegServerIp  OBJECT-TYPE
            SYNTAX      IpAddress
            MAX-ACCESS  read-create
            STATUS      current
            DESCRIPTION
                 "Backup register Server Ip."
            ::= { zxAnEponRmVoipMgcpProfileEntry 5 }

    zxAnEponRmVoipMgcpBackRegServerPort  OBJECT-TYPE
            SYNTAX      INTEGER(1001..65535)
            MAX-ACCESS  read-create
            STATUS      current
            DESCRIPTION
                 "Backup register Server port."
            DEFVAL { 2727 }
            ::= { zxAnEponRmVoipMgcpProfileEntry 6 }

    zxAnEponRmVoipMgcpOnuHeartbeatMode  OBJECT-TYPE
            SYNTAX      INTEGER {
                none(1),
                mgcp(2)
                }
            MAX-ACCESS  read-create
            STATUS      current
            DESCRIPTION
                 "Heart beat mode.
                  None-Heart beat is closed;
                  mgcp-MGCP protocol format."
            DEFVAL { mgcp }
            ::= { zxAnEponRmVoipMgcpProfileEntry 7 }

    zxAnEponRmVoipMgcpOnuHeartbeatCycle  OBJECT-TYPE
            SYNTAX      INTEGER(30..3600)
            MAX-ACCESS  read-create
            STATUS      current
            DESCRIPTION
                 "The cycle time of heart beat, UNIT:second."
            DEFVAL { 30 }
            ::= { zxAnEponRmVoipMgcpProfileEntry 8 }

    zxAnEponRmVoipMgcpOnuHeartbeatCount  OBJECT-TYPE
            SYNTAX      INTEGER(1..3)
            MAX-ACCESS  read-create
            STATUS      current
            DESCRIPTION
                 "The count of heart beat, UNIT:count."
            DEFVAL { 3 }
            ::= { zxAnEponRmVoipMgcpProfileEntry 9 }

    zxAnEponRmVoipMgcpMgRegMode  OBJECT-TYPE
            SYNTAX      INTEGER {
                domainName(1),
                ip(2),
                deviceName(3)
                }
            MAX-ACCESS  read-create
            STATUS      current
            DESCRIPTION
                 "Media gate register mode.
                  domainName-Use domain name;
                  ip-Use IP address;
                  deviceName-Use device name."
            DEFVAL { domainName }
            ::= { zxAnEponRmVoipMgcpProfileEntry 10 }

    zxAnEponRmVoipMgcpMgPort  OBJECT-TYPE
            SYNTAX      INTEGER(1001..65535)
            MAX-ACCESS  read-create
            STATUS      current
            DESCRIPTION
                 "Meida gate port."
            DEFVAL { 2427 }
            ::= { zxAnEponRmVoipMgcpProfileEntry 11 }

    zxAnEponRmVoipMgcpRowStatus  OBJECT-TYPE
            SYNTAX      RowStatus
            MAX-ACCESS  read-create
            STATUS      current
            DESCRIPTION
                 "H.248 protocol profile table RowStatus. "
            ::= { zxAnEponRmVoipMgcpProfileEntry 30 }

--------------------------------------------------------------------------------
-- 1.35.9 Voip SIP protocol profile table index next
--------------------------------------------------------------------------------
    zxAnEponRmVoipSipProfileIdxNext OBJECT-TYPE
                SYNTAX      INTEGER
                MAX-ACCESS  read-only
                STATUS      current
                DESCRIPTION
                "Use this value as index to create an entry of zxAnEponRmVoipSipProfileTable"
                ::= { zxAnEponRmVoipProfileMgmt 9 }

--------------------------------------------------------------------------------
-- 1.35.10 Voip SIP protocol profile table
--------------------------------------------------------------------------------
    zxAnEponRmVoipSipProfileTable  OBJECT-TYPE
            SYNTAX      SEQUENCE OF ZxAnEponRmVoipSipProfileEntry
            MAX-ACCESS  not-accessible
            STATUS      current
            DESCRIPTION
                "EPON remote management SIP protocol profile table."
            ::= {zxAnEponRmVoipProfileMgmt 10}

    zxAnEponRmVoipSipProfileEntry  OBJECT-TYPE
            SYNTAX      ZxAnEponRmVoipSipProfileEntry
            MAX-ACCESS  not-accessible
            STATUS      current
            DESCRIPTION
               "EPON remote management voip SIP protocol profile entry."
            INDEX    {zxAnEponRmVoipSipProfileIdx }
            ::= {zxAnEponRmVoipSipProfileTable 1}

    ZxAnEponRmVoipSipProfileEntry ::=
            SEQUENCE {
                zxAnEponRmVoipSipProfileIdx             INTEGER,
                zxAnEponRmVoipSipProfileName            DisplayString,
                zxAnEponRmVoipSipMgPort                 INTEGER,
                                zxAnEponRmVoipSipRegServerIp            IpAddress,
                zxAnEponRmVoipSipRegServerPort          INTEGER,
                zxAnEponRmVoipSipBackRegServerIp        IpAddress,
                                zxAnEponRmVoipSipBackRegServerPort      INTEGER,
                                zxAnEponRmVoipSipProxyServerIp          IpAddress,
                zxAnEponRmVoipSipProxyServerPort        INTEGER,
                zxAnEponRmVoipSipBackProxyServerIp      IpAddress,
                                zxAnEponRmVoipSipBackProxyServerPort    INTEGER,
                zxAnEponRmVoipSipOutBoundServerIp       IpAddress,
                                zxAnEponRmVoipSipOutBoundServerPort     INTEGER,
                                zxAnEponRmVoipSipRegInterval            INTEGER,
                                zxAnEponRmVoipSipHeartbeatSwitch        INTEGER,
                                zxAnEponRmVoipSipHeartbeatCycle         INTEGER,
                                zxAnEponRmVoipSipHeartbeatCount         INTEGER,
                zxAnEponRmVoipSipRowStatus              RowStatus
                }

    zxAnEponRmVoipSipProfileIdx  OBJECT-TYPE
            SYNTAX      INTEGER
            MAX-ACCESS  not-accessible
            STATUS      current
            DESCRIPTION
                 "EPON remote management voip SIP protocol profile index."
            ::= { zxAnEponRmVoipSipProfileEntry 1 }

    zxAnEponRmVoipSipProfileName  OBJECT-TYPE
            SYNTAX      DisplayString ( SIZE(1..32) )
            MAX-ACCESS  read-create
            STATUS      current
            DESCRIPTION
                 "EPON remote management voip SIP profile name."
            ::= { zxAnEponRmVoipSipProfileEntry 2 }

    zxAnEponRmVoipSipMgPort  OBJECT-TYPE
            SYNTAX      INTEGER(1001..65535)
            MAX-ACCESS  read-create
            STATUS      current
            DESCRIPTION
                 "Meida gate port."
            DEFVAL { 5060 }
            ::= { zxAnEponRmVoipSipProfileEntry 3 }

    zxAnEponRmVoipSipRegServerIp  OBJECT-TYPE
            SYNTAX      IpAddress
            MAX-ACCESS  read-create
            STATUS      current
            DESCRIPTION
                 "Register Server Ip."
            ::= { zxAnEponRmVoipSipProfileEntry 4 }

    zxAnEponRmVoipSipRegServerPort  OBJECT-TYPE
            SYNTAX      INTEGER(1001..65535)
            MAX-ACCESS  read-create
            STATUS      current
            DESCRIPTION
                 "Register Server port."
            DEFVAL { 5060 }
            ::= { zxAnEponRmVoipSipProfileEntry 5 }

    zxAnEponRmVoipSipBackRegServerIp  OBJECT-TYPE
            SYNTAX      IpAddress
            MAX-ACCESS  read-create
            STATUS      current
            DESCRIPTION
                 "Backup register Server Ip."
            ::= { zxAnEponRmVoipSipProfileEntry 6 }

    zxAnEponRmVoipSipBackRegServerPort  OBJECT-TYPE
            SYNTAX      INTEGER(1001..65535)
            MAX-ACCESS  read-create
            STATUS      current
            DESCRIPTION
                 "Backup register Server port."
            DEFVAL { 5060 }
            ::= { zxAnEponRmVoipSipProfileEntry 7 }

    zxAnEponRmVoipSipProxyServerIp  OBJECT-TYPE
            SYNTAX      IpAddress
            MAX-ACCESS  read-create
            STATUS      current
            DESCRIPTION
                 "Proxy Server Ip."
            ::= { zxAnEponRmVoipSipProfileEntry 8 }

    zxAnEponRmVoipSipProxyServerPort  OBJECT-TYPE
            SYNTAX      INTEGER(1001..65535)
            MAX-ACCESS  read-create
            STATUS      current
            DESCRIPTION
                 "Proxy Server port."
            DEFVAL { 5060 }
            ::= { zxAnEponRmVoipSipProfileEntry 9 }

    zxAnEponRmVoipSipBackProxyServerIp  OBJECT-TYPE
            SYNTAX      IpAddress
            MAX-ACCESS  read-create
            STATUS      current
            DESCRIPTION
                 "Backup proxy server ip."
            ::= { zxAnEponRmVoipSipProfileEntry 10 }

    zxAnEponRmVoipSipBackProxyServerPort  OBJECT-TYPE
            SYNTAX      INTEGER(1001..65535)
            MAX-ACCESS  read-create
            STATUS      current
            DESCRIPTION
                 "Backup proxy server port."
            DEFVAL { 5060 }
            ::= { zxAnEponRmVoipSipProfileEntry 11 }

    zxAnEponRmVoipSipOutBoundServerIp  OBJECT-TYPE
            SYNTAX      IpAddress
            MAX-ACCESS  read-create
            STATUS      current
            DESCRIPTION
                 "Outbound server ip."
            ::= { zxAnEponRmVoipSipProfileEntry 12 }

    zxAnEponRmVoipSipOutBoundServerPort  OBJECT-TYPE
            SYNTAX      INTEGER(1001..65535)
            MAX-ACCESS  read-create
            STATUS      current
            DESCRIPTION
                 "Outbond server port."
            DEFVAL { 5060 }
            ::= { zxAnEponRmVoipSipProfileEntry 13 }

    zxAnEponRmVoipSipRegInterval  OBJECT-TYPE
            SYNTAX      INTEGER(0..65535)
            MAX-ACCESS  read-create
            STATUS      current
            DESCRIPTION
                 "Register interval, UNIT:second."
            DEFVAL { 3600 }
            ::= { zxAnEponRmVoipSipProfileEntry 14 }


    zxAnEponRmVoipSipHeartbeatSwitch  OBJECT-TYPE
            SYNTAX      INTEGER {
                off(1),
                on(2)
                }
            MAX-ACCESS  read-create
            STATUS      current
            DESCRIPTION
                 "Heart beat switch."
            DEFVAL { on }
            ::= { zxAnEponRmVoipSipProfileEntry 15 }

    zxAnEponRmVoipSipHeartbeatCycle  OBJECT-TYPE
            SYNTAX      INTEGER(0..65535)
            MAX-ACCESS  read-create
            STATUS      current
            DESCRIPTION
                 "The cycle of heart beat, UNIT:second."
            DEFVAL { 20 }
            ::= { zxAnEponRmVoipSipProfileEntry 16 }

    zxAnEponRmVoipSipHeartbeatCount  OBJECT-TYPE
            SYNTAX      INTEGER(1..3)
            MAX-ACCESS  read-create
            STATUS      current
            DESCRIPTION
                 "The count of heart beat, UNIT:count."
            DEFVAL { 3 }
            ::= { zxAnEponRmVoipSipProfileEntry 17 }

    zxAnEponRmVoipSipRowStatus  OBJECT-TYPE
            SYNTAX      RowStatus
            MAX-ACCESS  read-create
            STATUS      current
            DESCRIPTION
                 "SIP protocol profile table RowStatus. "
            ::= { zxAnEponRmVoipSipProfileEntry 30 }

--------------------------------------------------------------------------------
-- 1.35.11 Voip Fax protocol profile table index next
--------------------------------------------------------------------------------
    zxAnEponRmVoipFaxProfileIdxNext OBJECT-TYPE
                SYNTAX      INTEGER
                MAX-ACCESS  read-only
                STATUS      current
                DESCRIPTION
                "Use this value as index to create an entry of zxAnEponRmVoipFaxProfileTable"
                ::= { zxAnEponRmVoipProfileMgmt 11 }

--------------------------------------------------------------------------------
-- 1.35.12 Voip Fax protocol profile table
--------------------------------------------------------------------------------
    zxAnEponRmVoipFaxProfileTable  OBJECT-TYPE
            SYNTAX      SEQUENCE OF ZxAnEponRmVoipFaxProfileEntry
            MAX-ACCESS  not-accessible
            STATUS      current
            DESCRIPTION
                "EPON remote management Fax protocol profile table."
            ::= {zxAnEponRmVoipProfileMgmt 12}

    zxAnEponRmVoipFaxProfileEntry  OBJECT-TYPE
            SYNTAX      ZxAnEponRmVoipFaxProfileEntry
            MAX-ACCESS  not-accessible
            STATUS      current
            DESCRIPTION
               "EPON remote management voip Fax protocol profile entry."
            INDEX    {zxAnEponRmVoipFaxProfileIdx }
            ::= {zxAnEponRmVoipFaxProfileTable 1}

    ZxAnEponRmVoipFaxProfileEntry ::=
            SEQUENCE {
                zxAnEponRmVoipFaxProfileIdx         INTEGER,
                zxAnEponRmVoipFaxProfileName        DisplayString,
                zxAnEponRmVoipFaxMode               INTEGER,
                zxAnEponRmVoipFaxControlMode        INTEGER,
                zxAnEponRmVoipFaxRowStatus          RowStatus
                }

    zxAnEponRmVoipFaxProfileIdx  OBJECT-TYPE
            SYNTAX      INTEGER
            MAX-ACCESS  not-accessible
            STATUS      current
            DESCRIPTION
                 "EPON remote management voip Fax protocol profile index."
            ::= { zxAnEponRmVoipFaxProfileEntry 1 }

    zxAnEponRmVoipFaxProfileName  OBJECT-TYPE
            SYNTAX      DisplayString ( SIZE(1..32) )
            MAX-ACCESS  read-create
            STATUS      current
            DESCRIPTION
                 "EPON remote management voip Fax profile name."
            ::= { zxAnEponRmVoipFaxProfileEntry 2 }

    zxAnEponRmVoipFaxMode  OBJECT-TYPE
            SYNTAX      INTEGER {
                t30(1),
                t38(2)
                }
            MAX-ACCESS  read-create
            STATUS      current
            DESCRIPTION
                 "Fax mode."
            DEFVAL { t30 }
            ::= { zxAnEponRmVoipFaxProfileEntry 3 }

    zxAnEponRmVoipFaxControlMode  OBJECT-TYPE
            SYNTAX      INTEGER {
                none(1),
                rtcp(2),
                ss(3),
                autoVbd(4)
                }
            MAX-ACCESS  read-create
            STATUS      current
            DESCRIPTION
                 "Fax control mode.
                  none-No control mode;
                  rtcp-RTCP control mode;
                  ss-Software switch control mode;
                  autoVbd-Automatic VBD mode."
            DEFVAL { ss }
            ::= { zxAnEponRmVoipFaxProfileEntry 4 }

    zxAnEponRmVoipFaxRowStatus  OBJECT-TYPE
            SYNTAX      RowStatus
            MAX-ACCESS  read-create
            STATUS      current
            DESCRIPTION
                 "Fax protocol profile table RowStatus. "
            ::= { zxAnEponRmVoipFaxProfileEntry 30 }

------------------------------------------------------------------------------
-- 1.36 EPON ONU VOIP remote management(OAM)
------------------------------------------------------------------------------

    zxAnEponRmVoipMgmt                OBJECT IDENTIFIER ::= { zxAnEponOnuExtendedAttrMgmt 36}


--------------------------------------------------------------------------------
-- 1.36.1 Voip ip parameter management table
--------------------------------------------------------------------------------
    zxAnEponRmVoipIpInfoTable  OBJECT-TYPE
            SYNTAX      SEQUENCE OF ZxAnEponRmVoipIpInfoEntry
            MAX-ACCESS  not-accessible
            STATUS      current
            DESCRIPTION
                "EPON remote management ip parameter management table."
            ::= {zxAnEponRmVoipMgmt 1}

    zxAnEponRmVoipIpInfoEntry  OBJECT-TYPE
            SYNTAX      ZxAnEponRmVoipIpInfoEntry
            MAX-ACCESS  not-accessible
            STATUS      current
            DESCRIPTION
               "EPON remote management ip parameter management entry."
            INDEX    { zxAnEponOnuIfIndex,zxAnEponOnuCardIndex }
            ::= {zxAnEponRmVoipIpInfoTable 1}

    ZxAnEponRmVoipIpInfoEntry ::=
            SEQUENCE {
                zxAnEponOnuCardIndex                INTEGER,
                zxAnEponRmVoipIpAddress             IpAddress,
                zxAnEponRmVoipIpNetMask             IpAddress
                }

    zxAnEponOnuCardIndex  OBJECT-TYPE
            SYNTAX      INTEGER
            MAX-ACCESS  not-accessible
            STATUS      current
            DESCRIPTION
                 "Card number of the onu. It is 0 if onu is SFU which have no card."
            ::= { zxAnEponRmVoipIpInfoEntry 1 }

    zxAnEponRmVoipIpAddress  OBJECT-TYPE
            SYNTAX      IpAddress
            MAX-ACCESS  read-write
            STATUS      current
            DESCRIPTION
                 "Voip ipaddress of the onu(or onu card)."
            ::= { zxAnEponRmVoipIpInfoEntry 2 }

    zxAnEponRmVoipIpNetMask  OBJECT-TYPE
            SYNTAX      IpAddress
            MAX-ACCESS  read-write
            STATUS      current
            DESCRIPTION
                 "Voip net mask of the onu(or onu card)."
            ::= { zxAnEponRmVoipIpInfoEntry 3 }

--------------------------------------------------------------------------------
-- 1.36.2 Voip PPPoE parameter management table
--------------------------------------------------------------------------------

    zxAnEponRmVoipPppoeInfoTable  OBJECT-TYPE
            SYNTAX      SEQUENCE OF ZxAnEponRmVoipPppoeInfoEntry
            MAX-ACCESS  not-accessible
            STATUS      current
            DESCRIPTION
                "EPON remote management PPPoE parameter management table."
            ::= {zxAnEponRmVoipMgmt 2}

    zxAnEponRmVoipPppoeInfoEntry  OBJECT-TYPE
            SYNTAX      ZxAnEponRmVoipPppoeInfoEntry
            MAX-ACCESS  not-accessible
            STATUS      current
            DESCRIPTION
               "EPON remote management PPPoE parameter management entry."
            INDEX    { zxAnEponOnuIfIndex,zxAnEponOnuCardIndex }
            ::= {zxAnEponRmVoipPppoeInfoTable 1}

    ZxAnEponRmVoipPppoeInfoEntry ::=
            SEQUENCE {
                zxAnEponRmVoipPppoeUserName         DisplayString,
                zxAnEponRmVoipPppoePassword         DisplayString
                }

    zxAnEponRmVoipPppoeUserName  OBJECT-TYPE
            SYNTAX      DisplayString  ( SIZE ( 1 .. 32  ) )
            MAX-ACCESS  read-write
            STATUS      current
            DESCRIPTION
                 "Voip PPPoE username the onu(or onu card)."
            ::= { zxAnEponRmVoipPppoeInfoEntry 1 }

    zxAnEponRmVoipPppoePassword  OBJECT-TYPE
            SYNTAX      DisplayString  ( SIZE ( 1 .. 32  ) )
            MAX-ACCESS  read-write
            STATUS      current
            DESCRIPTION
                 "Voip PPPoE password the onu(or onu card)."
            ::= { zxAnEponRmVoipPppoeInfoEntry 2 }

--------------------------------------------------------------------------------
-- 1.36.3 Voip meida gateway domain name table
--------------------------------------------------------------------------------
    zxAnEponRmVoipH248MgcpAttrTable  OBJECT-TYPE
            SYNTAX      SEQUENCE OF ZxAnEponRmVoipH248MgcpAttrEntry
            MAX-ACCESS  not-accessible
            STATUS      current
            DESCRIPTION
                "EPON remote management voip meida gateway domain name table."
            ::= {zxAnEponRmVoipMgmt 3}

    zxAnEponRmVoipH248MgcpAttrEntry  OBJECT-TYPE
            SYNTAX      ZxAnEponRmVoipH248MgcpAttrEntry
            MAX-ACCESS  not-accessible
            STATUS      current
            DESCRIPTION
               "EPON remote management voip meida gateway domain name entry."
            INDEX    { zxAnEponOnuIfIndex,zxAnEponOnuCardIndex }
            ::= {zxAnEponRmVoipH248MgcpAttrTable 1}

    ZxAnEponRmVoipH248MgcpAttrEntry ::=
            SEQUENCE {
                zxAnEponRmVoipH248MgcpMID         DisplayString,
                zxAnEponRmVoipH248MgcpActiveMgc   INTEGER
                }

    zxAnEponRmVoipH248MgcpMID  OBJECT-TYPE
            SYNTAX      DisplayString  ( SIZE ( 1 .. 64  ) )
            MAX-ACCESS  read-write
            STATUS      current
            DESCRIPTION
                 "Voip H248 or MGCP media gateway domain name."
            ::= { zxAnEponRmVoipH248MgcpAttrEntry 1 }

    zxAnEponRmVoipH248MgcpActiveMgc  OBJECT-TYPE
            SYNTAX      INTEGER {
                secondary(1),
                primary(2)
                }
            MAX-ACCESS  read-only
            STATUS      current
            DESCRIPTION
                 "Active MGC."
            DEFVAL { primary }
            ::= { zxAnEponRmVoipH248MgcpAttrEntry 2 }

--------------------------------------------------------------------------------
-- 1.36.4 Voip H.248/MGCP user TID config table
--------------------------------------------------------------------------------
    zxAnEponRmVoipH248MgcpUserTidCfgTable  OBJECT-TYPE
            SYNTAX      SEQUENCE OF ZxAnEponRmVoipH248MgcpUserTidCfgEntry
            MAX-ACCESS  not-accessible
            STATUS      current
            DESCRIPTION
                "EPON remote management voip H.248/MGCP user TID config table."
            ::= {zxAnEponRmVoipMgmt 4}

    zxAnEponRmVoipH248MgcpUserTidCfgEntry  OBJECT-TYPE
            SYNTAX      ZxAnEponRmVoipH248MgcpUserTidCfgEntry
            MAX-ACCESS  not-accessible
            STATUS      current
            DESCRIPTION
                "EPON remote management voip H.248/MGCP user TID config entry."
            INDEX    { zxAnEponOnuIfIndex,zxAnEponOnuCardIndex,zxAnEponRmVoipH248MgcpUserTidGroupIdx }
            ::= {zxAnEponRmVoipH248MgcpUserTidCfgTable 1}

    ZxAnEponRmVoipH248MgcpUserTidCfgEntry ::=
            SEQUENCE {
                zxAnEponRmVoipH248MgcpUserTidGroupIdx       INTEGER,
                zxAnEponRmVoipH248MgcpUserTidBeginIdx       INTEGER,
                zxAnEponRmVoipH248MgcpUserTidNumber         INTEGER,
                zxAnEponRmVoipH248MgcpUserTidPrefix         DisplayString,
                zxAnEponRmVoipH248MgcpUserTidBeginDigit     DisplayString,
                zxAnEponRmVoipH248MgcpUserTidDigitAlignMode INTEGER,
                zxAnEponRmVoipH248MgcpUserTidDigitLength    INTEGER,
                zxAnEponRmVoipH248MgcpUserTidRowStatus      RowStatus
                }

    zxAnEponRmVoipH248MgcpUserTidGroupIdx  OBJECT-TYPE
            SYNTAX      INTEGER
            MAX-ACCESS  not-accessible
            STATUS      current
            DESCRIPTION
                 "User TID group index."
            ::= { zxAnEponRmVoipH248MgcpUserTidCfgEntry 1 }


    zxAnEponRmVoipH248MgcpUserTidBeginIdx  OBJECT-TYPE
            SYNTAX      INTEGER(1..255)
            MAX-ACCESS  read-create
            STATUS      current
            DESCRIPTION
                 "The begin index of this user TID group."
            ::= { zxAnEponRmVoipH248MgcpUserTidCfgEntry 2 }

    zxAnEponRmVoipH248MgcpUserTidNumber  OBJECT-TYPE
            SYNTAX      INTEGER(1..255)
            MAX-ACCESS  read-create
            STATUS      current
            DESCRIPTION
                 "The item number of this user TID group."
            ::= { zxAnEponRmVoipH248MgcpUserTidCfgEntry 3 }

    zxAnEponRmVoipH248MgcpUserTidPrefix  OBJECT-TYPE
            SYNTAX      DisplayString  ( SIZE ( 1 .. 16  ) )
            MAX-ACCESS  read-create
            STATUS      current
            DESCRIPTION
                 "The prefix of this user TID."
            ::= { zxAnEponRmVoipH248MgcpUserTidCfgEntry 4 }

    zxAnEponRmVoipH248MgcpUserTidBeginDigit  OBJECT-TYPE
            SYNTAX      DisplayString  ( SIZE ( 0 .. 5  ) )
            MAX-ACCESS  read-create
            STATUS      current
            DESCRIPTION
                 "The begin digit of this user TID."
            ::= { zxAnEponRmVoipH248MgcpUserTidCfgEntry 5 }

    zxAnEponRmVoipH248MgcpUserTidDigitAlignMode  OBJECT-TYPE
            SYNTAX      INTEGER {
                align(1),
                noAlign(2)
                }
            MAX-ACCESS  read-create
            STATUS      current
            DESCRIPTION
                 "The align mode of this user TID."
            DEFVAL { align }
            ::= { zxAnEponRmVoipH248MgcpUserTidCfgEntry 6 }

    zxAnEponRmVoipH248MgcpUserTidDigitLength  OBJECT-TYPE
            SYNTAX      INTEGER(0..5)
            MAX-ACCESS  read-create
            STATUS      current
            DESCRIPTION
                 "The digit length number of this user TID."
            ::= { zxAnEponRmVoipH248MgcpUserTidCfgEntry 7 }

    zxAnEponRmVoipH248MgcpUserTidRowStatus  OBJECT-TYPE
            SYNTAX      RowStatus
            MAX-ACCESS  read-create
            STATUS      current
            DESCRIPTION
                 "The row status of this user TID group."
            ::= { zxAnEponRmVoipH248MgcpUserTidCfgEntry 30 }

--------------------------------------------------------------------------------
-- 1.36.5 Voip H.248/MGCP rtp TID config table
--------------------------------------------------------------------------------
    zxAnEponRmVoipH248MgcpRtpTidCfgTable  OBJECT-TYPE
            SYNTAX      SEQUENCE OF ZxAnEponRmVoipH248MgcpRtpTidCfgEntry
            MAX-ACCESS  not-accessible
            STATUS      current
            DESCRIPTION
                "EPON remote management voip H.248/MGCP rtp TID config table."
            ::= {zxAnEponRmVoipMgmt 5}

    zxAnEponRmVoipH248MgcpRtpTidCfgEntry  OBJECT-TYPE
            SYNTAX      ZxAnEponRmVoipH248MgcpRtpTidCfgEntry
            MAX-ACCESS  not-accessible
            STATUS      current
            DESCRIPTION
                "EPON remote management voip H.248/MGCP rtp TID config entry."
            INDEX    { zxAnEponOnuIfIndex,zxAnEponOnuCardIndex }
            ::= {zxAnEponRmVoipH248MgcpRtpTidCfgTable 1}

    ZxAnEponRmVoipH248MgcpRtpTidCfgEntry ::=
            SEQUENCE {
                zxAnEponRmVoipH248MgcpRtpTidPrefix          DisplayString,
                zxAnEponRmVoipH248MgcpRtpTidBeginDigit      DisplayString,
                zxAnEponRmVoipH248MgcpRtpTidDigitAlignMode  INTEGER,
                zxAnEponRmVoipH248MgcpRtpTidDigitLength     INTEGER,
                zxAnEponRmVoipH248MgcpRtpTidNum             INTEGER
                }

    zxAnEponRmVoipH248MgcpRtpTidPrefix  OBJECT-TYPE
            SYNTAX      DisplayString  ( SIZE ( 1 .. 16  ) )
            MAX-ACCESS  read-write
            STATUS      current
            DESCRIPTION
                 "The prefix of this rtp TID."
            ::= { zxAnEponRmVoipH248MgcpRtpTidCfgEntry 1 }

    zxAnEponRmVoipH248MgcpRtpTidBeginDigit  OBJECT-TYPE
            SYNTAX      DisplayString  ( SIZE ( 0 .. 5  ) )
            MAX-ACCESS  read-write
            STATUS      current
            DESCRIPTION
                 "The begin digit of this rtp TID."
            ::= { zxAnEponRmVoipH248MgcpRtpTidCfgEntry 2 }

    zxAnEponRmVoipH248MgcpRtpTidDigitAlignMode  OBJECT-TYPE
            SYNTAX      INTEGER {
                align(1),
                noAlign(2)
                }
            MAX-ACCESS  read-write
            STATUS      current
            DESCRIPTION
                 "The align mode of this rtp TID."
            DEFVAL { align }
            ::= { zxAnEponRmVoipH248MgcpRtpTidCfgEntry 3 }

    zxAnEponRmVoipH248MgcpRtpTidDigitLength  OBJECT-TYPE
            SYNTAX      INTEGER(0..5)
            MAX-ACCESS  read-write
            STATUS      current
            DESCRIPTION
                 "The digit length number of this rtp TID."
            ::= { zxAnEponRmVoipH248MgcpRtpTidCfgEntry 4 }

    zxAnEponRmVoipH248MgcpRtpTidNum  OBJECT-TYPE
            SYNTAX      INTEGER(1..255)
            MAX-ACCESS  read-write
            STATUS      current
            DESCRIPTION
                 "The number of this rtp TID."
            ::= { zxAnEponRmVoipH248MgcpRtpTidCfgEntry 5 }

--------------------------------------------------------------------------------
-- 1.36.6 Voip SIP user info table
--------------------------------------------------------------------------------
    zxAnEponRmVoipSipUserCfgTable  OBJECT-TYPE
            SYNTAX      SEQUENCE OF ZxAnEponRmVoipSipUserCfgEntry
            MAX-ACCESS  not-accessible
            STATUS      current
            DESCRIPTION
                "EPON remote management voip SIP user info table."
            ::= {zxAnEponRmVoipMgmt 6}

    zxAnEponRmVoipSipUserCfgEntry  OBJECT-TYPE
            SYNTAX      ZxAnEponRmVoipSipUserCfgEntry
            MAX-ACCESS  not-accessible
            STATUS      current
            DESCRIPTION
                "EPON remote management voip SIP user info entry."
            INDEX    { zxAnEponOnuIfIndex,zxAnEponOnuCardIndex,zxAnEponOnuPortId }
            ::= {zxAnEponRmVoipSipUserCfgTable 1}

    ZxAnEponRmVoipSipUserCfgEntry ::=
            SEQUENCE {
                zxAnEponRmVoipSipUserAccount    DisplayString,
                zxAnEponRmVoipSipUserName       DisplayString,
                zxAnEponRmVoipSipUserPassword   DisplayString
                }

    zxAnEponRmVoipSipUserAccount  OBJECT-TYPE
            SYNTAX      DisplayString  ( SIZE ( 1 .. 16  ) )
            MAX-ACCESS  read-write
            STATUS      current
            DESCRIPTION
                 "The SIP user account."
            ::= { zxAnEponRmVoipSipUserCfgEntry 1 }

    zxAnEponRmVoipSipUserName  OBJECT-TYPE
            SYNTAX      DisplayString  ( SIZE ( 1 .. 32  ) )
            MAX-ACCESS  read-write
            STATUS      current
            DESCRIPTION
                 "The SIP user name."
            ::= { zxAnEponRmVoipSipUserCfgEntry 2 }

    zxAnEponRmVoipSipUserPassword  OBJECT-TYPE
            SYNTAX      DisplayString  ( SIZE ( 1 .. 16  ) )
            MAX-ACCESS  read-write
            STATUS      current
            DESCRIPTION
                 "The SIP user password."
            ::= { zxAnEponRmVoipSipUserCfgEntry 3 }

--------------------------------------------------------------------------------
-- 1.36.7 Voip card basic info table
--------------------------------------------------------------------------------
    zxAnEponRmVoipBaseInfoTable  OBJECT-TYPE
            SYNTAX      SEQUENCE OF ZxAnEponRmVoipBaseInfoEntry
            MAX-ACCESS  not-accessible
            STATUS      current
            DESCRIPTION
                "EPON remote management voip basic info table."
            ::= {zxAnEponRmVoipMgmt 7}

    zxAnEponRmVoipBaseInfoEntry  OBJECT-TYPE
            SYNTAX      ZxAnEponRmVoipBaseInfoEntry
            MAX-ACCESS  not-accessible
            STATUS      current
            DESCRIPTION
                "EPON remote management voip basic info entry."
            INDEX    { zxAnEponOnuIfIndex,zxAnEponOnuCardIndex }
            ::= {zxAnEponRmVoipBaseInfoTable 1}

    ZxAnEponRmVoipBaseInfoEntry ::=
            SEQUENCE {
                zxAnEponRmVoipMacAddress            MacAddress,
                zxAnEponRmVoipProtocolSupported     BITS,
                zxAnEponRmVoipSoftwareVersion       DisplayString,
                zxAnEponRmVoipSoftwareVersionTime   DisplayString,
                zxAnEponRmVoipUserCount             INTEGER,
                zxAnEponRmVoipProtocolUsed          INTEGER
                }

    zxAnEponRmVoipMacAddress  OBJECT-TYPE
            SYNTAX      MacAddress
            MAX-ACCESS  read-only
            STATUS      current
            DESCRIPTION
                 "The mac address of the voip card."
            ::= { zxAnEponRmVoipBaseInfoEntry 1 }

    zxAnEponRmVoipProtocolSupported  OBJECT-TYPE
            SYNTAX      BITS {
                sip(0),
                h248(1),
                mgcp(2)
                }
            MAX-ACCESS  read-only
            STATUS      current
            DESCRIPTION
                 "The supported protocol of the voip card."
            ::= { zxAnEponRmVoipBaseInfoEntry 2 }

    zxAnEponRmVoipSoftwareVersion  OBJECT-TYPE
            SYNTAX      DisplayString  ( SIZE ( 0 .. 32  ) )
            MAX-ACCESS  read-only
            STATUS      current
            DESCRIPTION
                 "The software version of the voip card."
            ::= { zxAnEponRmVoipBaseInfoEntry 3 }

    zxAnEponRmVoipSoftwareVersionTime  OBJECT-TYPE
            SYNTAX      DisplayString  ( SIZE ( 0 .. 32  ) )
            MAX-ACCESS  read-only
            STATUS      current
            DESCRIPTION
                 "The software version time of the voip card."
            ::= { zxAnEponRmVoipBaseInfoEntry 4 }

    zxAnEponRmVoipUserCount  OBJECT-TYPE
            SYNTAX      INTEGER
            MAX-ACCESS  read-only
            STATUS      current
            DESCRIPTION
                 "The max user count of this voip card."
            ::= { zxAnEponRmVoipBaseInfoEntry 5 }


    zxAnEponRmVoipProtocolUsed  OBJECT-TYPE
            SYNTAX      INTEGER {
                sip(1),
                h248(2),
                mgcp(3)
                }
            MAX-ACCESS  read-only
            STATUS      current
            DESCRIPTION
                 "The voip protocol used."
            ::= { zxAnEponRmVoipBaseInfoEntry 6 }

--------------------------------------------------------------------------------
-- 1.36.8 Voip H248/MGCP user tid info table
--------------------------------------------------------------------------------
    zxAnEponRmVoipH248MgcpUserTidInfoTable  OBJECT-TYPE
            SYNTAX      SEQUENCE OF ZxAnEponRmVoipH248MgcpUserTidInfoEntry
            MAX-ACCESS  not-accessible
            STATUS      current
            DESCRIPTION
                "EPON remote management voip H248/MGCP user tid info table."
            ::= {zxAnEponRmVoipMgmt 8}

    zxAnEponRmVoipH248MgcpUserTidInfoEntry  OBJECT-TYPE
            SYNTAX      ZxAnEponRmVoipH248MgcpUserTidInfoEntry
            MAX-ACCESS  not-accessible
            STATUS      current
            DESCRIPTION
                "EPON remote management voip H248/MGCP user tid info entry."
            INDEX    { zxAnEponOnuIfIndex,zxAnEponOnuCardIndex,zxAnEponOnuPortId }
            ::= {zxAnEponRmVoipH248MgcpUserTidInfoTable 1}

    ZxAnEponRmVoipH248MgcpUserTidInfoEntry ::=
            SEQUENCE {
                zxAnEponRmVoipH248MgcpUserTidName   DisplayString
                }

    zxAnEponRmVoipH248MgcpUserTidName  OBJECT-TYPE
            SYNTAX      DisplayString  ( SIZE ( 0 .. 32  ) )
            MAX-ACCESS  read-only
            STATUS      current
            DESCRIPTION
                 "The user tid of onu port."
            ::= { zxAnEponRmVoipH248MgcpUserTidInfoEntry 1 }

--------------------------------------------------------------------------------
-- 1.36.9 Voip H248/MGCP rtp tid info table
--------------------------------------------------------------------------------
    zxAnEponRmVoipH248MgcpRtpTidInfoTable  OBJECT-TYPE
            SYNTAX      SEQUENCE OF ZxAnEponRmVoipH248MgcpRtpTidInfoEntry
            MAX-ACCESS  not-accessible
            STATUS      current
            DESCRIPTION
                "EPON remote management voip H248/MGCP rtp tid info table."
            ::= {zxAnEponRmVoipMgmt 9}

    zxAnEponRmVoipH248MgcpRtpTidInfoEntry  OBJECT-TYPE
            SYNTAX      ZxAnEponRmVoipH248MgcpRtpTidInfoEntry
            MAX-ACCESS  not-accessible
            STATUS      current
            DESCRIPTION
                "EPON remote management voip H248/MGCP rtp tid info entry."
            INDEX    { zxAnEponOnuIfIndex,zxAnEponOnuCardIndex }
            ::= {zxAnEponRmVoipH248MgcpRtpTidInfoTable 1}

    ZxAnEponRmVoipH248MgcpRtpTidInfoEntry ::=
            SEQUENCE {
                zxAnEponRmVoipH248MgcpRtpTidNumber      INTEGER,
                zxAnEponRmVoipH248MgcpRtpTidFirstName   DisplayString
                }

    zxAnEponRmVoipH248MgcpRtpTidNumber  OBJECT-TYPE
            SYNTAX      INTEGER
            MAX-ACCESS  read-only
            STATUS      current
            DESCRIPTION
                 "The rtp tid number of onu."
            ::= { zxAnEponRmVoipH248MgcpRtpTidInfoEntry 1 }

    zxAnEponRmVoipH248MgcpRtpTidFirstName  OBJECT-TYPE
            SYNTAX      DisplayString  ( SIZE ( 0 .. 32  ) )
            MAX-ACCESS  read-only
            STATUS      current
            DESCRIPTION
                 "The first rtp tid name of onu."
            ::= { zxAnEponRmVoipH248MgcpRtpTidInfoEntry 2 }

--------------------------------------------------------------------------------
-- 1.36.10 Voip module status table
--------------------------------------------------------------------------------
    zxAnEponRmVoipModuleStatusTable  OBJECT-TYPE
            SYNTAX      SEQUENCE OF ZxAnEponRmVoipModuleStatusEntry
            MAX-ACCESS  not-accessible
            STATUS      current
            DESCRIPTION
                "EPON remote management voip operation status table."
            ::= {zxAnEponRmVoipMgmt 10}

    zxAnEponRmVoipModuleStatusEntry  OBJECT-TYPE
            SYNTAX      ZxAnEponRmVoipModuleStatusEntry
            MAX-ACCESS  not-accessible
            STATUS      current
            DESCRIPTION
                "EPON remote management voip operation status entry."
            INDEX    { zxAnEponOnuIfIndex,zxAnEponOnuCardIndex }
            ::= {zxAnEponRmVoipModuleStatusTable 1}

    ZxAnEponRmVoipModuleStatusEntry ::=
            SEQUENCE {
                zxAnEponRmVoipModuleStatus    INTEGER,
                zxAnEponRmVoipModuleAction  INTEGER
                }

    zxAnEponRmVoipModuleStatus  OBJECT-TYPE
            SYNTAX      INTEGER {
                registering(1),
                registerSuccess(2),
                fault(3),
                deregister(4),
                rebooting(5),
                other(255)
                }
            MAX-ACCESS  read-only
            STATUS      current
            DESCRIPTION
                 "The voip operation status."
            ::= { zxAnEponRmVoipModuleStatusEntry 1 }

    zxAnEponRmVoipModuleAction  OBJECT-TYPE
            SYNTAX      INTEGER {
                register(1),
                deregister(2),
                reset(3),
                restore(4)
                }
            MAX-ACCESS  read-write
            STATUS      current
            DESCRIPTION
                 "The voip module action."
            ::= { zxAnEponRmVoipModuleStatusEntry 2 }

--------------------------------------------------------------------------------
-- 1.36.11 Voip user interface status table
--------------------------------------------------------------------------------
    zxAnEponRmVoipUserIfStatusTable  OBJECT-TYPE
            SYNTAX      SEQUENCE OF ZxAnEponRmVoipUserIfStatusEntry
            MAX-ACCESS  not-accessible
            STATUS      current
            DESCRIPTION
                "EPON remote management voip user interface status table."
            ::= {zxAnEponRmVoipMgmt 11}

    zxAnEponRmVoipUserIfStatusEntry  OBJECT-TYPE
            SYNTAX      ZxAnEponRmVoipUserIfStatusEntry
            MAX-ACCESS  not-accessible
            STATUS      current
            DESCRIPTION
                "EPON remote management voip user interface status entry."
            INDEX    { zxAnEponOnuIfIndex,zxAnEponOnuCardIndex,zxAnEponOnuPortId }
            ::= {zxAnEponRmVoipUserIfStatusTable 1}

    ZxAnEponRmVoipUserIfStatusEntry ::=
            SEQUENCE {
                zxAnEponRmVoipPortOperStatus     INTEGER,
                zxAnEponRmVoipPortServiceType    INTEGER,
                zxAnEponRmVoipPortServiceState   INTEGER,
                zxAnEponRmVoipPortCodecMode      INTEGER,
                zxAnEponRmVoipPortAction         INTEGER,
                zxAnEponRmVoipPortReversalCtrl   INTEGER,
                zxAnEponRmVoipPortPcmToPktGain   Integer32,
                zxAnEponRmVoipPortPktToPcmGain   Integer32
                }

    zxAnEponRmVoipPortOperStatus  OBJECT-TYPE
            SYNTAX      INTEGER {
                registering(1),
                idle(2),
                hold(3),
                dialing(4),
                ringing(5),
                ringingBack(6),
                connecting(7),
                connected(8),
                releasing(9),
                busy(10),
                registerFail(11),
                deactive(12)
                }
            MAX-ACCESS  read-only
            STATUS      current
            DESCRIPTION
                 "The voip port operation status."
            ::= { zxAnEponRmVoipUserIfStatusEntry 1 }

    zxAnEponRmVoipPortServiceType  OBJECT-TYPE
            SYNTAX      INTEGER {
                normal(1),
                innerSpc(2),
                ipSpc(3),
                notInService(4),
                notSupport(5)
                }
            MAX-ACCESS  read-only
            STATUS      current
            DESCRIPTION
                 "The voip port service type.The enum value 1 to 4 used for
                 ZTE ONU, and 5 used for other vendor's ONU."
            ::= { zxAnEponRmVoipUserIfStatusEntry 2 }

    zxAnEponRmVoipPortServiceState  OBJECT-TYPE
            SYNTAX      INTEGER {
                endLocal(1),
                endRemote(2),
                endAuto(3),
                normalState(4)
                }
            MAX-ACCESS  read-only
            STATUS      current
            DESCRIPTION
                 "The voip port service state."
            ::= { zxAnEponRmVoipUserIfStatusEntry 3 }

    zxAnEponRmVoipPortCodecMode  OBJECT-TYPE
            SYNTAX      INTEGER {
                g711U(1),
                g711A(2),
                g723(3),
                g729(4),
                g726(5),
                t38(6),
                connectionless(7),
                other(8)
                }
            MAX-ACCESS  read-only
            STATUS      current
            DESCRIPTION
                 "The voip port service state."
            ::= { zxAnEponRmVoipUserIfStatusEntry 4 }

    zxAnEponRmVoipPortAction  OBJECT-TYPE
            SYNTAX      INTEGER {
                register(1),
                deregister(2)
                }
            MAX-ACCESS  read-write
            STATUS      current
            DESCRIPTION
                 "The voip port action."
            ::= { zxAnEponRmVoipUserIfStatusEntry 5 }

    zxAnEponRmVoipPortReversalCtrl  OBJECT-TYPE
            SYNTAX        INTEGER
            {
                enable(1),
                disable(2)
            }
            MAX-ACCESS    read-write
            STATUS        current
            DESCRIPTION   "Polarity Reversal Control"
            DEFVAL { disable }
            ::= { zxAnEponRmVoipUserIfStatusEntry 6 }

    zxAnEponRmVoipPortPcmToPktGain  OBJECT-TYPE
            SYNTAX        Integer32
            MAX-ACCESS    read-write
            STATUS        current
            DESCRIPTION   "PCM To Packet Gain (dB), The Display Range is -20~20"
            ::= { zxAnEponRmVoipUserIfStatusEntry 7 }

    zxAnEponRmVoipPortPktToPcmGain  OBJECT-TYPE
            SYNTAX        Integer32
            MAX-ACCESS    read-write
            STATUS        current
            DESCRIPTION   "Packet To PCM Gain (dB), The Display Range is -20~20"
            ::= { zxAnEponRmVoipUserIfStatusEntry 8 }

--------------------------------------------------------------------------------
-- 1.36.12 Voip profile apply table
--------------------------------------------------------------------------------
    zxAnEponRmVoipProfileApplyTable  OBJECT-TYPE
            SYNTAX      SEQUENCE OF ZxAnEponRmVoipProfileApplyEntry
            MAX-ACCESS  not-accessible
            STATUS      current
            DESCRIPTION
                "EPON remote management voip profile apply table."
            ::= {zxAnEponRmVoipMgmt 12}

    zxAnEponRmVoipProfileApplyEntry  OBJECT-TYPE
            SYNTAX      ZxAnEponRmVoipProfileApplyEntry
            MAX-ACCESS  not-accessible
            STATUS      current
            DESCRIPTION
                "EPON remote management voip profile apply entry."
            INDEX    { zxAnEponOnuIfIndex }
            ::= {zxAnEponRmVoipProfileApplyTable 1}

    ZxAnEponRmVoipProfileApplyEntry ::=
            SEQUENCE {
                zxAnEponRmVoipCurrIpProfileIdx          INTEGER,
                zxAnEponRmVoipCurrVlanProfileIdx        INTEGER,
                zxAnEponRmVoipCurrProtocolProfileType   INTEGER,
                zxAnEponRmVoipCurrProtocolProfileIdx    INTEGER,
                zxAnEponRmVoipCurrFaxProfileIdx         INTEGER
                }

    zxAnEponRmVoipCurrIpProfileIdx  OBJECT-TYPE
            SYNTAX      INTEGER
            MAX-ACCESS  read-write
            STATUS      current
            DESCRIPTION
                 "The voip ip profile index."
            ::= { zxAnEponRmVoipProfileApplyEntry 1 }

    zxAnEponRmVoipCurrVlanProfileIdx  OBJECT-TYPE
            SYNTAX      INTEGER
            MAX-ACCESS  read-write
            STATUS      current
            DESCRIPTION
                 "The voip VLAN profile index."
            ::= { zxAnEponRmVoipProfileApplyEntry 2 }

    zxAnEponRmVoipCurrProtocolProfileType  OBJECT-TYPE
            SYNTAX      INTEGER {
                sip(1),
                h248(2),
                mgcp(3)
                }
            MAX-ACCESS  read-write
            STATUS      current
            DESCRIPTION
                 "The voip protocol profile type."
            ::= { zxAnEponRmVoipProfileApplyEntry 3 }

    zxAnEponRmVoipCurrProtocolProfileIdx  OBJECT-TYPE
            SYNTAX      INTEGER
            MAX-ACCESS  read-write
            STATUS      current
            DESCRIPTION
                 "The voip protocol profile index."
            ::= { zxAnEponRmVoipProfileApplyEntry 4 }

    zxAnEponRmVoipCurrFaxProfileIdx  OBJECT-TYPE
            SYNTAX      INTEGER
            MAX-ACCESS  read-write
            STATUS      current
            DESCRIPTION
                 "The voip fax profile index."
            ::= { zxAnEponRmVoipProfileApplyEntry 5 }

--------------------------------------------------------------------------------
-- 1.36.13 Voip SIP attribute table
--------------------------------------------------------------------------------
    zxAnEponRmVoipSipAttrTable  OBJECT-TYPE
            SYNTAX      SEQUENCE OF ZxAnEponRmVoipSipAttrEntry
            MAX-ACCESS  not-accessible
            STATUS      current
            DESCRIPTION
                "EPON remote management voip SIP attribute table."
            ::= {zxAnEponRmVoipMgmt 13}

    zxAnEponRmVoipSipAttrEntry  OBJECT-TYPE
            SYNTAX      ZxAnEponRmVoipSipAttrEntry
            MAX-ACCESS  not-accessible
            STATUS      current
            DESCRIPTION
                "EPON remote management voip SIP attribute entry."
            INDEX    { zxAnEponOnuIfIndex,zxAnEponOnuCardIndex }
            ::= {zxAnEponRmVoipSipAttrTable 1}

    ZxAnEponRmVoipSipAttrEntry ::=
            SEQUENCE {
                zxAnEponRmVoipSipActiveProxyServer         INTEGER
                }

    zxAnEponRmVoipSipActiveProxyServer  OBJECT-TYPE
            SYNTAX      INTEGER{
                secondary(1),
                primary(2)
                }
            MAX-ACCESS  read-only
            STATUS      current
            DESCRIPTION
                 "The active proxy server."
            ::= { zxAnEponRmVoipSipAttrEntry 1 }

--------------------------------------------------------------------------------
-- 1.36.14 Voip SIP attribute table
--------------------------------------------------------------------------------
    zxAnEponRmVoipSipDigitMapTable  OBJECT-TYPE
            SYNTAX      SEQUENCE OF ZxAnEponRmVoipSipDigitMapEntry
            MAX-ACCESS  not-accessible
            STATUS      current
            DESCRIPTION
                "EPON remote management voip SIP DigitMap table."
            ::= {zxAnEponRmVoipMgmt 14}

    zxAnEponRmVoipSipDigitMapEntry  OBJECT-TYPE
            SYNTAX      ZxAnEponRmVoipSipDigitMapEntry
            MAX-ACCESS  not-accessible
            STATUS      current
            DESCRIPTION
                "EPON remote management voip SIP DigitMap entry."
            INDEX    { zxAnEponOnuIfIndex, zxAnEponOnuCardIndex }
            ::= {zxAnEponRmVoipSipDigitMapTable 1}

    ZxAnEponRmVoipSipDigitMapEntry ::=
            SEQUENCE {
                zxEponRmVoipSipDigitMap         DisplayString
                }

    zxEponRmVoipSipDigitMap  OBJECT-TYPE
            SYNTAX      DisplayString( SIZE(1..1024) )
            MAX-ACCESS  read-write
            STATUS      current
            DESCRIPTION
                 "voip SIP DigitMap entry"
            ::= { zxAnEponRmVoipSipDigitMapEntry 1 }

--------------------------------------------------------------------------------
-- 1.36.15 Voip present call number table
--------------------------------------------------------------------------------
    zxAnEponOnuVoipPresentingTable  OBJECT-TYPE
            SYNTAX      SEQUENCE OF ZxAnEponOnuVoipPresentingEntry
            MAX-ACCESS  not-accessible
            STATUS      current
            DESCRIPTION
                "EPON remote management voip present table."
            ::= {zxAnEponRmVoipMgmt 15}

    zxAnEponOnuVoipPresentingEntry  OBJECT-TYPE
            SYNTAX      ZxAnEponOnuVoipPresentingEntry
            MAX-ACCESS  not-accessible
            STATUS      current
            DESCRIPTION
                "EPON remote management voip present entry."
            INDEX    { zxAnEponOnuIfIndex,zxAnEponOnuCardIndex,zxAnEponOnuPortId }
            ::= {zxAnEponOnuVoipPresentingTable 1}

    ZxAnEponOnuVoipPresentingEntry ::=
            SEQUENCE {
                zxAnEponOnuVoipPresentingCallNbrState            INTEGER,
                zxAnEponOnuVoipPresentingCallNbrType             INTEGER
                }

    zxAnEponOnuVoipPresentingCallNbrState  OBJECT-TYPE
            SYNTAX      INTEGER {
                disable(1),
                enable(2)
                }
            MAX-ACCESS  read-write
            STATUS      current
            DESCRIPTION
                 "voip present call number state entry"
            ::= { zxAnEponOnuVoipPresentingEntry 1 }

    zxAnEponOnuVoipPresentingCallNbrType  OBJECT-TYPE
            SYNTAX      INTEGER {
                fsk(1),
                dtmf(2)
                }
            MAX-ACCESS  read-write
            STATUS      current
            DESCRIPTION
                 "voip present call type entry"
            ::= { zxAnEponOnuVoipPresentingEntry 2 }

--------------------------------------------------------------------------------
-- 1.36.16 Voip timer config table
--------------------------------------------------------------------------------
    zxAnEponOnuVoipTimerConfigTable  OBJECT-TYPE
            SYNTAX      SEQUENCE OF ZxAnEponOnuVoipTimerConfigEntry
            MAX-ACCESS  not-accessible
            STATUS      current
            DESCRIPTION
                "EPON remote management voip timer config table."
            ::= {zxAnEponRmVoipMgmt 16}

    zxAnEponOnuVoipTimerConfigEntry  OBJECT-TYPE
            SYNTAX      ZxAnEponOnuVoipTimerConfigEntry
            MAX-ACCESS  not-accessible
            STATUS      current
            DESCRIPTION
                "EPON remote management voip timer config entry."
            INDEX    { zxAnEponOnuIfIndex, zxAnEponOnuCardIndex }
            ::= {zxAnEponOnuVoipTimerConfigTable 1}

    ZxAnEponOnuVoipTimerConfigEntry ::=
            SEQUENCE {
                zxAnEponOnuVoipTimerConfigDml         INTEGER,
                zxAnEponOnuVoipTimerConfigDms         INTEGER
                }

    zxAnEponOnuVoipTimerConfigDml  OBJECT-TYPE
            SYNTAX      INTEGER(1..60)
            MAX-ACCESS  read-write
            STATUS      current
            DESCRIPTION
                 "voip timer config DML entry"
            DEFVAL { 5 }
            ::= { zxAnEponOnuVoipTimerConfigEntry 1 }

    zxAnEponOnuVoipTimerConfigDms  OBJECT-TYPE
            SYNTAX      INTEGER(1..60)
            MAX-ACCESS  read-write
            STATUS      current
            DESCRIPTION
                 "voip timer config DMS entry"
            DEFVAL { 2 }
            ::= { zxAnEponOnuVoipTimerConfigEntry 2 }

--------------------------------------------------------------------------------
-- 1.36.17 Voip Statistics Table
--------------------------------------------------------------------------------
    zxAnEponOnuVoipStatsTable  OBJECT-TYPE
            SYNTAX      SEQUENCE OF ZxAnEponOnuVoipStatsEntry
            MAX-ACCESS  not-accessible
            STATUS      current
            DESCRIPTION
                "EPON Remote Management Voip Statistics Table"
            ::= {zxAnEponRmVoipMgmt 17}

    zxAnEponOnuVoipStatsEntry  OBJECT-TYPE
            SYNTAX      ZxAnEponOnuVoipStatsEntry
            MAX-ACCESS  not-accessible
            STATUS      current
            DESCRIPTION
                "EPON Remote Management Voip Statistics Entry"
            INDEX
                { zxAnEponOnuIfIndex, zxAnEponOnuCardIndex ,zxAnEponOnuPortId}
            ::= {zxAnEponOnuVoipStatsTable 1}

    ZxAnEponOnuVoipStatsEntry ::=
            SEQUENCE {
                zxAnEponOnuVoipRxPkts                Counter64,
                zxAnEponOnuVoipTxPkts                Counter64,
                zxAnEponOnuVoipAverageDelay          INTEGER,
                zxAnEponOnuVoipAverageJitter         INTEGER,
                zxAnEponOnuVoipLoss                  INTEGER,
                zxAnEponRmUniVoipRxMediaDataRate     Gauge32,
                zxAnEponRmUniVoipTxMediaDataRate     Gauge32,
                zxAnEponRmUniVoipCurCallDuration     Unsigned32,
                zxAnEponRmUniVoipTotCallDuration     Unsigned32,
                zxAnEponRmUniVoipCallTimes           Unsigned32
                }

    zxAnEponOnuVoipRxPkts  OBJECT-TYPE
            SYNTAX      Counter64
            MAX-ACCESS  read-only
            STATUS      current
            DESCRIPTION
                 "Received Packets"
            ::= { zxAnEponOnuVoipStatsEntry 1 }

    zxAnEponOnuVoipTxPkts  OBJECT-TYPE
            SYNTAX      Counter64
            MAX-ACCESS  read-only
            STATUS      current
            DESCRIPTION
                 "Transmitted Packets"
            ::= { zxAnEponOnuVoipStatsEntry 2 }

    zxAnEponOnuVoipAverageDelay  OBJECT-TYPE
            SYNTAX      INTEGER (0 .. 65535)
            MAX-ACCESS  read-only
            STATUS      current
            DESCRIPTION
                 "Average Delay (ms)"
            ::= { zxAnEponOnuVoipStatsEntry 3 }

    zxAnEponOnuVoipAverageJitter  OBJECT-TYPE
            SYNTAX      INTEGER (0 .. 65535)
            MAX-ACCESS  read-only
            STATUS      current
            DESCRIPTION
                 "Average Jitter (ms)"
            ::= { zxAnEponOnuVoipStatsEntry 4 }

    zxAnEponOnuVoipLoss  OBJECT-TYPE
            SYNTAX      INTEGER (0 .. 100)
            MAX-ACCESS  read-only
            STATUS      current
            DESCRIPTION
                 "Packet Loss Ratio (%)"
            ::= { zxAnEponOnuVoipStatsEntry 5 }

    zxAnEponRmUniVoipRxMediaDataRate  OBJECT-TYPE
            SYNTAX      Gauge32
            UNITS       "kbps"
            MAX-ACCESS  read-only
            STATUS      current
            DESCRIPTION
                 "This attribute identifies received rate of media data."
            ::= { zxAnEponOnuVoipStatsEntry 6 }

    zxAnEponRmUniVoipTxMediaDataRate  OBJECT-TYPE
            SYNTAX      Gauge32
            UNITS       "kbps"
            MAX-ACCESS  read-only
            STATUS      current
            DESCRIPTION
                 "This attribute identifies transmitted rate of media data."
            ::= { zxAnEponOnuVoipStatsEntry 7 }

    zxAnEponRmUniVoipCurCallDuration  OBJECT-TYPE
            SYNTAX      Unsigned32
            UNITS       "Seconds"
            MAX-ACCESS  read-only
            STATUS      current
            DESCRIPTION
                 "This attribute identifies the duration of current call in
                 seconds."
            ::= { zxAnEponOnuVoipStatsEntry 8 }

    zxAnEponRmUniVoipTotCallDuration  OBJECT-TYPE
            SYNTAX      Unsigned32
            UNITS       "Seconds"
            MAX-ACCESS  read-only
            STATUS      current
            DESCRIPTION
                 "This attribute identifies the duration of total calls in
                 seconds."
            ::= { zxAnEponOnuVoipStatsEntry 9 }

    zxAnEponRmUniVoipCallTimes  OBJECT-TYPE
            SYNTAX      Unsigned32
            MAX-ACCESS  read-only
            STATUS      current
            DESCRIPTION
                 "This attribute identifies the total number of call times."
            ::= { zxAnEponOnuVoipStatsEntry 10 }

--------------------------------------------------------------------------------
-- 1.36.18 Voip Other Config Table
--------------------------------------------------------------------------------
    zxAnEponOnuVoipOtherConfigTable  OBJECT-TYPE
            SYNTAX          SEQUENCE OF ZxAnEponOnuVoipOtherConfigEntry
            MAX-ACCESS      not-accessible
            STATUS          current
            DESCRIPTION     "EPON remote management Voip Other Config Table"
            ::= {zxAnEponRmVoipMgmt 18}

    zxAnEponOnuVoipOtherConfigEntry  OBJECT-TYPE
            SYNTAX          ZxAnEponOnuVoipOtherConfigEntry
            MAX-ACCESS      not-accessible
            STATUS          current
            DESCRIPTION     "EPON remote management Voip Other Config Entry."
            INDEX    { zxAnEponOnuIfIndex, zxAnEponOnuCardIndex }
            ::= {zxAnEponOnuVoipOtherConfigTable 1}

    ZxAnEponOnuVoipOtherConfigEntry ::=
            SEQUENCE {
                zxAnEponOnuVoipComfortableNoise           INTEGER,
                zxAnEponOnuVoipSilenceDetection           INTEGER,
                zxAnEponOnuVoipEchoCanceller              INTEGER,
                zxAnEponOnuVoipDtmpTransferMode           INTEGER
                }

    zxAnEponOnuVoipComfortableNoise  OBJECT-TYPE
            SYNTAX        INTEGER
            {
                enable(1),
                disable(2)
            }
            MAX-ACCESS      read-write
            STATUS          current
            DESCRIPTION     "Comfortable Noise"
            DEFVAL          { disable }
            ::= { zxAnEponOnuVoipOtherConfigEntry 1 }

     zxAnEponOnuVoipSilenceDetection  OBJECT-TYPE
            SYNTAX        INTEGER
            {
                enable(1),
                disable(2)
            }
            MAX-ACCESS      read-write
            STATUS          current
            DESCRIPTION     "Silence Detection"
            DEFVAL          { disable }
            ::= { zxAnEponOnuVoipOtherConfigEntry 2 }

    zxAnEponOnuVoipEchoCanceller  OBJECT-TYPE
            SYNTAX        INTEGER
            {
                enable(1),
                disable(2)
            }
            MAX-ACCESS      read-write
            STATUS          current
            DESCRIPTION     "Echo Canceller"
            DEFVAL          { disable }
            ::= { zxAnEponOnuVoipOtherConfigEntry 3 }

    zxAnEponOnuVoipDtmpTransferMode  OBJECT-TYPE
            SYNTAX         INTEGER
            {
                voiceCoding(1),
                nredRfc2833(2),
                redRfc2833(3),
                aal2OrIetf(4),
                noForwarding(5)
            }
            MAX-ACCESS     read-write
            STATUS         current
            DESCRIPTION    "DTMF Transfer Mode"
            ::= { zxAnEponOnuVoipOtherConfigEntry 4 }

--------------------------------------------------------------------------------
-- 1.36.19 zxAnEponRmOnuVoipSrvPerfTable
--------------------------------------------------------------------------------
    zxAnEponRmOnuVoipSrvPerfTable  OBJECT-TYPE
            SYNTAX      SEQUENCE OF ZxAnEponRmOnuVoipSrvPerfEntry
            MAX-ACCESS  not-accessible
            STATUS      current
            DESCRIPTION
                "Performance monitoring data related to the VoIP service of
                ONU."
            ::= {zxAnEponRmVoipMgmt 19}

    zxAnEponRmOnuVoipSrvPerfEntry  OBJECT-TYPE
            SYNTAX      ZxAnEponRmOnuVoipSrvPerfEntry
            MAX-ACCESS  not-accessible
            STATUS      current
            DESCRIPTION
                "It is entry in the zxAnEponRmOnuVoipSrvPerfTable."
            INDEX
                { zxAnEponOnuIfIndex}
            ::= {zxAnEponRmOnuVoipSrvPerfTable 1}

    ZxAnEponRmOnuVoipSrvPerfEntry ::=
            SEQUENCE {
                zxAnEponRmOnuVoipRxSignalMsg         Counter64,
                zxAnEponRmOnuVoipTxSignalMsg         Counter64,
                zxAnEponRmOnuVoipLossSignalMsg       Counter32,
                zxAnEponRmOnuVoipReTxSignalMsg       Counter32,
                zxAnEponRmOnuVoipErrSignalMsg        Counter32,
                zxAnEponRmOnuVoipUnknowSignalMsg     Counter32
                }

    zxAnEponRmOnuVoipRxSignalMsg  OBJECT-TYPE
            SYNTAX      Counter64
            MAX-ACCESS  read-only
            STATUS      current
            DESCRIPTION
                 "This attribute identifies the total number of received
                 signalling messages."
            ::= { zxAnEponRmOnuVoipSrvPerfEntry 1 }

    zxAnEponRmOnuVoipTxSignalMsg  OBJECT-TYPE
            SYNTAX      Counter64
            MAX-ACCESS  read-only
            STATUS      current
            DESCRIPTION
                 "This attribute identifies the total number of transmitted
                 signalling messages."
            ::= { zxAnEponRmOnuVoipSrvPerfEntry 2 }

    zxAnEponRmOnuVoipLossSignalMsg  OBJECT-TYPE
            SYNTAX      Counter32
            MAX-ACCESS  read-only
            STATUS      current
            DESCRIPTION
                 "This attribute identifies the total number of lost signalling
                 messages."
            ::= { zxAnEponRmOnuVoipSrvPerfEntry 3 }

    zxAnEponRmOnuVoipReTxSignalMsg  OBJECT-TYPE
            SYNTAX      Counter32
            MAX-ACCESS  read-only
            STATUS      current
            DESCRIPTION
                 "This attribute identifies the number of retransmitted
                 signalling messages."
            ::= { zxAnEponRmOnuVoipSrvPerfEntry 4 }

    zxAnEponRmOnuVoipErrSignalMsg  OBJECT-TYPE
            SYNTAX      Counter32
            MAX-ACCESS  read-only
            STATUS      current
            DESCRIPTION
                 "This attribute identifies the total number of errored
                 signalling messages."
            ::= { zxAnEponRmOnuVoipSrvPerfEntry 5 }

    zxAnEponRmOnuVoipUnknowSignalMsg  OBJECT-TYPE
            SYNTAX      Counter32
            MAX-ACCESS  read-only
            STATUS      current
            DESCRIPTION
                 "This attribute identifies the total number of unknown
                 signalling messages."
            ::= { zxAnEponRmOnuVoipSrvPerfEntry 6 }

--------------------------------------------------------------------------------
-- 1.37 Onu capability extended table
--------------------------------------------------------------------------------
    zxAnEponOnuCapabilityExtTable  OBJECT-TYPE
            SYNTAX      SEQUENCE OF ZxAnEponOnuCapabilityExtEntry
            MAX-ACCESS  not-accessible
            STATUS      current
            DESCRIPTION
                "EPON remote management ONU capability extended table."
            ::= {zxAnEponOnuExtendedAttrMgmt 37}

    zxAnEponOnuCapabilityExtEntry  OBJECT-TYPE
            SYNTAX      ZxAnEponOnuCapabilityExtEntry
            MAX-ACCESS  not-accessible
            STATUS      current
            DESCRIPTION
                "EPON remote management ONU capability extended entry."
            INDEX    { zxAnEponOnuIfIndex }
            ::= {zxAnEponOnuCapabilityExtTable 1}

    ZxAnEponOnuCapabilityExtEntry ::=
            SEQUENCE {
                zxAnEponOnuType                         INTEGER,
                zxAnEponOnuMultiLlid                    INTEGER,
                zxAnEponOnuProtection                   INTEGER,
                zxAnEponOnuPonPorts                     INTEGER,
                zxAnEponOnuSlots                        INTEGER,
                zxAnEponOnuBatteryBackupStatus          INTEGER,
                zxAnEponOnuIsSupportIpv6                INTEGER,
                zxAnEponOnuPwrSdSupportMode             INTEGER,
                zxAnEponOnuSlaNumber                    Integer32
                }

    zxAnEponOnuType  OBJECT-TYPE
            SYNTAX      INTEGER {
                sfu(1),
                hgu(2),
                sbu(3),
                ethMduCompactBox(4),
                ethMduCards(5),
                dslMduCardsCompactBox(6),
                dslMduCardsRack(7),
                bybridMduCards(8),
                mtu(9)
                }
            MAX-ACCESS  read-only
            STATUS      current
            DESCRIPTION
                 "Service type of the ONU."
            DEFVAL  {sfu}
            ::= { zxAnEponOnuCapabilityExtEntry 1 }

    zxAnEponOnuMultiLlid  OBJECT-TYPE
            SYNTAX      INTEGER(0..8)
            MAX-ACCESS  read-only
            STATUS      current
            DESCRIPTION
                 "LLID number of the onu."
            ::= { zxAnEponOnuCapabilityExtEntry 2 }

    zxAnEponOnuProtection  OBJECT-TYPE
            SYNTAX      INTEGER {
                notSupport(1),
                typeC(2),
                typeD(3)
                }
            MAX-ACCESS  read-only
            STATUS      current
            DESCRIPTION
                 "Protect type of the ONU."
            DEFVAL  {notSupport}
            ::= { zxAnEponOnuCapabilityExtEntry 3 }

    zxAnEponOnuPonPorts  OBJECT-TYPE
            SYNTAX      INTEGER
            MAX-ACCESS  read-only
            STATUS      current
            DESCRIPTION
                 "PON interface number of the ONU."
            ::= { zxAnEponOnuCapabilityExtEntry 4 }

    zxAnEponOnuSlots  OBJECT-TYPE
            SYNTAX      INTEGER
            MAX-ACCESS  read-only
            STATUS      current
            DESCRIPTION
                 "Slot number of the ONU."
            ::= { zxAnEponOnuCapabilityExtEntry 5 }

    zxAnEponOnuBatteryBackupStatus  OBJECT-TYPE
            SYNTAX      INTEGER{
                noBatteryBackup(1),
                batteryBackup(2)
                }
            MAX-ACCESS  read-only
            STATUS      current
            DESCRIPTION
                 "Battery backup mode of the ONU."
            ::= { zxAnEponOnuCapabilityExtEntry 6 }

     zxAnEponOnuIsSupportIpv6  OBJECT-TYPE
        SYNTAX      INTEGER{
                supported(1),
                unsupported(2)
                }
        MAX-ACCESS  read-only
        STATUS      current
        DESCRIPTION
            "ONU supports IPv6 function whether or not."
        ::= { zxAnEponOnuCapabilityExtEntry 7 }

    zxAnEponOnuPwrSdSupportMode  OBJECT-TYPE
        SYNTAX      INTEGER {
            unsupported(1),
            supportTx(2),
            supportTrx(3)
            }
        MAX-ACCESS  read-only
        STATUS      current
        DESCRIPTION
             "ONU power shutting down supporting mode. When OLT detected
              the rogue ONU, OLT would shut down the rogue ONU.
              Rogue ONU can be shut down whether or not, depending on this
              capability of the ONU.
              Value are defined as follows:
             1  Unsupported.
             2  Only supports transmitting mode.
             3  Supports transmitting and receiving mode at
                the same time."
        ::= { zxAnEponOnuCapabilityExtEntry 8 }

    zxAnEponOnuSlaNumber  OBJECT-TYPE
        SYNTAX       Integer32(1..8)
        MAX-ACCESS  read-only
        STATUS      current
        DESCRIPTION
             "The SLA(service level agreement) service number,
              value '1' represents not supporting SLA."
        ::= { zxAnEponOnuCapabilityExtEntry 9 }
--------------------------------------------------------------------------------
-- 1.38 Onu interface table
--------------------------------------------------------------------------------
    zxAnEponOnuInterfaceTable  OBJECT-TYPE
            SYNTAX      SEQUENCE OF ZxAnEponOnuInterfaceEntry
            MAX-ACCESS  not-accessible
            STATUS      current
            DESCRIPTION
                "EPON remote management ONU capability extended table."
            ::= {zxAnEponOnuExtendedAttrMgmt 38}

    zxAnEponOnuInterfaceEntry  OBJECT-TYPE
            SYNTAX      ZxAnEponOnuInterfaceEntry
            MAX-ACCESS  not-accessible
            STATUS      current
            DESCRIPTION
                "EPON remote management ONU capability extended entry."
            INDEX    { zxAnEponOnuIfIndex,zxAnEponOnuInterfaceType }
            ::= {zxAnEponOnuInterfaceTable 1}

    ZxAnEponOnuInterfaceEntry ::=
            SEQUENCE {
                zxAnEponOnuInterfaceType                INTEGER,
                zxAnEponOnuInterfaceNum                 INTEGER
                }

    zxAnEponOnuInterfaceType  OBJECT-TYPE
            SYNTAX      INTEGER {
                ge(1),
                fe(2),
                voip(3),
                tdm(4),
                adsl2Plus(5),
                vdsl2(6),
                wlan(7),
                usb(8),
                catvRf(9)
                }
            MAX-ACCESS  read-only
            STATUS      current
            DESCRIPTION
                 "Interface type of the ONU."
            ::= { zxAnEponOnuInterfaceEntry 1 }

    zxAnEponOnuInterfaceNum  OBJECT-TYPE
            SYNTAX      INTEGER
            MAX-ACCESS  read-only
            STATUS      current
            DESCRIPTION
                 "Interface number."
            ::= { zxAnEponOnuInterfaceEntry 2 }

--------------------------------------------------------------------------------
-- 1.39 MDU/MTU card operation table
--------------------------------------------------------------------------------
    zxAnEponMduCardTable  OBJECT-TYPE
            SYNTAX      SEQUENCE OF ZxAnEponMduCardEntry
            MAX-ACCESS  not-accessible
            STATUS      current
            DESCRIPTION
                "EPON remote management card operation table."
            ::= {zxAnEponOnuExtendedAttrMgmt 39}

    zxAnEponMduCardEntry  OBJECT-TYPE
            SYNTAX      ZxAnEponMduCardEntry
            MAX-ACCESS  not-accessible
            STATUS      current
            DESCRIPTION
                "EPON remote management card operation entry."
            INDEX    { zxAnEponOnuIfIndex,zxAnEponOnuCardIndex }
            ::= {zxAnEponMduCardTable 1}

    ZxAnEponMduCardEntry ::=
            SEQUENCE {
                zxAnEponMduCardOperStatus   INTEGER,
                zxAnEponMduCardAdminStatus  INTEGER
                }

    zxAnEponMduCardOperStatus  OBJECT-TYPE
            SYNTAX      INTEGER
                {
                 inService   (1),
                 notInService(2),
                 hwOnline(3),
                 hwOffline(4),
                 configuring(5),
                 configFailed(6),
                 typeMismatch(7),
                 deactived(8),
                 faulty(9),
                 invalid(10)
                }
            MAX-ACCESS      read-only
            STATUS          current
            DESCRIPTION     "This MIB is defined for the card status on MDU.
              inService(1)   --  card pluged in,running normally and service is being
                                 provided normally.
              notInService(2)--  card pluged in,running normally but service is stopped.
              hwOnline(3)    --  card pluged in AND card communication is ok,but software isn't running now.
              hwOffline(4)   --  card is pulled out or card not pluged in,but added to agent's database only
              configuring(5) --  card pluged in,but it is configuring
              configFailed(6)--  card pluged in,but configuration failed
              typeMismatch(7)--  card pluged in,but it's type is mismatch
              deactived(8)   --  card pluged in,but it is deactivated by a manager
              faulty(9)      --  fault occurs when card is running normally
              invalid(10)    --  invalid card instance,such as adding card failed.
            "
            ::= { zxAnEponMduCardEntry 1 }

    zxAnEponMduCardAdminStatus OBJECT-TYPE
            SYNTAX       INTEGER
                {
                    reset(1),
                    switch(2),
                    stopService(3),
                    active(4),
                    deactive(5)
                }
            MAX-ACCESS      read-write
            STATUS          current
            DESCRIPTION     "This MIB is defined for the card admin status on the card.
                             For example:reset(1),switch(2)
                             reset(1)    -- reset the card.
                             switch(2)   -- switch card between master and slave status.
                             stopService(3) -- stop service normally.
                             active(4)   -- activate this card and enable the service.
                             deactive(5) -- deactivate this card and disable the
                                            service forcedly.
                             "
            ::=  {  zxAnEponMduCardEntry  2  }


------------------------------------------------------------------------------
-- 1.40 EPON MDU SNMP parameter management(OAM)
------------------------------------------------------------------------------

    zxAnEponMduSnmpParamMgmt                OBJECT IDENTIFIER ::= { zxAnEponOnuExtendedAttrMgmt 40}

--------------------------------------------------------------------------------
-- 1.40.1 MDU SNMP parameter table
--------------------------------------------------------------------------------
    zxAnEponMduSnmpParamTable  OBJECT-TYPE
            SYNTAX      SEQUENCE OF ZxAnEponMduSnmpParamEntry
            MAX-ACCESS  not-accessible
            STATUS      current
            DESCRIPTION
                "EPON remote management MDU snmp parameter table."
            ::= {zxAnEponMduSnmpParamMgmt 1}

    zxAnEponMduSnmpParamEntry  OBJECT-TYPE
            SYNTAX      ZxAnEponMduSnmpParamEntry
            MAX-ACCESS  not-accessible
            STATUS      current
            DESCRIPTION
                "EPON remote management MDU snmp parameter entry."
            INDEX    { zxAnEponOnuIfIndex }
            ::= {zxAnEponMduSnmpParamTable 1}

    ZxAnEponMduSnmpParamEntry ::=
            SEQUENCE {
                zxEponMduSnmpVersion        INTEGER,
                zxEponMduSnmpServicePort    INTEGER,
                zxEponMduSnmpTrapPort       INTEGER,
                zxEponMduSnmpReadCommunity  DisplayString,
                zxEponMduSnmpWriteCommunity DisplayString
                }

    zxEponMduSnmpVersion  OBJECT-TYPE
            SYNTAX      INTEGER
                {
                  snmpV1(1),
                  snmpV2c(2),
                  snmpV3(3)
                }
            MAX-ACCESS      read-write
            STATUS          current
            DESCRIPTION     "This MIB is defined for SNMP version of the MDU."
            DEFVAL { snmpV2c }
            ::= { zxAnEponMduSnmpParamEntry 1 }

    zxEponMduSnmpServicePort  OBJECT-TYPE
            SYNTAX          INTEGER(1..65535)
            MAX-ACCESS      read-write
            STATUS          current
            DESCRIPTION     "This MIB is defined for SNMP service port of the MDU."
            DEFVAL { 161 }
            ::= { zxAnEponMduSnmpParamEntry 2 }

    zxEponMduSnmpTrapPort  OBJECT-TYPE
            SYNTAX          INTEGER(1..65535)
            MAX-ACCESS      read-write
            STATUS          current
            DESCRIPTION     "This MIB is defined for SNMP trap port of the MDU."
            DEFVAL { 162 }
            ::= { zxAnEponMduSnmpParamEntry 3 }

    zxEponMduSnmpReadCommunity  OBJECT-TYPE
            SYNTAX          DisplayString(SIZE(0..32))
            MAX-ACCESS      read-write
            STATUS          current
            DESCRIPTION     "This MIB is defined for SNMP read community of the MDU."
            DEFVAL { public }
            ::= { zxAnEponMduSnmpParamEntry 4 }

    zxEponMduSnmpWriteCommunity  OBJECT-TYPE
            SYNTAX          DisplayString(SIZE(0..32))
            MAX-ACCESS      read-write
            STATUS          current
            DESCRIPTION     "This MIB is defined for SNMP write community of the MDU."
            DEFVAL { public }
            ::= { zxAnEponMduSnmpParamEntry 5 }

--------------------------------------------------------------------------------
-- 1.40.2 MDU SNMP trap server table
--------------------------------------------------------------------------------

    zxEponMduSnmpTrapHostTable OBJECT-TYPE
        SYNTAX SEQUENCE OF ZxEponMduSnmpTrapHostEntry
        MAX-ACCESS not-accessible
        STATUS current
        DESCRIPTION
            "A list of trap destination entries."
        ::= { zxAnEponMduSnmpParamMgmt 2 }

    zxEponMduSnmpTrapHostEntry OBJECT-TYPE
        SYNTAX ZxEponMduSnmpTrapHostEntry
        MAX-ACCESS not-accessible
        STATUS current
        DESCRIPTION
            "This entry includes a destination IP address to which traps are
            sent for this community."
        INDEX { zxAnEponOnuIfIndex,zxEponMduSnmpTrapHostIndex }
        ::= { zxEponMduSnmpTrapHostTable 1 }

    ZxEponMduSnmpTrapHostEntry ::= SEQUENCE {
        zxEponMduSnmpTrapHostIndex          Integer32,
        zxEponMduSnmpTrapHostIpAddr         IpAddress,
        zxEponMduSnmpTrapHostSnmpVer        INTEGER,
        zxEponMduSnmpTrapHostCommunity      DisplayString,
        zxEponMduSnmpTrapHostMinEventLevel  INTEGER,
        zxEponMduSnmpTrapHostEnable         INTEGER,
        zxEponMduSnmpTrapHostRowStatus      RowStatus
    }

    zxEponMduSnmpTrapHostIndex  OBJECT-TYPE
        SYNTAX Integer32(1..8)
        MAX-ACCESS not-accessible
        STATUS current
        DESCRIPTION
            "The index of a reciever."
        ::= { zxEponMduSnmpTrapHostEntry 1 }

    zxEponMduSnmpTrapHostIpAddr  OBJECT-TYPE
        SYNTAX IpAddress
        MAX-ACCESS read-write
        STATUS current
        DESCRIPTION
            "The destination address for traps on behalf of this entry."
        ::= { zxEponMduSnmpTrapHostEntry 2 }

    zxEponMduSnmpTrapHostSnmpVer  OBJECT-TYPE
        SYNTAX  INTEGER
                {
                  snmpV1(1),
                  snmpV2c(2),
                  snmpV3(3)
                }
        MAX-ACCESS read-write
        STATUS current
        DESCRIPTION
            "It is the snmp version which a reciever expects."
        DEFVAL { snmpV2c }
        ::= { zxEponMduSnmpTrapHostEntry 3 }



    zxEponMduSnmpTrapHostCommunity  OBJECT-TYPE
        SYNTAX DisplayString(SIZE(0..32))
        MAX-ACCESS read-write
        STATUS current
        DESCRIPTION
            "The community that a reciever expects."
        ::= { zxEponMduSnmpTrapHostEntry 4 }


    zxEponMduSnmpTrapHostMinEventLevel  OBJECT-TYPE
        SYNTAX INTEGER {
                     critical(0),
                     major(1),
                     minor(2),
                     warning(3),
                     indeterminate(4),
                     cleared(5),
                     notification(6)
                    }
        MAX-ACCESS read-write
        STATUS current
        DESCRIPTION
            "The min event level that a reciever expects.If the actual event
            level is more serious then this value,the event will be sent to
            Event Reciever. For example,if this value is cleared(5),all the
            events that the level in critical(0),major(1),minor(2),warning(3),
            indeterminate(4) and cleared(5) will be sent,but notification will
            not be sent.

            The event levels are defined in ITU-T X.733.

           -  critical: The Critical severity level indicates that a service
             affecting condition has occurred and an immediate corrective action
             is required.  Such a severity can be reported, for example, when
             a managed object becomes totally out of service and its capability
             must be restored.

           -   major: The Major severity level indicates that a service
            affecting condition has developed and an urgent corrective action
            is required.  Such a severity can be reported, for example, when
            there is a severe degradation in the capability of the managed
            object and its full capability must be restored.

           -   minor: The Minor severity level indicates the existence of
            a non-service affecting fault condition and that corrective action
            should be taken in order to prevent a more serious (for example,
            service affecting) fault. Such a severity can be reported,
            for example, when the detected alarm condition is not currently
            degrading the capacity of the managed object.

           -   warning: The Warning severity level indicates the detection of
            a potential or impending service affecting fault, before any
            significant effects have been felt. Action should be taken to
            further diagnose (if necessary) and correct the problem in order
            to prevent it from becoming a more serious service affecting fault.

           -   cleared: The Cleared severity level indicates the clearing of
            one or more previously reported alarms. This alarm clears all
            alarms for this managed object that have the same Alarm type,
            Probable cause and Specific problems (if given).
            Multiple associated notifications may be cleared by using
            the Correlated notifications parameter (defined below).
            This Recommendation | International Standard does not require that
            the clearing of previously reported alarms be reported.
            Therefore, a managing system cannot assume that the absence of
            an alarm with the Cleared severity level means that the condition
            that caused the generation of previous alarms is still present.
               Managed object definers shall state if, and under which
            conditions, the Cleared severity level is used.

            -  indeterminate: The Indeterminate severity level indicates that
            the severity level cannot be determined.


            -  notification: The notification severity level indicates that
            only a infomation to be report and it is either a fault or
            a potential fault.

            "
        DEFVAL { notification }
        ::= { zxEponMduSnmpTrapHostEntry 5 }


    zxEponMduSnmpTrapHostEnable  OBJECT-TYPE
        SYNTAX INTEGER
            {
                enable(1),
                disable(2)
            }

        MAX-ACCESS read-write
        STATUS current
        DESCRIPTION
            "Enable or disable a reciever to recieve the event."
        DEFVAL { enable }
        ::= { zxEponMduSnmpTrapHostEntry 6 }


    zxEponMduSnmpTrapHostRowStatus  OBJECT-TYPE
        SYNTAX RowStatus
        MAX-ACCESS read-write
        STATUS current
        DESCRIPTION
            "This entry's row status."
        ::= { zxEponMduSnmpTrapHostEntry 7 }

--------------------------------------------------------------------------------
-- 1.41 ONU multicast VLAN switch table
--------------------------------------------------------------------------------
    zxAnEponOnuMVlanSwitchTable  OBJECT-TYPE
            SYNTAX      SEQUENCE OF ZxAnEponOnuMVlanSwitchEntry
            MAX-ACCESS  not-accessible
            STATUS      current
            DESCRIPTION
                "EPON remote management ONU Multicast VLAN switch table."
            ::= {zxAnEponOnuExtendedAttrMgmt 41}

    zxAnEponOnuMVlanSwitchEntry  OBJECT-TYPE
            SYNTAX      ZxAnEponOnuMVlanSwitchEntry
            MAX-ACCESS  not-accessible
            STATUS      current
            DESCRIPTION
                "EPON remote management ONU Multicast VLAN switch entry."
            INDEX    { zxAnEponOnuIfIndex,zxAnEponOnuPortId,zxAnEponOnuMVlan,zxAnEponOnuIptvUserVlan }
            ::= {zxAnEponOnuMVlanSwitchTable 1}

    ZxAnEponOnuMVlanSwitchEntry ::=
            SEQUENCE {
                zxAnEponOnuMVlan                INTEGER,
                zxAnEponOnuIptvUserVlan         INTEGER,
                zxAnEponOnuMVlanSwitchRowStatus RowStatus
                }

    zxAnEponOnuMVlan  OBJECT-TYPE
            SYNTAX      INTEGER(1..4094)
            MAX-ACCESS  read-create
            STATUS      current
            DESCRIPTION
                 "Multicast VLAN."
            ::= { zxAnEponOnuMVlanSwitchEntry 1 }

    zxAnEponOnuIptvUserVlan  OBJECT-TYPE
            SYNTAX      INTEGER(1..4094)
            MAX-ACCESS  read-create
            STATUS      current
            DESCRIPTION
                 "IPTV user vlan."
            ::= { zxAnEponOnuMVlanSwitchEntry 2 }

    zxAnEponOnuMVlanSwitchRowStatus  OBJECT-TYPE
            SYNTAX      RowStatus
            MAX-ACCESS  read-create
            STATUS      current
            DESCRIPTION
                 "ONU multicast VLAN switch table RowStatus. "
            ::= { zxAnEponOnuMVlanSwitchEntry 10 }

--------------------------------------------------------------------------------
-- 1.42 ONU port loop detect table
--------------------------------------------------------------------------------
    zxAnEponOnuPortTable  OBJECT-TYPE
            SYNTAX      SEQUENCE OF ZxAnEponOnuPortEntry
            MAX-ACCESS  not-accessible
            STATUS      current
            DESCRIPTION
                "EPON remote management ONU port table."
            ::= {zxAnEponOnuExtendedAttrMgmt 42}

    zxAnEponOnuPortEntry  OBJECT-TYPE
            SYNTAX      ZxAnEponOnuPortEntry
            MAX-ACCESS  not-accessible
            STATUS      current
            DESCRIPTION
                "EPON remote management ONU port entry."
            INDEX    { zxAnEponOnuIfIndex,zxAnEponOnuPortId }
            ::= {zxAnEponOnuPortTable 1}

    ZxAnEponOnuPortEntry ::=
            SEQUENCE {
                zxAnEponOnuPortLoopbackDetectStatus    INTEGER,
                zxAnEponOnuPortLoopbackAutoSdEn        INTEGER
                }

    zxAnEponOnuPortLoopbackDetectStatus  OBJECT-TYPE
            SYNTAX      INTEGER {
                disable(1),
                enable(2)
                }
            MAX-ACCESS  read-write
            STATUS      current
            DESCRIPTION
                 "ONU port self loopback detect status."
            ::= { zxAnEponOnuPortEntry 1 }

    zxAnEponOnuPortLoopbackAutoSdEn  OBJECT-TYPE
        SYNTAX      INTEGER {
            enabled(1),
            disabled(2)
            }
        MAX-ACCESS  read-write
        STATUS      current
        DESCRIPTION
            "When zxAnEponOnuPortLoopbackAutoSdEn is enabled, port will
             be shut down automatically after port loopback was detected."
        DEFVAL { disabled }
       ::= { zxAnEponOnuPortEntry 2 }

--------------------------------------------------------------------------------
-- 1.43 ONU LLID queue table
--------------------------------------------------------------------------------
    zxAnEponOnuLlidQueueTable  OBJECT-TYPE
            SYNTAX      SEQUENCE OF ZxAnEponOnuLlidQueueEntry
            MAX-ACCESS  not-accessible
            STATUS      current
            DESCRIPTION
                "EPON remote management ONU LLID queue table."
            ::= {zxAnEponOnuExtendedAttrMgmt 43}

    zxAnEponOnuLlidQueueEntry  OBJECT-TYPE
            SYNTAX      ZxAnEponOnuLlidQueueEntry
            MAX-ACCESS  not-accessible
            STATUS      current
            DESCRIPTION
                "EPON remote management ONU LLID queue entry."
            INDEX    { zxAnEponOnuIfIndex,zxAnEponOnuLlid }
            ::= {zxAnEponOnuLlidQueueTable 1}

    ZxAnEponOnuLlidQueueEntry ::=
            SEQUENCE {
                zxAnEponOnuLlid                   INTEGER,
                zxAnEponOnuLlidQueue1WrrWeight    INTEGER,
                zxAnEponOnuLlidQueue2WrrWeight    INTEGER,
                zxAnEponOnuLlidQueue3WrrWeight    INTEGER,
                zxAnEponOnuLlidQueue4WrrWeight    INTEGER,
                zxAnEponOnuLlidQueue5WrrWeight    INTEGER,
                zxAnEponOnuLlidQueue6WrrWeight    INTEGER,
                zxAnEponOnuLlidQueue7WrrWeight    INTEGER,
                zxAnEponOnuLlidQueue8WrrWeight    INTEGER
                }

    zxAnEponOnuLlid  OBJECT-TYPE
            SYNTAX      INTEGER
            MAX-ACCESS  not-accessible
            STATUS      current
            DESCRIPTION
                 "ONU LLID."
            ::= { zxAnEponOnuLlidQueueEntry 1 }

    zxAnEponOnuLlidQueue1WrrWeight  OBJECT-TYPE
            SYNTAX      INTEGER(0..100)
            MAX-ACCESS  read-write
            STATUS      current
            DESCRIPTION
                 "ONU LLID queue WRR weight."
            ::= { zxAnEponOnuLlidQueueEntry 2 }

    zxAnEponOnuLlidQueue2WrrWeight  OBJECT-TYPE
            SYNTAX      INTEGER(0..100)
            MAX-ACCESS  read-write
            STATUS      current
            DESCRIPTION
                 "ONU LLID queue WRR weight."
            ::= { zxAnEponOnuLlidQueueEntry 3 }

    zxAnEponOnuLlidQueue3WrrWeight  OBJECT-TYPE
            SYNTAX      INTEGER(0..100)
            MAX-ACCESS  read-write
            STATUS      current
            DESCRIPTION
                 "ONU LLID queue WRR weight."
            ::= { zxAnEponOnuLlidQueueEntry 4 }

    zxAnEponOnuLlidQueue4WrrWeight  OBJECT-TYPE
            SYNTAX      INTEGER(0..100)
            MAX-ACCESS  read-write
            STATUS      current
            DESCRIPTION
                 "ONU LLID queue WRR weight."
            ::= { zxAnEponOnuLlidQueueEntry 5 }

    zxAnEponOnuLlidQueue5WrrWeight  OBJECT-TYPE
            SYNTAX      INTEGER(0..100)
            MAX-ACCESS  read-write
            STATUS      current
            DESCRIPTION
                 "ONU LLID queue WRR weight."
            ::= { zxAnEponOnuLlidQueueEntry 6 }

    zxAnEponOnuLlidQueue6WrrWeight  OBJECT-TYPE
            SYNTAX      INTEGER(0..100)
            MAX-ACCESS  read-write
            STATUS      current
            DESCRIPTION
                 "ONU LLID queue WRR weight."
            ::= { zxAnEponOnuLlidQueueEntry 7 }

    zxAnEponOnuLlidQueue7WrrWeight  OBJECT-TYPE
            SYNTAX      INTEGER(0..100)
            MAX-ACCESS  read-write
            STATUS      current
            DESCRIPTION
                 "ONU LLID queue WRR weight."
            ::= { zxAnEponOnuLlidQueueEntry 8 }

    zxAnEponOnuLlidQueue8WrrWeight  OBJECT-TYPE
            SYNTAX      INTEGER(0..100)
            MAX-ACCESS  read-write
            STATUS      current
            DESCRIPTION
                 "ONU LLID queue WRR weight."
            ::= { zxAnEponOnuLlidQueueEntry 9 }

--------------------------------------------------------------------------------
-- 1.44 ONU PON attribute table
--------------------------------------------------------------------------------
    zxAnEponOnuPonIfTable  OBJECT-TYPE
            SYNTAX      SEQUENCE OF ZxAnEponOnuPonIfEntry
            MAX-ACCESS  not-accessible
            STATUS      current
            DESCRIPTION
                "EPON remote management ONU PON attribute table."
            ::= {zxAnEponOnuExtendedAttrMgmt 44}

    zxAnEponOnuPonIfEntry  OBJECT-TYPE
            SYNTAX      ZxAnEponOnuPonIfEntry
            MAX-ACCESS  not-accessible
            STATUS      current
            DESCRIPTION
                "EPON remote management ONU PON attribute entry."
            INDEX    { zxAnEponOnuIfIndex }
            ::= {zxAnEponOnuPonIfTable 1}

    ZxAnEponOnuPonIfEntry ::=
            SEQUENCE {
                zxAnEponOnuActivePonIf            INTEGER
                }

    zxAnEponOnuActivePonIf  OBJECT-TYPE
            SYNTAX      INTEGER(1..2)
            MAX-ACCESS  read-write
            STATUS      current
            DESCRIPTION
                 "ONU active PON interface."
            ::= { zxAnEponOnuPonIfEntry 1 }

------------------------------------------------------------------------------
-- 1.45 EPON ONU SLA management(OAM)
------------------------------------------------------------------------------

    zxAnEponOnuSlaMgmt                OBJECT IDENTIFIER ::= { zxAnEponOnuExtendedAttrMgmt 45}

--------------------------------------------------------------------------------
-- 1.45.1 zxAnEponOnuSlaProfileIdxNext
--------------------------------------------------------------------------------
        zxAnEponOnuSlaProfileIdxNext OBJECT-TYPE
                SYNTAX      INTEGER
                MAX-ACCESS  read-only
                STATUS      current
                DESCRIPTION
                "Use this value as index to create an entry of zxAnEponOnuSlaProfileTable"
                ::= { zxAnEponOnuSlaMgmt 1 }

--------------------------------------------------------------------------------
-- 1.45.2 zxAnEponOnuSlaProfileTable
--------------------------------------------------------------------------------

    zxAnEponOnuSlaProfileTable  OBJECT-TYPE
            SYNTAX      SEQUENCE OF ZxAnEponOnuSlaProfileEntry
            MAX-ACCESS  not-accessible
            STATUS      current
            DESCRIPTION
                "EPON remote management ONU SLA table."
            ::= {zxAnEponOnuSlaMgmt 2}

    zxAnEponOnuSlaProfileEntry  OBJECT-TYPE
            SYNTAX      ZxAnEponOnuSlaProfileEntry
            MAX-ACCESS  not-accessible
            STATUS      current
            DESCRIPTION
                "EPON remote management ONU SLA entry."
            INDEX    { zxAnEponOnuSlaProfileIndex }
            ::= {zxAnEponOnuSlaProfileTable 1}

    ZxAnEponOnuSlaProfileEntry ::=
            SEQUENCE {
                zxAnEponOnuSlaProfileIndex              INTEGER,
                                zxAnEponOnuSlaProfileName               DisplayString,
                                zxAnEponOnuServiceDbaEnable             INTEGER,
                zxAnEponOnuBestEffortSchedulingScheme   INTEGER,
                zxAnEponOnuHighPriorityBoundary         INTEGER,
                zxAnEponOnuServiceDbaCycleLength        INTEGER,
                                zxAnEponOnuSlaServiceIdxNext            INTEGER,
                                zxAnEponOnuSlaProfileRowStatus          RowStatus
                }

        zxAnEponOnuSlaProfileIndex  OBJECT-TYPE
            SYNTAX      INTEGER
            MAX-ACCESS  not-accessible
            STATUS      current
            DESCRIPTION
                 "EPON remote management SLA profile index."
            ::= { zxAnEponOnuSlaProfileEntry 1 }

        zxAnEponOnuSlaProfileName  OBJECT-TYPE
            SYNTAX      DisplayString ( SIZE(1..32) )
            MAX-ACCESS  read-create
            STATUS      current
            DESCRIPTION
                 "EPON remote management SLA profile name."
            ::= { zxAnEponOnuSlaProfileEntry 2 }

    zxAnEponOnuServiceDbaEnable  OBJECT-TYPE
            SYNTAX      INTEGER {
                disable(1),
                enable(2)
                }
            MAX-ACCESS  read-create
            STATUS      current
            DESCRIPTION
                 "ONU service dba state."
            ::= { zxAnEponOnuSlaProfileEntry 3 }

    zxAnEponOnuBestEffortSchedulingScheme  OBJECT-TYPE
            SYNTAX      INTEGER {
                sp(1),
                wrr(2),
                spWrr(3)
                }
            MAX-ACCESS  read-create
            STATUS      current
            DESCRIPTION
                 "ONU best effort scheduling scheme."
            ::= { zxAnEponOnuSlaProfileEntry 4 }

    zxAnEponOnuHighPriorityBoundary  OBJECT-TYPE
            SYNTAX      INTEGER(0..7)
            MAX-ACCESS  read-create
            STATUS      current
            DESCRIPTION
                 "ONU high priority boundary."
            ::= { zxAnEponOnuSlaProfileEntry 5 }

    zxAnEponOnuServiceDbaCycleLength  OBJECT-TYPE
            SYNTAX      INTEGER
            MAX-ACCESS  read-create
            STATUS      current
            DESCRIPTION
                 "ONU service dba cycle length."
            ::= { zxAnEponOnuSlaProfileEntry 6 }

        zxAnEponOnuSlaServiceIdxNext  OBJECT-TYPE
            SYNTAX      INTEGER
            MAX-ACCESS  read-only
            STATUS      current
            DESCRIPTION
                 "Use this value as index to create an entry of zxAnEponOnuServiceQueueTable."
            ::= { zxAnEponOnuSlaProfileEntry 29 }

        zxAnEponOnuSlaProfileRowStatus  OBJECT-TYPE
            SYNTAX      RowStatus
            MAX-ACCESS  read-create
            STATUS      current
            DESCRIPTION
                 "SLA profile table RowStatus."
            ::= { zxAnEponOnuSlaProfileEntry 30 }

--------------------------------------------------------------------------------
-- 1.45.3 ONU service queue table
--------------------------------------------------------------------------------
    zxAnEponOnuServiceQueueTable  OBJECT-TYPE
            SYNTAX      SEQUENCE OF ZxAnEponOnuServiceQueueEntry
            MAX-ACCESS  not-accessible
            STATUS      current
            DESCRIPTION
                "EPON remote management ONU service queue attribute table."
            ::= {zxAnEponOnuSlaMgmt 3}

    zxAnEponOnuServiceQueueEntry  OBJECT-TYPE
            SYNTAX      ZxAnEponOnuServiceQueueEntry
            MAX-ACCESS  not-accessible
            STATUS      current
            DESCRIPTION
                "EPON remote management ONU service queue attribute entry."
            INDEX    { zxAnEponOnuSlaProfileIndex,zxAnEponOnuSlaServiceIdx }
            ::= {zxAnEponOnuServiceQueueTable 1}

    ZxAnEponOnuServiceQueueEntry ::=
            SEQUENCE {
                zxAnEponOnuSlaServiceIdx                INTEGER,
                zxAnEponOnuServiceName                  DisplayString,
                zxAnEponOnuQueueId                      INTEGER,
                zxAnEponOnuServiceFixedPktSize          INTEGER,
                zxAnEponOnuServiceFixedBandwidth        INTEGER,
                zxAnEponOnuServiceAssuredBandwidth      INTEGER,
                zxAnEponOnuServiceBestEffortBandwidth   INTEGER,
                zxAnEponOnuServiceWrrWeight             INTEGER,
                zxAnEponOnuServiceRowStatus             RowStatus
                }

    zxAnEponOnuSlaServiceIdx  OBJECT-TYPE
            SYNTAX      INTEGER(1..8)
            MAX-ACCESS  read-create
            STATUS      current
            DESCRIPTION
                 "ONU service ID."
            ::= { zxAnEponOnuServiceQueueEntry 1 }

    zxAnEponOnuServiceName  OBJECT-TYPE
            SYNTAX      DisplayString
            MAX-ACCESS  read-create
            STATUS      current
            DESCRIPTION
                 "ONU service Name."
            ::= { zxAnEponOnuServiceQueueEntry 2 }

    zxAnEponOnuQueueId  OBJECT-TYPE
            SYNTAX      INTEGER
            MAX-ACCESS  read-create
            STATUS      current
            DESCRIPTION
                 "ONU service queue number."
            ::= { zxAnEponOnuServiceQueueEntry 3 }

    zxAnEponOnuServiceFixedPktSize  OBJECT-TYPE
            SYNTAX      INTEGER
            MAX-ACCESS  read-create
            STATUS      current
            DESCRIPTION
                 "ONU service queue number."
            ::= { zxAnEponOnuServiceQueueEntry 4 }

    zxAnEponOnuServiceFixedBandwidth  OBJECT-TYPE
            SYNTAX      INTEGER
            MAX-ACCESS  read-create
            STATUS      current
            DESCRIPTION
                 "ONU service queue number."
            ::= { zxAnEponOnuServiceQueueEntry 5 }

    zxAnEponOnuServiceAssuredBandwidth  OBJECT-TYPE
            SYNTAX      INTEGER
            MAX-ACCESS  read-create
            STATUS      current
            DESCRIPTION
                 "ONU service queue number."
            ::= { zxAnEponOnuServiceQueueEntry 6 }

    zxAnEponOnuServiceBestEffortBandwidth  OBJECT-TYPE
            SYNTAX      INTEGER
            MAX-ACCESS  read-create
            STATUS      current
            DESCRIPTION
                 "ONU service queue number."
            ::= { zxAnEponOnuServiceQueueEntry 7 }

    zxAnEponOnuServiceWrrWeight  OBJECT-TYPE
            SYNTAX      INTEGER(0..100)
            MAX-ACCESS  read-create
            STATUS      current
            DESCRIPTION
                 "ONU service WRR weight. 0 means sp, 1-100 means WRR weight."
            ::= { zxAnEponOnuServiceQueueEntry 8 }

    zxAnEponOnuServiceRowStatus  OBJECT-TYPE
            SYNTAX      RowStatus
            MAX-ACCESS  read-create
            STATUS      current
            DESCRIPTION
                 "ONU multicast VLAN switch table RowStatus. "
            ::= { zxAnEponOnuServiceQueueEntry 30 }

--------------------------------------------------------------------------------
-- 1.45.4 ONU SLA profile apply table
--------------------------------------------------------------------------------

        zxAnEponOnuSlaProfileApplyTable  OBJECT-TYPE
            SYNTAX      SEQUENCE OF ZxAnEponOnuSlaProfileApplyEntry
            MAX-ACCESS  not-accessible
            STATUS      current
            DESCRIPTION
                "EPON remote management SLA profile apply table."
            ::= {zxAnEponOnuSlaMgmt 4}

    zxAnEponOnuSlaProfileApplyEntry  OBJECT-TYPE
            SYNTAX      ZxAnEponOnuSlaProfileApplyEntry
            MAX-ACCESS  not-accessible
            STATUS      current
            DESCRIPTION
                "EPON remote management SLA profile apply entry."
            INDEX    { zxAnEponOnuIfIndex }
            ::= {zxAnEponOnuSlaProfileApplyTable 1}

    ZxAnEponOnuSlaProfileApplyEntry ::=
            SEQUENCE {
                zxAnEponOnuCurrSlaProfileIdx          INTEGER

                }

    zxAnEponOnuCurrSlaProfileIdx  OBJECT-TYPE
            SYNTAX      INTEGER
            MAX-ACCESS  read-write
            STATUS      current
            DESCRIPTION
                 "The SLA profile index."
            ::= { zxAnEponOnuSlaProfileApplyEntry 1 }

--------------------------------------------------------------------------------
-- 1.46 ONU holdover table
--------------------------------------------------------------------------------
    zxAnEponOnuHoldoverTable  OBJECT-TYPE
            SYNTAX      SEQUENCE OF ZxAnEponOnuHoldoverEntry
            MAX-ACCESS  not-accessible
            STATUS      current
            DESCRIPTION
                "EPON remote management ONU holdover table."
            ::= {zxAnEponOnuExtendedAttrMgmt 46}

    zxAnEponOnuHoldoverEntry  OBJECT-TYPE
            SYNTAX      ZxAnEponOnuHoldoverEntry
            MAX-ACCESS  not-accessible
            STATUS      current
            DESCRIPTION
                "EPON remote management ONU holdover entry."
            INDEX    { zxAnEponOnuIfIndex }
            ::= {zxAnEponOnuHoldoverTable 1}

    ZxAnEponOnuHoldoverEntry ::=
            SEQUENCE {
                zxAnEponOnuHoldoverState   INTEGER,
                zxAnEponOnuHoldoverTime    INTEGER
                }

    zxAnEponOnuHoldoverState  OBJECT-TYPE
            SYNTAX      INTEGER {
                disable(1),
                enable(2)
                }
            MAX-ACCESS  read-write
            STATUS      current
            DESCRIPTION
                 "ONU optical protection holdover status."
            DEFVAL { disable }
            ::= { zxAnEponOnuHoldoverEntry 1 }

    zxAnEponOnuHoldoverTime  OBJECT-TYPE
            SYNTAX      INTEGER(500..1000)
            MAX-ACCESS  read-write
            STATUS      current
            DESCRIPTION
                 "ONU optical protection holdover time. Unit is ms"
            DEFVAL { 500 }
            ::= { zxAnEponOnuHoldoverEntry 2 }

------------------------------------------------------------------------------
-- 1.48 EPON ONU alarm management(OAM)
------------------------------------------------------------------------------

    zxAnEponOnuAlarmMgmt                OBJECT IDENTIFIER ::= { zxAnEponOnuExtendedAttrMgmt 48}

--------------------------------------------------------------------------------
-- 1.48.1 ONU alarm control table
--------------------------------------------------------------------------------
    zxAnEponOnuLvlAlarmCtrlTable  OBJECT-TYPE
            SYNTAX      SEQUENCE OF ZxAnEponOnuLvlAlarmCtrlEntry
            MAX-ACCESS  not-accessible
            STATUS      current
            DESCRIPTION
                "EPON remote management ONU level alarm control table."
            ::= {zxAnEponOnuAlarmMgmt 1}

    zxAnEponOnuLvlAlarmCtrlEntry  OBJECT-TYPE
            SYNTAX      ZxAnEponOnuLvlAlarmCtrlEntry
            MAX-ACCESS  not-accessible
            STATUS      current
            DESCRIPTION
                "EPON remote management ONU  level alarm control entry."
            INDEX    { zxAnEponOnuIfIndex,zxAnEponOnuLvlAlarmCode }
            ::= {zxAnEponOnuLvlAlarmCtrlTable 1}

    ZxAnEponOnuLvlAlarmCtrlEntry ::=
            SEQUENCE {
                zxAnEponOnuLvlAlarmCode               INTEGER,
                zxAnEponOnuLvlAlarmEnable             INTEGER,
                zxAnEponOnuLvlAlarmThreshold          INTEGER,
                zxAnEponOnuLvlAlarmRestoreThreshold   INTEGER
                }

    zxAnEponOnuLvlAlarmCode  OBJECT-TYPE
            SYNTAX      INTEGER
            MAX-ACCESS  not-accessible
            STATUS      current
            DESCRIPTION
                 "ONU alarm id."
            ::= { zxAnEponOnuLvlAlarmCtrlEntry 1 }

    zxAnEponOnuLvlAlarmEnable  OBJECT-TYPE
            SYNTAX      INTEGER {
                disable(1),
                enable(2)
                }
            MAX-ACCESS  read-write
            STATUS      current
            DESCRIPTION
                 "ONU level alarm control status."
            ::= { zxAnEponOnuLvlAlarmCtrlEntry 2 }

    zxAnEponOnuLvlAlarmThreshold  OBJECT-TYPE
            SYNTAX      INTEGER
            MAX-ACCESS  read-write
            STATUS      current
            DESCRIPTION
                 "ONU level alarm threshold."
            ::= { zxAnEponOnuLvlAlarmCtrlEntry 3 }

    zxAnEponOnuLvlAlarmRestoreThreshold  OBJECT-TYPE
            SYNTAX      INTEGER
            MAX-ACCESS  read-write
            STATUS      current
            DESCRIPTION
                 "ONU level alarm restore threshold."
            ::= { zxAnEponOnuLvlAlarmCtrlEntry 4 }

--------------------------------------------------------------------------------
-- 1.48.2 ONU PON alarm control table
--------------------------------------------------------------------------------
    zxAnEponOnuPonAlarmCtrlTable  OBJECT-TYPE
            SYNTAX      SEQUENCE OF ZxAnEponOnuPonAlarmCtrlEntry
            MAX-ACCESS  not-accessible
            STATUS      current
            DESCRIPTION
                "EPON remote management ONU PON alarm control table."
            ::= {zxAnEponOnuAlarmMgmt 2}

    zxAnEponOnuPonAlarmCtrlEntry  OBJECT-TYPE
            SYNTAX      ZxAnEponOnuPonAlarmCtrlEntry
            MAX-ACCESS  not-accessible
            STATUS      current
            DESCRIPTION
                "EPON remote management ONU PON alarm control entry."
            INDEX    { zxAnEponOnuIfIndex,zxAnEponOnuPortId,zxAnEponOnuPonAlarmCode }
            ::= {zxAnEponOnuPonAlarmCtrlTable 1}

    ZxAnEponOnuPonAlarmCtrlEntry ::=
            SEQUENCE {
                zxAnEponOnuPonAlarmCode                 INTEGER,
                zxAnEponOnuPonAlarmEnable               INTEGER,
                zxAnEponOnuPonAlarmThreshold            INTEGER,
                zxAnEponOnuPonAlarmRestoreThreshold     INTEGER
                }

    zxAnEponOnuPonAlarmCode  OBJECT-TYPE
            SYNTAX      INTEGER
            MAX-ACCESS  not-accessible
            STATUS      current
            DESCRIPTION
                 "ONU PON alarm id."
            ::= { zxAnEponOnuPonAlarmCtrlEntry 1 }

    zxAnEponOnuPonAlarmEnable  OBJECT-TYPE
            SYNTAX      INTEGER {
                disable(1),
                enable(2)
                }
            MAX-ACCESS  read-write
            STATUS      current
            DESCRIPTION
                 "ONU PON alarm control status."
            ::= { zxAnEponOnuPonAlarmCtrlEntry 2 }

    zxAnEponOnuPonAlarmThreshold  OBJECT-TYPE
            SYNTAX      INTEGER
            MAX-ACCESS  read-write
            STATUS      current
            DESCRIPTION
                 "ONU PON alarm threshold."
            ::= { zxAnEponOnuPonAlarmCtrlEntry 3 }

    zxAnEponOnuPonAlarmRestoreThreshold  OBJECT-TYPE
            SYNTAX      INTEGER
            MAX-ACCESS  read-write
            STATUS      current
            DESCRIPTION
                 "ONU PON alarm restore threshold."
            ::= { zxAnEponOnuPonAlarmCtrlEntry 4 }

--------------------------------------------------------------------------------
-- 1.48.3 ONU UNI alarm control table
--------------------------------------------------------------------------------
    zxAnEponOnuUniAlarmCtrlTable  OBJECT-TYPE
            SYNTAX      SEQUENCE OF ZxAnEponOnuUniAlarmCtrlEntry
            MAX-ACCESS  not-accessible
            STATUS      current
            DESCRIPTION
                "EPON remote management ONU UNI alarm control table."
            ::= {zxAnEponOnuAlarmMgmt 3}

    zxAnEponOnuUniAlarmCtrlEntry  OBJECT-TYPE
            SYNTAX      ZxAnEponOnuUniAlarmCtrlEntry
            MAX-ACCESS  not-accessible
            STATUS      current
            DESCRIPTION
                "EPON remote management ONU UNI alarm control entry."
            INDEX    { zxAnEponOnuIfIndex,zxAnEponOnuPortId,zxAnEponOnuUniAlarmCode }
            ::= {zxAnEponOnuUniAlarmCtrlTable 1}

    ZxAnEponOnuUniAlarmCtrlEntry ::=
            SEQUENCE {
                zxAnEponOnuUniAlarmCode                 INTEGER,
                zxAnEponOnuUniAlarmEnable               INTEGER,
                zxAnEponOnuUniAlarmThreshold            Unsigned32,
                zxAnEponOnuUniAlarmRestoreThresh        Unsigned32
                }

    zxAnEponOnuUniAlarmCode  OBJECT-TYPE
            SYNTAX      INTEGER
            MAX-ACCESS  not-accessible
            STATUS      current
            DESCRIPTION
                 "ONU UNI alarm id."
            ::= { zxAnEponOnuUniAlarmCtrlEntry 1 }

    zxAnEponOnuUniAlarmEnable  OBJECT-TYPE
            SYNTAX      INTEGER {
                disable(1),
                enable(2)
                }
            MAX-ACCESS  read-write
            STATUS      current
            DESCRIPTION
                 "ONU UNI alarm control status."
            ::= { zxAnEponOnuUniAlarmCtrlEntry 2 }

    zxAnEponOnuUniAlarmThreshold  OBJECT-TYPE
        SYNTAX      Unsigned32 (0..4294967295)
        MAX-ACCESS  read-write
        STATUS      current
        DESCRIPTION
            "ONU UNI alarm threshold."
        ::= { zxAnEponOnuUniAlarmCtrlEntry 3 }

    zxAnEponOnuUniAlarmRestoreThresh  OBJECT-TYPE
        SYNTAX      Unsigned32 (0..4294967295)
        MAX-ACCESS  read-write
        STATUS      current
        DESCRIPTION
             "ONU UNI alarm restore threshold."
        ::= { zxAnEponOnuUniAlarmCtrlEntry 4 }

------------------------------------------------------------------------------
-- 1.49 EPON ONU version management(OAM)
------------------------------------------------------------------------------

    zxAnEponOnuVersionMgmt                OBJECT IDENTIFIER ::= { zxAnEponOnuExtendedAttrMgmt 49}

--------------------------------------------------------------------------------
-- 1.49.1 ONU version table
--------------------------------------------------------------------------------
    zxAnEponOnuVersionTable  OBJECT-TYPE
            SYNTAX      SEQUENCE OF ZxAnEponOnuVersionEntry
            MAX-ACCESS  not-accessible
            STATUS      current
            DESCRIPTION
                "EPON remote management ONU version table."
            ::= {zxAnEponOnuVersionMgmt 1}

    zxAnEponOnuVersionEntry  OBJECT-TYPE
            SYNTAX      ZxAnEponOnuVersionEntry
            MAX-ACCESS  not-accessible
            STATUS      current
            DESCRIPTION
                "EPON remote management ONU version entry."
            INDEX    { zxAnEponOnuVersionId }
            ::= {zxAnEponOnuVersionTable 1}

    ZxAnEponOnuVersionEntry ::=
            SEQUENCE {
                zxAnEponOnuVersionId            INTEGER,
                zxAnEponOnuVersionFileName      DisplayString,
                zxAnEponOnuVersionType          DisplayString,
                zxAnEponOnuVersionTag           DisplayString,
                zxAnEponOnuVersionBuildTime     DisplayString
                }

    zxAnEponOnuVersionId  OBJECT-TYPE
            SYNTAX      INTEGER
            MAX-ACCESS  read-only
            STATUS      current
            DESCRIPTION
                 "ONU version ID."
            ::= { zxAnEponOnuVersionEntry 1 }

    zxAnEponOnuVersionFileName  OBJECT-TYPE
            SYNTAX      DisplayString
            MAX-ACCESS  read-only
            STATUS      current
            DESCRIPTION
                 "ONU version name."
            ::= { zxAnEponOnuVersionEntry 2 }

    zxAnEponOnuVersionType  OBJECT-TYPE
            SYNTAX      DisplayString
            MAX-ACCESS  read-only
            STATUS      current
            DESCRIPTION
                 "ONU version type."
            ::= { zxAnEponOnuVersionEntry 3 }

    zxAnEponOnuVersionTag  OBJECT-TYPE
            SYNTAX      DisplayString
            MAX-ACCESS  read-only
            STATUS      current
            DESCRIPTION
                 "ONU version tag."
            ::= { zxAnEponOnuVersionEntry 4 }

    zxAnEponOnuVersionBuildTime  OBJECT-TYPE
            SYNTAX      DisplayString
            MAX-ACCESS  read-only
            STATUS      current
            DESCRIPTION
                 "ONU version build time."
            ::= { zxAnEponOnuVersionEntry 5 }

--------------------------------------------------------------------------------
-- 1.49.2 ONU version update table
--------------------------------------------------------------------------------
    zxAnEponOnuVersionUpdateTable  OBJECT-TYPE
            SYNTAX      SEQUENCE OF ZxAnEponOnuVersionUpdateEntry
            MAX-ACCESS  not-accessible
            STATUS      current
            DESCRIPTION
                "EPON remote management ONU version update table."
            ::= {zxAnEponOnuVersionMgmt 2}

    zxAnEponOnuVersionUpdateEntry  OBJECT-TYPE
            SYNTAX      ZxAnEponOnuVersionUpdateEntry
            MAX-ACCESS  not-accessible
            STATUS      current
            DESCRIPTION
                "EPON remote management ONU version update entry."
            INDEX    { zxAnEponOnuVersionId }
            ::= {zxAnEponOnuVersionUpdateTable 1}

    ZxAnEponOnuVersionUpdateEntry ::=
            SEQUENCE {
                zxAnEponOnuVersionUpdateOnuType DisplayString,
                zxAnEponOnuVersionUpdateLocType INTEGER,
                zxAnEponOnuVersionUpdateSlotId  INTEGER,
                zxAnEponOnuVersionUpdateOltId   INTEGER,
                zxAnEponOnuVersionUpdateOnuList DisplayString,
                zxAnEponOnuVersionUpdateAction  INTEGER
                }

    zxAnEponOnuVersionUpdateOnuType  OBJECT-TYPE
            SYNTAX      DisplayString
            MAX-ACCESS  read-write
            STATUS      current
            DESCRIPTION
                 "ONU type of this version."
            ::= { zxAnEponOnuVersionUpdateEntry 1 }

    zxAnEponOnuVersionUpdateLocType  OBJECT-TYPE
            SYNTAX      INTEGER {
                slot(1),
                olt(2),
                onuList(3)
                }
            MAX-ACCESS  read-write
            STATUS      current
            DESCRIPTION
                 "ONU version update location type.
                  If type is slot(1), only zxAnEponOnuVersionUpdateSlotId needed;
                  If type is olt(2), zxAnEponOnuVersionUpdateSlotId
                     and zxAnEponOnuVersionUpdateOltId is needed;
                  If type is onuList(3), zxAnEponOnuVersionUpdateSlotId,
                     zxAnEponOnuVersionUpdateOltId and zxAnEponOnuVersionUpdateOnuList is needed;
                 "
            ::= { zxAnEponOnuVersionUpdateEntry 2 }

    zxAnEponOnuVersionUpdateSlotId  OBJECT-TYPE
            SYNTAX      INTEGER
            MAX-ACCESS  read-write
            STATUS      current
            DESCRIPTION
                 "ONU version update slot ID."
            ::= { zxAnEponOnuVersionUpdateEntry 3 }

    zxAnEponOnuVersionUpdateOltId  OBJECT-TYPE
            SYNTAX      INTEGER
            MAX-ACCESS  read-write
            STATUS      current
            DESCRIPTION
                 "ONU version update OLT ID."
            ::= { zxAnEponOnuVersionUpdateEntry 4 }

    zxAnEponOnuVersionUpdateOnuList  OBJECT-TYPE
            SYNTAX      DisplayString
            MAX-ACCESS  read-write
            STATUS      current
            DESCRIPTION
                 "ONU version update ONU list. Example: 2-5,8,15"
            ::= { zxAnEponOnuVersionUpdateEntry 5 }

    zxAnEponOnuVersionUpdateAction  OBJECT-TYPE
            SYNTAX      INTEGER {
                download(1),
                downloadAndActivate(2),
                downloadAndCommit(3),
                activate(4),
                commit(5),
                abort(99)
                }
            MAX-ACCESS  read-write
            STATUS      current
            DESCRIPTION
                 "ONU version update action type."
            ::= { zxAnEponOnuVersionUpdateEntry 6 }

--------------------------------------------------------------------------------
-- 1.49.3 ONU version update status table
--------------------------------------------------------------------------------
    zxAnEponOnuVersionUpdateStatusTable  OBJECT-TYPE
            SYNTAX      SEQUENCE OF ZxAnEponOnuVersionUpdateStatusEntry
            MAX-ACCESS  not-accessible
            STATUS      current
            DESCRIPTION
                "EPON remote management ONU version update status table."
            ::= {zxAnEponOnuVersionMgmt 3}

    zxAnEponOnuVersionUpdateStatusEntry  OBJECT-TYPE
            SYNTAX      ZxAnEponOnuVersionUpdateStatusEntry
            MAX-ACCESS  not-accessible
            STATUS      current
            DESCRIPTION
                "EPON remote management ONU version update status entry."
            INDEX    { zxAnEponOnuIfIndex }
            ::= {zxAnEponOnuVersionUpdateStatusTable 1}

    ZxAnEponOnuVersionUpdateStatusEntry ::=
            SEQUENCE {
                zxAnEponOnuVersionUpdateState           INTEGER,
                zxAnEponOnuVersionUpdateAbortReason     INTEGER,
                zxAnEponOnuVersionUpdateErrCode         INTEGER,
                zxAnEponOnuVersionUpdateErrMsg          DisplayString,
                zxAnEponOnuVersionUpdateProgress        INTEGER,
                zxAnEponOnuCurrentUsedVersionName       DisplayString,
                zxAnEponOnuCurrentUsedVersionTime       DisplayString,
                zxAnEponOnuUpdatingVersionName          DisplayString,
                zxAnEponOnuUpdatingVersionTime          DisplayString
                }

    zxAnEponOnuVersionUpdateState  OBJECT-TYPE
            SYNTAX      INTEGER {
                notStart(1),
                updateFailed(2),
                downloading(3),
                waitEndResponse(4),
                finished(5)
                }
            MAX-ACCESS  read-only
            STATUS      current
            DESCRIPTION
                 "ONU version update status."
            ::= { zxAnEponOnuVersionUpdateStatusEntry 1 }

    zxAnEponOnuVersionUpdateAbortReason  OBJECT-TYPE
            SYNTAX      INTEGER {
                none(1),
                downloadError(2),
                downloadTimeout(3),
                onuReturnError(4),
                endDownloadCheckError(5),
                userAbort(6),
                onuOffLine(7)
                }
            MAX-ACCESS  read-only
            STATUS      current
            DESCRIPTION
                 "ONU version update abort reason."
            ::= { zxAnEponOnuVersionUpdateStatusEntry 2 }

    zxAnEponOnuVersionUpdateErrCode  OBJECT-TYPE
            SYNTAX      INTEGER
            MAX-ACCESS  read-only
            STATUS      current
            DESCRIPTION
                 "ONU version update error code."
            ::= { zxAnEponOnuVersionUpdateStatusEntry 3 }

    zxAnEponOnuVersionUpdateErrMsg  OBJECT-TYPE
            SYNTAX      DisplayString( SIZE ( 1 .. 128  ) )
            MAX-ACCESS  read-only
            STATUS      current
            DESCRIPTION
                 "ONU version update error message."
            ::= { zxAnEponOnuVersionUpdateStatusEntry 4 }

    zxAnEponOnuVersionUpdateProgress  OBJECT-TYPE
            SYNTAX      INTEGER(1..100)
            MAX-ACCESS  read-only
            STATUS      current
            DESCRIPTION
                 "ONU version update current percent."
            ::= { zxAnEponOnuVersionUpdateStatusEntry 5 }

    zxAnEponOnuCurrentUsedVersionName  OBJECT-TYPE
            SYNTAX      DisplayString
            MAX-ACCESS  read-only
            STATUS      current
            DESCRIPTION
                 "ONU current using version name."
            ::= { zxAnEponOnuVersionUpdateStatusEntry 6 }

    zxAnEponOnuCurrentUsedVersionTime  OBJECT-TYPE
            SYNTAX      DisplayString
            MAX-ACCESS  read-only
            STATUS      current
            DESCRIPTION
                 "ONU current using version time."
            ::= { zxAnEponOnuVersionUpdateStatusEntry 7 }

    zxAnEponOnuUpdatingVersionName  OBJECT-TYPE
            SYNTAX      DisplayString
            MAX-ACCESS  read-only
            STATUS      current
            DESCRIPTION
                 "ONU updating version name."
            ::= { zxAnEponOnuVersionUpdateStatusEntry 8 }

    zxAnEponOnuUpdatingVersionTime  OBJECT-TYPE
            SYNTAX      DisplayString
            MAX-ACCESS  read-only
            STATUS      current
            DESCRIPTION
                 "ONU updating version time."
            ::= { zxAnEponOnuVersionUpdateStatusEntry 9 }

--------------------------------------------------------------------------------
-- 1.49.4 ONU version action table
--------------------------------------------------------------------------------
    zxAnEponOnuVersionActionTable  OBJECT-TYPE
            SYNTAX      SEQUENCE OF ZxAnEponOnuVersionActionEntry
            MAX-ACCESS  not-accessible
            STATUS      current
            DESCRIPTION
                "EPON remote management ONU version action table."
            ::= {zxAnEponOnuVersionMgmt 4}

    zxAnEponOnuVersionActionEntry  OBJECT-TYPE
            SYNTAX      ZxAnEponOnuVersionActionEntry
            MAX-ACCESS  not-accessible
            STATUS      current
            DESCRIPTION
                "EPON remote management ONU version action entry."
            INDEX    { zxAnEponOnuIfIndex,zxAnEponOnuVersionImageIndex }
            ::= {zxAnEponOnuVersionActionTable 1}

    ZxAnEponOnuVersionActionEntry ::=
            SEQUENCE {
                zxAnEponOnuVersionImageIndex            INTEGER,
                zxAnEponOnuVersionImageAction           INTEGER,
                zxAnEponOnuVersionImageCommitState      INTEGER,
                zxAnEponOnuVersionImageActiveState      INTEGER,
                zxAnEponOnuVersionImageValidState       INTEGER
                }

    zxAnEponOnuVersionImageIndex  OBJECT-TYPE
            SYNTAX      INTEGER
            MAX-ACCESS  not-accessible
            STATUS      current
            DESCRIPTION
                 "ONU version image index."
            ::= { zxAnEponOnuVersionActionEntry 1 }

    zxAnEponOnuVersionImageAction  OBJECT-TYPE
            SYNTAX      INTEGER {
                activate(1),
                commit(2)
                }
            MAX-ACCESS  read-write
            STATUS      current
            DESCRIPTION
                 "ONU version image action type."
            ::= { zxAnEponOnuVersionActionEntry 2 }

    zxAnEponOnuVersionImageCommitState  OBJECT-TYPE
            SYNTAX      INTEGER {
                committed(1),
                notCommitted(2)
                }
            MAX-ACCESS  read-only
            STATUS      current
            DESCRIPTION
                 "ONU version image commit status."
            ::= { zxAnEponOnuVersionActionEntry 3 }

    zxAnEponOnuVersionImageActiveState  OBJECT-TYPE
            SYNTAX      INTEGER {
                actived(1),
                notActived(2)
                }
            MAX-ACCESS  read-only
            STATUS      current
            DESCRIPTION
                 "ONU version image active status."
            ::= { zxAnEponOnuVersionActionEntry 4 }

    zxAnEponOnuVersionImageValidState  OBJECT-TYPE
            SYNTAX      INTEGER {
                valid(1),
                notValid(2)
                }
            MAX-ACCESS  read-only
            STATUS      current
            DESCRIPTION
                 "ONU version image valid status."
            ::= { zxAnEponOnuVersionActionEntry 5 }

------------------------------------------------------------------------------
-- 1.50 EPON ONU PON MAC Shaping management(OAM)
------------------------------------------------------------------------------

    zxAnEponOnuPonMacShapingMgmt                OBJECT IDENTIFIER ::= { zxAnEponOnuExtendedAttrMgmt 50}

--------------------------------------------------------------------------------
-- 1.50.1 ONU PON MAC Shaping Attribute table
--------------------------------------------------------------------------------
    zxAnEponOnuPonMacShapingTable  OBJECT-TYPE
            SYNTAX      SEQUENCE OF ZxAnEponOnuPonMacShapingEntry
            MAX-ACCESS  not-accessible
            STATUS      current
            DESCRIPTION
                "EPON remote management ONU PON MAC Shaping attribute table."
            ::= {zxAnEponOnuPonMacShapingMgmt 1}

    zxAnEponOnuPonMacShapingEntry  OBJECT-TYPE
            SYNTAX      ZxAnEponOnuPonMacShapingEntry
            MAX-ACCESS  not-accessible
            STATUS      current
            DESCRIPTION
                "EPON remote management ONU PON MAC Shaping attribute entry."
            INDEX    { zxAnEponOnuIfIndex }
            ::= {zxAnEponOnuPonMacShapingTable 1}

    ZxAnEponOnuPonMacShapingEntry ::=
            SEQUENCE {
                zxAnEponOnuShappingAdminStatus          INTEGER,
                zxAnEponOnuShappingCir                  INTEGER,
                zxAnEponOnuShappingCbs                  INTEGER
                }

    zxAnEponOnuShappingAdminStatus  OBJECT-TYPE
            SYNTAX      INTEGER {
                enable(1),
                disable(2)
                }
            MAX-ACCESS  read-write
            STATUS      current
            DESCRIPTION
                 "It indicate ONU PON MAC shapping admin status.
                 enable  -- downstream rate limiting enable by shapping
                 disable -- downstream rate limiting disabled or restore the ONU default configuration"
            DEFVAL { disable }
            ::= { zxAnEponOnuPonMacShapingEntry 1 }

    zxAnEponOnuShappingCir  OBJECT-TYPE
            SYNTAX      INTEGER(0..16777215)
            MAX-ACCESS  read-write
            STATUS      current
            DESCRIPTION
                 "This parameter indicates the Downstream committed Information Rate. The parameter presents the rate in Kbps"
            ::= { zxAnEponOnuPonMacShapingEntry 2 }

    zxAnEponOnuShappingCbs  OBJECT-TYPE
            SYNTAX      INTEGER(1522..16777215)
            MAX-ACCESS  read-write
            STATUS      current
            DESCRIPTION
                 "This parameter identifies the depth of this token bucket to tolerant the certain burst. The unit of CBS is byte"
            ::= { zxAnEponOnuPonMacShapingEntry 3 }

--------------------------------------------------------------------------------
-- 1.50.2 ONU PON MAC Shaping Buffer table
--------------------------------------------------------------------------------
    zxAnEponOnuPonMacBufferTable  OBJECT-TYPE
            SYNTAX      SEQUENCE OF ZxAnEponOnuPonMacBufferEntry
            MAX-ACCESS  not-accessible
            STATUS      current
            DESCRIPTION
                "EPON remote management ONU PON MAC shaping buffer table."
            ::= {zxAnEponOnuPonMacShapingMgmt 2}

    zxAnEponOnuPonMacBufferEntry  OBJECT-TYPE
            SYNTAX      ZxAnEponOnuPonMacBufferEntry
            MAX-ACCESS  not-accessible
            STATUS      current
            DESCRIPTION
                "EPON remote management ONU PON MAC Shaping buffer entry."
            INDEX    { zxAnEponOnuIfIndex }
            ::= {zxAnEponOnuPonMacBufferTable 1}

    ZxAnEponOnuPonMacBufferEntry ::=
            SEQUENCE {
                zxAnEponOnuPonMacDsBufferAdminStatus    INTEGER,
                zxAnEponOnuPonMacDsBufferOperStatus     INTEGER,
                zxAnEponOnuPonMacDsConfBufferSize       INTEGER,
                zxAnEponOnuPonMacDsActBufferSize        INTEGER,
                zxAnEponOnuPonMacUsBufferAdminStatus    INTEGER,
                zxAnEponOnuPonMacUsBufferOperStatus     INTEGER,
                zxAnEponOnuPonMacUsConfBufferSize       INTEGER,
                zxAnEponOnuPonMacUsActBufferSize        INTEGER
                }

    zxAnEponOnuPonMacDsBufferAdminStatus  OBJECT-TYPE
            SYNTAX      INTEGER {
                enable(1),
                disable(2)
                }
            MAX-ACCESS  read-write
            STATUS      current
            DESCRIPTION
                 "It indicate ONU PON MAC shapping DS buffer admin status.
                 enable  -- buffer enabled
                 disable -- buffer disabled or restore the ONU default configuration"
            DEFVAL { disable }
            ::= { zxAnEponOnuPonMacBufferEntry 1 }

    zxAnEponOnuPonMacDsBufferOperStatus  OBJECT-TYPE
            SYNTAX      INTEGER {
                enable(1),
                disable(2)
                }
            MAX-ACCESS  read-only
            STATUS      current
            DESCRIPTION
                 "It indicate ONU PON MAC shapping DS buffer operation status.
                 enable  -- buffer enabled
                 disable -- buffer disabled or restore the ONU default configuration"
            ::= { zxAnEponOnuPonMacBufferEntry 2 }

    zxAnEponOnuPonMacDsConfBufferSize  OBJECT-TYPE
            SYNTAX      INTEGER
            MAX-ACCESS  read-write
            STATUS      current
            DESCRIPTION
                 "This parameter identifies the DS configuration buffer size. Unit in bytes."
            ::= { zxAnEponOnuPonMacBufferEntry 3 }

    zxAnEponOnuPonMacDsActBufferSize  OBJECT-TYPE
            SYNTAX      INTEGER
            MAX-ACCESS  read-only
            STATUS      current
            DESCRIPTION
                 "This parameter identifies the DS actual buffer size. Unit in bytes."
            ::= { zxAnEponOnuPonMacBufferEntry 4 }

    zxAnEponOnuPonMacUsBufferAdminStatus  OBJECT-TYPE
            SYNTAX      INTEGER {
                enable(1),
                disable(2)
                }
            MAX-ACCESS  read-write
            STATUS      current
            DESCRIPTION
                 "It indicate ONU PON MAC shapping US buffer admin status.
                 enable  -- buffer enabled
                 disable -- buffer disabled or restore the ONU default configuration"
            DEFVAL { disable }
            ::= { zxAnEponOnuPonMacBufferEntry 5 }

    zxAnEponOnuPonMacUsBufferOperStatus  OBJECT-TYPE
            SYNTAX      INTEGER {
                enable(1),
                disable(2)
                }
            MAX-ACCESS  read-only
            STATUS      current
            DESCRIPTION
                 "It indicate ONU PON MAC shapping US buffer operation status.
                 enable  -- buffer enabled
                 disable -- buffer disabled or restore the ONU default configuration"
            ::= { zxAnEponOnuPonMacBufferEntry 6 }

    zxAnEponOnuPonMacUsConfBufferSize  OBJECT-TYPE
            SYNTAX      INTEGER
            MAX-ACCESS  read-write
            STATUS      current
            DESCRIPTION
                 "This parameter identifies the US configuration buffer size. Unit in bytes."
            ::= { zxAnEponOnuPonMacBufferEntry 7 }

    zxAnEponOnuPonMacUsActBufferSize  OBJECT-TYPE
            SYNTAX      INTEGER
            MAX-ACCESS  read-only
            STATUS      current
            DESCRIPTION
                 "This parameter identifies the US actual buffer size. Unit in bytes."
            ::= { zxAnEponOnuPonMacBufferEntry 8 }

--------------------------------------------------------------------------------
-- 1.50.3 ONU PON MAC Shaping Buffer Capability  table
--------------------------------------------------------------------------------
    zxAnEponOnuPonMacBufferCapabilityTable  OBJECT-TYPE
            SYNTAX      SEQUENCE OF ZxAnEponOnuPonMacBufferCapabilityEntry
            MAX-ACCESS  not-accessible
            STATUS      current
            DESCRIPTION
                "EPON remote management ONU PON MAC shaping buffer capability table."
            ::= {zxAnEponOnuPonMacShapingMgmt 3}

    zxAnEponOnuPonMacBufferCapabilityEntry  OBJECT-TYPE
            SYNTAX      ZxAnEponOnuPonMacBufferCapabilityEntry
            MAX-ACCESS  not-accessible
            STATUS      current
            DESCRIPTION
                "EPON remote management ONU PON MAC Shaping buffer capability entry."
            INDEX    { zxAnEponOnuIfIndex }
            ::= {zxAnEponOnuPonMacBufferCapabilityTable 1}

    ZxAnEponOnuPonMacBufferCapabilityEntry ::=
            SEQUENCE {
                zxAnEponOnuPonMacBufferCapability       INTEGER,
                zxAnEponOnuPonMacMinDsBufferSize        INTEGER,
                zxAnEponOnuPonMacMaxDsBufferSize        INTEGER,
                zxAnEponOnuPonMacMinUsBufferSize        INTEGER,
                zxAnEponOnuPonMacMaxUsBufferSize        INTEGER
                }

    zxAnEponOnuPonMacBufferCapability  OBJECT-TYPE
            SYNTAX      INTEGER {
                enable(1),
                disable(2)
                }
            MAX-ACCESS  read-only
            STATUS      current
            DESCRIPTION
                 "It indicate ONU PON MAC shapping buffer capability.
                 enable  -- ONU support buffer management
                 disable -- ONU don't support buffer management"
            DEFVAL { disable }
            ::= { zxAnEponOnuPonMacBufferCapabilityEntry 1 }

    zxAnEponOnuPonMacMinDsBufferSize  OBJECT-TYPE
            SYNTAX      INTEGER
            MAX-ACCESS  read-only
            STATUS      current
            DESCRIPTION
                 "This parameter identifies the Minimum buffer size of DS direction. Unit in bytes."
            ::= { zxAnEponOnuPonMacBufferCapabilityEntry 2 }

    zxAnEponOnuPonMacMaxDsBufferSize  OBJECT-TYPE
            SYNTAX      INTEGER
            MAX-ACCESS  read-only
            STATUS      current
            DESCRIPTION
                 "This parameter identifies the Maximum buffer size of DS direction. Unit in bytes."
            ::= { zxAnEponOnuPonMacBufferCapabilityEntry 3 }

    zxAnEponOnuPonMacMinUsBufferSize  OBJECT-TYPE
            SYNTAX      INTEGER
            MAX-ACCESS  read-only
            STATUS      current
            DESCRIPTION
                 "This parameter identifies the Minimum buffer size of US direction. Unit in bytes."
            ::= { zxAnEponOnuPonMacBufferCapabilityEntry 4 }

    zxAnEponOnuPonMacMaxUsBufferSize  OBJECT-TYPE
            SYNTAX      INTEGER
            MAX-ACCESS  read-only
            STATUS      current
            DESCRIPTION
                 "This parameter identifies the Maximum buffer size of US direction. Unit in bytes."
            ::= { zxAnEponOnuPonMacBufferCapabilityEntry 5 }


------------------------------------------------------------------------------
-- 1.51 EPON ONU PON UNI MAC Table management(OAM)
------------------------------------------------------------------------------
    zxAnEponOnuUniMacTable  OBJECT-TYPE
            SYNTAX      SEQUENCE OF ZxAnEponOnuUniMacEntry
            MAX-ACCESS  not-accessible
            STATUS      current
            DESCRIPTION
                "EPON remote management ONU UNI MAC table."
            ::= {zxAnEponOnuExtendedAttrMgmt 51}

    zxAnEponOnuUniMacEntry  OBJECT-TYPE
            SYNTAX      ZxAnEponOnuUniMacEntry
            MAX-ACCESS  not-accessible
            STATUS      current
            DESCRIPTION
                "EPON remote management ONU UNI MAC entry."
            INDEX    { zxAnEponOnuIfIndex,zxAnEponOnuPortId,zxAnEponOnuUniVlanId, zxAnEponOnuUniMacSequenceNo}
            ::= {zxAnEponOnuUniMacTable 1}

    ZxAnEponOnuUniMacEntry ::=
            SEQUENCE {
                zxAnEponOnuUniVlanId                    INTEGER,
                zxAnEponOnuUniMacSequenceNo             INTEGER,
                zxAnEponOnuUniMacType                   INTEGER,
                zxAnEponOnuUniMacAddress                MacAddress
                }

    zxAnEponOnuUniVlanId  OBJECT-TYPE
            SYNTAX      INTEGER (1..4094)
            MAX-ACCESS  not-accessible
            STATUS      current
            DESCRIPTION
                 "The vlan id."
            ::= { zxAnEponOnuUniMacEntry 1 }

    zxAnEponOnuUniMacSequenceNo  OBJECT-TYPE
            SYNTAX      INTEGER
            MAX-ACCESS  not-accessible
            STATUS      current
            DESCRIPTION
                 "The MAC address table Sequence Number."
            ::= { zxAnEponOnuUniMacEntry 2 }

    zxAnEponOnuUniMacType  OBJECT-TYPE
            SYNTAX      INTEGER {
                dynamic(1),
                static(2)
                }
            MAX-ACCESS  read-only
            STATUS      current
            DESCRIPTION
                 "A MAC address type to forward and/or filter, such as dynamic or static MAC."
            ::= { zxAnEponOnuUniMacEntry 3 }

    zxAnEponOnuUniMacAddress  OBJECT-TYPE
            SYNTAX      MacAddress
            MAX-ACCESS  read-only
            STATUS      current
            DESCRIPTION
                 "A unicast MAC address for which the bridge has forwarding and/or filtering information."
            ::= { zxAnEponOnuUniMacEntry 4 }

------------------------------------------------------------------------------
--  2.zxAnEponOnuExtendedActionMgmt
------------------------------------------------------------------------------

    zxAnEponOnuActionTable OBJECT-TYPE
        SYNTAX       SEQUENCE OF ZxAnEponOnuActionEntry
        MAX-ACCESS   not-accessible
        STATUS       current
        DESCRIPTION
          "Update ONU parameters during run-time."
          ::= { zxAnEponOnuExtendedActionMgmt 1 }

    zxAnEponOnuActionEntry OBJECT-TYPE
        SYNTAX      ZxAnEponOnuActionEntry
        MAX-ACCESS  not-accessible
        STATUS      current
        DESCRIPTION " "
        INDEX   { zxAnEponOnuIfIndex}
        ::= { zxAnEponOnuActionTable 1 }

    ZxAnEponOnuActionEntry ::=
        SEQUENCE {
                zxAnEponOnuAction                INTEGER
                }

    zxAnEponOnuAction OBJECT-TYPE
        SYNTAX      INTEGER{
                      reset(1)
                    }
        MAX-ACCESS  read-write
        STATUS      current
        DESCRIPTION
                "Reset the ONU"
        ::= { zxAnEponOnuActionEntry 1}

    zxAnEponOnuSaveActionTable OBJECT-TYPE
        SYNTAX       SEQUENCE OF ZxAnEponOnuSaveActionEntry
        MAX-ACCESS   not-accessible
        STATUS       current
        DESCRIPTION
          "Save onu config action."
          ::= { zxAnEponOnuExtendedActionMgmt 2 }

    zxAnEponOnuSaveActionEntry OBJECT-TYPE
        SYNTAX      ZxAnEponOnuSaveActionEntry
        MAX-ACCESS  not-accessible
        STATUS      current
        DESCRIPTION " "
        INDEX   { zxAnEponOnuIfIndex}
        ::= { zxAnEponOnuSaveActionTable 1 }

    ZxAnEponOnuSaveActionEntry ::=
        SEQUENCE {
                zxAnEponOnuSaveAction                INTEGER
                }

    zxAnEponOnuSaveAction OBJECT-TYPE
        SYNTAX      INTEGER{
                      save(1),
                      clear(2),
                      restoreFactory(3)
                    }
        MAX-ACCESS  read-write
        STATUS      current
        DESCRIPTION
                "Remote ONU Action."
        ::= { zxAnEponOnuSaveActionEntry 1}


   --  Begjing HomeGateway

     zxAnEponOnuSetHGMACCodeTable OBJECT-TYPE
        SYNTAX       SEQUENCE OF ZxAnEponOnuSetHGMACCodeEntry
        MAX-ACCESS   not-accessible
        STATUS       current
        DESCRIPTION
          "Set onu Home Gateway Mac Code."
          ::= { zxAnEponOnuExtendedActionMgmt 3 }

    zxAnEponOnuSetHGMACCodeEntry OBJECT-TYPE
        SYNTAX      ZxAnEponOnuSetHGMACCodeEntry
        MAX-ACCESS  not-accessible
        STATUS      current
        DESCRIPTION " "
        INDEX   { zxAnEponOnuIfIndex}
        ::= { zxAnEponOnuSetHGMACCodeTable 1 }

    ZxAnEponOnuSetHGMACCodeEntry ::=
        SEQUENCE {
                 zxAnEponOnuHGMACCode         OCTET STRING
                }

    zxAnEponOnuHGMACCode OBJECT-TYPE
        SYNTAX      OCTET STRING
        MAX-ACCESS  read-write
        STATUS      current
        DESCRIPTION
                "Onu Home Gateway MAC Code"
        ::= { zxAnEponOnuSetHGMACCodeEntry 1}

     zxAnEponOnuHGMACVlanTable OBJECT-TYPE
        SYNTAX       SEQUENCE OF ZxAnEponOnuHGMACVlanEntry
        MAX-ACCESS   not-accessible
        STATUS       current
        DESCRIPTION
          "Set onu Home Gateway Vlan."
          ::= { zxAnEponOnuExtendedActionMgmt 4 }

    zxAnEponOnuHGMACVlanEntry OBJECT-TYPE
        SYNTAX      ZxAnEponOnuHGMACVlanEntry
        MAX-ACCESS  not-accessible
        STATUS      current
        DESCRIPTION " "
        INDEX   { zxAnEponOnuIfIndex}
        ::= { zxAnEponOnuHGMACVlanTable 1 }

    ZxAnEponOnuHGMACVlanEntry ::=
        SEQUENCE {
                 zxAnEponOnuHGVlan         INTEGER
                }

    zxAnEponOnuHGVlan OBJECT-TYPE
        SYNTAX      INTEGER(1..4094)
        MAX-ACCESS  read-write
        STATUS      current
        DESCRIPTION
                "Onu Home Gateway MAC Vlan"
        ::= { zxAnEponOnuHGMACVlanEntry 1}

   zxAnEponOnuHGStateTable OBJECT-TYPE
        SYNTAX       SEQUENCE OF ZxAnEponOnuHGStateEntry
        MAX-ACCESS   not-accessible
        STATUS       current
        DESCRIPTION
          "ONU Home Gateway state."
          ::= { zxAnEponOnuExtendedActionMgmt 5 }

    zxAnEponOnuHGStateEntry OBJECT-TYPE
        SYNTAX      ZxAnEponOnuHGStateEntry
        MAX-ACCESS  not-accessible
        STATUS      current
        DESCRIPTION " "
        INDEX       { zxAnEponOnuIfIndex,zxAnEponOnuPortId }
        ::= { zxAnEponOnuHGStateTable 1 }

    ZxAnEponOnuHGStateEntry ::=
        SEQUENCE {
                zxAnEponOnuHGMAC    MacAddress,
                zxEponOnuHGState          INTEGER
                }

    zxAnEponOnuHGMAC OBJECT-TYPE
        SYNTAX      MacAddress
        MAX-ACCESS  read-write
        STATUS      current
        DESCRIPTION
                ""
        ::= { zxAnEponOnuHGStateEntry 1}

    zxEponOnuHGState  OBJECT-TYPE
        SYNTAX      INTEGER(0..1)
        MAX-ACCESS  read-write
        STATUS      current
        DESCRIPTION
                ""
        ::= { zxAnEponOnuHGStateEntry 2 }



 ------------------------------------------------------------------------------
--  3.zxAnEponOnuStdAttrMgmt
------------------------------------------------------------------------------

    zxAnEponOnuPhyMgmtTable OBJECT-TYPE
        SYNTAX       SEQUENCE OF ZxAnEponOnuPhyMgmtEntry
        MAX-ACCESS   not-accessible
        STATUS       current
        DESCRIPTION
          "ONU PHY entity managed object table."
          ::= { zxAnEponOnuStdAttrMgmt 1 }

    zxAnEponOnuPhyMgmtEntry OBJECT-TYPE
        SYNTAX      ZxAnEponOnuPhyMgmtEntry
        MAX-ACCESS  not-accessible
        STATUS      current
        DESCRIPTION ""
        INDEX       { zxAnEponOnuIfIndex,zxAnEponOnuPortId}
        ::= { zxAnEponOnuPhyMgmtTable 1 }

    ZxAnEponOnuPhyMgmtEntry ::=
        SEQUENCE {
                zxAnEponOnuPhyAdminState         INTEGER
                }

    zxAnEponOnuPhyAdminState OBJECT-TYPE
        SYNTAX     INTEGER{
                    disabled(1),
                    enabled(2)}
        MAX-ACCESS  read-write
        STATUS      current
        DESCRIPTION
                "The ONU PHY admin state."
        DEFVAL  {disabled}
        ::= { zxAnEponOnuPhyMgmtEntry 1}

    zxAnEponOnuAutoNegAttrTable OBJECT-TYPE
        SYNTAX       SEQUENCE OF ZxAnEponOnuAutoNegAttrEntry
        MAX-ACCESS   not-accessible
        STATUS       current
        DESCRIPTION
          "ONU port autonegotiation entity managed object table."
          ::= { zxAnEponOnuStdAttrMgmt 2 }

    zxAnEponOnuAutoNegAttrEntry OBJECT-TYPE
        SYNTAX      ZxAnEponOnuAutoNegAttrEntry
        MAX-ACCESS  not-accessible
        STATUS      current
        DESCRIPTION " "
        INDEX       { zxAnEponOnuIfIndex,zxAnEponOnuPortId}
        ::= { zxAnEponOnuAutoNegAttrTable 1 }

    ZxAnEponOnuAutoNegAttrEntry ::=
        SEQUENCE {
                zxAnEponOnuAutoNegAdminState          INTEGER,
                zxAnEponOnuAutoNegCapability          BITS,
                zxAnEponOnuAutoNegCapAdvertised       BITS,
                zxAnEponOnuEthIfConfDuplexSpeed       INTEGER,
                zxAnEponOnuEthIfActualDuplex          INTEGER,
                zxAnEponOnuEthIfActualSpeed           INTEGER
                }

    zxAnEponOnuAutoNegAdminState    OBJECT-TYPE
        SYNTAX     INTEGER{
                    disabled(1),
                    enabled(2)}
        MAX-ACCESS  read-write
        STATUS      current
        DESCRIPTION
                "Setting this object to enabled(2) will cause
                      the interface which has the auto-negotiation
                      signaling ability to be enabled."
        DEFVAL  {enabled}
        ::= { zxAnEponOnuAutoNegAttrEntry 1}

    zxAnEponOnuAutoNegCapability OBJECT-TYPE
        SYNTAX      BITS{
                     zx-GLOBAL(0),
                     zx-OTHER(1),
                     zx-UNKNOWN(2),
                     zx-10BASE-T(3),
                     zx-10BASE-TFD(4),
                     zx-100BASE-T4(5),
                     zx-100BASE-TX(6),
                     zx-100BASE-TXFD(7),
                     zx-FDX-PAUSE(8),
                     zx-FDX-APAUSE(9),
                     zx-FDX-SPAUSE(10),
                     zx-FDX-BPAUSE(11),
                     zx-100BASE-T2(12),
                     zx-100BASE-T2FD(13),
                     zx-1000BASE-X(14),
                     zx-1000BASE-XFD(15),
                     zx-1000BASE-T(16),
                     zx-1000BASE-TFD(17),
                     zx-REM-FAULT1(18),
                     zx-REM-FAULT2(19),
                     zx-ISO-ETHERNET(20)
                    }
        MAX-ACCESS  read-only
        STATUS      current
        DESCRIPTION
                ""
        ::= { zxAnEponOnuAutoNegAttrEntry 2}

    zxAnEponOnuAutoNegCapAdvertised OBJECT-TYPE
        SYNTAX      BITS{
                     zx-GLOBAL(0),
                     zx-OTHER(1),
                     zx-UNKNOWN(2),
                     zx-10BASE-T(3),
                     zx-10BASE-TFD(4),
                     zx-100BASE-T4(5),
                     zx-100BASE-TX(6),
                     zx-100BASE-TXFD(7),
                     zx-FDX-PAUSE(8),
                     zx-FDX-APAUSE(9),
                     zx-FDX-SPAUSE(10),
                     zx-FDX-BPAUSE(11),
                     zx-100BASE-T2(12),
                     zx-100BASE-T2FD(13),
                     zx-1000BASE-X(14),
                     zx-1000BASE-XFD(15),
                     zx-1000BASE-T(16),
                     zx-1000BASE-TFD(17),
                     zx-REM-FAULT1(18),
                     zx-REM-FAULT2(19),
                     zx-ISO-ETHERNET(20)
                    }
        MAX-ACCESS  read-only
        STATUS      current
        DESCRIPTION
                ""
        ::= { zxAnEponOnuAutoNegAttrEntry 3}

    zxAnEponOnuEthIfConfDuplexSpeed OBJECT-TYPE
        SYNTAX          INTEGER
        {
             auto-negotiate(1),
             half-10(2), -- 10M-half
             full-10(3), -- 10M-full
             half-100(4),-- 100M-half
             full-100(5),-- 100M-full
             full-1000(6),-- 1000M-full
             full-10000(7),-- 10000M-full
             illegal(99)
        }
        MAX-ACCESS      read-write
        STATUS          current
        DESCRIPTION
            "DURABLE: { auto_negotiate:all }
            The desired speed and duplex for this interface. If the selected
            control is not possible on the interface, a value of illegal(99)
            is returned.  If the port type does NOT support the default
            of auto_negotiate(1), then the application initializes the
            port to a valid value (e.g., 1000full(6)).  Note that not all
            controls are possible for all interfaces.  For example, only
            full-1000(6) is available for Gigabit Ethernet interfaces."
        ::= { zxAnEponOnuAutoNegAttrEntry 4 }

    zxAnEponOnuEthIfActualDuplex OBJECT-TYPE
        SYNTAX          INTEGER
        {
             auto-negotiate(1),
             half(2),
             full(3)
        }
        MAX-ACCESS      read-only
        STATUS          current
        DESCRIPTION
            "The actual duplex for this interface. "
        ::= { zxAnEponOnuAutoNegAttrEntry 5 }


    zxAnEponOnuEthIfActualSpeed OBJECT-TYPE
        SYNTAX          INTEGER
        {
             speed-10(1),
             speed-100(2),
             speed-1000(3),
             speed-10000(4),
             auto-speed(5)
        }
        MAX-ACCESS      read-only
        STATUS          current
        DESCRIPTION
            "The actual speed for this interface. "
        ::= { zxAnEponOnuAutoNegAttrEntry 6 }



    zxAnEponOnuFecMgmtTable OBJECT-TYPE
        SYNTAX       SEQUENCE OF ZxAnEponOnuFecMgmtEntry
        MAX-ACCESS   not-accessible
        STATUS       current
        DESCRIPTION
          "ONU PHY entity managed object table."
          ::= { zxAnEponOnuStdAttrMgmt 3 }

    zxAnEponOnuFecMgmtEntry OBJECT-TYPE
        SYNTAX      ZxAnEponOnuFecMgmtEntry
        MAX-ACCESS  not-accessible
        STATUS      current
        DESCRIPTION ""
        INDEX       { zxAnEponOnuIfIndex}
        ::= { zxAnEponOnuFecMgmtTable 1 }

    ZxAnEponOnuFecMgmtEntry ::=
        SEQUENCE {
                zxAnEponOnuFecAbility         INTEGER,
                zxAnEponOnuFecMode            INTEGER
                }

    zxAnEponOnuFecAbility OBJECT-TYPE
        SYNTAX      INTEGER{
                    unknown(1),
                    supported(2),
                    notsupported(3)
                   }
        MAX-ACCESS  read-only
        STATUS      current
        DESCRIPTION
                "A read-only value that indicates the if the 1000BASE-PX PHY supports the optional FEC
                Sublayer for forward error correction."
        ::= { zxAnEponOnuFecMgmtEntry 1}

    zxAnEponOnuFecMode OBJECT-TYPE
        SYNTAX      INTEGER{
                    unknown(1),
                    enabled(2),
                    disabled(3)
                   }
        MAX-ACCESS  read-write
        STATUS      current
        DESCRIPTION
                "A read-write value that indicates the mode of operation of the 1000BASE-PX PHY optional FEC
                Sublayer for Forward error correction."
        DEFVAL  {disabled}
        ::= { zxAnEponOnuFecMgmtEntry 2}

 ------------------------------------------------------------------------------
--  4.zxAnEponOnuStdActionMgmt
------------------------------------------------------------------------------
    zxAnEponOnuAutoNegActionTable OBJECT-TYPE
        SYNTAX       SEQUENCE OF ZxAnEponOnuAutoNegActionEntry
        MAX-ACCESS   not-accessible
        STATUS       current
        DESCRIPTION
          "ONU PHY entity managed object table."
          ::= { zxAnEponOnuStdActionMgmt 1 }

    zxAnEponOnuAutoNegActionEntry OBJECT-TYPE
        SYNTAX      ZxAnEponOnuAutoNegActionEntry
        MAX-ACCESS  not-accessible
        STATUS      current
        DESCRIPTION ""
        INDEX       { zxAnEponOnuIfIndex,zxAnEponOnuPortId}
        ::= { zxAnEponOnuAutoNegActionTable 1 }

    ZxAnEponOnuAutoNegActionEntry ::=
        SEQUENCE {
                zxAnEponOnuAutoNegAction         INTEGER
                }

    zxAnEponOnuAutoNegAction OBJECT-TYPE
        SYNTAX      INTEGER{
                      restart(1)
                    }
        MAX-ACCESS  read-write
        STATUS      current
        DESCRIPTION
                ""
        ::= { zxAnEponOnuAutoNegActionEntry 1}

------------------------------------------------------------------------------
--  5.zxAnEponOnuDbaAttrMgmt
------------------------------------------------------------------------------

    zxAnEponOnuDbaQueueThresholdsTable OBJECT-TYPE
        SYNTAX       SEQUENCE OF ZxAnEponOnuDbaQueueThresholdsEntry
        MAX-ACCESS   not-accessible
        STATUS       current
        DESCRIPTION
          "ONU DBA managed object table."
          ::= { zxAnEponOnuDbaAttrMgmt 1 }

    zxAnEponOnuDbaQueueThresholdsEntry OBJECT-TYPE
        SYNTAX      ZxAnEponOnuDbaQueueThresholdsEntry
        MAX-ACCESS  not-accessible
        STATUS      current
        DESCRIPTION ""
        INDEX       { zxAnEponOnuIfIndex,zxAnEponOnuDbaQueueSetIndex}
        ::= { zxAnEponOnuDbaQueueThresholdsTable 1 }

    ZxAnEponOnuDbaQueueThresholdsEntry ::=
        SEQUENCE {
                zxAnEponOnuDbaQueueSetIndex                  INTEGER,
                zxAnEponOnuDbaQueueThresholds1               INTEGER,
                zxAnEponOnuDbaQueueThresholds2               INTEGER,
                zxAnEponOnuDbaQueueThresholds3               INTEGER,
                zxAnEponOnuDbaQueueThresholds4               INTEGER,
                zxAnEponOnuDbaQueueThresholds5               INTEGER,
                zxAnEponOnuDbaQueueThresholds6               INTEGER,
                zxAnEponOnuDbaQueueThresholds7               INTEGER,
                zxAnEponOnuDbaQueueThresholds8               INTEGER
                }

    zxAnEponOnuDbaQueueSetIndex OBJECT-TYPE
        SYNTAX     INTEGER(1..3)
        MAX-ACCESS  not-accessible
        STATUS      current
        DESCRIPTION
                ""
        ::= { zxAnEponOnuDbaQueueThresholdsEntry 1}

    zxAnEponOnuDbaQueueThresholds1 OBJECT-TYPE
        SYNTAX     INTEGER
        MAX-ACCESS  read-write
        STATUS      current
        DESCRIPTION
                ""
        ::= { zxAnEponOnuDbaQueueThresholdsEntry 2}

    zxAnEponOnuDbaQueueThresholds2 OBJECT-TYPE
        SYNTAX     INTEGER
        MAX-ACCESS  read-write
        STATUS      current
        DESCRIPTION
                ""
        ::= { zxAnEponOnuDbaQueueThresholdsEntry 3}

    zxAnEponOnuDbaQueueThresholds3 OBJECT-TYPE
        SYNTAX     INTEGER
        MAX-ACCESS  read-write
        STATUS      current
        DESCRIPTION
                ""
        ::= { zxAnEponOnuDbaQueueThresholdsEntry 4}

    zxAnEponOnuDbaQueueThresholds4 OBJECT-TYPE
        SYNTAX     INTEGER
        MAX-ACCESS  read-write
        STATUS      current
        DESCRIPTION
                ""
        ::= { zxAnEponOnuDbaQueueThresholdsEntry 5}

    zxAnEponOnuDbaQueueThresholds5 OBJECT-TYPE
        SYNTAX     INTEGER
        MAX-ACCESS  read-write
        STATUS      current
        DESCRIPTION
                ""
        ::= { zxAnEponOnuDbaQueueThresholdsEntry 6}

    zxAnEponOnuDbaQueueThresholds6 OBJECT-TYPE
        SYNTAX     INTEGER
        MAX-ACCESS  read-write
        STATUS      current
        DESCRIPTION
                ""
        ::= { zxAnEponOnuDbaQueueThresholdsEntry 7}

    zxAnEponOnuDbaQueueThresholds7 OBJECT-TYPE
        SYNTAX     INTEGER
        MAX-ACCESS  read-write
        STATUS      current
        DESCRIPTION
                ""
        ::= { zxAnEponOnuDbaQueueThresholdsEntry 8}

    zxAnEponOnuDbaQueueThresholds8 OBJECT-TYPE
        SYNTAX     INTEGER
        MAX-ACCESS  read-write
        STATUS      current
        DESCRIPTION
                ""
        ::= { zxAnEponOnuDbaQueueThresholdsEntry 9}

    zxAnEponOnuDbaQueueSetActiveTable OBJECT-TYPE
        SYNTAX       SEQUENCE OF ZxAnEponOnuDbaQueueSetActiveEntry
        MAX-ACCESS   not-accessible
        STATUS       current
        DESCRIPTION
          "Active ONU DBA queueSet table."
          ::= { zxAnEponOnuDbaAttrMgmt 2 }

    zxAnEponOnuDbaQueueSetActiveEntry OBJECT-TYPE
        SYNTAX      ZxAnEponOnuDbaQueueSetActiveEntry
        MAX-ACCESS  not-accessible
        STATUS      current
        DESCRIPTION ""
        INDEX       { zxAnEponOnuIfIndex }
        ::= { zxAnEponOnuDbaQueueSetActiveTable 1 }

    ZxAnEponOnuDbaQueueSetActiveEntry ::=
        SEQUENCE {
                  zxAnEponOnuDbaQueueSetList                  OCTET STRING
                }

    zxAnEponOnuDbaQueueSetList OBJECT-TYPE
        SYNTAX      OCTET STRING
        MAX-ACCESS  read-write
        STATUS      current
        DESCRIPTION
                ""
        ::= { zxAnEponOnuDbaQueueSetActiveEntry 1}

------------------------------------------------------------------------------
--  6.zxAnEponOnuProfileMgmt
------------------------------------------------------------------------------
    zxAnEponOnuProfileIndexNextTable OBJECT-TYPE
        SYNTAX       SEQUENCE OF ZxAnEponOnuProfileIndexNextEntry
        MAX-ACCESS   not-accessible
        STATUS       current
        DESCRIPTION
          "ONU DBA managed object table."
          ::= { zxAnEponOnuProfileMgmt 1 }

    zxAnEponOnuProfileIndexNextEntry OBJECT-TYPE
        SYNTAX      ZxAnEponOnuProfileIndexNextEntry
        MAX-ACCESS  not-accessible
        STATUS      current
        DESCRIPTION ""
        INDEX       { zxAnEponOnuIfIndex }
        ::= { zxAnEponOnuProfileIndexNextTable 1 }

    ZxAnEponOnuProfileIndexNextEntry ::=
        SEQUENCE {
                zxAnEponOnuClassMarkingConditionIdNext                  INTEGER,
                zxAnEponOnuClassMarkingRuleIdNext                       INTEGER
                }

   zxAnEponOnuClassMarkingConditionIdNext OBJECT-TYPE
        SYNTAX            INTEGER
        MAX-ACCESS        read-only
        STATUS            current
        DESCRIPTION
            "This object contains the value to be used for
            zxAnEponOnuClassMarkingConditionId when creating entries in the
            zxAnEponOnuClassMarkingConditionTable. The value 0 indicates that no
            unassigned entries are available.  To obtain the
            value of zxAnEponOnuClassMarkingConditionIdNext for a new entry in the
            zxAnEponOnuClassMarkingConditionTable, the manager issues a management
            protocol retrieval operation. The agent will
            determine through its local policy when this
            index value will be made available for reuse."
        ::= { zxAnEponOnuProfileIndexNextEntry 1 }

  zxAnEponOnuClassMarkingRuleIdNext OBJECT-TYPE
       SYNTAX            INTEGER
       MAX-ACCESS        read-only
       STATUS            current
       DESCRIPTION
            "This object contains the value to be used for
            zxAnEponOnuClassMarkingRuleId when creating entries in the
            zxAnEponOnuClassMarkingRuleTable. The value 0 indicates that no
            unassigned entries are available.  To obtain the
            value of zxAnEponOnuClassMarkingRuleIdNext for a new entry in the
            zxAnEponOnuClassMarkingRuleTable, the manager issues a management
            protocol retrieval operation. The agent will
            determine through its local policy when this
            index value will be made available for reuse."
        ::= { zxAnEponOnuProfileIndexNextEntry 2 }

------------------------------------------------------------------------------
--  7.zxAnEponOnuPfmncStatis
------------------------------------------------------------------------------
  zxAnEponOnuPfmncStatisTable OBJECT-TYPE
        SYNTAX       SEQUENCE OF ZxAnEponOnuPfmncStatisEntry
        MAX-ACCESS   not-accessible
        STATUS       current
        DESCRIPTION
          "ONU DBA managed object table."
          ::= { zxAnEponOnuPfmncStatis 1 }

    zxAnEponOnuPfmncStatisEntry OBJECT-TYPE
        SYNTAX      ZxAnEponOnuPfmncStatisEntry
        MAX-ACCESS  not-accessible
        STATUS      current
        DESCRIPTION ""
        INDEX       { zxAnEponOnuIfIndex, zxAnEponOnuPortId, portType }
        ::= { zxAnEponOnuPfmncStatisTable 1 }

    ZxAnEponOnuPfmncStatisEntry ::=
        SEQUENCE {
                portType    INTEGER,
                parameter1  Counter64,
                parameter2  Counter64,
                      parameter3  Counter64,
                      parameter4  Counter64,
                      parameter5  Counter64,
                      parameter6  Counter64,
                parameter7  Counter64,
                      parameter8  Counter64,
                      parameter9  Counter64,
                      parameter10  Counter64,
                      parameter11  Counter64,
                      parameter12  Counter64,
                      parameter13  Counter64
                }

    portType  OBJECT-TYPE
        SYNTAX      INTEGER
        MAX-ACCESS  not-accessible
        STATUS      current
        DESCRIPTION
                "0: ether port"
        DEFVAL { 0 }
        ::= { zxAnEponOnuPfmncStatisEntry 1}

    parameter1 OBJECT-TYPE
        SYNTAX      Counter64
        MAX-ACCESS  read-only
        STATUS      current
        DESCRIPTION
                ""
        ::= { zxAnEponOnuPfmncStatisEntry 2}

    parameter2 OBJECT-TYPE
        SYNTAX      Counter64
        MAX-ACCESS  read-only
        STATUS      current
        DESCRIPTION
                ""
        ::= { zxAnEponOnuPfmncStatisEntry 3 }


    parameter3 OBJECT-TYPE
        SYNTAX      Counter64
        MAX-ACCESS  read-only
        STATUS      current
        DESCRIPTION
                ""
        ::= { zxAnEponOnuPfmncStatisEntry 4 }


    parameter4 OBJECT-TYPE
        SYNTAX      Counter64
        MAX-ACCESS  read-only
        STATUS      current
        DESCRIPTION
                ""
        ::= { zxAnEponOnuPfmncStatisEntry 5 }

    parameter5 OBJECT-TYPE
        SYNTAX      Counter64
        MAX-ACCESS  read-only
        STATUS      current
        DESCRIPTION
                ""
        ::= { zxAnEponOnuPfmncStatisEntry 6 }

    parameter6 OBJECT-TYPE
        SYNTAX      Counter64
        MAX-ACCESS  read-only
        STATUS      current
        DESCRIPTION
                ""
        ::= { zxAnEponOnuPfmncStatisEntry 7 }

    parameter7 OBJECT-TYPE
        SYNTAX      Counter64
        MAX-ACCESS  read-only
        STATUS      current
        DESCRIPTION
                ""
        ::= { zxAnEponOnuPfmncStatisEntry 8 }

    parameter8 OBJECT-TYPE
        SYNTAX      Counter64
        MAX-ACCESS  read-only
        STATUS      current
        DESCRIPTION
                ""
        ::= { zxAnEponOnuPfmncStatisEntry 9 }

    parameter9 OBJECT-TYPE
        SYNTAX      Counter64
        MAX-ACCESS  read-only
        STATUS      current
        DESCRIPTION
                ""
        ::= { zxAnEponOnuPfmncStatisEntry 10 }

    parameter10 OBJECT-TYPE
        SYNTAX      Counter64
        MAX-ACCESS  read-only
        STATUS      current
        DESCRIPTION
                ""
        ::= { zxAnEponOnuPfmncStatisEntry 11 }

    parameter11 OBJECT-TYPE
        SYNTAX      Counter64
        MAX-ACCESS  read-only
        STATUS      current
        DESCRIPTION
                ""
        ::= { zxAnEponOnuPfmncStatisEntry 12 }

    parameter12 OBJECT-TYPE
        SYNTAX      Counter64
        MAX-ACCESS  read-only
        STATUS      current
        DESCRIPTION
                ""
        ::= { zxAnEponOnuPfmncStatisEntry 13 }

    parameter13 OBJECT-TYPE
        SYNTAX      Counter64
        MAX-ACCESS  read-only
        STATUS      current
        DESCRIPTION
                ""
        ::= { zxAnEponOnuPfmncStatisEntry 14 }

-------------------------------------------------------------------------------
--  zxAnEponRmPerfConfTable
-------------------------------------------------------------------------------

    zxAnEponRmPerfConfTable OBJECT-TYPE
        SYNTAX       SEQUENCE OF ZxAnEponRmPerfConfEntry
        MAX-ACCESS   not-accessible
        STATUS       current
        DESCRIPTION
          "EPON remote ONU performance configuration table."
          ::= { zxAnEponOnuPfmncStatis 2 }

    zxAnEponRmPerfConfEntry OBJECT-TYPE
        SYNTAX      ZxAnEponRmPerfConfEntry
        MAX-ACCESS  not-accessible
        STATUS      current
        DESCRIPTION "EPON remote ONU performance configuration entry."
        INDEX       { zxAnEponOnuIfIndex, zxAnEponRmPerfOnuPortType,
                      zxAnEponOnuPortId }
        ::= { zxAnEponRmPerfConfTable 1 }

    ZxAnEponRmPerfConfEntry ::= SEQUENCE {
            zxAnEponRmPerfOnuPortType          INTEGER,
            zxAnEponRmPerfOnuHisStatInterval   Integer32,
            zxAnEponRmPerfConfRowStatus        RowStatus
            }

    zxAnEponRmPerfOnuPortType OBJECT-TYPE
        SYNTAX      INTEGER{
                    ponPort(1),
                    ethPort(2)
                    }
        MAX-ACCESS  not-accessible
        STATUS      current
        DESCRIPTION
        "ONU port type. Query zxAnEponOnuPonPorts value as the upper limit of
        zxAnEponOnuPortId if zxAnEponRmPerfOnuPortType is ponPort(1),
        and zxAnEponOnuPortId range is [0,zxAnEponOnuPortId). Query ethernet
        port number from ONU type profile as zxAnEponOnuPortId maximum
        value and zxAnEponOnuPortId range is [1, ethernet port number] if
        zxAnEponRmPerfOnuPortType is ethPort(2)."
        ::= { zxAnEponRmPerfConfEntry 1}

    zxAnEponRmPerfOnuHisStatInterval  OBJECT-TYPE
        SYNTAX      Integer32(1..2147483647)
        UNITS       "Seconds"
        MAX-ACCESS  read-create
        STATUS      current
        DESCRIPTION
        "History performance statistics interval of ONU."
        DEFVAL { 900 }
        ::= { zxAnEponRmPerfConfEntry 2 }

    zxAnEponRmPerfConfRowStatus  OBJECT-TYPE
        SYNTAX      RowStatus
        MAX-ACCESS  read-create
        STATUS      current
        DESCRIPTION
        "The status of this conceptual row.
         Table zxAnEponRmEthCurPerfTable and zxAnEponRmEthHisPerfTable
         controlled by this attribute at the same time.

         The supported actions of this conceptual row only include:
         'createAndGo' and 'destroy'.

         To create a row in this table, a manager must
         set this object to createAndGo(4).

         To delete a row in this table, a manager must
         set this object to destroy(6).

         To query this object, always return 1."
        ::= { zxAnEponRmPerfConfEntry 50 }

-------------------------------------------------------------------------------
--  zxAnEponRmEthCurPerfTable
-------------------------------------------------------------------------------
    zxAnEponRmEthCurPerfTable OBJECT-TYPE
        SYNTAX       SEQUENCE OF ZxAnEponRmEthCurPerfEntry
        MAX-ACCESS   not-accessible
        STATUS       current
        DESCRIPTION
        "EPON remote ONU ethernet current performance statistics table."
        ::= { zxAnEponOnuPfmncStatis 3 }

    zxAnEponRmEthCurPerfEntry OBJECT-TYPE
        SYNTAX      ZxAnEponRmEthCurPerfEntry
        MAX-ACCESS  not-accessible
        STATUS      current
        DESCRIPTION
        "EPON remote ONU ethernet current performance statistics entry."
        INDEX       { zxAnEponOnuIfIndex, zxAnEponRmPerfOnuPortType,
                      zxAnEponOnuPortId }
        ::= { zxAnEponRmEthCurPerfTable 1 }

    ZxAnEponRmEthCurPerfEntry ::= SEQUENCE {
            zxAnEponRmCurDsDropEvents          Counter64,
            zxAnEponRmCurDsOctets              Counter64,
            zxAnEponRmCurDsPkts                Counter64,
            zxAnEponRmCurDsBcastPkts           Counter64,
            zxAnEponRmCurDsMcastPkts           Counter64,
            zxAnEponRmCurDsCrcErrPkts          Counter64,
            zxAnEponRmCurDsUndersizePkts       Counter64,
            zxAnEponRmCurDsOversizePkts        Counter64,
            zxAnEponRmCurDsFragments           Counter64,
            zxAnEponRmCurDsJabbers             Counter64,
            zxAnEponRmCurDsPkts64Octets        Counter64,
            zxAnEponRmCurDs65To127Octets       Counter64,
            zxAnEponRmCurDs128To255Octets      Counter64,
            zxAnEponRmCurDs256To511Octets      Counter64,
            zxAnEponRmCurDs512To1023Octets     Counter64,
            zxAnEponRmCurDs1024To1518Octets    Counter64,
            zxAnEponRmCurDsDiscards            Counter64,
            zxAnEponRmCurDsErrors              Counter64,
            zxAnEponRmCurUsDropEvents          Counter64,
            zxAnEponRmCurUsOctets              Counter64,
            zxAnEponRmCurUsPkts                Counter64,
            zxAnEponRmCurUsBcastPkts           Counter64,
            zxAnEponRmCurUsMcastPkts           Counter64,
            zxAnEponRmCurUsCrcErrPkts          Counter64,
            zxAnEponRmCurUsUndersizePkts       Counter64,
            zxAnEponRmCurUsOversizePkts        Counter64,
            zxAnEponRmCurUsFragments           Counter64,
            zxAnEponRmCurUsJabbers             Counter64,
            zxAnEponRmCurUsPkts64Octets        Counter64,
            zxAnEponRmCurUs65To127Octets       Counter64,
            zxAnEponRmCurUs128To255Octets      Counter64,
            zxAnEponRmCurUs256To511Octets      Counter64,
            zxAnEponRmCurUs512To1023Octets     Counter64,
            zxAnEponRmCurUs1024To1518Octets    Counter64,
            zxAnEponRmCurUsDiscards            Counter64,
            zxAnEponRmCurUsErrors              Counter64,
            zxAnEponRmCurPortStatusChanges     Counter64
            }

    zxAnEponRmCurDsDropEvents OBJECT-TYPE
        SYNTAX      Counter64
        MAX-ACCESS  read-only
        STATUS      current
        DESCRIPTION
        "Downstream dropped events."
        ::= { zxAnEponRmEthCurPerfEntry 1}

    zxAnEponRmCurDsOctets OBJECT-TYPE
        SYNTAX      Counter64
        MAX-ACCESS  read-only
        STATUS      current
        DESCRIPTION
        "Downstream octets."
        ::= { zxAnEponRmEthCurPerfEntry 2}

    zxAnEponRmCurDsPkts OBJECT-TYPE
        SYNTAX      Counter64
        MAX-ACCESS  read-only
        STATUS      current
        DESCRIPTION
        "Downstream packets."
        ::= { zxAnEponRmEthCurPerfEntry 3}

    zxAnEponRmCurDsBcastPkts OBJECT-TYPE
        SYNTAX      Counter64
        MAX-ACCESS  read-only
        STATUS      current
        DESCRIPTION
        "Downstream broadcast packets."
        ::= { zxAnEponRmEthCurPerfEntry 4}

    zxAnEponRmCurDsMcastPkts OBJECT-TYPE
        SYNTAX      Counter64
        MAX-ACCESS  read-only
        STATUS      current
        DESCRIPTION
        "Downstream multicast packets."
        ::= { zxAnEponRmEthCurPerfEntry 5}

    zxAnEponRmCurDsCrcErrPkts OBJECT-TYPE
        SYNTAX      Counter64
        MAX-ACCESS  read-only
        STATUS      current
        DESCRIPTION
        "Downstream CRC errored packets."
        ::= { zxAnEponRmEthCurPerfEntry 6}

    zxAnEponRmCurDsUndersizePkts OBJECT-TYPE
        SYNTAX      Counter64
        MAX-ACCESS  read-only
        STATUS      current
        DESCRIPTION
        "Downstream undersize packets."
        ::= { zxAnEponRmEthCurPerfEntry 7}

    zxAnEponRmCurDsOversizePkts OBJECT-TYPE
        SYNTAX      Counter64
        MAX-ACCESS  read-only
        STATUS      current
        DESCRIPTION
        "Downstream oversize packets."
        ::= { zxAnEponRmEthCurPerfEntry 8}

    zxAnEponRmCurDsFragments OBJECT-TYPE
        SYNTAX      Counter64
        MAX-ACCESS  read-only
        STATUS      current
        DESCRIPTION
        "Downstream fragments."
        ::= { zxAnEponRmEthCurPerfEntry 9}

    zxAnEponRmCurDsJabbers OBJECT-TYPE
        SYNTAX      Counter64
        MAX-ACCESS  read-only
        STATUS      current
        DESCRIPTION
        "Downstream jabbers ."
        ::= { zxAnEponRmEthCurPerfEntry 10}

    zxAnEponRmCurDsPkts64Octets OBJECT-TYPE
        SYNTAX      Counter64
        MAX-ACCESS  read-only
        STATUS      current
        DESCRIPTION
        "Downstream packets that were 64 octets long."
        ::= { zxAnEponRmEthCurPerfEntry 11}

    zxAnEponRmCurDs65To127Octets OBJECT-TYPE
        SYNTAX      Counter64
        MAX-ACCESS  read-only
        STATUS      current
        DESCRIPTION
        "Downstream packets that were 65..127 octets long."
        ::= { zxAnEponRmEthCurPerfEntry 12}

    zxAnEponRmCurDs128To255Octets OBJECT-TYPE
        SYNTAX      Counter64
        MAX-ACCESS  read-only
        STATUS      current
        DESCRIPTION
        "Downstream packets that were 128..255 octets long."
        ::= { zxAnEponRmEthCurPerfEntry 13}

    zxAnEponRmCurDs256To511Octets OBJECT-TYPE
        SYNTAX      Counter64
        MAX-ACCESS  read-only
        STATUS      current
        DESCRIPTION
        "Downstream packets that were 256..511 octets long."
        ::= { zxAnEponRmEthCurPerfEntry 14}

    zxAnEponRmCurDs512To1023Octets OBJECT-TYPE
        SYNTAX      Counter64
        MAX-ACCESS  read-only
        STATUS      current
        DESCRIPTION
        "Downstream packets that were 512..2023 octets long."
        ::= { zxAnEponRmEthCurPerfEntry 15}

    zxAnEponRmCurDs1024To1518Octets OBJECT-TYPE
        SYNTAX      Counter64
        MAX-ACCESS  read-only
        STATUS      current
        DESCRIPTION
        "Downstream packets that were 1024..1518 octets long."
        ::= { zxAnEponRmEthCurPerfEntry 16}

    zxAnEponRmCurDsDiscards OBJECT-TYPE
        SYNTAX      Counter64
        MAX-ACCESS  read-only
        STATUS      current
        DESCRIPTION
        "Downstream discarded packets."
        ::= { zxAnEponRmEthCurPerfEntry 17}

    zxAnEponRmCurDsErrors OBJECT-TYPE
        SYNTAX      Counter64
        MAX-ACCESS  read-only
        STATUS      current
        DESCRIPTION
        "Downstream errored packets."
        ::= { zxAnEponRmEthCurPerfEntry 18}

    zxAnEponRmCurUsDropEvents OBJECT-TYPE
        SYNTAX      Counter64
        MAX-ACCESS  read-only
        STATUS      current
        DESCRIPTION
        "Upstream dropped events."
        ::= { zxAnEponRmEthCurPerfEntry 19}

    zxAnEponRmCurUsOctets OBJECT-TYPE
        SYNTAX      Counter64
        MAX-ACCESS  read-only
        STATUS      current
        DESCRIPTION
        "Upstream octets."
        ::= { zxAnEponRmEthCurPerfEntry 20}

    zxAnEponRmCurUsPkts OBJECT-TYPE
        SYNTAX      Counter64
        MAX-ACCESS  read-only
        STATUS      current
        DESCRIPTION
        "Upstream packets."
        ::= { zxAnEponRmEthCurPerfEntry 21}

    zxAnEponRmCurUsBcastPkts OBJECT-TYPE
        SYNTAX      Counter64
        MAX-ACCESS  read-only
        STATUS      current
        DESCRIPTION
        "Upstream broadcast packets."
        ::= { zxAnEponRmEthCurPerfEntry 22}

    zxAnEponRmCurUsMcastPkts OBJECT-TYPE
        SYNTAX      Counter64
        MAX-ACCESS  read-only
        STATUS      current
        DESCRIPTION
        "Upstream multicast packets."
        ::= { zxAnEponRmEthCurPerfEntry 23}

    zxAnEponRmCurUsCrcErrPkts OBJECT-TYPE
        SYNTAX      Counter64
        MAX-ACCESS  read-only
        STATUS      current
        DESCRIPTION
        "Upstream CRC errored packets."
        ::= { zxAnEponRmEthCurPerfEntry 24}

    zxAnEponRmCurUsUndersizePkts OBJECT-TYPE
        SYNTAX      Counter64
        MAX-ACCESS  read-only
        STATUS      current
        DESCRIPTION
        "Upstream undersize packets."
        ::= { zxAnEponRmEthCurPerfEntry 25}

    zxAnEponRmCurUsOversizePkts OBJECT-TYPE
        SYNTAX      Counter64
        MAX-ACCESS  read-only
        STATUS      current
        DESCRIPTION
        "Upstream oversize packets."
        ::= { zxAnEponRmEthCurPerfEntry 26}

    zxAnEponRmCurUsFragments OBJECT-TYPE
        SYNTAX      Counter64
        MAX-ACCESS  read-only
        STATUS      current
        DESCRIPTION
        "Upstream fragments."
        ::= { zxAnEponRmEthCurPerfEntry 27}

    zxAnEponRmCurUsJabbers OBJECT-TYPE
        SYNTAX      Counter64
        MAX-ACCESS  read-only
        STATUS      current
        DESCRIPTION
        "Upstream jabbers ."
        ::= { zxAnEponRmEthCurPerfEntry 28}

    zxAnEponRmCurUsPkts64Octets OBJECT-TYPE
        SYNTAX      Counter64
        MAX-ACCESS  read-only
        STATUS      current
        DESCRIPTION
        "Upstream packets that were 64 octets long."
        ::= { zxAnEponRmEthCurPerfEntry 29}

    zxAnEponRmCurUs65To127Octets OBJECT-TYPE
        SYNTAX      Counter64
        MAX-ACCESS  read-only
        STATUS      current
        DESCRIPTION
        "Upstream packets that were 65..127 octets long."
        ::= { zxAnEponRmEthCurPerfEntry 30}

    zxAnEponRmCurUs128To255Octets OBJECT-TYPE
        SYNTAX      Counter64
        MAX-ACCESS  read-only
        STATUS      current
        DESCRIPTION
        "Upstream packets that were 128..255 octets long."
        ::= { zxAnEponRmEthCurPerfEntry 31}

    zxAnEponRmCurUs256To511Octets OBJECT-TYPE
        SYNTAX      Counter64
        MAX-ACCESS  read-only
        STATUS      current
        DESCRIPTION
        "Upstream packets that were 256..511 octets long."
        ::= { zxAnEponRmEthCurPerfEntry 32}

    zxAnEponRmCurUs512To1023Octets OBJECT-TYPE
        SYNTAX      Counter64
        MAX-ACCESS  read-only
        STATUS      current
        DESCRIPTION
        "Upstream packets that were 512..1023 octets long."
        ::= { zxAnEponRmEthCurPerfEntry 33}

    zxAnEponRmCurUs1024To1518Octets OBJECT-TYPE
        SYNTAX      Counter64
        MAX-ACCESS  read-only
        STATUS      current
        DESCRIPTION
        "Upstream packets that were 1024..1518 octets long."
        ::= { zxAnEponRmEthCurPerfEntry 34}

    zxAnEponRmCurUsDiscards OBJECT-TYPE
        SYNTAX      Counter64
        MAX-ACCESS  read-only
        STATUS      current
        DESCRIPTION
        "Upstream discarded packets."
        ::= { zxAnEponRmEthCurPerfEntry 35}

    zxAnEponRmCurUsErrors OBJECT-TYPE
        SYNTAX      Counter64
        MAX-ACCESS  read-only
        STATUS      current
        DESCRIPTION
        "Upstream error packets."
        ::= { zxAnEponRmEthCurPerfEntry 36}

    zxAnEponRmCurPortStatusChanges     OBJECT-TYPE
        SYNTAX      Counter64
        MAX-ACCESS  read-only
        STATUS      current
        DESCRIPTION
        "ONU port status changed times. The value is 0
        if zxAnEponRmPerfOnuPortType is ponPort(1)."
        ::= { zxAnEponRmEthCurPerfEntry 37 }

------------------------------------------------------------------------------
-- zxAnEponRmEthHisPerfTable
------------------------------------------------------------------------------

   zxAnEponRmEthHisPerfTable OBJECT-TYPE
        SYNTAX       SEQUENCE OF ZxAnEponRmEthHisPerfEntry
        MAX-ACCESS   not-accessible
        STATUS       current
        DESCRIPTION
          "EPON remote ONU ethernet historical performance statistics table."
          ::= { zxAnEponOnuPfmncStatis 4 }

    zxAnEponRmEthHisPerfEntry OBJECT-TYPE
        SYNTAX      ZxAnEponRmEthHisPerfEntry
        MAX-ACCESS  not-accessible
        STATUS      current
        DESCRIPTION
        "EPON remote ONU ethernet historical performance statistics entry."
        INDEX       { zxAnEponOnuIfIndex, zxAnEponRmPerfOnuPortType,
                      zxAnEponOnuPortId, zxAnEponRmEthHisIntervalNo }
        ::= { zxAnEponRmEthHisPerfTable 1 }

    ZxAnEponRmEthHisPerfEntry ::= SEQUENCE {
            zxAnEponRmEthHisIntervalNo         Integer32,
            zxAnEponRmHisDsDropEvents          Counter64,
            zxAnEponRmHisDsOctets              Counter64,
            zxAnEponRmHisDsPkts                Counter64,
            zxAnEponRmHisDsBcastPkts           Counter64,
            zxAnEponRmHisDsMcastPkts           Counter64,
            zxAnEponRmHisDsCrcErrPkts          Counter64,
            zxAnEponRmHisDsUndersizePkts       Counter64,
            zxAnEponRmHisDsOversizePkts        Counter64,
            zxAnEponRmHisDsFragments           Counter64,
            zxAnEponRmHisDsJabbers             Counter64,
            zxAnEponRmHisDsPkts64Octets        Counter64,
            zxAnEponRmHisDs65To127Octets       Counter64,
            zxAnEponRmHisDs128To255Octets      Counter64,
            zxAnEponRmHisDs256To511Octets      Counter64,
            zxAnEponRmHisDs512To1023Octets     Counter64,
            zxAnEponRmHisDs1024To1518Octets    Counter64,
            zxAnEponRmHisDsDiscards            Counter64,
            zxAnEponRmHisDsErrors              Counter64,
            zxAnEponRmHisUsDropEvents          Counter64,
            zxAnEponRmHisUsOctets              Counter64,
            zxAnEponRmHisUsPkts                Counter64,
            zxAnEponRmHisUsBcastPkts           Counter64,
            zxAnEponRmHisUsMcastPkts           Counter64,
            zxAnEponRmHisUsCrcErrPkts          Counter64,
            zxAnEponRmHisUsUndersizePkts       Counter64,
            zxAnEponRmHisUsOversizePkts        Counter64,
            zxAnEponRmHisUsFragments           Counter64,
            zxAnEponRmHisUsJabbers             Counter64,
            zxAnEponRmHisUsPkts64Octets        Counter64,
            zxAnEponRmHisUs65To127Octets       Counter64,
            zxAnEponRmHisUs128To255Octets      Counter64,
            zxAnEponRmHisUs256To511Octets      Counter64,
            zxAnEponRmHisUs512To1023Octets     Counter64,
            zxAnEponRmHisUs1024To1518Octets    Counter64,
            zxAnEponRmHisUsDiscards            Counter64,
            zxAnEponRmHisUsErrors              Counter64,
            zxAnEponRmHisPortStatusChanges     Counter64
            }

    zxAnEponRmEthHisIntervalNo    OBJECT-TYPE
        SYNTAX      Integer32(1..96)
        MAX-ACCESS  not-accessible
        STATUS      current
        DESCRIPTION
        "In the case of zxAnEponRmPerfOnuHisStatInterval is default value,
        performance data interval number 1 is the the most recent
        previous interval; interval 96 is 24 hours ago.
        Intervals 2..96 are optional."
        ::= { zxAnEponRmEthHisPerfEntry 1 }

      zxAnEponRmHisDsDropEvents OBJECT-TYPE
        SYNTAX      Counter64
        MAX-ACCESS  read-only
        STATUS      current
        DESCRIPTION
        "History data of downstream dropped events."
        ::= { zxAnEponRmEthHisPerfEntry 2}

    zxAnEponRmHisDsOctets OBJECT-TYPE
        SYNTAX      Counter64
        MAX-ACCESS  read-only
        STATUS      current
        DESCRIPTION
        "History data of downstream octets."
        ::= { zxAnEponRmEthHisPerfEntry 3}

    zxAnEponRmHisDsPkts OBJECT-TYPE
        SYNTAX      Counter64
        MAX-ACCESS  read-only
        STATUS      current
        DESCRIPTION
        "History data of downstream packets."
        ::= { zxAnEponRmEthHisPerfEntry 4}

    zxAnEponRmHisDsBcastPkts OBJECT-TYPE
        SYNTAX      Counter64
        MAX-ACCESS  read-only
        STATUS      current
        DESCRIPTION
        "History data of downstream broadcast packets."
        ::= { zxAnEponRmEthHisPerfEntry 5}

    zxAnEponRmHisDsMcastPkts OBJECT-TYPE
        SYNTAX      Counter64
        MAX-ACCESS  read-only
        STATUS      current
        DESCRIPTION
        "History data of downstream multicast packets."
        ::= { zxAnEponRmEthHisPerfEntry 6}

    zxAnEponRmHisDsCrcErrPkts OBJECT-TYPE
        SYNTAX      Counter64
        MAX-ACCESS  read-only
        STATUS      current
        DESCRIPTION
        "History data of downstream CRC errored packets."
        ::= { zxAnEponRmEthHisPerfEntry 7}

    zxAnEponRmHisDsUndersizePkts OBJECT-TYPE
        SYNTAX      Counter64
        MAX-ACCESS  read-only
        STATUS      current
        DESCRIPTION
        "History data of downstream undersize packets."
        ::= { zxAnEponRmEthHisPerfEntry 8}

    zxAnEponRmHisDsOversizePkts OBJECT-TYPE
        SYNTAX      Counter64
        MAX-ACCESS  read-only
        STATUS      current
        DESCRIPTION
        "History data of downstream oversize packets."
        ::= { zxAnEponRmEthHisPerfEntry 9}

    zxAnEponRmHisDsFragments OBJECT-TYPE
        SYNTAX      Counter64
        MAX-ACCESS  read-only
        STATUS      current
        DESCRIPTION
        "History data of downstream fragments."
        ::= { zxAnEponRmEthHisPerfEntry 10}

    zxAnEponRmHisDsJabbers OBJECT-TYPE
        SYNTAX      Counter64
        MAX-ACCESS  read-only
        STATUS      current
        DESCRIPTION
        "History data of downstream jabbers."
        ::= { zxAnEponRmEthHisPerfEntry 11}

    zxAnEponRmHisDsPkts64Octets OBJECT-TYPE
        SYNTAX      Counter64
        MAX-ACCESS  read-only
        STATUS      current
        DESCRIPTION
        "History data of downstream packets that were 64 octets long."
        ::= { zxAnEponRmEthHisPerfEntry 12}

    zxAnEponRmHisDs65To127Octets OBJECT-TYPE
        SYNTAX      Counter64
        MAX-ACCESS  read-only
        STATUS      current
        DESCRIPTION
        "History data of downstream packets that were 65..127 octets long."
        ::= { zxAnEponRmEthHisPerfEntry 13}

    zxAnEponRmHisDs128To255Octets OBJECT-TYPE
        SYNTAX      Counter64
        MAX-ACCESS  read-only
        STATUS      current
        DESCRIPTION
        "History data of downstream packets that were 128..255 octets long."
        ::= { zxAnEponRmEthHisPerfEntry 14}

    zxAnEponRmHisDs256To511Octets OBJECT-TYPE
        SYNTAX      Counter64
        MAX-ACCESS  read-only
        STATUS      current
        DESCRIPTION
        "History data of downstream packets that were 256..511 octets long."
        ::= { zxAnEponRmEthHisPerfEntry 15}

    zxAnEponRmHisDs512To1023Octets OBJECT-TYPE
        SYNTAX      Counter64
        MAX-ACCESS  read-only
        STATUS      current
        DESCRIPTION
        "History data of downstream packets that were 512..1023 octets long."
        ::= { zxAnEponRmEthHisPerfEntry 16}

    zxAnEponRmHisDs1024To1518Octets OBJECT-TYPE
        SYNTAX      Counter64
        MAX-ACCESS  read-only
        STATUS      current
        DESCRIPTION
        "History data of downstream packets that were 1024..1518 octets long."
        ::= { zxAnEponRmEthHisPerfEntry 17}

    zxAnEponRmHisDsDiscards OBJECT-TYPE
        SYNTAX      Counter64
        MAX-ACCESS  read-only
        STATUS      current
        DESCRIPTION
        "History data of downstream discarded packets."
        ::= { zxAnEponRmEthHisPerfEntry 18}

    zxAnEponRmHisDsErrors OBJECT-TYPE
        SYNTAX      Counter64
        MAX-ACCESS  read-only
        STATUS      current
        DESCRIPTION
        "History data of downstream errored packets."
        ::= { zxAnEponRmEthHisPerfEntry 19}

    zxAnEponRmHisUsDropEvents OBJECT-TYPE
        SYNTAX      Counter64
        MAX-ACCESS  read-only
        STATUS      current
        DESCRIPTION
        "History data of upstream dropped events."
        ::= { zxAnEponRmEthHisPerfEntry 20}

    zxAnEponRmHisUsOctets OBJECT-TYPE
        SYNTAX      Counter64
        MAX-ACCESS  read-only
        STATUS      current
        DESCRIPTION
        "History data of upstream octets."
        ::= { zxAnEponRmEthHisPerfEntry 21}

    zxAnEponRmHisUsPkts OBJECT-TYPE
        SYNTAX      Counter64
        MAX-ACCESS  read-only
        STATUS      current
        DESCRIPTION
        "History data of upstream packets."
        ::= { zxAnEponRmEthHisPerfEntry 22}

    zxAnEponRmHisUsBcastPkts OBJECT-TYPE
        SYNTAX      Counter64
        MAX-ACCESS  read-only
        STATUS      current
        DESCRIPTION
        "History data of upstream broadcast packets."
        ::= { zxAnEponRmEthHisPerfEntry 23}

    zxAnEponRmHisUsMcastPkts OBJECT-TYPE
        SYNTAX      Counter64
        MAX-ACCESS  read-only
        STATUS      current
        DESCRIPTION
        "History data of upstream multicast packets."
        ::= { zxAnEponRmEthHisPerfEntry 24}

    zxAnEponRmHisUsCrcErrPkts OBJECT-TYPE
        SYNTAX      Counter64
        MAX-ACCESS  read-only
        STATUS      current
        DESCRIPTION
        "History data of upstream CRC errored packets."
        ::= { zxAnEponRmEthHisPerfEntry 25}

    zxAnEponRmHisUsUndersizePkts OBJECT-TYPE
        SYNTAX      Counter64
        MAX-ACCESS  read-only
        STATUS      current
        DESCRIPTION
        "History data of upstream undersize packets."
        ::= { zxAnEponRmEthHisPerfEntry 26}

    zxAnEponRmHisUsOversizePkts OBJECT-TYPE
        SYNTAX      Counter64
        MAX-ACCESS  read-only
        STATUS      current
        DESCRIPTION
        "History data of upstream oversize packets."
        ::= { zxAnEponRmEthHisPerfEntry 27}

    zxAnEponRmHisUsFragments OBJECT-TYPE
        SYNTAX      Counter64
        MAX-ACCESS  read-only
        STATUS      current
        DESCRIPTION
        "History data of upstream fragments."
        ::= { zxAnEponRmEthHisPerfEntry 28}

    zxAnEponRmHisUsJabbers OBJECT-TYPE
        SYNTAX      Counter64
        MAX-ACCESS  read-only
        STATUS      current
        DESCRIPTION
        "History data of upstream jabbers."
        ::= { zxAnEponRmEthHisPerfEntry 29}

    zxAnEponRmHisUsPkts64Octets OBJECT-TYPE
        SYNTAX      Counter64
        MAX-ACCESS  read-only
        STATUS      current
        DESCRIPTION
        "History data of upstream packets that were 64 octets long."
        ::= { zxAnEponRmEthHisPerfEntry 30}

    zxAnEponRmHisUs65To127Octets OBJECT-TYPE
        SYNTAX      Counter64
        MAX-ACCESS  read-only
        STATUS      current
        DESCRIPTION
        "History data of upstream packets that were 65..127 octets long."
        ::= { zxAnEponRmEthHisPerfEntry 31}

    zxAnEponRmHisUs128To255Octets OBJECT-TYPE
        SYNTAX      Counter64
        MAX-ACCESS  read-only
        STATUS      current
        DESCRIPTION
        "History data of upstream packets that were 128..255 octets long."
        ::= { zxAnEponRmEthHisPerfEntry 32}

    zxAnEponRmHisUs256To511Octets OBJECT-TYPE
        SYNTAX      Counter64
        MAX-ACCESS  read-only
        STATUS      current
        DESCRIPTION
        "History data of upstream packets that were 256..511 octets long."
        ::= { zxAnEponRmEthHisPerfEntry 33}

    zxAnEponRmHisUs512To1023Octets OBJECT-TYPE
        SYNTAX      Counter64
        MAX-ACCESS  read-only
        STATUS      current
        DESCRIPTION
        "History data of upstream packets that were 512..1023 octets long."
        ::= { zxAnEponRmEthHisPerfEntry 34}

    zxAnEponRmHisUs1024To1518Octets OBJECT-TYPE
        SYNTAX      Counter64
        MAX-ACCESS  read-only
        STATUS      current
        DESCRIPTION
        "History data of upstream packets that were 1024..1518 octets long."
        ::= { zxAnEponRmEthHisPerfEntry 35}

    zxAnEponRmHisUsDiscards OBJECT-TYPE
        SYNTAX      Counter64
        MAX-ACCESS  read-only
        STATUS      current
        DESCRIPTION
        "History data of upstream discarded packets."
        ::= { zxAnEponRmEthHisPerfEntry 36}

    zxAnEponRmHisUsErrors OBJECT-TYPE
        SYNTAX      Counter64
        MAX-ACCESS  read-only
        STATUS      current
        DESCRIPTION
        "History data of upstream error packets."
        ::= { zxAnEponRmEthHisPerfEntry 37}

    zxAnEponRmHisPortStatusChanges     OBJECT-TYPE
        SYNTAX      Counter64
        MAX-ACCESS  read-only
        STATUS      current
        DESCRIPTION
        "History data of ONU port status changed times.
        The value is 0 if zxAnEponRmPerfOnuPortType is ponPort(1)."
        ::= { zxAnEponRmEthHisPerfEntry 38 }

 ------------------------------------------------------------------------------
--  8.zxAnPtpExtOamMgmt
------------------------------------------------------------------------------
 zxAnPtpExtOamTable OBJECT-TYPE
        SYNTAX       SEQUENCE OF ZxAnPtpExtOamEntry
        MAX-ACCESS   not-accessible
        STATUS       current
        DESCRIPTION
          "PTP card extended oam object table."
          ::= { zxAnPtpExtOamMgmt 2 }

    zxAnPtpExtOamEntry OBJECT-TYPE
        SYNTAX      ZxAnPtpExtOamEntry
        MAX-ACCESS  not-accessible
        STATUS      current
        DESCRIPTION "PTP card extended oam object entry."
        INDEX       { zxAnPtpIfIndex}
        ::= { zxAnPtpExtOamTable 1 }

    ZxAnPtpExtOamEntry ::=
        SEQUENCE {
                zxAnPtpIfIndex           Integer32,
                zxAnPtpExtOamAdminStatus  INTEGER
                }

    zxAnPtpIfIndex OBJECT-TYPE
        SYNTAX      Integer32
        MAX-ACCESS  not-accessible
        STATUS      current
        DESCRIPTION
            "The 4 bytes index includes:
            interface type(bit31~28);shelfId(bit27~24);slotId(bit23~19);
            oltId(bit18~16);onu(bit15~bit8);reserved(bit7~bit0)."
        ::= { zxAnPtpExtOamEntry 1}

    zxAnPtpExtOamAdminStatus OBJECT-TYPE
        SYNTAX      INTEGER{
                       enabled(1),
                       disabled(2)
                    }
        MAX-ACCESS  read-write
        STATUS      current
        DESCRIPTION
                "PTP card extended oam administrative status."
        ::= { zxAnPtpExtOamEntry 2}

------------------------------------------------------------------------------
--  101.zxAnEponOnuCustomMgmt
--  101.31 zxAnEponOnuTkMgmt
--  101.31.31 zxAnEponOnuTkAttrMgmt
--  101.31.31.31 zxAnEponOnuTkGlobalTable
--  101.31.31.32 zxAnEponOnuTkPortTable
--  101.31.31.33 zxAnEponOnuTkLoopbackTable
--  101.31.31.34 zxAnEponOnuTkLinkBlockTable
--  101.31.31.35 zxAnEponOnuTkOpticalCtrlTable
--  101.31.31.36 zxAnEponOnuTkRstpCtrlTable
--  101.31.31.37 zxAnEponOnuTkMacLearningTable
--  101.31.31.38 zxAnEponOnuTkSnoopingTable
--  101.31.31.39 zxAnEponOnuTkIgmpTable
--  101.31.31.40 zxAnEponOnuTkLoopDetectTable
--  101.31.31.41 zxAnEponOnuTkPortShapingTable

--  101.31.32 zxAnEponOnuTkActionMgmt
--  101.31.32.31 zxAnEponOnuTkRestoreActionTable
--  101.31.32.32 zxAnEponOnuTkUpdateVerTable
--  101.31.32.33 zxAnEponOnuTkAutoUpdateVerTable

--  101.31.33 zxAnEponOnuTkStatisticMgmt
--  101.31.33.31 zxAnEponOnuTkGlobalStatTable
--  101.31.33.32 zxAnEponOnuTkPortStatTable
------------------------------------------------------------------------------

     zxAnEponOnuTkMgmt                         OBJECT IDENTIFIER ::= { zxAnEponOnuCustomMgmt 31}
     zxAnEponOnuTkAttrMgmt                     OBJECT IDENTIFIER ::= { zxAnEponOnuTkMgmt 31}
     zxAnEponOnuTkActionMgmt                   OBJECT IDENTIFIER ::= { zxAnEponOnuTkMgmt 32}
     zxAnEponOnuTkStatisticMgmt                OBJECT IDENTIFIER ::= { zxAnEponOnuTkMgmt 33}


  ------------------------------------------------------------------------------
  --  101.31.31.31 zxAnEponOnuTkGlobalTable
  ------------------------------------------------------------------------------
       zxAnEponOnuTkGlobalTable OBJECT-TYPE
        SYNTAX       SEQUENCE OF ZxAnEponOnuTkGlobalEntry
        MAX-ACCESS   not-accessible
        STATUS       current
        DESCRIPTION
          "Tk ONU Global Attribute Table."
          ::= { zxAnEponOnuTkAttrMgmt 31 }

     zxAnEponOnuTkGlobalEntry OBJECT-TYPE
        SYNTAX      ZxAnEponOnuTkGlobalEntry
        MAX-ACCESS  not-accessible
        STATUS      current
        DESCRIPTION "Tk ONU Global Attribute Entry."
        INDEX       { zxAnEponOnuIfIndex }
        ::= { zxAnEponOnuTkGlobalTable 1 }

     ZxAnEponOnuTkGlobalEntry ::=
        SEQUENCE {
                zxAnEponOnuTkFirmwareVer                  DisplayString,
                zxAnEponOnuTkModeName                     DisplayString
        }

    zxAnEponOnuTkFirmwareVer OBJECT-TYPE
        SYNTAX      DisplayString
        MAX-ACCESS  read-only
        STATUS      current
        DESCRIPTION
                "ONU firmware version."
        ::= { zxAnEponOnuTkGlobalEntry 1 }

    zxAnEponOnuTkModeName OBJECT-TYPE
        SYNTAX      DisplayString
        MAX-ACCESS  read-only
        STATUS      current
        DESCRIPTION
                "ONU mode name."
        ::= { zxAnEponOnuTkGlobalEntry 2 }


  ------------------------------------------------------------------------------
  --  101.31.31.32 zxAnEponOnuTkPortTable
  ------------------------------------------------------------------------------
     zxAnEponOnuTkPortTable OBJECT-TYPE
        SYNTAX       SEQUENCE OF ZxAnEponOnuTkPortEntry
        MAX-ACCESS   not-accessible
        STATUS       current
        DESCRIPTION
          "Tk ONU Port Attribute Table."
          ::= { zxAnEponOnuTkAttrMgmt 32 }

     zxAnEponOnuTkPortEntry OBJECT-TYPE
        SYNTAX      ZxAnEponOnuTkPortEntry
        MAX-ACCESS  not-accessible
        STATUS      current
        DESCRIPTION "Tk ONU Port Attribute Entry."
        INDEX       { zxAnEponOnuIfIndex, zxAnEponOnuPortId }
        ::= { zxAnEponOnuTkPortTable 1 }

     ZxAnEponOnuTkPortEntry ::=
        SEQUENCE {
                zxAnEponOnuTkPortOperStatus               INTEGER,
                zxAnEponOnuTkPortAutoNegStatus            INTEGER,
                zxAnEponOnuTkPortFlowCtrlStatus           INTEGER,
                zxAnEponOnuTkPortDuplexMode               INTEGER,
                zxAnEponOnuTkPortAdminStatus              INTEGER
        }

    zxAnEponOnuTkPortOperStatus OBJECT-TYPE
        SYNTAX      INTEGER{
                      enable(1),
                      disable(2)
                    }
        MAX-ACCESS  read-only
        STATUS      current
        DESCRIPTION
                "Tk ONU Port operation status."
        ::= { zxAnEponOnuTkPortEntry 1 }

    zxAnEponOnuTkPortAutoNegStatus OBJECT-TYPE
        SYNTAX      INTEGER{
                      enable(1),
                      disable(2)
                    }
        MAX-ACCESS  read-write
        STATUS      current
        DESCRIPTION
                "Tk ONU Port Auto-negotiation status."
        ::= { zxAnEponOnuTkPortEntry 2 }


    zxAnEponOnuTkPortFlowCtrlStatus OBJECT-TYPE
        SYNTAX      INTEGER{
                      enable(1),
                      disable(2)
                    }
        MAX-ACCESS  read-only
        STATUS      current
        DESCRIPTION
                "Tk ONU port flow control  status."
        ::= { zxAnEponOnuTkPortEntry 3 }

    zxAnEponOnuTkPortDuplexMode OBJECT-TYPE
        SYNTAX      INTEGER{
                      half(1),
                      full(2)
                    }
        MAX-ACCESS  read-only
        STATUS      current
        DESCRIPTION
                "Tk ONU port Duplex mode."
        ::= { zxAnEponOnuTkPortEntry 4 }

    zxAnEponOnuTkPortAdminStatus OBJECT-TYPE
        SYNTAX      INTEGER{
                      enable(1),
                      disable(2)
                    }
        MAX-ACCESS  read-write
        STATUS      current
        DESCRIPTION
                "Tk ONU Port administrative status."
        ::= { zxAnEponOnuTkPortEntry 5 }

------------------------------------------------------------------------------
--  101.31.31.33 zxAnEponOnuTkLoopbackTable
------------------------------------------------------------------------------
     zxAnEponOnuTkLoopbackTable OBJECT-TYPE
        SYNTAX       SEQUENCE OF ZxAnEponOnuTkLoopbackEntry
        MAX-ACCESS   not-accessible
        STATUS       current
        DESCRIPTION
          "Tk ONU loop back Table."
          ::= { zxAnEponOnuTkAttrMgmt 33 }

     zxAnEponOnuTkLoopbackEntry OBJECT-TYPE
        SYNTAX      ZxAnEponOnuTkLoopbackEntry
        MAX-ACCESS  not-accessible
        STATUS      current
        DESCRIPTION "Tk ONU loop back Entry."
        INDEX       { zxAnEponOnuIfIndex }
        ::= { zxAnEponOnuTkLoopbackTable 1 }

     ZxAnEponOnuTkLoopbackEntry ::=
        SEQUENCE {
                zxAnEponOnuTkLoopbackAdminStatus          INTEGER
        }

    zxAnEponOnuTkLoopbackAdminStatus OBJECT-TYPE
        SYNTAX      INTEGER{
                      enable(1),
                      disable(2)
                    }
        MAX-ACCESS  read-write
        STATUS      current
        DESCRIPTION
                "Tk ONU loop back administrative status."
        ::= { zxAnEponOnuTkLoopbackEntry 1 }

------------------------------------------------------------------------------
--  101.31.31.34 zxAnEponOnuTkLinkBlockTable
------------------------------------------------------------------------------
     zxAnEponOnuTkLinkBlockTable OBJECT-TYPE
        SYNTAX       SEQUENCE OF ZxAnEponOnuTkLinkBlockEntry
        MAX-ACCESS   not-accessible
        STATUS       current
        DESCRIPTION
          "Tk ONU link block Table."
          ::= { zxAnEponOnuTkAttrMgmt 34 }

     zxAnEponOnuTkLinkBlockEntry OBJECT-TYPE
        SYNTAX      ZxAnEponOnuTkLinkBlockEntry
        MAX-ACCESS  not-accessible
        STATUS      current
        DESCRIPTION "Tk ONU link block Entry."
        INDEX       { zxAnEponOnuIfIndex }
        ::= { zxAnEponOnuTkLinkBlockTable 1 }

     ZxAnEponOnuTkLinkBlockEntry ::=
        SEQUENCE {
                zxAnEponOnuTkLinkBlockAdminStatus          INTEGER,
                zxAnEponOnuTkLinkBlockOamType              INTEGER
        }

    zxAnEponOnuTkLinkBlockAdminStatus OBJECT-TYPE
        SYNTAX      INTEGER{
                      enable(1),
                      disable(2)
                    }
        MAX-ACCESS  read-write
        STATUS      current
        DESCRIPTION
                "Tk ONU link block administrative status."
        ::= { zxAnEponOnuTkLinkBlockEntry 1 }

    zxAnEponOnuTkLinkBlockOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkLinkBlockEntry 2 }

------------------------------------------------------------------------------
--  101.31.31.35 zxAnEponOnuTkOpticalCtrlTable
------------------------------------------------------------------------------
     zxAnEponOnuTkOpticalCtrlTable OBJECT-TYPE
        SYNTAX       SEQUENCE OF ZxAnEponOnuTkOpticalCtrlEntry
        MAX-ACCESS   not-accessible
        STATUS       current
        DESCRIPTION
          "Tk ONU Optical Table."
          ::= { zxAnEponOnuTkAttrMgmt 35 }

     zxAnEponOnuTkOpticalCtrlEntry OBJECT-TYPE
        SYNTAX      ZxAnEponOnuTkOpticalCtrlEntry
        MAX-ACCESS  not-accessible
        STATUS      current
        DESCRIPTION "Tk ONU Optical Entry."
        INDEX       { zxAnEponOnuIfIndex }
        ::= { zxAnEponOnuTkOpticalCtrlTable 1 }

     ZxAnEponOnuTkOpticalCtrlEntry ::=
        SEQUENCE {
                zxAnEponOnuTkOpticalBlockStatus             INTEGER,
                zxAnEponOnuTkOpticalBlockDurationTime       INTEGER,
                zxAnEponOnuTkOpticalBlockOamType            INTEGER
        }

    zxAnEponOnuTkOpticalBlockStatus OBJECT-TYPE
        SYNTAX      INTEGER{
                      enable(1),
                      disable(2)
                    }
        MAX-ACCESS  read-write
        STATUS      current
        DESCRIPTION
                "Tk ONU optical administrative status."
        DEFVAL { disable }
        ::= { zxAnEponOnuTkOpticalCtrlEntry 1 }

    zxAnEponOnuTkOpticalBlockDurationTime OBJECT-TYPE
        SYNTAX      INTEGER(1..255)
        UNITS       "second"
        MAX-ACCESS  read-write
        STATUS      current
        DESCRIPTION
                "Tk ONU optical aged time,255 is forever."
        DEFVAL { 255 }
        ::= { zxAnEponOnuTkOpticalCtrlEntry 2 }

    zxAnEponOnuTkOpticalBlockOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkOpticalCtrlEntry 3 }

------------------------------------------------------------------------------
--  101.31.31.36 zxAnEponOnuTkRstpCtrlTable
------------------------------------------------------------------------------
     zxAnEponOnuTkRstpCtrlTable OBJECT-TYPE
        SYNTAX       SEQUENCE OF ZxAnEponOnuTkRstpCtrlEntry
        MAX-ACCESS   not-accessible
        STATUS       current
        DESCRIPTION
          "Tk ONU RSTP Table."
          ::= { zxAnEponOnuTkAttrMgmt 36 }

     zxAnEponOnuTkRstpCtrlEntry OBJECT-TYPE
        SYNTAX      ZxAnEponOnuTkRstpCtrlEntry
        MAX-ACCESS  not-accessible
        STATUS      current
        DESCRIPTION "Tk ONU RSTP Entry."
        INDEX       { zxAnEponOnuIfIndex }
        ::= { zxAnEponOnuTkRstpCtrlTable 1 }

     ZxAnEponOnuTkRstpCtrlEntry ::=
        SEQUENCE {
                zxAnEponOnuTkRstpAdminStatus          INTEGER
        }

    zxAnEponOnuTkRstpAdminStatus OBJECT-TYPE
        SYNTAX      INTEGER{
                      enable(1),
                      disable(2),
                      passthrough(3)
                    }
        MAX-ACCESS  read-write
        STATUS      current
        DESCRIPTION
                "Tk ONU RSTP protocol administrative status."
        DEFVAL { enable }
        ::= { zxAnEponOnuTkRstpCtrlEntry 1 }

------------------------------------------------------------------------------
--  101.31.31.37 zxAnEponOnuTkMacLearningTable
------------------------------------------------------------------------------
     zxAnEponOnuTkMacLearningTable OBJECT-TYPE
        SYNTAX       SEQUENCE OF ZxAnEponOnuTkMacLearningEntry
        MAX-ACCESS   not-accessible
        STATUS       current
        DESCRIPTION
          "Tk ONU RSTP Table."
          ::= { zxAnEponOnuTkAttrMgmt 37 }

     zxAnEponOnuTkMacLearningEntry OBJECT-TYPE
        SYNTAX      ZxAnEponOnuTkMacLearningEntry
        MAX-ACCESS  not-accessible
        STATUS      current
        DESCRIPTION "Tk ONU RSTP Entry."
        INDEX       { zxAnEponOnuIfIndex,zxAnEponOnuPortId }
        ::= { zxAnEponOnuTkMacLearningTable 1 }

     ZxAnEponOnuTkMacLearningEntry ::=
        SEQUENCE {
                zxAnEponOnuTkMacLearningMaxNum     INTEGER,
                zxAnEponOnuTkMacLearningOamType    INTEGER
        }


    zxAnEponOnuTkMacLearningMaxNum OBJECT-TYPE
        SYNTAX      INTEGER(0..64)
        MAX-ACCESS  read-write
        STATUS      current
        DESCRIPTION
                "Tk ONU max MAC learning number."
        DEFVAL { 64 }
        ::= { zxAnEponOnuTkMacLearningEntry 1 }


    zxAnEponOnuTkMacLearningOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkMacLearningEntry 2 }


------------------------------------------------------------------------------
--  101.31.31.38 zxAnEponOnuTkSnoopingTable
------------------------------------------------------------------------------
     zxAnEponOnuTkSnoopingTable OBJECT-TYPE
        SYNTAX       SEQUENCE OF ZxAnEponOnuTkSnoopingEntry
        MAX-ACCESS   not-accessible
        STATUS       current
        DESCRIPTION
          "Tk ONU RSTP Table."
          ::= { zxAnEponOnuTkAttrMgmt 38 }

     zxAnEponOnuTkSnoopingEntry OBJECT-TYPE
        SYNTAX      ZxAnEponOnuTkSnoopingEntry
        MAX-ACCESS  not-accessible
        STATUS      current
        DESCRIPTION "Tk ONU Snooping Entry."
        INDEX       { zxAnEponOnuIfIndex }
        ::= { zxAnEponOnuTkSnoopingTable 1 }

     ZxAnEponOnuTkSnoopingEntry ::=
        SEQUENCE {
                zxAnEponOnuTkSnoopingCtrl          INTEGER,
                zxAnEponOnuTkSnoopingRobustCnt     INTEGER,
                zxAnEponOnuTkSnoopingLsmq          INTEGER,
                zxAnEponOnuTkSnoopingMaxGroupNum      INTEGER

        }

    zxAnEponOnuTkSnoopingCtrl OBJECT-TYPE
        SYNTAX      INTEGER{
                      enable(1),
                      disable(2)
                    }
        MAX-ACCESS  read-write
        STATUS      current
        DESCRIPTION
                "Tk ONU MAC learning number control status."
        ::= { zxAnEponOnuTkSnoopingEntry 1 }

    zxAnEponOnuTkSnoopingRobustCnt OBJECT-TYPE
        SYNTAX      INTEGER(0..12)
        MAX-ACCESS  read-write
        STATUS      current
        DESCRIPTION
                "Tk ONU Snooping Robust Count."
        ::= { zxAnEponOnuTkSnoopingEntry 2 }

    zxAnEponOnuTkSnoopingLsmq OBJECT-TYPE
        SYNTAX      INTEGER(0..12)
        MAX-ACCESS  read-write
        STATUS      current
        DESCRIPTION
                "Tk ONU Snooping Last Member Query Count."
        ::= { zxAnEponOnuTkSnoopingEntry 3 }

     zxAnEponOnuTkSnoopingMaxGroupNum OBJECT-TYPE
        SYNTAX      INTEGER(0..16)
        MAX-ACCESS  read-write
        STATUS      current
        DESCRIPTION
                "Tk ONU Snooping group number."
        ::= { zxAnEponOnuTkSnoopingEntry 4 }

------------------------------------------------------------------------------
--  101.31.31.39 zxAnEponOnuTkIgmpTable
------------------------------------------------------------------------------
      zxAnEponOnuTkIgmpTable OBJECT-TYPE
        SYNTAX       SEQUENCE OF ZxAnEponOnuTkIgmpEntry
        MAX-ACCESS   not-accessible
        STATUS       current
        DESCRIPTION
          "Tk ONU RSTP Table."
          ::= { zxAnEponOnuTkAttrMgmt 39 }

     zxAnEponOnuTkIgmpEntry OBJECT-TYPE
        SYNTAX      ZxAnEponOnuTkIgmpEntry
        MAX-ACCESS  not-accessible
        STATUS      current
        DESCRIPTION "Tk ONU Snooping Entry."
        INDEX       { zxAnEponOnuIfIndex,zxAnEponOnuTkIgmpVlanId,zxAnEponOnuTkIgmpIpAddr}
        ::= { zxAnEponOnuTkIgmpTable 1 }

     ZxAnEponOnuTkIgmpEntry ::=
        SEQUENCE {
                zxAnEponOnuTkIgmpVlanId            INTEGER,
                zxAnEponOnuTkIgmpIpAddr            IpAddress,
                zxAnEponOnuTkIgmpPortList          OCTET STRING
        }


    zxAnEponOnuTkIgmpVlanId OBJECT-TYPE
        SYNTAX      INTEGER(1..4094)
        MAX-ACCESS  not-accessible
        STATUS      current
        DESCRIPTION
                "Tk ONU MAC IGMP VLAN id."
        ::= { zxAnEponOnuTkIgmpEntry 1 }

    zxAnEponOnuTkIgmpIpAddr OBJECT-TYPE
        SYNTAX      IpAddress
        MAX-ACCESS  not-accessible
        STATUS      current
        DESCRIPTION
                "Tk ONU MAC IGMP IP address."
        ::= { zxAnEponOnuTkIgmpEntry 2 }

    zxAnEponOnuTkIgmpPortList OBJECT-TYPE
        SYNTAX      OCTET STRING
        MAX-ACCESS  read-only
        STATUS      current
        DESCRIPTION
                "Tk ONU MAC IGMP port list."
        ::= { zxAnEponOnuTkIgmpEntry 3 }


------------------------------------------------------------------------------
--  101.31.31.40 zxAnEponOnuTkLoopDetectTable
------------------------------------------------------------------------------
      zxAnEponOnuTkLoopDetectTable OBJECT-TYPE
        SYNTAX       SEQUENCE OF ZxAnEponOnuTkLoopDetectEntry
        MAX-ACCESS   not-accessible
        STATUS       current
        DESCRIPTION
          "Tk ONU Loop back Detect Table."
          ::= { zxAnEponOnuTkAttrMgmt 40 }

     zxAnEponOnuTkLoopDetectEntry OBJECT-TYPE
        SYNTAX      ZxAnEponOnuTkLoopDetectEntry
        MAX-ACCESS  not-accessible
        STATUS      current
        DESCRIPTION "Tk ONU Loop back Detect Entry."
        INDEX       { zxAnEponOnuIfIndex }
        ::= { zxAnEponOnuTkLoopDetectTable 1 }

     ZxAnEponOnuTkLoopDetectEntry ::=
        SEQUENCE {
                zxAnEponOnuTkLoopDetectAdminStatus INTEGER,
                zxAnEponOnuTkLoopDetectInterval    INTEGER,
                zxAnEponOnuTkLoopDetectOamType     INTEGER
        }

    zxAnEponOnuTkLoopDetectAdminStatus OBJECT-TYPE
        SYNTAX      INTEGER{
                      enable(1),
                      disable(2)
                    }
        MAX-ACCESS  read-write
        STATUS      current
        DESCRIPTION
                "Tk ONU loop back detect administrative status."
        ::= { zxAnEponOnuTkLoopDetectEntry 1 }

    zxAnEponOnuTkLoopDetectInterval OBJECT-TYPE
        SYNTAX      INTEGER(1..255)
        UNITS       "second"
        MAX-ACCESS  read-write
        STATUS      current
        DESCRIPTION
                "Tk ONU loop back detect interval."
        ::= { zxAnEponOnuTkLoopDetectEntry 2 }

    zxAnEponOnuTkLoopDetectOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkLoopDetectEntry 3 }

------------------------------------------------------------------------------
--  101.31.31.41 zxAnEponOnuTkPortShapingTable
------------------------------------------------------------------------------
      zxAnEponOnuTkPortShapingTable OBJECT-TYPE
        SYNTAX       SEQUENCE OF ZxAnEponOnuTkPortShapingEntry
        MAX-ACCESS   not-accessible
        STATUS       current
        DESCRIPTION
          "Tk ONU Port Shaping Table."
          ::= { zxAnEponOnuTkAttrMgmt 41 }

     zxAnEponOnuTkPortShapingEntry OBJECT-TYPE
        SYNTAX      ZxAnEponOnuTkPortShapingEntry
        MAX-ACCESS  not-accessible
        STATUS      current
        DESCRIPTION "Tk ONU Port Shaping Entry."
        INDEX       { zxAnEponOnuIfIndex, zxAnEponOnuPortId }
        ::= { zxAnEponOnuTkPortShapingTable 1 }

     ZxAnEponOnuTkPortShapingEntry ::=
        SEQUENCE {
                zxAnEponOnuTkPortDsShapingAdminStatus INTEGER,
                zxAnEponOnuTkPortDsShapingRate        INTEGER,
                zxAnEponOnuTkPortDsShapingOamType     INTEGER
        }

    zxAnEponOnuTkPortDsShapingAdminStatus OBJECT-TYPE
        SYNTAX      INTEGER{
                      enable(1),
                      disable(2)
                    }
        MAX-ACCESS  read-write
        STATUS      current
        DESCRIPTION
                "Tk ONU Ethernet port downstream shaping  administrative status."
        ::= { zxAnEponOnuTkPortShapingEntry 1 }

    zxAnEponOnuTkPortDsShapingRate OBJECT-TYPE
        SYNTAX      INTEGER
        UNITS       "kbps"
        MAX-ACCESS  read-write
        STATUS      current
        DESCRIPTION
                "Tk ONU Ethernet downstream shaping rate."
        ::= { zxAnEponOnuTkPortShapingEntry 2 }

    zxAnEponOnuTkPortDsShapingOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkPortShapingEntry 3 }


------------------------------------------------------------------------------
--  101.31.32.31 zxAnEponOnuTkRestoreActionTable
------------------------------------------------------------------------------
      zxAnEponOnuTkRestoreActionTable OBJECT-TYPE
        SYNTAX       SEQUENCE OF ZxAnEponOnuTkRestoreActionEntry
        MAX-ACCESS   not-accessible
        STATUS       current
        DESCRIPTION
          "Tk ONU restore action Table."
          ::= { zxAnEponOnuTkActionMgmt 31 }

     zxAnEponOnuTkRestoreActionEntry OBJECT-TYPE
        SYNTAX      ZxAnEponOnuTkRestoreActionEntry
        MAX-ACCESS  not-accessible
        STATUS      current
        DESCRIPTION "Tk ONU restore action Entry."
        INDEX       { zxAnEponOnuIfIndex }
        ::= { zxAnEponOnuTkRestoreActionTable 1 }

     ZxAnEponOnuTkRestoreActionEntry ::=
        SEQUENCE {
                zxAnEponOnuTkRestoreFactorySettings       INTEGER,
                zxAnEponOnuTkRestoreOamType               INTEGER
        }

    zxAnEponOnuTkRestoreFactorySettings OBJECT-TYPE
        SYNTAX      INTEGER{
                      restore(1)
                    }
        MAX-ACCESS  read-write
        STATUS      current
        DESCRIPTION
                "Tk ONU restore ONU factory settings."
        ::= { zxAnEponOnuTkRestoreActionEntry 1 }

    zxAnEponOnuTkRestoreOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkRestoreActionEntry 2 }


------------------------------------------------------------------------------
--  101.31.32.32 zxAnEponOnuTkUpdateVerTable
------------------------------------------------------------------------------
      zxAnEponOnuTkUpdateVerTable OBJECT-TYPE
        SYNTAX       SEQUENCE OF ZxAnEponOnuTkUpdateVerEntry
        MAX-ACCESS   not-accessible
        STATUS       current
        DESCRIPTION
          "Tk ONU update version action Table."
          ::= { zxAnEponOnuTkActionMgmt 32 }

     zxAnEponOnuTkUpdateVerEntry OBJECT-TYPE
        SYNTAX      ZxAnEponOnuTkUpdateVerEntry
        MAX-ACCESS  not-accessible
        STATUS      current
        DESCRIPTION "Tk ONU update version action Entry."
        INDEX       { zxAnEponOnuIfIndex }
        ::= { zxAnEponOnuTkUpdateVerTable 1 }

     ZxAnEponOnuTkUpdateVerEntry ::=
        SEQUENCE {
                zxAnEponOnuTkVerType            INTEGER,
                zxAnEponOnuTkVerName            DisplayString,
                zxAnEponOnuTkUpdateStatus       INTEGER,
                zxAnEponOnuTkUpdateProgress     INTEGER,
                zxAnEponOnuTkOnuAckCode         INTEGER,
                zxAnEponOnuTkErrorCode          INTEGER,
                zxAnEponOnuTkUpdattingVerName   DisplayString
        }

    zxAnEponOnuTkVerType OBJECT-TYPE
        SYNTAX      INTEGER{
                      boot(1),
                      application(2),
                      personality(3),
                      diagnostic(4),
                      dsan(5)
                    }
        MAX-ACCESS  read-write
        STATUS      current
        DESCRIPTION
                "Tk ONU version type."
        ::= { zxAnEponOnuTkUpdateVerEntry 1 }

    zxAnEponOnuTkVerName OBJECT-TYPE
        SYNTAX      DisplayString
        MAX-ACCESS  read-write
        STATUS      current
        DESCRIPTION
                "Tk ONU version name."
        ::= { zxAnEponOnuTkUpdateVerEntry 2 }

    zxAnEponOnuTkUpdateStatus OBJECT-TYPE
        SYNTAX      INTEGER{
                      noStart(1),
                      failed(2),
                      downloading(3),
                      writtingImage(4),
                      finished(5)
                    }
        MAX-ACCESS  read-only
        STATUS      current
        DESCRIPTION
                "Tk ONU version update status."
        ::= { zxAnEponOnuTkUpdateVerEntry 3 }

    zxAnEponOnuTkUpdateProgress OBJECT-TYPE
        SYNTAX      INTEGER( 0..100 )
        UNITS       "percent"
        MAX-ACCESS  read-only
        STATUS      current
        DESCRIPTION
                "Tk ONU version update progress."
        ::= { zxAnEponOnuTkUpdateVerEntry 4 }


    zxAnEponOnuTkOnuAckCode OBJECT-TYPE
        SYNTAX      INTEGER
        MAX-ACCESS  read-only
        STATUS      current
        DESCRIPTION
                " ONU ACK Code:
                  0x0:CRC error
                  0x1:actual data size is not equal to the marked data size
                  0x2:sequence number is more big than total image size
                  0x3:failed to write an image into flash memory
                  0x4:pasonu_flash_image_burn function was received with wrong parameter
                  0x5:flash write OK"
        ::= { zxAnEponOnuTkUpdateVerEntry 5 }

    zxAnEponOnuTkErrorCode OBJECT-TYPE
        SYNTAX      INTEGER
        MAX-ACCESS  read-only
        STATUS      current
        DESCRIPTION
                " Error Code:
                  1:unknown
                  2:download error
                  3:download timeout
                  4:ONU return error
                  5:user abort
                  6:ONU offline"
        ::= { zxAnEponOnuTkUpdateVerEntry 6 }

    zxAnEponOnuTkUpdattingVerName OBJECT-TYPE
        SYNTAX      DisplayString
        MAX-ACCESS  read-only
        STATUS      current
        DESCRIPTION
                "Tk ONU updatting version name."
        ::= { zxAnEponOnuTkUpdateVerEntry 7 }


------------------------------------------------------------------------------
--  101.31.32.32 zxAnEponOnuTkAutoUpdateVerTable
------------------------------------------------------------------------------
      zxAnEponOnuTkAutoUpdateVerTable OBJECT-TYPE
        SYNTAX       SEQUENCE OF ZxAnEponOnuTkAutoUpdateVerEntry
        MAX-ACCESS   not-accessible
        STATUS       current
        DESCRIPTION
          "Tk ONU update version action Table."
          ::= { zxAnEponOnuTkActionMgmt 33 }

     zxAnEponOnuTkAutoUpdateVerEntry OBJECT-TYPE
        SYNTAX      ZxAnEponOnuTkAutoUpdateVerEntry
        MAX-ACCESS  not-accessible
        STATUS      current
        DESCRIPTION "Tk ONU update version action Entry."
        INDEX       { zxAnEponOltIfIndex }
        ::= { zxAnEponOnuTkAutoUpdateVerTable 1 }

     ZxAnEponOnuTkAutoUpdateVerEntry ::=
        SEQUENCE {
                zxAnEponOltIfIndex                   INTEGER,
                zxAnEponOnuTkAutoUpdateAdminStatus   INTEGER,
                zxAnEponOnuTkVerActiveMode           INTEGER
        }

    zxAnEponOltIfIndex OBJECT-TYPE
        SYNTAX      INTEGER
        MAX-ACCESS  not-accessible
        STATUS      current
        DESCRIPTION
            "The 4 bytes index includes:
            interface type(bit31~28);shelfId(bit27~24);slotId(bit23~16);oltId(bit15~8);reserved(bit7~bit0)"
        ::= { zxAnEponOnuTkAutoUpdateVerEntry 1 }


    zxAnEponOnuTkAutoUpdateAdminStatus OBJECT-TYPE
        SYNTAX      INTEGER{
                      enable(1),
                      disable(2)
                    }
        MAX-ACCESS  read-write
        STATUS      current
        DESCRIPTION
                "Tk ONU auto update administrative status."
        ::= { zxAnEponOnuTkAutoUpdateVerEntry 2 }


    zxAnEponOnuTkVerActiveMode OBJECT-TYPE
        SYNTAX      INTEGER{
                      immediately(1),
                      next(2)
                    }
        MAX-ACCESS  read-write
        STATUS      current
        DESCRIPTION
                "Tk ONU version active mode.
                1:active version immediately
                2:active version manual or by ONU online again"
        ::= { zxAnEponOnuTkAutoUpdateVerEntry 3 }


------------------------------------------------------------------------------
--  101.31.33.31 zxAnEponOnuTkGlobalStatTable
------------------------------------------------------------------------------
    zxAnEponOnuTkGlobalStatTable OBJECT-TYPE
        SYNTAX       SEQUENCE OF ZxAnEponOnuTkGlobalStatEntry
        MAX-ACCESS   not-accessible
        STATUS       current
        DESCRIPTION
          "Tk ONU Statistic Info."
          ::= { zxAnEponOnuTkStatisticMgmt 31 }

    zxAnEponOnuTkGlobalStatEntry OBJECT-TYPE
        SYNTAX      ZxAnEponOnuTkGlobalStatEntry
        MAX-ACCESS  not-accessible
        STATUS      current
        DESCRIPTION " "
        INDEX       { zxAnEponOnuIfIndex }
        ::= { zxAnEponOnuTkGlobalStatTable 1 }


    ZxAnEponOnuTkGlobalStatEntry ::=
        SEQUENCE {
                zxAnEponOnuTkGlobalStatResetCounter               INTEGER,
                zxAnEponOnuTkGlobalStatOamType                    INTEGER,
                zxAnEponOnuTkGlobalStatTxRegReq                   Counter64,
                zxAnEponOnuTkGlobalStatRxReg                      Counter64,
                zxAnEponOnuTkGlobalStatTxRegAck                   Counter64,
                zxAnEponOnuTkGlobalStatRxGateFrames               Counter64,
                zxAnEponOnuTkGlobalStatTxReportFrames             Counter64
                }



    zxAnEponOnuTkGlobalStatResetCounter OBJECT-TYPE
        SYNTAX     INTEGER
        MAX-ACCESS  read-write
        STATUS      current
        DESCRIPTION
                ""
        ::= { zxAnEponOnuTkGlobalStatEntry 1}

    zxAnEponOnuTkGlobalStatOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkGlobalStatEntry 2 }


     zxAnEponOnuTkGlobalStatTxRegReq OBJECT-TYPE
        SYNTAX     Counter64
        MAX-ACCESS  read-only
        STATUS      current
        DESCRIPTION
                "Number of Register Requests Frames from transmitted upstream."
        ::= { zxAnEponOnuTkGlobalStatEntry 32}

     zxAnEponOnuTkGlobalStatRxReg OBJECT-TYPE
        SYNTAX     Counter64
        MAX-ACCESS  read-only
        STATUS      current
        DESCRIPTION
                "Number of Register Frames sent for the link"
        ::= { zxAnEponOnuTkGlobalStatEntry 33}

      zxAnEponOnuTkGlobalStatTxRegAck OBJECT-TYPE
        SYNTAX     Counter64
        MAX-ACCESS  read-only
        STATUS      current
        DESCRIPTION
                "Number of Register Ack's Frames from transmitted upstream"
        ::= { zxAnEponOnuTkGlobalStatEntry 34}

      zxAnEponOnuTkGlobalStatRxGateFrames OBJECT-TYPE
        SYNTAX     Counter64
        MAX-ACCESS  read-only
        STATUS      current
        DESCRIPTION
                "Number of Gate Frames Received"
        ::= { zxAnEponOnuTkGlobalStatEntry 35}

      zxAnEponOnuTkGlobalStatTxReportFrames OBJECT-TYPE
        SYNTAX     Counter64
        MAX-ACCESS  read-only
        STATUS      current
        DESCRIPTION
                "Number of Report Frames from transmitted upstream"
        ::= { zxAnEponOnuTkGlobalStatEntry 36}

------------------------------------------------------------------------------
--  101.31.33.32 zxAnEponOnuTkPortStatTable
------------------------------------------------------------------------------
      zxAnEponOnuTkPortStatTable OBJECT-TYPE
        SYNTAX       SEQUENCE OF ZxAnEponOnuTkPortStatEntry
        MAX-ACCESS   not-accessible
        STATUS       current
        DESCRIPTION
          "Tk ONUPort Statistic Info."
          ::= { zxAnEponOnuTkStatisticMgmt 32}

    zxAnEponOnuTkPortStatEntry OBJECT-TYPE
        SYNTAX      ZxAnEponOnuTkPortStatEntry
        MAX-ACCESS  not-accessible
        STATUS      current
        DESCRIPTION ""
        INDEX       { zxAnEponOnuIfIndex,zxAnEponOnuPortId }
        ::= { zxAnEponOnuTkPortStatTable 1 }

    ZxAnEponOnuTkPortStatEntry ::=
        SEQUENCE {
                zxAnEponOnuTkPortStatResetCounter        INTEGER,
                zxAnEponOnuTkPortStatOamType             INTEGER,
                zxAnEponOnuTkPortStatTxFrames            Counter64,
                zxAnEponOnuTkPortStatTxBytes             Counter64,
                zxAnEponOnuTkPortStatTxMulticast         Counter64,
                zxAnEponOnuTkPortStatTxBroadcast         Counter64,
                zxAnEponOnuTkPortStatTxDropedFrames      Counter64,
                zxAnEponOnuTkPortStatRxFrames            Counter64,
                zxAnEponOnuTkPortStatRxBytes             Counter64,
                zxAnEponOnuTkPortStatRxMulticast         Counter64,
                zxAnEponOnuTkPortStatRxBroadcast         Counter64,
                zxAnEponOnuTkPortStatRxOversizeFrames    Counter64,
                zxAnEponOnuTkPortStatRxUnderSizeFrames   Counter64,
                zxAnEponOnuTkPortStatRxCrcFrames         Counter64
                }

       zxAnEponOnuTkPortStatResetCounter OBJECT-TYPE
        SYNTAX     INTEGER
        MAX-ACCESS  read-write
        STATUS      current
        DESCRIPTION
                ""
        ::= { zxAnEponOnuTkPortStatEntry 1}

    zxAnEponOnuTkPortStatOamType OBJECT-TYPE
        SYNTAX      INTEGER{
                      tk-oam(1),
                      kt-oam(2)
                    }
        MAX-ACCESS  read-write
        STATUS      current
        DESCRIPTION
                "Tk ONU oam type."
        DEFVAL { tk-oam }
        ::= { zxAnEponOnuTkPortStatEntry 2 }

       zxAnEponOnuTkPortStatTxFrames OBJECT-TYPE
        SYNTAX      Counter64
        MAX-ACCESS  read-only
        STATUS      current
        DESCRIPTION
                "Number of data frames successfully transmitted"
        ::= { zxAnEponOnuTkPortStatEntry 31}

       zxAnEponOnuTkPortStatTxBytes OBJECT-TYPE
        SYNTAX      Counter64
        MAX-ACCESS  read-only
        STATUS      current
        DESCRIPTION
                "Number of bytes successfully transmitted."
        ::= { zxAnEponOnuTkPortStatEntry 32}

       zxAnEponOnuTkPortStatTxMulticast OBJECT-TYPE
        SYNTAX      Counter64
        MAX-ACCESS  read-only
        STATUS      current
        DESCRIPTION
                "Number of successfully transmitted Multicast packet."
        ::= { zxAnEponOnuTkPortStatEntry 33}

       zxAnEponOnuTkPortStatTxBroadcast OBJECT-TYPE
        SYNTAX      Counter64
        MAX-ACCESS  read-only
        STATUS      current
        DESCRIPTION
                "Number of successfully transmitted Broadcast packet."
        ::= { zxAnEponOnuTkPortStatEntry 34}

      zxAnEponOnuTkPortStatTxDropedFrames OBJECT-TYPE
        SYNTAX      Counter64
        MAX-ACCESS  read-only
        STATUS      current
        DESCRIPTION
                "Frames Dropped"
        ::= { zxAnEponOnuTkPortStatEntry 35}

      zxAnEponOnuTkPortStatRxFrames OBJECT-TYPE
        SYNTAX      Counter64
        MAX-ACCESS  read-only
        STATUS      current
        DESCRIPTION
                "Number of received frames."
        ::= { zxAnEponOnuTkPortStatEntry 36}

      zxAnEponOnuTkPortStatRxBytes OBJECT-TYPE
        SYNTAX      Counter64
        MAX-ACCESS  read-only
        STATUS      current
        DESCRIPTION
                "Number of received good bytes."
        ::= { zxAnEponOnuTkPortStatEntry 37}

      zxAnEponOnuTkPortStatRxMulticast OBJECT-TYPE
        SYNTAX      Counter64
        MAX-ACCESS  read-only
        STATUS      current
        DESCRIPTION
                "Number of received Multicast packet."
        ::= { zxAnEponOnuTkPortStatEntry 38}

       zxAnEponOnuTkPortStatRxBroadcast OBJECT-TYPE
        SYNTAX      Counter64
        MAX-ACCESS  read-only
        STATUS      current
        DESCRIPTION
                "Number of received Broadcast packet."
        ::= { zxAnEponOnuTkPortStatEntry 39}

       zxAnEponOnuTkPortStatRxOversizeFrames OBJECT-TYPE
        SYNTAX      Counter64
        MAX-ACCESS  read-only
        STATUS      current
        DESCRIPTION
                "Number of received packet with the frame size greater than allowed."
        ::= { zxAnEponOnuTkPortStatEntry 40}

       zxAnEponOnuTkPortStatRxUnderSizeFrames OBJECT-TYPE
        SYNTAX      Counter64
        MAX-ACCESS  read-only
        STATUS      current
        DESCRIPTION
                "Number of runt frames received."
        ::= { zxAnEponOnuTkPortStatEntry 41}

       zxAnEponOnuTkPortStatRxCrcFrames OBJECT-TYPE
        SYNTAX      Counter64
        MAX-ACCESS  read-only
        STATUS      current
        DESCRIPTION
                "Number of Frames received that have a CRC32 error"
        ::= { zxAnEponOnuTkPortStatEntry 42}



    zxAnEponOnuMgmtIpDHCPCfgTable  OBJECT-TYPE
            SYNTAX      SEQUENCE OF ZxAnEponOnuMgmtIpDHCPCfgEntry
            MAX-ACCESS  not-accessible
            STATUS      current
            DESCRIPTION
                "EPON ONU REMOTE MGMT-IP DHCP Config TABLE."
            ::= {zxAnEponOnuExtendedAttrMgmt 52}

    zxAnEponOnuMgmtIpDHCPCfgEntry  OBJECT-TYPE
            SYNTAX      ZxAnEponOnuMgmtIpDHCPCfgEntry
            MAX-ACCESS  not-accessible
            STATUS      current
            DESCRIPTION
                "EPON ONU REMOTE MGMT-IP DHCP Config ENTRY."
            INDEX    { zxAnEponOnuIfIndex}
            ::= {zxAnEponOnuMgmtIpDHCPCfgTable 1}

    ZxAnEponOnuMgmtIpDHCPCfgEntry ::=
            SEQUENCE {
                zxAnEponOnuMgmtIpDHCPCfgVlan            INTEGER,
                zxAnEponOnuMgmtIpDHCPCfgPriority        INTEGER,
                zxAnEponOnuMgmtIpDHCPCfgEnableState     INTEGER,
                zxAnEponOnuMgmtIpDHCPCfgState           INTEGER
                }

    zxAnEponOnuMgmtIpDHCPCfgVlan  OBJECT-TYPE
            SYNTAX      INTEGER (1..4094)
            MAX-ACCESS  read-write
            STATUS      current
            DESCRIPTION
                 "The vlan id."
            ::= { zxAnEponOnuMgmtIpDHCPCfgEntry 1 }

    zxAnEponOnuMgmtIpDHCPCfgPriority  OBJECT-TYPE
            SYNTAX      INTEGER (0..7)
            MAX-ACCESS  read-write
            STATUS      current
            DESCRIPTION
                 "The priority of vlan config."
            ::= { zxAnEponOnuMgmtIpDHCPCfgEntry 2 }

    zxAnEponOnuMgmtIpDHCPCfgEnableState  OBJECT-TYPE
            SYNTAX      INTEGER {
                enable(1),
                disable(2)
                }
            MAX-ACCESS  read-write
            STATUS      current
            DESCRIPTION
                 "enable or disable ONU DHCP config."
            ::= { zxAnEponOnuMgmtIpDHCPCfgEntry 3 }

    zxAnEponOnuMgmtIpDHCPCfgState  OBJECT-TYPE
            SYNTAX      INTEGER {
                init(0),
                selecting(1),
                requesting(2),
                init-reboot(3),
                rebooting(4),
                bound(5),
                renewing(6),
                rebinding(7)
                }
            MAX-ACCESS  read-only
            STATUS      current
            DESCRIPTION
                 "Status of ONU DHCP config."
            ::= { zxAnEponOnuMgmtIpDHCPCfgEntry 4 }

------------------------------------------------------------------------
-- 1.53 EPON ONU WAN management(OAM)
------------------------------------------------------------------------

    zxAnEponRmOnuWanMgmt  OBJECT IDENTIFIER ::= { zxAnEponOnuExtendedAttrMgmt 53}

------------------------------------------------------------------------
-- 1.53.2 zxAnEponRmWanPrfTable
------------------------------------------------------------------------
    zxAnEponRmWanPrfTable  OBJECT-TYPE
        SYNTAX         SEQUENCE OF ZxAnEponRmWanPrfEntry
        MAX-ACCESS     not-accessible
        STATUS         current
        DESCRIPTION
            "EPON WAN(wide area network) profile table."
        ::= { zxAnEponRmOnuWanMgmt 2 }

    zxAnEponRmWanPrfEntry   OBJECT-TYPE
        SYNTAX         ZxAnEponRmWanPrfEntry
        MAX-ACCESS     not-accessible
        STATUS         current
        DESCRIPTION
            "An entry of the EPON WAN profile table."
        INDEX    { zxAnEponRmWanPrfName }
        ::= { zxAnEponRmWanPrfTable 1 }

    ZxAnEponRmWanPrfEntry ::=
        SEQUENCE {
                 zxAnEponRmWanPrfName               DisplayString,
                 zxAnEponRmWanPrfWorkMode           INTEGER,
                 zxAnEponRmWanPrfSrvType            BITS,
                 zxAnEponRmWanPrfIpStackMode        INTEGER,
                 zxAnEponRmWanPrfNatNum             Integer32,
                 zxAnEponRmWanPrfTransTagMode       INTEGER,
                 zxAnEponRmWanPrfTagTpid            Integer32,
                 zxAnEponRmWanPrfTagVid             Integer32,
                 zxAnEponRmWanPrfTagPrior           Integer32,
                 zxAnEponRmWanPrfMaxTransUnit       Integer32,
                 zxAnEponRmWanPrfMVid               Integer32,
                 zxAnEponRmWanPrfBindLanPortList    BITS,
                 zxAnEponRmWanPrfBindSsidList       BITS,
                 zxAnEponRmWanPrfRowStatus          RowStatus
                 }

    zxAnEponRmWanPrfName    OBJECT-TYPE
        SYNTAX      DisplayString(SIZE(1..32))
        MAX-ACCESS  not-accessible
        STATUS      current
        DESCRIPTION
            "This object identifies a row in this table."
        ::= { zxAnEponRmWanPrfEntry 1 }

    zxAnEponRmWanPrfWorkMode    OBJECT-TYPE
        SYNTAX      INTEGER{
                    bridge(1),
                    route(2)
                    }
        MAX-ACCESS   read-create
        STATUS       current
        DESCRIPTION
            "It indicates the WAN work mode."
        DEFVAL { bridge }
        ::= { zxAnEponRmWanPrfEntry 2 }

    zxAnEponRmWanPrfSrvType    OBJECT-TYPE
        SYNTAX      BITS{
                    internet(0),
                    tr069(1),
                    voip(2),
                    other(3)
                    }
        MAX-ACCESS   read-create
        STATUS       current
        DESCRIPTION
            "It indicates the service type of the WAN. The default value is
            internet."
        ::= { zxAnEponRmWanPrfEntry 3 }

    zxAnEponRmWanPrfIpStackMode   OBJECT-TYPE
        SYNTAX      INTEGER{
                    ipv4(1),
                    ipv6(2),
                    ipv4AndIpv6(3)
                    }
        MAX-ACCESS   read-create
        STATUS       current
        DESCRIPTION
            "It indicates the IP stack mode. It is relation to
            'zxAnEponRmWanPrfWorkMode'. It is valid only when
            'zxAnEponRmWanPrfWorkMode' is route."
        DEFVAL { ipv4 }
        ::= { zxAnEponRmWanPrfEntry 4 }

    zxAnEponRmWanPrfNatNum OBJECT-TYPE
        SYNTAX       Integer32(0..65535)
        MAX-ACCESS   read-create
        STATUS       current
        DESCRIPTION
            "It indicates the configuration of the NAT. 0 is disable, 65535 is
            no limit, other is the actual NAT number."
        DEFVAL { 0 }
        ::= { zxAnEponRmWanPrfEntry 5 }

    zxAnEponRmWanPrfTransTagMode    OBJECT-TYPE
        SYNTAX      INTEGER{
                    transparent(1),
                    tagged(2),
                    untagged(3)
                    }
        MAX-ACCESS   read-create
        STATUS       current
        DESCRIPTION
            "It indicates the 802.1Q tag mode. If it is tag mode, vid, priority
            and tpid must be set if it is tag mode."
        DEFVAL { transparent }
        ::= { zxAnEponRmWanPrfEntry 6 }

    zxAnEponRmWanPrfTagTpid   OBJECT-TYPE
        SYNTAX       Integer32(1..65535)
        MAX-ACCESS   read-create
        STATUS       current
        DESCRIPTION
            "It indicates the tag protocal identifier. It is relation to
             'zxAnEponRmWanPrfTransTagMode'. It is valid only when
             'zxAnEponRmWanPrfTransTagMode' is tagged."
        DEFVAL { 33024 }
        ::= { zxAnEponRmWanPrfEntry 7 }

    zxAnEponRmWanPrfTagVid   OBJECT-TYPE
        SYNTAX       Integer32(1..4094)
        MAX-ACCESS   read-create
        STATUS       current
        DESCRIPTION
            "It indicates the vlan identifier. It is relation to
            'zxAnEponRmWanPrfTransTagMode'. It is valid only when
            'zxAnEponRmWanPrfTransTagMode' is tagged."
        DEFVAL { 4092 }
        ::= { zxAnEponRmWanPrfEntry 8 }

    zxAnEponRmWanPrfTagPrior   OBJECT-TYPE
        SYNTAX       Integer32(0..7)
        MAX-ACCESS   read-create
        STATUS       current
        DESCRIPTION
            "It indicates the vlan priority. It is relation to
            'zxAnEponRmWanPrfTransTagMode'.  It is valid only when
            'zxAnEponRmWanPrfTransTagMode' is tagged."
        DEFVAL { 1 }
        ::= { zxAnEponRmWanPrfEntry 9 }

    zxAnEponRmWanPrfMaxTransUnit   OBJECT-TYPE
        SYNTAX       Integer32(1..2000)
        MAX-ACCESS   read-create
        STATUS       current
        DESCRIPTION
            "It indicates the maximum transmission unit."
        DEFVAL { 1522 }
        ::= { zxAnEponRmWanPrfEntry 10 }

    zxAnEponRmWanPrfMVid   OBJECT-TYPE
        SYNTAX       Integer32(1..4094|4096)
        MAX-ACCESS   read-create
        STATUS       current
        DESCRIPTION
            "It indicates the multicast vlan identifier. It is relation to
            'zxAnEponRmWanPrfSrvType'. It is valid only when
            'zxAnEponRmWanPrfSrvType' is internet or other."
        DEFVAL { 4096 }
        ::= { zxAnEponRmWanPrfEntry 11 }

    zxAnEponRmWanPrfBindLanPortList  OBJECT-TYPE
        SYNTAX      BITS{
                    lan1(0),
                    lan2(1),
                    lan3(2),
                    lan4(3),
                    lan5(4),
                    lan6(5),
                    lan7(6),
                    lan8(7),
                    lan9(8),
                    lan10(9),
                    lan11(10),
                    lan12(11),
                    lan13(12),
                    lan14(13),
                    lan15(14),
                    lan16(15)
                    }
        MAX-ACCESS   read-create
        STATUS       current
        DESCRIPTION
            "It indicates the Ethernet ports those bound to the WAN."
        ::= { zxAnEponRmWanPrfEntry 12 }

    zxAnEponRmWanPrfBindSsidList   OBJECT-TYPE
        SYNTAX      BITS{
                    ssid1(0),
                    ssid2(1),
                    ssid3(2),
                    ssid4(3),
                    ssid5(4),
                    ssid6(5),
                    ssid7(6),
                    ssid8(7),
                    ssid9(8),
                    ssid10(9),
                    ssid11(10),
                    ssid12(11),
                    ssid13(12),
                    ssid14(13),
                    ssid15(14),
                    ssid16(15)
                    }
        MAX-ACCESS   read-create
        STATUS       current
        DESCRIPTION
            "It indicates the SSIDs those bound to the WAN."
        ::= { zxAnEponRmWanPrfEntry 13 }

    zxAnEponRmWanPrfRowStatus     OBJECT-TYPE
        SYNTAX      RowStatus
        MAX-ACCESS  read-create
        STATUS      current
        DESCRIPTION
            "The status of this conceptual row.

            The supported actions of this conceptual row only include:

            To create a row in this table, a manager must set this object to
            createAndGo(4).

            In particular, a newly created row cannot be created until the
            corresponding 'zxAnEponRmWanPrfName' have been set.

            To delete a row in this table, a manager must set this object to
            destroy(6).

            To query this object, always return 1."
        ::= { zxAnEponRmWanPrfEntry 50 }

------------------------------------------------------------------------------
-- 1.53.3 zxAnEponRmOnuWanConfTable
------------------------------------------------------------------------------
    zxAnEponRmOnuWanConfTable  OBJECT-TYPE
        SYNTAX         SEQUENCE OF ZxAnEponRmOnuWanConfEntry
        MAX-ACCESS     not-accessible
        STATUS         current
        DESCRIPTION
            "EPON ONU WAN profile link IPv4 configuration table."
        ::= { zxAnEponRmOnuWanMgmt 3 }

    zxAnEponRmOnuWanConfEntry OBJECT-TYPE
        SYNTAX         ZxAnEponRmOnuWanConfEntry
        MAX-ACCESS     not-accessible
        STATUS         current
        DESCRIPTION
            "An entry in the EPON ONU WAN link IPV4 configuration."
        INDEX    { zxAnEponOnuIfIndex, zxAnEponRmOnuWanPortId }
        ::= { zxAnEponRmOnuWanConfTable 1 }

    ZxAnEponRmOnuWanConfEntry ::=
        SEQUENCE {
                 zxAnEponRmOnuWanPortId                   Integer32,
                 zxAnEponRmOnuWanPrfName                  DisplayString,
                 zxAnEponRmOnuWanIpAllocationMode         INTEGER,
                 zxAnEponRmOnuWanIpAddr                   IpAddress,
                 zxAnEponRmOnuWanIpMask                   IpAddress,
                 zxAnEponRmOnuWanIpGateway                IpAddress,
                 zxAnEponRmOnuWanPriDnsSvrIp              IpAddress,
                 zxAnEponRmOnuWanSecDnsSvrIp              IpAddress,
                 zxAnEponRmOnuWanPppoeAuthMode            INTEGER,
                 zxAnEponRmOnuWanPppoeUserName            DisplayString,
                 zxAnEponRmOnuWanPppoePassword            DisplayString,
                 zxAnEponRmOnuWanPppoePrxyNum             Integer32,
                 zxAnEponRmOnuWanPppoePrxyUserNum         Integer32,
                 zxAnEponRmOnuWanPortUpTime               Unsigned32,
                 zxAnEponRmOnuWanConfRowStatus            RowStatus
                 }

    zxAnEponRmOnuWanPortId     OBJECT-TYPE
        SYNTAX      Integer32(1..8)
        MAX-ACCESS  not-accessible
        STATUS      current
        DESCRIPTION
             "An ONU WAN port identifier."
        ::= { zxAnEponRmOnuWanConfEntry 1 }

    zxAnEponRmOnuWanPrfName    OBJECT-TYPE
        SYNTAX      DisplayString(SIZE(1..32))
        MAX-ACCESS  read-create
        STATUS      current
        DESCRIPTION
            "It indicates the ONU WAN profile name."
        ::= { zxAnEponRmOnuWanConfEntry 2 }

    zxAnEponRmOnuWanIpAllocationMode    OBJECT-TYPE
        SYNTAX         INTEGER{
                       static(1),
                       dhcp(2),
                       pppoe(3)
                       }
        MAX-ACCESS     read-create
        STATUS         current
        DESCRIPTION
            "It indicates that the way the ONU gets the IP confiurations of the
            Wan."
        DEFVAL { static }
        ::= { zxAnEponRmOnuWanConfEntry 3 }

    zxAnEponRmOnuWanIpAddr    OBJECT-TYPE
        SYNTAX         IpAddress
        MAX-ACCESS     read-create
        STATUS         current
        DESCRIPTION
            "It indicates the ONU WAN IP address. It is relation to
            'zxAnEponRmOnuWanIpAllocationMode'. It is valid only when
            'zxAnEponRmOnuWanIpAllocationMode' is static. It returns the current
            IP address when getting, return 0 for DHCP or PPPoE failed."
        ::= { zxAnEponRmOnuWanConfEntry 4 }

    zxAnEponRmOnuWanIpMask    OBJECT-TYPE
        SYNTAX        IpAddress
        MAX-ACCESS    read-create
        STATUS        current
        DESCRIPTION
            "It indicates the ONU WAN IP mask. It is relation to
            'zxAnEponRmOnuWanIpAllocationMode'. It is valid only when
            'zxAnEponRmOnuWanIpAllocationMode' is static. It returns the current
            IP mask when getting, return 0 for DHCP or PPPoE failed."
        ::= { zxAnEponRmOnuWanConfEntry 5 }

    zxAnEponRmOnuWanIpGateway    OBJECT-TYPE
        SYNTAX        IpAddress
        MAX-ACCESS    read-create
        STATUS        current
        DESCRIPTION
            "It indicates the ONU WAN IP gateway. It is relation to
            'zxAnEponRmOnuWanIpAllocationMode'. It is valid only when
            'zxAnEponRmOnuWanIpAllocationMode' is static. It returns the current
            IP gateway when getting, return 0 for DHCP or PPPoE failed."
        ::= { zxAnEponRmOnuWanConfEntry 6 }

    zxAnEponRmOnuWanPriDnsSvrIp    OBJECT-TYPE
        SYNTAX        IpAddress
        MAX-ACCESS    read-create
        STATUS        current
        DESCRIPTION
            "It indicates the ONU WAN primary DNS server IP address. It is
            relation to 'zxAnEponRmOnuWanIpAllocationMode'. It is valid only when
            'zxAnEponRmOnuWanIpAllocationMode' is static. It returns the current
            Primary DNS Server IP gateway when getting, return 0 for DHCP or
            PPPoE failed."
        ::= { zxAnEponRmOnuWanConfEntry 7 }

    zxAnEponRmOnuWanSecDnsSvrIp    OBJECT-TYPE
        SYNTAX        IpAddress
        MAX-ACCESS    read-create
        STATUS        current
        DESCRIPTION
            "It indicates the ONU WAN secondary DNS server IP address. It is
            relation to 'zxEponRmOnuWANIpAllocationMode'. It is valid only
            when 'zxAnEponRmOnuWanIpAllocationMode' is static. It returns the
            current Secondary DNS Server IP gateway when getting, return 0 for
            DHCP or PPPoE failed."
        ::= { zxAnEponRmOnuWanConfEntry 8 }

    zxAnEponRmOnuWanPppoeAuthMode    OBJECT-TYPE
        SYNTAX        INTEGER{
                      auto(1),
                      chap(2),
                      pap(3)
                      }
        MAX-ACCESS    read-create
        STATUS        current
        DESCRIPTION
            "It indicates the ONU WAN PPPoE authentication mode. It is relation
            to 'zxAnEponRmOnuWanIpAllocationMode' and 'zxAnEponRmWanPrfSrvType'. It
            is valid only when 'zxAnEponRmOnuWanIpAllocationMode' is PPPoE, and
            'zxAnEponRmWanPrfSrvType' include internet."
        DEFVAL { auto }
        ::= { zxAnEponRmOnuWanConfEntry 9 }

    zxAnEponRmOnuWanPppoeUserName    OBJECT-TYPE
        SYNTAX        DisplayString(SIZE(0..32))
        MAX-ACCESS    read-create
        STATUS        current
        DESCRIPTION
            "It indicates the ONU WAN PPPoE username. It is relation to
            'zxAnEponRmOnuWanIpAllocationMode' and 'zxAnEponRmWanPrfSrvType'. It is
            valid only when 'zxAnEponRmOnuWanIpAllocationMode' is PPPoE, and
            'zxAnEponRmWanPrfSrvType' include internet. It use ASCII coding. The
            value is on the low position, When 'zxAnEponRmOnuWanPppoeUserName'
            is less 32 byte, fill 0x00 on the high position."
        ::= { zxAnEponRmOnuWanConfEntry 10 }

    zxAnEponRmOnuWanPppoePassword    OBJECT-TYPE
        SYNTAX        DisplayString(SIZE(0..32))
        MAX-ACCESS    read-create
        STATUS        current
        DESCRIPTION
            "It indicates the ONU Wan PPPoE password. It is relation to
            'zxAnEponRmOnuWanIpAllocationMode' and 'zxAnEponRmWanPrfSrvType'. It is
            valid only when 'zxAnEponRmOnuWanIpAllocationMode' is PPPoE, and
            'zxAnEponRmWanPrfSrvType' include internet. It use ASCII coding. The
            value is on the low position, When 'zxAnEponRmOnuWanPppoeUserName' is
            less 32 byte, fill 0x00 on the high position."
        ::= { zxAnEponRmOnuWanConfEntry 11 }

    zxAnEponRmOnuWanPppoePrxyNum    OBJECT-TYPE
        SYNTAX        Integer32(0..65535)
        MAX-ACCESS    read-create
        STATUS        current
        DESCRIPTION
            "It indicates the ONU WAN PPPoE proxy number. It is relation to
            'zxAnEponRmOnuWanIpAllocationMode' and 'zxAnEponRmWanPrfSrvType'. It is
            valid only when 'zxAnEponRmOnuWanIpAllocationMode' is PPPoE, and
            'zxAnEponRmWanPrfSrvType' include internet. 0 is disable, 65535 is no
            limit, other is PPPoE proxy number."
        ::= { zxAnEponRmOnuWanConfEntry 12 }

    zxAnEponRmOnuWanPppoePrxyUserNum    OBJECT-TYPE
        SYNTAX        Integer32(0..65535)
        MAX-ACCESS    read-create
        STATUS        current
        DESCRIPTION
            "It indicates the ONU WAN PPPoE proxy user number. It is relation to
            'zxAnEponRmOnuWanIpAllocationMode' and 'zxAnEponRmWanPrfSrvType'. It is
            valid only when 'zxAnEponRmOnuWanIpAllocationMode' is PPPoE, and
            'zxAnEponRmWanPrfSrvType' include internet. 0 is disable, 65535 is no
            limit, other is PPPoE proxy user number."
        ::= { zxAnEponRmOnuWanConfEntry 13 }

    zxAnEponRmOnuWanPortUpTime     OBJECT-TYPE
        SYNTAX       Unsigned32(0..4294967295)
        UNITS       "Seconds"
        MAX-ACCESS   read-only
        STATUS       current
        DESCRIPTION
            "It indicates the elapsed time that the IPv4 WAN is active. It
            starts counting when the WAN is working properly. 0 is not active."
        DEFVAL { 0 }
        ::= { zxAnEponRmOnuWanConfEntry 14 }

    zxAnEponRmOnuWanConfRowStatus     OBJECT-TYPE
        SYNTAX      RowStatus
        MAX-ACCESS  read-create
        STATUS      current
        DESCRIPTION
            "The status of this conceptual row.

            The supported actions of this conceptual row only include:

            To create a row in this table, a manager must set this object to
            createAndGo(4).

            In particular, a newly created row can be modified.

            To delete a row in this table, a manager must set this object to
            destroy(6).

            To query this object, always return 1."
        ::= { zxAnEponRmOnuWanConfEntry 50 }
------------------------------------------------------------------------------
-- 1.53.4 zxAnEponRmOnuWanGlobalConfTable
------------------------------------------------------------------------------
    zxAnEponRmOnuWanGlobalConfTable  OBJECT-TYPE
        SYNTAX         SEQUENCE OF ZxAnEponRmOnuWanGlobalConfEntry
        MAX-ACCESS     not-accessible
        STATUS         current
        DESCRIPTION
            "WAN global configuration table of ONU."
        ::= { zxAnEponRmOnuWanMgmt 4 }

    zxAnEponRmOnuWanGlobalConfEntry OBJECT-TYPE
        SYNTAX         ZxAnEponRmOnuWanGlobalConfEntry
        MAX-ACCESS     not-accessible
        STATUS         current
        DESCRIPTION
            "It is entry in the zxAnEponRmOnuWanGlobalConfTable."
        INDEX    { zxAnEponOnuIfIndex }
        ::= { zxAnEponRmOnuWanGlobalConfTable 1 }

    ZxAnEponRmOnuWanGlobalConfEntry ::=
        SEQUENCE {
                 zxAnEponRmOnuWanGlbMaxUserNum          Integer32
                 }

    zxAnEponRmOnuWanGlbMaxUserNum     OBJECT-TYPE
        SYNTAX      Integer32(0..255)
        MAX-ACCESS  read-write
        STATUS      current
        DESCRIPTION
             "This attribute identifies the maximum user number of WAN.
             The value 254 means the ONU's internal policy.
             The value 255 means no limit."
        DEFVAL { 254 }
        ::= { zxAnEponRmOnuWanGlobalConfEntry 1 }

----------------------------------------------------------------
------ ONU Power Saving Management
----------------------------------------------------------------
    zxAnEponOnuPowerSavingMgmt  OBJECT IDENTIFIER ::=
                                              { zxAnEponOnuExtendedAttrMgmt 55}

    zxAnEponOnuPowerSavingTable  OBJECT-TYPE
        SYNTAX      SEQUENCE OF ZxAnEponOnuPowerSavingEntry
        MAX-ACCESS  not-accessible
        STATUS      current
        DESCRIPTION
            "EPON ONU power saving table."
        ::= {zxAnEponOnuPowerSavingMgmt 2}

    zxAnEponOnuPowerSavingEntry  OBJECT-TYPE
        SYNTAX      ZxAnEponOnuPowerSavingEntry
        MAX-ACCESS  not-accessible
        STATUS      current
        DESCRIPTION
           "EPON ONU power saving entry."
        INDEX    {zxAnEponOnuIfIndex }
        ::= {zxAnEponOnuPowerSavingTable 1}

    ZxAnEponOnuPowerSavingEntry ::=
        SEQUENCE {
            zxAnEponOnuPwrSaveEnable              INTEGER,
            zxAnEponOnuPwrSaveSleepMode           BITS,
            zxAnEponOnuPwrSaveSleepConfMode       INTEGER,
            zxAnEponOnuPwrSaveEarlyWakeUp         INTEGER,
            zxAnEponOnuPwrSaveEarlyWakeUpEn       INTEGER,
            zxAnEponOnuPwrSaveSleepDuration       Integer32,
            zxAnEponOnuPwrSaveWakeUpDuration      Integer32,
            zxAnEponOnuPwrSaveMaxRefreshTime      Unsigned32
            }

    zxAnEponOnuPwrSaveEnable  OBJECT-TYPE
        SYNTAX      INTEGER{
             enabled(1),
             disabled(2)
             }
        MAX-ACCESS  read-write
        STATUS      current
        DESCRIPTION
             "Enable or disable EPON ONU power saving function."
        DEFVAL  { disabled }
        ::= { zxAnEponOnuPowerSavingEntry 1 }

    zxAnEponOnuPwrSaveSleepMode  OBJECT-TYPE
        SYNTAX  BITS {
            tx(0),
            trx(1)
        }
        MAX-ACCESS  read-only
        STATUS      current
        DESCRIPTION
             "EPON ONU power saving sleep mode.
             Value are defined as follows:
             00  Unsupported.
             10  Only supports transmitting sleep mode.
             01  Only supports transmitting and receiving sleep mode at
                the same time.
             11  Supports transmitting sleep mode or supports transmitting and
                receiving sleep mode at the same time.
             "
        ::= { zxAnEponOnuPowerSavingEntry 2 }

    zxAnEponOnuPwrSaveSleepConfMode  OBJECT-TYPE
        SYNTAX      INTEGER{
            tx(1),
            trx(2)
            }
        MAX-ACCESS  read-write
        STATUS      current
        DESCRIPTION
             "ONU power saving configuration mode.
             Value are defined as follows:
             1  Only supports transmitting sleep mode.
             2  Supports transmitting and receiving sleep mode at
                the same time.
             "
        DEFVAL { onlyTx }
        ::= { zxAnEponOnuPowerSavingEntry 3 }

    zxAnEponOnuPwrSaveEarlyWakeUp  OBJECT-TYPE
        SYNTAX      INTEGER{
            supported(1),
            unsupported(2)
            }

        MAX-ACCESS  read-only
        STATUS      current
        DESCRIPTION
             "EPON ONU early wake-up function."
        ::= { zxAnEponOnuPowerSavingEntry 4 }

    zxAnEponOnuPwrSaveEarlyWakeUpEn  OBJECT-TYPE
        SYNTAX      INTEGER{
            enabled(1),
            disabled(2)
            }
        MAX-ACCESS  read-write
        STATUS      current
        DESCRIPTION
             "Enable or disable EPON ONU early wake-up function."
        DEFVAL { disabled }
        ::= { zxAnEponOnuPowerSavingEntry 5 }

    zxAnEponOnuPwrSaveSleepDuration  OBJECT-TYPE
        SYNTAX      Integer32(0..62500000)
        UNITS       "TQ"
        MAX-ACCESS  read-write
        STATUS      current
        DESCRIPTION
             "ONU sleep duration."
        DEFVAL { 0 }
        ::= { zxAnEponOnuPowerSavingEntry 6 }

    zxAnEponOnuPwrSaveWakeUpDuration  OBJECT-TYPE
        SYNTAX      Integer32(0..62500000)
        UNITS       "TQ"
        MAX-ACCESS  read-write
        STATUS      current
        DESCRIPTION
             "ONU wake-up duration."
        DEFVAL { 0 }
        ::= { zxAnEponOnuPowerSavingEntry 7 }

    zxAnEponOnuPwrSaveMaxRefreshTime  OBJECT-TYPE
        SYNTAX      Unsigned32(0..4294967295)
        UNITS       "125Microseconds"
        MAX-ACCESS  read-write
        STATUS      current
        DESCRIPTION
             "The maximum power saving refreshing time."
        DEFVAL     { 8000 }
        ::= { zxAnEponOnuPowerSavingEntry 8 }

----------------------------------------------------------------
------ ONU protection management
----------------------------------------------------------------
    zxAnEponOnuProtectMgmt  OBJECT IDENTIFIER ::=
                                              { zxAnEponOnuExtendedAttrMgmt 56}

    zxAnOnuProtectConfTable  OBJECT-TYPE
        SYNTAX      SEQUENCE OF ZxAnOnuProtectConfEntry
        MAX-ACCESS  not-accessible
        STATUS      current
        DESCRIPTION
            "EPON ONU protection configuration table."
        ::= {zxAnEponOnuProtectMgmt 56}

    zxAnOnuProtectConfEntry  OBJECT-TYPE
        SYNTAX      ZxAnOnuProtectConfEntry
        MAX-ACCESS  not-accessible
        STATUS      current
        DESCRIPTION
           "EPON ONU protection parameters configuration entry."
        INDEX    {zxAnEponOnuIfIndex }
        ::= {zxAnOnuProtectConfTable 1}

    ZxAnOnuProtectConfEntry ::=
        SEQUENCE {
            zxAnOnuProtectLosTimeByOptSignal      Integer32,
            zxAnOnuProtectLosTimeByMpcp           Integer32
            }

    zxAnOnuProtectLosTimeByOptSignal  OBJECT-TYPE
        SYNTAX      Integer32(1..65535)
        UNITS       "Milliseconds"
        MAX-ACCESS  read-write
        STATUS      current
        DESCRIPTION
            "Time to confirm EPON ONU LOS by detecting optical signal."
        DEFVAL { 2 }
        ::= { zxAnOnuProtectConfEntry 1 }

    zxAnOnuProtectLosTimeByMpcp  OBJECT-TYPE
        SYNTAX      Integer32(1..65535)
        UNITS       "Milliseconds"
        MAX-ACCESS  read-write
        STATUS      current
        DESCRIPTION
             "Time to confirm EPON ONU LOS by MPCP detecting message."
        DEFVAL { 55 }
        ::= { zxAnOnuProtectConfEntry 2 }
END
