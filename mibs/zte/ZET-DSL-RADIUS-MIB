ZET-DSL-RADIUS-MIB DEFINITIONS ::= BEGIN
IMPORTS
    ifIndex                                    FROM IF-MIB
    MODULE-IDENTITY, OBJECT-TYPE, IpAddress    FROM SNMPv2-SMI
    DisplayString, RowStatus                   FROM SNMPv2-TC
    enterprises                                FROM RFC1155-SMI;

zxDslRadiusMib MODULE-IDENTITY
        LAST-UPDATED    "0706090000Z"
        ORGANIZATION    "Zhongxing Telcom Co. Ltd."
        CONTACT-INFO    "E-mail: suchunshan@zte.com.cn"
        DESCRIPTION     "RADIUS Control MIB definition."
    ::= { zxDsl 34 }



zte OBJECT IDENTIFIER ::= { enterprises 3902 }
zxDsl OBJECT IDENTIFIER ::= { zte 1004 }

zxDslRadiusClient      OBJECT IDENTIFIER ::= { zxDslRadiusMib 1 }

zxDslRadiusClientAuthSvrTable OBJECT-TYPE
      SYNTAX SEQUENCE OF ZxDslRadiusClientAuthSvrEntry
      MAX-ACCESS not-accessible
      STATUS     current
      DESCRIPTION
            "The (conceptual) table listing the RADIUS accounting
             servers with which the client shares a secret."
      ::= { zxDslRadiusClient 1 }

zxDslRadiusClientAuthSvrEntry OBJECT-TYPE
      SYNTAX     ZxDslRadiusClientAuthSvrEntry
      MAX-ACCESS not-accessible
      STATUS     current
      DESCRIPTION
            "An entry (conceptual row) representing a RADIUS
             accounting server with which the client shares a secret."
      INDEX      { zxDslRadiusClientAuthSvrIndex }
      ::= { zxDslRadiusClientAuthSvrTable 1 }

ZxDslRadiusClientAuthSvrEntry ::= SEQUENCE {
      zxDslRadiusClientAuthSvrIndex      INTEGER,
      zxDslRadiusClientAuthAddress       IpAddress,
      zxDslRadiusClientAuthPortNumber    INTEGER,
      zxDslRadiusClientAuthSecret        DisplayString,
      zxDslRadiusClientAuthRowStatus     RowStatus
}

zxDslRadiusClientAuthSvrIndex OBJECT-TYPE
      SYNTAX     INTEGER
      MAX-ACCESS not-accessible
      STATUS     current
      DESCRIPTION
            "The index of the RADIUS authentication server
             referred to in this table entry."
      ::= { zxDslRadiusClientAuthSvrEntry 1 }

zxDslRadiusClientAuthAddress OBJECT-TYPE
      SYNTAX     IpAddress
      MAX-ACCESS read-create
      STATUS     current
      DESCRIPTION
            "The IP address of the RADIUS authentication server
             referred to in this table entry."
      ::= { zxDslRadiusClientAuthSvrEntry 2 }

zxDslRadiusClientAuthPortNumber  OBJECT-TYPE
      SYNTAX INTEGER
      MAX-ACCESS read-create
      STATUS current
      DESCRIPTION
            "The UDP port the client is using to send requests to
             this server."
      ::= { zxDslRadiusClientAuthSvrEntry 3 }

zxDslRadiusClientAuthSecret OBJECT-TYPE
    SYNTAX      DisplayString (SIZE (0..32))
    MAX-ACCESS  read-create
    STATUS      current
    DESCRIPTION
        ""
    REFERENCE
        "1"
    ::= { zxDslRadiusClientAuthSvrEntry 4}


zxDslRadiusClientAuthRowStatus OBJECT-TYPE
    SYNTAX      RowStatus
    MAX-ACCESS  read-create
    STATUS      current
    DESCRIPTION
        "This object indicates the status of this entry."
    ::= { zxDslRadiusClientAuthSvrEntry 5 }

END
