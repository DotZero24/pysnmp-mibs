ZTE-AN-BFD-STD-MIB DEFINITIONS ::= BEGIN

    IMPORTS
        MODULE-IDENTITY, OBJECT-TYPE, NOTIFICATION-TYPE,
            mib-2, Integer32, Unsigned32, Counter32, Counter64
            FROM SNMPv2-SMI

        TEXTUAL-CONVENTION, TruthValue, RowStatus,
            StorageType, TimeStamp
            FROM SNMPv2-TC

        MODULE-COMPLIANCE, OBJECT-GROUP, NOTIFICATION-GROUP
            FROM SNMPv2-CONF

        InterfaceIndexOrZero
            FROM IF-MIB

        InetAddress, InetAddressType, InetPortNumber
            FROM INET-ADDRESS-MIB

        zxAn
            FROM ZTE-AN-TC-MIB;

    zxAnBfdStdMib MODULE-IDENTITY
        LAST-UPDATED "201003031200Z" -- 3 March 2010 12:00:00 EST
        ORGANIZATION "IETF Bidirectional Forwarding Detection
                      Working Group"
        CONTACT-INFO
            "Thomas D. Nadeau
             BT
             Email:  tom.nadeau@bt.com

             Zafar Ali
             Cisco Systems, Inc.
             Email:  zali@cisco.com

             Nobo Akiya
             Cisco Systems, G.K.
             Email:  nobo@cisco.com"
        DESCRIPTION
            "Bidirectional Forwarding Management Information Base.
             This MIB is currently under the draft submitted by BT and Cisco,
             so the implement of current network management and network elements
             are temporary.
             This draft is currently in Standard Track phase. When the formal
             standard to be released, network management and network elements
             must re-implement in accordance with the official standards."
        REVISION "201003031200Z" -- 3 March 2010 12:00:00 EST
        DESCRIPTION
            "Initial version."
         ::= { zxAn 16 }

  -- Top level components of this MIB module.

    zxAnBfdStdNotifications OBJECT IDENTIFIER ::= { zxAnBfdStdMib 0 }

    zxAnBfdStdObjects       OBJECT IDENTIFIER ::= { zxAnBfdStdMib 1 }

    zxAnBfdStdConformance   OBJECT IDENTIFIER ::= { zxAnBfdStdMib 2 }

    zxAnBfdStdGlobalObjects OBJECT IDENTIFIER ::= { zxAnBfdStdObjects 1 }

 -- Textual Conventions

    ZxAnBfdStdSessIndexTC ::= TEXTUAL-CONVENTION
    DISPLAY-HINT   "d"
    STATUS         current
    DESCRIPTION
        "An index used to uniquely identify BFD sessions."
    SYNTAX Unsigned32 (1..4294967295)

    ZxAnBfdStdInterval ::= TEXTUAL-CONVENTION
    DISPLAY-HINT   "d"
    STATUS         current
    DESCRIPTION
        "The BFD interval delay in microseconds."
    SYNTAX Unsigned32 (0..4294967295)

    ZxAnBfdStdMultiplier ::= TEXTUAL-CONVENTION
    DISPLAY-HINT   "d"
    STATUS         current
    DESCRIPTION
        "The BFD failure detection multiplier."
    SYNTAX Unsigned32 (1..255)

    ZxAnBfdStdDiag ::= TEXTUAL-CONVENTION
    STATUS         current
    DESCRIPTION
        "A common BFD diagnostic code."
    SYNTAX INTEGER {
        controlDetectionTimeExpired(1),
        echoFunctionFailed(2),
        neighborSignaledSessionDown(3),
        forwardingPlaneReset(4),
        pathDown(5),
        concatenatedPathDown(6),
        administrativelyDown(7),
        reverseConcatenatedPathDown(8),
        noDiagnostic(99)
    }

 -- BFD General Variables

 -- These parameters apply globally to the Systems'
 -- BFD Process.

    zxAnBfdStdAdminStatus OBJECT-TYPE
        SYNTAX     INTEGER {
            enabled(1),
            disabled(2)
        }
        MAX-ACCESS read-write
        STATUS     current
        DESCRIPTION
            "The global administrative status of BFD in this router.
             The value 'enabled' denotes that the BFD Process is
             active on at least one interface; 'disabled' disables
             it on all interfaces."
        DEFVAL { enabled }
        ::= { zxAnBfdStdGlobalObjects 1 }

    zxAnBfdStdSessTrapsEnable OBJECT-TYPE
        SYNTAX     TruthValue
        MAX-ACCESS read-write
        STATUS     current
        DESCRIPTION
            "If this object is set to true(1), then it enables
             the emission of zxAnBfdStdSessUp and zxAnBfdStdSessDown
             notifications; otherwise these notifications are not
             emitted."
        REFERENCE
            "See also RFC3413 for explanation that
             notifications are under the ultimate control of the
             MIB modules in this document."
        DEFVAL { false }
        ::= { zxAnBfdStdGlobalObjects 2 }

 -- BFD Session Table
 -- The BFD Session Table specifies BFD session specific
 -- information.

    zxAnBfdStdSessTable OBJECT-TYPE
        SYNTAX     SEQUENCE OF ZxAnBfdStdSessEntry
        MAX-ACCESS not-accessible
        STATUS     current
        DESCRIPTION
            "The BFD Session Table describes the BFD sessions."
        REFERENCE
            "BFD Version 0 (draft-katz-ward-bfd-02.txt) and
             BFD Version 1 (draft-ietf-bfd-base-11.txt)"
        ::= { zxAnBfdStdObjects 2 }

    zxAnBfdStdSessEntry OBJECT-TYPE
        SYNTAX     ZxAnBfdStdSessEntry
        MAX-ACCESS not-accessible
        STATUS     current
        DESCRIPTION
            "The BFD Session Entry describes BFD session."
        INDEX { zxAnBfdStdSessIndex }
        ::= { zxAnBfdStdSessTable 1 }

    ZxAnBfdStdSessEntry ::= SEQUENCE {
        zxAnBfdStdSessIndex                    ZxAnBfdStdSessIndexTC,
        zxAnBfdStdSessVersionNumber            Unsigned32,
        zxAnBfdStdSessType                     INTEGER,
        zxAnBfdStdSessMHopUniLinkMode          INTEGER,
        zxAnBfdStdSessDiscriminator            Unsigned32,
        zxAnBfdStdSessRemoteDiscr              Unsigned32,
        zxAnBfdStdSessDestinationUdpPort       InetPortNumber,
        zxAnBfdStdSessSourceUdpPort            InetPortNumber,
        zxAnBfdStdSessEchoSourceUdpPort        InetPortNumber,
        zxAnBfdStdSessAdminStatus              INTEGER,
        zxAnBfdStdSessState                    INTEGER,
        zxAnBfdStdSessRemoteHeardFlag          TruthValue,
        zxAnBfdStdSessDiag                     ZxAnBfdStdDiag,
        zxAnBfdStdSessOperMode                 INTEGER,
        zxAnBfdStdSessDesiredDmdMode           TruthValue,
        zxAnBfdStdSessCtrlPlaneIndep           TruthValue,
        zxAnBfdStdSessMultipointFlag           TruthValue,
        zxAnBfdStdSessInterface                InterfaceIndexOrZero,
        zxAnBfdStdSessPeerIpAddrType           InetAddressType,
        zxAnBfdStdSessPeerIpAddr               InetAddress,
        zxAnBfdStdSessGTSM                     TruthValue,
        zxAnBfdStdSessGTSMTTL                  Unsigned32,
        zxAnBfdStdSessDesiredMinTxIntv         ZxAnBfdStdInterval,
        zxAnBfdStdSessReqMinRxIntv             ZxAnBfdStdInterval,
        zxAnBfdStdSessReqMinEchoRxIntv         ZxAnBfdStdInterval,
        zxAnBfdStdSessDetectMult               ZxAnBfdStdMultiplier,
        zxAnBfdStdSessNegInterval              ZxAnBfdStdInterval,
        zxAnBfdStdSessNegEchoInterval          ZxAnBfdStdInterval,
        zxAnBfdStdSessNegDetectMult            ZxAnBfdStdMultiplier,
        zxAnBfdStdSessAuthPresFlag             TruthValue,
        zxAnBfdStdSessAuthType                 INTEGER,
        zxAnBfdStdSessAuthKeyID                Integer32,
        zxAnBfdStdSessAuthKey                  OCTET STRING,
        zxAnBfdStdSessIpAddrType               InetAddressType,
        zxAnBfdStdSessIpAddr                   InetAddress,
        zxAnBfdStdSessAppType                  INTEGER,
        zxAnBfdStdSessStorType                 StorageType,
        zxAnBfdStdSessRowStatus                RowStatus
    }

    zxAnBfdStdSessIndex OBJECT-TYPE
        SYNTAX     ZxAnBfdStdSessIndexTC
        MAX-ACCESS not-accessible
        STATUS     current
        DESCRIPTION
            "This object contains an index used to represent a
             unique BFD session on this device."
        ::= { zxAnBfdStdSessEntry 1 }

    zxAnBfdStdSessVersionNumber OBJECT-TYPE
        SYNTAX     Unsigned32 (0..7)
        MAX-ACCESS read-create
        STATUS     current
        DESCRIPTION
            "The version number of the BFD protocol that this session
             is running in. Write access is available for this object
             to provide ability to set desired version for this
             BFD session."
        REFERENCE
            "BFD Version 0 (draft-katz-ward-bfd-02.txt) and
             BFD Version 1 (draft-ietf-bfd-base-11.txt)"
        DEFVAL { 1 }
        ::= { zxAnBfdStdSessEntry 2 }

    zxAnBfdStdSessType OBJECT-TYPE
        SYNTAX     INTEGER {
            singleHop(1),
            multiHopTotallyArbitraryPaths(2),
            multiHopOutOfBandSignaling(3),
            multiHopUnidirectionalLinks(4)
        }
        MAX-ACCESS read-only
        STATUS     current
        DESCRIPTION
            "This object specifies the type of this BFD session."
        REFERENCE
            "draft-ietf-bfd-v4v6-1hop-11 and
             draft-ietf-bfd-multihop-09"
        ::= { zxAnBfdStdSessEntry 3 }

    zxAnBfdStdSessMHopUniLinkMode OBJECT-TYPE
        SYNTAX     INTEGER {
            none(1),
            active(2),
            passive(3)
        }
        MAX-ACCESS read-only
        STATUS     current
        DESCRIPTION
            "For zxAnBfdStdSessType of multiHopUnidirectionalLinks(4), this
             object specifies whether this BFD session is running in
             active(2) mode or passive(3) mode. For all other BFD
             zxAnBfdStdSessType BFD sessions, none(1) MUST be specified."
        REFERENCE
            "draft-ietf-bfd-multihop-09, Section 3.3"
        ::= { zxAnBfdStdSessEntry 4 }

    zxAnBfdStdSessDiscriminator OBJECT-TYPE
        SYNTAX     Unsigned32 (1..4294967295)
        MAX-ACCESS read-only
        STATUS     current
        DESCRIPTION
            "This object specifies the local discriminator for this BFD
             session, used to uniquely identify it."
        ::= { zxAnBfdStdSessEntry 5 }

    zxAnBfdStdSessRemoteDiscr OBJECT-TYPE
        SYNTAX     Unsigned32 (0 | 1..4294967295)
        MAX-ACCESS read-only
        STATUS     current
        DESCRIPTION
            "This object specifies the session discriminator chosen
             by the remote system for this BFD session.  The value may
             be zero(0) if the remote discriminator is not yet known
             or if the session is in the down or adminDown(1) state."
        REFERENCE
            "draft-ietf-bfd-base-11, Section 6.8.6."
        ::= { zxAnBfdStdSessEntry 6 }

    zxAnBfdStdSessDestinationUdpPort OBJECT-TYPE
        SYNTAX     InetPortNumber
        MAX-ACCESS read-only
        STATUS     current
        DESCRIPTION
            "This object specifies the destination UDP port used for
             this BFD session. The value maybe zero(0) if the session
             is in adminDown(1) state."
        REFERENCE
            "Port 3784 (draft-ietf-bfd-v4v6-1hop-11),
             Port 3785 (draft-ietf-bfd-v4v6-1hop-11), and
             Port 4784 (draft-ietf-bfd-multihop-09)"
        DEFVAL { 0 }
        ::= { zxAnBfdStdSessEntry 7 }

    zxAnBfdStdSessSourceUdpPort OBJECT-TYPE
        SYNTAX     InetPortNumber
        MAX-ACCESS read-create
        STATUS     current
        DESCRIPTION
            "This object specifies the source UDP port of BFD control
             packets for this BFD session. The value maybe zero(0) if
             the session is in adminDown(1) state."
        REFERENCE
            "draft-ietf-bfd-v4v6-1hop-11 and
             draft-ietf-bfd-multihop-09"
        DEFVAL { 0 }
        ::= { zxAnBfdStdSessEntry 8 }

    zxAnBfdStdSessEchoSourceUdpPort OBJECT-TYPE
        SYNTAX     InetPortNumber
        MAX-ACCESS read-create
        STATUS     current
        DESCRIPTION
            "This object specifies the source UDP port of BFD echo
             packets for this BFD session. The value maybe zero(0) if
             the session is not running in the echo mode, or the
             session is in adminDown(1) state."
        REFERENCE
            "draft-ietf-bfd-v4v6-1hop-11 and
             draft-ietf-bfd-multihop-09"
        DEFVAL { 0 }
        ::= { zxAnBfdStdSessEntry 9 }

    zxAnBfdStdSessAdminStatus OBJECT-TYPE
        SYNTAX     INTEGER {
                            stop(1),
                            start(2)
                   }
        MAX-ACCESS read-create
        STATUS     current
        DESCRIPTION
                "A transition from 'stop' to 'start' will start
                 the BFD state machine for the session. The state
                 machine will have an initial state of down.
                 A transition from 'start' to 'stop' will cause
                 the BFD sesssion to be brought down to
                 adminDown(1). Care should be used in providing
                 write access to this object without adequate
                 authentication."
        DEFVAL { 2 }
        ::= { zxAnBfdStdSessEntry 10 }

    zxAnBfdStdSessState OBJECT-TYPE
        SYNTAX     INTEGER {
            adminDown(1),
            down(2),
            init(3),
            up(4),
            failing(5)
        }
        MAX-ACCESS read-only
        STATUS     current
        DESCRIPTION
            "The perceived state of the BFD session.
             BFD State failing(5) is only applicable if this BFD
             session is running version 0.
             Upon creation of a new BFD session via this MIB, the
             suggested initial state is down(2)."
        DEFVAL { 2 }
        ::= { zxAnBfdStdSessEntry 11 }

    zxAnBfdStdSessRemoteHeardFlag OBJECT-TYPE
        SYNTAX     TruthValue
        MAX-ACCESS read-only
        STATUS     current
        DESCRIPTION
            "This object specifies status of BFD packet reception from
             the remote system. Specifically, it is set to true(1) if
             the local system is actively receiving BFD packets from the
             remote system, and is set to false(2) if the local system
             has not received BFD packets recently (within the detection
             time) or if the local system is attempting to tear down
             the BFD session."
        REFERENCE
            "BFD Version 0 (draft-katz-ward-bfd-02.txt) and
             BFD Version 1 (draft-ietf-bfd-base-11.txt)"
        DEFVAL { false }
        ::= { zxAnBfdStdSessEntry 12 }

    zxAnBfdStdSessDiag OBJECT-TYPE
        SYNTAX     ZxAnBfdStdDiag
        MAX-ACCESS accessible-for-notify
        STATUS     current
        DESCRIPTION
            "A diagnostic code specifying the local system's reason
             for the last transition of the session from up(4)
             to some other state."
        ::= { zxAnBfdStdSessEntry 13 }

    zxAnBfdStdSessOperMode OBJECT-TYPE
        SYNTAX     INTEGER {
            asyncModeWEchoFunction(1),
            asynchModeWOEchoFunction(2),
            demandModeWEchoFunction(3),
            demandModeWOEchoFunction(4)
        }
        MAX-ACCESS read-only
        STATUS     current
        DESCRIPTION
            "This object specifies current operating mode that BFD
             session is operating in."
        ::= { zxAnBfdStdSessEntry 14 }

    zxAnBfdStdSessDesiredDmdMode OBJECT-TYPE
        SYNTAX     TruthValue
        MAX-ACCESS read-create
        STATUS     current
        DESCRIPTION
            "This object indicates that the local system's
             desire to use Demand mode. Specifically, it is set
             to true(1) if the local system wishes to use
             Demand mode or false(2) if not"
        DEFVAL { false }
        ::= { zxAnBfdStdSessEntry 15 }

    zxAnBfdStdSessCtrlPlaneIndep OBJECT-TYPE
        SYNTAX     TruthValue
        MAX-ACCESS read-only
        STATUS     current
        DESCRIPTION
            "This object indicates that the local system's
             ability to continue to function through a disruption of
             the control plane. Specifically, it is set
             to true(1) if the local system BFD implementation is
             independent of the control plane. Otherwise, the
             value is set to false(2)"
        DEFVAL { false }
        ::= { zxAnBfdStdSessEntry 16 }

    zxAnBfdStdSessMultipointFlag OBJECT-TYPE
        SYNTAX     TruthValue
        MAX-ACCESS read-only
        STATUS     current
        DESCRIPTION
            "This object indicates the Multipoint (M) bit for this
             session. It is set to true(1) if Multipoint (M) bit is
             set to 1. Otherwise, the value is set to false(2)"
        DEFVAL { false }
        ::= { zxAnBfdStdSessEntry 17 }

    zxAnBfdStdSessInterface OBJECT-TYPE
        SYNTAX     InterfaceIndexOrZero
        MAX-ACCESS read-create
        STATUS     current
        DESCRIPTION
            "This object contains an interface index used to indicate
             the interface which this BFD session is running on. This
             value can be zero if there is no interface associated
             with this BFD session."
        ::= { zxAnBfdStdSessEntry 18 }

    zxAnBfdStdSessPeerIpAddrType OBJECT-TYPE
        SYNTAX     InetAddressType
        MAX-ACCESS read-create
        STATUS     current
        DESCRIPTION
            "This object specifies IP address type of the neighboring IP
             address which is being monitored with this BFD session.

             Only values unknown(0), ipv4(1), ipv6(2), or ipv6z(4)
             have to be supported.

             A value of unknown(0) is allowed only when
             the outgoing interface is of type point-to-point, or
             when the BFD session is not associated with a specific
             interface.

             If any other unsupported values are attempted in a set
             operation, the agent MUST return an inconsistentValue
             error."
      ::= { zxAnBfdStdSessEntry 19 }

    zxAnBfdStdSessPeerIpAddr OBJECT-TYPE
        SYNTAX     InetAddress
        MAX-ACCESS read-create
        STATUS     current
        DESCRIPTION
            "This object specifies the neighboring IP address which is
             being monitored with this BFD session.
             It can also be used to enabled BFD on a specific
             interface. The value is set to zero when BFD session is not
             associated with a specific interface."
        ::= { zxAnBfdStdSessEntry 20 }

    zxAnBfdStdSessGTSM OBJECT-TYPE
        SYNTAX  TruthValue
        MAX-ACCESS read-create
        STATUS current
        DESCRIPTION
           "Setting the value of this object to true(1) will enable GTSM
            protection of the BFD session.  GTSM MUST be enabled on a
            singleHop(1) session if no authentication is in use."
        REFERENCE
           "RFC 5082 - The Generalized TTL Security Mechanism (GTSM).
            draft-ietf-bfd-v4v6-1hop-11, Sec. 5"
        DEFVAL { false }
        ::= { zxAnBfdStdSessEntry 21 }

    zxAnBfdStdSessGTSMTTL OBJECT-TYPE
        SYNTAX Unsigned32 (0..255)
        MAX-ACCESS read-create
        STATUS current
        DESCRIPTION
            "This object is valid only when zxAnBfdStdSessGTSM protection is
             enabled on the system. This object specifies the minimum
             allowed TTL for received BFD control packets. For
             singleHop(1) session, if GTSM protection is enabled,
             this object SHOULD be set to maximum TTL allowed for
             single hop."
        REFERENCE
           "RFC 5082 - The Generalized TTL Security Mechanism (GTSM).
            draft-ietf-bfd-v4v6-1hop-11, Sec. 5"
        DEFVAL { 0 }
        ::= { zxAnBfdStdSessEntry 22 }

    zxAnBfdStdSessDesiredMinTxIntv OBJECT-TYPE
        SYNTAX     ZxAnBfdStdInterval
        MAX-ACCESS read-create
        STATUS     current
        DESCRIPTION
            "This object specifies the minimum interval, in
             microseconds, that the local system would like to use when
             transmitting BFD Control packets."
        ::= { zxAnBfdStdSessEntry 23 }

    zxAnBfdStdSessReqMinRxIntv OBJECT-TYPE
        SYNTAX     ZxAnBfdStdInterval
        MAX-ACCESS read-create
        STATUS     current
        DESCRIPTION
            "This object specifies the minimum interval, in
             microseconds, between received  BFD Control packets the
             local system is capable of supporting."
        ::= { zxAnBfdStdSessEntry 24 }

    zxAnBfdStdSessReqMinEchoRxIntv OBJECT-TYPE
        SYNTAX     ZxAnBfdStdInterval
        MAX-ACCESS read-create
        STATUS     current
        DESCRIPTION
            "This object specifies the minimum interval, in
             microseconds, between received BFD Echo packets that this
             system is capable of supporting."
        ::= { zxAnBfdStdSessEntry 25 }

    zxAnBfdStdSessDetectMult OBJECT-TYPE
        SYNTAX     ZxAnBfdStdMultiplier
        MAX-ACCESS read-create
        STATUS     current
        DESCRIPTION
            "This object specifies the Detect time multiplier."
        ::= { zxAnBfdStdSessEntry 26 }

    zxAnBfdStdSessNegInterval OBJECT-TYPE
        SYNTAX     ZxAnBfdStdInterval
        MAX-ACCESS read-only
        STATUS     current
        DESCRIPTION
            "This object specifies the negotiated interval, in
             microseconds, that the local system is transmitting
             BFD Control packets."
        ::= { zxAnBfdStdSessEntry 27 }

    zxAnBfdStdSessNegEchoInterval OBJECT-TYPE
        SYNTAX     ZxAnBfdStdInterval
        MAX-ACCESS read-only
        STATUS     current
        DESCRIPTION
            "This object specifies the negotiated interval, in
             microseconds, that the local system is transmitting
             BFD echo packets. Value is expected to be zero if
             the sessions is not running in echo mode."
        ::= { zxAnBfdStdSessEntry 28 }

    zxAnBfdStdSessNegDetectMult OBJECT-TYPE
        SYNTAX     ZxAnBfdStdMultiplier
        MAX-ACCESS read-only
        STATUS     current
        DESCRIPTION
            "This object specifies the Detect time multiplier."
        ::= { zxAnBfdStdSessEntry 29 }

    zxAnBfdStdSessAuthPresFlag OBJECT-TYPE
        SYNTAX     TruthValue
        MAX-ACCESS read-only
        STATUS     current
        DESCRIPTION
            "This object indicates that the local system's
             desire to use Authentication. Specifically, it is set
             to true(1) if the local system wishes the session
             to be authenticated or false(2) if not."
        REFERENCE
            "draft-ietf-bfd-base-11, Sections 4.2 - 4.4"
        DEFVAL { false }
        ::= { zxAnBfdStdSessEntry 30 }

    zxAnBfdStdSessAuthType OBJECT-TYPE
        SYNTAX     INTEGER {
            simplePassword(1),
            keyedMD5(2),
            meticulousKeyedMD5(3),
            keyedSHA1(4),
            meticulousKeyedSHA1(5),
            reserved(99)
        }
        MAX-ACCESS read-create
        STATUS     current
        DESCRIPTION
            "The Authentication Type used for this BFD session.
             This field is valid only when the Authentication
             Present bit is set. Max-access to this object as well as
             other authentication related objects are set to
             read-create in order to support management of a single
             key ID at a time, key rotation is not handled. Key update
             in practice must be done by atomic update using a set
             containing all affected objects in the same varBindList
             or otherwise risk the session dropping."
        REFERENCE
            "draft-ietf-bfd-base-11, Sections 4.2 - 4.4"
        ::= { zxAnBfdStdSessEntry 31 }

    zxAnBfdStdSessAuthKeyID OBJECT-TYPE
        SYNTAX     Integer32 (-1 | 0..255)
        MAX-ACCESS read-create
        STATUS     current
        DESCRIPTION
            "The authentication key ID in use for this session.  This
             object permits multiple keys to be active simultaneously.

             When zxAnBfdStdSessAuthPresFlag is false(2), then the value
             of this object MUST be -1.  The value -1 indicates that
             no Authentication Key ID will be present in the optional
             BFD Authentication Section."
        REFERENCE
            "draft-ietf-bfd-base-11, Sections 4.2 - 4.4"
        DEFVAL { -1 }
        ::= { zxAnBfdStdSessEntry 32 }

    zxAnBfdStdSessAuthKey OBJECT-TYPE
        SYNTAX     OCTET STRING (SIZE (0..252))
        MAX-ACCESS read-create
        STATUS     current
        DESCRIPTION
            "The authentication key.  When the
             zxAnBfdStdSessAuthType is simplePassword(1), the value
             of this object is the password present in the BFD packets.

             When the zxAnBfdStdSessAuthentication type is one of the keyed
             authentication types, this value is used in the
             computation of the key present in the BFD authentication
             packet."
        REFERENCE
            "draft-ietf-bfd-base-11, Sections 4.2 - 4.4"
        ::= { zxAnBfdStdSessEntry 33 }

    zxAnBfdStdSessIpAddrType OBJECT-TYPE
        SYNTAX     InetAddressType
        MAX-ACCESS read-create
        STATUS     current
        DESCRIPTION
            "This object specifies IP address type of the local IP
             address which is being monitored with this BFD session.

             Only values unknown(0), ipv4(1), ipv6(2), or ipv6z(4)
             have to be supported.

             A value of unknown(0) is allowed only when
             the outgoing interface is of type point-to-point, or
             when the BFD session is not associated with a specific
             interface.

             If any other unsupported values are attempted in a set
             operation, the agent MUST return an inconsistentValue
             error."
      ::= { zxAnBfdStdSessEntry 34 }

    zxAnBfdStdSessIpAddr OBJECT-TYPE
        SYNTAX     InetAddress
        MAX-ACCESS read-create
        STATUS     current
        DESCRIPTION
            "This object specifies the local IP address which is
             being monitored with this BFD session.
             It can also be used to enabled BFD on a specific
             interface. The value is set to zero when BFD session is not
             associated with a specific interface."
        ::= { zxAnBfdStdSessEntry 35 }

    zxAnBfdStdSessAppType OBJECT-TYPE
        SYNTAX     INTEGER {
            bgp(1),
            ospf(2),
            isis(4),
            rsvp(8),
            ldp(16),
            static(32),
            rsvpLsp(64),
            ldpLsp(128),
            vrrp(256),
            pbr(512),
            pw(1024),
            pim(2048)
        }
        MAX-ACCESS read-create
        STATUS     current
        DESCRIPTION
            "The application Type used for this BFD session."
        REFERENCE
            "draft-ietf-bfd-base-11, Sections 4.2 - 4.4"
        ::= { zxAnBfdStdSessEntry 36 }

    zxAnBfdStdSessStorType OBJECT-TYPE
        SYNTAX     StorageType
        MAX-ACCESS read-create
        STATUS     current
        DESCRIPTION
            "This variable indicates the storage type for this
             object. Conceptual rows having the value
             'permanent' need not allow write-access to any
             columnar objects in the row."
        ::= { zxAnBfdStdSessEntry 60 }

    zxAnBfdStdSessRowStatus OBJECT-TYPE
        SYNTAX     RowStatus
        MAX-ACCESS read-create
        STATUS     current
        DESCRIPTION
            "This variable is used to create, modify, and/or
             delete a row in this table. When a row in this
             table has a row in the active(1) state, no
             objects in this row can be modified except the
             zxAnBfdStdSessRowStatus and zxAnBfdStdSessStorageType."
        ::= { zxAnBfdStdSessEntry 61 }

 -- BFD Session Performance Table

    zxAnBfdStdSessPerfTable OBJECT-TYPE
        SYNTAX     SEQUENCE OF ZxAnBfdStdSessPerfEntry
        MAX-ACCESS not-accessible
        STATUS     current
        DESCRIPTION
            "This table specifies BFD Session performance counters."
        ::= { zxAnBfdStdObjects 3 }

    zxAnBfdStdSessPerfEntry OBJECT-TYPE
        SYNTAX     ZxAnBfdStdSessPerfEntry
        MAX-ACCESS not-accessible
        STATUS     current
        DESCRIPTION
            "An entry in this table is created by a BFD-enabled node for
             every BFD Session. zxAnBfdStdCounterDiscontinuityTime is used to
             indicate potential discontinuity for all counter objects
             in this table."
        AUGMENTS    { zxAnBfdStdSessEntry }
        ::= { zxAnBfdStdSessPerfTable 1 }

    ZxAnBfdStdSessPerfEntry ::= SEQUENCE {
       zxAnBfdStdSessPerfCtrlPktIn           Counter32,
       zxAnBfdStdSessPerfCtrlPktOut          Counter32,
       zxAnBfdStdSessPerfCtrlPktDrop         Counter32,
       zxAnBfdStdSessPerfCtrlPktDLT          TimeStamp,
       zxAnBfdStdSessPerfEchoPktIn           Counter32,
       zxAnBfdStdSessPerfEchoPktOut          Counter32,
       zxAnBfdStdSessPerfEchoPktDrop         Counter32,
       zxAnBfdStdSessPerfEchoPktDLT          TimeStamp,
       zxAnBfdStdSessUpTime                  TimeStamp,
       zxAnBfdStdSessPerfLastSessDT          TimeStamp,
       zxAnBfdStdSessPerfLastCommLDC         ZxAnBfdStdDiag,
       zxAnBfdStdSessPerfSessUpCount         Counter32,
       zxAnBfdStdSessPerfDiscTime            TimeStamp,

       -- High Capacity Counters
       zxAnBfdStdSessPerfCtrlPktInHC         Counter64,
       zxAnBfdStdSessPerfCtrlPktOutHC        Counter64,
       zxAnBfdStdSessPerfCtrlPktDropHC       Counter64,
       zxAnBfdStdSessPerfEchoPktInHC         Counter64,
       zxAnBfdStdSessPerfEchoPktOutHC        Counter64,
       zxAnBfdStdSessPerfEchoPktDropHC       Counter64
    }

 -- Ed Note: should we add per-diag code counts here,

    zxAnBfdStdSessPerfCtrlPktIn OBJECT-TYPE
        SYNTAX     Counter32
        MAX-ACCESS read-only
        STATUS     current
        DESCRIPTION
            "The total number of BFD control messages received for this
             BFD session."
        ::= { zxAnBfdStdSessPerfEntry 1 }

    zxAnBfdStdSessPerfCtrlPktOut OBJECT-TYPE
        SYNTAX     Counter32
        MAX-ACCESS read-only
        STATUS     current
        DESCRIPTION
            "The total number of BFD control messages sent for this BFD
             session."
        ::= { zxAnBfdStdSessPerfEntry 2 }

    zxAnBfdStdSessPerfCtrlPktDrop OBJECT-TYPE
        SYNTAX     Counter32
        MAX-ACCESS read-only
        STATUS     current
        DESCRIPTION
            "The total number of BFD control messages received for this
             session yet dropped for being invalid."
        ::= { zxAnBfdStdSessPerfEntry 3 }

    zxAnBfdStdSessPerfCtrlPktDLT OBJECT-TYPE
        SYNTAX     TimeStamp
        MAX-ACCESS read-only
        STATUS     current
        DESCRIPTION
            "The value of sysUpTime on the most recent occasion at
             which received BFD control message for this session was
             dropped. If no such up event exists, this object contains
             a zero value."
        ::= { zxAnBfdStdSessPerfEntry 4 }

    zxAnBfdStdSessPerfEchoPktIn OBJECT-TYPE
        SYNTAX     Counter32
        MAX-ACCESS read-only
        STATUS     current
        DESCRIPTION
            "The total number of BFD echo messages received for this
             BFD session."
        ::= { zxAnBfdStdSessPerfEntry 5 }

    zxAnBfdStdSessPerfEchoPktOut OBJECT-TYPE
        SYNTAX     Counter32
        MAX-ACCESS read-only
        STATUS     current
        DESCRIPTION
            "The total number of BFD echo messages sent for this BFD
             session."
        ::= { zxAnBfdStdSessPerfEntry 6 }

    zxAnBfdStdSessPerfEchoPktDrop OBJECT-TYPE
        SYNTAX     Counter32
        MAX-ACCESS read-only
        STATUS     current
        DESCRIPTION
            "The total number of BFD echo messages received for this
             session yet dropped for being invalid."
        ::= { zxAnBfdStdSessPerfEntry 7 }

    zxAnBfdStdSessPerfEchoPktDLT OBJECT-TYPE
        SYNTAX     TimeStamp
        MAX-ACCESS read-only
        STATUS     current
        DESCRIPTION
            "The value of sysUpTime on the most recent occasion at
             which received BFD echo message for this session was
             dropped. If no such up event exists, this object contains
             a zero value."
        ::= { zxAnBfdStdSessPerfEntry 8 }

    zxAnBfdStdSessUpTime OBJECT-TYPE
        SYNTAX     TimeStamp
        MAX-ACCESS read-only
        STATUS     current
        DESCRIPTION
            "The value of sysUpTime on the most recent occasion at which
             the session came up. If no such up event exists this object
             contains a zero value."
        ::= { zxAnBfdStdSessPerfEntry 9 }

    zxAnBfdStdSessPerfLastSessDT OBJECT-TYPE
        SYNTAX     TimeStamp
        MAX-ACCESS read-only
        STATUS     current
        DESCRIPTION
            "The value of sysUpTime on the most recent occasion at
             which the last time communication was lost with the
             neighbor. If no such down event exist this object
             contains a zero value."
        ::= { zxAnBfdStdSessPerfEntry 10 }

    zxAnBfdStdSessPerfLastCommLDC OBJECT-TYPE
        SYNTAX     ZxAnBfdStdDiag
        MAX-ACCESS read-only
        STATUS     current
        DESCRIPTION
            "The BFD diag code for the last time communication was lost
             with the neighbor. If no such down event exists this object
             contains a zero value."
        ::= { zxAnBfdStdSessPerfEntry 11 }

    zxAnBfdStdSessPerfSessUpCount OBJECT-TYPE
        SYNTAX     Counter32
        MAX-ACCESS read-only
        STATUS     current
        DESCRIPTION
            "The number of times this session has gone into the Up
             state since the system last rebooted."
        ::= { zxAnBfdStdSessPerfEntry 12 }

    zxAnBfdStdSessPerfDiscTime OBJECT-TYPE
        SYNTAX     TimeStamp
        MAX-ACCESS read-only
        STATUS     current
        DESCRIPTION
          "The value of sysUpTime on the most recent occasion at
           which any one or more of the session counters suffered
           a discontinuity.
           The relevant counters are the specific instances associated
           with this BFD session of any Counter32 object contained in
           the zxAnBfdStdSessPerfTable. If no such discontinuities have
           occurred since the last re-initialization of the local
           management subsystem, then this object contains a zero
           value."
        ::= { zxAnBfdStdSessPerfEntry 13 }

    zxAnBfdStdSessPerfCtrlPktInHC OBJECT-TYPE
        SYNTAX     Counter64
        MAX-ACCESS read-only
        STATUS     current
        DESCRIPTION
            "This value represents the total number of BFD control
             messages received for this BFD session. It MUST be equal
             to the least significant 32 bits of zxAnBfdStdSessPerfCtrlPktIn
             if zxAnBfdStdSessPerfCtrlPktInHC is supported according to
             the rules spelled out in RFC2863."
        ::= { zxAnBfdStdSessPerfEntry 14 }

    zxAnBfdStdSessPerfCtrlPktOutHC OBJECT-TYPE
        SYNTAX     Counter64
        MAX-ACCESS read-only
        STATUS     current
        DESCRIPTION
            "This value represents the total number of
             total number of BFD control messages transmitted for this
             BFD session. It MUST be equal to the
             least significant 32 bits of zxAnBfdStdSessPerfCtrlPktOut
             if zxAnBfdStdSessPerfCtrlPktOutHC is supported according to
             the rules spelled out in RFC2863."
        ::= { zxAnBfdStdSessPerfEntry 15 }

    zxAnBfdStdSessPerfCtrlPktDropHC OBJECT-TYPE
        SYNTAX     Counter64
        MAX-ACCESS read-only
        STATUS     current
        DESCRIPTION
            "This value represents the total number of BFD control
             messages received for this BFD session yet dropped for
             being invalid. It MUST be equal to the least significant
             32 bits of zxAnBfdStdSessPerfCtrlPktDrop if
             zxAnBfdStdSessPerfCtrlPktDropHC is supported according to the
             rules spelled out in RFC2863."
        ::= { zxAnBfdStdSessPerfEntry 16 }

    zxAnBfdStdSessPerfEchoPktInHC OBJECT-TYPE
        SYNTAX     Counter64
        MAX-ACCESS read-only
        STATUS     current
        DESCRIPTION
            "This value represents the total number of BFD echo messages
             received for this BFD session. It MUST be equal to the
             least significant 32 bits of zxAnBfdStdSessPerfEchoPktIn
             if zxAnBfdStdSessPerfEchoPktInHC is supported according to
             the rules spelled out in RFC2863."
        ::= { zxAnBfdStdSessPerfEntry 17 }

    zxAnBfdStdSessPerfEchoPktOutHC OBJECT-TYPE
        SYNTAX     Counter64
        MAX-ACCESS read-only
        STATUS     current
        DESCRIPTION
            "This value represents the total number of
             total number of BFD echo messages transmitted for this
             BFD session. It MUST be equal to the
             least significant 32 bits of zxAnBfdStdSessPerfEchoPktOut
             if zxAnBfdStdSessPerfEchoPktOutHC is supported according to
             the rules spelled out in RFC2863."
        ::= { zxAnBfdStdSessPerfEntry 18 }

    zxAnBfdStdSessPerfEchoPktDropHC OBJECT-TYPE
        SYNTAX     Counter64
        MAX-ACCESS read-only
        STATUS     current
        DESCRIPTION
            "This value represents the total number of BFD echo
             messages received for this BFD session yet dropped
             for being invalid. It MUST be equal to the least
             significant 32 bits of zxAnBfdStdSessPerfEchoPktDrop if
             zxAnBfdStdSessPerfEchoPktDropHC is supported according to
             the rules spelled out in RFC2863."
        ::= { zxAnBfdStdSessPerfEntry 19 }

 -- BFD Session Discriminator Mapping Table

    zxAnBfdStdSessDiscMapTable OBJECT-TYPE
        SYNTAX     SEQUENCE OF ZxAnBfdStdSessDiscMapEntry
        MAX-ACCESS not-accessible
        STATUS     current
        DESCRIPTION
            "The BFD Session Discriminator Mapping Table maps a
             local discriminator value to associated BFD sessions'
             ZxAnBfdStdSessIndexTC used in the zxAnBfdStdSessionTable."
        ::= { zxAnBfdStdObjects 4 }

    zxAnBfdStdSessDiscMapEntry OBJECT-TYPE
        SYNTAX     ZxAnBfdStdSessDiscMapEntry
        MAX-ACCESS not-accessible
        STATUS     current
        DESCRIPTION
            "The BFD Session Discriminator Map Entry describes
             BFD session that is mapped to this ZxAnBfdStdSessIndexTC."
        INDEX { zxAnBfdStdSessDiscIndex }
        ::= { zxAnBfdStdSessDiscMapTable 1 }

    ZxAnBfdStdSessDiscMapEntry ::= SEQUENCE {
        zxAnBfdStdSessDiscIndex               Unsigned32,
        zxAnBfdStdSessDiscMapIndex            ZxAnBfdStdSessIndexTC
    }

    zxAnBfdStdSessDiscIndex OBJECT-TYPE
        SYNTAX     Unsigned32 (1..4294967295)
        MAX-ACCESS not-accessible
        STATUS     current
        DESCRIPTION
            "This object specifies the local discriminator for this BFD
             session, used to uniquely identify it."
        ::= { zxAnBfdStdSessDiscMapEntry 1 }

    zxAnBfdStdSessDiscMapIndex OBJECT-TYPE
        SYNTAX     ZxAnBfdStdSessIndexTC
        MAX-ACCESS read-only
        STATUS     current
        DESCRIPTION
            "This object specifies the zxAnBfdStdIndex referred to by
             the indexes of this row. In essence, a mapping is
             provided between these indexes and the zxAnBfdStdSessTable."
        ::= { zxAnBfdStdSessDiscMapEntry 2 }

 -- BFD Session IP Mapping Table

    zxAnBfdStdSessIpMapTable OBJECT-TYPE
        SYNTAX     SEQUENCE OF ZxAnBfdStdSessIpMapEntry
        MAX-ACCESS not-accessible
        STATUS     current
        DESCRIPTION
            "The BFD Session IP Mapping Table maps given
             zxAnBfdStdSessInterface, zxAnBfdStdSessPeerIpAddrType, and
             zxAnBfdStdSessPeerIpAddr to an associated BFD sessions'
             ZxAnBfdStdSessIndexTC used in the zxAnBfdStdSessionTable.
             This table SHOULD contains those BFD sessions of singleHop(1)
             type."
        ::= { zxAnBfdStdObjects 5 }

    zxAnBfdStdSessIpMapEntry OBJECT-TYPE
        SYNTAX     ZxAnBfdStdSessIpMapEntry
        MAX-ACCESS not-accessible
        STATUS     current
        DESCRIPTION
           "The BFD Session IP Map Entry describes
            BFD session that is mapped to this ZxAnBfdStdSessIndexTC."
        INDEX {
            zxAnBfdStdSessIfIndex,
            zxAnBfdStdSessPeerIpAddressType,
            zxAnBfdStdSessPeerIpAddress
        }
        ::= { zxAnBfdStdSessIpMapTable 1 }

    ZxAnBfdStdSessIpMapEntry ::= SEQUENCE {
        zxAnBfdStdSessIfIndex               InterfaceIndexOrZero,
        zxAnBfdStdSessPeerIpAddressType       InetAddressType,
        zxAnBfdStdSessPeerIpAddress           InetAddress,
        zxAnBfdStdSessIpMapIndex            ZxAnBfdStdSessIndexTC
    }

    zxAnBfdStdSessIfIndex OBJECT-TYPE
        SYNTAX     InterfaceIndexOrZero
        MAX-ACCESS not-accessible
        STATUS     current
        DESCRIPTION
            "This object contains an interface index used to indicate
             the interface which this BFD session is running on. This
             value can be zero if there is no interface associated
             with this BFD session."
        ::= { zxAnBfdStdSessIpMapEntry 1 }

    zxAnBfdStdSessPeerIpAddressType OBJECT-TYPE
        SYNTAX     InetAddressType
        MAX-ACCESS not-accessible
        STATUS     current
        DESCRIPTION
            "This object specifies IP address type of the neighboring IP
             address which is being monitored with this BFD session.

             Only values unknown(0), ipv4(1), ipv6(2), or ipv6z(4)
             have to be supported.

             A value of unknown(0) is allowed only when
             the outgoing interface is of type point-to-point, or
             when the BFD session is not associated with a specific
             interface.

             If any other unsupported values are attempted in a set
             operation, the agent MUST return an inconsistentValue
             error."
      ::= { zxAnBfdStdSessIpMapEntry 2 }

    zxAnBfdStdSessPeerIpAddress OBJECT-TYPE
        SYNTAX     InetAddress
        MAX-ACCESS not-accessible
        STATUS     current
        DESCRIPTION
            "This object specifies the neighboring IP address which is
             being monitored with this BFD session.
             It can also be used to enabled BFD on a specific
             interface. The value is set to zero when BFD session is not
             associated with a specific interface."
        ::= { zxAnBfdStdSessIpMapEntry 3 }

    zxAnBfdStdSessIpMapIndex OBJECT-TYPE
        SYNTAX     ZxAnBfdStdSessIndexTC
        MAX-ACCESS read-only
        STATUS     current
        DESCRIPTION
            "This object specifies the zxAnBfdStdIndex referred to by
             the indexes of this row. In essence, a mapping is
             provided between these indexes and the zxAnBfdStdSessTable."
        ::= { zxAnBfdStdSessIpMapEntry 4 }

 -- Notification Configuration

    zxAnBfdStdSessUp NOTIFICATION-TYPE
        OBJECTS {
            zxAnBfdStdSessDiag, -- low range value
            zxAnBfdStdSessDiag  -- high range value
        }
        STATUS     current
        DESCRIPTION
            "This notification is generated when the
             zxAnBfdStdSessState object for one or more contiguous
             entries in zxAnBfdStdSessTable are about to enter the up(4)
             state from some other state. The included values of
             zxAnBfdStdSessDiag MUST both be set equal to this
             new state (i.e: up(4)).  The two instances of
             zxAnBfdStdSessDiag in this notification indicate the range
             of indexes that are affected.  Note that all the indexes
             of the two ends of the range can be derived from the
             instance identifiers of these two objects.  For the
             cases where a contiguous range of sessions
             have transitioned into the up(4) state at roughly
             the same time, the device SHOULD issue a single
             notification for each range of contiguous indexes in
             an effort to minimize the emission of a large number
             of notifications.  If a notification has to be
             issued for just a single zxAnBfdStdSessEntry, then
             the instance identifier (and values) of the two
             zxAnBfdStdSessDiag objects MUST be the identical."
        ::= { zxAnBfdStdNotifications 1 }

    zxAnBfdStdSessDown NOTIFICATION-TYPE
        OBJECTS {
            zxAnBfdStdSessDiag, -- low range value
            zxAnBfdStdSessDiag  -- high range value
        }
        STATUS     current
        DESCRIPTION
            "This notification is generated when the
             zxAnBfdStdSessState object for one or more contiguous
             entries in zxAnBfdStdSessTable are about to enter the down(2)
             or adminDown(1) states from some other state. The included
             values of zxAnBfdStdSessDiag MUST both be set equal to this new
             state (i.e: down(2) or adminDown(1)).  The two instances
             of zxAnBfdStdSessDiag in this notification indicate the range
             of indexes that are affected.  Note that all the indexes
             of the two ends of the range can be derived from the
             instance identifiers of these two objects.  For
             cases where a contiguous range of sessions
             have transitioned into the down(2) or adminDown(1) states
             at roughly the same time, the device SHOULD issue a single
             notification for each range of contiguous indexes in
             an effort to minimize the emission of a large number
             of notifications.  If a notification has to be
             issued for just a single zxAnBfdStdSessEntry, then
             the instance identifier (and values) of the two
             zxAnBfdStdSessDiag objects MUST be the identical."
        ::= { zxAnBfdStdNotifications 2 }


END
