ZTE-AN-INTERFACE-ETH-PERF-MIB DEFINITIONS ::= BEGIN

    IMPORTS
        MODULE-IDENTITY, OBJECT-TYPE, NOTIFICATION-TYPE,
        Integer32, Gauge32, Counter64                  FROM SNMPv2-SMI
        RowStatus, DisplayString, TruthValue,
        TEXTUAL-CONVENTION, DateAndTime                FROM SNMPv2-TC
        MODULE-COMPLIANCE, OBJECT-GROUP                FROM SNMPv2-CONF
        ifIndex                                        FROM IF-MIB
        zxAnInterfaceMib                               FROM ZTE-AN-INTERFACE-MIB
        HCPerfCurrentCount                             FROM HC-PerfHist-TC-MIB;

    zxAnInterfaceEthPerfMib MODULE-IDENTITY
        LAST-UPDATED    "201109132000Z"
        ORGANIZATION    "ZTE Corporation"
        CONTACT-INFO    " Zhang Weiping   ZTE Corporation
                         Mail: zhang.weiping@zte.com.cn
                         Tel : 021-68896470"
        DESCRIPTION     "The MIB module for the Performance Management of ZTE
                        Access Node interface."

        REVISION        "201109132000Z"
        DESCRIPTION
           "Modify this mib according to standard."

        REVISION        "201109101600Z"
        DESCRIPTION
            "Modify the description."

        REVISION        "201107021400Z"
        DESCRIPTION
            "Initial version of this MIB module."
        ::= {zxAnInterfaceMib 12}

--------------------------------------------------------------------------------
-- Following management objects are defined.
-- 1. zxAnEthIfCurr15MinPerfTable
-- 2. zxAnEthIfCurr1DayPerfTable
-- 3. zxAnEthIfHis15MinPerfTable
-- 4. zxAnEthIfHis1DayPerfTable
-- 5. zxAnEthIfAlmProfileConfTable
-- 6. zxAnEthIfAlmProfileApplyTable
-- 7. zxAnEthIfAlmProfileTable
-- Following conformance information is defined.
-- 31. zxAnEthIfPerfConformance
--------------------------------------------------------------------------------
    zxAnEthIfPerfObjects     OBJECT IDENTIFIER ::= { zxAnInterfaceEthPerfMib 2 }

--------------------------------------------------------------------------------
-- 1. zxAnEthIfCurr15MinPerfTable
--------------------------------------------------------------------------------

    zxAnEthIfCurr15MinPerfTable    OBJECT-TYPE
        SYNTAX      SEQUENCE OF ZxAnEthIfCurr15MinPerfEntry
        MAX-ACCESS  not-accessible
        STATUS      current
        DESCRIPTION
             "The 15 minutes interval performance data table of the ethernet
            interfaces."
        ::= { zxAnEthIfPerfObjects 2 }

    zxAnEthIfCurr15MinPerfEntry    OBJECT-TYPE
        SYNTAX      ZxAnEthIfCurr15MinPerfEntry
        MAX-ACCESS  not-accessible
        STATUS      current
        DESCRIPTION
            "The 15 minutes interval performance data entry of the ethernet
            interfaces."
        INDEX   { ifIndex}
        ::= { zxAnEthIfCurr15MinPerfTable 1 }

    ZxAnEthIfCurr15MinPerfEntry ::= SEQUENCE {
        zxAnEthIfC15MTimeElapsed            Gauge32,
        zxAnEthIfC15MInOctets               Counter64,
        zxAnEthIfC15MInPkts                 Counter64,
        zxAnEthIfC15MInUcastPkts            Counter64,
        zxAnEthIfC15MInMcastPkts            Counter64,
        zxAnEthIfC15MInBcastPkts            Counter64,
        zxAnEthIfC15MInOversizedPkts        Counter64,
        zxAnEthIfC15MInUndersizedPkts       Counter64,
        zxAnEthIfC15MOutOctets              Counter64,
        zxAnEthIfC15MOutPkts                Counter64,
        zxAnEthIfC15MOutUcastPkts           Counter64,
        zxAnEthIfC15MOutMcastPkts           Counter64,
        zxAnEthIfC15MOutBcastPkts           Counter64,
        zxAnEthIfC15MOutPausePkts           Counter64,
        zxAnEthIfC15MOutDiscardPkts         Counter64,
        zxAnEthIfC15MOutCollisions          Counter64,
        zxAnEthIfC15MSingleCollisions       Counter64,
        zxAnEthIfC15MMultipleCollisions     Counter64,
        zxAnEthIfC15MFcsErrors              Counter64,
        zxAnEthIfC15MAlignmentErrors        Counter64,
        zxAnEthIfC15MReset                  INTEGER
        }

    zxAnEthIfC15MTimeElapsed OBJECT-TYPE
        SYNTAX      Gauge32(0..899)
        UNITS       "seconds"
        MAX-ACCESS  read-only
        STATUS      current
        DESCRIPTION
            "Number of seconds that have elapsed since the beginning of the
             current 15 minutes interval."
        ::= { zxAnEthIfCurr15MinPerfEntry 1 }

    zxAnEthIfC15MInOctets    OBJECT-TYPE
        SYNTAX      Counter64
        MAX-ACCESS  read-only
        STATUS      current
        DESCRIPTION
            "The total number of octets received on the interface,
            including framing characters in current 15 minutes interval."
        ::= { zxAnEthIfCurr15MinPerfEntry 2 }

    zxAnEthIfC15MInPkts    OBJECT-TYPE
        SYNTAX      Counter64
        MAX-ACCESS  read-only
        STATUS      current
        DESCRIPTION
            "The total number of packets received on the interface,
            including framing characters in current 15 minutes interval."
        ::= { zxAnEthIfCurr15MinPerfEntry 3 }

    zxAnEthIfC15MInUcastPkts    OBJECT-TYPE
        SYNTAX      Counter64
        MAX-ACCESS  read-only
        STATUS      current
        DESCRIPTION
            "The number of packets, delivered by this sub-layer to a
            higher (sub-)layer, which were not addressed to a multicast
            or broadcast address at this sub-layer in current 15 minutes
            interval."
        ::= { zxAnEthIfCurr15MinPerfEntry 4 }

    zxAnEthIfC15MInMcastPkts    OBJECT-TYPE
        SYNTAX      Counter64
        MAX-ACCESS  read-only
        STATUS      current
        DESCRIPTION
            "The number of packets, delivered by this sub-layer to a
            higher (sub-)layer, which were addressed to a multicast
            address at this sub-layer in current 15 minutes interval.
            For a MAC layer protocol, this includes both Group and
            Functional addresses."
        ::= { zxAnEthIfCurr15MinPerfEntry 5 }

    zxAnEthIfC15MInBcastPkts    OBJECT-TYPE
        SYNTAX      Counter64
        MAX-ACCESS  read-only
        STATUS      current
        DESCRIPTION
            "The number of packets, delivered by this sub-layer to a
            higher (sub-)layer, which were addressed to a broadcast
            address at this sub-layer in current 15 minutes interval."
        ::= { zxAnEthIfCurr15MinPerfEntry 6 }

    zxAnEthIfC15MInOversizedPkts    OBJECT-TYPE
        SYNTAX      Counter64
        MAX-ACCESS  read-only
        STATUS      current
        DESCRIPTION
            "The number of packets,whick above the configured MTU-size,
             e.g.mtu = 2000 (frames >2000 are discarded) in current 15
             minutes interval."
        ::= { zxAnEthIfCurr15MinPerfEntry 7 }

    zxAnEthIfC15MInUndersizedPkts    OBJECT-TYPE
        SYNTAX      Counter64
        MAX-ACCESS  read-only
        STATUS      current
        DESCRIPTION
            "The number of packets,whick above the min port size,
             the value is 64 in current 15 minutes interval."
        ::= { zxAnEthIfCurr15MinPerfEntry 8 }

    zxAnEthIfC15MOutOctets    OBJECT-TYPE
        SYNTAX      Counter64
        MAX-ACCESS  read-only
        STATUS      current
        DESCRIPTION
            "The total number of octets transmitted out of the interface,
            including framing characters in current 15 minutes interval."
        ::= { zxAnEthIfCurr15MinPerfEntry 9 }

    zxAnEthIfC15MOutPkts    OBJECT-TYPE
        SYNTAX      Counter64
        MAX-ACCESS  read-only
        STATUS      current
        DESCRIPTION
            "The total number of packets transmitted out of the interface,
            including framing characters in current 15 minutes interval."
        ::= { zxAnEthIfCurr15MinPerfEntry 10 }

    zxAnEthIfC15MOutUcastPkts    OBJECT-TYPE
        SYNTAX      Counter64
        MAX-ACCESS  read-only
        STATUS      current
        DESCRIPTION
            "The total number of packets that higher-level protocols
            requested be transmitted, and which were not addressed to a
            multicast or broadcast address at this sub-layer, including
            those that were discarded or not sent in current 15 minutes
            interval."
        ::= { zxAnEthIfCurr15MinPerfEntry 11 }

    zxAnEthIfC15MOutMcastPkts    OBJECT-TYPE
        SYNTAX      Counter64
        MAX-ACCESS  read-only
        STATUS      current
        DESCRIPTION
            "The total number of packets that higher-level protocols
            requested be transmitted, and which were addressed to a
            multicast address at this sub-layer, including those that
            were discarded or not sent in current 15 minutes interval.
            For a MAC layer protocol, this includes both Group and
            Functional addresses."
        ::= { zxAnEthIfCurr15MinPerfEntry 12 }

    zxAnEthIfC15MOutBcastPkts    OBJECT-TYPE
        SYNTAX      Counter64
        MAX-ACCESS  read-only
        STATUS      current
        DESCRIPTION
            "The total number of packets that higher-level protocols
            requested be transmitted, and which were addressed to a
            broadcast address at this sub-layer, including those that
            were discarded or not sent in current 15 minutes interval."
        ::= { zxAnEthIfCurr15MinPerfEntry 13 }

    zxAnEthIfC15MOutPausePkts    OBJECT-TYPE
        SYNTAX      Counter64
        MAX-ACCESS  read-only
        STATUS      current
        DESCRIPTION
            "A count of MAC Control frames transmitted on
             this interface with an opcode indicating the
             PAUSE operation in current 15 minutes interval."
        ::= { zxAnEthIfCurr15MinPerfEntry 14 }

    zxAnEthIfC15MOutDiscardPkts    OBJECT-TYPE
        SYNTAX      Counter64
        MAX-ACCESS  read-only
        STATUS      current
        DESCRIPTION
            "The number of outbound packets which were chosen to be
            discarded even though no errors had been detected to prevent
            their being transmitted in current 15 minutes interval."
        ::= { zxAnEthIfCurr15MinPerfEntry 15 }

    zxAnEthIfC15MOutCollisions    OBJECT-TYPE
        SYNTAX      Counter64
        MAX-ACCESS  read-only
        STATUS      current
        DESCRIPTION
            "A count of frames that are involved in out collision and
             are subsequently transmitted successfully in current 15
             minutes interval."
        ::= { zxAnEthIfCurr15MinPerfEntry 16 }

    zxAnEthIfC15MSingleCollisions    OBJECT-TYPE
        SYNTAX      Counter64
        MAX-ACCESS  read-only
        STATUS      current
        DESCRIPTION
            "A count of frames that are involved in a single
             collision, and are subsequently transmitted
             successfully in current 15 minutes interval."
        ::= { zxAnEthIfCurr15MinPerfEntry 17 }

    zxAnEthIfC15MMultipleCollisions    OBJECT-TYPE
        SYNTAX      Counter64
        MAX-ACCESS  read-only
        STATUS      current
        DESCRIPTION
            "A count of frames that are involved in more
             than one collision and are subsequently
             transmitted successfully in current 15 minutes
             interval."
        ::= { zxAnEthIfCurr15MinPerfEntry 18 }

    zxAnEthIfC15MFcsErrors    OBJECT-TYPE
        SYNTAX      Counter64
        MAX-ACCESS  read-only
        STATUS      current
        DESCRIPTION
            "A count of frames received on a particular
             interface that are an integral number of octets
             in length but do not pass the FCS check.  This
             count does not include frames received with
             frame-too-long or frame-too-short error in current
             15 minutes interval."
        ::= { zxAnEthIfCurr15MinPerfEntry 19 }

    zxAnEthIfC15MAlignmentErrors    OBJECT-TYPE
        SYNTAX      Counter64
        MAX-ACCESS  read-only
        STATUS      current
        DESCRIPTION
            "A count of frames received on a particular
             interface that are not an integral number of
             octets in length and do not pass the FCS check
             in current 15 minutes interval."
        ::= { zxAnEthIfCurr15MinPerfEntry 20 }

    zxAnEthIfC15MReset OBJECT-TYPE
        SYNTAX      INTEGER
            {
                perfReset(1)
            }
        MAX-ACCESS  read-write
        STATUS      current
        DESCRIPTION
            "Clear all the current 15 minutes performance variables.
             When get this variable, always return 1."
        ::= { zxAnEthIfCurr15MinPerfEntry 100 }

--------------------------------------------------------------------------------
-- 2. zxAnEthIfCurr1DayPerfTable
--------------------------------------------------------------------------------

    zxAnEthIfCurr1DayPerfTable    OBJECT-TYPE
        SYNTAX      SEQUENCE OF ZxAnEthIfCurr1DayPerfEntry
        MAX-ACCESS  not-accessible
        STATUS      current
        DESCRIPTION
             "The 1 day interval performance data table of the ethernet
            interfaces."
        ::= { zxAnEthIfPerfObjects 3 }

    zxAnEthIfCurr1DayPerfEntry    OBJECT-TYPE
        SYNTAX      ZxAnEthIfCurr1DayPerfEntry
        MAX-ACCESS  not-accessible
        STATUS      current
        DESCRIPTION
            "The 1 day interval performance data entry of the ethernet
            interfaces."
        INDEX   { ifIndex}
        ::= { zxAnEthIfCurr1DayPerfTable 1 }

    ZxAnEthIfCurr1DayPerfEntry ::= SEQUENCE {
        zxAnEthIfC1DTimeElapsed            Gauge32,
        zxAnEthIfC1DInOctets               Counter64,
        zxAnEthIfC1DInPkts                 Counter64,
        zxAnEthIfC1DInUcastPkts            Counter64,
        zxAnEthIfC1DInMcastPkts            Counter64,
        zxAnEthIfC1DInBcastPkts            Counter64,
        zxAnEthIfC1DInOversizedPkts        Counter64,
        zxAnEthIfC1DInUndersizedPkts       Counter64,
        zxAnEthIfC1DOutOctets              Counter64,
        zxAnEthIfC1DOutPkts                Counter64,
        zxAnEthIfC1DOutUcastPkts           Counter64,
        zxAnEthIfC1DOutMcastPkts           Counter64,
        zxAnEthIfC1DOutBcastPkts           Counter64,
        zxAnEthIfC1DOutPausePkts           Counter64,
        zxAnEthIfC1DOutDiscardPkts         Counter64,
        zxAnEthIfC1DOutCollisions          Counter64,
        zxAnEthIfC1DSingleCollisions       Counter64,
        zxAnEthIfC1DMultipleCollisions     Counter64,
        zxAnEthIfC1DFcsErrors              Counter64,
        zxAnEthIfC1DAlignmentErrors        Counter64,
        zxAnEthIfC1DReset                  INTEGER
        }

    zxAnEthIfC1DTimeElapsed OBJECT-TYPE
        SYNTAX      Gauge32(0..86399)
        UNITS       "seconds"
        MAX-ACCESS  read-only
        STATUS      current
        DESCRIPTION
            "Number of seconds that have elapsed since the beginning of the
             current 1 day interval."
        ::= { zxAnEthIfCurr1DayPerfEntry 1 }

    zxAnEthIfC1DInOctets    OBJECT-TYPE
        SYNTAX      Counter64
        MAX-ACCESS  read-only
        STATUS      current
        DESCRIPTION
            "The total number of octets received on the interface,
            including framing characters in current one day interval."
        ::= { zxAnEthIfCurr1DayPerfEntry 2 }

    zxAnEthIfC1DInPkts    OBJECT-TYPE
        SYNTAX      Counter64
        MAX-ACCESS  read-only
        STATUS      current
        DESCRIPTION
            "The total number of packets received on the interface,
            including framing characters in current one day interval."
        ::= { zxAnEthIfCurr1DayPerfEntry 3 }

    zxAnEthIfC1DInUcastPkts    OBJECT-TYPE
        SYNTAX      Counter64
        MAX-ACCESS  read-only
        STATUS      current
        DESCRIPTION
            "The number of packets, delivered by this sub-layer to a
            higher (sub-)layer, which were not addressed to a multicast
            or broadcast address at this sub-layer in current one day
            interval."
        ::= { zxAnEthIfCurr1DayPerfEntry 4 }

    zxAnEthIfC1DInMcastPkts    OBJECT-TYPE
        SYNTAX      Counter64
        MAX-ACCESS  read-only
        STATUS      current
        DESCRIPTION
            "The number of packets, delivered by this sub-layer to a
            higher (sub-)layer, which were addressed to a multicast
            address at this sub-layer in current one day interval.
            For a MAC layer protocol, this includes both Group and
            Functional addresses."
        ::= { zxAnEthIfCurr1DayPerfEntry 5 }

    zxAnEthIfC1DInBcastPkts    OBJECT-TYPE
        SYNTAX      Counter64
        MAX-ACCESS  read-only
        STATUS      current
        DESCRIPTION
            "The number of packets, delivered by this sub-layer to a
            higher (sub-)layer, which were addressed to a broadcast
            address at this sub-layer in current one day interval."
        ::= { zxAnEthIfCurr1DayPerfEntry 6 }

    zxAnEthIfC1DInOversizedPkts    OBJECT-TYPE
        SYNTAX      Counter64
        MAX-ACCESS  read-only
        STATUS      current
        DESCRIPTION
            "The number of packets,whick above the configured MTU-size,
             e.g.mtu = 2000 (frames >2000 are discarded) in current one
              day interval."
        ::= { zxAnEthIfCurr1DayPerfEntry 7 }

    zxAnEthIfC1DInUndersizedPkts    OBJECT-TYPE
        SYNTAX      Counter64
        MAX-ACCESS  read-only
        STATUS      current
        DESCRIPTION
            "The number of packets,whick above the min port size,
             the value is 64 in current one day interval."
        ::= { zxAnEthIfCurr1DayPerfEntry 8 }

    zxAnEthIfC1DOutOctets    OBJECT-TYPE
        SYNTAX      Counter64
        MAX-ACCESS  read-only
        STATUS      current
        DESCRIPTION
            "The total number of octets transmitted out of the interface,
            including framing characters in current one day interval."
        ::= { zxAnEthIfCurr1DayPerfEntry 9 }

    zxAnEthIfC1DOutPkts    OBJECT-TYPE
        SYNTAX      Counter64
        MAX-ACCESS  read-only
        STATUS      current
        DESCRIPTION
            "The total number of packets transmitted out of the interface,
            including framing characters in current one day interval."
        ::= { zxAnEthIfCurr1DayPerfEntry 10 }

    zxAnEthIfC1DOutUcastPkts    OBJECT-TYPE
        SYNTAX      Counter64
        MAX-ACCESS  read-only
        STATUS      current
        DESCRIPTION
            "The total number of packets that higher-level protocols
            requested be transmitted, and which were not addressed to a
            multicast or broadcast address at this sub-layer, including
            those that were discarded or not sent in current one day
            interval."
        ::= { zxAnEthIfCurr1DayPerfEntry 11 }

    zxAnEthIfC1DOutMcastPkts    OBJECT-TYPE
        SYNTAX      Counter64
        MAX-ACCESS  read-only
        STATUS      current
        DESCRIPTION
            "The total number of packets that higher-level protocols
            requested be transmitted, and which were addressed to a
            multicast address at this sub-layer, including those that
            were discarded or not sent in current one day interval.
            For a MAC layer protocol, this includes both Group and
            Functional addresses."
        ::= { zxAnEthIfCurr1DayPerfEntry 12 }

    zxAnEthIfC1DOutBcastPkts    OBJECT-TYPE
        SYNTAX      Counter64
        MAX-ACCESS  read-only
        STATUS      current
        DESCRIPTION
            "The total number of packets that higher-level protocols
            requested be transmitted, and which were addressed to a
            broadcast address at this sub-layer, including those that
            were discarded or not sent in current one day interval."
        ::= { zxAnEthIfCurr1DayPerfEntry 13 }

    zxAnEthIfC1DOutPausePkts    OBJECT-TYPE
        SYNTAX      Counter64
        MAX-ACCESS  read-only
        STATUS      current
        DESCRIPTION
            "A count of MAC Control frames transmitted on
             this interface with an opcode indicating the
             PAUSE operation in current one day interval."
        ::= { zxAnEthIfCurr1DayPerfEntry 14 }

    zxAnEthIfC1DOutDiscardPkts    OBJECT-TYPE
        SYNTAX      Counter64
        MAX-ACCESS  read-only
        STATUS      current
        DESCRIPTION
            "The number of outbound packets which were chosen to be
            discarded even though no errors had been detected to prevent
            their being transmitted in current one day interval."
        ::= { zxAnEthIfCurr1DayPerfEntry 15 }

    zxAnEthIfC1DOutCollisions    OBJECT-TYPE
        SYNTAX      Counter64
        MAX-ACCESS  read-only
        STATUS      current
        DESCRIPTION
            "A count of frames that are involved in out collision and
             are subsequently transmitted successfully in current one
             day interval."
        ::= { zxAnEthIfCurr1DayPerfEntry 16 }

    zxAnEthIfC1DSingleCollisions    OBJECT-TYPE
        SYNTAX      Counter64
        MAX-ACCESS  read-only
        STATUS      current
        DESCRIPTION
            "A count of frames that are involved in a single
             collision, and are subsequently transmitted
             successfully in current one day interval."
        ::= { zxAnEthIfCurr1DayPerfEntry 17 }

    zxAnEthIfC1DMultipleCollisions    OBJECT-TYPE
        SYNTAX      Counter64
        MAX-ACCESS  read-only
        STATUS      current
        DESCRIPTION
            "A count of frames that are involved in more
             than one collision and are subsequently
             transmitted successfully in current one day
             interval."
        ::= { zxAnEthIfCurr1DayPerfEntry 18 }

    zxAnEthIfC1DFcsErrors    OBJECT-TYPE
        SYNTAX      Counter64
        MAX-ACCESS  read-only
        STATUS      current
        DESCRIPTION
            "A count of frames received on a particular
             interface that are an integral number of octets
             in length but do not pass the FCS check.  This
             count does not include frames received with
             frame-too-long or frame-too-short error in current
             one day interval."
        ::= { zxAnEthIfCurr1DayPerfEntry 19 }

    zxAnEthIfC1DAlignmentErrors    OBJECT-TYPE
        SYNTAX      Counter64
        MAX-ACCESS  read-only
        STATUS      current
        DESCRIPTION
            "A count of frames received on a particular
             interface that are not an integral number of
             octets in length and do not pass the FCS check
             in current one day interval."
        ::= { zxAnEthIfCurr1DayPerfEntry 20 }

    zxAnEthIfC1DReset OBJECT-TYPE
        SYNTAX      INTEGER
            {
                perfReset(1)
            }
        MAX-ACCESS  read-write
        STATUS      current
        DESCRIPTION
            "Clear all the current 1 day performance variables.
             When get this variable, always return 1."
        ::= { zxAnEthIfCurr1DayPerfEntry 100 }

--------------------------------------------------------------------------------
-- 3. zxAnEthIfHis15MinPerfTable
--------------------------------------------------------------------------------

    zxAnEthIfHis15MinPerfTable    OBJECT-TYPE
        SYNTAX      SEQUENCE OF ZxAnEthIfHis15MinPerfEntry
        MAX-ACCESS  not-accessible
        STATUS      current
        DESCRIPTION
             "The 15 minutes interval history performance data table of the
            ethernet interfaces."
        ::= { zxAnEthIfPerfObjects 4 }

    zxAnEthIfHis15MinPerfEntry    OBJECT-TYPE
        SYNTAX      ZxAnEthIfHis15MinPerfEntry
        MAX-ACCESS  not-accessible
        STATUS      current
        DESCRIPTION
            "The 15 minutes interval performance data entry of the ethernet
            interfaces."
        INDEX   { ifIndex, zxAnEthIfH15MIntervalNo }
        ::= { zxAnEthIfHis15MinPerfTable 1 }

    ZxAnEthIfHis15MinPerfEntry ::= SEQUENCE {
        zxAnEthIfH15MIntervalNo             Integer32,
        zxAnEthIfH15MIntervalValidData      TruthValue,
        zxAnEthIfH15MDateTime               DateAndTime,
        zxAnEthIfH15MInOctets               Counter64,
        zxAnEthIfH15MInPkts                 Counter64,
        zxAnEthIfH15MInUcastPkts            Counter64,
        zxAnEthIfH15MInMcastPkts            Counter64,
        zxAnEthIfH15MInBcastPkts            Counter64,
        zxAnEthIfH15MInOversizedPkts        Counter64,
        zxAnEthIfH15MInUndersizedPkts       Counter64,
        zxAnEthIfH15MOutOctets              Counter64,
        zxAnEthIfH15MOutPkts                Counter64,
        zxAnEthIfH15MOutUcastPkts           Counter64,
        zxAnEthIfH15MOutMcastPkts           Counter64,
        zxAnEthIfH15MOutBcastPkts           Counter64,
        zxAnEthIfH15MOutPausePkts           Counter64,
        zxAnEthIfH15MOutDiscardPkts         Counter64,
        zxAnEthIfH15MOutCollisions          Counter64,
        zxAnEthIfH15MSingleCollisions       Counter64,
        zxAnEthIfH15MMultipleCollisions     Counter64,
        zxAnEthIfH15MFcsErrors              Counter64,
        zxAnEthIfH15MAlignmentErrors        Counter64
        }

    zxAnEthIfH15MIntervalNo    OBJECT-TYPE
        SYNTAX      Integer32(1..96)
        MAX-ACCESS  not-accessible
        STATUS      current
        DESCRIPTION
             "Performance data interval number 1 is the the most recent
              previous interval; interval 96 is 24 hours ago.
              Intervals 2..96 are optional."
        ::= { zxAnEthIfHis15MinPerfEntry 1 }

    zxAnEthIfH15MIntervalValidData    OBJECT-TYPE
        SYNTAX      TruthValue
        MAX-ACCESS  read-only
        STATUS      current
        DESCRIPTION
             "Performance data valid flag.
              true(1) means valid.
              false(2) means invalidm and the performace data is useless."
        ::= { zxAnEthIfHis15MinPerfEntry 2 }

    zxAnEthIfH15MDateTime    OBJECT-TYPE
        SYNTAX      DateAndTime
        MAX-ACCESS  read-only
        STATUS      current
        DESCRIPTION
             "The 15 minutes interval performance data generation time."
        ::= { zxAnEthIfHis15MinPerfEntry 3 }

    zxAnEthIfH15MInOctets    OBJECT-TYPE
        SYNTAX      Counter64
        MAX-ACCESS  read-only
        STATUS      current
        DESCRIPTION
            "The total number of octets received on the interface,
            including framing characters in historical 15 minutes interval."
        ::= { zxAnEthIfHis15MinPerfEntry 4 }

    zxAnEthIfH15MInPkts    OBJECT-TYPE
        SYNTAX      Counter64
        MAX-ACCESS  read-only
        STATUS      current
        DESCRIPTION
            "The total number of packets received on the interface,
            including framing characters in historical 15 minutes interval."
        ::= { zxAnEthIfHis15MinPerfEntry 5 }

    zxAnEthIfH15MInUcastPkts    OBJECT-TYPE
        SYNTAX      Counter64
        MAX-ACCESS  read-only
        STATUS      current
        DESCRIPTION
            "The number of packets, delivered by this sub-layer to a
            higher (sub-)layer, which were not addressed to a multicast
            or broadcast address at this sub-layer in historical 15 minutes
            interval."
        ::= { zxAnEthIfHis15MinPerfEntry 6 }

    zxAnEthIfH15MInMcastPkts    OBJECT-TYPE
        SYNTAX      Counter64
        MAX-ACCESS  read-only
        STATUS      current
        DESCRIPTION
            "The number of packets, delivered by this sub-layer to a
            higher (sub-)layer, which were addressed to a multicast
            address at this sub-layer in historical 15 minutes interval.
            For a MAC layer protocol, this includes both Group and
            Functional addresses."
        ::= { zxAnEthIfHis15MinPerfEntry 7 }

    zxAnEthIfH15MInBcastPkts    OBJECT-TYPE
        SYNTAX      Counter64
        MAX-ACCESS  read-only
        STATUS      current
        DESCRIPTION
            "The number of packets, delivered by this sub-layer to a
            higher (sub-)layer, which were addressed to a broadcast
            address at this sub-layer in historical 15 minutes interval."
        ::= { zxAnEthIfHis15MinPerfEntry 8 }

    zxAnEthIfH15MInOversizedPkts    OBJECT-TYPE
        SYNTAX      Counter64
        MAX-ACCESS  read-only
        STATUS      current
        DESCRIPTION
            "The number of packets,whick above the configured MTU-size,
             e.g.mtu = 2000 (frames >2000 are discarded) in historical 15
             minutes interval."
        ::= { zxAnEthIfHis15MinPerfEntry 9 }

    zxAnEthIfH15MInUndersizedPkts    OBJECT-TYPE
        SYNTAX      Counter64
        MAX-ACCESS  read-only
        STATUS      current
        DESCRIPTION
            "The number of packets,whick above the min port size,
             the value is 64 in historical 15 minutes interval."
        ::= { zxAnEthIfHis15MinPerfEntry 10 }

    zxAnEthIfH15MOutOctets    OBJECT-TYPE
        SYNTAX      Counter64
        MAX-ACCESS  read-only
        STATUS      current
        DESCRIPTION
            "The total number of octets transmitted out of the interface,
            including framing characters in historical 15 minutes interval."
        ::= { zxAnEthIfHis15MinPerfEntry 11 }

    zxAnEthIfH15MOutPkts    OBJECT-TYPE
        SYNTAX      Counter64
        MAX-ACCESS  read-only
        STATUS      current
        DESCRIPTION
            "The total number of packets transmitted out of the interface,
            including framing characters in historical 15 minutes interval."
        ::= { zxAnEthIfHis15MinPerfEntry 12 }

    zxAnEthIfH15MOutUcastPkts    OBJECT-TYPE
        SYNTAX      Counter64
        MAX-ACCESS  read-only
        STATUS      current
        DESCRIPTION
            "The total number of packets that higher-level protocols
            requested be transmitted, and which were not addressed to a
            multicast or broadcast address at this sub-layer, including
            those that were discarded or not sent in historical 15 minutes
            interval."
        ::= { zxAnEthIfHis15MinPerfEntry 13 }

    zxAnEthIfH15MOutMcastPkts    OBJECT-TYPE
        SYNTAX      Counter64
        MAX-ACCESS  read-only
        STATUS      current
        DESCRIPTION
            "The total number of packets that higher-level protocols
            requested be transmitted, and which were addressed to a
            multicast address at this sub-layer, including those that
            were discarded or not sent in historical 15 minutes interval.
            For a MAC layer protocol, this includes both Group and
            Functional addresses."
        ::= { zxAnEthIfHis15MinPerfEntry 14 }

    zxAnEthIfH15MOutBcastPkts    OBJECT-TYPE
        SYNTAX      Counter64
        MAX-ACCESS  read-only
        STATUS      current
        DESCRIPTION
            "The total number of packets that higher-level protocols
            requested be transmitted, and which were addressed to a
            broadcast address at this sub-layer, including those that
            were discarded or not sent in historical 15 minutes interval."
        ::= { zxAnEthIfHis15MinPerfEntry 15 }

    zxAnEthIfH15MOutPausePkts    OBJECT-TYPE
        SYNTAX      Counter64
        MAX-ACCESS  read-only
        STATUS      current
        DESCRIPTION
            "A count of MAC Control frames transmitted on
             this interface with an opcode indicating the
             PAUSE operation in historical 15 minutes interval."
        ::= { zxAnEthIfHis15MinPerfEntry 16 }

    zxAnEthIfH15MOutDiscardPkts    OBJECT-TYPE
        SYNTAX      Counter64
        MAX-ACCESS  read-only
        STATUS      current
        DESCRIPTION
            "The number of outbound packets which were chosen to be
            discarded even though no errors had been detected to prevent
            their being transmitted in historical 15 minutes interval."
        ::= { zxAnEthIfHis15MinPerfEntry 17 }

    zxAnEthIfH15MOutCollisions    OBJECT-TYPE
        SYNTAX      Counter64
        MAX-ACCESS  read-only
        STATUS      current
        DESCRIPTION
            "A count of frames that are involved in out collision and
             are subsequently transmitted successfully in historical 15
             minutes interval."
        ::= { zxAnEthIfHis15MinPerfEntry 18 }

    zxAnEthIfH15MSingleCollisions    OBJECT-TYPE
        SYNTAX      Counter64
        MAX-ACCESS  read-only
        STATUS      current
        DESCRIPTION
            "A count of frames that are involved in a single
             collision, and are subsequently transmitted
             successfully in historical 15 minutes interval."
        ::= { zxAnEthIfHis15MinPerfEntry 19 }

    zxAnEthIfH15MMultipleCollisions    OBJECT-TYPE
        SYNTAX      Counter64
        MAX-ACCESS  read-only
        STATUS      current
        DESCRIPTION
            "A count of frames that are involved in more
             than one collision and are subsequently
             transmitted successfully in historical 15 minutes
             interval."
        ::= { zxAnEthIfHis15MinPerfEntry 20 }

    zxAnEthIfH15MFcsErrors    OBJECT-TYPE
        SYNTAX      Counter64
        MAX-ACCESS  read-only
        STATUS      current
        DESCRIPTION
            "A count of frames received on a particular
             interface that are an integral number of octets
             in length but do not pass the FCS check.  This
             count does not include frames received with
             frame-too-long or frame-too-short error in historical
             15 minutes interval."
        ::= { zxAnEthIfHis15MinPerfEntry 21 }

    zxAnEthIfH15MAlignmentErrors    OBJECT-TYPE
        SYNTAX      Counter64
        MAX-ACCESS  read-only
        STATUS      current
        DESCRIPTION
            "A count of frames received on a particular
             interface that are not an integral number of
             octets in length and do not pass the FCS check
             in historical 15 minutes interval."
        ::= { zxAnEthIfHis15MinPerfEntry 22 }

--------------------------------------------------------------------------------
-- 4. zxAnEthIfHis1DayPerfTable
--------------------------------------------------------------------------------

    zxAnEthIfHis1DayPerfTable    OBJECT-TYPE
        SYNTAX      SEQUENCE OF ZxAnEthIfHis1DayPerfEntry
        MAX-ACCESS  not-accessible
        STATUS      current
        DESCRIPTION
             "The 1 day interval history performance data table of the ethernet
            interfaces."
        ::= { zxAnEthIfPerfObjects 5 }

    zxAnEthIfHis1DayPerfEntry    OBJECT-TYPE
        SYNTAX      ZxAnEthIfHis1DayPerfEntry
        MAX-ACCESS  not-accessible
        STATUS      current
        DESCRIPTION
            "The 1 day interval performance data entry of the ethernet
            interfaces."
        INDEX   { ifIndex, zxAnEthIfH1DIntervalNo }
        ::= { zxAnEthIfHis1DayPerfTable 1 }

    ZxAnEthIfHis1DayPerfEntry ::= SEQUENCE {
        zxAnEthIfH1DIntervalNo             Integer32,
        zxAnEthIfH1DIntervalValidData      TruthValue,
        zxAnEthIfH1DDateTime               DateAndTime,
        zxAnEthIfH1DInOctets               Counter64,
        zxAnEthIfH1DInPkts                 Counter64,
        zxAnEthIfH1DInUcastPkts            Counter64,
        zxAnEthIfH1DInMcastPkts            Counter64,
        zxAnEthIfH1DInBcastPkts            Counter64,
        zxAnEthIfH1DInOversizedPkts        Counter64,
        zxAnEthIfH1DInUndersizedPkts       Counter64,
        zxAnEthIfH1DOutOctets              Counter64,
        zxAnEthIfH1DOutPkts                Counter64,
        zxAnEthIfH1DOutUcastPkts           Counter64,
        zxAnEthIfH1DOutMcastPkts           Counter64,
        zxAnEthIfH1DOutBcastPkts           Counter64,
        zxAnEthIfH1DOutPausePkts           Counter64,
        zxAnEthIfH1DOutDiscardPkts         Counter64,
        zxAnEthIfH1DOutCollisions          Counter64,
        zxAnEthIfH1DSingleCollisions       Counter64,
        zxAnEthIfH1DMultipleCollisions     Counter64,
        zxAnEthIfH1DFcsErrors              Counter64,
        zxAnEthIfH1DAlignmentErrors        Counter64
        }

    zxAnEthIfH1DIntervalNo  OBJECT-TYPE
        SYNTAX      Integer32(1..7)
        MAX-ACCESS  not-accessible
        STATUS      current
        DESCRIPTION
             "Performance data interval number 1 is the the most recent
              previous interval; interval 7 is 1 week ago.
              Intervals 2..7 are optional."
        ::= { zxAnEthIfHis1DayPerfEntry 1 }

    zxAnEthIfH1DIntervalValidData    OBJECT-TYPE
        SYNTAX      TruthValue
        MAX-ACCESS  read-only
        STATUS      current
        DESCRIPTION
             "Performance data valid flag.
              true(1) means valid.
              false(2) means invalidm and the performace data is useless."
        ::= { zxAnEthIfHis1DayPerfEntry 2 }

    zxAnEthIfH1DDateTime    OBJECT-TYPE
        SYNTAX      DateAndTime
        MAX-ACCESS  read-only
        STATUS      current
        DESCRIPTION
             "The 1 day interval performance data generation time."
        ::= { zxAnEthIfHis1DayPerfEntry 3 }

    zxAnEthIfH1DInOctets    OBJECT-TYPE
        SYNTAX      Counter64
        MAX-ACCESS  read-only
        STATUS      current
        DESCRIPTION
            "The total number of octets received on the interface,
            including framing characters in historical one day interval."
        ::= { zxAnEthIfHis1DayPerfEntry 4 }

    zxAnEthIfH1DInPkts    OBJECT-TYPE
        SYNTAX      Counter64
        MAX-ACCESS  read-only
        STATUS      current
        DESCRIPTION
            "The total number of packets received on the interface,
            including framing characters in historical one day interval."
        ::= { zxAnEthIfHis1DayPerfEntry 5 }

    zxAnEthIfH1DInUcastPkts    OBJECT-TYPE
        SYNTAX      Counter64
        MAX-ACCESS  read-only
        STATUS      current
        DESCRIPTION
            "The number of packets, delivered by this sub-layer to a
            higher (sub-)layer, which were not addressed to a multicast
            or broadcast address at this sub-layer in historical one day
            interval."
        ::= { zxAnEthIfHis1DayPerfEntry 6 }

    zxAnEthIfH1DInMcastPkts    OBJECT-TYPE
        SYNTAX      Counter64
        MAX-ACCESS  read-only
        STATUS      current
        DESCRIPTION
            "The number of packets, delivered by this sub-layer to a
            higher (sub-)layer, which were addressed to a multicast
            address at this sub-layer in historical one day interval.
            For a MAC layer protocol, this includes both Group and
            Functional addresses."
        ::= { zxAnEthIfHis1DayPerfEntry 7 }

    zxAnEthIfH1DInBcastPkts    OBJECT-TYPE
        SYNTAX      Counter64
        MAX-ACCESS  read-only
        STATUS      current
        DESCRIPTION
            "The number of packets, delivered by this sub-layer to a
            higher (sub-)layer, which were addressed to a broadcast
            address at this sub-layer in historical one day interval."
        ::= { zxAnEthIfHis1DayPerfEntry 8 }

    zxAnEthIfH1DInOversizedPkts    OBJECT-TYPE
        SYNTAX      Counter64
        MAX-ACCESS  read-only
        STATUS      current
        DESCRIPTION
            "The number of packets,whick above the configured MTU-size,
             e.g.mtu = 2000 (frames >2000 are discarded) in current one
              day interval."
        ::= { zxAnEthIfHis1DayPerfEntry 9 }

    zxAnEthIfH1DInUndersizedPkts    OBJECT-TYPE
        SYNTAX      Counter64
        MAX-ACCESS  read-only
        STATUS      current
        DESCRIPTION
            "The number of packets,whick above the min port size,
             the value is 64 in historical one day interval."
        ::= { zxAnEthIfHis1DayPerfEntry 10 }

    zxAnEthIfH1DOutOctets    OBJECT-TYPE
        SYNTAX      Counter64
        MAX-ACCESS  read-only
        STATUS      current
        DESCRIPTION
            "The total number of octets transmitted out of the interface,
            including framing characters in historical one day interval."
        ::= { zxAnEthIfHis1DayPerfEntry 11 }

    zxAnEthIfH1DOutPkts    OBJECT-TYPE
        SYNTAX      Counter64
        MAX-ACCESS  read-only
        STATUS      current
        DESCRIPTION
            "The total number of packets transmitted out of the interface,
            including framing characters in historical one day interval."
        ::= { zxAnEthIfHis1DayPerfEntry 12 }

    zxAnEthIfH1DOutUcastPkts    OBJECT-TYPE
        SYNTAX      Counter64
        MAX-ACCESS  read-only
        STATUS      current
        DESCRIPTION
            "The total number of packets that higher-level protocols
            requested be transmitted, and which were not addressed to a
            multicast or broadcast address at this sub-layer, including
            those that were discarded or not sent in historical one day
            interval."
        ::= { zxAnEthIfHis1DayPerfEntry 13 }

    zxAnEthIfH1DOutMcastPkts    OBJECT-TYPE
        SYNTAX      Counter64
        MAX-ACCESS  read-only
        STATUS      current
        DESCRIPTION
            "The total number of packets that higher-level protocols
            requested be transmitted, and which were addressed to a
            multicast address at this sub-layer, including those that
            were discarded or not sent in historical one day interval.
            For a MAC layer protocol, this includes both Group and
            Functional addresses."
        ::= { zxAnEthIfHis1DayPerfEntry 14 }

    zxAnEthIfH1DOutBcastPkts    OBJECT-TYPE
        SYNTAX      Counter64
        MAX-ACCESS  read-only
        STATUS      current
        DESCRIPTION
            "The total number of packets that higher-level protocols
            requested be transmitted, and which were addressed to a
            broadcast address at this sub-layer, including those that
            were discarded or not sent in historical one day interval."
        ::= { zxAnEthIfHis1DayPerfEntry 15 }

    zxAnEthIfH1DOutPausePkts    OBJECT-TYPE
        SYNTAX      Counter64
        MAX-ACCESS  read-only
        STATUS      current
        DESCRIPTION
            "A count of MAC Control frames transmitted on
             this interface with an opcode indicating the
             PAUSE operation in historical one day interval."
        ::= { zxAnEthIfHis1DayPerfEntry 16 }

    zxAnEthIfH1DOutDiscardPkts    OBJECT-TYPE
        SYNTAX      Counter64
        MAX-ACCESS  read-only
        STATUS      current
        DESCRIPTION
            "The number of outbound packets which were chosen to be
            discarded even though no errors had been detected to prevent
            their being transmitted in historical one day interval."
        ::= { zxAnEthIfHis1DayPerfEntry 17 }

    zxAnEthIfH1DOutCollisions    OBJECT-TYPE
        SYNTAX      Counter64
        MAX-ACCESS  read-only
        STATUS      current
        DESCRIPTION
            "A count of frames that are involved in out collision and
             are subsequently transmitted successfully in historical one
             day interval."
        ::= { zxAnEthIfHis1DayPerfEntry 18 }

    zxAnEthIfH1DSingleCollisions    OBJECT-TYPE
        SYNTAX      Counter64
        MAX-ACCESS  read-only
        STATUS      current
        DESCRIPTION
            "A count of frames that are involved in a single
             collision, and are subsequently transmitted
             successfully in historical one day interval."
        ::= { zxAnEthIfHis1DayPerfEntry 19 }

    zxAnEthIfH1DMultipleCollisions    OBJECT-TYPE
        SYNTAX      Counter64
        MAX-ACCESS  read-only
        STATUS      current
        DESCRIPTION
            "A count of frames that are involved in more
             than one collision and are subsequently
             transmitted successfully in historical one day
             interval."
        ::= { zxAnEthIfHis1DayPerfEntry 20 }

    zxAnEthIfH1DFcsErrors    OBJECT-TYPE
        SYNTAX      Counter64
        MAX-ACCESS  read-only
        STATUS      current
        DESCRIPTION
            "A count of frames received on a particular
             interface that are an integral number of octets
             in length but do not pass the FCS check.  This
             count does not include frames received with
             frame-too-long or frame-too-short error in historical
             one day interval."
        ::= { zxAnEthIfHis1DayPerfEntry 21 }

    zxAnEthIfH1DAlignmentErrors    OBJECT-TYPE
        SYNTAX      Counter64
        MAX-ACCESS  read-only
        STATUS      current
        DESCRIPTION
            "A count of frames received on a particular
             interface that are not an integral number of
             octets in length and do not pass the FCS check
             in historical one day interval."
        ::= { zxAnEthIfHis1DayPerfEntry 22 }

--------------------------------------------------------------------------------
-- 5. zxAnEthIfAlmProfileConfTable
--------------------------------------------------------------------------------

    zxAnEthIfAlmProfileConfTable   OBJECT-TYPE
        SYNTAX      SEQUENCE OF ZxAnEthIfAlmProfileConfEntry
        MAX-ACCESS  not-accessible
        STATUS      current
        DESCRIPTION
             "The performance alarm threshold profile table of the ethernet
            interfaces."
        ::= { zxAnEthIfPerfObjects 6 }

    zxAnEthIfAlmProfileConfEntry   OBJECT-TYPE
        SYNTAX      ZxAnEthIfAlmProfileConfEntry
        MAX-ACCESS  not-accessible
        STATUS      current
        DESCRIPTION
            "The performance alarm threshold profile entry of the ethernet
            interfaces.These variables in the profile configuration is optional,
            if not configured, it means the correspongding alarm is not
            reported, but the alarm and clear alarm threshold configuration is
            needed to bind."
        INDEX   { zxAnEthIfAlmProfileName, zxAnEthIfPerfVariable }
        ::= { zxAnEthIfAlmProfileConfTable 1 }

    ZxAnEthIfAlmProfileConfEntry ::= SEQUENCE {
        zxAnEthIfAlmProfileName        DisplayString,
        zxAnEthIfPerfVariable          OBJECT IDENTIFIER,
        zxAnEthIfRiseAlmThresh         HCPerfCurrentCount,
        zxAnEthIfClrRiseAlmThresh      HCPerfCurrentCount,
        zxAnEthIfRiseWarnThresh        HCPerfCurrentCount,
        zxAnEthIfClrRiseWarnThresh     HCPerfCurrentCount,
        zxAnEthIfFallWarnThresh        HCPerfCurrentCount,
        zxAnEthIfClrFallWarnThresh     HCPerfCurrentCount,
        zxAnEthIfFallAlmThresh         HCPerfCurrentCount,
        zxAnEthIfClrFallAlmThresh      HCPerfCurrentCount,
        zxAnEthIfThreshUsed            BITS,
        zxAnEthIfAlmProfileConfRowStatus   RowStatus
        }

    zxAnEthIfAlmProfileName  OBJECT-TYPE
        SYNTAX      DisplayString (SIZE (1..32))
        MAX-ACCESS  not-accessible
        STATUS      current
        DESCRIPTION
            "The profile name."
        ::= { zxAnEthIfAlmProfileConfEntry 1 }

    zxAnEthIfPerfVariable  OBJECT-TYPE
        SYNTAX      OBJECT IDENTIFIER
        MAX-ACCESS  not-accessible
        STATUS      current
        DESCRIPTION
            "The object identifier of performance variables."
        ::= { zxAnEthIfAlmProfileConfEntry 2 }

    zxAnEthIfRiseAlmThresh  OBJECT-TYPE
        SYNTAX      HCPerfCurrentCount
        MAX-ACCESS  read-create
        STATUS      current
        DESCRIPTION
            "The threshold for rising alarm."
        ::= { zxAnEthIfAlmProfileConfEntry 3 }

    zxAnEthIfClrRiseAlmThresh  OBJECT-TYPE
        SYNTAX      HCPerfCurrentCount
        MAX-ACCESS  read-create
        STATUS      current
        DESCRIPTION
            "The threshold for rising alarm restore."
        ::= { zxAnEthIfAlmProfileConfEntry 4 }

    zxAnEthIfRiseWarnThresh  OBJECT-TYPE
        SYNTAX      HCPerfCurrentCount
        MAX-ACCESS  read-create
        STATUS      current
        DESCRIPTION
            "The threshold for rising warning."
        ::= { zxAnEthIfAlmProfileConfEntry 5 }

    zxAnEthIfClrRiseWarnThresh  OBJECT-TYPE
        SYNTAX      HCPerfCurrentCount
        MAX-ACCESS  read-create
        STATUS      current
        DESCRIPTION
            "The threshold for rising warning restore."
        ::= { zxAnEthIfAlmProfileConfEntry 6 }

    zxAnEthIfFallWarnThresh  OBJECT-TYPE
        SYNTAX      HCPerfCurrentCount
        MAX-ACCESS  read-create
        STATUS      current
        DESCRIPTION
            "The threshold for falling warning."
        ::= { zxAnEthIfAlmProfileConfEntry 7 }

    zxAnEthIfClrFallWarnThresh  OBJECT-TYPE
        SYNTAX      HCPerfCurrentCount
        MAX-ACCESS  read-create
        STATUS      current
        DESCRIPTION
            "The threshold for falling warning restore."
        ::= { zxAnEthIfAlmProfileConfEntry 8 }

    zxAnEthIfFallAlmThresh  OBJECT-TYPE
        SYNTAX      HCPerfCurrentCount
        MAX-ACCESS  read-create
        STATUS      current
        DESCRIPTION
            "The threshold for falling alarm."
        ::= { zxAnEthIfAlmProfileConfEntry 9 }

    zxAnEthIfClrFallAlmThresh  OBJECT-TYPE
        SYNTAX      HCPerfCurrentCount
        MAX-ACCESS  read-create
        STATUS      current
        DESCRIPTION
            "The threshold for falling alarm restore."
        ::= { zxAnEthIfAlmProfileConfEntry 10 }

    zxAnEthIfThreshUsed  OBJECT-TYPE
         SYNTAX           BITS
           {
               riseAlmThresh(0),
               riseAlmClrThresh(1),
               riseWarnThresh(2),
               riseWarnClrThresh(3),
               fallWarnThresh(4),
               fallWarnClrThresh(5),
               fallAlmThresh(6),
               fallAlmClrThresh(7)
           }
        MAX-ACCESS  read-create
        STATUS      current
        DESCRIPTION
            "The threshold used flag."
        ::= { zxAnEthIfAlmProfileConfEntry 11 }

    zxAnEthIfAlmProfileConfRowStatus  OBJECT-TYPE
        SYNTAX      RowStatus
        MAX-ACCESS  read-create
        STATUS      current
        DESCRIPTION
            "The status of this conceptual row.

             To create a row in this table, a manager must
             set this object to createAndGo(4).

             To delete a row in this table, a manager must
             set this object to destroy(6). "
        ::= { zxAnEthIfAlmProfileConfEntry 50 }

--------------------------------------------------------------------------------
-- 6. zxAnEthIfAlmProfileApplyTable

--------------------------------------------------------------------------------

    zxAnEthIfAlmProfileApplyTable   OBJECT-TYPE
        SYNTAX      SEQUENCE OF ZxAnEthIfAlmProfileApplyEntry
        MAX-ACCESS  not-accessible
        STATUS      current
        DESCRIPTION
             "The performance alarm threshold profile configuration table of
              the ethernet interfaces."
        ::= { zxAnEthIfPerfObjects 7 }

    zxAnEthIfAlmProfileApplyEntry   OBJECT-TYPE
        SYNTAX      ZxAnEthIfAlmProfileApplyEntry
        MAX-ACCESS  not-accessible
        STATUS      current
        DESCRIPTION
            "The performance alarm threshold profile configuration entry of
             the ethernet interfaces."
        INDEX   { ifIndex }
        ::= { zxAnEthIfAlmProfileApplyTable 1 }

    ZxAnEthIfAlmProfileApplyEntry ::= SEQUENCE {
        zxAnEthIfAlmPrf                DisplayString,
        zxAnEthIfAlmPrfApplyRowStatus      RowStatus
        }

    zxAnEthIfAlmPrf  OBJECT-TYPE
        SYNTAX      DisplayString (SIZE (1..32))
        MAX-ACCESS  read-create
        STATUS      current
        DESCRIPTION
            "The performance alarm threshold profile."
        ::= { zxAnEthIfAlmProfileApplyEntry 1 }

     zxAnEthIfAlmPrfApplyRowStatus  OBJECT-TYPE
        SYNTAX      RowStatus
        MAX-ACCESS  read-create
        STATUS      current
        DESCRIPTION
            "The status of this conceptual row.

             To create a row in this table, a manager must
             set this object to createAndGo(4).

             To delete a row in this table, a manager must
             set this object to destroy(6). "
        ::= { zxAnEthIfAlmProfileApplyEntry 50 }


--------------------------------------------------------------------------------
-- 7. zxAnEthIfAlmProfileTable
--------------------------------------------------------------------------------

    zxAnEthIfAlmProfileTable   OBJECT-TYPE
        SYNTAX      SEQUENCE OF ZxAnEthIfAlmProfileEntry
        MAX-ACCESS  not-accessible
        STATUS      current
        DESCRIPTION
             "The performance alarm threshold profile table of the ethernet
            interfaces.It can be used to delete all of the performance alarm
            threshold profiles which has the same name configured in
            'zxAnEthIfAlmProfileConfTable'."
        ::= { zxAnEthIfPerfObjects 8 }

    zxAnEthIfAlmProfileEntry   OBJECT-TYPE
        SYNTAX      ZxAnEthIfAlmProfileEntry
        MAX-ACCESS  not-accessible
        STATUS      current
        DESCRIPTION
            "The performance alarm threshold profile entry of the ethernet
            interfaces."
        INDEX   { zxAnEthIfAlmProfileName}
        ::= { zxAnEthIfAlmProfileTable 1 }

    ZxAnEthIfAlmProfileEntry ::= SEQUENCE {
        zxAnEthIfAlmProfileRowStatus   RowStatus
        }

    zxAnEthIfAlmProfileRowStatus  OBJECT-TYPE
        SYNTAX      RowStatus
        MAX-ACCESS  read-create
        STATUS      current
        DESCRIPTION
            "The status of this profile.

             To create a profile in this table, a manager must
             set this object to createAndGo(4).

             To delete a profile in this table, a manager must
             set this object to destroy(6). "
        ::= { zxAnEthIfAlmProfileEntry 50 }

--------------------------------------------------------------------------------
-- 31. zxAnEthIfPerfConformance
--------------------------------------------------------------------------------

    zxAnEthIfPerfConformance      OBJECT IDENTIFIER
        ::= { zxAnInterfaceEthPerfMib 4 }

    zxAnEthIfPerfCompliances      OBJECT IDENTIFIER
        ::= { zxAnEthIfPerfConformance 1 }
    zxAnEthIfPerfGroups           OBJECT IDENTIFIER
        ::= { zxAnEthIfPerfConformance 2 }

    zxAnEthIfPerfCompliance MODULE-COMPLIANCE
        STATUS      current
        DESCRIPTION
            "The compliance statement for entities which implement the
             ZTE-AN-INTERFACE-ETH-PERF-MIB."

        MODULE       -- this module
            MANDATORY-GROUPS {
                   zxAnEthIfPerfCurr15MinGroup,
                   zxAnEthIfPerfCurr1DayGroup,
                   zxAnEthIfPerfHis15MinGroup,
                   zxAnEthIfPerfHis1DayGroup,
                   zxAnEthIfPerfAlmProfileGroup,
                   zxAnEthIfAlmProfileApplyGroup,
                   zxAnEthIfAlmProfileGroup
                   }
        ::= { zxAnEthIfPerfCompliances 1 }

-- Units of compliance

    zxAnEthIfPerfCurr15MinGroup OBJECT-GROUP
        OBJECTS {
            zxAnEthIfC15MTimeElapsed,
            zxAnEthIfC15MInOctets,
            zxAnEthIfC15MInPkts,
            zxAnEthIfC15MInUcastPkts,
            zxAnEthIfC15MInMcastPkts,
            zxAnEthIfC15MInBcastPkts,
            zxAnEthIfC15MInOversizedPkts,
            zxAnEthIfC15MInUndersizedPkts,
            zxAnEthIfC15MOutOctets,
            zxAnEthIfC15MOutPkts,
            zxAnEthIfC15MOutUcastPkts,
            zxAnEthIfC15MOutMcastPkts,
            zxAnEthIfC15MOutBcastPkts,
            zxAnEthIfC15MOutPausePkts,
            zxAnEthIfC15MOutCollisions,
            zxAnEthIfC15MOutDiscardPkts,
            zxAnEthIfC15MSingleCollisions,
            zxAnEthIfC15MMultipleCollisions,
            zxAnEthIfC15MFcsErrors,
            zxAnEthIfC15MAlignmentErrors,
            zxAnEthIfC15MReset
        }
        STATUS  current
        DESCRIPTION
            "A collection of objects providing for 15 minutes interval
             performance data of interfaces."
        ::= { zxAnEthIfPerfGroups 1 }

    zxAnEthIfPerfCurr1DayGroup OBJECT-GROUP
        OBJECTS {
            zxAnEthIfC1DTimeElapsed,
            zxAnEthIfC1DInOctets,
            zxAnEthIfC1DInPkts,
            zxAnEthIfC1DInUcastPkts,
            zxAnEthIfC1DInMcastPkts,
            zxAnEthIfC1DInBcastPkts,
            zxAnEthIfC1DInOversizedPkts,
            zxAnEthIfC1DInUndersizedPkts,
            zxAnEthIfC1DOutOctets,
            zxAnEthIfC1DOutPkts,
            zxAnEthIfC1DOutUcastPkts,
            zxAnEthIfC1DOutMcastPkts,
            zxAnEthIfC1DOutBcastPkts,
            zxAnEthIfC1DOutPausePkts,
            zxAnEthIfC1DOutCollisions,
            zxAnEthIfC1DOutDiscardPkts,
            zxAnEthIfC1DSingleCollisions,
            zxAnEthIfC1DMultipleCollisions,
            zxAnEthIfC1DFcsErrors,
            zxAnEthIfC1DAlignmentErrors,
            zxAnEthIfC1DReset
        }
        STATUS  current
        DESCRIPTION
            "A collection of objects providing 1 day interval performance data
             of interfaces."
        ::= { zxAnEthIfPerfGroups 2 }

    zxAnEthIfPerfHis15MinGroup OBJECT-GROUP
        OBJECTS {
            zxAnEthIfH15MIntervalValidData,
            zxAnEthIfH15MDateTime,
            zxAnEthIfH15MInOctets,
            zxAnEthIfH15MInPkts,
            zxAnEthIfH15MInUcastPkts,
            zxAnEthIfH15MInMcastPkts,
            zxAnEthIfH15MInBcastPkts,
            zxAnEthIfH15MInOversizedPkts,
            zxAnEthIfH15MInUndersizedPkts,
            zxAnEthIfH15MOutOctets,
            zxAnEthIfH15MOutPkts,
            zxAnEthIfH15MOutUcastPkts,
            zxAnEthIfH15MOutMcastPkts,
            zxAnEthIfH15MOutBcastPkts,
            zxAnEthIfH15MOutPausePkts,
            zxAnEthIfH15MOutCollisions,
            zxAnEthIfH15MOutDiscardPkts,
            zxAnEthIfH15MSingleCollisions,
            zxAnEthIfH15MMultipleCollisions,
            zxAnEthIfH15MFcsErrors,
            zxAnEthIfH15MAlignmentErrors
        }
        STATUS  current
        DESCRIPTION
            "A collection of objects providing for 15 minutes interval
             performance data of interfaces."
        ::= { zxAnEthIfPerfGroups 3 }

    zxAnEthIfPerfHis1DayGroup OBJECT-GROUP
        OBJECTS {
            zxAnEthIfH1DIntervalValidData,
            zxAnEthIfH1DDateTime,
            zxAnEthIfH1DInOctets,
            zxAnEthIfH1DInPkts,
            zxAnEthIfH1DInUcastPkts,
            zxAnEthIfH1DInMcastPkts,
            zxAnEthIfH1DInBcastPkts,
            zxAnEthIfH1DInOversizedPkts,
            zxAnEthIfH1DInUndersizedPkts,
            zxAnEthIfH1DOutOctets,
            zxAnEthIfH1DOutPkts,
            zxAnEthIfH1DOutUcastPkts,
            zxAnEthIfH1DOutMcastPkts,
            zxAnEthIfH1DOutBcastPkts,
            zxAnEthIfH1DOutPausePkts,
            zxAnEthIfH1DOutCollisions,
            zxAnEthIfH1DOutDiscardPkts,
            zxAnEthIfH1DSingleCollisions,
            zxAnEthIfH1DMultipleCollisions,
            zxAnEthIfH1DFcsErrors,
            zxAnEthIfH1DAlignmentErrors
        }
        STATUS  current
        DESCRIPTION
            "A collection of objects providing 1 day interval performance data
             of interfaces."
        ::= { zxAnEthIfPerfGroups 4 }

    zxAnEthIfPerfAlmProfileGroup OBJECT-GROUP
        OBJECTS {
            zxAnEthIfRiseAlmThresh,
            zxAnEthIfClrRiseAlmThresh,
            zxAnEthIfRiseWarnThresh,
            zxAnEthIfClrRiseWarnThresh,
            zxAnEthIfFallWarnThresh,
            zxAnEthIfClrFallWarnThresh,
            zxAnEthIfFallAlmThresh,
            zxAnEthIfClrFallAlmThresh,
            zxAnEthIfThreshUsed,
            zxAnEthIfAlmProfileConfRowStatus
        }
        STATUS  current
        DESCRIPTION
            "A collection of objects providing for performance alarm threshold
             profile of interfaces."
        ::= { zxAnEthIfPerfGroups 5 }

    zxAnEthIfAlmProfileApplyGroup OBJECT-GROUP
        OBJECTS {
            zxAnEthIfAlmPrf,
            zxAnEthIfAlmPrfApplyRowStatus
        }
        STATUS  current
        DESCRIPTION
            "A collection of objects providing for performance alarm threshold
             profile apply control configuration information."
        ::= { zxAnEthIfPerfGroups 6 }

    zxAnEthIfAlmProfileGroup OBJECT-GROUP
        OBJECTS {
            zxAnEthIfAlmProfileRowStatus
        }
        STATUS  current
        DESCRIPTION
            "A collection of objects providing for performance alarm threshold
             profile  configuration information."
        ::= { zxAnEthIfPerfGroups 7 }

END
