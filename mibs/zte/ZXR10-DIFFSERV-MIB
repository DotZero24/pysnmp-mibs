--  Protocol private MIB Definitions
--  if compiles this mib with mg-soft, there must be mpls-vpn.mib and zxr10.mib files and rfc1213.mib in
--  the same director.


    ZXR10-DIFFSERV-MIB DEFINITIONS ::= BEGIN

    IMPORTS

        MODULE-IDENTITY, OBJECT-TYPE, enterprises         FROM SNMPv2-SMI

        ifIndex                        FROM RFC1213-MIB;

    zte OBJECT IDENTIFIER ::= { enterprises 3902 }
    zxr10 OBJECT IDENTIFIER ::= { zte 3}
    zxr10protocol OBJECT IDENTIFIER ::= { zxr10 101}

    zxr10DiffServ MODULE-IDENTITY
        LAST-UPDATED "0909100951Z"  -- 10 Sep 2009 9:51:00 AM
        ORGANIZATION "ZXR10 ROS DiffServ Group"
        CONTACT-INFO
            "          Nanjing Institute of ZTE Corporation
              Postal:  No.68 Zijinghua Rd. Yuhuatai District,
                       Nanjing,
                       China
              Tel:     +86 25 52871647
              E-mail:  hu.jun11@zte.com.cn"

        DESCRIPTION
            "This MIB Module provides Textual Conventions
             and OBJECT-ID Objects to be used by zxros qos module."
        ::= { zxr10protocol 8 }

    DisplayString ::= OCTET STRING
        --  This data type is used to model textual information taken
        --  from the NVT ASCII character set.  By convention, objects
        --  with this syntax are declared as having
        --
        --       SIZE (0..255)

-- begin for data type definition

    DiffServPacketTos ::= INTEGER
                          {
                              ip-dscp(1),
                              vlan-8021p(2),
                              mpls-exp(3)
                          }

    DiffServClass ::= INTEGER
                      {
                          cs7(0),
                          cs6(1),
                          ef(2),
                          af4(3),
                          af3(4),
                          af2(5),
                          af1(6),
                          be(7)
                      }

    DiffServColor ::= INTEGER
                      {
                          green(0),
                          yellow(1),
                          red(2)
                      }

    DiffServScheuldingMode ::= INTEGER
                               {
                                   pq(1),
                                   wfq(2),
                                   wrr(3),
                                   dwrr(4)
                               }

    DiffServDroppingMode ::= INTEGER
                             {
                                 wred(1),
                                 tail-drop(2)
                             }

    DiffServTunnelingMode ::= INTEGER
                              {
                                  uniform(1),
                                  pipe(2),
                                  short-pipe(3)
                              }

    DiffServPolicingAction ::= INTEGER
                               {
                                   discard(1),
                                   pass(2),
                                   remark-pass(3)
                               }

    DiffServTosTrustType ::= INTEGER
                             {
                                 trust-8021p(1),
                                 trust-dscp(2),
                                 trust-exp(3)
                             }

    DiffServPolicingMode ::= INTEGER
                             {
                                 blind(1),
                                 aware(2)
                             }

    DiffServVPNMode ::= INTEGER
                        {
                            vpls(1),
                            vll(2),
                            vls(3),
                            vlan-vll(4)
                        }

-- end for data type definition

-- The follow part defined some objects which will be used in this qos mib file later

-- DiffServ-Domain MIB Inbound Table

     zxr10DiffServDomainInTable  OBJECT-TYPE
              SYNTAX  SEQUENCE OF Zxr10DiffServDomainInEntry
              MAX-ACCESS  not-accessible
              STATUS  current
              DESCRIPTION
                      ""
               ::= { zxr10DiffServ 1 }

     zxr10DiffServDomainInEntry  OBJECT-TYPE
              SYNTAX  Zxr10DiffServDomainInEntry
              MAX-ACCESS  not-accessible
              STATUS  current
              DESCRIPTION
                      ""
              INDEX  { zxr10DiffServDomainInName,
                       zxr10DiffServDomainInToSType,
                       zxr10DiffServDomainInToSValue }
              ::= { zxr10DiffServDomainInTable 1 }

     Zxr10DiffServDomainInEntry ::=
              SEQUENCE {
                           zxr10DiffServDomainInName
                               DisplayString,
                           zxr10DiffServDomainInToSType
                               DiffServPacketTos,
                           zxr10DiffServDomainInToSValue
                               INTEGER,
                           zxr10DiffServDomainInServClass
                               DiffServClass,
                           zxr10DiffServDomainInColor
                               DiffServColor
                       }

     zxr10DiffServDomainInName  OBJECT-TYPE
              SYNTAX  DisplayString
              MAX-ACCESS  read-only
              STATUS  current
              DESCRIPTION
                      ""
              ::= { zxr10DiffServDomainInEntry 1 }

     zxr10DiffServDomainInToSType  OBJECT-TYPE
              SYNTAX  DiffServPacketTos
              MAX-ACCESS  read-only
              STATUS  current
              DESCRIPTION
                      ""
              ::= { zxr10DiffServDomainInEntry 2 }

     zxr10DiffServDomainInToSValue   OBJECT-TYPE
              SYNTAX   INTEGER
              MAX-ACCESS  read-only
              STATUS  current
              DESCRIPTION
                      ""
              ::= { zxr10DiffServDomainInEntry 3 }

     zxr10DiffServDomainInServClass   OBJECT-TYPE
              SYNTAX  DiffServClass
              MAX-ACCESS  read-only
              STATUS  current
              DESCRIPTION
                  ""
             ::= { zxr10DiffServDomainInEntry 4 }

     zxr10DiffServDomainInColor   OBJECT-TYPE
              SYNTAX  DiffServColor
              MAX-ACCESS  read-only
              STATUS  current
              DESCRIPTION
                  ""
             ::= { zxr10DiffServDomainInEntry 5 }

-- DiffServ-Domain MIB Inbound Table Ends

-- DiffServ-Domain MIB Outbound Table

     zxr10DiffServDomainOutTable  OBJECT-TYPE
              SYNTAX  SEQUENCE OF Zxr10DiffServDomainOutEntry
              MAX-ACCESS  not-accessible
              STATUS  current
              DESCRIPTION
                      ""
               ::= { zxr10DiffServ 2 }

     zxr10DiffServDomainOutEntry  OBJECT-TYPE
              SYNTAX  Zxr10DiffServDomainOutEntry
              MAX-ACCESS  not-accessible
              STATUS  current
              DESCRIPTION
                      ""
              INDEX  { zxr10DiffServDomainOutName,
                       zxr10DiffServDomainOutServClass,
                       zxr10DiffServDomainOutColor,
                       zxr10DiffServDomainOutToSType }
              ::= { zxr10DiffServDomainOutTable 1 }

     Zxr10DiffServDomainOutEntry ::=
              SEQUENCE {
                           zxr10DiffServDomainOutName
                               DisplayString,
                           zxr10DiffServDomainOutServClass
                               DiffServClass,
                           zxr10DiffServDomainOutColor
                               DiffServColor,
                           zxr10DiffServDomainOutToSType
                               DiffServPacketTos,
                           zxr10DiffServDomainOutToSValue
                               INTEGER
                       }

     zxr10DiffServDomainOutName  OBJECT-TYPE
              SYNTAX  DisplayString
              MAX-ACCESS  read-only
              STATUS  current
              DESCRIPTION
                      ""
              ::= { zxr10DiffServDomainOutEntry 1 }

     zxr10DiffServDomainOutServClass   OBJECT-TYPE
              SYNTAX  DiffServClass
              MAX-ACCESS  read-only
              STATUS  current
              DESCRIPTION
                  ""
             ::= { zxr10DiffServDomainOutEntry 2 }

     zxr10DiffServDomainOutColor   OBJECT-TYPE
              SYNTAX  DiffServColor
              MAX-ACCESS  read-only
              STATUS  current
              DESCRIPTION
                  ""
             ::= { zxr10DiffServDomainOutEntry 3 }

     zxr10DiffServDomainOutToSType  OBJECT-TYPE
              SYNTAX  DiffServPacketTos
              MAX-ACCESS  read-only
              STATUS  current
              DESCRIPTION
                      ""
              ::= { zxr10DiffServDomainOutEntry 4 }

     zxr10DiffServDomainOutToSValue   OBJECT-TYPE
              SYNTAX   INTEGER
              MAX-ACCESS  read-only
              STATUS  current
              DESCRIPTION
                      ""
              ::= { zxr10DiffServDomainOutEntry 5 }

-- DiffServ-Domain MIB Outbound Table Ends

-- Flow-Drop-Pattern MIB Table

     zxr10DiffServDropPatternTable  OBJECT-TYPE
              SYNTAX  SEQUENCE OF Zxr10DiffServDropPatternEntry
              MAX-ACCESS  not-accessible
              STATUS  current
              DESCRIPTION
                      ""
               ::= { zxr10DiffServ 3 }

     zxr10DiffServDropPatternEntry  OBJECT-TYPE
              SYNTAX  Zxr10DiffServDropPatternEntry
              MAX-ACCESS  not-accessible
              STATUS  current
              DESCRIPTION
                      ""
              INDEX  { zxr10DiffServDropPatternName,
                       zxr10DiffServDropPatternColor }
              ::= { zxr10DiffServDropPatternTable 1 }

     Zxr10DiffServDropPatternEntry ::=
              SEQUENCE {
                           zxr10DiffServDropPatternName
                               DisplayString,
                           zxr10DiffServDropPatternColor
                               DiffServColor,
                           zxr10DiffServDropPatternMode
                               DiffServDroppingMode,
                           zxr10DiffServDropLowThreshold
                               INTEGER,
                           zxr10DiffServDropHighThreshold
                               INTEGER,
                           zxr10DiffServDropProbability
                               INTEGER
                       }

     zxr10DiffServDropPatternName  OBJECT-TYPE
              SYNTAX  DisplayString
              MAX-ACCESS  read-only
              STATUS  current
              DESCRIPTION
                      ""
              ::= { zxr10DiffServDropPatternEntry 1 }

     zxr10DiffServDropPatternColor   OBJECT-TYPE
              SYNTAX  DiffServColor
              MAX-ACCESS  read-only
              STATUS  current
              DESCRIPTION
                  ""
             ::= { zxr10DiffServDropPatternEntry 2 }

     zxr10DiffServDropPatternMode   OBJECT-TYPE
              SYNTAX  DiffServDroppingMode
              MAX-ACCESS  read-only
              STATUS  current
              DESCRIPTION
                  ""
             ::= { zxr10DiffServDropPatternEntry 3 }

     zxr10DiffServDropLowThreshold   OBJECT-TYPE
              SYNTAX   INTEGER
              MAX-ACCESS  read-only
              STATUS  current
              DESCRIPTION
                      ""
              ::= { zxr10DiffServDropPatternEntry 4 }

     zxr10DiffServDropHighThreshold  OBJECT-TYPE
              SYNTAX  INTEGER
              MAX-ACCESS  read-only
              STATUS  current
              DESCRIPTION
                      ""
              ::= { zxr10DiffServDropPatternEntry 5 }

     zxr10DiffServDropProbability   OBJECT-TYPE
              SYNTAX   INTEGER
              MAX-ACCESS  read-only
              STATUS  current
              DESCRIPTION
                      ""
              ::= { zxr10DiffServDropPatternEntry 6 }

-- Flow-Drop-Pattern MIB Table Ends

-- Flow-Pattern MIB Table

     zxr10DiffServFlowPatternTable  OBJECT-TYPE
              SYNTAX  SEQUENCE OF Zxr10DiffServFlowPatternEntry
              MAX-ACCESS  not-accessible
              STATUS  current
              DESCRIPTION
                      ""
               ::= { zxr10DiffServ 4 }

     zxr10DiffServFlowPatternEntry  OBJECT-TYPE
              SYNTAX  Zxr10DiffServFlowPatternEntry
              MAX-ACCESS  not-accessible
              STATUS  current
              DESCRIPTION
                      ""
              INDEX  { zxr10DiffServFlowPatternName,
                       zxr10DiffServFlowServiceClass }
              ::= { zxr10DiffServFlowPatternTable 1 }

     Zxr10DiffServFlowPatternEntry ::=
              SEQUENCE {
                           zxr10DiffServFlowPatternName
                               DisplayString,
                           zxr10DiffServFlowServiceClass
                               DiffServClass,
                           zxr10DiffServFlowSchedulingMode
                               DiffServScheuldingMode,
                           zxr10DiffServSchedulingWeight
                               INTEGER,
                           zxr10DiffServFlowShapingCir
                               INTEGER,
                           zxr10DiffServFlowShapingCbs
                               INTEGER,
                           zxr10DiffServFlowShapingPir
                               INTEGER,
                           zxr10DiffServFlowShapingPbs
                               INTEGER,
                           zxr10DiffServFlowDropPatternName
                               DisplayString
                       }

     zxr10DiffServFlowPatternName  OBJECT-TYPE
              SYNTAX  DisplayString
              MAX-ACCESS  read-only
              STATUS  current
              DESCRIPTION
                      ""
              ::= { zxr10DiffServFlowPatternEntry 1 }

     zxr10DiffServFlowServiceClass   OBJECT-TYPE
              SYNTAX  DiffServClass
              MAX-ACCESS  read-only
              STATUS  current
              DESCRIPTION
                  ""
             ::= { zxr10DiffServFlowPatternEntry 2 }

     zxr10DiffServFlowSchedulingMode   OBJECT-TYPE
              SYNTAX  DiffServScheuldingMode
              MAX-ACCESS  read-only
              STATUS  current
              DESCRIPTION
                  ""
             ::= { zxr10DiffServFlowPatternEntry 3 }

     zxr10DiffServSchedulingWeight  OBJECT-TYPE
              SYNTAX  INTEGER
              MAX-ACCESS  read-only
              STATUS  current
              DESCRIPTION
                      ""
              ::= { zxr10DiffServFlowPatternEntry 4 }

     zxr10DiffServFlowShapingCir   OBJECT-TYPE
              SYNTAX   INTEGER
              MAX-ACCESS  read-only
              STATUS  current
              DESCRIPTION
                      ""
              ::= { zxr10DiffServFlowPatternEntry 5 }

     zxr10DiffServFlowShapingCbs   OBJECT-TYPE
              SYNTAX   INTEGER
              MAX-ACCESS  read-only
              STATUS  current
              DESCRIPTION
                      ""
              ::= { zxr10DiffServFlowPatternEntry 6 }

     zxr10DiffServFlowShapingPir   OBJECT-TYPE
              SYNTAX   INTEGER
              MAX-ACCESS  read-only
              STATUS  current
              DESCRIPTION
                      ""
              ::= { zxr10DiffServFlowPatternEntry 7 }

     zxr10DiffServFlowShapingPbs   OBJECT-TYPE
              SYNTAX   INTEGER
              MAX-ACCESS  read-only
              STATUS  current
              DESCRIPTION
                      ""
              ::= { zxr10DiffServFlowPatternEntry 8 }

     zxr10DiffServFlowDropPatternName   OBJECT-TYPE
              SYNTAX   DisplayString
              MAX-ACCESS  read-only
              STATUS  current
              DESCRIPTION
                      ""
              ::= { zxr10DiffServFlowPatternEntry 9 }

-- Flow-Pattern MIB Table Ends

-- Intf-QoS-Policy MIB Table

     zxr10DiffServIntfTable  OBJECT-TYPE
              SYNTAX  SEQUENCE OF Zxr10DiffServIntfEntry
              MAX-ACCESS  not-accessible
              STATUS  current
              DESCRIPTION
                      ""
               ::= { zxr10DiffServ 5 }

     zxr10DiffServIntfEntry  OBJECT-TYPE
              SYNTAX  Zxr10DiffServIntfEntry
              MAX-ACCESS  not-accessible
              STATUS  current
              DESCRIPTION
                      ""
              INDEX  { ifIndex }
              ::= { zxr10DiffServIntfTable 1 }

     Zxr10DiffServIntfEntry ::=
              SEQUENCE {
                           zxr10DiffServIntfName
                               DisplayString,
                           zxr10DiffServIntfFlowPatternName
                               DisplayString,
                           zxr10DiffServIntfDomainName
                               DisplayString,
                           zxr10DiffServIntfDomainAppVlanRange
                               DisplayString,
                           zxr10DiffServIntfTrustType
                               DiffServTosTrustType,
                           zxr10DiffServIntfTrustAppVlanRange
                               DisplayString,
                           zxr10DiffServIntfTunnelingMode
                               DiffServTunnelingMode,
                           zxr10DiffServIntfInPolicingMode
                               DiffServPolicingMode,
                           zxr10DiffServIntfInPolicingCir
                               INTEGER,
                           zxr10DiffServIntfInPolicingCbs
                               INTEGER,
                           zxr10DiffServIntfInPolicingPir
                               INTEGER,
                           zxr10DiffServIntfInPolicingPbs
                               INTEGER,
                           zxr10DiffServIntfInPolicingGreenAction
                               DiffServPolicingAction,
                           zxr10DiffServIntfInPolicingGreenRemarkClass
                               DiffServClass,
                           zxr10DiffServIntfInPolicingGreenRemarkColor
                               DiffServColor,
                           zxr10DiffServIntfInPolicingYellowAction
                               DiffServPolicingAction,
                           zxr10DiffServIntfInPolicingYellowRemarkClass
                               DiffServClass,
                           zxr10DiffServIntfInPolicingYellowRemarkColor
                               DiffServColor,
                           zxr10DiffServIntfInPolicingRedAction
                               DiffServPolicingAction,
                           zxr10DiffServIntfInPolicingRedRemarkClass
                               DiffServClass,
                           zxr10DiffServIntfInPolicingRedRemarkColor
                               DiffServColor,
                           zxr10DiffServIntfOutPolicingMode
                               DiffServPolicingMode,
                           zxr10DiffServIntfOutPolicingCir
                               INTEGER,
                           zxr10DiffServIntfOutPolicingCbs
                               INTEGER,
                           zxr10DiffServIntfOutPolicingPir
                               INTEGER,
                           zxr10DiffServIntfOutPolicingPbs
                               INTEGER,
                           zxr10DiffServIntfOutPolicingGreenAction
                               DiffServPolicingAction,
                           zxr10DiffServIntfOutPolicingGreenRemarkClass
                               DiffServClass,
                           zxr10DiffServIntfOutPolicingGreenRemarkColor
                               DiffServColor,
                           zxr10DiffServIntfOutPolicingYellowAction
                               DiffServPolicingAction,
                           zxr10DiffServIntfOutPolicingYellowRemarkClass
                               DiffServClass,
                           zxr10DiffServIntfOutPolicingYellowRemarkColor
                               DiffServColor,
                           zxr10DiffServIntfOutPolicingRedAction
                               DiffServPolicingAction,
                           zxr10DiffServIntfOutPolicingRedRemarkClass
                               DiffServClass,
                           zxr10DiffServIntfOutPolicingRedRemarkColor
                               DiffServColor,
                           zxr10DiffServIntfOutShapingCir
                               INTEGER,
                           zxr10DiffServIntfOutShapingCbs
                               INTEGER,
                           zxr10DiffServIntfOutShapingPir
                               INTEGER,
                           zxr10DiffServIntfOutShapingPbs
                               INTEGER,
                           zxr10DiffServIntfTunnelingServClass
                               DiffServClass,
                           zxr10DiffServIntfTunnelingColor
                               DiffServColor
                       }

     zxr10DiffServIntfName  OBJECT-TYPE
              SYNTAX  DisplayString
              MAX-ACCESS  read-only
              STATUS  current
              DESCRIPTION
                      ""
              ::= { zxr10DiffServIntfEntry 1 }

     zxr10DiffServIntfFlowPatternName   OBJECT-TYPE
              SYNTAX  DisplayString
              MAX-ACCESS  read-only
              STATUS  current
              DESCRIPTION
                  ""
             ::= { zxr10DiffServIntfEntry 2 }

     zxr10DiffServIntfDomainName   OBJECT-TYPE
              SYNTAX  DisplayString
              MAX-ACCESS  read-only
              STATUS  current
              DESCRIPTION
                  ""
             ::= { zxr10DiffServIntfEntry 3 }

     zxr10DiffServIntfDomainAppVlanRange   OBJECT-TYPE
              SYNTAX  DisplayString
              MAX-ACCESS  read-only
              STATUS  current
              DESCRIPTION
                  ""
             ::= { zxr10DiffServIntfEntry 4 }

     zxr10DiffServIntfTrustType  OBJECT-TYPE
              SYNTAX  DiffServTosTrustType
              MAX-ACCESS  read-only
              STATUS  current
              DESCRIPTION
                      ""
              ::= { zxr10DiffServIntfEntry 5 }

     zxr10DiffServIntfTrustAppVlanRange   OBJECT-TYPE
              SYNTAX  DisplayString
              MAX-ACCESS  read-only
              STATUS  current
              DESCRIPTION
                  ""
             ::= { zxr10DiffServIntfEntry 6 }

     zxr10DiffServIntfTunnelingMode   OBJECT-TYPE
              SYNTAX   DiffServTunnelingMode
              MAX-ACCESS  read-only
              STATUS  current
              DESCRIPTION
                      ""
              ::= { zxr10DiffServIntfEntry 7 }

     zxr10DiffServIntfInPolicingMode   OBJECT-TYPE
              SYNTAX   DiffServPolicingMode
              MAX-ACCESS  read-only
              STATUS  current
              DESCRIPTION
                      ""
              ::= { zxr10DiffServIntfEntry 8 }

     zxr10DiffServIntfInPolicingCir   OBJECT-TYPE
              SYNTAX   INTEGER
              MAX-ACCESS  read-only
              STATUS  current
              DESCRIPTION
                      ""
              ::= { zxr10DiffServIntfEntry 9 }

     zxr10DiffServIntfInPolicingCbs   OBJECT-TYPE
              SYNTAX   INTEGER
              MAX-ACCESS  read-only
              STATUS  current
              DESCRIPTION
                      ""
              ::= { zxr10DiffServIntfEntry 10 }

     zxr10DiffServIntfInPolicingPir   OBJECT-TYPE
              SYNTAX   INTEGER
              MAX-ACCESS  read-only
              STATUS  current
              DESCRIPTION
                      ""
              ::= { zxr10DiffServIntfEntry 11 }

     zxr10DiffServIntfInPolicingPbs   OBJECT-TYPE
              SYNTAX   INTEGER
              MAX-ACCESS  read-only
              STATUS  current
              DESCRIPTION
                      ""
              ::= { zxr10DiffServIntfEntry 12 }

     zxr10DiffServIntfInPolicingGreenAction   OBJECT-TYPE
              SYNTAX   DiffServPolicingAction
              MAX-ACCESS  read-only
              STATUS  current
              DESCRIPTION
                      ""
              ::= { zxr10DiffServIntfEntry 13 }

     zxr10DiffServIntfInPolicingGreenRemarkClass   OBJECT-TYPE
              SYNTAX   DiffServClass
              MAX-ACCESS  read-only
              STATUS  current
              DESCRIPTION
                      ""
              ::= { zxr10DiffServIntfEntry 14 }

     zxr10DiffServIntfInPolicingGreenRemarkColor   OBJECT-TYPE
              SYNTAX   DiffServColor
              MAX-ACCESS  read-only
              STATUS  current
              DESCRIPTION
                      ""
              ::= { zxr10DiffServIntfEntry 15 }

     zxr10DiffServIntfInPolicingYellowAction   OBJECT-TYPE
              SYNTAX   DiffServPolicingAction
              MAX-ACCESS  read-only
              STATUS  current
              DESCRIPTION
                      ""
              ::= { zxr10DiffServIntfEntry 16 }

     zxr10DiffServIntfInPolicingYellowRemarkClass   OBJECT-TYPE
              SYNTAX   DiffServClass
              MAX-ACCESS  read-only
              STATUS  current
              DESCRIPTION
                      ""
              ::= { zxr10DiffServIntfEntry 17 }

     zxr10DiffServIntfInPolicingYellowRemarkColor   OBJECT-TYPE
              SYNTAX   DiffServColor
              MAX-ACCESS  read-only
              STATUS  current
              DESCRIPTION
                      ""
              ::= { zxr10DiffServIntfEntry 18 }

     zxr10DiffServIntfInPolicingRedAction   OBJECT-TYPE
              SYNTAX   DiffServPolicingAction
              MAX-ACCESS  read-only
              STATUS  current
              DESCRIPTION
                      ""
              ::= { zxr10DiffServIntfEntry 19 }

     zxr10DiffServIntfInPolicingRedRemarkClass   OBJECT-TYPE
              SYNTAX   DiffServClass
              MAX-ACCESS  read-only
              STATUS  current
              DESCRIPTION
                      ""
              ::= { zxr10DiffServIntfEntry 20 }

     zxr10DiffServIntfInPolicingRedRemarkColor   OBJECT-TYPE
              SYNTAX   DiffServColor
              MAX-ACCESS  read-only
              STATUS  current
              DESCRIPTION
                      ""
              ::= { zxr10DiffServIntfEntry 21 }

     zxr10DiffServIntfOutPolicingMode   OBJECT-TYPE
              SYNTAX   DiffServPolicingMode
              MAX-ACCESS  read-only
              STATUS  current
              DESCRIPTION
                      ""
              ::= { zxr10DiffServIntfEntry 22 }

     zxr10DiffServIntfOutPolicingCir   OBJECT-TYPE
              SYNTAX   INTEGER
              MAX-ACCESS  read-only
              STATUS  current
              DESCRIPTION
                      ""
              ::= { zxr10DiffServIntfEntry 23 }

     zxr10DiffServIntfOutPolicingCbs   OBJECT-TYPE
              SYNTAX   INTEGER
              MAX-ACCESS  read-only
              STATUS  current
              DESCRIPTION
                      ""
              ::= { zxr10DiffServIntfEntry 24 }

     zxr10DiffServIntfOutPolicingPir   OBJECT-TYPE
              SYNTAX   INTEGER
              MAX-ACCESS  read-only
              STATUS  current
              DESCRIPTION
                      ""
              ::= { zxr10DiffServIntfEntry 25 }

     zxr10DiffServIntfOutPolicingPbs   OBJECT-TYPE
              SYNTAX   INTEGER
              MAX-ACCESS  read-only
              STATUS  current
              DESCRIPTION
                      ""
              ::= { zxr10DiffServIntfEntry 26 }

     zxr10DiffServIntfOutPolicingGreenAction   OBJECT-TYPE
              SYNTAX   DiffServPolicingAction
              MAX-ACCESS  read-only
              STATUS  current
              DESCRIPTION
                      ""
              ::= { zxr10DiffServIntfEntry 27 }

     zxr10DiffServIntfOutPolicingGreenRemarkClass   OBJECT-TYPE
              SYNTAX   DiffServClass
              MAX-ACCESS  read-only
              STATUS  current
              DESCRIPTION
                      ""
              ::= { zxr10DiffServIntfEntry 28 }

     zxr10DiffServIntfOutPolicingGreenRemarkColor   OBJECT-TYPE
              SYNTAX   DiffServColor
              MAX-ACCESS  read-only
              STATUS  current
              DESCRIPTION
                      ""
              ::= { zxr10DiffServIntfEntry 29 }

     zxr10DiffServIntfOutPolicingYellowAction   OBJECT-TYPE
              SYNTAX   DiffServPolicingAction
              MAX-ACCESS  read-only
              STATUS  current
              DESCRIPTION
                      ""
              ::= { zxr10DiffServIntfEntry 30 }

     zxr10DiffServIntfOutPolicingYellowRemarkClass   OBJECT-TYPE
              SYNTAX   DiffServClass
              MAX-ACCESS  read-only
              STATUS  current
              DESCRIPTION
                      ""
              ::= { zxr10DiffServIntfEntry 31 }

     zxr10DiffServIntfOutPolicingYellowRemarkColor   OBJECT-TYPE
              SYNTAX   DiffServColor
              MAX-ACCESS  read-only
              STATUS  current
              DESCRIPTION
                      ""
              ::= { zxr10DiffServIntfEntry 32 }

     zxr10DiffServIntfOutPolicingRedAction   OBJECT-TYPE
              SYNTAX   DiffServPolicingAction
              MAX-ACCESS  read-only
              STATUS  current
              DESCRIPTION
                      ""
              ::= { zxr10DiffServIntfEntry 33 }

     zxr10DiffServIntfOutPolicingRedRemarkClass   OBJECT-TYPE
              SYNTAX   DiffServClass
              MAX-ACCESS  read-only
              STATUS  current
              DESCRIPTION
                      ""
              ::= { zxr10DiffServIntfEntry 34 }

     zxr10DiffServIntfOutPolicingRedRemarkColor   OBJECT-TYPE
              SYNTAX   DiffServColor
              MAX-ACCESS  read-only
              STATUS  current
              DESCRIPTION
                      ""
              ::= { zxr10DiffServIntfEntry 35 }

     zxr10DiffServIntfOutShapingCir   OBJECT-TYPE
              SYNTAX   INTEGER
              MAX-ACCESS  read-only
              STATUS  current
              DESCRIPTION
                      ""
              ::= { zxr10DiffServIntfEntry 36 }

     zxr10DiffServIntfOutShapingCbs   OBJECT-TYPE
              SYNTAX   INTEGER
              MAX-ACCESS  read-only
              STATUS  current
              DESCRIPTION
                      ""
              ::= { zxr10DiffServIntfEntry 37 }

     zxr10DiffServIntfOutShapingPir   OBJECT-TYPE
              SYNTAX   INTEGER
              MAX-ACCESS  read-only
              STATUS  current
              DESCRIPTION
                      ""
              ::= { zxr10DiffServIntfEntry 38 }

     zxr10DiffServIntfOutShapingPbs   OBJECT-TYPE
              SYNTAX   INTEGER
              MAX-ACCESS  read-only
              STATUS  current
              DESCRIPTION
                      ""
              ::= { zxr10DiffServIntfEntry 39 }

     zxr10DiffServIntfTunnelingServClass   OBJECT-TYPE
              SYNTAX   DiffServClass
              MAX-ACCESS  read-only
              STATUS  current
              DESCRIPTION
                      ""
              ::= { zxr10DiffServIntfEntry 40 }

     zxr10DiffServIntfTunnelingColor   OBJECT-TYPE
              SYNTAX   DiffServColor
              MAX-ACCESS  read-only
              STATUS  current
              DESCRIPTION
                      ""
              ::= { zxr10DiffServIntfEntry 41 }

-- Intf-QoS-Policy MIB Table Ends

-- Tunnel-QoS-Policy MIB Table

     zxr10DiffServTunnelTable  OBJECT-TYPE
              SYNTAX  SEQUENCE OF Zxr10DiffServTunnelEntry
              MAX-ACCESS  not-accessible
              STATUS  current
              DESCRIPTION
                      ""
               ::= { zxr10DiffServ 6 }

     zxr10DiffServTunnelEntry  OBJECT-TYPE
              SYNTAX  Zxr10DiffServTunnelEntry
              MAX-ACCESS  not-accessible
              STATUS  current
              DESCRIPTION
                      ""
              INDEX  { zxr10DiffServTunnelNo }
              ::= { zxr10DiffServTunnelTable 1 }

     Zxr10DiffServTunnelEntry ::=
              SEQUENCE {
                           zxr10DiffServTunnelNo
                               INTEGER,
                           zxr10DiffServTunnelFlowPatternName
                               DisplayString,
                           zxr10DiffServTunnelTunnelingMode
                               DiffServTunnelingMode,
                           zxr10DiffServTunnelPolicingMode
                               DiffServPolicingMode,
                           zxr10DiffServTunnelPolicingCir
                               INTEGER,
                           zxr10DiffServTunnelPolicingCbs
                               INTEGER,
                           zxr10DiffServTunnelPolicingPir
                               INTEGER,
                           zxr10DiffServTunnelPolicingPbs
                               INTEGER,
                           zxr10DiffServTunnelShapingCir
                               INTEGER,
                           zxr10DiffServTunnelShapingCbs
                               INTEGER,
                           zxr10DiffServTunnelShapingPir
                               INTEGER,
                           zxr10DiffServTunnelShapingPbs
                               INTEGER,
                           zxr10DiffServTunnelIntfName1
                               DisplayString,
                           zxr10DiffServTunnelDomainName1
                               DisplayString,
                           zxr10DiffServTunnelIntfName2
                               DisplayString,
                           zxr10DiffServTunnelDomainName2
                               DisplayString,
                           zxr10DiffServTunnelTunnelingServClass
                               DiffServClass,
                           zxr10DiffServTunnelTunnelingColor
                               DiffServColor

                       }

     zxr10DiffServTunnelNo  OBJECT-TYPE
              SYNTAX  INTEGER
              MAX-ACCESS  read-only
              STATUS  current
              DESCRIPTION
                      ""
              ::= { zxr10DiffServTunnelEntry 1 }

     zxr10DiffServTunnelFlowPatternName   OBJECT-TYPE
              SYNTAX  DisplayString
              MAX-ACCESS  read-only
              STATUS  current
              DESCRIPTION
                  ""
             ::= { zxr10DiffServTunnelEntry 2 }

     zxr10DiffServTunnelTunnelingMode   OBJECT-TYPE
              SYNTAX  DiffServTunnelingMode
              MAX-ACCESS  read-only
              STATUS  current
              DESCRIPTION
                  ""
             ::= { zxr10DiffServTunnelEntry 3 }

     zxr10DiffServTunnelPolicingMode   OBJECT-TYPE
              SYNTAX   DiffServPolicingMode
              MAX-ACCESS  read-only
              STATUS  current
              DESCRIPTION
                      ""
              ::= { zxr10DiffServTunnelEntry 4 }

     zxr10DiffServTunnelPolicingCir   OBJECT-TYPE
              SYNTAX   INTEGER
              MAX-ACCESS  read-only
              STATUS  current
              DESCRIPTION
                      ""
              ::= { zxr10DiffServTunnelEntry 5 }

     zxr10DiffServTunnelPolicingCbs   OBJECT-TYPE
              SYNTAX   INTEGER
              MAX-ACCESS  read-only
              STATUS  current
              DESCRIPTION
                      ""
              ::= { zxr10DiffServTunnelEntry 6 }

     zxr10DiffServTunnelPolicingPir   OBJECT-TYPE
              SYNTAX   INTEGER
              MAX-ACCESS  read-only
              STATUS  current
              DESCRIPTION
                      ""
              ::= { zxr10DiffServTunnelEntry 7 }

     zxr10DiffServTunnelPolicingPbs   OBJECT-TYPE
              SYNTAX   INTEGER
              MAX-ACCESS  read-only
              STATUS  current
              DESCRIPTION
                      ""
              ::= { zxr10DiffServTunnelEntry 8 }

     zxr10DiffServTunnelShapingCir   OBJECT-TYPE
              SYNTAX   INTEGER
              MAX-ACCESS  read-only
              STATUS  current
              DESCRIPTION
                      ""
              ::= { zxr10DiffServTunnelEntry 9 }

     zxr10DiffServTunnelShapingCbs   OBJECT-TYPE
              SYNTAX   INTEGER
              MAX-ACCESS  read-only
              STATUS  current
              DESCRIPTION
                      ""
              ::= { zxr10DiffServTunnelEntry 10 }

     zxr10DiffServTunnelShapingPir   OBJECT-TYPE
              SYNTAX   INTEGER
              MAX-ACCESS  read-only
              STATUS  current
              DESCRIPTION
                      ""
              ::= { zxr10DiffServTunnelEntry 11 }

     zxr10DiffServTunnelShapingPbs   OBJECT-TYPE
              SYNTAX   INTEGER
              MAX-ACCESS  read-only
              STATUS  current
              DESCRIPTION
                      ""
              ::= { zxr10DiffServTunnelEntry 12 }

     zxr10DiffServTunnelIntfName1   OBJECT-TYPE
              SYNTAX  DisplayString
              MAX-ACCESS  read-only
              STATUS  current
              DESCRIPTION
                  ""
             ::= { zxr10DiffServTunnelEntry 13 }

     zxr10DiffServTunnelDomainName1   OBJECT-TYPE
              SYNTAX  DisplayString
              MAX-ACCESS  read-only
              STATUS  current
              DESCRIPTION
                  ""
             ::= { zxr10DiffServTunnelEntry 14 }

     zxr10DiffServTunnelIntfName2   OBJECT-TYPE
              SYNTAX  DisplayString
              MAX-ACCESS  read-only
              STATUS  current
              DESCRIPTION
                  ""
             ::= { zxr10DiffServTunnelEntry 15 }

     zxr10DiffServTunnelDomainName2   OBJECT-TYPE
              SYNTAX  DisplayString
              MAX-ACCESS  read-only
              STATUS  current
              DESCRIPTION
                  ""
             ::= { zxr10DiffServTunnelEntry 16 }

     zxr10DiffServTunnelTunnelingServClass   OBJECT-TYPE
              SYNTAX   DiffServClass
              MAX-ACCESS  read-only
              STATUS  current
              DESCRIPTION
                      ""
              ::= { zxr10DiffServTunnelEntry 17 }

     zxr10DiffServTunnelTunnelingColor   OBJECT-TYPE
              SYNTAX   DiffServColor
              MAX-ACCESS  read-only
              STATUS  current
              DESCRIPTION
                      ""
              ::= { zxr10DiffServTunnelEntry 18 }

-- Tunnel-QoS-Policy MIB Table Ends

-- PW-QoS-Policy MIB Table

     zxr10DiffServPWTable  OBJECT-TYPE
              SYNTAX  SEQUENCE OF Zxr10DiffServPWEntry
              MAX-ACCESS  not-accessible
              STATUS  current
              DESCRIPTION
                      ""
               ::= { zxr10DiffServ 7 }

     zxr10DiffServPWEntry  OBJECT-TYPE
              SYNTAX  Zxr10DiffServPWEntry
              MAX-ACCESS  not-accessible
              STATUS  current
              DESCRIPTION
                      ""
              INDEX  { zxr10DiffServPWName }
              ::= { zxr10DiffServPWTable 1 }

     Zxr10DiffServPWEntry ::=
              SEQUENCE {
                           zxr10DiffServPWName
                               DisplayString,
                           zxr10DiffServPWFlowPatternName
                               DisplayString,
                           zxr10DiffServPWPolicingMode
                               DiffServPolicingMode,
                           zxr10DiffServPWPolicingCir
                               INTEGER,
                           zxr10DiffServPWPolicingCbs
                               INTEGER,
                           zxr10DiffServPWPolicingPir
                               INTEGER,
                           zxr10DiffServPWPolicingPbs
                               INTEGER,
                           zxr10DiffServPWShapingCir
                               INTEGER,
                           zxr10DiffServPWShapingCbs
                               INTEGER,
                           zxr10DiffServPWShapingPir
                               INTEGER,
                           zxr10DiffServPWShapingPbs
                               INTEGER,
                           zxr10DiffServPWDomainName
                               DisplayString
                       }

     zxr10DiffServPWName  OBJECT-TYPE
              SYNTAX  DisplayString
              MAX-ACCESS  read-only
              STATUS  current
              DESCRIPTION
                      ""
              ::= { zxr10DiffServPWEntry 1 }

     zxr10DiffServPWFlowPatternName   OBJECT-TYPE
              SYNTAX  DisplayString
              MAX-ACCESS  read-only
              STATUS  current
              DESCRIPTION
                  ""
             ::= { zxr10DiffServPWEntry 2 }

     zxr10DiffServPWPolicingMode   OBJECT-TYPE
              SYNTAX   DiffServPolicingMode
              MAX-ACCESS  read-only
              STATUS  current
              DESCRIPTION
                      ""
              ::= { zxr10DiffServPWEntry 3 }

     zxr10DiffServPWPolicingCir   OBJECT-TYPE
              SYNTAX   INTEGER
              MAX-ACCESS  read-only
              STATUS  current
              DESCRIPTION
                      ""
              ::= { zxr10DiffServPWEntry 4 }

     zxr10DiffServPWPolicingCbs   OBJECT-TYPE
              SYNTAX   INTEGER
              MAX-ACCESS  read-only
              STATUS  current
              DESCRIPTION
                      ""
              ::= { zxr10DiffServPWEntry 5 }

     zxr10DiffServPWPolicingPir   OBJECT-TYPE
              SYNTAX   INTEGER
              MAX-ACCESS  read-only
              STATUS  current
              DESCRIPTION
                      ""
              ::= { zxr10DiffServPWEntry 6 }

     zxr10DiffServPWPolicingPbs   OBJECT-TYPE
              SYNTAX   INTEGER
              MAX-ACCESS  read-only
              STATUS  current
              DESCRIPTION
                      ""
              ::= { zxr10DiffServPWEntry 7 }

     zxr10DiffServPWShapingCir   OBJECT-TYPE
              SYNTAX   INTEGER
              MAX-ACCESS  read-only
              STATUS  current
              DESCRIPTION
                      ""
              ::= { zxr10DiffServPWEntry 8 }

     zxr10DiffServPWShapingCbs   OBJECT-TYPE
              SYNTAX   INTEGER
              MAX-ACCESS  read-only
              STATUS  current
              DESCRIPTION
                      ""
              ::= { zxr10DiffServPWEntry 9 }

     zxr10DiffServPWShapingPir   OBJECT-TYPE
              SYNTAX   INTEGER
              MAX-ACCESS  read-only
              STATUS  current
              DESCRIPTION
                      ""
              ::= { zxr10DiffServPWEntry 10 }

     zxr10DiffServPWShapingPbs   OBJECT-TYPE
              SYNTAX   INTEGER
              MAX-ACCESS  read-only
              STATUS  current
              DESCRIPTION
                      ""
              ::= { zxr10DiffServPWEntry 11 }

     zxr10DiffServPWDomainName   OBJECT-TYPE
              SYNTAX  DisplayString
              MAX-ACCESS  read-only
              STATUS  current
              DESCRIPTION
                  ""
             ::= { zxr10DiffServPWEntry 12 }

-- PW-QoS-Policy MIB Table Ends

-- CIP-QoS-Policy MIB Table

     zxr10DiffServCIPTable  OBJECT-TYPE
              SYNTAX  SEQUENCE OF Zxr10DiffServCIPEntry
              MAX-ACCESS  not-accessible
              STATUS  current
              DESCRIPTION
                      ""
               ::= { zxr10DiffServ 8 }

     zxr10DiffServCIPEntry  OBJECT-TYPE
              SYNTAX  Zxr10DiffServCIPEntry
              MAX-ACCESS  not-accessible
              STATUS  current
              DESCRIPTION
                      ""
              INDEX  { zxr10DiffServCIPNo }
              ::= { zxr10DiffServCIPTable 1 }

     Zxr10DiffServCIPEntry ::=
              SEQUENCE {
                           zxr10DiffServCIPNo
                               INTEGER,
                           zxr10DiffServCIPPolicingMode
                               DiffServPolicingMode,
                           zxr10DiffServCIPPolicingCir
                               INTEGER,
                           zxr10DiffServCIPPolicingCbs
                               INTEGER,
                           zxr10DiffServCIPPolicingPir
                               INTEGER,
                           zxr10DiffServCIPPolicingPbs
                               INTEGER
                       }

     zxr10DiffServCIPNo  OBJECT-TYPE
              SYNTAX  INTEGER
              MAX-ACCESS  read-only
              STATUS  current
              DESCRIPTION
                      ""
              ::= { zxr10DiffServCIPEntry 1 }

     zxr10DiffServCIPPolicingMode   OBJECT-TYPE
              SYNTAX   DiffServPolicingMode
              MAX-ACCESS  read-only
              STATUS  current
              DESCRIPTION
                      ""
              ::= { zxr10DiffServCIPEntry 2 }

     zxr10DiffServCIPPolicingCir   OBJECT-TYPE
              SYNTAX   INTEGER
              MAX-ACCESS  read-only
              STATUS  current
              DESCRIPTION
                      ""
              ::= { zxr10DiffServCIPEntry 3 }

     zxr10DiffServCIPPolicingCbs   OBJECT-TYPE
              SYNTAX   INTEGER
              MAX-ACCESS  read-only
              STATUS  current
              DESCRIPTION
                      ""
              ::= { zxr10DiffServCIPEntry 4 }

     zxr10DiffServCIPPolicingPir   OBJECT-TYPE
              SYNTAX   INTEGER
              MAX-ACCESS  read-only
              STATUS  current
              DESCRIPTION
                      ""
              ::= { zxr10DiffServCIPEntry 5 }

     zxr10DiffServCIPPolicingPbs   OBJECT-TYPE
              SYNTAX   INTEGER
              MAX-ACCESS  read-only
              STATUS  current
              DESCRIPTION
                      ""
              ::= { zxr10DiffServCIPEntry 6 }

-- CIP-QoS-Policy MIB Table Ends

-- VPN-QoS-Policy MIB Table

     zxr10DiffServVPNTable  OBJECT-TYPE
              SYNTAX  SEQUENCE OF Zxr10DiffServVPNEntry
              MAX-ACCESS  not-accessible
              STATUS  current
              DESCRIPTION
                      ""
               ::= { zxr10DiffServ 9 }

     zxr10DiffServVPNEntry  OBJECT-TYPE
              SYNTAX  Zxr10DiffServVPNEntry
              MAX-ACCESS  not-accessible
              STATUS  current
              DESCRIPTION
                      ""
              INDEX  { zxr10DiffServVPNMode,
                       zxr10DiffServVPNName }
              ::= { zxr10DiffServVPNTable 1 }

     Zxr10DiffServVPNEntry ::=
              SEQUENCE {
                           zxr10DiffServVPNMode
                               DiffServVPNMode,
                           zxr10DiffServVPNName
                               DisplayString,
                           zxr10DiffServVPNTunnelingMode
                               DiffServTunnelingMode,
                           zxr10DiffServVPNPolicingMode
                               DiffServPolicingMode,
                           zxr10DiffServVPNPolicingCir
                               INTEGER,
                           zxr10DiffServVPNPolicingCbs
                               INTEGER,
                           zxr10DiffServVPNPolicingPir
                               INTEGER,
                           zxr10DiffServVPNPolicingPbs
                               INTEGER
                       }

     zxr10DiffServVPNMode  OBJECT-TYPE
              SYNTAX  DiffServVPNMode
              MAX-ACCESS  read-only
              STATUS  current
              DESCRIPTION
                      ""
              ::= { zxr10DiffServVPNEntry 1 }

     zxr10DiffServVPNName   OBJECT-TYPE
              SYNTAX   DisplayString
              MAX-ACCESS  read-only
              STATUS  current
              DESCRIPTION
                      ""
              ::= { zxr10DiffServVPNEntry 2 }

     zxr10DiffServVPNTunnelingMode   OBJECT-TYPE
              SYNTAX   DiffServTunnelingMode
              MAX-ACCESS  read-only
              STATUS  current
              DESCRIPTION
                      ""
              ::= { zxr10DiffServVPNEntry 3 }

     zxr10DiffServVPNPolicingMode   OBJECT-TYPE
              SYNTAX   DiffServPolicingMode
              MAX-ACCESS  read-only
              STATUS  current
              DESCRIPTION
                      ""
              ::= { zxr10DiffServVPNEntry 4 }

     zxr10DiffServVPNPolicingCir   OBJECT-TYPE
              SYNTAX   INTEGER
              MAX-ACCESS  read-only
              STATUS  current
              DESCRIPTION
                      ""
              ::= { zxr10DiffServVPNEntry 5 }

     zxr10DiffServVPNPolicingCbs   OBJECT-TYPE
              SYNTAX   INTEGER
              MAX-ACCESS  read-only
              STATUS  current
              DESCRIPTION
                      ""
              ::= { zxr10DiffServVPNEntry 6 }

     zxr10DiffServVPNPolicingPir   OBJECT-TYPE
              SYNTAX   INTEGER
              MAX-ACCESS  read-only
              STATUS  current
              DESCRIPTION
                      ""
              ::= { zxr10DiffServVPNEntry 7 }

     zxr10DiffServVPNPolicingPbs   OBJECT-TYPE
              SYNTAX   INTEGER
              MAX-ACCESS  read-only
              STATUS  current
              DESCRIPTION
                      ""
              ::= { zxr10DiffServVPNEntry 8 }

-- VPN-QoS-Policy MIB Table Ends

-- class-map MIB Table

     zxr10DiffServClsMapTable  OBJECT-TYPE
              SYNTAX  SEQUENCE OF Zxr10DiffServClsMapEntry
              MAX-ACCESS  not-accessible
              STATUS  current
              DESCRIPTION
                      ""
               ::= { zxr10DiffServ 10 }

     zxr10DiffServClsMapEntry  OBJECT-TYPE
              SYNTAX  Zxr10DiffServClsMapEntry
              MAX-ACCESS  not-accessible
              STATUS  current
              DESCRIPTION
                      ""
              INDEX  { zxr10DiffServClsMapName,
                       zxr10DiffServClsMatchSequence }
              ::= { zxr10DiffServClsMapTable 1 }

     Zxr10DiffServClsMapEntry ::=
              SEQUENCE {
                           zxr10DiffServClsMapName
                               DisplayString,
                           zxr10DiffServClsMatchSequence
                               INTEGER,
                           zxr10DiffServClsMatchSvlanID
                               DisplayString,
                           zxr10DiffServClsMatchCvlanID
                               DisplayString,
                           zxr10DiffServClsMatchSVlanPri
                               DisplayString,
                           zxr10DiffServClsMatchVpi
                               DisplayString,
                           zxr10DiffServClsMatchVci
                               DisplayString
                       }

     zxr10DiffServClsMapName  OBJECT-TYPE
              SYNTAX  DisplayString
              MAX-ACCESS  read-only
              STATUS  current
              DESCRIPTION
                      ""
              ::= { zxr10DiffServClsMapEntry 1 }

     zxr10DiffServClsMatchSequence   OBJECT-TYPE
              SYNTAX  INTEGER
              MAX-ACCESS  not-accessible
              STATUS  current
              DESCRIPTION
                      ""
              ::= { zxr10DiffServClsMapEntry 2 }

     zxr10DiffServClsMatchSvlanID   OBJECT-TYPE
              SYNTAX   DisplayString
              MAX-ACCESS  read-only
              STATUS  current
              DESCRIPTION
                      ""
              ::= { zxr10DiffServClsMapEntry 3 }

     zxr10DiffServClsMatchCvlanID   OBJECT-TYPE
              SYNTAX   DisplayString
              MAX-ACCESS  read-only
              STATUS  current
              DESCRIPTION
                      ""
              ::= { zxr10DiffServClsMapEntry 4 }

     zxr10DiffServClsMatchSVlanPri   OBJECT-TYPE
              SYNTAX   DisplayString
              MAX-ACCESS  read-only
              STATUS  current
              DESCRIPTION
                      ""
              ::= { zxr10DiffServClsMapEntry 5 }

     zxr10DiffServClsMatchVpi   OBJECT-TYPE
              SYNTAX   DisplayString
              MAX-ACCESS  read-only
              STATUS  current
              DESCRIPTION
                      ""
              ::= { zxr10DiffServClsMapEntry 6 }

     zxr10DiffServClsMatchVci   OBJECT-TYPE
              SYNTAX   DisplayString
              MAX-ACCESS  read-only
              STATUS  current
              DESCRIPTION
                      ""
              ::= { zxr10DiffServClsMapEntry 7 }

-- class-map MIB Table Ends

     END
