--------------------------------------------------------------------------
-- File Name : ZTE-DSL-PORT-MIB.mib
-- Date      : 2007-12-15
-- Author    : ZTE Nms dept.

--
-- Zte DSL Mib for Access Node
--------------------------------------------------------------------------
ZTE-DSL-PORT-MIB DEFINITIONS ::= BEGIN

    IMPORTS
       MODULE-IDENTITY, OBJECT-TYPE, Unsigned32,Integer32, Counter32,
       NOTIFICATION-TYPE                                        FROM SNMPv2-SMI
       enterprises                                              FROM SNMPv2-SMI
       ifIndex                                                  FROM IF-MIB
       DisplayString,TEXTUAL-CONVENTION,TruthValue,RowStatus    FROM SNMPv2-TC
       SnmpAdminString                                 FROM SNMP-FRAMEWORK-MIB;


    zxDslPortMib MODULE-IDENTITY
        LAST-UPDATED    "200712161500Z"
        ORGANIZATION "ZTE Corporation"
        CONTACT-INFO "ZTE NMS dept.
                      Su Chunshan   68896292 "
        DESCRIPTION  "This MIB defines managed objects of zte xDSL mgmt . "
        ::= { zxDsl 43 }



    zte OBJECT IDENTIFIER ::= { enterprises 3902 }
    zxDsl OBJECT IDENTIFIER ::= { zte 1004 }


    zxDslPortMibObjects OBJECT IDENTIFIER ::= { zxDslPortMib 1 }


    zxDslPortObjects            OBJECT IDENTIFIER  ::= {zxDslPortMibObjects 1}
    zxDslPortTrapObjects        OBJECT IDENTIFIER  ::= {zxDslPortMibObjects 3}



--------------------------------------------------------------------------------
-- Following objects are defined.
-- 1.Port table

-- 2.Trap
--------------------------------------------------------------------------------


--------------------------------------------------------------------------------
-- 1.Port table
--------------------------------------------------------------------------------
    zxDslPortTable   OBJECT-TYPE
        SYNTAX      SEQUENCE  OF  ZxDslPortEntry
        MAX-ACCESS  not-accessible
        STATUS      current
        DESCRIPTION "This table includes the dsl port information."
        ::=  { zxDslPortObjects  10 }

    zxDslPortEntry   OBJECT-TYPE
        SYNTAX      ZxDslPortEntry
        MAX-ACCESS  not-accessible
        STATUS      current
        DESCRIPTION "An entry in zxDslPortTable."
        INDEX       { ifIndex  }
        ::=  { zxDslPortTable 1 }

    ZxDslPortEntry  ::=  SEQUENCE {
        zxDslPortLockStatus               INTEGER
        }


    zxDslPortLockStatus OBJECT-TYPE
        SYNTAX          INTEGER
        {
            unlock(1),
            lock(2)
        }
        MAX-ACCESS      read-write
        STATUS          current
        DESCRIPTION     "
            Operate the interface.
            lock   -- disable the service and alarm of this port
            unlock -- release the lock status
            "
        ::=  {  zxDslPortEntry  1  }



END
