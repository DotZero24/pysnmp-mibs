-- File Name : ES-GroupManagement.mib
-- Date      : Wed Nov 10 10:43:24 CST 2004
-- Author    : AdventNet Agent Toolkit Java Edition - MIB Editor 5



ES-GroupManagement-MIB	DEFINITIONS ::= BEGIN
	IMPORTS
		RowStatus, TEXTUAL-CONVENTION
			FROM SNMPv2-TC
		OBJECT-TYPE, Integer32, IpAddress, Unsigned32, enterprises
			FROM SNMPv2-SMI;

-- TEXTUAL-CONVENTIONS --
	MacAddress ::= TEXTUAL-CONVENTION
		DISPLAY-HINT	""
		STATUS			current
		DESCRIPTION
			"Represents an 802 MAC address represented in the
             `canonical' order defined by IEEE 802.1a, i.e., as if it
             were transmitted least significant bit first, even though
             802.5 (in contrast to other 802.x protocols) requires MAC
             addresses to be transmitted most significant bit first."
		SYNTAX 			OCTET STRING

    zte	OBJECT IDENTIFIER
		::=  {  enterprises  3902  }

	ethernetSwitch	OBJECT IDENTIFIER
		::=  {  zte  15  }

	groupManagement	OBJECT IDENTIFIER
		::=  {  ethernetSwitch  4  }

	groupParam	OBJECT IDENTIFIER
		::=  {  groupManagement  1  }

	neighborDiscovery	OBJECT IDENTIFIER
		::=  {  groupManagement  2  }

	topologyCollect	OBJECT IDENTIFIER
		::=  {  groupManagement  3  }

	memberManage	OBJECT IDENTIFIER
		::=  {  groupManagement  4  }

	gmEnterpriseTrap	OBJECT IDENTIFIER
		::=  {  groupManagement  5  }

	gmHandtime	OBJECT-TYPE
		SYNTAX			Integer32  ( 1 .. 300  )
		MAX-ACCESS		read-write
		STATUS			current
		DESCRIPTION		"Group member shakehand timer interval"
		::=  {  groupParam  1  }

	gmHoldtime	OBJECT-TYPE
		SYNTAX			Integer32  ( 1 .. 300  )
		MAX-ACCESS		read-write
		STATUS			current
		DESCRIPTION		"Group member shakehand hold timer interval.
		                This item only for command switch."
		::=  {  groupParam  2  }

	gmName	OBJECT-TYPE
		SYNTAX			OCTET STRING  ( SIZE ( 0 .. 32  ) )
		MAX-ACCESS		read-write
		STATUS			current
		DESCRIPTION		"Group descriptive name.
		                This item only for command switch."
		::=  {  groupParam  3  }

	gmSwitchRole	OBJECT-TYPE
		SYNTAX			INTEGER  { commandSwitch ( 1 ) , memberSwitch ( 2 ) , candidateSwitch ( 3 ) , independentSwitch ( 4 ) }
		MAX-ACCESS		read-write
		STATUS			current
		DESCRIPTION		"Description"
		::=  {  groupParam  4  }

	gmIpPool	OBJECT-TYPE
		SYNTAX			OCTET STRING
		MAX-ACCESS		read-write
		STATUS			current
		DESCRIPTION		"the format of this item is xx/xx.xx.xx.xx/xx. Among this string,
                        the first segment represents layer 3 ipport number, the second
                        segment  represents layer 3 ipAddress, the third segment represents
                        net mask. eg: 12/192.168.2.8/24. Command switch and member switch can't
                        set this item.Member switch can't get this item."
		::=  {  groupParam  5  }

	tftpServerIpAddr	OBJECT-TYPE
		SYNTAX			IpAddress
		MAX-ACCESS		read-write
		STATUS			current
		DESCRIPTION		"Get/set tftp server ip address for the group.
		                This item only for command switch."
		::=  {  groupParam  6  }

	belongedCmdMac	OBJECT-TYPE
		SYNTAX			MacAddress
		MAX-ACCESS		read-only
		STATUS			current
		DESCRIPTION		"This item only for member switch.
		                It indicates the command switch mac address of the group
		                which this member switch belonged to."
		::=  {  groupParam  7  }

	dpAdminStatus	OBJECT-TYPE
		SYNTAX			INTEGER  { enable ( 1 ) , disable ( 2 ) }
		MAX-ACCESS		read-write
		STATUS			current
		DESCRIPTION		"Enable/disable neighbor discovery function."
		::=  {  neighborDiscovery  1  }

	dpTimer	OBJECT-TYPE
		SYNTAX			Integer32  ( 5 .. 255  )
		MAX-ACCESS		read-write
		STATUS			current
		DESCRIPTION		"Description"
		::=  {  neighborDiscovery  2  }

	dpHoldtime	OBJECT-TYPE
		SYNTAX			Integer32  ( 10 .. 255  )
		MAX-ACCESS		read-write
		STATUS			current
		DESCRIPTION		"Description"
		::=  {  neighborDiscovery  3  }

	dpPortTable	OBJECT-TYPE
		SYNTAX		SEQUENCE  OF  DpPortEntry
		MAX-ACCESS	not-accessible
		STATUS		current
		DESCRIPTION	"Description"
		::=  { neighborDiscovery  4 }

	dpPortEntry	OBJECT-TYPE
		SYNTAX		DpPortEntry
		MAX-ACCESS	not-accessible
		STATUS		current
		DESCRIPTION	"Row Description"
		INDEX		{  dpPortId  }
		::=  { dpPortTable 1 }

	DpPortEntry  ::=  SEQUENCE {
		dpPortId  Integer32,
		dpPortAdminStatus  INTEGER
		}


	dpPortId	OBJECT-TYPE
		SYNTAX			Integer32
		MAX-ACCESS		not-accessible
		STATUS			current
		DESCRIPTION		"Port id "
		::=  {  dpPortEntry  1  }


	dpPortAdminStatus	OBJECT-TYPE
		SYNTAX			INTEGER  { enable ( 1 ) , disable ( 2 ) }
		MAX-ACCESS		read-write
		STATUS			current
		DESCRIPTION		"Enable or Disable zdp on port "
		::=  {  dpPortEntry  2  }

	dpTrunkTable	OBJECT-TYPE
		SYNTAX		SEQUENCE  OF  DpTrunkEntry
		MAX-ACCESS	not-accessible
		STATUS		current
		DESCRIPTION	"Description"
		::=  { neighborDiscovery  5 }

	dpTrunkEntry	OBJECT-TYPE
		SYNTAX		DpTrunkEntry
		MAX-ACCESS	not-accessible
		STATUS		current
		DESCRIPTION	"Row Description"
		INDEX		{  dpTrunkId  }
		::=  { dpTrunkTable 1 }

	DpTrunkEntry  ::=  SEQUENCE {
		dpTrunkId  Integer32,
		dpTrunkAdminStatus  INTEGER
		}


	dpTrunkId	OBJECT-TYPE
		SYNTAX			Integer32
		MAX-ACCESS		not-accessible
		STATUS			current
		DESCRIPTION		"Trunk id"
		::=  {  dpTrunkEntry  1  }


	dpTrunkAdminStatus	OBJECT-TYPE
		SYNTAX			INTEGER  { enable ( 1 ) , disable ( 2 ) }
		MAX-ACCESS		read-write
		STATUS			current
		DESCRIPTION		"enable or disable zdp on trunk"
		::=  {  dpTrunkEntry  2  }

	dpDevPortTable	OBJECT-TYPE
		SYNTAX		SEQUENCE  OF  DpDevPortEntry
		MAX-ACCESS	not-accessible
		STATUS		current
		DESCRIPTION	"Description"
		::=  { neighborDiscovery  6 }

	dpDevPortEntry	OBJECT-TYPE
		SYNTAX		DpDevPortEntry
		MAX-ACCESS	not-accessible
		STATUS		current
		DESCRIPTION	"Row Description"
		INDEX		{  dpLocalPortId ,  dpPortPeerMac}
		::=  { dpDevPortTable 1 }

	DpDevPortEntry  ::=  SEQUENCE {
		dpLocalPortId    Integer32,
		dpPortPeerMac  MacAddress,
		dpPortHoldTime       Integer32,
		dpPortPeerPlatform  OCTET STRING,
		dpPortPeerPort  OCTET STRING
		}

	dpLocalPortId	OBJECT-TYPE
		SYNTAX			Integer32
		MAX-ACCESS		not-accessible
		STATUS			current
		DESCRIPTION		"Local-Port"
		::=  {  dpDevPortEntry  1  }

	dpPortPeerMac	OBJECT-TYPE
		SYNTAX			MacAddress
		MAX-ACCESS		read-only
		STATUS			current
		DESCRIPTION		"Device mac address."
		::=  {  dpDevPortEntry  2  }


	dpPortHoldTime	OBJECT-TYPE
		SYNTAX			Integer32
		MAX-ACCESS		read-only
		STATUS			current
		DESCRIPTION		"Zdp hold-Time "
		::=  {  dpDevPortEntry  3  }


	dpPortPeerPlatform	OBJECT-TYPE
		SYNTAX			OCTET STRING
		MAX-ACCESS		read-only
		STATUS			current
		DESCRIPTION		"The device type, running platform. "
		::=  {  dpDevPortEntry  4  }

	dpPortPeerPort	OBJECT-TYPE
		SYNTAX			OCTET STRING
		MAX-ACCESS		read-only
		STATUS			current
		DESCRIPTION		""
		::=  {  dpDevPortEntry  5  }

	dpDevTrunkTable	OBJECT-TYPE
		SYNTAX		SEQUENCE  OF  DpDevTrunkEntry
		MAX-ACCESS	not-accessible
		STATUS		current
		DESCRIPTION	"Description"
		::=  { neighborDiscovery  7 }

	dpDevTrunkEntry	OBJECT-TYPE
		SYNTAX		DpDevTrunkEntry
		MAX-ACCESS	not-accessible
		STATUS		current
		DESCRIPTION	"Row Description"
		INDEX		{  dpLocalTrunkId ,  dpTrunkPeerMac}
		::=  { dpDevTrunkTable 1 }

	DpDevTrunkEntry  ::=  SEQUENCE {
		dpLocalTrunkId    Integer32,
		dpTrunkPeerMac  MacAddress,
		dpTrunkHoldTime       Integer32,
		dpTrunkPeerPlatform  OCTET STRING,
		dpTrunkPeerTrunk  OCTET STRING
		}

	dpLocalTrunkId	OBJECT-TYPE
		SYNTAX			Integer32
		MAX-ACCESS		not-accessible
		STATUS			current
		DESCRIPTION		"Local-Trunk "
		::=  {  dpDevTrunkEntry  1  }

	dpTrunkPeerMac	OBJECT-TYPE
		SYNTAX			MacAddress
		MAX-ACCESS		read-only
		STATUS			current
		DESCRIPTION		"Device mac address."
		::=  {  dpDevTrunkEntry  2  }


	dpTrunkHoldTime	OBJECT-TYPE
		SYNTAX			Integer32
		MAX-ACCESS		read-only
		STATUS			current
		DESCRIPTION		"Zdp holdtime"
		::=  {  dpDevTrunkEntry  3  }


	dpTrunkPeerPlatform	OBJECT-TYPE
		SYNTAX			OCTET STRING
		MAX-ACCESS		read-only
		STATUS			current
		DESCRIPTION		"The device type, running platform. "
		::=  {  dpDevTrunkEntry  4  }

	dpTrunkPeerTrunk	OBJECT-TYPE
		SYNTAX			OCTET STRING
		MAX-ACCESS		read-only
		STATUS			current
		DESCRIPTION		""
		::=  {  dpDevTrunkEntry  5  }

	tpAdminStatus	OBJECT-TYPE
		SYNTAX			INTEGER  { enable ( 1 ) , disable ( 2 ) }
		MAX-ACCESS		read-write
		STATUS			current
		DESCRIPTION		"Description"
		::=  {  topologyCollect  1  }

	tpVlan	OBJECT-TYPE
		SYNTAX			Integer32  ( 1 .. 4094  )
		MAX-ACCESS		read-write
		STATUS			current
		DESCRIPTION		"The value of this item can't be changed while gmSwitchRole is commandSwitch"
		::=  {  topologyCollect  2  }

	tpHop	OBJECT-TYPE
		SYNTAX			Integer32  ( 1 .. 128  )
		MAX-ACCESS		read-write
		STATUS			current
		DESCRIPTION		"Description"
		::=  {  topologyCollect  3  }

	tpTimer	OBJECT-TYPE
		SYNTAX			Integer32  ( 0 .. 60  )
		MAX-ACCESS		read-write
		STATUS			current
		DESCRIPTION		"Description"
		::=  {  topologyCollect  4  }

	tpHopDelay	OBJECT-TYPE
		SYNTAX			Integer32  ( 1 .. 1000  )
		MAX-ACCESS		read-write
		STATUS			current
		DESCRIPTION		"Description"
		::=  {  topologyCollect  5  }

	tpPortDelay	OBJECT-TYPE
		SYNTAX			Integer32  ( 1 .. 100  )
		MAX-ACCESS		read-write
		STATUS			current
		DESCRIPTION		"Description"
		::=  {  topologyCollect  6  }

	tpStart	OBJECT-TYPE
		SYNTAX			INTEGER  { start ( 1 ) }
		MAX-ACCESS		read-write
		STATUS			current
		DESCRIPTION		"The value get from this item is insignificant.
		                Setting this item will start a topology collection process."
		::=  {  topologyCollect  7  }

	tpPortTable	OBJECT-TYPE
		SYNTAX		SEQUENCE  OF  TpPortEntry
		MAX-ACCESS	not-accessible
		STATUS		current
		DESCRIPTION	"Description"
		::=  { topologyCollect  8 }

	tpPortEntry	OBJECT-TYPE
		SYNTAX		TpPortEntry
		MAX-ACCESS	not-accessible
		STATUS		current
		DESCRIPTION	"Each entry contains port config for topology"
		INDEX		{  tpPortId  }
		::=  { tpPortTable 1 }

	TpPortEntry  ::=  SEQUENCE {
		tpPortId  Integer32,
		tpPortAdminStatus  INTEGER
		}


	tpPortId	OBJECT-TYPE
		SYNTAX			Integer32
		MAX-ACCESS		not-accessible
		STATUS			current
		DESCRIPTION		"The port id to index topology collection."
		::=  {  tpPortEntry  1  }


	tpPortAdminStatus	OBJECT-TYPE
		SYNTAX			INTEGER  { enable ( 1 ) , disable ( 2 ) }
		MAX-ACCESS		read-write
		STATUS			current
		DESCRIPTION		"Enable/disable topology collection on certain port"
		::=  {  tpPortEntry  2  }

	tpTrunkTable	OBJECT-TYPE
		SYNTAX		SEQUENCE  OF  TpTrunkEntry
		MAX-ACCESS	not-accessible
		STATUS		current
		DESCRIPTION	"Description"
		::=  { topologyCollect  9 }

	tpTrunkEntry	OBJECT-TYPE
		SYNTAX		TpTrunkEntry
		MAX-ACCESS	not-accessible
		STATUS		current
		DESCRIPTION	"Each row contains trunk config for topology"
		INDEX		{  tpTrunkId  }
		::=  { tpTrunkTable 1 }

	TpTrunkEntry  ::=  SEQUENCE {
		tpTrunkId  Integer32,
		tpTrunkAdminStatus  INTEGER
		}


	tpTrunkId	OBJECT-TYPE
		SYNTAX			Integer32
		MAX-ACCESS		not-accessible
		STATUS			current
		DESCRIPTION		"Trunk id."
		::=  {  tpTrunkEntry  1  }


	tpTrunkAdminStatus	OBJECT-TYPE
		SYNTAX			INTEGER  { enable ( 1 ) , disable ( 2 ) }
		MAX-ACCESS		read-write
		STATUS			current
		DESCRIPTION		"Enable/disable topology collection on certain trunk"
		::=  {  tpTrunkEntry  2  }

	tpDeviceTable	OBJECT-TYPE
		SYNTAX		SEQUENCE  OF  TpDeviceEntry
		MAX-ACCESS	not-accessible
		STATUS		current
		DESCRIPTION	"Device in the network topology."
		::=  { topologyCollect  10 }

	tpDeviceEntry	OBJECT-TYPE
		SYNTAX		TpDeviceEntry
		MAX-ACCESS	not-accessible
		STATUS		current
		DESCRIPTION	"Each row contains a device info that was collected"
		INDEX		{  deviceMac  }
		::=  { tpDeviceTable 1 }

	TpDeviceEntry  ::=  SEQUENCE {
		deviceMac  MacAddress,
		deviceId  Integer32,
		deviceIpAddr  IpAddress,
		deviceHop  Integer32,
		devicePlatform  OCTET STRING,
		deviceRole  INTEGER,
		devicePeerPort  OCTET STRING,
		deviceBelongedMac  MacAddress,
		deviceBelongedIpAddr  IpAddress
		}

	deviceMac	OBJECT-TYPE
		SYNTAX			MacAddress
		MAX-ACCESS		read-only
		STATUS			current
		DESCRIPTION		"Device mac address."
		::=  {  tpDeviceEntry  1  }


	deviceId	OBJECT-TYPE
		SYNTAX			Integer32  ( -2147483648 .. 2147483647  )
		MAX-ACCESS		read-only
		STATUS			current
		DESCRIPTION		"Device id."
		::=  {  tpDeviceEntry  2  }


	deviceIpAddr	OBJECT-TYPE
		SYNTAX			IpAddress
		MAX-ACCESS		read-only
		STATUS			current
		DESCRIPTION		"Device ipaddress"
		::=  {  tpDeviceEntry  3  }

	deviceHop	OBJECT-TYPE
		SYNTAX			Integer32
		MAX-ACCESS		read-only
		STATUS			current
		DESCRIPTION		"Device hop"
		::=  {  tpDeviceEntry  4  }


	devicePlatform	OBJECT-TYPE
		SYNTAX			OCTET STRING
		MAX-ACCESS		read-only
		STATUS			current
		DESCRIPTION		"The device type, running platform. "
		::=  {  tpDeviceEntry  5  }


	deviceRole	OBJECT-TYPE
		SYNTAX			INTEGER  { commandSwitch ( 1 ) , memberSwitch ( 2 ) , candidateSwitch ( 3 ) , independentSwitch ( 4 ) }
		MAX-ACCESS		read-write
		STATUS			current
		DESCRIPTION		"The value indicates the switch role in the topology,
		                But only command switch can set value of this item.
		                Furthermore, only memberSwitch ( 2 ) can be set which means
		                adding a device of the topology to the group."
		::=  {  tpDeviceEntry  6  }


	devicePeerPort	OBJECT-TYPE
		SYNTAX			OCTET STRING
		MAX-ACCESS		read-only
		STATUS			current
		DESCRIPTION		""
		::=  {  tpDeviceEntry  7  }


	deviceBelongedMac	OBJECT-TYPE
		SYNTAX			MacAddress
		MAX-ACCESS		read-only
		STATUS			current
		DESCRIPTION		"It indicates the command switch mac address of the group
		                which this device belonged to. If the device role is not
		                member switch, the item value is the device sysmac."
		::=  {  tpDeviceEntry  8  }

	deviceBelongedIpAddr	OBJECT-TYPE
		SYNTAX			IpAddress
		MAX-ACCESS		read-only
		STATUS			current
		DESCRIPTION		"It indicates the command switch ip address of the group
		                which this device belonged to. If the device role is not
		                member switch, the item value is 0."
		::=  {  tpDeviceEntry  9  }


	memberTable	OBJECT-TYPE
		SYNTAX		SEQUENCE  OF  MemberEntry
		MAX-ACCESS	not-accessible
		STATUS		current
		DESCRIPTION	"Only command switch can have a memberTable."
		::=  { memberManage  1 }

	memberEntry	OBJECT-TYPE
		SYNTAX		MemberEntry
		MAX-ACCESS	not-accessible
		STATUS		current
		DESCRIPTION	"Each row contains all of the info of a member of
		            a group which managed by this command switch"
		INDEX		{  memMac  }
		::=  { memberTable 1 }

	MemberEntry  ::=  SEQUENCE {
		memMac  MacAddress,
		memId  Integer32,
		memIpAddr  IpAddress,
		memMask  IpAddress,
		memStatus  INTEGER,
		memRole  INTEGER,
		snmpPortMap  Unsigned32,
		httpPortMap  Integer32,
		ftpPortMap  Integer32,
		tftpPortMap  Integer32,
		telnetPortMap  Integer32,
		sshPortMap  Integer32,
		memSaveConfig  INTEGER,
		memEraseConfig  INTEGER,
		memReboot  INTEGER
		}

	memMac	OBJECT-TYPE
		SYNTAX			MacAddress
		MAX-ACCESS		read-only
		STATUS			current
		DESCRIPTION		"Member macaddress "
		::=  {  memberEntry  1  }


	memId	OBJECT-TYPE
		SYNTAX			Integer32
		MAX-ACCESS		read-only
		STATUS			current
		DESCRIPTION		"Member id"
		::=  {  memberEntry  2  }


	memIpAddr	OBJECT-TYPE
		SYNTAX			IpAddress
		MAX-ACCESS		read-only
		STATUS			current
		DESCRIPTION		"Member ipaddress "
		::=  {  memberEntry  3  }


	memMask	OBJECT-TYPE
		SYNTAX			IpAddress
		MAX-ACCESS		read-only
		STATUS			current
		DESCRIPTION		"Member netmask"
		::=  {  memberEntry  4  }


	memStatus	OBJECT-TYPE
		SYNTAX			INTEGER  { up ( 1 ) , down ( 2 ) }
		MAX-ACCESS		read-only
		STATUS			current
		DESCRIPTION		"Member status "
		::=  {  memberEntry  5  }


	memRole	OBJECT-TYPE
		SYNTAX			INTEGER  { memberSwitch ( 1 ) , candidateSwitch ( 2 ) }
		MAX-ACCESS		read-write
		STATUS			current
		DESCRIPTION		"When set memRole as candidateSwitch(2),
		                this member will be delete from the group"
		::=  {  memberEntry  6  }


	snmpPortMap	OBJECT-TYPE
		SYNTAX			Unsigned32
		MAX-ACCESS		read-only
		STATUS			current
		DESCRIPTION		"Well-known port mapping to private port by memId."
		::=  {  memberEntry  7  }


	httpPortMap	OBJECT-TYPE
		SYNTAX			Integer32  ( -2147483648 .. 2147483647  )
		MAX-ACCESS		read-only
		STATUS			current
		DESCRIPTION		"Column Description"
		::=  {  memberEntry  8  }


	ftpPortMap	OBJECT-TYPE
		SYNTAX			Integer32  ( -2147483648 .. 2147483647  )
		MAX-ACCESS		read-only
		STATUS			current
		DESCRIPTION		"Description"
		::=  {  memberEntry  9  }


	tftpPortMap	OBJECT-TYPE
		SYNTAX			Integer32  ( -2147483648 .. 2147483647  )
		MAX-ACCESS		read-only
		STATUS			current
		DESCRIPTION		"Description"
		::=  {  memberEntry  10  }


	telnetPortMap	OBJECT-TYPE
		SYNTAX			Integer32
		MAX-ACCESS		read-only
		STATUS			current
		DESCRIPTION		"Description"
		::=  {  memberEntry  11  }


	sshPortMap	OBJECT-TYPE
		SYNTAX			Integer32
		MAX-ACCESS		read-only
		STATUS			current
		DESCRIPTION		"Description"
		::=  {  memberEntry  12  }

	memSaveConfig	OBJECT-TYPE
		SYNTAX			INTEGER  { yes ( 1 ) , no ( 2 ) }
		MAX-ACCESS		read-write
		STATUS			current
		DESCRIPTION		"Save the member switch's running-config information or not. "
		::=  {  memberEntry  13  }

	memEraseConfig	OBJECT-TYPE
		SYNTAX			INTEGER  { yes ( 1 ) , no ( 2 ) }
		MAX-ACCESS		read-write
		STATUS			current
		DESCRIPTION		"Erase the member switch's running-config information or not.
		                 The operation will be likely to cut the relation of member switch
		                 and command switch."
		::=  {  memberEntry  14  }

	memReboot	OBJECT-TYPE
		SYNTAX			INTEGER  { yes ( 1 ) , no ( 2 ) }
		MAX-ACCESS		read-write
		STATUS			current
		DESCRIPTION		"Reboot the member switch,The operation will be likely to lose the
		                 relation of member switch and command switch."
		::=  {  memberEntry  15  }

	gmTopologyChange	NOTIFICATION-TYPE
		STATUS			current
		DESCRIPTION		"This trap sended by command switch to notify topology change."
		::=  {  gmEnterpriseTrap  1  }

	gmMemberUpDown	NOTIFICATION-TYPE
		OBJECTS			{ memMac, memId, memIpAddr, memStatus }
		STATUS			current
		DESCRIPTION		"The trap indicates nms that member switch transfer between connect or disconnect with command switch."
		::=  {  gmEnterpriseTrap  2  }

END
