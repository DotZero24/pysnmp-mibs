ZTE-DSL-CPE-MIB DEFINITIONS ::= BEGIN

        IMPORTS
            ifIndex
                FROM IF-MIB
			MODULE-IDENTITY, OBJECT-TYPE, TimeTicks, Counter32, Gauge32, enterprises, IpAddress
				FROM SNMPv2-SMI;


    zte OBJECT IDENTIFIER ::= { enterprises 3092 }
	zxDsl	OBJECT IDENTIFIER ::= { zte 2 }
	zxDslam OBJECT IDENTIFIER ::= { zxDsl 3 }

        zxcpeConifgInfoTable OBJECT-TYPE

			SYNTAX SEQUENCE OF zxcpeConifgInfoEntry
			MAX-ACCESS not-accessible
			STATUS current
			DESCRIPTION
				"
				CPE configuration table
				"
			::= { zxDslam  26 }

		zxcpeConifgInfoEntry OBJECT-TYPE
			SYNTAX zxcpeConifgInfoEntry
			MAX-ACCESS not-accessible
			STATUS current
			DESCRIPTION
				"
				CPE configuration entry
				"
			INDEX { ifIndex}
			::= { zxcpeConifgInfoTable 1 }

		zxcpeConifgInfoEntry ::=
			SEQUENCE {
				zxcpeAutoCfgAdminStatus
					INTEGER,
				zxcpePvcAdminStatus
					INTEGER,
				zxcpePvcVpi
					INTEGER,
				zxcpePvcVci
					INTEGER,
				zxcpeSysInfoConfigId
					DisplayString
			 }

          	zxcpeAutoCfgAdminStatus OBJECT-TYPE
	     		SYNTAX INTEGER {
				enable(1),
				disable(2)
				}
	     		MAX-ACCESS read-write
	     		STATUS current
	     		DESCRIPTION
		     	"
		 	Auto configuration administatus of CPE"
                         DEFVAL { disable }
	     		::= { zxcpeConifgInfoEntry 1 }

		zxcpePvcAdminStatus OBJECT-TYPE
			SYNTAX INTEGER {
				create(1),
				delete(2)
				}
			MAX-ACCESS read-write
			STATUS current
			DESCRIPTION
				"
				CPE base PVC administatus
				"
                        DEFVAL { delete }
			::= { zxcpeConifgInfoEntry 2 }

		zxcpePvcVpi OBJECT-TYPE
			SYNTAX INTEGER
			MAX-ACCESS read-write
			STATUS current
			DESCRIPTION
				"
				CPE PVC VPI
				"
			::= { zxcpeConifgInfoEntry 3 }

		zxcpePvcVci OBJECT-TYPE
			SYNTAX INTEGER
			MAX-ACCESS read-write
			STATUS current
			DESCRIPTION
				"
				CPE PVC VCI
				"
			::= { zxcpeConifgInfoEntry 4 }

		zxcpeSysInfoConfigId OBJECT-TYPE
			SYNTAX DisplayString (SIZE (0..16))
			MAX-ACCESS read-only
			STATUS current
			DESCRIPTION
				"
				CPE configuration id"
			::= { zxcpeConifgInfoEntry 5 }


        zxcpeTrapInfoTable OBJECT-TYPE
			SYNTAX SEQUENCE OF zxcpeTrapInfoEntry
			MAX-ACCESS not-accessible
			STATUS current
			DESCRIPTION
				"
				CPE trap infomation table
				"
			::= { zxDslam  27 }

		zxcpeTrapInfoEntry  OBJECT-TYPE
			SYNTAX zxcpeTrapInfoEntry
			MAX-ACCESS not-accessible
			STATUS current
			DESCRIPTION
				"
				CPE trap infomation entry
				"
			INDEX { ifIndex}
			::= { zxcpeTrapInfoTable 1 }

		zxcpeTrapInfoEntry  ::=
			SEQUENCE {
				zxcpeAdministrableStatus
					INTEGER,
				zxcpeAutoCfgOperStatus
					INTEGER,
				zxcpeSysInfoFirmwareVersion
					DisplayString,
				zxcpeSysInfoSystemVersion
					DisplayString,
				zxcpeSysInfoProductId
					DisplayString,
				zxcpeSysInfoVendorId
					DisplayString,
				zxcpeSysInfoManufacturerOui
					DisplayString,
				zxcpeSysInfoWorkMode
					INTEGER,
			    zxcpeSysInfoSerialNumber
			    	DisplayString,
				zxcpeSysInfoMibVersion
					DisplayString
			 }

          	zxcpeAdministrableStatus OBJECT-TYPE
	     		SYNTAX INTEGER {
				up(1),
				down(2)
				}
	     		MAX-ACCESS read-only
	     		STATUS current
	     		DESCRIPTION
		     	"
		 	status of CPE"
                        DEFVAL { down }
	     		::= { zxcpeTrapInfoEntry  1 }

		zxcpeAutoCfgOperStatus OBJECT-TYPE
			SYNTAX INTEGER {
				yes(1),
				no(2),
				timeout(3)
				}
			MAX-ACCESS read-only
			STATUS current
			DESCRIPTION
				"
				CPE auto configuration status
				"
                        DEFVAL { no }
			::= { zxcpeTrapInfoEntry  2 }

		zxcpeSysInfoFirmwareVersion OBJECT-TYPE
			SYNTAX DisplayString (SIZE (0..16))
			MAX-ACCESS read-only
			STATUS current
			DESCRIPTION
				"
				CPE firmware vresion
				"
			::= { zxcpeTrapInfoEntry  3 }

		zxcpeSysInfoSystemVersion OBJECT-TYPE
			SYNTAX DisplayString (SIZE (0..16))
			MAX-ACCESS read-only
			STATUS current
			DESCRIPTION
				"
				CPE system vresion
				"
			::= { zxcpeTrapInfoEntry  4 }

		zxcpeSysInfoProductId OBJECT-TYPE
			SYNTAX  DisplayString (SIZE (0..16))
			MAX-ACCESS read-only
			STATUS current
			DESCRIPTION
				"
				CPE product id"
			::= { zxcpeTrapInfoEntry  5 }

		zxcpeSysInfoVendorId OBJECT-TYPE
			SYNTAX DisplayString (SIZE (0..16))
			MAX-ACCESS read-only
			STATUS current
			DESCRIPTION
				"
				CPE vendor id
				"
			::= { zxcpeTrapInfoEntry  6 }

		zxcpeSysInfoManufacturerOui OBJECT-TYPE
			SYNTAX DisplayString (SIZE (0..3))
			MAX-ACCESS read-only
			STATUS current
			DESCRIPTION
				"
				CPE Manufacturer Oui
				"
			::= { zxcpeTrapInfoEntry  7 }

		zxcpeSysInfoWorkMode OBJECT-TYPE
			SYNTAX INTEGER {
				bridge(1),
				router(2)
				}
			MAX-ACCESS read-only
			STATUS current
			DESCRIPTION
				"
				CPE Work Mode
				"
			::= { zxcpeTrapInfoEntry  8 }

		zxcpeSysInfoSerialNumber OBJECT-TYPE
			SYNTAX OCTET STRING (SIZE (0..32))
			MAX-ACCESS read-only
			STATUS current
			DESCRIPTION "CPE's physical number "
			::= { zxcpeTrapInfoEntry 9 }

		zxcpeSysInfoMibVersion OBJECT-TYPE
			SYNTAX DisplayString (SIZE (0..8))
			MAX-ACCESS read-only
			STATUS current
			DESCRIPTION
				"
				CPE Mib Version"
			::= { zxcpeTrapInfoEntry  10 }

    END
