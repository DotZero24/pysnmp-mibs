-- File Name : Es2952Mib.mib
-- Date      : Thu Apr 26 14:58:11 CST 2006
-- Author    : AdventNet Agent Toolkit Java Edition - MIB Editor 6



Es2952-MIB	DEFINITIONS ::= BEGIN
	IMPORTS
		TEXTUAL-CONVENTION
			FROM SNMPv2-TC
		OBJECT-TYPE, Integer32, Unsigned32, IpAddress, enterprises
			FROM SNMPv2-SMI;

-- TEXTUAL-CONVENTIONS --
	PortList ::= TEXTUAL-CONVENTION
		DISPLAY-HINT	""
		STATUS			current
		DESCRIPTION
			"Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
		SYNTAX 			OCTET STRING

	MacAddress ::= TEXTUAL-CONVENTION
		DISPLAY-HINT	""
		STATUS			current
		DESCRIPTION
			"Represents an 802 MAC address represented in the
             `canonical' order defined by IEEE 802.1a, i.e., as if it
             were transmitted least significant bit first, even though
             802.5 (in contrast to other 802.x protocols) requires MAC
             addresses to be transmitted most significant bit first."
		SYNTAX 			OCTET STRING

	DisplayString ::= OCTET STRING
    --  This data type is used to model textual information taken
    --  from the NVT ASCII character set.  By convention, objects
    --  with this syntax are declared as having
    --  SIZE (0..255)

    zte	OBJECT IDENTIFIER
		::=  {  enterprises  3902  }

	ethernetSwitch	OBJECT IDENTIFIER
		::=  {  zte  15  }

	layer2Switch	OBJECT IDENTIFIER
		::=  {  ethernetSwitch  2  }

	series2952Switch	OBJECT IDENTIFIER
		::=  {  layer2Switch  11  }

	switchSystem	OBJECT IDENTIFIER
		::=  {  series2952Switch  1  }

	port	OBJECT IDENTIFIER
		::=  {  series2952Switch  2  }

	vlan	OBJECT IDENTIFIER
		::=  {  series2952Switch  3  }

	mirror	OBJECT IDENTIFIER
		::=  {  series2952Switch  4  }

	qos	OBJECT IDENTIFIER
		::=  {  series2952Switch  5  }

	pvlan	OBJECT IDENTIFIER
		::=  {  series2952Switch  6  }

	lacp	OBJECT IDENTIFIER
		::=  {  series2952Switch  7  }

	layer3	OBJECT IDENTIFIER
		::=  {  series2952Switch  8  }

	loopDetect	OBJECT IDENTIFIER
		::=  {  series2952Switch  9  }

	vlanTranslation	OBJECT IDENTIFIER
		::=  {  series2952Switch  10  }

	stp	OBJECT IDENTIFIER
		::=  {  series2952Switch  11  }

        vct	OBJECT IDENTIFIER
		::=  {  series2952Switch  12  }

        syslog	OBJECT IDENTIFIER
		::=  {  series2952Switch  13  }

        ntp  	OBJECT IDENTIFIER
		::=  {  series2952Switch  14  }

	loginUser	OBJECT IDENTIFIER
		::=  {  series2952Switch  15  }

	snmpConfig  OBJECT IDENTIFIER
		::=  {  series2952Switch  16  }

	acl      	OBJECT IDENTIFIER
		::=  {  series2952Switch  17  }

	fdb      	OBJECT IDENTIFIER
		::=  {  series2952Switch  18  }

	p8021xRelay	OBJECT IDENTIFIER
		::=  {  series2952Switch  19  }

	igmpSnooping	OBJECT IDENTIFIER
		::=  {  series2952Switch  20  }

        epon    	OBJECT IDENTIFIER
		::=  {  series2952Switch  21  }

        ethernetOam	OBJECT IDENTIFIER
		::=  {  series2952Switch  22  }

	opticalInformation OBJECT IDENTIFIER
		::=  {  series2952Switch  23  }


	cpuLoad5s	OBJECT-TYPE
		SYNTAX			Integer32
		MAX-ACCESS		read-only
		STATUS			current
		DESCRIPTION		"The Avg. Value of CPU Load for 5 seconds described by percent."
		::=  {  switchSystem  1  }

	cpuLoad30s	OBJECT-TYPE
		SYNTAX			Integer32
		MAX-ACCESS		read-only
		STATUS			current
		DESCRIPTION		"The Avg. Value of CPU Load for 30 seconds described by percent."
		::=  {  switchSystem  2  }

	cpuLoad2m	OBJECT-TYPE
		SYNTAX			Integer32
		MAX-ACCESS		read-only
		STATUS			current
		DESCRIPTION		"The Avg. Value of CPU Load for 2 minutes described by percent."
		::=  {  switchSystem  3  }

	maxCpuLoad	OBJECT-TYPE
		SYNTAX			Integer32
		MAX-ACCESS		read-only
		STATUS			current
		DESCRIPTION		"The cpu max utility described by percent."
		::=  {  switchSystem  4  }

	memUtilityRatio	OBJECT-TYPE
		SYNTAX			Integer32
		MAX-ACCESS		read-only
		STATUS			current
		DESCRIPTION		"The utility ratio of system memery described by percent."
		::=  {  switchSystem  5  }

	switchType	OBJECT-TYPE
		SYNTAX			OCTET STRING
		MAX-ACCESS		read-only
		STATUS			current
		DESCRIPTION		"The switch type."
		::=  {  switchSystem  6  }

	switchMac	OBJECT-TYPE
		SYNTAX			MacAddress
		MAX-ACCESS		read-only
		STATUS			current
		DESCRIPTION		"The mac address of device."
		::=  {  switchSystem  7  }

	reboot	OBJECT-TYPE
		SYNTAX			INTEGER  { yes ( 1 ) , no ( 2 ) }
		MAX-ACCESS		read-write
		STATUS			current
		DESCRIPTION		"reboot system or not"
		::=  {  switchSystem  8  }

	saveConfig	OBJECT-TYPE
		SYNTAX			INTEGER  { yes ( 1 ) , no ( 2 ) }
		MAX-ACCESS		read-write
		STATUS			current
		DESCRIPTION		"save running-config information or not"
		::=  {  switchSystem  9  }

	sysDateTime	OBJECT-TYPE
		SYNTAX			OCTET STRING  ( SIZE ( 0 .. 20  ) )
		MAX-ACCESS		read-write
		STATUS			current
		DESCRIPTION		"System current date and time.
		                 The format is YYYYMMDD-hh:mm:ss,such as 20060424-09:30:20."
		::=  {  switchSystem  10  }

	portNumber	OBJECT-TYPE
		SYNTAX			Unsigned32
		MAX-ACCESS		read-only
		STATUS			current
		DESCRIPTION		"The number of network interfaces (regardless of
                        their current state) present on this system."
		::=  {  port  1  }

	portTable	OBJECT-TYPE
		SYNTAX		SEQUENCE  OF  PortEntry
		MAX-ACCESS	not-accessible
		STATUS		current
		DESCRIPTION	" A list of port entries. The number of
                    entries is given by the value of portNumber. "
		::=  { port  4 }

	portEntry	OBJECT-TYPE
		SYNTAX		PortEntry
		MAX-ACCESS	not-accessible
		STATUS		current
		DESCRIPTION	"A port entry containing objects at the
                    subnetwork layer and below for a particular
                    port. "
		INDEX		{  portId  }
		::=  { portTable 1 }

	PortEntry  ::=  SEQUENCE {
		portId  Unsigned32,
		portName  OCTET STRING,
		portDescr  OCTET STRING,
		portAdminStatus  INTEGER,
		portOperStatus  INTEGER,
		portAdminWorkMode  INTEGER,
		portOperDuplex  INTEGER,
		portOperSpeed  INTEGER,
		portPvid  Integer32,
		portFlowControl  INTEGER,
                portVlanMode  OCTET STRING,
		portSecurity  INTEGER,
		portPriority  Integer32,
		portMulticast  INTEGER,
		portMediaType  INTEGER,
		isPortInTrunk  INTEGER,
		portLoopdetectStatus  OCTET STRING,
		dynamicMacMaxCount  Integer32
		}


	portId	OBJECT-TYPE
		SYNTAX			Unsigned32
		MAX-ACCESS		read-only
		STATUS			current
		DESCRIPTION		"The port id"
		::=  {  portEntry  1  }


	portName	OBJECT-TYPE
		SYNTAX			OCTET STRING  ( SIZE ( 0 .. 200  ) )
		MAX-ACCESS		read-write
		STATUS			current
		DESCRIPTION		"Port name(maxsize:200,number 1~255 are reserved)."
		::=  {  portEntry  2  }


	portDescr	OBJECT-TYPE
		SYNTAX			OCTET STRING  ( SIZE ( 0 .. 200  ) )
		MAX-ACCESS		read-write
		STATUS			current
		DESCRIPTION		"Description of a port"
		::=  {  portEntry  3  }


	portAdminStatus	OBJECT-TYPE
		SYNTAX			INTEGER  { enable ( 1 ) , disable ( 2 ) }
		MAX-ACCESS		read-write
		STATUS			current
		DESCRIPTION		"The desired state of the port."
		::=  {  portEntry  4  }


	portOperStatus	OBJECT-TYPE
		SYNTAX			INTEGER  { linkUp ( 1 ) , linkDown ( 2 ) }
		MAX-ACCESS		read-only
		STATUS			current
		DESCRIPTION		"The current operational state of the port."
		::=  {  portEntry  5  }


	portAdminWorkMode	OBJECT-TYPE
		SYNTAX			INTEGER  {auto-10M(1),auto-100M(2),auto-1000M(3),auto-auto(4),half-10M(5),half-100M(6),half-1000M(7),half-auto(8),full-10M(9),full-100M(10),full-1000M(11),full-auto(12)}
		MAX-ACCESS		read-write
		STATUS			current
		DESCRIPTION		"This item config port working mode."
		::=  {  portEntry  6  }


	portOperDuplex	OBJECT-TYPE
		SYNTAX			INTEGER  { full ( 1 ) , half ( 2 ) }
		MAX-ACCESS		read-only
		STATUS			current
		DESCRIPTION		"The actual port duplex mode"
		::=  {  portEntry  7  }


	portOperSpeed	OBJECT-TYPE
		SYNTAX			INTEGER  { speed-10M ( 1 ) , speed-100M ( 2 ) , speed-1000M ( 3 ) }
		MAX-ACCESS		read-only
		STATUS			current
		DESCRIPTION		"The actual port speed"
		::=  {  portEntry  8  }


	portPvid	OBJECT-TYPE
		SYNTAX			Integer32  ( 1 .. 4094  )
		MAX-ACCESS		read-write
		STATUS			current
		DESCRIPTION		"Port default vlan id"
		::=  {  portEntry  9  }


	portFlowControl	OBJECT-TYPE
		SYNTAX			INTEGER  { enable ( 1 ) , disable ( 2 ) }
		MAX-ACCESS		read-write
		STATUS			current
		DESCRIPTION		"Port's flowcontrol"
		::=  {  portEntry  10  }


	portVlanMode	OBJECT-TYPE
		SYNTAX			OCTET STRING
		MAX-ACCESS		read-write
		STATUS			current
		DESCRIPTION		"Port's vlan-mode .(only valid in the pon port) .
The first character means:
1 : port's vlan-mode for transparent-mode .
2 : port's vlan-mode for translation-mode .
3 : port's vlan-mode for tag-mode .  when being 3,the following characters have the format
 of 3-100, which means the port's vlan-mode is tag-mode and tag value is 100(DefaultVlanId) . "
		::=  {  portEntry  11  }


	portSecurity	OBJECT-TYPE
		SYNTAX			INTEGER  { enable ( 1 ) , disable ( 2 ) }
		MAX-ACCESS		read-write
		STATUS			current
		DESCRIPTION		"Port mac-address learning. PortSecurity enabled means forbid
		                this port learning mac-address, whereas permit mac-address
		                self-learning."
		::=  {  portEntry  12  }


	portPriority	OBJECT-TYPE
		SYNTAX			Integer32  ( 0 .. 7  )
		MAX-ACCESS		read-write
		STATUS			current
		DESCRIPTION		"Port's priority"
		::=  {  portEntry  13  }


	portMulticast	OBJECT-TYPE
		SYNTAX			INTEGER  { forward ( 1 ) , discard ( 2 ) }
		MAX-ACCESS		read-write
		STATUS			current
		DESCRIPTION		"Port forward or discard multicast packet."
		::=  {  portEntry  14  }


	portMediaType	OBJECT-TYPE
		SYNTAX			INTEGER  { mt100BaseT ( 1 ) , mt100BaseFX ( 2 ) , mt1000BaseX ( 3 ) , mt1000BaseT ( 4 ) , unKnown ( 5 ) }
		MAX-ACCESS		read-only
		STATUS			current
		DESCRIPTION		"Media type of the port."
		::=  {  portEntry  15  }


	isPortInTrunk	OBJECT-TYPE
		SYNTAX			INTEGER  { true ( 1 ) , false ( 2 ) }
		MAX-ACCESS		read-only
		STATUS			current
		DESCRIPTION		"This item indicates whether a port has been added to a trunk or not."
		::=  {  portEntry  16  }

        portLoopdetectStatus	OBJECT-TYPE
		SYNTAX			OCTET STRING   ( SIZE ( 0 .. 200  ) )
		MAX-ACCESS		read-only
		STATUS			current
		DESCRIPTION		"Loopdetect status of the port.The first character means:
		                 0 : port_notInTrunk_down
		                 1 : port_notInTrunk_up_loopdetDisable
		                 2 : port_notInTrunk_up_loopdetEnable_noLoop
		                 3 : port_notInTrunk_up_loopdetEnable_Loop_noBlock
		                 4 : port_notInTrunk_up_loopdetEnable_Loop_Block
		                 5 : port_InTrunk_down
		                 6 : port_InTrunk_up_loopdetDisable
		                 7 : port_InTrunk_up_loopdetEnable_noLoop
		                 8 : port_InTrunk_up_loopdetEnable_Loop_noBlock
		                 9 : port_InTrunk_up_loopdetEnable_Loop_Block
		                 when being 4 or 9,the following characters have the format
		                 of 4-3 which means the port is looped and blocked in vlan 3."
		::=  {  portEntry  17 }

	dynamicMacMaxCount	OBJECT-TYPE
		SYNTAX			Integer32  ( 0 .. 100  )
		MAX-ACCESS		read-write
		STATUS			current
		DESCRIPTION		"Port's sum of dynamic macaddress."
		::=  {  portEntry  18  }

--	portAclAdminStatus	OBJECT-TYPE
--		SYNTAX			OCTET STRING   ( SIZE ( 0 .. 20  ) )
--		MAX-ACCESS		read-write
--		STATUS			current
--		DESCRIPTION		"The desired state of the port in acl number .
--		                 The format is X-Y;
--		                 X: 1 means enable , 2 means disable ;
--		                 Y: acl number. The scope is 0-349."
--		::=  {  portEntry  19  }


	dynamicMacExceedTrap	NOTIFICATION-TYPE
		OBJECTS			{ portId, dynamicMacMaxCount}
		STATUS			current
		DESCRIPTION		"The trap indicates dynamic macaddress exceed the limit set for the port."
		::=  {  port  5  }

	maxVlanId	OBJECT-TYPE
		SYNTAX			Unsigned32
		MAX-ACCESS		read-only
		STATUS			current
		DESCRIPTION		"Max vlan id."
		::=  {  vlan  1  }

	maxSupportedVlans	OBJECT-TYPE
		SYNTAX			Unsigned32
		MAX-ACCESS		read-only
		STATUS			current
		DESCRIPTION		"The maximum number of IEEE 802.1Q VLANs that this
                        device supports."
		::=  {  vlan  2  }

	vlanTable	OBJECT-TYPE
		SYNTAX		SEQUENCE  OF  VlanEntry
		MAX-ACCESS	not-accessible
		STATUS		current
		DESCRIPTION	"A table containing static config information for
                    each VLAN configured into the device by (local or
                    network) management. All entries are permanent and will
                    be restored after the device is reset. "
		::=  { vlan  3 }

	vlanEntry	OBJECT-TYPE
		SYNTAX		VlanEntry
		MAX-ACCESS	not-accessible
		STATUS		current
		DESCRIPTION	"Each entry contains all config of a vlan."
		INDEX		{  vlanId  }
		::=  { vlanTable 1 }

	VlanEntry  ::=  SEQUENCE {
		vlanId  Integer32,
--		vlanFdbId  Integer32,
		vlanUntaggedPorts  PortList,
		vlanTaggedPorts  PortList,
		vlanName  OCTET STRING,
		vlanAdminStatus  INTEGER,
		vlanUntaggedTrunks  PortList,
		vlanTaggedTrunks  PortList
--		vlanTaggedTrunks  PortList,
--		vlanAclAdminStatus OCTET STRING
		}


	vlanId	OBJECT-TYPE
		SYNTAX			Integer32  ( 1 .. 4094  )
		MAX-ACCESS		not-accessible
		STATUS			current
		DESCRIPTION		"Vlan id"
		::=  {  vlanEntry  1  }


--	vlanFdbId	OBJECT-TYPE
--		SYNTAX			Integer32  ( 1 .. 256  )
--		MAX-ACCESS		read-write
--		STATUS			current
--		DESCRIPTION		"The Filtering Database id used by this vlan."
--		::=  {  vlanEntry  2  }


	vlanUntaggedPorts	OBJECT-TYPE
		SYNTAX			PortList
		MAX-ACCESS		read-write
		STATUS			current
		DESCRIPTION		"Untagged ports in this vlan."
		::=  {  vlanEntry  3  }


	vlanTaggedPorts	OBJECT-TYPE
		SYNTAX			PortList
		MAX-ACCESS		read-write
		STATUS			current
		DESCRIPTION		"Tagged ports in this vlan."
		::=  {  vlanEntry  4  }

	vlanName	OBJECT-TYPE
		SYNTAX			OCTET STRING  ( SIZE ( 0 .. 64  ) )
		MAX-ACCESS		read-write
		STATUS			current
		DESCRIPTION		"Descriptive name of the vlan."
		::=  {  vlanEntry  5  }


	vlanAdminStatus	OBJECT-TYPE
		SYNTAX			INTEGER  { enable ( 1 ) , disable ( 2 ) }
		MAX-ACCESS		read-write
		STATUS			current
		DESCRIPTION		"The desired state of the vlan."
		::=  {  vlanEntry  6  }


	vlanUntaggedTrunks	OBJECT-TYPE
		SYNTAX			PortList
		MAX-ACCESS		read-write
		STATUS			current
		DESCRIPTION		"Untagged trunk in the vlan"
		::=  {  vlanEntry  7  }


	vlanTaggedTrunks	OBJECT-TYPE
		SYNTAX			PortList
		MAX-ACCESS		read-write
		STATUS			current
		DESCRIPTION		"Tagged trunks in the vlan"
		::=  {  vlanEntry  8  }

--	vlanAclAdminStatus	OBJECT-TYPE
--		SYNTAX			OCTET STRING   ( SIZE ( 0 .. 20  ) )
--		MAX-ACCESS		read-write
--		STATUS			current
--		DESCRIPTION		"The desired state of the vlan in acl number .
--		                 The format is X-Y;
--		                 X: 1 means enable , 2 means disable ;
--		                 Y: acl number. The scope is 0-349."
--		::=  {  vlanEntry  9  }

	vlanAssistantTable	OBJECT-TYPE
		SYNTAX		SEQUENCE  OF  VlanAssistantEntry
		MAX-ACCESS	not-accessible
		STATUS		current
		DESCRIPTION	"Vlan in this table means that vlan is enabled
		            or has a descriptive name or contains ports/trunks."
		::=  { vlan  4 }

	vlanAssistantEntry	OBJECT-TYPE
		SYNTAX		VlanAssistantEntry
		MAX-ACCESS	not-accessible
		STATUS		current
		DESCRIPTION	"Row Description"
		INDEX		{  assVlanId  }
		::=  { vlanAssistantTable 1 }

	VlanAssistantEntry  ::=  SEQUENCE {
		assVlanId  Integer32
		}


	assVlanId	OBJECT-TYPE
		SYNTAX			Integer32
		MAX-ACCESS		read-only
		STATUS			current
		DESCRIPTION		"Vlan id"
		::=  {  vlanAssistantEntry  1  }

	sourcePortsIngress	OBJECT-TYPE
		SYNTAX			PortList
		MAX-ACCESS		read-write
		STATUS			current
		DESCRIPTION		"Mirroring source ports for ingress"
		::=  {  mirror  1  }

	sourcePortsEgress	OBJECT-TYPE
		SYNTAX			PortList
		MAX-ACCESS		read-write
		STATUS			current
		DESCRIPTION		"Mirroring source ports for egress"
		::=  {  mirror  2  }

	desPortIngress	OBJECT-TYPE
		SYNTAX			Unsigned32
		MAX-ACCESS		read-write
		STATUS			current
		DESCRIPTION		"Mirroring destination port for ingress. Each device has only one ."
		::=  {  mirror  3  }

	desPortEgress	OBJECT-TYPE
		SYNTAX			Unsigned32
		MAX-ACCESS		read-write
		STATUS			current
		DESCRIPTION		"Mirroring destination port for egress. Each device has only one ."
		::=  {  mirror  4  }

	--
	queueScheduleWeight	OBJECT-TYPE
		SYNTAX			OCTET STRING   ( SIZE ( 0 .. 20  ) )
		MAX-ACCESS		read-write
		STATUS			current
		DESCRIPTION		"The item is only valid for fePorts.
		                 The format is W0-W1-W2-W3.Each takes the value of 1-32.
		                 For Example : 2-3-4-5
		                 means queue0-weight :2;
		                       queue1-weight :3;
		                       queue2-weight :4;
		                       queue3-weight :5."
		::=  {  qos  1  }

	queueScheduleMode0	OBJECT-TYPE
		SYNTAX			OCTET STRING   ( SIZE ( 0 .. 20  ) )
		MAX-ACCESS		read-only
		STATUS			current
		DESCRIPTION		"The item is only valid for fePorts.
		                 The format is W0-W1-W2-W3.
						 Each takes the value of 1-32, which means wrr mode;
						 or 0,which means sp mode.
		                 For Example : 1-2-4-8
		                 means queue0-weight :1;
		                       queue1-weight :2;
		                       queue2-weight :4;
		                       queue3-weight :8."
		::=  {  qos  2  }

	queueScheduleMode1	OBJECT-TYPE
		SYNTAX			OCTET STRING   ( SIZE ( 0 .. 20  ) )
		MAX-ACCESS		read-only
		STATUS			current
		DESCRIPTION		"The item is only valid for fePorts.
		                 The format is W0-W1-W2-W3.
						 Each takes the value of 1-32, which means wrr mode;
						 or 0,which means sp mode.
		                 For Example : 0-0-0-0
		                 means sp mode is used in queue schedule mode 1."
		::=  {  qos  3  }

	queueScheduleMode2	OBJECT-TYPE
		SYNTAX			OCTET STRING   ( SIZE ( 0 .. 20  ) )
		MAX-ACCESS		read-only
		STATUS			current
		DESCRIPTION		"The item is only valid for fePorts.
		                 The format is W0-W1-W2-W3.
						 Each takes the value of 1-32, which means wrr mode;
						 or 0,which means sp mode.
		                 For Example : 1-2-4-0
		                 means queue0-weight :1;
		                       queue1-weight :2;
		                       queue2-weight :4;
		                       queue3-weight :sp mode."
		::=  {  qos  4  }

	queueScheduleMode3	OBJECT-TYPE
		SYNTAX			OCTET STRING   ( SIZE ( 0 .. 20  ) )
		MAX-ACCESS		read-only
		STATUS			current
		DESCRIPTION		"The item is only valid for fePorts.
		                 The format is W0-W1-W2-W3.
						 Each takes the value of 1-32, which means wrr mode;
						 or 0,which means sp mode.
		                 For Example : 1-2-0-0
		                 means queue0-weight :1;
		                       queue1-weight :2;
		                       queue2-weight :sp mode;
		                       queue3-weight :sp mode."
		::=  {  qos  5  }

	qosPrimapUsrToTraffic	OBJECT-TYPE
		SYNTAX			OCTET STRING
		MAX-ACCESS		read-write
		STATUS			current
		DESCRIPTION		"For fePort,qos priority-map includes user-priority to traffic-class.
The format of this item is array of  eight  traffic-class  values corresponding to 0-7 user-priority.
Each   traffic-class vaule is between 0 and 3.
For example:set 12301321 means remappingtag   traffic-class
0                              1
1                              2
2                              3
3                              0
4                              1
5                              3
6                              2
7                              1"
		::=  {  qos  6  }

	qosPolicerTable	OBJECT-TYPE
		SYNTAX		SEQUENCE  OF  QosPolicerEntry
		MAX-ACCESS	not-accessible
		STATUS		current
		DESCRIPTION	"Description"
		::=  { qos  7 }

	qosPolicerEntry	OBJECT-TYPE
		SYNTAX		QosPolicerEntry
		MAX-ACCESS	not-accessible
		STATUS		current
		DESCRIPTION	"Row Description"
		INDEX		{  policerID  }
		::=  { qosPolicerTable 1 }

	QosPolicerEntry  ::=  SEQUENCE {
		policerID         Unsigned32,
		qosPolicerPara    Unsigned32,
		qosExceededOper   INTEGER ,
		qosPolicerBurst   Unsigned32
		}

	policerID	OBJECT-TYPE
		SYNTAX			Unsigned32
		MAX-ACCESS		not-accessible
		STATUS			current
		DESCRIPTION		"Column Description.The scope is 0-255."
		REFERENCE		"ip-priority"
		::=  {  qosPolicerEntry  1  }

	qosPolicerPara	OBJECT-TYPE
		SYNTAX			Unsigned32
		MAX-ACCESS		read-write
		STATUS			current
		DESCRIPTION		"qosGlobalProfile setting.If 0 means the policer is not existed.
						 The valid scope is 32-25165824,which means 32K-24Gbps."
		::=  {  qosPolicerEntry  2  }

	qosExceededOper	OBJECT-TYPE
		SYNTAX			INTEGER  { noOperation ( 1 ) , drop ( 2 ) }
		MAX-ACCESS		read-write
		STATUS			current
		DESCRIPTION		"no-operation  means  no operation on the packets;
						 drop means drop the packets.
						 Notice:This item is valid only after qosPolicerPara is valid."
		::=  {  qosPolicerEntry  3  }

	qosPolicerBurst	OBJECT-TYPE
		SYNTAX			Unsigned32
		MAX-ACCESS		read-write
		STATUS			current
		DESCRIPTION		"qosGlobalProfile setting for burstSize.If 0 get,means the policer is not existed.
		                 The item can be set only after qosPolicerPara is valid.
		                 The valid scope is  2000-2147450880,which means (2000-2G)byte.
		                 If 0 set,means the policer burstSize set according to qos rule."
		::=  {  qosPolicerEntry  4  }


	ipPriToTrafficTable	OBJECT-TYPE
		SYNTAX		SEQUENCE  OF  IpPriToTrafficEntry
		MAX-ACCESS	not-accessible
		STATUS		current
		DESCRIPTION	"Description"
		::=  { qos  8 }

	ipPriToTrafficEntry	OBJECT-TYPE
		SYNTAX		IpPriToTrafficEntry
		MAX-ACCESS	not-accessible
		STATUS		current
		DESCRIPTION	"Row Description"
		INDEX		{  ipPriority  }
		::=  { ipPriToTrafficTable 1 }

	IpPriToTrafficEntry  ::=  SEQUENCE {
		ipPriority  Unsigned32,
		tcFePort Unsigned32,
		tcGePort Unsigned32
		}

	ipPriority	OBJECT-TYPE
		SYNTAX			Unsigned32
		MAX-ACCESS		not-accessible
		STATUS			current
		DESCRIPTION		"Column Description"
		REFERENCE		"ip-priority"
		::=  {  ipPriToTrafficEntry  1  }

	tcFePort	OBJECT-TYPE
		SYNTAX			Unsigned32  ( 0 .. 3  )
		MAX-ACCESS		read-write
		STATUS			current
		DESCRIPTION		"traffic-class corresponding to ipPriority. The value is between 0 and 3."
		::=  {  ipPriToTrafficEntry  2  }

	tcGePort	OBJECT-TYPE
		SYNTAX			Unsigned32  ( 0 .. 7  )
		MAX-ACCESS		read-write
		STATUS			current
		DESCRIPTION		"traffic-class corresponding to ipPriority. The value is between 0 and 7."
		::=  {  ipPriToTrafficEntry  3  }
--
	fePortIngBandTable	OBJECT-TYPE
		SYNTAX		SEQUENCE  OF  FePortIngBandEntry
		MAX-ACCESS	not-accessible
		STATUS		current
		DESCRIPTION	"A list of port entries. The number of
                    entries is given by the value of portNumber. "
		::=  { qos  9 }

	fePortIngBandEntry	OBJECT-TYPE
		SYNTAX		FePortIngBandEntry
		MAX-ACCESS	not-accessible
		STATUS		current
		DESCRIPTION	"A port entry containing objects at the
                    subnetwork layer and below for a particular
                    port. "
		INDEX		{  fePortID ,sessionNo }
		::=  { fePortIngBandTable 1 }


	FePortIngBandEntry  ::=  SEQUENCE {
		fePortID  Unsigned32,
		sessionNo  Unsigned32,
		sessionStatus  INTEGER,
		feIngressRate  Unsigned32,
		feIngressPkType  PortList,
		quePriorityStatus  PortList,
		mgmtNoRatelimitStatus  INTEGER
		}

	fePortID	OBJECT-TYPE
		SYNTAX			Unsigned32
		MAX-ACCESS		read-only
		STATUS			current
		DESCRIPTION		"The port ID.The value is devID*100+localPort.
		                 For example, 802 means devID is 8 and localPort is 2."
		::=  {  fePortIngBandEntry  1  }

	sessionNo	OBJECT-TYPE
		SYNTAX			Unsigned32
		MAX-ACCESS		read-only
		STATUS			current
		DESCRIPTION		"The session No.The scope is 0-3.
		                 0 means broadcast suppression;
		                 1 means multicast suppression;
		                 2 means rate limit;
		                 3 means user configure."
		::=  {  fePortIngBandEntry  2  }

	sessionStatus  	OBJECT-TYPE
		SYNTAX			INTEGER  { enable ( 1 ) , disable ( 2 ) }
		MAX-ACCESS		read-write
		STATUS			current
		DESCRIPTION		"Enable or disable the feport's ingress bandwidth session.
		                 Note：the item can be set to be enable only after feIngressRate has configed."
		::=  {  fePortIngBandEntry  3  }

	feIngressRate  	OBJECT-TYPE
		SYNTAX			Unsigned32
		MAX-ACCESS		read-write
		STATUS			current
		DESCRIPTION		"feport's ingress bandwidth rate value(kbps).
						 The scope is 64-100000 ."
		::=  {  fePortIngBandEntry  4  }

	feIngressPkType	OBJECT-TYPE
		SYNTAX			PortList
		MAX-ACCESS		read-write
		STATUS			current
		DESCRIPTION		"The item show status of packet type .
						 In turn means unknownmulticast(1),broadcast(2),multicast(3),unicast(4),
						         MGMT(5),ARP(6),tcp-control(7),tcp-data(8),udp(9),non-tcpudp(10);
						    0 means disable,1 means enable.
						 Notice: disable all type is not permitted."
		::=  {  fePortIngBandEntry  5  }

	quePriorityStatus	OBJECT-TYPE
		SYNTAX			PortList
		MAX-ACCESS		read-write
		STATUS			current
		DESCRIPTION		"The item show status of queue-priority .
						 In turn means queues-priority 0,1,2,3;
						    0 means disable,1 means enable."
		::=  {  fePortIngBandEntry  6  }

	mgmtNoRatelimitStatus	OBJECT-TYPE
		SYNTAX			INTEGER  { enable ( 1 ) , disable ( 2 ) }
		MAX-ACCESS		read-write
		STATUS			current
		DESCRIPTION		"Enable or disable mgmtNoRatelimit"
		::=  {  fePortIngBandEntry  7  }

	gePortIngBandTable	OBJECT-TYPE
		SYNTAX		SEQUENCE  OF  GePortIngBandEntry
		MAX-ACCESS	not-accessible
		STATUS		current
		DESCRIPTION	"A list of port entries. The number of
                    entries is given by the value of portNumber. "
		::=  { qos  10 }

	gePortIngBandEntry	OBJECT-TYPE
		SYNTAX		GePortIngBandEntry
		MAX-ACCESS	not-accessible
		STATUS		current
		DESCRIPTION	"A port entry containing objects at the
                    subnetwork layer and below for a particular
                    port. "
		INDEX		{  gePortID  }
		::=  { gePortIngBandTable 1 }


	GePortIngBandEntry  ::=  SEQUENCE {
		gePortID  Unsigned32,
		geIngressStatus  INTEGER,
		geIngressRate Integer32,
		geIngressPkType  PortList
		}

	gePortID	OBJECT-TYPE
		SYNTAX			Unsigned32
		MAX-ACCESS		read-only
		STATUS			current
		DESCRIPTION		"The port ID.The value is devID*100+localPort.
		                 For example, 802 means devID is 8 and localPort is 2."
		::=  {  gePortIngBandEntry  1  }

	geIngressStatus	OBJECT-TYPE
		SYNTAX			INTEGER  { on ( 1 ) , off ( 2 ) }
		MAX-ACCESS		read-write
		STATUS			current
		DESCRIPTION		"Set geport's ingress bandwidth on or off.
					     Note：the item can be set to be enable only after geIngressRate has configed."
		::=  {  gePortIngBandEntry  2  }

	geIngressRate	OBJECT-TYPE
		SYNTAX			Integer32
		MAX-ACCESS		read-write
		STATUS			current
		DESCRIPTION		"The item show ingress rate for gigabit ethernet port .
		                 2000-1000000 means valid ingress bandwidth."
		::=  {  gePortIngBandEntry  3  }

	geIngressPkType	OBJECT-TYPE
		SYNTAX			PortList
		MAX-ACCESS		read-write
		STATUS			current
		DESCRIPTION		"The item show status of packet type .
						 In turn means unicast(1),nounicast(2),multicast(3),broadcast(4);
						    0 means disable,1 means enable."
		::=  {  gePortIngBandEntry  4  }

	geQueScheTable	OBJECT-TYPE
		SYNTAX		SEQUENCE  OF  GeQueScheEntry
		MAX-ACCESS	not-accessible
		STATUS		current
		DESCRIPTION	"Description"
		::=  { qos  11 }

	geQueScheEntry	OBJECT-TYPE
		SYNTAX		GeQueScheEntry
		MAX-ACCESS	not-accessible
		STATUS		current
		DESCRIPTION	"Row Description"
		INDEX		{  gePortSessionID , queueID }
		::=  { geQueScheTable 1 }

	GeQueScheEntry  ::=  SEQUENCE {
		gePortSessionID      Unsigned32,
		queueID              Unsigned32,
		queueSchedule        OCTET STRING
		}

	gePortSessionID	OBJECT-TYPE
		SYNTAX			Unsigned32
		MAX-ACCESS		not-accessible
		STATUS			current
		DESCRIPTION		"Column Description"
		REFERENCE		"ip-priority"
		::=  {  geQueScheEntry  1  }

	queueID     	OBJECT-TYPE
		SYNTAX			Unsigned32
		MAX-ACCESS		not-accessible
		STATUS			current
		DESCRIPTION		"Queue ID"
		::=  {  geQueScheEntry  2  }

	queueSchedule	OBJECT-TYPE
		SYNTAX			OCTET STRING
		MAX-ACCESS		read-write
		STATUS			current
		DESCRIPTION		"The format is X-Y.
		                 X :1,means strict priority mode,Y is not necessary;
		                    2,means sdwrr mode and group 0;
		                    3,means sdwrr mode and group 1.
		                 Y :queue weight,1-32.
		                 Notes: sdwrr mode must be set in series ,
		                 		sdwrr0 and sdwrr1 can not be lumped together."
		::=  {  geQueScheEntry  3  }
--

	geQosPrimapUsrToTraffic	OBJECT-TYPE
		SYNTAX			OCTET STRING
		MAX-ACCESS		read-write
		STATUS			current
		DESCRIPTION		"For gePort,qos priority-map includes user-priority to traffic-class.
The format of this item is array of  eight  traffic-class  values corresponding to 0-7 user-priority.
Each   traffic-class vaule is between 0 and 7.
For example:set 12501721 means remappingtag   traffic-class
0                              1
1                              2
2                              5
3                              0
4                              1
5                              7
6                              2
7                              1"
		::=  {  qos  12  }

--
	gePortIp2UserTable	OBJECT-TYPE
		SYNTAX		SEQUENCE  OF  GePortIp2UserEntry
		MAX-ACCESS	not-accessible
		STATUS		current
		DESCRIPTION	"Description"
		::=  { qos  13 }

	gePortIp2UserEntry	OBJECT-TYPE
		SYNTAX		GePortIp2UserEntry
		MAX-ACCESS	not-accessible
		STATUS		current
		DESCRIPTION	"Row Description"
		INDEX		{  ipPriority  }
		::=  { gePortIp2UserTable 1 }

	GePortIp2UserEntry  ::=  SEQUENCE {
		userPriority  Unsigned32
		}

	userPriority	OBJECT-TYPE
		SYNTAX			Unsigned32  ( 0 .. 3  )
		MAX-ACCESS		read-write
		STATUS			current
		DESCRIPTION		"For gePort,userPriority corresponding to ipPriority.
		                 The value is between 0 and 7."
		::=  {  gePortIp2UserEntry  2  }

--
portQosParamTable	OBJECT-TYPE
		SYNTAX		SEQUENCE  OF  PortQosParamEntry
		MAX-ACCESS	not-accessible
		STATUS		current
		DESCRIPTION	"A list of port entries. The number of
                    entries is given by the value of portNumber. "
		::=  { qos  14 }

	portQosParamEntry	OBJECT-TYPE
		SYNTAX		PortQosParamEntry
		MAX-ACCESS	not-accessible
		STATUS		current
		DESCRIPTION	"A port entry containing objects at the
                    subnetwork layer and below for a particular
                    port. "
		INDEX		{  portID  }
		::=  { portQosParamTable 1 }

	PortQosParamEntry  ::=  SEQUENCE {
		portID  Unsigned32,
		bandWidthEgress  OCTET STRING,
		upPriorityEnable  INTEGER,
		dscpPriorityEnable  INTEGER,
		queScheduleMode     INTEGER,
		remaptagToPriority  OCTET STRING
		}

	portID	OBJECT-TYPE
		SYNTAX			Unsigned32
		MAX-ACCESS		not-accessible
		STATUS			current
		DESCRIPTION		"The port ID.The value is devID*100+localPort.
		                 For example, 802 means devID is 8 and localPort is 2."
		::=  {  portQosParamEntry  1  }


	bandWidthEgress	OBJECT-TYPE
		SYNTAX			OCTET STRING
		MAX-ACCESS		read-write
		STATUS			current
		DESCRIPTION		"port's  egress bandwidth restrict, The format is 0 or R-BR.
						 0 means clear the port's original egress bandwidth config.
		                 For fePort:
		                   	R:means rate ,the scope is 64-100000 ;
		                   	BR:means burstSize,0(no burstSize);
		                 For gePort:
		                 	R:means rate ,the scope is 281-1000000 ;
		                   	BR:means burstSize,the scope is 0(default burstSize),4-16380."
		::=  {  portQosParamEntry  2  }

	upPriorityEnable	OBJECT-TYPE
		SYNTAX			INTEGER  { enable ( 1 ) , disable ( 2 ) }
		MAX-ACCESS		read-write
		STATUS			current
		DESCRIPTION		"Enable or disable userPriority."
		::=  {  portQosParamEntry  3  }

	dscpPriorityEnable	OBJECT-TYPE
		SYNTAX			INTEGER  { enable ( 1 ) , disable ( 2 ) }
		MAX-ACCESS		read-write
		STATUS			current
		DESCRIPTION		"Enable or disable dscpPriority"
		::=  {  portQosParamEntry  4 }

	queScheduleMode	OBJECT-TYPE
		SYNTAX			INTEGER  { wrr0 ( 0 ) , sp ( 1 ) , wrr1-sp ( 2 ) , wrr2-sp ( 3 ) , session0 ( 4 ) , session1 ( 5 )}
		MAX-ACCESS		read-write
		STATUS			current
		DESCRIPTION		"Port's queue-schedule mode.
		                 For fePort:
		                 wrr0     means Weight0-weight1-weight2-weight3;
		                 sp       means SP-SP-SP-SP;
  						 wrr1-sp  means Weight0-weight1-weight2-sp;
  						 wrr2-sp  means Weight0-weight1-sp-sp.
  						 For gePort:  session0,session1."
		::=  {  portQosParamEntry  5 }


	remaptagToPriority	OBJECT-TYPE
		SYNTAX			OCTET STRING
		MAX-ACCESS		read-write
		STATUS			current
		DESCRIPTION		"Qos priority-map includes remappingtag to traffic-class.
The format of this item is array of  eight  traffic-class  values corresponding to 0-7 remappingtag.
Each   traffic-class vaule is between 0 and 7.
For example:set 15301371 means
remappingtag   traffic-class
0                              1
1                              5
2                              3
3                              0
4                              1
5                              3
6                              7
7                              1
Note:The remaptagToPriority attribute of gigabits port can not be changed
to another configuratinon except for the default one. "
		::=  {  portQosParamEntry  6  }

	sessionMaxNum	OBJECT-TYPE
		SYNTAX			Unsigned32  ( 1 .. 20  )
		MAX-ACCESS		read-only
		STATUS			current
		DESCRIPTION		"Pvlan session max num,default 4."
		::=  {  pvlan  1  }

	pvlanTable	OBJECT-TYPE
		SYNTAX		SEQUENCE  OF  PvlanEntry
		MAX-ACCESS	not-accessible
		STATUS		current
		DESCRIPTION	" A list of pvlan entries. The number of
                    entries is given by the value of session number. "
		::=  { pvlan  2 }

	pvlanEntry	OBJECT-TYPE
		SYNTAX		PvlanEntry
		MAX-ACCESS	not-accessible
		STATUS		current
		DESCRIPTION	"A pvlan entry . "
		INDEX		{  sessionId  }
		::=  { pvlanTable 1 }

	PvlanEntry  ::=  SEQUENCE {
		sessionId  Unsigned32,
		proAndIsoPortOrTrunk  OCTET STRING
		}

	sessionId	OBJECT-TYPE
		SYNTAX			Unsigned32
		MAX-ACCESS		not-accessible
		STATUS			current
		DESCRIPTION		"The server id"
		::=  {  pvlanEntry  1  }

   proAndIsoPortOrTrunk	OBJECT-TYPE
		SYNTAX			OCTET STRING
		MAX-ACCESS		read-write
		STATUS			current
		DESCRIPTION		"pvlan setting including promiscuous port(or trunk) and isolated port(or ports).
		                 The format is 0 or Px-xxxxxxxx or Tx-xxxxxxxx.
		                 if 0 means no pvlan config.Others:
		                 The first part is Px,means promiscuous port x;
		                                   Tx,means promiscuous trunk x;
		                 The second part is xxxxxxxx,means isolated port in portlist format.
		                 For example:  P3-18000000
		                         means pvlan promiscuous port :port 3;
		                                     isolated port :port 4,5."
		::=  {  pvlanEntry  2  }

	lacpAdminStatus	OBJECT-TYPE
		SYNTAX			INTEGER  { enable ( 1 ) , disable ( 2 ) }
		MAX-ACCESS		read-write
		STATUS			current
		DESCRIPTION		"The desired state of Link Aggregation Control Protocol(LACP)."
		::=  {  lacp  1  }

	lacpPriority	OBJECT-TYPE
		SYNTAX			Unsigned32  ( 1 .. 65535  )
		MAX-ACCESS		read-write
		STATUS			current
		DESCRIPTION		"LACP priority value."
		::=  {  lacp  2  }

	trunkNumber	OBJECT-TYPE
		SYNTAX			Unsigned32
		MAX-ACCESS		read-only
		STATUS			current
		DESCRIPTION		"The number of trunks (regardless of their current state)
                        present on this system."
		::=  {  lacp  3  }

	trunkTable	OBJECT-TYPE
		SYNTAX		SEQUENCE  OF  TrunkEntry
		MAX-ACCESS	not-accessible
		STATUS		current
		DESCRIPTION	"A table of all trunks' config."
		::=  { lacp  4 }

	trunkEntry	OBJECT-TYPE
		SYNTAX		TrunkEntry
		MAX-ACCESS	not-accessible
		STATUS		current
		DESCRIPTION	"Each entry contains config of a trunk."
		INDEX		{  trunkId  }
		::=  { trunkTable 1 }

	TrunkEntry  ::=  SEQUENCE {
		trunkId  Unsigned32,
		trunkPvid  Integer32,
		trunkMulticast  INTEGER,
		trunkPorts  PortList,
		trunkMode  INTEGER
--		trunkAclAdminStatus  OCTET STRING
		}


	trunkId	OBJECT-TYPE
		SYNTAX			Unsigned32  ( 1 .. 7  )
		MAX-ACCESS		not-accessible
		STATUS			current
		DESCRIPTION		"Trunk id."
		::=  {  trunkEntry  1  }


	trunkPvid	OBJECT-TYPE
		SYNTAX			Integer32  ( 1 .. 4094  )
		MAX-ACCESS		read-write
		STATUS			current
		DESCRIPTION		"Trunk default vlan id."
		::=  {  trunkEntry  2  }


	trunkMulticast	OBJECT-TYPE
		SYNTAX			INTEGER  { forward ( 1 ) , discard ( 2 ) }
		MAX-ACCESS		read-write
		STATUS			current
		DESCRIPTION		"Trunk forward/discard multicast packet."
		::=  {  trunkEntry  3  }


	trunkPorts	OBJECT-TYPE
		SYNTAX			PortList
		MAX-ACCESS		read-write
		STATUS			current
		DESCRIPTION		"Ports in lacp link aggregation group."
		::=  {  trunkEntry  4  }


	trunkMode	OBJECT-TYPE
		SYNTAX			INTEGER  { dynamic ( 1 ) , static ( 2 ) , mixed (3)}
		MAX-ACCESS		read-write
		STATUS			current
		DESCRIPTION		"Aggregator mode"
		::=  {  trunkEntry  5  }

--	trunkAclAdminStatus	OBJECT-TYPE
--		SYNTAX			OCTET STRING   ( SIZE ( 0 .. 20  ) )
--		MAX-ACCESS		read-write
--		STATUS			current
--		DESCRIPTION		"The desired state of the trunk in acl number .
--		                 The format is X-Y;
--		                 X: 1 means enable , 2 means disable ;
--		                 Y: acl number. The scope is 0-349."
--		::=  {  trunkEntry  6  }

	lacpPortTable	OBJECT-TYPE
		SYNTAX		SEQUENCE  OF  LacpPortEntry
		MAX-ACCESS	not-accessible
		STATUS		current
		DESCRIPTION	"The table of all ports' config for LACP."
		::=  { lacp  5 }

	lacpPortEntry	OBJECT-TYPE
		SYNTAX		LacpPortEntry
		MAX-ACCESS	not-accessible
		STATUS		current
		DESCRIPTION	"Each entry contains port config for LACP."
		INDEX		{  lacpPortId  }
		::=  { lacpPortTable 1 }

	LacpPortEntry  ::=  SEQUENCE {
		lacpPortId  Integer32,
		lacpPortMode  INTEGER,
		lacpPortTimeout  INTEGER
		}


	lacpPortId	OBJECT-TYPE
		SYNTAX			Integer32  ( -2147483648 .. 2147483647  )
		MAX-ACCESS		not-accessible
		STATUS			current
		DESCRIPTION		"The port id to index lacp config."
		::=  {  lacpPortEntry  1  }


	lacpPortMode	OBJECT-TYPE
		SYNTAX			INTEGER  { active ( 1 ) , passive ( 2 ) }
		MAX-ACCESS		read-write
		STATUS			current
		DESCRIPTION		"Port's aggregator mode in LACP"
		::=  {  lacpPortEntry  2  }


	lacpPortTimeout	OBJECT-TYPE
		SYNTAX			INTEGER  { short ( 1 ) , long ( 2 ) }
		MAX-ACCESS		read-write
		STATUS			current
		DESCRIPTION		"LACP aggregator timeout"
		::=  {  lacpPortEntry  3  }

	layer3PortTable	OBJECT-TYPE
		SYNTAX		SEQUENCE  OF  Layer3PortEntry
		MAX-ACCESS	not-accessible
		STATUS		current
		DESCRIPTION	"The layer 3 port table contains config
		            of all layer 3 ports of the device."
		::=  { layer3  1 }

	layer3PortEntry	OBJECT-TYPE
		SYNTAX		Layer3PortEntry
		MAX-ACCESS	not-accessible
		STATUS		current
		DESCRIPTION	"An entry of layer 3 port config"
		INDEX		{  layer3PortId  }
		::=  { layer3PortTable 1 }

	Layer3PortEntry  ::=  SEQUENCE {
		layer3PortId  Unsigned32,
		layer3PortIpAddrAndMask  OCTET STRING,
		layer3PortMacAddr  MacAddress,
		layer3PortVlanId  Integer32,
		layer3PortAdminStatus  INTEGER
		}


	layer3PortId	OBJECT-TYPE
		SYNTAX			Unsigned32
		MAX-ACCESS		not-accessible
		STATUS			current
		DESCRIPTION		"Layer 3 port id"
		::=  {  layer3PortEntry  1  }


	layer3PortIpAddrAndMask	OBJECT-TYPE
		SYNTAX			OCTET STRING
		MAX-ACCESS		read-write
		STATUS			current
		DESCRIPTION		"the format of this item is xx.xx.xx.xx/xx. Among this string,
                         the first  segment represents layer 3 ipAddress, the second
                         segment represents net mask. eg: 192.168.2.8/24.
                         Others 0 means delete primary ip address."
		::=  {  layer3PortEntry  2  }


	layer3PortMacAddr	OBJECT-TYPE
		SYNTAX			MacAddress  ( SIZE ( 6  ) )
		MAX-ACCESS		read-write
		STATUS			current
		DESCRIPTION		"Mac address of a layer 3 port. The scope of zte mac is
                                        00:d0:d0:f0:00:00~00:d0:d0:ff:ff:ff."
		::=  {  layer3PortEntry  3  }


	layer3PortVlanId	OBJECT-TYPE
		SYNTAX			Integer32  ( 1 .. 4094  )
		MAX-ACCESS		read-write
		STATUS			current
		DESCRIPTION		"Vlan id binded to a layer 3 port."
		::=  {  layer3PortEntry  4  }


	layer3PortAdminStatus	OBJECT-TYPE
		SYNTAX			INTEGER  { enable ( 1 ) , disable ( 2 ) }
		MAX-ACCESS		read-write
		STATUS			current
		DESCRIPTION		"The desired state of the layer 3 port."
		::=  {  layer3PortEntry  5  }

	loopDetectBlockDelay	OBJECT-TYPE
		SYNTAX			Unsigned32  ( 1 .. 1080  )
		MAX-ACCESS		read-write
		STATUS			current
		DESCRIPTION		"Loopback block delay interval(minute).
		                After delay-interval, the trunk or port
		                blocked because of loopback will be unblocked."
		::=  {  loopDetect  1  }

	loopDetectSendPktInterval	OBJECT-TYPE
		SYNTAX			Unsigned32  ( 5 .. 60  )
		MAX-ACCESS		read-write
		STATUS			current
		DESCRIPTION		"Loopback block send packet interval(second)."
		::=  {  loopDetect  2  }

	loopDetectPortTable	OBJECT-TYPE
		SYNTAX		SEQUENCE  OF  LoopDetectPortEntry
		MAX-ACCESS	not-accessible
		STATUS		current
		DESCRIPTION	"Loopback detection config and result of trunks."
		::=  { loopDetect  3 }

	loopDetectPortEntry	OBJECT-TYPE
		SYNTAX		LoopDetectPortEntry
		MAX-ACCESS	not-accessible
		STATUS		current
		DESCRIPTION	"A port entry containing loopback detection
		            config and status."
		INDEX		{  loopDetectPortId  }
		::=  { loopDetectPortTable 1 }

	LoopDetectPortEntry  ::=  SEQUENCE {
		loopDetectPortId  Integer32 ,
		loopDetectPortAdminStatus  OCTET STRING,
		loopDetectPortProtectStatus  INTEGER,
		loopDetectPortLoopStatus  INTEGER,
		loopDetectPortBlockStatus  INTEGER,
		loopDetectPortInVlan       Unsigned32
		}


	loopDetectPortId	OBJECT-TYPE
		SYNTAX			Integer32
		MAX-ACCESS		read-only
		STATUS			current
		DESCRIPTION		"Port id."
		::=  {  loopDetectPortEntry  1  }


	loopDetectPortAdminStatus	OBJECT-TYPE
		SYNTAX			OCTET STRING   ( SIZE ( 0 .. 200  ) )
		MAX-ACCESS		read-write
		STATUS			current
		DESCRIPTION		"This item indicates whether permit loop back
		                detection on this port or not.The first character means:
		                0-disable;1:enable(port based);2:enable(vlan based);
		                The format of 0 means the port disable loopdetect in all vlans.
		                The format of 1 means the port enable loopdetect in default vlan.
		                The format of 2-3 means the port enables loopdetect in vlan 3."
		::=  {  loopDetectPortEntry  2  }


	loopDetectPortProtectStatus	OBJECT-TYPE
		SYNTAX			INTEGER  { enable ( 1 ) , disable ( 2 ) }
		MAX-ACCESS		read-write
		STATUS			current
		DESCRIPTION		"Whether block this port or not while detect loopback."
		::=  {  loopDetectPortEntry  3  }


	loopDetectPortLoopStatus	OBJECT-TYPE
		SYNTAX			INTEGER  { yes ( 1 ) , no ( 2 ) }
		MAX-ACCESS		read-only
		STATUS			current
		DESCRIPTION		"Item value indicates whether this port is loopback."
		::=  {  loopDetectPortEntry  4  }

        loopDetectPortBlockStatus	OBJECT-TYPE
		SYNTAX			INTEGER  { yes ( 1 ) , no ( 2 ) }
		MAX-ACCESS		read-only
		STATUS			current
		DESCRIPTION		"Item value indicates whether this port is blocked."
		::=  {  loopDetectPortEntry  5  }

       loopDetectPortInVlan	OBJECT-TYPE
		SYNTAX			Unsigned32( 0 .. 4095 )
		MAX-ACCESS		read-only
		STATUS			current
		DESCRIPTION		"VlanID which the port belong to when looped and blocked.
		                 0 means default vlanID which the port is in when looped and blocked;
		                 1-4094 means some vlanID which the port belongs to when looped and blocked ;
		                 4095 means the port is not in the status of  looped and blocked. "
		::=  {  loopDetectPortEntry  6  }

	loopDetectTrunkTable	OBJECT-TYPE
		SYNTAX		SEQUENCE  OF  LoopDetectTrunkEntry
		MAX-ACCESS	not-accessible
		STATUS		current
		DESCRIPTION	"Loopback detection config and result of trunks."
		::=  { loopDetect  4 }

	loopDetectTrunkEntry	OBJECT-TYPE
		SYNTAX		LoopDetectTrunkEntry
		MAX-ACCESS	not-accessible
		STATUS		current
		DESCRIPTION	"A trunk entry containing loopback detection
		            config and status."
		INDEX		{  loopDetectTrunkId  }
		::=  { loopDetectTrunkTable 1 }

	LoopDetectTrunkEntry  ::=  SEQUENCE {
		loopDetectTrunkId  Integer32,
		loopDetectTrunkAdminStatus  OCTET STRING,
		loopDetectTrunkProtectStatus  INTEGER,
		loopDetectTrunkLoopStatus  INTEGER ,
		loopDetectTrunkBlockStatus  INTEGER,
		loopDetectTrunkInVlan    Unsigned32
		}


	loopDetectTrunkId	OBJECT-TYPE
		SYNTAX			Integer32
		MAX-ACCESS		read-only
		STATUS			current
		DESCRIPTION		"Trunk id."
		::=  {  loopDetectTrunkEntry  1  }


	loopDetectTrunkAdminStatus	OBJECT-TYPE
		SYNTAX			OCTET STRING   ( SIZE ( 0 .. 200  ) )
		MAX-ACCESS		read-write
		STATUS			current
		DESCRIPTION		"This item indicates whether permit loopback
                        detection on this trunk or not.The first character means:
		                0-disable;1:enable(trunk based);2:enable(vlan based);
		                The format of 0 means the trunk disable loopdetect in all vlans.
		                The format of 1 means the trunk enable loopdetect in default vlan.
		                The format of 2-3 means the trunk enables loopdetect in vlan 3 ."
		::=  {  loopDetectTrunkEntry  2  }


	loopDetectTrunkProtectStatus	OBJECT-TYPE
		SYNTAX			INTEGER  { enable ( 1 ) , disable ( 2 ) }
		MAX-ACCESS		read-write
		STATUS			current
		DESCRIPTION		"Whether block this trunk or not while detect loopback."
		::=  {  loopDetectTrunkEntry  3  }


	loopDetectTrunkLoopStatus	OBJECT-TYPE
		SYNTAX			INTEGER  { yes ( 1 ) , no ( 2 ) }
		MAX-ACCESS		read-only
		STATUS			current
		DESCRIPTION		"Item value indicates whether this trunk is loopback."
		::=  {  loopDetectTrunkEntry  4  }

	loopDetectTrunkBlockStatus	OBJECT-TYPE
		SYNTAX			INTEGER  { yes ( 1 ) , no ( 2 ) }
		MAX-ACCESS		read-only
		STATUS			current
		DESCRIPTION		"Item value indicates whether this trunk is blocked."
		::=  {  loopDetectTrunkEntry  5  }

    loopDetectTrunkInVlan	OBJECT-TYPE
		SYNTAX			Unsigned32( 0 .. 4095 )
		MAX-ACCESS		read-only
		STATUS			current
		DESCRIPTION		"VlanID which the trunk belong to when looped and blocked.
		                 0 means default vlanID which the trunk is in when looped and blocked;
		                 1-4094 means some vlanID which the  trunk belongs to when looped and blocked ;
		                 4095 means the trunk is not in the status of  looped and blocked. "
		::=  {  loopDetectTrunkEntry  6  }

	loopDetectPortTrap	NOTIFICATION-TYPE
		OBJECTS			{ loopDetectPortId, loopDetectPortInVlan,loopDetectPortBlockStatus}
		STATUS			current
		DESCRIPTION		"The trap indicates nms that port based loopdetect status."
		::=  {  loopDetect  5 }

	loopDetectTrunkTrap	NOTIFICATION-TYPE
		OBJECTS			{ loopDetectTrunkId, loopDetectTrunkInVlan,trunkPorts,loopDetectTrunkBlockStatus}
		STATUS			current
		DESCRIPTION		"The trap indicates nms that trunk based loopdetect status."
		::=  {  loopDetect  6 }

	vlanTranslationTable	OBJECT-TYPE
		SYNTAX		SEQUENCE OF VlanTranslationEntry
		MAX-ACCESS	not-accessible
		STATUS		current
		DESCRIPTION	"Description vlan-translation ."
		::=  { vlanTranslation  1 }

	vlanTranslationEntry	OBJECT-TYPE
		SYNTAX		VlanTranslationEntry
		MAX-ACCESS	not-accessible
		STATUS		current
		DESCRIPTION	"Description"
		INDEX		{  ingressPortId  }
		::=  { vlanTranslationTable 1 }

	VlanTranslationEntry  ::=  SEQUENCE {
		ingressPortId          INTEGER,
                vlanTranslationEnable  INTEGER,
		vlanTranslationStatus  OCTET STRING
		}

	ingressPortId	OBJECT-TYPE
		SYNTAX			INTEGER
		MAX-ACCESS		read-only
		STATUS			current
		DESCRIPTION		"feport id"
		::=  {  vlanTranslationEntry  1  }

	vlanTranslationEnable	OBJECT-TYPE
		SYNTAX			INTEGER { enable ( 1 ) , disable ( 2 ) }
		MAX-ACCESS		read-write
		STATUS			current
		DESCRIPTION		"vlan-translation state ."
		::=  {  vlanTranslationEntry  2  }

	vlanTranslationStatus	OBJECT-TYPE
		SYNTAX			OCTET STRING
		MAX-ACCESS		read-write
		STATUS			current
		DESCRIPTION		" This item indicates whether permit vlan-translation
 on this port or not. The format is INV/EGP/EGV or 0.
 0 : means clear vlan-translation on the port.
 INV : means ingress-vlan (support vlan-list format).
 EGP : means egress-port (geport-id) .
 EGV : means egress-vlan (support vlan-list format).
 Such as 100-102/26/500,506-507 ,which means on this ports set ingress-vlan is 100-102 ,
egress-port is 26 ,egress-vlan is 500,506-507 . "
		::=  {  vlanTranslationEntry  3  }

	stpAdminStatus	OBJECT-TYPE
		SYNTAX			INTEGER  { enable ( 1 ) , disable ( 2 ) }
		MAX-ACCESS		read-write
		STATUS			current
		DESCRIPTION		"Description"
		::=  {  stp  1  }

	vctPortTable	OBJECT-TYPE
		SYNTAX		SEQUENCE  OF  VctPortEntry
		MAX-ACCESS	not-accessible
		STATUS		current
		DESCRIPTION	"The table of all ports' virtual cable test."
		::=  { vct  1 }

	vctPortEntry	OBJECT-TYPE
		SYNTAX		VctPortEntry
		MAX-ACCESS	not-accessible
		STATUS		current
		DESCRIPTION	"Each entry contains port config for VCT."
		INDEX		{  vctPortId  }
		::=  { vctPortTable 1 }

	VctPortEntry  ::=  SEQUENCE {
		vctPortId  Integer32,
		vctDo  INTEGER,
		vctIsValid  INTEGER,
		vctPair1Result  INTEGER,
		vctPair1Lenth  Integer32,
		vctPair2Result  INTEGER,
		vctPair2Lenth  Integer32,
		vctPair3Result  INTEGER,
		vctPair3Lenth  Integer32,
		vctPair4Result  INTEGER,
		vctPair4Lenth  Integer32
		}


	vctPortId	OBJECT-TYPE
		SYNTAX			Integer32  ( -2147483648 .. 2147483647  )
		MAX-ACCESS		not-accessible
		STATUS			current
		DESCRIPTION		"The port id to index vct config."
		::=  {  vctPortEntry  1  }

    vctDo	OBJECT-TYPE
        SYNTAX			INTEGER  { yes ( 1 ) , no ( 2 ) }
		MAX-ACCESS		read-write
		STATUS			current
		DESCRIPTION		"The value get from this item is insignificant.
		                Setting this item will start a virtual cable test process."
        ::=  {  vctPortEntry  2  }

    vctIsValid	OBJECT-TYPE
        SYNTAX			INTEGER  { no ( 1 ) , yes2 ( 2 ) , yes4 ( 3 ) }
		MAX-ACCESS		read-only
		STATUS			current
		DESCRIPTION		"This item indicates whether the port surports vct or
		                whether the result is valid. yes2 means there are 2 pairs,
		                yes4 means there are 4 pairs."
        ::=  {  vctPortEntry  3  }

    vctPair1Result	OBJECT-TYPE
        SYNTAX			INTEGER  { good ( 1 ) , open ( 2 ) , short ( 3 ) , impMismatch ( 4 ) }
		MAX-ACCESS		read-only
		STATUS			current
		DESCRIPTION		"This item indicates the cable status: open,
		                short or impedance mismatch."
        ::=  {  vctPortEntry  4  }

    vctPair1Lenth	OBJECT-TYPE
        SYNTAX			Integer32 (0..65535)
		MAX-ACCESS		read-only
		STATUS			current
		DESCRIPTION		"This item indicates fault position."
        ::=  {  vctPortEntry  5  }

    vctPair2Result	OBJECT-TYPE
        SYNTAX			INTEGER  { good ( 1 ) , open ( 2 ) , short ( 3 ) , impMismatch ( 4 ) }
		MAX-ACCESS		read-only
		STATUS			current
		DESCRIPTION		"This item indicates the cable status: open,
		                short or impedance mismatch."
        ::=  {  vctPortEntry  6  }

    vctPair2Lenth	OBJECT-TYPE
        SYNTAX			Integer32 (0..65535)
		MAX-ACCESS		read-only
		STATUS			current
		DESCRIPTION		"This item indicates fault position."
        ::=  {  vctPortEntry  7  }

    vctPair3Result	OBJECT-TYPE
        SYNTAX			INTEGER  { good ( 1 ) , open ( 2 ) , short ( 3 ) , impMismatch ( 4 ) }
		MAX-ACCESS		read-only
		STATUS			current
		DESCRIPTION		"This item indicates the cable status: open,
		                short or impedance mismatch."
        ::=  {  vctPortEntry  8  }

    vctPair3Lenth	OBJECT-TYPE
        SYNTAX			Integer32 (0..65535)
		MAX-ACCESS		read-only
		STATUS			current
		DESCRIPTION		"This item indicates fault position."
        ::=  {  vctPortEntry  9  }

    vctPair4Result	OBJECT-TYPE
        SYNTAX			INTEGER  { good ( 1 ) , open ( 2 ) , short ( 3 ) , impMismatch ( 4 ) }
		MAX-ACCESS		read-only
		STATUS			current
		DESCRIPTION		"This item indicates the cable status: open,
		                short or impedance mismatch."
        ::=  {  vctPortEntry  10  }

    vctPair4Lenth	OBJECT-TYPE
        SYNTAX			Integer32 (0..65535)
		MAX-ACCESS		read-only
		STATUS			current
		DESCRIPTION		"This item indicates fault position."
        ::=  {  vctPortEntry  11  }

   syslogStatus	OBJECT-TYPE
		SYNTAX			INTEGER  { enable ( 1 ) , disable ( 2 ) }
		MAX-ACCESS		read-write
		STATUS			current
		DESCRIPTION		"Syslog status :enable or disable"
		::=  {  syslog  1  }

   syslogLevel	OBJECT-TYPE
		SYNTAX			Integer32  ( 0 .. 7  )
		MAX-ACCESS		read-write
		STATUS			current
		DESCRIPTION		"Syslog level:
		                 0       Emergency: system is unusable
                         1       Alert: action must be taken immediately
                         2       Critical: critical conditions
                         3       Error: error conditions
                         4       Warning: warning conditions
                         5       Notice: normal but significant condition
                         6       Informational: informational messages
                         7       Debug: debug-level messages   "
		::=  {  syslog  2  }

   enabledModule OBJECT-TYPE
		SYNTAX			PortList
		MAX-ACCESS		read-write
		STATUS			current
		DESCRIPTION		"Syslog enabled module,Only 9,26,27,29 can be supported now.
		                 0-driver;1-vct;2-inter;3-8021x;4-groupman
		                 5-igmpsnp;6-lacp;7-loopdet;8-mstp;9-radius
		                 10-syslog;11-file;12-routerware;13-comm;14-disp
		                 15-mux;16-sshsvr;17-qos;18-qinq;19-rtwl
		                 20-sche;21-debug;22-cli;23-conf;24-mib
		                 25-sdp;26-alarm;27-AAA(userctrl);28-console;29-commandlog"
		::=  {  syslog  3  }

	serverMaxNum	OBJECT-TYPE
		SYNTAX			Integer32  ( 0 .. 20  )
		MAX-ACCESS		read-only
		STATUS			current
		DESCRIPTION		"Syslog server max num,default 5."
		::=  {  syslog  4  }

	serverTable	OBJECT-TYPE
		SYNTAX		SEQUENCE  OF  ServerEntry
		MAX-ACCESS	not-accessible
		STATUS		current
		DESCRIPTION	" A list of server entries. The number of

                    entries is given by the value of serverNumber. "
		::=  { syslog  5 }

	serverEntry	OBJECT-TYPE
		SYNTAX		ServerEntry
		MAX-ACCESS	not-accessible
		STATUS		current
		DESCRIPTION	"A server entry . "
		INDEX		{  serverId  }
		::=  { serverTable 1 }

	ServerEntry  ::=  SEQUENCE {
		serverId  Unsigned32,
		serverIP  OCTET STRING,
		serverName  OCTET STRING,
		serverAdminStatus  INTEGER
		}


	serverId	OBJECT-TYPE
		SYNTAX			Unsigned32
		MAX-ACCESS		not-accessible
		STATUS			current
		DESCRIPTION		"The server id"
		::=  {  serverEntry  1  }

   serverIP 	OBJECT-TYPE
		SYNTAX			OCTET STRING
		MAX-ACCESS		read-write
		STATUS			current
		DESCRIPTION		"the format of this item is xx.xx.xx.xx. eg: 192.168.2.8.
		                 The value must be valid ipaddress.Others 0 means delete
		                 primary IP address ."
		::=  {  serverEntry  2  }

   serverName	OBJECT-TYPE
		SYNTAX			OCTET STRING  ( SIZE ( 0 .. 20  ) )
		MAX-ACCESS		read-write
		STATUS			current
		DESCRIPTION		"Server name valid only as serverAdminStatus is enable."
		::=  {  serverEntry  3 }

    serverAdminStatus	OBJECT-TYPE
		SYNTAX			INTEGER  { enable ( 1 ) , disable ( 2 ) }
		MAX-ACCESS		read-only
		STATUS			current
		DESCRIPTION		"The desired state of syslog server."
		::=  {  serverEntry  4  }

    synchronizeStatus	OBJECT-TYPE
		SYNTAX			INTEGER  { enable ( 1 ) , disable ( 2 ) }
		MAX-ACCESS		read-only
		STATUS			current
		DESCRIPTION		"Ntp synchronize status "
		::=  {  ntp          1  }

	protocolStatus   	OBJECT-TYPE
		SYNTAX			INTEGER  { enable ( 1 ) , disable ( 2 ) }
		MAX-ACCESS		read-write
		STATUS			current
		DESCRIPTION		"Ntp protocol status"
		::=  {  ntp          2  }

	srvIpAddrAndVersion	OBJECT-TYPE
		SYNTAX			OCTET STRING
		MAX-ACCESS		read-write
		STATUS			current
		DESCRIPTION		"the format of this item is xx.xx.xx.xx-x.
		                 Among this string,  the first  segment
		                 represents ntp server ipAddress, the value 0.0.0.0
		                 is invalid; the second segment represents  ntp
		                 version , only 1 or 2 or 3 valid.
		                 eg: 192.168.2.8-3."
 		::=  {  ntp          3  }

	sourceIpAddr    	OBJECT-TYPE
		SYNTAX			OCTET STRING
		MAX-ACCESS		read-write
		STATUS			current
		DESCRIPTION		"represents ntp source ipAddress. IP Address 0.0.0.0 is also valid."
		::=  {  ntp          4  }

   --
   userTable	OBJECT-TYPE
		SYNTAX		SEQUENCE  OF  UserEntry
		MAX-ACCESS	not-accessible
		STATUS		current
		DESCRIPTION	"A table containing loginUser configuration. "
		::=  { loginUser  1 }

   userEntry	OBJECT-TYPE
		SYNTAX		UserEntry
		MAX-ACCESS	not-accessible
		STATUS		current
		DESCRIPTION	"Each entry contains all config of an user."
		INDEX		{  userName  }
		::=  { userTable 1 }

   UserEntry  ::=  SEQUENCE {
		userName  DisplayString,
		userAttr  INTEGER,
		loginPass OCTET STRING,
		adminPass OCTET STRING
		}

   userName	OBJECT-TYPE
		SYNTAX			DisplayString (SIZE (0..15))
		MAX-ACCESS		read-only
		STATUS			current
		DESCRIPTION		"Community name .The character '?' is forbidded."
		::=  {  userEntry  1  }

   userAttr	OBJECT-TYPE
		SYNTAX			INTEGER  {  clear ( 1 ) , administrator ( 2 ) , guest ( 3 )   }
		MAX-ACCESS		read-write
		STATUS			current
		DESCRIPTION		"User attribute.'1' means clear the user."
		::=  {  userEntry  2  }

  loginPass        OBJECT-TYPE
		SYNTAX			OCTET STRING  ( SIZE ( 0 .. 16  ) )
		MAX-ACCESS		read-write
		STATUS			current
		DESCRIPTION		"Login password which attached to user.The character '?' is forbidded."
		::=  {  userEntry  3  }

    adminPass        OBJECT-TYPE
		SYNTAX			OCTET STRING  ( SIZE ( 0 .. 16  ) )
		MAX-ACCESS		read-write
		STATUS			current
		DESCRIPTION		"Admin password which attached to user.The character '?' is forbidded."
		::=  {  userEntry  4  }
   --
   communityTable	OBJECT-TYPE
		SYNTAX		SEQUENCE  OF  CommunityEntry
		MAX-ACCESS	not-accessible
		STATUS		current
		DESCRIPTION	"A table containing snmp community configuration. "
		::=  { snmpConfig  1 }

   communityEntry	OBJECT-TYPE
		SYNTAX		CommunityEntry
		MAX-ACCESS	not-accessible
		STATUS		current
		DESCRIPTION	"Each entry contains all config of a community."
		INDEX		{  communityName  }
		::=  { communityTable 1 }

   CommunityEntry  ::=  SEQUENCE {
		communityName  DisplayString,
		communityAttr  INTEGER,
		viewAttached  OCTET STRING
		}

   communityName	OBJECT-TYPE
		SYNTAX			DisplayString (SIZE (0..12))
		MAX-ACCESS		read-only
		STATUS			current
		DESCRIPTION		"Community name ."
		::=  {  communityEntry  1  }

   communityAttr	OBJECT-TYPE
		SYNTAX			INTEGER  {  clear ( 1 ) , public ( 2 ) , private ( 3 )   }
		MAX-ACCESS		read-write
		STATUS			current
		DESCRIPTION		"Community attribute.'1' means clear the community."
		::=  {  communityEntry  2  }

  viewAttached        OBJECT-TYPE
		SYNTAX			OCTET STRING  ( SIZE ( 0 .. 12  ) )
		MAX-ACCESS		read-write
		STATUS			current
		DESCRIPTION		"View which attached to community."
		::=  {  communityEntry  3  }

    viewTable	OBJECT-TYPE
		SYNTAX		SEQUENCE  OF  ViewEntry
		MAX-ACCESS	not-accessible
		STATUS		current
		DESCRIPTION	"A table containing snmp view configuration. "
		::=  { snmpConfig  2 }

	viewEntry	OBJECT-TYPE
		SYNTAX		ViewEntry
		MAX-ACCESS	not-accessible
		STATUS		current
		DESCRIPTION	"Each entry contains all config of a view."
		INDEX		{  viewIndex , viewName  }
		::=  { viewTable 1 }

	ViewEntry  ::=  SEQUENCE {
		viewIndex Unsigned32,
		viewName  OCTET STRING,
		attrAndOid OCTET STRING
		}

	viewIndex	OBJECT-TYPE
		SYNTAX			Unsigned32
		MAX-ACCESS		not-accessible
		STATUS			current
		DESCRIPTION		"Index of the view table . The scope is 1-32 . The value get from this item is insignificant. "
		::=  {  viewEntry  1  }

	viewName	OBJECT-TYPE
		SYNTAX			OCTET STRING  ( SIZE ( 1 .. 12  ) )
		MAX-ACCESS		read-only
		STATUS			current
		DESCRIPTION		"View name ."
		::=  {  viewEntry  2  }


	attrAndOid        OBJECT-TYPE
		SYNTAX			OCTET STRING  ( SIZE ( 0 .. 150  ) )
		MAX-ACCESS		read-write
		STATUS			current
		DESCRIPTION		"View attribute and OID which attached to view.
				 The set value is not always equal with the get value.
		                 The format is 0 or x-y or 3.x is 1,which means include,
		                 2 which means exclude.y is the oid. such as .1.3.6.
		                 when x is 0,clear the view.
		                 when x is 3,the setting is the default(include .1.3.6.1)."
		::=  {  viewEntry  3  }

   trapHostTable	OBJECT-TYPE
		SYNTAX		SEQUENCE  OF  TrapHostEntry
		MAX-ACCESS	not-accessible
		STATUS		current
		DESCRIPTION	"A table containing snmp traphost configuration. "
		::=  { snmpConfig  3 }

   trapHostEntry	OBJECT-TYPE
		SYNTAX		TrapHostEntry
		MAX-ACCESS	not-accessible
		STATUS		current
		DESCRIPTION	"Each entry contains all config of a traphost."
		INDEX		{  traphostIP , traphostType,commuName }
		::=  { trapHostTable 1 }

   TrapHostEntry  ::=  SEQUENCE {
		traphostIP  IpAddress,
		traphostType  Unsigned32,
		commuName     OCTET STRING,
                traphostVer   INTEGER
		}

   traphostIP	OBJECT-TYPE
		SYNTAX			IpAddress
		MAX-ACCESS		not-accessible
		STATUS			current
		DESCRIPTION		"Traphost IPAddress ."
		::=  {  trapHostEntry  1  }

   traphostType      OBJECT-TYPE
		SYNTAX			Unsigned32
		MAX-ACCESS		not-accessible
		STATUS			current
		DESCRIPTION		"Host type.
                                        1: trap ; 2: inform ."
		::=  {  trapHostEntry  2  }

   commuName	OBJECT-TYPE
		SYNTAX			OCTET STRING  ( SIZE ( 1 .. 12  ) )
		MAX-ACCESS		read-only
		STATUS			current
		DESCRIPTION		"SNMPv3 user name"
		::=  {  trapHostEntry  3  }
   traphostVer      OBJECT-TYPE
		SYNTAX			INTEGER
		MAX-ACCESS		read-write
		STATUS			current
		DESCRIPTION		"Traphost Version.
                                 0: clear the traphost config;
		                 1:  version 1;(only valid in the trap type).
		                 2: version 2c;
		                 3: version 3 using the AuthNoPriv security level;
		                 4: version 3 using the NoAuthNoPriv security level;
		                 5: version 3 using the AuthAndPriv security level. "
		::=  {  trapHostEntry  4  }

   trapEnable       OBJECT-TYPE
		SYNTAX			PortList
		MAX-ACCESS		read-write
		STATUS			current
		DESCRIPTION		"Set trap message enable or disable.The message is the following in turn:
		                 1.coldStartTrap;2.warmStartTrap;3.linkDownTrap;4.linkUpTrap;
		                 5. authFailTrap;6.topologyChangeTrap;7.memberUpDownTrap;
		                 8.portLoopdetectTrap;9. trunkLoopdetectTrap;10.dynamicMacExceedTrap;
		                 11.linkMonitorTrap;12.remoteLinkTrap;13.dyingGaspTrap;
		                 14.remoteDiscovery..."
		::=  {  snmpConfig  4  }

	timeAclTable	OBJECT-TYPE
		SYNTAX		SEQUENCE  OF  TimeAclEntry
		MAX-ACCESS	not-accessible
		STATUS		current
		DESCRIPTION	"A table containing time configuration for acl . "
		::=  {  acl        1 }

	timeAclEntry	OBJECT-TYPE
		SYNTAX		TimeAclEntry
		MAX-ACCESS	not-accessible
		STATUS		current
		DESCRIPTION	"Each entry contains all config of basic acl."
		INDEX		{  timeRangeName }
		::=  { timeAclTable 1 }

	TimeAclEntry  ::=  SEQUENCE {
		timeRangeName     OCTET STRING,
		timeRange         OCTET STRING
		}

	timeRangeName      OBJECT-TYPE
		SYNTAX			OCTET STRING  ( SIZE ( 1 .. 16  ) )
		MAX-ACCESS		not-accessible
		STATUS			current
		DESCRIPTION		"Timerange ID . The scope is 1-16 characters. "
		::=  {  timeAclEntry  1  }

	timeRange       OBJECT-TYPE
		SYNTAX			OCTET STRING  ( SIZE ( 0 .. 150  ) )
		MAX-ACCESS		read-write
		STATUS			current
		DESCRIPTION		"The format is Z(YYYYMMDD(?)*hh:mm-YYYYMMDD(?)*hh:mm);
                         Z takes the following value:
                         0:clear the timeRange ,no word followed;
                         1:monday;
                         2:tuesday;
                         3:wednesday;
                         4:thursday;
                         5:friday;
                         6:Saturday;
                         7:sunday;
                         8:day-working;
                         9:day-off;
                         10:daily;
                         11:absolute time;
                         YYYYMMDD is the format of date ,such as 20040208;
                                  If '?',means no limit;
                         hh:mm is the format of time,such as 01:55."
		::=  {  timeAclEntry   2  }

	basicAclTable	OBJECT-TYPE
		SYNTAX		SEQUENCE  OF  BasicAclEntry
		MAX-ACCESS	not-accessible
		STATUS		current
		DESCRIPTION	"A table containing basic acl configuration. "
		::=  {  acl        2 }

	basicAclEntry	OBJECT-TYPE
		SYNTAX		BasicAclEntry
		MAX-ACCESS	not-accessible
		STATUS		current
		DESCRIPTION	"Each entry contains all config of basic acl."
		INDEX		{  basicACLNo , basicRuleID }
		::=  { basicAclTable 1 }

	BasicAclEntry  ::=  SEQUENCE {
		basicACLNo          Unsigned32,
		basicRuleID         Unsigned32,
		ruleBasicStatus     INTEGER,
		ruleBasicACL        OCTET STRING
		}

	basicACLNo      OBJECT-TYPE
		SYNTAX			Unsigned32
		MAX-ACCESS		not-accessible
		STATUS			current
		DESCRIPTION		"Basic acl number . The scope is 1-99. "
		::=  {  basicAclEntry  1  }

	basicRuleID      OBJECT-TYPE
		SYNTAX			Unsigned32
		MAX-ACCESS		not-accessible
		STATUS			current
		DESCRIPTION		"RuleID in Basic acl number mode.  "
		::=  {  basicAclEntry  2  }

	ruleBasicStatus    OBJECT-TYPE
		SYNTAX			INTEGER  { enable ( 1 ) , disable ( 2 ) }
		MAX-ACCESS		read-write
		STATUS			current
		DESCRIPTION		"When the ruleID is cleared ,the status is disable."
		::=  {  basicAclEntry  3  }

	ruleBasicACL    OBJECT-TYPE
		SYNTAX			OCTET STRING
		MAX-ACCESS		read-write
		STATUS			current
		DESCRIPTION		"Basic acl config.
		                 The format is X-A.B.C.D/N-F.
                         X is 1:deny;2:permit;
                         'A.B.C.D/N'is source ip and mask.If 'x' means any;
                         F : 0 means no fragment set;1 means fragment set."
		::=  {  basicAclEntry  4  }

	extendedAclTable	OBJECT-TYPE
		SYNTAX		SEQUENCE  OF  ExtendedAclEntry
		MAX-ACCESS	not-accessible
		STATUS		current
		DESCRIPTION	"A table containing extended acl configuration. "
		::=  {  acl        3 }

	extendedAclEntry	OBJECT-TYPE
		SYNTAX		ExtendedAclEntry
		MAX-ACCESS	not-accessible
		STATUS		current
		DESCRIPTION	"Each entry contains all config of extended acl."
		INDEX		{  extendedACLNo , extendedRuleID  }
		::=  { extendedAclTable 1 }

	ExtendedAclEntry  ::=  SEQUENCE {
		extendedACLNo       Unsigned32,
		extendedRuleID      Unsigned32,
		ruleExtendedStatus     INTEGER,
	    ruleExtendedProtocol  OCTET STRING
		}

	extendedACLNo      OBJECT-TYPE
		SYNTAX			Unsigned32
		MAX-ACCESS		not-accessible
		STATUS			current
		DESCRIPTION		"Extended acl number .The scope is 100-199. "
		::=  {  extendedAclEntry  1  }

	extendedRuleID      OBJECT-TYPE
		SYNTAX			Unsigned32
		MAX-ACCESS		not-accessible
		STATUS			current
		DESCRIPTION		"RuleID in extended acl number mode. "
		::=  {  extendedAclEntry  2  }

	ruleExtendedStatus    OBJECT-TYPE
		SYNTAX			INTEGER  { enable ( 1 ) , disable ( 2 ) }
		MAX-ACCESS		read-write
		STATUS			current
		DESCRIPTION		"When the ruleID is cleared ,the status is disable."
		::=  {  extendedAclEntry  3  }

	ruleExtendedProtocol   OBJECT-TYPE
		SYNTAX			OCTET STRING
		MAX-ACCESS		read-write
		STATUS			current
		DESCRIPTION		"Extended acl config for other protocol.
		                 The format is P:RULE.
		                 P means protocol value,
		                 P is IC,known as icmp(1) protocol,
		                   the format of RULE is X-A.B.C.D/N-A.B.C.D/N-IC-C-D-F;
		                 P is I,known as ip protocol,
		                   the format of RULE is X-A.B.C.D/N-A.B.C.D/N-D-F;
		                 P is T,known as tcp(6) protocol,
		                   the format of RULE is X-A.B.C.D/N-S-A.B.C.D/N-DE-E-D-F;
		                 P is U,known as udp(17) protocol,
		                   the format of RULE is X-A.B.C.D/N-S-A.B.C.D/N-DE-D-F;
		                 P is A,known as arp protocol,
		                   the format of RULE is X-A.B.C.D/N-A.B.C.D/N;
		                 P is 0-255(except 1,6 and 17),known as protocol id 0-255(except 1,6 and 17),
		                   the format of RULE is X-A.B.C.D/N-A.B.C.D/N-D-F;
                                 If P is 1(ICMP),the format of RULE is X-A.B.C.D/N-A.B.C.D/N-IC-C-D-F;
                                 If P is 6(TCP),the format of RULE is X-A.B.C.D/N-S-A.B.C.D/N-DE-E-D-F;
                                 If P is 17(UDP),the format of RULE is X-A.B.C.D/N-S-A.B.C.D/N-DE-D-F;
		                 Here
                         X is 1:deny;2:permit;
                         the first A.B.C.D/N is source ip and mask.if 'x' means any;
                         the second A.B.C.D/N is destination ip and mask.if 'x' means any;
                         IC takes the value of 0-255;
                                0 means no icmp message type set;
                                1-255 means icmp message type (0-254) set ;
                         C takes the value of 0-255;
                                0 means no icmp code type set;
                                1-255 means icmp code type (0-254) set ;
                         E: 0 means tcp connectiong mode set;
                            1 means establishing set;2 means established set;
                         S takes the format of P*Q,P:
                              0: no source port set,Q is also 0;
                              1-65536: source port 0-65535 ,same scope for Q.
                         DE takes the format of P*Q,P:
                              0: no destination port set,Q is also 0;
                              1-65536: destination port 0-65535 ,same scope for Q.
                         D takes the value of 0-64;
                                0 means no dscp value set;
                                1-64 means dscp value (0-63) set ;
                         F : 0 means no fragment set;1 means fragment set."
		::=  {  extendedAclEntry  4  }

	linkAclTable	OBJECT-TYPE
		SYNTAX		SEQUENCE  OF  LinkAclEntry
		MAX-ACCESS	not-accessible
		STATUS		current
		DESCRIPTION	"A table containing link acl configuration. "
		::=  {  acl        4 }

	linkAclEntry	OBJECT-TYPE
		SYNTAX		LinkAclEntry
		MAX-ACCESS	not-accessible
		STATUS		current
		DESCRIPTION	"Each entry contains all config of link acl."
		INDEX		{  linkACLNo , linkRuleID }
		::=  { linkAclTable 1 }

	LinkAclEntry  ::=  SEQUENCE {
		linkACLNo         Unsigned32,
		linkRuleID        Unsigned32,
		ruleLinkStatus    INTEGER,
		ruleLinkProtocol  OCTET STRING
		}

	linkACLNo        OBJECT-TYPE
		SYNTAX			Unsigned32
		MAX-ACCESS		not-accessible
		STATUS			current
		DESCRIPTION		"Link acl number .The scope is 200-299. "
		::=  {  linkAclEntry  1  }

	linkRuleID        OBJECT-TYPE
		SYNTAX			Unsigned32
		MAX-ACCESS		not-accessible
		STATUS			current
		DESCRIPTION		"RuleID in link acl number mode . "
		::=  {  linkAclEntry  2  }

	ruleLinkStatus    OBJECT-TYPE
		SYNTAX			INTEGER  { enable ( 1 ) , disable ( 2 ) }
		MAX-ACCESS		read-write
		STATUS			current
		DESCRIPTION		"When the ruleID is cleared ,the status is disable."
		::=  {  linkAclEntry  3  }

	ruleLinkProtocol    OBJECT-TYPE
		SYNTAX			OCTET STRING
		MAX-ACCESS		read-write
		STATUS			current
		DESCRIPTION		"Link acl config for protocol.
		                 The format is P:RULE.
                                 P means protocol value,
                                 P is I,known as ip protocol,
                                   the format of RULE is X-C-V-M-SM-DM;
                                 P is A,known as arp protocol,
                                   the format of RULE is X-C-V-M-SM-DM;
                                 P is O,known as other,except ip and arp,
                                   the format of RULE is X-D-E-C-V-M-SM-DM;
                                 P is X, known as any,
                                   the format of RULE is X-C-V-M;
                                 Here
                         X is 1:deny;2:permit;
                                 D:0 means no select dsap-ssap and ether-type;
                                   1 means select dsap-ssap(0);2 means select ether-type(1);
                                 E takes the dsap-ssap(0-65535) or ether-type(1501-65535) value;
                                   0 means no dsap-ssap or ether-type set;
                                   if D is 1,1-65536 means dsap-ssap value(0-65535)set;
                                   if D is 2,1501-65535 means ether-type value set;
                         C:0 means no cos set;1-8 means cos value 0-7;
                         V:0 means no vlanID set;1-4094,vlanID;
                         M: 0 means no vlan mask set;1-65536 means vlan mask value(0x0000-0xffff)set;
                         SM: x means any;
                             y(HH.HH.HH.HH.HH.HH*HH.HH.HH.HH.HH.HH)
                             means source mac and mask;
                         DM: x means any;
                             y(HH.HH.HH.HH.HH.HH*HH.HH.HH.HH.HH.HH)
                             means destinatinon mac and mask."
		::=  {  linkAclEntry  4  }

    hybridAclTable	OBJECT-TYPE
		SYNTAX		SEQUENCE  OF  HybridAclEntry
		MAX-ACCESS	not-accessible
		STATUS		current
		DESCRIPTION	"A table containing hybrid acl configuration. "
		::=  {  acl        5 }

	hybridAclEntry	OBJECT-TYPE
		SYNTAX		HybridAclEntry
		MAX-ACCESS	not-accessible
		STATUS		current
		DESCRIPTION	"Each entry contains all config of hybrid acl."
		INDEX		{  hybridACLNo , hybridRuleID }
		::=  { hybridAclTable 1 }

	HybridAclEntry  ::=  SEQUENCE {
		hybridACLNo         Unsigned32,
		hybridRuleID        Unsigned32,
		ruleHybridStatus    INTEGER,
		ruleHybridProtocol  OCTET STRING
		}

	hybridACLNo        OBJECT-TYPE
		SYNTAX			Unsigned32
		MAX-ACCESS		not-accessible
		STATUS			current
		DESCRIPTION		"Hybrid acl number .The scope is 300-399. "
		::=  {  hybridAclEntry  1  }

	hybridRuleID        OBJECT-TYPE
		SYNTAX			Unsigned32
		MAX-ACCESS		not-accessible
		STATUS			current
		DESCRIPTION		"RuleID in hybrid acl number mode. "
		::=  {  hybridAclEntry  2  }

	ruleHybridStatus    OBJECT-TYPE
		SYNTAX			INTEGER  { enable ( 1 ) , disable ( 2 ) }
		MAX-ACCESS		read-write
		STATUS			current
		DESCRIPTION		"When the ruleID is cleared ,the status is disable."
		::=  {  hybridAclEntry  3  }

	ruleHybridProtocol  OBJECT-TYPE
		SYNTAX			OCTET STRING
		MAX-ACCESS		read-write
		STATUS			current
		DESCRIPTION		"Hybrid acl config. This table does not support IPV6.
		                 The format is P:RULE.
		                 P means protocol value,
		                 P is I,known as ip protocol,
		                   the format of RULE is X-A.B.C.D/N-A.B.C.D/N-D-F-C-V-M-SM-DM;
		                 P is T,known as tcp(6) protocol,
		                   the format of RULE is X-A.B.C.D/N-S-A.B.C.D/N-DE-D-F-C-V-M-SM-DM;
		                 P is U,known as udp(17) protocol,
		                   the format of RULE is X-A.B.C.D/N-S-A.B.C.D/N-DE-D-F-C-V-M-SM-DM;
		                 P is A,known as arp protocol,
		                   the format of RULE is X-A.B.C.D/N-A.B.C.D/N-C-V-M-SM-DM;
                                 P is X,means as any,
                                   the format of RULE is X-E-C-V-M-SM-DM;
		                 P is 0-255(except 6 and 17),known as protocol id 0-255(except 6 and 17),
		                   the format of RULE is X-A.B.C.D/N-A.B.C.D/N-D-F-C-V-M-SM-DM;
                                 If P is 6(TCP),the format of RULE is X-A.B.C.D/N-S-A.B.C.D/N-DE-D-F-C-V-M-SM-DM;
                                 If P is 17(UDP),the format of RULE is X-A.B.C.D/N-S-A.B.C.D/N-DE-D-F-C-V-M-SM-DM;
		                 Here
                         X is 1:deny;2:permit;
                         The first A.B.C.D/N is source ip and mask.if 'x' means any;
                         The second A.B.C.D/N is destination ip and mask.if 'x' means any;
                         S takes the format of P*Q,P:
                              0: no source port set,Q is also 0;
                              1-65536: source port 0-65535 ,same scope for Q.
                         DE takes the format of P*Q,P:
                              0: no destination port set,Q is also 0;
                              1-65536: destination port 0-65535 ,same scope for Q.
                         E takes the ethernet-type of 1501-65535;
                           0 means no ethernet-type set;
                           1501-65535 means ethernet-type;
                         D takes the value of 0-64;
                                0 means no dscp set;
                                1-64 means dscp value (0-63) set ;
                         F: 0 means no fragment set;1 means fragment set;
                         C: 0 means no cos set;1-8 means cos value 0-7;
                         V: 0 means no vlanID set;1-4094,vlanID;
                         M: 0 means no vlan mask set;1-65536 means vlan mask value(0x0000-0xffff)set;
                         SM:x means any;
                            y(HH.HH.HH.HH.HH.HH*HH.HH.HH.HH.HH.HH)
                              means source mac and mask;
                         DM:x means any;
                            y(HH.HH.HH.HH.HH.HH*HH.HH.HH.HH.HH.HH)
                              means destinatinon mac and mask."
		::=  {  hybridAclEntry  4  }

        globalAclTable	OBJECT-TYPE
		SYNTAX		SEQUENCE  OF  GlobalAclEntry
		MAX-ACCESS	not-accessible
		STATUS		current
		DESCRIPTION	"A table containing global acl configuration. "
		::=  {  acl        6 }

	globalAclEntry	OBJECT-TYPE
		SYNTAX		GlobalAclEntry
		MAX-ACCESS	not-accessible
		STATUS		current
		DESCRIPTION	"Each entry contains all config of global acl."
		INDEX		{  globalACLNo , globalRuleID }
		::=  { globalAclTable 1 }

	GlobalAclEntry  ::=  SEQUENCE {
		globalACLNo         Unsigned32,
		globalRuleID        Unsigned32,
		ruleGlobalStatus    INTEGER,
		ruleGlobalProtocol  OCTET STRING
		}

	globalACLNo        OBJECT-TYPE
		SYNTAX			Unsigned32
		MAX-ACCESS		not-accessible
		STATUS			current
		DESCRIPTION		"Global acl number(400) . "
		::=  {  globalAclEntry  1  }

	globalRuleID        OBJECT-TYPE
		SYNTAX			Unsigned32
		MAX-ACCESS		not-accessible
		STATUS			current
		DESCRIPTION		"RuleID in global acl number mode. The scope is 1-16"
		::=  {  globalAclEntry  2  }

	ruleGlobalStatus    OBJECT-TYPE
		SYNTAX			INTEGER  { enable ( 1 ) , disable ( 2 ) }
		MAX-ACCESS		read-write
		STATUS			current
		DESCRIPTION		"When the ruleID is cleared ,the status is disable."
		::=  {  globalAclEntry  3  }

	ruleGlobalProtocol  OBJECT-TYPE
		SYNTAX			OCTET STRING
		MAX-ACCESS		read-write
		STATUS			current
		DESCRIPTION		"Global acl config for protocol.
		                 The format is P:RULE.
		                 P means protocol value,
		                 P is I,known as ip protocol,
		                   the format of RULE is X-PI-A.B.C.D/N-A.B.C.D/N-D-F-C-V-M-SM-DM;
		                 P is T,known as tcp(6) protocol,
		                   the format of RULE is X-PI-A.B.C.D/N-S-A.B.C.D/N-DE-D-F-C-V-M-SM-DM;
		                 P is U,known as udp(17) protocol,
		                   the format of RULE is X-PI-A.B.C.D/N-S-A.B.C.D/N-DE-D-F-C-V-M-SM-DM;
		                 P is A,known as arp protocol,
		                   the format of RULE is X-PI-A.B.C.D/N-A.B.C.D/N-C-V-M-SM-DM;
                                 P is X,means as any,
                                   the format of RULE is X-PI-E-C-V-M-SM-DM;
		                 P is 0-255(except 6 and 17),known as protocol id 0-255(except 6 and 17),
		                   the format of RULE is X-PI-A.B.C.D/N-A.B.C.D/N-D-F-C-V-M-SM-DM;
                                 If P is 6(TCP),the format of RULE is X-PI-A.B.C.D/N-S-A.B.C.D/N-DE-D-F-C-V-M-SM-DM;
                                 If P is 17(UDP),the format of RULE is X-PI-A.B.C.D/N-S-A.B.C.D/N-DE-D-F-C-V-M-SM-DM;
		                 RULE here:
                         X is 1:deny;2:permit;
                         PI takes portid;x means any port;
                         The first A.B.C.D/N is source ip and mask.if 'x' means any;
                         The second A.B.C.D/N is destination ip and mask.if 'x' means any;
                         S takes the format of P*Q,P:
                              0: no source port set,Q is also 0;
                              1-65536: source port 0-65535 ,same scope for Q.
                         DE takes the format of P*Q,P:
                              0: no destination port set,Q is also 0;
                              1-65536: destination port 0-65535 ,same scope for Q.
                         E takes the ethernet-type of 1501-65535;
                           0 means no ethernet-type set;
                           1501-65535 means ethernet-type;
                         D takes the value of 0-64;
                                0 means no dscp set;
                                1-64 means dscp value (0-63) set ;
                         F: 0 means no fragment set;1 means fragment set;
                         C: 0 means no cos set;1-8 means cos value 0-7;
                         V: 0 means no vlanID set;1-4094,vlanID;
                         M: 0 means no vlan mask set;1-65536 means vlan mask value(0x0000-0xffff)set;
                         SM:x means any;
                            y(HH.HH.HH.HH.HH.HH*HH.HH.HH.HH.HH.HH)
                              means source mac and mask;
                         DM:x means any;
                            y(HH.HH.HH.HH.HH.HH*HH.HH.HH.HH.HH.HH)
                              means destinatinon mac and mask."
		::=  {  globalAclEntry  4  }

	fdbAgingTime	OBJECT-TYPE
	SYNTAX			Integer32  ( 40 .. 1260  )
	MAX-ACCESS		read-write
	STATUS			current
	DESCRIPTION		"fdb aging time (unit:second).The deault value is 240."
	::= {  fdb  1  }

	fdbFilterTable OBJECT-TYPE
    SYNTAX      SEQUENCE OF FdbFilterEntry
    MAX-ACCESS  not-accessible
    STATUS      current
    DESCRIPTION
        "A table that contains configuration and control
        information for each Filtering macaddress
        operating on this device.  "
    ::= { fdb 2 }

	fdbFilterEntry OBJECT-TYPE
    SYNTAX      FdbFilterEntry
    MAX-ACCESS  not-accessible
    STATUS      current
    DESCRIPTION
        "Information about a specific Filtering Database."
    INDEX   { fdbID ,fdbFilterAddress}
    ::= { fdbFilterTable 1 }

	FdbFilterEntry  ::=  SEQUENCE {
        fdbID
            Unsigned32,
        fdbFilterAddress
            MacAddress,
        fdbFilterType
            INTEGER
    }

	fdbID OBJECT-TYPE
    SYNTAX       Unsigned32
    MAX-ACCESS   not-accessible
    STATUS       current
    DESCRIPTION
        "The identity of this Filtering Database."
    ::= { fdbFilterEntry 1 }

	fdbFilterAddress OBJECT-TYPE
    SYNTAX      MacAddress
    MAX-ACCESS  not-accessible
    STATUS      current
    DESCRIPTION
        "A filter MAC address for which the device has
        filtering information."
    ::= { fdbFilterEntry 2 }

	fdbFilterType OBJECT-TYPE
    SYNTAX       INTEGER  { both ( 1 ),clear (2)}
    MAX-ACCESS   read-write
    STATUS       current
    DESCRIPTION
        "The current type for the filtering macaddress."
    ::= { fdbFilterEntry 3 }

    fdbStaticPortTable OBJECT-TYPE
    SYNTAX      SEQUENCE OF FdbStaticPortEntry
    MAX-ACCESS  not-accessible
    STATUS      current
    DESCRIPTION
        "A table that contains configuration and control
        information for each static macaddress
        operating on this device.  "
    ::= { fdb 3 }

	fdbStaticPortEntry OBJECT-TYPE
    SYNTAX      FdbStaticPortEntry
    MAX-ACCESS  not-accessible
    STATUS      current
    DESCRIPTION
        "Information about a specific Filtering Database."
    INDEX   { fdbID ,fdbStaticAddress}
    ::= { fdbStaticPortTable 1 }

	FdbStaticPortEntry  ::=  SEQUENCE {
        fdbStaticAddress
            MacAddress,
        portBindMac
            Unsigned32
    }

	fdbStaticAddress OBJECT-TYPE
    SYNTAX      MacAddress
    MAX-ACCESS  not-accessible
    STATUS      current
    DESCRIPTION
        "A filter MAC address for which the device has
        filtering information."
    ::= { fdbStaticPortEntry 2 }

	portBindMac OBJECT-TYPE
    SYNTAX       Unsigned32
    MAX-ACCESS   read-write
    STATUS       current
    DESCRIPTION
        "The port id which binding macaddress and fid.If 0 means clear the fdb entry."
    ::= { fdbStaticPortEntry 3 }

    fdbStaticTrunkTable OBJECT-TYPE
    SYNTAX      SEQUENCE OF FdbStaticTrunkEntry
    MAX-ACCESS  not-accessible
    STATUS      current
    DESCRIPTION
        "A table that contains configuration and control
        information for each static macaddress
        operating on this device.  "
    ::= { fdb 4 }

	fdbStaticTrunkEntry OBJECT-TYPE
    SYNTAX      FdbStaticTrunkEntry
    MAX-ACCESS  not-accessible
    STATUS      current
    DESCRIPTION
        "Information about a specific Filtering Database."
    INDEX   { fdbID ,fdbStaticAddress}
    ::= { fdbStaticTrunkTable 1 }

	FdbStaticTrunkEntry  ::=  SEQUENCE {
        trunkBindMac
            Unsigned32
    }

	trunkBindMac OBJECT-TYPE
    SYNTAX       Unsigned32
    MAX-ACCESS   read-write
    STATUS       current
    DESCRIPTION
        "The trunk id which binding macaddress and fid.If 0 means clear the fdb entry."
    ::= { fdbStaticTrunkEntry 3 }

    p8021xRelayAdminStatus	OBJECT-TYPE
		SYNTAX			INTEGER  { enable ( 1 ) , disable ( 2 ) , invalid( 3 ) }
		MAX-ACCESS		read-write
		STATUS			current
		DESCRIPTION		"Description"
		::=  {  p8021xRelay  1  }

    --
	multiGroupTable	OBJECT-TYPE
		SYNTAX		SEQUENCE  OF  MultiGroupEntry
		MAX-ACCESS	not-accessible
		STATUS		current
		DESCRIPTION	" A list of pvlan entries. The number of
                    entries is given by the value of session number. "
		::=  { igmpSnooping  1 }

	multiGroupEntry	OBJECT-TYPE
		SYNTAX		MultiGroupEntry
		MAX-ACCESS	not-accessible
		STATUS		current
		DESCRIPTION	"Multicast group entry. "
		INDEX		{  number  }
		::=  { multiGroupTable 1 }

	MultiGroupEntry  ::=  SEQUENCE {
		number          Unsigned32,
		vlanID          Unsigned32,
		multiGroup     IpAddress,
		portList        PortList,
		trunkList        PortList
		}

	number      OBJECT-TYPE
		SYNTAX			Unsigned32
		MAX-ACCESS		not-accessible
		STATUS			current
		DESCRIPTION		"The number of multicast group"
		::=  {  multiGroupEntry  1  }

	vlanID      OBJECT-TYPE
		SYNTAX			Unsigned32
		MAX-ACCESS		read-only
		STATUS			current
		DESCRIPTION		"Vlan id"
		::=  {  multiGroupEntry  2  }

	multiGroup OBJECT-TYPE
		SYNTAX			IpAddress
		MAX-ACCESS		read-only
		STATUS			current
		DESCRIPTION		"Multicast group ipAddress"
		::=  {  multiGroupEntry  3  }

	portList    OBJECT-TYPE
		SYNTAX			PortList
		MAX-ACCESS		read-only
		STATUS			current
		DESCRIPTION		"ports of the muliticast group"
		::=  {  multiGroupEntry  4  }

       trunkList    OBJECT-TYPE
		SYNTAX			PortList
		MAX-ACCESS		read-only
		STATUS			current
		DESCRIPTION		"trunks of the muliticast group"
		::=  {  multiGroupEntry  5  }

--	portPonStatus	    OBJECT-TYPE
--		SYNTAX			INTEGER  { enable ( 1 ) , disable ( 2 ) }
--		MAX-ACCESS		read-write
--		STATUS			current
--		DESCRIPTION		"Onu port pon status."
--		::=  {  epon  1  }

	ponReset	OBJECT-TYPE
		SYNTAX			INTEGER { reset(1) }
		MAX-ACCESS		read-write
		STATUS			current
		DESCRIPTION		" The value get from this item is insignificant.
                                         Setting this item will reset onu. "
		::=  {  epon  2  }

        portPonInfo   	OBJECT IDENTIFIER ::=  { epon  3 }

	portPonAdminStatus   	OBJECT-TYPE
		SYNTAX			INTEGER  { up ( 1 ) , down ( 2 ) }
		MAX-ACCESS	        read-only
		STATUS			current
		DESCRIPTION	" Port pon status ."
		::=  { portPonInfo  1 }

        portPonStpState   	OBJECT-TYPE
		SYNTAX			OCTET STRING
		MAX-ACCESS	        read-only
		STATUS			current
		DESCRIPTION	" Port pon stp state ."
		::=  { portPonInfo  2 }

	portPonFecTx   	OBJECT-TYPE
		SYNTAX			INTEGER
		MAX-ACCESS	        read-only
		STATUS			current
		DESCRIPTION	" Port pon Fec Tx ."
		::=  { portPonInfo  3 }

	portPonFecRx   	OBJECT-TYPE
		SYNTAX			INTEGER
		MAX-ACCESS	        read-only
		STATUS			current
		DESCRIPTION	" Port pon Fec Tx . "
		::=  { portPonInfo  4 }

	portPonType   	OBJECT-TYPE
		SYNTAX			OCTET STRING
		MAX-ACCESS	        read-only
		STATUS			current
		DESCRIPTION	" Port pon type. "
		::=  { portPonInfo  5 }

	portPonOperStatus   	OBJECT-TYPE
		SYNTAX			INTEGER  { up ( 1 ) , down ( 2 ) }
		MAX-ACCESS	        read-only
		STATUS			current
		DESCRIPTION	" Port pon oper status."
		::=  { portPonInfo  6 }

	portPonLlidPortsNum    OBJECT-TYPE
		SYNTAX			INTEGER
		MAX-ACCESS	        read-only
		STATUS			current
		DESCRIPTION	"Port pon llid ports num . "
		::=  { portPonInfo  7 }

	ponOamInfo   	OBJECT IDENTIFIER ::=  { epon  4 }

	localOamAdmin   	OBJECT-TYPE
		SYNTAX			INTEGER
		MAX-ACCESS	        read-only
		STATUS			current
		DESCRIPTION	" Pon local oam admin ."
		::=  { ponOamInfo   1 }

	localOamOper   	OBJECT-TYPE
		SYNTAX			INTEGER
		MAX-ACCESS	        read-only
		STATUS			current
		DESCRIPTION	" Pon local oam  oper ."
		::=  { ponOamInfo   2 }

	localOamMode   	OBJECT-TYPE
		SYNTAX			INTEGER
		MAX-ACCESS	        read-only
		STATUS			current
		DESCRIPTION	" Pon local oam mode ."
		::=  { ponOamInfo   3 }

	localOamMaxPdu   	OBJECT-TYPE
		SYNTAX			INTEGER
		MAX-ACCESS	        read-only
		STATUS			current
		DESCRIPTION	" Pon local oam max oampdu."
		::=  { ponOamInfo   4 }

	localOamRevision   	OBJECT-TYPE
		SYNTAX			INTEGER
		MAX-ACCESS	        read-only
		STATUS			current
		DESCRIPTION	" Pon local oam  revision."
		::=  { ponOamInfo   5 }

	localOamFuncSupport   	OBJECT-TYPE
		SYNTAX			INTEGER
		MAX-ACCESS	        read-only
		STATUS			current
		DESCRIPTION	" Pon local oam funcsupport."
		::=  { ponOamInfo   6 }

	peerOamStatus   	OBJECT-TYPE
		SYNTAX			INTEGER
		MAX-ACCESS	        read-only
		STATUS			current
		DESCRIPTION	" Pon peer oam status. "
		::=  { ponOamInfo   7 }

	peerOamMacAddr   	OBJECT-TYPE
		SYNTAX			MacAddress
		MAX-ACCESS	        read-only
		STATUS			current
		DESCRIPTION	" Pon peer oam macaddr ."
		::=  { ponOamInfo   8 }

	peerOamOUI   	OBJECT-TYPE
		SYNTAX			OCTET STRING
		MAX-ACCESS	        read-only
		STATUS			current
		DESCRIPTION	" Pon peer oam OUI ."
		::=  { ponOamInfo   9 }

	peerOamVendor   	OBJECT-TYPE
		SYNTAX			INTEGER
		MAX-ACCESS	        read-only
		STATUS			current
		DESCRIPTION	" Pon peer oam vendor."
		::=  { ponOamInfo   10 }

	peerOamMode   	OBJECT-TYPE
		SYNTAX			INTEGER
		MAX-ACCESS	        read-only
		STATUS			current
		DESCRIPTION	" Pon peer oam mode ."
		::=  { ponOamInfo   11 }

	peerOamMaxPdu   	OBJECT-TYPE
		SYNTAX			INTEGER
		MAX-ACCESS	        read-only
		STATUS			current
		DESCRIPTION	" Pon peer oam max oampdu ."
		::=  { ponOamInfo   12 }

	peerOamRevision   	OBJECT-TYPE
		SYNTAX			INTEGER
		MAX-ACCESS	        read-only
		STATUS			current
		DESCRIPTION	" Pon peer oam revision. "
		::=  { ponOamInfo   13 }

	peerOamFuncSupport   	OBJECT-TYPE
		SYNTAX			INTEGER
		MAX-ACCESS	        read-only
		STATUS			current
		DESCRIPTION	" Pon peer oam funcsupport . "
		::=  { ponOamInfo   14 }

	ponLoopbackStatus   	OBJECT-TYPE
		SYNTAX			OCTET STRING
		MAX-ACCESS	        read-only
		STATUS			current
		DESCRIPTION	" Onu pon loopback status ."
		::=  { ponOamInfo   15 }

	ponFirmwareInfo	OBJECT IDENTIFIER ::=  { epon  5 }

	eponStatus   	OBJECT-TYPE
		SYNTAX			INTEGER{ registered( 1 ),deregistered( 2 ),discovered( 3 ),lost( 4 ),unknown( 5 ) }
		MAX-ACCESS	        read-only
		STATUS			current
		DESCRIPTION	" Epon status. "
		::=  { ponFirmwareInfo 1 }

	softWareVersion   	OBJECT-TYPE
		SYNTAX			OCTET STRING
		MAX-ACCESS	        read-only
		STATUS			current
		DESCRIPTION	" Epon software version . The format is MA.MI.RE-BU ."
		::=  { ponFirmwareInfo 2 }

	loaderVersion   	OBJECT-TYPE
		SYNTAX			OCTET STRING
		MAX-ACCESS	        read-only
		STATUS			current
		DESCRIPTION	"  Epon loader version .The format is MA.MI.RE-BU ."
		::=  { ponFirmwareInfo 3 }

	registerOltInfo   	OBJECT-TYPE
		SYNTAX			OCTET STRING
		MAX-ACCESS	        read-only
		STATUS			current
		DESCRIPTION	" Epon register olt information .The format is ID-LL-PP ."
		::=  { ponFirmwareInfo 4 }

	registerOnuInfo   	OBJECT-TYPE
		SYNTAX			OCTET STRING
		MAX-ACCESS	        read-only
		STATUS			current
		DESCRIPTION	" Epon register onu information mac .
The format is MA0:MA1:MA2:MA3:MA4:MA5-LL ."
		::=  { ponFirmwareInfo 5 }

	portNum   	OBJECT-TYPE
		SYNTAX			INTEGER
		MAX-ACCESS	        read-only
		STATUS			current
		DESCRIPTION	" Epon port num ."
		::=  { ponFirmwareInfo 6 }

	registered	OBJECT-TYPE
		SYNTAX			INTEGER{ yes( 1 ),no( 2 )}
		MAX-ACCESS	        read-only
		STATUS			current
		DESCRIPTION	" Registered ."
		::=  { ponFirmwareInfo 7 }

	authenticated	OBJECT-TYPE
		SYNTAX			INTEGER{ yes( 1 ),no( 2 )}
		MAX-ACCESS	        read-only
		STATUS			current
		DESCRIPTION	" Authenticated ."
		::=  { ponFirmwareInfo 8 }

	ponConfigMac   	OBJECT-TYPE
		SYNTAX			MacAddress
		MAX-ACCESS	        read-only
		STATUS			current
		DESCRIPTION	" Pon config macaddr ."
		::=  { ponFirmwareInfo  9 }

	modeAndOamVer	OBJECT-TYPE
		SYNTAX			INTEGER
		MAX-ACCESS	        read-only
		STATUS			current
		DESCRIPTION	" Modes and Oam Version ."
		::=  { ponFirmwareInfo 10 }

	mpcpTimeout	OBJECT-TYPE
		SYNTAX			INTEGER
		MAX-ACCESS	        read-only
		STATUS			current
		DESCRIPTION	" Mpcp Timeout ."
		::=  { ponFirmwareInfo 11 }

	ctrlVlan	OBJECT-TYPE
		SYNTAX			INTEGER
		MAX-ACCESS	        read-only
		STATUS			current
		DESCRIPTION	" Ctrl Vlan ."
		::=  { ponFirmwareInfo 12 }

	vendPonUni   	OBJECT-TYPE
		SYNTAX			OCTET STRING
		MAX-ACCESS	        read-only
		STATUS			current
		DESCRIPTION	" The format is VC-PC-UC .
VC means vendor code value;
PC means pon config value;
UC means uni config value."
		::=  { ponFirmwareInfo 13 }

	ctcOui   	OBJECT-TYPE
		SYNTAX			OCTET STRING
		MAX-ACCESS	        read-only
		STATUS			current
		DESCRIPTION	" ctc Oui. "
		::=  { ponFirmwareInfo 14 }

	ctcVendor   	OBJECT-TYPE
		SYNTAX			OCTET STRING
		MAX-ACCESS	        read-only
		STATUS			current
		DESCRIPTION	" Ctc Vendor "
		::=  { ponFirmwareInfo 15 }

	ctcModel   	OBJECT-TYPE
		SYNTAX			OCTET STRING
		MAX-ACCESS	        read-only
		STATUS			current
		DESCRIPTION	" Ctc Model ."
		::=  { ponFirmwareInfo 16 }

	ethernetOamStatus	    OBJECT-TYPE
		SYNTAX			INTEGER  { enable ( 1 ) , disable ( 2 ) }
		MAX-ACCESS		read-write
		STATUS			current
		DESCRIPTION		"The desired state of the ethernetOam."
		::=  {  ethernetOam  1  }

	ethernetOamOuiDescr OBJECT-TYPE
		SYNTAX			OCTET STRING
		MAX-ACCESS		read-write
		STATUS			current
		DESCRIPTION		"Set organizationally unique identifier.
		The format of this item is xx-xx-xx, default:00-15-EB."
		::=  {  ethernetOam  2  }

	orgSpecificTimeStamp	    OBJECT-TYPE
		SYNTAX			INTEGER
		MAX-ACCESS		read-write
		STATUS			current
		DESCRIPTION		"Set link event time stamp for link monitor.
		The scope is 1-10, default:10(100ms)."
		::=  {  ethernetOam  3  }

	remoteLoopbackTimeout	    OBJECT-TYPE
		SYNTAX			INTEGER
		MAX-ACCESS		read-write
		STATUS			current
		DESCRIPTION		"Set Ethernet Oam remote loopback timeout.
		The scope is 1-10, default:3(s). Suggest three times than
		loopback ports period."
		::=  {  ethernetOam  4  }

	ethernetOamIfConfigTable	OBJECT-TYPE
		SYNTAX		SEQUENCE  OF  EthernetOamIfConfigEntry
		MAX-ACCESS	not-accessible
		STATUS		current
		DESCRIPTION	"Config port's ethernet oam."
		::=  { ethernetOam  5 }

	ethernetOamIfConfigEntry	OBJECT-TYPE
		SYNTAX		EthernetOamIfConfigEntry
		MAX-ACCESS	not-accessible
		STATUS		current
		DESCRIPTION	""
		INDEX		{  portId  }
		::=  { ethernetOamIfConfigTable 1 }

	EthernetOamIfConfigEntry  ::=  SEQUENCE {
		ethernetOamIfStatus                       INTEGER,
		remoteLoopbackIfStatus                    INTEGER,
		ifPeriodTimeoutMode                       OCTET STRING,
		ifLinkMonitorStatus                       INTEGER,
		ifLinkSymbolPeriodThresholdWindow         OCTET STRING,
		ifLinkFrameThresholdWindow                OCTET STRING,
		ifLinkFramePeriodThresholdWindow          OCTET STRING,
		ifLinkFrameSecondsThresholdWindow         OCTET STRING
		}

	ethernetOamIfStatus      OBJECT-TYPE
		SYNTAX			INTEGER { enable ( 1 ) , disable ( 2 ) }
		MAX-ACCESS		read-write
		STATUS			current
		DESCRIPTION		"Config port's ethernet oam enable or disable."
		::=  {  ethernetOamIfConfigEntry  2  }

	remoteLoopbackIfStatus      OBJECT-TYPE
		SYNTAX			INTEGER{ start ( 1 ) , stop ( 2 ) }
		MAX-ACCESS		read-write
		STATUS			current
		DESCRIPTION		"start or stop port remote loopback."
		::=  {  ethernetOamIfConfigEntry  3  }

	ifPeriodTimeoutMode         OBJECT-TYPE
		SYNTAX			OCTET STRING
		MAX-ACCESS		read-write
		STATUS			current
		DESCRIPTION		"set ethernet oam discovery period, link timeout and discovery mode.
		The format is P-T-M .
		P : set ethernet oam discovery period time. The scope is 1-10, default:10(100ms);
		T : set ethernet oam link timeout time. The scope is 2-20 , default:5(s);
		M : set ethernet oam discovery mode active or passive, default:active;
		    1 takes the discovery mode active; 2 takes the discovery mode passive;
		For example: 3-14-2
		means:
		set ethernet oam discovery period time is 3,
		set ethernet oam link timeout time is 14,
		set ethernet oam discovery mode passive ."
		::=  {  ethernetOamIfConfigEntry  4  }

	ifLinkMonitorStatus    OBJECT-TYPE
		SYNTAX			INTEGER { enable ( 1 ) , disable ( 2 ) }
		MAX-ACCESS		read-write
		STATUS			current
		DESCRIPTION		"Config link monitor enable or disable."
		::=  {  ethernetOamIfConfigEntry  5  }

	ifLinkSymbolPeriodThresholdWindow    OBJECT-TYPE
		SYNTAX			OCTET STRING
		MAX-ACCESS		read-write
		STATUS			current
		DESCRIPTION		"Config link monitor symbol-period threshold and window.
		The format is T-W .
		T : set symbol period threshold. The scope is 1-65535, default:1 ;
		W : set symbol period window. The scope is 1-65535,default:1(million symbols);
	  For example: 300-40
		means:
		set symbol period threshold 300 ;
		set symbol period window 40 ;"
		::=  {  ethernetOamIfConfigEntry  6  }

	ifLinkFrameThresholdWindow    OBJECT-TYPE
		SYNTAX			OCTET STRING
		MAX-ACCESS		read-write
		STATUS			current
		DESCRIPTION		"Config link monitor frame threshold and window .
		The format is T-W .
		T : set frame threshold.The scope is 1-65535, default:1 ;
		W : set frame window. The scope is 1-60,default:1(s);
	  For example: 300-40
		means:
		set frame threshold 300 ;
		set frame window 40 ;"
		::=  {  ethernetOamIfConfigEntry  7  }


	ifLinkFramePeriodThresholdWindow    OBJECT-TYPE
		SYNTAX			OCTET STRING
		MAX-ACCESS		read-write
		STATUS			current
		DESCRIPTION		"Config link monitor frame-period threshold and window .
		The format is T-W .
		T : set frame period threshold. The scope is 1-65535, default:1 ;
		W : set frame period window.The scope is 1-600000, default:100(ten thousand frames);
	  For example: 300-40
		means:
		set frame period threshold 300 ;
		set frame period window 40 ;"
		::=  {  ethernetOamIfConfigEntry  8  }

	ifLinkFrameSecondsThresholdWindow      OBJECT-TYPE
		SYNTAX			OCTET STRING
		MAX-ACCESS		read-write
		STATUS			current
		DESCRIPTION		"Config link monitor frame-seconds threshold and window .
		The format is T-W .
		T : set frame seconds threshold. The scope is 1-900, default:1(s) ;
		W : set frame seconds window.The scope is 10-900,default:60(s);
	  For example: 300-40
		means:
		set frame seconds threshold 300 ;
		set frame seconds window 40 ;"
		::=  {  ethernetOamIfConfigEntry  9  }

	ethernetOamShowTable	OBJECT-TYPE
		SYNTAX		SEQUENCE  OF  EthernetOamShowEntry
		MAX-ACCESS	not-accessible
		STATUS		current
		DESCRIPTION
		"Show ethernet oam configuration information"
		::=  { ethernetOam 6 }

	ethernetOamShowEntry	OBJECT-TYPE
		SYNTAX		EthernetOamShowEntry
		MAX-ACCESS	not-accessible
		STATUS		current
		DESCRIPTION     ""
		INDEX		{  portId  }
		::=  { ethernetOamShowTable 1 }

	EthernetOamShowEntry  ::=  SEQUENCE {
		ethernetOamShowDiscovery    OCTET STRING,
		ethernetOamShowLinkMonitor  OCTET STRING,
		ethernetOamShowStatistics   OCTET STRING
		}

	ethernetOamShowDiscovery 	OBJECT-TYPE
		SYNTAX		OCTET STRING
		MAX-ACCESS	read-only
		STATUS		current
		DESCRIPTION
		" Show ethernet oam discovery information. "
		::=  { ethernetOamShowEntry 2 }

	ethernetOamShowLinkMonitor	OBJECT-TYPE
		SYNTAX		OCTET STRING
		MAX-ACCESS	read-only
		STATUS		current
		DESCRIPTION
		" Show ethernet oam statistics information. "
		::=  { ethernetOamShowEntry 3 }

	ethernetOamShowStatistics  	OBJECT-TYPE
		SYNTAX		OCTET STRING
		MAX-ACCESS	read-only
		STATUS		current
		DESCRIPTION
		" Show ethernet oam link monitor information. "
		::=  { ethernetOamShowEntry 4 }

	linkMonitorSymbolPeriodTrap	NOTIFICATION-TYPE
		OBJECTS			{ portId, switchMac, remoteMAC }
		STATUS			current
		DESCRIPTION		"The trap indicates nms that link monitor symbol period status."
		::=  {  ethernetOam  7 }

	linkMonitorFrameTrap	NOTIFICATION-TYPE
		OBJECTS			{ portId, switchMac, remoteMAC }
		STATUS			current
		DESCRIPTION		"The trap indicates nms that link monitor frame status."
		::=  {  ethernetOam  8 }

	linkMonitorFramePeriodTrap	NOTIFICATION-TYPE
		OBJECTS			{ portId, switchMac, remoteMAC }
		STATUS			current
		DESCRIPTION		"The trap indicates nms that link monitor frame period status."
		::=  {  ethernetOam  9 }

	linkMonitorFrameSecondsTrap	NOTIFICATION-TYPE
		OBJECTS			{ portId, switchMac, remoteMAC }
		STATUS			current
		DESCRIPTION		"The trap indicates nms that link monitor frame seconds status."
		::=  {  ethernetOam  10 }

	remoteLinkFailTrap	NOTIFICATION-TYPE
		OBJECTS			{ portId, switchMac, remoteMAC }
		STATUS			current
		DESCRIPTION		"The trap indicates nms that remote link Fail."
		::=  {  ethernetOam  11 }

	remoteLinkOKTrap	NOTIFICATION-TYPE
		OBJECTS			{ portId, switchMac, remoteMAC }
		STATUS			current
		DESCRIPTION		"The trap indicates nms that remote link OK."
		::=  {  ethernetOam  12 }

	dyingGaspTrap	NOTIFICATION-TYPE
		OBJECTS			{ portId, switchMac, remoteMAC }
		STATUS			current
		DESCRIPTION		"The trap indicates nms that dying gasp status."
		::=  {  ethernetOam  13 }

	remoteDiscoveryFailTrap	NOTIFICATION-TYPE
		OBJECTS			{ portId, switchMac, remoteMAC }
		STATUS			current
		DESCRIPTION		"The trap indicates nms that remote discovery Fail."
		::=  {  ethernetOam  14 }

	remoteMAC      OBJECT-TYPE
		SYNTAX			MacAddress
		MAX-ACCESS		not-accessible
		STATUS			current
		DESCRIPTION		"Store remote MAC."
		::=  {  ethernetOam  15  }

	opticalInfoTable OBJECT-TYPE
		SYNTAX		SEQUENCE  OF  OpticalInfoEntry
		MAX-ACCESS	not-accessible
		STATUS		current
		DESCRIPTION	" Ethnet configuration table "
		::=  { opticalInformation 1 }

	opticalInfoEntry  OBJECT-TYPE
        SYNTAX  OpticalInfoEntry
        MAX-ACCESS  not-accessible
        STATUS  current
        DESCRIPTION
            ""
        INDEX  { opticalInfoPortId }
        ::= { opticalInfoTable 1 }

      OpticalInfoEntry ::=
              SEQUENCE {
                opticalInfoPortId
                    Unsigned32,
                opticalInfoIfName
                    DisplayString,
                opticalInfoOnline
                    INTEGER,
                opticalInfoSWaveLenth
                    Integer32,
                opticalInfoPowerSupport
                    INTEGER,
                opticalInfoSRxPower
                    DisplayString,
                opticalInfoSRxPowerValid
                    INTEGER,
                opticalInfoSTxPower
                    DisplayString,
                opticalInfoSTxPowerValid
                    INTEGER,
                opticalInfoSTxPowerStatus
                    INTEGER,
                opticalInfoSRxPowerStatus
                    INTEGER,
                opticalInfoVName
                    DisplayString,
                opticalInfoType
                    DisplayString,
                opticalInfoVSn
                    DisplayString,
                opticalInfoDistanse
                    Integer32,
                opticalInfoMode
                    INTEGER
              }

	opticalInfoPortId	OBJECT-TYPE
		SYNTAX			Unsigned32
		MAX-ACCESS		read-only
		STATUS			current
		DESCRIPTION		"The port id"
		::=  {  opticalInfoEntry  1  }

    opticalInfoIfName  OBJECT-TYPE
        SYNTAX  DisplayString(SIZE(0..32))
        MAX-ACCESS  read-only
        STATUS  current
        DESCRIPTION
            "Physical Ethnet interface ifName"
        ::= { opticalInfoEntry 2 }
    opticalInfoOnline  OBJECT-TYPE
        SYNTAX      INTEGER  { online ( 1 ) , offline ( 2 ) }
        MAX-ACCESS  read-only
        STATUS  current
        DESCRIPTION
            "Optical Module Info Online"
        ::= { opticalInfoEntry 3 }

    opticalInfoSWaveLenth  OBJECT-TYPE
        SYNTAX  Integer32
        MAX-ACCESS  read-only
        STATUS  current
        DESCRIPTION
            "Optical Module Info S_waveLenth(nm)"
        ::= { opticalInfoEntry 11 }

   opticalInfoPowerSupport   OBJECT-TYPE
        SYNTAX  INTEGER  { supported ( 1 ) , unsupported ( 2 ) }
        MAX-ACCESS  read-only
        STATUS  current
        DESCRIPTION
            "Optical Module Info power_supported"
        ::= { opticalInfoEntry 12 }


   opticalInfoSRxPower  OBJECT-TYPE
        SYNTAX  DisplayString(SIZE(0..32))
        MAX-ACCESS  read-only
        STATUS  current
        DESCRIPTION
            "Optical Module Info S_rxPower(mW)"
        ::= { opticalInfoEntry 13 }

    opticalInfoSRxPowerValid  OBJECT-TYPE
        SYNTAX      INTEGER  { valid ( 1 ) , invalid ( 2 ) }
        MAX-ACCESS  read-only
        STATUS  current
        DESCRIPTION
            "Optical Module Info S_rxPowerValid"
        ::= { opticalInfoEntry 14 }

    opticalInfoSTxPower  OBJECT-TYPE
        SYNTAX  DisplayString(SIZE(0..32))
        MAX-ACCESS  read-only
        STATUS  current
        DESCRIPTION
            "Optical Module Info S_txPower(mW)"
        ::= { opticalInfoEntry 15 }

    opticalInfoSTxPowerValid  OBJECT-TYPE
        SYNTAX      INTEGER  { valid ( 1 ) , invalid ( 2 ) }
        MAX-ACCESS  read-only
        STATUS  current
        DESCRIPTION
            "Optical Module Info S_txPowerValid"
        ::= { opticalInfoEntry 16 }

    opticalInfoSTxPowerStatus   OBJECT-TYPE
		SYNTAX			INTEGER  {normal ( 0 ) , warning ( 1 ) , alarm ( 2 ) , null ( 3 ) }
		MAX-ACCESS		read-only
		STATUS			current
		DESCRIPTION		"Optical Module Info S_txPowerStatus"
        ::= { opticalInfoEntry 17 }

    opticalInfoSRxPowerStatus   OBJECT-TYPE
		SYNTAX			INTEGER  {normal ( 0 ) , warning ( 1 ) , alarm ( 2 ) , null ( 3 ) }
		MAX-ACCESS		read-only
		STATUS			current
		DESCRIPTION		"Optical Module Info S_rxPowerStatus"
        ::= { opticalInfoEntry 18 }

    opticalInfoVName  OBJECT-TYPE
        SYNTAX  DisplayString(SIZE(0..32))
        MAX-ACCESS  read-only
        STATUS  current
        DESCRIPTION
            "Optical Module Info VName"
        ::= { opticalInfoEntry 23 }

    opticalInfoType  OBJECT-TYPE
        SYNTAX  DisplayString(SIZE(0..32))
        MAX-ACCESS  read-only
        STATUS  current
        DESCRIPTION
            "Optical Module Info type"
        ::= { opticalInfoEntry 24 }


    opticalInfoVSn  OBJECT-TYPE
        SYNTAX  DisplayString(SIZE(0..32))
        MAX-ACCESS  read-only
        STATUS  current
        DESCRIPTION
            "Optical Module Info VSn"
        ::= { opticalInfoEntry 26 }

     opticalInfoDistanse OBJECT-TYPE
        SYNTAX  Integer32
        MAX-ACCESS  read-only
        STATUS  current
        DESCRIPTION
            "Optical Module Info Distance(m)"
        ::= { opticalInfoEntry 27 }

     opticalInfoMode OBJECT-TYPE
		SYNTAX			INTEGER  {null ( 0 ) , single ( 1 ) , multi ( 2 ), copper ( 3 ) }
		MAX-ACCESS		read-only
		STATUS			current
		DESCRIPTION		"The mode of the optical fiber."
        ::= { opticalInfoEntry 28 }

    --
        END
