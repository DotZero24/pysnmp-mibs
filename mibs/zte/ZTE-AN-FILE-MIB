--------------------------------------------------------------------------------
-- File Name : ZTE-AN-FILE-MIB.mib
-- Date      : 2010-03-10
-- Author    : ZTE Shanghai Nms dept.

--
-- Zte File Management Mib for Access Node
--
--
--------------------------------------------------------------------------------


ZTE-AN-FILE-MIB    DEFINITIONS ::= BEGIN
    IMPORTS
        RowStatus, DisplayString,TruthValue             FROM SNMPv2-TC
        MODULE-IDENTITY, OBJECT-TYPE,
        Integer32, NOTIFICATION-TYPE                    FROM SNMPv2-SMI
        InetAddressType, InetAddress                    FROM INET-ADDRESS-MIB
        zxAn                                            FROM ZTE-AN-TC-MIB;


    zxAnFileMib    MODULE-IDENTITY
        LAST-UPDATED    "201003101500Z"
        ORGANIZATION    "ZTE Corporation"
        CONTACT-INFO    "suchunshan,zhangzhikun
                        Mail: zhang.zhikun@zte.com.cn
                        Tel : 021-68896247"
        DESCRIPTION     "This MIB defines zte Access Node managed objects."
        ::=  {  zxAn  14  }


    zxAnFileStorageDevMgmt  OBJECT IDENTIFIER   ::=  {  zxAnFileMib  1  }
    zxAnFileMgmt            OBJECT IDENTIFIER   ::=  {  zxAnFileMib  2  }
    zxAnFileTrapObjects     OBJECT IDENTIFIER   ::=  {  zxAnFileMib  10  }

    zxAnFileCopyMgmt        OBJECT IDENTIFIER   ::=  {  zxAnFileMgmt  20  }
    zxAnFileSynchMgmt       OBJECT IDENTIFIER   ::=  {  zxAnFileMgmt  30  }
    zxAnSoftwareMgmt        OBJECT IDENTIFIER   ::=  {  zxAnFileMgmt  50  }

-------------------------------------------------------------------------------
-- Following objects are defined.
-- 1.Storage Device Table
-- 2.Storage Device Sequence Used to Startup
-- 3.File Table
-- 4.Software Version Table
-- 5.Card Running Version Table
-- 6.Software Patch Table
-- 7.Software Running Patch Table
-- 8.Update Boot Software
-- 9.Update Boot Software Status Table
-- 10.File Copy Operation Table
-- 11.File Synchronization Status Between Master And Slave Control Card
-- 12.File Server Table
-- 13.Automatic Backup Configuration Table
-- 14.Automatic Backup Status Table
-- 15.File Management Traps
-- 16.Software Automatic Update Management
-------------------------------------------------------------------------------



-------------------------------------------------------------------------------
-- 1.Storage Device Table
-------------------------------------------------------------------------------
    zxAnFileStorageDevTable   OBJECT-TYPE
        SYNTAX      SEQUENCE  OF  ZxAnFileStorageDevEntry
        MAX-ACCESS  not-accessible
        STATUS      current
        DESCRIPTION "This table includes file storage devices information in NE
                    equipment."
        ::=  { zxAnFileStorageDevMgmt  1 }

    zxAnFileStorageDevEntry   OBJECT-TYPE
        SYNTAX      ZxAnFileStorageDevEntry
        MAX-ACCESS  not-accessible
        STATUS      current
        DESCRIPTION "An entry in zxAnFileStorageDevTable."
        INDEX   {zxAnFileStorageDevRack,zxAnFileStorageDevShelf,
                zxAnFileStorageDevSlot,zxAnFileStorageDevSubCard,
                zxAnFileStorageDevType,zxAnFileStorageDevId}
        ::=  { zxAnFileStorageDevTable 1 }

    ZxAnFileStorageDevEntry  ::=  SEQUENCE {
        zxAnFileStorageDevRack                Integer32,
        zxAnFileStorageDevShelf               Integer32,
        zxAnFileStorageDevSlot                Integer32,
        zxAnFileStorageDevSubCard             Integer32,
        zxAnFileStorageDevType                DisplayString,
        zxAnFileStorageDevId                  Integer32,
        zxAnFileStorageDevTotalSpace          Integer32,
        zxAnFileStorageDevAvailableSpace      Integer32,
        zxAnFileStorageDevOperStatus          INTEGER,
        zxAnFileStorageDevAdminStatus         INTEGER
        }

    zxAnFileStorageDevRack          OBJECT-TYPE
        SYNTAX          Integer32
        MAX-ACCESS      not-accessible
        STATUS          current
        DESCRIPTION     "The ID of the rack which containing the storage
                         device,such as SD card or flash."
        ::=  {  zxAnFileStorageDevEntry  1  }

    zxAnFileStorageDevShelf          OBJECT-TYPE
        SYNTAX          Integer32
        MAX-ACCESS      not-accessible
        STATUS          current
        DESCRIPTION     "The ID of the shelf which containing the storage
                         device,such as SD card or flash."
        ::=  {  zxAnFileStorageDevEntry 2  }

    zxAnFileStorageDevSlot          OBJECT-TYPE
        SYNTAX          Integer32
        MAX-ACCESS      not-accessible
        STATUS          current
        DESCRIPTION     "The ID of the slot which containing the storage device
                         ,such as SD card or flash."
        ::=  {  zxAnFileStorageDevEntry  3  }

    zxAnFileStorageDevSubCard       OBJECT-TYPE
        SYNTAX          Integer32
        MAX-ACCESS      not-accessible
        STATUS          current
        DESCRIPTION     "The ID of the subcard which containing the storage
                        device,such as SD card or flash."
        ::=  {  zxAnFileStorageDevEntry  4  }

    zxAnFileStorageDevType          OBJECT-TYPE
        SYNTAX          DisplayString  ( SIZE ( 1 .. 32  ) )
        MAX-ACCESS      not-accessible
        STATUS          current
        DESCRIPTION     "The type of the storage device,such as 'flash' or
                         'sd'."
        ::=  {  zxAnFileStorageDevEntry  5  }



    zxAnFileStorageDevId            OBJECT-TYPE
        SYNTAX          Integer32
        MAX-ACCESS      not-accessible
        STATUS          current
        DESCRIPTION     "The ID of the storage device. It starts with 1. "
        ::=  {  zxAnFileStorageDevEntry  6  }


    zxAnFileStorageDevTotalSpace    OBJECT-TYPE
        SYNTAX          Integer32
        UNITS           "KB"
        MAX-ACCESS      read-only
        STATUS          current
        DESCRIPTION     "The total space of the storage device."
        ::=  {  zxAnFileStorageDevEntry  7  }

    zxAnFileStorageDevAvailableSpace OBJECT-TYPE
        SYNTAX          Integer32
        UNITS           "KB"
        MAX-ACCESS      read-only
        STATUS          current
        DESCRIPTION     "The available space of the storage device."
        ::=  {  zxAnFileStorageDevEntry  8  }

    zxAnFileStorageDevOperStatus      OBJECT-TYPE
        SYNTAX          INTEGER
                      {
                          ready(1),
                          notReady(2)
                      }
        MAX-ACCESS      read-only
        STATUS          current
        DESCRIPTION     "If the storage device is available."
        ::=  {  zxAnFileStorageDevEntry  9  }

    zxAnFileStorageDevAdminStatus          OBJECT-TYPE
        SYNTAX          INTEGER
                      {
                          remove(1)
                      }
        MAX-ACCESS      read-write
        STATUS          current
        DESCRIPTION     "The operation of removing the storage device from
                        running status.If this operation is success,then
                        zxAnFileStorageDevOperStatus should turn to
                        notReady(2). "
        ::=  {  zxAnFileStorageDevEntry  10  }


-------------------------------------------------------------------------------
-- 2.Storage Device Sequence Used to Startup
-------------------------------------------------------------------------------
    zxAnStartupSeqTable   OBJECT-TYPE
        SYNTAX      SEQUENCE  OF  ZxAnStartupSeqEntry
        MAX-ACCESS  not-accessible
        STATUS      current
        DESCRIPTION "This table defines the startup sequence of storage
                    devices. "
        ::=  { zxAnFileStorageDevMgmt  5 }

    zxAnStartupSeqEntry   OBJECT-TYPE
        SYNTAX      ZxAnStartupSeqEntry
        MAX-ACCESS  not-accessible
        STATUS      current
        DESCRIPTION "An entry in zxAnStartupSeqTable."
        INDEX       { zxAnStartupSeqIndex }
        ::=  { zxAnStartupSeqTable 1 }

    ZxAnStartupSeqEntry  ::=  SEQUENCE {
        zxAnStartupSeqIndex              Integer32,
        zxAnStartupSeqRack               Integer32,
        zxAnStartupSeqShelf              Integer32,
        zxAnStartupSeqSlot               Integer32,
        zxAnStartupSeqSubCard            Integer32,
        zxAnStartupSeqDevType            DisplayString,
        zxAnStartupSeqDevId              Integer32
        }

    zxAnStartupSeqIndex          OBJECT-TYPE
        SYNTAX          Integer32
        MAX-ACCESS      not-accessible
        STATUS          current
        DESCRIPTION     "The sequence of storage device used to loading the
                        configuration when NE startup.  '1' means the first
                        startup storage device."
        ::=  {  zxAnStartupSeqEntry  1  }

    zxAnStartupSeqRack          OBJECT-TYPE
        SYNTAX          Integer32
        MAX-ACCESS      read-write
        STATUS          current
        DESCRIPTION     "The ID of the rack which containing the storage device
                        ,such as SD card or flash."
        ::=  {  zxAnStartupSeqEntry  2  }

    zxAnStartupSeqShelf          OBJECT-TYPE
        SYNTAX          Integer32
        MAX-ACCESS      read-write
        STATUS          current
        DESCRIPTION     "The ID of the shelf which containing the storage device
                        ,such as SD card or flash."
        ::=  {  zxAnStartupSeqEntry 3 }

    zxAnStartupSeqSlot          OBJECT-TYPE
        SYNTAX          Integer32
        MAX-ACCESS      read-write
        STATUS          current
        DESCRIPTION     "The ID of the slot which containing the storage device,
                        such as SD card or flash."
        ::=  {  zxAnStartupSeqEntry  4  }

    zxAnStartupSeqSubCard          OBJECT-TYPE
        SYNTAX          Integer32
        MAX-ACCESS      read-write
        STATUS          current
        DESCRIPTION     "The ID of the subcard which containing the storage
                        device, such as SD card or flash.If no subcard exists,
                        then it is 0."
        DEFVAL          { 0 }
        ::=  {  zxAnStartupSeqEntry  5  }

    zxAnStartupSeqDevType          OBJECT-TYPE
        SYNTAX          DisplayString  ( SIZE ( 1 .. 32  ) )
        MAX-ACCESS      read-write
        STATUS          current
        DESCRIPTION     "The type of storage device,such as 'flash' or 'sd'."
        DEFVAL          { "flash" }
        ::=  {  zxAnStartupSeqEntry  6  }


    zxAnStartupSeqDevId          OBJECT-TYPE
        SYNTAX          Integer32
        MAX-ACCESS      read-write
        STATUS          current
        DESCRIPTION     "This object indicates the device ID.It starts with 1. "
        ::=  {  zxAnStartupSeqEntry  7  }


------------------------------------------------------------------------------
-- 3.File Table
------------------------------------------------------------------------------

   zxAnFileTable   OBJECT-TYPE
        SYNTAX      SEQUENCE  OF  ZxAnFileEntry
        MAX-ACCESS  not-accessible
        STATUS      current
        DESCRIPTION "A table entry containing file information ."
        ::=  { zxAnFileMgmt  1 }

    zxAnFileEntry   OBJECT-TYPE
        SYNTAX      ZxAnFileEntry
        MAX-ACCESS  not-accessible
        STATUS      current
        DESCRIPTION "An entry of zxAnFileTable"
        INDEX       { zxAnFileStorageDevRack,zxAnFileStorageDevShelf,
                      zxAnFileStorageDevSlot,zxAnFileStorageDevSubCard,
                      zxAnFileStorageDevType,zxAnFileStorageDevId,zxAnFileName}
        ::=  { zxAnFileTable 1 }

    ZxAnFileEntry  ::=  SEQUENCE {
        zxAnFileName                DisplayString,
        zxAnFileType                INTEGER,
        zxAnFileSize                Integer32,
        zxAnFileModifyTime          DisplayString,
        zxAnFilePermissions         BITS,
        zxAnDirOwner                INTEGER,
        zxAnDirTotalFilesCount      Integer32,
        zxAnFileAdminStatus         INTEGER
        }


    zxAnFileName      OBJECT-TYPE
        SYNTAX          DisplayString ( SIZE ( 0 .. 64  ) )
        MAX-ACCESS      not-accessible
        STATUS          current
        DESCRIPTION     "File name."
        ::=  {  zxAnFileEntry  1  }

    zxAnFileType       OBJECT-TYPE
        SYNTAX          INTEGER
        {
                       file(1),
                       directory(2)
        }
        MAX-ACCESS      read-only
        STATUS          current
        DESCRIPTION     "This object indicates this object is a file or a
                         folder."
        ::=  {  zxAnFileEntry  2  }

    zxAnFileSize       OBJECT-TYPE
        SYNTAX          Integer32
        UNITS           "byte"
        MAX-ACCESS      read-only
        STATUS          current
        DESCRIPTION     "File size."
        ::=  {  zxAnFileEntry  3  }


    zxAnFileModifyTime  OBJECT-TYPE
        SYNTAX          DisplayString  ( SIZE ( 1 .. 20  ) )
        MAX-ACCESS      read-only
        STATUS          current
        DESCRIPTION    "The last file modification time.The format is
                        yyyy-mm-dd HH:MM:SS.For example,  2001-01-01 02:22:33 "
        ::=  {  zxAnFileEntry  4  }


    zxAnFilePermissions  OBJECT-TYPE
        SYNTAX          BITS
        {
             read(0),
             write(1),
             execute(2)-- reserved now
        }
        MAX-ACCESS      read-only
        STATUS          current
        DESCRIPTION     "Access permissions of file or folder ."
        ::=  {  zxAnFileEntry  5  }


    zxAnDirOwner    OBJECT-TYPE
        SYNTAX          INTEGER
        {
                   system (1) ,
                   user(2)
        }
        MAX-ACCESS      read-only
        STATUS          current
        DESCRIPTION     "The owner of the folder.system(1) indicates the folder
                        is invisible to the ordinary user."
        ::=  {  zxAnFileEntry  6  }

    zxAnDirTotalFilesCount          OBJECT-TYPE
        SYNTAX          Integer32
        MAX-ACCESS      read-only
        STATUS          current
        DESCRIPTION     "The count of all files in a folder."
        ::=  {  zxAnFileEntry  7  }



    zxAnFileAdminStatus       OBJECT-TYPE
        SYNTAX          INTEGER
        {
             erase(1),         -- delete file,but folder can't be deleted
             synchToSlave(2),   -- synch file or folder to slave control card
             cancelSynchToSlave(3)  -- cancel the operation synchToSlave(2)
        }
        MAX-ACCESS      read-write
        STATUS          current
        DESCRIPTION     " Adminstrative status of file or folder.
                        If it is set to synchToSlave(2),then the status,progress
                        and result is shown in zxAnFileSyncStatusTable. "
        ::=  {  zxAnFileEntry  8  }


--------------------------------------------------------------------------------
-- 4.Software Version Table
--------------------------------------------------------------------------------
    zxAnSoftwareVersionTable   OBJECT-TYPE
        SYNTAX      SEQUENCE  OF  ZxAnSoftwareVersionEntry
        MAX-ACCESS  not-accessible
        STATUS      current
        DESCRIPTION "This table includes the saved software version information
                    in NE."
        ::=  { zxAnSoftwareMgmt  2 }

    zxAnSoftwareVersionEntry   OBJECT-TYPE
        SYNTAX      ZxAnSoftwareVersionEntry
        MAX-ACCESS  not-accessible
        STATUS      current
        DESCRIPTION "An entry in zxAnSoftwareVersionTable."
        INDEX       {zxAnFileStorageDevRack,zxAnFileStorageDevShelf,
                    zxAnFileStorageDevSlot,zxAnFileStorageDevSubCard,
                    zxAnFileStorageDevType,zxAnFileStorageDevId,
                    zxAnSwVersionFileName}
        ::=  { zxAnSoftwareVersionTable 1 }

    ZxAnSoftwareVersionEntry  ::=  SEQUENCE {
        zxAnSwVersionFileName       DisplayString,
        zxAnSwVersionType           DisplayString,
        zxAnSwVersion               DisplayString,
        zxAnSwVersionFileSize       Integer32,
        zxAnSwVersionBuildTime      DisplayString,
        zxAnSwVersionActiveStatus   INTEGER,
        zxAnSwVersionAdminStatus    INTEGER,
        zxAnSwVersionActivatedTime  DisplayString
        }


    zxAnSwVersionFileName      OBJECT-TYPE
        SYNTAX          DisplayString  ( SIZE ( 1 .. 64  ) )
        MAX-ACCESS      not-accessible
        STATUS          current
        DESCRIPTION     "The file name of the software."
        ::=  {  zxAnSoftwareVersionEntry  1  }

    zxAnSwVersionType         OBJECT-TYPE
        SYNTAX          DisplayString  ( SIZE ( 1 .. 64  ) )
        MAX-ACCESS      read-only
        STATUS          current
        DESCRIPTION     "The type of the software,it is often the main type
                        of a card,such as GCSA,EIG. "
        ::=  {  zxAnSoftwareVersionEntry  2  }

    zxAnSwVersion           OBJECT-TYPE
        SYNTAX          DisplayString  ( SIZE ( 1 .. 64  ) )
        MAX-ACCESS      read-only
        STATUS          current
        DESCRIPTION     "The version of the software."
        ::=  {  zxAnSoftwareVersionEntry  3  }

    zxAnSwVersionFileSize       OBJECT-TYPE
        SYNTAX          Integer32
        UNITS           "byte"
        MAX-ACCESS      read-only
        STATUS          current
        DESCRIPTION     "The size of the software."
        ::=  {  zxAnSoftwareVersionEntry  4  }

    zxAnSwVersionBuildTime       OBJECT-TYPE
        SYNTAX          DisplayString  ( SIZE ( 1 .. 20  ) )
        MAX-ACCESS      read-only
        STATUS          current
        DESCRIPTION    "The version build time.The format is
                        yyyy-mm-dd HH:MM:SS. For example,
                        2001-01-01 02:22:33 "
        ::=  {  zxAnSoftwareVersionEntry  5  }

    zxAnSwVersionActiveStatus       OBJECT-TYPE
        SYNTAX          INTEGER
        {
             activeAndRunning(1),
             activeButNotRunning(2),
             deactiveButRunning(3),
             deactiveAndNotRunning(4),
             na(5)    -- this attribute is not available for this softeware
        }
        MAX-ACCESS      read-only
        STATUS          current
        DESCRIPTION    " The software active status."
        ::=  {  zxAnSoftwareVersionEntry  6  }


    zxAnSwVersionAdminStatus       OBJECT-TYPE
        SYNTAX          INTEGER
        {
             activate(1)
        }
        MAX-ACCESS      read-write
        STATUS          current
        DESCRIPTION    "Activate the software."
        ::=  {  zxAnSoftwareVersionEntry  7  }


    zxAnSwVersionActivatedTime       OBJECT-TYPE
        SYNTAX          DisplayString  ( SIZE ( 1 .. 20  ) )
        MAX-ACCESS      read-only
        STATUS          current
        DESCRIPTION    "The software activated time.The format is
                        yyyy-mm-dd HH:MM:SS.For example,2001-01-01 02:22:33 "
        ::=  {  zxAnSoftwareVersionEntry  8  }

-------------------------------------------------------------------------------
-- 5.Card Running Version Table
-------------------------------------------------------------------------------
    zxAnCardRunningVersionTable   OBJECT-TYPE
        SYNTAX      SEQUENCE  OF  ZxAnCardRunningVersionEntry
        MAX-ACCESS  not-accessible
        STATUS      current
        DESCRIPTION "This table includes the Card version information."
        ::=  { zxAnSoftwareMgmt  3 }

    zxAnCardRunningVersionEntry   OBJECT-TYPE
        SYNTAX      ZxAnCardRunningVersionEntry
        MAX-ACCESS  not-accessible
        STATUS      current
        DESCRIPTION "An entry in zxAnCardRunningTable."
        INDEX       {  zxAnCardSwRack,zxAnCardSwShelf,
                       zxAnCardSwSlot,zxAnCardSwSubCard  }
        ::=  { zxAnCardRunningVersionTable 1 }

    ZxAnCardRunningVersionEntry  ::=  SEQUENCE {
        zxAnCardSwRack                       Integer32,
        zxAnCardSwShelf                      Integer32,
        zxAnCardSwSlot                       Integer32,
        zxAnCardSwSubCard                    Integer32,
        zxAnCardRunningVerStorageDevType     DisplayString,
        zxAnCardRunningVerStorageDevId       Integer32,
        zxAnCardRunningHwVersion             DisplayString,
        zxAnCardRunningSwVersion             DisplayString,
        zxAnCardRunningSwVerFileName         DisplayString,
        zxAnCardRunningSwVersionType         DisplayString,
        zxAnCardRunningSwVerFileSize         Integer32,
        zxAnCardRunningSwVerBuildTime        DisplayString,
        zxAnCardRunningSwBootFileName        DisplayString,
        zxAnCardRunningSwBootVersionType     DisplayString,
        zxAnCardRunningSwBootVersion         DisplayString,
        zxAnCardRunningSwBootFileSize        Integer32,
        zxAnCardRunningSwBootBuildTime       DisplayString,
        zxAnCardRunningSwFw1FileName         DisplayString,
        zxAnCardRunningSwFw1VersionType      DisplayString,
        zxAnCardRunningSwFw1Version          DisplayString,
        zxAnCardRunningSwFw1FileSize         Integer32,
        zxAnCardRunningSwFw1BuildTime        DisplayString,
        zxAnCardRunningSwFw2FileName         DisplayString,
        zxAnCardRunningSwFw2VersionType      DisplayString,
        zxAnCardRunningSwFw2Version          DisplayString,
        zxAnCardRunningSwFw2FileSize         Integer32,
        zxAnCardRunningSwFw2BuildTime        DisplayString,
        zxAnCardRunningSwFw3FileName         DisplayString,
        zxAnCardRunningSwFw3VersionType      DisplayString,
        zxAnCardRunningSwFw3Version          DisplayString,
        zxAnCardRunningSwFw3FileSize         Integer32,
        zxAnCardRunningSwFw3BuildTime        DisplayString
        }

    zxAnCardSwRack          OBJECT-TYPE
        SYNTAX          Integer32
        MAX-ACCESS      not-accessible
        STATUS          current
        DESCRIPTION     "The ID of the rack which containing the storage device
                        ,such as SD card or flash."
        ::=  {  zxAnCardRunningVersionEntry  1  }

    zxAnCardSwShelf          OBJECT-TYPE
        SYNTAX          Integer32
        MAX-ACCESS      not-accessible
        STATUS          current
        DESCRIPTION     "The ID of the shelf which containing the storage device
                        ,such as SD card or flash."
        ::=  {  zxAnCardRunningVersionEntry 2  }

    zxAnCardSwSlot          OBJECT-TYPE
        SYNTAX          Integer32
        MAX-ACCESS      not-accessible
        STATUS          current
        DESCRIPTION     "The ID of the slot which containing the storage device
                        ,such as SD card or flash."
        ::=  {  zxAnCardRunningVersionEntry  3  }

    zxAnCardSwSubCard       OBJECT-TYPE
        SYNTAX          Integer32
        MAX-ACCESS      not-accessible
        STATUS          current
        DESCRIPTION     "The ID of the subcard which containing the storage
                        device,such as SD card or flash."
        ::=  {  zxAnCardRunningVersionEntry  4  }

    zxAnCardRunningVerStorageDevType          OBJECT-TYPE
        SYNTAX          DisplayString  ( SIZE ( 1 .. 32  ) )
        MAX-ACCESS      read-only
        STATUS          current
        DESCRIPTION     "Type of storage device,such as 'flash' or 'sd'."
        ::=  {  zxAnCardRunningVersionEntry  5  }


    zxAnCardRunningVerStorageDevId          OBJECT-TYPE
        SYNTAX          Integer32
        MAX-ACCESS      read-only
        STATUS          current
        DESCRIPTION     "Storage device ID. It starts with '1'. "
        ::=  {  zxAnCardRunningVersionEntry  6  }

    zxAnCardRunningHwVersion         OBJECT-TYPE
        SYNTAX          DisplayString  ( SIZE ( 1 .. 64  ) )
        MAX-ACCESS      read-only
        STATUS          current
        DESCRIPTION     "Hardware version of the card."
        ::=  {  zxAnCardRunningVersionEntry  7  }

    zxAnCardRunningSwVersion              OBJECT-TYPE
        SYNTAX          DisplayString  ( SIZE ( 1 .. 64  ) )
        MAX-ACCESS      read-only
        STATUS          current
        DESCRIPTION     "Version of the software running on the card."
        ::=  {  zxAnCardRunningVersionEntry  8  }

    zxAnCardRunningSwVerFileName         OBJECT-TYPE
        SYNTAX          DisplayString  ( SIZE ( 1 .. 64  ) )
        MAX-ACCESS      read-only
        STATUS          current
        DESCRIPTION     "File name of the software running on the card."
        ::=  {  zxAnCardRunningVersionEntry  9  }

    zxAnCardRunningSwVersionType         OBJECT-TYPE
        SYNTAX          DisplayString  ( SIZE ( 1 .. 64  ) )
        MAX-ACCESS      read-only
        STATUS          current
        DESCRIPTION     "The type of the software,it is often the main type
                        of a card,such as GCSA,EIG. "
        ::=  {  zxAnCardRunningVersionEntry  10  }

    zxAnCardRunningSwVerFileSize       OBJECT-TYPE
        SYNTAX          Integer32
        UNITS           "byte"
        MAX-ACCESS      read-only
        STATUS          current
        DESCRIPTION     "File size of the software running on the card."
        ::=  {  zxAnCardRunningVersionEntry  11  }

    zxAnCardRunningSwVerBuildTime       OBJECT-TYPE
        SYNTAX          DisplayString  ( SIZE ( 1 .. 20  ) )
        MAX-ACCESS      read-only
        STATUS          current
        DESCRIPTION    "The software version build time.The format is
                        yyyy-mm-dd HH:MM:SS.For example,2001-01-01 02:22:33"
        ::=  {  zxAnCardRunningVersionEntry  12  }

    zxAnCardRunningSwBootFileName         OBJECT-TYPE
        SYNTAX          DisplayString  ( SIZE ( 1 .. 64  ) )
        MAX-ACCESS      read-only
        STATUS          current
        DESCRIPTION     "Name of the boot software running on the card."
        ::=  {  zxAnCardRunningVersionEntry  17  }

    zxAnCardRunningSwBootVersionType         OBJECT-TYPE
        SYNTAX          DisplayString  ( SIZE ( 1 .. 64  ) )
        MAX-ACCESS      read-only
        STATUS          current
        DESCRIPTION     "The type of the boot software,it is often the main
                         type of a card,such as GCSA,EIG. "
        ::=  {  zxAnCardRunningVersionEntry  18  }

    zxAnCardRunningSwBootVersion              OBJECT-TYPE
        SYNTAX          DisplayString  ( SIZE ( 1 .. 64  ) )
        MAX-ACCESS      read-only
        STATUS          current
        DESCRIPTION     "Version of the boot software running on the card."
        ::=  {  zxAnCardRunningVersionEntry  19  }

    zxAnCardRunningSwBootFileSize       OBJECT-TYPE
        SYNTAX          Integer32
        UNITS           "byte"
        MAX-ACCESS      read-only
        STATUS          current
        DESCRIPTION     "File size of the boot software running on the card."
        ::=  {  zxAnCardRunningVersionEntry  20  }

    zxAnCardRunningSwBootBuildTime       OBJECT-TYPE
        SYNTAX          DisplayString  ( SIZE ( 1 .. 20  ) )
        MAX-ACCESS      read-only
        STATUS          current
        DESCRIPTION    "The boot software build time.The format is
                        yyyy-mm-dd HH:MM:SS.For example, 2001-01-01 02:22:33 "
        ::=  {  zxAnCardRunningVersionEntry  21  }

    zxAnCardRunningSwFw1FileName         OBJECT-TYPE
        SYNTAX          DisplayString  ( SIZE ( 1 .. 64  ) )
        MAX-ACCESS      read-only
        STATUS          current
        DESCRIPTION     "Name of the firmware running on the card."
        ::=  {  zxAnCardRunningVersionEntry  26  }

    zxAnCardRunningSwFw1VersionType         OBJECT-TYPE
        SYNTAX          DisplayString  ( SIZE ( 1 .. 64  ) )
        MAX-ACCESS      read-only
        STATUS          current
        DESCRIPTION     "The type of the firmware,it is often the main type
                        of a card,such as GCSA,EIG. "
        ::=  {  zxAnCardRunningVersionEntry  27  }

    zxAnCardRunningSwFw1Version              OBJECT-TYPE
        SYNTAX          DisplayString  ( SIZE ( 1 .. 64  ) )
        MAX-ACCESS      read-only
        STATUS          current
        DESCRIPTION     "Version of the firmware running on the card."
        ::=  {  zxAnCardRunningVersionEntry  28  }

    zxAnCardRunningSwFw1FileSize       OBJECT-TYPE
        SYNTAX          Integer32
        UNITS           "byte"
        MAX-ACCESS      read-only
        STATUS          current
        DESCRIPTION     "size of the firmware running on the card."
        ::=  {  zxAnCardRunningVersionEntry  29  }

    zxAnCardRunningSwFw1BuildTime       OBJECT-TYPE
        SYNTAX          DisplayString  ( SIZE ( 1 .. 20  ) )
        MAX-ACCESS      read-only
        STATUS          current
        DESCRIPTION    "The firmware build time.The format is
                        yyyy-mm-dd HH:MM:SS.For example, 2001-01-01 02:22:33 "
        ::=  {  zxAnCardRunningVersionEntry  30  }


    zxAnCardRunningSwFw2FileName         OBJECT-TYPE
        SYNTAX          DisplayString  ( SIZE ( 1 .. 64  ) )
        MAX-ACCESS      read-only
        STATUS          current
        DESCRIPTION     "File name of the firmware running on the card."
        ::=  {  zxAnCardRunningVersionEntry  35  }

    zxAnCardRunningSwFw2VersionType         OBJECT-TYPE
        SYNTAX          DisplayString  ( SIZE ( 1 .. 64  ) )
        MAX-ACCESS      read-only
        STATUS          current
        DESCRIPTION     "The type of the firmware,it is often the main type
                        of a card,such as GCSA,EIG. "
        ::=  {  zxAnCardRunningVersionEntry  36  }

    zxAnCardRunningSwFw2Version              OBJECT-TYPE
        SYNTAX          DisplayString  ( SIZE ( 1 .. 64  ) )
        MAX-ACCESS      read-only
        STATUS          current
        DESCRIPTION     "Version of the firmware running on the card."
        ::=  {  zxAnCardRunningVersionEntry  37  }

    zxAnCardRunningSwFw2FileSize       OBJECT-TYPE
        SYNTAX          Integer32
        UNITS           "byte"
        MAX-ACCESS      read-only
        STATUS          current
        DESCRIPTION     "File size of the firmware running on the card."
        ::=  {  zxAnCardRunningVersionEntry  38  }

    zxAnCardRunningSwFw2BuildTime       OBJECT-TYPE
        SYNTAX          DisplayString  ( SIZE ( 1 .. 20  ) )
        MAX-ACCESS      read-only
        STATUS          current
        DESCRIPTION    "The firmware build time.The format is
                        yyyy-mm-dd HH:MM:SS.For example, 2001-01-01 02:22:33 "
        ::=  {  zxAnCardRunningVersionEntry  39  }

    zxAnCardRunningSwFw3FileName         OBJECT-TYPE
        SYNTAX          DisplayString  ( SIZE ( 1 .. 64  ) )
        MAX-ACCESS      read-only
        STATUS          current
        DESCRIPTION     "File name of the firmware running on the card."
        ::=  {  zxAnCardRunningVersionEntry  44  }

    zxAnCardRunningSwFw3VersionType         OBJECT-TYPE
        SYNTAX          DisplayString  ( SIZE ( 1 .. 64  ) )
        MAX-ACCESS      read-only
        STATUS          current
        DESCRIPTION     "The type of the firmware,it is often the main type
                        of a card,such as GCSA,EIG. "
        ::=  {  zxAnCardRunningVersionEntry  45  }

    zxAnCardRunningSwFw3Version              OBJECT-TYPE
        SYNTAX          DisplayString  ( SIZE ( 1 .. 64  ) )
        MAX-ACCESS      read-only
        STATUS          current
        DESCRIPTION     "Firmware version of the firmware running on the card."
        ::=  {  zxAnCardRunningVersionEntry  46  }

    zxAnCardRunningSwFw3FileSize       OBJECT-TYPE
        SYNTAX          Integer32
        UNITS           "byte"
        MAX-ACCESS      read-only
        STATUS          current
        DESCRIPTION     "File size of the firmware running on the card."
        ::=  {  zxAnCardRunningVersionEntry  47  }

    zxAnCardRunningSwFw3BuildTime       OBJECT-TYPE
        SYNTAX          DisplayString  ( SIZE ( 1 .. 20  ) )
        MAX-ACCESS      read-only
        STATUS          current
        DESCRIPTION    "Firmware build time.The format is
                        yyyy-mm-dd HH:MM:SS.For example, 2001-01-01 02:22:33 "
        ::=  {  zxAnCardRunningVersionEntry  48  }

------------------------------------------------------------------------------
-- 6.Software Patch Table
------------------------------------------------------------------------------
    zxAnSoftwarePatchTable   OBJECT-TYPE
        SYNTAX      SEQUENCE  OF  ZxAnSoftwarePatchEntry
        MAX-ACCESS  not-accessible
        STATUS      current
        DESCRIPTION "A table entry containing software patch information."
        ::=  { zxAnSoftwareMgmt  4 }

    zxAnSoftwarePatchEntry   OBJECT-TYPE
        SYNTAX      ZxAnSoftwarePatchEntry
        MAX-ACCESS  not-accessible
        STATUS      current
        DESCRIPTION "Software patch information entry"
        INDEX       {  zxAnFileStorageDevRack,zxAnFileStorageDevShelf,
                      zxAnFileStorageDevSlot,zxAnFileStorageDevSubCard,
                      zxAnFileStorageDevType,zxAnFileStorageDevId,
                      zxAnSwPatchName  }
        ::=  { zxAnSoftwarePatchTable 1 }

    ZxAnSoftwarePatchEntry  ::=  SEQUENCE {
        zxAnSwPatchName           DisplayString,
        zxAnSwPatchOwnerSwVersion DisplayString,
        zxAnSwPatchVersion        DisplayString,
        zxAnSwPatchSize           Integer32,
        zxAnSwPatchBuildTime      DisplayString,
        zxAnSwPatchDesc           DisplayString,
        zxAnSwPatchAdminStatus    INTEGER,
        zxAnSwPatchActiveStatus   INTEGER,
        zxAnSwPatchOperFailedReason   INTEGER
    }

    zxAnSwPatchName      OBJECT-TYPE
        SYNTAX          DisplayString ( SIZE ( 0 .. 64  ) )
        MAX-ACCESS      not-accessible
        STATUS          current
        DESCRIPTION     "the file name of the patch "
        ::=  {  zxAnSoftwarePatchEntry  1  }

    zxAnSwPatchOwnerSwVersion  OBJECT-TYPE
        SYNTAX          DisplayString ( SIZE ( 0 .. 32  ) )
        MAX-ACCESS      read-only
        STATUS          current
        DESCRIPTION     "The software version of the patch belonging to."
        ::=  {  zxAnSoftwarePatchEntry  2  }

    zxAnSwPatchVersion  OBJECT-TYPE
        SYNTAX          DisplayString ( SIZE ( 0 .. 32  ) )
        MAX-ACCESS      read-only
        STATUS          current
        DESCRIPTION     "The version of the patch."
        ::=  {  zxAnSoftwarePatchEntry  3  }

    zxAnSwPatchSize OBJECT-TYPE
        SYNTAX          Integer32
        UNITS           "byte"
        MAX-ACCESS      read-only
        STATUS          current
        DESCRIPTION     "The size of the patch."
        ::=  {  zxAnSoftwarePatchEntry  4  }

    zxAnSwPatchBuildTime  OBJECT-TYPE
        SYNTAX          DisplayString  ( SIZE ( 1 .. 20  ) )
        MAX-ACCESS      read-only
        STATUS          current
        DESCRIPTION    "The software patch build time.The format is
                      yyyy-mm-dd HH:MM:SS. For example,  2001-01-01 02:22:33 "
        ::=  {  zxAnSoftwarePatchEntry  5  }

    zxAnSwPatchDesc  OBJECT-TYPE
        SYNTAX          DisplayString ( SIZE ( 0 .. 255  ) )
        MAX-ACCESS      read-only
        STATUS          current
        DESCRIPTION     "The patch description"
        ::=  {  zxAnSoftwarePatchEntry  6  }


    zxAnSwPatchAdminStatus  OBJECT-TYPE
        SYNTAX          INTEGER
                    {
                        activate(1),
                        deactivate(2),
                        temporarilyactivate(3)
                    }
        MAX-ACCESS      read-write
        STATUS          current
        DESCRIPTION     "The software patch administrative status."
        ::=  {  zxAnSoftwarePatchEntry  7  }

    zxAnSwPatchActiveStatus  OBJECT-TYPE
        SYNTAX          INTEGER
                    {
                        inactive(1),
                        activating(2),
                        partialActivated(3),
                        activated(4),
                        activeFailed(5)
                    }
        MAX-ACCESS      read-only
        STATUS          current
        DESCRIPTION     "The software patch current active status."
        ::=  {  zxAnSoftwarePatchEntry  8  }

    zxAnSwPatchOperFailedReason  OBJECT-TYPE
        SYNTAX          INTEGER
                    {
                        noError(1),
                        invalidPatchName(2),
                        patchTooBig(3),
                        patchCheckFailed(4),
                        timeout(5),
                        otherOperationInProgress(6),
                        versionMismatch(7),
                        alreadyInactive(8),
                        alreadyActivated(9),
                        otherErrors(255)
                    }
        MAX-ACCESS      read-only
        STATUS          current
        DESCRIPTION     "The software patch operation failed reason."
        ::=  {  zxAnSoftwarePatchEntry  9  }

------------------------------------------------------------------------------
-- 7.Software Running Patch Table
------------------------------------------------------------------------------
    zxAnSoftwareRunningPatchTable   OBJECT-TYPE
        SYNTAX      SEQUENCE  OF  ZxAnSoftwareRunningPatchEntry
        MAX-ACCESS  not-accessible
        STATUS      current
        DESCRIPTION "A table entry containing the running software patch
                      information."
        ::=  { zxAnSoftwareMgmt  5 }

    zxAnSoftwareRunningPatchEntry   OBJECT-TYPE
        SYNTAX      ZxAnSoftwareRunningPatchEntry
        MAX-ACCESS  not-accessible
        STATUS      current
        DESCRIPTION "Software patch information entry"
        INDEX       {  zxAnFileStorageDevRack,zxAnFileStorageDevShelf,
                      zxAnFileStorageDevSlot,zxAnFileStorageDevSubCard,
                      zxAnFileStorageDevType,zxAnFileStorageDevId,
                      zxAnRunningPatchName  }
        ::=  { zxAnSoftwareRunningPatchTable 1 }

    ZxAnSoftwareRunningPatchEntry  ::=  SEQUENCE {
        zxAnRunningPatchName           DisplayString,
        zxAnRunningPatchOwnerSwVersion DisplayString,
        zxAnRunningPatchVersion        DisplayString,
        zxAnRunningPatchSize           Integer32,
        zxAnRunningPatchBuildTime      DisplayString,
        zxAnRunningPatchActivatedTime  DisplayString,
        zxAnRunningPatchDesc           DisplayString
        }

    zxAnRunningPatchName      OBJECT-TYPE
        SYNTAX          DisplayString ( SIZE ( 0 .. 64  ) )
        MAX-ACCESS      not-accessible
        STATUS          current
        DESCRIPTION     "The file name of the patch "
        ::=  {  zxAnSoftwareRunningPatchEntry  1  }

    zxAnRunningPatchOwnerSwVersion  OBJECT-TYPE
        SYNTAX          DisplayString ( SIZE ( 0 .. 32  ) )
        MAX-ACCESS      read-only
        STATUS          current
        DESCRIPTION     "The software version of the patch belonging to."
        ::=  {  zxAnSoftwareRunningPatchEntry  2  }

    zxAnRunningPatchVersion  OBJECT-TYPE
        SYNTAX          DisplayString ( SIZE ( 0 .. 32  ) )
        MAX-ACCESS      read-only
        STATUS          current
        DESCRIPTION     "The version of the patch."
        ::=  {  zxAnSoftwareRunningPatchEntry  3  }

    zxAnRunningPatchSize OBJECT-TYPE
        SYNTAX          Integer32
        UNITS           "byte"
        MAX-ACCESS      read-only
        STATUS          current
        DESCRIPTION     "The size of the patch."
        ::=  {  zxAnSoftwareRunningPatchEntry  4  }

    zxAnRunningPatchBuildTime  OBJECT-TYPE
        SYNTAX          DisplayString  ( SIZE ( 1 .. 20  ) )
        MAX-ACCESS      read-only
        STATUS          current
        DESCRIPTION    "The software patch build time.The format is
                      yyyy-mm-dd HH:MM:SS. For example,  2001-01-01 02:22:33 "
        ::=  {  zxAnSoftwareRunningPatchEntry  5  }

    zxAnRunningPatchActivatedTime  OBJECT-TYPE
        SYNTAX          DisplayString  ( SIZE ( 1 .. 20  ) )
        MAX-ACCESS      read-only
        STATUS          current
        DESCRIPTION    "The time of the software patch is activated.The format
                      is yyyy-mm-dd HH:MM:SS.For example,2001-01-01 02:22:33 "
        ::=  {  zxAnSoftwareRunningPatchEntry  6  }

    zxAnRunningPatchDesc  OBJECT-TYPE
        SYNTAX          DisplayString ( SIZE ( 0 .. 255  ) )
        MAX-ACCESS      read-only
        STATUS          current
        DESCRIPTION     "The description of running patch"
        ::=  {  zxAnSoftwareRunningPatchEntry  7  }

------------------------------------------------------------------------------
-- 8.Update Boot Software
------------------------------------------------------------------------------
    zxAnCardUpdateObjects        OBJECT IDENTIFIER   ::= {zxAnSoftwareMgmt 6}
    zxAnCardUpdateGlobalObjects  OBJECT IDENTIFIER   ::=
                                                 { zxAnCardUpdateObjects  1 }
    zxAnCardBootSoftwareUpdate     OBJECT-TYPE
        SYNTAX          OBJECT IDENTIFIER
        MAX-ACCESS      read-write
        STATUS          current
        DESCRIPTION     "This value is an oid indicating the card index
            which will update its boot software from control card,
            and it includes
            {zxAnFileStorageDevRack,zxAnFileStorageDevShelf,
            zxAnFileStorageDevSlot, zxAnFileStorageDevSubCard } ,
            such as oid {1.1.3.0},  that is rack1.shelf1.slot3.subcard0  "
        ::=  {  zxAnCardUpdateGlobalObjects  1  }

------------------------------------------------------------------------------
-- 9.Update Boot Software Status Table
------------------------------------------------------------------------------
     zxAnCardSwUpdateStatusTable   OBJECT-TYPE
        SYNTAX      SEQUENCE  OF  ZxAnCardSwUpdateStatusEntry
        MAX-ACCESS  not-accessible
        STATUS      current
        DESCRIPTION "A table entry containing status information of
                    files updating software from control card to line card.
                    The boot software updating is supported only now."
        ::=  { zxAnCardUpdateObjects  2}

    zxAnCardSwUpdateStatusEntry   OBJECT-TYPE
        SYNTAX      ZxAnCardSwUpdateStatusEntry
        MAX-ACCESS  not-accessible
        STATUS      current
        DESCRIPTION "An entry of zxAnCardSwUpdateStatusTable."
        INDEX       {  zxAnCardSwRack,zxAnCardSwShelf,
                       zxAnCardSwSlot,zxAnCardSwSubCard  }
        ::=  { zxAnCardSwUpdateStatusTable 1 }

    ZxAnCardSwUpdateStatusEntry  ::=  SEQUENCE {
        zxAnCardSoftwareUpdateStatus           INTEGER,
        zxAnCardSoftwareUpdateProgress         INTEGER,
        zxAnCardSwUpdateFailedReason     DisplayString
        }

    zxAnCardSoftwareUpdateStatus       OBJECT-TYPE
        SYNTAX           INTEGER
        {
                notStarted(1),
                processing (2),
                failed(3),
                success(4)
        }
        MAX-ACCESS      read-only
        STATUS          current
        DESCRIPTION     "Status of updating software from control card to
                        line card."
        ::=  {  zxAnCardSwUpdateStatusEntry  1  }

    zxAnCardSoftwareUpdateProgress       OBJECT-TYPE
        SYNTAX          INTEGER  (0..100)
        UNITS           "%"
        MAX-ACCESS      read-only
        STATUS          current
        DESCRIPTION     "The progress of software updating."
        ::=  {  zxAnCardSwUpdateStatusEntry  2  }

    zxAnCardSwUpdateFailedReason     OBJECT-TYPE
        SYNTAX          DisplayString  ( SIZE ( 1 .. 64  ) )
        MAX-ACCESS      read-only
        STATUS          current
        DESCRIPTION     "The failed reason of updating software
                        from control card to line card."
        ::=  {  zxAnCardSwUpdateStatusEntry  3  }

------------------------------------------------------------------------------
-- 10.File Copy Operation Table
------------------------------------------------------------------------------

--
-- File Copy Operation will be started when zxAnFileCopySrcFileSpecific and
-- zxAnFileCopyDestDirSpecific are configured at same time.
--

    zxAnFileCopySrcFileSpecific     OBJECT-TYPE
        SYNTAX          OBJECT IDENTIFIER
        MAX-ACCESS      read-write
        STATUS          current
        DESCRIPTION     "This value is an oid which indicats the file index of
            the copied file, and it includes
            {zxAnFileStorageDevRack,zxAnFileStorageDevShelf,
            zxAnFileStorageDevSlot, zxAnFileStorageDevSubCard,
            zxAnFileStorageDevType,zxAnFileStorageDevId,zxAnFileName} ,
            such as oid {1.1.3.0.2.115.100.1.7.108.111.103.46.116.120.116},
            that is rack1.shelf1.slot3.subcard0.sd.1.log.txt  "
        ::=  {  zxAnFileCopyMgmt  1  }


    zxAnFileCopyDestDirSpecific     OBJECT-TYPE
        SYNTAX          OBJECT IDENTIFIER
        MAX-ACCESS      read-write
        STATUS          current
        DESCRIPTION     "This value is an oid which indicats the destination
            directory index of the copied file, and it includes
            {zxAnFileStorageDevRack,zxAnFileStorageDevShelf,
            zxAnFileStorageDevSlot, zxAnFileStorageDevSubCard,
            zxAnFileStorageDevType,zxAnFileStorageDevId } ,
            such as oid {1.1.3.0.5.102.108.97.115.104.1.3.108.111.103},
            that is rack1.shelf1.slot3.subcard0.flash.1.log "
        ::=  {  zxAnFileCopyMgmt  2  }


    zxAnFileCopyCancel     OBJECT-TYPE
        SYNTAX          INTEGER
                      {
                        cancel(1)
                      }
        MAX-ACCESS      read-write
        STATUS          current
        DESCRIPTION     "Cancel current file copy."
        ::=  {  zxAnFileCopyMgmt  3  }


     zxAnFileCopyStatusTable   OBJECT-TYPE
        SYNTAX      SEQUENCE  OF  ZxAnFileCopyStatusEntry
        MAX-ACCESS  not-accessible
        STATUS      current
        DESCRIPTION "A table entry containing  files copy  status information ."
        ::=  { zxAnFileCopyMgmt  15 }

    zxAnFileCopyStatusEntry   OBJECT-TYPE
        SYNTAX      ZxAnFileCopyStatusEntry
        MAX-ACCESS  not-accessible
        STATUS      current
        DESCRIPTION "An entry of zxAnFileCopyStatusTable."
        INDEX       {  zxAnFileStorageDevRack,zxAnFileStorageDevShelf,
                      zxAnFileStorageDevSlot,zxAnFileStorageDevSubCard,
                      zxAnFileStorageDevType,zxAnFileStorageDevId,
                      zxAnCopyFileName }
        ::=  { zxAnFileCopyStatusTable 1 }

    ZxAnFileCopyStatusEntry  ::=  SEQUENCE {
        zxAnCopyFileName             DisplayString,
        zxAnFileCopyStatus           INTEGER,
        zxAnFileCopyProgress         INTEGER,
        zxAnFileCopyFailedReason     DisplayString
        }

    zxAnCopyFileName      OBJECT-TYPE
        SYNTAX          DisplayString ( SIZE ( 0 .. 64  ) )
        MAX-ACCESS      not-accessible
        STATUS          current
        DESCRIPTION     "The name of file to be copied ."
        ::=  {  zxAnFileCopyStatusEntry  1  }

    zxAnFileCopyStatus       OBJECT-TYPE
        SYNTAX           INTEGER
        {
                notStarted (1) ,
                inprogress (2) ,
                success (3) ,
                failed (4)
        }
        UNITS           "byte"
        MAX-ACCESS      read-only
        STATUS          current
        DESCRIPTION     "Status of copying file ."
        ::=  {  zxAnFileCopyStatusEntry  2  }

    zxAnFileCopyProgress       OBJECT-TYPE
        SYNTAX          INTEGER  (0..100)
        UNITS           "%"
        MAX-ACCESS      read-only
        STATUS          current
        DESCRIPTION     "Total progress of copying file."
        ::=  {  zxAnFileCopyStatusEntry  3  }

    zxAnFileCopyFailedReason     OBJECT-TYPE
        SYNTAX          DisplayString  ( SIZE ( 1 .. 64  ) )
        MAX-ACCESS      read-only
        STATUS          current
        DESCRIPTION     "Failed reason of copying file ."
        ::=  {  zxAnFileCopyStatusEntry  4  }


------------------------------------------------------------------------------
-- 11.File Synchronization Status Between Master And Slave Control Card
------------------------------------------------------------------------------

   zxAnFileSyncStatusTable   OBJECT-TYPE
        SYNTAX      SEQUENCE  OF  ZxAnFileSyncStatusEntry
        MAX-ACCESS  not-accessible
        STATUS      current
        DESCRIPTION "A table entry containing status information of
                    files synchronization from master card to slave card."
        ::=  { zxAnFileSynchMgmt  9 }

    zxAnFileSyncStatusEntry   OBJECT-TYPE
        SYNTAX      ZxAnFileSyncStatusEntry
        MAX-ACCESS  not-accessible
        STATUS      current
        DESCRIPTION "An entry of zxAnFileSyncStatusTable."
        INDEX       {  zxAnFileStorageDevRack,zxAnFileStorageDevShelf,
                       zxAnFileStorageDevSlot,zxAnFileStorageDevSubCard,
                       zxAnFileStorageDevType,zxAnFileStorageDevId,
                       zxAnFileSyncFileName }
        ::=  { zxAnFileSyncStatusTable 1 }

    ZxAnFileSyncStatusEntry  ::=  SEQUENCE {
        zxAnFileSyncFileName         DisplayString,
        zxAnFileSyncStatus           INTEGER,
        zxAnFileSyncProgress         INTEGER,
        zxAnFileSyncFailedReason     DisplayString
        }

    zxAnFileSyncFileName      OBJECT-TYPE
        SYNTAX          DisplayString ( SIZE ( 0 .. 64  ) )
        MAX-ACCESS      not-accessible
        STATUS          current
        DESCRIPTION     "Name of file to be synchronized from master card to
                         slave control card."
        ::=  {  zxAnFileSyncStatusEntry  1  }

    zxAnFileSyncStatus       OBJECT-TYPE
        SYNTAX           INTEGER
        {
                notStarted(1),
                processing (2),
                failed(3),
                success(4),
                sameversion(5)
        }
        UNITS           "byte"
        MAX-ACCESS      read-only
        STATUS          current
        DESCRIPTION     "Status of synchronization file from master card to
                         slave card."
        ::=  {  zxAnFileSyncStatusEntry  2  }

    zxAnFileSyncProgress       OBJECT-TYPE
        SYNTAX          INTEGER  (0..100)
        UNITS           "%"
        MAX-ACCESS      read-only
        STATUS          current
        DESCRIPTION     "The total progress of sync file."
        ::=  {  zxAnFileSyncStatusEntry  3  }

    zxAnFileSyncFailedReason     OBJECT-TYPE
        SYNTAX          DisplayString  ( SIZE ( 1 .. 64  ) )
        MAX-ACCESS      read-only
        STATUS          current
        DESCRIPTION     "The failed reason of synchronization file
                        from master card to slave card."
        ::=  {  zxAnFileSyncStatusEntry  4  }

------------------------------------------------------------------------------
-- 16.Software Automatic Update Management
------------------------------------------------------------------------------
    zxAnSwAutoUpdateMgmt   OBJECT IDENTIFIER  ::=  {  zxAnSoftwareMgmt  7  }
    zxAnSwAutoUpdateChkGroup  OBJECT IDENTIFIER
                                      ::=  {  zxAnSwAutoUpdateMgmt  1  }
    zxAnSwAutoUpdateGroup  OBJECT IDENTIFIER  ::=  {  zxAnSwAutoUpdateMgmt  2  }

    zxAnSwAutoUpdateChkEnable OBJECT-TYPE
        SYNTAX      INTEGER{
            enable(1),
            disable(2)
        }
        MAX-ACCESS  read-write
        STATUS      current
        DESCRIPTION
            "Enable or disable the software periodic check function."
        DEFVAL    { disable }
        ::=  {  zxAnSwAutoUpdateChkGroup  1 }

    zxAnSwAutoUpdateChkStartTime OBJECT-TYPE
        SYNTAX      DisplayString(SIZE( 0..19))
        MAX-ACCESS  read-write
        STATUS      current
        DESCRIPTION
            "The start time of software periodic check.
            For example:yyyy-mm-dd HH:MM:SS.(2001-01-01 02:22:33)."
        ::=  {  zxAnSwAutoUpdateChkGroup  2  }

    zxAnSwAutoUpdateChkInterval OBJECT-TYPE
        SYNTAX      Integer32(0..8760)
        UNITS       "hours"
        MAX-ACCESS  read-write
        STATUS      current
        DESCRIPTION
            "The interval of software periodic check.
            Value 0 means unconfigured."
        DEFVAL    { 24 }
        ::=  {  zxAnSwAutoUpdateChkGroup  3  }

    zxAnSwAutoUpdateCurrChkStartTime OBJECT-TYPE
        SYNTAX      DisplayString(SIZE( 0..19))
        MAX-ACCESS  read-only
        STATUS      current
        DESCRIPTION
            "The start time of current software periodic check.
            For example:yyyy-mm-dd HH:MM:SS.(2001-01-01 02:22:33)."
        ::=  {  zxAnSwAutoUpdateChkGroup  4  }

    zxAnSwAutoUpdateChkDifferFiles OBJECT-TYPE
        SYNTAX      DisplayString(SIZE(0..255))
        MAX-ACCESS  read-only
        STATUS      current
        DESCRIPTION
            "The different files name between NE and file server.
            File name is separated by ',', For example:xxx,xxx,xxx."
        ::=  {  zxAnSwAutoUpdateChkGroup  5  }

    zxAnSwAutoUpdateChkStatus OBJECT-TYPE
        SYNTAX      INTEGER  {
            notStarted(1),
            inProgress(2),
            success(3),
            failed(4)
        }
        MAX-ACCESS  read-only
        STATUS      current
        DESCRIPTION
            "The status of software periodic check."
        ::=  {  zxAnSwAutoUpdateChkGroup  6  }

    zxAnSwAutoUpdateChkFailedReason OBJECT-TYPE
        SYNTAX      INTEGER  {
            noError(1),
            fileServerUnconfigured(2),
            fileServerConnectFailed(3),
            fileServerLoginFailed(4),
            fileServerPathError(5),
            fileServerProtocolTypeError(6),
            deviceCheckFailed(7),
            otherErrors(255)
        }
        MAX-ACCESS  read-only
        STATUS      current
        DESCRIPTION
            "The failed reason of software periodic check."
        ::=  {  zxAnSwAutoUpdateChkGroup  7  }

    zxAnSwAutoUpdateAction OBJECT-TYPE
        SYNTAX      INTEGER{
            start(1)
        }
        MAX-ACCESS  read-write
        STATUS      current
        DESCRIPTION
            "The automatic update action.
            It means to start the automatic update progress."
        ::=  {  zxAnSwAutoUpdateGroup  1  }

    zxAnSwAutoUpdateActiveEnable OBJECT-TYPE
        SYNTAX      INTEGER{
            enable(1),
            disable(2)
        }
        MAX-ACCESS  read-write
        STATUS      current
        DESCRIPTION
            "Enable or disable the software active function. Active means to
            reset card except control card."
        DEFVAL    { enable }
        ::=  {  zxAnSwAutoUpdateGroup  2  }

    zxAnSwAutoUpdateVerBackupEnable OBJECT-TYPE
        SYNTAX      INTEGER{
            enable(1),
            disable(2)
        }
        MAX-ACCESS  read-write
        STATUS      current
        DESCRIPTION
            "Enable or disable the version file backup function."
        DEFVAL    { enable }
        ::=  {  zxAnSwAutoUpdateGroup  3  }

    zxAnSwAutoUpdateStatus OBJECT-TYPE
        SYNTAX      INTEGER{
            notStarted(1),
            updateStarting(2),
            backingUpFile(3),
            versionFileAnalyzing(4),
            versionFileDownloading(5),
            versionFileDownloadComplete(6),
            masterSlaveSynchronizing(7),
            masterSlaveSyncComplete(8),
            versionFileLoading(9),
            bootUpdating(10),
            bootUpdateComplete(11),
            updateSuccess(12),
            readyToReboot(13),
            sameVersion(14),
            updateFailed(255)
        }
        MAX-ACCESS  read-only
        STATUS      current
        DESCRIPTION
            "The status of automatic update."
        ::=  {  zxAnSwAutoUpdateGroup  4  }

    zxAnSwAutoUpdateCurrFileName OBJECT-TYPE
        SYNTAX      DisplayString(SIZE(0..64))
        MAX-ACCESS  read-only
        STATUS      current
        DESCRIPTION
            "The name of current file which is updated."
        ::=  {  zxAnSwAutoUpdateGroup  5  }

    zxAnSwAutoUpdateCurrFileSize OBJECT-TYPE
        SYNTAX      Integer32
        UNITS       "bytes"
        MAX-ACCESS  read-only
        STATUS      current
        DESCRIPTION
            "The size of current file which is updated."
        ::=  {  zxAnSwAutoUpdateGroup  6  }

    zxAnSwAutoUpdateCurrFileProgress OBJECT-TYPE
        SYNTAX      Integer32(0..100)
        UNITS       "percent"
        MAX-ACCESS  read-only
        STATUS      current
        DESCRIPTION
             "The updating progress of current file."
        ::=  {  zxAnSwAutoUpdateGroup  7  }

    zxAnSwAutoUpdateTotalFiles OBJECT-TYPE
        SYNTAX      Integer32
        MAX-ACCESS  read-only
        STATUS      current
        DESCRIPTION
            "Total count of files will be updated."
        ::=  {  zxAnSwAutoUpdateGroup  8  }

    zxAnSwAutoUpdateSuccessFiles OBJECT-TYPE
        SYNTAX      Integer32
        MAX-ACCESS  read-only
        STATUS      current
        DESCRIPTION
            "Count of files which are updated successfully."
        ::=  {  zxAnSwAutoUpdateGroup  9  }

    zxAnSwAutoUpdateFailedReason OBJECT-TYPE
        SYNTAX      INTEGER{
            noError(1),
            backupDataError(2),
            backupLogError(3),
            backupConfigurationError(4),
            backupVersionFileError(5),
            backupOtherError(6),
            analyzingConfigurationError(7),
            analyzingVersionFileError(8),
            diskFull(9),
            downloadingVersionFileError(10),
            updateVersionFileError(11),
            updateBootError(12),
            masterSlaveSynchronizeError(13),
            updateConflict(14),
            unavailableServer(15),
            slaveCardNotInService(16),
            otherErrors(255)
        }
        MAX-ACCESS  read-only
        STATUS      current
        DESCRIPTION
            "The failed reason of automatic update."
        ::=  {  zxAnSwAutoUpdateGroup  10  }



--------------------------------------------------------------------------------
-- 15.File Management Traps
--------------------------------------------------------------------------------

    zxAnSwUpdateTrapGroup    OBJECT IDENTIFIER  ::= { zxAnFileTrapObjects 2 }


--------------------------------------------------------------------------------
-- 15.2 Update Traps
--------------------------------------------------------------------------------

    zxAnSwAutoUpdateFinished NOTIFICATION-TYPE
        OBJECTS { zxAnSwAutoUpdateStatus,zxAnSwAutoUpdateFailedReason }
        STATUS  current
        DESCRIPTION
            "A zxAnSwAutoUpdateFinished is sent when the agent has detected that
            the automatic update is finished."
        ::= { zxAnSwUpdateTrapGroup 1 }

    zxAnSwAutoUpdateVersionDiffer NOTIFICATION-TYPE
        OBJECTS { zxAnSwAutoUpdateCurrChkStartTime,
                  zxAnSwAutoUpdateChkDifferFiles }
        STATUS  current
        DESCRIPTION
            "A zxAnSwAutoUpdateVersionDiffer is sent when the agent has
            detected different version files between NE and file server."
        ::= { zxAnSwUpdateTrapGroup 2 }

    zxAnSwAutoUpdateVersionChkFailed NOTIFICATION-TYPE
        OBJECTS { zxAnSwAutoUpdateCurrChkStartTime,
                  zxAnSwAutoUpdateChkFailedReason }
        STATUS  current
        DESCRIPTION
            "A zxAnSwAutoUpdateVersionChkFailed is sent when the agent has
            detected that version check is failed."
        ::= { zxAnSwUpdateTrapGroup 3 }
END
