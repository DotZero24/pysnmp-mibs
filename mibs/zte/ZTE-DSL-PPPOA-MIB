ZTE-DSL-PPPOA-MIB  DEFINITIONS ::= BEGIN
  IMPORTS
    TEXTUAL-CONVENTION, DisplayString,MacAddress,RowStatus    FROM SNMPv2-TC
    MODULE-IDENTITY, OBJECT-TYPE, enterprises, Integer32      FROM SNMPv2-SMI
    ifIndex                                                   FROM IF-MIB;


  zxDslPppoaMib  MODULE-IDENTITY
    LAST-UPDATED  "200701311000Z"
    ORGANIZATION  "ZTE Corporation"
    CONTACT-INFO  "suchunshan
                  Mail: suchunshan@zte.com.cn
                  Tel : 021-68896292"
    DESCRIPTION   "This MIB defines zte dsl DHCP function modules' managed objects."
    ::=  {  zxDsl  29  }

    zte       OBJECT IDENTIFIER ::= { enterprises 3902 }
    zxDsl     OBJECT IDENTIFIER ::= { zte 1004 }


    zxDslPppoaGlobal OBJECT IDENTIFIER ::= { zxDslPppoaMib 1 }


--------------------------------------------------------------------------------
-- Following objects are defined.
-- 1.PPPoA Global
-- 2.Mac Pool Table
-- 3.PPPoA Interface Table
--------------------------------------------------------------------------------



------------------------------------------------------------------------------
-- 1.PPPoA Global
------------------------------------------------------------------------------

  zxDslPppoaEchoTimeout OBJECT-TYPE
        SYNTAX      Integer32(1..1800)
        UNITS       "sec"
        MAX-ACCESS  read-write
        STATUS      current
        DESCRIPTION
            "The timeout of PPPOA echo ."
          ::= { zxDslPppoaGlobal 1}


  zxDslPppoaoeAutoAdapt  OBJECT-TYPE
            SYNTAX      Integer32 {
                enable  (1),
                disable (2)
                }
            MAX-ACCESS  read-write
            STATUS      current
            DESCRIPTION
                "Enable or disable adaption of PPPoA and PPPoE automatically ."
            ::= {zxDslPppoaGlobal 2 }



------------------------------------------------------------------------------
-- 2.Mac Pool Table
------------------------------------------------------------------------------


  zxDslMacPoolTable OBJECT-TYPE
        SYNTAX SEQUENCE OF ZxDslMacPoolEntry
        MAX-ACCESS not-accessible
        STATUS current
        DESCRIPTION
            "Mac Pool information table"
        ::= { zxDslPppoaMib 2 }

   zxDslMacPoolEntry OBJECT-TYPE
        SYNTAX ZxDslMacPoolEntry
        MAX-ACCESS not-accessible
        STATUS current
        DESCRIPTION
            "Mac Pool information table"
      INDEX { zxDslMacPoolIndex }
        ::= { zxDslMacPoolTable 1 }

    ZxDslMacPoolEntry ::= SEQUENCE
    {
        zxDslMacPoolIndex           Integer32,
        zxDslMacPoolStartMac        MacAddress,
        zxDslMacPoolSize            Integer32,
        zxDslMacPoolAvailableSize   Integer32,
        zxDslMacPoolType            INTEGER,
        zxDslMacPoolRowStatus       RowStatus
    }


     zxDslMacPoolIndex OBJECT-TYPE
        SYNTAX      Integer32(1..32)
        MAX-ACCESS  not-accessible
        STATUS      current
        DESCRIPTION
            "The idex of this table."
          ::= { zxDslMacPoolEntry 1}


     zxDslMacPoolStartMac OBJECT-TYPE
        SYNTAX      MacAddress
        MAX-ACCESS  read-create
        STATUS      current
        DESCRIPTION
            "Strating MacAddress in the pool."
          ::= { zxDslMacPoolEntry 2}


     zxDslMacPoolSize OBJECT-TYPE
        SYNTAX      Integer32(1..1024)
        MAX-ACCESS  read-create
        STATUS      current
        DESCRIPTION
            "The size of this MacAddress pool."
          ::= { zxDslMacPoolEntry 3}


     zxDslMacPoolAvailableSize OBJECT-TYPE
        SYNTAX      Integer32(0..1024)
        MAX-ACCESS  read-only
        STATUS      current
        DESCRIPTION
            "The available space of the pool,that is the number of MacAddress
        will be allocated."
          ::= { zxDslMacPoolEntry 4}


     zxDslMacPoolType OBJECT-TYPE
        SYNTAX      INTEGER
             {
                    ipoa(1),
                    mat(2),
                    pppoa(3)
             }
        MAX-ACCESS  read-create
        STATUS      current
        DESCRIPTION
            "The type of the pool,such as IPOA, MAT,PPPoA."
          ::= { zxDslMacPoolEntry 5}

     zxDslMacPoolRowStatus OBJECT-TYPE
        SYNTAX      RowStatus
        MAX-ACCESS  read-create
        STATUS      current
        DESCRIPTION
            "The RowStatus of the instance."
          ::= { zxDslMacPoolEntry 6}



------------------------------------------------------------------------------
-- 3.PPPoA Interface Table
------------------------------------------------------------------------------


  zxDslPppoaInterfaceTable OBJECT-TYPE
        SYNTAX SEQUENCE OF ZxDslPppoaInterfaceEntry
        MAX-ACCESS not-accessible
        STATUS current
        DESCRIPTION
            "PPPoA Interface information table"
        ::= { zxDslPppoaMib 3 }

   zxDslPppoaInterfaceEntry OBJECT-TYPE
        SYNTAX ZxDslPppoaInterfaceEntry
        MAX-ACCESS not-accessible
        STATUS current
        DESCRIPTION
            "PPPoA Interface information table"
      INDEX { zxDslPppoaIfIndex,zxDslPppoaIfPvcNo }
        ::= { zxDslPppoaInterfaceTable 1 }

    ZxDslPppoaInterfaceEntry ::= SEQUENCE
    {
        zxDslPppoaIfIndex                 Integer32,
        zxDslPppoaIfPvcNo                 Integer32,
        zxDslPppoaIfAdminStatus           INTEGER,
        zxDslPppoaIfMacAssignMode         INTEGER,
        zxDslPppoaIfMacPoolIndex          Integer32,
        zxDslPppoaIfManualAssignedMac     MacAddress,
        zxDslPppoaIfActualMac             MacAddress,
        zxDslPppoaIfMgmtOperstatus        INTEGER,
        zxDslPppoaIfSeesionId             Integer32,
        zxDslPppoaIfServerMac             MacAddress,
        zxDslPppoaIfLcpCfgReqPkts         Counter32,
        zxDslPppoaIfEchoAckPkts           Counter32,
        zxDslPppoaIfLcpTerminateReqPkts   Counter32,
        zxDslPppoaIfPadoPkts              Counter32,
        zxDslPppoaIfPadsPkts              Counter32,
        zxDslPppoaIfPadtPkts              Counter32,
        zxDslPppoaIfAction                Counter32
    }



     zxDslPppoaIfIndex OBJECT-TYPE
        SYNTAX      Integer32
        MAX-ACCESS  not-accessible
        STATUS      current
        DESCRIPTION
            "The interface idex of user port."
          ::= { zxDslPppoaInterfaceEntry 1}


     zxDslPppoaIfPvcNo OBJECT-TYPE
        SYNTAX      Integer32
        MAX-ACCESS  not-accessible
        STATUS      current
        DESCRIPTION
            "The Pvc No. of user port."
          ::= { zxDslPppoaInterfaceEntry 2}


     zxDslPppoaIfAdminStatus OBJECT-TYPE
        SYNTAX      INTEGER
             {
                    enable(1),
                    disable(2)
             }
        MAX-ACCESS  read-write
        STATUS      current
        DESCRIPTION
            "The administrative status of the port PPPoA."
          ::= { zxDslPppoaInterfaceEntry 3}


     zxDslPppoaIfMacAssignMode OBJECT-TYPE
        SYNTAX      INTEGER
             {
                    fromAssignedPool(1),
                    manualAssigned(2),
                    auto(3)   -- search all pools
             }
        MAX-ACCESS  read-write
        STATUS      current
        DESCRIPTION
            "The assignment mode of the user's MacAddress."
          ::= { zxDslPppoaInterfaceEntry 4}


     zxDslPppoaIfMacPoolIndex OBJECT-TYPE
        SYNTAX      Integer32
        MAX-ACCESS  read-write
        STATUS      current
        DESCRIPTION
            "MacPoolIndex to be used to get a MacAddress.It must be configured
            when zxDslPppoaIfMacAssignMode=fromAssignedPool(1). "
          ::= { zxDslPppoaInterfaceEntry 5}



     zxDslPppoaIfManualAssignedMac OBJECT-TYPE
        SYNTAX      MacAddress
        MAX-ACCESS  read-write
        STATUS      current
        DESCRIPTION
            "The MacAddress manual assigned to the port."
          ::= { zxDslPppoaInterfaceEntry 6}



     zxDslPppoaIfActualMac OBJECT-TYPE
        SYNTAX      MacAddress
        MAX-ACCESS  read-only
        STATUS      current
        DESCRIPTION
            "The Actual MacAddress that the port obtained."
          ::= { zxDslPppoaInterfaceEntry 7}


    zxDslPppoaIfMgmtOperstatus  OBJECT-TYPE
        SYNTAX      INTEGER
             {
                  invalidState(0) ,
                  waitLcpCfgreq(1),
                  waitPado(2),
                  waitPads(3),
                  waitRetry(4),
                  pppoeConnnect(5)
             }
        MAX-ACCESS  read-only
        STATUS      current
        DESCRIPTION
            "The PPPOA management operatinal status."
          ::= { zxDslPppoaInterfaceEntry 8}



     zxDslPppoaIfSeesionId OBJECT-TYPE
        SYNTAX      Integer32
        MAX-ACCESS  read-only
        STATUS      current
        DESCRIPTION
            "The SeesionId that the port obtained from server."
          ::= { zxDslPppoaInterfaceEntry 9}



     zxDslPppoaIfServerMac OBJECT-TYPE
        SYNTAX      MacAddress
        MAX-ACCESS  read-only
        STATUS      current
        DESCRIPTION
            "The Server MacAddress that the port obtained from server."
          ::= { zxDslPppoaInterfaceEntry 10}


     zxDslPppoaIfLcpCfgReqPkts OBJECT-TYPE
        SYNTAX      Counter32
        MAX-ACCESS  read-only
        STATUS      current
        DESCRIPTION
            "The recieved LcpCfgReqPkts from userside."
          ::= { zxDslPppoaInterfaceEntry 11}



     zxDslPppoaIfEchoAckPkts OBJECT-TYPE
        SYNTAX      Counter32
        MAX-ACCESS  read-only
        STATUS      current
        DESCRIPTION
            "The recieved LcpCfgReqPkts from userside."
          ::= { zxDslPppoaInterfaceEntry 12}




     zxDslPppoaIfLcpTerminateReqPkts OBJECT-TYPE
        SYNTAX      Counter32
        MAX-ACCESS  read-only
        STATUS      current
        DESCRIPTION
            "The recieved LcpTerminateReqPkts from userside."
          ::= { zxDslPppoaInterfaceEntry 13}



     zxDslPppoaIfPadoPkts OBJECT-TYPE
        SYNTAX      Counter32
        MAX-ACCESS  read-only
        STATUS      current
        DESCRIPTION
            "The recieved PadoPkts from server."
          ::= { zxDslPppoaInterfaceEntry 14}



     zxDslPppoaIfPadsPkts OBJECT-TYPE
        SYNTAX      Counter32
        MAX-ACCESS  read-only
        STATUS      current
        DESCRIPTION
            "The recieved PadsPkt from server."
          ::= { zxDslPppoaInterfaceEntry 15}



     zxDslPppoaIfPadtPkts OBJECT-TYPE
        SYNTAX      Counter32
        MAX-ACCESS  read-only
        STATUS      current
        DESCRIPTION
            "The recieved PadtPkts from server."
          ::= { zxDslPppoaInterfaceEntry 16}

     zxDslPppoaIfAction OBJECT-TYPE
        SYNTAX      Counter32
        MAX-ACCESS  read-write
        STATUS      current
        DESCRIPTION
            "action(1): update the dynamic data of pppoa user"
          ::= { zxDslPppoaInterfaceEntry 17}

END
