-- ########################################################################
-- #
-- # CLAVISTER-TRAPS-MIB:  Clavister AB
-- #
-- # Copyright (c) by Clavister AB
-- # All rights reserved.
-- #
-- ########################################################################

CLAVISTER-TRAPS-MIB DEFINITIONS ::= BEGIN

IMPORTS
    clavisterOSTrap, clavisterOSTrapInfo
        FROM CLAVISTER-SMI
    MODULE-COMPLIANCE, NOTIFICATION-GROUP, OBJECT-GROUP
        FROM SNMPv2-CONF
    MODULE-IDENTITY, NOTIFICATION-TYPE, OBJECT-TYPE
        FROM SNMPv2-SMI
    DisplayString
        FROM SNMPv2-TC;

clavisterOSTrapMibModule MODULE-IDENTITY
    LAST-UPDATED "201510211700Z"
    ORGANIZATION
        "Clavister AB"
    CONTACT-INFO
        "Clavister Support

         Clavister AB
         Sjogatan 6J
         SE-891 60 ORNSKOLDSVIK
         SWEDEN

         Tel: +46-660-299200
         https://www.clavister.com/support/"
    DESCRIPTION
        "Clavister Trap MIB."

    REVISION  "201510211700Z"
    DESCRIPTION
        "Updated contact info"
    REVISION    "200710310000Z"
    DESCRIPTION
        "Initial version."


    ::= { clavisterOSTrapInfo 0 }
clavisterOSTrapVarSeverity OBJECT-TYPE
    SYNTAX      INTEGER
                  { emergency(0),
                    alert(1),
                    critical(2),
                    error(3),
                    warning(4),
                    notice(5),
                    info(6),
                    debug(7) }
    MAX-ACCESS  accessible-for-notify
    STATUS      current
    DESCRIPTION
        "Severity"
    ::= { clavisterOSTrapInfo 4 }

clavisterOSTrapVarCategory OBJECT-TYPE
    SYNTAX      DisplayString
    MAX-ACCESS  accessible-for-notify
    STATUS      current
    DESCRIPTION
        "Category"
    ::= { clavisterOSTrapInfo 5 }

clavisterOSTrapVarID OBJECT-TYPE
    SYNTAX      DisplayString
    MAX-ACCESS  accessible-for-notify
    STATUS      current
    DESCRIPTION
        "ID"
    ::= { clavisterOSTrapInfo 6 }

clavisterOSTrapVarEvent OBJECT-TYPE
    SYNTAX      DisplayString
    MAX-ACCESS  accessible-for-notify
    STATUS      current
    DESCRIPTION
        "Event"
    ::= { clavisterOSTrapInfo 7 }

clavisterOSTrapVarAction OBJECT-TYPE
    SYNTAX      DisplayString
    MAX-ACCESS  accessible-for-notify
    STATUS      current
    DESCRIPTION
        "Action"
    ::= { clavisterOSTrapInfo 8 }

clavisterOSTrapVarTime OBJECT-TYPE
    SYNTAX      DisplayString
    MAX-ACCESS  accessible-for-notify
    STATUS      current
    DESCRIPTION
        "Timestamp of event"
    ::= { clavisterOSTrapInfo 9 }

clavisterOSTrapVarMessage OBJECT-TYPE
    SYNTAX      DisplayString
    MAX-ACCESS  accessible-for-notify
    STATUS      current
    DESCRIPTION
        "Formated string with all variables"
    ::= { clavisterOSTrapInfo 10 }

clavisterOSGenericTrap NOTIFICATION-TYPE
    OBJECTS     { clavisterOSTrapVarSeverity,
                  clavisterOSTrapVarCategory,
                  clavisterOSTrapVarID,
                  clavisterOSTrapVarEvent,
                  clavisterOSTrapVarAction,
                  clavisterOSTrapVarTime,
                  clavisterOSTrapVarMessage }
    STATUS      current
    DESCRIPTION
        "Generic Event"
    ::= { clavisterOSTrap 1 }

clavisterOSTrapGroupTrap NOTIFICATION-GROUP
    NOTIFICATIONS { clavisterOSGenericTrap }
    STATUS      current
    DESCRIPTION
        "Traps"
    ::= { clavisterOSTrapInfo 1 }

clavisterOSTrapGroupVar OBJECT-GROUP
    OBJECTS     { clavisterOSTrapVarSeverity,
                  clavisterOSTrapVarCategory,
                  clavisterOSTrapVarID,
                  clavisterOSTrapVarEvent,
                  clavisterOSTrapVarAction,
                  clavisterOSTrapVarTime,
                  clavisterOSTrapVarMessage }
    STATUS      current
    DESCRIPTION
        "Variables"
    ::= { clavisterOSTrapInfo 2 }

clavisterOSTrapCompliance MODULE-COMPLIANCE
    STATUS      current
    DESCRIPTION
        "Compliance"

    MODULE      -- this module

        MANDATORY-GROUPS
                { clavisterOSTrapGroupTrap,
                  clavisterOSTrapGroupVar }

    ::= { clavisterOSTrapInfo 3 }

END -- end of module CLAVISTER-TRAPS-MIB.
