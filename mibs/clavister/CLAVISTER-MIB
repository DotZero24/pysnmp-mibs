-- ########################################################################
-- #
-- # CLAVISTER-MIB:  Clavister AB
-- #
-- # Copyright (c) by Clavister AB
-- # All rights reserved.
-- #
-- ########################################################################

CLAVISTER-MIB DEFINITIONS ::= BEGIN

IMPORTS
    clavisterMibConfs, clavisterMibModules, clavisterMibObjectGroups,
    clavisterOSStats
        FROM CLAVISTER-SMI
    MODULE-COMPLIANCE, OBJECT-GROUP
        FROM SNMPv2-CONF
    Counter32, Counter64, Gauge32, Integer32, MODULE-IDENTITY,
    OBJECT-TYPE
        FROM SNMPv2-SMI
    DisplayString
        FROM SNMPv2-TC;

clavisterStatsMibModule MODULE-IDENTITY
    LAST-UPDATED "201803021300Z"
    ORGANIZATION
        "Clavister AB"
    CONTACT-INFO
        "Clavister Support

         Clavister AB
         Sjogatan 6J
         SE-891 60 ORNSKOLDSVIK
         SWEDEN

         Tel: +46-660-299200
         https://www.clavister.com/support/"
    DESCRIPTION
        "The MIB module for Clavister Core products."

    REVISION  "201803021300Z"
    DESCRIPTION
        "Added DNS ALG counters"
    REVISION  "201703281300Z"
    DESCRIPTION
        "Added Threat Prevention Blacklist counters"
    REVISION  "201701161200Z"
    DESCRIPTION
        "Added High Availability Status"
    REVISION  "201511231200Z"
    DESCRIPTION
        "Full statistics for E20"
    REVISION  "201510211700Z"
    DESCRIPTION
        "Updated contact info"
    REVISION  "201509211700Z"
    DESCRIPTION
        "Added switch statistics for E20"
    REVISION  "201509161200Z"
    DESCRIPTION
        "Added Fastpath statistics values"
    REVISION  "201403311200Z"
    DESCRIPTION
        "Added crypto accelerator statistics"
    REVISION  "201312101200Z"
    DESCRIPTION
        "Added memory counters"
    REVISION  "201009021139Z"
    DESCRIPTION
        "Added 64-bit counters"
    REVISION  "200911091339Z"
    DESCRIPTION
        "Updated contact info and added values for opened and closed connections per second"
    REVISION  "200811181605Z"
    DESCRIPTION
        "Added value for timer usage"
    REVISION  "200810141227Z"
    DESCRIPTION
        "Added values for memory usage and TCP buffer usage"
    REVISION  "200803061018Z"
    DESCRIPTION
        "Added SMTP ALG statistics"
    REVISION    "200708161019Z"
    DESCRIPTION
        "Extending the mib by adding more statistics values"
    REVISION    "200705280800Z"
    DESCRIPTION
        "Added Clavister interface statistics table"
    REVISION    "200702130900Z"
    DESCRIPTION
        "Initial version."


    ::= { clavisterMibModules 1 }

clvSystem OBJECT IDENTIFIER
    ::= { clavisterOSStats 1 }

clvSysCpuLoad OBJECT-TYPE
    SYNTAX      Gauge32
    MAX-ACCESS  read-only
    STATUS      current
    DESCRIPTION
        "The system cpu load."
    ::= { clvSystem 1 }

clvSysForwardedBits OBJECT-TYPE
    SYNTAX      Counter32
    MAX-ACCESS  read-only
    STATUS      current
    DESCRIPTION
        "The number of bits forwarded through the gateway."
    ::= { clvSystem 2 }

clvSysForwardedPackets OBJECT-TYPE
    SYNTAX      Counter32
    MAX-ACCESS  read-only
    STATUS      current
    DESCRIPTION
        "Total number of forwarded packets."
    ::= { clvSystem 3 }

clvSysBuffUse OBJECT-TYPE
    SYNTAX      Gauge32
    MAX-ACCESS  read-only
    STATUS      current
    DESCRIPTION
        "The current number of buffers in use."
    ::= { clvSystem 4 }

clvSysConns OBJECT-TYPE
    SYNTAX      Gauge32
    MAX-ACCESS  read-only
    STATUS      current
    DESCRIPTION
        "The number of connections."
    ::= { clvSystem 5 }

clvSysPerStateCounters OBJECT IDENTIFIER
    ::= { clvSystem 6 }

clvSysPscTcpSyn OBJECT-TYPE
    SYNTAX      Gauge32
    MAX-ACCESS  read-only
    STATUS      current
    DESCRIPTION
        "Number of TCP connections in the SYN state."
    ::= { clvSysPerStateCounters 1 }

clvSysPscTcpOpen OBJECT-TYPE
    SYNTAX      Gauge32
    MAX-ACCESS  read-only
    STATUS      current
    DESCRIPTION
        "Number of TCP connections in the OPEN state."
    ::= { clvSysPerStateCounters 2 }

clvSysPscTcpFin OBJECT-TYPE
    SYNTAX      Gauge32
    MAX-ACCESS  read-only
    STATUS      current
    DESCRIPTION
        "Number of TCP connections in the FIN state."
    ::= { clvSysPerStateCounters 3 }

clvSysPscUdp OBJECT-TYPE
    SYNTAX      Gauge32
    MAX-ACCESS  read-only
    STATUS      current
    DESCRIPTION
        "Number of UDP connections."
    ::= { clvSysPerStateCounters 4 }

clvSysPscIcmp OBJECT-TYPE
    SYNTAX      Gauge32
    MAX-ACCESS  read-only
    STATUS      current
    DESCRIPTION
        "Number of ICMP connections."
    ::= { clvSysPerStateCounters 5 }

clvSysPscOther OBJECT-TYPE
    SYNTAX      Gauge32
    MAX-ACCESS  read-only
    STATUS      current
    DESCRIPTION
        "Number of other connections."
    ::= { clvSysPerStateCounters 6 }

clvIfStatsTable OBJECT-TYPE
    SYNTAX      SEQUENCE OF ClvIfStatsEntry
    MAX-ACCESS  not-accessible
    STATUS      current
    DESCRIPTION
        "A table of Clavister specific interfaces statistics"
    ::= { clvSystem 7 }

clvIfStatsEntry OBJECT-TYPE
    SYNTAX      ClvIfStatsEntry
    MAX-ACCESS  not-accessible
    STATUS      current
    DESCRIPTION
        "The row in a table of Clavister specific interface statistics"
    INDEX       { clvIfStatsIndex }
    ::= { clvIfStatsTable 1 }

ClvIfStatsEntry ::= SEQUENCE {
    clvIfStatsIndex     Integer32,
    clvIfName           DisplayString,
    clvIfFragsIn        Counter32,
    clvIfFragReassOk    Counter32,
    clvIfFragReassFail  Counter32,
    clvIfPktsInCnt      Counter32,
    clvIfPktsOutCnt     Counter32,
    clvIfBitsInCnt      Counter32,
    clvIfBitsOutCnt     Counter32,
    clvIfPktsTotCnt     Counter32,
    clvIfBitsTotCnt     Counter32,
    clvIfHCPktsInCnt    Counter64,
    clvIfHCPktsOutCnt   Counter64,
    clvIfHCBitsInCnt    Counter64,
    clvIfHCBitsOutCnt   Counter64,
    clvIfHCPktsTotCnt   Counter64,
    clvIfHCBitsTotCnt   Counter64
}

clvIfStatsIndex OBJECT-TYPE
    SYNTAX      Integer32 (1..2147483647)
    MAX-ACCESS  not-accessible
    STATUS      current
    DESCRIPTION
        "Index of a row in clvSysIfStatsTable"
    ::= { clvIfStatsEntry 1 }

clvIfName OBJECT-TYPE
    SYNTAX      DisplayString
    MAX-ACCESS  read-only
    STATUS      current
    DESCRIPTION
        "The name of the interface."
    ::= { clvIfStatsEntry 2 }

clvIfFragsIn OBJECT-TYPE
    SYNTAX      Counter32
    MAX-ACCESS  read-only
    STATUS      current
    DESCRIPTION
        "Number of IP packet fragments received
         in the interface."
    ::= { clvIfStatsEntry 3 }

clvIfFragReassOk OBJECT-TYPE
    SYNTAX      Counter32
    MAX-ACCESS  read-only
    STATUS      current
    DESCRIPTION
        "Number of complete IP packets successfully
         reassembled from the fragments received in
         the interface."
    ::= { clvIfStatsEntry 4 }

clvIfFragReassFail OBJECT-TYPE
    SYNTAX      Counter32
    MAX-ACCESS  read-only
    STATUS      current
    DESCRIPTION
        "Number of packets that could not be reassembled,
         either due to resource starvation, illegal fragmentation,
         or just packet loss."
    ::= { clvIfStatsEntry 5 }

clvIfPktsInCnt OBJECT-TYPE
    SYNTAX      Counter32
    MAX-ACCESS  read-only
    STATUS      current
    DESCRIPTION
        "Number of packets received by the interface."
    ::= { clvIfStatsEntry 6 }

clvIfPktsOutCnt OBJECT-TYPE
    SYNTAX      Counter32
    MAX-ACCESS  read-only
    STATUS      current
    DESCRIPTION
        "Number of packets sent by the interface"
    ::= { clvIfStatsEntry 7 }

clvIfBitsInCnt OBJECT-TYPE
    SYNTAX      Counter32
    MAX-ACCESS  read-only
    STATUS      current
    DESCRIPTION
        "Number of bits received by the interface"
    ::= { clvIfStatsEntry 8 }

clvIfBitsOutCnt OBJECT-TYPE
    SYNTAX      Counter32
    MAX-ACCESS  read-only
    STATUS      current
    DESCRIPTION
        "Number of bits sent by the interface"
    ::= { clvIfStatsEntry 9 }

clvIfPktsTotCnt OBJECT-TYPE
    SYNTAX      Counter32
    MAX-ACCESS  read-only
    STATUS      current
    DESCRIPTION
        "Total number of packets transmitted by the interface"
    ::= { clvIfStatsEntry 10 }

clvIfBitsTotCnt OBJECT-TYPE
    SYNTAX      Counter32
    MAX-ACCESS  read-only
    STATUS      current
    DESCRIPTION
        "Total number of bits transmitted by the interface"
    ::= { clvIfStatsEntry 11 }

clvIfHCPktsInCnt OBJECT-TYPE
    SYNTAX      Counter64
    MAX-ACCESS  read-only
    STATUS      current
    DESCRIPTION
        "Number of packets received by the interface.
        This object is a 64-bit version of clvIfPktsInCnt."
    ::= { clvIfStatsEntry 12 }

clvIfHCPktsOutCnt OBJECT-TYPE
    SYNTAX      Counter64
    MAX-ACCESS  read-only
    STATUS      current
    DESCRIPTION
        "Number of packets sent by the interface.
        This object is a 64-bit version of clvIfPktsOutCnt."
    ::= { clvIfStatsEntry 13 }

clvIfHCBitsInCnt OBJECT-TYPE
    SYNTAX      Counter64
    MAX-ACCESS  read-only
    STATUS      current
    DESCRIPTION
        "Number of bits received by the interface.
        This object is a 64-bit version of clvIfBitsInCnt."
    ::= { clvIfStatsEntry 14 }

clvIfHCBitsOutCnt OBJECT-TYPE
    SYNTAX      Counter64
    MAX-ACCESS  read-only
    STATUS      current
    DESCRIPTION
        "Number of bits sent by the interface.
        This object is a 64-bit version of clvIfBitsOutCnt."
    ::= { clvIfStatsEntry 15 }

clvIfHCPktsTotCnt OBJECT-TYPE
    SYNTAX      Counter64
    MAX-ACCESS  read-only
    STATUS      current
    DESCRIPTION
        "Total number of packets transmitted by the interface.
        This object is a 64-bit version of clvIfPktsTotCnt."
    ::= { clvIfStatsEntry 16 }

clvIfHCBitsTotCnt OBJECT-TYPE
    SYNTAX      Counter64
    MAX-ACCESS  read-only
    STATUS      current
    DESCRIPTION
        "Total number of bits transmitted by the interface.
        This object is a 64-bit version of clvIfBitsTotCnt."
    ::= { clvIfStatsEntry 17 }

clvSwitchPortsTable OBJECT-TYPE
    SYNTAX      SEQUENCE OF ClvPortStatsEntry
    MAX-ACCESS  not-accessible
    STATUS      current
    DESCRIPTION
        "A table of Clavister specific interfaces statistics"
    ::= { clvSystem 20 }

clvPortStatsEntry OBJECT-TYPE
    SYNTAX      ClvPortStatsEntry
    MAX-ACCESS  not-accessible
    STATUS      current
    DESCRIPTION
        "The row in a table of Clavister specific interface statistics"
    INDEX       { clvPortStatsIndex }
    ::= { clvSwitchPortsTable 1 }

ClvPortStatsEntry ::= SEQUENCE {
    clvPortStatsIndex   Integer32,
    clvPortLink         DisplayString,
    clvPortSpeed        Integer32,
    clvPortDuplex       DisplayString,
    clvPortInBytes      Counter64,
    clvPortOutBytes     Counter64,
    clvPortInBadOctets  Counter64,
    clvPortInMulticast  Counter64,
    clvPortOutMulticast Counter64,
    clvPortInBroadcast  Counter64,
    clvPortOutBroadcast Counter64,
    clvPortInRxErr      Counter64,
    clvPortInFCSErr     Counter64,
    clvPortOutFCSErr    Counter64,
    clvPortInUnicast    Counter64,
    clvPortOutUnicast   Counter64,
    clvPortCollisions   Counter64,
    clvPortLate         Counter64,
    clvPortDeferred     Counter64,
    clvPortExcessive    Counter64,
    clvPortSingle       Counter64,
    clvPortInPause      Counter64,
    clvPortOutPause     Counter64,
    clvPortMultiple     Counter64,
    clvPortInUndersize  Counter64,
    clvPortInFragments  Counter64,
    clvPortInOverSize   Counter64,
    clvPortInJabber     Counter64,
    clvPortInDiscards   Counter64,
    clvPortInFiltered   Counter64,
    clvPortOutFiltered  Counter64
}

clvPortStatsIndex OBJECT-TYPE
    SYNTAX      Integer32 (1..2147483647)
    MAX-ACCESS  not-accessible
    STATUS      current
    DESCRIPTION
        "Index of a row in clvSwitchPortsTable"
    ::= { clvPortStatsEntry 1 }

clvPortLink OBJECT-TYPE
    SYNTAX      DisplayString
    MAX-ACCESS  read-only
    STATUS      current
    DESCRIPTION
        "Port link status"
    ::= { clvPortStatsEntry 6 }

clvPortSpeed OBJECT-TYPE
    SYNTAX      Integer32 (1..2147483647)
    MAX-ACCESS  read-only
    STATUS      current
    DESCRIPTION
        "Port speed in Mbps"
    ::= { clvPortStatsEntry 11 }

clvPortDuplex OBJECT-TYPE
    SYNTAX      DisplayString
    MAX-ACCESS  read-only
    STATUS      current
    DESCRIPTION
        "Duplex mode for port"
    ::= { clvPortStatsEntry 16 }

clvPortInBytes OBJECT-TYPE
    SYNTAX      Counter64
    MAX-ACCESS  read-only
    STATUS      current
    DESCRIPTION
        "Number of packets received by the port."
    ::= { clvPortStatsEntry 21 }

clvPortOutBytes OBJECT-TYPE
    SYNTAX      Counter64
    MAX-ACCESS  read-only
    STATUS      current
    DESCRIPTION
        "Number of packets sent by the port."
    ::= { clvPortStatsEntry 26 }

clvPortInBadOctets OBJECT-TYPE
    SYNTAX      Counter64
    MAX-ACCESS  read-only
    STATUS      current
    DESCRIPTION
         "The sum of lengths of all bad Ethernet frames received."
    ::= { clvPortStatsEntry 31 }

clvPortInMulticast OBJECT-TYPE
    SYNTAX      Counter64
    MAX-ACCESS  read-only
    STATUS      current
    DESCRIPTION
         "The number of good frames received that have a Multicast destination MAC address."
    ::= { clvPortStatsEntry 36 }

clvPortOutMulticast OBJECT-TYPE
    SYNTAX      Counter64
    MAX-ACCESS  read-only
    STATUS      current
    DESCRIPTION
         "The number of good frames sent that have a Multicast destination MAC address."
    ::= { clvPortStatsEntry 41 }

clvPortInBroadcast OBJECT-TYPE
    SYNTAX      Counter64
    MAX-ACCESS  read-only
    STATUS      current
    DESCRIPTION
         "The number of good frames received that have a Broadcast destination MAC address."
    ::= { clvPortStatsEntry 46 }

clvPortOutBroadcast OBJECT-TYPE
    SYNTAX      Counter64
    MAX-ACCESS  read-only
    STATUS      current
    DESCRIPTION
         "The number of good frames sent that have a Broadcast destination MAC address."
    ::= { clvPortStatsEntry 51 }

clvPortInRxErr OBJECT-TYPE
    SYNTAX      Counter64
    MAX-ACCESS  read-only
    STATUS      current
    DESCRIPTION
         "Total frames received with an RxErr signal from the PHY."
    ::= { clvPortStatsEntry 56 }

clvPortInFCSErr OBJECT-TYPE
    SYNTAX      Counter64
    MAX-ACCESS  read-only
    STATUS      current
    DESCRIPTION
         "Total frames received with a CRC error not counted in InFragments InJabber or InRxErr."
    ::= { clvPortStatsEntry 61 }

clvPortOutFCSErr OBJECT-TYPE
    SYNTAX      Counter64
    MAX-ACCESS  read-only
    STATUS      current
    DESCRIPTION
         "The number of frames transmitted with an invalid FCS."
    ::= { clvPortStatsEntry 66 }

clvPortInUnicast OBJECT-TYPE
    SYNTAX      Counter64
    MAX-ACCESS  read-only
    STATUS      current
    DESCRIPTION
         "The number of good frames received that have a Unicast destination MAC address."
    ::= { clvPortStatsEntry 71 }

clvPortOutUnicast OBJECT-TYPE
    SYNTAX      Counter64
    MAX-ACCESS  read-only
    STATUS      current
    DESCRIPTION
         "The number of frames sent that have a Unicast destination MAC address."
    ::= { clvPortStatsEntry 76 }

clvPortCollisions OBJECT-TYPE
    SYNTAX      Counter64
    MAX-ACCESS  read-only
    STATUS      current
    DESCRIPTION
         "The number of collision events not including Single Multiple Excessive or Late. Half-duplex only."
    ::= { clvPortStatsEntry 81 }

clvPortLate OBJECT-TYPE
    SYNTAX      Counter64
    MAX-ACCESS  read-only
    STATUS      current
    DESCRIPTION
         "The number of times a collision is detected later than 512 bits-times into the transmission of a frame. Half-duplex only."
    ::= { clvPortStatsEntry 86 }

clvPortDeferred OBJECT-TYPE
    SYNTAX      Counter64
    MAX-ACCESS  read-only
    STATUS      current
    DESCRIPTION
         "The total number of successfully transmitted frames that are delayed with no collisions. Half-duplex only."
    ::= { clvPortStatsEntry 91 }

clvPortExcessive OBJECT-TYPE
    SYNTAX      Counter64
    MAX-ACCESS  read-only
    STATUS      current
    DESCRIPTION
         "The number of droppped frames that experienced 16 consecutive collisions. Half-duplex only"
    ::= { clvPortStatsEntry 96 }

clvPortSingle OBJECT-TYPE
    SYNTAX      Counter64
    MAX-ACCESS  read-only
    STATUS      current
    DESCRIPTION
         "The total number of successfully transmitted frames that experienced exactly one collision. Half-duplex only."
    ::= { clvPortStatsEntry 101 }

clvPortInPause OBJECT-TYPE
    SYNTAX      Counter64
    MAX-ACCESS  read-only
    STATUS      current
    DESCRIPTION
         "The number of good frames received that have a Pause destination MAC address."
    ::= { clvPortStatsEntry 106 }

clvPortOutPause OBJECT-TYPE
    SYNTAX      Counter64
    MAX-ACCESS  read-only
    STATUS      current
    DESCRIPTION
         "The number of Flow Control frames sent."
    ::= { clvPortStatsEntry 111 }

clvPortMultiple OBJECT-TYPE
    SYNTAX      Counter64
    MAX-ACCESS  read-only
    STATUS      current
    DESCRIPTION
         "The total number of successfully transmitted frames that experienced more than one collision. Half-duplex only."
    ::= { clvPortStatsEntry 116 }

clvPortInUndersize OBJECT-TYPE
    SYNTAX      Counter64
    MAX-ACCESS  read-only
    STATUS      current
    DESCRIPTION
         "Total frames received with a length of less than 64 octets but with a valid FCS"
    ::= { clvPortStatsEntry 121 }

clvPortInFragments OBJECT-TYPE
    SYNTAX      Counter64
    MAX-ACCESS  read-only
    STATUS      current
    DESCRIPTION
         "Total frames received with a length of less than 64 octets and an invalid FCS."
    ::= { clvPortStatsEntry 126 }

clvPortInOverSize OBJECT-TYPE
    SYNTAX      Counter64
    MAX-ACCESS  read-only
    STATUS      current
    DESCRIPTION
         "Total frames received with a length of more than MaxSize octets but with a valid FCS."
    ::= { clvPortStatsEntry 131 }

clvPortInJabber OBJECT-TYPE
    SYNTAX      Counter64
    MAX-ACCESS  read-only
    STATUS      current
    DESCRIPTION
         "Total frames received with a length of more than MaxSize octets but with an invalid FCS."
    ::= { clvPortStatsEntry 136 }

clvPortInDiscards OBJECT-TYPE
    SYNTAX      Counter64
    MAX-ACCESS  read-only
    STATUS      current
    DESCRIPTION
         "The number of good non-filtered frames that could not be forwarded due to a lack of buffer space."
    ::= { clvPortStatsEntry 141 }

clvPortInFiltered OBJECT-TYPE
    SYNTAX      Counter64
    MAX-ACCESS  read-only
    STATUS      current
    DESCRIPTION
         "The number of good frames that were filtered due to ingress switch policy rules."
    ::= { clvPortStatsEntry 146 }

clvPortOutFiltered OBJECT-TYPE
    SYNTAX      Counter64
    MAX-ACCESS  read-only
    STATUS      current
    DESCRIPTION
         "The number of good frames that were filtered due to egress switch policy rules."
    ::= { clvPortStatsEntry 151 }

clvIfRxRingTable OBJECT-TYPE
    SYNTAX      SEQUENCE OF ClvIfRxRingEntry
    MAX-ACCESS  not-accessible
    STATUS      current
    DESCRIPTION
        "A table of Clavister specific interface Rx ring statistics"
    ::= { clvSystem 8 }

clvIfRxRingEntry OBJECT-TYPE
    SYNTAX      ClvIfRxRingEntry
    MAX-ACCESS  not-accessible
    STATUS      current
    DESCRIPTION
        "The row in a table of Clavister specific interface Rx ring
         statistics."
    INDEX       { clvIfRxRingIndex }
    ::= { clvIfRxRingTable 1 }

ClvIfRxRingEntry ::= SEQUENCE {
    clvIfRxRingIndex        Integer32,
    clvIfRxRingFifoErrors   Counter32,
    clvIfRxDespools         Gauge32,
    clvIfRxAvgUse           Gauge32,
    clvIfRxRingSaturation   Gauge32,
    clvRxRingFlooded        Gauge32
}

clvIfRxRingIndex OBJECT-TYPE
    SYNTAX      Integer32 (1..2147483647)
    MAX-ACCESS  not-accessible
    STATUS      current
    DESCRIPTION
        "Index of a row in clvIfRxRingTable."
    ::= { clvIfRxRingEntry 1 }

clvIfRxRingFifoErrors OBJECT-TYPE
    SYNTAX      Counter32
    MAX-ACCESS  read-only
    STATUS      current
    DESCRIPTION
        "Rx Ring number of FIFO errors."
    ::= { clvIfRxRingEntry 2 }

clvIfRxDespools OBJECT-TYPE
    SYNTAX      Gauge32
    MAX-ACCESS  read-only
    STATUS      current
    DESCRIPTION
        "Number of despool events per second."
    ::= { clvIfRxRingEntry 3 }

clvIfRxAvgUse OBJECT-TYPE
    SYNTAX      Gauge32
    MAX-ACCESS  read-only
    STATUS      current
    DESCRIPTION
        "Rx Ring average usage."
    ::= { clvIfRxRingEntry 4 }

clvIfRxRingSaturation OBJECT-TYPE
    SYNTAX      Gauge32
    MAX-ACCESS  read-only
    STATUS      current
    DESCRIPTION
        "Rx Ring saturation. Percentage of ring use per despool
         event when the ring has been more than half full."
    ::= { clvIfRxRingEntry 5 }

clvRxRingFlooded OBJECT-TYPE
    SYNTAX      Gauge32
    MAX-ACCESS  read-only
    STATUS      current
    DESCRIPTION
        "Rx Ring number of despool events for which
         the ring has been completely flooded"
    ::= { clvIfRxRingEntry 6 }

clvIfTxRingTable OBJECT-TYPE
    SYNTAX      SEQUENCE OF ClvIfTxRingEntry
    MAX-ACCESS  not-accessible
    STATUS      current
    DESCRIPTION
        "A table of Clavister specific interface Tx ring statistics"
    ::= { clvSystem 9 }

clvIfTxRingEntry OBJECT-TYPE
    SYNTAX      ClvIfTxRingEntry
    MAX-ACCESS  not-accessible
    STATUS      current
    DESCRIPTION
        "The row in a table of Clavister specific interface Tx ring
         statistics."
    INDEX       { clvIfTxRingIndex }
    ::= { clvIfTxRingTable 1 }

ClvIfTxRingEntry ::= SEQUENCE {
    clvIfTxRingIndex        Integer32,
    clvIfTxDespools         Gauge32,
    clvIfTxAvgUse           Gauge32,
    clvIfTxRingSaturation   Gauge32,
    clvRxTingFlooded        Gauge32
}

clvIfTxRingIndex OBJECT-TYPE
    SYNTAX      Integer32 (1..2147483647)
    MAX-ACCESS  not-accessible
    STATUS      current
    DESCRIPTION
        "Index of a row in clvIfRxRingTable."
    ::= { clvIfTxRingEntry 1 }

clvIfTxDespools OBJECT-TYPE
    SYNTAX      Gauge32
    MAX-ACCESS  read-only
    STATUS      current
    DESCRIPTION
        "Tx Ring number of despool event per second (polls when
         there is at least one buffer in the ring)"
    ::= { clvIfTxRingEntry 2 }

clvIfTxAvgUse OBJECT-TYPE
    SYNTAX      Gauge32
    MAX-ACCESS  read-only
    STATUS      current
    DESCRIPTION
        "Tx Ring number of despool events when the ring has
         been completely flooded"
    ::= { clvIfTxRingEntry 3 }

clvIfTxRingSaturation OBJECT-TYPE
    SYNTAX      Gauge32
    MAX-ACCESS  read-only
    STATUS      current
    DESCRIPTION
        "Tx Ring percentage of use per despool event when the
         ring has been more than half full."
    ::= { clvIfTxRingEntry 4 }

clvRxTingFlooded OBJECT-TYPE
    SYNTAX      Gauge32
    MAX-ACCESS  read-only
    STATUS      current
    DESCRIPTION
        "Tx Ring number of despool events for in which the ring has
         been completely flooded"
    ::= { clvIfTxRingEntry 5 }

clvIfVlanStatsTable OBJECT-TYPE
    SYNTAX      SEQUENCE OF ClvIfVlanStatsEntry
    MAX-ACCESS  not-accessible
    STATUS      current
    DESCRIPTION
        "A table of Clavister VLAN statistics"
    ::= { clvSystem 10 }

clvIfVlanStatsEntry OBJECT-TYPE
    SYNTAX      ClvIfVlanStatsEntry
    MAX-ACCESS  not-accessible
    STATUS      current
    DESCRIPTION
        "The row in a table of clvIfVlanStatsTable. Each has an index
         equal to the ifIndex of the corresponding physical interface"
    INDEX       { clvIfVlanIndex }
    ::= { clvIfVlanStatsTable 1 }

ClvIfVlanStatsEntry ::= SEQUENCE {
    clvIfVlanIndex              Integer32,
    clvIfVlanUntaggedInPkts     Counter32,
    clvIfVlanUntaggedOutPkts    Counter32,
    clvIfVlanUntaggedTotPkts    Counter32,
    clvIfVlanUntaggedInOctets   Counter32,
    clvIfVlanUntaggedOutOctets  Counter32,
    clvIfVlanUntaggedTotOctets  Counter32
}

clvIfVlanIndex OBJECT-TYPE
    SYNTAX      Integer32 (1..2147483647)
    MAX-ACCESS  not-accessible
    STATUS      current
    DESCRIPTION
        "Extended index of a row in clvIfVlanStatsTable."
    ::= { clvIfVlanStatsEntry 1 }

clvIfVlanUntaggedInPkts OBJECT-TYPE
    SYNTAX      Counter32
    MAX-ACCESS  read-only
    STATUS      current
    DESCRIPTION
        "Number of untagged packets received by the interface."
    ::= { clvIfVlanStatsEntry 2 }

clvIfVlanUntaggedOutPkts OBJECT-TYPE
    SYNTAX      Counter32
    MAX-ACCESS  read-only
    STATUS      current
    DESCRIPTION
        "Number of untagged packets sent by the interface."
    ::= { clvIfVlanStatsEntry 3 }

clvIfVlanUntaggedTotPkts OBJECT-TYPE
    SYNTAX      Counter32
    MAX-ACCESS  read-only
    STATUS      current
    DESCRIPTION
        "Total number of untagged packets processed by the interface."
    ::= { clvIfVlanStatsEntry 4 }

clvIfVlanUntaggedInOctets OBJECT-TYPE
    SYNTAX      Counter32
    MAX-ACCESS  read-only
    STATUS      current
    DESCRIPTION
        "Total number of octects in untagged packets received by the interface."
    ::= { clvIfVlanStatsEntry 5 }

clvIfVlanUntaggedOutOctets OBJECT-TYPE
    SYNTAX      Counter32
    MAX-ACCESS  read-only
    STATUS      current
    DESCRIPTION
        "Total number of octects in untagged packets sent by the interface."
    ::= { clvIfVlanStatsEntry 6 }

clvIfVlanUntaggedTotOctets OBJECT-TYPE
    SYNTAX      Counter32
    MAX-ACCESS  read-only
    STATUS      current
    DESCRIPTION
        "Total number of octects in untagged packets processed by the
         interface."
    ::= { clvIfVlanStatsEntry 7 }

clvHWSensorTable OBJECT-TYPE
    SYNTAX      SEQUENCE OF ClvHWSensorEntry
    MAX-ACCESS  not-accessible
    STATUS      current
    DESCRIPTION
        "Table of hardware sensors."
    ::= { clvSystem 11 }

clvHWSensorEntry OBJECT-TYPE
    SYNTAX      ClvHWSensorEntry
    MAX-ACCESS  not-accessible
    STATUS      current
    DESCRIPTION
        "Entry  of table of hardware sensors."
    INDEX       { clvHWSensorIndex }
    ::= { clvHWSensorTable 1 }

ClvHWSensorEntry ::= SEQUENCE {
    clvHWSensorIndex    Integer32,
    clvHWSensorName     DisplayString,
    clvHWSensorValue    Gauge32,
    clvHWSensorUnit     DisplayString
}

clvHWSensorIndex OBJECT-TYPE
    SYNTAX      Integer32 (1..2147483647)
    MAX-ACCESS  not-accessible
    STATUS      current
    DESCRIPTION
        "Index of the entries of the sensor table."
    ::= { clvHWSensorEntry 1 }

clvHWSensorName OBJECT-TYPE
    SYNTAX      DisplayString
    MAX-ACCESS  read-only
    STATUS      current
    DESCRIPTION
        "The description of the sensor."
    ::= { clvHWSensorEntry 2 }

clvHWSensorValue OBJECT-TYPE
    SYNTAX      Gauge32
    MAX-ACCESS  read-only
    STATUS      current
    DESCRIPTION
        "The value of the sensor."
    ::= { clvHWSensorEntry 3 }

clvHWSensorUnit OBJECT-TYPE
    SYNTAX      DisplayString
    MAX-ACCESS  read-only
    STATUS      current
    DESCRIPTION
        "The description of the unit of the value measured by sensor."
    ::= { clvHWSensorEntry 4 }

clvSysMemUsage OBJECT-TYPE
    SYNTAX      Gauge32
    MAX-ACCESS  read-only
    STATUS      current
    DESCRIPTION
        "The current memory usage."
    ::= { clvSystem 12 }

clvSysTCPUsage OBJECT IDENTIFIER
    ::= { clvSystem 13 }

clvSysTCPRecvSmall OBJECT-TYPE
    SYNTAX      Gauge32
    MAX-ACCESS  read-only
    STATUS      current
    DESCRIPTION
        "Small TCP receive windows usage."
    ::= { clvSysTCPUsage 1 }

clvSysTCPRecvLarge OBJECT-TYPE
    SYNTAX      Gauge32
    MAX-ACCESS  read-only
    STATUS      current
    DESCRIPTION
        "Large TCP receive windows usage."
    ::= { clvSysTCPUsage 2 }

clvSysTCPSendSmall OBJECT-TYPE
    SYNTAX      Gauge32
    MAX-ACCESS  read-only
    STATUS      current
    DESCRIPTION
        "Small TCP send windows usage."
    ::= { clvSysTCPUsage 3 }

clvSysTCPSendLarge OBJECT-TYPE
    SYNTAX      Gauge32
    MAX-ACCESS  read-only
    STATUS      current
    DESCRIPTION
        "Large TCP send windows usage."
    ::= { clvSysTCPUsage 4 }

clvSysTimerUsage OBJECT-TYPE
    SYNTAX      Gauge32
    MAX-ACCESS  read-only
    STATUS      current
    DESCRIPTION
        "The current number of timers in use."
    ::= { clvSystem 14 }

clvSysConnOPS OBJECT-TYPE
    SYNTAX      Gauge32
    MAX-ACCESS  read-only
    STATUS      current
    DESCRIPTION
        "The number of connections opened per second."
    ::= { clvSystem 15 }

clvSysConnCPS OBJECT-TYPE
    SYNTAX      Gauge32
    MAX-ACCESS  read-only
    STATUS      current
    DESCRIPTION
        "The number of connections closed per second."
    ::= { clvSystem 16 }

clvSysHCForwardedBits OBJECT-TYPE
    SYNTAX      Counter64
    MAX-ACCESS  read-only
    STATUS      current
    DESCRIPTION
        "The number of bits forwarded through the gateway."
    ::= { clvSystem 17 }

clvSysMemUsedKiB OBJECT-TYPE
    SYNTAX      Gauge32
    MAX-ACCESS  read-only
    STATUS      current
    DESCRIPTION
        "Amount of used memory in KiB"
    ::= { clvSystem 18 }

clvSysMemFreeKiB OBJECT-TYPE
    SYNTAX      Gauge32
    MAX-ACCESS  read-only
    STATUS      current
    DESCRIPTION
        "Amount of free memory in KiB."
    ::= { clvSystem 19 }

clvSysConnRPS OBJECT-TYPE
    SYNTAX      Gauge32
    MAX-ACCESS  read-only
    STATUS      current
    DESCRIPTION
        "The number of connections replaced per second."
    ::= { clvSystem 21 }


clvVPN OBJECT IDENTIFIER
    ::= { clavisterOSStats 2 }

clvIPsec OBJECT IDENTIFIER
    ::= { clvVPN 1 }

clvIKEv1Global OBJECT IDENTIFIER
    ::= { clvIPsec 1 }

clvIKEv1SAsActive OBJECT-TYPE
    SYNTAX      Gauge32
    MAX-ACCESS  read-only
    STATUS      current
    DESCRIPTION
        "Number of active IKEv1 SAs."
    ::= { clvIKEv1Global 1 }

clvIKEv1AggrModeSuccessful OBJECT-TYPE
    SYNTAX      Counter32
    MAX-ACCESS  read-only
    STATUS      current
    DESCRIPTION
        "Number of successful IKEv1 aggressive mode negotiations."
    ::= { clvIKEv1Global 2 }

clvIKEv1NegsActive OBJECT-TYPE
    SYNTAX      Gauge32
    MAX-ACCESS  read-only
    STATUS      current
    DESCRIPTION
        "Number of active IKEv1 negotiations."
    ::= { clvIKEv1Global 3 }

clvIKEv1NegsSuccessful OBJECT-TYPE
    SYNTAX      Counter32
    MAX-ACCESS  read-only
    STATUS      current
    DESCRIPTION
        "Number of successful IKEv1 negotiations."
    ::= { clvIKEv1Global 4 }

clvIKEv1NegsFailed OBJECT-TYPE
    SYNTAX      Counter32
    MAX-ACCESS  read-only
    STATUS      current
    DESCRIPTION
        "Number of failed IKEv1 negotiations."
    ::= { clvIKEv1Global 5 }

clvIKEv1PacketsRecv OBJECT-TYPE
    SYNTAX      Counter32
    MAX-ACCESS  read-only
    STATUS      current
    DESCRIPTION
        "Number of IKEv1 packets received."
    ::= { clvIKEv1Global 6 }

clvIKEv1BytesRecv OBJECT-TYPE
    SYNTAX      Counter32
    MAX-ACCESS  read-only
    STATUS      current
    DESCRIPTION
        "Number of bytes in IKEv1 packets received."
    ::= { clvIKEv1Global 7 }

clvIKEv1PacketsSent OBJECT-TYPE
    SYNTAX      Counter32
    MAX-ACCESS  read-only
    STATUS      current
    DESCRIPTION
        "Number of IKEv1 packets sent."
    ::= { clvIKEv1Global 8 }

clvIKEv1BytesSent OBJECT-TYPE
    SYNTAX      Counter32
    MAX-ACCESS  read-only
    STATUS      current
    DESCRIPTION
        "Number of bytes in IKEv1 packets sent."
    ::= { clvIKEv1Global 9 }

clvIKEv1PacketsResent OBJECT-TYPE
    SYNTAX      Counter32
    MAX-ACCESS  read-only
    STATUS      current
    DESCRIPTION
        "Number of IKEv1 Packets resent."
    ::= { clvIKEv1Global 10 }

clvIKEv2Global OBJECT IDENTIFIER
    ::= { clvIPsec 2 }

clvIKEv2SAsActive OBJECT-TYPE
    SYNTAX      Gauge32
    MAX-ACCESS  read-only
    STATUS      current
    DESCRIPTION
        "Number of active IKEv2 SAs."
    ::= { clvIKEv2Global 1 }

clvIKEv2NegsActive OBJECT-TYPE
    SYNTAX      Gauge32
    MAX-ACCESS  read-only
    STATUS      current
    DESCRIPTION
        "Number of active IKEv2 negotiations."
    ::= { clvIKEv2Global 2 }

clvIKEv2NegsSuccessful OBJECT-TYPE
    SYNTAX      Counter32
    MAX-ACCESS  read-only
    STATUS      current
    DESCRIPTION
        "Number of successful IKEv2 negotiations."
    ::= { clvIKEv2Global 3 }

clvIKEv2NegsFailed OBJECT-TYPE
    SYNTAX      Counter32
    MAX-ACCESS  read-only
    STATUS      current
    DESCRIPTION
        "Number of failed IKEv2 negotiations."
    ::= { clvIKEv2Global 4 }

clvIKEv2RekeysActive OBJECT-TYPE
    SYNTAX      Gauge32
    MAX-ACCESS  read-only
    STATUS      current
    DESCRIPTION
        "Number of active IKEv2 rekeys."
    ::= { clvIKEv2Global 5 }

clvIKEv2RekeysSuccessful OBJECT-TYPE
    SYNTAX      Counter32
    MAX-ACCESS  read-only
    STATUS      current
    DESCRIPTION
        "Number of successful IKEv2 rekeys."
    ::= { clvIKEv2Global 6 }

clvIKEv2RekeysFailed OBJECT-TYPE
    SYNTAX      Counter32
    MAX-ACCESS  read-only
    STATUS      current
    DESCRIPTION
        "Number of failed IKEv2 rekeys."
    ::= { clvIKEv2Global 7 }

clvIKEv2PacketsRecv OBJECT-TYPE
    SYNTAX      Counter32
    MAX-ACCESS  read-only
    STATUS      current
    DESCRIPTION
        "Number of IKEv2 packets received."
    ::= { clvIKEv2Global 8 }

clvIKEv2BytesRecv OBJECT-TYPE
    SYNTAX      Counter32
    MAX-ACCESS  read-only
    STATUS      current
    DESCRIPTION
        "Number of bytes in IKEv2 packets received."
    ::= { clvIKEv2Global 9 }

clvIKEv2PacketsSent OBJECT-TYPE
    SYNTAX      Counter32
    MAX-ACCESS  read-only
    STATUS      current
    DESCRIPTION
        "Number of IKEv2 packets sent."
    ::= { clvIKEv2Global 10 }

clvIKEv2BytesSent OBJECT-TYPE
    SYNTAX      Counter32
    MAX-ACCESS  read-only
    STATUS      current
    DESCRIPTION
        "Number of bytes in IKEv2 packets sent."
    ::= { clvIKEv2Global 11 }

clvIKEv2PacketsResent OBJECT-TYPE
    SYNTAX      Counter32
    MAX-ACCESS  read-only
    STATUS      current
    DESCRIPTION
        "Number of IKEv2 Packets resent."
    ::= { clvIKEv2Global 12 }

clvIKEGlobal OBJECT IDENTIFIER
    ::= { clvIPsec 3 }

clvIKESAsActive OBJECT-TYPE
    SYNTAX      Gauge32
    MAX-ACCESS  read-only
    STATUS      current
    DESCRIPTION
        "Number of active IKE SAs."
    ::= { clvIKEGlobal 1 }

clvIKEAggrModeSuccessful OBJECT-TYPE
    SYNTAX      Counter32
    MAX-ACCESS  read-only
    STATUS      current
    DESCRIPTION
        "Number of successful IKE aggressive mode negotiations."
    ::= { clvIKEGlobal 2 }

clvIKENegsActive OBJECT-TYPE
    SYNTAX      Gauge32
    MAX-ACCESS  read-only
    STATUS      current
    DESCRIPTION
        "Number of active IKE negotiations."
    ::= { clvIKEGlobal 3 }

clvIKENegsSuccessful OBJECT-TYPE
    SYNTAX      Counter32
    MAX-ACCESS  read-only
    STATUS      current
    DESCRIPTION
        "Number of successful IKE negotiations."
    ::= { clvIKEGlobal 4 }

clvIKENegsFailed OBJECT-TYPE
    SYNTAX      Counter32
    MAX-ACCESS  read-only
    STATUS      current
    DESCRIPTION
        "Number of failed IKE negotiations."
    ::= { clvIKEGlobal 5 }

clvIKERekeysActive OBJECT-TYPE
    SYNTAX      Gauge32
    MAX-ACCESS  read-only
    STATUS      current
    DESCRIPTION
        "Number of active IKE rekeys."
    ::= { clvIKEGlobal 6 }

clvIKERekeysSuccessful OBJECT-TYPE
    SYNTAX      Counter32
    MAX-ACCESS  read-only
    STATUS      current
    DESCRIPTION
        "Number of successful IKE rekeys."
    ::= { clvIKEGlobal 7 }

clvIKERekeysFailed OBJECT-TYPE
    SYNTAX      Counter32
    MAX-ACCESS  read-only
    STATUS      current
    DESCRIPTION
        "Number of failed IKE rekeys."
    ::= { clvIKEGlobal 8 }

clvIKEPacketsRecv OBJECT-TYPE
    SYNTAX      Counter32
    MAX-ACCESS  read-only
    STATUS      current
    DESCRIPTION
        "Number of IKE packets received."
    ::= { clvIKEGlobal 9 }

clvIKEBytesRecv OBJECT-TYPE
    SYNTAX      Counter32
    MAX-ACCESS  read-only
    STATUS      current
    DESCRIPTION
        "Number of bytes in IKE packets received."
    ::= { clvIKEGlobal 10 }

clvIKEPacketsSent OBJECT-TYPE
    SYNTAX      Counter32
    MAX-ACCESS  read-only
    STATUS      current
    DESCRIPTION
        "Number of IKE packets sent."
    ::= { clvIKEGlobal 11 }

clvIKEBytesSent OBJECT-TYPE
    SYNTAX      Counter32
    MAX-ACCESS  read-only
    STATUS      current
    DESCRIPTION
        "Number of bytes in IKE packets sent."
    ::= { clvIKEGlobal 12 }

clvIKEPacketsResent OBJECT-TYPE
    SYNTAX      Counter32
    MAX-ACCESS  read-only
    STATUS      current
    DESCRIPTION
        "Number of IKE Packets resent."
    ::= { clvIKEGlobal 13 }

clvIPsecGlobal OBJECT IDENTIFIER
    ::= { clvIPsec 4 }

clvIPsecSAsActive OBJECT-TYPE
    SYNTAX      Gauge32
    MAX-ACCESS  read-only
    STATUS      current
    DESCRIPTION
        "Number of active IPsec SAs."
    ::= { clvIPsecGlobal 1 }

clvIPsecNegsActive OBJECT-TYPE
    SYNTAX      Gauge32
    MAX-ACCESS  read-only
    STATUS      current
    DESCRIPTION
        "Number of active IPsec negotiations."
    ::= { clvIPsecGlobal 2 }

clvIPsecNegsSuccessful OBJECT-TYPE
    SYNTAX      Counter32
    MAX-ACCESS  read-only
    STATUS      current
    DESCRIPTION
        "Number of successful IPsec negotiations."
    ::= { clvIPsecGlobal 3 }

clvIPsecNegsFailed OBJECT-TYPE
    SYNTAX      Counter32
    MAX-ACCESS  read-only
    STATUS      current
    DESCRIPTION
        "Number of failed IPsec negotiations."
    ::= { clvIPsecGlobal 4 }

clvIPsecRekeysActive OBJECT-TYPE
    SYNTAX      Gauge32
    MAX-ACCESS  read-only
    STATUS      current
    DESCRIPTION
        "Number of active IPsec rekeys."
    ::= { clvIPsecGlobal 5 }

clvIPsecRekeysSuccessful OBJECT-TYPE
    SYNTAX      Counter32
    MAX-ACCESS  read-only
    STATUS      current
    DESCRIPTION
        "Number of successful IPsec rekeys."
    ::= { clvIPsecGlobal 6 }

clvIPsecRekeysFailed OBJECT-TYPE
    SYNTAX      Counter32
    MAX-ACCESS  read-only
    STATUS      current
    DESCRIPTION
        "Number of failed IPsec rekeys."
    ::= { clvIPsecGlobal 7 }

clvIPsecESPPacketsRecv OBJECT-TYPE
    SYNTAX      Counter32
    MAX-ACCESS  read-only
    STATUS      current
    DESCRIPTION
        "Number of ESP packets received."
    ::= { clvIPsecGlobal 8 }

clvIPsecESPBytesRecv OBJECT-TYPE
    SYNTAX      Counter32
    MAX-ACCESS  read-only
    STATUS      current
    DESCRIPTION
        "Number of bytes in ESP packets received."
    ::= { clvIPsecGlobal 9 }

clvIPsecESPPacketsSent OBJECT-TYPE
    SYNTAX      Counter32
    MAX-ACCESS  read-only
    STATUS      current
    DESCRIPTION
        "Number of ESP packets sent out."
    ::= { clvIPsecGlobal 10 }

clvIPsecESPBytesSent OBJECT-TYPE
    SYNTAX      Counter32
    MAX-ACCESS  read-only
    STATUS      current
    DESCRIPTION
        "Number of bytes in ESP packets sent out."
    ::= { clvIPsecGlobal 11 }

clvIPsecOutTotalDrop OBJECT-TYPE
    SYNTAX      Counter32
    MAX-ACCESS  read-only
    STATUS      current
    DESCRIPTION
        "Number of outbound packets dropped."
    ::= { clvIPsecGlobal 12 }

clvIPsecOutNoRuleDrop OBJECT-TYPE
    SYNTAX      Counter32
    MAX-ACCESS  read-only
    STATUS      current
    DESCRIPTION
        "Number of outbound packets dropped due to missing internal policy."
    ::= { clvIPsecGlobal 13 }

clvIPsecOutRuleDrop OBJECT-TYPE
    SYNTAX      Counter32
    MAX-ACCESS  read-only
    STATUS      current
    DESCRIPTION
        "Number of outbound packets dropped due to matching an internal drop policy."
    ::= { clvIPsecGlobal 14 }

clvIPsecOutNoTriggerDrop OBJECT-TYPE
    SYNTAX      Counter32
    MAX-ACCESS  read-only
    STATUS      current
    DESCRIPTION
        "Number of outbound packets dropped while waiting for a previously triggered tunnel setup to complete."
    ::= { clvIPsecGlobal 15 }

clvIPsecOutTriggerDrop OBJECT-TYPE
    SYNTAX      Counter32
    MAX-ACCESS  read-only
    STATUS      current
    DESCRIPTION
        "Number of outbound packets dropped while triggering tunnel setup."
    ::= { clvIPsecGlobal 16 }

clvIPsecOutSeqOverflowDrop OBJECT-TYPE
    SYNTAX      Counter32
    MAX-ACCESS  read-only
    STATUS      current
    DESCRIPTION
        "Number of outbound packets dropped due to sequence number overflow."
    ::= { clvIPsecGlobal 17 }

clvIPsecInTotalDrop OBJECT-TYPE
    SYNTAX      Counter32
    MAX-ACCESS  read-only
    STATUS      current
    DESCRIPTION
        "Number of inbound packets dropped."
    ::= { clvIPsecGlobal 18 }

clvIPsecInAntiReplayDrop OBJECT-TYPE
    SYNTAX      Counter32
    MAX-ACCESS  read-only
    STATUS      current
    DESCRIPTION
        "Number of inbound packets dropped due to replay detected."
    ::= { clvIPsecGlobal 19 }

clvIPsecInAuthErrorDrop OBJECT-TYPE
    SYNTAX      Counter32
    MAX-ACCESS  read-only
    STATUS      current
    DESCRIPTION
        "Number of inbound packets dropped due to authentication errors, i.e. ICV errors."
    ::= { clvIPsecGlobal 20 }

clvIPsecInCorruptDrop OBJECT-TYPE
    SYNTAX      Counter32
    MAX-ACCESS  read-only
    STATUS      current
    DESCRIPTION
        "Number of inbound packets dropped due to being corrupt."
    ::= { clvIPsecGlobal 21 }

clvIPsecInNHErrorDrop OBJECT-TYPE
    SYNTAX      Counter32
    MAX-ACCESS  read-only
    STATUS      current
    DESCRIPTION
        "Number of inbound packets dropped due to next header mismatches."
    ::= { clvIPsecGlobal 22 }

clvIPsecInPadErrorDrop OBJECT-TYPE
    SYNTAX      Counter32
    MAX-ACCESS  read-only
    STATUS      current
    DESCRIPTION
        "Number of inbound packets dropped due to padding errors."
    ::= { clvIPsecGlobal 23 }

clvIPsecInSelectorErrorDrop OBJECT-TYPE
    SYNTAX      Counter32
    MAX-ACCESS  read-only
    STATUS      current
    DESCRIPTION
        "Number of inbound packets dropped due to selector errors."
    ::= { clvIPsecGlobal 24 }

clvIPsecInUnknownSPIDrop OBJECT-TYPE
    SYNTAX      Counter32
    MAX-ACCESS  read-only
    STATUS      current
    DESCRIPTION
        "Number of inbound packets dropped due to SPI lookup failures."
    ::= { clvIPsecGlobal 25 }

clvIPsecIfStatsTable OBJECT-TYPE
    SYNTAX      SEQUENCE OF ClvIPsecIfStatsEntry
    MAX-ACCESS  not-accessible
    STATUS      current
    DESCRIPTION
        "A list of IPsecTunnel statistics."
    ::= { clvIPsec 5 }

clvIPsecIfStatsEntry OBJECT-TYPE
    SYNTAX      ClvIPsecIfStatsEntry
    MAX-ACCESS  not-accessible
    STATUS      current
    DESCRIPTION
        "The statistics of an IPsecTunnel."
    INDEX       { clvIPsecIfIndex }
    ::= { clvIPsecIfStatsTable 1 }

ClvIPsecIfStatsEntry ::= SEQUENCE {
    clvIPsecIfIndex                    Integer32,
    clvIPsecIfName                     DisplayString,
    clvIPsecIfIKESAsActive             Gauge32,
    clvIPsecIfIKENegsSuccessful        Counter32,
    clvIPsecIfIKERekeysSuccessful      Counter32,
    clvIPsecIfIKERekeysFailed          Counter32,
    clvIPsecIfIPsecSAsActive           Gauge32,
    clvIPsecIfIPsecNegsSuccessful      Counter32,
    clvIPsecIfIPsecRekeysSuccessful    Counter32,
    clvIPsecIfIPsecRekeysFailed        Counter32,
    clvIPsecIfESPPacketsRecv           Counter32,
    clvIPsecIfESPBytesRecv             Counter32,
    clvIPsecIfESPPacketsSent           Counter32,
    clvIPsecIfESPBytesSent             Counter32,
    clvIPsecIfOutTotalDrop             Counter32,
    clvIPsecIfOutNoRuleDrop            Counter32,
    clvIPsecIfOutRuleDrop              Counter32,
    clvIPsecIfOutNoTriggerDrop         Counter32,
    clvIPsecIfOutTriggerDrop           Counter32,
    clvIPsecIfOutSeqOverflowDrop       Counter32,
    clvIPsecIfInTotalDrop              Counter32,
    clvIPsecIfInAntiReplayDrop         Counter32,
    clvIPsecIfInAuthErrorDrop          Counter32,
    clvIPsecIfInCorruptDrop            Counter32,
    clvIPsecIfInNHErrorDrop            Counter32,
    clvIPsecIfInPadErrorDrop           Counter32,
    clvIPsecIfInSelectorErrorDrop      Counter32
}

clvIPsecIfIndex OBJECT-TYPE
    SYNTAX      Integer32 (1..2147483647)
    MAX-ACCESS  not-accessible
    STATUS      current
    DESCRIPTION
        "The index of the IPsecTunnel."
    ::= { clvIPsecIfStatsEntry 1 }

clvIPsecIfName OBJECT-TYPE
    SYNTAX      DisplayString
    MAX-ACCESS  read-only
    STATUS      current
    DESCRIPTION
        "The name of the IPsecTunnel."
    ::= { clvIPsecIfStatsEntry 2 }

clvIPsecIfIKESAsActive OBJECT-TYPE
    SYNTAX      Gauge32
    MAX-ACCESS  read-only
    STATUS      current
    DESCRIPTION
        "Number of active IKE SAs."
    ::= { clvIPsecIfStatsEntry 3 }

clvIPsecIfIKENegsSuccessful OBJECT-TYPE
    SYNTAX      Counter32
    MAX-ACCESS  read-only
    STATUS      current
    DESCRIPTION
        "Number of successful IKE negotiations."
    ::= { clvIPsecIfStatsEntry 4 }

clvIPsecIfIKERekeysSuccessful OBJECT-TYPE
    SYNTAX      Counter32
    MAX-ACCESS  read-only
    STATUS      current
    DESCRIPTION
        "Number of successful IKE rekeys."
    ::= { clvIPsecIfStatsEntry 5 }

clvIPsecIfIKERekeysFailed OBJECT-TYPE
    SYNTAX      Counter32
    MAX-ACCESS  read-only
    STATUS      current
    DESCRIPTION
        "Number of failed IKE rekeys."
    ::= { clvIPsecIfStatsEntry 6 }

clvIPsecIfIPsecSAsActive OBJECT-TYPE
    SYNTAX      Gauge32
    MAX-ACCESS  read-only
    STATUS      current
    DESCRIPTION
        "Number of active IPsec SAs."
    ::= { clvIPsecIfStatsEntry 7 }

clvIPsecIfIPsecNegsSuccessful OBJECT-TYPE
    SYNTAX      Counter32
    MAX-ACCESS  read-only
    STATUS      current
    DESCRIPTION
        "Number of successful IPsec negotiations."
    ::= { clvIPsecIfStatsEntry 8 }

clvIPsecIfIPsecRekeysSuccessful OBJECT-TYPE
    SYNTAX      Counter32
    MAX-ACCESS  read-only
    STATUS      current
    DESCRIPTION
        "Number of successful IPsec rekeys."
    ::= { clvIPsecIfStatsEntry 9 }

clvIPsecIfIPsecRekeysFailed OBJECT-TYPE
    SYNTAX      Counter32
    MAX-ACCESS  read-only
    STATUS      current
    DESCRIPTION
        "Number of failed IPsec rekeys."
    ::= { clvIPsecIfStatsEntry 10 }

clvIPsecIfESPPacketsRecv OBJECT-TYPE
    SYNTAX      Counter32
    MAX-ACCESS  read-only
    STATUS      current
    DESCRIPTION
        "Number of ESP packets received."
    ::= { clvIPsecIfStatsEntry 11 }

clvIPsecIfESPBytesRecv OBJECT-TYPE
    SYNTAX      Counter32
    MAX-ACCESS  read-only
    STATUS      current
    DESCRIPTION
        "Number of bytes in ESP packets received."
    ::= { clvIPsecIfStatsEntry 12 }

clvIPsecIfESPPacketsSent OBJECT-TYPE
    SYNTAX      Counter32
    MAX-ACCESS  read-only
    STATUS      current
    DESCRIPTION
        "Number of ESP packets sent out."
    ::= { clvIPsecIfStatsEntry 13 }

clvIPsecIfESPBytesSent OBJECT-TYPE
    SYNTAX      Counter32
    MAX-ACCESS  read-only
    STATUS      current
    DESCRIPTION
        "Number of bytes in ESP packets sent out."
    ::= { clvIPsecIfStatsEntry 14 }

 clvIPsecIfOutTotalDrop OBJECT-TYPE
    SYNTAX      Counter32
    MAX-ACCESS  read-only
    STATUS      current
    DESCRIPTION
        "Number of outbound packets dropped."
    ::= { clvIPsecIfStatsEntry 15 }

clvIPsecIfOutNoRuleDrop OBJECT-TYPE
    SYNTAX      Counter32
    MAX-ACCESS  read-only
    STATUS      current
    DESCRIPTION
        "Number of outbound packets dropped due to missing internal policy."
    ::= { clvIPsecIfStatsEntry 16 }

clvIPsecIfOutRuleDrop OBJECT-TYPE
    SYNTAX      Counter32
    MAX-ACCESS  read-only
    STATUS      current
    DESCRIPTION
        "Number of outbound packets dropped due to matching an internal drop policy."
    ::= { clvIPsecIfStatsEntry 17 }

clvIPsecIfOutNoTriggerDrop OBJECT-TYPE
    SYNTAX      Counter32
    MAX-ACCESS  read-only
    STATUS      current
    DESCRIPTION
        "Number of outbound packets dropped while waiting for a previously triggered tunnel setup to complete."
    ::= { clvIPsecIfStatsEntry 18 }

clvIPsecIfOutTriggerDrop OBJECT-TYPE
    SYNTAX      Counter32
    MAX-ACCESS  read-only
    STATUS      current
    DESCRIPTION
        "Number of outbound packets dropped while triggering tunnel setup."
    ::= { clvIPsecIfStatsEntry 19 }

clvIPsecIfOutSeqOverflowDrop OBJECT-TYPE
    SYNTAX      Counter32
    MAX-ACCESS  read-only
    STATUS      current
    DESCRIPTION
        "Number of outbound packets dropped due to sequence number overflow."
    ::= { clvIPsecIfStatsEntry 20 }

clvIPsecIfInTotalDrop OBJECT-TYPE
    SYNTAX      Counter32
    MAX-ACCESS  read-only
    STATUS      current
    DESCRIPTION
        "Number of inbound packets dropped."
    ::= { clvIPsecIfStatsEntry 21 }

clvIPsecIfInAntiReplayDrop OBJECT-TYPE
    SYNTAX      Counter32
    MAX-ACCESS  read-only
    STATUS      current
    DESCRIPTION
        "Number of inbound packets dropped due to replay detected."
    ::= { clvIPsecIfStatsEntry 22 }

clvIPsecIfInAuthErrorDrop OBJECT-TYPE
    SYNTAX      Counter32
    MAX-ACCESS  read-only
    STATUS      current
    DESCRIPTION
        "Number of inbound packets dropped due to authentication errors, i.e. ICV errors."
    ::= { clvIPsecIfStatsEntry 23 }

clvIPsecIfInCorruptDrop OBJECT-TYPE
    SYNTAX      Counter32
    MAX-ACCESS  read-only
    STATUS      current
    DESCRIPTION
        "Number of inbound packets dropped due to being corrupt."
    ::= { clvIPsecIfStatsEntry 24 }

clvIPsecIfInNHErrorDrop OBJECT-TYPE
    SYNTAX      Counter32
    MAX-ACCESS  read-only
    STATUS      current
    DESCRIPTION
        "Number of inbound packets dropped due to next header mismatches."
    ::= { clvIPsecIfStatsEntry 25 }

clvIPsecIfInPadErrorDrop OBJECT-TYPE
    SYNTAX      Counter32
    MAX-ACCESS  read-only
    STATUS      current
    DESCRIPTION
        "Number of inbound packets dropped due to padding errors."
    ::= { clvIPsecIfStatsEntry 26 }

clvIPsecIfInSelectorErrorDrop OBJECT-TYPE
    SYNTAX      Counter32
    MAX-ACCESS  read-only
    STATUS      current
    DESCRIPTION
        "Number of inbound packets dropped due to selector errors."
    ::= { clvIPsecIfStatsEntry 27 }

clvCryptoDeviceTable OBJECT-TYPE
    SYNTAX      SEQUENCE OF ClvCryptoDeviceEntry
    MAX-ACCESS  not-accessible
    STATUS      current
    DESCRIPTION
        "A list of hw accelerated crypto devices."
    ::= { clvVPN 2 }

clvCryptoDeviceEntry OBJECT-TYPE
    SYNTAX      ClvCryptoDeviceEntry
    MAX-ACCESS  not-accessible
    STATUS      current
    DESCRIPTION
        "The attributes of a crypto device statistics."
    INDEX       { clvCryptoIndex }
    ::= { clvCryptoDeviceTable 1 }

ClvCryptoDeviceEntry ::= SEQUENCE {
    clvCryptoIndex                 Integer32,
    clvCryptoName                  DisplayString,
    clvCryptoOutContexts           Gauge32,
    clvCryptoInContexts            Gauge32,
    clvCryptoOutPackets            Counter32,
    clvCryptoInPackets             Counter32,
    clvCryptoDestUpdates           Counter32,
    clvCryptoDestUpdateErrors      Counter32,
    clvCryptoOutTotalDrop          Counter32,
    clvCryptoOutSeqOverflowDrop    Counter32,
    clvCryptoInTotalDrop           Counter32,
    clvCryptoInAntiReplayDrop      Counter32,
    clvCryptoInAuthErrorDrop       Counter32,
    clvCryptoInNHErrorDrop         Counter32,
    clvCryptoInPadErrorDrop        Counter32,
    clvCryptoInSelectorErrorDrop   Counter32,
    clvCryptoInUnknownSPIDrop      Counter32,
    clvCryptoFPOutPackets          Counter32,
    clvCryptoFPInPackets           Counter32,
    clvCryptoCongestionDrop        Counter32
}

clvCryptoIndex OBJECT-TYPE
    SYNTAX      Integer32 (1..2147483647)
    MAX-ACCESS  not-accessible
    STATUS      current
    DESCRIPTION
        "The index of the crypto device."
    ::= { clvCryptoDeviceEntry 1 }

clvCryptoName OBJECT-TYPE
    SYNTAX      DisplayString
    MAX-ACCESS  read-only
    STATUS      current
    DESCRIPTION
        "The name of the crypto device."
    ::= { clvCryptoDeviceEntry 2 }

clvCryptoOutContexts OBJECT-TYPE
    SYNTAX      Gauge32
    MAX-ACCESS  read-only
    STATUS      current
    DESCRIPTION
        "Number of contexts for encryption."
    ::= { clvCryptoDeviceEntry 3 }

clvCryptoInContexts OBJECT-TYPE
    SYNTAX      Gauge32
    MAX-ACCESS  read-only
    STATUS      current
    DESCRIPTION
        "Number of contexts for decryption."
    ::= { clvCryptoDeviceEntry 4 }

clvCryptoOutPackets OBJECT-TYPE
    SYNTAX      Counter32
    MAX-ACCESS  read-only
    STATUS      current
    DESCRIPTION
        "Number of encrypted packets."
    ::= { clvCryptoDeviceEntry 5 }

clvCryptoInPackets OBJECT-TYPE
    SYNTAX      Counter32
    MAX-ACCESS  read-only
    STATUS      current
    DESCRIPTION
        "Number of decrypted packets."
    ::= { clvCryptoDeviceEntry 6 }

clvCryptoDestUpdates OBJECT-TYPE
    SYNTAX      Counter32
    MAX-ACCESS  read-only
    STATUS      current
    DESCRIPTION
        "Number of successful destination updates."
    ::= { clvCryptoDeviceEntry 7 }

clvCryptoDestUpdateErrors OBJECT-TYPE
    SYNTAX      Counter32
    MAX-ACCESS  read-only
    STATUS      current
    DESCRIPTION
        "Number of destination update errors."
    ::= { clvCryptoDeviceEntry 8 }

clvCryptoOutTotalDrop OBJECT-TYPE
    SYNTAX      Counter32
    MAX-ACCESS  read-only
    STATUS      current
    DESCRIPTION
        "Number of outbound packets dropped."
    ::= { clvCryptoDeviceEntry 9 }

clvCryptoOutSeqOverflowDrop OBJECT-TYPE
    SYNTAX      Counter32
    MAX-ACCESS  read-only
    STATUS      current
    DESCRIPTION
        "Number of outbound packets dropped due to sequence number overflow."
    ::= { clvCryptoDeviceEntry 10 }

clvCryptoInTotalDrop OBJECT-TYPE
    SYNTAX      Counter32
    MAX-ACCESS  read-only
    STATUS      current
    DESCRIPTION
        "Number of inbound packets dropped."
    ::= { clvCryptoDeviceEntry 11 }

clvCryptoInAntiReplayDrop OBJECT-TYPE
    SYNTAX      Counter32
    MAX-ACCESS  read-only
    STATUS      current
    DESCRIPTION
        "Number of inbound packets dropped due to replay detected."
    ::= { clvCryptoDeviceEntry 12 }

clvCryptoInAuthErrorDrop OBJECT-TYPE
    SYNTAX      Counter32
    MAX-ACCESS  read-only
    STATUS      current
    DESCRIPTION
        "Number of inbound packets dropped due to authentication errors, i.e. ICV errors."
    ::= { clvCryptoDeviceEntry 13 }

clvCryptoInNHErrorDrop OBJECT-TYPE
    SYNTAX      Counter32
    MAX-ACCESS  read-only
    STATUS      current
    DESCRIPTION
        "Number of inbound packets dropped due to next header mismatches."
    ::= { clvCryptoDeviceEntry 14 }

clvCryptoInPadErrorDrop OBJECT-TYPE
    SYNTAX      Counter32
    MAX-ACCESS  read-only
    STATUS      current
    DESCRIPTION
        "Number of inbound packets dropped due to padding errors."
    ::= { clvCryptoDeviceEntry 15 }

clvCryptoInSelectorErrorDrop OBJECT-TYPE
    SYNTAX      Counter32
    MAX-ACCESS  read-only
    STATUS      current
    DESCRIPTION
        "Number of inbound packets dropped due to selector errors."
    ::= { clvCryptoDeviceEntry 16 }

clvCryptoInUnknownSPIDrop OBJECT-TYPE
    SYNTAX      Counter32
    MAX-ACCESS  read-only
    STATUS      current
    DESCRIPTION
        "Number of inbound packets dropped due to SPI lookup failures."
    ::= { clvCryptoDeviceEntry 17 }

clvCryptoFPOutPackets OBJECT-TYPE
    SYNTAX      Counter32
    MAX-ACCESS  read-only
    STATUS      current
    DESCRIPTION
        "Number of fastpath encrypted packets."
    ::= { clvCryptoDeviceEntry 18 }

clvCryptoFPInPackets OBJECT-TYPE
    SYNTAX      Counter32
    MAX-ACCESS  read-only
    STATUS      current
    DESCRIPTION
        "Number of fastpath decrypted packets."
    ::= { clvCryptoDeviceEntry 19 }

clvCryptoCongestionDrop OBJECT-TYPE
    SYNTAX      Counter32
    MAX-ACCESS  read-only
    STATUS      current
    DESCRIPTION
        "Number of packets dropped due to congestion."
    ::= { clvCryptoDeviceEntry 20 }

clvRules OBJECT IDENTIFIER
    ::= { clavisterOSStats 3 }

clvRuleUseTable OBJECT-TYPE
    SYNTAX      SEQUENCE OF ClvRuleUseEntry
    MAX-ACCESS  not-accessible
    STATUS      current
    DESCRIPTION
        "A list of general rules usage statistics."
    ::= { clvRules 2 }

clvRuleUseEntry OBJECT-TYPE
    SYNTAX      ClvRuleUseEntry
    MAX-ACCESS  not-accessible
    STATUS      current
    DESCRIPTION
        "The statistics over a rule usage."
    INDEX       { clvRuleIndex }
    ::= { clvRuleUseTable 1 }

ClvRuleUseEntry ::= SEQUENCE {
    clvRuleIndex    Integer32,
    clvRuleName     DisplayString,
    clvRuleUse      Counter32
}

clvRuleIndex OBJECT-TYPE
    SYNTAX      Integer32 (1..2147483647)
    MAX-ACCESS  not-accessible
    STATUS      current
    DESCRIPTION
        "The rule usage index."
    ::= { clvRuleUseEntry 1 }

clvRuleName OBJECT-TYPE
    SYNTAX      DisplayString
    MAX-ACCESS  read-only
    STATUS      current
    DESCRIPTION
        "The name of the rule."
    ::= { clvRuleUseEntry 2 }

clvRuleUse OBJECT-TYPE
    SYNTAX      Counter32
    MAX-ACCESS  read-only
    STATUS      current
    DESCRIPTION
        "The number of times a rule was used."
    ::= { clvRuleUseEntry 3 }

clvIPPools OBJECT IDENTIFIER
    ::= { clavisterOSStats 4 }

clvIPPoolsNumber OBJECT-TYPE
    SYNTAX      Integer32
    MAX-ACCESS  read-only
    STATUS      current
    DESCRIPTION
        "The number of IP pools"
    ::= { clvIPPools 1 }

clvIPPoolTable OBJECT-TYPE
    SYNTAX      SEQUENCE OF ClvIPPoolEntry
    MAX-ACCESS  not-accessible
    STATUS      current
    DESCRIPTION
        "A list of IP pools"
    ::= { clvIPPools 2 }

clvIPPoolEntry OBJECT-TYPE
    SYNTAX      ClvIPPoolEntry
    MAX-ACCESS  not-accessible
    STATUS      current
    DESCRIPTION
        "The attributes of an IP pool"
    INDEX       { clvIPPoolIndex }
    ::= { clvIPPoolTable 1 }

ClvIPPoolEntry ::= SEQUENCE {
    clvIPPoolIndex          Integer32,
    clvIPPoolName           DisplayString,
    clvIPPoolPrepare        Gauge32,
    clvIPPoolFree           Gauge32,
    clvIPPoolMisses         Gauge32,
    clvIPPoolClientFails    Gauge32,
    clvIPPoolUsed           Gauge32
}

clvIPPoolIndex OBJECT-TYPE
    SYNTAX      Integer32 (1..2147483647)
    MAX-ACCESS  not-accessible
    STATUS      current
    DESCRIPTION
        "The IP pool index"
    ::= { clvIPPoolEntry 1 }

clvIPPoolName OBJECT-TYPE
    SYNTAX      DisplayString
    MAX-ACCESS  read-only
    STATUS      current
    DESCRIPTION
        "The IP pool name"
    ::= { clvIPPoolEntry 2 }

clvIPPoolPrepare OBJECT-TYPE
    SYNTAX      Gauge32
    MAX-ACCESS  read-only
    STATUS      current
    DESCRIPTION
        "Number of IP pool objects in prepare mode."
    ::= { clvIPPoolEntry 3 }

clvIPPoolFree OBJECT-TYPE
    SYNTAX      Gauge32
    MAX-ACCESS  read-only
    STATUS      current
    DESCRIPTION
        "Number of available IPs in the pool."
    ::= { clvIPPoolEntry 4 }

clvIPPoolMisses OBJECT-TYPE
    SYNTAX      Gauge32
    MAX-ACCESS  read-only
    STATUS      current
    DESCRIPTION
        "Number of missed IP pool negotiations for other reasons
         than lack of available IP addresses."
    ::= { clvIPPoolEntry 5 }

clvIPPoolClientFails OBJECT-TYPE
    SYNTAX      Gauge32
    MAX-ACCESS  read-only
    STATUS      current
    DESCRIPTION
        "Number of failed IP pool transactions."
    ::= { clvIPPoolEntry 6 }

clvIPPoolUsed OBJECT-TYPE
    SYNTAX      Gauge32
    MAX-ACCESS  read-only
    STATUS      current
    DESCRIPTION
        "Number of IP numbers in use from the pool."
    ::= { clvIPPoolEntry 7 }

clvDHCPServer OBJECT IDENTIFIER
    ::= { clavisterOSStats 5 }

clvDHCPTotalRejected OBJECT-TYPE
    SYNTAX      Gauge32
    MAX-ACCESS  read-only
    STATUS      current
    DESCRIPTION
        "Total number of rejected packets (all rules)."
    ::= { clvDHCPServer 1 }

clvDHCPRuleTable OBJECT-TYPE
    SYNTAX      SEQUENCE OF ClvDHCPRuleEntry
    MAX-ACCESS  not-accessible
    STATUS      current
    DESCRIPTION
        "A list of all DHCP server rules usage statistics."
    ::= { clvDHCPServer 2 }

clvDHCPRuleEntry OBJECT-TYPE
    SYNTAX      ClvDHCPRuleEntry
    MAX-ACCESS  not-accessible
    STATUS      current
    DESCRIPTION
        "The attributes of a DHCP server rule statistics."
    INDEX       { clvDHCPRuleIndex }
    ::= { clvDHCPRuleTable 1 }

ClvDHCPRuleEntry ::= SEQUENCE {
    clvDHCPRuleIndex                Integer32,
    clvDHCPRuleName                 DisplayString,
    clvDHCPRuleUsage                Gauge32,
    clvDHCPRuleUsagePercent         Gauge32,
    clvDHCPActiveClients            Gauge32,
    clvDHCPActiveClientsPercent     Gauge32,
    clvDHCPRejectedRequests         Gauge32,
    clvDHCPTotalLeases              Gauge32
}

clvDHCPRuleIndex OBJECT-TYPE
    SYNTAX      Integer32 (1..2147483647)
    MAX-ACCESS  not-accessible
    STATUS      current
    DESCRIPTION
        "The DHCP server rule  index"
    ::= { clvDHCPRuleEntry 1 }

clvDHCPRuleName OBJECT-TYPE
    SYNTAX      DisplayString
    MAX-ACCESS  read-only
    STATUS      current
    DESCRIPTION
        "The DHCP server rule name."
    ::= { clvDHCPRuleEntry 2 }

clvDHCPRuleUsage OBJECT-TYPE
    SYNTAX      Gauge32
    MAX-ACCESS  read-only
    STATUS      current
    DESCRIPTION
        "Number of used IPs in the pool."
    ::= { clvDHCPRuleEntry 3 }

clvDHCPRuleUsagePercent OBJECT-TYPE
    SYNTAX      Gauge32
    MAX-ACCESS  read-only
    STATUS      current
    DESCRIPTION
        "The percentage of the used IPs in
         relation to the IP pool size."
    ::= { clvDHCPRuleEntry 4 }

clvDHCPActiveClients OBJECT-TYPE
    SYNTAX      Gauge32
    MAX-ACCESS  read-only
    STATUS      current
    DESCRIPTION
        "Number of currently active clients."
    ::= { clvDHCPRuleEntry 5 }

clvDHCPActiveClientsPercent OBJECT-TYPE
    SYNTAX      Gauge32
    MAX-ACCESS  read-only
    STATUS      current
    DESCRIPTION
        "The number of currently active clients
         as a percentage of the pool size."
    ::= { clvDHCPRuleEntry 6 }

clvDHCPRejectedRequests OBJECT-TYPE
    SYNTAX      Gauge32
    MAX-ACCESS  read-only
    STATUS      current
    DESCRIPTION
        "Number of rejected requests matching
         the current rule."
    ::= { clvDHCPRuleEntry 7 }

clvDHCPTotalLeases OBJECT-TYPE
    SYNTAX      Gauge32
    MAX-ACCESS  read-only
    STATUS      current
    DESCRIPTION
        "Total number of leases in the pool."
    ::= { clvDHCPRuleEntry 8 }

clvDHCPv6Server OBJECT IDENTIFIER
    ::= { clavisterOSStats 14 }

clvDHCPv6TotalRejected OBJECT-TYPE
    SYNTAX      Gauge32
    MAX-ACCESS  read-only
    STATUS      current
    DESCRIPTION
        "Total number of rejected packets (all rules)."
    ::= { clvDHCPv6Server 1 }

clvDHCPv6RuleTable OBJECT-TYPE
    SYNTAX      SEQUENCE OF ClvDHCPv6RuleEntry
    MAX-ACCESS  not-accessible
    STATUS      current
    DESCRIPTION
        "A list of all DHCPv6 server rules usage statistics."
    ::= { clvDHCPv6Server 2 }

clvDHCPv6RuleEntry OBJECT-TYPE
    SYNTAX      ClvDHCPv6RuleEntry
    MAX-ACCESS  not-accessible
    STATUS      current
    DESCRIPTION
        "The attributes of a DHCPv6 server rule statistics."
    INDEX       { clvDHCPv6RuleIndex }
    ::= { clvDHCPv6RuleTable 1 }

ClvDHCPv6RuleEntry ::= SEQUENCE {
    clvDHCPv6RuleIndex                Integer32,
    clvDHCPv6RuleName                 DisplayString,
    clvDHCPv6RuleUsage                Gauge32,
    clvDHCPv6RuleUsagePercent         Gauge32,
    clvDHCPv6ActiveClients            Gauge32,
    clvDHCPv6ActiveClientsPercent     Gauge32,
    clvDHCPv6RejectedRequests         Gauge32,
    clvDHCPv6TotalLeases              Gauge32
}

clvDHCPv6RuleIndex OBJECT-TYPE
    SYNTAX      Integer32 (1..2147483647)
    MAX-ACCESS  not-accessible
    STATUS      current
    DESCRIPTION
        "The DHCPv6 server rule  index"
    ::= { clvDHCPv6RuleEntry 1 }

clvDHCPv6RuleName OBJECT-TYPE
    SYNTAX      DisplayString
    MAX-ACCESS  read-only
    STATUS      current
    DESCRIPTION
        "The DHCPv6 server rule name."
    ::= { clvDHCPv6RuleEntry 2 }

clvDHCPv6RuleUsage OBJECT-TYPE
    SYNTAX      Gauge32
    MAX-ACCESS  read-only
    STATUS      current
    DESCRIPTION
        "Number of used IPs in the pool."
    ::= { clvDHCPv6RuleEntry 3 }

clvDHCPv6RuleUsagePercent OBJECT-TYPE
    SYNTAX      Gauge32
    MAX-ACCESS  read-only
    STATUS      current
    DESCRIPTION
        "The percentage of the used IPs in
         relation to the IP pool size."
    ::= { clvDHCPv6RuleEntry 4 }

clvDHCPv6ActiveClients OBJECT-TYPE
    SYNTAX      Gauge32
    MAX-ACCESS  read-only
    STATUS      current
    DESCRIPTION
        "Number of currently active clients."
    ::= { clvDHCPv6RuleEntry 5 }

clvDHCPv6ActiveClientsPercent OBJECT-TYPE
    SYNTAX      Gauge32
    MAX-ACCESS  read-only
    STATUS      current
    DESCRIPTION
        "The number of currently active clients
         as a percentage of the pool size."
    ::= { clvDHCPv6RuleEntry 6 }

clvDHCPv6RejectedRequests OBJECT-TYPE
    SYNTAX      Gauge32
    MAX-ACCESS  read-only
    STATUS      current
    DESCRIPTION
        "Number of rejected requests matching
         the current rule."
    ::= { clvDHCPv6RuleEntry 7 }

clvDHCPv6TotalLeases OBJECT-TYPE
    SYNTAX      Gauge32
    MAX-ACCESS  read-only
    STATUS      current
    DESCRIPTION
        "Total number of leases in the pool."
    ::= { clvDHCPv6RuleEntry 8 }

clvUserAuth OBJECT IDENTIFIER
    ::= { clavisterOSStats 6 }

clvUserAuthHTTPUsers OBJECT-TYPE
    SYNTAX      Gauge32
    MAX-ACCESS  read-only
    STATUS      current
    DESCRIPTION
        "Number of currently logged in HTTP users."
    ::= { clvUserAuth 1 }

clvUserAuthXAUTHUsers OBJECT-TYPE
    SYNTAX      Gauge32
    MAX-ACCESS  read-only
    STATUS      current
    DESCRIPTION
        "Number of currently logged in XAUTH users."
    ::= { clvUserAuth 2 }

clvUserAuthHTTPSUsers OBJECT-TYPE
    SYNTAX      Gauge32
    MAX-ACCESS  read-only
    STATUS      current
    DESCRIPTION
        "Number of currently logged in HTTPS users."
    ::= { clvUserAuth 3 }

clvUserAuthPPPUsers OBJECT-TYPE
    SYNTAX      Gauge32
    MAX-ACCESS  read-only
    STATUS      current
    DESCRIPTION
        "Number of currently logged in PPP users."
    ::= { clvUserAuth 4 }

clvUserAuthEAPUsers OBJECT-TYPE
    SYNTAX      Gauge32
    MAX-ACCESS  read-only
    STATUS      current
    DESCRIPTION
        "Number of currently logged in EAP users."
    ::= { clvUserAuth 5 }

clvUserAuthRuleUseTable OBJECT-TYPE
    SYNTAX      SEQUENCE OF ClvUserAuthRuleUseEntry
    MAX-ACCESS  not-accessible
    STATUS      current
    DESCRIPTION
        "Table of user authentication rule usage."
    ::= { clvUserAuth 6 }

clvUserAuthRuleUseEntry OBJECT-TYPE
    SYNTAX      ClvUserAuthRuleUseEntry
    MAX-ACCESS  not-accessible
    STATUS      current
    DESCRIPTION
        "The attributes of an authentication rule
         usage statistics."
    INDEX       { clvUserAuthRuleIndex }
    ::= { clvUserAuthRuleUseTable 1 }

ClvUserAuthRuleUseEntry ::= SEQUENCE {
    clvUserAuthRuleIndex    Integer32,
    clvUserAuthRuleName     DisplayString,
    clvUserAuthRuleUse      Counter32
}

clvUserAuthRuleIndex OBJECT-TYPE
    SYNTAX      Integer32 (1..2147483647)
    MAX-ACCESS  not-accessible
    STATUS      current
    DESCRIPTION
        "The rule usage index."
    ::= { clvUserAuthRuleUseEntry 1 }

clvUserAuthRuleName OBJECT-TYPE
    SYNTAX      DisplayString
    MAX-ACCESS  read-only
    STATUS      current
    DESCRIPTION
        "The name of the rule."
    ::= { clvUserAuthRuleUseEntry 2 }

clvUserAuthRuleUse OBJECT-TYPE
    SYNTAX      Counter32
    MAX-ACCESS  read-only
    STATUS      current
    DESCRIPTION
        "The number of times o rule was used."
    ::= { clvUserAuthRuleUseEntry 3 }

clvUserAuthIDAwareUsers OBJECT-TYPE
    SYNTAX      Gauge32
    MAX-ACCESS  read-only
    STATUS      current
    DESCRIPTION
        "Number of currently logged in Identity Awareness users."
    ::= { clvUserAuth 7 }

clvUserAuthRADIUSRelayUsers OBJECT-TYPE
    SYNTAX      Gauge32
    MAX-ACCESS  read-only
    STATUS      current
    DESCRIPTION
        "Number of currently logged in RADIUS relay users."
    ::= { clvUserAuth 8 }

clvRADIUSRelay OBJECT IDENTIFIER
    ::= { clavisterOSStats 15 }

clvRADIUSRelayRequests OBJECT-TYPE
    SYNTAX      Gauge32
    MAX-ACCESS  read-only
    STATUS      current
    DESCRIPTION
        "Total RADIUS relay request packets."
    ::= { clvRADIUSRelay 1 }

clvRADIUSRelayChallenges OBJECT-TYPE
    SYNTAX      Gauge32
    MAX-ACCESS  read-only
    STATUS      current
    DESCRIPTION
        "Total RADIUS relay challenge packets."
    ::= { clvRADIUSRelay 2 }

clvRADIUSRelayAccepts OBJECT-TYPE
    SYNTAX      Gauge32
    MAX-ACCESS  read-only
    STATUS      current
    DESCRIPTION
        "Total RADIUS relay access-accept packets."
    ::= { clvRADIUSRelay 3 }

clvRADIUSRelayRejects OBJECT-TYPE
    SYNTAX      Gauge32
    MAX-ACCESS  read-only
    STATUS      current
    DESCRIPTION
        "Total RADIUS relay access-reject packets."
    ::= { clvRADIUSRelay 4 }

clvRADIUSRelayUnknowns OBJECT-TYPE
    SYNTAX      Gauge32
    MAX-ACCESS  read-only
    STATUS      current
    DESCRIPTION
        "Total RADIUS relay unknown packets"
    ::= { clvRADIUSRelay 5 }

clvRADIUSRelayFailures OBJECT-TYPE
    SYNTAX      Gauge32
    MAX-ACCESS  read-only
    STATUS      current
    DESCRIPTION
        "Total RADIUS relay failed authentications."
    ::= { clvRADIUSRelay 6 }

clvThreatPrevention OBJECT IDENTIFIER
    ::= { clavisterOSStats 17 }

clvTPBlacklistThresholdAdd OBJECT-TYPE
    SYNTAX      Counter32
    MAX-ACCESS  read-only
    STATUS      current
    DESCRIPTION
        "Total IPs added to blacklist by threshold rules."
    ::= { clvThreatPrevention 1 }

clvTPBlacklistThresholdHit OBJECT-TYPE
    SYNTAX      Counter32
    MAX-ACCESS  read-only
    STATUS      current
    DESCRIPTION
        "Total hits on IP blacklisted by threshold rule."
    ::= { clvThreatPrevention 2 }

clvTPBlacklistIDPAdd OBJECT-TYPE
    SYNTAX      Counter32
    MAX-ACCESS  read-only
    STATUS      current
    DESCRIPTION
        "Total IPs blacklisted by IDP."
    ::= { clvThreatPrevention 3 }

clvTPBlacklistIDPHit OBJECT-TYPE
    SYNTAX      Counter32
    MAX-ACCESS  read-only
    STATUS      current
    DESCRIPTION
        "Total hits on IP blacklisted by IDP rule."
    ::= { clvThreatPrevention 4 }

clvTPBlacklistDoSAdd OBJECT-TYPE
    SYNTAX      Counter32
    MAX-ACCESS  read-only
    STATUS      current
    DESCRIPTION
        "Total IPs blacklisted by DoS Protection."
    ::= { clvThreatPrevention 5 }

clvTPBlacklistDoSHit OBJECT-TYPE
    SYNTAX      Counter32
    MAX-ACCESS  read-only
    STATUS      current
    DESCRIPTION
        "Total hits on IP blacklisted by DoS Protection."
    ::= { clvThreatPrevention 6 }

clvTPBlacklistBotnetAdd OBJECT-TYPE
    SYNTAX      Counter32
    MAX-ACCESS  read-only
    STATUS      current
    DESCRIPTION
        "Total IPs blacklisted by Botnet Protection."
    ::= { clvThreatPrevention 7 }

clvTPBlacklistBotnetHit OBJECT-TYPE
    SYNTAX      Counter32
    MAX-ACCESS  read-only
    STATUS      current
    DESCRIPTION
        "Total hits on IP blacklisted by Botnet Protection."
    ::= { clvThreatPrevention 8 }

clvTPBlacklistScannerAdd OBJECT-TYPE
    SYNTAX      Counter32
    MAX-ACCESS  read-only
    STATUS      current
    DESCRIPTION
        "Total IPs blacklisted by Scanner Protection."
    ::= { clvThreatPrevention 9 }

clvTPBlacklistScannerHit OBJECT-TYPE
    SYNTAX      Counter32
    MAX-ACCESS  read-only
    STATUS      current
    DESCRIPTION
        "Total hits on IP blacklisted by Scanner Protection."
    ::= { clvThreatPrevention 10 }

clvTPBlacklistGeoIpAdd OBJECT-TYPE
    SYNTAX      Counter32
    MAX-ACCESS  read-only
    STATUS      current
    DESCRIPTION
        "Total IPs blacklisted by DoS/GeoIP Protection."
    ::= { clvThreatPrevention 11 }

clvTPBlacklistGeoIpHit OBJECT-TYPE
    SYNTAX      Counter32
    MAX-ACCESS  read-only
    STATUS      current
    DESCRIPTION
        "Total hits on IP blacklisted by DoS/GeoIP Protection."
    ::= { clvThreatPrevention 12 }

clvTPBlacklistRestAdd OBJECT-TYPE
    SYNTAX      Gauge32
    MAX-ACCESS  read-only
    STATUS      current
    DESCRIPTION
        "Total IPs blacklisted by REST API."
    ::= { clvThreatPrevention 13 }

clvTPBlacklistRestHit OBJECT-TYPE
    SYNTAX      Gauge32
    MAX-ACCESS  read-only
    STATUS      current
    DESCRIPTION
        "Total hits on IP blacklisted by REST API."
    ::= { clvThreatPrevention 14 }

clvLinkMonitor OBJECT IDENTIFIER
    ::= { clavisterOSStats 7 }

clvLinkMonGrp OBJECT-TYPE
    SYNTAX      Integer32
    MAX-ACCESS  read-only
    STATUS      current
    DESCRIPTION
        "The number of groups of monitored links"
    ::= { clvLinkMonitor 1 }

clvLinkMonGrpTable OBJECT-TYPE
    SYNTAX      SEQUENCE OF ClvLinkMonGrpEntry
    MAX-ACCESS  not-accessible
    STATUS      current
    DESCRIPTION
        "Table of link monitor groups."
    ::= { clvLinkMonitor 2 }

clvLinkMonGrpEntry OBJECT-TYPE
    SYNTAX      ClvLinkMonGrpEntry
    MAX-ACCESS  not-accessible
    STATUS      current
    DESCRIPTION
        "The attributes of a link monitor group"
    INDEX       { clvLinkMonGrpIndex }
    ::= { clvLinkMonGrpTable 1 }

ClvLinkMonGrpEntry ::= SEQUENCE {
    clvLinkMonGrpIndex      Integer32,
    clvLinkMonGrpName       DisplayString,
    clvLinkMonGrpHostsUp    Gauge32
}

clvLinkMonGrpIndex OBJECT-TYPE
    SYNTAX      Integer32 (1..2147483647)
    MAX-ACCESS  not-accessible
    STATUS      current
    DESCRIPTION
        "The index row in the table of link monitor groups."
    ::= { clvLinkMonGrpEntry 1 }

clvLinkMonGrpName OBJECT-TYPE
    SYNTAX      DisplayString
    MAX-ACCESS  read-only
    STATUS      current
    DESCRIPTION
        "The link monitor group name."
    ::= { clvLinkMonGrpEntry 2 }

clvLinkMonGrpHostsUp OBJECT-TYPE
    SYNTAX      Gauge32
    MAX-ACCESS  read-only
    STATUS      current
    DESCRIPTION
        "The percentage of monitored hosts available."
    ::= { clvLinkMonGrpEntry 3 }

clvLinkMonHostTable OBJECT-TYPE
    SYNTAX      SEQUENCE OF ClvLinkMonHostEntry
    MAX-ACCESS  not-accessible
    STATUS      current
    DESCRIPTION
        "Table of link monitored hosts in a link monitor group."
    ::= { clvLinkMonitor 3 }

clvLinkMonHostEntry OBJECT-TYPE
    SYNTAX      ClvLinkMonHostEntry
    MAX-ACCESS  not-accessible
    STATUS      current
    DESCRIPTION
        "The attributes of a monitored host."
    INDEX       { clvLinkMonGrpIndex, clvLinkMonHostIndex }
    ::= { clvLinkMonHostTable 1 }

ClvLinkMonHostEntry ::= SEQUENCE {
    clvLinkMonHostIndex             Integer32,
    clvLinkMonHostId                DisplayString,
    clvLinkMonHostShortTermLoss     Gauge32,
    clvLinkMonHostPacketsLost       Counter32
}

clvLinkMonHostIndex OBJECT-TYPE
    SYNTAX      Integer32 (1..2147483647)
    MAX-ACCESS  not-accessible
    STATUS      current
    DESCRIPTION
        "The index an host in the table of link monitor hosts."
    ::= { clvLinkMonHostEntry 1 }

clvLinkMonHostId OBJECT-TYPE
    SYNTAX      DisplayString
    MAX-ACCESS  read-only
    STATUS      current
    DESCRIPTION
        "The monitored host identifier."
    ::= { clvLinkMonHostEntry 2 }

clvLinkMonHostShortTermLoss OBJECT-TYPE
    SYNTAX      Gauge32
    MAX-ACCESS  read-only
    STATUS      current
    DESCRIPTION
        "The percentage of short term lost packets."
    ::= { clvLinkMonHostEntry 3 }

clvLinkMonHostPacketsLost OBJECT-TYPE
    SYNTAX      Counter32
    MAX-ACCESS  read-only
    STATUS      current
    DESCRIPTION
        "Total number of lost monitoring packets."
    ::= { clvLinkMonHostEntry 4 }

clvPipes OBJECT IDENTIFIER
    ::= { clavisterOSStats 8 }

clvPipeUsers OBJECT-TYPE
    SYNTAX      Gauge32
    MAX-ACCESS  read-only
    STATUS      current
    DESCRIPTION
        "The current number of users, as defined by the grouping
         settings of each pipe, being tracked in the pipes system.
         Note that this value corresponds to the number of users
         active in each time slice of 1/20th of a second, and not
         to the number of users having open connections."
    ::= { clvPipes 1 }

clvPipeTable OBJECT-TYPE
    SYNTAX      SEQUENCE OF ClvPipeEntry
    MAX-ACCESS  not-accessible
    STATUS      current
    DESCRIPTION
        "Table of pipes"
    ::= { clvPipes 2 }

clvPipeEntry OBJECT-TYPE
    SYNTAX      ClvPipeEntry
    MAX-ACCESS  not-accessible
    STATUS      current
    DESCRIPTION
        "A entry of the pipes table"
    INDEX       { clvPipeIndex }
    ::= { clvPipeTable 1 }

ClvPipeEntry ::= SEQUENCE {
    clvPipeIndex            Integer32,
    clvPipeName             DisplayString,
    clvPipeMinPrec          Integer32,
    clvPipeMaxPrec          Integer32,
    clvPipeDefPrec          Integer32,
    clvPipeNumPrec          Integer32,
    clvPipeNumUsers         Gauge32,
    clvPipeCurrentBps       Gauge32,
    clvPipeCurrentPps       Gauge32,
    clvPipeDelayedPackets   Counter32,
    clvPipeDropedPackets    Counter32
}

clvPipeIndex OBJECT-TYPE
    SYNTAX      Integer32 (1..2147483647)
    MAX-ACCESS  not-accessible
    STATUS      current
    DESCRIPTION
        "The pipe index"
    ::= { clvPipeEntry 1 }

clvPipeName OBJECT-TYPE
    SYNTAX      DisplayString
    MAX-ACCESS  read-only
    STATUS      current
    DESCRIPTION
        "The name of the pipe"
    ::= { clvPipeEntry 2 }

clvPipeMinPrec OBJECT-TYPE
    SYNTAX      Integer32
    MAX-ACCESS  read-only
    STATUS      current
    DESCRIPTION
        "The minimum of the range of pipe precedences."
    ::= { clvPipeEntry 3 }

clvPipeMaxPrec OBJECT-TYPE
    SYNTAX      Integer32
    MAX-ACCESS  read-only
    STATUS      current
    DESCRIPTION
        "The maximum of the range of pipe precedences."
    ::= { clvPipeEntry 4 }

clvPipeDefPrec OBJECT-TYPE
    SYNTAX      Integer32
    MAX-ACCESS  read-only
    STATUS      current
    DESCRIPTION
        "The precedence assigned to a packet for which has not one
         already done by a Pipe Rule."
    ::= { clvPipeEntry 5 }

clvPipeNumPrec OBJECT-TYPE
    SYNTAX      Integer32
    MAX-ACCESS  read-only
    STATUS      current
    DESCRIPTION
        "The number of pipe precedences"
    ::= { clvPipeEntry 6 }

clvPipeNumUsers OBJECT-TYPE
    SYNTAX      Gauge32
    MAX-ACCESS  read-only
    STATUS      current
    DESCRIPTION
        "The current number of users, as defined by the grouping settings
         of each pipe, being tracked in the pipes system. This value
         corresponds to the number of users active in each time slice
         and not to the number of users having  open connections."
    ::= { clvPipeEntry 7 }

clvPipeCurrentBps OBJECT-TYPE
    SYNTAX      Gauge32
    MAX-ACCESS  read-only
    STATUS      current
    DESCRIPTION
        "The current throughput of a pipe, in bits per second, as a sum of
         the corresponding values for all precedences."
    ::= { clvPipeEntry 8 }

clvPipeCurrentPps OBJECT-TYPE
    SYNTAX      Gauge32
    MAX-ACCESS  read-only
    STATUS      current
    DESCRIPTION
        "The current throughput of a pipe, in packets per second, as a sum of
         the corresponding values for all precedences."
    ::= { clvPipeEntry 9 }

clvPipeDelayedPackets OBJECT-TYPE
    SYNTAX      Counter32
    MAX-ACCESS  read-only
    STATUS      current
    DESCRIPTION
        "The number of times packets have been delayed as a result of a pipe,
         or pipe user having used up its allotted bandwidth. Note that one single
         packet may be delayed several times; if a pipe is really full, this
         count may exceed the number of packets actually passing through the
         pipe."
    ::= { clvPipeEntry 10 }

clvPipeDropedPackets OBJECT-TYPE
    SYNTAX      Counter32
    MAX-ACCESS  read-only
    STATUS      current
    DESCRIPTION
        "The number of packets dropped by a pipe. Packets are dropped when
         unit is running out of packet buffers. This occurs when excessive
         amounts of packets need to be queued for later delivery. The packet
         dropped is always the one that has been queued the longest time
         globally, which means that the connection suffering from packet loss
         will be the one most overloading the system."
    ::= { clvPipeEntry 11 }

clvPipePrecTable OBJECT-TYPE
    SYNTAX      SEQUENCE OF ClvPipePrecEntry
    MAX-ACCESS  not-accessible
    STATUS      current
    DESCRIPTION
        "There is a one to many relation between a pipe and its precedences.
         The number of precedences is a instance attribute of each pipe.
         This table extends the pipes table in order to express the relation
         between a pipe and the respective precedences."
    ::= { clvPipes 3 }

clvPipePrecEntry OBJECT-TYPE
    SYNTAX      ClvPipePrecEntry
    MAX-ACCESS  not-accessible
    STATUS      current
    DESCRIPTION
        "An entry of the table of pipe precedences. These table entries
         are characterized by been indexed by two values. The first index
         the same as the pipe index of the corresponding row in table of
         pipes and the second index is the index of the set of precedences
         of the corresponding pipe."
    INDEX       { clvPipeIndex, clvPipePrecIndex }
    ::= { clvPipePrecTable 1 }

ClvPipePrecEntry ::= SEQUENCE {
    clvPipePrecIndex            Integer32,
    clvPipePrec                 Integer32,
    clvPipePrecBps              Gauge32,
    clvPipePrecTotalPps         Gauge32,
    clvPipePrecReservedBps      Gauge32,
    clvPipePrecDynLimBps        Gauge32,
    clvPipePrecDynUsrLimBps     Gauge32,
    clvPipePrecDelayedPackets   Counter32,
    clvPipePrecDropedPackets    Counter32
}

clvPipePrecIndex OBJECT-TYPE
    SYNTAX      Integer32 (1..2147483647)
    MAX-ACCESS  not-accessible
    STATUS      current
    DESCRIPTION
        "Index of a precedence of a specific pipe. This is the second index
         of the entries of pipe precedence table described by object
         clvPipePrecEntry."
    ::= { clvPipePrecEntry 1 }

clvPipePrec OBJECT-TYPE
    SYNTAX      Integer32
    MAX-ACCESS  read-only
    STATUS      current
    DESCRIPTION
        "The precedence value"
    ::= { clvPipePrecEntry 2 }

clvPipePrecBps OBJECT-TYPE
    SYNTAX      Gauge32
    MAX-ACCESS  read-only
    STATUS      current
    DESCRIPTION
        "The current throughput of the pipe, in bits per second, with
         the corresponding precedence."
    ::= { clvPipePrecEntry 3 }

clvPipePrecTotalPps OBJECT-TYPE
    SYNTAX      Gauge32
    MAX-ACCESS  read-only
    STATUS      current
    DESCRIPTION
        "The current throughput of the pipe precedence, in packets per second."
    ::= { clvPipePrecEntry 4 }

clvPipePrecReservedBps OBJECT-TYPE
    SYNTAX      Gauge32
    MAX-ACCESS  read-only
    STATUS      current
    DESCRIPTION
        "The current bandwidth allocated to the precedence."
    ::= { clvPipePrecEntry 5 }

clvPipePrecDynLimBps OBJECT-TYPE
    SYNTAX      Gauge32
    MAX-ACCESS  read-only
    STATUS      current
    DESCRIPTION
        "The current bandwidth limit applied the precedence."
    ::= { clvPipePrecEntry 6 }

clvPipePrecDynUsrLimBps OBJECT-TYPE
    SYNTAX      Gauge32
    MAX-ACCESS  read-only
    STATUS      current
    DESCRIPTION
        "The current precedence bandwidth limit per user of the pipe."
    ::= { clvPipePrecEntry 7 }

clvPipePrecDelayedPackets OBJECT-TYPE
    SYNTAX      Counter32
    MAX-ACCESS  read-only
    STATUS      current
    DESCRIPTION
        "The number of times packets have been delayed as a result of a
         precedence, or pipe user having used up its allotted bandwidth.
         Note that one single packet may be delayed several times; if a
         pipe is really full, this count may exceed the number of packets
         of this precedence actually passing through the pipe."
    ::= { clvPipePrecEntry 8 }

clvPipePrecDropedPackets OBJECT-TYPE
    SYNTAX      Counter32
    MAX-ACCESS  read-only
    STATUS      current
    DESCRIPTION
        "The number of pipe dropped packets with the corresponding precedence."
    ::= { clvPipePrecEntry 9 }

clvALG OBJECT IDENTIFIER
    ::= { clavisterOSStats 9 }

clvAlgSessions OBJECT-TYPE
    SYNTAX      Gauge32
    MAX-ACCESS  read-only
    STATUS      current
    DESCRIPTION
        "Total ALG sessions"
    ::= { clvALG 1 }

clvAlgConnections OBJECT-TYPE
    SYNTAX      Gauge32
    MAX-ACCESS  read-only
    STATUS      current
    DESCRIPTION
        "Total ALG connections"
    ::= { clvALG 2 }

clvAlgTCPStreams OBJECT-TYPE
    SYNTAX      Gauge32
    MAX-ACCESS  read-only
    STATUS      current
    DESCRIPTION
        "Total ALG TCP streams"
    ::= { clvALG 3 }

clvHttpAlg OBJECT IDENTIFIER
    ::= { clvALG 4 }

clvHttpAlgTable OBJECT-TYPE
    SYNTAX      SEQUENCE OF ClvHttpAlgEntry
    MAX-ACCESS  not-accessible
    STATUS      current
    DESCRIPTION
        "Table of HTTP ALG objects."
    ::= { clvHttpAlg 1 }

clvHttpAlgEntry OBJECT-TYPE
    SYNTAX      ClvHttpAlgEntry
    MAX-ACCESS  not-accessible
    STATUS      current
    DESCRIPTION
        "A row of the table of HTTP ALG objects."
    INDEX       { clvHttpAlgIndex }
    ::= { clvHttpAlgTable 1 }

ClvHttpAlgEntry ::= SEQUENCE {
    clvHttpAlgIndex             Integer32,
    clvHttpAlgName              DisplayString,
    clvHttpAlgTotalRequested    Gauge32,
    clvHttpAlgTotalAllowed      Gauge32,
    clvHttpAlgTotalBlocked      Gauge32
}

clvHttpAlgIndex OBJECT-TYPE
    SYNTAX      Integer32 (1..2147483647)
    MAX-ACCESS  not-accessible
    STATUS      current
    DESCRIPTION
        "The index of an entry of the Table of HTTP ALG objects."
    ::= { clvHttpAlgEntry 1 }

clvHttpAlgName OBJECT-TYPE
    SYNTAX      DisplayString
    MAX-ACCESS  read-only
    STATUS      current
    DESCRIPTION
        "The name of an HTTP ALG object."
    ::= { clvHttpAlgEntry 2 }

clvHttpAlgTotalRequested OBJECT-TYPE
    SYNTAX      Gauge32
    MAX-ACCESS  read-only
    STATUS      current
    DESCRIPTION
        "Total number of URL requests."
    ::= { clvHttpAlgEntry 3 }

clvHttpAlgTotalAllowed OBJECT-TYPE
    SYNTAX      Gauge32
    MAX-ACCESS  read-only
    STATUS      current
    DESCRIPTION
        "Total number of allowed URL requests."
    ::= { clvHttpAlgEntry 4 }

clvHttpAlgTotalBlocked OBJECT-TYPE
    SYNTAX      Gauge32
    MAX-ACCESS  read-only
    STATUS      current
    DESCRIPTION
        "Total number of blocked URL requests."
    ::= { clvHttpAlgEntry 5 }

clvHttpAlgCntFltTable OBJECT-TYPE
    SYNTAX      SEQUENCE OF ClvHttpAlgCntFltEntry
    MAX-ACCESS  not-accessible
    STATUS      current
    DESCRIPTION
        "Table of HTTP ALG content filtering rules."
    ::= { clvHttpAlg 2 }

clvHttpAlgCntFltEntry OBJECT-TYPE
    SYNTAX      ClvHttpAlgCntFltEntry
    MAX-ACCESS  not-accessible
    STATUS      current
    DESCRIPTION
        "Entry of the table of HTTP ALG content filtering rules."
    INDEX       { clvHttpAlgIndex, clvHttpAlgCntFltIndex }
    ::= { clvHttpAlgCntFltTable 1 }

ClvHttpAlgCntFltEntry ::= SEQUENCE {
    clvHttpAlgCntFltIndex       Integer32,
    clvHttpAlgCntFltName        DisplayString,
    clvHttpAlgCntFltRequests    Gauge32,
    clvHttpAlgCntFltAllowed     Gauge32,
    clvHttpAlgCntFltBlocked     Gauge32
}

clvHttpAlgCntFltIndex OBJECT-TYPE
    SYNTAX      Integer32 (1..2147483647)
    MAX-ACCESS  not-accessible
    STATUS      current
    DESCRIPTION
        "The index of an entry of the Table of HTTP ALG
         content filtering objects."
    ::= { clvHttpAlgCntFltEntry 1 }

clvHttpAlgCntFltName OBJECT-TYPE
    SYNTAX      DisplayString
    MAX-ACCESS  read-only
    STATUS      current
    DESCRIPTION
        "The name of the a HTTP ALG content filtering."
    ::= { clvHttpAlgCntFltEntry 2 }

clvHttpAlgCntFltRequests OBJECT-TYPE
    SYNTAX      Gauge32
    MAX-ACCESS  read-only
    STATUS      current
    DESCRIPTION
        "Total number of URLs intercepted by a content
         filtering object."
    ::= { clvHttpAlgCntFltEntry 3 }

clvHttpAlgCntFltAllowed OBJECT-TYPE
    SYNTAX      Gauge32
    MAX-ACCESS  read-only
    STATUS      current
    DESCRIPTION
        "Total number of URLs intercepted and allowed
         by a content filtering object."
    ::= { clvHttpAlgCntFltEntry 4 }

clvHttpAlgCntFltBlocked OBJECT-TYPE
    SYNTAX      Gauge32
    MAX-ACCESS  read-only
    STATUS      current
    DESCRIPTION
        "Total number of URLs intercepted and blocked
         by a content filtering object."
    ::= { clvHttpAlgCntFltEntry 5 }

clvSmtpAlg OBJECT IDENTIFIER
    ::= { clvALG 5 }

clvSmtpAlgTable OBJECT-TYPE
    SYNTAX  SEQUENCE OF ClvSmtpAlgEntry
    MAX-ACCESS  not-accessible
    STATUS  current
    DESCRIPTION
  "Table of SMTP ALG objects."
    ::= { clvSmtpAlg 1 }

clvSmtpAlgEntry OBJECT-TYPE
   SYNTAX  ClvSmtpAlgEntry
   MAX-ACCESS  not-accessible
    STATUS      current
    DESCRIPTION
        "A row of the table of SMTP ALG objects."
    INDEX       { clvSmtpAlgIndex }
    ::= { clvSmtpAlgTable 1 }

ClvSmtpAlgEntry ::= SEQUENCE {
    clvSmtpAlgIndex           Integer32,
    clvSmtpAlgName            DisplayString,
    clvSmtpAlgTotCheckedSes   Gauge32,
    clvSmtpAlgTotSpamSes      Gauge32,
    clvSmtpAlgTotDroppedSes   Gauge32
}

clvSmtpAlgIndex OBJECT-TYPE
    SYNTAX      Integer32 (1..2147483647)
    MAX-ACCESS  not-accessible
    STATUS      current
    DESCRIPTION
        "The index of an entry of the Table of SMTP ALG objects."
    ::= { clvSmtpAlgEntry 1 }

clvSmtpAlgName OBJECT-TYPE
    SYNTAX      DisplayString
    MAX-ACCESS  read-only
    STATUS      current
    DESCRIPTION
        "The name of an SMTP ALG object."
    ::= { clvSmtpAlgEntry 2 }

clvSmtpAlgTotCheckedSes OBJECT-TYPE
    SYNTAX      Gauge32
    MAX-ACCESS  read-only
    STATUS      current
    DESCRIPTION
        "Total sessions checked by the SMTP ALG of corresponding index."
    ::= { clvSmtpAlgEntry 3 }

clvSmtpAlgTotSpamSes OBJECT-TYPE
    SYNTAX      Gauge32
    MAX-ACCESS  read-only
    STATUS      current
    DESCRIPTION
        "Total spam sessions detected by the SMTP ALG of corresponding index."
    ::= { clvSmtpAlgEntry 4 }

clvSmtpAlgTotDroppedSes OBJECT-TYPE
    SYNTAX      Gauge32
    MAX-ACCESS  read-only
    STATUS      current
    DESCRIPTION
        "Total dropped sessions for the SMTP ALG of corresponding index."
    ::= { clvSmtpAlgEntry 5 }


clvSmtpAlgDnsBlTable OBJECT-TYPE
    SYNTAX  SEQUENCE OF ClvSmtpAlgDnsBlEntry
    MAX-ACCESS  not-accessible
    STATUS  current
    DESCRIPTION
  "Table of SMTP ALG DNS black list objects."
    ::= { clvSmtpAlg 2 }


clvSmtpAlgDnsBlEntry OBJECT-TYPE
   SYNTAX  ClvSmtpAlgDnsBlEntry
   MAX-ACCESS  not-accessible
    STATUS      current
    DESCRIPTION
        "A row of the table of SMTP ALG DNS black list objects."
    INDEX       { clvSmtpAlgIndex, clvSmtpAlgDnsBlIndex }
    ::= { clvSmtpAlgDnsBlTable 1 }


ClvSmtpAlgDnsBlEntry ::= SEQUENCE {
    clvSmtpAlgDnsBlIndex  Integer32,
    clvSmtpAlgDnsBlName    DisplayString,
    clvSmtpAlgDnsBlChecked      Gauge32,
    clvSmtpAlgDnsBlMatched  Gauge32,
    clvSmtpAlgDnsBlFailChecks  Gauge32
}

clvSmtpAlgDnsBlIndex OBJECT-TYPE
    SYNTAX      Integer32 (1..2147483647)
    MAX-ACCESS  not-accessible
    STATUS      current
    DESCRIPTION
        "The index of an entry of the SMTP ALG DNS black list objects."
    ::= { clvSmtpAlgDnsBlEntry 1 }

clvSmtpAlgDnsBlName OBJECT-TYPE
    SYNTAX      DisplayString
    MAX-ACCESS  read-only
    STATUS      current
    DESCRIPTION
  "The SMTP DNS black list name."
    ::= { clvSmtpAlgDnsBlEntry 2 }

clvSmtpAlgDnsBlChecked OBJECT-TYPE
    SYNTAX      Gauge32
    MAX-ACCESS  read-only
    STATUS      current
    DESCRIPTION
  "Total sessions checked against SMTP ALG DNS black list of corresponding index"
    ::= { clvSmtpAlgDnsBlEntry 3 }

clvSmtpAlgDnsBlMatched OBJECT-TYPE
    SYNTAX      Gauge32
    MAX-ACCESS  read-only
    STATUS      current
    DESCRIPTION
  "Total sessions that matched SMTP ALG DNS black list of corresponding index"
    ::= { clvSmtpAlgDnsBlEntry 4 }

clvSmtpAlgDnsBlFailChecks OBJECT-TYPE
    SYNTAX      Gauge32
    MAX-ACCESS  read-only
    STATUS      current
    DESCRIPTION
  "Total failed checks for the SMTP ALG DNS black list of corresponding index"
    ::= { clvSmtpAlgDnsBlEntry 5 }

clvDnsAlg OBJECT IDENTIFIER
    ::= { clvALG 6 }

clvDnsAlgFwdDnsReqs OBJECT-TYPE
    SYNTAX      Counter64
    MAX-ACCESS  read-only
    STATUS      current
    DESCRIPTION
        "Forwarded DNS Queries"
    ::= { clvDnsAlg 1 }

clvDnsAlgFwdDnsResps OBJECT-TYPE
    SYNTAX      Counter64
    MAX-ACCESS  read-only
    STATUS      current
    DESCRIPTION
        "Forwarded DNS Responses"
    ::= { clvDnsAlg 2 }

clvDnsAlgMalCliMsgs OBJECT-TYPE
    SYNTAX      Counter64
    MAX-ACCESS  read-only
    STATUS      current
    DESCRIPTION
        "Malformed Client Messages"
    ::= { clvDnsAlg 3 }

clvDnsAlgMalSrvMsgs OBJECT-TYPE
    SYNTAX      Counter64
    MAX-ACCESS  read-only
    STATUS      current
    DESCRIPTION
        "Malformed Server Messages"
    ::= { clvDnsAlg 4 }

clvDnsAlgDropCliMsgs OBJECT-TYPE
    SYNTAX      Counter64
    MAX-ACCESS  read-only
    STATUS      current
    DESCRIPTION
        "Dropped Client Messages"
    ::= { clvDnsAlg 5 }

clvDnsAlgDropSrvMsgs OBJECT-TYPE
    SYNTAX      Counter64
    MAX-ACCESS  read-only
    STATUS      current
    DESCRIPTION
        "Dropped Server Messages"
    ::= { clvDnsAlg 6 }

clvDnsAlgCurDnsSes OBJECT-TYPE
    SYNTAX      Gauge32
    MAX-ACCESS  read-only
    STATUS      current
    DESCRIPTION
        "Current DNS Session"
    ::= { clvDnsAlg 7 }

clvDnsAlgTotDnsSes OBJECT-TYPE
    SYNTAX      Counter64
    MAX-ACCESS  read-only
    STATUS      current
    DESCRIPTION
        "Total DNS Session"
    ::= { clvDnsAlg 8 }

clvDHCPRelay OBJECT IDENTIFIER
    ::= { clavisterOSStats 11 }

clvDHCPRelayCurClients OBJECT-TYPE
    SYNTAX      Gauge32
    MAX-ACCESS  read-only
    STATUS      current
    DESCRIPTION
        "Total DHCP relay active relayed clients."
    ::= { clvDHCPRelay 1 }

clvDHCPRelayCurTrans OBJECT-TYPE
    SYNTAX      Gauge32
    MAX-ACCESS  read-only
    STATUS      current
    DESCRIPTION
        "Ongoing DHCP relay transactions."
    ::= { clvDHCPRelay 2 }

clvDHCPRelayRejected OBJECT-TYPE
    SYNTAX      Gauge32
    MAX-ACCESS  read-only
    STATUS      current
    DESCRIPTION
        "Total DHCP relay packets rejected."
    ::= { clvDHCPRelay 3 }

clvDHCPRelayRuleTable OBJECT-TYPE
    SYNTAX      SEQUENCE OF ClvDHCPRelayRuleEntry
    MAX-ACCESS  not-accessible
    STATUS      current
    DESCRIPTION
        "Table of DHCP relay rules."
    ::= { clvDHCPRelay 4 }

clvDHCPRelayRuleEntry OBJECT-TYPE
    SYNTAX      ClvDHCPRelayRuleEntry
    MAX-ACCESS  not-accessible
    STATUS      current
    DESCRIPTION
        "Entry of the table of DHCP relay rules"
    INDEX       { clvDHCPRelayRuleIndex }
    ::= { clvDHCPRelayRuleTable 1 }

ClvDHCPRelayRuleEntry ::= SEQUENCE {
    clvDHCPRelayRuleIndex       Integer32,
    clvDHCPRelayRuleName        DisplayString,
    clvDHCPRelayRuleHits        Gauge32,
    clvDHCPRelayRuleCurClients  Gauge32,
    clvDHCPRelayRuleRejCliPkts  Gauge32,
    clvDHCPRelayRuleRejSrvPkts  Gauge32
}

clvDHCPRelayRuleIndex OBJECT-TYPE
    SYNTAX      Integer32 (1..2147483647)
    MAX-ACCESS  not-accessible
    STATUS      current
    DESCRIPTION
        "Index of the table of DHCP relay rules."
    ::= { clvDHCPRelayRuleEntry 1 }

clvDHCPRelayRuleName OBJECT-TYPE
    SYNTAX      DisplayString
    MAX-ACCESS  read-only
    STATUS      current
    DESCRIPTION
        "Display name of a DHCP relay rule"
    ::= { clvDHCPRelayRuleEntry 2 }

clvDHCPRelayRuleHits OBJECT-TYPE
    SYNTAX      Gauge32
    MAX-ACCESS  read-only
    STATUS      current
    DESCRIPTION
        "Number of the times the DHCP relay rule with corresponding index was
         used."
    ::= { clvDHCPRelayRuleEntry 3 }

clvDHCPRelayRuleCurClients OBJECT-TYPE
    SYNTAX      Gauge32
    MAX-ACCESS  read-only
    STATUS      current
    DESCRIPTION
        "Number of active relayed clients by the DHCP relay rule with corresponding index."
    ::= { clvDHCPRelayRuleEntry 4 }

clvDHCPRelayRuleRejCliPkts OBJECT-TYPE
    SYNTAX      Gauge32
    MAX-ACCESS  read-only
    STATUS      current
    DESCRIPTION
        "Number of client packets rejected by a rule."
    ::= { clvDHCPRelayRuleEntry 5 }

clvDHCPRelayRuleRejSrvPkts OBJECT-TYPE
    SYNTAX      Gauge32
    MAX-ACCESS  read-only
    STATUS      current
    DESCRIPTION
        "Number of DHCP server packets rejected by the DHCP relay rule
         with the corresponding index."
    ::= { clvDHCPRelayRuleEntry 6 }

clvHA OBJECT IDENTIFIER
    ::= { clavisterOSStats 12 }

clvHASyncSendQueueLength OBJECT-TYPE
    SYNTAX      Gauge32
    MAX-ACCESS  read-only
    STATUS      current
    DESCRIPTION
        "Size of the queue used for the High Availability sync interface."
    ::= { clvHA 1 }

clvHASyncSendQueueUsagePkt OBJECT-TYPE
    SYNTAX      Gauge32
    MAX-ACCESS  read-only
    STATUS      current
    DESCRIPTION
        "High Availability Sync interface queue usage in number of packets."
    ::= { clvHA 2 }

clvHASyncSendQueueUsageOct OBJECT-TYPE
    SYNTAX      Gauge32
    MAX-ACCESS  read-only
    STATUS      current
    DESCRIPTION
        "High Availability Sync interface queue usage in number of octects."
    ::= { clvHA 3 }

clvHASyncSentPackets OBJECT-TYPE
    SYNTAX      Counter32
    MAX-ACCESS  read-only
    STATUS      current
    DESCRIPTION
        "Number High Availability packets sent on Sync."
    ::= { clvHA 4 }

clvHASyncSendResentPackets OBJECT-TYPE
    SYNTAX      Counter32
    MAX-ACCESS  read-only
    STATUS      current
    DESCRIPTION
        "Number of High Availability packets resent on Sync."
    ::= { clvHA 5 }

clvHAStatusRole OBJECT-TYPE
    SYNTAX      INTEGER { slave(0), master(1)}
    MAX-ACCESS  read-only
    STATUS      current
    DESCRIPTION
        "The configured HA role of the node. Either master(1) or slave(0)"
    ::= { clvHA 10 }

clvHAStatusState OBJECT-TYPE
    SYNTAX      INTEGER { inactive(0), active(1)}
    MAX-ACCESS  read-only
    STATUS      current
    DESCRIPTION
        "The current state of the system. In active(1) state, the node is the active
         part of the HA cluster and forwards traffic. In inactive(0) state, the node
         is in stand by. "
    ::= { clvHA 11 }

clvHAStatusTimeWithinState OBJECT-TYPE
    SYNTAX      Integer32
    MAX-ACCESS  read-only
    STATUS      current
    DESCRIPTION
        "The number of seconds that the system has been in the current state (active or inactive)"
    ::= { clvHA 12 }

clvAppControlTable OBJECT-TYPE
    SYNTAX      SEQUENCE OF ClvAppControlEntry
    MAX-ACCESS  not-accessible
    STATUS      current
    DESCRIPTION
        "A table of Clavister specific application control statistics"
    ::= { clavisterOSStats 13 }

clvAppControlEntry OBJECT-TYPE
    SYNTAX      ClvAppControlEntry
    MAX-ACCESS  not-accessible
    STATUS      current
    DESCRIPTION
        "The row in a table of Clavister specific application control statistics"
    INDEX       { clvAppCtrlIndex }
    ::= { clvAppControlTable 1 }

ClvAppControlEntry ::= SEQUENCE {
    clvAppCtrlIndex         Integer32,
    clvAppCtrlName          DisplayString,
    clvAppCtrlBytesFwd      Counter64,
    clvAppCtrlPacketsFwd    Counter64,
    clvAppCtrlClassified    Counter64
}

clvAppCtrlIndex OBJECT-TYPE
    SYNTAX      Integer32 (1..2147483647)
    MAX-ACCESS  not-accessible
    STATUS      current
    DESCRIPTION
        "Index of a row in clvAppControlTable"
    ::= { clvAppControlEntry 1 }

clvAppCtrlName OBJECT-TYPE
    SYNTAX      DisplayString
    MAX-ACCESS  read-only
    STATUS      current
    DESCRIPTION
        "The name of the application."
    ::= { clvAppControlEntry 2 }

clvAppCtrlBytesFwd OBJECT-TYPE
    SYNTAX      Counter64
    MAX-ACCESS  read-only
    STATUS      current
    DESCRIPTION
        "Number of bytes forwarded for this application."
    ::= { clvAppControlEntry 3 }

clvAppCtrlPacketsFwd OBJECT-TYPE
    SYNTAX      Counter64
    MAX-ACCESS  read-only
    STATUS      current
    DESCRIPTION
        "Number of packets forwarded for this application."
    ::= { clvAppControlEntry 4 }

clvAppCtrlClassified OBJECT-TYPE
    SYNTAX      Counter64
    MAX-ACCESS  read-only
    STATUS      current
    DESCRIPTION
        "Number of times this application has been classified."
    ::= { clvAppControlEntry 5 }

-- Anti-Spam
clvSpam OBJECT IDENTIFIER
    ::= { clavisterOSStats 16 }

clvSpamTotal OBJECT IDENTIFIER
    ::= { clvSpam 1 }

clvSpamIMAP OBJECT IDENTIFIER
    ::= { clvSpam 2 }

clvSpamPOP3 OBJECT IDENTIFIER
    ::= { clvSpam 3 }

clvSpamSMTP OBJECT IDENTIFIER
    ::= { clvSpam 4 }

-- Start of SpamTotal
clvSpamTotalScanned OBJECT-TYPE
    SYNTAX      Counter32
    MAX-ACCESS  read-only
    STATUS      current
    DESCRIPTION
        "Number of scanned emails."
    ::= { clvSpamTotal 2 }

clvSpamTotalSpam OBJECT-TYPE
    SYNTAX      Counter32
    MAX-ACCESS  read-only
    STATUS      current
    DESCRIPTION
        "Number of spam emails."
    ::= { clvSpamTotal 3 }

clvSpamTotalDomainCheck OBJECT-TYPE
    SYNTAX      Counter32
    MAX-ACCESS  read-only
    STATUS      current
    DESCRIPTION
        "Number of performed Domain Verification checks."
    ::= { clvSpamTotal 4 }

clvSpamTotalDomainMatch OBJECT-TYPE
    SYNTAX      Counter32
    MAX-ACCESS  read-only
    STATUS      current
    DESCRIPTION
        "Number of emails with forged reply-to domains."
    ::= { clvSpamTotal 5 }

clvSpamTotalLinkCheck OBJECT-TYPE
    SYNTAX      Counter32
    MAX-ACCESS  read-only
    STATUS      current
    DESCRIPTION
        "Number of emails inspected for undesirable links."
    ::= { clvSpamTotal 6 }

clvSpamTotalLinkMatch OBJECT-TYPE
    SYNTAX      Counter32
    MAX-ACCESS  read-only
    STATUS      current
    DESCRIPTION
        "Number of emails containing undesirable links."
    ::= { clvSpamTotal 7 }

clvSpamTotalLinkCount OBJECT-TYPE
    SYNTAX      Counter32
    MAX-ACCESS  read-only
    STATUS      current
    DESCRIPTION
        "Number of undesirable links found."
    ::= { clvSpamTotal 8 }

clvSpamTotalDNSBLCheck OBJECT-TYPE
    SYNTAX      Counter32
    MAX-ACCESS  read-only
    STATUS      current
    DESCRIPTION
        "Number of performed DNSBL checks."
    ::= { clvSpamTotal 9 }

clvSpamTotalDNSBLMatch OBJECT-TYPE
    SYNTAX      Counter32
    MAX-ACCESS  read-only
    STATUS      current
    DESCRIPTION
        "Number of emails from a blacklisted address."
    ::= { clvSpamTotal 10 }

clvSpamTotalDCCCheck OBJECT-TYPE
    SYNTAX      Counter32
    MAX-ACCESS  read-only
    STATUS      current
    DESCRIPTION
        "Number of performed DCC checks."
    ::= { clvSpamTotal 11 }

clvSpamTotalDCCMatch OBJECT-TYPE
    SYNTAX      Counter32
    MAX-ACCESS  read-only
    STATUS      current
    DESCRIPTION
        "Number of emails considered bulk by DCC."
    ::= { clvSpamTotal 12 }

clvSpamTotalProfileTable OBJECT-TYPE
    SYNTAX      SEQUENCE OF ClvSpamTotalProfileEntry
    MAX-ACCESS  not-accessible
    STATUS      current
    DESCRIPTION
        "A list of Email Profiles with Anti-Spam related statistics for each."
    ::= { clvSpamTotal 1 }

clvSpamTotalProfileEntry OBJECT-TYPE
    SYNTAX      ClvSpamTotalProfileEntry
    MAX-ACCESS  not-accessible
    STATUS      current
    DESCRIPTION
        "An entry in a list of Email Profiles."
    INDEX       { clvSpamTotalProfileIndex }
    ::= { clvSpamTotalProfileTable 1 }

ClvSpamTotalProfileEntry ::= SEQUENCE {
    clvSpamTotalProfileIndex         Integer32,
    clvSpamTotalProfileName          DisplayString,
    clvSpamTotalProfileScanned       Counter32,
    clvSpamTotalProfileSpam          Counter32,
    clvSpamTotalProfileDomainCheck   Counter32,
    clvSpamTotalProfileDomainMatch   Counter32,
    clvSpamTotalProfileLinkCheck     Counter32,
    clvSpamTotalProfileLinkMatch     Counter32,
    clvSpamTotalProfileLinkCount     Counter32,
    clvSpamTotalProfileDNSBLCheck    Counter32,
    clvSpamTotalProfileDNSBLMatch    Counter32,
    clvSpamTotalProfileDNSBL1Check   Counter32,
    clvSpamTotalProfileDNSBL1Match   Counter32,
    clvSpamTotalProfileDNSBL2Check   Counter32,
    clvSpamTotalProfileDNSBL2Match   Counter32,
    clvSpamTotalProfileDNSBL3Check   Counter32,
    clvSpamTotalProfileDNSBL3Match   Counter32,
    clvSpamTotalProfileDNSBL4Check   Counter32,
    clvSpamTotalProfileDNSBL4Match   Counter32,
    clvSpamTotalProfileDNSBL5Check   Counter32,
    clvSpamTotalProfileDNSBL5Match   Counter32,
    clvSpamTotalProfileDNSBL6Check   Counter32,
    clvSpamTotalProfileDNSBL6Match   Counter32,
    clvSpamTotalProfileDNSBL7Check   Counter32,
    clvSpamTotalProfileDNSBL7Match   Counter32,
    clvSpamTotalProfileDNSBL8Check   Counter32,
    clvSpamTotalProfileDNSBL8Match   Counter32,
    clvSpamTotalProfileDNSBL9Check   Counter32,
    clvSpamTotalProfileDNSBL9Match   Counter32,
    clvSpamTotalProfileDNSBL10Check  Counter32,
    clvSpamTotalProfileDNSBL10Match  Counter32,
    clvSpamTotalProfileDCCCheck      Counter32,
    clvSpamTotalProfileDCCMatch      Counter32
}

clvSpamTotalProfileIndex OBJECT-TYPE
    SYNTAX      Integer32 (1..2147483647)
    MAX-ACCESS  not-accessible
    STATUS      current
    DESCRIPTION
        "Index of an entry in clvSpamTotalProfileTable"
    ::= { clvSpamTotalProfileEntry 1 }

clvSpamTotalProfileName OBJECT-TYPE
    SYNTAX      DisplayString
    MAX-ACCESS  read-only
    STATUS      current
    DESCRIPTION
        "The name of the Email Profile."
    ::= { clvSpamTotalProfileEntry 2 }

clvSpamTotalProfileScanned OBJECT-TYPE
    SYNTAX      Counter32
    MAX-ACCESS  read-only
    STATUS      current
    DESCRIPTION
        "Number of scanned emails."
    ::= { clvSpamTotalProfileEntry 3 }

clvSpamTotalProfileSpam OBJECT-TYPE
    SYNTAX      Counter32
    MAX-ACCESS  read-only
    STATUS      current
    DESCRIPTION
        "Number of spam emails."
    ::= { clvSpamTotalProfileEntry 4 }

clvSpamTotalProfileDomainCheck OBJECT-TYPE
    SYNTAX      Counter32
    MAX-ACCESS  read-only
    STATUS      current
    DESCRIPTION
        "Number of performed Domain Verification checks."
    ::= { clvSpamTotalProfileEntry 5 }

clvSpamTotalProfileDomainMatch OBJECT-TYPE
    SYNTAX      Counter32
    MAX-ACCESS  read-only
    STATUS      current
    DESCRIPTION
        "Number of emails with forged reply-to domains."
    ::= { clvSpamTotalProfileEntry 6 }

clvSpamTotalProfileLinkCheck OBJECT-TYPE
    SYNTAX      Counter32
    MAX-ACCESS  read-only
    STATUS      current
    DESCRIPTION
        "Number of emails inspected for undesirable links."
    ::= { clvSpamTotalProfileEntry 7 }

clvSpamTotalProfileLinkMatch OBJECT-TYPE
    SYNTAX      Counter32
    MAX-ACCESS  read-only
    STATUS      current
    DESCRIPTION
        "Number of emails containing undesirable links."
    ::= { clvSpamTotalProfileEntry 8 }

clvSpamTotalProfileLinkCount OBJECT-TYPE
    SYNTAX      Counter32
    MAX-ACCESS  read-only
    STATUS      current
    DESCRIPTION
        "Number of undesirable links found."
    ::= { clvSpamTotalProfileEntry 9 }

clvSpamTotalProfileDNSBLCheck OBJECT-TYPE
    SYNTAX      Counter32
    MAX-ACCESS  read-only
    STATUS      current
    DESCRIPTION
        "Number of performed DNSBL checks."
    ::= { clvSpamTotalProfileEntry 10 }

clvSpamTotalProfileDNSBLMatch OBJECT-TYPE
    SYNTAX      Counter32
    MAX-ACCESS  read-only
    STATUS      current
    DESCRIPTION
        "Number of emails from a blacklisted address."
    ::= { clvSpamTotalProfileEntry 11 }

clvSpamTotalProfileDNSBL1Check OBJECT-TYPE
    SYNTAX      Counter32
    MAX-ACCESS  read-only
    STATUS      current
    DESCRIPTION
        "Number of performed DNSBL checks."
    ::= { clvSpamTotalProfileEntry 12 }

clvSpamTotalProfileDNSBL1Match OBJECT-TYPE
    SYNTAX      Counter32
    MAX-ACCESS  read-only
    STATUS      current
    DESCRIPTION
        "Number of emails from a blacklisted address."
    ::= { clvSpamTotalProfileEntry 13 }

clvSpamTotalProfileDNSBL2Check OBJECT-TYPE
    SYNTAX      Counter32
    MAX-ACCESS  read-only
    STATUS      current
    DESCRIPTION
        "Number of performed DNSBL checks."
    ::= { clvSpamTotalProfileEntry 14 }

clvSpamTotalProfileDNSBL2Match OBJECT-TYPE
    SYNTAX      Counter32
    MAX-ACCESS  read-only
    STATUS      current
    DESCRIPTION
        "Number of emails from a blacklisted address."
    ::= { clvSpamTotalProfileEntry 15 }

clvSpamTotalProfileDNSBL3Check OBJECT-TYPE
    SYNTAX      Counter32
    MAX-ACCESS  read-only
    STATUS      current
    DESCRIPTION
        "Number of performed DNSBL checks."
    ::= { clvSpamTotalProfileEntry 16 }

clvSpamTotalProfileDNSBL3Match OBJECT-TYPE
    SYNTAX      Counter32
    MAX-ACCESS  read-only
    STATUS      current
    DESCRIPTION
        "Number of emails from a blacklisted address."
    ::= { clvSpamTotalProfileEntry 17 }

clvSpamTotalProfileDNSBL4Check OBJECT-TYPE
    SYNTAX      Counter32
    MAX-ACCESS  read-only
    STATUS      current
    DESCRIPTION
        "Number of performed DNSBL checks."
    ::= { clvSpamTotalProfileEntry 18 }

clvSpamTotalProfileDNSBL4Match OBJECT-TYPE
    SYNTAX      Counter32
    MAX-ACCESS  read-only
    STATUS      current
    DESCRIPTION
        "Number of emails from a blacklisted address."
    ::= { clvSpamTotalProfileEntry 19 }

clvSpamTotalProfileDNSBL5Check OBJECT-TYPE
    SYNTAX      Counter32
    MAX-ACCESS  read-only
    STATUS      current
    DESCRIPTION
        "Number of performed DNSBL checks."
    ::= { clvSpamTotalProfileEntry 20 }

clvSpamTotalProfileDNSBL5Match OBJECT-TYPE
    SYNTAX      Counter32
    MAX-ACCESS  read-only
    STATUS      current
    DESCRIPTION
        "Number of emails from a blacklisted address."
    ::= { clvSpamTotalProfileEntry 21 }

clvSpamTotalProfileDNSBL6Check OBJECT-TYPE
    SYNTAX      Counter32
    MAX-ACCESS  read-only
    STATUS      current
    DESCRIPTION
        "Number of performed DNSBL checks."
    ::= { clvSpamTotalProfileEntry 22 }

clvSpamTotalProfileDNSBL6Match OBJECT-TYPE
    SYNTAX      Counter32
    MAX-ACCESS  read-only
    STATUS      current
    DESCRIPTION
        "Number of emails from a blacklisted address."
    ::= { clvSpamTotalProfileEntry 23 }

clvSpamTotalProfileDNSBL7Check OBJECT-TYPE
    SYNTAX      Counter32
    MAX-ACCESS  read-only
    STATUS      current
    DESCRIPTION
        "Number of performed DNSBL checks."
    ::= { clvSpamTotalProfileEntry 24 }

clvSpamTotalProfileDNSBL7Match OBJECT-TYPE
    SYNTAX      Counter32
    MAX-ACCESS  read-only
    STATUS      current
    DESCRIPTION
        "Number of emails from a blacklisted address."
    ::= { clvSpamTotalProfileEntry 25 }

clvSpamTotalProfileDNSBL8Check OBJECT-TYPE
    SYNTAX      Counter32
    MAX-ACCESS  read-only
    STATUS      current
    DESCRIPTION
        "Number of performed DNSBL checks."
    ::= { clvSpamTotalProfileEntry 26 }

clvSpamTotalProfileDNSBL8Match OBJECT-TYPE
    SYNTAX      Counter32
    MAX-ACCESS  read-only
    STATUS      current
    DESCRIPTION
        "Number of emails from a blacklisted address."
    ::= { clvSpamTotalProfileEntry 27 }

clvSpamTotalProfileDNSBL9Check OBJECT-TYPE
    SYNTAX      Counter32
    MAX-ACCESS  read-only
    STATUS      current
    DESCRIPTION
        "Number of performed DNSBL checks."
    ::= { clvSpamTotalProfileEntry 28 }

clvSpamTotalProfileDNSBL9Match OBJECT-TYPE
    SYNTAX      Counter32
    MAX-ACCESS  read-only
    STATUS      current
    DESCRIPTION
        "Number of emails from a blacklisted address."
    ::= { clvSpamTotalProfileEntry 29 }

clvSpamTotalProfileDNSBL10Check OBJECT-TYPE
    SYNTAX      Counter32
    MAX-ACCESS  read-only
    STATUS      current
    DESCRIPTION
        "Number of performed DNSBL checks."
    ::= { clvSpamTotalProfileEntry 30 }

clvSpamTotalProfileDNSBL10Match OBJECT-TYPE
    SYNTAX      Counter32
    MAX-ACCESS  read-only
    STATUS      current
    DESCRIPTION
        "Number of emails from a blacklisted address."
    ::= { clvSpamTotalProfileEntry 31 }

clvSpamTotalProfileDCCCheck OBJECT-TYPE
    SYNTAX      Counter32
    MAX-ACCESS  read-only
    STATUS      current
    DESCRIPTION
        "Number of performed DCC checks."
    ::= { clvSpamTotalProfileEntry 32 }

clvSpamTotalProfileDCCMatch OBJECT-TYPE
    SYNTAX      Counter32
    MAX-ACCESS  read-only
    STATUS      current
    DESCRIPTION
        "Number of emails considered bulk by DCC."
    ::= { clvSpamTotalProfileEntry 33 }
-- End of SpamTotal
-- Start of SpamIMAP
clvSpamIMAPScanned OBJECT-TYPE
    SYNTAX      Counter32
    MAX-ACCESS  read-only
    STATUS      current
    DESCRIPTION
        "Number of scanned emails."
    ::= { clvSpamIMAP 2 }

clvSpamIMAPSpam OBJECT-TYPE
    SYNTAX      Counter32
    MAX-ACCESS  read-only
    STATUS      current
    DESCRIPTION
        "Number of spam emails."
    ::= { clvSpamIMAP 3 }

clvSpamIMAPDomainCheck OBJECT-TYPE
    SYNTAX      Counter32
    MAX-ACCESS  read-only
    STATUS      current
    DESCRIPTION
        "Number of performed Domain Verification checks."
    ::= { clvSpamIMAP 4 }

clvSpamIMAPDomainMatch OBJECT-TYPE
    SYNTAX      Counter32
    MAX-ACCESS  read-only
    STATUS      current
    DESCRIPTION
        "Number of emails with forged reply-to domains."
    ::= { clvSpamIMAP 5 }

clvSpamIMAPLinkCheck OBJECT-TYPE
    SYNTAX      Counter32
    MAX-ACCESS  read-only
    STATUS      current
    DESCRIPTION
        "Number of emails inspected for undesirable links."
    ::= { clvSpamIMAP 6 }

clvSpamIMAPLinkMatch OBJECT-TYPE
    SYNTAX      Counter32
    MAX-ACCESS  read-only
    STATUS      current
    DESCRIPTION
        "Number of emails containing undesirable links."
    ::= { clvSpamIMAP 7 }

clvSpamIMAPLinkCount OBJECT-TYPE
    SYNTAX      Counter32
    MAX-ACCESS  read-only
    STATUS      current
    DESCRIPTION
        "Number of undesirable links found."
    ::= { clvSpamIMAP 8 }

clvSpamIMAPDNSBLCheck OBJECT-TYPE
    SYNTAX      Counter32
    MAX-ACCESS  read-only
    STATUS      current
    DESCRIPTION
        "Number of performed DNSBL checks."
    ::= { clvSpamIMAP 9 }

clvSpamIMAPDNSBLMatch OBJECT-TYPE
    SYNTAX      Counter32
    MAX-ACCESS  read-only
    STATUS      current
    DESCRIPTION
        "Number of emails from a blacklisted address."
    ::= { clvSpamIMAP 10 }

clvSpamIMAPDCCCheck OBJECT-TYPE
    SYNTAX      Counter32
    MAX-ACCESS  read-only
    STATUS      current
    DESCRIPTION
        "Number of performed DCC checks."
    ::= { clvSpamIMAP 11 }

clvSpamIMAPDCCMatch OBJECT-TYPE
    SYNTAX      Counter32
    MAX-ACCESS  read-only
    STATUS      current
    DESCRIPTION
        "Number of emails considered bulk by DCC."
    ::= { clvSpamIMAP 12 }

clvSpamIMAPProfileTable OBJECT-TYPE
    SYNTAX      SEQUENCE OF ClvSpamIMAPProfileEntry
    MAX-ACCESS  not-accessible
    STATUS      current
    DESCRIPTION
        "A list of Email Profiles with Anti-Spam related statistics for each."
    ::= { clvSpamIMAP 1 }

clvSpamIMAPProfileEntry OBJECT-TYPE
    SYNTAX      ClvSpamIMAPProfileEntry
    MAX-ACCESS  not-accessible
    STATUS      current
    DESCRIPTION
        "An entry in a list of Email Profiles."
    INDEX       { clvSpamIMAPProfileIndex }
    ::= { clvSpamIMAPProfileTable 1 }

ClvSpamIMAPProfileEntry ::= SEQUENCE {
    clvSpamIMAPProfileIndex         Integer32,
    clvSpamIMAPProfileName          DisplayString,
    clvSpamIMAPProfileScanned       Counter32,
    clvSpamIMAPProfileSpam          Counter32,
    clvSpamIMAPProfileDomainCheck   Counter32,
    clvSpamIMAPProfileDomainMatch   Counter32,
    clvSpamIMAPProfileLinkCheck     Counter32,
    clvSpamIMAPProfileLinkMatch     Counter32,
    clvSpamIMAPProfileLinkCount     Counter32,
    clvSpamIMAPProfileDNSBLCheck    Counter32,
    clvSpamIMAPProfileDNSBLMatch    Counter32,
    clvSpamIMAPProfileDNSBL1Check   Counter32,
    clvSpamIMAPProfileDNSBL1Match   Counter32,
    clvSpamIMAPProfileDNSBL2Check   Counter32,
    clvSpamIMAPProfileDNSBL2Match   Counter32,
    clvSpamIMAPProfileDNSBL3Check   Counter32,
    clvSpamIMAPProfileDNSBL3Match   Counter32,
    clvSpamIMAPProfileDNSBL4Check   Counter32,
    clvSpamIMAPProfileDNSBL4Match   Counter32,
    clvSpamIMAPProfileDNSBL5Check   Counter32,
    clvSpamIMAPProfileDNSBL5Match   Counter32,
    clvSpamIMAPProfileDNSBL6Check   Counter32,
    clvSpamIMAPProfileDNSBL6Match   Counter32,
    clvSpamIMAPProfileDNSBL7Check   Counter32,
    clvSpamIMAPProfileDNSBL7Match   Counter32,
    clvSpamIMAPProfileDNSBL8Check   Counter32,
    clvSpamIMAPProfileDNSBL8Match   Counter32,
    clvSpamIMAPProfileDNSBL9Check   Counter32,
    clvSpamIMAPProfileDNSBL9Match   Counter32,
    clvSpamIMAPProfileDNSBL10Check  Counter32,
    clvSpamIMAPProfileDNSBL10Match  Counter32,
    clvSpamIMAPProfileDCCCheck      Counter32,
    clvSpamIMAPProfileDCCMatch      Counter32
}

clvSpamIMAPProfileIndex OBJECT-TYPE
    SYNTAX      Integer32 (1..2147483647)
    MAX-ACCESS  not-accessible
    STATUS      current
    DESCRIPTION
        "Index of an entry in clvSpamIMAPProfileTable"
    ::= { clvSpamIMAPProfileEntry 1 }

clvSpamIMAPProfileName OBJECT-TYPE
    SYNTAX      DisplayString
    MAX-ACCESS  read-only
    STATUS      current
    DESCRIPTION
        "The name of the Email Profile."
    ::= { clvSpamIMAPProfileEntry 2 }

clvSpamIMAPProfileScanned OBJECT-TYPE
    SYNTAX      Counter32
    MAX-ACCESS  read-only
    STATUS      current
    DESCRIPTION
        "Number of scanned emails."
    ::= { clvSpamIMAPProfileEntry 3 }

clvSpamIMAPProfileSpam OBJECT-TYPE
    SYNTAX      Counter32
    MAX-ACCESS  read-only
    STATUS      current
    DESCRIPTION
        "Number of spam emails."
    ::= { clvSpamIMAPProfileEntry 4 }

clvSpamIMAPProfileDomainCheck OBJECT-TYPE
    SYNTAX      Counter32
    MAX-ACCESS  read-only
    STATUS      current
    DESCRIPTION
        "Number of performed Domain Verification checks."
    ::= { clvSpamIMAPProfileEntry 5 }

clvSpamIMAPProfileDomainMatch OBJECT-TYPE
    SYNTAX      Counter32
    MAX-ACCESS  read-only
    STATUS      current
    DESCRIPTION
        "Number of emails with forged reply-to domains."
    ::= { clvSpamIMAPProfileEntry 6 }

clvSpamIMAPProfileLinkCheck OBJECT-TYPE
    SYNTAX      Counter32
    MAX-ACCESS  read-only
    STATUS      current
    DESCRIPTION
        "Number of emails inspected for undesirable links."
    ::= { clvSpamIMAPProfileEntry 7 }

clvSpamIMAPProfileLinkMatch OBJECT-TYPE
    SYNTAX      Counter32
    MAX-ACCESS  read-only
    STATUS      current
    DESCRIPTION
        "Number of emails containing undesirable links."
    ::= { clvSpamIMAPProfileEntry 8 }

clvSpamIMAPProfileLinkCount OBJECT-TYPE
    SYNTAX      Counter32
    MAX-ACCESS  read-only
    STATUS      current
    DESCRIPTION
        "Number of undesirable links found."
    ::= { clvSpamIMAPProfileEntry 9 }

clvSpamIMAPProfileDNSBLCheck OBJECT-TYPE
    SYNTAX      Counter32
    MAX-ACCESS  read-only
    STATUS      current
    DESCRIPTION
        "Number of performed DNSBL checks."
    ::= { clvSpamIMAPProfileEntry 10 }

clvSpamIMAPProfileDNSBLMatch OBJECT-TYPE
    SYNTAX      Counter32
    MAX-ACCESS  read-only
    STATUS      current
    DESCRIPTION
        "Number of emails from a blacklisted address."
    ::= { clvSpamIMAPProfileEntry 11 }

clvSpamIMAPProfileDNSBL1Check OBJECT-TYPE
    SYNTAX      Counter32
    MAX-ACCESS  read-only
    STATUS      current
    DESCRIPTION
        "Number of performed DNSBL checks."
    ::= { clvSpamIMAPProfileEntry 12 }

clvSpamIMAPProfileDNSBL1Match OBJECT-TYPE
    SYNTAX      Counter32
    MAX-ACCESS  read-only
    STATUS      current
    DESCRIPTION
        "Number of emails from a blacklisted address."
    ::= { clvSpamIMAPProfileEntry 13 }

clvSpamIMAPProfileDNSBL2Check OBJECT-TYPE
    SYNTAX      Counter32
    MAX-ACCESS  read-only
    STATUS      current
    DESCRIPTION
        "Number of performed DNSBL checks."
    ::= { clvSpamIMAPProfileEntry 14 }

clvSpamIMAPProfileDNSBL2Match OBJECT-TYPE
    SYNTAX      Counter32
    MAX-ACCESS  read-only
    STATUS      current
    DESCRIPTION
        "Number of emails from a blacklisted address."
    ::= { clvSpamIMAPProfileEntry 15 }

clvSpamIMAPProfileDNSBL3Check OBJECT-TYPE
    SYNTAX      Counter32
    MAX-ACCESS  read-only
    STATUS      current
    DESCRIPTION
        "Number of performed DNSBL checks."
    ::= { clvSpamIMAPProfileEntry 16 }

clvSpamIMAPProfileDNSBL3Match OBJECT-TYPE
    SYNTAX      Counter32
    MAX-ACCESS  read-only
    STATUS      current
    DESCRIPTION
        "Number of emails from a blacklisted address."
    ::= { clvSpamIMAPProfileEntry 17 }

clvSpamIMAPProfileDNSBL4Check OBJECT-TYPE
    SYNTAX      Counter32
    MAX-ACCESS  read-only
    STATUS      current
    DESCRIPTION
        "Number of performed DNSBL checks."
    ::= { clvSpamIMAPProfileEntry 18 }

clvSpamIMAPProfileDNSBL4Match OBJECT-TYPE
    SYNTAX      Counter32
    MAX-ACCESS  read-only
    STATUS      current
    DESCRIPTION
        "Number of emails from a blacklisted address."
    ::= { clvSpamIMAPProfileEntry 19 }

clvSpamIMAPProfileDNSBL5Check OBJECT-TYPE
    SYNTAX      Counter32
    MAX-ACCESS  read-only
    STATUS      current
    DESCRIPTION
        "Number of performed DNSBL checks."
    ::= { clvSpamIMAPProfileEntry 20 }

clvSpamIMAPProfileDNSBL5Match OBJECT-TYPE
    SYNTAX      Counter32
    MAX-ACCESS  read-only
    STATUS      current
    DESCRIPTION
        "Number of emails from a blacklisted address."
    ::= { clvSpamIMAPProfileEntry 21 }

clvSpamIMAPProfileDNSBL6Check OBJECT-TYPE
    SYNTAX      Counter32
    MAX-ACCESS  read-only
    STATUS      current
    DESCRIPTION
        "Number of performed DNSBL checks."
    ::= { clvSpamIMAPProfileEntry 22 }

clvSpamIMAPProfileDNSBL6Match OBJECT-TYPE
    SYNTAX      Counter32
    MAX-ACCESS  read-only
    STATUS      current
    DESCRIPTION
        "Number of emails from a blacklisted address."
    ::= { clvSpamIMAPProfileEntry 23 }

clvSpamIMAPProfileDNSBL7Check OBJECT-TYPE
    SYNTAX      Counter32
    MAX-ACCESS  read-only
    STATUS      current
    DESCRIPTION
        "Number of performed DNSBL checks."
    ::= { clvSpamIMAPProfileEntry 24 }

clvSpamIMAPProfileDNSBL7Match OBJECT-TYPE
    SYNTAX      Counter32
    MAX-ACCESS  read-only
    STATUS      current
    DESCRIPTION
        "Number of emails from a blacklisted address."
    ::= { clvSpamIMAPProfileEntry 25 }

clvSpamIMAPProfileDNSBL8Check OBJECT-TYPE
    SYNTAX      Counter32
    MAX-ACCESS  read-only
    STATUS      current
    DESCRIPTION
        "Number of performed DNSBL checks."
    ::= { clvSpamIMAPProfileEntry 26 }

clvSpamIMAPProfileDNSBL8Match OBJECT-TYPE
    SYNTAX      Counter32
    MAX-ACCESS  read-only
    STATUS      current
    DESCRIPTION
        "Number of emails from a blacklisted address."
    ::= { clvSpamIMAPProfileEntry 27 }

clvSpamIMAPProfileDNSBL9Check OBJECT-TYPE
    SYNTAX      Counter32
    MAX-ACCESS  read-only
    STATUS      current
    DESCRIPTION
        "Number of performed DNSBL checks."
    ::= { clvSpamIMAPProfileEntry 28 }

clvSpamIMAPProfileDNSBL9Match OBJECT-TYPE
    SYNTAX      Counter32
    MAX-ACCESS  read-only
    STATUS      current
    DESCRIPTION
        "Number of emails from a blacklisted address."
    ::= { clvSpamIMAPProfileEntry 29 }

clvSpamIMAPProfileDNSBL10Check OBJECT-TYPE
    SYNTAX      Counter32
    MAX-ACCESS  read-only
    STATUS      current
    DESCRIPTION
        "Number of performed DNSBL checks."
    ::= { clvSpamIMAPProfileEntry 30 }

clvSpamIMAPProfileDNSBL10Match OBJECT-TYPE
    SYNTAX      Counter32
    MAX-ACCESS  read-only
    STATUS      current
    DESCRIPTION
        "Number of emails from a blacklisted address."
    ::= { clvSpamIMAPProfileEntry 31 }

clvSpamIMAPProfileDCCCheck OBJECT-TYPE
    SYNTAX      Counter32
    MAX-ACCESS  read-only
    STATUS      current
    DESCRIPTION
        "Number of performed DCC checks."
    ::= { clvSpamIMAPProfileEntry 32 }

clvSpamIMAPProfileDCCMatch OBJECT-TYPE
    SYNTAX      Counter32
    MAX-ACCESS  read-only
    STATUS      current
    DESCRIPTION
        "Number of emails considered bulk by DCC."
    ::= { clvSpamIMAPProfileEntry 33 }
-- End of SpamIMAP
-- Start of SpamPOP3
clvSpamPOP3Scanned OBJECT-TYPE
    SYNTAX      Counter32
    MAX-ACCESS  read-only
    STATUS      current
    DESCRIPTION
        "Number of scanned emails."
    ::= { clvSpamPOP3 2 }

clvSpamPOP3Spam OBJECT-TYPE
    SYNTAX      Counter32
    MAX-ACCESS  read-only
    STATUS      current
    DESCRIPTION
        "Number of spam emails."
    ::= { clvSpamPOP3 3 }

clvSpamPOP3DomainCheck OBJECT-TYPE
    SYNTAX      Counter32
    MAX-ACCESS  read-only
    STATUS      current
    DESCRIPTION
        "Number of performed Domain Verification checks."
    ::= { clvSpamPOP3 4 }

clvSpamPOP3DomainMatch OBJECT-TYPE
    SYNTAX      Counter32
    MAX-ACCESS  read-only
    STATUS      current
    DESCRIPTION
        "Number of emails with forged reply-to domains."
    ::= { clvSpamPOP3 5 }

clvSpamPOP3LinkCheck OBJECT-TYPE
    SYNTAX      Counter32
    MAX-ACCESS  read-only
    STATUS      current
    DESCRIPTION
        "Number of emails inspected for undesirable links."
    ::= { clvSpamPOP3 6 }

clvSpamPOP3LinkMatch OBJECT-TYPE
    SYNTAX      Counter32
    MAX-ACCESS  read-only
    STATUS      current
    DESCRIPTION
        "Number of emails containing undesirable links."
    ::= { clvSpamPOP3 7 }

clvSpamPOP3LinkCount OBJECT-TYPE
    SYNTAX      Counter32
    MAX-ACCESS  read-only
    STATUS      current
    DESCRIPTION
        "Number of undesirable links found."
    ::= { clvSpamPOP3 8 }

clvSpamPOP3DNSBLCheck OBJECT-TYPE
    SYNTAX      Counter32
    MAX-ACCESS  read-only
    STATUS      current
    DESCRIPTION
        "Number of performed DNSBL checks."
    ::= { clvSpamPOP3 9 }

clvSpamPOP3DNSBLMatch OBJECT-TYPE
    SYNTAX      Counter32
    MAX-ACCESS  read-only
    STATUS      current
    DESCRIPTION
        "Number of emails from a blacklisted address."
    ::= { clvSpamPOP3 10 }

clvSpamPOP3DCCCheck OBJECT-TYPE
    SYNTAX      Counter32
    MAX-ACCESS  read-only
    STATUS      current
    DESCRIPTION
        "Number of performed DCC checks."
    ::= { clvSpamPOP3 11 }

clvSpamPOP3DCCMatch OBJECT-TYPE
    SYNTAX      Counter32
    MAX-ACCESS  read-only
    STATUS      current
    DESCRIPTION
        "Number of emails considered bulk by DCC."
    ::= { clvSpamPOP3 12 }

clvSpamPOP3ProfileTable OBJECT-TYPE
    SYNTAX      SEQUENCE OF ClvSpamPOP3ProfileEntry
    MAX-ACCESS  not-accessible
    STATUS      current
    DESCRIPTION
        "A list of Email Profiles with Anti-Spam related statistics for each."
    ::= { clvSpamPOP3 1 }

clvSpamPOP3ProfileEntry OBJECT-TYPE
    SYNTAX      ClvSpamPOP3ProfileEntry
    MAX-ACCESS  not-accessible
    STATUS      current
    DESCRIPTION
        "An entry in a list of Email Profiles."
    INDEX       { clvSpamPOP3ProfileIndex }
    ::= { clvSpamPOP3ProfileTable 1 }

ClvSpamPOP3ProfileEntry ::= SEQUENCE {
    clvSpamPOP3ProfileIndex         Integer32,
    clvSpamPOP3ProfileName          DisplayString,
    clvSpamPOP3ProfileScanned       Counter32,
    clvSpamPOP3ProfileSpam          Counter32,
    clvSpamPOP3ProfileDomainCheck   Counter32,
    clvSpamPOP3ProfileDomainMatch   Counter32,
    clvSpamPOP3ProfileLinkCheck     Counter32,
    clvSpamPOP3ProfileLinkMatch     Counter32,
    clvSpamPOP3ProfileLinkCount     Counter32,
    clvSpamPOP3ProfileDNSBLCheck    Counter32,
    clvSpamPOP3ProfileDNSBLMatch    Counter32,
    clvSpamPOP3ProfileDNSBL1Check   Counter32,
    clvSpamPOP3ProfileDNSBL1Match   Counter32,
    clvSpamPOP3ProfileDNSBL2Check   Counter32,
    clvSpamPOP3ProfileDNSBL2Match   Counter32,
    clvSpamPOP3ProfileDNSBL3Check   Counter32,
    clvSpamPOP3ProfileDNSBL3Match   Counter32,
    clvSpamPOP3ProfileDNSBL4Check   Counter32,
    clvSpamPOP3ProfileDNSBL4Match   Counter32,
    clvSpamPOP3ProfileDNSBL5Check   Counter32,
    clvSpamPOP3ProfileDNSBL5Match   Counter32,
    clvSpamPOP3ProfileDNSBL6Check   Counter32,
    clvSpamPOP3ProfileDNSBL6Match   Counter32,
    clvSpamPOP3ProfileDNSBL7Check   Counter32,
    clvSpamPOP3ProfileDNSBL7Match   Counter32,
    clvSpamPOP3ProfileDNSBL8Check   Counter32,
    clvSpamPOP3ProfileDNSBL8Match   Counter32,
    clvSpamPOP3ProfileDNSBL9Check   Counter32,
    clvSpamPOP3ProfileDNSBL9Match   Counter32,
    clvSpamPOP3ProfileDNSBL10Check  Counter32,
    clvSpamPOP3ProfileDNSBL10Match  Counter32,
    clvSpamPOP3ProfileDCCCheck      Counter32,
    clvSpamPOP3ProfileDCCMatch      Counter32
}

clvSpamPOP3ProfileIndex OBJECT-TYPE
    SYNTAX      Integer32 (1..2147483647)
    MAX-ACCESS  not-accessible
    STATUS      current
    DESCRIPTION
        "Index of an entry in clvSpamPOP3ProfileTable"
    ::= { clvSpamPOP3ProfileEntry 1 }

clvSpamPOP3ProfileName OBJECT-TYPE
    SYNTAX      DisplayString
    MAX-ACCESS  read-only
    STATUS      current
    DESCRIPTION
        "The name of the Email Profile."
    ::= { clvSpamPOP3ProfileEntry 2 }

clvSpamPOP3ProfileScanned OBJECT-TYPE
    SYNTAX      Counter32
    MAX-ACCESS  read-only
    STATUS      current
    DESCRIPTION
        "Number of scanned emails."
    ::= { clvSpamPOP3ProfileEntry 3 }

clvSpamPOP3ProfileSpam OBJECT-TYPE
    SYNTAX      Counter32
    MAX-ACCESS  read-only
    STATUS      current
    DESCRIPTION
        "Number of spam emails."
    ::= { clvSpamPOP3ProfileEntry 4 }

clvSpamPOP3ProfileDomainCheck OBJECT-TYPE
    SYNTAX      Counter32
    MAX-ACCESS  read-only
    STATUS      current
    DESCRIPTION
        "Number of performed Domain Verification checks."
    ::= { clvSpamPOP3ProfileEntry 5 }

clvSpamPOP3ProfileDomainMatch OBJECT-TYPE
    SYNTAX      Counter32
    MAX-ACCESS  read-only
    STATUS      current
    DESCRIPTION
        "Number of emails with forged reply-to domains."
    ::= { clvSpamPOP3ProfileEntry 6 }

clvSpamPOP3ProfileLinkCheck OBJECT-TYPE
    SYNTAX      Counter32
    MAX-ACCESS  read-only
    STATUS      current
    DESCRIPTION
        "Number of emails inspected for undesirable links."
    ::= { clvSpamPOP3ProfileEntry 7 }

clvSpamPOP3ProfileLinkMatch OBJECT-TYPE
    SYNTAX      Counter32
    MAX-ACCESS  read-only
    STATUS      current
    DESCRIPTION
        "Number of emails containing undesirable links."
    ::= { clvSpamPOP3ProfileEntry 8 }

clvSpamPOP3ProfileLinkCount OBJECT-TYPE
    SYNTAX      Counter32
    MAX-ACCESS  read-only
    STATUS      current
    DESCRIPTION
        "Number of undesirable links found."
    ::= { clvSpamPOP3ProfileEntry 9 }

clvSpamPOP3ProfileDNSBLCheck OBJECT-TYPE
    SYNTAX      Counter32
    MAX-ACCESS  read-only
    STATUS      current
    DESCRIPTION
        "Number of performed DNSBL checks."
    ::= { clvSpamPOP3ProfileEntry 10 }

clvSpamPOP3ProfileDNSBLMatch OBJECT-TYPE
    SYNTAX      Counter32
    MAX-ACCESS  read-only
    STATUS      current
    DESCRIPTION
        "Number of emails from a blacklisted address."
    ::= { clvSpamPOP3ProfileEntry 11 }

clvSpamPOP3ProfileDNSBL1Check OBJECT-TYPE
    SYNTAX      Counter32
    MAX-ACCESS  read-only
    STATUS      current
    DESCRIPTION
        "Number of performed DNSBL checks."
    ::= { clvSpamPOP3ProfileEntry 12 }

clvSpamPOP3ProfileDNSBL1Match OBJECT-TYPE
    SYNTAX      Counter32
    MAX-ACCESS  read-only
    STATUS      current
    DESCRIPTION
        "Number of emails from a blacklisted address."
    ::= { clvSpamPOP3ProfileEntry 13 }

clvSpamPOP3ProfileDNSBL2Check OBJECT-TYPE
    SYNTAX      Counter32
    MAX-ACCESS  read-only
    STATUS      current
    DESCRIPTION
        "Number of performed DNSBL checks."
    ::= { clvSpamPOP3ProfileEntry 14 }

clvSpamPOP3ProfileDNSBL2Match OBJECT-TYPE
    SYNTAX      Counter32
    MAX-ACCESS  read-only
    STATUS      current
    DESCRIPTION
        "Number of emails from a blacklisted address."
    ::= { clvSpamPOP3ProfileEntry 15 }

clvSpamPOP3ProfileDNSBL3Check OBJECT-TYPE
    SYNTAX      Counter32
    MAX-ACCESS  read-only
    STATUS      current
    DESCRIPTION
        "Number of performed DNSBL checks."
    ::= { clvSpamPOP3ProfileEntry 16 }

clvSpamPOP3ProfileDNSBL3Match OBJECT-TYPE
    SYNTAX      Counter32
    MAX-ACCESS  read-only
    STATUS      current
    DESCRIPTION
        "Number of emails from a blacklisted address."
    ::= { clvSpamPOP3ProfileEntry 17 }

clvSpamPOP3ProfileDNSBL4Check OBJECT-TYPE
    SYNTAX      Counter32
    MAX-ACCESS  read-only
    STATUS      current
    DESCRIPTION
        "Number of performed DNSBL checks."
    ::= { clvSpamPOP3ProfileEntry 18 }

clvSpamPOP3ProfileDNSBL4Match OBJECT-TYPE
    SYNTAX      Counter32
    MAX-ACCESS  read-only
    STATUS      current
    DESCRIPTION
        "Number of emails from a blacklisted address."
    ::= { clvSpamPOP3ProfileEntry 19 }

clvSpamPOP3ProfileDNSBL5Check OBJECT-TYPE
    SYNTAX      Counter32
    MAX-ACCESS  read-only
    STATUS      current
    DESCRIPTION
        "Number of performed DNSBL checks."
    ::= { clvSpamPOP3ProfileEntry 20 }

clvSpamPOP3ProfileDNSBL5Match OBJECT-TYPE
    SYNTAX      Counter32
    MAX-ACCESS  read-only
    STATUS      current
    DESCRIPTION
        "Number of emails from a blacklisted address."
    ::= { clvSpamPOP3ProfileEntry 21 }

clvSpamPOP3ProfileDNSBL6Check OBJECT-TYPE
    SYNTAX      Counter32
    MAX-ACCESS  read-only
    STATUS      current
    DESCRIPTION
        "Number of performed DNSBL checks."
    ::= { clvSpamPOP3ProfileEntry 22 }

clvSpamPOP3ProfileDNSBL6Match OBJECT-TYPE
    SYNTAX      Counter32
    MAX-ACCESS  read-only
    STATUS      current
    DESCRIPTION
        "Number of emails from a blacklisted address."
    ::= { clvSpamPOP3ProfileEntry 23 }

clvSpamPOP3ProfileDNSBL7Check OBJECT-TYPE
    SYNTAX      Counter32
    MAX-ACCESS  read-only
    STATUS      current
    DESCRIPTION
        "Number of performed DNSBL checks."
    ::= { clvSpamPOP3ProfileEntry 24 }

clvSpamPOP3ProfileDNSBL7Match OBJECT-TYPE
    SYNTAX      Counter32
    MAX-ACCESS  read-only
    STATUS      current
    DESCRIPTION
        "Number of emails from a blacklisted address."
    ::= { clvSpamPOP3ProfileEntry 25 }

clvSpamPOP3ProfileDNSBL8Check OBJECT-TYPE
    SYNTAX      Counter32
    MAX-ACCESS  read-only
    STATUS      current
    DESCRIPTION
        "Number of performed DNSBL checks."
    ::= { clvSpamPOP3ProfileEntry 26 }

clvSpamPOP3ProfileDNSBL8Match OBJECT-TYPE
    SYNTAX      Counter32
    MAX-ACCESS  read-only
    STATUS      current
    DESCRIPTION
        "Number of emails from a blacklisted address."
    ::= { clvSpamPOP3ProfileEntry 27 }

clvSpamPOP3ProfileDNSBL9Check OBJECT-TYPE
    SYNTAX      Counter32
    MAX-ACCESS  read-only
    STATUS      current
    DESCRIPTION
        "Number of performed DNSBL checks."
    ::= { clvSpamPOP3ProfileEntry 28 }

clvSpamPOP3ProfileDNSBL9Match OBJECT-TYPE
    SYNTAX      Counter32
    MAX-ACCESS  read-only
    STATUS      current
    DESCRIPTION
        "Number of emails from a blacklisted address."
    ::= { clvSpamPOP3ProfileEntry 29 }

clvSpamPOP3ProfileDNSBL10Check OBJECT-TYPE
    SYNTAX      Counter32
    MAX-ACCESS  read-only
    STATUS      current
    DESCRIPTION
        "Number of performed DNSBL checks."
    ::= { clvSpamPOP3ProfileEntry 30 }

clvSpamPOP3ProfileDNSBL10Match OBJECT-TYPE
    SYNTAX      Counter32
    MAX-ACCESS  read-only
    STATUS      current
    DESCRIPTION
        "Number of emails from a blacklisted address."
    ::= { clvSpamPOP3ProfileEntry 31 }

clvSpamPOP3ProfileDCCCheck OBJECT-TYPE
    SYNTAX      Counter32
    MAX-ACCESS  read-only
    STATUS      current
    DESCRIPTION
        "Number of performed DCC checks."
    ::= { clvSpamPOP3ProfileEntry 32 }

clvSpamPOP3ProfileDCCMatch OBJECT-TYPE
    SYNTAX      Counter32
    MAX-ACCESS  read-only
    STATUS      current
    DESCRIPTION
        "Number of emails considered bulk by DCC."
    ::= { clvSpamPOP3ProfileEntry 33 }
-- End of SpamPOP3
-- Start of SpamSMTP
clvSpamSMTPScanned OBJECT-TYPE
    SYNTAX      Counter32
    MAX-ACCESS  read-only
    STATUS      current
    DESCRIPTION
        "Number of scanned emails."
    ::= { clvSpamSMTP 2 }

clvSpamSMTPSpam OBJECT-TYPE
    SYNTAX      Counter32
    MAX-ACCESS  read-only
    STATUS      current
    DESCRIPTION
        "Number of spam emails."
    ::= { clvSpamSMTP 3 }

clvSpamSMTPDomainCheck OBJECT-TYPE
    SYNTAX      Counter32
    MAX-ACCESS  read-only
    STATUS      current
    DESCRIPTION
        "Number of performed Domain Verification checks."
    ::= { clvSpamSMTP 4 }

clvSpamSMTPDomainMatch OBJECT-TYPE
    SYNTAX      Counter32
    MAX-ACCESS  read-only
    STATUS      current
    DESCRIPTION
        "Number of emails with forged reply-to domains."
    ::= { clvSpamSMTP 5 }

clvSpamSMTPLinkCheck OBJECT-TYPE
    SYNTAX      Counter32
    MAX-ACCESS  read-only
    STATUS      current
    DESCRIPTION
        "Number of emails inspected for undesirable links."
    ::= { clvSpamSMTP 6 }

clvSpamSMTPLinkMatch OBJECT-TYPE
    SYNTAX      Counter32
    MAX-ACCESS  read-only
    STATUS      current
    DESCRIPTION
        "Number of emails containing undesirable links."
    ::= { clvSpamSMTP 7 }

clvSpamSMTPLinkCount OBJECT-TYPE
    SYNTAX      Counter32
    MAX-ACCESS  read-only
    STATUS      current
    DESCRIPTION
        "Number of undesirable links found."
    ::= { clvSpamSMTP 8 }

clvSpamSMTPDNSBLCheck OBJECT-TYPE
    SYNTAX      Counter32
    MAX-ACCESS  read-only
    STATUS      current
    DESCRIPTION
        "Number of performed DNSBL checks."
    ::= { clvSpamSMTP 9 }

clvSpamSMTPDNSBLMatch OBJECT-TYPE
    SYNTAX      Counter32
    MAX-ACCESS  read-only
    STATUS      current
    DESCRIPTION
        "Number of emails from a blacklisted address."
    ::= { clvSpamSMTP 10 }

clvSpamSMTPDCCCheck OBJECT-TYPE
    SYNTAX      Counter32
    MAX-ACCESS  read-only
    STATUS      current
    DESCRIPTION
        "Number of performed DCC checks."
    ::= { clvSpamSMTP 11 }

clvSpamSMTPDCCMatch OBJECT-TYPE
    SYNTAX      Counter32
    MAX-ACCESS  read-only
    STATUS      current
    DESCRIPTION
        "Number of emails considered bulk by DCC."
    ::= { clvSpamSMTP 12 }

clvSpamSMTPProfileTable OBJECT-TYPE
    SYNTAX      SEQUENCE OF ClvSpamSMTPProfileEntry
    MAX-ACCESS  not-accessible
    STATUS      current
    DESCRIPTION
        "A list of Email Profiles with Anti-Spam related statistics for each."
    ::= { clvSpamSMTP 1 }

clvSpamSMTPProfileEntry OBJECT-TYPE
    SYNTAX      ClvSpamSMTPProfileEntry
    MAX-ACCESS  not-accessible
    STATUS      current
    DESCRIPTION
        "An entry in a list of Email Profiles."
    INDEX       { clvSpamSMTPProfileIndex }
    ::= { clvSpamSMTPProfileTable 1 }

ClvSpamSMTPProfileEntry ::= SEQUENCE {
    clvSpamSMTPProfileIndex         Integer32,
    clvSpamSMTPProfileName          DisplayString,
    clvSpamSMTPProfileScanned       Counter32,
    clvSpamSMTPProfileSpam          Counter32,
    clvSpamSMTPProfileDomainCheck   Counter32,
    clvSpamSMTPProfileDomainMatch   Counter32,
    clvSpamSMTPProfileLinkCheck     Counter32,
    clvSpamSMTPProfileLinkMatch     Counter32,
    clvSpamSMTPProfileLinkCount     Counter32,
    clvSpamSMTPProfileDNSBLCheck    Counter32,
    clvSpamSMTPProfileDNSBLMatch    Counter32,
    clvSpamSMTPProfileDNSBL1Check   Counter32,
    clvSpamSMTPProfileDNSBL1Match   Counter32,
    clvSpamSMTPProfileDNSBL2Check   Counter32,
    clvSpamSMTPProfileDNSBL2Match   Counter32,
    clvSpamSMTPProfileDNSBL3Check   Counter32,
    clvSpamSMTPProfileDNSBL3Match   Counter32,
    clvSpamSMTPProfileDNSBL4Check   Counter32,
    clvSpamSMTPProfileDNSBL4Match   Counter32,
    clvSpamSMTPProfileDNSBL5Check   Counter32,
    clvSpamSMTPProfileDNSBL5Match   Counter32,
    clvSpamSMTPProfileDNSBL6Check   Counter32,
    clvSpamSMTPProfileDNSBL6Match   Counter32,
    clvSpamSMTPProfileDNSBL7Check   Counter32,
    clvSpamSMTPProfileDNSBL7Match   Counter32,
    clvSpamSMTPProfileDNSBL8Check   Counter32,
    clvSpamSMTPProfileDNSBL8Match   Counter32,
    clvSpamSMTPProfileDNSBL9Check   Counter32,
    clvSpamSMTPProfileDNSBL9Match   Counter32,
    clvSpamSMTPProfileDNSBL10Check  Counter32,
    clvSpamSMTPProfileDNSBL10Match  Counter32,
    clvSpamSMTPProfileDCCCheck      Counter32,
    clvSpamSMTPProfileDCCMatch      Counter32
}

clvSpamSMTPProfileIndex OBJECT-TYPE
    SYNTAX      Integer32 (1..2147483647)
    MAX-ACCESS  not-accessible
    STATUS      current
    DESCRIPTION
        "Index of an entry in clvSpamSMTPProfileTable"
    ::= { clvSpamSMTPProfileEntry 1 }

clvSpamSMTPProfileName OBJECT-TYPE
    SYNTAX      DisplayString
    MAX-ACCESS  read-only
    STATUS      current
    DESCRIPTION
        "The name of the Email Profile."
    ::= { clvSpamSMTPProfileEntry 2 }

clvSpamSMTPProfileScanned OBJECT-TYPE
    SYNTAX      Counter32
    MAX-ACCESS  read-only
    STATUS      current
    DESCRIPTION
        "Number of scanned emails."
    ::= { clvSpamSMTPProfileEntry 3 }

clvSpamSMTPProfileSpam OBJECT-TYPE
    SYNTAX      Counter32
    MAX-ACCESS  read-only
    STATUS      current
    DESCRIPTION
        "Number of spam emails."
    ::= { clvSpamSMTPProfileEntry 4 }

clvSpamSMTPProfileDomainCheck OBJECT-TYPE
    SYNTAX      Counter32
    MAX-ACCESS  read-only
    STATUS      current
    DESCRIPTION
        "Number of performed Domain Verification checks."
    ::= { clvSpamSMTPProfileEntry 5 }

clvSpamSMTPProfileDomainMatch OBJECT-TYPE
    SYNTAX      Counter32
    MAX-ACCESS  read-only
    STATUS      current
    DESCRIPTION
        "Number of emails with forged reply-to domains."
    ::= { clvSpamSMTPProfileEntry 6 }

clvSpamSMTPProfileLinkCheck OBJECT-TYPE
    SYNTAX      Counter32
    MAX-ACCESS  read-only
    STATUS      current
    DESCRIPTION
        "Number of emails inspected for undesirable links."
    ::= { clvSpamSMTPProfileEntry 7 }

clvSpamSMTPProfileLinkMatch OBJECT-TYPE
    SYNTAX      Counter32
    MAX-ACCESS  read-only
    STATUS      current
    DESCRIPTION
        "Number of emails containing undesirable links."
    ::= { clvSpamSMTPProfileEntry 8 }

clvSpamSMTPProfileLinkCount OBJECT-TYPE
    SYNTAX      Counter32
    MAX-ACCESS  read-only
    STATUS      current
    DESCRIPTION
        "Number of undesirable links found."
    ::= { clvSpamSMTPProfileEntry 9 }

clvSpamSMTPProfileDNSBLCheck OBJECT-TYPE
    SYNTAX      Counter32
    MAX-ACCESS  read-only
    STATUS      current
    DESCRIPTION
        "Number of performed DNSBL checks."
    ::= { clvSpamSMTPProfileEntry 10 }

clvSpamSMTPProfileDNSBLMatch OBJECT-TYPE
    SYNTAX      Counter32
    MAX-ACCESS  read-only
    STATUS      current
    DESCRIPTION
        "Number of emails from a blacklisted address."
    ::= { clvSpamSMTPProfileEntry 11 }

clvSpamSMTPProfileDNSBL1Check OBJECT-TYPE
    SYNTAX      Counter32
    MAX-ACCESS  read-only
    STATUS      current
    DESCRIPTION
        "Number of performed DNSBL checks."
    ::= { clvSpamSMTPProfileEntry 12 }

clvSpamSMTPProfileDNSBL1Match OBJECT-TYPE
    SYNTAX      Counter32
    MAX-ACCESS  read-only
    STATUS      current
    DESCRIPTION
        "Number of emails from a blacklisted address."
    ::= { clvSpamSMTPProfileEntry 13 }

clvSpamSMTPProfileDNSBL2Check OBJECT-TYPE
    SYNTAX      Counter32
    MAX-ACCESS  read-only
    STATUS      current
    DESCRIPTION
        "Number of performed DNSBL checks."
    ::= { clvSpamSMTPProfileEntry 14 }

clvSpamSMTPProfileDNSBL2Match OBJECT-TYPE
    SYNTAX      Counter32
    MAX-ACCESS  read-only
    STATUS      current
    DESCRIPTION
        "Number of emails from a blacklisted address."
    ::= { clvSpamSMTPProfileEntry 15 }

clvSpamSMTPProfileDNSBL3Check OBJECT-TYPE
    SYNTAX      Counter32
    MAX-ACCESS  read-only
    STATUS      current
    DESCRIPTION
        "Number of performed DNSBL checks."
    ::= { clvSpamSMTPProfileEntry 16 }

clvSpamSMTPProfileDNSBL3Match OBJECT-TYPE
    SYNTAX      Counter32
    MAX-ACCESS  read-only
    STATUS      current
    DESCRIPTION
        "Number of emails from a blacklisted address."
    ::= { clvSpamSMTPProfileEntry 17 }

clvSpamSMTPProfileDNSBL4Check OBJECT-TYPE
    SYNTAX      Counter32
    MAX-ACCESS  read-only
    STATUS      current
    DESCRIPTION
        "Number of performed DNSBL checks."
    ::= { clvSpamSMTPProfileEntry 18 }

clvSpamSMTPProfileDNSBL4Match OBJECT-TYPE
    SYNTAX      Counter32
    MAX-ACCESS  read-only
    STATUS      current
    DESCRIPTION
        "Number of emails from a blacklisted address."
    ::= { clvSpamSMTPProfileEntry 19 }

clvSpamSMTPProfileDNSBL5Check OBJECT-TYPE
    SYNTAX      Counter32
    MAX-ACCESS  read-only
    STATUS      current
    DESCRIPTION
        "Number of performed DNSBL checks."
    ::= { clvSpamSMTPProfileEntry 20 }

clvSpamSMTPProfileDNSBL5Match OBJECT-TYPE
    SYNTAX      Counter32
    MAX-ACCESS  read-only
    STATUS      current
    DESCRIPTION
        "Number of emails from a blacklisted address."
    ::= { clvSpamSMTPProfileEntry 21 }

clvSpamSMTPProfileDNSBL6Check OBJECT-TYPE
    SYNTAX      Counter32
    MAX-ACCESS  read-only
    STATUS      current
    DESCRIPTION
        "Number of performed DNSBL checks."
    ::= { clvSpamSMTPProfileEntry 22 }

clvSpamSMTPProfileDNSBL6Match OBJECT-TYPE
    SYNTAX      Counter32
    MAX-ACCESS  read-only
    STATUS      current
    DESCRIPTION
        "Number of emails from a blacklisted address."
    ::= { clvSpamSMTPProfileEntry 23 }

clvSpamSMTPProfileDNSBL7Check OBJECT-TYPE
    SYNTAX      Counter32
    MAX-ACCESS  read-only
    STATUS      current
    DESCRIPTION
        "Number of performed DNSBL checks."
    ::= { clvSpamSMTPProfileEntry 24 }

clvSpamSMTPProfileDNSBL7Match OBJECT-TYPE
    SYNTAX      Counter32
    MAX-ACCESS  read-only
    STATUS      current
    DESCRIPTION
        "Number of emails from a blacklisted address."
    ::= { clvSpamSMTPProfileEntry 25 }

clvSpamSMTPProfileDNSBL8Check OBJECT-TYPE
    SYNTAX      Counter32
    MAX-ACCESS  read-only
    STATUS      current
    DESCRIPTION
        "Number of performed DNSBL checks."
    ::= { clvSpamSMTPProfileEntry 26 }

clvSpamSMTPProfileDNSBL8Match OBJECT-TYPE
    SYNTAX      Counter32
    MAX-ACCESS  read-only
    STATUS      current
    DESCRIPTION
        "Number of emails from a blacklisted address."
    ::= { clvSpamSMTPProfileEntry 27 }

clvSpamSMTPProfileDNSBL9Check OBJECT-TYPE
    SYNTAX      Counter32
    MAX-ACCESS  read-only
    STATUS      current
    DESCRIPTION
        "Number of performed DNSBL checks."
    ::= { clvSpamSMTPProfileEntry 28 }

clvSpamSMTPProfileDNSBL9Match OBJECT-TYPE
    SYNTAX      Counter32
    MAX-ACCESS  read-only
    STATUS      current
    DESCRIPTION
        "Number of emails from a blacklisted address."
    ::= { clvSpamSMTPProfileEntry 29 }

clvSpamSMTPProfileDNSBL10Check OBJECT-TYPE
    SYNTAX      Counter32
    MAX-ACCESS  read-only
    STATUS      current
    DESCRIPTION
        "Number of performed DNSBL checks."
    ::= { clvSpamSMTPProfileEntry 30 }

clvSpamSMTPProfileDNSBL10Match OBJECT-TYPE
    SYNTAX      Counter32
    MAX-ACCESS  read-only
    STATUS      current
    DESCRIPTION
        "Number of emails from a blacklisted address."
    ::= { clvSpamSMTPProfileEntry 31 }

clvSpamSMTPProfileDCCCheck OBJECT-TYPE
    SYNTAX      Counter32
    MAX-ACCESS  read-only
    STATUS      current
    DESCRIPTION
        "Number of performed DCC checks."
    ::= { clvSpamSMTPProfileEntry 32 }

clvSpamSMTPProfileDCCMatch OBJECT-TYPE
    SYNTAX      Counter32
    MAX-ACCESS  read-only
    STATUS      current
    DESCRIPTION
        "Number of emails considered bulk by DCC."
    ::= { clvSpamSMTPProfileEntry 33 }
-- End of SpamSMTP

clavisterStatsConformance OBJECT IDENTIFIER
    ::= { clavisterMibConfs 1 }

clavisterStatsRegGroups OBJECT IDENTIFIER
    ::= { clavisterMibObjectGroups 1 }

clvSystemObjectGroup OBJECT-GROUP
    OBJECTS     { clvSysCpuLoad,
                  clvSysForwardedBits,
                  clvSysForwardedPackets,
                  clvSysBuffUse,
                  clvSysConns,
                  clvHWSensorName,
                  clvHWSensorValue,
                  clvHWSensorUnit,
                  clvSysMemUsage,
                  clvSysTimerUsage,
                  clvSysConnOPS,
                  clvSysConnCPS,
                  clvSysHCForwardedBits,
                  clvSysMemUsedKiB,
                  clvSysMemFreeKiB }
    STATUS      current
    DESCRIPTION
        "System statistics Group"
    ::= { clavisterStatsRegGroups 1 }

clvIPsecObjectGroup OBJECT-GROUP
    OBJECTS     { clvIKESAsActive,
                  clvIKEAggrModeSuccessful,
                  clvIKENegsActive,
                  clvIKENegsSuccessful,
                  clvIKENegsFailed,
                  clvIKERekeysActive,
                  clvIKERekeysSuccessful,
                  clvIKERekeysFailed,
                  clvIKEPacketsRecv,
                  clvIKEBytesRecv,
                  clvIKEPacketsSent,
                  clvIKEBytesSent,
                  clvIKEPacketsResent}
    STATUS      current
    DESCRIPTION
        "IPsec Group"
    ::= { clavisterStatsRegGroups 2 }

clvStateCountersGroup OBJECT-GROUP
    OBJECTS     { clvSysPscTcpSyn,
                  clvSysPscTcpOpen,
                  clvSysPscTcpFin,
                  clvSysPscUdp,
                  clvSysPscIcmp,
                  clvSysPscOther }
    STATUS      current
    DESCRIPTION
        "Per state counters"
    ::= { clavisterStatsRegGroups 3 }

clvIPPoolGroup OBJECT-GROUP
    OBJECTS     { clvIPPoolsNumber,
                  clvIPPoolName,
                  clvIPPoolPrepare,
                  clvIPPoolFree,
                  clvIPPoolMisses,
                  clvIPPoolClientFails,
                  clvIPPoolUsed }
    STATUS      current
    DESCRIPTION
        "IP pool entry objects group"
    ::= { clavisterStatsRegGroups 4 }

clvDHCPServerGroup OBJECT-GROUP
    OBJECTS     { clvDHCPTotalRejected,
                  clvDHCPRuleName,
                  clvDHCPRuleUsage,
                  clvDHCPRuleUsagePercent,
                  clvDHCPActiveClients,
                  clvDHCPActiveClientsPercent,
                  clvDHCPRejectedRequests,
                  clvDHCPTotalLeases }
    STATUS      current
    DESCRIPTION
        "DHCP server rules objects."
    ::= { clavisterStatsRegGroups 5 }

clvRuleUseGroup OBJECT-GROUP
    OBJECTS     { clvRuleName, clvRuleUse }
    STATUS      current
    DESCRIPTION
        "Rule use objects."
    ::= { clavisterStatsRegGroups 6 }

clvUserAuthGroup OBJECT-GROUP
    OBJECTS     { clvUserAuthHTTPUsers, clvUserAuthXAUTHUsers,
                  clvUserAuthHTTPSUsers, clvUserAuthPPPUsers,
                  clvUserAuthEAPUsers, clvUserAuthRuleName,
                  clvUserAuthRuleUse,
                  clvUserAuthIDAwareUsers, clvUserAuthRADIUSRelayUsers }
    STATUS      current
    DESCRIPTION
        "User auth objects."
    ::= { clavisterStatsRegGroups 7 }

clvIfStatsGroup OBJECT-GROUP
    OBJECTS     { clvIfName,
                  clvIfFragsIn,
                  clvIfFragReassOk,
                  clvIfFragReassFail,
                  clvIfPktsInCnt,
                  clvIfPktsOutCnt,
                  clvIfBitsInCnt,
                  clvIfBitsOutCnt,
                  clvIfPktsTotCnt,
                  clvIfBitsTotCnt,
                  clvIfHCPktsInCnt,
                  clvIfHCPktsOutCnt,
                  clvIfHCBitsInCnt,
                  clvIfHCBitsOutCnt,
                  clvIfHCPktsTotCnt,
                  clvIfHCBitsTotCnt,
                  clvIfRxRingFifoErrors,
                  clvIfRxDespools,
                  clvIfRxAvgUse,
                  clvIfRxRingSaturation,
                  clvRxRingFlooded,
                  clvIfTxDespools,
                  clvIfTxAvgUse,
                  clvIfTxRingSaturation,
                  clvRxTingFlooded }
    STATUS      current
    DESCRIPTION
        "Clavister interface statistics group."
    ::= { clavisterStatsRegGroups 8 }

clvLinkMonitorGroup OBJECT-GROUP
    OBJECTS     { clvLinkMonGrp,
                  clvLinkMonGrpName,
                  clvLinkMonGrpHostsUp,
                  clvLinkMonHostId,
                  clvLinkMonHostShortTermLoss,
                  clvLinkMonHostPacketsLost }
    STATUS      current
    DESCRIPTION
        "Clavister link monitor statistics group"
    ::= { clavisterStatsRegGroups 9 }

clvPipesObjectGroup OBJECT-GROUP
    OBJECTS     { clvPipeUsers,
                  clvPipeName,
                  clvPipeMinPrec,
                  clvPipeMaxPrec,
                  clvPipeDefPrec,
                  clvPipeNumPrec,
                  clvPipeNumUsers,
                  clvPipeCurrentBps,
                  clvPipeCurrentPps,
                  clvPipeDelayedPackets,
                  clvPipeDropedPackets,
                  clvPipePrec,
                  clvPipePrecBps,
                  clvPipePrecTotalPps,
                  clvPipePrecReservedBps,
                  clvPipePrecDynLimBps,
                  clvPipePrecDynUsrLimBps,
                  clvPipePrecDelayedPackets,
                  clvPipePrecDropedPackets }
    STATUS      current
    DESCRIPTION
        "Clavister pipes statistics group"
    ::= { clavisterStatsRegGroups 10 }

clvDHCPRelayObjectGroup OBJECT-GROUP
    OBJECTS     { clvDHCPRelayCurClients,
                  clvDHCPRelayCurTrans,
                  clvDHCPRelayRejected,
                  clvDHCPRelayRuleName,
                  clvDHCPRelayRuleHits,
                  clvDHCPRelayRuleCurClients,
                  clvDHCPRelayRuleRejCliPkts,
                  clvDHCPRelayRuleRejSrvPkts }
    STATUS      current
    DESCRIPTION
        "Clavister DHCP relay statistics group"
    ::= { clavisterStatsRegGroups 12 }

clvAlgGroup OBJECT-GROUP
    OBJECTS     { clvAlgSessions,
                  clvAlgConnections,
                  clvAlgTCPStreams,
                  clvHttpAlgName,
                  clvHttpAlgTotalRequested,
                  clvHttpAlgTotalAllowed,
                  clvHttpAlgTotalBlocked,
                  clvHttpAlgCntFltName,
                  clvHttpAlgCntFltRequests,
                  clvHttpAlgCntFltAllowed,
                  clvHttpAlgCntFltBlocked }
    STATUS      current
    DESCRIPTION
        "Clavister HTTP ALG statistics group"
    ::= { clavisterStatsRegGroups 13 }

clvHAGroup OBJECT-GROUP
    OBJECTS     { clvHASyncSendQueueLength,
                  clvHASyncSendQueueUsagePkt,
                  clvHASyncSendQueueUsageOct,
                  clvHASyncSentPackets,
                  clvHASyncSendResentPackets }
    STATUS      current
    DESCRIPTION
        "Clavister HA statistics group"
    ::= { clavisterStatsRegGroups 14 }

clvIfVlanGroup OBJECT-GROUP
    OBJECTS     { clvIfVlanUntaggedInPkts,
                  clvIfVlanUntaggedOutPkts,
                  clvIfVlanUntaggedTotPkts,
                  clvIfVlanUntaggedInOctets,
                  clvIfVlanUntaggedOutOctets,
                  clvIfVlanUntaggedTotOctets }
    STATUS      current
    DESCRIPTION
        "Clavister VLAN statistics group"
    ::= { clavisterStatsRegGroups 15 }


clvSmtpAlgGroup OBJECT-GROUP
    OBJECTS { clvSmtpAlgName,
              clvSmtpAlgTotCheckedSes,
              clvSmtpAlgTotSpamSes,
              clvSmtpAlgTotDroppedSes,
              clvSmtpAlgDnsBlName,
              clvSmtpAlgDnsBlChecked,
              clvSmtpAlgDnsBlMatched,
              clvSmtpAlgDnsBlFailChecks }
   STATUS current
   DESCRIPTION
       "Clavister SMTP ALG objects group"
   ::= { clavisterStatsRegGroups 16 }

clvSysTCPGroup OBJECT-GROUP
    OBJECTS { clvSysTCPRecvSmall,
              clvSysTCPRecvLarge,
              clvSysTCPSendSmall,
              clvSysTCPSendLarge }
    STATUS current
    DESCRIPTION
      "Clavister TCP buffer usage group"
    ::= { clavisterStatsRegGroups 17 }

clvAppControlGroup OBJECT-GROUP
    OBJECTS { clvAppCtrlName,
              clvAppCtrlBytesFwd,
              clvAppCtrlPacketsFwd,
              clvAppCtrlClassified }
    STATUS current
    DESCRIPTION
      "Clavister TCP buffer usage group"
    ::= { clavisterStatsRegGroups 18 }

clvRADIUSRelayGroup OBJECT-GROUP
    OBJECTS { clvRADIUSRelayRequests,
              clvRADIUSRelayChallenges,
              clvRADIUSRelayAccepts,
              clvRADIUSRelayRejects,
              clvRADIUSRelayUnknowns,
              clvRADIUSRelayFailures }
    STATUS current
    DESCRIPTION
      "Clavister RADIUS relay usage group"
    ::= { clavisterStatsRegGroups 19 }

clvDHCPv6ServerGroup OBJECT-GROUP
    OBJECTS     { clvDHCPv6TotalRejected,
                  clvDHCPv6RuleName,
                  clvDHCPv6RuleUsage,
                  clvDHCPv6RuleUsagePercent,
                  clvDHCPv6ActiveClients,
                  clvDHCPv6ActiveClientsPercent,
                  clvDHCPv6RejectedRequests,
                  clvDHCPv6TotalLeases }
    STATUS      current
    DESCRIPTION
        "DHCPv6 server rules objects."
    ::= { clavisterStatsRegGroups 20 }

clvThreatPreventionGroup OBJECT-GROUP
    OBJECTS { clvTPBlacklistThresholdAdd,
              clvTPBlacklistThresholdHit,
              clvTPBlacklistIDPAdd,
              clvTPBlacklistIDPHit,
              clvTPBlacklistDoSAdd,
              clvTPBlacklistDoSHit,
              clvTPBlacklistBotnetAdd,
              clvTPBlacklistBotnetHit,
              clvTPBlacklistScannerAdd,
              clvTPBlacklistScannerHit,
              clvTPBlacklistGeoIpAdd,
              clvTPBlacklistGeoIpHit,
              clvTPBlacklistRestAdd,
              clvTPBlacklistRestHit }
    STATUS current
    DESCRIPTION
      "Clavister Threat Prevention blacklist group"
    ::= { clavisterStatsRegGroups 21 }

clvDnsAlgGroup OBJECT-GROUP
    OBJECTS { clvDnsAlgFwdDnsReqs,
              clvDnsAlgFwdDnsResps,
              clvDnsAlgMalCliMsgs,
              clvDnsAlgMalSrvMsgs,
              clvDnsAlgDropCliMsgs,
              clvDnsAlgDropSrvMsgs,
              clvDnsAlgCurDnsSes,
              clvDnsAlgTotDnsSes }
   STATUS current
   DESCRIPTION
       "Clavister DNS ALG objects group"
   ::= { clavisterStatsRegGroups 22 }

clavisterStatsCompliance MODULE-COMPLIANCE
    STATUS      current
    DESCRIPTION
        "Module Compliance"

    MODULE      -- this module

        MANDATORY-GROUPS
                { clvSystemObjectGroup,
                  clvIPsecObjectGroup,
                  clvStateCountersGroup,
                  clvIPPoolGroup,
                  clvDHCPServerGroup,
                  clvRuleUseGroup,
                  clvUserAuthGroup,
                  clvIfStatsGroup,
                  clvLinkMonitorGroup,
                  clvPipesObjectGroup,
                  clvDHCPRelayObjectGroup,
                  clvAlgGroup,
                  clvHAGroup,
                  clvIfVlanGroup,
                  clvSmtpAlgGroup,
                  clvSysTCPGroup,
                  clvAppControlGroup,
                  clvRADIUSRelayGroup,
                  clvDHCPv6ServerGroup,
                  clvThreatPreventionGroup,
                  clvDnsAlgGroup }

    ::= { clavisterStatsConformance 1 }

END -- end of module CLAVISTER-MIB.
