OBSERVIUM-MIB DEFINITIONS ::= BEGIN

IMPORTS
    enterprises, MODULE-IDENTITY, OBJECT-TYPE, Counter32,
    Gauge32, Counter64, Integer32, TimeTicks, mib-2,
    NOTIFICATION-TYPE                        FROM SNMPv2-SMI
    TEXTUAL-CONVENTION, DisplayString,
    PhysAddress, TruthValue, RowStatus,
    TimeStamp, AutonomousType, TestAndIncr   FROM SNMPv2-TC
    MODULE-COMPLIANCE, OBJECT-GROUP,
    NOTIFICATION-GROUP                       FROM SNMPv2-CONF
    snmpTraps                                FROM SNMPv2-MIB;

observium           OBJECT IDENTIFIER ::= { enterprises 36602 }
obsObjects          OBJECT IDENTIFIER ::= { observium 1 }
obsHostInfo         OBJECT IDENTIFIER ::= { obsObjects 1 }

obsLinuxDistro OBJECT-TYPE
    SYNTAX      DisplayString (SIZE (0..255))
    MAX-ACCESS  read-only
    STATUS      current
    DESCRIPTION
            "Linux distribution and version"
    ::= { obsHostInfo 2 }

obsCPUUsage OBJECT-TYPE
    SYNTAX  INTEGER
    ACCESS  read-only
    STATUS  mandatory
    DESCRIPTION
            "CPU Usage"
    ::= { obsHostInfo 3 }


END
