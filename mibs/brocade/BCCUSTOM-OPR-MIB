BCCUSTOM-OPR-MIB DEFINITIONS ::= BEGIN
 IMPORTS
 Integer32, OBJECT-IDENTITY, OBJECT-TYPE,
 IpAddress, MODULE-IDENTITY
 FROM SNMPv2-SMI

 fcSwitch
 FROM Brocade-REG-MIB;

 bcCustomOperation MODULE-IDENTITY
 LAST-UPDATED "200807291830Z"
 ORGANIZATION "Brocade Communications Systems, Inc."
 CONTACT-INFO "Customer Support Group
 Brocade Communications Systems,
 120 Holger Way,
 San Jose, CA 95134 U.S.A
 Tel: +1-408-333-6061
 Email: support@Brocade.COM
 WEB: www.brocade.com."
 DESCRIPTION "The MIB module is to get the details of T8000 Embedded switch.
            copyright (c) 2011-2018 Brocade Communications Systems, Inc.
            All rights reserved."
 REVISION    "201112191030Z" -- Dec 19, 2011 10:30am
 DESCRIPTION    "Initial version of this module."
 ::= { fcSwitch 52 }

 hwinfospsaveCmd OBJECT-IDENTITY
 STATUS  current
 DESCRIPTION   "The OID subtree for supportsave operation."
 ::= { bcCustomOperation 1 }

 hwinfospsaveSet OBJECT-TYPE
 SYNTAX OCTET STRING(SIZE(0..1024))
 MAX-ACCESS read-write
 STATUS current
 DESCRIPTION "Parameter required for FC switch to execute supportsave operation:
			FTP Server IP Type: IPV4/IPV6
			Server IP address: IP address of FTP server
			FTP User: FTP server username to login
			FTP Code: password of FTP server
			Command: which is  executed on the FC switch board.
			Filename: The name of info package after command executed.

			Used: Trigger 'supportsave' command  when received a trap
			of FC switch work abnormally."
 ::= { hwinfospsaveCmd 1 }

 hwinfospsaveGet OBJECT-TYPE
 SYNTAX INTEGER {
		success(0),
		ftperror(1),
		progressing(2),
		systemerror(3)
		}
 MAX-ACCESS read-only
 STATUS current
 DESCRIPTION "Get the state how the triggered Command executed.
			Command: which  is executed on the FC switch board.
			Used: Get state of Hwinfospsaveget execute.
 			0x0:  command execute success ,file already transferred to FTP server
			0x1:  FTP server connect Error
			0x2:  progressing
			0x3:  System Error."
 ::= { hwinfospsaveCmd 2 }

 hwUpdateFilecmd OBJECT-IDENTITY
 STATUS  current
 DESCRIPTION   "The OID subtree for Firmware download operation."
 ::= { bcCustomOperation 2 }

 hwUpdateFile OBJECT-TYPE
 SYNTAX OCTET STRING(SIZE(0..1024))
 MAX-ACCESS read-write
 STATUS current
 DESCRIPTION "Does Firmware upgrade of the FC switch.
 			Use a space between each attribute separated.
			1.The type, the current must be IPV4
			2.ftp Host ip
			3.ftp User name
			4.ftp Password
			5.The upgrade of the software loaded, you can bear with the path.
			Example:
			'IPV4 172.16.128.1 user password xcbf.cc'"
 ::= { hwUpdateFilecmd 1 }

 hwUpdateFileInfo OBJECT-TYPE
 SYNTAX OCTET STRING(SIZE(0..1024))
 MAX-ACCESS read-only
 STATUS  current
 DESCRIPTION "For getting firmware upgrade and progress status.
				Format is
				1. INT32 iStatus      'Update state'
				2. UINT8 ucResv[2]      'Reserved'
				Example:
				1.	Success - Firmwaredownload completed successfully
				2.	Inprogress - Firmwaredownload is going on
				3.	Another Firmware download in progress - When another
					download is going on
				4.  Invalid URI - Input URI is in incorrect format
				5.	Failure - Firmwaredownload is failed"

 ::= { hwUpdateFilecmd 2 }

 hwSoftwareVersion OBJECT-TYPE
 SYNTAX OCTET STRING(SIZE(0..4096))
 MAX-ACCESS read-only
 STATUS  current
 DESCRIPTION   "Software firmware version information.
 				Format is
				1. UINT32 hwSoftwareVersionNum 'The number of software'
				'Version of the software structure'
			    2. UINT8 ucNameLen 'Software name length'
    			3. char ucName[ucNameLen] 'Software Name'
    			Example (XCBC board) are as follows
				00.00.00.02. --- The number of software
				03. 		--- The length of the current version of the software (Firmware 1)
				32.31.38. 	--- The current version of the software 218 (Firmware 1)
				03. 		--- The length of the current version of the software (Firmware 2)
				32.31.38. 	--- The current version of the software 218 (Firmware 2"
 ::= { hwUpdateFilecmd 3 }

END
