-- Feature Keying MIB overview:
-- Feature Keying MIB falls under dnOS MIB node of the private subtree.



DNOS-KEYING-PRIVATE-MIB DEFINITIONS ::= BEGIN

-- Broadcom DNOS Keying MIB
-- Copyright 2016 Broadcom.
-- This SNMP Management Information Specification
-- embodies Broadcom's confidential and proprietary
-- intellectual property.  Broadcom retains all title
-- and ownership in the Specification including any revisions.

-- This Specification is supplied "AS IS", Broadcom
-- makes no warranty, either expressed or implied,
-- as to the use, operation, condition, or performance of the
-- Specification.



IMPORTS
    MODULE-IDENTITY, OBJECT-TYPE, NOTIFICATION-TYPE,
    Unsigned32                          FROM SNMPv2-SMI


    TEXTUAL-CONVENTION,RowStatus,
    RowPointer		                FROM SNMPv2-TC

    DisplayString		        FROM RFC1213-MIB
    dnOS                            FROM DELL-REF-MIB;

    fastPathKeyingPrivate MODULE-IDENTITY
           LAST-UPDATED "201101260000Z" -- 26 January 2011 12:00:00 GMT
           ORGANIZATION "Dell EMC"
           CONTACT-INFO ""

     DESCRIPTION
          "The Broadcom Private MIB for DNOS Keying Utility"

      -- Revision history.
      REVISION
          "201101260000Z" -- 26 January 2011 12:00:00 GMT
      DESCRIPTION
          "Add new Postal address change."
      REVISION
          "200705230000Z" -- 23 May 2007 12:00:00 GMT
      DESCRIPTION
          "Dell branding related changes."

      ::= { dnOS 24 }


     --**************************************************************************************
    -- agentFeatureKeyingGroup -> contains MIB objects displaying Key and associated Functionality
    --
    --**************************************************************************************

agentFeatureKeyingGroup OBJECT IDENTIFIER ::= { fastPathKeyingPrivate 1 }

agentFeatureKeyingEnableKey OBJECT-TYPE
	SYNTAX DisplayString
	MAX-ACCESS read-write
	STATUS current
	DESCRIPTION
		"Hexadecimal Key-string entered to enable an advance functionality."
	::={ agentFeatureKeyingGroup 1 }

agentFeatureKeyingDisableKey OBJECT-TYPE
	SYNTAX DisplayString
	MAX-ACCESS read-write
	STATUS current
	DESCRIPTION
		"Hexadecimal Key-string entered to disable an advance functionality."
	::={ agentFeatureKeyingGroup 2 }


agentFeatureKeyingTable OBJECT-TYPE
	SYNTAX	     SEQUENCE OF AgentFeatureKeyingEntry
	MAX-ACCESS   not-accessible
	STATUS       current
	DESCRIPTION "A table for license key and associated functionality. "
	::= { agentFeatureKeyingGroup 3 }

agentFeatureKeyingEntry OBJECT-TYPE
	SYNTAX AgentFeatureKeyingEntry
	MAX-ACCESS not-accessible
	STATUS current
	DESCRIPTION "Represents entry for key table"
	INDEX { agentFeatureKeyingIndex }
	::={ agentFeatureKeyingTable 1}

	AgentFeatureKeyingEntry ::=
		SEQUENCE {
		agentFeatureKeyingIndex
			Unsigned32,
		agentFeatureKeyingName
			DisplayString,
		agentFeatureKeyingStatus
			INTEGER
		}

	agentFeatureKeyingIndex OBJECT-TYPE
		SYNTAX Unsigned32
		MAX-ACCESS not-accessible
		STATUS current
		DESCRIPTION
			"A value corresponding to a keyable feature.When this table is walked,
		 	only values associated with keyable features are returned.This value
			must be equivalent to valid value of agentFeatureKeyingIndex."
		::={ agentFeatureKeyingEntry 1 }

	agentFeatureKeyingName OBJECT-TYPE
                SYNTAX DisplayString
		MAX-ACCESS read-only
		STATUS current
		DESCRIPTION
			"The abbreviated name of this component.This is also equivalent to
			agentFeatureKeyingName"
		::={ agentFeatureKeyingEntry 2 }

	agentFeatureKeyingStatus OBJECT-TYPE
		SYNTAX      INTEGER {
                    enable(1),
                    disable(2)
                    }
		MAX-ACCESS read-only
		STATUS current
		DESCRIPTION
			"Returns a value of (1) if the feature is enabled for management,
			(2) if disabled."
		::={agentFeatureKeyingEntry 3 }

END
