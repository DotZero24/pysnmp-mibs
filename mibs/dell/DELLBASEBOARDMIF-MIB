-- HIP Version = X131
--
-- MIB generated by miftomib version 1.0a

DELLBASEBOARDMIF-MIB DEFINITIONS ::= BEGIN

-- This is the MIF for Dell Servers

IMPORTS
    OBJECT-TYPE
    FROM RFC-1212
    enterprises
    FROM RFC1155-SMI
    DisplayString
    FROM RFC1213-MIB;

DmiInteger			::= INTEGER
DmiOctetstring		::= OCTET STRING
DmiDisplaystring	::= DisplayString
DmiDate				::= OCTET STRING (SIZE (28))
DmiComponentIndex	::= INTEGER

dell                	OBJECT IDENTIFIER ::= {enterprises 674}
server             	OBJECT IDENTIFIER ::= {dell 10890}
baseboard      	OBJECT IDENTIFIER ::= {server 1}
dmtfGroups          	OBJECT IDENTIFIER ::= {baseboard 1}

SComponentid ::= SEQUENCE {
	a1Manufacturer                          	DmiDisplaystring,
	a1Product                               	DmiDisplaystring,
	a1Version                               	DmiDisplaystring,
	a1SerialNumber                          	DmiDisplaystring,
	a1Installation                          	DmiDate,
	a1Verify                                	DmiInteger
}

tComponentid OBJECT-TYPE
	SYNTAX		SEQUENCE OF SComponentid
	ACCESS		not-accessible
	STATUS		mandatory
	DESCRIPTION	"This group defines attributes common to all components."
	::= {dmtfGroups 1}

eComponentid OBJECT-TYPE
	SYNTAX		SComponentid
	ACCESS		not-accessible
	STATUS		mandatory
	DESCRIPTION	""
	INDEX		{DmiComponentIndex}
	::= {tComponentid 1}

a1Manufacturer OBJECT-TYPE
	SYNTAX		DmiDisplaystring
	ACCESS		read-only
	STATUS		mandatory
	DESCRIPTION	"The name of the manufacturer that produced this component."
	::= {eComponentid 1}

a1Product OBJECT-TYPE
	SYNTAX		DmiDisplaystring
	ACCESS		read-only
	STATUS		mandatory
	DESCRIPTION	"The name of the component."
	::= {eComponentid 2}

a1Version OBJECT-TYPE
	SYNTAX		DmiDisplaystring
	ACCESS		read-only
	STATUS		mandatory
	DESCRIPTION	"The version for the component."
	::= {eComponentid 3}

a1SerialNumber OBJECT-TYPE
	SYNTAX		DmiDisplaystring
	ACCESS		read-only
	STATUS		mandatory
	DESCRIPTION	"The serial number for this instance of this component."
	::= {eComponentid 4}

a1Installation OBJECT-TYPE
	SYNTAX		DmiDate
	ACCESS		read-only
	STATUS		mandatory
	DESCRIPTION	"The time & date of the lastest installation of this component."
	::= {eComponentid 5}

a1Verify OBJECT-TYPE
	SYNTAX		INTEGER {
		vAnErrorOccurredCheckStatusCode         	(0),
		vThisComponentDoesNotExist              	(1),
		vTheVerifyIsNotSupported                	(2),
		vReserved                               	(3),
		vThisComponentExistsButTheFunctionalityI	(4),
		vThisComponentExistsButTheFunctionality1	(5),
		vThisComponentExistsAndIsNotFunctioningC	(6),
		vThisComponentExistsAndIsFunctioningCorr	(7)
	}
	ACCESS		read-only
	STATUS		mandatory
	DESCRIPTION	"A code that provides a level of verification that the component
is still installed and working."
	::= {eComponentid 6}

STemperature ::= SEQUENCE {
	a2Tempparentindex                       	DmiInteger,
	a2Tempindex                             	DmiInteger,
	a2Temptype                              	DmiInteger,
	a2Tempstatus                            	DmiInteger,
	a2Tempreading                           	DmiInteger,
	a2Tempminwarn                           	DmiDisplaystring,
	a2Tempmaxwarn                           	DmiDisplaystring,
	a2Tempminfail                           	DmiInteger,
	a2Tempmaxfail                           	DmiInteger,
	a2Templocation                          	DmiDisplaystring
}

tTemperature OBJECT-TYPE
	SYNTAX		SEQUENCE OF STemperature
	ACCESS		not-accessible
	STATUS		mandatory
	DESCRIPTION	"This group defines the attributes for the temperature probes
this system."
	::= {dmtfGroups 2}

eTemperature OBJECT-TYPE
	SYNTAX		STemperature
	ACCESS		not-accessible
	STATUS		mandatory
	DESCRIPTION	""
	INDEX		{DmiComponentIndex, a2Tempparentindex, a2Tempindex}
	::= {tTemperature 1}

a2Tempparentindex OBJECT-TYPE
	SYNTAX		DmiInteger
	ACCESS		read-only
	STATUS		mandatory
	DESCRIPTION	"An index into the chassis table."
	::= {eTemperature 1}

a2Tempindex OBJECT-TYPE
	SYNTAX		DmiInteger
	ACCESS		read-only
	STATUS		mandatory
	DESCRIPTION	"index into this temperature probe table."
	::= {eTemperature 2}

a2Temptype OBJECT-TYPE
	SYNTAX		INTEGER {
		vOther                                  	(1),
		vUnknown                                	(2),
		vTmc                                    	(3),
		vTvm                                    	(4),
		vEsm                                    	(5),
		vBackplane                              	(6),
		vHarrierBackplane                       	(7)
	}
	ACCESS		read-only
	STATUS		mandatory
	DESCRIPTION	"Defines the type of the temperature probe."
	::= {eTemperature 3}

a2Tempstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Current status of the temperature probe."
	::= {eTemperature 4}

a2Tempreading OBJECT-TYPE
	SYNTAX		DmiInteger
	ACCESS		read-only
	STATUS		mandatory
	DESCRIPTION	"The reading of the temperature probe in tenths of degrees."
	::= {eTemperature 5}

a2Tempminwarn OBJECT-TYPE
	SYNTAX		DmiDisplaystring
	ACCESS		read-write
	STATUS		mandatory
	DESCRIPTION	"The lower warning threshold for the temperature probe set
by the user."
	::= {eTemperature 6}

a2Tempmaxwarn OBJECT-TYPE
	SYNTAX		DmiDisplaystring
	ACCESS		read-write
	STATUS		mandatory
	DESCRIPTION	"The upper warning threshold for the temperature probe set
by the user."
	::= {eTemperature 7}

a2Tempminfail OBJECT-TYPE
	SYNTAX		DmiInteger
	ACCESS		read-only
	STATUS		mandatory
	DESCRIPTION	"The lower failure threshold for the temperature probe."
	::= {eTemperature 8}

a2Tempmaxfail OBJECT-TYPE
	SYNTAX		DmiInteger
	ACCESS		read-only
	STATUS		mandatory
	DESCRIPTION	"The upper failure threshold for the temperature probe."
	::= {eTemperature 9}

a2Templocation OBJECT-TYPE
	SYNTAX		DmiDisplaystring
	ACCESS		read-only
	STATUS		mandatory
	DESCRIPTION	"The location of this temperature probe within the system."
	::= {eTemperature 10}

SFan ::= SEQUENCE {
	a3Fansparentindex                       	DmiInteger,
	a3Fansindex                             	DmiInteger,
	a3Fanstype                              	DmiInteger,
	a3Fansstatus                            	DmiInteger,
	a3Fansreading                           	DmiInteger,
	a3Fanswarningmin                        	DmiDisplaystring,
	a3Fansmaxwarn                           	DmiDisplaystring,
	a3Fansminfail                           	DmiInteger,
	a3Fansmaxfail                           	DmiInteger,
	a3Fanslocation                          	DmiDisplaystring
}

tFan OBJECT-TYPE
	SYNTAX		SEQUENCE OF SFan
	ACCESS		not-accessible
	STATUS		mandatory
	DESCRIPTION	"This group defines the attributes for the fan probes this
system."
	::= {dmtfGroups 3}

eFan OBJECT-TYPE
	SYNTAX		SFan
	ACCESS		not-accessible
	STATUS		mandatory
	DESCRIPTION	""
	INDEX		{DmiComponentIndex, a3Fansparentindex, a3Fansindex}
	::= {tFan 1}

a3Fansparentindex OBJECT-TYPE
	SYNTAX		DmiInteger
	ACCESS		read-only
	STATUS		mandatory
	DESCRIPTION	"An index into the chassis table."
	::= {eFan 1}

a3Fansindex OBJECT-TYPE
	SYNTAX		DmiInteger
	ACCESS		read-only
	STATUS		mandatory
	DESCRIPTION	"index into this fan probe table."
	::= {eFan 2}

a3Fanstype OBJECT-TYPE
	SYNTAX		INTEGER {
		vOther                                  	(1),
		vUnknown                                	(2),
		vBoolean                                	(3),
		vRpm                                    	(4)
	}
	ACCESS		read-only
	STATUS		mandatory
	DESCRIPTION	"Defines the type of the fan probe."
	::= {eFan 3}

a3Fansstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Current status of the fan probe."
	::= {eFan 4}

a3Fansreading OBJECT-TYPE
	SYNTAX		DmiInteger
	ACCESS		read-only
	STATUS		mandatory
	DESCRIPTION	"The reading of the fan probe in RPM (or boolean)."
	::= {eFan 5}

a3Fanswarningmin OBJECT-TYPE
	SYNTAX		DmiDisplaystring
	ACCESS		read-write
	STATUS		mandatory
	DESCRIPTION	"The lower warning threshold for the fan probe set by the
user."
	::= {eFan 6}

a3Fansmaxwarn OBJECT-TYPE
	SYNTAX		DmiDisplaystring
	ACCESS		read-write
	STATUS		mandatory
	DESCRIPTION	"The upper warning threshold for the fan probe set by the
user."
	::= {eFan 7}

a3Fansminfail OBJECT-TYPE
	SYNTAX		DmiInteger
	ACCESS		read-only
	STATUS		mandatory
	DESCRIPTION	"The lower failure threshold for the fan probe."
	::= {eFan 8}

a3Fansmaxfail OBJECT-TYPE
	SYNTAX		DmiInteger
	ACCESS		read-only
	STATUS		mandatory
	DESCRIPTION	"The upper failure threshold for the fan probe."
	::= {eFan 9}

a3Fanslocation OBJECT-TYPE
	SYNTAX		DmiDisplaystring
	ACCESS		read-only
	STATUS		mandatory
	DESCRIPTION	"The location of this fan probe within the system."
	::= {eFan 10}

SVoltage ::= SEQUENCE {
	a4Voltparentindex                       	DmiInteger,
	a4Voltindex                             	DmiInteger,
	a4Volttype                              	DmiInteger,
	a4Voltstatus                            	DmiInteger,
	a4Voltreading                           	DmiInteger,
	a4Voltminwarn                           	DmiDisplaystring,
	a4Voltmaxwarn                           	DmiDisplaystring,
	a4Voltminfail                           	DmiInteger,
	a4Voltmaxfail                           	DmiInteger,
	a4Voltlocation                          	DmiDisplaystring
}

tVoltage OBJECT-TYPE
	SYNTAX		SEQUENCE OF SVoltage
	ACCESS		not-accessible
	STATUS		mandatory
	DESCRIPTION	"The Voltage group contains the data on all the voltage probes
in a system."
	::= {dmtfGroups 4}

eVoltage OBJECT-TYPE
	SYNTAX		SVoltage
	ACCESS		not-accessible
	STATUS		mandatory
	DESCRIPTION	""
	INDEX		{DmiComponentIndex, a4Voltparentindex, a4Voltindex}
	::= {tVoltage 1}

a4Voltparentindex OBJECT-TYPE
	SYNTAX		DmiInteger
	ACCESS		read-only
	STATUS		mandatory
	DESCRIPTION	"The chassis this voltage probe is connected to."
	::= {eVoltage 1}

a4Voltindex OBJECT-TYPE
	SYNTAX		DmiInteger
	ACCESS		read-only
	STATUS		mandatory
	DESCRIPTION	"the index of the voltage probe within the chassis."
	::= {eVoltage 2}

a4Volttype OBJECT-TYPE
	SYNTAX		INTEGER {
		vOther                                  	(1),
		vUnknown                                	(2),
		v-3_3v                                   	(3),
		v3_3v                                   	(4),
		v-5v                                    	(5),
		v5v                                    	(6),
		v-12v                                   	(7),
		v12v                                   	(8),
		v15v                                   	(9),
		vCore                                   	(10)
	}
	ACCESS		read-only
	STATUS		mandatory
	DESCRIPTION	"The type of voltage probe"
	::= {eVoltage 3}

a4Voltstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Status of the voltage probe."
	::= {eVoltage 4}

a4Voltreading OBJECT-TYPE
	SYNTAX		DmiInteger
	ACCESS		read-only
	STATUS		mandatory
	DESCRIPTION	"Current reading of the voltage probe, in millivolts."
	::= {eVoltage 5}

a4Voltminwarn OBJECT-TYPE
	SYNTAX		DmiDisplaystring
	ACCESS		read-write
	STATUS		mandatory
	DESCRIPTION	"lower warning threshold value for this voltage probe."
	::= {eVoltage 6}

a4Voltmaxwarn OBJECT-TYPE
	SYNTAX		DmiDisplaystring
	ACCESS		read-write
	STATUS		mandatory
	DESCRIPTION	"upper warning threshold value for this voltage probe."
	::= {eVoltage 7}

a4Voltminfail OBJECT-TYPE
	SYNTAX		DmiInteger
	ACCESS		read-only
	STATUS		mandatory
	DESCRIPTION	"lower failure threshold value for this voltage probe."
	::= {eVoltage 8}

a4Voltmaxfail OBJECT-TYPE
	SYNTAX		DmiInteger
	ACCESS		read-only
	STATUS		mandatory
	DESCRIPTION	"upper failure threshold value for this voltage probe."
	::= {eVoltage 9}

a4Voltlocation OBJECT-TYPE
	SYNTAX		DmiDisplaystring
	ACCESS		read-only
	STATUS		mandatory
	DESCRIPTION	"the location of this voltage probe within the system."
	::= {eVoltage 10}

SCurrent ::= SEQUENCE {
	a5Ampparentindex                        	DmiInteger,
	a5Ampindex                              	DmiInteger,
	a5Amptype                               	DmiInteger,
	a5Ampstatus                             	DmiInteger,
	a5Ampreading                            	DmiInteger,
	a5Ampminwarn                            	DmiDisplaystring,
	a5Ampmaxwarn                            	DmiDisplaystring,
	a5Ampminfail                            	DmiInteger,
	a5Ampmaxfail                            	DmiInteger,
	a5Amplocation                           	DmiDisplaystring
}

tCurrent OBJECT-TYPE
	SYNTAX		SEQUENCE OF SCurrent
	ACCESS		not-accessible
	STATUS		mandatory
	DESCRIPTION	"The Current group contains the data on all the Current probes
in a system."
	::= {dmtfGroups 5}

eCurrent OBJECT-TYPE
	SYNTAX		SCurrent
	ACCESS		not-accessible
	STATUS		mandatory
	DESCRIPTION	""
	INDEX		{DmiComponentIndex, a5Ampparentindex, a5Ampindex}
	::= {tCurrent 1}

a5Ampparentindex OBJECT-TYPE
	SYNTAX		DmiInteger
	ACCESS		read-only
	STATUS		mandatory
	DESCRIPTION	"The chassis this current probe is connected to."
	::= {eCurrent 1}

a5Ampindex OBJECT-TYPE
	SYNTAX		DmiInteger
	ACCESS		read-only
	STATUS		mandatory
	DESCRIPTION	"the index of the current probe within the chassis."
	::= {eCurrent 2}

a5Amptype OBJECT-TYPE
	SYNTAX		INTEGER {
		vOther                                  	(1),
		vUnknown                                	(2),
		v-3_3v                                   	(3),
		v3_3v                                   	(4),
		v-5v                                    	(5),
		v5v                                    	(6),
		v-12v                                   	(7),
		v12v                                   	(8)
	}
	ACCESS		read-only
	STATUS		mandatory
	DESCRIPTION	"The type of current probe"
	::= {eCurrent 3}

a5Ampstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Status of the current probe."
	::= {eCurrent 4}

a5Ampreading OBJECT-TYPE
	SYNTAX		DmiInteger
	ACCESS		read-only
	STATUS		mandatory
	DESCRIPTION	"Current reading of the current probe in milliamps."
	::= {eCurrent 5}

a5Ampminwarn OBJECT-TYPE
	SYNTAX		DmiDisplaystring
	ACCESS		read-write
	STATUS		mandatory
	DESCRIPTION	"lower warning threshold value for this current probe."
	::= {eCurrent 6}

a5Ampmaxwarn OBJECT-TYPE
	SYNTAX		DmiDisplaystring
	ACCESS		read-write
	STATUS		mandatory
	DESCRIPTION	"upper warning threshold value for this current probe."
	::= {eCurrent 7}

a5Ampminfail OBJECT-TYPE
	SYNTAX		DmiInteger
	ACCESS		read-only
	STATUS		mandatory
	DESCRIPTION	"lower failure threshold value for this current probe."
	::= {eCurrent 8}

a5Ampmaxfail OBJECT-TYPE
	SYNTAX		DmiInteger
	ACCESS		read-only
	STATUS		mandatory
	DESCRIPTION	"upper failure threshold value for this current probe."
	::= {eCurrent 9}

a5Amplocation OBJECT-TYPE
	SYNTAX		DmiDisplaystring
	ACCESS		read-only
	STATUS		mandatory
	DESCRIPTION	"the location of this current probe within the system."
	::= {eCurrent 10}

SPowerSupply ::= SEQUENCE {
	a6Pwrsupplyparentindex                  	DmiInteger,
	a6Pwrsupplyindex                        	DmiInteger,
	a6Pwrsupplytype                         	DmiInteger,
	a6Pwrsupplystatus                       	DmiInteger,
	a6Pwrsupplyonline                       	DmiDisplaystring
}

tPowerSupply OBJECT-TYPE
	SYNTAX		SEQUENCE OF SPowerSupply
	ACCESS		not-accessible
	STATUS		mandatory
	DESCRIPTION	"The Power Supply group contains the data on all the redundant
power supplies in a system."
	::= {dmtfGroups 6}

ePowerSupply OBJECT-TYPE
	SYNTAX		SPowerSupply
	ACCESS		not-accessible
	STATUS		mandatory
	DESCRIPTION	""
	INDEX		{DmiComponentIndex, a6Pwrsupplyparentindex, a6Pwrsupplyindex}
	::= {tPowerSupply 1}

a6Pwrsupplyparentindex OBJECT-TYPE
	SYNTAX		DmiInteger
	ACCESS		read-only
	STATUS		mandatory
	DESCRIPTION	"The chassis this power supply is connected to."
	::= {ePowerSupply 1}

a6Pwrsupplyindex OBJECT-TYPE
	SYNTAX		DmiInteger
	ACCESS		read-only
	STATUS		mandatory
	DESCRIPTION	"The index within the chassis of this power supply."
	::= {ePowerSupply 2}

a6Pwrsupplytype OBJECT-TYPE
	SYNTAX		INTEGER {
		vOther                                  	(1),
		vUnknown                                	(2),
		vPspb                                   	(3),
		v230w                                   	(4),
		v500w                                   	(5),
		v700w                                   	(6),
		v300w                                   	(7)
	}
	ACCESS		read-only
	STATUS		mandatory
	DESCRIPTION	"The type of power supply."
	::= {ePowerSupply 3}

a6Pwrsupplystatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"The current status of this power supply."
	::= {ePowerSupply 4}

a6Pwrsupplyonline OBJECT-TYPE
	SYNTAX		DmiDisplaystring
	ACCESS		read-write
	STATUS		mandatory
	DESCRIPTION	"The current online status of this power supply. Setting this
value to FALSE will turn off the power supply, setting it to TRUE will turn
on the power supply. "
	::= {ePowerSupply 5}

SGlobalPowerUnit ::= SEQUENCE {
	a7Pwrunitstatus                         	DmiInteger,
	a7Pwrunitgloballevel                    	DmiInteger,
	a7Pwrunitglobalmaxwarn                  	DmiDisplaystring,
	a7Pwrunitlevel33v                       	DmiInteger,
	a7Pwrunitmaxwarn33v                     	DmiDisplaystring,
	a7Pwrunitlevel5v                        	DmiInteger,
	a7Pwrunitmaxwarn5v                      	DmiDisplaystring,
	a7Pwrunitlevel12v                       	DmiInteger,
	a7Pwrunitmaxwarn12v                     	DmiDisplaystring,
	a7Pwrunituid                            	DmiDisplaystring,
	a7Pwrunitindex                          	DmiInteger
}

tGlobalPowerUnit OBJECT-TYPE
	SYNTAX		SEQUENCE OF SGlobalPowerUnit
	ACCESS		not-accessible
	STATUS		mandatory
	DESCRIPTION	"This group contains the global status for the power supplies
in the system."
	::= {dmtfGroups 7}

eGlobalPowerUnit OBJECT-TYPE
	SYNTAX		SGlobalPowerUnit
	ACCESS		not-accessible
	STATUS		mandatory
	DESCRIPTION	""
	INDEX		{DmiComponentIndex, a7Pwrunitindex}
	::= {tGlobalPowerUnit 1}

a7Pwrunitstatus OBJECT-TYPE
	SYNTAX		INTEGER {
		vOther                                  	(1),
		vUnknown                                	(2),
		vNotApplicableUnitNotRedundant          	(3),
		vOffline                                	(4),
		vFullyRedundant                         	(5),
		vDegradedRedundancy                     	(6),
		vRedundancyLost                         	(7)
	}
	ACCESS		read-only
	STATUS		mandatory
	DESCRIPTION	"The current redundancy status of the power unit."
	::= {eGlobalPowerUnit 1}

a7Pwrunitgloballevel OBJECT-TYPE
	SYNTAX		DmiInteger
	ACCESS		read-only
	STATUS		mandatory
	DESCRIPTION	"The current global power level usage, in percent."
	::= {eGlobalPowerUnit 2}

a7Pwrunitglobalmaxwarn OBJECT-TYPE
	SYNTAX		DmiDisplaystring
	ACCESS		read-write
	STATUS		mandatory
	DESCRIPTION	"Warning threshold, in percent"
	::= {eGlobalPowerUnit 3}

a7Pwrunitlevel33v OBJECT-TYPE
	SYNTAX		DmiInteger
	ACCESS		read-only
	STATUS		mandatory
	DESCRIPTION	"The current 3.3v power level usage, in percent."
	::= {eGlobalPowerUnit 4}

a7Pwrunitmaxwarn33v OBJECT-TYPE
	SYNTAX		DmiDisplaystring
	ACCESS		read-write
	STATUS		mandatory
	DESCRIPTION	"Warning threshold, in percent"
	::= {eGlobalPowerUnit 5}

a7Pwrunitlevel5v OBJECT-TYPE
	SYNTAX		DmiInteger
	ACCESS		read-only
	STATUS		mandatory
	DESCRIPTION	"The current 5v power level usage, in percent."
	::= {eGlobalPowerUnit 6}

a7Pwrunitmaxwarn5v OBJECT-TYPE
	SYNTAX		DmiDisplaystring
	ACCESS		read-write
	STATUS		mandatory
	DESCRIPTION	"Warning threshold, in percent"
	::= {eGlobalPowerUnit 7}

a7Pwrunitlevel12v OBJECT-TYPE
	SYNTAX		DmiInteger
	ACCESS		read-only
	STATUS		mandatory
	DESCRIPTION	"The current 12v power level usage, in percent."
	::= {eGlobalPowerUnit 8}

a7Pwrunitmaxwarn12v OBJECT-TYPE
	SYNTAX		DmiDisplaystring
	ACCESS		read-write
	STATUS		mandatory
	DESCRIPTION	"Warning threshold, in percent"
	::= {eGlobalPowerUnit 9}

a7Pwrunituid OBJECT-TYPE
	SYNTAX		DmiDisplaystring
	ACCESS		read-only
	STATUS		mandatory
	DESCRIPTION	"The unique ID for this power supply unit."
	::= {eGlobalPowerUnit 10}

a7Pwrunitindex OBJECT-TYPE
	SYNTAX		DmiInteger
	ACCESS		read-only
	STATUS		mandatory
	DESCRIPTION	"The index into the power supply unit table."
	::= {eGlobalPowerUnit 11}

SChassisExtension ::= SEQUENCE {
	a8Chassindex                            	DmiInteger,
	a8Chassglobstatus                       	DmiInteger,
	a8Chasstempstatus                       	DmiInteger,
	a8Chasstempprobes                       	DmiOctetstring,
	a8Chassfansstatus                       	DmiInteger,
	a8Chassfansprobes                       	DmiOctetstring,
	a8Chassvoltstatus                       	DmiInteger,
	a8Chassvoltprobes                       	DmiOctetstring,
	a8Chassampstatus                        	DmiInteger,
	a8Chassampprobes                        	DmiOctetstring,
	a8Chasspsstatus                         	DmiInteger,
	a8Chasspwrsupplies                      	DmiOctetstring,
	a8Chassservicetag                       	DmiDisplaystring,
	a8Chassuid                              	DmiDisplaystring,
	a8Chassbackplaneuid                     	DmiDisplaystring,
	a8Chassidentify                         	DmiDisplaystring,
	a8Chassfancontrol                       	DmiDisplaystring,
	a8Chassledconfig                        	DmiDisplaystring,
	a8Chassfaultclear                       	DmiDisplaystring
}

tChassisExtension OBJECT-TYPE
	SYNTAX		SEQUENCE OF SChassisExtension
	ACCESS		not-accessible
	STATUS		mandatory
	DESCRIPTION	"Global status of devices in chassis."
	::= {dmtfGroups 8}

eChassisExtension OBJECT-TYPE
	SYNTAX		SChassisExtension
	ACCESS		not-accessible
	STATUS		mandatory
	DESCRIPTION	""
	INDEX		{DmiComponentIndex, a8Chassindex}
	::= {tChassisExtension 1}

a8Chassindex OBJECT-TYPE
	SYNTAX		DmiInteger
	ACCESS		read-only
	STATUS		mandatory
	DESCRIPTION	"Physical container index"
	::= {eChassisExtension 1}

a8Chassglobstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Global status of all devices in chassis."
	::= {eChassisExtension 2}

a8Chasstempstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Global status of temperature probes."
	::= {eChassisExtension 3}

a8Chasstempprobes OBJECT-TYPE
	SYNTAX		DmiOctetstring
	ACCESS		read-only
	STATUS		mandatory
	DESCRIPTION	"This contains the statuses of all temp probes in the system,
one probe per octet.  The value of each octet is the value of the status
field."
	::= {eChassisExtension 4}

a8Chassfansstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Global status of fan sensors."
	::= {eChassisExtension 5}

a8Chassfansprobes OBJECT-TYPE
	SYNTAX		DmiOctetstring
	ACCESS		read-only
	STATUS		mandatory
	DESCRIPTION	"This contains the statuses of all fan probes in the system,
one probe per octet.  The value of each octet is the value of the status
field."
	::= {eChassisExtension 6}

a8Chassvoltstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Global status of voltage probes."
	::= {eChassisExtension 7}

a8Chassvoltprobes OBJECT-TYPE
	SYNTAX		DmiOctetstring
	ACCESS		read-only
	STATUS		mandatory
	DESCRIPTION	"This contains the statuses of all volt probes in the system,
one probe per octet.  The value of each octet is the value of the status
field."
	::= {eChassisExtension 8}

a8Chassampstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Global status of current probes."
	::= {eChassisExtension 9}

a8Chassampprobes OBJECT-TYPE
	SYNTAX		DmiOctetstring
	ACCESS		read-only
	STATUS		mandatory
	DESCRIPTION	"This contains the statuses of all amp probes in the system,
one probe per octet.  The value of each octet is the value of the status
field."
	::= {eChassisExtension 10}

a8Chasspsstatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Global status of power supplies."
	::= {eChassisExtension 11}

a8Chasspwrsupplies OBJECT-TYPE
	SYNTAX		DmiOctetstring
	ACCESS		read-only
	STATUS		mandatory
	DESCRIPTION	"This contains the statuses of all power supplies in the system,
one probe per octet.  The value of each octet is the value of the status
field."
	::= {eChassisExtension 12}

a8Chassservicetag OBJECT-TYPE
	SYNTAX		DmiDisplaystring
	ACCESS		read-only
	STATUS		mandatory
	DESCRIPTION	"This is the service tag for this chassis, if it exists."
	::= {eChassisExtension 13}

a8Chassuid OBJECT-TYPE
	SYNTAX		DmiDisplaystring
	ACCESS		read-only
	STATUS		mandatory
	DESCRIPTION	"This is the Unique ID for this chassis, if it exists."
	::= {eChassisExtension 14}

a8Chassbackplaneuid OBJECT-TYPE
	SYNTAX		DmiDisplaystring
	ACCESS		read-only
	STATUS		mandatory
	DESCRIPTION	"This is the Unique ID for the backplane in this chassis."
	::= {eChassisExtension 15}

a8Chassidentify OBJECT-TYPE
	SYNTAX		DmiDisplaystring
	ACCESS		read-write
	STATUS		mandatory
	DESCRIPTION	"This attribute is used to visually identify a disk pod or
other chassis by causing its lights to flash. Setting this value to non-zero
turns on the identify, setting it back to zero turns it off."
	::= {eChassisExtension 16}

a8Chassfancontrol OBJECT-TYPE
	SYNTAX		DmiDisplaystring
	ACCESS		read-write
	STATUS		mandatory
	DESCRIPTION	"This attribute is used to control the fan speed in a chassis.
 If the value is 0, then fan control is notavailable.  A value of 2 indicates
maximum cooling.  Avalue of 1 indicates minimize fan noise (and speed)."
	::= {eChassisExtension 17}

a8Chassledconfig OBJECT-TYPE
	SYNTAX		DmiDisplaystring
	ACCESS		read-write
	STATUS		mandatory
	DESCRIPTION	"This attribute is used to configure which fault conditionscause
the fault LED to flash.  If the value is 0, thenthis feature is not available.
 A value of 16 indicatesflash for failure conditions.  A value of 8 indicatesfla
h for failure and warning conditions."
	::= {eChassisExtension 18}

a8Chassfaultclear OBJECT-TYPE
	SYNTAX		DmiDisplaystring
	ACCESS		read-write
	STATUS		mandatory
	DESCRIPTION	"This attribute is used to clear the hard drive fault LED.If
this value is non-zero, then it is available.  Writingany value to this attribut
 will clear the hard drive faultLED."
	::= {eChassisExtension 19}

SPhysicalContainerGlobalTable ::= SEQUENCE {
	a9ContainerOrChassisType                	DmiInteger,
	a9ContainerAssetTag                     	DmiDisplaystring,
	a9ChassisLockPresent                    	DmiInteger,
	a9ContainerChassisBootupState           	DmiInteger,
	a9PowerState                            	DmiInteger,
	a9ThermalState                          	DmiInteger,
	a9FruGroupIndex                         	DmiInteger,
	a9OperationalGroupIndex                 	DmiInteger,
	a9ContainerIndex                        	DmiInteger,
	a9ContainerName                         	DmiDisplaystring,
	a9ContainerLocation                     	DmiDisplaystring,
	a9ContainerSecurityStatus               	DmiInteger
}

tPhysicalContainerGlobalTable OBJECT-TYPE
	SYNTAX		SEQUENCE OF SPhysicalContainerGlobalTable
	ACCESS		not-accessible
	STATUS		mandatory
	DESCRIPTION	"The chassis class contains information about chassis."
	::= {dmtfGroups 9}

ePhysicalContainerGlobalTable OBJECT-TYPE
	SYNTAX		SPhysicalContainerGlobalTable
	ACCESS		not-accessible
	STATUS		mandatory
	DESCRIPTION	""
	INDEX		{DmiComponentIndex, a9ContainerIndex}
	::= {tPhysicalContainerGlobalTable 1}

a9ContainerOrChassisType OBJECT-TYPE
	SYNTAX		INTEGER {
		vOther                                  	(1),
		vUnknown                                	(2),
		vDesktop                                	(3),
		vLowProfileDesktop                      	(4),
		vPizzaBox                               	(5),
		vMiniTower                              	(6),
		vTower                                  	(7),
		vPortable                               	(8),
		vLaptop                                 	(9),
		vNotebook                               	(10),
		vHandheld                               	(11),
		vDockingStation                         	(12),
		vAllInOne                               	(13),
		vSubNotebook                            	(14),
		vSpace-saving                           	(15),
		vLunchBox                               	(16),
		vMainSystemChassis                      	(17),
		vExpansionChassis                       	(18),
		vSubchassis                             	(19),
		vBusExpansionChassis                    	(20),
		vPeripheralChassis                      	(21),
		vRaidChassis                            	(22),
		vRackMountChassis                       	(23)
	}
	ACCESS		read-only
	STATUS		mandatory
	DESCRIPTION	"The type of container or chassis."
	::= {ePhysicalContainerGlobalTable 1}

a9ContainerAssetTag OBJECT-TYPE
	SYNTAX		DmiDisplaystring
	ACCESS		read-write
	STATUS		mandatory
	DESCRIPTION	"The Container asset tag string.  This asset tag string is
writeable by the system administrator."
	::= {ePhysicalContainerGlobalTable 2}

a9ChassisLockPresent OBJECT-TYPE
	SYNTAX		INTEGER {
		vFalse                                  	(0),
		vTrue                                   	(1),
		vUnknown                                	(2)
	}
	ACCESS		read-only
	STATUS		mandatory
	DESCRIPTION	"If true, a chassis lock is present on the container."
	::= {ePhysicalContainerGlobalTable 3}

a9ContainerChassisBootupState OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"The current state of this system when it booted."
	::= {ePhysicalContainerGlobalTable 4}

a9PowerState OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"The current state of the power supply for this system."
	::= {ePhysicalContainerGlobalTable 5}

a9ThermalState OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"The current thermal state of this container."
	::= {ePhysicalContainerGlobalTable 6}

a9FruGroupIndex OBJECT-TYPE
	SYNTAX		DmiInteger
	ACCESS		read-only
	STATUS		mandatory
	DESCRIPTION	"If this is a field Replacable Unit or if it is part of another
FRU, this provides an index into the FRU table; value=-1 indicates that the
group is not a FRU"
	::= {ePhysicalContainerGlobalTable 7}

a9OperationalGroupIndex OBJECT-TYPE
	SYNTAX		DmiInteger
	ACCESS		read-only
	STATUS		mandatory
	DESCRIPTION	"The index into the Operational State table for this device,
if applicable."
	::= {ePhysicalContainerGlobalTable 8}

a9ContainerIndex OBJECT-TYPE
	SYNTAX		DmiInteger
	ACCESS		read-only
	STATUS		mandatory
	DESCRIPTION	"A unique index for the Physical Container in the Physical
Container Global Table."
	::= {ePhysicalContainerGlobalTable 9}

a9ContainerName OBJECT-TYPE
	SYNTAX		DmiDisplaystring
	ACCESS		read-write
	STATUS		mandatory
	DESCRIPTION	"This is any 64-octet long name that the user or system administr
tor wishes to give this specific physical container."
	::= {ePhysicalContainerGlobalTable 10}

a9ContainerLocation OBJECT-TYPE
	SYNTAX		DmiDisplaystring
	ACCESS		read-write
	STATUS		mandatory
	DESCRIPTION	"This attribute is a string name for the location of the containe
.  This attribute is read-write and may be set to any appropriate value by
the user. The string may be 128 octets long."
	::= {ePhysicalContainerGlobalTable 11}

a9ContainerSecurityStatus OBJECT-TYPE
	SYNTAX		INTEGER {
		vOther                                  	(1),
		vUnknown                                	(2),
		vNoSecurityBreachDetected               	(3),
		vContainerSecurityBreachAttempted       	(4),
		vContainerSecurityBreached              	(5)
	}
	ACCESS		read-only
	STATUS		mandatory
	DESCRIPTION	"This attribute describes whether the Container is physically
secure or not.  This includes the state of the door lock, or the boot devices
or the keyboard or mouse."
	::= {ePhysicalContainerGlobalTable 12}

SSystemControl ::= SEQUENCE {
	a10AutomaticCapabilities                	DmiInteger,
	a10AutomaticSettings                    	DmiDisplaystring,
	a10NotificationNumber                   	DmiDisplaystring,
	a10ManualCapabilities                   	DmiInteger,
	a10ManualControl                        	DmiDisplaystring
}

tSystemControl OBJECT-TYPE
	SYNTAX		SEQUENCE OF SSystemControl
	ACCESS		not-accessible
	STATUS		mandatory
	DESCRIPTION	"This group defines whether System Control functions are availabl
 and enabled."
	::= {dmtfGroups 10}

eSystemControl OBJECT-TYPE
	SYNTAX		SSystemControl
	ACCESS		not-accessible
	STATUS		mandatory
	DESCRIPTION	""
	INDEX		{DmiComponentIndex}
	::= {tSystemControl 1}

a10AutomaticCapabilities OBJECT-TYPE
	SYNTAX		DmiInteger
	ACCESS		read-only
	STATUS		mandatory
	DESCRIPTION	"Indicates which Automatic  Capabilities are available for
the current operating system. Encoding is as follows:   0x1 = Supports Reboot
 0x2 = Supports Power Cycle  0x4 = Supports Notification If value is nonzero,
Watchdog is supported."
	::= {eSystemControl 1}

a10AutomaticSettings OBJECT-TYPE
	SYNTAX		DmiDisplaystring
	ACCESS		read-write
	STATUS		mandatory
	DESCRIPTION	"Indicates which Automatic Settings are enabled by the user.
Encoding is as follows:  0x1 = Enabled w/ Reboot 0x2 = Enabled w/ Power Cycle
0x4 = Enabled w/ Notification If value is nonzero, Watchdog is Enabled."
	::= {eSystemControl 2}

a10NotificationNumber OBJECT-TYPE
	SYNTAX		DmiDisplaystring
	ACCESS		read-write
	STATUS		mandatory
	DESCRIPTION	"The number to dial when the watchdog timer elapses."
	::= {eSystemControl 3}

a10ManualCapabilities OBJECT-TYPE
	SYNTAX		DmiInteger
	ACCESS		read-only
	STATUS		mandatory
	DESCRIPTION	"Describes which system reset actions may occur.Bit encodings:
                                 0x1 = Reboot 0x2 = Power Off 0x4 = Power
Cycle 0x8 = Shutdown OS"
	::= {eSystemControl 4}

a10ManualControl OBJECT-TYPE
	SYNTAX		DmiDisplaystring
	ACCESS		read-write
	STATUS		mandatory
	DESCRIPTION	"Setting this value will immediately perform one of the following
functions. Encoding as follows: Bit encoding:  0x1 = Reboot  0x2 = Power
Off  0x4 = Power Cycle  0x8 = Shutdown OS"
	::= {eSystemControl 5}

SEsmEventLog ::= SEQUENCE {
	a11Esmlogindex                          	DmiInteger,
	a11Esmlogdata                           	DmiDisplaystring
}

tEsmEventLog OBJECT-TYPE
	SYNTAX		SEQUENCE OF SEsmEventLog
	ACCESS		not-accessible
	STATUS		mandatory
	DESCRIPTION	"ESM Event Log."
	::= {dmtfGroups 11}

eEsmEventLog OBJECT-TYPE
	SYNTAX		SEsmEventLog
	ACCESS		not-accessible
	STATUS		mandatory
	DESCRIPTION	""
	INDEX		{DmiComponentIndex, a11Esmlogindex}
	::= {tEsmEventLog 1}

a11Esmlogindex OBJECT-TYPE
	SYNTAX		DmiInteger
	ACCESS		read-only
	STATUS		mandatory
	DESCRIPTION	"KEY: The index to this log."
	::= {eEsmEventLog 1}

a11Esmlogdata OBJECT-TYPE
	SYNTAX		DmiDisplaystring
	ACCESS		read-write
	STATUS		mandatory
	DESCRIPTION	"The event log data for the ESM."
	::= {eEsmEventLog 2}

SPostEventLog ::= SEQUENCE {
	a12Postlogindex                         	DmiInteger,
	a12Postlogdata                          	DmiOctetstring
}

tPostEventLog OBJECT-TYPE
	SYNTAX		SEQUENCE OF SPostEventLog
	ACCESS		not-accessible
	STATUS		mandatory
	DESCRIPTION	"POST Codes Event Log."
	::= {dmtfGroups 12}

ePostEventLog OBJECT-TYPE
	SYNTAX		SPostEventLog
	ACCESS		not-accessible
	STATUS		mandatory
	DESCRIPTION	""
	INDEX		{DmiComponentIndex, a12Postlogindex}
	::= {tPostEventLog 1}

a12Postlogindex OBJECT-TYPE
	SYNTAX		DmiInteger
	ACCESS		read-only
	STATUS		mandatory
	DESCRIPTION	"KEY: The index into the post log."
	::= {ePostEventLog 1}

a12Postlogdata OBJECT-TYPE
	SYNTAX		DmiOctetstring
	ACCESS		read-only
	STATUS		mandatory
	DESCRIPTION	"The event log data."
	::= {ePostEventLog 2}

SUserSecurityGroup ::= SEQUENCE {
	a13UserIndex                            	DmiInteger,
	a13UserName                             	DmiDisplaystring,
	a13UserControl                          	DmiDisplaystring
}

tUserSecurityGroup OBJECT-TYPE
	SYNTAX		SEQUENCE OF SUserSecurityGroup
	ACCESS		not-accessible
	STATUS		mandatory
	DESCRIPTION	"Security Group - contains user database: Used by both DSA
and Baseboard components."
	::= {dmtfGroups 13}

eUserSecurityGroup OBJECT-TYPE
	SYNTAX		SUserSecurityGroup
	ACCESS		not-accessible
	STATUS		mandatory
	DESCRIPTION	""
	INDEX		{DmiComponentIndex, a13UserIndex}
	::= {tUserSecurityGroup 1}

a13UserIndex OBJECT-TYPE
	SYNTAX		DmiInteger
	ACCESS		read-only
	STATUS		mandatory
	DESCRIPTION	"Keyed ID for this group."
	::= {eUserSecurityGroup 1}

a13UserName OBJECT-TYPE
	SYNTAX		DmiDisplaystring
	ACCESS		read-only
	STATUS		mandatory
	DESCRIPTION	"User name. First user name is 'create', allows creation."
	::= {eUserSecurityGroup 2}

a13UserControl OBJECT-TYPE
	SYNTAX		DmiDisplaystring
	ACCESS		read-write
	STATUS		mandatory
	DESCRIPTION	"User control. Used for creating/deleting/editing users."
	::= {eUserSecurityGroup 3}

SDialupControl ::= SEQUENCE {
	a14DialupCapability                     	DmiInteger,
	a14CallbackNumber                       	DmiDisplaystring
}

tDialupControl OBJECT-TYPE
	SYNTAX		SEQUENCE OF SDialupControl
	ACCESS		not-accessible
	STATUS		mandatory
	DESCRIPTION	"Dialup Control - contains information used by the ESM dialup
interface."
	::= {dmtfGroups 14}

eDialupControl OBJECT-TYPE
	SYNTAX		SDialupControl
	ACCESS		not-accessible
	STATUS		mandatory
	DESCRIPTION	""
	INDEX		{DmiComponentIndex}
	::= {tDialupControl 1}

a14DialupCapability OBJECT-TYPE
	SYNTAX		INTEGER {
		vFalse                                  	(0),
		vTrue                                   	(1)
	}
	ACCESS		read-only
	STATUS		mandatory
	DESCRIPTION	"Specifies if this system supports dialup."
	::= {eDialupControl 1}

a14CallbackNumber OBJECT-TYPE
	SYNTAX		DmiDisplaystring
	ACCESS		read-write
	STATUS		mandatory
	DESCRIPTION	"The number to callback when a dialup connection is established."
	::= {eDialupControl 2}

SFirmwareInformation ::= SEQUENCE {
	a15FirmwareChassisIndex                 	DmiInteger,
	a15FirmwareIndex                        	DmiInteger,
	a15FirmwareType                         	DmiInteger,
	a15FirmwareVersion                      	DmiDisplaystring,
	a15FirmwareStatus                       	DmiInteger
}

tFirmwareInformation OBJECT-TYPE
	SYNTAX		SEQUENCE OF SFirmwareInformation
	ACCESS		not-accessible
	STATUS		mandatory
	DESCRIPTION	"Firmware Information - Contains version/status of firmware."
	::= {dmtfGroups 15}

eFirmwareInformation OBJECT-TYPE
	SYNTAX		SFirmwareInformation
	ACCESS		not-accessible
	STATUS		mandatory
	DESCRIPTION	""
	INDEX		{DmiComponentIndex, a15FirmwareChassisIndex, a15FirmwareIndex}
	::= {tFirmwareInformation 1}

a15FirmwareChassisIndex OBJECT-TYPE
	SYNTAX		DmiInteger
	ACCESS		read-only
	STATUS		mandatory
	DESCRIPTION	"Firmware chassis index"
	::= {eFirmwareInformation 1}

a15FirmwareIndex OBJECT-TYPE
	SYNTAX		DmiInteger
	ACCESS		read-only
	STATUS		mandatory
	DESCRIPTION	"Index into the firmware information table"
	::= {eFirmwareInformation 2}

a15FirmwareType OBJECT-TYPE
	SYNTAX		INTEGER {
		vOther                                  	(1),
		vUnknown                                	(2),
		vBios                                   	(3),
		vEsm                                    	(4),
		vPspb                                   	(5),
		vBackplane                              	(6)
	}
	ACCESS		read-write
	STATUS		mandatory
	DESCRIPTION	"The type of this firmware."
	::= {eFirmwareInformation 3}

a15FirmwareVersion OBJECT-TYPE
	SYNTAX		DmiDisplaystring
	ACCESS		read-only
	STATUS		mandatory
	DESCRIPTION	"Version level of this firmware"
	::= {eFirmwareInformation 4}

a15FirmwareStatus OBJECT-TYPE
	SYNTAX		INTEGER {
		vOther                                  	(1),
		vUnknown                                	(2),
		vOk                                     	(3),
		vNon-critical                           	(4),
		vCritical                               	(5),
		vNon-recoverable                        	(6)
	}
	ACCESS		read-only
	STATUS		mandatory
	DESCRIPTION	"Current status of this firmware, if applicable"
	::= {eFirmwareInformation 5}

SMiftomib ::= SEQUENCE {
	a99DellBaseboardMib                     	DmiDisplaystring,
	a99MibOid                               	DmiDisplaystring,
	a99DisableTraps                         	DmiInteger
}

tMiftomib OBJECT-TYPE
	SYNTAX		SEQUENCE OF SMiftomib
	ACCESS		not-accessible
	STATUS		mandatory
	DESCRIPTION	"This group maps the DMI attributes to SNMP."
	::= {dmtfGroups 99}

eMiftomib OBJECT-TYPE
	SYNTAX		SMiftomib
	ACCESS		not-accessible
	STATUS		mandatory
	DESCRIPTION	""
	INDEX		{DmiComponentIndex}
	::= {tMiftomib 1}

a99DellBaseboardMib OBJECT-TYPE
	SYNTAX		DmiDisplaystring
	ACCESS		read-only
	STATUS		mandatory
	DESCRIPTION	"The MIB name that defines thif MIF"
	::= {eMiftomib 1}

a99MibOid OBJECT-TYPE
	SYNTAX		DmiDisplaystring
	ACCESS		read-only
	STATUS		mandatory
	DESCRIPTION	"The MIB OID that corresponds to this MIF"
	::= {eMiftomib 2}

a99DisableTraps OBJECT-TYPE
	SYNTAX		DmiInteger
	ACCESS		read-only
	STATUS		mandatory
	DESCRIPTION	"Setting this value to 1 disables trap generation."
	::= {eMiftomib 3}

STemperatureProbeAlerts ::= SEQUENCE {
	a102EventType                           	DmiInteger,
	a102EventSeverity                       	DmiInteger,
	a102IsEventStateBased                   	DmiInteger,
	a102EventStateKey                       	DmiInteger,
	a102AssociatedGroup                     	DmiDisplaystring,
	a102EventSystem                         	DmiInteger,
	a102EventSubsystem                      	DmiInteger,
	a102EventSolution                       	DmiInteger,
	a102InstanceDataPresent                 	DmiInteger,
	a102VendorSpecificMessage               	DmiDisplaystring,
	a102VendorSpecificData                  	DmiOctetstring,
	a102VendorTrapNumber                    	DmiInteger
}

tTemperatureProbeAlerts OBJECT-TYPE
	SYNTAX		SEQUENCE OF STemperatureProbeAlerts
	ACCESS		not-accessible
	STATUS		mandatory
	DESCRIPTION	""
	::= {dmtfGroups 102}

eTemperatureProbeAlerts OBJECT-TYPE
	SYNTAX		STemperatureProbeAlerts
	ACCESS		not-accessible
	STATUS		mandatory
	DESCRIPTION	""
	INDEX		{DmiComponentIndex, a102AssociatedGroup}
	::= {tTemperatureProbeAlerts 1}

a102EventType OBJECT-TYPE
	SYNTAX		INTEGER {
		vCoolingDeviceStatusChange              	(1)
	}
	ACCESS		read-only
	STATUS		mandatory
	DESCRIPTION	"The type of event that has occurred."
	::= {eTemperatureProbeAlerts 1}

a102EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eTemperatureProbeAlerts 2}

a102IsEventStateBased OBJECT-TYPE
	SYNTAX		INTEGER {
		vFalse                                  	(0),
		vTrue                                   	(1)
	}
	ACCESS		read-only
	STATUS		mandatory
	DESCRIPTION	""
	::= {eTemperatureProbeAlerts 3}

a102EventStateKey OBJECT-TYPE
	SYNTAX		DmiInteger
	ACCESS		read-only
	STATUS		mandatory
	DESCRIPTION	""
	::= {eTemperatureProbeAlerts 4}

a102AssociatedGroup OBJECT-TYPE
	SYNTAX		DmiDisplaystring
	ACCESS		read-only
	STATUS		mandatory
	DESCRIPTION	""
	::= {eTemperatureProbeAlerts 5}

a102EventSystem OBJECT-TYPE
	SYNTAX		DmiInteger
	ACCESS		read-only
	STATUS		mandatory
	DESCRIPTION	""
	::= {eTemperatureProbeAlerts 6}

a102EventSubsystem OBJECT-TYPE
	SYNTAX		DmiInteger
	ACCESS		read-only
	STATUS		mandatory
	DESCRIPTION	""
	::= {eTemperatureProbeAlerts 7}

a102EventSolution OBJECT-TYPE
	SYNTAX		INTEGER {
		vOther                                  	(1),
		vUnknown                                	(2)
	}
	ACCESS		read-only
	STATUS		mandatory
	DESCRIPTION	""
	::= {eTemperatureProbeAlerts 8}

a102InstanceDataPresent OBJECT-TYPE
	SYNTAX		INTEGER {
		vFalse                                  	(0),
		vTrue                                   	(1)
	}
	ACCESS		read-only
	STATUS		mandatory
	DESCRIPTION	""
	::= {eTemperatureProbeAlerts 9}

a102VendorSpecificMessage OBJECT-TYPE
	SYNTAX		DmiDisplaystring
	ACCESS		read-only
	STATUS		mandatory
	DESCRIPTION	""
	::= {eTemperatureProbeAlerts 10}

a102VendorSpecificData OBJECT-TYPE
	SYNTAX		DmiOctetstring
	ACCESS		read-only
	STATUS		mandatory
	DESCRIPTION	""
	::= {eTemperatureProbeAlerts 11}

a102VendorTrapNumber OBJECT-TYPE
	SYNTAX		DmiInteger
	ACCESS		read-only
	STATUS		mandatory
	DESCRIPTION	""
	::= {eTemperatureProbeAlerts 12}

SFanSensorAlerts ::= SEQUENCE {
	a103EventType                           	DmiInteger,
	a103EventSeverity                       	DmiInteger,
	a103IsEventStateBased                   	DmiInteger,
	a103EventStateKey                       	DmiInteger,
	a103AssociatedGroup                     	DmiDisplaystring,
	a103EventSystem                         	DmiInteger,
	a103EventSubsystem                      	DmiInteger,
	a103EventSolution                       	DmiInteger,
	a103InstanceDataPresent                 	DmiInteger,
	a103VendorSpecificMessage               	DmiDisplaystring,
	a103VendorSpecificData                  	DmiOctetstring,
	a103VendorTrapNumber                    	DmiInteger
}

tFanSensorAlerts OBJECT-TYPE
	SYNTAX		SEQUENCE OF SFanSensorAlerts
	ACCESS		not-accessible
	STATUS		mandatory
	DESCRIPTION	""
	::= {dmtfGroups 103}

eFanSensorAlerts OBJECT-TYPE
	SYNTAX		SFanSensorAlerts
	ACCESS		not-accessible
	STATUS		mandatory
	DESCRIPTION	""
	INDEX		{DmiComponentIndex, a103AssociatedGroup}
	::= {tFanSensorAlerts 1}

a103EventType OBJECT-TYPE
	SYNTAX		INTEGER {
		vCoolingDeviceStatusChange              	(1)
	}
	ACCESS		read-only
	STATUS		mandatory
	DESCRIPTION	"The type of event that has occurred."
	::= {eFanSensorAlerts 1}

a103EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eFanSensorAlerts 2}

a103IsEventStateBased OBJECT-TYPE
	SYNTAX		INTEGER {
		vFalse                                  	(0),
		vTrue                                   	(1)
	}
	ACCESS		read-only
	STATUS		mandatory
	DESCRIPTION	""
	::= {eFanSensorAlerts 3}

a103EventStateKey OBJECT-TYPE
	SYNTAX		DmiInteger
	ACCESS		read-only
	STATUS		mandatory
	DESCRIPTION	""
	::= {eFanSensorAlerts 4}

a103AssociatedGroup OBJECT-TYPE
	SYNTAX		DmiDisplaystring
	ACCESS		read-only
	STATUS		mandatory
	DESCRIPTION	""
	::= {eFanSensorAlerts 5}

a103EventSystem OBJECT-TYPE
	SYNTAX		DmiInteger
	ACCESS		read-only
	STATUS		mandatory
	DESCRIPTION	""
	::= {eFanSensorAlerts 6}

a103EventSubsystem OBJECT-TYPE
	SYNTAX		DmiInteger
	ACCESS		read-only
	STATUS		mandatory
	DESCRIPTION	""
	::= {eFanSensorAlerts 7}

a103EventSolution OBJECT-TYPE
	SYNTAX		INTEGER {
		vOther                                  	(1),
		vUnknown                                	(2)
	}
	ACCESS		read-only
	STATUS		mandatory
	DESCRIPTION	""
	::= {eFanSensorAlerts 8}

a103InstanceDataPresent OBJECT-TYPE
	SYNTAX		INTEGER {
		vFalse                                  	(0),
		vTrue                                   	(1)
	}
	ACCESS		read-only
	STATUS		mandatory
	DESCRIPTION	""
	::= {eFanSensorAlerts 9}

a103VendorSpecificMessage OBJECT-TYPE
	SYNTAX		DmiDisplaystring
	ACCESS		read-only
	STATUS		mandatory
	DESCRIPTION	""
	::= {eFanSensorAlerts 10}

a103VendorSpecificData OBJECT-TYPE
	SYNTAX		DmiOctetstring
	ACCESS		read-only
	STATUS		mandatory
	DESCRIPTION	""
	::= {eFanSensorAlerts 11}

a103VendorTrapNumber OBJECT-TYPE
	SYNTAX		DmiInteger
	ACCESS		read-only
	STATUS		mandatory
	DESCRIPTION	""
	::= {eFanSensorAlerts 12}

SVoltageProbeAlerts ::= SEQUENCE {
	a104EventType                           	DmiInteger,
	a104EventSeverity                       	DmiInteger,
	a104IsEventStateBased                   	DmiInteger,
	a104EventStateKey                       	DmiInteger,
	a104AssociatedGroup                     	DmiDisplaystring,
	a104EventSystem                         	DmiInteger,
	a104EventSubsystem                      	DmiInteger,
	a104EventSolution                       	DmiInteger,
	a104InstanceDataPresent                 	DmiInteger,
	a104VendorSpecificMessage               	DmiDisplaystring,
	a104VendorSpecificData                  	DmiOctetstring,
	a104VendorTrapNumber                    	DmiInteger
}

tVoltageProbeAlerts OBJECT-TYPE
	SYNTAX		SEQUENCE OF SVoltageProbeAlerts
	ACCESS		not-accessible
	STATUS		mandatory
	DESCRIPTION	""
	::= {dmtfGroups 104}

eVoltageProbeAlerts OBJECT-TYPE
	SYNTAX		SVoltageProbeAlerts
	ACCESS		not-accessible
	STATUS		mandatory
	DESCRIPTION	""
	INDEX		{DmiComponentIndex, a104AssociatedGroup}
	::= {tVoltageProbeAlerts 1}

a104EventType OBJECT-TYPE
	SYNTAX		INTEGER {
		vPowerSupplyStatusChange                	(1)
	}
	ACCESS		read-only
	STATUS		mandatory
	DESCRIPTION	"The type of event that has occurred."
	::= {eVoltageProbeAlerts 1}

a104EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eVoltageProbeAlerts 2}

a104IsEventStateBased OBJECT-TYPE
	SYNTAX		INTEGER {
		vFalse                                  	(0),
		vTrue                                   	(1)
	}
	ACCESS		read-only
	STATUS		mandatory
	DESCRIPTION	""
	::= {eVoltageProbeAlerts 3}

a104EventStateKey OBJECT-TYPE
	SYNTAX		DmiInteger
	ACCESS		read-only
	STATUS		mandatory
	DESCRIPTION	""
	::= {eVoltageProbeAlerts 4}

a104AssociatedGroup OBJECT-TYPE
	SYNTAX		DmiDisplaystring
	ACCESS		read-only
	STATUS		mandatory
	DESCRIPTION	""
	::= {eVoltageProbeAlerts 5}

a104EventSystem OBJECT-TYPE
	SYNTAX		DmiInteger
	ACCESS		read-only
	STATUS		mandatory
	DESCRIPTION	""
	::= {eVoltageProbeAlerts 6}

a104EventSubsystem OBJECT-TYPE
	SYNTAX		DmiInteger
	ACCESS		read-only
	STATUS		mandatory
	DESCRIPTION	""
	::= {eVoltageProbeAlerts 7}

a104EventSolution OBJECT-TYPE
	SYNTAX		INTEGER {
		vOther                                  	(1),
		vUnknown                                	(2)
	}
	ACCESS		read-only
	STATUS		mandatory
	DESCRIPTION	""
	::= {eVoltageProbeAlerts 8}

a104InstanceDataPresent OBJECT-TYPE
	SYNTAX		INTEGER {
		vFalse                                  	(0),
		vTrue                                   	(1)
	}
	ACCESS		read-only
	STATUS		mandatory
	DESCRIPTION	""
	::= {eVoltageProbeAlerts 9}

a104VendorSpecificMessage OBJECT-TYPE
	SYNTAX		DmiDisplaystring
	ACCESS		read-only
	STATUS		mandatory
	DESCRIPTION	""
	::= {eVoltageProbeAlerts 10}

a104VendorSpecificData OBJECT-TYPE
	SYNTAX		DmiOctetstring
	ACCESS		read-only
	STATUS		mandatory
	DESCRIPTION	""
	::= {eVoltageProbeAlerts 11}

a104VendorTrapNumber OBJECT-TYPE
	SYNTAX		DmiInteger
	ACCESS		read-only
	STATUS		mandatory
	DESCRIPTION	""
	::= {eVoltageProbeAlerts 12}

SCurrentProbeAlerts ::= SEQUENCE {
	a105EventType                           	DmiInteger,
	a105EventSeverity                       	DmiInteger,
	a105IsEventStateBased                   	DmiInteger,
	a105EventStateKey                       	DmiInteger,
	a105AssociatedGroup                     	DmiDisplaystring,
	a105EventSystem                         	DmiInteger,
	a105EventSubsystem                      	DmiInteger,
	a105EventSolution                       	DmiInteger,
	a105InstanceDataPresent                 	DmiInteger,
	a105VendorSpecificMessage               	DmiDisplaystring,
	a105VendorSpecificData                  	DmiOctetstring,
	a105VendorTrapNumber                    	DmiInteger
}

tCurrentProbeAlerts OBJECT-TYPE
	SYNTAX		SEQUENCE OF SCurrentProbeAlerts
	ACCESS		not-accessible
	STATUS		mandatory
	DESCRIPTION	""
	::= {dmtfGroups 105}

eCurrentProbeAlerts OBJECT-TYPE
	SYNTAX		SCurrentProbeAlerts
	ACCESS		not-accessible
	STATUS		mandatory
	DESCRIPTION	""
	INDEX		{DmiComponentIndex, a105AssociatedGroup}
	::= {tCurrentProbeAlerts 1}

a105EventType OBJECT-TYPE
	SYNTAX		INTEGER {
		vPowerSupplyStatusChange                	(1)
	}
	ACCESS		read-only
	STATUS		mandatory
	DESCRIPTION	"The type of event that has occurred."
	::= {eCurrentProbeAlerts 1}

a105EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eCurrentProbeAlerts 2}

a105IsEventStateBased OBJECT-TYPE
	SYNTAX		INTEGER {
		vFalse                                  	(0),
		vTrue                                   	(1)
	}
	ACCESS		read-only
	STATUS		mandatory
	DESCRIPTION	""
	::= {eCurrentProbeAlerts 3}

a105EventStateKey OBJECT-TYPE
	SYNTAX		DmiInteger
	ACCESS		read-only
	STATUS		mandatory
	DESCRIPTION	""
	::= {eCurrentProbeAlerts 4}

a105AssociatedGroup OBJECT-TYPE
	SYNTAX		DmiDisplaystring
	ACCESS		read-only
	STATUS		mandatory
	DESCRIPTION	""
	::= {eCurrentProbeAlerts 5}

a105EventSystem OBJECT-TYPE
	SYNTAX		DmiInteger
	ACCESS		read-only
	STATUS		mandatory
	DESCRIPTION	""
	::= {eCurrentProbeAlerts 6}

a105EventSubsystem OBJECT-TYPE
	SYNTAX		DmiInteger
	ACCESS		read-only
	STATUS		mandatory
	DESCRIPTION	""
	::= {eCurrentProbeAlerts 7}

a105EventSolution OBJECT-TYPE
	SYNTAX		INTEGER {
		vOther                                  	(1),
		vUnknown                                	(2)
	}
	ACCESS		read-only
	STATUS		mandatory
	DESCRIPTION	""
	::= {eCurrentProbeAlerts 8}

a105InstanceDataPresent OBJECT-TYPE
	SYNTAX		INTEGER {
		vFalse                                  	(0),
		vTrue                                   	(1)
	}
	ACCESS		read-only
	STATUS		mandatory
	DESCRIPTION	""
	::= {eCurrentProbeAlerts 9}

a105VendorSpecificMessage OBJECT-TYPE
	SYNTAX		DmiDisplaystring
	ACCESS		read-only
	STATUS		mandatory
	DESCRIPTION	""
	::= {eCurrentProbeAlerts 10}

a105VendorSpecificData OBJECT-TYPE
	SYNTAX		DmiOctetstring
	ACCESS		read-only
	STATUS		mandatory
	DESCRIPTION	""
	::= {eCurrentProbeAlerts 11}

a105VendorTrapNumber OBJECT-TYPE
	SYNTAX		DmiInteger
	ACCESS		read-only
	STATUS		mandatory
	DESCRIPTION	""
	::= {eCurrentProbeAlerts 12}

SPowerUnitAlerts ::= SEQUENCE {
	a107EventType                           	DmiInteger,
	a107EventSeverity                       	DmiInteger,
	a107IsEventStateBased                   	DmiInteger,
	a107EventStateKey                       	DmiInteger,
	a107AssociatedGroup                     	DmiDisplaystring,
	a107EventSystem                         	DmiInteger,
	a107EventSubsystem                      	DmiInteger,
	a107EventSolution                       	DmiInteger,
	a107InstanceDataPresent                 	DmiInteger,
	a107VendorSpecificMessage               	DmiDisplaystring,
	a107VendorSpecificData                  	DmiOctetstring,
	a107VendorTrapNumber                    	DmiInteger
}

tPowerUnitAlerts OBJECT-TYPE
	SYNTAX		SEQUENCE OF SPowerUnitAlerts
	ACCESS		not-accessible
	STATUS		mandatory
	DESCRIPTION	""
	::= {dmtfGroups 107}

ePowerUnitAlerts OBJECT-TYPE
	SYNTAX		SPowerUnitAlerts
	ACCESS		not-accessible
	STATUS		mandatory
	DESCRIPTION	""
	INDEX		{DmiComponentIndex, a107AssociatedGroup}
	::= {tPowerUnitAlerts 1}

a107EventType OBJECT-TYPE
	SYNTAX		INTEGER {
		vPowerSupplyRedundancyChange            	(1),
		vPowerSupplyStatusChange                	(2)
	}
	ACCESS		read-only
	STATUS		mandatory
	DESCRIPTION	"The type of event that has occurred."
	::= {ePowerUnitAlerts 1}

a107EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {ePowerUnitAlerts 2}

a107IsEventStateBased OBJECT-TYPE
	SYNTAX		INTEGER {
		vFalse                                  	(0),
		vTrue                                   	(1)
	}
	ACCESS		read-only
	STATUS		mandatory
	DESCRIPTION	""
	::= {ePowerUnitAlerts 3}

a107EventStateKey OBJECT-TYPE
	SYNTAX		DmiInteger
	ACCESS		read-only
	STATUS		mandatory
	DESCRIPTION	""
	::= {ePowerUnitAlerts 4}

a107AssociatedGroup OBJECT-TYPE
	SYNTAX		DmiDisplaystring
	ACCESS		read-only
	STATUS		mandatory
	DESCRIPTION	""
	::= {ePowerUnitAlerts 5}

a107EventSystem OBJECT-TYPE
	SYNTAX		DmiInteger
	ACCESS		read-only
	STATUS		mandatory
	DESCRIPTION	""
	::= {ePowerUnitAlerts 6}

a107EventSubsystem OBJECT-TYPE
	SYNTAX		DmiInteger
	ACCESS		read-only
	STATUS		mandatory
	DESCRIPTION	""
	::= {ePowerUnitAlerts 7}

a107EventSolution OBJECT-TYPE
	SYNTAX		INTEGER {
		vOther                                  	(1),
		vUnknown                                	(2)
	}
	ACCESS		read-only
	STATUS		mandatory
	DESCRIPTION	""
	::= {ePowerUnitAlerts 8}

a107InstanceDataPresent OBJECT-TYPE
	SYNTAX		INTEGER {
		vFalse                                  	(0),
		vTrue                                   	(1)
	}
	ACCESS		read-only
	STATUS		mandatory
	DESCRIPTION	""
	::= {ePowerUnitAlerts 9}

a107VendorSpecificMessage OBJECT-TYPE
	SYNTAX		DmiDisplaystring
	ACCESS		read-only
	STATUS		mandatory
	DESCRIPTION	""
	::= {ePowerUnitAlerts 10}

a107VendorSpecificData OBJECT-TYPE
	SYNTAX		DmiOctetstring
	ACCESS		read-only
	STATUS		mandatory
	DESCRIPTION	""
	::= {ePowerUnitAlerts 11}

a107VendorTrapNumber OBJECT-TYPE
	SYNTAX		DmiInteger
	ACCESS		read-only
	STATUS		mandatory
	DESCRIPTION	""
	::= {ePowerUnitAlerts 12}

SChassisEventGeneration ::= SEQUENCE {
	a108EventType                           	DmiInteger,
	a108EventSeverity                       	DmiInteger,
	a108IsEventStateBased                   	DmiInteger,
	a108EventStateKey                       	DmiInteger,
	a108AssociatedGroup                     	DmiDisplaystring,
	a108EventSystem                         	DmiInteger,
	a108EventSubsystem                      	DmiInteger,
	a108EventSolution                       	DmiInteger,
	a108InstanceDataPresent                 	DmiInteger,
	a108VendorSpecificMessage               	DmiDisplaystring,
	a108VendorSpecificData                  	DmiOctetstring,
	a108VendorTrapNumber                    	DmiInteger
}

tChassisEventGeneration OBJECT-TYPE
	SYNTAX		SEQUENCE OF SChassisEventGeneration
	ACCESS		not-accessible
	STATUS		mandatory
	DESCRIPTION	""
	::= {dmtfGroups 108}

eChassisEventGeneration OBJECT-TYPE
	SYNTAX		SChassisEventGeneration
	ACCESS		not-accessible
	STATUS		mandatory
	DESCRIPTION	""
	INDEX		{DmiComponentIndex, a108AssociatedGroup}
	::= {tChassisEventGeneration 1}

a108EventType OBJECT-TYPE
	SYNTAX		INTEGER {
		vMemoryEccError                         	(1)
	}
	ACCESS		read-only
	STATUS		mandatory
	DESCRIPTION	"The type of event that has occurred."
	::= {eChassisEventGeneration 1}

a108EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eChassisEventGeneration 2}

a108IsEventStateBased OBJECT-TYPE
	SYNTAX		INTEGER {
		vFalse                                  	(0),
		vTrue                                   	(1)
	}
	ACCESS		read-only
	STATUS		mandatory
	DESCRIPTION	""
	::= {eChassisEventGeneration 3}

a108EventStateKey OBJECT-TYPE
	SYNTAX		DmiInteger
	ACCESS		read-only
	STATUS		mandatory
	DESCRIPTION	""
	::= {eChassisEventGeneration 4}

a108AssociatedGroup OBJECT-TYPE
	SYNTAX		DmiDisplaystring
	ACCESS		read-only
	STATUS		mandatory
	DESCRIPTION	""
	::= {eChassisEventGeneration 5}

a108EventSystem OBJECT-TYPE
	SYNTAX		DmiInteger
	ACCESS		read-only
	STATUS		mandatory
	DESCRIPTION	""
	::= {eChassisEventGeneration 6}

a108EventSubsystem OBJECT-TYPE
	SYNTAX		DmiInteger
	ACCESS		read-only
	STATUS		mandatory
	DESCRIPTION	""
	::= {eChassisEventGeneration 7}

a108EventSolution OBJECT-TYPE
	SYNTAX		INTEGER {
		vOther                                  	(1),
		vUnknown                                	(2)
	}
	ACCESS		read-only
	STATUS		mandatory
	DESCRIPTION	""
	::= {eChassisEventGeneration 8}

a108InstanceDataPresent OBJECT-TYPE
	SYNTAX		INTEGER {
		vFalse                                  	(0),
		vTrue                                   	(1)
	}
	ACCESS		read-only
	STATUS		mandatory
	DESCRIPTION	""
	::= {eChassisEventGeneration 9}

a108VendorSpecificMessage OBJECT-TYPE
	SYNTAX		DmiDisplaystring
	ACCESS		read-only
	STATUS		mandatory
	DESCRIPTION	""
	::= {eChassisEventGeneration 10}

a108VendorSpecificData OBJECT-TYPE
	SYNTAX		DmiOctetstring
	ACCESS		read-only
	STATUS		mandatory
	DESCRIPTION	""
	::= {eChassisEventGeneration 11}

a108VendorTrapNumber OBJECT-TYPE
	SYNTAX		DmiInteger
	ACCESS		read-only
	STATUS		mandatory
	DESCRIPTION	""
	::= {eChassisEventGeneration 12}

SContainerEventGeneration ::= SEQUENCE {
	a109EventType                           	DmiInteger,
	a109EventSeverity                       	DmiInteger,
	a109IsEventStateBased                   	DmiInteger,
	a109EventStateKey                       	DmiInteger,
	a109AssociatedGroup                     	DmiDisplaystring,
	a109EventSystem                         	DmiInteger,
	a109EventSubsystem                      	DmiInteger,
	a109EventSolution                       	DmiInteger,
	a109InstanceDataPresent                 	DmiInteger,
	a109VendorSpecificMessage               	DmiDisplaystring,
	a109VendorSpecificData                  	DmiOctetstring,
	a109VendorTrapNumber                    	DmiInteger
}

tContainerEventGeneration OBJECT-TYPE
	SYNTAX		SEQUENCE OF SContainerEventGeneration
	ACCESS		not-accessible
	STATUS		mandatory
	DESCRIPTION	""
	::= {dmtfGroups 109}

eContainerEventGeneration OBJECT-TYPE
	SYNTAX		SContainerEventGeneration
	ACCESS		not-accessible
	STATUS		mandatory
	DESCRIPTION	""
	INDEX		{DmiComponentIndex, a109AssociatedGroup}
	::= {tContainerEventGeneration 1}

a109EventType OBJECT-TYPE
	SYNTAX		INTEGER {
		vSecuritySettingsChange                 	(1),
		vPowerSupplyStatusChange                	(2),
		vCoolingDeviceStatusChange              	(3),
		vPhysicalDeviceStatusChange             	(4),
		vLogicalDeviceStatusChange              	(5),
		vContainerSecurityBreach                	(6),
		vConfigurationError                     	(7)
	}
	ACCESS		read-only
	STATUS		mandatory
	DESCRIPTION	"The type of event that has occurred."
	::= {eContainerEventGeneration 1}

a109EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eContainerEventGeneration 2}

a109IsEventStateBased OBJECT-TYPE
	SYNTAX		INTEGER {
		vFalse                                  	(0),
		vTrue                                   	(1)
	}
	ACCESS		read-only
	STATUS		mandatory
	DESCRIPTION	""
	::= {eContainerEventGeneration 3}

a109EventStateKey OBJECT-TYPE
	SYNTAX		DmiInteger
	ACCESS		read-only
	STATUS		mandatory
	DESCRIPTION	""
	::= {eContainerEventGeneration 4}

a109AssociatedGroup OBJECT-TYPE
	SYNTAX		DmiDisplaystring
	ACCESS		read-only
	STATUS		mandatory
	DESCRIPTION	""
	::= {eContainerEventGeneration 5}

a109EventSystem OBJECT-TYPE
	SYNTAX		DmiInteger
	ACCESS		read-only
	STATUS		mandatory
	DESCRIPTION	""
	::= {eContainerEventGeneration 6}

a109EventSubsystem OBJECT-TYPE
	SYNTAX		DmiInteger
	ACCESS		read-only
	STATUS		mandatory
	DESCRIPTION	""
	::= {eContainerEventGeneration 7}

a109EventSolution OBJECT-TYPE
	SYNTAX		INTEGER {
		vOther                                  	(1),
		vUnknown                                	(2)
	}
	ACCESS		read-only
	STATUS		mandatory
	DESCRIPTION	""
	::= {eContainerEventGeneration 8}

a109InstanceDataPresent OBJECT-TYPE
	SYNTAX		INTEGER {
		vFalse                                  	(0),
		vTrue                                   	(1)
	}
	ACCESS		read-only
	STATUS		mandatory
	DESCRIPTION	""
	::= {eContainerEventGeneration 9}

a109VendorSpecificMessage OBJECT-TYPE
	SYNTAX		DmiDisplaystring
	ACCESS		read-only
	STATUS		mandatory
	DESCRIPTION	""
	::= {eContainerEventGeneration 10}

a109VendorSpecificData OBJECT-TYPE
	SYNTAX		DmiOctetstring
	ACCESS		read-only
	STATUS		mandatory
	DESCRIPTION	""
	::= {eContainerEventGeneration 11}

a109VendorTrapNumber OBJECT-TYPE
	SYNTAX		DmiInteger
	ACCESS		read-only
	STATUS		mandatory
	DESCRIPTION	""
	::= {eContainerEventGeneration 12}

SResetEventGeneration ::= SEQUENCE {
	a110EventType                           	DmiInteger,
	a110EventSeverity                       	DmiInteger,
	a110IsEventStateBased                   	DmiInteger,
	a110EventStateKey                       	DmiInteger,
	a110AssociatedGroup                     	DmiDisplaystring,
	a110EventSystem                         	DmiInteger,
	a110EventSubsystem                      	DmiInteger,
	a110EventSolution                       	DmiInteger,
	a110InstanceDataPresent                 	DmiInteger,
	a110VendorSpecificMessage               	DmiDisplaystring,
	a110VendorSpecificData                  	DmiOctetstring,
	a110VendorTrapNumber                    	DmiInteger
}

tResetEventGeneration OBJECT-TYPE
	SYNTAX		SEQUENCE OF SResetEventGeneration
	ACCESS		not-accessible
	STATUS		mandatory
	DESCRIPTION	""
	::= {dmtfGroups 110}

eResetEventGeneration OBJECT-TYPE
	SYNTAX		SResetEventGeneration
	ACCESS		not-accessible
	STATUS		mandatory
	DESCRIPTION	""
	INDEX		{DmiComponentIndex, a110AssociatedGroup}
	::= {tResetEventGeneration 1}

a110EventType OBJECT-TYPE
	SYNTAX		INTEGER {
		vSystemUp                               	(1)
	}
	ACCESS		read-only
	STATUS		mandatory
	DESCRIPTION	"The type of event that has occurred."
	::= {eResetEventGeneration 1}

a110EventSeverity OBJECT-TYPE
	SYNTAX		INTEGER {
		vMonitor                                	(1),
		vInformation                            	(2),
		vOk                                     	(4),
		vNon-critical                           	(8),
		vCritical                               	(10),
		vNon-recoverable                        	(12)
	}
	ACCESS		read-only
	STATUS		mandatory
	DESCRIPTION	"The severity of this event."
	::= {eResetEventGeneration 2}

a110IsEventStateBased OBJECT-TYPE
	SYNTAX		INTEGER {
		vFalse                                  	(0),
		vTrue                                   	(1)
	}
	ACCESS		read-only
	STATUS		mandatory
	DESCRIPTION	""
	::= {eResetEventGeneration 3}

a110EventStateKey OBJECT-TYPE
	SYNTAX		DmiInteger
	ACCESS		read-only
	STATUS		mandatory
	DESCRIPTION	""
	::= {eResetEventGeneration 4}

a110AssociatedGroup OBJECT-TYPE
	SYNTAX		DmiDisplaystring
	ACCESS		read-only
	STATUS		mandatory
	DESCRIPTION	""
	::= {eResetEventGeneration 5}

a110EventSystem OBJECT-TYPE
	SYNTAX		DmiInteger
	ACCESS		read-only
	STATUS		mandatory
	DESCRIPTION	""
	::= {eResetEventGeneration 6}

a110EventSubsystem OBJECT-TYPE
	SYNTAX		DmiInteger
	ACCESS		read-only
	STATUS		mandatory
	DESCRIPTION	""
	::= {eResetEventGeneration 7}

a110EventSolution OBJECT-TYPE
	SYNTAX		INTEGER {
		vOther                                  	(1),
		vUnknown                                	(2)
	}
	ACCESS		read-only
	STATUS		mandatory
	DESCRIPTION	""
	::= {eResetEventGeneration 8}

a110InstanceDataPresent OBJECT-TYPE
	SYNTAX		INTEGER {
		vFalse                                  	(0),
		vTrue                                   	(1)
	}
	ACCESS		read-only
	STATUS		mandatory
	DESCRIPTION	""
	::= {eResetEventGeneration 9}

a110VendorSpecificMessage OBJECT-TYPE
	SYNTAX		DmiDisplaystring
	ACCESS		read-only
	STATUS		mandatory
	DESCRIPTION	""
	::= {eResetEventGeneration 10}

a110VendorSpecificData OBJECT-TYPE
	SYNTAX		DmiOctetstring
	ACCESS		read-only
	STATUS		mandatory
	DESCRIPTION	""
	::= {eResetEventGeneration 11}

a110VendorTrapNumber OBJECT-TYPE
	SYNTAX		DmiInteger
	ACCESS		read-only
	STATUS		mandatory
	DESCRIPTION	""
	::= {eResetEventGeneration 12}


-- Below are the TRAP definitions for the dell server baseboard

tTrapGroup OBJECT-TYPE
    SYNTAX        SEQUENCE OF STrapGroup
    ACCESS        not-accessible
    STATUS        mandatory
    DESCRIPTION    "This group defines attributes needed for Trap
            definition. This group does not exist in MIF file"
    ::= {dmtfGroups 9999}

STrapGroup ::= SEQUENCE {
    a9999AlertSystem         OCTET STRING,
    a9999AlertGroup          OCTET STRING,
    a9999AlertMessage        OCTET STRING,
    a9999AlertSeverity       DmiInteger,
    a9999AlertData           OCTET STRING
}

eTrapGroup OBJECT-TYPE
    SYNTAX        STrapGroup
    ACCESS        not-accessible
    STATUS        mandatory
    DESCRIPTION    ""
    INDEX        {DmiComponentIndex}
    ::= {tTrapGroup 1}

a9999AlertSystem  OBJECT-TYPE
    SYNTAX        OCTET STRING
    ACCESS        read-only
    STATUS        mandatory
    DESCRIPTION    "Name of the system generating the alert"
    ::= {eTrapGroup 1}

a9999AlertGroup   OBJECT-TYPE
    SYNTAX        OCTET STRING
    ACCESS        read-only
    STATUS        mandatory
    DESCRIPTION    "DMI group generating the alert"
    ::= {eTrapGroup 2}

a9999AlertMessage OBJECT-TYPE
    SYNTAX        OCTET STRING
    ACCESS        read-only
    STATUS        mandatory
    DESCRIPTION    "Alert message"
    ::= {eTrapGroup 3}

a9999AlertSeverity OBJECT-TYPE
    SYNTAX        DmiInteger
    ACCESS        read-only
    STATUS        mandatory
    DESCRIPTION    "DMI alert severity"
    ::= {eTrapGroup 4}

a9999AlertData     OBJECT-TYPE
    SYNTAX        OCTET STRING
    ACCESS        read-only
    STATUS        mandatory
    DESCRIPTION    "Alert data"
    ::= {eTrapGroup 5}

dmtfAlert260   TRAP-TYPE
    ENTERPRISE baseboard
    VARIABLES  { a9999AlertSystem,
                 a9999AlertGroup,
                 a9999AlertMessage,
                 a9999AlertSeverity,
                 a9999AlertData}

    DESCRIPTION "Temperature sensor violation detected"

    --NMS trap annotation

    --#TYPE       "DMI BASEBRDD Alert Event"
    --#SUMMARY    "Event Data: (%s on %s)"
    --#ARGUMENTS  {2, 0}
    --#SEVERITY   CRITICAL
    --#TIMEINDEX  12
    ::= 260

dmtfAlert261   TRAP-TYPE
    ENTERPRISE baseboard
    VARIABLES  { a9999AlertSystem,
                 a9999AlertGroup,
                 a9999AlertMessage,
                 a9999AlertSeverity,
                 a9999AlertData}

    DESCRIPTION "Temperature sensor reading returned to normal"

    --NMS trap annotation

    --#TYPE       "DMI BASEBRDD Alert Event"
    --#SUMMARY    "Event Data: (%s on %s)"
    --#ARGUMENTS  {2, 0}
    --#SEVERITY   CRITICAL
    --#TIMEINDEX  12
    ::= 261


dmtfAlert300   TRAP-TYPE
    ENTERPRISE baseboard
    VARIABLES  { a9999AlertSystem,
                 a9999AlertGroup,
                 a9999AlertMessage,
                 a9999AlertSeverity,
                 a9999AlertData}

    DESCRIPTION "Temperature sensor warning detected"

    --NMS trap annotation

    --#TYPE       "DMI BASEBRDD Alert Event"
    --#SUMMARY    "Event Data: (%s on %s)"
    --#ARGUMENTS  {2, 0}
    --#SEVERITY   CRITICAL
    --#TIMEINDEX  12
    ::= 300

dmtfAlert301   TRAP-TYPE
    ENTERPRISE baseboard
    VARIABLES  { a9999AlertSystem,
                 a9999AlertGroup,
                 a9999AlertMessage,
                 a9999AlertSeverity,
                 a9999AlertData}

    DESCRIPTION "Temperature sensor warning returned to normal"

    --NMS trap annotation

    --#TYPE       "DMI BASEBRDD Alert Event"
    --#SUMMARY    "Event Data: (%s on %s)"
    --#ARGUMENTS  {2, 0}
    --#SEVERITY   CRITICAL
    --#TIMEINDEX  12
    ::= 301

dmtfAlert268   TRAP-TYPE
    ENTERPRISE baseboard
    VARIABLES  { a9999AlertSystem,
                 a9999AlertGroup,
                 a9999AlertMessage,
                 a9999AlertSeverity,
                 a9999AlertData}

    DESCRIPTION "Fan sensor detected a failure"

    --NMS trap annotation

    --#TYPE       "DMI BASEBRDD Alert Event"
    --#SUMMARY    "Event Data: (%s on %s)"
    --#ARGUMENTS  {2, 0}
    --#SEVERITY   CRITICAL
    --#TIMEINDEX  12
    ::= 268

dmtfAlert269   TRAP-TYPE
    ENTERPRISE baseboard
    VARIABLES  { a9999AlertSystem,
                 a9999AlertGroup,
                 a9999AlertMessage,
                 a9999AlertSeverity,
                 a9999AlertData}

    DESCRIPTION "Fan sensor reading returned to normal"

    --NMS trap annotation

    --#TYPE       "DMI BASEBRDD Alert Event"
    --#SUMMARY    "Event Data: (%s on %s)"
    --#ARGUMENTS  {2, 0}
    --#SEVERITY   CRITICAL
    --#TIMEINDEX  12
    ::= 269

dmtfAlert304   TRAP-TYPE
    ENTERPRISE baseboard
    VARIABLES  { a9999AlertSystem,
                 a9999AlertGroup,
                 a9999AlertMessage,
                 a9999AlertSeverity,
                 a9999AlertData}

    DESCRIPTION "Fan sensor warning detected"

    --NMS trap annotation

    --#TYPE       "DMI BASEBRDD Alert Event"
    --#SUMMARY    "Event Data: (%s on %s)"
    --#ARGUMENTS  {2, 0}
    --#SEVERITY   CRITICAL
    --#TIMEINDEX  12
    ::= 304

dmtfAlert305   TRAP-TYPE
    ENTERPRISE baseboard
    VARIABLES  { a9999AlertSystem,
                 a9999AlertGroup,
                 a9999AlertMessage,
                 a9999AlertSeverity,
                 a9999AlertData}

    DESCRIPTION "Fan sensor warning returned to normal"

    --NMS trap annotation

    --#TYPE       "DMI BASEBRDD Alert Event"
    --#SUMMARY    "Event Data: (%s on %s)"
    --#ARGUMENTS  {2, 0}
    --#SEVERITY   CRITICAL
    --#TIMEINDEX  12
    ::= 305

dmtfAlert272   TRAP-TYPE
    ENTERPRISE baseboard
    VARIABLES  { a9999AlertSystem,
                 a9999AlertGroup,
                 a9999AlertMessage,
                 a9999AlertSeverity,
                 a9999AlertData}

    DESCRIPTION "Voltage sensor detected a failure"

    --NMS trap annotation

    --#TYPE       "DMI BASEBRDD Alert Event"
    --#SUMMARY    "Event Data: (%s on %s)"
    --#ARGUMENTS  {2, 0}
    --#SEVERITY   CRITICAL
    --#TIMEINDEX  12
    ::= 272

dmtfAlert273   TRAP-TYPE
    ENTERPRISE baseboard
    VARIABLES  { a9999AlertSystem,
                 a9999AlertGroup,
                 a9999AlertMessage,
                 a9999AlertSeverity,
                 a9999AlertData}

    DESCRIPTION "Voltage sensor reading returned to normal"

    --NMS trap annotation

    --#TYPE       "DMI BASEBRDD Alert Event"
    --#SUMMARY    "Event Data: (%s on %s)"
    --#ARGUMENTS  {2, 0}
    --#SEVERITY   CRITICAL
    --#TIMEINDEX  12
    ::= 273

dmtfAlert302   TRAP-TYPE
    ENTERPRISE baseboard
    VARIABLES  { a9999AlertSystem,
                 a9999AlertGroup,
                 a9999AlertMessage,
                 a9999AlertSeverity,
                 a9999AlertData}

    DESCRIPTION "Voltage sensor warning detected"

    --NMS trap annotation

    --#TYPE       "DMI BASEBRDD Alert Event"
    --#SUMMARY    "Event Data: (%s on %s)"
    --#ARGUMENTS  {2, 0}
    --#SEVERITY   CRITICAL
    --#TIMEINDEX  12
    ::= 302

dmtfAlert303   TRAP-TYPE
    ENTERPRISE baseboard
    VARIABLES  { a9999AlertSystem,
                 a9999AlertGroup,
                 a9999AlertMessage,
                 a9999AlertSeverity,
                 a9999AlertData}

    DESCRIPTION "Voltage sensor warning returned to normal"

    --NMS trap annotation

    --#TYPE       "DMI BASEBRDD Alert Event"
    --#SUMMARY    "Event Data: (%s on %s)"
    --#ARGUMENTS  {2, 0}
    --#SEVERITY   CRITICAL
    --#TIMEINDEX  12
    ::= 303

dmtfAlert306   TRAP-TYPE
    ENTERPRISE baseboard
    VARIABLES  { a9999AlertSystem,
                 a9999AlertGroup,
                 a9999AlertMessage,
                 a9999AlertSeverity,
                 a9999AlertData}

    DESCRIPTION "Current sensor detected a failure"

    --NMS trap annotation

    --#TYPE       "DMI BASEBRDD Alert Event"
    --#SUMMARY    "Event Data: (%s on %s)"
    --#ARGUMENTS  {2, 0}
    --#SEVERITY   CRITICAL
    --#TIMEINDEX  12
    ::= 306

dmtfAlert307   TRAP-TYPE
    ENTERPRISE baseboard
    VARIABLES  { a9999AlertSystem,
                 a9999AlertGroup,
                 a9999AlertMessage,
                 a9999AlertSeverity,
                 a9999AlertData}

    DESCRIPTION "Current sensor reading returned to normal"

    --NMS trap annotation

    --#TYPE       "DMI BASEBRDD Alert Event"
    --#SUMMARY    "Event Data: (%s on %s)"
    --#ARGUMENTS  {2, 0}
    --#SEVERITY   CRITICAL
    --#TIMEINDEX  12
    ::= 307

dmtfAlert308   TRAP-TYPE
    ENTERPRISE baseboard
    VARIABLES  { a9999AlertSystem,
                 a9999AlertGroup,
                 a9999AlertMessage,
                 a9999AlertSeverity,
                 a9999AlertData}

    DESCRIPTION "Current sensor warning detected"

    --NMS trap annotation

    --#TYPE       "DMI BASEBRDD Alert Event"
    --#SUMMARY    "Event Data: (%s on %s)"
    --#ARGUMENTS  {2, 0}
    --#SEVERITY   CRITICAL
    --#TIMEINDEX  12
    ::= 308

dmtfAlert309   TRAP-TYPE
    ENTERPRISE baseboard
    VARIABLES  { a9999AlertSystem,
                 a9999AlertGroup,
                 a9999AlertMessage,
                 a9999AlertSeverity,
                 a9999AlertData}

    DESCRIPTION "Current sensor warning returned to normal"

    --NMS trap annotation

    --#TYPE       "DMI BASEBRDD Alert Event"
    --#SUMMARY    "Event Data: (%s on %s)"
    --#ARGUMENTS  {2, 0}
    --#SEVERITY   CRITICAL
    --#TIMEINDEX  12
    ::= 309

dmtfAlert310   TRAP-TYPE
    ENTERPRISE baseboard
    VARIABLES  { a9999AlertSystem,
                 a9999AlertGroup,
                 a9999AlertMessage,
                 a9999AlertSeverity,
                 a9999AlertData}

    DESCRIPTION "Power supply lost redundancy detected"

    --NMS trap annotation

    --#TYPE       "DMI BASEBRDD Alert Event"
    --#SUMMARY    "Event Data: (%s on %s)"
    --#ARGUMENTS  {2, 0}
    --#SEVERITY   CRITICAL
    --#TIMEINDEX  12
    ::= 310

dmtfAlert311   TRAP-TYPE
    ENTERPRISE baseboard
    VARIABLES  { a9999AlertSystem,
                 a9999AlertGroup,
                 a9999AlertMessage,
                 a9999AlertSeverity,
                 a9999AlertData}

    DESCRIPTION "Power supply regained redundancy"

    --NMS trap annotation

    --#TYPE       "DMI BASEBRDD Alert Event"
    --#SUMMARY    "Event Data: (%s on %s)"
    --#ARGUMENTS  {2, 0}
    --#SEVERITY   CRITICAL
    --#TIMEINDEX  12
    ::= 311

dmtfAlert312   TRAP-TYPE
    ENTERPRISE baseboard
    VARIABLES  { a9999AlertSystem,
                 a9999AlertGroup,
                 a9999AlertMessage,
                 a9999AlertSeverity,
                 a9999AlertData}

    DESCRIPTION "Power supply degraded redundancy detected"

    --NMS trap annotation

    --#TYPE       "DMI BASEBRDD Alert Event"
    --#SUMMARY    "Event Data: (%s on %s)"
    --#ARGUMENTS  {2, 0}
    --#SEVERITY   CRITICAL
    --#TIMEINDEX  12
    ::= 312

dmtfAlert313   TRAP-TYPE
    ENTERPRISE baseboard
    VARIABLES  { a9999AlertSystem,
                 a9999AlertGroup,
                 a9999AlertMessage,
                 a9999AlertSeverity,
                 a9999AlertData}

    DESCRIPTION "Power supply degraded redundancy returned to normal"

    --NMS trap annotation

    --#TYPE       "DMI BASEBRDD Alert Event"
    --#SUMMARY    "Event Data: (%s on %s)"
    --#ARGUMENTS  {2, 0}
    --#SEVERITY   CRITICAL
    --#TIMEINDEX  12
    ::= 313

dmtfAlert314   TRAP-TYPE
    ENTERPRISE baseboard
    VARIABLES  { a9999AlertSystem,
                 a9999AlertGroup,
                 a9999AlertMessage,
                 a9999AlertSeverity,
                 a9999AlertData}

    DESCRIPTION "Power supply failure detected"

    --NMS trap annotation

    --#TYPE       "DMI BASEBRDD Alert Event"
    --#SUMMARY    "Event Data: (%s on %s)"
    --#ARGUMENTS  {2, 0}
    --#SEVERITY   CRITICAL
    --#TIMEINDEX  12
    ::= 314

dmtfAlert315   TRAP-TYPE
    ENTERPRISE baseboard
    VARIABLES  { a9999AlertSystem,
                 a9999AlertGroup,
                 a9999AlertMessage,
                 a9999AlertSeverity,
                 a9999AlertData}

    DESCRIPTION "Power supply failure returned to normal"

    --NMS trap annotation

    --#TYPE       "DMI BASEBRDD Alert Event"
    --#SUMMARY    "Event Data: (%s on %s)"
    --#ARGUMENTS  {2, 0}
    --#SEVERITY   CRITICAL
    --#TIMEINDEX  12
    ::= 315

dmtfAlert320   TRAP-TYPE
    ENTERPRISE baseboard
    VARIABLES  { a9999AlertSystem,
                 a9999AlertGroup,
                 a9999AlertMessage,
                 a9999AlertSeverity,
                 a9999AlertData}

    DESCRIPTION "Chassis intrusion detected"

    --NMS trap annotation

    --#TYPE       "DMI BASEBRDD Alert Event"
    --#SUMMARY    "Event Data: (%s on %s)"
    --#ARGUMENTS  {2, 0}
    --#SEVERITY   CRITICAL
    --#TIMEINDEX  12
    ::= 320

dmtfAlert321   TRAP-TYPE
    ENTERPRISE baseboard
    VARIABLES  { a9999AlertSystem,
                 a9999AlertGroup,
                 a9999AlertMessage,
                 a9999AlertSeverity,
                 a9999AlertData}

    DESCRIPTION "Chassis intrusion returned to normal"

    --NMS trap annotation

    --#TYPE       "DMI BASEBRDD Alert Event"
    --#SUMMARY    "Event Data: (%s on %s)"
    --#ARGUMENTS  {2, 0}
    --#SEVERITY   CRITICAL
    --#TIMEINDEX  12
    ::= 321

dmtfAlert330   TRAP-TYPE
    ENTERPRISE baseboard
    VARIABLES  { a9999AlertSystem,
                 a9999AlertGroup,
                 a9999AlertMessage,
                 a9999AlertSeverity,
                 a9999AlertData}

    DESCRIPTION "System Up"

    --NMS trap annotation

    --#TYPE       "DMI BASEBRDD Alert Event"
    --#SUMMARY    "Event Data: (%s on %s)"
    --#ARGUMENTS  {2, 0}
    --#SEVERITY   CRITICAL
    --#TIMEINDEX  12
    ::= 330

dmtfAlert323   TRAP-TYPE
    ENTERPRISE baseboard
    VARIABLES  { a9999AlertSystem,
                 a9999AlertGroup,
                 a9999AlertMessage,
                 a9999AlertSeverity,
                 a9999AlertData}

    DESCRIPTION "Memory ECC fault detected"

    --NMS trap annotation

    --#TYPE       "DMI BASEBRDD Alert Event"
    --#SUMMARY    "Event Data: (%s on %s)"
    --#ARGUMENTS  {2, 0}
    --#SEVERITY   CRITICAL
    --#TIMEINDEX  12
    ::= 323

dmtfAlert325   TRAP-TYPE
    ENTERPRISE baseboard
    VARIABLES  { a9999AlertSystem,
                 a9999AlertGroup,
                 a9999AlertMessage,
                 a9999AlertSeverity,
                 a9999AlertData}

    DESCRIPTION "Lost connection to storage system"

    --NMS trap annotation

    --#TYPE       "DMI BASEBRDD Alert Event"
    --#SUMMARY    "Event Data: (%s on %s)"
    --#ARGUMENTS  {2, 0}
    --#SEVERITY   CRITICAL
    --#TIMEINDEX  12
    ::= 325

dmtfAlert326   TRAP-TYPE
    ENTERPRISE baseboard
    VARIABLES  { a9999AlertSystem,
                 a9999AlertGroup,
                 a9999AlertMessage,
                 a9999AlertSeverity,
                 a9999AlertData}

    DESCRIPTION "Established connection to storage system"

    --NMS trap annotation

    --#TYPE       "DMI BASEBRDD Alert Event"
    --#SUMMARY    "Event Data: (%s on %s)"
    --#ARGUMENTS  {2, 0}
    --#SEVERITY   CRITICAL
    --#TIMEINDEX  12
    ::= 326

dmtfAlert327   TRAP-TYPE
    ENTERPRISE baseboard
    VARIABLES  { a9999AlertSystem,
                 a9999AlertGroup,
                 a9999AlertMessage,
                 a9999AlertSeverity,
                 a9999AlertData}

    DESCRIPTION "Reestablished connection to storage system"

    --NMS trap annotation

    --#TYPE       "DMI BASEBRDD Alert Event"
    --#SUMMARY    "Event Data: (%s on %s)"
    --#ARGUMENTS  {2, 0}
    --#SEVERITY   CRITICAL
    --#TIMEINDEX  12
    ::= 327
END
