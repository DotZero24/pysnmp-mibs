Dell-CDB-MIB DEFINITIONS ::= BEGIN

-- Title:                Dell ROS
--                       Private CDB MIB
-- Version:              7.46
-- Date:                 15-Jan-2007

IMPORTS
    rnd                                          FROM Dell-MIB
    OBJECT-TYPE, MODULE-IDENTITY                 FROM SNMPv2-SMI
    TruthValue                                   FROM SNMPv2-TC;

rlCDB MODULE-IDENTITY
                LAST-UPDATED "200701020000Z"
                ORGANIZATION "Dell"

                CONTACT-INFO
                      "www.dell.com"
                DESCRIPTION
                      "This private MIB module defines CDB private MIBs."
                REVISION "200701020000Z"
                DESCRIPTION
                      "Initial revision."
        ::= { rnd 94 }

rlStartupCDBChanged OBJECT-TYPE
    SYNTAX TruthValue
    MAX-ACCESS read-only
    STATUS current
    DESCRIPTION
        "Indicates whether the startup CDB has changed between the router's
         last two reboots"
    ::= {rlCDB 1 }

rlManualReboot OBJECT-TYPE
    SYNTAX TruthValue
    MAX-ACCESS read-only
    STATUS current
    DESCRIPTION
        "Indicates whether the device was shutdown orderly before reboot or
         not (i.e. power failure)"
    ::= {rlCDB 2 }

rlStartupCDBEmpty OBJECT-TYPE
    SYNTAX TruthValue
    MAX-ACCESS read-only
    STATUS current
    DESCRIPTION
        "Indicates whether the startup-cdb is empty, meaning: does not include
         any user configuration."
    ::= {rlCDB 3 }
END
