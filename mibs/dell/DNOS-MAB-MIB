DNOS-MAB-MIB DEFINITIONS ::= BEGIN

-- Broadcom FastPath MAB MIB
-- Copyright 2018 Broadcom.
-- This SNMP Management Information Specification
-- embodies Broadcom's confidential and proprietary
-- intellectual property.  Broadcom retains all title
-- and ownership in the Specification including any revisions.

-- This Specification is supplied "AS IS", Broadcom
-- makes no warranty, either expressed or implied,
-- as to the use, operation, condition, or performance of the
-- Specification.

IMPORTS
    MODULE-IDENTITY, OBJECT-TYPE, NOTIFICATION-TYPE,
    Unsigned32, TimeTicks               FROM SNMPv2-SMI
    TEXTUAL-CONVENTION,
    RowStatus,MacAddress,DateAndTime    FROM SNMPv2-TC
    DisplayString                       FROM RFC1213-MIB
    InterfaceIndex                      FROM IF-MIB
    dnOS                            FROM DELL-REF-MIB;

    fastPathMab MODULE-IDENTITY
           LAST-UPDATED "201805050000Z" -- 5 May 2018 12:00:00 GMT
           ORGANIZATION "Dell EMC"
           CONTACT-INFO ""

     DESCRIPTION
          "The Dell Networking Private MIB for MAC Authentication Bypass (MAB)
           feature"

      -- Revision history.
     REVISION
          "201712150000Z" -- 15 December 2017 12:00:00 GMT
     DESCRIPTION
          "Initial version."

     ::= { dnOS 75 }

agentMabGlobalConfigGroup OBJECT IDENTIFIER ::= { fastPathMab 1 }

    agentMABRequestAttr1GroupSize OBJECT-TYPE
         SYNTAX       INTEGER {
                        one(1),
                        two(2),
                        four(4),
                        twelve(12)
                      }
         MAX-ACCESS   read-write
         STATUS       current
         DESCRIPTION
                     "Specifies the group size used by switch to format the
                      attribute1 of MAB request."
         ::= { agentMabGlobalConfigGroup 1 }

    agentMABRequestAttr1Separator OBJECT-TYPE
         SYNTAX       INTEGER {
                        ieft(1),
                        legacy(2),
                        dot(3)
                      }
         MAX-ACCESS   read-write
         STATUS       current
         DESCRIPTION
                     "Specifies the separator used by switch to format the
                      attribute1 of MAB request."
         ::= { agentMabGlobalConfigGroup 2 }

    agentMABRequestAttr1Case OBJECT-TYPE
         SYNTAX       INTEGER {
                        upper(1),
                        lower(2)
                      }
         MAX-ACCESS   read-write
         STATUS       current
         DESCRIPTION
                     "Specifies the case used by switch to format the attribute1
                      of MAB request."
         ::= { agentMabGlobalConfigGroup 3 }

--*****************************************************************************
-- agentMabPortConfigGroup -> Contains MIB objects configuring/displaying MAB
-- Port details and associated Functionality
--
--*****************************************************************************

    agentMabPortConfigGroup OBJECT IDENTIFIER ::= { fastPathMab 2 }

--------------------------------------------------------------
-- The MAB Port Table
--------------------------------------------------------------

    agentMabPortConfigTable OBJECT-TYPE
         SYNTAX       SEQUENCE OF AgentMabPortConfigEntry
         MAX-ACCESS   not-accessible
         STATUS       current
         DESCRIPTION
                     "A table for MAB Port details and associated functionality."
         ::= { agentMabPortConfigGroup 1 }

    agentMabPortConfigEntry OBJECT-TYPE
         SYNTAX       AgentMabPortConfigEntry
         MAX-ACCESS   not-accessible
         STATUS       current
         DESCRIPTION
                     "Represents entry for port configuration table."
         INDEX        { agentMabIfIndex}
         ::= {agentMabPortConfigTable 1 }

    AgentMabPortConfigEntry ::= SEQUENCE {
        agentMabIfIndex
             InterfaceIndex,
        agentMABPortEnabled
             INTEGER,
        agentMabPortOperational
             INTEGER,
        agentMabPortAuthType
             INTEGER
    }

    agentMabIfIndex      OBJECT-TYPE
         SYNTAX       InterfaceIndex
         MAX-ACCESS   not-accessible
         STATUS       current
         DESCRIPTION
                     "The interface index for which the mab configuration is
                      required."
         ::= { agentMabPortConfigEntry 1 }

    agentMABPortEnabled    OBJECT-TYPE
         SYNTAX       INTEGER {
                        enable(1),
                        disable(2)
                      }
         MAX-ACCESS   read-write
         STATUS       current
         DESCRIPTION
                     "Specifies if Mac-based bypass authentication is configured
                      for the port."
         DEFVAL {disable}
         ::= {  agentMabPortConfigEntry 2}

    agentMabPortOperational OBJECT-TYPE
         SYNTAX       INTEGER {
                        enable(1),
                        disable(2)
                      }
         MAX-ACCESS   read-only
         STATUS       current
         DESCRIPTION
                     "Displays the operational value of the Mac-based
                      authentication bypass mode (MAB) on the port."
         DEFVAL {disable}
         ::= {  agentMabPortConfigEntry 3}

    agentMabPortAuthType OBJECT-TYPE
         SYNTAX       INTEGER {
                        eapMd5(1),
                        pap(2),
                        chap(3)
                      }
         MAX-ACCESS   read-write
         STATUS       current
         DESCRIPTION
                     "Sets/Displays the authentication type used by Mac-based
                      authentication bypass mode (MAB) on the port. "
         DEFVAL { eapMd5 }
         ::= {  agentMabPortConfigEntry 4}

END
