--------------------------------------------------------------------------------
-- DELL REMOTE CONSOLE SWITCH (1082DS/2162DS/4322DS) TRAP MIB
--
-- Copyright 2012 Dell Corporation
--
-- Revision: 1.16.0
--
-- Last Modified: Thu, 23 Feb 2012
--
--------------------------------------------------------------------------------

DELLRCSG2-TRAP-MIB DEFINITIONS ::= BEGIN

IMPORTS
   Gauge,enterprises,TimeTicks,IpAddress,Counter,NetworkAddress
      FROM RFC1155-SMI
   OBJECT-TYPE
      FROM RFC-1212
   DisplayString,PhysAddress
      FROM RFC1213-MIB
   TRAP-TYPE
      FROM RFC-1215;

--------------------------------------------------------------------------------
-- Object Groupings
--------------------------------------------------------------------------------

dell OBJECT IDENTIFIER ::= { enterprises 10418 }
dellrcsg2 OBJECT IDENTIFIER ::= { dell 18 }
dellrcsg2Products OBJECT IDENTIFIER ::= { dellrcsg2 21 }
dellrcsg2Management OBJECT IDENTIFIER ::= { dellrcsg2 22 }

-- Below is the value returned by each appliance in mib-2.system.sysObjectID
--
dellrcs1082ds OBJECT IDENTIFIER ::= { dellrcsg2Products 17 } -- 10418.18.21.17
dellrcs2162ds OBJECT IDENTIFIER ::= { dellrcsg2Products 24 } -- 10418.18.21.24
dellrcs4322ds OBJECT IDENTIFIER ::= { dellrcsg2Products 26 } -- 10418.18.21.26

dellrcsg2TrapObject OBJECT IDENTIFIER ::= { dellrcsg2Management 6 } -- 1.3.6.1.4.1.10418.18.22.6

--
-- A UTF8String represents a series of UTF-8 encoded characters. UTF-8 encoding
-- provides the ability to encode all characters defined in the Universal
-- Multiple-Octet Coded Character Set (UCS) and all characters defined in the
-- Unicode Standard. UCS is defined in international standard ISO 10646. Unicode
-- encompasses a subset of UCS. See http:
-- on Unicode. See RFC2279 for more information on UTF-8 encoding.
--

UTF8String ::= OCTET STRING

ImageFileUpgradeResultsEnum ::= INTEGER
{
   imageUpgradeTftpNoSocket(1), -- TFTP No Socket
   imageUpgradeTftpConnectFailure(2), -- TFTP server TFTP connect failed
   imageUpgradeTftpRequestDenied(3), -- TFTP server request denied
   imageUpgradeTftpBadPacket(4), -- TFTP err - non-data packet received
   imageUpgradeTftpOOS(5), -- TFTP err - too many packets out
                                        -- of sequence
   imageUpgradeTftpTooBig(6), -- TFTP err - transferred data exceeds
                                        -- file size
   imageUpgradeTftpTimeout(7), -- TFTP err - timeout during transfer,
                                        -- retries exceeded
   imageUpgradeAlreadyInProgress(8), -- Update already in progress
   imageUpgradeCannotStart(9), -- Update thread did not start
   imageUpgradeMemoryError(10), -- Update memory allocation error
   imageUpgradeTftpProtocolError(11), -- TFTP protocol error occurred could
                                        -- not complete transfer
   imageUpgradeBadType(12), -- The Image type does not match the
                                        -- region (BOOT or APP) to update
   imageUpgradeInvalidAppDowngrade(13), -- Invalid downgrade version
   imageUpgradeChecksumError(14), -- Checksum Error
   imageUpgradeFlashError(15), -- Flash Error
   imageUpgradeInternalError(16), -- Internal error
   imageUpgradeFileNotFound(17), -- File not found
   imageUpgradeBadHeader(18), -- Invalid image header
   imageUpgradeIncompatibleHeader(19), -- Header is not compatible
   imageUpgradeTftpXferFail(20), -- TFTP transfer failed
   imageUpgradeTftpSvrNoResponse(21), -- No response from TFTP server
   imageUpgradeNetworkUnreachable(22), -- Network unreachable
   imageUpgradeSuccess(9999) -- Success
}

--
-- An enumeration of SIP upgrade results.
--

SIPUpgradeResultsEnum ::= INTEGER
{
   sipUpgradeNoFirmwareImage(1), -- No firmware image present
   sipUpgradeLostContact(2), -- Lost communication with the SIP
   sipUpgradeFailedRestart(3), -- The SIP did not restart after upgrade
   sipUpgradeFailedVerify(4), -- The SIP failed to upgrade to correct Version
   sipUpgradeSuccess(9999) -- Success
}

--------------------------------------------------------------------------------
-- Trap Object Group (dellrcsg2TrapObject) 1.3.6.1.4.1.10418.18.22.6
--
-- The following objects are implemented only for the generation of
-- TRAPs. The objects are sent in traps and are not accessible in
-- any other way.
--------------------------------------------------------------------------------

dellrcsg2TrapObjectUserName OBJECT-TYPE
      SYNTAX UTF8String ( SIZE (3..16) )
      ACCESS not-accessible
      STATUS mandatory
  --% AVAILABILITY public
      DESCRIPTION
         "This object is sent in a trap to identify the name of the user
         for which the trap condition occured. If the trap condition occurred
         as a result of activity on the local port (OSD), then the value of this
         object will be the following string:

            Local User
         "
      ::= { dellrcsg2TrapObject 1 }


dellrcsg2TrapObjectTargetUserName OBJECT-TYPE
      SYNTAX UTF8String ( SIZE (3..16) )
      ACCESS not-accessible
      STATUS mandatory
  --% AVAILABILITY public
      DESCRIPTION
         "This object is sent in a trap to identify the name of the target
         user for which a trap condition occurred.
         "
      ::= { dellrcsg2TrapObject 2 }


dellrcsg2TrapObjectImageType OBJECT-TYPE
      SYNTAX UTF8String ( SIZE (0..64) )
      ACCESS not-accessible
      STATUS mandatory
  --% AVAILABILITY public
      DESCRIPTION
         "This object is sent in a trap to identify the type of software image
         for which the trap condition occured.
         "
      ::= { dellrcsg2TrapObject 3 }


dellrcsg2TrapObjectImageNewVersion OBJECT-TYPE
      SYNTAX UTF8String ( SIZE (0..32) )
      ACCESS not-accessible
      STATUS mandatory
  --% AVAILABILITY public
      DESCRIPTION
         "This object is sent in a trap to identify the version of the new
         software image the RCS is being upgraded to.
         "
      ::= { dellrcsg2TrapObject 4 }


dellrcsg2TrapObjectImageCurrentVersion OBJECT-TYPE
      SYNTAX UTF8String ( SIZE (0..32) )
      ACCESS not-accessible
      STATUS mandatory
  --% AVAILABILITY public
      DESCRIPTION
         "This object is sent in a trap to identify the version of the
         software image that the RCS is currently running.
         "
      ::= { dellrcsg2TrapObject 5 }


dellrcsg2TrapObjectSessionIdentifier OBJECT-TYPE
      SYNTAX UTF8String ( SIZE (0..32) )
      ACCESS not-accessible
      STATUS mandatory
  --% AVAILABILITY public
      DESCRIPTION
         "This object is sent in a trap to identify the session
         for which the trap condition occurred. The value will be
         the name of a target device if the target device name is known, otherwise
         the value will be the connection path to a target device.

         If the value is a connection path it will have the
         following format:

            SIP i:Channel c

         Where i is the ID of the SIP, and c is the tiered switch
         channel number (0 if there is no switch in the path).
         "
      ::= { dellrcsg2TrapObject 6 }


dellrcsg2TrapObjectSIPId OBJECT-TYPE
      SYNTAX UTF8String ( SIZE (0..32) )
      ACCESS not-accessible
      STATUS mandatory
  --% AVAILABILITY public
      DESCRIPTION
         "This object is sent in a trap to identify the SIP for
         which the trap condition occurred.
         "
      ::= { dellrcsg2TrapObject 7 }


dellrcsg2TrapObjectTieredSwitchName OBJECT-TYPE
      SYNTAX UTF8String ( SIZE (0..15) )
      ACCESS not-accessible
      STATUS mandatory
  --% AVAILABILITY public
      DESCRIPTION
         "This object is sent in a trap to identify the tiered switch
         for which the trap condition occurred.
         "
      ::= { dellrcsg2TrapObject 8 }


dellrcsg2TrapObjectOldTieredSwitchName OBJECT-TYPE
      SYNTAX UTF8String ( SIZE (0..15) )
      ACCESS not-accessible
      STATUS mandatory
  --% AVAILABILITY public
      DESCRIPTION
         "This object is sent in a trap to identify the old name of a
         tiered switch whose name was changed.
         "
      ::= { dellrcsg2TrapObject 9 }


dellrcsg2TrapObjectTargetDeviceName OBJECT-TYPE
      SYNTAX UTF8String ( SIZE (0..15) )
      ACCESS not-accessible
      STATUS mandatory
  --% AVAILABILITY public
      DESCRIPTION
         "This object is sent in a trap to identify the target device for
         which the trap condition occurred.
         "
      ::= { dellrcsg2TrapObject 10 }


dellrcsg2TrapObjectOldTargetDeviceName OBJECT-TYPE
      SYNTAX UTF8String ( SIZE (0..15) )
      ACCESS not-accessible
      STATUS mandatory
  --% AVAILABILITY public
      DESCRIPTION
         "This object is sent in a trap to identify the old name of
         a target device whose name was changed.
         "
      ::= { dellrcsg2TrapObject 11 }


dellrcsg2TrapObjectFileName OBJECT-TYPE
      SYNTAX DisplayString ( SIZE (0..255) )
      ACCESS not-accessible
      STATUS mandatory
  --% AVAILABILITY public
      DESCRIPTION
         "This object is sent in a trap to identify the name of a file
         for which the trap condition occurred.
         "
      ::= { dellrcsg2TrapObject 12 }



dellrcsg2TrapObjectLockReason OBJECT-TYPE
      SYNTAX UTF8String( SIZE (0..64) )
      ACCESS not-accessible
      STATUS mandatory
  --% AVAILABILITY public
      DESCRIPTION
         "This object is sent in a trap to explain the reason for which a
         user account has been locked.
         "
      ::= { dellrcsg2TrapObject 13 }


dellrcsg2TrapObjectUnlockReason OBJECT-TYPE
      SYNTAX UTF8String( SIZE (0..64) )
      ACCESS not-accessible
      STATUS mandatory
  --% AVAILABILITY public
      DESCRIPTION
         "This object is sent in a trap to explain the reason for which a
         user account has been unlocked.
         "
      ::= { dellrcsg2TrapObject 14 }



dellrcsg2TrapObjectUserAddress OBJECT-TYPE
      SYNTAX DisplayString( SIZE (0..40) )
      ACCESS not-accessible
      STATUS mandatory
  --% AVAILABILITY public
      DESCRIPTION
         "This object is sent in a trap to identify the user address for
         which a trap condition occurred.

         For a remote user, the value is the IPv4 or IPv6 IP address.
         For a local user, the value is the Local Port of the user.
         "
      ::= { dellrcsg2TrapObject 15 }


dellrcsg2TrapObjectSIPImageUpgradeResult OBJECT-TYPE
      SYNTAX SIPUpgradeResultsEnum
      ACCESS not-accessible
      STATUS mandatory
  --% AVAILABILITY public
      DESCRIPTION
         "This object is sent in a trap to report the result of a SIP
         image upgrade.
         "
      ::= { dellrcsg2TrapObject 16 }


dellrcsg2TrapObjectTypeOfImage OBJECT-TYPE
      SYNTAX INTEGER {
                        boot(1),
                        app(2)
                     }
      ACCESS not-accessible
      STATUS mandatory
  --% AVAILABILITY public
      DESCRIPTION
         "This object is sent in a trap to report the type of software
         image for which the trap condition occurred.
         "
      ::= { dellrcsg2TrapObject 17 }



dellrcsg2TrapObjectVirtualMediaDriveAccessMode OBJECT-TYPE
      SYNTAX INTEGER {
                        readonly(1),
                        readwrite(2)
                     }
      ACCESS not-accessible
      STATUS mandatory
  --% AVAILABILITY public
      DESCRIPTION
         "This object is sent in a trap to report the access mode
          associated with a virtual drive for which
          the trap condition occurred.
         "
      ::= { dellrcsg2TrapObject 18 }


dellrcsg2TrapObjectVirtualMediaDriveType OBJECT-TYPE
      SYNTAX INTEGER {
                        floppyMemoryKey(1),
                        cdDvdRom(2),
                        generic(3)
                     }
      ACCESS not-accessible
      STATUS mandatory
  --% AVAILABILITY public
      DESCRIPTION
         "This object is sent in a trap to report the type associated
          with a virtual drive for which the trap condition
          occurred.
         "
      ::= { dellrcsg2TrapObject 19 }



dellrcsg2TrapObjectImageFileUpgradeResult OBJECT-TYPE
      SYNTAX ImageFileUpgradeResultsEnum
      ACCESS not-accessible
      STATUS mandatory
  --% AVAILABILITY public
      DESCRIPTION
         "This object is sent in a trap to report the results of a
          TFTP or ASMP image upgrade."
      ::= { dellrcsg2TrapObject 20 }



dellrcsg2TrapObjectPduDevicePort OBJECT-TYPE
      SYNTAX INTEGER (1..2)
      ACCESS not-accessible
      STATUS mandatory
  --% AVAILABILITY public
      DESCRIPTION
         "This object is sent in a trap to identify the RCS port
         that the power device is attached to for which the trap condition
         occurred.
         "
      ::= { dellrcsg2TrapObject 21 }


dellrcsg2TrapObjectPduOutlet OBJECT-TYPE
      SYNTAX INTEGER (1..16)
      ACCESS not-accessible
      STATUS mandatory
  --% AVAILABILITY public
      DESCRIPTION
         "This object is sent in a trap to identify the power device outlet
         number for which the trap condition occurred.
         "
      ::= { dellrcsg2TrapObject 22 }



dellrcsg2TrapObjectOldName OBJECT-TYPE
      SYNTAX UTF8String ( SIZE (0..64) )
      ACCESS not-accessible
      STATUS mandatory
  --% AVAILABILITY public
      DESCRIPTION
         "This object is sent in a trap to identify the old name of a port
         or power device outlet for which the trap condition occurred.
         "
      ::= { dellrcsg2TrapObject 23 }


dellrcsg2TrapObjectItemName OBJECT-TYPE
      SYNTAX UTF8String ( SIZE (0..64) )
      ACCESS not-accessible
      STATUS mandatory
  --% AVAILABILITY public
      DESCRIPTION
         "This object is sent in a trap to identify the name of a port
         or power device outlet for which the trap condition occurred.
         "
      ::= { dellrcsg2TrapObject 24 }



dellrcsg2TrapObjectPduDeviceInlet OBJECT-TYPE
      SYNTAX INTEGER
      ACCESS not-accessible
      STATUS mandatory
  --% AVAILABILITY public
      DESCRIPTION
         "This object is sent in a trap to identify the inlet of a power device
         for which the trap condition occurred.
         "
      ::= { dellrcsg2TrapObject 25 }

dellrcsg2TrapObjectPduDeviceNumber OBJECT-TYPE
      SYNTAX INTEGER
      ACCESS not-accessible
      STATUS mandatory
  --% AVAILABILITY public
      DESCRIPTION
         "This object is sent in a trap to identify the power device number
         that is attached to a RCS port for which the trap
         condition occurred.
         "
      ::= { dellrcsg2TrapObject 26 }



dellrcsg2TrapObjectInputPort OBJECT-TYPE
      SYNTAX INTEGER
      ACCESS not-accessible
      STATUS mandatory
  --% AVAILABILITY public
      DESCRIPTION
         "This object is sent in a trap to identify the RCS input port
         number for which the trap condition occurred. An input port is defined
         here as an ARI port that interfaces the data traffic coming from
         or going directly or indirectly to a target device. The values range
         from 1 to the maximum number of ARI ports.
         "
      ::= { dellrcsg2TrapObject 27 }


dellrcsg2TrapObjectOldInputPort OBJECT-TYPE
      SYNTAX INTEGER
      ACCESS not-accessible
      STATUS mandatory
  --% AVAILABILITY public
      DESCRIPTION
         "This object is sent in a trap to identify the old RCS input port
         number for which the trap condition occurred. An input port is defined
         here as an ARI port that interfaces the data traffic coming from
         or going directly or indirectly to a target device. The values range
         from 1 to the maximum number of ARI ports.
         "
      ::= { dellrcsg2TrapObject 28 }


dellrcsg2TrapObjectPowerSupply OBJECT-TYPE
      SYNTAX DisplayString ( SIZE (0..5) )
      ACCESS not-accessible
      STATUS mandatory
  --% AVAILABILITY public
      DESCRIPTION
         "This object is sent in a trap to identify the power supply
         for which the trap condition occurred.
         "
      ::= { dellrcsg2TrapObject 29 }


dellrcsg2TrapObjectPreviousScreenResolution OBJECT-TYPE
      SYNTAX DisplayString ( SIZE (0..32) )
      ACCESS not-accessible
      STATUS mandatory
  --% AVAILABILITY public
      DESCRIPTION
         "This object is sent in a trap to identify the previous screen
         resolution of the target target device.
         "
      ::= { dellrcsg2TrapObject 30 }


dellrcsg2TrapObjectCurrentScreenResolution OBJECT-TYPE
      SYNTAX DisplayString ( SIZE (0..32) )
      ACCESS not-accessible
      STATUS mandatory
  --% AVAILABILITY public
      DESCRIPTION
         "This object is sent in a trap to identify the current screen
         resolution of the target server.
         "
      ::= { dellrcsg2TrapObject 31 }


dellrcsg2TrapObjectAggregatedTargetDeviceStatusChanged OBJECT-TYPE
      SYNTAX OCTET STRING ( SIZE (12..5122) )
      ACCESS not-accessible
      STATUS mandatory
  --% AVAILABILITY public
      DESCRIPTION
         "This object is sent in a trap to report server status changes. This
         object will report the status change of multiple servers (connection
         paths) in an aggregated encoding format as indicated below.

         Note that on bootup the RCS will send this object in the
         dellrcsg2AggregatedTargetDeviceStatusChangedTrap containing the status of all
         connection paths in the RCS. Thereafter the RCS will
         send this object in the dellrcsg2AggregatedTargetDeviceStatusChangedTrap containing
         only the connection paths whose status has changed.

         This object is composed of two sections, which are the header section
         and the connection path section. The header section provides version
         information and is the first 2 bytes of this object. The connection
         path section provides information on each of the connection paths and
         is defined in the bytes following the header.

         Header Section
         --------------

         Byte 1 = Start indicator for the header section. The value of the
                       start indicator is always zero. The value of the start
                       indicator provides means for management applications to
                       determine that this object has a header section. All
                       previous implementations of this object have a non-zero
                       value in the first byte.

         Byte 2 = Version of the aggregate object. The version provides
                       means to identify the format/structure of this aggregate
                       object. The format of the aggregate object, as described
                       here, is identified with a value of 3 for the version.


         Connection Path Section
         -----------------------

         The connection path section is composed of 1 or more connection paths.
         The information for each connection path is packed into 10 bytes as
         follows:

         Byte 1 = The RCS input port number associated with this
                       connection path. The input port is an ARI port that
                       interfaces the data traffic coming from or going directly
                       or indirectly to a target device or a power device.

                       Note that a power device will report the port number as
                       100 + the power device port number. For the first power
                       device port, Byte 1 will report 101 for the power device.
                       This will avoid potential port conflicts for ARI and
                       power device ports. In the event that additional power
                       device ports are available, the number will reflect the
                       power device port number (i.e. 101, 102, etc.)

         Byte 2 = The tiered switch channel number associated with this
                       connection path. The value will be 0 if a switch channel
                       is not associated with this connection path.

                       For power devices, this Byte will represent the power
                       device number. Byte 3 will contain the outlet number
                       for this connection path.

         Byte 3 ~ 8 = The EID of the SIP associated with this connection path.
                       Each byte in this field will encode two digits of the
                       SIP's EID number. For example, if the actual EID number
                       on the label attached to a SIP is 520255-0346DC then
                       bytes 3 through 8 would contain the following hex values:

                          Byte 3 = 0x52
                          Byte 4 = 0x02
                          Byte 5 = 0x55
                          Byte 6 = 0x03
                          Byte 7 = 0x46
                          Byte 8 = 0xDC

                       Note that the dash character is not represented in
                       the encoded value.

                       For a power device, the first byte (Byte 3) will
                       represent the outlet number and the remaining 5 bytes
                       (Byte 4-8) will be 0.

         Byte 9 ~ the left most 4 bits

                     = The left most four bits of the 9th byte shall be used
                       to encode / decode the following integer value to
                       represent the power status of a connected server or the
                       power status of a power device outlet.

                       One of the following values can be reported:

                       1 = Off - The connection path does not have power,
                                    which could be the result of the following
                                    situation: the SIP is unplugged or the
                                    SIP is plugged in but receives no power
                                    from the target device.

                       2 = On - The connection path has power.


         Byte 9 ~ the right most 4 bits

                     = The right most four bits of the 9th byte shall be used
                       to encode / decode the following integer value to
                       represent the viewer session status of a connection path.
                       For a power device or power device outlet, this value is
                       always 1 since viewer sessions are not supported.

                       One of the following values can be reported:

                       1 = Idle - There is not a viewer session active on
                                      this connection path.

                       2 = Active - There is an active viewer session on this
                                      connection path.

                       3 = Blocked - The connection path is blocked meaning a
                                      viewer session cannot be established to
                                      this connection path because of another
                                      viewer session is currently using a
                                      resource required by this connection path
                                      in order to establish a connection path.
                                      A viewer session cannot be blocked by
                                      a virtual media session.

         Byte 10 ~ the left most 4 bits

                     = The left most four bits of the 10th byte shall be used
                       to encode / decode the following integer value to
                       represent the virtual media session status of a
                       connection path. For a power device or power device
                       outlet, this value is always 1 since virtual media
                       sessions are not supported.

                       One of the following values can be reported:

                       1 = Idle - There is not a virtual media session
                                      active on this connection path.

                       2 = Active - There is a virtual media session on this
                                      connection path.

                       3 = Blocked - The connection path is blocked meaning a
                                      virtual media session cannot be
                                      established to this connection path
                                      because of another virtual media session
                                      is currently using a resource required by
                                      this connection path in order to establish
                                      a connection path. A virtual media session
                                      cannot be blocked by a viewer session.

         Byte 10 ~ the right most 4 bits
                     = The right most four bits of the 10th byte shall be used
                       for future use and they will have a value of 0.

         Every connection path will be packed into this object in 10 byte
         increments one after the other. The connection paths do not have to be
         packed in any specific order. Note that the size of this object could
         conceivably be as large as shown in the following calculation with
         these assumptions.
            - 24 channel switch connected to each port of the RCS
            - 4 power devices connected to RCS, each having 32 outlets

         (((16 ports X 24 channels) + (4 power devices X 32 power device outlets))
            X 10 bytes) + (2 byte Header) = 5122.
         "
      ::= { dellrcsg2TrapObject 32 }



dellrcsg2TrapObjectPduDeviceCircuit OBJECT-TYPE
      SYNTAX INTEGER
      ACCESS not-accessible
      STATUS mandatory
  --% AVAILABILITY public
      DESCRIPTION
         "This object is sent in a trap to identify the circuit of a power
         device for which the trap condition occurred.
         "
      ::= { dellrcsg2TrapObject 33 }



dellrcsg2TrapObjectSessionType OBJECT-TYPE
      SYNTAX DisplayString( SIZE (0..16) )
      ACCESS not-accessible
      STATUS mandatory
  --% AVAILABILITY public
      DESCRIPTION
         "This object is sent in a trap to identify the session type for
         which a trap condition occurred.

         The value is KVM for a KVM session,
         or Serial for a Serial session.
         "
      ::= { dellrcsg2TrapObject 34 }

--------------------------------------------------------------------------------
-- Enterprise Traps
--------------------------------------------------------------------------------

dellrcsg2RebootStartedTrap TRAP-TYPE
      ENTERPRISE dellrcsg2Products
      VARIABLES { dellrcsg2TrapObjectUserName }
      DESCRIPTION
         "The RCS is in the process of rebooting.

         The name of the user who initiated the reboot
         is contained in dellrcsg2TrapObjectUserName.
         "

      --#SUMMARY "The RCS is rebooting. Command issued by user: %s."
      --#ARGUMENTS { 0 }
      --#SEVERITY INFORMATIONAL
      --#FACILITY KERNEL
      --#CATEGORY "Status Events"
      --% TrapTypeEnum=5
      ::= 1


dellrcsg2UserLoginTrap TRAP-TYPE
      ENTERPRISE dellrcsg2Products
      VARIABLES { dellrcsg2TrapObjectUserName }
      DESCRIPTION
         "A user logged into the RCS.

         The name of the user who logged in
         is contained in dellrcsg2TrapObjectUserName.
         "

      --#SUMMARY "User logged into the RCS. User: %s."
      --#ARGUMENTS { 0 }
      --#SEVERITY INFORMATIONAL
      --#FACILITY SECURITY
      --#CATEGORY "Status Events"
      --% TrapTypeEnum=6
      ::= 2


dellrcsg2UserLogoutTrap TRAP-TYPE
      ENTERPRISE dellrcsg2Products
      VARIABLES { dellrcsg2TrapObjectUserName }
      DESCRIPTION
         "A user logged out of the RCS.

         The name of the user who logged out is contained
         in dellrcsg2TrapObjectUserName.
         "

      --#SUMMARY "User logged out of the RCS. User: %s."
      --#ARGUMENTS { 0 }
      --#SEVERITY INFORMATIONAL
      --#FACILITY SECURITY
      --#CATEGORY "Status Events"
      --% TrapTypeEnum=7
      ::= 3


dellrcsg2TargetSessionStartedTrap TRAP-TYPE
      ENTERPRISE dellrcsg2Products
      VARIABLES {
                     dellrcsg2TrapObjectUserName,
                     dellrcsg2TrapObjectSessionIdentifier,
                     dellrcsg2TrapObjectUserAddress,
                     dellrcsg2TrapObjectSessionType
                  }
      DESCRIPTION
         "A target session has started. This may be a serial or KVM
         session, depending on the type of target.

         The name of the user who is connected to the session
         is contained in dellrcsg2TrapObjectUserName.

         The session identifier is contained in
         dellrcsg2TrapObjectSessionIdentifier.

         The user address is contained in
         dellrcsg2TrapObjectUserAddress.

         The session type is contained in
         dellrcsg2TrapObjectSessionType.
         "

      --#SUMMARY "Target session started. User: %s. Target device: %s. Address: %s. Type: %s."
      --#ARGUMENTS { 0, 1, 2, 3 }
      --#SEVERITY INFORMATIONAL
      --#FACILITY SECURITY
      --#CATEGORY "Status Events"
      --% TrapTypeEnum=8
      ::= 4


dellrcsg2TargetSessionStoppedTrap TRAP-TYPE
      ENTERPRISE dellrcsg2Products
      VARIABLES {
                     dellrcsg2TrapObjectUserName,
                     dellrcsg2TrapObjectSessionIdentifier,
                     dellrcsg2TrapObjectUserAddress,
                     dellrcsg2TrapObjectSessionType
                  }
      DESCRIPTION
         "A target session has stoppped. This may be a serial or KVM
         session, depending on the type of target.

         The name of the user who was connected to the session
         is contained in dellrcsg2TrapObjectUserName.

         The session identifier is contained in
         dellrcsg2TrapObjectSessionIdentifier.

         The user address is contained in
         dellrcsg2TrapObjectUserAddress.

         The session type is contained in
         dellrcsg2TrapObjectSessionType.
         "

      --#SUMMARY "Target session stopped. User: %s. Target device: %s. Address: %s. Type: %s."
      --#ARGUMENTS { 0, 1, 2, 3 }
      --#SEVERITY INFORMATIONAL
      --#FACILITY SECURITY
      --#CATEGORY "Status Events"
      --% TrapTypeEnum=9
      ::= 5


dellrcsg2TargetSessionTerminatedTrap TRAP-TYPE
      ENTERPRISE dellrcsg2Products
      VARIABLES {
                     dellrcsg2TrapObjectUserName,
                     dellrcsg2TrapObjectTargetUserName,
                     dellrcsg2TrapObjectSessionIdentifier,
                     dellrcsg2TrapObjectUserAddress,
                     dellrcsg2TrapObjectSessionType
                  }
      DESCRIPTION
         "A target session has been terminated by another
         user. This may be a serial or KVM session, depending on the
         type of target.

         The name of the user who terminated the session is
         contained in dellrcsg2TrapObjectUserName if available. An empty
         string is reported if a user name is not available.

         The name of the user who was terminated from the session
         is contained in dellrcsg2TrapObjectTargetUserName.

         The session identifier is contained in
         dellrcsg2TrapObjectSessionIdentifier.

         The user address is contained in
         dellrcsg2TrapObjectUserAddress.

         The session type is contained in
         dellrcsg2TrapObjectSessionType.
         "

      --#SUMMARY "Target session terminated. Commanded by user: %s. User: %s. Target device: %s. Address: %s. Type: %s."
      --#ARGUMENTS { 0, 1, 2, 3, 4 }
      --#SEVERITY INFORMATIONAL
      --#FACILITY SECURITY
      --#CATEGORY "Status Events"
      --% TrapTypeEnum=10
      ::= 6


dellrcsg2LocalPortSessionStartedTrap TRAP-TYPE
      ENTERPRISE dellrcsg2Products
      VARIABLES { dellrcsg2TrapObjectSessionIdentifier }
      DESCRIPTION
         "A local port target session has started.

         The session identifier is contained in
         dellrcsg2TrapObjectSessionIdentifier.

         This Trap is deprecated and is no longer used.
         "

      --#SUMMARY "Local port target session started. Target device: %s."
      --#ARGUMENTS { 0 }
      --#SEVERITY INFORMATIONAL
      --#FACILITY SECURITY
      --#CATEGORY "Status Events"
      --% TrapTypeEnum=11
      ::= 7


dellrcsg2LocalPortSessionStoppedTrap TRAP-TYPE
      ENTERPRISE dellrcsg2Products
      VARIABLES { dellrcsg2TrapObjectSessionIdentifier }
      DESCRIPTION
         "A local port target session has stopped.

         The session identifier is contained in
         dellrcsg2TrapObjectSessionIdentifier.

         This Trap is deprecated and is no longer used.
         "

      --#SUMMARY "Local port target session stopped. Target device: %s."
      --#ARGUMENTS { 0 }
      --#SEVERITY INFORMATIONAL
      --#FACILITY SECURITY
      --#CATEGORY "Status Events"
      --% TrapTypeEnum=12
      ::= 8


dellrcsg2LocalPortSessionTerminatedTrap TRAP-TYPE
      ENTERPRISE dellrcsg2Products
      VARIABLES {
                     dellrcsg2TrapObjectUserName,
                     dellrcsg2TrapObjectSessionIdentifier
                  }
      DESCRIPTION
         "A local port target session has been terminated by another
          user.

          The name of the user who terminated the session is
          contained in dellrcsg2TrapObjectUserName.


          The session identifier is contained in
          dellrcsg2TrapObjectSessionIdentifier.

          This Trap is deprecated and is no longer used.
         "

      --#SUMMARY "Local Port Target session terminated. Command issued by user: %s. Target device: %s."
      --#ARGUMENTS { 0, 1 }
      --#SEVERITY INFORMATIONAL
      --#FACILITY SECURITY
      --#CATEGORY "Status Events"
      --% TrapTypeEnum=13
      ::= 9


dellrcsg2ImageFileUpgradeStarted TRAP-TYPE
      ENTERPRISE dellrcsg2Products
      VARIABLES {
                     dellrcsg2TrapObjectUserName,
                     dellrcsg2TrapObjectFileName,
                     dellrcsg2TrapObjectImageNewVersion,
                     dellrcsg2TrapObjectImageCurrentVersion
                  }
      DESCRIPTION
         "The RCS has started an image upgrade.

         The name of the user who originally started the image upgrade is
         contained in dellrcsg2TrapObjectUserName if available. An empty
         string is reported if a user name is not available.

         The URL of the file that was loaded is contained in
         dellrcsg2TrapObjectFileName.

         The version of the image that the RCS is upgrading to is
         contained in dellrcsg2TrapObjectImageNewVersion.

         The version of the image that the RCS is currently running
         is contained in dellrcsg2TrapObjectImageCurrentVersion.
         "

      --#SUMMARY "Image upgrade started. Command issued by user: %s. File: %s. New version: %s. Current version: %s"
      --#ARGUMENTS { 0, 1, 2, 3 }
      --#SEVERITY INFORMATIONAL
      --#FACILITY SYSTEM
      --#CATEGORY "Status Events"
      --% TrapTypeEnum=14
      ::= 10


dellrcsg2ImageFileUpgradeResultsTrap TRAP-TYPE
      ENTERPRISE dellrcsg2Products
      VARIABLES { dellrcsg2TrapObjectImageFileUpgradeResult }
      DESCRIPTION
         "The result of an image upgrade."

      --#SUMMARY "Image upgrade result: %d"
      --#ARGUMENTS { 0 }
      --#SEVERITY INFORMATIONAL
      --#FACILITY SYSTEM
      --#CATEGORY "Status Events"
      --% TrapTypeEnum=15
      ::= 11


dellrcsg2UserAddedTrap TRAP-TYPE
      ENTERPRISE dellrcsg2Products
      VARIABLES {
                     dellrcsg2TrapObjectUserName,
                     dellrcsg2TrapObjectTargetUserName
                  }
      DESCRIPTION
         "A new user has been added to the local user database.

         The name of the user who added the new user is contained
         in dellrcsg2TrapObjectUserName.

         The name of the new user is contained in
         dellrcsg2TrapObjectTargetUserName.
         "

      --#SUMMARY "New user added to local user database. Command issued by user: %s. New user: %s."
      --#ARGUMENTS { 0, 1 }
      --#SEVERITY INFORMATIONAL
      --#FACILITY SECURITY
      --#CATEGORY "Configuration Events"
      --% TrapTypeEnum=16
      ::= 12


dellrcsg2UserDeletedTrap TRAP-TYPE
      ENTERPRISE dellrcsg2Products
      VARIABLES {
                     dellrcsg2TrapObjectUserName,
                     dellrcsg2TrapObjectTargetUserName
                  }
      DESCRIPTION
         "A user has been deleted from the local user database.

         The name of the user who deleted the user is contained
         in dellrcsg2TrapObjectUserName.

         The name of the user who was deleted is contained
         in dellrcsg2TrapObjectTargetUserName.
         "

      --#SUMMARY "User deleted from local user database. Command issued by user: %s. Deleted user: %s."
      --#ARGUMENTS { 0, 1 }
      --#SEVERITY INFORMATIONAL
      --#FACILITY SECURITY
      --#CATEGORY "Configuration Events"
      --% TrapTypeEnum=17
      ::= 13


dellrcsg2UserModifiedTrap TRAP-TYPE
      ENTERPRISE dellrcsg2Products
      VARIABLES {
                     dellrcsg2TrapObjectUserName,
                     dellrcsg2TrapObjectTargetUserName
                  }
      DESCRIPTION
         "A user was modified.

         The name of the user who modified the user is contained
         in dellrcsg2TrapObjectUserName.

         The name of the user who was modified is contained
         in dellrcsg2TrapObjectTargetUserName.
         "

      --#SUMMARY "User modified in local user database. Command issued by user: %s. Modified user: %s."
      --#ARGUMENTS { 0, 1 }
      --#SEVERITY INFORMATIONAL
      --#FACILITY SECURITY
      --#CATEGORY "Configuration Events"
      --% TrapTypeEnum=18
      ::= 14



dellrcsg2UserLockedTrap TRAP-TYPE
      ENTERPRISE dellrcsg2Products
      VARIABLES {
                     dellrcsg2TrapObjectTargetUserName,
                     dellrcsg2TrapObjectLockReason
                  }
      DESCRIPTION
         "A user account has been locked.

         The name of the user who was locked is contained
         in dellrcsg2TrapObjectTargetUserName.

         The reason for which the user account has been locked is contained
         in dellrcsg2TrapObjectLockReason.
         "

      --#SUMMARY "User account has been locked. Locked user: %s. Reason: %s"
      --#ARGUMENTS { 0, 1 }
      --#SEVERITY MINOR
      --#FACILITY SECURITY
      --#CATEGORY "Status Events"
      --% TrapTypeEnum=19
      ::= 15


dellrcsg2UserUnlockedTrap TRAP-TYPE
      ENTERPRISE dellrcsg2Products
      VARIABLES {
                     dellrcsg2TrapObjectUserName,
                     dellrcsg2TrapObjectTargetUserName,
                     dellrcsg2TrapObjectUnlockReason
                  }
      DESCRIPTION
         "A user account has been unlocked.

         The name of the user who unlocked the user is contained
         in dellrcsg2TrapObjectUserName. When the user account is unlocked
         by a RCS reboot or by the expiration of the lockout period
         (as specified in the dellrcsg2TrapObjectUnlockReason object), the
         name of the user will be blank.

         The name of the user who was unlocked is contained
         in dellrcsg2TrapObjectTargetUserName.

         The reason for which the user account has been unlocked is contained
         in dellrcsg2TrapObjectUnlockReason.
         "

      --#SUMMARY "User account has been unlocked. Command issued by user: %s. Unlocked user: %s. Reason: %s"
      --#ARGUMENTS { 0, 1, 2 }
      --#SEVERITY MINOR
      --#FACILITY SECURITY
      --#CATEGORY "Status Events"
      --% TrapTypeEnum=20
      ::= 16



dellrcsg2UserAuthenticationFailureTrap TRAP-TYPE
      ENTERPRISE dellrcsg2Products
      VARIABLES { dellrcsg2TrapObjectUserName }
      DESCRIPTION
         "A user failed to authenticate with the RCS.

         The name of the user who failed to authenticate
         is contained in dellrcsg2TrapObjectUserName.
         "

      --#SUMMARY "User authentication failed with the RCS. User: %s."
      --#ARGUMENTS { 0 }
      --#SEVERITY INFORMATIONAL
      --#FACILITY SECURITY
      --#CATEGORY "Status Events"
      --% TrapTypeEnum=21
      ::= 17


dellrcsg2SIPAddedTrap TRAP-TYPE
      ENTERPRISE dellrcsg2Products
      VARIABLES { dellrcsg2TrapObjectSIPId }
      DESCRIPTION
         "A SIP was added. The ID of the SIP which was added is
         contained in dellrcsg2TrapObjectSIPId.
         "

      --#SUMMARY "SIP added. SIP ID: %s."
      --#ARGUMENTS { 0 }
      --#SEVERITY INFORMATIONAL
      --#FACILITY SYSTEM
      --#CATEGORY "Configuration Events"
      --% TrapTypeEnum=22
      ::= 18


dellrcsg2SIPRemovedTrap TRAP-TYPE
      ENTERPRISE dellrcsg2Products
      VARIABLES { dellrcsg2TrapObjectSIPId }
      DESCRIPTION
         "A SIP was removed. The ID of the SIP which was removed is
         contained in dellrcsg2TrapObjectSIPId.
         "

      --#SUMMARY "SIP removed. SIP ID: %s."
      --#ARGUMENTS { 0 }
      --#SEVERITY INFORMATIONAL
      --#FACILITY SYSTEM
      --#CATEGORY "Configuration Events"
      --% TrapTypeEnum=23
      ::= 19


dellrcsg2SIPMovedTrap TRAP-TYPE
      ENTERPRISE dellrcsg2Products
      VARIABLES {
                    dellrcsg2TrapObjectSIPId,
                    dellrcsg2TrapObjectTargetDeviceName,
                    dellrcsg2TrapObjectInputPort,
                    dellrcsg2TrapObjectOldInputPort
                  }
      DESCRIPTION
         "A SIP was moved.

         The ID of the SIP which was moved is contained in dellrcsg2TrapObjectSIPId.

         The name of the target device attached to the SIP is contained in
         dellrcsg2TrapObjectTargetDeviceName.

         The input port number on the RCS that the SIP is now
         connected to is contained in dellrcsg2TrapObjectInputPort.

         The input port number on the RCS that the SIP
         was previously connected to is contained in
         dellrcsg2TrapObjectOldInputPort.
         "

      --#SUMMARY "SIP moved. SIP ID: %s."
      --#ARGUMENTS { 0, 1, 2, 3 }
      --#SEVERITY INFORMATIONAL
      --#FACILITY SYSTEM
      --#CATEGORY "Configuration Events"
      --% TrapTypeEnum=24
      ::= 20


dellrcsg2TargetDeviceNameChangedTrap TRAP-TYPE
      ENTERPRISE dellrcsg2Products
      VARIABLES {
                     dellrcsg2TrapObjectOldTargetDeviceName,
                     dellrcsg2TrapObjectTargetDeviceName,
                     dellrcsg2TrapObjectSIPId
                  }
      DESCRIPTION
         "The name of a server has changed.

         The previous name of the server is contained in
         dellrcsg2TrapObjectOldTargetDeviceName.

         The new name of the server is contained in
         dellrcsg2TrapObjectTargetDeviceName.

         The ID of the SIP the server is attached to is
         contained in dellrcsg2TrapObjectSIPId.
         "

      --#SUMMARY "Target device name changed. Old name: %s. New name: %s. Attached to SIP: %s."
      --#ARGUMENTS { 0, 1, 2 }
      --#SEVERITY INFORMATIONAL
      --#FACILITY SYSTEM
      --#CATEGORY "Configuration Events"
      --% TrapTypeEnum=25
      ::= 21


dellrcsg2TieredSwitchAddedTrap TRAP-TYPE
      ENTERPRISE dellrcsg2Products
      VARIABLES {
                    dellrcsg2TrapObjectTieredSwitchName,
                    dellrcsg2TrapObjectSIPId
                  }
      DESCRIPTION
         "A tiered switch was added. The name of the switch
         which was added is contained in dellrcsg2TrapObjectTieredSwitchName.

         The ID of the SIP the switch was added to is contained
         in dellrcsg2TrapObjectSIPId.
         "

      --#SUMMARY "Tiered switch added. Tiered switch name: %s. Attached to SIP: %s."
      --#ARGUMENTS { 0, 1 }
      --#SEVERITY INFORMATIONAL
      --#FACILITY SYSTEM
      --#CATEGORY "Configuration Events"
      --% TrapTypeEnum=26
      ::= 22


dellrcsg2TieredSwitchRemovedTrap TRAP-TYPE
      ENTERPRISE dellrcsg2Products
      VARIABLES {
                    dellrcsg2TrapObjectTieredSwitchName,
                    dellrcsg2TrapObjectSIPId
                  }
      DESCRIPTION
         "A tiered switch was removed. The name of the switch
         which was removed is contained in
         dellrcsg2TrapObjectTieredSwitchName.

         The ID of the SIP the switch was attached to is contained
         in dellrcsg2TrapObjectSIPId.
         "

      --#SUMMARY "Tiered switch removed. Tiered switch name: %s. Was attached to SIP: %s."
      --#ARGUMENTS { 0, 1 }
      --#SEVERITY INFORMATIONAL
      --#FACILITY SYSTEM
      --#CATEGORY "Configuration Events"
      --% TrapTypeEnum=27
      ::= 23


dellrcsg2TieredSwitchNameChangedTrap TRAP-TYPE
      ENTERPRISE dellrcsg2Products
      VARIABLES {
                     dellrcsg2TrapObjectOldTieredSwitchName,
                     dellrcsg2TrapObjectTieredSwitchName,
                     dellrcsg2TrapObjectSIPId
                  }
      DESCRIPTION
         "The name of a tiered switch has changed.

         The previous name of the tiered switch is contained in
         dellrcsg2TrapObjectOldTieredSwitchName.

         The new name of the tiered switch is contained in
         dellrcsg2TrapObjectTieredSwitchName.

         The ID of the SIP the switch is attached to is contained
         in dellrcsg2TrapObjectSIPId.
         "

      --#SUMMARY "Tiered switch name changed. Old name: %s. New name: %s. Attached to SIP: %s."
      --#ARGUMENTS { 0, 1, 2 }
      --#SEVERITY INFORMATIONAL
      --#FACILITY SYSTEM
      --#CATEGORY "Configuration Events"
      --% TrapTypeEnum=28
      ::= 24


dellrcsg2ConfigurationFileLoadedTrap TRAP-TYPE
      ENTERPRISE dellrcsg2Products
      VARIABLES {
                     dellrcsg2TrapObjectUserName,
                     dellrcsg2TrapObjectFileName
                  }
      DESCRIPTION
         "The RCS has loaded a configuration file.

         The name of the user who commanded the RCS to
         load the configuration file is contained in
         dellrcsg2TrapObjectUserName.

         The URL of the file that was loaded is contained in
         dellrcsg2TrapObjectFileName.
         "

      --#SUMMARY "Configuration file loaded in the RCS. Command issued by user: %s. Name of file loaded: %s."
      --#ARGUMENTS { 0, 1 }
      --#SEVERITY INFORMATIONAL
      --#FACILITY SYSTEM
      --#CATEGORY "Configuration Events"
      --% TrapTypeEnum=29
      ::= 25


dellrcsg2UserDatabaseFileLoadedTrap TRAP-TYPE
      ENTERPRISE dellrcsg2Products
      VARIABLES {
                     dellrcsg2TrapObjectUserName,
                     dellrcsg2TrapObjectFileName
                  }
      DESCRIPTION
         "The RCS has loaded a user database file.

          The name of the user who commanded the RCS to
          load the user database file is contained in
          dellrcsg2TrapObjectUserName.

          The URL of the file that was loaded is contained in
          dellrcsg2TrapObjectFileName.
         "

      --#SUMMARY "User database file loaded in the RCS. Command issued by user: %s. Name of file loaded: %s."
      --#ARGUMENTS { 0, 1 }
      --#SEVERITY INFORMATIONAL
      --#FACILITY SECURITY
      --#CATEGORY "Configuration Events"
      --% TrapTypeEnum=30
      ::= 26



dellrcsg2CaCertificateLoaded TRAP-TYPE
      ENTERPRISE dellrcsg2Products
      VARIABLES {
                     dellrcsg2TrapObjectUserName
                  }
      DESCRIPTION
         "A user has loaded a new CA Certificate in the RCS.

          The name of the user who loaded the certificate is
          contained in dellrcsg2TrapObjectUserName.
         "
      --#TYPE "CA Certificate has been updated"
      --#SUMMARY "CA Certificate has been updated, by User: %s."
      --#ARGUMENTS { 0 }
      --#SEVERITY INFORMATIONAL
      --#FACILITY SECURITY
      --#CATEGORY "Status Events"
      --% TrapTypeEnum=31
      ::= 27



--
-- SIP Update Traps
--

dellrcsg2SIPImageUpgradeStarted TRAP-TYPE
      ENTERPRISE dellrcsg2Products
      VARIABLES {
                     dellrcsg2TrapObjectUserName,
                     dellrcsg2TrapObjectTypeOfImage,
                     dellrcsg2TrapObjectImageNewVersion,
                     dellrcsg2TrapObjectImageCurrentVersion,
                     dellrcsg2TrapObjectTargetDeviceName,
                     dellrcsg2TrapObjectSIPId
                  }
      DESCRIPTION
         "A software image upgrade has started on a SIP.

         The name of the user who originally started the image upgrade is
         contained in dellrcsg2TrapObjectUserName if available. An empty
         string is reported if a user name is not available.

         The type of software image being upgraded is contained in
         dellrcsg2TrapObjectSIPTypeOfImage.

         The software image version the SIP is upgrading to is
         contained in dellrcsg2TrapObjectImageNewVersion.

         The software image version the SIP is currently running
         is contained in dellrcsg2TrapObjectImageCurrentVersion.

         The name of the server connected to the SIP being upgraded is
         contained in dellrcsg2TrapObjectTargetDeviceName.

         The ID of the SIP being upgraded is contained in
         dellrcsg2TrapObjectSIPId
         "
      --#SUMMARY "SIP image upgrade started. Command issued by user: %s. Image type: %d. New version: %s. Current version: %s. Target device: %s. SIP ID: %s."
      --#ARGUMENTS { 0, 1, 2, 3, 4, 5 }
      --#SEVERITY INFORMATIONAL
      --#FACILITY SYSTEM
      --#CATEGORY "Status Events"
      --% TrapTypeEnum=32
      ::= 28


dellrcsg2SIPImageUpgradeResultTrap TRAP-TYPE
      ENTERPRISE dellrcsg2Products
      VARIABLES {
                     dellrcsg2TrapObjectSIPImageUpgradeResult,
                     dellrcsg2TrapObjectTargetUserName,
                     dellrcsg2TrapObjectTypeOfImage,
                     dellrcsg2TrapObjectImageNewVersion,
                     dellrcsg2TrapObjectImageCurrentVersion,
                     dellrcsg2TrapObjectTargetDeviceName,
                     dellrcsg2TrapObjectSIPId
                  }
      DESCRIPTION
         "The result of a SIP software image upgrade.

         The image upgrade result is contained in
         dellrcsg2TrapObjectSIPImageUpgradeResult.

         The name of the user who originally started the image upgrade is
         contained in dellrcsg2TrapObjectUserName if available. An empty
         string is reported if a user name is not available.

         The type of software image the upgrade result is for is contained in
         dellrcsg2TrapObjectTypeOfImage.

         The software image version the SIP attempted to upgrade to
         is contained in dellrcsg2TrapObjectImageNewVersion.

         The software image version the SIP is running is contained
         in dellrcsg2TrapObjectImageCurrentVersion. If the software image
         upgrade was successful then this version will match the version
         reported in dellrcsg2TrapObjectImageNewVersion.

         The name of the server connected to the SIP is
         contained in dellrcsg2TrapObjectTargetDeviceName.

         The ID of the SIP the result is for is contained in
         dellrcsg2TrapObjectSIPId.

         "
      --#SUMMARY "SIP image upgrade result. Result: %d. Upgrade was started by user: %s. Upgrade image type: %d. Upgrade version: %s. Running version: %s. Target device: %s. SIP ID: %s."
      --#ARGUMENTS { 0, 1, 2, 3, 4, 5, 6 }
      --#SEVERITY INFORMATIONAL
      --#FACILITY SYSTEM
      --#CATEGORY "Status Events"
      --% TrapTypeEnum=33
      ::= 29


dellrcsg2SIPRestartedTrap TRAP-TYPE
      ENTERPRISE dellrcsg2Products
      VARIABLES {
                     dellrcsg2TrapObjectTargetDeviceName,
                     dellrcsg2TrapObjectSIPId
                  }
      DESCRIPTION
         "A SIP has restarted. A SIP will restart after
          a SIP image upgrade completes.

          The name of the server connected to the SIP is
          contained in dellrcsg2TrapObjectTargetDeviceName.

          The ID of the SIP that restarted is for is contained in
          dellrcsg2TrapObjectSIPId.
         "
      --#SUMMARY "SIP restarted. Target device: %s. SIP ID: %s."
      --#ARGUMENTS { 0, 1 }
      --#SEVERITY INFORMATIONAL
      --#FACILITY SYSTEM
      --#CATEGORY "Status Events"
      --% TrapTypeEnum=34
      ::= 30



--
-- Virtual Media Traps
--

dellrcsg2VirtualMediaSessionStartedTrap TRAP-TYPE
      ENTERPRISE dellrcsg2Products
      VARIABLES {
                     dellrcsg2TrapObjectUserName,
                     dellrcsg2TrapObjectTargetDeviceName,
                     dellrcsg2TrapObjectSIPId,
                     dellrcsg2TrapObjectUserAddress
                  }
      DESCRIPTION
         "A Virtual Media session to a server has started. A target
          session to the server must have been established by the same user
          prior to starting the VM session.

          The name of the user who connected to the VM session
          is contained in dellrcsg2TrapObjectUserName.

          The name of the server the user connected to is contained in
          dellrcsg2TrapObjectTargetDeviceName.

          The ID of the SIP the target session is using is contained in
          dellrcsg2TrapObjectSIPId.

          The user address is contained in
          dellrcsg2TrapObjectUserAddress.
        "
      --#SUMMARY "Virtual media session started. User: %s. Target device: %s. SIP: %s. Address: %s."
      --#ARGUMENTS { 0, 1, 2, 3 }
      --#SEVERITY INFORMATIONAL
      --#FACILITY SECURITY
      --#CATEGORY "Status Events"
      --% TrapTypeEnum=35
      ::= 31


dellrcsg2VirtualMediaSessionStoppedTrap TRAP-TYPE
      ENTERPRISE dellrcsg2Products
      VARIABLES {
                     dellrcsg2TrapObjectUserName,
                     dellrcsg2TrapObjectTargetDeviceName,
                     dellrcsg2TrapObjectUserAddress
                  }
      DESCRIPTION
         "A virtual media session to a server has stopped.

          The name of the user who was connected to the VM session
          is contained in dellrcsg2TrapObjectUserName.

          The name of the server the user was connected to is contained in
          dellrcsg2TrapObjectTargetDeviceName.

          The user address is contained in
          dellrcsg2TrapObjectUserAddress.
         "
      --#SUMMARY "Virtual media session stopped. User: %s. Target device: %s. Address: %s."
      --#ARGUMENTS { 0, 1, 2 }
      --#SEVERITY INFORMATIONAL
      --#FACILITY SECURITY
      --#CATEGORY "Status Events"
      --% TrapTypeEnum=36
      ::= 32


dellrcsg2VirtualMediaSessionTerminatedTrap TRAP-TYPE
      ENTERPRISE dellrcsg2Products
      VARIABLES {
                     dellrcsg2TrapObjectUserName,
                     dellrcsg2TrapObjectTargetUserName,
                     dellrcsg2TrapObjectTargetDeviceName,
                     dellrcsg2TrapObjectUserAddress
                  }
      DESCRIPTION
         "A virtual media session has been terminated or preempted
          by another user.

          The name of the user who terminated or preempted the VM session is
          contained in dellrcsg2TrapObjectUserName if available. An empty
          string is reported if a user name is not available. A user
          name will not be available if a remote session was terminated
          or preempted from the OSCAR interface and OSCAR authentication is
          disabled.

          The name of the user who was terminated or preempted from the VM
          session is contained in dellrcsg2TrapObjectTargetUserName.

          The name of the server the user was connected to contained in
          dellrcsg2TrapObjectTargetDeviceName.

          The user address is contained in
          dellrcsg2TrapObjectUserAddress.
         "
      --#SUMMARY "Virtual media session terminated. Command issued by user: %s. Terminated user: %s. Target device: %s. Address: %s."
      --#ARGUMENTS { 0, 1, 2, 3 }
      --#SEVERITY INFORMATIONAL
      --#FACILITY SECURITY
      --#CATEGORY "Status Events"
      --% TrapTypeEnum=37
      ::= 33


dellrcsg2VirtualMediaSessionReservedTrap TRAP-TYPE
      ENTERPRISE dellrcsg2Products
      VARIABLES {
                     dellrcsg2TrapObjectUserName,
                     dellrcsg2TrapObjectTargetDeviceName,
                     dellrcsg2TrapObjectUserAddress
                  }
      DESCRIPTION
         "A user established a reserved virtual media session.

         The name of the user who has established a reserved virtual media session
         is contained in dellrcsg2TrapObjectUserName.

         The name of the server the user was connected to is contained in
         dellrcsg2TrapObjectTargetDeviceName.

         The user address is contained in
         dellrcsg2TrapObjectUserAddress.
         "
      --#SUMMARY "Virtual media session has been reserved. User: %s. Target device: %s. Address: %s."
      --#ARGUMENTS { 0, 1, 2 }
      --#SEVERITY INFORMATIONAL
      --#FACILITY SECURITY
      --#CATEGORY "Status Events"
      --% TrapTypeEnum=38
      ::= 34


dellrcsg2VirtualMediaSessionUnreservedTrap TRAP-TYPE
      ENTERPRISE dellrcsg2Products
      VARIABLES {
                     dellrcsg2TrapObjectUserName,
                     dellrcsg2TrapObjectTargetDeviceName,
                     dellrcsg2TrapObjectUserAddress
                  }
      DESCRIPTION
         "A user established a non-reserved virtual media session.

         The name of the user who has established a non-reserved virtual media session
         is contained in dellrcsg2TrapObjectUserName.

         The name of the server the user was connected to is contained in
         dellrcsg2TrapObjectTargetDeviceName.

         The user address is contained in
         dellrcsg2TrapObjectUserAddress.
         "
      --#SUMMARY "User has established a non-reserved virtual media session. User: %s. Target device: %s. Address: %s."
      --#ARGUMENTS { 0, 1, 2 }
      --#SEVERITY INFORMATIONAL
      --#FACILITY SECURITY
      --#CATEGORY "Status Events"
      --% TrapTypeEnum=39
      ::= 35


dellrcsg2VirtualMediaDriveMapped TRAP-TYPE
      ENTERPRISE dellrcsg2Products
      VARIABLES {
                     dellrcsg2TrapObjectUserName,
                     dellrcsg2TrapObjectTargetDeviceName,
                     dellrcsg2TrapObjectVirtualMediaDriveType,
                     dellrcsg2TrapObjectVirtualMediaDriveAccessMode,
                     dellrcsg2TrapObjectUserAddress
                  }
      DESCRIPTION
         "A virtual media drive has been mapped.

         The name of the user who has established the virtual media session
         is contained in dellrcsg2TrapObjectUserName.

         The name of the server the user was connected to is contained in
         dellrcsg2TrapObjectTargetDeviceName.

         The type of drive that has been mapped is contained in
         dellrcsg2TrapObjectVirtualMediaDriveType.

         The access mode for the drive that has been mapped is contained in
         dellrcsg2TrapObjectVirtualMediaDriveAccessMode.

         The user address is contained in
         dellrcsg2TrapObjectUserAddress.
         "
      --#SUMMARY "Virtual media has been mapped. User: %s. Target device: %s Type: %d. Access Mode: %d. Address: %s."
      --#ARGUMENTS { 0, 1, 2, 3, 4 }
      --#SEVERITY INFORMATIONAL
      --#FACILITY SYSTEM
      --#CATEGORY "Status Events"
      --% TrapTypeEnum=40
      ::= 36


dellrcsg2VirtualMediaDriveUnmapped TRAP-TYPE
      ENTERPRISE dellrcsg2Products
      VARIABLES {
                     dellrcsg2TrapObjectUserName,
                     dellrcsg2TrapObjectTargetDeviceName,
                     dellrcsg2TrapObjectVirtualMediaDriveType,
                     dellrcsg2TrapObjectVirtualMediaDriveAccessMode,
                     dellrcsg2TrapObjectUserAddress
                  }
      DESCRIPTION
         "A virtual media drive has been unmapped.

         The name of the user who has established the virtual media session
         is contained in dellrcsg2TrapObjectUserName.

         The name of the server the user was connected to is contained in
         dellrcsg2TrapObjectTargetDeviceName.

         The type of drive that has been unmapped is contained in
         dellrcsg2TrapObjectVirtualMediaDriveType.

         The access mode for the drive that has been unmapped is contained in
         dellrcsg2TrapObjectVirtualMediaDriveAccessMode.

         The user address is contained in
         dellrcsg2TrapObjectUserAddress.
         "
      --#SUMMARY "Virtual media has been unmapped. User: %s. Target device: %s Type: %d. Access Mode: %d. Address: %s."
      --#ARGUMENTS { 0, 1, 2, 3, 4 }
      --#SEVERITY INFORMATIONAL
      --#FACILITY SYSTEM
      --#CATEGORY "Status Events"
      --% TrapTypeEnum=41
      ::= 37


dellrcsg2LocalPortVirtualMediaSessionStartedTrap TRAP-TYPE
      ENTERPRISE dellrcsg2Products
      VARIABLES {
                     dellrcsg2TrapObjectUserName,
                     dellrcsg2TrapObjectTargetDeviceName,
                     dellrcsg2TrapObjectSIPId
                  }
      DESCRIPTION
         "A local user has started a Virtual Media session to a server. A target
          session to the server must have been established by a local user
          prior to starting the VM session.

          The name of the user who connected to the VM session
          is contained in dellrcsg2TrapObjectUserName.

          The name of the server the user connected to is contained in
          dellrcsg2TrapObjectTargetDeviceName.

          The ID of the SIP the target session is using is contained in
          dellrcsg2TrapObjectSIPId.

          This Trap is deprecated and is no longer used.
        "
      --#SUMMARY "Local virtual media session started. User: %s. Target device: %s. SIP: %s."
      --#ARGUMENTS { 0, 1, 2 }
      --#SEVERITY INFORMATIONAL
      --#FACILITY SECURITY
      --#CATEGORY "Status Events"
      --% TrapTypeEnum=42
      ::= 38


dellrcsg2LocalPortVirtualMediaSessionStoppedTrap TRAP-TYPE
      ENTERPRISE dellrcsg2Products
      VARIABLES {
                     dellrcsg2TrapObjectUserName,
                     dellrcsg2TrapObjectTargetDeviceName
                  }
      DESCRIPTION
         "A local user has stopped a Virtual Media session to a server.

          The name of the user who was connected to the VM session
          is contained in dellrcsg2TrapObjectUserName.

          The name of the server the user was connected to is contained in
          dellrcsg2TrapObjectTargetDeviceName.

          This Trap is deprecated and is no longer used.
         "
      --#SUMMARY "Local virtual media session stopped. User: %s. Target device: %s."
      --#ARGUMENTS { 0, 1 }
      --#SEVERITY INFORMATIONAL
      --#FACILITY SECURITY
      --#CATEGORY "Status Events"
      --% TrapTypeEnum=43
      ::= 39


dellrcsg2LocalPortVirtualMediaSessionTerminatedTrap TRAP-TYPE
      ENTERPRISE dellrcsg2Products
      VARIABLES {
                     dellrcsg2TrapObjectUserName,
                     dellrcsg2TrapObjectTargetDeviceName
                  }
      DESCRIPTION
         "A local virtual media session has been terminated or preempted
          by another user.

          The name of the user who terminated or preempted the VM session is
          contained in dellrcsg2TrapObjectUserName if available. An empty
          string is reported if a user name is not available.

          The name of the server the user was connected to contained in
          dellrcsg2TrapObjectTargetDeviceName.

          This Trap is deprecated and is no longer used.
         "
      --#TYPE "Local Port Virtual Media Session Terminated"
      --#SUMMARY "Local Port Virtual Media session terminated. Command issued by user: %s. Target device: %s."
      --#ARGUMENTS { 0, 1 }
      --#SEVERITY INFORMATIONAL
      --#FACILITY SECURITY
      --#CATEGORY "Status Events"
      --% TrapTypeEnum=44
      ::= 40


dellrcsg2LocalPortVirtualMediaDriveMapped TRAP-TYPE
      ENTERPRISE dellrcsg2Products
      VARIABLES { dellrcsg2TrapObjectSessionIdentifier,
                    dellrcsg2TrapObjectVirtualMediaDriveType,
                    dellrcsg2TrapObjectVirtualMediaDriveAccessMode }
      DESCRIPTION
         "A user on the local port has mapped a virtual media drive to the server.

         The session identifier is contained in dellrcsg2TrapObjectSessionIdentifier.

         The type of drive that has been unmapped is contained in
         dellrcsg2TrapObjectVirtualMediaDriveType.

         The access mode for the drive that has been unmapped is contained in
         dellrcsg2TrapObjectVirtualMediaDriveAccessMode.

         This Trap is deprecated and is no longer used.
         "

      --#TYPE "Local Port Virtual Media Drive Mapped Trap"
      --#SUMMARY "Virtual Media Drive Mapped on the local port. Target device: %s."
      --#ARGUMENTS { 0 }
      --#SEVERITY INFORMATIONAL
      --#FACILITY SYSTEM
      --#CATEGORY "Status Events"
      --% TrapTypeEnum=45
      ::= 41


dellrcsg2LocalPortVirtualMediaDriveUnmapped TRAP-TYPE
      ENTERPRISE dellrcsg2Products
      VARIABLES { dellrcsg2TrapObjectSessionIdentifier,
                    dellrcsg2TrapObjectVirtualMediaDriveType,
                    dellrcsg2TrapObjectVirtualMediaDriveAccessMode }
      DESCRIPTION
         "A user on the local port has unmapped a virtual media drive to the server.

         The session identifier is contained in
         dellrcsg2TrapObjectSessionIdentifier.

         The type of drive that has been unmapped is contained in
         dellrcsg2TrapObjectVirtualMediaDriveType.

         The access mode for the drive that has been unmapped is contained in
         dellrcsg2TrapObjectVirtualMediaDriveAccessMode.

         This Trap is deprecated and is no longer used.
         "

      --#TYPE "Local Port Virtual Media Drive Unmapped Trap"
      --#SUMMARY "Virtual Media Drive Unmapped on the local port. Target device: %s."
      --#ARGUMENTS { 0 }
      --#SEVERITY INFORMATIONAL
      --#FACILITY SYSTEM
      --#CATEGORY "Status Events"
      --% TrapTypeEnum=46
      ::= 42


dellrcsg2LocalPortVirtualMediaSessionReservedTrap TRAP-TYPE
      ENTERPRISE dellrcsg2Products
      VARIABLES {
                     dellrcsg2TrapObjectTargetDeviceName
                  }
      DESCRIPTION
         "A local user has reserved a virtual media session.

          The name of the server the user was connected to is contained in
          dellrcsg2TrapObjectTargetDeviceName.

          This Trap is deprecated and is no longer used.
         "
      --#TYPE "Local Port Virtual Media Session Reserved"
      --#SUMMARY "Local Port virtual media session has been reserved. Target device: %s."
      --#ARGUMENTS { 0 }
      --#SEVERITY INFORMATIONAL
      --#FACILITY SYSTEM
      --#CATEGORY "Status Events"
      --% TrapTypeEnum=47
      ::= 43


dellrcsg2LocalPortVirtualMediaSessionUnreservedTrap TRAP-TYPE
      ENTERPRISE dellrcsg2Products
      VARIABLES {
                     dellrcsg2TrapObjectTargetDeviceName
                  }
      DESCRIPTION
         "A user has unreserved a local virtual media session.

          The name of the server the user was connected to is contained in
          dellrcsg2TrapObjectTargetDeviceName.

          This Trap is deprecated and is no longer used.
         "
      --#TYPE "Local Port Virtual Media Session Unreserved"
      --#SUMMARY "Local Port virtual media session has been unreserved. Target device: %s."
      --#ARGUMENTS { 0 }
      --#SEVERITY INFORMATIONAL
      --#FACILITY SECURITY
      --#CATEGORY "Status Events"
      --% TrapTypeEnum=48
      ::= 44



dellrcsg2ScreenResolutionChangedTrap TRAP-TYPE
      ENTERPRISE dellrcsg2Products
      VARIABLES {
                     dellrcsg2TrapObjectUserName,
                     dellrcsg2TrapObjectTargetDeviceName,
                     dellrcsg2TrapObjectPreviousScreenResolution,
                     dellrcsg2TrapObjectCurrentScreenResolution,
                     dellrcsg2TrapObjectSessionIdentifier
                  }
      DESCRIPTION
         "The screen resolution of a server was changed.

         The name of the user who changed the screen resolution is contained
         in dellrcsg2TrapObjectUserName if available. An empty string is
         reported if a user name is not available. A user name will not be
         available if the target session controlling the server was started
         from the local interface and local authentication is disabled.

         The name of the server the screen resolution was changed on is
         contained in dellrcsg2TrapObjectTargetDeviceName.

         The previous screen resolution is contained in
         dellrcsg2TrapObjectPreviousScreenResolution.

         The new screen resolution is contained in
         dellrcsg2TrapObjectCurrentScreenResolution.

         The session identifier is contained in
         dellrcsg2TrapObjectSessionIdentifier.

         "
      --#SUMMARY "Screen resolution changed. User: %s. Target device: %s. Previous Resolution: %s. New Resolution: %s. Session: %s."
      --#ARGUMENTS { 0, 1, 2, 3, 4 }
      --#SEVERITY INFORMATIONAL
      --#FACILITY SYSTEM
      --#CATEGORY "Status Events"
      --% TrapTypeEnum=49
      ::= 45


dellrcsg2AggregatedTargetDeviceStatusChangedTrap TRAP-TYPE
      ENTERPRISE dellrcsg2Products
      VARIABLES { dellrcsg2TrapObjectAggregatedTargetDeviceStatusChanged }
      DESCRIPTION
         "The status of one or more servers (connection paths) has
         changed.

         A list of connection paths whose status has changed is contained
         in dellrcsg2TrapObjectAggregatedTargetDeviceStatusChanged.

         This trap is always sent by the RCS on bootup to report the
         current status of all connection paths. Thereafter the trap is sent
         when there is a change in connection path status and will include only
         those paths whose status has changed.
         "
      --#SUMMARY "Aggregate server status changed."
      --#SEVERITY INFORMATIONAL
      --#FACILITY SYSTEM
      --#CATEGORY "Status Events"
      --% TrapTypeEnum=50
      ::= 46


dellrcsg2FactoryDefaultsSetTrap TRAP-TYPE
      ENTERPRISE dellrcsg2Products
      DESCRIPTION
         "The RCS has been commanded to set itself to factory defaults.

         The RCS sends this trap after being commanded to set itself
         to factory defaults but prior to actually reverting to factory
         defaults.
         "
      --#SUMMARY "The RCS was commanded to set itself to factory defaults."
      --#SEVERITY INFORMATIONAL
      --#FACILITY SYSTEM
      --#CATEGORY "Configuration Events"
      --% TrapTypeEnum=51
      ::= 47


dellrcsg2PowerSupplyFailureTrap TRAP-TYPE
      ENTERPRISE dellrcsg2Products
      VARIABLES {
                     dellrcsg2TrapObjectPowerSupply
                  }
      DESCRIPTION
         "A power supply failure has ocurred, for RCSes with dual power supplies.

          The power supply which has failed is indicated in dellrcsg2TrapObjectPowerSupply.
         "
      --#SUMMARY "Power Supply %s has failed"
      --#ARGUMENTS { 0 }
      --#SEVERITY INFORMATIONAL
      --#FACILITY SYSTEM
      --#CATEGORY "Status Events"
      --% TrapTypeEnum=52
      ::= 48


dellrcsg2PowerSupplyRestoredTrap TRAP-TYPE
      ENTERPRISE dellrcsg2Products
      VARIABLES {
                     dellrcsg2TrapObjectPowerSupply
                  }
      DESCRIPTION
         "A power supply has been restored, for RCSes with dual power supplies.

          The power supply which has been restored is indicated in dellrcsg2TrapObjectPowerSupply.
         "
      --#SUMMARY "Power Supply %s has been restored"
      --#ARGUMENTS { 0 }
      --#SEVERITY INFORMATIONAL
      --#FACILITY SYSTEM
      --#CATEGORY "Status Events"
      --% TrapTypeEnum=53
      ::= 49



--
-- PDU Traps
--

dellrcsg2PduDeviceOnlineTrap TRAP-TYPE
      ENTERPRISE dellrcsg2Products
      VARIABLES {
                     dellrcsg2TrapObjectPduDevicePort,
                     dellrcsg2TrapObjectPduDeviceNumber
                  }
      DESCRIPTION
         "A power device attached to the RCS is detected to be online.

          This trap is sent upon initialization of the power device if it is
          online and responding. Subsequent traps are sent if the power device
          transitions from offline to online.

          The port number on the RCS that the power device is attached to
          is contained in dellrcsg2TrapObjectPduDevicePort.

          The number of the power device that is connected to a port of the
          RCS is contained in dellrcsg2TrapObjectPduDeviceNumber.
         "

      --#SUMMARY "A power device is online. Port number: %d. Power device number: %d."
      --#ARGUMENTS { 0, 1 }
      --#SEVERITY MINOR
      --#FACILITY SYSTEM
      --#CATEGORY "Status Events"
      --% TrapTypeEnum=54
      ::= 50


dellrcsg2PduDeviceOfflineTrap TRAP-TYPE
      ENTERPRISE dellrcsg2Products
      VARIABLES {
                     dellrcsg2TrapObjectPduDevicePort,
                     dellrcsg2TrapObjectPduDeviceNumber
                  }
      DESCRIPTION
         "A power device attached to the RCS is detected to be offline.

         This trap is sent upon initialization of the power device if it is not
         responding. Subsequent traps are sent if the power device transitions
         from online to offline.

         The port number on the RCS that the power device is attached to
         is contained in dellrcsg2TrapObjectPduDevicePort.

         The number of the power device that is connected to a port of the
         RCS is contained in dellrcsg2TrapObjectPduDeviceNumber.
       "

      --#SUMMARY "A power device is offline. Port number: %d. Power device number: %d."
      --#ARGUMENTS { 0, 1 }
      --#SEVERITY CRITICAL
      --#FACILITY SYSTEM
      --#CATEGORY "Error Events"
      --% TrapTypeEnum=55
      ::= 51


dellrcsg2PduOutletOnCommandTrap TRAP-TYPE
      ENTERPRISE dellrcsg2Products
      VARIABLES {
                     dellrcsg2TrapObjectUserName,
                     dellrcsg2TrapObjectTargetDeviceName,
                     dellrcsg2TrapObjectPduDevicePort,
                     dellrcsg2TrapObjectPduDeviceNumber,
                     dellrcsg2TrapObjectPduOutlet
                  }
      DESCRIPTION
         "A outlet on a power device has been issued the on command.

         The port number on the RCS that the power device is attached to
         is contained in dellrcsg2TrapObjectPduDevicePort.

         The outlet number that was issued the on command is contained
         in dellrcsg2TrapObjectPduOutlet.

         The name of the server connected to the power device outlet is
         contained in dellrcsg2TrapObjectTargetDeviceName.

         The number of the power device that is connected to a port of the
         RCS is contained in dellrcsg2TrapObjectPduDeviceNumber.
         "

      --#SUMMARY "The on command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=56
      ::= 52


dellrcsg2PduOutletOffCommandTrap TRAP-TYPE
      ENTERPRISE dellrcsg2Products
      VARIABLES {
                     dellrcsg2TrapObjectUserName,
                     dellrcsg2TrapObjectTargetDeviceName,
                     dellrcsg2TrapObjectPduDevicePort,
                     dellrcsg2TrapObjectPduDeviceNumber,
                     dellrcsg2TrapObjectPduOutlet
                  }
      DESCRIPTION
         "A outlet on a power device has been issued the off command.

         The port number on the RCS that the power device is attached to
         is contained in dellrcsg2TrapObjectPduDevicePort.

         The outlet number that was issued the off command is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "The off command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=57
      ::= 53


dellrcsg2PduOutletRebootCommandTrap TRAP-TYPE
      ENTERPRISE dellrcsg2Products
      VARIABLES {
                     dellrcsg2TrapObjectUserName,
                     dellrcsg2TrapObjectTargetDeviceName,
                     dellrcsg2TrapObjectPduDevicePort,
                     dellrcsg2TrapObjectPduDeviceNumber,
                     dellrcsg2TrapObjectPduOutlet
                  }
      DESCRIPTION
         "A outlet on a power device has been issued the reboot command.

         The port number on the RCS that the power device is attached to
         is contained in dellrcsg2TrapObjectPduDevicePort.

         The outlet number that was issued the reboot command is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "The reboot command was issued to a power device outlet. Command issued by user: %s. Target device: %s. Port number: %d. Power device number: %d. Outlet number: %d."
      --#ARGUMENTS { 0, 1, 2, 3, 4 }
      --#SEVERITY INFORMATIONAL
      --#FACILITY SECURITY
      --#CATEGORY "Status Events"
      --% TrapTypeEnum=58
      ::= 54



dellrcsg2PduOutletOnSenseFailTrap TRAP-TYPE
      ENTERPRISE dellrcsg2Products
      VARIABLES {
                     dellrcsg2TrapObjectTargetDeviceName,
                     dellrcsg2TrapObjectPduDevicePort,
                     dellrcsg2TrapObjectPduDeviceNumber,
                     dellrcsg2TrapObjectPduOutlet
                  }
      DESCRIPTION
         "A power device attached to the RCS has detected an on sense
         failure for a outlet.

         An on sense failure occurs when a outlet should be in the on state
         but is actually in the off state.

         The port number on the RCS that the power device is attached to
         is contained in dellrcsg2TrapObjectPduDevicePort.

         The outlet number that has the failure is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "Power device outlet on sense failure. Target device: %s. Port number: %d. Power device number: %d. Outlet number: %d."
      --#ARGUMENTS { 0, 1, 2, 3 }
      --#SEVERITY CRITICAL
      --#FACILITY SYSTEM
      --#CATEGORY "Error Events"
      --% TrapTypeEnum=59
      ::= 55


dellrcsg2PduOutletOffSenseFailTrap TRAP-TYPE
      ENTERPRISE dellrcsg2Products
      VARIABLES {
                     dellrcsg2TrapObjectTargetDeviceName,
                     dellrcsg2TrapObjectPduDevicePort,
                     dellrcsg2TrapObjectPduDeviceNumber,
                     dellrcsg2TrapObjectPduOutlet
                  }
      DESCRIPTION
         "A power device attached to the RCS has detected an off sense
         failure for a outlet.

         An off sense failure occurs when a outlet should be in the off state
         but is actually in the on state.

         The port number on the RCS that the power device is attached to
         is contained in dellrcsg2TrapObjectPduDevicePort.

         The outlet number that has the failure is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "Power device outlet off sense failure. Target device: %s. Port number: %d. Power device number: %d. Outlet number: %d."
      --#ARGUMENTS { 0, 1, 2, 3 }
      --#SEVERITY CRITICAL
      --#FACILITY SYSTEM
      --#CATEGORY "Error Events"
      --% TrapTypeEnum=60
      ::= 56



dellrcsg2PduStatusOutletOnTrap TRAP-TYPE
      ENTERPRISE dellrcsg2Products
      VARIABLES {
                     dellrcsg2TrapObjectTargetDeviceName,
                     dellrcsg2TrapObjectPduDevicePort,
                     dellrcsg2TrapObjectPduDeviceNumber,
                     dellrcsg2TrapObjectPduOutlet
                  }
      DESCRIPTION
         "A power device outlet has changed to the on state.

         The port number on the RCS that the power device is attached to
         is contained in dellrcsg2TrapObjectPduDevicePort.

         The outlet number that has changed to the on state is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "Power device outlet state changed to on. Target device: %s. Port number: %d. Power device number: %d. Outlet number: %d."
      --#ARGUMENTS { 0, 1, 2, 3 }
      --#SEVERITY MINOR
      --#FACILITY SYSTEM
      --#CATEGORY "Status Events"
      --% TrapTypeEnum=61
      ::= 57


dellrcsg2PduStatusOutletOffTrap TRAP-TYPE
      ENTERPRISE dellrcsg2Products
      VARIABLES {
                     dellrcsg2TrapObjectTargetDeviceName,
                     dellrcsg2TrapObjectPduDevicePort,
                     dellrcsg2TrapObjectPduDeviceNumber,
                     dellrcsg2TrapObjectPduOutlet
                  }
      DESCRIPTION
         "A power device outlet has changed to the off state.

         The port number on the RCS that the power device is attached to
         is contained in dellrcsg2TrapObjectPduDevicePort.

         The outlet number that has changed to the off state is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "Power device outlet state changed to off. Target device: %s. Port number: %d. Power device number: %d. Outlet number: %d."
      --#ARGUMENTS { 0, 1, 2, 3 }
      --#SEVERITY MAJOR
      --#FACILITY SYSTEM
      --#CATEGORY "Status Events"
      --% TrapTypeEnum=62
      ::= 58


dellrcsg2PduPortNameChangedTrap TRAP-TYPE
      ENTERPRISE dellrcsg2Products
      VARIABLES {
                     dellrcsg2TrapObjectOldName,
                     dellrcsg2TrapObjectItemName,
                     dellrcsg2TrapObjectPduDevicePort,
                     dellrcsg2TrapObjectPduDeviceNumber
                  }
      DESCRIPTION
         "The name of a power device port has changed.

         The previous name of the power device port is contained in
         dellrcsg2TrapObjectOldName.

         The new name of the power device port is contained in
         dellrcsg2TrapObjectItemName.

         The port number on the RCS that the power device is attached to
         is contained in dellrcsg2TrapObjectPduDevicePort.

         The number of the power device that is connected to a port of the
         RCS is contained in dellrcsg2TrapObjectPduDeviceNumber.
         "
      --#SUMMARY "Power device port name changed. Old name: %s. New name: %s. Port number: %d. Power device number: %d."
      --#ARGUMENTS { 0, 1, 2, 3 }
      --#SEVERITY INFORMATIONAL
      --#FACILITY SYSTEM
      --#CATEGORY "Configuration Events"
      --% TrapTypeEnum=63
      ::= 59


dellrcsg2PduOutletNameChangedTrap TRAP-TYPE
      ENTERPRISE dellrcsg2Products
      VARIABLES {
                     dellrcsg2TrapObjectOldName,
                     dellrcsg2TrapObjectItemName,
                     dellrcsg2TrapObjectPduDevicePort,
                     dellrcsg2TrapObjectPduDeviceNumber,
                     dellrcsg2TrapObjectPduOutlet
                  }
      DESCRIPTION
         "The name of a power device outlet has changed.

         The previous name of the power device outlet is contained in
         dellrcsg2TrapObjectOldName.

         The new name of the power device outlet is contained in
         dellrcsg2TrapObjectItemName.

         The port number on the RCS that the power device is attached to
         is contained in dellrcsg2TrapObjectPduDevicePort.

         The number of the power device that is connected to a port of the
         RCS is contained in dellrcsg2TrapObjectPduDeviceNumber.

         The outlet number of the power device is contained in
         dellrcsg2TrapObjectPduOutlet.
         "
      --#SUMMARY "Power device outlet name changed. Old name: %s. New name: %s. Port number: %d. Power device number: %d. Outlet number: %d."
      --#ARGUMENTS { 0, 1, 2, 3, 4 }
      --#SEVERITY INFORMATIONAL
      --#FACILITY SYSTEM
      --#CATEGORY "Configuration Events"
      --% TrapTypeEnum=64
      ::= 60


dellrcsg2PduInletTotalLoadHighTrap TRAP-TYPE
      ENTERPRISE dellrcsg2Products
      VARIABLES {
                     dellrcsg2TrapObjectPduDevicePort,
                     dellrcsg2TrapObjectPduDeviceNumber,
                     dellrcsg2TrapObjectPduDeviceInlet
                  }
      DESCRIPTION
         "A power device attached to the RCS has exceeded the maximum
         threshold for total load of an inlet.

         The port number on the RCS that the power device is attached to
         is contained in dellrcsg2TrapObjectPduDevicePort.

         The number of the power device that is connected to a port of the
         RCS is contained in dellrcsg2TrapObjectPduDeviceNumber.

         The inlet of the power device is contained in
         dellrcsg2TrapObjectPduDeviceInlet.
         "
      --#SUMMARY "Power device inlet exceeded the total load maximum threshold. Port number: %d. Power device number: %d. Inlet: %d."
      --#ARGUMENTS { 0, 1, 2 }
      --#SEVERITY MAJOR
      --#FACILITY SYSTEM
      --#CATEGORY "Threshold Events"
      --% TrapTypeEnum=65
      ::= 61


dellrcsg2PduInletTotalLoadLowTrap TRAP-TYPE
      ENTERPRISE dellrcsg2Products
      VARIABLES {
                     dellrcsg2TrapObjectPduDevicePort,
                     dellrcsg2TrapObjectPduDeviceNumber,
                     dellrcsg2TrapObjectPduDeviceInlet
                  }
      DESCRIPTION
         "A power device attached to the RCS has gone beneath the minimum
          threshold for total load.

          The port number on the RCS that the power device is attached to
          is contained in dellrcsg2TrapObjectPduDevicePort.

          The number of the power device that is connected to a port of the
          RCS is contained in dellrcsg2TrapObjectPduDeviceNumber.

          The inlet of the power device is contained in
          dellrcsg2TrapObjectPduDeviceInlet.
         "
      --#SUMMARY "Power device inlet exceeded the total load minimum threshold. Port number: %d. Power device number: %d. Inlet: %d."
      --#ARGUMENTS { 0, 1, 2 }
      --#SEVERITY MAJOR
      --#FACILITY SYSTEM
      --#CATEGORY "Threshold Events"
      --% TrapTypeEnum=66
      ::= 62


dellrcsg2PduDeviceNameChangedTrap TRAP-TYPE
      ENTERPRISE dellrcsg2Products
      VARIABLES {
                     dellrcsg2TrapObjectOldName,
                     dellrcsg2TrapObjectItemName,
                     dellrcsg2TrapObjectPduDevicePort,
                     dellrcsg2TrapObjectPduDeviceNumber
                  }
      DESCRIPTION
         "The name of a power device has changed.

         The previous name of the power device is contained in
         dellrcsg2TrapObjectOldName.

         The new name of the power device is contained in
         dellrcsg2TrapObjectItemName.

         The port number on the RCS that the power device is attached to
         is contained in dellrcsg2TrapObjectPduDevicePort.

         The number of the power device that is connected to a port of the
         RCS is contained in dellrcsg2TrapObjectPduDeviceNumber.
         "
      --#SUMMARY "Power device name changed. Old name: %s. New name: %s. Port number: %d. Power device number: %d."
      --#ARGUMENTS { 0, 1, 2, 3 }
      --#SEVERITY INFORMATIONAL
      --#FACILITY SYSTEM
      --#CATEGORY "Configuration Events"
      --% TrapTypeEnum=67
      ::= 63


dellrcsg2PduInletNameChangedTrap TRAP-TYPE
      ENTERPRISE dellrcsg2Products
      VARIABLES {
                     dellrcsg2TrapObjectOldName,
                     dellrcsg2TrapObjectItemName,
                     dellrcsg2TrapObjectPduDevicePort,
                     dellrcsg2TrapObjectPduDeviceNumber,
                     dellrcsg2TrapObjectPduDeviceInlet
                  }
      DESCRIPTION
         "The name of a power device inlet has changed.

          The previous name of the power device inlet is contained in
          dellrcsg2TrapObjectOldName.

          The new name of the power device inlet is contained in
          dellrcsg2TrapObjectItemName.

          The port number on the RCS that the power device is attached to
          is contained in dellrcsg2TrapObjectPduDevicePort.

          The number of the power device that is connected to a port of the
          RCS is contained in dellrcsg2TrapObjectPduDeviceNumber.

          The inlet of the power device is contained in
          dellrcsg2TrapObjectPduDeviceInlet.
         "
      --#SUMMARY "Power device inlet name changed. Old name: %s. New name: %s. Port number: %d. Power device number: %d. Inlet: %d."
      --#ARGUMENTS { 0, 1, 2, 3, 4 }
      --#SEVERITY INFORMATIONAL
      --#FACILITY SYSTEM
      --#CATEGORY "Configuration Events"
      --% TrapTypeEnum=68
      ::= 64



dellrcsg2PduOutletLockCommandTrap TRAP-TYPE
      ENTERPRISE dellrcsg2Products
      VARIABLES {
                     dellrcsg2TrapObjectUserName,
                     dellrcsg2TrapObjectTargetDeviceName,
                     dellrcsg2TrapObjectPduDevicePort,
                     dellrcsg2TrapObjectPduDeviceNumber,
                     dellrcsg2TrapObjectPduOutlet
                  }
      DESCRIPTION
         "A outlet on a power device has been issued the lock command.

         The name of the user who originally started the image upgrade is
         contained in dellrcsg2TrapObjectUserName if available. An empty
         string is reported if a user name is not available.

         The port number on the RCS that the power device is attached to
         is contained in dellrcsg2TrapObjectPduDevicePort.

         The outlet number that was issued the lock command is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "The lock command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=69
      ::= 65


dellrcsg2PduOutletUnlockCommandTrap TRAP-TYPE
      ENTERPRISE dellrcsg2Products
      VARIABLES {
                     dellrcsg2TrapObjectUserName,
                     dellrcsg2TrapObjectTargetDeviceName,
                     dellrcsg2TrapObjectPduDevicePort,
                     dellrcsg2TrapObjectPduDeviceNumber,
                     dellrcsg2TrapObjectPduOutlet
                  }
      DESCRIPTION
         "A outlet on a power device has been issued the unlock command.

         The name of the user who originally started the image upgrade is
         contained in dellrcsg2TrapObjectUserName if available. An empty
         string is reported if a user name is not available.

         The port number on the RCS that the power device is attached to
         is contained in dellrcsg2TrapObjectPduDevicePort.

         The outlet number that was issued the unlock command is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "The unlock command was issued to a power device outlet. Command issued by user: %s. Target device: %s. Port number: %d. Power device number: %d. Outlet number: %d."
      --#ARGUMENTS { 0, 1, 2, 3, 4 }
      --#SEVERITY MINOR
      --#FACILITY SECURITY
      --#CATEGORY "Status Events"
      --% TrapTypeEnum=70
      ::= 66


dellrcsg2PduStatusOutletLockTrap TRAP-TYPE
      ENTERPRISE dellrcsg2Products
      VARIABLES {
                     dellrcsg2TrapObjectTargetDeviceName,
                     dellrcsg2TrapObjectPduDevicePort,
                     dellrcsg2TrapObjectPduDeviceNumber,
                     dellrcsg2TrapObjectPduOutlet
                  }
      DESCRIPTION
         "A power device outlet has changed to the lock state.

         The port number on the RCS that the power device is attached to
         is contained in dellrcsg2TrapObjectPduDevicePort.

         The outlet number that has changed to the lock state is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "Power device outlet state changed to lock. Target device: %s. Port number: %d. Power device number: %d. Outlet number: %d."
      --#ARGUMENTS { 0, 1, 2, 3 }
      --#SEVERITY MINOR
      --#FACILITY SYSTEM
      --#CATEGORY "Status Events"
      --% TrapTypeEnum=71
      ::= 67


dellrcsg2PduStatusOutletUnlockTrap TRAP-TYPE
      ENTERPRISE dellrcsg2Products
      VARIABLES {
                     dellrcsg2TrapObjectTargetDeviceName,
                     dellrcsg2TrapObjectPduDevicePort,
                     dellrcsg2TrapObjectPduDeviceNumber,
                     dellrcsg2TrapObjectPduOutlet
                  }
      DESCRIPTION
         "A power device outlet has changed to the unlock state.

         The port number on the RCS that the power device is attached to
         is contained in dellrcsg2TrapObjectPduDevicePort.

         The outlet number that has changed to the unlock state is contained
         in dellrcsg2TrapObjectPduOutlet.

         The name of the server connected to the power device outlet is
         contained in dellrcsg2TrapObjectTargetDeviceName.

         The number of the power device that is connected to a port of the
         RCS is contained in dellrcsg2TrapObjectPduDeviceNumber.
         "
      --#SUMMARY "Power device outlet state changed to unlock. Target device: %s. Port number: %d. Power device number: %d. Outlet number: %d."
      --#ARGUMENTS { 0, 1, 2, 3 }
      --#SEVERITY MINOR
      --#FACILITY SYSTEM
      --#CATEGORY "Status Events"
      --% TrapTypeEnum=72
      ::= 68


dellrcsg2PduImageFileUpgradeStartedTrap TRAP-TYPE
      ENTERPRISE dellrcsg2Products
      VARIABLES {
                     dellrcsg2TrapObjectUserName,
                     dellrcsg2TrapObjectTypeOfImage,
                     dellrcsg2TrapObjectImageNewVersion,
                     dellrcsg2TrapObjectImageCurrentVersion,
                     dellrcsg2TrapObjectPduDevicePort,
                     dellrcsg2TrapObjectPduDeviceNumber
                  }
      DESCRIPTION
         "The RCS has started an upgrade of the power device software image file.


         The name of the user who initiated the image upgrade is contained
         in dellrcsg2TrapObjectUserName if available.

         The type of software image being upgraded is contained in
         dellrcsg2TrapObjectTypeOfImage.

         The software image version the RCS is upgrading the power device to is
         contained in dellrcsg2TrapObjectImageNewVersion.

         The software image version the power device is currently running
         is contained in dellrcsg2TrapObjectImageCurrentVersion.

         The port number on the RCS that the power device is attached to
         is contained in dellrcsg2TrapObjectPduDevicePort.

         The number of the power device that is connected to a port of the
         RCS is contained in dellrcsg2TrapObjectPduDeviceNumber.
         "
      --#SUMMARY "Power Device Image upgrade started. Command issued by user: %s. Image type: %d. New version: %s. Current version: %s. Port number: %d. Power device number: %d."
      --#ARGUMENTS { 0, 1, 2, 3, 4, 5 }
      --#SEVERITY INFORMATIONAL
      --#FACILITY SYSTEM
      --#CATEGORY "Configuration Events"
      --% TrapTypeEnum=73
      ::= 69


dellrcsg2PduImageFileUpgradeResultTrap TRAP-TYPE
      ENTERPRISE dellrcsg2Products
      VARIABLES {
                     dellrcsg2TrapObjectImageFileUpgradeResult,
                     dellrcsg2TrapObjectUserName,
                     dellrcsg2TrapObjectTypeOfImage,
                     dellrcsg2TrapObjectImageNewVersion,
                     dellrcsg2TrapObjectImageCurrentVersion,
                     dellrcsg2TrapObjectPduDevicePort,
                     dellrcsg2TrapObjectPduDeviceNumber

                  }
      DESCRIPTION
         "The result of a software image file upgrade for a power device.

         The result is contained in dellrcsg2TrapObjectImageFileUpgradeResult.

         The name of the user who originally started the image upgrade is
         contained in dellrcsg2TrapObjectUserName if available. An empty
         string is reported if a user name is not available.

         The type of software image the upgrade result is for is contained in
         dellrcsg2TrapObjectTypeOfImage.

         The software image version the RCS attempted to upgrade to
         is contained in dellrcsg2TrapObjectImageNewVersion.

         The software image version the RCS is running is contained
         in dellrcsg2TrapObjectImageCurrentVersion. If the software image
         upgrade was successful then this version will match the version
         reported in dellrcsg2TrapObjectImageNewVersion.

         The port number on the RCS that the power device is attached to
         is contained in dellrcsg2TrapObjectPduDevicePort.

         The number of the power device that is connected to a port of the
         RCS is contained in dellrcsg2TrapObjectPduDeviceNumber.
         "
      --#SUMMARY "Power device image upgrade result. Result: %d. Upgrade was started by user: %s. Upgrade image type: %d. Upgrade version: %s. Running version: %s. Port number: %d. Power device number: %d."
      --#ARGUMENTS { 0, 1, 2, 3, 4, 5, 6 }
      --#SEVERITY INFORMATIONAL
      --#FACILITY SYSTEM
      --#CATEGORY "Configuration Events"
      --% TrapTypeEnum=74
      ::= 70



dellrcsg2PduCircuitNameChangedTrap TRAP-TYPE
      ENTERPRISE dellrcsg2Products
      VARIABLES {
                     dellrcsg2TrapObjectOldName,
                     dellrcsg2TrapObjectItemName,
                     dellrcsg2TrapObjectPduDevicePort,
                     dellrcsg2TrapObjectPduDeviceNumber,
                     dellrcsg2TrapObjectPduDeviceCircuit
                  }
      DESCRIPTION
         "The name of a power device circuit has changed.

          The previous name of the power device circuit is contained in
          dellrcsg2TrapObjectOldName.

          The new name of the power device circuit is contained in
          dellrcsg2TrapObjectItemName.

          The port number on the RCS that the power device is attached to
          is contained in dellrcsg2TrapObjectPduDevicePort.

          The number of the power device that is connected to a port of the
          RCS is contained in dellrcsg2TrapObjectPduDeviceNumber.

          The circuit of the power device is contained in
          dellrcsg2TrapObjectPduDeviceCircuit.
         "
      --#SUMMARY "Power device circuit name changed. Old name: %s. New name: %s. Port number: %d. Power device number: %d. Circuit: %d."
      --#ARGUMENTS { 0, 1, 2, 3, 4 }
      --#SEVERITY INFORMATIONAL
      --#FACILITY SYSTEM
      --#CATEGORY "Configuration Events"
      --% TrapTypeEnum=75
      ::= 71


dellrcsg2PduDeviceTotalLoadHighTrap TRAP-TYPE
      ENTERPRISE dellrcsg2Products
      VARIABLES {
                     dellrcsg2TrapObjectPduDevicePort,
                     dellrcsg2TrapObjectPduDeviceNumber
                  }
      DESCRIPTION
         "A power device attached to the RCS has exceeded the maximum
         threshold for total load of the device.

         The port number on the RCS that the power device is attached to
         is contained in dellrcsg2TrapObjectPduDevicePort.

         The number of the power device that is connected to a port of the
         RCS is contained in dellrcsg2TrapObjectPduDeviceNumber.

         "
      --#SUMMARY "Power device exceeded the total load maximum threshold. Port number: %d. Power device number: %d. "
      --#ARGUMENTS { 0, 1 }
      --#SEVERITY MAJOR
      --#FACILITY SYSTEM
      --#CATEGORY "Threshold Events"
      --% TrapTypeEnum=76
      ::= 72


dellrcsg2PduCircuitTotalLoadHighTrap TRAP-TYPE
      ENTERPRISE dellrcsg2Products
      VARIABLES {
                     dellrcsg2TrapObjectPduDevicePort,
                     dellrcsg2TrapObjectPduDeviceNumber,
                     dellrcsg2TrapObjectPduDeviceCircuit
                  }
      DESCRIPTION
         "A power device attached to the RCS has exceeded the maximum
         threshold for total load of a circuit.

         The port number on the RCS that the power device is attached to
         is contained in dellrcsg2TrapObjectPduDevicePort.

         The number of the power device that is connected to a port of the
         RCS is contained in dellrcsg2TrapObjectPduDeviceNumber.

         The circuit of the power device is contained in
         dellrcsg2TrapObjectPduDeviceCircuit.
         "
      --#SUMMARY "Power device circuit exceeded the total load maximum threshold. Port number: %d. Power device number: %d. Circuit: %d."
      --#ARGUMENTS { 0, 1, 2 }
      --#SEVERITY MAJOR
      --#FACILITY SYSTEM
      --#CATEGORY "Threshold Events"
      --% TrapTypeEnum=77
      ::= 73


dellrcsg2PduOutletTotalLoadHighTrap TRAP-TYPE
      ENTERPRISE dellrcsg2Products
      VARIABLES {
                     dellrcsg2TrapObjectPduDevicePort,
                     dellrcsg2TrapObjectPduDeviceNumber,
                     dellrcsg2TrapObjectPduOutlet
                  }
      DESCRIPTION
         "A power device attached to the RCS has exceeded the maximum
         threshold for total load of an Outlet.

         The port number on the RCS that the power device is attached to
         is contained in dellrcsg2TrapObjectPduDevicePort.

         The number of the power device that is connected to a port of the
         RCS is contained in dellrcsg2TrapObjectPduDeviceNumber.

         The circuit of the power device is contained in
         dellrcsg2TrapObjectPduOutlet.
         "
      --#SUMMARY "Power device outlet exceeded the total load maximum threshold. Port number: %d. Power device number: %d. Outlet: %d."
      --#ARGUMENTS { 0, 1, 2 }
      --#SEVERITY MAJOR
      --#FACILITY SYSTEM
      --#CATEGORY "Threshold Events"
      --% TrapTypeEnum=78
      ::= 74



dellrcsg2FanFailureTrap TRAP-TYPE
      ENTERPRISE dellrcsg2Products
      DESCRIPTION
         "A fan failure has ocurred.
         "
      --#SUMMARY "Fan failure has been detected."
      --#ARGUMENTS { }
      --#SEVERITY MAJOR
      --#FACILITY SYSTEM
      --#CATEGORY "Status Events"
      --% TrapTypeEnum=79
      ::= 75


dellrcsg2TemperatureRangeTrap TRAP-TYPE
      ENTERPRISE dellrcsg2Products
      DESCRIPTION
         "Unit temperature outside operating range has been reached.

         This trap is generated for a high temperature or low temperature
         which is outside operating range.
         "
      --#SUMMARY "Temperature is outside operating range."
      --#ARGUMENTS { }
      --#SEVERITY MAJOR
      --#FACILITY SYSTEM
      --#CATEGORY "Status Events"
      --% TrapTypeEnum=80
      ::= 76

dellrcsg2SmartCardInsertedTrap TRAP-TYPE
      ENTERPRISE dellrcsg2Products
      VARIABLES {
                     dellrcsg2TrapObjectUserName,
                     dellrcsg2TrapObjectSessionIdentifier,
                     dellrcsg2TrapObjectUserAddress
                  }
      DESCRIPTION
         "A smart card has been inserted.

         The name of the user who is connected to the session
         is contained in dellrcsg2TrapObjectUserName.

         The session identifier is contained in
         dellrcsg2TrapObjectSessionIdentifier.

         The user address is contained in
         dellrcsg2TrapObjectUserAddress.
         "

      --#SUMMARY "Smart Card inserted. User: %s. Target device: %s. Address: %s."
      --#ARGUMENTS { 0, 1, 2 }
      --#SEVERITY INFORMATIONAL
      --#FACILITY SECURITY
      --#CATEGORY "Status Events"
      --% TrapTypeEnum=81
      ::= 77

dellrcsg2SmartCardRemovedTrap TRAP-TYPE
      ENTERPRISE dellrcsg2Products
      VARIABLES {
                     dellrcsg2TrapObjectUserName,
                     dellrcsg2TrapObjectSessionIdentifier,
                     dellrcsg2TrapObjectUserAddress
                  }
      DESCRIPTION
         "A smart card has been removed.

         The name of the user who is connected to the session
         is contained in dellrcsg2TrapObjectUserName.

         The session identifier is contained in
         dellrcsg2TrapObjectSessionIdentifier.

         The user address is contained in
         dellrcsg2TrapObjectUserAddress.
         "

      --#SUMMARY "Smart Card removed. User: %s. Target device: %s. Address: %s."
      --#ARGUMENTS { 0, 1, 2 }
      --#SEVERITY INFORMATIONAL
      --#FACILITY SECURITY
      --#CATEGORY "Status Events"
      --% TrapTypeEnum=82
      ::= 78

END
