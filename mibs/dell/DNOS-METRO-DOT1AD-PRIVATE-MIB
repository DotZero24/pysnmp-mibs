-- Dot1ad MIB overview:

-- Dot1ad Private MIB falls under dnOS METRO MIB node of the private subtree.
-- Various MIB groups defined within this MIB are:

-- Config Group -> All objects within this group are conceptual MIB table:

--    1) Interface Type Table - The Interface Type Table entry contains type.

--    2) L2 Tunneling Table - Each L2 Tunneling Table entry in the private MIB represents a single
--       match criterion that belongs to a Tunnel Action.


-- General Notes:

--    1) All objects of this MIB are prefixed with 'agentDot1ad' followed by the name of the
--       object with the first letter in uppercase.

DNOS-METRO-DOT1AD-PRIVATE-MIB DEFINITIONS ::= BEGIN

-- Broadcom DNOS Dot1ad MIB
-- Copyright 2016 Broadcom.
-- This SNMP Management Information Specification
-- embodies Broadcom's confidential and proprietary
-- intellectual property.  Broadcom retains all title
-- and ownership in the Specification including any revisions.

-- This Specification is supplied "AS IS", Broadcom
-- makes no warranty, either expressed or implied,
-- as to the use, operation, condition, or performance of the
-- Specification.


IMPORTS
    MODULE-IDENTITY, OBJECT-TYPE,
    NOTIFICATION-TYPE, IpAddress,
    Integer32,Unsigned32                FROM SNMPv2-SMI


    TEXTUAL-CONVENTION,RowStatus,
    RowPointer,MacAddress,
    StorageType,TruthValue              FROM SNMPv2-TC

    IANAifType                          FROM IANAifType-MIB
    ifIndex,InterfaceIndex              FROM IF-MIB
    DisplayString                       FROM RFC1213-MIB
    dnOS,AgentPortMask              FROM DELL-REF-MIB;

    fastPathDot1adPrivateMIB MODULE-IDENTITY
        LAST-UPDATED "201101260000Z" -- 26 Jan 2011 12:00:00 GMT
        ORGANIZATION "Dell EMC"
        CONTACT-INFO ""
        DESCRIPTION
          "The Broadcom Private MIB for DNOS Dot1ad"

        -- Revision history.
        REVISION
          "201101260000Z" -- 26 Jan 2011 12:00:00 GMT
        DESCRIPTION
          "Postal address updated."
        REVISION
          "200805270000Z" -- 27 May 2008 12:00:00 GMT
        DESCRIPTION
          "Initial vertion."

    ::= { dnOS 40 }


--**************************************************************************************
--       dot1adDataTunnelingGroup
--**************************************************************************************

    dot1adDataTunnelingGroup        OBJECT IDENTIFIER ::= { fastPathDot1adPrivateMIB 1 }

--**************************************************************************************
--       dot1adProtocolTunnelingGroup
--**************************************************************************************

    dot1adProtocolTunnelingGroup        OBJECT IDENTIFIER ::= { fastPathDot1adPrivateMIB 2 }


--**************************************************************************************
--    agentDot1adServiceConfigGroup
--**************************************************************************************

    agentDot1adServiceConfigGroup        OBJECT IDENTIFIER ::= { dot1adDataTunnelingGroup 1 }

    agentDot1adServiceTable OBJECT-TYPE
         SYNTAX      SEQUENCE OF AgentDot1adServiceEntry
         MAX-ACCESS  not-accessible
         STATUS      current
         DESCRIPTION
                     "A table entries specifying the Dot1ad sevice Details"
         ::= { agentDot1adServiceConfigGroup 1 }

    agentDot1adServiceEntry OBJECT-TYPE
         SYNTAX      AgentDot1adServiceEntry
         MAX-ACCESS  not-accessible
         STATUS      current
         DESCRIPTION
                     "Represents a Dot1ad Sevice Table"
         INDEX       {
                       agentDot1adServiceVLanId
                     }
         ::= { agentDot1adServiceTable  1 }

 AgentDot1adServiceEntry ::=
         SEQUENCE {
          agentDot1adServiceVLanId             Integer32,
          agentDot1adServiceRowStatus          RowStatus,
          agentDot1adServiceName               DisplayString,
          agentDot1adServiceType               INTEGER,
          agentDot1adServiceNNIList			       AgentPortMask,
          agentDot1adServiceNNIListCount       Integer32
         }

     agentDot1adServiceVLanId OBJECT-TYPE
         SYNTAX      Integer32 (0..2147483647)
         MAX-ACCESS  read-only
         STATUS      current
         DESCRIPTION
                     "Service VLAN ID."
         ::= { agentDot1adServiceEntry 1 }

     agentDot1adServiceRowStatus OBJECT-TYPE
         SYNTAX      RowStatus
         MAX-ACCESS  read-create
         STATUS      current
         DESCRIPTION
                      "The row status variable is used according to installation
          and removal conventions for conceptual rows."
         ::= { agentDot1adServiceEntry 2 }

     agentDot1adServiceName OBJECT-TYPE
         SYNTAX      DisplayString (SIZE(1..31))
         MAX-ACCESS  read-create
         STATUS      current
         DESCRIPTION
                     "Service Name."
         ::= { agentDot1adServiceEntry 3 }

     agentDot1adServiceType OBJECT-TYPE
         SYNTAX      INTEGER {
                               e-line(1),
                               e-lan(2),
                               e-tree(3),
                               tls(4)
                             }
         MAX-ACCESS  read-write
         STATUS      current
         DESCRIPTION
                     "Service Type."
         ::= { agentDot1adServiceEntry 4 }

     agentDot1adServiceNNIList OBJECT-TYPE
         SYNTAX      AgentPortMask
         MAX-ACCESS  read-write
         STATUS      current
         DESCRIPTION
                     "NNI Interface List Mask"
         ::= { agentDot1adServiceEntry 5 }

     agentDot1adServiceNNIListCount OBJECT-TYPE
         SYNTAX      Integer32
         MAX-ACCESS read-only
         STATUS      current
         DESCRIPTION
                     "NNI Interface List Count"
         ::= { agentDot1adServiceEntry 6 }

    agentDot1adSubscriptionConfigGroup        OBJECT IDENTIFIER ::= { dot1adDataTunnelingGroup 2 }

    agentDot1adSubscriptionTable OBJECT-TYPE
         SYNTAX      SEQUENCE OF AgentDot1adSubscriptionEntry
         MAX-ACCESS  not-accessible
         STATUS      current
         DESCRIPTION
                     "A table entries specifying the Dot1ad sevice Subscription Details"
         ::= { agentDot1adSubscriptionConfigGroup 1 }

    agentDot1adSubscriptionEntry OBJECT-TYPE
         SYNTAX      AgentDot1adSubscriptionEntry
         MAX-ACCESS  not-accessible
         STATUS      current
         DESCRIPTION
                     "Represents a Dot1ad Sevice Subscription Table"
         INDEX       {
                       agentDot1adSubscriptionInterfaceIfIndex,
                       agentDot1adSubscriptionNewServiceVLanId,
                       agentDot1adSubscriptionNewCustomerVLanId
                     }
         ::= { agentDot1adSubscriptionTable  1 }

    AgentDot1adSubscriptionEntry ::=
         SEQUENCE {
          agentDot1adSubscriptionInterfaceIfIndex     Integer32,
          agentDot1adSubscriptionNewServiceVLanId     Integer32,
          agentDot1adSubscriptionNewCustomerVLanId    Integer32,
          agentDot1adSubscriptionServiceName          DisplayString,
          agentDot1adSubscriptionName                 DisplayString,
          agentDot1adSubscriptionMatchCriteria        INTEGER,
          agentDot1adSubscriptionServiceVLanId        Integer32,
          agentDot1adSubscriptionCustomerVLanId       Integer32,
          agentDot1adSubscriptionPriority             Integer32,
          agentDot1adSubscriptionMatchAction          INTEGER,
          agentDot1adSubscriptionNNIList              AgentPortMask,
          agentDot1adSubscriptionNNIListCount         Integer32,
          agentDot1adSubscriptionRowStatus            RowStatus
         }

    agentDot1adSubscriptionInterfaceIfIndex OBJECT-TYPE
         SYNTAX      Integer32 (0..2147483647)
         MAX-ACCESS  read-only
         STATUS      current
         DESCRIPTION
                     "Service Subscription Interface Index."
         ::= { agentDot1adSubscriptionEntry 1 }

    agentDot1adSubscriptionNewServiceVLanId OBJECT-TYPE
         SYNTAX      Integer32 (0..2147483647)
         MAX-ACCESS  read-only
         STATUS      current
         DESCRIPTION
                     "New Service VLAN ID."
         ::= { agentDot1adSubscriptionEntry 2 }

    agentDot1adSubscriptionNewCustomerVLanId OBJECT-TYPE
         SYNTAX      Integer32 (0..2147483647)
         MAX-ACCESS  read-only
         STATUS      current
         DESCRIPTION
                     "New Customer VLAN ID."
         ::= { agentDot1adSubscriptionEntry 3 }

    agentDot1adSubscriptionServiceName OBJECT-TYPE
         SYNTAX      DisplayString (SIZE(1..31))
         MAX-ACCESS  read-write
         STATUS      current
         DESCRIPTION
                     "Subscription's Service Name."
         ::= { agentDot1adSubscriptionEntry 4 }

    agentDot1adSubscriptionName OBJECT-TYPE
         SYNTAX      DisplayString (SIZE(1..31))
         MAX-ACCESS  read-write
         STATUS      current
         DESCRIPTION
                     "Service Subscription Name."
         ::= { agentDot1adSubscriptionEntry 5 }

    agentDot1adSubscriptionMatchCriteria OBJECT-TYPE
         SYNTAX      INTEGER {
                               none(0),
                               untagged(1),
                               priority-tagged(2),
                               vlan-tagged(3)
                             }
         MAX-ACCESS  read-write
         STATUS      current
         DESCRIPTION
                     "Service Subscription Match Criteria."
         ::= { agentDot1adSubscriptionEntry 6 }

    agentDot1adSubscriptionServiceVLanId OBJECT-TYPE
         SYNTAX      Integer32
         MAX-ACCESS  read-write
         STATUS      current
         DESCRIPTION
                     "Service VLAN ID for the given Subscription."
         ::= { agentDot1adSubscriptionEntry 7 }

    agentDot1adSubscriptionCustomerVLanId OBJECT-TYPE
         SYNTAX      Integer32
         MAX-ACCESS  read-write
         STATUS      current
         DESCRIPTION
                     "Customer VLAN ID."
         ::= { agentDot1adSubscriptionEntry 8 }

    agentDot1adSubscriptionPriority OBJECT-TYPE
         SYNTAX      Integer32
         MAX-ACCESS  read-write
         STATUS      current
         DESCRIPTION
                     "Service Subscription Priority."
         ::= { agentDot1adSubscriptionEntry 9 }

    agentDot1adSubscriptionMatchAction OBJECT-TYPE
         SYNTAX      INTEGER {
                               none(0),
                               assign-customer-VLANID(1),
                               re-mark-customer-VLANID(2),
                               remove-customer-VLANID(3)
                             }
         MAX-ACCESS  read-write
         STATUS      current
         DESCRIPTION
                     "Service Subscription Match Action."
         ::= { agentDot1adSubscriptionEntry 10 }

     agentDot1adSubscriptionNNIList OBJECT-TYPE
         SYNTAX      AgentPortMask
         MAX-ACCESS  read-write
         STATUS      current
         DESCRIPTION
                     "NNI Interface List"
         ::= { agentDot1adSubscriptionEntry 11 }

     agentDot1adSubscriptionNNIListCount OBJECT-TYPE
         SYNTAX      Integer32
         MAX-ACCESS read-only
         STATUS      current
         DESCRIPTION
                     "NNI Interface List Count"
         ::= { agentDot1adSubscriptionEntry 12 }

    agentDot1adSubscriptionRowStatus OBJECT-TYPE
         SYNTAX      RowStatus
         MAX-ACCESS  read-create
         STATUS      current
         DESCRIPTION
                      "The row status variable is used according to installation
          and removal conventions for conceptual rows."
         ::= { agentDot1adSubscriptionEntry 13 }
--**************************************************************************************
--    AgentDot1adInterfaceTypeConfigGroup
--**************************************************************************************

    agentDot1adInterfaceTypeConfigGroup        OBJECT IDENTIFIER ::= { dot1adProtocolTunnelingGroup 1 }

    agentDot1adInterfaceTypeTable OBJECT-TYPE
         SYNTAX      SEQUENCE OF AgentDot1adInterfaceTypeEntry
         MAX-ACCESS  not-accessible
         STATUS      current
         DESCRIPTION
                      "A table of the interface entries specifying the type of Dot1ad interface
                      and the interface's capability to preserve customer tag's dot1p value."
         ::= { agentDot1adInterfaceTypeConfigGroup 1 }

    agentDot1adInterfaceTypeEntry OBJECT-TYPE
         SYNTAX      AgentDot1adInterfaceTypeEntry
         MAX-ACCESS  not-accessible
         STATUS      current
         DESCRIPTION
                     "Represents a interface type in Dot1ad Interface Table"
         INDEX       {
                       agentDot1adInterfaceIfIndex
                     }
         ::= { agentDot1adInterfaceTypeTable  1 }


    AgentDot1adInterfaceTypeEntry ::=
         SEQUENCE {
          agentDot1adInterfaceIfIndex           InterfaceIndex,
          agentDot1adInterfaceType              INTEGER,
          agentDot1adInterfacePreserveCTAGDot1p INTEGER
         }

     agentDot1adInterfaceIfIndex OBJECT-TYPE
         SYNTAX      InterfaceIndex
         MAX-ACCESS  not-accessible
         STATUS      current
         DESCRIPTION
                     "Interface on which the Dot1ad interface type is specified."
         ::= { agentDot1adInterfaceTypeEntry 1 }

     agentDot1adInterfaceType         OBJECT-TYPE
         SYNTAX      INTEGER {
                               uni(0),
                               uni-p(1),
                               uni-s(2),
                               nni(3),
                               switchport(4)
                             }
         MAX-ACCESS  read-write

         STATUS      current
         DESCRIPTION
                     "Specify DOT1AD interface type as  UNI UNI-P UNI-S or NNI.
			(0)	to specify the interface as UNI
			(1)	to specify the interface as UNI-P
			(2)	to specify the interface as UNI-S
			(3)	to specify the interface as NNI
			(4)	to specify the interface as ordinary switch port "
         ::= { agentDot1adInterfaceTypeEntry 2 }

     agentDot1adInterfacePreserveCTAGDot1p         OBJECT-TYPE
         SYNTAX      INTEGER {
                               disable(0),
                               enable(1)
                             }
         MAX-ACCESS  read-write

         STATUS      current
         DESCRIPTION
                     "enable/disable the interface's capability to
                     preserve the Customer tag's dot1p value
                        (0)     to disable
                        (1)     to enable"
         DEFVAL { disable }
         ::= { agentDot1adInterfaceTypeEntry 3 }


--**********************************************************************************
-- agentL2TunnelingConfigGroup
--
--**********************************************************************************

    agentL2TunnelingConfigGroup        OBJECT IDENTIFIER ::= { dot1adProtocolTunnelingGroup 2 }

    agentL2ProtocolTunnelingTable OBJECT-TYPE
         SYNTAX      SEQUENCE OF AgentL2ProtocolTunnelingEntry
         MAX-ACCESS  not-accessible
         STATUS      current
         DESCRIPTION
                     "A table of the L2 Protocol Tunneling entries"
         ::= { agentL2TunnelingConfigGroup 1 }


    agentL2ProtocolTunnelingEntry OBJECT-TYPE
         SYNTAX      AgentL2ProtocolTunnelingEntry
         MAX-ACCESS  not-accessible
         STATUS      current
         DESCRIPTION
                    "Represents a VLAN-reservedMAC-tunnelAction mapping Entry in L2-ProtocolTunneling Table"
	 INDEX       {
                       agentL2ProtocolTunnelingVlanId,
                       agentL2ProtocolTunnelingMACAddress,
                       agentL2ProtocolTunnelingProtocolId
                     }

         ::= { agentL2ProtocolTunnelingTable 1 }

     AgentL2ProtocolTunnelingEntry ::=
          SEQUENCE {
              agentL2ProtocolTunnelingVlanId     Integer32,
              agentL2ProtocolTunnelingMACAddress MacAddress,
              agentL2ProtocolTunnelingProtocolId Integer32,
              agentL2ProtocolTunnelingAction     INTEGER,
              agentL2ProtocolTunnelingRowStatus  RowStatus

          }

     agentL2ProtocolTunnelingVlanId OBJECT-TYPE
         SYNTAX      Integer32 (0..2147483647)
         MAX-ACCESS  read-create
         STATUS      current
         DESCRIPTION
                     "VLAN on which this tunneling action for a given reserved MAC address and Protocol-id is going to be added."
         ::= { agentL2ProtocolTunnelingEntry 1 }

     agentL2ProtocolTunnelingMACAddress OBJECT-TYPE
         SYNTAX      MacAddress
         MAX-ACCESS  read-create
         STATUS      current
         DESCRIPTION
                     "L2 Protocol reserved MAC address to which this tunneling action is going to be applied.
                      Valid Range:01:80:c2:00:00:00 to 01:80:c2:00:00:3f"
         ::= { agentL2ProtocolTunnelingEntry 2 }

     agentL2ProtocolTunnelingProtocolId OBJECT-TYPE
         SYNTAX      Integer32 (0..2147483647)
         MAX-ACCESS  read-create
         STATUS      current
         DESCRIPTION
                     "L2 Protocol type in MAC header to which this tunneling action is going to be applied.
                      Valid Range:0x0600 t0 0xffff.
                      Use 0x0000 to avoid Protocol ID configuration in snmpset.
                      Get value 0x0000 means protocol ID is not configured."
         ::= { agentL2ProtocolTunnelingEntry 3 }

     agentL2ProtocolTunnelingAction OBJECT-TYPE
         SYNTAX      INTEGER {
                               terminate(0),
                               tunnel(1),
                               discard(2),
                               discard-shutdown(3)
                              }
         MAX-ACCESS  read-create
         STATUS      current
         DESCRIPTION
                     "The tunneling Action could be of type
			(0)	to terminate the L2 control packet with specified MAC address, VLAN ID and Protocol ID.
			(1)	to tunnel the L2 control packet with specified MAC address, VLAN ID and Protocol ID.
			(2)	to Discard the L2 control packet with specified MAC address, VLAN ID and Protocol ID.
			(3)	to Discard the L2 control packet with specified MAC address, VLAN ID and Protocol ID and shutdown the received interface."

         ::= { agentL2ProtocolTunnelingEntry 4}

    agentL2ProtocolTunnelingRowStatus OBJECT-TYPE
         SYNTAX      RowStatus
         MAX-ACCESS  read-create
         STATUS      current
         DESCRIPTION
                     "The status of this conceptual row.

                     active(1)      - Tunneling Entry is active
                     createAndGo(4) - Set to create an instance
                     destroy(6)     - Set to delete an instance"
         ::= { agentL2ProtocolTunnelingEntry 5 }


END
