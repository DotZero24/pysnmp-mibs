-- Copyright (C) 2008-2012 Aricent Group . All Rights Reserved

-- $Id: fssntp.mib,v 1.15 2016/03/11 11:27:10 siva Exp $

FSSNTP-MIB DEFINITIONS ::= BEGIN

IMPORTS
    OBJECT-TYPE,MODULE-IDENTITY,
    IpAddress,  Counter32,Unsigned32,Integer32,TimeTicks, enterprises FROM SNMPv2-SMI
    DisplayString,RowStatus,TruthValue FROM SNMPv2-TC
    InetAddressType, InetAddress  FROM INET-ADDRESS-MIB;              -- [RFC4001]

fsSntpMIB MODULE-IDENTITY
     LAST-UPDATED "201209050000Z"
     ORGANIZATION "ARICENT COMMUNICATIONS SOFTWARE"
     CONTACT-INFO "support@aricent.com"
     DESCRIPTION " This mib module is for SNTP  "
     REVISION "201209050000Z"
     DESCRIPTION " This mib module is for SNTP  "
     ::= { enterprises futuresoftware(2076) 149}

fsSntp              OBJECT IDENTIFIER ::= { fsSntpMIB 1 }

fsSntpScalars       OBJECT IDENTIFIER ::= { fsSntp 1 }
fsSntpUnicast       OBJECT IDENTIFIER ::= { fsSntp 2 }
fsSntpBroadcast     OBJECT IDENTIFIER ::= { fsSntp 3 }
fsSntpMulticast     OBJECT IDENTIFIER ::= { fsSntp 4 }
fsSntpAnycast       OBJECT IDENTIFIER ::= { fsSntp 5 }


fsSntpGlobalTrace     OBJECT-TYPE
	SYNTAX	      Integer32 (0..65535)
	MAX-ACCESS    read-write
	STATUS	      current
	DESCRIPTION
		" This is used to enable Trace Statements in SNTP Module.
		A four byte integer value is specified for enabling the level
		of tracing.Each Bit in the four byte integer variable represents
		a level of Trace. The bits represents the levels as
		follows: 0 - Init and Shutdown, 1 - Management, 2 - Data Path,
		3 - Control Plane, 4 - packet Dump, 5 - All resources except
		buffer, 6 - All Failures, 7 - Buffer.  The remaining
		bits are unused. The combination of levels are also allowed.
		For example if the bits 1 and 2 are set, then the Trace
		statements related to management and Data Path will be printed.
		The administrator have to enter the corresponding integer value
		 for the bits set. For example if bits 1 and 2 are set then
		 admin has to give the value 6."
	DEFVAL	{ 0 }
	::= { fsSntpScalars 1 }

fsSntpGlobalDebug	 OBJECT-TYPE
	SYNTAX	      Integer32 (0..65535)
	MAX-ACCESS    read-write
	STATUS	      current
	DESCRIPTION
		" This is used to enable Debug statements in SNTP module.
                  A Four byte integer value is specified for enabling the
                  level of debugging. Each bit in the four byte integer
                  variable represents a level of debugging. The combination of
                  levels are also allowed. The user have to enter the
                  corresponding integer value for the bit set."
	DEFVAL	{ 0 }
	::= { fsSntpScalars 2 }

fsSntpAdminStatus OBJECT-TYPE
    SYNTAX     INTEGER { disabled (0), enabled (1) }
    MAX-ACCESS read-write
    STATUS     current
    DESCRIPTION
        "To enable or disable the sntp client module. All configuration will be
        acitve only when the SNTP module is enabled"
    DEFVAL  { disabled }
    ::= { fsSntpScalars 3 }

fsSntpClientVersion  OBJECT-TYPE
    SYNTAX     INTEGER {version1 (1), version2 (2), version3 (3), version4 (4)}
    MAX-ACCESS read-write
    STATUS     current
    DESCRIPTION
        "The SNTP client module can run in any one version 1, version 2,
        version 3 or version 4. All the SNTP requests are sent out with the
        current configured version number. When required, the administrator
        can change the current version number"
    DEFVAL { version4 }
    ::= { fsSntpScalars 4 }

fsSntpClientAddressingMode  OBJECT-TYPE
    SYNTAX     INTEGER {unicast (1), broadcast (2), multicast (3), manycast (4)}
    MAX-ACCESS read-write
    STATUS     current
    DESCRIPTION
        " unicast:
        - SNTP client operates in a point-to-point fashion.  A unicast
        client sends a request to a designated server at its unicast address
        and expects a reply from which it can determine the time and,
        optionally, the round-trip delay and local clock offset relative to
        the server.

        broadcast:
        - SNTP client operates in a point-to-multipoint fashion. The SNTP
        server uses an IP local broadcast address instead of a multicast
        address.  The broadcast address is scoped to a single subnet, while a
        multicast address has Internet wide scope.

        multicast:
        - SNTP client operates in point-to-multipoint fashion.  The SNTP server
        uses a multicast group address to send unsolicited SNTP messages to
        clients.  The client listens on this address and sends no requests for
        updates.

        manycast:
        - SNTP client operates in a multipoint-to-point fashion.

	manycast(broadcast)- The SNTP client sends a request to a designated IPv4
		  	     local broadcast address.One or more manycast servers
			     reply with their individual unicast addresses.After that
			     the communication between client and server is unicast.

	manycast(multicast)- The SNTP client sends a request to a designated IPv4 or
			     IPv6 multicast group address. One or more manycast
			     servers reply with their individual unicast addresses.
			     After that the communication between client and server
			     is unicast.This mode is currently not supported because
			     the server is not replying in this case."

    DEFVAL  { unicast }
    ::= { fsSntpScalars 5 }

fsSntpClientPort     OBJECT-TYPE
    SYNTAX     Integer32 ( 123 | 1025..65535)
    MAX-ACCESS read-write
    STATUS     current
    DESCRIPTION
        "The SNTP client module by default listens on well-know port number 123.
         When required, the Administrator can change the SNTP Client port value
         to non-default."
    DEFVAL {123}
    ::= { fsSntpScalars 6 }

fsSntpTimeDisplayFormat OBJECT-TYPE
    SYNTAX     INTEGER { hours (1), ampm  (2) }
    MAX-ACCESS read-write
    STATUS     current
    DESCRIPTION
        " The administrator can view the system time in 12 hr AM/PM or 24
        hours format. "
    DEFVAL  { hours }
    ::= { fsSntpScalars 7 }

fsSntpAuthKeyId OBJECT-TYPE
    SYNTAX     Integer32
    MAX-ACCESS read-write
    STATUS     current
    DESCRIPTION
        "Key Identifier  is an integer identifying the cryptographic key used
        to generate the message-authentication code"
     ::= { fsSntpScalars 8 }

fsSntpAuthAlgorithm OBJECT-TYPE
    SYNTAX     INTEGER { none (0), md5 (1)}
    MAX-ACCESS read-write
    STATUS     current
    DESCRIPTION
        "When the NTP authentication scheme is implemented, the Key Identifier
        and Message Digest fields contain the message authentication code (MAC)
        information. Message Digest-5 (MD5) is the Authentication
	algorithm that can be used. Default
        Authentication supported is none"
    DEFVAL  { none }
     ::= { fsSntpScalars  9 }

fsSntpAuthKey  OBJECT-TYPE
    SYNTAX     OCTET STRING (SIZE(0..16))
    MAX-ACCESS read-write
    STATUS     current
    DESCRIPTION
        "Authentication key is cryptographic key that is used to implement NTP
        Authentication "
     ::= { fsSntpScalars  10 }

fsSntpTimeZone OBJECT-TYPE
    SYNTAX     DisplayString (SIZE (6))
    MAX-ACCESS read-write
    STATUS     current
    DESCRIPTION
        "To set the system time zone with respect to UTC. ie plus indicates
        forward time zone ( ahead of UTC Time eg: +05:30) and minus indicates
        backward time zone (behind UTC time eg: -03:30). The valid format is
        (+/-)HH:MM"
    ::= { fsSntpScalars 11 }

 fsSntpDSTStartTime OBJECT-TYPE
    SYNTAX     DisplayString (SIZE (20))
    MAX-ACCESS read-write
    STATUS     current
    DESCRIPTION
        " Daylight saving time (DST) is a system of setting clocks ahead so
        that both sunrise and sunset occur at a later hour. The effect is
        additional daylight in the evening. Many countries observe DST,
        although most have their own rules and regulations for when it begins
        and ends. The dates of DST may change from year to year. In valid
        conditions start DST should be lesser than end DST and end DST
        should be revised accordingly after start DST configuration. The Valid
        format  [weekofmonth-weekofday-month,HH:MM].
        Example:- Third-Mon-Apr,17:30 "
    ::= { fsSntpScalars 12 }


 fsSntpDSTEndTime OBJECT-TYPE
    SYNTAX     DisplayString (SIZE (20))
    MAX-ACCESS read-write
    STATUS     current
    DESCRIPTION
        " Daylight saving time (DST) is a system of setting clocks ahead so
        that both sunrise and sunset occur at a later hour. The effect is
        additional daylight in the evening. Many countries observe DST,
        although most have their own rules and regulations for when it begins
        and ends. The dates of DST may change from year to year. The Valid
        format  [weekofmonth-weekofday-month,HH:MM].
        Example:- Last-Sun-Nov,16:20 "
   ::= { fsSntpScalars 13 }

fsSntpClientUptime OBJECT-TYPE
    SYNTAX      Unsigned32
    MAX-ACCESS  read-only
    STATUS      current
    DESCRIPTION
        "The uptime of the SNTP client entity in seconds."
    ::= { fsSntpScalars 14 }

fsSntpClientStatus OBJECT-TYPE
    SYNTAX      INTEGER {
                            notRunning(1),
                            notSynchronized(2),
                            noneConfigured(3),
                            syncToLocal(4),
                            syncToPrimaryServer(5),
                            syncToSecondaryServer(6),
                            unknown(99)
                        }
    MAX-ACCESS  read-only
    STATUS      current
    DESCRIPTION
        "The status of the SNTP client as integer value."
    ::= { fsSntpScalars 15 }

fsSntpServerReplyRxCount OBJECT-TYPE
    SYNTAX      Counter32
    MAX-ACCESS  read-only
    STATUS	    current
    DESCRIPTION
        "Number of SNTP server replies that has received by SNTP client."
    ::= { fsSntpScalars 16 }

fsSntpClientReqTxCount OBJECT-TYPE
    SYNTAX      Counter32
    MAX-ACCESS  read-only
    STATUS      current
    DESCRIPTION
        "Number of requests the SNTP client has Transmitted."
    ::= { fsSntpScalars 17 }

fsSntpPktInDiscardCount OBJECT-TYPE
    SYNTAX      Counter32
    MAX-ACCESS  read-only
    STATUS      current
    DESCRIPTION
        "Number of replies the SNTP client has rejected."
    ::= { fsSntpScalars 18 }


-- Unicast Objects

fsSntpServerAutoDiscovery  OBJECT-TYPE
    SYNTAX     INTEGER { disabled (0), enabled (1) }
    MAX-ACCESS read-write
    STATUS     current
    DESCRIPTION
        " The SNTP servers can be configured or discovered. When Auto Discover
        is disabled, the SNTP client gets the time from the configured servers.
        When Auto Discover is enabled, the SNTP client gets the time from servers
        learnt through DHPC client. This is valid only in Unicast
        Addressing mode."
    DEFVAL  { disabled }
    ::= { fsSntpUnicast 1 }

fsSntpUnicastPollInterval OBJECT-TYPE
    SYNTAX      Unsigned32 (16..262144)
    UNITS       "seconds"
    MAX-ACCESS  read-write
    STATUS      current
    DESCRIPTION
        "The number of seconds between successive SNTP request transmissions. The
	Poll interval value is expressed as exponent of two."
    DEFVAL { 64 }
    ::= {fsSntpUnicast 2 }

fsSntpUnicastPollTimeout OBJECT-TYPE
    SYNTAX      Unsigned32 (1..30)
    UNITS       "seconds"
    MAX-ACCESS  read-write
    STATUS      current
    DESCRIPTION
        "The number of seconds to wait for a response from a SNTP server
        before considering the attempt to have 'timed out' "
    DEFVAL { 5 }
    ::= {fsSntpUnicast 3 }

fsSntpUnicastPollRetry OBJECT-TYPE
    SYNTAX      Unsigned32 (0..10)
    MAX-ACCESS  read-write
    STATUS      current
    DESCRIPTION
        "The number of times to retry a request to a SNTP server
        that has not successfully responded.  For example, assume this object
        has been SET to a value of 2.  When the SNTP client queries a given
        server it will send 1 SNTP request frame. If that original attempt
        fails, the client will retry up to a maximum of 2 more times before
        giving up and attempting the next server."
    DEFVAL { 3 }
    ::= { fsSntpUnicast 4 }


-- fsSntpUnicastServer Table
-- This table is for configuring the unicast server table

fsSntpUnicastServerTable OBJECT-TYPE
    SYNTAX      SEQUENCE OF FsSntpUnicastServerEntry
    MAX-ACCESS  not-accessible
    STATUS      current
    DESCRIPTION
            "The table contains configured SNTP/NTP servers in the system."
    ::= {fsSntpUnicast 5 }

fsSntpUnicastServerEntry  OBJECT-TYPE
    SYNTAX      FsSntpUnicastServerEntry
    MAX-ACCESS  not-accessible
    STATUS      current
    DESCRIPTION
            " Each entry in the table contains necessary information to
            send SNTP request to the servers."
         INDEX {fsSntpUnicastServerAddrType, fsSntpUnicastServerAddr }
    ::= { fsSntpUnicastServerTable 1 }

FsSntpUnicastServerEntry ::= SEQUENCE {
    fsSntpUnicastServerAddrType         InetAddressType,
    fsSntpUnicastServerAddr             InetAddress,
    fsSntpUnicastServerVersion          INTEGER,
    fsSntpUnicastServerPort             Integer32,
    fsSntpUnicastServerType             INTEGER,
    fsSntpUnicastServerLastUpdateTime   DisplayString,
    fsSntpUnicastServerTxRequests       Counter32,
    fsSntpUnicastServerRowStatus        RowStatus
}

fsSntpUnicastServerAddrType OBJECT-TYPE
    SYNTAX      InetAddressType
    MAX-ACCESS  not-accessible
    STATUS      current
    DESCRIPTION
        "The Address type of the unicast server in the Unicast Addressing mode.
        It can be IPv4 or IPv6 unicast address or DNS"
    ::= { fsSntpUnicastServerEntry 1 }

fsSntpUnicastServerAddr OBJECT-TYPE
    SYNTAX      InetAddress
    MAX-ACCESS  not-accessible
    STATUS      current
    DESCRIPTION
        " This object specifies the unicast IPv4/IPv6 server address in the Unicast Addressing mode.
		  It supports hostname when the fsSntpUnicastServerAddrType is set as DNS type.
          Host name is a string value with maximum size 63."
    ::= { fsSntpUnicastServerEntry 2}

fsSntpUnicastServerVersion OBJECT-TYPE
    SYNTAX      INTEGER {version3 (3),version4 (4)}
    MAX-ACCESS  read-write
    STATUS      current
    DESCRIPTION
        "the sntp version supported by the server"
    ::= { fsSntpUnicastServerEntry 3 }

fsSntpUnicastServerPort OBJECT-TYPE
    SYNTAX      Integer32 ( 123 | 1025..36564)
    MAX-ACCESS  read-write
    STATUS      current
    DESCRIPTION
        "the sntp port on which the server is UP"
    ::= { fsSntpUnicastServerEntry 4 }

fsSntpUnicastServerType OBJECT-TYPE
    SYNTAX      INTEGER { primary  (1), secondary (2) }
    MAX-ACCESS  read-write
    STATUS      current
    DESCRIPTION
        "In Unicast addressing mode, we can have primary and secondary servers.
        This flag is to distinguish between primary and secondary server.
        SNTP client sends request to different servers until it receives
        successful response. This flag tells the order in which to query the
        servers."
    ::= { fsSntpUnicastServerEntry 5 }

fsSntpUnicastServerLastUpdateTime OBJECT-TYPE
    SYNTAX      DisplayString
    MAX-ACCESS  read-only
    STATUS      current
    DESCRIPTION
        "The local time when the system time was successful"
    ::= { fsSntpUnicastServerEntry 6 }

fsSntpUnicastServerTxRequests OBJECT-TYPE
    SYNTAX      Counter32
    MAX-ACCESS  read-only
    STATUS      current
    DESCRIPTION
        "The number of SNTP request sent in the Unicast addressing mode."
    ::= { fsSntpUnicastServerEntry 7 }

fsSntpUnicastServerRowStatus OBJECT-TYPE
    SYNTAX      RowStatus
    MAX-ACCESS  read-write
    STATUS      current
    DESCRIPTION
        " The activation of a row adds server entry. The destruction of a row
        removes server entry"
    ::= {fsSntpUnicastServerEntry 8}

-- Broadcast objects

fsSntpSendRequestInBcastMode	OBJECT-TYPE
    SYNTAX	INTEGER { disabled (0), enabled (1) }
    MAX-ACCESS	read-write
    STATUS	current
    DESCRIPTION
        "when enabled the sntp request will be sent to the broadcast server to
        calculate the dealy time. This is valid only in broadcast
        addressing mode"
    DEFVAL { disabled }
    ::= { fsSntpBroadcast 1 }

fsSntpPollTimeoutInBcastMode OBJECT-TYPE
    SYNTAX      Unsigned32 (1..30)
    UNITS       "seconds"
    MAX-ACCESS  read-write
    STATUS      current
    DESCRIPTION
        "The number of seconds to wait for a response from a SNTP server before
        considering the attempt to have 'timed out'. This is valid only in
        broadcast addressing mode "
    DEFVAL { 5 }
    ::= {fsSntpBroadcast 2 }

fsSntpDelayTimeInBcastMode	OBJECT-TYPE
    SYNTAX	Unsigned32 (1000..15000)
    UNITS       "microseconds"
    MAX-ACCESS	read-write
    STATUS	current
    DESCRIPTION
        " The broadcast server may send reply for the request. When the SNTP
        client does get response from the boradcast server,
        this value is taken as delay time "
    DEFVAL { 8000 }
    ::= { fsSntpBroadcast 3 }

fsSntpPrimaryServerAddrInBcastMode OBJECT-TYPE
    SYNTAX      IpAddress
    MAX-ACCESS  read-only
    STATUS      current
    DESCRIPTION
        " The primary server IP address learnt in Broadcast addressing mode "
    ::= { fsSntpBroadcast 4 }

fsSntpSecondaryServerAddrInBcastMode OBJECT-TYPE
    SYNTAX      IpAddress
    MAX-ACCESS  read-only
    STATUS      current
    DESCRIPTION
        " The secondary server IP address learnt in Broadcast addressing mode"
    ::= {fsSntpBroadcast 5 }


-- Multicast Objects

fsSntpSendRequestInMcastMode	OBJECT-TYPE
    SYNTAX	INTEGER { disabled (0), enabled (1) }
    MAX-ACCESS	read-write
    STATUS	current
    DESCRIPTION
        " when enabled the sntp request will be sent to the multicast server to
        calculate the dealy time."
    DEFVAL { disabled }
    ::= { fsSntpMulticast 1 }

fsSntpPollTimeoutInMcastMode OBJECT-TYPE
    SYNTAX      Unsigned32 (1..30)
    UNITS       "seconds"
    MAX-ACCESS  read-write
    STATUS      current
    DESCRIPTION
        "The number of seconds to wait for a response from a SNTP
        server before considering the attempt to have 'timed out'"
    DEFVAL { 5 }
    ::= {fsSntpMulticast 2 }

fsSntpDelayTimeInMcastMode	OBJECT-TYPE
    SYNTAX	Unsigned32 (1000..15000)
    UNITS       "microseconds"
    MAX-ACCESS	read-write
    STATUS	current
    DESCRIPTION
        " this is taken as delay time  when there is no response from the
        multicast server  "
    DEFVAL { 8000 }
    ::= { fsSntpMulticast 3 }

fsSntpGrpAddrTypeInMcastMode OBJECT-TYPE
    SYNTAX     InetAddressType
    MAX-ACCESS read-write
    STATUS     current
    DESCRIPTION
        " The multicast group address can be configured by the administrator."
    ::= {fsSntpMulticast  4 }

fsSntpGrpAddrInMcastMode OBJECT-TYPE
    SYNTAX     InetAddress
    MAX-ACCESS read-write
    STATUS     current
    DESCRIPTION
        " The multicast group address can be configured by the administrator."
    ::= {fsSntpMulticast 5 }

fsSntpPrimaryServerAddrTypeInMcastMode OBJECT-TYPE
    SYNTAX     InetAddressType
    MAX-ACCESS read-only
    STATUS     current
    DESCRIPTION
        "The address type of the primary server learnt in Multicast addressing
        mode"
    ::= {fsSntpMulticast  6 }

fsSntpPrimaryServerAddrInMcastMode OBJECT-TYPE
    SYNTAX     InetAddress
    MAX-ACCESS read-only
    STATUS     current
    DESCRIPTION
        " The primary server IP address learnt in Multicast addressing mode "
    ::= { fsSntpMulticast  7 }

fsSntpSecondaryServerAddrTypeInMcastMode OBJECT-TYPE
    SYNTAX     InetAddressType
    MAX-ACCESS read-only
    STATUS     current
    DESCRIPTION
        "The address type of the secondary server learnt in Multicast
        addressing mode"
    ::= { fsSntpMulticast  8 }

fsSntpSecondaryServerAddrInMcastMode OBJECT-TYPE
    SYNTAX     InetAddress
    MAX-ACCESS read-only
    STATUS     current
    DESCRIPTION
        " The secondary server IP address learnt in Multicast addressing mode "
    ::= { fsSntpMulticast  9 }

-- Anycast Objects

fsSntpAnycastPollInterval OBJECT-TYPE
    SYNTAX      Unsigned32 (16..16384)
    UNITS       "seconds"
    MAX-ACCESS  read-write
    STATUS      current
    DESCRIPTION
        "This object specifies the number of seconds between successive SNTP request
	 transmissions.For Example, if the Poll Interval is 64 secs, the Sntp client
	 sends the client request every 64 sec. If the server is not found it sends
	 the request packet to the broadcast or multicast address every 64 sec. If server
	 is found, it sends the client request to unicast address every 64 sec. The Poll
	 interval value is expressed as exponent of two."
    DEFVAL { 64 }
    ::= {fsSntpAnycast 1 }

fsSntpAnycastPollTimeout OBJECT-TYPE
    SYNTAX      Unsigned32 (1..30)
    UNITS       "seconds"
    MAX-ACCESS  read-write
    STATUS      current
    DESCRIPTION
        "The number of seconds to wait for a response from a SNTP server
        before considering the attempt to have 'timed out'."
    DEFVAL { 5 }
    ::= {fsSntpAnycast 2 }

fsSntpAnycastPollRetry OBJECT-TYPE
    SYNTAX      Unsigned32 (0..10)
    MAX-ACCESS  read-write
    STATUS      current
    DESCRIPTION
        "The number of times to retry a request to a SNTP server
        that has not successfully responded.
        For example, assume this object has been SET to a value of 2.
        When the SNTP client queries a given server it will send 1 SNTP
        request frame.  If that original attempt fails, the client will
        retry up to a maximum of 2 more times before giving up and
        attempting the new server by sending request to the broadcast
	or multicast address"
    DEFVAL { 3 }
    ::= { fsSntpAnycast 3 }

fsSntpServerTypeInAcastMode  OBJECT-TYPE
    SYNTAX     INTEGER { broadcast (1), multicast (2) }
    MAX-ACCESS read-write
    STATUS     current
    DESCRIPTION
        "To set the type of servers to be used in Manycast addressing mode
	 i.e to find a manycast server the client can send the request to either
	 broadcast or multicast address."
    DEFVAL  { broadcast }
    ::= { fsSntpAnycast  4 }

fsSntpGrpAddrTypeInAcastMode OBJECT-TYPE
    SYNTAX     InetAddressType
    MAX-ACCESS read-write
    STATUS     current
    DESCRIPTION
        "The address type of the server configured by the administrator
	 i.e the address is either IPv4 address or IPv6 address"
    ::= {fsSntpAnycast  5 }

fsSntpGrpAddrInAcastMode OBJECT-TYPE
    SYNTAX     InetAddress
    MAX-ACCESS read-write
    STATUS     current
    DESCRIPTION
        "The multicast group address can be configured by the administrator.
	 i.e to which address the client will send the requesr packet to find
	 out the manycast server."
    ::= {fsSntpAnycast 6 }


fsSntpPrimaryServerAddrTypeInAcastMode OBJECT-TYPE
    SYNTAX     InetAddressType
    MAX-ACCESS read-only
    STATUS     current
    DESCRIPTION
        "The address type of the primary server learnt in Manycast addressing
        mode i.e IPv4 address or IPv6 address."
    ::= {fsSntpAnycast  7 }

fsSntpPrimaryServerAddrInAcastMode OBJECT-TYPE
    SYNTAX     InetAddress
    MAX-ACCESS read-only
    STATUS     current
    DESCRIPTION
        "The primary server IP address learnt in Manycast addressing mode
	 after sending the request packet to the broadcast or multicast address."
    ::= { fsSntpAnycast  8 }

fsSntpSecondaryServerAddrTypeInAcastMode OBJECT-TYPE
    SYNTAX     InetAddressType
    MAX-ACCESS read-only
    STATUS     obsolete
    DESCRIPTION
        "The address type of the secondary server learnt in Manycast addressing mode"
    ::= { fsSntpAnycast  9 }

fsSntpSecondaryServerAddrInAcastMode OBJECT-TYPE
    SYNTAX     InetAddress
    MAX-ACCESS read-only
    STATUS     obsolete
    DESCRIPTION
        " The IP address of secondary server, learnt in Manycast addressing
        mode "
    ::= { fsSntpAnycast  10 }

END
