-- ----------------------------------------------------------------------------
--
--  SIAE MICROELETTRONICA s.p.a.
--
--  Via Michelangelo Buonarroti, 21
--  20093 - Cologno Monzese
--  Milano
--  ITALY
--
-- ----------------------------------------------------------------------------
-- ----------------------------------------------------------------------------

SIAE-SAFE-MODE-MIB
        DEFINITIONS ::= BEGIN

        IMPORTS
             MODULE-IDENTITY, OBJECT-TYPE, IpAddress
        FROM SNMPv2-SMI
             DisplayString
        FROM SNMPv2-TC
             siaeMib
        FROM SIAE-TREE-MIB
             AlarmStatus, AlarmSeverityCode
        FROM SIAE-ALARM-MIB;

    safeMode MODULE-IDENTITY
        LAST-UPDATED "201603100000Z"
        ORGANIZATION "SIAE MICROELETTRONICA spa"
        CONTACT-INFO
            "SIAE MICROELETTONICA s.p.a.
             Via Michelangelo Buonarroti, 21
             20093 - Cologno Monzese
             Milano - ITALY
             Phone :  +39-02-27325-1
             E-mail: help.help@siaemic.com
            "
        DESCRIPTION
            "Management information for safe mode.
            "
        REVISION "201603100000Z"
        DESCRIPTION
            "Initial version 01.00.00
            "
    ::= { siaeMib 99 }

----------------------------------------------------------------------------------
--  Safe Mode
----------------------------------------------------------------------------------
--
--  This MIB describes alarms and control parameters to manage the safe mode.
--  Safe mode is a feature to recover situations where a software failure loop
--  is detected: in these cases the equipment try to exit from the loop enabling
--  less features. After exiting this failure loop the equipment will be in a
--  safe mode status; when only auxiliary features are disable the recovery can
--  be done by remote using equipment IP address and equipment credentials;
--  when more features are disabled the recovery can be done
--  only in site with rescue credentials and rescue IP address.
----------------------------------------------------------------------------------

------ Beginning --------------------------------------------------------------

    safeModeMibVersion  OBJECT-TYPE
        SYNTAX      INTEGER
        MAX-ACCESS  read-only
        STATUS      current
        DESCRIPTION
            "Numerical version of this module.
             The string version of this MIB have the following format:
                XX.YY.ZZ
             so, for example, the value 1 should be interpreted as 00.00.01
             and the value 10001 should be interpreted as 01.00.01."
    ::= {safeMode 1}

    safeModeAlarm  OBJECT-TYPE
        SYNTAX      AlarmStatus
        MAX-ACCESS  read-only
        STATUS      current
        DESCRIPTION
            "Safe mode alarm with associated severity. This object
             indicates that the equipment is in safe mode.
            "
    ::= {safeMode 2}

    safeModeAlarmSeverityCode  OBJECT-TYPE
        SYNTAX      AlarmSeverityCode
        MAX-ACCESS  read-write
        STATUS      current
        DESCRIPTION
            "Defines the severity associated to the safeModeAlarm
             and enables/disables the trap generation on status change event.
            "
        DEFVAL {minorTrapEnable}
    ::= {safeMode 3}

    safeModeStatus OBJECT-TYPE
        SYNTAX      INTEGER {
                             safeModeStatusInactive     (1),
                             safeModeStatusNoAuxService (2),
                             safeModeStatusLinkMngmt    (3),
                             safeModeStatusSiteMngmt    (4),
                             safeModeStatusSiteDefault  (5),
                             safeModeStatusSiteRescue   (6)
                            }
        MAX-ACCESS  read-only
        STATUS      current
        DESCRIPTION
            "The safe mode status of the equipment.
             Equipment in normal-mode has safe mode status inactive"
    ::= {safeMode 4}

    safeModeRescueAdminStatus   OBJECT-TYPE
        SYNTAX      INTEGER {
                             disable (1),
                             enable  (2)
                            }
        MAX-ACCESS  read-write
        STATUS      current
        DESCRIPTION
            "This object enables or disables the site-rescue ."
        DEFVAL {enable}
    ::= {safeMode 5}

    safeModeRescuePwd  OBJECT-TYPE
        SYNTAX      DisplayString    (SIZE(1..31))
        MAX-ACCESS  read-write
        STATUS      current
        DESCRIPTION
            "This object specifies the login password of the rescue
             user."
    ::= {safeMode 6}

    safeModeRescueIpAddress  OBJECT-TYPE
        SYNTAX      IpAddress
        MAX-ACCESS  read-write
        STATUS      current
        DESCRIPTION
            "Ip address of the equipment in status site-rescue"
        DEFVAL { 'ac14fd0d'H }  -- 172.20.253.13
    ::= {safeMode 7}

    safeModeRescueIpNetMask  OBJECT-TYPE
        SYNTAX      IpAddress
        MAX-ACCESS  read-write
        STATUS      current
        DESCRIPTION
            "The subnet Mask associated with the Rescue IP address.
             The value of the Mask is an IP address with all the network bits set to 1
             and all the hosts bits set to 0."
    ::= {safeMode 8}



------ End group -----------------------------------------------------------------

END
