ARICENT-ACLEXT-MIB DEFINITIONS ::= BEGIN

IMPORTS
       MODULE-IDENTITY, OBJECT-TYPE,
       enterprises, Unsigned32, Integer32, Counter32, Counter64
           FROM SNMPv2-SMI
       TEXTUAL-CONVENTION
           FROM SNMPv2-TC
       issAclL2FilterEntry, issAclMgmtFilterEntry
           FROM ARICENT-ISS-ACL-MIB;

smfutacl  MODULE-IDENTITY
        LAST-UPDATED "201209050000Z"
        ORGANIZATION "ARICENT COMMUNICATIONS SOFTWARE"
        CONTACT-INFO "|||||"
        DESCRIPTION  "This MIB defines the objects. OID assign for siae
                     is (29601.100.1)"

        ::=  { enterprises aricent-communication-holding-ltd(29601) 100 1 4}

smAclClass         OBJECT IDENTIFIER ::= { smfutacl 1 }

smAclL2FilterExtTable OBJECT-TYPE
    SYNTAX       SEQUENCE OF SmAclL2FilterExtEntry
    MAX-ACCESS   not-accessible
    STATUS       current
    DESCRIPTION
       "This table contains the Multifield Classifier details. It takes input
        from the ACL or priority-map table and outputs a CLASS for the
        traffic-class pattern/match."
    ::= { smAclClass 1 }

smAclL2FilterExtEntry OBJECT-TYPE
    SYNTAX       SmAclL2FilterExtEntry
    MAX-ACCESS   not-accessible
    STATUS   current
    DESCRIPTION
       "A Multi-field Classifier entry maps an ACL entry or a priority-map
        to a CLASS of Service."
    AUGMENTS { issAclL2FilterEntry }
    ::= { smAclL2FilterExtTable 1 }

SmAclL2FilterExtEntry ::= SEQUENCE {
    smAclL2FilterCfiDeiBit INTEGER
    }

smAclL2FilterCfiDeiBit OBJECT-TYPE
   SYNTAX      INTEGER {
                    set (1),
                    reset (0),
                    none (2)
               }
   MAX-ACCESS  read-write
   STATUS      current
   DESCRIPTION
      "This object should be is used set the CFI/DEI bit on the external VLAN to add a qualifier OuterVlanCfi
	  in the hardware. This object should be used with mac-access list with IN direction."
   DEFVAL  { 2 }
   ::= { smAclL2FilterExtEntry 1 }

smAclMgmtExtTable OBJECT-TYPE
   SYNTAX      SEQUENCE OF SmAclMgmtExtEntry
   MAX-ACCESS  not-accessible
   STATUS      current
   DESCRIPTION
       " A table to configure Extended Management filter rules in the system.
       "
   ::= { smAclClass 2 }

smAclMgmtExtEntry OBJECT-TYPE
   SYNTAX      SmAclMgmtExtEntry
   MAX-ACCESS  not-accessible
   STATUS      current
   DESCRIPTION
       " Each entry in this table is a Management filter rule.
         Index to the table is Management filter number. "
   AUGMENTS { issAclMgmtFilterEntry }
   ::= { smAclMgmtExtTable 1 }

SmAclMgmtExtEntry ::=
   SEQUENCE {
      smAclMgmtExtProtocol
        BITS
  }

smAclMgmtExtProtocol OBJECT-TYPE
   SYNTAX BITS {
                 tcp  (0),
                 udp  (1),
                 icmp (2),
                 ospf (3)
               }
   MAX-ACCESS  read-write
   STATUS      current
   DESCRIPTION
       "This object selects the protocol on which mgt filter is applied
        (tcp, udp, icmp, ospf, etc...). By default it is applied on both
        tcp and udp.
       "
   DEFVAL { { tcp, udp } }
   ::= {smAclMgmtExtEntry 1}

END
