AC-PM-Control-MIB DEFINITIONS ::= BEGIN


    IMPORTS


        OBJECT-TYPE,
        MODULE-IDENTITY                             FROM SNMPv2-SMI
        TAddress,
        DisplayString,
        DateAndTime, TEXTUAL-CONVENTION             FROM SNMPv2-TC
        IpAddress                                   FROM RFC1155-SMI
        Unsigned32,
		Integer32,
        enterprises                                 FROM SNMPv2-SMI
		SnmpAdminString								FROM SNMP-FRAMEWORK-MIB
		audioCodes,
		acRegistrations,
		acGeneric,
		acProducts,acBoardMibs,acPerformance		FROM AUDIOCODES-TYPES-MIB;


acPMControl  MODULE-IDENTITY
    LAST-UPDATED "201311101856Z"          --Sunday, November 10 2013
    ORGANIZATION "AudioCodes Ltd"
    CONTACT-INFO
    "Postal: Support
			 AudioCodes LTD
             1 Hayarden Street
             Airport City
			 Lod, ISRAEL 70151
     Tel:    972-3-9764000
     Fax:    972-3-9764040
     Email:  support@audiocodes.com
     Web:    www.audiocodes.com"


    DESCRIPTION
    "The AC-PM-Control MIB offers performance monitoring
For the Control related elements in Audiocodes' devices.
The Configuration sub-tree is for configuring the interval
Period length for the entire AC-PM-Control MIB, and the
different tables' thresholds.
The Data sub-tree presents the tables of monitored
elements.

Note  - for the entire MIB the value (-1) means the value
Asked for is either not supported or currently not relevant
(this is for when values asked for are for intervals not yet
recorded."



    ::= {acPerformance 8}








     acPMControlConfiguration OBJECT IDENTIFIER ::= {acPMControl 1}


     acPMControlConfigurationPeriodLength OBJECT-TYPE
       SYNTAX Unsigned32 (0..894780)
       MAX-ACCESS read-write
       STATUS current
       DESCRIPTION
           "Length of monitoring intervals for entire MIB.
Time is in minutes.
Access: Instant."
       ::= {acPMControlConfiguration 1}



     acPMControlConfigurationResetTotalCounters OBJECT-TYPE
       SYNTAX INTEGER {
                  resetCountersDone(1)
,
                  resetTotalCounters(2)

                  }
       MAX-ACCESS read-write
       STATUS current
       DESCRIPTION
           "Total-Counters Reset.  To reset the total counters, set the
value of this object to resetTotalCounters(2).
Access: Instant."
       ::= {acPMControlConfiguration 2}



     acPMCPConnectionAttributes OBJECT IDENTIFIER ::= {acPMControlConfiguration 32}


     acPMCPConnectionAttributesLifetimeHighThreshold OBJECT-TYPE
       SYNTAX Unsigned32 (0..2147483647)
       MAX-ACCESS read-write
       STATUS current
       DESCRIPTION
           "High threshold.
Access: Instant."
       ::= {acPMCPConnectionAttributes 1}



     acPMCPConnectionAttributesLifetimeLowThreshold OBJECT-TYPE
       SYNTAX Unsigned32 (0..2147483647)
       MAX-ACCESS read-write
       STATUS current
       DESCRIPTION
           "Low threshold.
Access: Instant."
       ::= {acPMCPConnectionAttributes 2}



     acPMCPConnectionAttributesStateHighThreshold OBJECT-TYPE
       SYNTAX Unsigned32 (0..2147483647)
       MAX-ACCESS read-write
       STATUS current
       DESCRIPTION
           "High threshold.
Access: Instant."
       ::= {acPMCPConnectionAttributes 3}



     acPMCPConnectionAttributesStateLowThreshold OBJECT-TYPE
       SYNTAX Unsigned32 (0..2147483647)
       MAX-ACCESS read-write
       STATUS current
       DESCRIPTION
           "Low threshold.
Access: Instant."
       ::= {acPMCPConnectionAttributes 4}



     acPMCPConnectionAttributesCommandCounterHighThreshold OBJECT-TYPE
       SYNTAX Unsigned32 (0..2147483647)
       MAX-ACCESS read-write
       STATUS current
       DESCRIPTION
           "High threshold.
Access: Instant."
       ::= {acPMCPConnectionAttributes 5}



     acPMCPConnectionAttributesCommandCounterLowThreshold OBJECT-TYPE
       SYNTAX Unsigned32 (0..2147483647)
       MAX-ACCESS read-write
       STATUS current
       DESCRIPTION
           "Low threshold.
Access: Instant."
       ::= {acPMCPConnectionAttributes 6}



     acPMCPConnectionAttributesRetransmissionCountHighThreshold OBJECT-TYPE
       SYNTAX Unsigned32 (0..2147483647)
       MAX-ACCESS read-write
       STATUS current
       DESCRIPTION
           "High threshold.
Access: Instant."
       ::= {acPMCPConnectionAttributes 7}



     acPMCPConnectionAttributesRetransmissionCountLowThreshold OBJECT-TYPE
       SYNTAX Unsigned32 (0..2147483647)
       MAX-ACCESS read-write
       STATUS current
       DESCRIPTION
           "Low threshold.
Access: Instant."
       ::= {acPMCPConnectionAttributes 8}



     acPMCPConnectionAttributesActiveContextCountHighThreshold OBJECT-TYPE
       SYNTAX Unsigned32 (0..2147483647)
       MAX-ACCESS read-write
       STATUS current
       DESCRIPTION
           "High threshold.
Access: Instant."
       ::= {acPMCPConnectionAttributes 9}



     acPMCPConnectionAttributesActiveContextCountLowThreshold OBJECT-TYPE
       SYNTAX Unsigned32 (0..2147483647)
       MAX-ACCESS read-write
       STATUS current
       DESCRIPTION
           "Low threshold.
Access: Instant."
       ::= {acPMCPConnectionAttributes 10}



     acPMCPConnectionAttributesCommandSuccessCountHighThreshold OBJECT-TYPE
       SYNTAX Unsigned32 (0..2147483647)
       MAX-ACCESS read-write
       STATUS obsolete
       DESCRIPTION
           "High threshold.
Access: Instant."
       ::= {acPMCPConnectionAttributes 11}



     acPMCPConnectionAttributesCommandSuccessCountLowThreshold OBJECT-TYPE
       SYNTAX Unsigned32 (0..2147483647)
       MAX-ACCESS read-write
       STATUS obsolete
       DESCRIPTION
           "Low threshold.
Access: Instant."
       ::= {acPMCPConnectionAttributes 12}



     acPMCPConnectionAttributesCommandFailureCountHighThreshold OBJECT-TYPE
       SYNTAX Unsigned32 (0..2147483647)
       MAX-ACCESS read-write
       STATUS obsolete
       DESCRIPTION
           "High threshold.
Access: Instant."
       ::= {acPMCPConnectionAttributes 13}



     acPMCPConnectionAttributesCommandFailureCountLowThreshold OBJECT-TYPE
       SYNTAX Unsigned32 (0..2147483647)
       MAX-ACCESS read-write
       STATUS obsolete
       DESCRIPTION
           "Low threshold.
Access: Instant."
       ::= {acPMCPConnectionAttributes 14}



     acPMCPConnectionAttributesCommandProcessTimeHighThreshold OBJECT-TYPE
       SYNTAX Unsigned32 (0..2147483647)
       MAX-ACCESS read-write
       STATUS current
       DESCRIPTION
           "High threshold.
Access: Instant."
       ::= {acPMCPConnectionAttributes 15}



     acPMCPConnectionAttributesCommandProcessTimeLowThreshold OBJECT-TYPE
       SYNTAX Unsigned32 (0..2147483647)
       MAX-ACCESS read-write
       STATUS current
       DESCRIPTION
           "Low threshold.
Access: Instant."
       ::= {acPMCPConnectionAttributes 16}



     acPMCPConnectionAttributesTransactionProcessTimerHighThreshold OBJECT-TYPE
       SYNTAX Unsigned32 (0..2147483647)
       MAX-ACCESS read-write
       STATUS current
       DESCRIPTION
           "High threshold.
Access: Instant."
       ::= {acPMCPConnectionAttributes 17}



     acPMCPConnectionAttributesTransactionProcessTimerLowThreshold OBJECT-TYPE
       SYNTAX Unsigned32 (0..2147483647)
       MAX-ACCESS read-write
       STATUS current
       DESCRIPTION
           "Low threshold.
Access: Instant."
       ::= {acPMCPConnectionAttributes 18}



     acPMMegacoAttributes OBJECT IDENTIFIER ::= {acPMControlConfiguration 33}


     acPMMegacoAttributesServiceChangeCountHighThreshold OBJECT-TYPE
       SYNTAX Unsigned32 (0..2147483647)
       MAX-ACCESS read-write
       STATUS current
       DESCRIPTION
           "High threshold.
Access: Instant."
       ::= {acPMMegacoAttributes 1}



     acPMMegacoAttributesServiceChangeCountLowThreshold OBJECT-TYPE
       SYNTAX Unsigned32 (0..2147483647)
       MAX-ACCESS read-write
       STATUS current
       DESCRIPTION
           "Low threshold.
Access: Instant."
       ::= {acPMMegacoAttributes 2}



     acPMMegacoAttributesCmdSuccessCountHighThreshold OBJECT-TYPE
       SYNTAX Unsigned32 (0..2147483647)
       MAX-ACCESS read-write
       STATUS obsolete
       DESCRIPTION
           "High threshold.
Access: Instant."
       ::= {acPMMegacoAttributes 3}



     acPMMegacoAttributesCmdSuccessCountLowThreshold OBJECT-TYPE
       SYNTAX Unsigned32 (0..2147483647)
       MAX-ACCESS read-write
       STATUS obsolete
       DESCRIPTION
           "Low threshold.
Access: Instant."
       ::= {acPMMegacoAttributes 4}



     acPMMegacoAttributesCmdFailureCountHighThreshold OBJECT-TYPE
       SYNTAX Unsigned32 (0..2147483647)
       MAX-ACCESS read-write
       STATUS obsolete
       DESCRIPTION
           "High threshold.
Access: Instant."
       ::= {acPMMegacoAttributes 5}



     acPMMegacoAttributesCmdFailureCountLowThreshold OBJECT-TYPE
       SYNTAX Unsigned32 (0..2147483647)
       MAX-ACCESS read-write
       STATUS obsolete
       DESCRIPTION
           "Low threshold.
Access: Instant."
       ::= {acPMMegacoAttributes 6}



     acPMSipAttributes OBJECT IDENTIFIER ::= {acPMControlConfiguration 34}


     acPMSipAttributesCallDurationHighThreshold OBJECT-TYPE
       SYNTAX Unsigned32 (0..2147483647)
       MAX-ACCESS read-write
       STATUS current
       DESCRIPTION
           "High threshold.
Access: Instant."
       ::= {acPMSipAttributes 1}



     acPMSipAttributesCallDurationLowThreshold OBJECT-TYPE
       SYNTAX Unsigned32 (0..2147483647)
       MAX-ACCESS read-write
       STATUS current
       DESCRIPTION
           "Low threshold.
Access: Instant."
       ::= {acPMSipAttributes 2}



     acPMSipAttributesTrunkGroupUtilizationHighThreshold OBJECT-TYPE
       SYNTAX Unsigned32 (0..2016)
       MAX-ACCESS read-write
       STATUS current
       DESCRIPTION
           "High threshold.
Access: Instant."
       ::= {acPMSipAttributes 3}



     acPMSipAttributesTrunkGroupUtilizationLowThreshold OBJECT-TYPE
       SYNTAX Unsigned32 (0..2016)
       MAX-ACCESS read-write
       STATUS current
       DESCRIPTION
           "Low threshold.
Access: Instant."
       ::= {acPMSipAttributes 4}



     acPMSipAttributesTrunkGroupPercentageUtilizationHighThreshold OBJECT-TYPE
       SYNTAX Unsigned32 (0..100)
       MAX-ACCESS read-write
       STATUS current
       DESCRIPTION
           "High threshold.
Access: Instant."
       ::= {acPMSipAttributes 5}



     acPMSipAttributesTrunkGroupPercentageUtilizationLowThreshold OBJECT-TYPE
       SYNTAX Unsigned32 (0..100)
       MAX-ACCESS read-write
       STATUS current
       DESCRIPTION
           "Low threshold.
Access: Instant."
       ::= {acPMSipAttributes 6}



     acPMSipAttributesTrunkGroupNoResourcesCallsHighThreshold OBJECT-TYPE
       SYNTAX Unsigned32 (0..2147483647)
       MAX-ACCESS read-write
       STATUS current
       DESCRIPTION
           "High threshold.
Access: Instant."
       ::= {acPMSipAttributes 7}



     acPMSipAttributesTrunkGroupNoResourcesCallsLowThreshold OBJECT-TYPE
       SYNTAX Unsigned32 (0..2147483647)
       MAX-ACCESS read-write
       STATUS current
       DESCRIPTION
           "Low threshold.
Access: Instant."
       ::= {acPMSipAttributes 8}



     acPMSipAttributesIPGroupINVITEDialogsHighThreshold OBJECT-TYPE
       SYNTAX Unsigned32 (0..2147483647)
       MAX-ACCESS read-write
       STATUS current
       DESCRIPTION
           "High threshold.
Access: Instant."
       ::= {acPMSipAttributes 25}



     acPMSipAttributesIPGroupINVITEDialogsLowThreshold OBJECT-TYPE
       SYNTAX Unsigned32 (0..2147483647)
       MAX-ACCESS read-write
       STATUS current
       DESCRIPTION
           "Low threshold.
Access: Instant."
       ::= {acPMSipAttributes 26}



     acPMSipAttributesTrunkGroupAllTrunksBusyPercentageHighThreshold OBJECT-TYPE
       SYNTAX Unsigned32 (0..100)
       MAX-ACCESS read-write
       STATUS current
       DESCRIPTION
           "High threshold.
Access: Instant."
       ::= {acPMSipAttributes 33}



     acPMSipAttributesTrunkGroupAllTrunksBusyPercentageLowThreshold OBJECT-TYPE
       SYNTAX Unsigned32 (0..100)
       MAX-ACCESS read-write
       STATUS current
       DESCRIPTION
           "Low threshold.
Access: Instant."
       ::= {acPMSipAttributes 34}



     acPMMediaRealmAttributes OBJECT IDENTIFIER ::= {acPMControlConfiguration 35}


     acPMMediaRealmAttributesMediaRealmBytesTxHighThreshold OBJECT-TYPE
       SYNTAX Unsigned32 (0..2147483647)
       MAX-ACCESS read-write
       STATUS current
       DESCRIPTION
           "High threshold.
Access: Instant."
       ::= {acPMMediaRealmAttributes 1}



     acPMMediaRealmAttributesMediaRealmBytesTxLowThreshold OBJECT-TYPE
       SYNTAX Unsigned32 (0..2147483647)
       MAX-ACCESS read-write
       STATUS current
       DESCRIPTION
           "Low threshold.
Access: Instant."
       ::= {acPMMediaRealmAttributes 2}



     acPMMediaRealmAttributesMediaRealmBytesRxHighThreshold OBJECT-TYPE
       SYNTAX Unsigned32 (0..2147483647)
       MAX-ACCESS read-write
       STATUS current
       DESCRIPTION
           "High threshold.
Access: Instant."
       ::= {acPMMediaRealmAttributes 3}



     acPMMediaRealmAttributesMediaRealmBytesRxLowThreshold OBJECT-TYPE
       SYNTAX Unsigned32 (0..2147483647)
       MAX-ACCESS read-write
       STATUS current
       DESCRIPTION
           "Low threshold.
Access: Instant."
       ::= {acPMMediaRealmAttributes 4}



     acPMMediaRealmAttributesMediaRealmPacketsTxHighThreshold OBJECT-TYPE
       SYNTAX Unsigned32 (0..2147483647)
       MAX-ACCESS read-write
       STATUS current
       DESCRIPTION
           "High threshold.
Access: Instant."
       ::= {acPMMediaRealmAttributes 5}



     acPMMediaRealmAttributesMediaRealmPacketsTxLowThreshold OBJECT-TYPE
       SYNTAX Unsigned32 (0..2147483647)
       MAX-ACCESS read-write
       STATUS current
       DESCRIPTION
           "Low threshold.
Access: Instant."
       ::= {acPMMediaRealmAttributes 6}



     acPMMediaRealmAttributesMediaRealmPacketsRxHighThreshold OBJECT-TYPE
       SYNTAX Unsigned32 (0..2147483647)
       MAX-ACCESS read-write
       STATUS current
       DESCRIPTION
           "High threshold.
Access: Instant."
       ::= {acPMMediaRealmAttributes 7}



     acPMMediaRealmAttributesMediaRealmPacketsRxLowThreshold OBJECT-TYPE
       SYNTAX Unsigned32 (0..2147483647)
       MAX-ACCESS read-write
       STATUS current
       DESCRIPTION
           "Low threshold.
Access: Instant."
       ::= {acPMMediaRealmAttributes 8}



     acPMMediaRealmAttributesVERealmPacketDelayHighThreshold OBJECT-TYPE
       SYNTAX Unsigned32 (0..2147483647)
       MAX-ACCESS read-write
       STATUS current
       DESCRIPTION
           "High threshold.
Access: Instant."
       ::= {acPMMediaRealmAttributes 9}



     acPMMediaRealmAttributesVERealmPacketDelayLowThreshold OBJECT-TYPE
       SYNTAX Unsigned32 (0..2147483647)
       MAX-ACCESS read-write
       STATUS current
       DESCRIPTION
           "Low threshold.
Access: Instant."
       ::= {acPMMediaRealmAttributes 10}



     acPMMediaRealmAttributesVERealmPacketJitterHighThreshold OBJECT-TYPE
       SYNTAX Unsigned32 (0..2147483647)
       MAX-ACCESS read-write
       STATUS current
       DESCRIPTION
           "High threshold.
Access: Instant."
       ::= {acPMMediaRealmAttributes 11}



     acPMMediaRealmAttributesVERealmPacketJitterLowThreshold OBJECT-TYPE
       SYNTAX Unsigned32 (0..2147483647)
       MAX-ACCESS read-write
       STATUS current
       DESCRIPTION
           "Low threshold.
Access: Instant."
       ::= {acPMMediaRealmAttributes 12}



     acPMMediaRealmAttributesRealmMOSHighThreshold OBJECT-TYPE
       SYNTAX Unsigned32 (0..2147483647)
       MAX-ACCESS read-write
       STATUS current
       DESCRIPTION
           "High threshold.
Access: Instant."
       ::= {acPMMediaRealmAttributes 13}



     acPMMediaRealmAttributesRealmMOSLowThreshold OBJECT-TYPE
       SYNTAX Unsigned32 (0..2147483647)
       MAX-ACCESS read-write
       STATUS current
       DESCRIPTION
           "Low threshold.
Access: Instant."
       ::= {acPMMediaRealmAttributes 14}



     acPMMediaRealmAttributesMediaRealmBwRxHighThreshold OBJECT-TYPE
       SYNTAX Unsigned32 (0..2147483647)
       MAX-ACCESS read-write
       STATUS current
       DESCRIPTION
           "High threshold.
Access: Instant."
       ::= {acPMMediaRealmAttributes 15}



     acPMMediaRealmAttributesMediaRealmBwRxLowThreshold OBJECT-TYPE
       SYNTAX Unsigned32 (0..2147483647)
       MAX-ACCESS read-write
       STATUS current
       DESCRIPTION
           "Low threshold.
Access: Instant."
       ::= {acPMMediaRealmAttributes 16}



     acPMMediaRealmAttributesMediaRealmBwTxHighThreshold OBJECT-TYPE
       SYNTAX Unsigned32 (0..2147483647)
       MAX-ACCESS read-write
       STATUS current
       DESCRIPTION
           "High threshold.
Access: Instant."
       ::= {acPMMediaRealmAttributes 17}



     acPMMediaRealmAttributesMediaRealmBwTxLowThreshold OBJECT-TYPE
       SYNTAX Unsigned32 (0..2147483647)
       MAX-ACCESS read-write
       STATUS current
       DESCRIPTION
           "Low threshold.
Access: Instant."
       ::= {acPMMediaRealmAttributes 18}



     acPMControlData OBJECT IDENTIFIER ::= {acPMControl 2}


     acPMControlDataAcPMControlTimeFromStartOfInterval OBJECT-TYPE
       SYNTAX Unsigned32 (0..2147483647)
       MAX-ACCESS read-only
       STATUS current
       DESCRIPTION
           "The time in seconds since the start of the current interval.
MIB specific."
       ::= {acPMControlData 1}



     acPMCPConnection OBJECT IDENTIFIER ::= {acPMControlData 31}


     -- ****************************************
     -- acPMCPConnectionLifetime table declaration
     -- ****************************************
     acPMCPConnectionLifetimeTable OBJECT-TYPE
       SYNTAX SEQUENCE OF AcPMCPConnectionLifetimeEntry
       MAX-ACCESS not-accessible
       STATUS current
       DESCRIPTION
           "Connection lifetime in seconds."
       ::= {acPMCPConnection 1}



     -- ****************************************
     -- acPMCPConnectionLifetime table entry
     -- ****************************************
     acPMCPConnectionLifetimeEntry OBJECT-TYPE
       SYNTAX AcPMCPConnectionLifetimeEntry
       MAX-ACCESS not-accessible
       STATUS current
       DESCRIPTION
           ""
       INDEX {acPMCPConnectionLifetimeInterval}
       ::= {acPMCPConnectionLifetimeTable 1}



     -- ****************************************
     -- acPMCPConnectionLifetime TABLE
     -- ****************************************
     AcPMCPConnectionLifetimeEntry ::= SEQUENCE {
       acPMCPConnectionLifetimeInterval                Unsigned32,
       acPMCPConnectionLifetimeVal                     Gauge32,
       acPMCPConnectionLifetimeAverage                 Integer32,
       acPMCPConnectionLifetimeMax                     Integer32,
       acPMCPConnectionLifetimeMin                     Integer32,
       acPMCPConnectionLifetimeVolume                  Counter32,
       acPMCPConnectionLifetimeTimeBelowLowThreshold   Integer32,
       acPMCPConnectionLifetimeTimeBetweenThresholds   Integer32,
       acPMCPConnectionLifetimeTimeAboveHighThreshold  Integer32,
       acPMCPConnectionLifetimeFullDayAverage          Integer32,
       acPMCPConnectionLifetimeTotal                   Integer32
     }



     acPMCPConnectionLifetimeInterval OBJECT-TYPE
       SYNTAX Unsigned32 (0..4)
       MAX-ACCESS not-accessible
       STATUS current
       DESCRIPTION
           "Interval index.
0 - current period (incomplete monitoring - mid period).
1 - Last full period.
2 - One before last
3 - Two before last
4 - Three before last."
       ::= {acPMCPConnectionLifetimeEntry 1}



     acPMCPConnectionLifetimeVal OBJECT-TYPE
       SYNTAX Gauge32
       MAX-ACCESS read-only
       STATUS current
       DESCRIPTION
           "Value of gauge or counter."
       ::= {acPMCPConnectionLifetimeEntry 2}



     acPMCPConnectionLifetimeAverage OBJECT-TYPE
       SYNTAX Integer32 (-1..2147483647)
       MAX-ACCESS read-only
       STATUS current
       DESCRIPTION
           "Average value with in the period time."
       ::= {acPMCPConnectionLifetimeEntry 3}



     acPMCPConnectionLifetimeMax OBJECT-TYPE
       SYNTAX Integer32 (-1..2147483647)
       MAX-ACCESS read-only
       STATUS current
       DESCRIPTION
           "Maximum value with in the period time."
       ::= {acPMCPConnectionLifetimeEntry 4}



     acPMCPConnectionLifetimeMin OBJECT-TYPE
       SYNTAX Integer32 (-1..2147483647)
       MAX-ACCESS read-only
       STATUS current
       DESCRIPTION
           "Minimum value with in the period time."
       ::= {acPMCPConnectionLifetimeEntry 5}



     acPMCPConnectionLifetimeVolume OBJECT-TYPE
       SYNTAX Counter32
       MAX-ACCESS read-only
       STATUS current
       DESCRIPTION
           "Activity volume."
       ::= {acPMCPConnectionLifetimeEntry 6}



     acPMCPConnectionLifetimeTimeBelowLowThreshold OBJECT-TYPE
       SYNTAX Integer32 (-1..100)
       MAX-ACCESS read-only
       STATUS current
       DESCRIPTION
           "Percent of interval time for which gauge is below what was determined
as the low threshold."
       ::= {acPMCPConnectionLifetimeEntry 7}



     acPMCPConnectionLifetimeTimeBetweenThresholds OBJECT-TYPE
       SYNTAX Integer32 (-1..100)
       MAX-ACCESS read-only
       STATUS current
       DESCRIPTION
           "Percent of interval time for which gauge is above what was determined
as the high threshold."
       ::= {acPMCPConnectionLifetimeEntry 8}



     acPMCPConnectionLifetimeTimeAboveHighThreshold OBJECT-TYPE
       SYNTAX Integer32 (-1..100)
       MAX-ACCESS read-only
       STATUS current
       DESCRIPTION
           "Percent of interval time for which gauge is between what were
determined as the low and high thresholds."
       ::= {acPMCPConnectionLifetimeEntry 9}



     acPMCPConnectionLifetimeFullDayAverage OBJECT-TYPE
       SYNTAX Integer32 (-1..2147483647)
       MAX-ACCESS read-only
       STATUS current
       DESCRIPTION
           "The average of full 24 hours."
       ::= {acPMCPConnectionLifetimeEntry 10}



     acPMCPConnectionLifetimeTotal OBJECT-TYPE
       SYNTAX Integer32 (-1..2147483647)
       MAX-ACCESS read-only
       STATUS current
       DESCRIPTION
           "Total since last reset."
       ::= {acPMCPConnectionLifetimeEntry 11}



     -- ****************************************
     -- acPMCPConnectionState table declaration
     -- ****************************************
     acPMCPConnectionStateTable OBJECT-TYPE
       SYNTAX SEQUENCE OF AcPMCPConnectionStateEntry
       MAX-ACCESS not-accessible
       STATUS current
       DESCRIPTION
           "MGC connection activity indicator."
       ::= {acPMCPConnection 2}



     -- ****************************************
     -- acPMCPConnectionState table entry
     -- ****************************************
     acPMCPConnectionStateEntry OBJECT-TYPE
       SYNTAX AcPMCPConnectionStateEntry
       MAX-ACCESS not-accessible
       STATUS current
       DESCRIPTION
           ""
       INDEX {acPMCPConnectionStateInterval}
       ::= {acPMCPConnectionStateTable 1}



     -- ****************************************
     -- acPMCPConnectionState TABLE
     -- ****************************************
     AcPMCPConnectionStateEntry ::= SEQUENCE {
       acPMCPConnectionStateInterval                   Unsigned32,
       acPMCPConnectionStateChanges                    Gauge32,
       acPMCPConnectionStateActiveTime                 Integer32
     }



     acPMCPConnectionStateInterval OBJECT-TYPE
       SYNTAX Unsigned32 (0..2)
       MAX-ACCESS not-accessible
       STATUS current
       DESCRIPTION
           "Interval index.
0 - current period (incomplete monitoring - mid period).
1 - Last full period.
2 - One before last."
       ::= {acPMCPConnectionStateEntry 1}



     acPMCPConnectionStateChanges OBJECT-TYPE
       SYNTAX Gauge32
       MAX-ACCESS read-only
       STATUS current
       DESCRIPTION
           "Activity volume."
       ::= {acPMCPConnectionStateEntry 2}



     acPMCPConnectionStateActiveTime OBJECT-TYPE
       SYNTAX Integer32 (-1..100)
       MAX-ACCESS read-only
       STATUS current
       DESCRIPTION
           "Percent of interval time for which gauge is between what were
determined as the low and high thresholds."
       ::= {acPMCPConnectionStateEntry 3}



     -- ****************************************
     -- acPMCPCommandCounter table declaration
     -- ****************************************
     acPMCPCommandCounterTable OBJECT-TYPE
       SYNTAX SEQUENCE OF AcPMCPCommandCounterEntry
       MAX-ACCESS not-accessible
       STATUS current
       DESCRIPTION
           "MGC command/response counters. Index: 0=sent commands, 1=received commands"
       ::= {acPMCPConnection 3}



     -- ****************************************
     -- acPMCPCommandCounter table entry
     -- ****************************************
     acPMCPCommandCounterEntry OBJECT-TYPE
       SYNTAX AcPMCPCommandCounterEntry
       MAX-ACCESS not-accessible
       STATUS current
       DESCRIPTION
           ""
       INDEX {acPMCPCommandCounterDirection,acPMCPCommandCounterInterval}
       ::= {acPMCPCommandCounterTable 1}



     -- ****************************************
     -- acPMCPCommandCounter TABLE
     -- ****************************************
     AcPMCPCommandCounterEntry ::= SEQUENCE {
       acPMCPCommandCounterDirection                   INTEGER,
       acPMCPCommandCounterInterval                    Unsigned32,
       acPMCPCommandCounterVal                         Counter32,
       acPMCPCommandCounterTotal                       Integer32
     }



     acPMCPCommandCounterDirection OBJECT-TYPE
       SYNTAX INTEGER {
                  tx(0)
,
                  rx(1)

                  }
       MAX-ACCESS not-accessible
       STATUS current
       DESCRIPTION
           "Direction index.
 0 - transmit
 1 - receive."
       ::= {acPMCPCommandCounterEntry 1}



     acPMCPCommandCounterInterval OBJECT-TYPE
       SYNTAX Unsigned32 (0..2)
       MAX-ACCESS not-accessible
       STATUS current
       DESCRIPTION
           "Interval index.
0 - current period (incomplete monitoring - mid period).
1 - Last full period.
2 - One before last."
       ::= {acPMCPCommandCounterEntry 2}



     acPMCPCommandCounterVal OBJECT-TYPE
       SYNTAX Counter32
       MAX-ACCESS read-only
       STATUS current
       DESCRIPTION
           "Value of gauge or counter."
       ::= {acPMCPCommandCounterEntry 3}



     acPMCPCommandCounterTotal OBJECT-TYPE
       SYNTAX Integer32 (-1..2147483647)
       MAX-ACCESS read-only
       STATUS current
       DESCRIPTION
           "Total since last reset."
       ::= {acPMCPCommandCounterEntry 4}



     -- ****************************************
     -- acPMCPRetransmissionCount table declaration
     -- ****************************************
     acPMCPRetransmissionCountTable OBJECT-TYPE
       SYNTAX SEQUENCE OF AcPMCPRetransmissionCountEntry
       MAX-ACCESS not-accessible
       STATUS current
       DESCRIPTION
           "Number of transaction retransmissions.
The first direction (tx(0)) counts the transactions sent from the board,
while the second direction (rx(1)) counts the incoming retransmissions."
       ::= {acPMCPConnection 4}



     -- ****************************************
     -- acPMCPRetransmissionCount table entry
     -- ****************************************
     acPMCPRetransmissionCountEntry OBJECT-TYPE
       SYNTAX AcPMCPRetransmissionCountEntry
       MAX-ACCESS not-accessible
       STATUS current
       DESCRIPTION
           ""
       INDEX {acPMCPRetransmissionCountDirection,acPMCPRetransmissionCountInterval}
       ::= {acPMCPRetransmissionCountTable 1}



     -- ****************************************
     -- acPMCPRetransmissionCount TABLE
     -- ****************************************
     AcPMCPRetransmissionCountEntry ::= SEQUENCE {
       acPMCPRetransmissionCountDirection              INTEGER,
       acPMCPRetransmissionCountInterval               Unsigned32,
       acPMCPRetransmissionCountVal                    Gauge32,
       acPMCPRetransmissionCountTotal                  Integer32
     }



     acPMCPRetransmissionCountDirection OBJECT-TYPE
       SYNTAX INTEGER {
                  tx(0)
,
                  rx(1)

                  }
       MAX-ACCESS not-accessible
       STATUS current
       DESCRIPTION
           "Direction index.
 0 - transmit
 1 - receive."
       ::= {acPMCPRetransmissionCountEntry 1}



     acPMCPRetransmissionCountInterval OBJECT-TYPE
       SYNTAX Unsigned32 (0..2)
       MAX-ACCESS not-accessible
       STATUS current
       DESCRIPTION
           "Interval index.
0 - current period (incomplete monitoring - mid period).
1 - Last full period.
2 - One before last."
       ::= {acPMCPRetransmissionCountEntry 2}



     acPMCPRetransmissionCountVal OBJECT-TYPE
       SYNTAX Gauge32
       MAX-ACCESS read-only
       STATUS current
       DESCRIPTION
           "Value of gauge or counter."
       ::= {acPMCPRetransmissionCountEntry 3}



     acPMCPRetransmissionCountTotal OBJECT-TYPE
       SYNTAX Integer32 (-1..2147483647)
       MAX-ACCESS read-only
       STATUS current
       DESCRIPTION
           "Total since last reset."
       ::= {acPMCPRetransmissionCountEntry 4}



     -- ****************************************
     -- acPMActiveContextCount table declaration
     -- ****************************************
     acPMActiveContextCountTable OBJECT-TYPE
       SYNTAX SEQUENCE OF AcPMActiveContextCountEntry
       MAX-ACCESS not-accessible
       STATUS current
       DESCRIPTION
           "Number of active contexts"
       ::= {acPMCPConnection 5}



     -- ****************************************
     -- acPMActiveContextCount table entry
     -- ****************************************
     acPMActiveContextCountEntry OBJECT-TYPE
       SYNTAX AcPMActiveContextCountEntry
       MAX-ACCESS not-accessible
       STATUS current
       DESCRIPTION
           ""
       INDEX {acPMActiveContextCountInterval}
       ::= {acPMActiveContextCountTable 1}



     -- ****************************************
     -- acPMActiveContextCount TABLE
     -- ****************************************
     AcPMActiveContextCountEntry ::= SEQUENCE {
       acPMActiveContextCountInterval                  Unsigned32,
       acPMActiveContextCountVal                       Gauge32,
       acPMActiveContextCountAverage                   Integer32,
       acPMActiveContextCountMax                       Integer32,
       acPMActiveContextCountMin                       Integer32,
       acPMActiveContextCountVolume                    Counter32,
       acPMActiveContextCountTimeBelowLowThreshold     Integer32,
       acPMActiveContextCountTimeBetweenThresholds     Integer32,
       acPMActiveContextCountTimeAboveHighThreshold    Integer32,
       acPMActiveContextCountFullDayAverage            Integer32,
       acPMActiveContextCountTotal                     Integer32
     }



     acPMActiveContextCountInterval OBJECT-TYPE
       SYNTAX Unsigned32 (0..2)
       MAX-ACCESS not-accessible
       STATUS current
       DESCRIPTION
           "Interval index.
0 - current period (incomplete monitoring - mid period).
1 - Last full period.
2 - One before last."
       ::= {acPMActiveContextCountEntry 1}



     acPMActiveContextCountVal OBJECT-TYPE
       SYNTAX Gauge32
       MAX-ACCESS read-only
       STATUS current
       DESCRIPTION
           "Value of gauge or counter."
       ::= {acPMActiveContextCountEntry 2}



     acPMActiveContextCountAverage OBJECT-TYPE
       SYNTAX Integer32 (-1..2147483647)
       MAX-ACCESS read-only
       STATUS current
       DESCRIPTION
           "Average value with in the period time."
       ::= {acPMActiveContextCountEntry 3}



     acPMActiveContextCountMax OBJECT-TYPE
       SYNTAX Integer32 (-1..2147483647)
       MAX-ACCESS read-only
       STATUS current
       DESCRIPTION
           "Maximum value with in the period time."
       ::= {acPMActiveContextCountEntry 4}



     acPMActiveContextCountMin OBJECT-TYPE
       SYNTAX Integer32 (-1..2147483647)
       MAX-ACCESS read-only
       STATUS current
       DESCRIPTION
           "Minimum value with in the period time."
       ::= {acPMActiveContextCountEntry 5}



     acPMActiveContextCountVolume OBJECT-TYPE
       SYNTAX Counter32
       MAX-ACCESS read-only
       STATUS current
       DESCRIPTION
           "Activity volume."
       ::= {acPMActiveContextCountEntry 6}



     acPMActiveContextCountTimeBelowLowThreshold OBJECT-TYPE
       SYNTAX Integer32 (-1..100)
       MAX-ACCESS read-only
       STATUS current
       DESCRIPTION
           "Percent of interval time for which gauge is below what was determined
as the low threshold."
       ::= {acPMActiveContextCountEntry 7}



     acPMActiveContextCountTimeBetweenThresholds OBJECT-TYPE
       SYNTAX Integer32 (-1..100)
       MAX-ACCESS read-only
       STATUS current
       DESCRIPTION
           "Percent of interval time for which gauge is above what was determined
as the high threshold."
       ::= {acPMActiveContextCountEntry 8}



     acPMActiveContextCountTimeAboveHighThreshold OBJECT-TYPE
       SYNTAX Integer32 (-1..100)
       MAX-ACCESS read-only
       STATUS current
       DESCRIPTION
           "Percent of interval time for which gauge is between what were
determined as the low and high thresholds."
       ::= {acPMActiveContextCountEntry 9}



     acPMActiveContextCountFullDayAverage OBJECT-TYPE
       SYNTAX Integer32 (-1..2147483647)
       MAX-ACCESS read-only
       STATUS current
       DESCRIPTION
           "The average of full 24 hours."
       ::= {acPMActiveContextCountEntry 10}



     acPMActiveContextCountTotal OBJECT-TYPE
       SYNTAX Integer32 (-1..2147483647)
       MAX-ACCESS read-only
       STATUS current
       DESCRIPTION
           "Total since last reset."
       ::= {acPMActiveContextCountEntry 11}



     -- ****************************************
     -- acPMCPCommandSuccessCount table declaration
     -- ****************************************
     acPMCPCommandSuccessCountTable OBJECT-TYPE
       SYNTAX SEQUENCE OF AcPMCPCommandSuccessCountEntry
       MAX-ACCESS not-accessible
       STATUS obsolete
       DESCRIPTION
           "Number of successful commands, per command type. Index: 0=add, 1=move, 2=modify, 3=subtract, 4=SC, 5=AuditValue, 6=AuditCapabilities, 7=Notify"
       ::= {acPMCPConnection 6}



     -- ****************************************
     -- acPMCPCommandSuccessCount table entry
     -- ****************************************
     acPMCPCommandSuccessCountEntry OBJECT-TYPE
       SYNTAX AcPMCPCommandSuccessCountEntry
       MAX-ACCESS not-accessible
       STATUS obsolete
       DESCRIPTION
           ""
       INDEX {acPMCPCommandSuccessCountCommandType,acPMCPCommandSuccessCountInterval}
       ::= {acPMCPCommandSuccessCountTable 1}



     -- ****************************************
     -- acPMCPCommandSuccessCount TABLE
     -- ****************************************
     AcPMCPCommandSuccessCountEntry ::= SEQUENCE {
       acPMCPCommandSuccessCountCommandType            INTEGER,
       acPMCPCommandSuccessCountInterval               Unsigned32,
       acPMCPCommandSuccessCountVal                    Gauge32,
       acPMCPCommandSuccessCountTotal                  Integer32
     }



     acPMCPCommandSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCommandSuccessCountEntry 1}



     acPMCPCommandSuccessCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandSuccessCountEntry 2}



     acPMCPCommandSuccessCountVal OBJECT-TYPE
       SYNTAX Gauge32
       MAX-ACCESS read-only
       STATUS obsolete
       DESCRIPTION
           "Value of gauge or counter."
       ::= {acPMCPCommandSuccessCountEntry 3}



     acPMCPCommandSuccessCountTotal OBJECT-TYPE
       SYNTAX Integer32 (-1..2147483647)
       MAX-ACCESS read-only
       STATUS obsolete
       DESCRIPTION
           "Total since last reset."
       ::= {acPMCPCommandSuccessCountEntry 4}



     -- ****************************************
     -- acPMCPCommandFailureCount table declaration
     -- ****************************************
     acPMCPCommandFailureCountTable OBJECT-TYPE
       SYNTAX SEQUENCE OF AcPMCPCommandFailureCountEntry
       MAX-ACCESS not-accessible
       STATUS obsolete
       DESCRIPTION
           "Number of failing commands, per command type. Index: 0=add, 1=move, 2=modify, 3=subtract, 4=SC, 5=AuditValue, 6=AuditCapabilities, 7=Notify"
       ::= {acPMCPConnection 7}



     -- ****************************************
     -- acPMCPCommandFailureCount table entry
     -- ****************************************
     acPMCPCommandFailureCountEntry OBJECT-TYPE
       SYNTAX AcPMCPCommandFailureCountEntry
       MAX-ACCESS not-accessible
       STATUS obsolete
       DESCRIPTION
           ""
       INDEX {acPMCPCommandFailureCountCommandType,acPMCPCommandFailureCountInterval}
       ::= {acPMCPCommandFailureCountTable 1}



     -- ****************************************
     -- acPMCPCommandFailureCount TABLE
     -- ****************************************
     AcPMCPCommandFailureCountEntry ::= SEQUENCE {
       acPMCPCommandFailureCountCommandType            INTEGER,
       acPMCPCommandFailureCountInterval               Unsigned32,
       acPMCPCommandFailureCountVal                    Gauge32,
       acPMCPCommandFailureCountTotal                  Integer32
     }



     acPMCPCommandFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS obsolete
       DESCRIPTION
           "Command type:
 0=add, 1=move, 2=modify, 3=subtract, 4=SC, 5=AuditValue, 6=AuditCapabilities,
7=Notify."
       ::= {acPMCPCommandFailureCountEntry 1}



     acPMCPCommandFailureCountInterval OBJECT-TYPE
       SYNTAX Unsigned32 (0..2)
       MAX-ACCESS not-accessible
       STATUS obsolete
       DESCRIPTION
           "Interval index.
0 - current period (incomplete monitoring - mid period).
1 - Last full period.
2 - One before last."
       ::= {acPMCPCommandFailureCountEntry 2}



     acPMCPCommandFailureCountVal OBJECT-TYPE
       SYNTAX Gauge32
       MAX-ACCESS read-only
       STATUS obsolete
       DESCRIPTION
           "Value of gauge or counter."
       ::= {acPMCPCommandFailureCountEntry 3}



     acPMCPCommandFailureCountTotal OBJECT-TYPE
       SYNTAX Integer32 (-1..2147483647)
       MAX-ACCESS read-only
       STATUS current
       DESCRIPTION
           "Total since last reset."
       ::= {acPMCPCommandFailureCountEntry 4}



     -- ****************************************
     -- acPMcpCmdProcessTime table declaration
     -- ****************************************
     acPMcpCmdProcessTimeTable OBJECT-TYPE
       SYNTAX SEQUENCE OF AcPMcpCmdProcessTimeEntry
       MAX-ACCESS not-accessible
       STATUS current
       DESCRIPTION
           "Processing time (in Microseconds), per command type."
       ::= {acPMCPConnection 8}



     -- ****************************************
     -- acPMcpCmdProcessTime table entry
     -- ****************************************
     acPMcpCmdProcessTimeEntry OBJECT-TYPE
       SYNTAX AcPMcpCmdProcessTimeEntry
       MAX-ACCESS not-accessible
       STATUS current
       DESCRIPTION
           ""
       INDEX {acPMcpCmdProcessTimeInterval}
       ::= {acPMcpCmdProcessTimeTable 1}



     -- ****************************************
     -- acPMcpCmdProcessTime TABLE
     -- ****************************************
     AcPMcpCmdProcessTimeEntry ::= SEQUENCE {
       acPMcpCmdProcessTimeInterval                    Unsigned32,
       acPMcpCmdProcessTimeVal                         Gauge32,
       acPMcpCmdProcessTimeAverage                     Integer32,
       acPMcpCmdProcessTimeMax                         Integer32,
       acPMcpCmdProcessTimeMin                         Integer32,
       acPMcpCmdProcessTimeVolume                      Counter32,
       acPMcpCmdProcessTimeTimeBelowLowThreshold       Integer32,
       acPMcpCmdProcessTimeTimeBetweenThresholds       Integer32,
       acPMcpCmdProcessTimeTimeAboveHighThreshold      Integer32,
       acPMcpCmdProcessTimeFullDayAverage              Integer32,
       acPMcpCmdProcessTimeTotal                       Integer32
     }



     acPMcpCmdProcessTimeInterval OBJECT-TYPE
       SYNTAX Unsigned32 (0..2)
       MAX-ACCESS not-accessible
       STATUS current
       DESCRIPTION
           "Interval index.
0 - current period (incomplete monitoring - mid period).
1 - Last full period.
2 - One before last."
       ::= {acPMcpCmdProcessTimeEntry 1}



     acPMcpCmdProcessTimeVal OBJECT-TYPE
       SYNTAX Gauge32
       MAX-ACCESS read-only
       STATUS current
       DESCRIPTION
           "Value of gauge or counter."
       ::= {acPMcpCmdProcessTimeEntry 2}



     acPMcpCmdProcessTimeAverage OBJECT-TYPE
       SYNTAX Integer32 (-1..2147483647)
       MAX-ACCESS read-only
       STATUS current
       DESCRIPTION
           "Average value with in the period time."
       ::= {acPMcpCmdProcessTimeEntry 3}



     acPMcpCmdProcessTimeMax OBJECT-TYPE
       SYNTAX Integer32 (-1..2147483647)
       MAX-ACCESS read-only
       STATUS current
       DESCRIPTION
           "Maximum value with in the period time."
       ::= {acPMcpCmdProcessTimeEntry 4}



     acPMcpCmdProcessTimeMin OBJECT-TYPE
       SYNTAX Integer32 (-1..2147483647)
       MAX-ACCESS read-only
       STATUS current
       DESCRIPTION
           "Minimum value with in the period time."
       ::= {acPMcpCmdProcessTimeEntry 5}



     acPMcpCmdProcessTimeVolume OBJECT-TYPE
       SYNTAX Counter32
       MAX-ACCESS read-only
       STATUS current
       DESCRIPTION
           "Activity volume."
       ::= {acPMcpCmdProcessTimeEntry 6}



     acPMcpCmdProcessTimeTimeBelowLowThreshold OBJECT-TYPE
       SYNTAX Integer32 (-1..100)
       MAX-ACCESS read-only
       STATUS current
       DESCRIPTION
           "Percent of interval time for which gauge is below what was determined
as the low threshold."
       ::= {acPMcpCmdProcessTimeEntry 7}



     acPMcpCmdProcessTimeTimeBetweenThresholds OBJECT-TYPE
       SYNTAX Integer32 (-1..100)
       MAX-ACCESS read-only
       STATUS current
       DESCRIPTION
           "Percent of interval time for which gauge is above what was determined
as the high threshold."
       ::= {acPMcpCmdProcessTimeEntry 8}



     acPMcpCmdProcessTimeTimeAboveHighThreshold OBJECT-TYPE
       SYNTAX Integer32 (-1..100)
       MAX-ACCESS read-only
       STATUS current
       DESCRIPTION
           "Percent of interval time for which gauge is between what were
determined as the low and high thresholds."
       ::= {acPMcpCmdProcessTimeEntry 9}



     acPMcpCmdProcessTimeFullDayAverage OBJECT-TYPE
       SYNTAX Integer32 (-1..2147483647)
       MAX-ACCESS read-only
       STATUS current
       DESCRIPTION
           "The average of full 24 hours."
       ::= {acPMcpCmdProcessTimeEntry 10}



     acPMcpCmdProcessTimeTotal OBJECT-TYPE
       SYNTAX Integer32 (-1..2147483647)
       MAX-ACCESS read-only
       STATUS current
       DESCRIPTION
           "Total since last reset."
       ::= {acPMcpCmdProcessTimeEntry 11}



     -- ****************************************
     -- acPMcpTransactionProcessTimer table declaration
     -- ****************************************
     acPMcpTransactionProcessTimerTable OBJECT-TYPE
       SYNTAX SEQUENCE OF AcPMcpTransactionProcessTimerEntry
       MAX-ACCESS not-accessible
       STATUS current
       DESCRIPTION
           "Processing time (in Microseconds), For transaction request."
       ::= {acPMCPConnection 9}



     -- ****************************************
     -- acPMcpTransactionProcessTimer table entry
     -- ****************************************
     acPMcpTransactionProcessTimerEntry OBJECT-TYPE
       SYNTAX AcPMcpTransactionProcessTimerEntry
       MAX-ACCESS not-accessible
       STATUS current
       DESCRIPTION
           ""
       INDEX {acPMcpTransactionProcessTimerInterval}
       ::= {acPMcpTransactionProcessTimerTable 1}



     -- ****************************************
     -- acPMcpTransactionProcessTimer TABLE
     -- ****************************************
     AcPMcpTransactionProcessTimerEntry ::= SEQUENCE {
       acPMcpTransactionProcessTimerInterval           Unsigned32,
       acPMcpTransactionProcessTimerVal                Gauge32,
       acPMcpTransactionProcessTimerAverage            Integer32,
       acPMcpTransactionProcessTimerMax                Integer32,
       acPMcpTransactionProcessTimerMin                Integer32,
       acPMcpTransactionProcessTimerVolume             Counter32,
       acPMcpTransactionProcessTimerTimeBelowLowThreshold
                                                       Integer32,
       acPMcpTransactionProcessTimerTimeBetweenThresholds
                                                       Integer32,
       acPMcpTransactionProcessTimerTimeAboveHighThreshold
                                                       Integer32,
       acPMcpTransactionProcessTimerFullDayAverage     Integer32,
       acPMcpTransactionProcessTimerTotal              Integer32
     }



     acPMcpTransactionProcessTimerInterval OBJECT-TYPE
       SYNTAX Unsigned32 (0..2)
       MAX-ACCESS not-accessible
       STATUS current
       DESCRIPTION
           "Interval index.
0 - current period (incomplete monitoring - mid period).
1 - Last full period.
2 - One before last."
       ::= {acPMcpTransactionProcessTimerEntry 1}



     acPMcpTransactionProcessTimerVal OBJECT-TYPE
       SYNTAX Gauge32
       MAX-ACCESS read-only
       STATUS current
       DESCRIPTION
           "Value of gauge or counter."
       ::= {acPMcpTransactionProcessTimerEntry 2}



     acPMcpTransactionProcessTimerAverage OBJECT-TYPE
       SYNTAX Integer32 (-1..2147483647)
       MAX-ACCESS read-only
       STATUS current
       DESCRIPTION
           "Average value with in the period time."
       ::= {acPMcpTransactionProcessTimerEntry 3}



     acPMcpTransactionProcessTimerMax OBJECT-TYPE
       SYNTAX Integer32 (-1..2147483647)
       MAX-ACCESS read-only
       STATUS current
       DESCRIPTION
           "Maximum value with in the period time."
       ::= {acPMcpTransactionProcessTimerEntry 4}



     acPMcpTransactionProcessTimerMin OBJECT-TYPE
       SYNTAX Integer32 (-1..2147483647)
       MAX-ACCESS read-only
       STATUS current
       DESCRIPTION
           "Minimum value with in the period time."
       ::= {acPMcpTransactionProcessTimerEntry 5}



     acPMcpTransactionProcessTimerVolume OBJECT-TYPE
       SYNTAX Counter32
       MAX-ACCESS read-only
       STATUS current
       DESCRIPTION
           "Activity volume."
       ::= {acPMcpTransactionProcessTimerEntry 6}



     acPMcpTransactionProcessTimerTimeBelowLowThreshold OBJECT-TYPE
       SYNTAX Integer32 (-1..100)
       MAX-ACCESS read-only
       STATUS current
       DESCRIPTION
           "Percent of interval time for which gauge is below what was determined
as the low threshold."
       ::= {acPMcpTransactionProcessTimerEntry 7}



     acPMcpTransactionProcessTimerTimeBetweenThresholds OBJECT-TYPE
       SYNTAX Integer32 (-1..100)
       MAX-ACCESS read-only
       STATUS current
       DESCRIPTION
           "Percent of interval time for which gauge is above what was determined
as the high threshold."
       ::= {acPMcpTransactionProcessTimerEntry 8}



     acPMcpTransactionProcessTimerTimeAboveHighThreshold OBJECT-TYPE
       SYNTAX Integer32 (-1..100)
       MAX-ACCESS read-only
       STATUS current
       DESCRIPTION
           "Percent of interval time for which gauge is between what were
determined as the low and high thresholds."
       ::= {acPMcpTransactionProcessTimerEntry 9}



     acPMcpTransactionProcessTimerFullDayAverage OBJECT-TYPE
       SYNTAX Integer32 (-1..2147483647)
       MAX-ACCESS read-only
       STATUS current
       DESCRIPTION
           "The average of full 24 hours."
       ::= {acPMcpTransactionProcessTimerEntry 10}



     acPMcpTransactionProcessTimerTotal OBJECT-TYPE
       SYNTAX Integer32 (-1..2147483647)
       MAX-ACCESS read-only
       STATUS current
       DESCRIPTION
           "Total since last reset."
       ::= {acPMcpTransactionProcessTimerEntry 11}



     -- ****************************************
     -- acPMCPCallAttemptsPerSec table declaration
     -- ****************************************
     acPMCPCallAttemptsPerSecTable OBJECT-TYPE
       SYNTAX SEQUENCE OF AcPMCPCallAttemptsPerSecEntry
       MAX-ACCESS not-accessible
       STATUS current
       DESCRIPTION
           "Number of Call attempts (successful and unsuccessful)  for second"
       ::= {acPMCPConnection 10}



     -- ****************************************
     -- acPMCPCallAttemptsPerSec table entry
     -- ****************************************
     acPMCPCallAttemptsPerSecEntry OBJECT-TYPE
       SYNTAX AcPMCPCallAttemptsPerSecEntry
       MAX-ACCESS not-accessible
       STATUS current
       DESCRIPTION
           ""
       INDEX {acPMCPCallAttemptsPerSecInterval}
       ::= {acPMCPCallAttemptsPerSecTable 1}



     -- ****************************************
     -- acPMCPCallAttemptsPerSec TABLE
     -- ****************************************
     AcPMCPCallAttemptsPerSecEntry ::= SEQUENCE {
       acPMCPCallAttemptsPerSecInterval                Unsigned32,
       acPMCPCallAttemptsPerSecVal                     Gauge32,
       acPMCPCallAttemptsPerSecAverage                 Integer32,
       acPMCPCallAttemptsPerSecMax                     Integer32,
       acPMCPCallAttemptsPerSecMin                     Integer32,
       acPMCPCallAttemptsPerSecVolume                  Counter32
     }



     acPMCPCallAttemptsPerSecInterval OBJECT-TYPE
       SYNTAX Unsigned32 (0..2)
       MAX-ACCESS not-accessible
       STATUS current
       DESCRIPTION
           "Interval index.
0 - current period (incomplete monitoring - mid period).
1 - Last full period.
2 - One before last."
       ::= {acPMCPCallAttemptsPerSecEntry 1}



     acPMCPCallAttemptsPerSecVal OBJECT-TYPE
       SYNTAX Gauge32
       MAX-ACCESS read-only
       STATUS current
       DESCRIPTION
           "Value of gauge or counter."
       ::= {acPMCPCallAttemptsPerSecEntry 2}



     acPMCPCallAttemptsPerSecAverage OBJECT-TYPE
       SYNTAX Integer32 (-1..2147483647)
       MAX-ACCESS read-only
       STATUS current
       DESCRIPTION
           "Average value with in the period time."
       ::= {acPMCPCallAttemptsPerSecEntry 3}



     acPMCPCallAttemptsPerSecMax OBJECT-TYPE
       SYNTAX Integer32 (-1..2147483647)
       MAX-ACCESS read-only
       STATUS current
       DESCRIPTION
           "Maximum value with in the period time."
       ::= {acPMCPCallAttemptsPerSecEntry 4}



     acPMCPCallAttemptsPerSecMin OBJECT-TYPE
       SYNTAX Integer32 (-1..2147483647)
       MAX-ACCESS read-only
       STATUS current
       DESCRIPTION
           "Minimum value with in the period time."
       ::= {acPMCPCallAttemptsPerSecEntry 5}



     acPMCPCallAttemptsPerSecVolume OBJECT-TYPE
       SYNTAX Counter32
       MAX-ACCESS read-only
       STATUS current
       DESCRIPTION
           "Activity volume."
       ::= {acPMCPCallAttemptsPerSecEntry 6}



     acPMMegaco OBJECT IDENTIFIER ::= {acPMControlData 41}


     -- ****************************************
     -- acPMMegacoServiceChangeCount table declaration
     -- ****************************************
     acPMMegacoServiceChangeCountTable OBJECT-TYPE
       SYNTAX SEQUENCE OF AcPMMegacoServiceChangeCountEntry
       MAX-ACCESS not-accessible
       STATUS current
       DESCRIPTION
           "Number of service changes, per method. Index: 0=FailOver, 1=Forced, 2=Graceful, 3=Restart, 4=Disconnected, 5=Handoff"
       ::= {acPMMegaco 1}



     -- ****************************************
     -- acPMMegacoServiceChangeCount table entry
     -- ****************************************
     acPMMegacoServiceChangeCountEntry OBJECT-TYPE
       SYNTAX AcPMMegacoServiceChangeCountEntry
       MAX-ACCESS not-accessible
       STATUS current
       DESCRIPTION
           ""
       INDEX {acPMMegacoServiceChangeCountMethod,acPMMegacoServiceChangeCountInterval}
       ::= {acPMMegacoServiceChangeCountTable 1}



     -- ****************************************
     -- acPMMegacoServiceChangeCount TABLE
     -- ****************************************
     AcPMMegacoServiceChangeCountEntry ::= SEQUENCE {
       acPMMegacoServiceChangeCountMethod              INTEGER,
       acPMMegacoServiceChangeCountInterval            Unsigned32,
       acPMMegacoServiceChangeCountVal                 Gauge32
     }



     acPMMegacoServiceChangeCountMethod OBJECT-TYPE
       SYNTAX INTEGER {
                  failOver(0)
,
                  forced(1)
,
                  graceful(2)
,
                  restart(3)
,
                  disconnected(4)
,
                  handoff(5)

                  }
       MAX-ACCESS not-accessible
       STATUS current
       DESCRIPTION
           "Method:
0=FailOver, 1=Forced, 2=Graceful, 3=Restart, 4=Disconnected,
5=Handoff."
       ::= {acPMMegacoServiceChangeCountEntry 1}



     acPMMegacoServiceChangeCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoServiceChangeCountEntry 2}



     acPMMegacoServiceChangeCountVal OBJECT-TYPE
       SYNTAX Gauge32
       MAX-ACCESS read-only
       STATUS current
       DESCRIPTION
           "Value of gauge or counter."
       ::= {acPMMegacoServiceChangeCountEntry 3}



     -- ****************************************
     -- acPMCPCmdSuccessCount table declaration
     -- ****************************************
     acPMCPCmdSuccessCountTable OBJECT-TYPE
       SYNTAX SEQUENCE OF AcPMCPCmdSuccessCountEntry
       MAX-ACCESS not-accessible
       STATUS current
       DESCRIPTION
           "Number of successful commands, per command type. Index: 0=add, 1=move, 2=modify, 3=subtract, 4=SC, 5=AuditValue, 6=AuditCapabilities, 7=Notify"
       ::= {acPMMegaco 2}



     -- ****************************************
     -- acPMCPCmdSuccessCount table entry
     -- ****************************************
     acPMCPCmdSuccessCountEntry OBJECT-TYPE
       SYNTAX AcPMCPCmdSuccessCountEntry
       MAX-ACCESS not-accessible
       STATUS current
       DESCRIPTION
           ""
       INDEX {acPMCPCmdSuccessCountCommandType,acPMCPCmdSuccessCountInterval}
       ::= {acPMCPCmdSuccessCountTable 1}



     -- ****************************************
     -- acPMCPCmdSuccessCount TABLE
     -- ****************************************
     AcPMCPCmdSuccessCountEntry ::= SEQUENCE {
       acPMCPCmdSuccessCountCommandType                INTEGER,
       acPMCPCmdSuccessCountInterval                   Unsigned32,
       acPMCPCmdSuccessCountVal                        Gauge32,
       acPMCPCmdSuccessCountTotal                      Integer32
     }



     acPMCPCmdSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:
 0=add, 1=move, 2=modify, 3=subtract, 4=SC, 5=AuditValue, 6=AuditCapabilities,
7=Notify."
       ::= {acPMCPCmdSuccessCountEntry 1}



     acPMCPCmdSuccessCountInterval OBJECT-TYPE
       SYNTAX Unsigned32 (0..2)
       MAX-ACCESS not-accessible
       STATUS current
       DESCRIPTION
           "Interval index.
0 - current period (incomplete monitoring - mid period).
1 - Last full period.
2 - One before last."
       ::= {acPMCPCmdSuccessCountEntry 2}



     acPMCPCmdSuccessCountVal OBJECT-TYPE
       SYNTAX Gauge32
       MAX-ACCESS read-only
       STATUS current
       DESCRIPTION
           "Value of gauge or counter."
       ::= {acPMCPCmdSuccessCountEntry 3}



     acPMCPCmdSuccessCountTotal OBJECT-TYPE
       SYNTAX Integer32 (-1..2147483647)
       MAX-ACCESS read-only
       STATUS current
       DESCRIPTION
           "Total since last reset."
       ::= {acPMCPCmdSuccessCountEntry 4}



     -- ****************************************
     -- acPMCPCmdFailureCount table declaration
     -- ****************************************
     acPMCPCmdFailureCountTable OBJECT-TYPE
       SYNTAX SEQUENCE OF AcPMCPCmdFailureCountEntry
       MAX-ACCESS not-accessible
       STATUS current
       DESCRIPTION
           "Number of failing commands, per command type. Index: 0=add, 1=move, 2=modify, 3=subtract, 4=SC, 5=AuditValue, 6=AuditCapabilities, 7=Notify"
       ::= {acPMMegaco 3}



     -- ****************************************
     -- acPMCPCmdFailureCount table entry
     -- ****************************************
     acPMCPCmdFailureCountEntry OBJECT-TYPE
       SYNTAX AcPMCPCmdFailureCountEntry
       MAX-ACCESS not-accessible
       STATUS current
       DESCRIPTION
           ""
       INDEX {acPMCPCmdFailureCountCommandType,acPMCPCmdFailureCountInterval}
       ::= {acPMCPCmdFailureCountTable 1}



     -- ****************************************
     -- acPMCPCmdFailureCount TABLE
     -- ****************************************
     AcPMCPCmdFailureCountEntry ::= SEQUENCE {
       acPMCPCmdFailureCountCommandType                INTEGER,
       acPMCPCmdFailureCountInterval                   Unsigned32,
       acPMCPCmdFailureCountVal                        Gauge32,
       acPMCPCmdFailureCountTotal                      Integer32
     }



     acPMCPCmdFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:
 0=add, 1=move, 2=modify, 3=subtract, 4=SC, 5=AuditValue, 6=AuditCapabilities,
7=Notify."
       ::= {acPMCPCmdFailureCountEntry 1}



     acPMCPCmdFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMCPCmdFailureCountEntry 2}



     acPMCPCmdFailureCountVal OBJECT-TYPE
       SYNTAX Gauge32
       MAX-ACCESS read-only
       STATUS current
       DESCRIPTION
           "Value of gauge or counter."
       ::= {acPMCPCmdFailureCountEntry 3}



     acPMCPCmdFailureCountTotal OBJECT-TYPE
       SYNTAX Integer32 (-1..2147483647)
       MAX-ACCESS read-only
       STATUS current
       DESCRIPTION
           "Total since last reset."
       ::= {acPMCPCmdFailureCountEntry 4}



     -- ****************************************
     -- acPMcpUMTSHandOverCount table declaration
     -- ****************************************
     acPMcpUMTSHandOverCountTable OBJECT-TYPE
       SYNTAX SEQUENCE OF AcPMcpUMTSHandOverCountEntry
       MAX-ACCESS not-accessible
       STATUS current
       DESCRIPTION
           "Number of active channels per trunk (index: trunk number)."
       ::= {acPMMegaco 4}



     -- ****************************************
     -- acPMcpUMTSHandOverCount table entry
     -- ****************************************
     acPMcpUMTSHandOverCountEntry OBJECT-TYPE
       SYNTAX AcPMcpUMTSHandOverCountEntry
       MAX-ACCESS not-accessible
       STATUS current
       DESCRIPTION
           ""
       INDEX {acPMcpUMTSHandOverCountInterval}
       ::= {acPMcpUMTSHandOverCountTable 1}



     -- ****************************************
     -- acPMcpUMTSHandOverCount TABLE
     -- ****************************************
     AcPMcpUMTSHandOverCountEntry ::= SEQUENCE {
       acPMcpUMTSHandOverCountInterval                 Unsigned32,
       acPMcpUMTSHandOverCountVal                      Gauge32
     }



     acPMcpUMTSHandOverCountInterval OBJECT-TYPE
       SYNTAX Unsigned32 (0..2)
       MAX-ACCESS not-accessible
       STATUS current
       DESCRIPTION
           "Interval index.
0 - current period (incomplete monitoring - mid period).
1 - Last full period.
2 - One before last."
       ::= {acPMcpUMTSHandOverCountEntry 1}



     acPMcpUMTSHandOverCountVal OBJECT-TYPE
       SYNTAX Gauge32
       MAX-ACCESS read-only
       STATUS current
       DESCRIPTION
           "Value of gauge or counter."
       ::= {acPMcpUMTSHandOverCountEntry 2}



     -- ****************************************
     -- acPMMegacoAddFailureCount table declaration
     -- ****************************************
     acPMMegacoAddFailureCountTable OBJECT-TYPE
       SYNTAX SEQUENCE OF AcPMMegacoAddFailureCountEntry
       MAX-ACCESS not-accessible
       STATUS current
       DESCRIPTION
           "Number of Megaco failures for Add"
       ::= {acPMMegaco 5}



     -- ****************************************
     -- acPMMegacoAddFailureCount table entry
     -- ****************************************
     acPMMegacoAddFailureCountEntry OBJECT-TYPE
       SYNTAX AcPMMegacoAddFailureCountEntry
       MAX-ACCESS not-accessible
       STATUS current
       DESCRIPTION
           ""
       INDEX {acPMMegacoAddFailureCountInterval}
       ::= {acPMMegacoAddFailureCountTable 1}



     -- ****************************************
     -- acPMMegacoAddFailureCount TABLE
     -- ****************************************
     AcPMMegacoAddFailureCountEntry ::= SEQUENCE {
       acPMMegacoAddFailureCountInterval               Unsigned32,
       acPMMegacoAddFailureCountVal                    Gauge32
     }



     acPMMegacoAddFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoAddFailureCountEntry 1}



     acPMMegacoAddFailureCountVal OBJECT-TYPE
       SYNTAX Gauge32
       MAX-ACCESS read-only
       STATUS current
       DESCRIPTION
           "Value of gauge or counter."
       ::= {acPMMegacoAddFailureCountEntry 2}



     -- ****************************************
     -- acPMMegacoModifyFailureCount table declaration
     -- ****************************************
     acPMMegacoModifyFailureCountTable OBJECT-TYPE
       SYNTAX SEQUENCE OF AcPMMegacoModifyFailureCountEntry
       MAX-ACCESS not-accessible
       STATUS current
       DESCRIPTION
           "Number of Megaco failures for Modify "
       ::= {acPMMegaco 6}



     -- ****************************************
     -- acPMMegacoModifyFailureCount table entry
     -- ****************************************
     acPMMegacoModifyFailureCountEntry OBJECT-TYPE
       SYNTAX AcPMMegacoModifyFailureCountEntry
       MAX-ACCESS not-accessible
       STATUS current
       DESCRIPTION
           ""
       INDEX {acPMMegacoModifyFailureCountInterval}
       ::= {acPMMegacoModifyFailureCountTable 1}



     -- ****************************************
     -- acPMMegacoModifyFailureCount TABLE
     -- ****************************************
     AcPMMegacoModifyFailureCountEntry ::= SEQUENCE {
       acPMMegacoModifyFailureCountInterval            Unsigned32,
       acPMMegacoModifyFailureCountVal                 Gauge32
     }



     acPMMegacoModifyFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoModifyFailureCountEntry 1}



     acPMMegacoModifyFailureCountVal OBJECT-TYPE
       SYNTAX Gauge32
       MAX-ACCESS read-only
       STATUS current
       DESCRIPTION
           "Value of gauge or counter."
       ::= {acPMMegacoModifyFailureCountEntry 2}



     -- ****************************************
     -- acPMMegacoSuccessfulAddWithLoopback table declaration
     -- ****************************************
     acPMMegacoSuccessfulAddWithLoopbackTable OBJECT-TYPE
       SYNTAX SEQUENCE OF AcPMMegacoSuccessfulAddWithLoopbackEntry
       MAX-ACCESS not-accessible
       STATUS current
       DESCRIPTION
           "Number of successful Megaco Add commands with  loopback."
       ::= {acPMMegaco 7}



     -- ****************************************
     -- acPMMegacoSuccessfulAddWithLoopback table entry
     -- ****************************************
     acPMMegacoSuccessfulAddWithLoopbackEntry OBJECT-TYPE
       SYNTAX AcPMMegacoSuccessfulAddWithLoopbackEntry
       MAX-ACCESS not-accessible
       STATUS current
       DESCRIPTION
           ""
       INDEX {acPMMegacoSuccessfulAddWithLoopbackInterval}
       ::= {acPMMegacoSuccessfulAddWithLoopbackTable 1}



     -- ****************************************
     -- acPMMegacoSuccessfulAddWithLoopback TABLE
     -- ****************************************
     AcPMMegacoSuccessfulAddWithLoopbackEntry ::= SEQUENCE {
       acPMMegacoSuccessfulAddWithLoopbackInterval     Unsigned32,
       acPMMegacoSuccessfulAddWithLoopbackVal          Gauge32
     }



     acPMMegacoSuccessfulAddWithLoopbackInterval OBJECT-TYPE
       SYNTAX Unsigned32 (0..2)
       MAX-ACCESS not-accessible
       STATUS current
       DESCRIPTION
           "Interval index.
0 - current period (incomplete monitoring - mid period).
1 - Last full period.
2 - One before last."
       ::= {acPMMegacoSuccessfulAddWithLoopbackEntry 1}



     acPMMegacoSuccessfulAddWithLoopbackVal OBJECT-TYPE
       SYNTAX Gauge32
       MAX-ACCESS read-only
       STATUS current
       DESCRIPTION
           "Value of gauge or counter."
       ::= {acPMMegacoSuccessfulAddWithLoopbackEntry 2}



     -- ****************************************
     -- acPMMegacoFailedAddWithLoopback table declaration
     -- ****************************************
     acPMMegacoFailedAddWithLoopbackTable OBJECT-TYPE
       SYNTAX SEQUENCE OF AcPMMegacoFailedAddWithLoopbackEntry
       MAX-ACCESS not-accessible
       STATUS current
       DESCRIPTION
           "Number of failed  Megaco Add commands with  loopback."
       ::= {acPMMegaco 8}



     -- ****************************************
     -- acPMMegacoFailedAddWithLoopback table entry
     -- ****************************************
     acPMMegacoFailedAddWithLoopbackEntry OBJECT-TYPE
       SYNTAX AcPMMegacoFailedAddWithLoopbackEntry
       MAX-ACCESS not-accessible
       STATUS current
       DESCRIPTION
           ""
       INDEX {acPMMegacoFailedAddWithLoopbackInterval}
       ::= {acPMMegacoFailedAddWithLoopbackTable 1}



     -- ****************************************
     -- acPMMegacoFailedAddWithLoopback TABLE
     -- ****************************************
     AcPMMegacoFailedAddWithLoopbackEntry ::= SEQUENCE {
       acPMMegacoFailedAddWithLoopbackInterval         Unsigned32,
       acPMMegacoFailedAddWithLoopbackVal              Gauge32
     }



     acPMMegacoFailedAddWithLoopbackInterval OBJECT-TYPE
       SYNTAX Unsigned32 (0..2)
       MAX-ACCESS not-accessible
       STATUS current
       DESCRIPTION
           "Interval index.
0 - current period (incomplete monitoring - mid period).
1 - Last full period.
2 - One before last."
       ::= {acPMMegacoFailedAddWithLoopbackEntry 1}



     acPMMegacoFailedAddWithLoopbackVal OBJECT-TYPE
       SYNTAX Gauge32
       MAX-ACCESS read-only
       STATUS current
       DESCRIPTION
           "Value of gauge or counter."
       ::= {acPMMegacoFailedAddWithLoopbackEntry 2}



     -- ****************************************
     -- acPMMegacoOutgoingCommandSuccessCount table declaration
     -- ****************************************
     acPMMegacoOutgoingCommandSuccessCountTable OBJECT-TYPE
       SYNTAX SEQUENCE OF AcPMMegacoOutgoingCommandSuccessCountEntry
       MAX-ACCESS not-accessible
       STATUS current
       DESCRIPTION
           "Number of successful Megaco outgoing commands."
       ::= {acPMMegaco 9}



     -- ****************************************
     -- acPMMegacoOutgoingCommandSuccessCount table entry
     -- ****************************************
     acPMMegacoOutgoingCommandSuccessCountEntry OBJECT-TYPE
       SYNTAX AcPMMegacoOutgoingCommandSuccessCountEntry
       MAX-ACCESS not-accessible
       STATUS current
       DESCRIPTION
           ""
       INDEX {acPMMegacoOutgoingCommandSuccessCountInterval}
       ::= {acPMMegacoOutgoingCommandSuccessCountTable 1}



     -- ****************************************
     -- acPMMegacoOutgoingCommandSuccessCount TABLE
     -- ****************************************
     AcPMMegacoOutgoingCommandSuccessCountEntry ::= SEQUENCE {
       acPMMegacoOutgoingCommandSuccessCountInterval   Unsigned32,
       acPMMegacoOutgoingCommandSuccessCountVal        Gauge32
     }



     acPMMegacoOutgoingCommandSuccessCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoOutgoingCommandSuccessCountEntry 1}



     acPMMegacoOutgoingCommandSuccessCountVal OBJECT-TYPE
       SYNTAX Gauge32
       MAX-ACCESS read-only
       STATUS current
       DESCRIPTION
           "Value of gauge or counter."
       ::= {acPMMegacoOutgoingCommandSuccessCountEntry 2}



     -- ****************************************
     -- acPMMegacoOutgoingCommandFailureCount table declaration
     -- ****************************************
     acPMMegacoOutgoingCommandFailureCountTable OBJECT-TYPE
       SYNTAX SEQUENCE OF AcPMMegacoOutgoingCommandFailureCountEntry
       MAX-ACCESS not-accessible
       STATUS current
       DESCRIPTION
           "Number of failed  Megaco  outgoing commands ."
       ::= {acPMMegaco 10}



     -- ****************************************
     -- acPMMegacoOutgoingCommandFailureCount table entry
     -- ****************************************
     acPMMegacoOutgoingCommandFailureCountEntry OBJECT-TYPE
       SYNTAX AcPMMegacoOutgoingCommandFailureCountEntry
       MAX-ACCESS not-accessible
       STATUS current
       DESCRIPTION
           ""
       INDEX {acPMMegacoOutgoingCommandFailureCountInterval}
       ::= {acPMMegacoOutgoingCommandFailureCountTable 1}



     -- ****************************************
     -- acPMMegacoOutgoingCommandFailureCount TABLE
     -- ****************************************
     AcPMMegacoOutgoingCommandFailureCountEntry ::= SEQUENCE {
       acPMMegacoOutgoingCommandFailureCountInterval   Unsigned32,
       acPMMegacoOutgoingCommandFailureCountVal        Gauge32
     }



     acPMMegacoOutgoingCommandFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMegacoOutgoingCommandFailureCountEntry 1}



     acPMMegacoOutgoingCommandFailureCountVal OBJECT-TYPE
       SYNTAX Gauge32
       MAX-ACCESS read-only
       STATUS current
       DESCRIPTION
           "Value of gauge or counter."
       ::= {acPMMegacoOutgoingCommandFailureCountEntry 2}



     acPMMGCP OBJECT IDENTIFIER ::= {acPMControlData 51}


     -- ****************************************
     -- acPMMGCPRsipReasonCount table declaration
     -- ****************************************
     acPMMGCPRsipReasonCountTable OBJECT-TYPE
       SYNTAX SEQUENCE OF AcPMMGCPRsipReasonCountEntry
       MAX-ACCESS not-accessible
       STATUS current
       DESCRIPTION
           "Number of RSIPs, per reason code."
       ::= {acPMMGCP 1}



     -- ****************************************
     -- acPMMGCPRsipReasonCount table entry
     -- ****************************************
     acPMMGCPRsipReasonCountEntry OBJECT-TYPE
       SYNTAX AcPMMGCPRsipReasonCountEntry
       MAX-ACCESS not-accessible
       STATUS current
       DESCRIPTION
           ""
       INDEX {acPMMGCPRsipReasonCountReasonCode,acPMMGCPRsipReasonCountInterval}
       ::= {acPMMGCPRsipReasonCountTable 1}



     -- ****************************************
     -- acPMMGCPRsipReasonCount TABLE
     -- ****************************************
     AcPMMGCPRsipReasonCountEntry ::= SEQUENCE {
       acPMMGCPRsipReasonCountReasonCode               INTEGER,
       acPMMGCPRsipReasonCountInterval                 Unsigned32,
       acPMMGCPRsipReasonCountVal                      Counter32
     }



     acPMMGCPRsipReasonCountReasonCode OBJECT-TYPE
       SYNTAX INTEGER {
                  restart(0)
,
                  forced(1)
,
                  disconnected(2)
,
                  keepAlive(3)
,
                  graceful(4)
,
                  cancelGraceful(5)
,
                  resetBoard(6)
,
                  nonVoice(7)

                  }
       MAX-ACCESS not-accessible
       STATUS current
       DESCRIPTION
           "Reason code. Index: 0=Restart, 1=Forced, 2=Disconnected, 3=KeepAlive,
4=Graceful, 5=CancelGraceful, 6=ResetBoard, 7=NonVoice."
       ::= {acPMMGCPRsipReasonCountEntry 1}



     acPMMGCPRsipReasonCountInterval OBJECT-TYPE
       SYNTAX Unsigned32 (0..2)
       MAX-ACCESS not-accessible
       STATUS current
       DESCRIPTION
           "Interval index.
0 - current period (incomplete monitoring - mid period).
1 - Last full period.
2 - One before last."
       ::= {acPMMGCPRsipReasonCountEntry 2}



     acPMMGCPRsipReasonCountVal OBJECT-TYPE
       SYNTAX Counter32
       MAX-ACCESS read-only
       STATUS current
       DESCRIPTION
           "Value of gauge or counter."
       ::= {acPMMGCPRsipReasonCountEntry 3}



     -- ****************************************
     -- acPMMGCPGeneratedDLCX table declaration
     -- ****************************************
     acPMMGCPGeneratedDLCXTable OBJECT-TYPE
       SYNTAX SEQUENCE OF AcPMMGCPGeneratedDLCXEntry
       MAX-ACCESS not-accessible
       STATUS current
       DESCRIPTION
           "This parameter counts the number of gateway-generated DLCX commands (as opposed to DLCX commands received from the call-agent)."
       ::= {acPMMGCP 2}



     -- ****************************************
     -- acPMMGCPGeneratedDLCX table entry
     -- ****************************************
     acPMMGCPGeneratedDLCXEntry OBJECT-TYPE
       SYNTAX AcPMMGCPGeneratedDLCXEntry
       MAX-ACCESS not-accessible
       STATUS current
       DESCRIPTION
           ""
       INDEX {acPMMGCPGeneratedDLCXInterval}
       ::= {acPMMGCPGeneratedDLCXTable 1}



     -- ****************************************
     -- acPMMGCPGeneratedDLCX TABLE
     -- ****************************************
     AcPMMGCPGeneratedDLCXEntry ::= SEQUENCE {
       acPMMGCPGeneratedDLCXInterval                   Unsigned32,
       acPMMGCPGeneratedDLCXVal                        Counter32
     }



     acPMMGCPGeneratedDLCXInterval OBJECT-TYPE
       SYNTAX Unsigned32 (0..2)
       MAX-ACCESS not-accessible
       STATUS current
       DESCRIPTION
           "Interval index.
0 - current period (incomplete monitoring - mid period).
1 - Last full period.
2 - One before last."
       ::= {acPMMGCPGeneratedDLCXEntry 1}



     acPMMGCPGeneratedDLCXVal OBJECT-TYPE
       SYNTAX Counter32
       MAX-ACCESS read-only
       STATUS current
       DESCRIPTION
           "Value of gauge or counter."
       ::= {acPMMGCPGeneratedDLCXEntry 2}



     -- ****************************************
     -- acPMMGCPCommandSuccessCount table declaration
     -- ****************************************
     acPMMGCPCommandSuccessCountTable OBJECT-TYPE
       SYNTAX SEQUENCE OF AcPMMGCPCommandSuccessCountEntry
       MAX-ACCESS not-accessible
       STATUS current
       DESCRIPTION
           "Number of successful commands, per command type. Index: EPCF (0),CRCX (1),MDCX (2),DLCX (3),RQNT (4),NTFY (5),AUEP(6),AUCX (7),RSIP(8)."
       ::= {acPMMGCP 3}



     -- ****************************************
     -- acPMMGCPCommandSuccessCount table entry
     -- ****************************************
     acPMMGCPCommandSuccessCountEntry OBJECT-TYPE
       SYNTAX AcPMMGCPCommandSuccessCountEntry
       MAX-ACCESS not-accessible
       STATUS current
       DESCRIPTION
           ""
       INDEX {acPMMGCPCommandSuccessCountCommandType,acPMMGCPCommandSuccessCountInterval}
       ::= {acPMMGCPCommandSuccessCountTable 1}



     -- ****************************************
     -- acPMMGCPCommandSuccessCount TABLE
     -- ****************************************
     AcPMMGCPCommandSuccessCountEntry ::= SEQUENCE {
       acPMMGCPCommandSuccessCountCommandType          INTEGER,
       acPMMGCPCommandSuccessCountInterval             Unsigned32,
       acPMMGCPCommandSuccessCountVal                  Gauge32,
       acPMMGCPCommandSuccessCountTotal                Integer32
     }



     acPMMGCPCommandSuccessCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:EPCF (0),CRCX (1),MDCX (2),DLCX (3),RQNT (4),NTFY
(5),AUEP(6),AUCX (7),RSIP(8)."
       ::= {acPMMGCPCommandSuccessCountEntry 1}



     acPMMGCPCommandSuccessCountInterval OBJECT-TYPE
       SYNTAX Unsigned32 (0..2)
       MAX-ACCESS not-accessible
       STATUS current
       DESCRIPTION
           "Interval index.
0 - current period (incomplete monitoring - mid period).
1 - Last full period.
2 - One before last."
       ::= {acPMMGCPCommandSuccessCountEntry 2}



     acPMMGCPCommandSuccessCountVal OBJECT-TYPE
       SYNTAX Gauge32
       MAX-ACCESS read-only
       STATUS current
       DESCRIPTION
           "Value of gauge or counter."
       ::= {acPMMGCPCommandSuccessCountEntry 3}



     acPMMGCPCommandSuccessCountTotal OBJECT-TYPE
       SYNTAX Integer32 (-1..2147483647)
       MAX-ACCESS read-only
       STATUS current
       DESCRIPTION
           "Total since last reset."
       ::= {acPMMGCPCommandSuccessCountEntry 4}



     -- ****************************************
     -- acPMMGCPCommandFailureCount table declaration
     -- ****************************************
     acPMMGCPCommandFailureCountTable OBJECT-TYPE
       SYNTAX SEQUENCE OF AcPMMGCPCommandFailureCountEntry
       MAX-ACCESS not-accessible
       STATUS current
       DESCRIPTION
           "Number of failing commands, per command type. Index: EPCF (0),CRCX (1),MDCX (2),DLCX (3),RQNT (4),NTFY (5),AUEP(6),AUCX (7),RSIP(8)."
       ::= {acPMMGCP 4}



     -- ****************************************
     -- acPMMGCPCommandFailureCount table entry
     -- ****************************************
     acPMMGCPCommandFailureCountEntry OBJECT-TYPE
       SYNTAX AcPMMGCPCommandFailureCountEntry
       MAX-ACCESS not-accessible
       STATUS current
       DESCRIPTION
           ""
       INDEX {acPMMGCPCommandFailureCountCommandType,acPMMGCPCommandFailureCountInterval}
       ::= {acPMMGCPCommandFailureCountTable 1}



     -- ****************************************
     -- acPMMGCPCommandFailureCount TABLE
     -- ****************************************
     AcPMMGCPCommandFailureCountEntry ::= SEQUENCE {
       acPMMGCPCommandFailureCountCommandType          INTEGER,
       acPMMGCPCommandFailureCountInterval             Unsigned32,
       acPMMGCPCommandFailureCountVal                  Gauge32,
       acPMMGCPCommandFailureCountTotal                Integer32
     }



     acPMMGCPCommandFailureCountCommandType OBJECT-TYPE
       SYNTAX INTEGER {
                  add(0)
,
                  move(1)
,
                  modify(2)
,
                  subtract(3)
,
                  sc(4)
,
                  auditValue(5)
,
                  auditCapabilities(6)
,
                  notify(7)

                  }
       MAX-ACCESS not-accessible
       STATUS current
       DESCRIPTION
           "Command type:EPCF (0),CRCX (1),MDCX (2),DLCX (3),RQNT (4),NTFY
(5),AUEP(6),AUCX (7),RSIP(8)."
       ::= {acPMMGCPCommandFailureCountEntry 1}



     acPMMGCPCommandFailureCountInterval OBJECT-TYPE
       SYNTAX Unsigned32 (0..2)
       MAX-ACCESS not-accessible
       STATUS current
       DESCRIPTION
           "Interval index.
0 - current period (incomplete monitoring - mid period).
1 - Last full period.
2 - One before last."
       ::= {acPMMGCPCommandFailureCountEntry 2}



     acPMMGCPCommandFailureCountVal OBJECT-TYPE
       SYNTAX Gauge32
       MAX-ACCESS read-only
       STATUS current
       DESCRIPTION
           "Value of gauge or counter."
       ::= {acPMMGCPCommandFailureCountEntry 3}



     acPMMGCPCommandFailureCountTotal OBJECT-TYPE
       SYNTAX Integer32 (-1..2147483647)
       MAX-ACCESS read-only
       STATUS current
       DESCRIPTION
           "Total since last reset."
       ::= {acPMMGCPCommandFailureCountEntry 4}



     -- ****************************************
     -- acPMMGCPLoopbackCRCX table declaration
     -- ****************************************
     acPMMGCPLoopbackCRCXTable OBJECT-TYPE
       SYNTAX SEQUENCE OF AcPMMGCPLoopbackCRCXEntry
       MAX-ACCESS not-accessible
       STATUS current
       DESCRIPTION
           ""
       ::= {acPMMGCP 5}



     -- ****************************************
     -- acPMMGCPLoopbackCRCX table entry
     -- ****************************************
     acPMMGCPLoopbackCRCXEntry OBJECT-TYPE
       SYNTAX AcPMMGCPLoopbackCRCXEntry
       MAX-ACCESS not-accessible
       STATUS current
       DESCRIPTION
           ""
       INDEX {acPMMGCPLoopbackCRCXInterval}
       ::= {acPMMGCPLoopbackCRCXTable 1}



     -- ****************************************
     -- acPMMGCPLoopbackCRCX TABLE
     -- ****************************************
     AcPMMGCPLoopbackCRCXEntry ::= SEQUENCE {
       acPMMGCPLoopbackCRCXInterval                    Unsigned32,
       acPMMGCPLoopbackCRCXVal                         Counter32
     }



     acPMMGCPLoopbackCRCXInterval OBJECT-TYPE
       SYNTAX Unsigned32 (0..2)
       MAX-ACCESS not-accessible
       STATUS current
       DESCRIPTION
           "Interval index.
0 - current period (incomplete monitoring - mid period).
1 - Last full period.
2 - One before last."
       ::= {acPMMGCPLoopbackCRCXEntry 1}



     acPMMGCPLoopbackCRCXVal OBJECT-TYPE
       SYNTAX Counter32
       MAX-ACCESS read-only
       STATUS current
       DESCRIPTION
           "Value of gauge or counter."
       ::= {acPMMGCPLoopbackCRCXEntry 2}



     -- ****************************************
     -- acPMMGCPFailedLoopbackCRCX table declaration
     -- ****************************************
     acPMMGCPFailedLoopbackCRCXTable OBJECT-TYPE
       SYNTAX SEQUENCE OF AcPMMGCPFailedLoopbackCRCXEntry
       MAX-ACCESS not-accessible
       STATUS current
       DESCRIPTION
           ""
       ::= {acPMMGCP 6}



     -- ****************************************
     -- acPMMGCPFailedLoopbackCRCX table entry
     -- ****************************************
     acPMMGCPFailedLoopbackCRCXEntry OBJECT-TYPE
       SYNTAX AcPMMGCPFailedLoopbackCRCXEntry
       MAX-ACCESS not-accessible
       STATUS current
       DESCRIPTION
           ""
       INDEX {acPMMGCPFailedLoopbackCRCXInterval}
       ::= {acPMMGCPFailedLoopbackCRCXTable 1}



     -- ****************************************
     -- acPMMGCPFailedLoopbackCRCX TABLE
     -- ****************************************
     AcPMMGCPFailedLoopbackCRCXEntry ::= SEQUENCE {
       acPMMGCPFailedLoopbackCRCXInterval              Unsigned32,
       acPMMGCPFailedLoopbackCRCXVal                   Counter32
     }



     acPMMGCPFailedLoopbackCRCXInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedLoopbackCRCXEntry 1}



     acPMMGCPFailedLoopbackCRCXVal OBJECT-TYPE
       SYNTAX Counter32
       MAX-ACCESS read-only
       STATUS current
       DESCRIPTION
           "Value of gauge or counter."
       ::= {acPMMGCPFailedLoopbackCRCXEntry 2}



     -- ****************************************
     -- acPMMGCPGeneratedNTFY table declaration
     -- ****************************************
     acPMMGCPGeneratedNTFYTable OBJECT-TYPE
       SYNTAX SEQUENCE OF AcPMMGCPGeneratedNTFYEntry
       MAX-ACCESS not-accessible
       STATUS current
       DESCRIPTION
           ""
       ::= {acPMMGCP 7}



     -- ****************************************
     -- acPMMGCPGeneratedNTFY table entry
     -- ****************************************
     acPMMGCPGeneratedNTFYEntry OBJECT-TYPE
       SYNTAX AcPMMGCPGeneratedNTFYEntry
       MAX-ACCESS not-accessible
       STATUS current
       DESCRIPTION
           ""
       INDEX {acPMMGCPGeneratedNTFYInterval}
       ::= {acPMMGCPGeneratedNTFYTable 1}



     -- ****************************************
     -- acPMMGCPGeneratedNTFY TABLE
     -- ****************************************
     AcPMMGCPGeneratedNTFYEntry ::= SEQUENCE {
       acPMMGCPGeneratedNTFYInterval                   Unsigned32,
       acPMMGCPGeneratedNTFYVal                        Counter32
     }



     acPMMGCPGeneratedNTFYInterval OBJECT-TYPE
       SYNTAX Unsigned32 (0..2)
       MAX-ACCESS not-accessible
       STATUS current
       DESCRIPTION
           "Interval index.
0 - current period (incomplete monitoring - mid period).
1 - Last full period.
2 - One before last."
       ::= {acPMMGCPGeneratedNTFYEntry 1}



     acPMMGCPGeneratedNTFYVal OBJECT-TYPE
       SYNTAX Counter32
       MAX-ACCESS read-only
       STATUS current
       DESCRIPTION
           "Value of gauge or counter."
       ::= {acPMMGCPGeneratedNTFYEntry 2}



     -- ****************************************
     -- acPMMGCPFailedNTFYResponses table declaration
     -- ****************************************
     acPMMGCPFailedNTFYResponsesTable OBJECT-TYPE
       SYNTAX SEQUENCE OF AcPMMGCPFailedNTFYResponsesEntry
       MAX-ACCESS not-accessible
       STATUS current
       DESCRIPTION
           ""
       ::= {acPMMGCP 8}



     -- ****************************************
     -- acPMMGCPFailedNTFYResponses table entry
     -- ****************************************
     acPMMGCPFailedNTFYResponsesEntry OBJECT-TYPE
       SYNTAX AcPMMGCPFailedNTFYResponsesEntry
       MAX-ACCESS not-accessible
       STATUS current
       DESCRIPTION
           ""
       INDEX {acPMMGCPFailedNTFYResponsesInterval}
       ::= {acPMMGCPFailedNTFYResponsesTable 1}



     -- ****************************************
     -- acPMMGCPFailedNTFYResponses TABLE
     -- ****************************************
     AcPMMGCPFailedNTFYResponsesEntry ::= SEQUENCE {
       acPMMGCPFailedNTFYResponsesInterval             Unsigned32,
       acPMMGCPFailedNTFYResponsesVal                  Counter32
     }



     acPMMGCPFailedNTFYResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedNTFYResponsesEntry 1}



     acPMMGCPFailedNTFYResponsesVal OBJECT-TYPE
       SYNTAX Counter32
       MAX-ACCESS read-only
       STATUS current
       DESCRIPTION
           "Value of gauge or counter."
       ::= {acPMMGCPFailedNTFYResponsesEntry 2}



     -- ****************************************
     -- acPMMGCPFailedRSIPResponses table declaration
     -- ****************************************
     acPMMGCPFailedRSIPResponsesTable OBJECT-TYPE
       SYNTAX SEQUENCE OF AcPMMGCPFailedRSIPResponsesEntry
       MAX-ACCESS not-accessible
       STATUS current
       DESCRIPTION
           ""
       ::= {acPMMGCP 9}



     -- ****************************************
     -- acPMMGCPFailedRSIPResponses table entry
     -- ****************************************
     acPMMGCPFailedRSIPResponsesEntry OBJECT-TYPE
       SYNTAX AcPMMGCPFailedRSIPResponsesEntry
       MAX-ACCESS not-accessible
       STATUS current
       DESCRIPTION
           ""
       INDEX {acPMMGCPFailedRSIPResponsesInterval}
       ::= {acPMMGCPFailedRSIPResponsesTable 1}



     -- ****************************************
     -- acPMMGCPFailedRSIPResponses TABLE
     -- ****************************************
     AcPMMGCPFailedRSIPResponsesEntry ::= SEQUENCE {
       acPMMGCPFailedRSIPResponsesInterval             Unsigned32,
       acPMMGCPFailedRSIPResponsesVal                  Counter32
     }



     acPMMGCPFailedRSIPResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedRSIPResponsesEntry 1}



     acPMMGCPFailedRSIPResponsesVal OBJECT-TYPE
       SYNTAX Counter32
       MAX-ACCESS read-only
       STATUS current
       DESCRIPTION
           "Value of gauge or counter."
       ::= {acPMMGCPFailedRSIPResponsesEntry 2}



     -- ****************************************
     -- acPMMGCPFailedCRCXResponses table declaration
     -- ****************************************
     acPMMGCPFailedCRCXResponsesTable OBJECT-TYPE
       SYNTAX SEQUENCE OF AcPMMGCPFailedCRCXResponsesEntry
       MAX-ACCESS not-accessible
       STATUS current
       DESCRIPTION
           "Number of failed responses to CRCX commands, per reason code."
       ::= {acPMMGCP 10}



     -- ****************************************
     -- acPMMGCPFailedCRCXResponses table entry
     -- ****************************************
     acPMMGCPFailedCRCXResponsesEntry OBJECT-TYPE
       SYNTAX AcPMMGCPFailedCRCXResponsesEntry
       MAX-ACCESS not-accessible
       STATUS current
       DESCRIPTION
           ""
       INDEX {acPMMGCPFailedCRCXResponsesReasonCode,acPMMGCPFailedCRCXResponsesInterval}
       ::= {acPMMGCPFailedCRCXResponsesTable 1}



     -- ****************************************
     -- acPMMGCPFailedCRCXResponses TABLE
     -- ****************************************
     AcPMMGCPFailedCRCXResponsesEntry ::= SEQUENCE {
       acPMMGCPFailedCRCXResponsesReasonCode           INTEGER,
       acPMMGCPFailedCRCXResponsesInterval             Unsigned32,
       acPMMGCPFailedCRCXResponsesVal                  Counter32
     }



     acPMMGCPFailedCRCXResponsesReasonCode OBJECT-TYPE
       SYNTAX INTEGER {
                  reasoncode-400(0)
,
                  reasoncode-401(1)
,
                  reasoncode-402(2)
,
                  reasoncode-403(3)
,
                  reasoncode-404(4)
,
                  reasoncode-405(5)
,
                  reasoncode-406(6)
,
                  reasoncode-407(7)
,
                  reasoncode-409(8)
,
                  reasoncode-410(9)
,
                  reasoncode-500(10)
,
                  reasoncode-501(11)
,
                  reasoncode-502(12)
,
                  reasoncode-503(13)
,
                  reasoncode-504(14)
,
                  reasoncode-505(15)
,
                  reasoncode-506(16)
,
                  reasoncode-507(17)
,
                  reasoncode-508(18)
,
                  reasoncode-509(19)
,
                  reasoncode-510(20)
,
                  reasoncode-511(21)
,
                  reasoncode-512(22)
,
                  reasoncode-513(23)
,
                  reasoncode-514(24)
,
                  reasoncode-515(25)
,
                  reasoncode-516(26)
,
                  reasoncode-517(27)
,
                  reasoncode-518(28)
,
                  reasoncode-519(29)
,
                  reasoncode-520(30)
,
                  reasoncode-521(31)
,
                  reasoncode-522(32)
,
                  reasoncode-523(33)
,
                  reasoncode-524(34)
,
                  reasoncode-525(35)
,
                  reasoncode-526(36)
,
                  reasoncode-527(37)
,
                  reasoncode-528(38)
,
                  reasoncode-529(39)
,
                  reasoncode-530(40)
,
                  reasoncode-531(41)
,
                  reasoncode-532(42)
,
                  reasoncode-533(43)
,
                  reasoncode-534(44)
,
                  reasoncode-535(45)
,
                  reasoncode-536(46)
,
                  reasoncode-537(47)
,
                  reasoncode-538(48)
,
                  reasoncode-539(49)
,
                  reasoncode-540(50)
,
                  reasoncode-541(51)

                  }
       MAX-ACCESS not-accessible
       STATUS current
       DESCRIPTION
           "Reason code Index. The Numbers at the values are as in the RFC."
       ::= {acPMMGCPFailedCRCXResponsesEntry 1}



     acPMMGCPFailedCRCXResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedCRCXResponsesEntry 2}



     acPMMGCPFailedCRCXResponsesVal OBJECT-TYPE
       SYNTAX Counter32
       MAX-ACCESS read-only
       STATUS current
       DESCRIPTION
           "Value of gauge or counter."
       ::= {acPMMGCPFailedCRCXResponsesEntry 3}



     -- ****************************************
     -- acPMMGCPFailedMDCXResponses table declaration
     -- ****************************************
     acPMMGCPFailedMDCXResponsesTable OBJECT-TYPE
       SYNTAX SEQUENCE OF AcPMMGCPFailedMDCXResponsesEntry
       MAX-ACCESS not-accessible
       STATUS current
       DESCRIPTION
           "Number of failed responses to CRCX commands, per reason code."
       ::= {acPMMGCP 11}



     -- ****************************************
     -- acPMMGCPFailedMDCXResponses table entry
     -- ****************************************
     acPMMGCPFailedMDCXResponsesEntry OBJECT-TYPE
       SYNTAX AcPMMGCPFailedMDCXResponsesEntry
       MAX-ACCESS not-accessible
       STATUS current
       DESCRIPTION
           ""
       INDEX {acPMMGCPFailedMDCXResponsesReasonCode,acPMMGCPFailedMDCXResponsesInterval}
       ::= {acPMMGCPFailedMDCXResponsesTable 1}



     -- ****************************************
     -- acPMMGCPFailedMDCXResponses TABLE
     -- ****************************************
     AcPMMGCPFailedMDCXResponsesEntry ::= SEQUENCE {
       acPMMGCPFailedMDCXResponsesReasonCode           INTEGER,
       acPMMGCPFailedMDCXResponsesInterval             Unsigned32,
       acPMMGCPFailedMDCXResponsesVal                  Counter32
     }



     acPMMGCPFailedMDCXResponsesReasonCode OBJECT-TYPE
       SYNTAX INTEGER {
                  reasoncode-400(0)
,
                  reasoncode-401(1)
,
                  reasoncode-402(2)
,
                  reasoncode-403(3)
,
                  reasoncode-404(4)
,
                  reasoncode-405(5)
,
                  reasoncode-406(6)
,
                  reasoncode-407(7)
,
                  reasoncode-409(8)
,
                  reasoncode-410(9)
,
                  reasoncode-500(10)
,
                  reasoncode-501(11)
,
                  reasoncode-502(12)
,
                  reasoncode-503(13)
,
                  reasoncode-504(14)
,
                  reasoncode-505(15)
,
                  reasoncode-506(16)
,
                  reasoncode-507(17)
,
                  reasoncode-508(18)
,
                  reasoncode-509(19)
,
                  reasoncode-510(20)
,
                  reasoncode-511(21)
,
                  reasoncode-512(22)
,
                  reasoncode-513(23)
,
                  reasoncode-514(24)
,
                  reasoncode-515(25)
,
                  reasoncode-516(26)
,
                  reasoncode-517(27)
,
                  reasoncode-518(28)
,
                  reasoncode-519(29)
,
                  reasoncode-520(30)
,
                  reasoncode-521(31)
,
                  reasoncode-522(32)
,
                  reasoncode-523(33)
,
                  reasoncode-524(34)
,
                  reasoncode-525(35)
,
                  reasoncode-526(36)
,
                  reasoncode-527(37)
,
                  reasoncode-528(38)
,
                  reasoncode-529(39)
,
                  reasoncode-530(40)
,
                  reasoncode-531(41)
,
                  reasoncode-532(42)
,
                  reasoncode-533(43)
,
                  reasoncode-534(44)
,
                  reasoncode-535(45)
,
                  reasoncode-536(46)
,
                  reasoncode-537(47)
,
                  reasoncode-538(48)
,
                  reasoncode-539(49)
,
                  reasoncode-540(50)
,
                  reasoncode-541(51)

                  }
       MAX-ACCESS not-accessible
       STATUS current
       DESCRIPTION
           "Reason code Index. The Numbers at the values are as in the RFC."
       ::= {acPMMGCPFailedMDCXResponsesEntry 1}



     acPMMGCPFailedMDCXResponsesInterval OBJECT-TYPE
       SYNTAX Unsigned32 (0..2)
       MAX-ACCESS not-accessible
       STATUS current
       DESCRIPTION
           "Interval index.
0 - current period (incomplete monitoring - mid period).
1 - Last full period.
2 - One before last."
       ::= {acPMMGCPFailedMDCXResponsesEntry 2}



     acPMMGCPFailedMDCXResponsesVal OBJECT-TYPE
       SYNTAX Counter32
       MAX-ACCESS read-only
       STATUS current
       DESCRIPTION
           "Value of gauge or counter."
       ::= {acPMMGCPFailedMDCXResponsesEntry 3}



     -- ****************************************
     -- acPMMGCPGeneratedDLCXPerReasonCode table declaration
     -- ****************************************
     acPMMGCPGeneratedDLCXPerReasonCodeTable OBJECT-TYPE
       SYNTAX SEQUENCE OF AcPMMGCPGeneratedDLCXPerReasonCodeEntry
       MAX-ACCESS not-accessible
       STATUS current
       DESCRIPTION
           "Number of gateway-generated DLCX commands per reason code. when you choose 0 its 900(ENDPOINT_MALFUNCTIONING) and so on."
       ::= {acPMMGCP 12}



     -- ****************************************
     -- acPMMGCPGeneratedDLCXPerReasonCode table entry
     -- ****************************************
     acPMMGCPGeneratedDLCXPerReasonCodeEntry OBJECT-TYPE
       SYNTAX AcPMMGCPGeneratedDLCXPerReasonCodeEntry
       MAX-ACCESS not-accessible
       STATUS current
       DESCRIPTION
           ""
       INDEX {acPMMGCPGeneratedDLCXPerReasonCodeReasonCode,acPMMGCPGeneratedDLCXPerReasonCodeInterval}
       ::= {acPMMGCPGeneratedDLCXPerReasonCodeTable 1}



     -- ****************************************
     -- acPMMGCPGeneratedDLCXPerReasonCode TABLE
     -- ****************************************
     AcPMMGCPGeneratedDLCXPerReasonCodeEntry ::= SEQUENCE {
       acPMMGCPGeneratedDLCXPerReasonCodeReasonCode    INTEGER,
       acPMMGCPGeneratedDLCXPerReasonCodeInterval      Unsigned32,
       acPMMGCPGeneratedDLCXPerReasonCodeVal           Counter32
     }



     acPMMGCPGeneratedDLCXPerReasonCodeReasonCode OBJECT-TYPE
       SYNTAX INTEGER {
                  eNDPOINT-MALFUNCTIONING-900(0)
,
                  eNDPOINT-TAKEN-OUT-OF-SERVICE-901(1)
,
                  lOSS-OF-LOWER-LAYER-CONNECTIVITY-902(2)
,
                  qOS-RESOURCE-RESERVATION-WAS-LOST-903(3)
,
                  mANUAL-INTERVENTION-904(4)
,
                  fACILITY-FAILURE-905(5)

                  }
       MAX-ACCESS not-accessible
       STATUS current
       DESCRIPTION
           "Reason code Index. The Numbers at the values are as in the RFC."
       ::= {acPMMGCPGeneratedDLCXPerReasonCodeEntry 1}



     acPMMGCPGeneratedDLCXPerReasonCodeInterval OBJECT-TYPE
       SYNTAX Unsigned32 (0..2)
       MAX-ACCESS not-accessible
       STATUS current
       DESCRIPTION
           "Interval index.
0 - current period (incomplete monitoring - mid period).
1 - Last full period.
2 - One before last."
       ::= {acPMMGCPGeneratedDLCXPerReasonCodeEntry 2}



     acPMMGCPGeneratedDLCXPerReasonCodeVal OBJECT-TYPE
       SYNTAX Counter32
       MAX-ACCESS read-only
       STATUS current
       DESCRIPTION
           "Value of gauge or counter."
       ::= {acPMMGCPGeneratedDLCXPerReasonCodeEntry 3}



     acPMSIP OBJECT IDENTIFIER ::= {acPMControlData 52}


     -- ****************************************
     -- acPMSIPAttemptedCalls table declaration
     -- ****************************************
     acPMSIPAttemptedCallsTable OBJECT-TYPE
       SYNTAX SEQUENCE OF AcPMSIPAttemptedCallsEntry
       MAX-ACCESS not-accessible
       STATUS current
       DESCRIPTION
           "Number of attempted calls (Index 0 for TEL2IP and Index 1 for IP2TEL)"
       ::= {acPMSIP 1}



     -- ****************************************
     -- acPMSIPAttemptedCalls table entry
     -- ****************************************
     acPMSIPAttemptedCallsEntry OBJECT-TYPE
       SYNTAX AcPMSIPAttemptedCallsEntry
       MAX-ACCESS not-accessible
       STATUS current
       DESCRIPTION
           ""
       INDEX {acPMSIPAttemptedCallsDirection,acPMSIPAttemptedCallsInterval}
       ::= {acPMSIPAttemptedCallsTable 1}



     -- ****************************************
     -- acPMSIPAttemptedCalls TABLE
     -- ****************************************
     AcPMSIPAttemptedCallsEntry ::= SEQUENCE {
       acPMSIPAttemptedCallsDirection                  INTEGER,
       acPMSIPAttemptedCallsInterval                   Unsigned32,
       acPMSIPAttemptedCallsVal                        Counter32
     }



     acPMSIPAttemptedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPAttemptedCallsEntry 1}



     acPMSIPAttemptedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPAttemptedCallsEntry 2}



     acPMSIPAttemptedCallsVal OBJECT-TYPE
       SYNTAX Counter32
       MAX-ACCESS read-only
       STATUS current
       DESCRIPTION
           "Value of gauge or counter."
       ::= {acPMSIPAttemptedCallsEntry 3}



     -- ****************************************
     -- acPMSIPCallDuration table declaration
     -- ****************************************
     acPMSIPCallDurationTable OBJECT-TYPE
       SYNTAX SEQUENCE OF AcPMSIPCallDurationEntry
       MAX-ACCESS not-accessible
       STATUS current
       DESCRIPTION
           "Call Duration (Index 0 for Tel2IP and Index 1 for IP2Tel);The Total preprty gives the sum of all calls duration, while the Value property is for the last call only"
       ::= {acPMSIP 2}



     -- ****************************************
     -- acPMSIPCallDuration table entry
     -- ****************************************
     acPMSIPCallDurationEntry OBJECT-TYPE
       SYNTAX AcPMSIPCallDurationEntry
       MAX-ACCESS not-accessible
       STATUS current
       DESCRIPTION
           ""
       INDEX {acPMSIPCallDurationDirection,acPMSIPCallDurationInterval}
       ::= {acPMSIPCallDurationTable 1}



     -- ****************************************
     -- acPMSIPCallDuration TABLE
     -- ****************************************
     AcPMSIPCallDurationEntry ::= SEQUENCE {
       acPMSIPCallDurationDirection                    INTEGER,
       acPMSIPCallDurationInterval                     Unsigned32,
       acPMSIPCallDurationVal                          Gauge32,
       acPMSIPCallDurationAverage                      Integer32,
       acPMSIPCallDurationMax                          Integer32,
       acPMSIPCallDurationMin                          Integer32,
       acPMSIPCallDurationVolume                       Counter32,
       acPMSIPCallDurationTimeBelowLowThreshold        Integer32,
       acPMSIPCallDurationTimeBetweenThresholds        Integer32,
       acPMSIPCallDurationTimeAboveHighThreshold       Integer32,
       acPMSIPCallDurationFullDayAverage               Integer32,
       acPMSIPCallDurationTotal                        Integer32
     }



     acPMSIPCallDurationDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPCallDurationEntry 1}



     acPMSIPCallDurationInterval OBJECT-TYPE
       SYNTAX Unsigned32 (0..2)
       MAX-ACCESS not-accessible
       STATUS current
       DESCRIPTION
           "Interval index.
0 - current period (incomplete monitoring - mid period).
1 - Last full period.
2 - One before last."
       ::= {acPMSIPCallDurationEntry 2}



     acPMSIPCallDurationVal OBJECT-TYPE
       SYNTAX Gauge32
       MAX-ACCESS read-only
       STATUS current
       DESCRIPTION
           "Value of gauge or counter."
       ::= {acPMSIPCallDurationEntry 3}



     acPMSIPCallDurationAverage OBJECT-TYPE
       SYNTAX Integer32 (-1..2147483647)
       MAX-ACCESS read-only
       STATUS current
       DESCRIPTION
           "Average value with in the period time."
       ::= {acPMSIPCallDurationEntry 4}



     acPMSIPCallDurationMax OBJECT-TYPE
       SYNTAX Integer32 (-1..2147483647)
       MAX-ACCESS read-only
       STATUS current
       DESCRIPTION
           "Maximum value with in the period time."
       ::= {acPMSIPCallDurationEntry 5}



     acPMSIPCallDurationMin OBJECT-TYPE
       SYNTAX Integer32 (-1..2147483647)
       MAX-ACCESS read-only
       STATUS current
       DESCRIPTION
           "Minimum value with in the period time."
       ::= {acPMSIPCallDurationEntry 6}



     acPMSIPCallDurationVolume OBJECT-TYPE
       SYNTAX Counter32
       MAX-ACCESS read-only
       STATUS current
       DESCRIPTION
           "Activity volume."
       ::= {acPMSIPCallDurationEntry 7}



     acPMSIPCallDurationTimeBelowLowThreshold OBJECT-TYPE
       SYNTAX Integer32 (-1..100)
       MAX-ACCESS read-only
       STATUS current
       DESCRIPTION
           "Percent of interval time for which gauge is below what was determined
as the low threshold."
       ::= {acPMSIPCallDurationEntry 8}



     acPMSIPCallDurationTimeBetweenThresholds OBJECT-TYPE
       SYNTAX Integer32 (-1..100)
       MAX-ACCESS read-only
       STATUS current
       DESCRIPTION
           "Percent of interval time for which gauge is above what was determined
as the high threshold."
       ::= {acPMSIPCallDurationEntry 9}



     acPMSIPCallDurationTimeAboveHighThreshold OBJECT-TYPE
       SYNTAX Integer32 (-1..100)
       MAX-ACCESS read-only
       STATUS current
       DESCRIPTION
           "Percent of interval time for which gauge is between what were
determined as the low and high thresholds."
       ::= {acPMSIPCallDurationEntry 10}



     acPMSIPCallDurationFullDayAverage OBJECT-TYPE
       SYNTAX Integer32 (-1..2147483647)
       MAX-ACCESS read-only
       STATUS current
       DESCRIPTION
           "The average of full 24 hours."
       ::= {acPMSIPCallDurationEntry 11}



     acPMSIPCallDurationTotal OBJECT-TYPE
       SYNTAX Integer32 (-1..2147483647)
       MAX-ACCESS read-only
       STATUS current
       DESCRIPTION
           "Total since last reset."
       ::= {acPMSIPCallDurationEntry 12}



     -- ****************************************
     -- acPMSIPNoMatchCalls table declaration
     -- ****************************************
     acPMSIPNoMatchCallsTable OBJECT-TYPE
       SYNTAX SEQUENCE OF AcPMSIPNoMatchCallsEntry
       MAX-ACCESS not-accessible
       STATUS current
       DESCRIPTION
           "Number of no match calls (Index 0 for TEL2IP and Index 1 for IP2TEL)"
       ::= {acPMSIP 3}



     -- ****************************************
     -- acPMSIPNoMatchCalls table entry
     -- ****************************************
     acPMSIPNoMatchCallsEntry OBJECT-TYPE
       SYNTAX AcPMSIPNoMatchCallsEntry
       MAX-ACCESS not-accessible
       STATUS current
       DESCRIPTION
           ""
       INDEX {acPMSIPNoMatchCallsDirection,acPMSIPNoMatchCallsInterval}
       ::= {acPMSIPNoMatchCallsTable 1}



     -- ****************************************
     -- acPMSIPNoMatchCalls TABLE
     -- ****************************************
     AcPMSIPNoMatchCallsEntry ::= SEQUENCE {
       acPMSIPNoMatchCallsDirection                    INTEGER,
       acPMSIPNoMatchCallsInterval                     Unsigned32,
       acPMSIPNoMatchCallsVal                          Counter32
     }



     acPMSIPNoMatchCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoMatchCallsEntry 1}



     acPMSIPNoMatchCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoMatchCallsEntry 2}



     acPMSIPNoMatchCallsVal OBJECT-TYPE
       SYNTAX Counter32
       MAX-ACCESS read-only
       STATUS current
       DESCRIPTION
           "Value of gauge or counter."
       ::= {acPMSIPNoMatchCallsEntry 3}



     -- ****************************************
     -- acPMSIPBusyCalls table declaration
     -- ****************************************
     acPMSIPBusyCallsTable OBJECT-TYPE
       SYNTAX SEQUENCE OF AcPMSIPBusyCallsEntry
       MAX-ACCESS not-accessible
       STATUS current
       DESCRIPTION
           "Number of busy calls (Index 0 for TEL2IP and Index 1 for IP2TEL)"
       ::= {acPMSIP 4}



     -- ****************************************
     -- acPMSIPBusyCalls table entry
     -- ****************************************
     acPMSIPBusyCallsEntry OBJECT-TYPE
       SYNTAX AcPMSIPBusyCallsEntry
       MAX-ACCESS not-accessible
       STATUS current
       DESCRIPTION
           ""
       INDEX {acPMSIPBusyCallsDirection,acPMSIPBusyCallsInterval}
       ::= {acPMSIPBusyCallsTable 1}



     -- ****************************************
     -- acPMSIPBusyCalls TABLE
     -- ****************************************
     AcPMSIPBusyCallsEntry ::= SEQUENCE {
       acPMSIPBusyCallsDirection                       INTEGER,
       acPMSIPBusyCallsInterval                        Unsigned32,
       acPMSIPBusyCallsVal                             Counter32
     }



     acPMSIPBusyCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPBusyCallsEntry 1}



     acPMSIPBusyCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPBusyCallsEntry 2}



     acPMSIPBusyCallsVal OBJECT-TYPE
       SYNTAX Counter32
       MAX-ACCESS read-only
       STATUS current
       DESCRIPTION
           "Value of gauge or counter."
       ::= {acPMSIPBusyCallsEntry 3}



     -- ****************************************
     -- acPMSIPNoAnswerCalls table declaration
     -- ****************************************
     acPMSIPNoAnswerCallsTable OBJECT-TYPE
       SYNTAX SEQUENCE OF AcPMSIPNoAnswerCallsEntry
       MAX-ACCESS not-accessible
       STATUS current
       DESCRIPTION
           "Number of no answer calls (Index 0 for TEL2IP and Index 1 for IP2TEL)"
       ::= {acPMSIP 5}



     -- ****************************************
     -- acPMSIPNoAnswerCalls table entry
     -- ****************************************
     acPMSIPNoAnswerCallsEntry OBJECT-TYPE
       SYNTAX AcPMSIPNoAnswerCallsEntry
       MAX-ACCESS not-accessible
       STATUS current
       DESCRIPTION
           ""
       INDEX {acPMSIPNoAnswerCallsDirection,acPMSIPNoAnswerCallsInterval}
       ::= {acPMSIPNoAnswerCallsTable 1}



     -- ****************************************
     -- acPMSIPNoAnswerCalls TABLE
     -- ****************************************
     AcPMSIPNoAnswerCallsEntry ::= SEQUENCE {
       acPMSIPNoAnswerCallsDirection                   INTEGER,
       acPMSIPNoAnswerCallsInterval                    Unsigned32,
       acPMSIPNoAnswerCallsVal                         Counter32
     }



     acPMSIPNoAnswerCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoAnswerCallsEntry 1}



     acPMSIPNoAnswerCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoAnswerCallsEntry 2}



     acPMSIPNoAnswerCallsVal OBJECT-TYPE
       SYNTAX Counter32
       MAX-ACCESS read-only
       STATUS current
       DESCRIPTION
           "Value of gauge or counter."
       ::= {acPMSIPNoAnswerCallsEntry 3}



     -- ****************************************
     -- acPMSIPNoRouteCalls table declaration
     -- ****************************************
     acPMSIPNoRouteCallsTable OBJECT-TYPE
       SYNTAX SEQUENCE OF AcPMSIPNoRouteCallsEntry
       MAX-ACCESS not-accessible
       STATUS current
       DESCRIPTION
           "Number of no route calls (Index 0 for TEL2IP and Index 1 for IP2TEL)"
       ::= {acPMSIP 6}



     -- ****************************************
     -- acPMSIPNoRouteCalls table entry
     -- ****************************************
     acPMSIPNoRouteCallsEntry OBJECT-TYPE
       SYNTAX AcPMSIPNoRouteCallsEntry
       MAX-ACCESS not-accessible
       STATUS current
       DESCRIPTION
           ""
       INDEX {acPMSIPNoRouteCallsDirection,acPMSIPNoRouteCallsInterval}
       ::= {acPMSIPNoRouteCallsTable 1}



     -- ****************************************
     -- acPMSIPNoRouteCalls TABLE
     -- ****************************************
     AcPMSIPNoRouteCallsEntry ::= SEQUENCE {
       acPMSIPNoRouteCallsDirection                    INTEGER,
       acPMSIPNoRouteCallsInterval                     Unsigned32,
       acPMSIPNoRouteCallsVal                          Counter32
     }



     acPMSIPNoRouteCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoRouteCallsEntry 1}



     acPMSIPNoRouteCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoRouteCallsEntry 2}



     acPMSIPNoRouteCallsVal OBJECT-TYPE
       SYNTAX Counter32
       MAX-ACCESS read-only
       STATUS current
       DESCRIPTION
           "Value of gauge or counter."
       ::= {acPMSIPNoRouteCallsEntry 3}



     -- ****************************************
     -- acPMSIPFailCalls table declaration
     -- ****************************************
     acPMSIPFailCallsTable OBJECT-TYPE
       SYNTAX SEQUENCE OF AcPMSIPFailCallsEntry
       MAX-ACCESS not-accessible
       STATUS current
       DESCRIPTION
           "Number of calls that failed because of other reasons (Index 0 for TEL2IP and Index 1 for IP2TEL)"
       ::= {acPMSIP 7}



     -- ****************************************
     -- acPMSIPFailCalls table entry
     -- ****************************************
     acPMSIPFailCallsEntry OBJECT-TYPE
       SYNTAX AcPMSIPFailCallsEntry
       MAX-ACCESS not-accessible
       STATUS current
       DESCRIPTION
           ""
       INDEX {acPMSIPFailCallsDirection,acPMSIPFailCallsInterval}
       ::= {acPMSIPFailCallsTable 1}



     -- ****************************************
     -- acPMSIPFailCalls TABLE
     -- ****************************************
     AcPMSIPFailCallsEntry ::= SEQUENCE {
       acPMSIPFailCallsDirection                       INTEGER,
       acPMSIPFailCallsInterval                        Unsigned32,
       acPMSIPFailCallsVal                             Counter32
     }



     acPMSIPFailCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPFailCallsEntry 1}



     acPMSIPFailCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPFailCallsEntry 2}



     acPMSIPFailCallsVal OBJECT-TYPE
       SYNTAX Counter32
       MAX-ACCESS read-only
       STATUS current
       DESCRIPTION
           "Value of gauge or counter."
       ::= {acPMSIPFailCallsEntry 3}



     -- ****************************************
     -- acPMSIPEstablishedCalls table declaration
     -- ****************************************
     acPMSIPEstablishedCallsTable OBJECT-TYPE
       SYNTAX SEQUENCE OF AcPMSIPEstablishedCallsEntry
       MAX-ACCESS not-accessible
       STATUS current
       DESCRIPTION
           "Number of established calls (Index 0 for TEL2IP and Index 1 for IP2TEL)"
       ::= {acPMSIP 8}



     -- ****************************************
     -- acPMSIPEstablishedCalls table entry
     -- ****************************************
     acPMSIPEstablishedCallsEntry OBJECT-TYPE
       SYNTAX AcPMSIPEstablishedCallsEntry
       MAX-ACCESS not-accessible
       STATUS current
       DESCRIPTION
           ""
       INDEX {acPMSIPEstablishedCallsDirection,acPMSIPEstablishedCallsInterval}
       ::= {acPMSIPEstablishedCallsTable 1}



     -- ****************************************
     -- acPMSIPEstablishedCalls TABLE
     -- ****************************************
     AcPMSIPEstablishedCallsEntry ::= SEQUENCE {
       acPMSIPEstablishedCallsDirection                INTEGER,
       acPMSIPEstablishedCallsInterval                 Unsigned32,
       acPMSIPEstablishedCallsVal                      Counter32
     }



     acPMSIPEstablishedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPEstablishedCallsEntry 1}



     acPMSIPEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPEstablishedCallsEntry 2}



     acPMSIPEstablishedCallsVal OBJECT-TYPE
       SYNTAX Counter32
       MAX-ACCESS read-only
       STATUS current
       DESCRIPTION
           "Value of gauge or counter."
       ::= {acPMSIPEstablishedCallsEntry 3}



     -- ****************************************
     -- acPMSIPFaxAttemptedCalls table declaration
     -- ****************************************
     acPMSIPFaxAttemptedCallsTable OBJECT-TYPE
       SYNTAX SEQUENCE OF AcPMSIPFaxAttemptedCallsEntry
       MAX-ACCESS not-accessible
       STATUS current
       DESCRIPTION
           "Number of attempted fax calls (Index 0 for TEL2IP and Index 1 for IP2TEL)"
       ::= {acPMSIP 9}



     -- ****************************************
     -- acPMSIPFaxAttemptedCalls table entry
     -- ****************************************
     acPMSIPFaxAttemptedCallsEntry OBJECT-TYPE
       SYNTAX AcPMSIPFaxAttemptedCallsEntry
       MAX-ACCESS not-accessible
       STATUS current
       DESCRIPTION
           ""
       INDEX {acPMSIPFaxAttemptedCallsDirection,acPMSIPFaxAttemptedCallsInterval}
       ::= {acPMSIPFaxAttemptedCallsTable 1}



     -- ****************************************
     -- acPMSIPFaxAttemptedCalls TABLE
     -- ****************************************
     AcPMSIPFaxAttemptedCallsEntry ::= SEQUENCE {
       acPMSIPFaxAttemptedCallsDirection               INTEGER,
       acPMSIPFaxAttemptedCallsInterval                Unsigned32,
       acPMSIPFaxAttemptedCallsVal                     Counter32
     }



     acPMSIPFaxAttemptedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPFaxAttemptedCallsEntry 1}



     acPMSIPFaxAttemptedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPFaxAttemptedCallsEntry 2}



     acPMSIPFaxAttemptedCallsVal OBJECT-TYPE
       SYNTAX Counter32
       MAX-ACCESS read-only
       STATUS current
       DESCRIPTION
           "Value of gauge or counter."
       ::= {acPMSIPFaxAttemptedCallsEntry 3}



     -- ****************************************
     -- acPMSIPFaxSuccessCalls table declaration
     -- ****************************************
     acPMSIPFaxSuccessCallsTable OBJECT-TYPE
       SYNTAX SEQUENCE OF AcPMSIPFaxSuccessCallsEntry
       MAX-ACCESS not-accessible
       STATUS current
       DESCRIPTION
           "Number of success fax calls (Index 0 for TEL2IP and Index 1 for IP2TEL)"
       ::= {acPMSIP 10}



     -- ****************************************
     -- acPMSIPFaxSuccessCalls table entry
     -- ****************************************
     acPMSIPFaxSuccessCallsEntry OBJECT-TYPE
       SYNTAX AcPMSIPFaxSuccessCallsEntry
       MAX-ACCESS not-accessible
       STATUS current
       DESCRIPTION
           ""
       INDEX {acPMSIPFaxSuccessCallsDirection,acPMSIPFaxSuccessCallsInterval}
       ::= {acPMSIPFaxSuccessCallsTable 1}



     -- ****************************************
     -- acPMSIPFaxSuccessCalls TABLE
     -- ****************************************
     AcPMSIPFaxSuccessCallsEntry ::= SEQUENCE {
       acPMSIPFaxSuccessCallsDirection                 INTEGER,
       acPMSIPFaxSuccessCallsInterval                  Unsigned32,
       acPMSIPFaxSuccessCallsVal                       Counter32
     }



     acPMSIPFaxSuccessCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPFaxSuccessCallsEntry 1}



     acPMSIPFaxSuccessCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPFaxSuccessCallsEntry 2}



     acPMSIPFaxSuccessCallsVal OBJECT-TYPE
       SYNTAX Counter32
       MAX-ACCESS read-only
       STATUS current
       DESCRIPTION
           "Value of gauge or counter."
       ::= {acPMSIPFaxSuccessCallsEntry 3}



     -- ****************************************
     -- acPMSIPForwardedCalls table declaration
     -- ****************************************
     acPMSIPForwardedCallsTable OBJECT-TYPE
       SYNTAX SEQUENCE OF AcPMSIPForwardedCallsEntry
       MAX-ACCESS not-accessible
       STATUS current
       DESCRIPTION
           "Number of calls released due to forwarding (Index 0 for TEL2IP and Index 1 for IP2TEL)"
       ::= {acPMSIP 11}



     -- ****************************************
     -- acPMSIPForwardedCalls table entry
     -- ****************************************
     acPMSIPForwardedCallsEntry OBJECT-TYPE
       SYNTAX AcPMSIPForwardedCallsEntry
       MAX-ACCESS not-accessible
       STATUS current
       DESCRIPTION
           ""
       INDEX {acPMSIPForwardedCallsDirection,acPMSIPForwardedCallsInterval}
       ::= {acPMSIPForwardedCallsTable 1}



     -- ****************************************
     -- acPMSIPForwardedCalls TABLE
     -- ****************************************
     AcPMSIPForwardedCallsEntry ::= SEQUENCE {
       acPMSIPForwardedCallsDirection                  INTEGER,
       acPMSIPForwardedCallsInterval                   Unsigned32,
       acPMSIPForwardedCallsVal                        Counter32
     }



     acPMSIPForwardedCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPForwardedCallsEntry 1}



     acPMSIPForwardedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPForwardedCallsEntry 2}



     acPMSIPForwardedCallsVal OBJECT-TYPE
       SYNTAX Counter32
       MAX-ACCESS read-only
       STATUS current
       DESCRIPTION
           "Value of gauge or counter."
       ::= {acPMSIPForwardedCallsEntry 3}



     -- ****************************************
     -- acPMSIPNoResourcesCalls table declaration
     -- ****************************************
     acPMSIPNoResourcesCallsTable OBJECT-TYPE
       SYNTAX SEQUENCE OF AcPMSIPNoResourcesCallsEntry
       MAX-ACCESS not-accessible
       STATUS current
       DESCRIPTION
           "Number of calls released because of no resources (Index 0 for TEL2IP and Index 1 for IP2TEL)"
       ::= {acPMSIP 12}



     -- ****************************************
     -- acPMSIPNoResourcesCalls table entry
     -- ****************************************
     acPMSIPNoResourcesCallsEntry OBJECT-TYPE
       SYNTAX AcPMSIPNoResourcesCallsEntry
       MAX-ACCESS not-accessible
       STATUS current
       DESCRIPTION
           ""
       INDEX {acPMSIPNoResourcesCallsDirection,acPMSIPNoResourcesCallsInterval}
       ::= {acPMSIPNoResourcesCallsTable 1}



     -- ****************************************
     -- acPMSIPNoResourcesCalls TABLE
     -- ****************************************
     AcPMSIPNoResourcesCallsEntry ::= SEQUENCE {
       acPMSIPNoResourcesCallsDirection                INTEGER,
       acPMSIPNoResourcesCallsInterval                 Unsigned32,
       acPMSIPNoResourcesCallsVal                      Counter32
     }



     acPMSIPNoResourcesCallsDirection OBJECT-TYPE
       SYNTAX INTEGER {
                  tel2IP(0)
,
                  iP2Tel(1)

                  }
       MAX-ACCESS not-accessible
       STATUS current
       DESCRIPTION
           "Direction index - TEL2IP(0), IP2TEL(1)."
       ::= {acPMSIPNoResourcesCallsEntry 1}



     acPMSIPNoResourcesCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPNoResourcesCallsEntry 2}



     acPMSIPNoResourcesCallsVal OBJECT-TYPE
       SYNTAX Counter32
       MAX-ACCESS read-only
       STATUS current
       DESCRIPTION
           "Value of gauge or counter."
       ::= {acPMSIPNoResourcesCallsEntry 3}



     -- ****************************************
     -- acPMSIPTel2IPTrunkEstablishedCalls table declaration
     -- ****************************************
     acPMSIPTel2IPTrunkEstablishedCallsTable OBJECT-TYPE
       SYNTAX SEQUENCE OF AcPMSIPTel2IPTrunkEstablishedCallsEntry
       MAX-ACCESS not-accessible
       STATUS current
       DESCRIPTION
           "Number of Tel2IP established calls per trunk."
       ::= {acPMSIP 13}



     -- ****************************************
     -- acPMSIPTel2IPTrunkEstablishedCalls table entry
     -- ****************************************
     acPMSIPTel2IPTrunkEstablishedCallsEntry OBJECT-TYPE
       SYNTAX AcPMSIPTel2IPTrunkEstablishedCallsEntry
       MAX-ACCESS not-accessible
       STATUS current
       DESCRIPTION
           ""
       INDEX {acPMSIPTel2IPTrunkEstablishedCallsTrunkNum,acPMSIPTel2IPTrunkEstablishedCallsInterval}
       ::= {acPMSIPTel2IPTrunkEstablishedCallsTable 1}



     -- ****************************************
     -- acPMSIPTel2IPTrunkEstablishedCalls TABLE
     -- ****************************************
     AcPMSIPTel2IPTrunkEstablishedCallsEntry ::= SEQUENCE {
       acPMSIPTel2IPTrunkEstablishedCallsTrunkNum      Unsigned32,
       acPMSIPTel2IPTrunkEstablishedCallsInterval      Unsigned32,
       acPMSIPTel2IPTrunkEstablishedCallsVal           Counter32
     }



     acPMSIPTel2IPTrunkEstablishedCallsTrunkNum OBJECT-TYPE
       SYNTAX Unsigned32 (0..83)
       MAX-ACCESS not-accessible
       STATUS current
       DESCRIPTION
           "Trunk number.
0 is the first trunk."
       ::= {acPMSIPTel2IPTrunkEstablishedCallsEntry 1}



     acPMSIPTel2IPTrunkEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPTel2IPTrunkEstablishedCallsEntry 2}



     acPMSIPTel2IPTrunkEstablishedCallsVal OBJECT-TYPE
       SYNTAX Counter32
       MAX-ACCESS read-only
       STATUS current
       DESCRIPTION
           "Value of gauge or counter."
       ::= {acPMSIPTel2IPTrunkEstablishedCallsEntry 3}



     -- ****************************************
     -- acPMSIPIP2TelTrunkEstablishedCalls table declaration
     -- ****************************************
     acPMSIPIP2TelTrunkEstablishedCallsTable OBJECT-TYPE
       SYNTAX SEQUENCE OF AcPMSIPIP2TelTrunkEstablishedCallsEntry
       MAX-ACCESS not-accessible
       STATUS current
       DESCRIPTION
           "Number of IP2Tel established calls per trunk."
       ::= {acPMSIP 14}



     -- ****************************************
     -- acPMSIPIP2TelTrunkEstablishedCalls table entry
     -- ****************************************
     acPMSIPIP2TelTrunkEstablishedCallsEntry OBJECT-TYPE
       SYNTAX AcPMSIPIP2TelTrunkEstablishedCallsEntry
       MAX-ACCESS not-accessible
       STATUS current
       DESCRIPTION
           ""
       INDEX {acPMSIPIP2TelTrunkEstablishedCallsTrunkNum,acPMSIPIP2TelTrunkEstablishedCallsInterval}
       ::= {acPMSIPIP2TelTrunkEstablishedCallsTable 1}



     -- ****************************************
     -- acPMSIPIP2TelTrunkEstablishedCalls TABLE
     -- ****************************************
     AcPMSIPIP2TelTrunkEstablishedCallsEntry ::= SEQUENCE {
       acPMSIPIP2TelTrunkEstablishedCallsTrunkNum      Unsigned32,
       acPMSIPIP2TelTrunkEstablishedCallsInterval      Unsigned32,
       acPMSIPIP2TelTrunkEstablishedCallsVal           Counter32
     }



     acPMSIPIP2TelTrunkEstablishedCallsTrunkNum OBJECT-TYPE
       SYNTAX Unsigned32 (0..83)
       MAX-ACCESS not-accessible
       STATUS current
       DESCRIPTION
           "Trunk number.
0 is the first trunk."
       ::= {acPMSIPIP2TelTrunkEstablishedCallsEntry 1}



     acPMSIPIP2TelTrunkEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIP2TelTrunkEstablishedCallsEntry 2}



     acPMSIPIP2TelTrunkEstablishedCallsVal OBJECT-TYPE
       SYNTAX Counter32
       MAX-ACCESS read-only
       STATUS current
       DESCRIPTION
           "Value of gauge or counter."
       ::= {acPMSIPIP2TelTrunkEstablishedCallsEntry 3}



     -- ****************************************
     -- acPMSIPTel2IPTrunkGroupEstablishedCalls table declaration
     -- ****************************************
     acPMSIPTel2IPTrunkGroupEstablishedCallsTable OBJECT-TYPE
       SYNTAX SEQUENCE OF AcPMSIPTel2IPTrunkGroupEstablishedCallsEntry
       MAX-ACCESS not-accessible
       STATUS current
       DESCRIPTION
           "Number of Tel2IP established calls per trunk group."
       ::= {acPMSIP 15}



     -- ****************************************
     -- acPMSIPTel2IPTrunkGroupEstablishedCalls table entry
     -- ****************************************
     acPMSIPTel2IPTrunkGroupEstablishedCallsEntry OBJECT-TYPE
       SYNTAX AcPMSIPTel2IPTrunkGroupEstablishedCallsEntry
       MAX-ACCESS not-accessible
       STATUS current
       DESCRIPTION
           ""
       INDEX {acPMSIPTel2IPTrunkGroupEstablishedCallsGroupNum,acPMSIPTel2IPTrunkGroupEstablishedCallsInterval}
       ::= {acPMSIPTel2IPTrunkGroupEstablishedCallsTable 1}



     -- ****************************************
     -- acPMSIPTel2IPTrunkGroupEstablishedCalls TABLE
     -- ****************************************
     AcPMSIPTel2IPTrunkGroupEstablishedCallsEntry ::= SEQUENCE {
       acPMSIPTel2IPTrunkGroupEstablishedCallsGroupNum Unsigned32,
       acPMSIPTel2IPTrunkGroupEstablishedCallsInterval Unsigned32,
       acPMSIPTel2IPTrunkGroupEstablishedCallsVal      Counter32
     }



     acPMSIPTel2IPTrunkGroupEstablishedCallsGroupNum OBJECT-TYPE
       SYNTAX Unsigned32 (0..83)
       MAX-ACCESS not-accessible
       STATUS current
       DESCRIPTION
           "Trunk Group number.
0 is the first trunk group."
       ::= {acPMSIPTel2IPTrunkGroupEstablishedCallsEntry 1}



     acPMSIPTel2IPTrunkGroupEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPTel2IPTrunkGroupEstablishedCallsEntry 2}



     acPMSIPTel2IPTrunkGroupEstablishedCallsVal OBJECT-TYPE
       SYNTAX Counter32
       MAX-ACCESS read-only
       STATUS current
       DESCRIPTION
           "Value of gauge or counter."
       ::= {acPMSIPTel2IPTrunkGroupEstablishedCallsEntry 3}



     -- ****************************************
     -- acPMSIPIP2TelTrunkGroupEstablishedCalls table declaration
     -- ****************************************
     acPMSIPIP2TelTrunkGroupEstablishedCallsTable OBJECT-TYPE
       SYNTAX SEQUENCE OF AcPMSIPIP2TelTrunkGroupEstablishedCallsEntry
       MAX-ACCESS not-accessible
       STATUS current
       DESCRIPTION
           "Number of IP2Tel established calls per trunk group."
       ::= {acPMSIP 16}



     -- ****************************************
     -- acPMSIPIP2TelTrunkGroupEstablishedCalls table entry
     -- ****************************************
     acPMSIPIP2TelTrunkGroupEstablishedCallsEntry OBJECT-TYPE
       SYNTAX AcPMSIPIP2TelTrunkGroupEstablishedCallsEntry
       MAX-ACCESS not-accessible
       STATUS current
       DESCRIPTION
           ""
       INDEX {acPMSIPIP2TelTrunkGroupEstablishedCallsGroupNum,acPMSIPIP2TelTrunkGroupEstablishedCallsInterval}
       ::= {acPMSIPIP2TelTrunkGroupEstablishedCallsTable 1}



     -- ****************************************
     -- acPMSIPIP2TelTrunkGroupEstablishedCalls TABLE
     -- ****************************************
     AcPMSIPIP2TelTrunkGroupEstablishedCallsEntry ::= SEQUENCE {
       acPMSIPIP2TelTrunkGroupEstablishedCallsGroupNum Unsigned32,
       acPMSIPIP2TelTrunkGroupEstablishedCallsInterval Unsigned32,
       acPMSIPIP2TelTrunkGroupEstablishedCallsVal      Counter32
     }



     acPMSIPIP2TelTrunkGroupEstablishedCallsGroupNum OBJECT-TYPE
       SYNTAX Unsigned32 (0..83)
       MAX-ACCESS not-accessible
       STATUS current
       DESCRIPTION
           "Trunk Group number.
0 is the first trunk group."
       ::= {acPMSIPIP2TelTrunkGroupEstablishedCallsEntry 1}



     acPMSIPIP2TelTrunkGroupEstablishedCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIP2TelTrunkGroupEstablishedCallsEntry 2}



     acPMSIPIP2TelTrunkGroupEstablishedCallsVal OBJECT-TYPE
       SYNTAX Counter32
       MAX-ACCESS read-only
       STATUS current
       DESCRIPTION
           "Value of gauge or counter."
       ::= {acPMSIPIP2TelTrunkGroupEstablishedCallsEntry 3}



     -- ****************************************
     -- acPMSIPSRDDialogs table declaration
     -- ****************************************
     acPMSIPSRDDialogsTable OBJECT-TYPE
       SYNTAX SEQUENCE OF AcPMSIPSRDDialogsEntry
       MAX-ACCESS not-accessible
       STATUS current
       DESCRIPTION
           "Performance Monitoring gwSRDDialogs setup"
       ::= {acPMSIP 17}



     -- ****************************************
     -- acPMSIPSRDDialogs table entry
     -- ****************************************
     acPMSIPSRDDialogsEntry OBJECT-TYPE
       SYNTAX AcPMSIPSRDDialogsEntry
       MAX-ACCESS not-accessible
       STATUS current
       DESCRIPTION
           ""
       INDEX {acPMSIPSRDDialogsSrdNum,acPMSIPSRDDialogsInterval}
       ::= {acPMSIPSRDDialogsTable 1}



     -- ****************************************
     -- acPMSIPSRDDialogs TABLE
     -- ****************************************
     AcPMSIPSRDDialogsEntry ::= SEQUENCE {
       acPMSIPSRDDialogsSrdNum                         Unsigned32,
       acPMSIPSRDDialogsInterval                       Unsigned32,
       acPMSIPSRDDialogsVal                            Counter32
     }



     acPMSIPSRDDialogsSrdNum OBJECT-TYPE
       SYNTAX Unsigned32 (0..5)
       MAX-ACCESS not-accessible
       STATUS current
       DESCRIPTION
           "SRD number.
0 is the first SRD."
       ::= {acPMSIPSRDDialogsEntry 1}



     acPMSIPSRDDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPSRDDialogsEntry 2}



     acPMSIPSRDDialogsVal OBJECT-TYPE
       SYNTAX Counter32
       MAX-ACCESS read-only
       STATUS current
       DESCRIPTION
           "Value of gauge or counter."
       ::= {acPMSIPSRDDialogsEntry 3}



     -- ****************************************
     -- acPMSIPSRDInviteDialogs table declaration
     -- ****************************************
     acPMSIPSRDInviteDialogsTable OBJECT-TYPE
       SYNTAX SEQUENCE OF AcPMSIPSRDInviteDialogsEntry
       MAX-ACCESS not-accessible
       STATUS current
       DESCRIPTION
           "Performance Monitoring gwSRDSUBSCRIBEDialogs setup"
       ::= {acPMSIP 18}



     -- ****************************************
     -- acPMSIPSRDInviteDialogs table entry
     -- ****************************************
     acPMSIPSRDInviteDialogsEntry OBJECT-TYPE
       SYNTAX AcPMSIPSRDInviteDialogsEntry
       MAX-ACCESS not-accessible
       STATUS current
       DESCRIPTION
           ""
       INDEX {acPMSIPSRDInviteDialogsSrdNum,acPMSIPSRDInviteDialogsInterval}
       ::= {acPMSIPSRDInviteDialogsTable 1}



     -- ****************************************
     -- acPMSIPSRDInviteDialogs TABLE
     -- ****************************************
     AcPMSIPSRDInviteDialogsEntry ::= SEQUENCE {
       acPMSIPSRDInviteDialogsSrdNum                   Unsigned32,
       acPMSIPSRDInviteDialogsInterval                 Unsigned32,
       acPMSIPSRDInviteDialogsVal                      Counter32
     }



     acPMSIPSRDInviteDialogsSrdNum OBJECT-TYPE
       SYNTAX Unsigned32 (0..5)
       MAX-ACCESS not-accessible
       STATUS current
       DESCRIPTION
           "SRD number.
0 is the first SRD."
       ::= {acPMSIPSRDInviteDialogsEntry 1}



     acPMSIPSRDInviteDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPSRDInviteDialogsEntry 2}



     acPMSIPSRDInviteDialogsVal OBJECT-TYPE
       SYNTAX Counter32
       MAX-ACCESS read-only
       STATUS current
       DESCRIPTION
           "Value of gauge or counter."
       ::= {acPMSIPSRDInviteDialogsEntry 3}



     -- ****************************************
     -- acPMSIPSRDSubscribeDialogs table declaration
     -- ****************************************
     acPMSIPSRDSubscribeDialogsTable OBJECT-TYPE
       SYNTAX SEQUENCE OF AcPMSIPSRDSubscribeDialogsEntry
       MAX-ACCESS not-accessible
       STATUS current
       DESCRIPTION
           "Performance Monitoring gwSRDSUBSCRIBEDialogs setup"
       ::= {acPMSIP 19}



     -- ****************************************
     -- acPMSIPSRDSubscribeDialogs table entry
     -- ****************************************
     acPMSIPSRDSubscribeDialogsEntry OBJECT-TYPE
       SYNTAX AcPMSIPSRDSubscribeDialogsEntry
       MAX-ACCESS not-accessible
       STATUS current
       DESCRIPTION
           ""
       INDEX {acPMSIPSRDSubscribeDialogsSrdNum,acPMSIPSRDSubscribeDialogsInterval}
       ::= {acPMSIPSRDSubscribeDialogsTable 1}



     -- ****************************************
     -- acPMSIPSRDSubscribeDialogs TABLE
     -- ****************************************
     AcPMSIPSRDSubscribeDialogsEntry ::= SEQUENCE {
       acPMSIPSRDSubscribeDialogsSrdNum                Unsigned32,
       acPMSIPSRDSubscribeDialogsInterval              Unsigned32,
       acPMSIPSRDSubscribeDialogsVal                   Counter32
     }



     acPMSIPSRDSubscribeDialogsSrdNum OBJECT-TYPE
       SYNTAX Unsigned32 (0..5)
       MAX-ACCESS not-accessible
       STATUS current
       DESCRIPTION
           "SRD number.
0 is the first SRD."
       ::= {acPMSIPSRDSubscribeDialogsEntry 1}



     acPMSIPSRDSubscribeDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPSRDSubscribeDialogsEntry 2}



     acPMSIPSRDSubscribeDialogsVal OBJECT-TYPE
       SYNTAX Counter32
       MAX-ACCESS read-only
       STATUS current
       DESCRIPTION
           "Value of gauge or counter."
       ::= {acPMSIPSRDSubscribeDialogsEntry 3}



     -- ****************************************
     -- acPMSIPSRDOtherDialogs table declaration
     -- ****************************************
     acPMSIPSRDOtherDialogsTable OBJECT-TYPE
       SYNTAX SEQUENCE OF AcPMSIPSRDOtherDialogsEntry
       MAX-ACCESS not-accessible
       STATUS current
       DESCRIPTION
           "Performance Monitoring gwSRDOtherDialogs setup"
       ::= {acPMSIP 20}



     -- ****************************************
     -- acPMSIPSRDOtherDialogs table entry
     -- ****************************************
     acPMSIPSRDOtherDialogsEntry OBJECT-TYPE
       SYNTAX AcPMSIPSRDOtherDialogsEntry
       MAX-ACCESS not-accessible
       STATUS current
       DESCRIPTION
           ""
       INDEX {acPMSIPSRDOtherDialogsSrdNum,acPMSIPSRDOtherDialogsInterval}
       ::= {acPMSIPSRDOtherDialogsTable 1}



     -- ****************************************
     -- acPMSIPSRDOtherDialogs TABLE
     -- ****************************************
     AcPMSIPSRDOtherDialogsEntry ::= SEQUENCE {
       acPMSIPSRDOtherDialogsSrdNum                    Unsigned32,
       acPMSIPSRDOtherDialogsInterval                  Unsigned32,
       acPMSIPSRDOtherDialogsVal                       Counter32
     }



     acPMSIPSRDOtherDialogsSrdNum OBJECT-TYPE
       SYNTAX Unsigned32 (0..5)
       MAX-ACCESS not-accessible
       STATUS current
       DESCRIPTION
           "SRD number.
0 is the first SRD."
       ::= {acPMSIPSRDOtherDialogsEntry 1}



     acPMSIPSRDOtherDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPSRDOtherDialogsEntry 2}



     acPMSIPSRDOtherDialogsVal OBJECT-TYPE
       SYNTAX Counter32
       MAX-ACCESS read-only
       STATUS current
       DESCRIPTION
           "Value of gauge or counter."
       ::= {acPMSIPSRDOtherDialogsEntry 3}



     -- ****************************************
     -- acPMSIPIPGroupDialogs table declaration
     -- ****************************************
     acPMSIPIPGroupDialogsTable OBJECT-TYPE
       SYNTAX SEQUENCE OF AcPMSIPIPGroupDialogsEntry
       MAX-ACCESS not-accessible
       STATUS current
       DESCRIPTION
           "Performance Monitoring gwIPGroupDialogs setup"
       ::= {acPMSIP 21}



     -- ****************************************
     -- acPMSIPIPGroupDialogs table entry
     -- ****************************************
     acPMSIPIPGroupDialogsEntry OBJECT-TYPE
       SYNTAX AcPMSIPIPGroupDialogsEntry
       MAX-ACCESS not-accessible
       STATUS current
       DESCRIPTION
           ""
       INDEX {acPMSIPIPGroupDialogsIPGroupNum,acPMSIPIPGroupDialogsInterval}
       ::= {acPMSIPIPGroupDialogsTable 1}



     -- ****************************************
     -- acPMSIPIPGroupDialogs TABLE
     -- ****************************************
     AcPMSIPIPGroupDialogsEntry ::= SEQUENCE {
       acPMSIPIPGroupDialogsIPGroupNum                 Unsigned32,
       acPMSIPIPGroupDialogsInterval                   Unsigned32,
       acPMSIPIPGroupDialogsVal                        Counter32
     }



     acPMSIPIPGroupDialogsIPGroupNum OBJECT-TYPE
       SYNTAX Unsigned32 (0..33)
       MAX-ACCESS not-accessible
       STATUS current
       DESCRIPTION
           "IP Group number.
0 is the first IP Group."
       ::= {acPMSIPIPGroupDialogsEntry 1}



     acPMSIPIPGroupDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIPGroupDialogsEntry 2}



     acPMSIPIPGroupDialogsVal OBJECT-TYPE
       SYNTAX Counter32
       MAX-ACCESS read-only
       STATUS current
       DESCRIPTION
           "Value of gauge or counter."
       ::= {acPMSIPIPGroupDialogsEntry 3}



     -- ****************************************
     -- acPMSIPIPGroupInviteDialogs table declaration
     -- ****************************************
     acPMSIPIPGroupInviteDialogsTable OBJECT-TYPE
       SYNTAX SEQUENCE OF AcPMSIPIPGroupInviteDialogsEntry
       MAX-ACCESS not-accessible
       STATUS current
       DESCRIPTION
           "Performance Monitoring gwIPGroupINVITEDialogs setup"
       ::= {acPMSIP 22}



     -- ****************************************
     -- acPMSIPIPGroupInviteDialogs table entry
     -- ****************************************
     acPMSIPIPGroupInviteDialogsEntry OBJECT-TYPE
       SYNTAX AcPMSIPIPGroupInviteDialogsEntry
       MAX-ACCESS not-accessible
       STATUS current
       DESCRIPTION
           ""
       INDEX {acPMSIPIPGroupInviteDialogsIPGroupNum,acPMSIPIPGroupInviteDialogsInterval}
       ::= {acPMSIPIPGroupInviteDialogsTable 1}



     -- ****************************************
     -- acPMSIPIPGroupInviteDialogs TABLE
     -- ****************************************
     AcPMSIPIPGroupInviteDialogsEntry ::= SEQUENCE {
       acPMSIPIPGroupInviteDialogsIPGroupNum           Unsigned32,
       acPMSIPIPGroupInviteDialogsInterval             Unsigned32,
       acPMSIPIPGroupInviteDialogsVal                  Counter32,
       acPMSIPIPGroupInviteDialogsAverage              Unsigned32,
       acPMSIPIPGroupInviteDialogsMax                  Unsigned32,
       acPMSIPIPGroupInviteDialogsMin                  Unsigned32,
       acPMSIPIPGroupInviteDialogsTimeBelowLowThreshold
                                                       Unsigned32,
       acPMSIPIPGroupInviteDialogsTimeBetweenThresholds
                                                       Unsigned32,
       acPMSIPIPGroupInviteDialogsTimeAboveHighThreshold
                                                       Unsigned32
     }



     acPMSIPIPGroupInviteDialogsIPGroupNum OBJECT-TYPE
       SYNTAX Unsigned32 (0..33)
       MAX-ACCESS not-accessible
       STATUS current
       DESCRIPTION
           "IP Group number.
0 is the first IP Group."
       ::= {acPMSIPIPGroupInviteDialogsEntry 1}



     acPMSIPIPGroupInviteDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIPGroupInviteDialogsEntry 2}



     acPMSIPIPGroupInviteDialogsVal OBJECT-TYPE
       SYNTAX Counter32
       MAX-ACCESS read-only
       STATUS current
       DESCRIPTION
           "Value of gauge or counter."
       ::= {acPMSIPIPGroupInviteDialogsEntry 3}



     acPMSIPIPGroupInviteDialogsAverage OBJECT-TYPE
       SYNTAX Unsigned32 (0..2147483647)
       MAX-ACCESS read-only
       STATUS current
       DESCRIPTION
           "Average value with in the period time."
       ::= {acPMSIPIPGroupInviteDialogsEntry 4}



     acPMSIPIPGroupInviteDialogsMax OBJECT-TYPE
       SYNTAX Unsigned32 (0..2147483647)
       MAX-ACCESS read-only
       STATUS current
       DESCRIPTION
           "Maximum value with in the period time."
       ::= {acPMSIPIPGroupInviteDialogsEntry 5}



     acPMSIPIPGroupInviteDialogsMin OBJECT-TYPE
       SYNTAX Unsigned32 (0..2147483647)
       MAX-ACCESS read-only
       STATUS current
       DESCRIPTION
           "Minimum value with in the period time."
       ::= {acPMSIPIPGroupInviteDialogsEntry 6}



     acPMSIPIPGroupInviteDialogsTimeBelowLowThreshold OBJECT-TYPE
       SYNTAX Unsigned32 (0..100)
       MAX-ACCESS read-only
       STATUS current
       DESCRIPTION
           "Number (in seconds) of interval time for which gauge is below
what was determined as the low threshold."
       ::= {acPMSIPIPGroupInviteDialogsEntry 7}



     acPMSIPIPGroupInviteDialogsTimeBetweenThresholds OBJECT-TYPE
       SYNTAX Unsigned32 (0..100)
       MAX-ACCESS read-only
       STATUS current
       DESCRIPTION
           "Number (in seconds) of interval time for which gauge is between
what were determined as the low and high thresholds."
       ::= {acPMSIPIPGroupInviteDialogsEntry 8}



     acPMSIPIPGroupInviteDialogsTimeAboveHighThreshold OBJECT-TYPE
       SYNTAX Unsigned32 (0..100)
       MAX-ACCESS read-only
       STATUS current
       DESCRIPTION
           "Number (in seconds) of interval time for which gauge is above
what was determined as the high threshold."
       ::= {acPMSIPIPGroupInviteDialogsEntry 9}



     -- ****************************************
     -- acPMSIPIPGroupSubscribeDialogs table declaration
     -- ****************************************
     acPMSIPIPGroupSubscribeDialogsTable OBJECT-TYPE
       SYNTAX SEQUENCE OF AcPMSIPIPGroupSubscribeDialogsEntry
       MAX-ACCESS not-accessible
       STATUS current
       DESCRIPTION
           "Performance Monitoring gwIPGroupSUBSCRIBEDialogs setup"
       ::= {acPMSIP 23}



     -- ****************************************
     -- acPMSIPIPGroupSubscribeDialogs table entry
     -- ****************************************
     acPMSIPIPGroupSubscribeDialogsEntry OBJECT-TYPE
       SYNTAX AcPMSIPIPGroupSubscribeDialogsEntry
       MAX-ACCESS not-accessible
       STATUS current
       DESCRIPTION
           ""
       INDEX {acPMSIPIPGroupSubscribeDialogsIPGroupNum,acPMSIPIPGroupSubscribeDialogsInterval}
       ::= {acPMSIPIPGroupSubscribeDialogsTable 1}



     -- ****************************************
     -- acPMSIPIPGroupSubscribeDialogs TABLE
     -- ****************************************
     AcPMSIPIPGroupSubscribeDialogsEntry ::= SEQUENCE {
       acPMSIPIPGroupSubscribeDialogsIPGroupNum        Unsigned32,
       acPMSIPIPGroupSubscribeDialogsInterval          Unsigned32,
       acPMSIPIPGroupSubscribeDialogsVal               Counter32
     }



     acPMSIPIPGroupSubscribeDialogsIPGroupNum OBJECT-TYPE
       SYNTAX Unsigned32 (0..33)
       MAX-ACCESS not-accessible
       STATUS current
       DESCRIPTION
           "IP Group number.
0 is the first IP Group."
       ::= {acPMSIPIPGroupSubscribeDialogsEntry 1}



     acPMSIPIPGroupSubscribeDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIPGroupSubscribeDialogsEntry 2}



     acPMSIPIPGroupSubscribeDialogsVal OBJECT-TYPE
       SYNTAX Counter32
       MAX-ACCESS read-only
       STATUS current
       DESCRIPTION
           "Value of gauge or counter."
       ::= {acPMSIPIPGroupSubscribeDialogsEntry 3}



     -- ****************************************
     -- acPMSIPIPGroupOtherDialogs table declaration
     -- ****************************************
     acPMSIPIPGroupOtherDialogsTable OBJECT-TYPE
       SYNTAX SEQUENCE OF AcPMSIPIPGroupOtherDialogsEntry
       MAX-ACCESS not-accessible
       STATUS current
       DESCRIPTION
           "Performance Monitoring gwIPGroupOtherDialogs setup"
       ::= {acPMSIP 24}



     -- ****************************************
     -- acPMSIPIPGroupOtherDialogs table entry
     -- ****************************************
     acPMSIPIPGroupOtherDialogsEntry OBJECT-TYPE
       SYNTAX AcPMSIPIPGroupOtherDialogsEntry
       MAX-ACCESS not-accessible
       STATUS current
       DESCRIPTION
           ""
       INDEX {acPMSIPIPGroupOtherDialogsIPGroupNum,acPMSIPIPGroupOtherDialogsInterval}
       ::= {acPMSIPIPGroupOtherDialogsTable 1}



     -- ****************************************
     -- acPMSIPIPGroupOtherDialogs TABLE
     -- ****************************************
     AcPMSIPIPGroupOtherDialogsEntry ::= SEQUENCE {
       acPMSIPIPGroupOtherDialogsIPGroupNum            Unsigned32,
       acPMSIPIPGroupOtherDialogsInterval              Unsigned32,
       acPMSIPIPGroupOtherDialogsVal                   Counter32
     }



     acPMSIPIPGroupOtherDialogsIPGroupNum OBJECT-TYPE
       SYNTAX Unsigned32 (0..33)
       MAX-ACCESS not-accessible
       STATUS current
       DESCRIPTION
           "IP Group number.
0 is the first IP Group."
       ::= {acPMSIPIPGroupOtherDialogsEntry 1}



     acPMSIPIPGroupOtherDialogsInterval OBJECT-TYPE
       SYNTAX Unsigned32 (0..2)
       MAX-ACCESS not-accessible
       STATUS current
       DESCRIPTION
           "Interval index.
0 - current period (incomplete monitoring - mid period).
1 - Last full period.
2 - One before last."
       ::= {acPMSIPIPGroupOtherDialogsEntry 2}



     acPMSIPIPGroupOtherDialogsVal OBJECT-TYPE
       SYNTAX Counter32
       MAX-ACCESS read-only
       STATUS current
       DESCRIPTION
           "Value of gauge or counter."
       ::= {acPMSIPIPGroupOtherDialogsEntry 3}



     -- ****************************************
     -- acPMSIPTrunkGroupAllTrunksBusy table declaration
     -- ****************************************
     acPMSIPTrunkGroupAllTrunksBusyTable OBJECT-TYPE
       SYNTAX SEQUENCE OF AcPMSIPTrunkGroupAllTrunksBusyEntry
       MAX-ACCESS not-accessible
       STATUS current
       DESCRIPTION
           "Performance Monitoring gwTrunkGroupAllTrunksBusy setup"
       ::= {acPMSIP 25}



     -- ****************************************
     -- acPMSIPTrunkGroupAllTrunksBusy table entry
     -- ****************************************
     acPMSIPTrunkGroupAllTrunksBusyEntry OBJECT-TYPE
       SYNTAX AcPMSIPTrunkGroupAllTrunksBusyEntry
       MAX-ACCESS not-accessible
       STATUS current
       DESCRIPTION
           ""
       INDEX {acPMSIPTrunkGroupAllTrunksBusyTrunkGroupNum,acPMSIPTrunkGroupAllTrunksBusyInterval}
       ::= {acPMSIPTrunkGroupAllTrunksBusyTable 1}



     -- ****************************************
     -- acPMSIPTrunkGroupAllTrunksBusy TABLE
     -- ****************************************
     AcPMSIPTrunkGroupAllTrunksBusyEntry ::= SEQUENCE {
       acPMSIPTrunkGroupAllTrunksBusyTrunkGroupNum     Unsigned32,
       acPMSIPTrunkGroupAllTrunksBusyInterval          Unsigned32,
       acPMSIPTrunkGroupAllTrunksBusyVal               Counter32
     }



     acPMSIPTrunkGroupAllTrunksBusyTrunkGroupNum OBJECT-TYPE
       SYNTAX Unsigned32 (0..83)
       MAX-ACCESS not-accessible
       STATUS current
       DESCRIPTION
           "Trunk Group number.
0 is the first Trunk Group."
       ::= {acPMSIPTrunkGroupAllTrunksBusyEntry 1}



     acPMSIPTrunkGroupAllTrunksBusyInterval OBJECT-TYPE
       SYNTAX Unsigned32 (0..2)
       MAX-ACCESS not-accessible
       STATUS current
       DESCRIPTION
           "Interval index.
0 - current period (incomplete monitoring - mid period).
1 - Last full period.
2 - One before last."
       ::= {acPMSIPTrunkGroupAllTrunksBusyEntry 2}



     acPMSIPTrunkGroupAllTrunksBusyVal OBJECT-TYPE
       SYNTAX Counter32
       MAX-ACCESS read-only
       STATUS current
       DESCRIPTION
           "Value of gauge or counter."
       ::= {acPMSIPTrunkGroupAllTrunksBusyEntry 3}



     -- ****************************************
     -- acPMSIPTrunkGroupUtilization table declaration
     -- ****************************************
     acPMSIPTrunkGroupUtilizationTable OBJECT-TYPE
       SYNTAX SEQUENCE OF AcPMSIPTrunkGroupUtilizationEntry
       MAX-ACCESS not-accessible
       STATUS current
       DESCRIPTION
           "Processing time (in Microseconds), per command type."
       ::= {acPMSIP 26}



     -- ****************************************
     -- acPMSIPTrunkGroupUtilization table entry
     -- ****************************************
     acPMSIPTrunkGroupUtilizationEntry OBJECT-TYPE
       SYNTAX AcPMSIPTrunkGroupUtilizationEntry
       MAX-ACCESS not-accessible
       STATUS current
       DESCRIPTION
           ""
       INDEX {acPMSIPTrunkGroupUtilizationTrunkGroupNum,acPMSIPTrunkGroupUtilizationInterval}
       ::= {acPMSIPTrunkGroupUtilizationTable 1}



     -- ****************************************
     -- acPMSIPTrunkGroupUtilization TABLE
     -- ****************************************
     AcPMSIPTrunkGroupUtilizationEntry ::= SEQUENCE {
       acPMSIPTrunkGroupUtilizationTrunkGroupNum       Unsigned32,
       acPMSIPTrunkGroupUtilizationInterval            Unsigned32,
       acPMSIPTrunkGroupUtilizationVal                 Gauge32,
       acPMSIPTrunkGroupUtilizationTimeBelowLowThreshold
                                                       Unsigned32,
       acPMSIPTrunkGroupUtilizationTimeBetweenThresholds
                                                       Unsigned32,
       acPMSIPTrunkGroupUtilizationTimeAboveHighThreshold
                                                       Unsigned32,
       acPMSIPTrunkGroupUtilizationAverage             Unsigned32,
       acPMSIPTrunkGroupUtilizationMax                 Unsigned32,
       acPMSIPTrunkGroupUtilizationMin                 Unsigned32,
       acPMSIPTrunkGroupUtilizationTotal               Counter32,
       acPMSIPTrunkGroupUtilizationFullDayAverage      Unsigned32
     }



     acPMSIPTrunkGroupUtilizationTrunkGroupNum OBJECT-TYPE
       SYNTAX Unsigned32 (0..83)
       MAX-ACCESS not-accessible
       STATUS current
       DESCRIPTION
           "Trunk Group number.
0 is the first Trunk Group."
       ::= {acPMSIPTrunkGroupUtilizationEntry 1}



     acPMSIPTrunkGroupUtilizationInterval OBJECT-TYPE
       SYNTAX Unsigned32 (0..2)
       MAX-ACCESS not-accessible
       STATUS current
       DESCRIPTION
           "Interval index.
0 - current period (incomplete monitoring - mid period).
1 - Last full period.
2 - One before last."
       ::= {acPMSIPTrunkGroupUtilizationEntry 2}



     acPMSIPTrunkGroupUtilizationVal OBJECT-TYPE
       SYNTAX Gauge32
       MAX-ACCESS read-only
       STATUS current
       DESCRIPTION
           "Value of gauge or counter."
       ::= {acPMSIPTrunkGroupUtilizationEntry 3}



     acPMSIPTrunkGroupUtilizationTimeBelowLowThreshold OBJECT-TYPE
       SYNTAX Unsigned32 (0..100)
       MAX-ACCESS read-only
       STATUS current
       DESCRIPTION
           "Percent of interval time for which gauge is below what was determined
as the low threshold."
       ::= {acPMSIPTrunkGroupUtilizationEntry 4}



     acPMSIPTrunkGroupUtilizationTimeBetweenThresholds OBJECT-TYPE
       SYNTAX Unsigned32 (0..100)
       MAX-ACCESS read-only
       STATUS current
       DESCRIPTION
           "Percent of interval time for which gauge is between what were
determined as the low and high thresholds."
       ::= {acPMSIPTrunkGroupUtilizationEntry 5}



     acPMSIPTrunkGroupUtilizationTimeAboveHighThreshold OBJECT-TYPE
       SYNTAX Unsigned32 (0..100)
       MAX-ACCESS read-only
       STATUS current
       DESCRIPTION
           "Percent of interval time for which gauge is above what was determined
as the high threshold."
       ::= {acPMSIPTrunkGroupUtilizationEntry 6}



     acPMSIPTrunkGroupUtilizationAverage OBJECT-TYPE
       SYNTAX Unsigned32 (0..2016)
       MAX-ACCESS read-only
       STATUS current
       DESCRIPTION
           "Average value with in the period time."
       ::= {acPMSIPTrunkGroupUtilizationEntry 7}



     acPMSIPTrunkGroupUtilizationMax OBJECT-TYPE
       SYNTAX Unsigned32 (0..2016)
       MAX-ACCESS read-only
       STATUS current
       DESCRIPTION
           "Maximum value with in the period time."
       ::= {acPMSIPTrunkGroupUtilizationEntry 8}



     acPMSIPTrunkGroupUtilizationMin OBJECT-TYPE
       SYNTAX Unsigned32 (0..2016)
       MAX-ACCESS read-only
       STATUS current
       DESCRIPTION
           "Minimum value with in the period time."
       ::= {acPMSIPTrunkGroupUtilizationEntry 9}



     acPMSIPTrunkGroupUtilizationTotal OBJECT-TYPE
       SYNTAX Counter32
       MAX-ACCESS read-only
       STATUS current
       DESCRIPTION
           "Activity volume."
       ::= {acPMSIPTrunkGroupUtilizationEntry 10}



     acPMSIPTrunkGroupUtilizationFullDayAverage OBJECT-TYPE
       SYNTAX Unsigned32 (0..2016)
       MAX-ACCESS read-only
       STATUS current
       DESCRIPTION
           "The average of full 24 hours."
       ::= {acPMSIPTrunkGroupUtilizationEntry 11}



     -- ****************************************
     -- acPMSIPTrunkGroupPercentageUtilization table declaration
     -- ****************************************
     acPMSIPTrunkGroupPercentageUtilizationTable OBJECT-TYPE
       SYNTAX SEQUENCE OF AcPMSIPTrunkGroupPercentageUtilizationEntry
       MAX-ACCESS not-accessible
       STATUS current
       DESCRIPTION
           "Processing time (in Microseconds), per command type."
       ::= {acPMSIP 27}



     -- ****************************************
     -- acPMSIPTrunkGroupPercentageUtilization table entry
     -- ****************************************
     acPMSIPTrunkGroupPercentageUtilizationEntry OBJECT-TYPE
       SYNTAX AcPMSIPTrunkGroupPercentageUtilizationEntry
       MAX-ACCESS not-accessible
       STATUS current
       DESCRIPTION
           ""
       INDEX {acPMSIPTrunkGroupPercentageUtilizationTrunkGroupNum,acPMSIPTrunkGroupPercentageUtilizationInterval}
       ::= {acPMSIPTrunkGroupPercentageUtilizationTable 1}



     -- ****************************************
     -- acPMSIPTrunkGroupPercentageUtilization TABLE
     -- ****************************************
     AcPMSIPTrunkGroupPercentageUtilizationEntry ::= SEQUENCE {
       acPMSIPTrunkGroupPercentageUtilizationTrunkGroupNum
                                                       Unsigned32,
       acPMSIPTrunkGroupPercentageUtilizationInterval  Unsigned32,
       acPMSIPTrunkGroupPercentageUtilizationVal       Gauge32,
       acPMSIPTrunkGroupPercentageUtilizationTimeBelowLowThreshold
                                                       Unsigned32,
       acPMSIPTrunkGroupPercentageUtilizationTimeBetweenThresholds
                                                       Unsigned32,
       acPMSIPTrunkGroupPercentageUtilizationTimeAboveHighThreshold
                                                       Unsigned32,
       acPMSIPTrunkGroupPercentageUtilizationAverage   Unsigned32,
       acPMSIPTrunkGroupPercentageUtilizationMax       Unsigned32,
       acPMSIPTrunkGroupPercentageUtilizationMin       Unsigned32,
       acPMSIPTrunkGroupPercentageUtilizationFullDayAverage
                                                       Unsigned32
     }



     acPMSIPTrunkGroupPercentageUtilizationTrunkGroupNum OBJECT-TYPE
       SYNTAX Unsigned32 (0..83)
       MAX-ACCESS not-accessible
       STATUS current
       DESCRIPTION
           "Trunk Group number.
0 is the first Trunk Group."
       ::= {acPMSIPTrunkGroupPercentageUtilizationEntry 1}



     acPMSIPTrunkGroupPercentageUtilizationInterval OBJECT-TYPE
       SYNTAX Unsigned32 (0..2)
       MAX-ACCESS not-accessible
       STATUS current
       DESCRIPTION
           "Interval index.
0 - current period (incomplete monitoring - mid period).
1 - Last full period.
2 - One before last."
       ::= {acPMSIPTrunkGroupPercentageUtilizationEntry 2}



     acPMSIPTrunkGroupPercentageUtilizationVal OBJECT-TYPE
       SYNTAX Gauge32
       MAX-ACCESS read-only
       STATUS current
       DESCRIPTION
           "Current value of gauge in percentage."
       ::= {acPMSIPTrunkGroupPercentageUtilizationEntry 3}



     acPMSIPTrunkGroupPercentageUtilizationTimeBelowLowThreshold OBJECT-TYPE
       SYNTAX Unsigned32 (0..100)
       MAX-ACCESS read-only
       STATUS current
       DESCRIPTION
           "Percent of interval time for which gauge is below what was determined
as the low threshold."
       ::= {acPMSIPTrunkGroupPercentageUtilizationEntry 4}



     acPMSIPTrunkGroupPercentageUtilizationTimeBetweenThresholds OBJECT-TYPE
       SYNTAX Unsigned32 (0..100)
       MAX-ACCESS read-only
       STATUS current
       DESCRIPTION
           "Percent of interval time for which gauge is between what were
determined as the low and high thresholds."
       ::= {acPMSIPTrunkGroupPercentageUtilizationEntry 5}



     acPMSIPTrunkGroupPercentageUtilizationTimeAboveHighThreshold OBJECT-TYPE
       SYNTAX Unsigned32 (0..100)
       MAX-ACCESS read-only
       STATUS current
       DESCRIPTION
           "Percent of interval time for which gauge is above what was determined
as the high threshold."
       ::= {acPMSIPTrunkGroupPercentageUtilizationEntry 6}



     acPMSIPTrunkGroupPercentageUtilizationAverage OBJECT-TYPE
       SYNTAX Unsigned32 (0..100)
       MAX-ACCESS read-only
       STATUS current
       DESCRIPTION
           "Average percentage of utilization with in the period time."
       ::= {acPMSIPTrunkGroupPercentageUtilizationEntry 7}



     acPMSIPTrunkGroupPercentageUtilizationMax OBJECT-TYPE
       SYNTAX Unsigned32 (0..100)
       MAX-ACCESS read-only
       STATUS current
       DESCRIPTION
           "Maximum percentage of utilization with in the period time."
       ::= {acPMSIPTrunkGroupPercentageUtilizationEntry 8}



     acPMSIPTrunkGroupPercentageUtilizationMin OBJECT-TYPE
       SYNTAX Unsigned32 (0..100)
       MAX-ACCESS read-only
       STATUS current
       DESCRIPTION
           "Minimum percentage of utilization with in the period time."
       ::= {acPMSIPTrunkGroupPercentageUtilizationEntry 9}



     acPMSIPTrunkGroupPercentageUtilizationFullDayAverage OBJECT-TYPE
       SYNTAX Unsigned32 (0..100)
       MAX-ACCESS read-only
       STATUS current
       DESCRIPTION
           "The average percentage of utilization with in the past 24 hours."
       ::= {acPMSIPTrunkGroupPercentageUtilizationEntry 10}



     -- ****************************************
     -- acPMSIPTrunkGroupNoResourcesCalls table declaration
     -- ****************************************
     acPMSIPTrunkGroupNoResourcesCallsTable OBJECT-TYPE
       SYNTAX SEQUENCE OF AcPMSIPTrunkGroupNoResourcesCallsEntry
       MAX-ACCESS not-accessible
       STATUS current
       DESCRIPTION
           "Number of calls released because of no resources (Index for the Trunk Group ID)"
       ::= {acPMSIP 28}



     -- ****************************************
     -- acPMSIPTrunkGroupNoResourcesCalls table entry
     -- ****************************************
     acPMSIPTrunkGroupNoResourcesCallsEntry OBJECT-TYPE
       SYNTAX AcPMSIPTrunkGroupNoResourcesCallsEntry
       MAX-ACCESS not-accessible
       STATUS current
       DESCRIPTION
           ""
       INDEX {acPMSIPTrunkGroupNoResourcesCallsTrunkGroupNum,acPMSIPTrunkGroupNoResourcesCallsInterval}
       ::= {acPMSIPTrunkGroupNoResourcesCallsTable 1}



     -- ****************************************
     -- acPMSIPTrunkGroupNoResourcesCalls TABLE
     -- ****************************************
     AcPMSIPTrunkGroupNoResourcesCallsEntry ::= SEQUENCE {
       acPMSIPTrunkGroupNoResourcesCallsTrunkGroupNum  Unsigned32,
       acPMSIPTrunkGroupNoResourcesCallsInterval       Unsigned32,
       acPMSIPTrunkGroupNoResourcesCallsVal            Counter32,
       acPMSIPTrunkGroupNoResourcesCallsTotal          Counter32
     }



     acPMSIPTrunkGroupNoResourcesCallsTrunkGroupNum OBJECT-TYPE
       SYNTAX Unsigned32 (0..83)
       MAX-ACCESS not-accessible
       STATUS current
       DESCRIPTION
           "Trunk Group number.
0 is the first Trunk Group."
       ::= {acPMSIPTrunkGroupNoResourcesCallsEntry 1}



     acPMSIPTrunkGroupNoResourcesCallsInterval OBJECT-TYPE
       SYNTAX Unsigned32 (0..2)
       MAX-ACCESS not-accessible
       STATUS current
       DESCRIPTION
           "Interval index.
0 - current period (incomplete monitoring - mid period).
1 - Last full period.
2 - One before last."
       ::= {acPMSIPTrunkGroupNoResourcesCallsEntry 2}



     acPMSIPTrunkGroupNoResourcesCallsVal OBJECT-TYPE
       SYNTAX Counter32
       MAX-ACCESS read-only
       STATUS current
       DESCRIPTION
           "Value of gauge or counter."
       ::= {acPMSIPTrunkGroupNoResourcesCallsEntry 3}



     acPMSIPTrunkGroupNoResourcesCallsTotal OBJECT-TYPE
       SYNTAX Counter32
       MAX-ACCESS read-only
       STATUS current
       DESCRIPTION
           "Activity volume."
       ::= {acPMSIPTrunkGroupNoResourcesCallsEntry 4}



     -- ****************************************
     -- acPMSIPTrunkGroupCallDuration table declaration
     -- ****************************************
     acPMSIPTrunkGroupCallDurationTable OBJECT-TYPE
       SYNTAX SEQUENCE OF AcPMSIPTrunkGroupCallDurationEntry
       MAX-ACCESS not-accessible
       STATUS current
       DESCRIPTION
           "Call Duration of Trunk Group"
       ::= {acPMSIP 29}



     -- ****************************************
     -- acPMSIPTrunkGroupCallDuration table entry
     -- ****************************************
     acPMSIPTrunkGroupCallDurationEntry OBJECT-TYPE
       SYNTAX AcPMSIPTrunkGroupCallDurationEntry
       MAX-ACCESS not-accessible
       STATUS current
       DESCRIPTION
           ""
       INDEX {acPMSIPTrunkGroupCallDurationTrunkGroupNum,acPMSIPTrunkGroupCallDurationInterval}
       ::= {acPMSIPTrunkGroupCallDurationTable 1}



     -- ****************************************
     -- acPMSIPTrunkGroupCallDuration TABLE
     -- ****************************************
     AcPMSIPTrunkGroupCallDurationEntry ::= SEQUENCE {
       acPMSIPTrunkGroupCallDurationTrunkGroupNum      Unsigned32,
       acPMSIPTrunkGroupCallDurationInterval           Unsigned32,
       acPMSIPTrunkGroupCallDurationVal                Gauge32,
       acPMSIPTrunkGroupCallDurationAverage            Unsigned32,
       acPMSIPTrunkGroupCallDurationMax                Unsigned32,
       acPMSIPTrunkGroupCallDurationMin                Unsigned32,
       acPMSIPTrunkGroupCallDurationTotal              Counter32,
       acPMSIPTrunkGroupCallDurationFullDayAverage     Unsigned32
     }



     acPMSIPTrunkGroupCallDurationTrunkGroupNum OBJECT-TYPE
       SYNTAX Unsigned32 (0..83)
       MAX-ACCESS not-accessible
       STATUS current
       DESCRIPTION
           "Trunk Group number.
0 is the first Trunk Group."
       ::= {acPMSIPTrunkGroupCallDurationEntry 1}



     acPMSIPTrunkGroupCallDurationInterval OBJECT-TYPE
       SYNTAX Unsigned32 (0..2)
       MAX-ACCESS not-accessible
       STATUS current
       DESCRIPTION
           "Interval index.
0 - current period (incomplete monitoring - mid period).
1 - Last full period.
2 - One before last."
       ::= {acPMSIPTrunkGroupCallDurationEntry 2}



     acPMSIPTrunkGroupCallDurationVal OBJECT-TYPE
       SYNTAX Gauge32
       MAX-ACCESS read-only
       STATUS current
       DESCRIPTION
           "Value of gauge or counter."
       ::= {acPMSIPTrunkGroupCallDurationEntry 3}



     acPMSIPTrunkGroupCallDurationAverage OBJECT-TYPE
       SYNTAX Unsigned32 (0..2147483647)
       MAX-ACCESS read-only
       STATUS current
       DESCRIPTION
           "Average value with in the period time."
       ::= {acPMSIPTrunkGroupCallDurationEntry 4}



     acPMSIPTrunkGroupCallDurationMax OBJECT-TYPE
       SYNTAX Unsigned32 (0..2147483647)
       MAX-ACCESS read-only
       STATUS current
       DESCRIPTION
           "Maximum value with in the period time."
       ::= {acPMSIPTrunkGroupCallDurationEntry 5}



     acPMSIPTrunkGroupCallDurationMin OBJECT-TYPE
       SYNTAX Unsigned32 (0..2147483647)
       MAX-ACCESS read-only
       STATUS current
       DESCRIPTION
           "Minimum value with in the period time."
       ::= {acPMSIPTrunkGroupCallDurationEntry 6}



     acPMSIPTrunkGroupCallDurationTotal OBJECT-TYPE
       SYNTAX Counter32
       MAX-ACCESS read-only
       STATUS current
       DESCRIPTION
           "Sum duration of all calls of Trunk Group."
       ::= {acPMSIPTrunkGroupCallDurationEntry 7}



     acPMSIPTrunkGroupCallDurationFullDayAverage OBJECT-TYPE
       SYNTAX Unsigned32 (0..2147483647)
       MAX-ACCESS read-only
       STATUS current
       DESCRIPTION
           "The average of full 24 hours."
       ::= {acPMSIPTrunkGroupCallDurationEntry 8}



     -- ****************************************
     -- acPMSIPTrunkGroupAllTrunksBusyPercentage table declaration
     -- ****************************************
     acPMSIPTrunkGroupAllTrunksBusyPercentageTable OBJECT-TYPE
       SYNTAX SEQUENCE OF AcPMSIPTrunkGroupAllTrunksBusyPercentageEntry
       MAX-ACCESS not-accessible
       STATUS current
       DESCRIPTION
           "Performance Monitoring gwTrunkGroupAllTrunksBusyPercentage setup"
       ::= {acPMSIP 40}



     -- ****************************************
     -- acPMSIPTrunkGroupAllTrunksBusyPercentage table entry
     -- ****************************************
     acPMSIPTrunkGroupAllTrunksBusyPercentageEntry OBJECT-TYPE
       SYNTAX AcPMSIPTrunkGroupAllTrunksBusyPercentageEntry
       MAX-ACCESS not-accessible
       STATUS current
       DESCRIPTION
           ""
       INDEX {acPMSIPTrunkGroupAllTrunksBusyPercentageTrunkGroupNum,acPMSIPTrunkGroupAllTrunksBusyPercentageInterval}
       ::= {acPMSIPTrunkGroupAllTrunksBusyPercentageTable 1}



     -- ****************************************
     -- acPMSIPTrunkGroupAllTrunksBusyPercentage TABLE
     -- ****************************************
     AcPMSIPTrunkGroupAllTrunksBusyPercentageEntry ::= SEQUENCE {
       acPMSIPTrunkGroupAllTrunksBusyPercentageTrunkGroupNum
                                                       Unsigned32,
       acPMSIPTrunkGroupAllTrunksBusyPercentageInterval
                                                       Unsigned32,
       acPMSIPTrunkGroupAllTrunksBusyPercentageVal     Gauge32
     }



     acPMSIPTrunkGroupAllTrunksBusyPercentageTrunkGroupNum OBJECT-TYPE
       SYNTAX Unsigned32 (0..83)
       MAX-ACCESS not-accessible
       STATUS current
       DESCRIPTION
           "Trunk Group number.
0 is the first Trunk Group."
       ::= {acPMSIPTrunkGroupAllTrunksBusyPercentageEntry 1}



     acPMSIPTrunkGroupAllTrunksBusyPercentageInterval OBJECT-TYPE
       SYNTAX Unsigned32 (0..2)
       MAX-ACCESS not-accessible
       STATUS current
       DESCRIPTION
           "Interval index.
0 - current period (incomplete monitoring - mid period).
1 - Last full period.
2 - One before last."
       ::= {acPMSIPTrunkGroupAllTrunksBusyPercentageEntry 2}



     acPMSIPTrunkGroupAllTrunksBusyPercentageVal OBJECT-TYPE
       SYNTAX Gauge32
       MAX-ACCESS read-only
       STATUS current
       DESCRIPTION
           "Indicates the percentage of the previous interval (15-minute)
for which all the trunks were busy. Note: value of current
interval (acPMSIPTrunkGroupAllTrunksBusyPercentageInterval
= 0) is always equal to value of the previous interval."
       ::= {acPMSIPTrunkGroupAllTrunksBusyPercentageEntry 3}



     acPMMediaRealm  OBJECT IDENTIFIER ::= {acPMControlData 53}


     -- ****************************************
     -- acPMMediaRealmBytesTx table declaration
     -- ****************************************
     acPMMediaRealmBytesTxTable OBJECT-TYPE
       SYNTAX SEQUENCE OF AcPMMediaRealmBytesTxEntry
       MAX-ACCESS not-accessible
       STATUS current
       DESCRIPTION
           "Performance Monitoring MediaRealmBytesTx"
       ::= {acPMMediaRealm  1}



     -- ****************************************
     -- acPMMediaRealmBytesTx table entry
     -- ****************************************
     acPMMediaRealmBytesTxEntry OBJECT-TYPE
       SYNTAX AcPMMediaRealmBytesTxEntry
       MAX-ACCESS not-accessible
       STATUS current
       DESCRIPTION
           ""
       INDEX {acPMMediaRealmBytesTxMediaRealmNum,acPMMediaRealmBytesTxInterval}
       ::= {acPMMediaRealmBytesTxTable 1}



     -- ****************************************
     -- acPMMediaRealmBytesTx TABLE
     -- ****************************************
     AcPMMediaRealmBytesTxEntry ::= SEQUENCE {
       acPMMediaRealmBytesTxMediaRealmNum              Unsigned32,
       acPMMediaRealmBytesTxInterval                   Unsigned32,
       acPMMediaRealmBytesTxVal                        Counter32,
       acPMMediaRealmBytesTxVolume                     Counter32
     }



     acPMMediaRealmBytesTxMediaRealmNum OBJECT-TYPE
       SYNTAX Unsigned32 (0..63)
       MAX-ACCESS not-accessible
       STATUS current
       DESCRIPTION
           "Media Realm number.
0 is the first Media Realm."
       ::= {acPMMediaRealmBytesTxEntry 1}



     acPMMediaRealmBytesTxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmBytesTxEntry 2}



     acPMMediaRealmBytesTxVal OBJECT-TYPE
       SYNTAX Counter32
       MAX-ACCESS read-only
       STATUS current
       DESCRIPTION
           "Value of gauge or counter."
       ::= {acPMMediaRealmBytesTxEntry 3}



     acPMMediaRealmBytesTxVolume OBJECT-TYPE
       SYNTAX Counter32
       MAX-ACCESS read-only
       STATUS current
       DESCRIPTION
           "Activity volume."
       ::= {acPMMediaRealmBytesTxEntry 4}



     -- ****************************************
     -- acPMMediaRealmBytesRx table declaration
     -- ****************************************
     acPMMediaRealmBytesRxTable OBJECT-TYPE
       SYNTAX SEQUENCE OF AcPMMediaRealmBytesRxEntry
       MAX-ACCESS not-accessible
       STATUS current
       DESCRIPTION
           "Performance Monitoring MediaRealmBytesRx"
       ::= {acPMMediaRealm  2}



     -- ****************************************
     -- acPMMediaRealmBytesRx table entry
     -- ****************************************
     acPMMediaRealmBytesRxEntry OBJECT-TYPE
       SYNTAX AcPMMediaRealmBytesRxEntry
       MAX-ACCESS not-accessible
       STATUS current
       DESCRIPTION
           ""
       INDEX {acPMMediaRealmBytesRxMediaRealmNum,acPMMediaRealmBytesRxInterval}
       ::= {acPMMediaRealmBytesRxTable 1}



     -- ****************************************
     -- acPMMediaRealmBytesRx TABLE
     -- ****************************************
     AcPMMediaRealmBytesRxEntry ::= SEQUENCE {
       acPMMediaRealmBytesRxMediaRealmNum              Unsigned32,
       acPMMediaRealmBytesRxInterval                   Unsigned32,
       acPMMediaRealmBytesRxVal                        Counter32,
       acPMMediaRealmBytesRxVolume                     Counter32
     }



     acPMMediaRealmBytesRxMediaRealmNum OBJECT-TYPE
       SYNTAX Unsigned32 (0..63)
       MAX-ACCESS not-accessible
       STATUS current
       DESCRIPTION
           "Media Realm number.
0 is the first Media Realm."
       ::= {acPMMediaRealmBytesRxEntry 1}



     acPMMediaRealmBytesRxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmBytesRxEntry 2}



     acPMMediaRealmBytesRxVal OBJECT-TYPE
       SYNTAX Counter32
       MAX-ACCESS read-only
       STATUS current
       DESCRIPTION
           "Value of gauge or counter."
       ::= {acPMMediaRealmBytesRxEntry 3}



     acPMMediaRealmBytesRxVolume OBJECT-TYPE
       SYNTAX Counter32
       MAX-ACCESS read-only
       STATUS current
       DESCRIPTION
           "Activity volume."
       ::= {acPMMediaRealmBytesRxEntry 4}



     -- ****************************************
     -- acPMMediaRealmPacketsTx table declaration
     -- ****************************************
     acPMMediaRealmPacketsTxTable OBJECT-TYPE
       SYNTAX SEQUENCE OF AcPMMediaRealmPacketsTxEntry
       MAX-ACCESS not-accessible
       STATUS current
       DESCRIPTION
           "Performance Monitoring MediaRealmPacketsTx"
       ::= {acPMMediaRealm  3}



     -- ****************************************
     -- acPMMediaRealmPacketsTx table entry
     -- ****************************************
     acPMMediaRealmPacketsTxEntry OBJECT-TYPE
       SYNTAX AcPMMediaRealmPacketsTxEntry
       MAX-ACCESS not-accessible
       STATUS current
       DESCRIPTION
           ""
       INDEX {acPMMediaRealmPacketsTxMediaRealmNum,acPMMediaRealmPacketsTxInterval}
       ::= {acPMMediaRealmPacketsTxTable 1}



     -- ****************************************
     -- acPMMediaRealmPacketsTx TABLE
     -- ****************************************
     AcPMMediaRealmPacketsTxEntry ::= SEQUENCE {
       acPMMediaRealmPacketsTxMediaRealmNum            Unsigned32,
       acPMMediaRealmPacketsTxInterval                 Unsigned32,
       acPMMediaRealmPacketsTxVal                      Counter32,
       acPMMediaRealmPacketsTxVolume                   Counter32
     }



     acPMMediaRealmPacketsTxMediaRealmNum OBJECT-TYPE
       SYNTAX Unsigned32 (0..63)
       MAX-ACCESS not-accessible
       STATUS current
       DESCRIPTION
           "Media Realm number.
0 is the first Media Realm."
       ::= {acPMMediaRealmPacketsTxEntry 1}



     acPMMediaRealmPacketsTxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmPacketsTxEntry 2}



     acPMMediaRealmPacketsTxVal OBJECT-TYPE
       SYNTAX Counter32
       MAX-ACCESS read-only
       STATUS current
       DESCRIPTION
           "Value of gauge or counter."
       ::= {acPMMediaRealmPacketsTxEntry 3}



     acPMMediaRealmPacketsTxVolume OBJECT-TYPE
       SYNTAX Counter32
       MAX-ACCESS read-only
       STATUS current
       DESCRIPTION
           "Activity volume."
       ::= {acPMMediaRealmPacketsTxEntry 4}



     -- ****************************************
     -- acPMMediaRealmPacketsRx table declaration
     -- ****************************************
     acPMMediaRealmPacketsRxTable OBJECT-TYPE
       SYNTAX SEQUENCE OF AcPMMediaRealmPacketsRxEntry
       MAX-ACCESS not-accessible
       STATUS current
       DESCRIPTION
           "Performance Monitoring MediaRealmPacketsRx"
       ::= {acPMMediaRealm  4}



     -- ****************************************
     -- acPMMediaRealmPacketsRx table entry
     -- ****************************************
     acPMMediaRealmPacketsRxEntry OBJECT-TYPE
       SYNTAX AcPMMediaRealmPacketsRxEntry
       MAX-ACCESS not-accessible
       STATUS current
       DESCRIPTION
           ""
       INDEX {acPMMediaRealmPacketsRxMediaRealmNum,acPMMediaRealmPacketsRxInterval}
       ::= {acPMMediaRealmPacketsRxTable 1}



     -- ****************************************
     -- acPMMediaRealmPacketsRx TABLE
     -- ****************************************
     AcPMMediaRealmPacketsRxEntry ::= SEQUENCE {
       acPMMediaRealmPacketsRxMediaRealmNum            Unsigned32,
       acPMMediaRealmPacketsRxInterval                 Unsigned32,
       acPMMediaRealmPacketsRxVal                      Counter32,
       acPMMediaRealmPacketsRxVolume                   Counter32
     }



     acPMMediaRealmPacketsRxMediaRealmNum OBJECT-TYPE
       SYNTAX Unsigned32 (0..63)
       MAX-ACCESS not-accessible
       STATUS current
       DESCRIPTION
           "Media Realm number.
0 is the first Media Realm."
       ::= {acPMMediaRealmPacketsRxEntry 1}



     acPMMediaRealmPacketsRxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmPacketsRxEntry 2}



     acPMMediaRealmPacketsRxVal OBJECT-TYPE
       SYNTAX Counter32
       MAX-ACCESS read-only
       STATUS current
       DESCRIPTION
           "Value of gauge or counter."
       ::= {acPMMediaRealmPacketsRxEntry 3}



     acPMMediaRealmPacketsRxVolume OBJECT-TYPE
       SYNTAX Counter32
       MAX-ACCESS read-only
       STATUS current
       DESCRIPTION
           "Activity volume."
       ::= {acPMMediaRealmPacketsRxEntry 4}



     -- ****************************************
     -- acPMMediaRealmVERealmPacketDelay table declaration
     -- ****************************************
     acPMMediaRealmVERealmPacketDelayTable OBJECT-TYPE
       SYNTAX SEQUENCE OF AcPMMediaRealmVERealmPacketDelayEntry
       MAX-ACCESS not-accessible
       STATUS current
       DESCRIPTION
           "Performance Monitoring VERealmPacketDelay"
       ::= {acPMMediaRealm  5}



     -- ****************************************
     -- acPMMediaRealmVERealmPacketDelay table entry
     -- ****************************************
     acPMMediaRealmVERealmPacketDelayEntry OBJECT-TYPE
       SYNTAX AcPMMediaRealmVERealmPacketDelayEntry
       MAX-ACCESS not-accessible
       STATUS current
       DESCRIPTION
           ""
       INDEX {acPMMediaRealmVERealmPacketDelayMediaRealmNum,acPMMediaRealmVERealmPacketDelayInterval}
       ::= {acPMMediaRealmVERealmPacketDelayTable 1}



     -- ****************************************
     -- acPMMediaRealmVERealmPacketDelay TABLE
     -- ****************************************
     AcPMMediaRealmVERealmPacketDelayEntry ::= SEQUENCE {
       acPMMediaRealmVERealmPacketDelayMediaRealmNum   Unsigned32,
       acPMMediaRealmVERealmPacketDelayInterval        Unsigned32,
       acPMMediaRealmVERealmPacketDelayVal             Counter32,
       acPMMediaRealmVERealmPacketDelayAverage         Integer32,
       acPMMediaRealmVERealmPacketDelayMax             Integer32,
       acPMMediaRealmVERealmPacketDelayMin             Integer32
     }



     acPMMediaRealmVERealmPacketDelayMediaRealmNum OBJECT-TYPE
       SYNTAX Unsigned32 (0..63)
       MAX-ACCESS not-accessible
       STATUS current
       DESCRIPTION
           "Media Realm number.
0 is the first Media Realm."
       ::= {acPMMediaRealmVERealmPacketDelayEntry 1}



     acPMMediaRealmVERealmPacketDelayInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmVERealmPacketDelayEntry 2}



     acPMMediaRealmVERealmPacketDelayVal OBJECT-TYPE
       SYNTAX Counter32
       MAX-ACCESS read-only
       STATUS current
       DESCRIPTION
           "Value of gauge or counter."
       ::= {acPMMediaRealmVERealmPacketDelayEntry 3}



     acPMMediaRealmVERealmPacketDelayAverage OBJECT-TYPE
       SYNTAX Integer32 (-1..2150000000)
       MAX-ACCESS read-only
       STATUS current
       DESCRIPTION
           "Average value with in the period time."
       ::= {acPMMediaRealmVERealmPacketDelayEntry 4}



     acPMMediaRealmVERealmPacketDelayMax OBJECT-TYPE
       SYNTAX Integer32 (-1..2150000000)
       MAX-ACCESS read-only
       STATUS current
       DESCRIPTION
           "Maximum value with in the period time."
       ::= {acPMMediaRealmVERealmPacketDelayEntry 5}



     acPMMediaRealmVERealmPacketDelayMin OBJECT-TYPE
       SYNTAX Integer32 (-1..2150000000)
       MAX-ACCESS read-only
       STATUS current
       DESCRIPTION
           "Minimum value with in the period time."
       ::= {acPMMediaRealmVERealmPacketDelayEntry 6}



     -- ****************************************
     -- acPMMediaRealmVERealmPacketJitter table declaration
     -- ****************************************
     acPMMediaRealmVERealmPacketJitterTable OBJECT-TYPE
       SYNTAX SEQUENCE OF AcPMMediaRealmVERealmPacketJitterEntry
       MAX-ACCESS not-accessible
       STATUS current
       DESCRIPTION
           "Performance Monitoring VERealmPacketJitter"
       ::= {acPMMediaRealm  6}



     -- ****************************************
     -- acPMMediaRealmVERealmPacketJitter table entry
     -- ****************************************
     acPMMediaRealmVERealmPacketJitterEntry OBJECT-TYPE
       SYNTAX AcPMMediaRealmVERealmPacketJitterEntry
       MAX-ACCESS not-accessible
       STATUS current
       DESCRIPTION
           ""
       INDEX {acPMMediaRealmVERealmPacketJitterMediaRealmNum,acPMMediaRealmVERealmPacketJitterInterval}
       ::= {acPMMediaRealmVERealmPacketJitterTable 1}



     -- ****************************************
     -- acPMMediaRealmVERealmPacketJitter TABLE
     -- ****************************************
     AcPMMediaRealmVERealmPacketJitterEntry ::= SEQUENCE {
       acPMMediaRealmVERealmPacketJitterMediaRealmNum  Unsigned32,
       acPMMediaRealmVERealmPacketJitterInterval       Unsigned32,
       acPMMediaRealmVERealmPacketJitterVal            Counter32,
       acPMMediaRealmVERealmPacketJitterAverage        Integer32,
       acPMMediaRealmVERealmPacketJitterMax            Integer32,
       acPMMediaRealmVERealmPacketJitterMin            Integer32
     }



     acPMMediaRealmVERealmPacketJitterMediaRealmNum OBJECT-TYPE
       SYNTAX Unsigned32 (0..63)
       MAX-ACCESS not-accessible
       STATUS current
       DESCRIPTION
           "Media Realm number.
0 is the first Media Realm."
       ::= {acPMMediaRealmVERealmPacketJitterEntry 1}



     acPMMediaRealmVERealmPacketJitterInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmVERealmPacketJitterEntry 2}



     acPMMediaRealmVERealmPacketJitterVal OBJECT-TYPE
       SYNTAX Counter32
       MAX-ACCESS read-only
       STATUS current
       DESCRIPTION
           "Value of gauge or counter."
       ::= {acPMMediaRealmVERealmPacketJitterEntry 3}



     acPMMediaRealmVERealmPacketJitterAverage OBJECT-TYPE
       SYNTAX Integer32 (-1..2150000000)
       MAX-ACCESS read-only
       STATUS current
       DESCRIPTION
           "Average value with in the period time."
       ::= {acPMMediaRealmVERealmPacketJitterEntry 4}



     acPMMediaRealmVERealmPacketJitterMax OBJECT-TYPE
       SYNTAX Integer32 (-1..2150000000)
       MAX-ACCESS read-only
       STATUS current
       DESCRIPTION
           "Maximum value with in the period time."
       ::= {acPMMediaRealmVERealmPacketJitterEntry 5}



     acPMMediaRealmVERealmPacketJitterMin OBJECT-TYPE
       SYNTAX Integer32 (-1..2150000000)
       MAX-ACCESS read-only
       STATUS current
       DESCRIPTION
           "Minimum value with in the period time."
       ::= {acPMMediaRealmVERealmPacketJitterEntry 6}



     -- ****************************************
     -- acPMMediaRealmRealmMOS table declaration
     -- ****************************************
     acPMMediaRealmRealmMOSTable OBJECT-TYPE
       SYNTAX SEQUENCE OF AcPMMediaRealmRealmMOSEntry
       MAX-ACCESS not-accessible
       STATUS current
       DESCRIPTION
           "Performance Monitoring RealmMOS"
       ::= {acPMMediaRealm  7}



     -- ****************************************
     -- acPMMediaRealmRealmMOS table entry
     -- ****************************************
     acPMMediaRealmRealmMOSEntry OBJECT-TYPE
       SYNTAX AcPMMediaRealmRealmMOSEntry
       MAX-ACCESS not-accessible
       STATUS current
       DESCRIPTION
           ""
       INDEX {acPMMediaRealmRealmMOSMediaRealmNum,acPMMediaRealmRealmMOSInterval}
       ::= {acPMMediaRealmRealmMOSTable 1}



     -- ****************************************
     -- acPMMediaRealmRealmMOS TABLE
     -- ****************************************
     AcPMMediaRealmRealmMOSEntry ::= SEQUENCE {
       acPMMediaRealmRealmMOSMediaRealmNum             Unsigned32,
       acPMMediaRealmRealmMOSInterval                  Unsigned32,
       acPMMediaRealmRealmMOSVal                       Counter32,
       acPMMediaRealmRealmMOSAverage                   Integer32,
       acPMMediaRealmRealmMOSMax                       Integer32,
       acPMMediaRealmRealmMOSMin                       Integer32
     }



     acPMMediaRealmRealmMOSMediaRealmNum OBJECT-TYPE
       SYNTAX Unsigned32 (0..63)
       MAX-ACCESS not-accessible
       STATUS current
       DESCRIPTION
           "Media Realm number.
0 is the first Media Realm."
       ::= {acPMMediaRealmRealmMOSEntry 1}



     acPMMediaRealmRealmMOSInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmRealmMOSEntry 2}



     acPMMediaRealmRealmMOSVal OBJECT-TYPE
       SYNTAX Counter32
       MAX-ACCESS read-only
       STATUS current
       DESCRIPTION
           "Value of gauge or counter."
       ::= {acPMMediaRealmRealmMOSEntry 3}



     acPMMediaRealmRealmMOSAverage OBJECT-TYPE
       SYNTAX Integer32 (-1..2150000000)
       MAX-ACCESS read-only
       STATUS current
       DESCRIPTION
           "Average value with in the period time."
       ::= {acPMMediaRealmRealmMOSEntry 4}



     acPMMediaRealmRealmMOSMax OBJECT-TYPE
       SYNTAX Integer32 (-1..2150000000)
       MAX-ACCESS read-only
       STATUS current
       DESCRIPTION
           "Maximum value with in the period time."
       ::= {acPMMediaRealmRealmMOSEntry 5}



     acPMMediaRealmRealmMOSMin OBJECT-TYPE
       SYNTAX Integer32 (-1..2150000000)
       MAX-ACCESS read-only
       STATUS current
       DESCRIPTION
           "Minimum value with in the period time."
       ::= {acPMMediaRealmRealmMOSEntry 6}



     -- ****************************************
     -- acPMMediaRealmBwRx table declaration
     -- ****************************************
     acPMMediaRealmBwRxTable OBJECT-TYPE
       SYNTAX SEQUENCE OF AcPMMediaRealmBwRxEntry
       MAX-ACCESS not-accessible
       STATUS current
       DESCRIPTION
           "Performance Monitoring MediaRealmBwRx"
       ::= {acPMMediaRealm  8}



     -- ****************************************
     -- acPMMediaRealmBwRx table entry
     -- ****************************************
     acPMMediaRealmBwRxEntry OBJECT-TYPE
       SYNTAX AcPMMediaRealmBwRxEntry
       MAX-ACCESS not-accessible
       STATUS current
       DESCRIPTION
           ""
       INDEX {acPMMediaRealmBwRxMediaRealmNum,acPMMediaRealmBwRxInterval}
       ::= {acPMMediaRealmBwRxTable 1}



     -- ****************************************
     -- acPMMediaRealmBwRx TABLE
     -- ****************************************
     AcPMMediaRealmBwRxEntry ::= SEQUENCE {
       acPMMediaRealmBwRxMediaRealmNum                 Unsigned32,
       acPMMediaRealmBwRxInterval                      Unsigned32,
       acPMMediaRealmBwRxVal                           Counter32,
       acPMMediaRealmBwRxAverage                       Integer32,
       acPMMediaRealmBwRxMax                           Integer32,
       acPMMediaRealmBwRxMin                           Integer32,
       acPMMediaRealmBwRxTimeBelowLowThreshold         Integer32,
       acPMMediaRealmBwRxTimeBetweenThresholds         Integer32,
       acPMMediaRealmBwRxTimeAboveHighThreshold        Integer32,
       acPMMediaRealmBwRxFullDayAverage                Integer32,
       acPMMediaRealmBwRxTotal                         Counter32
     }



     acPMMediaRealmBwRxMediaRealmNum OBJECT-TYPE
       SYNTAX Unsigned32 (0..63)
       MAX-ACCESS not-accessible
       STATUS current
       DESCRIPTION
           "Media Realm number.
0 is the first Media Realm."
       ::= {acPMMediaRealmBwRxEntry 1}



     acPMMediaRealmBwRxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmBwRxEntry 2}



     acPMMediaRealmBwRxVal OBJECT-TYPE
       SYNTAX Counter32
       MAX-ACCESS read-only
       STATUS current
       DESCRIPTION
           "Value of gauge or counter."
       ::= {acPMMediaRealmBwRxEntry 3}



     acPMMediaRealmBwRxAverage OBJECT-TYPE
       SYNTAX Integer32 (-1..2150000000)
       MAX-ACCESS read-only
       STATUS current
       DESCRIPTION
           "Average value with in the period time."
       ::= {acPMMediaRealmBwRxEntry 4}



     acPMMediaRealmBwRxMax OBJECT-TYPE
       SYNTAX Integer32 (-1..2150000000)
       MAX-ACCESS read-only
       STATUS current
       DESCRIPTION
           "Maximum value with in the period time."
       ::= {acPMMediaRealmBwRxEntry 5}



     acPMMediaRealmBwRxMin OBJECT-TYPE
       SYNTAX Integer32 (-1..2150000000)
       MAX-ACCESS read-only
       STATUS current
       DESCRIPTION
           "Minimum value with in the period time."
       ::= {acPMMediaRealmBwRxEntry 6}



     acPMMediaRealmBwRxTimeBelowLowThreshold OBJECT-TYPE
       SYNTAX Integer32 (-1..100)
       MAX-ACCESS read-only
       STATUS current
       DESCRIPTION
           "Percent of interval time for which gauge is below what was determined
as the low threshold."
       ::= {acPMMediaRealmBwRxEntry 7}



     acPMMediaRealmBwRxTimeBetweenThresholds OBJECT-TYPE
       SYNTAX Integer32 (-1..100)
       MAX-ACCESS read-only
       STATUS current
       DESCRIPTION
           "Percent of interval time for which gauge is above what was determined
as the high threshold."
       ::= {acPMMediaRealmBwRxEntry 8}



     acPMMediaRealmBwRxTimeAboveHighThreshold OBJECT-TYPE
       SYNTAX Integer32 (-1..100)
       MAX-ACCESS read-only
       STATUS current
       DESCRIPTION
           "Percent of interval time for which gauge is between what were
determined as the low and high thresholds."
       ::= {acPMMediaRealmBwRxEntry 9}



     acPMMediaRealmBwRxFullDayAverage OBJECT-TYPE
       SYNTAX Integer32 (-1..2150000000)
       MAX-ACCESS read-only
       STATUS current
       DESCRIPTION
           "The average of full 24 hours."
       ::= {acPMMediaRealmBwRxEntry 10}



     acPMMediaRealmBwRxTotal OBJECT-TYPE
       SYNTAX Counter32
       MAX-ACCESS read-only
       STATUS current
       DESCRIPTION
           "Activity volume."
       ::= {acPMMediaRealmBwRxEntry 11}



     -- ****************************************
     -- acPMMediaRealmBwTx table declaration
     -- ****************************************
     acPMMediaRealmBwTxTable OBJECT-TYPE
       SYNTAX SEQUENCE OF AcPMMediaRealmBwTxEntry
       MAX-ACCESS not-accessible
       STATUS current
       DESCRIPTION
           "Performance Monitoring MediaRealmBwTx"
       ::= {acPMMediaRealm  9}



     -- ****************************************
     -- acPMMediaRealmBwTx table entry
     -- ****************************************
     acPMMediaRealmBwTxEntry OBJECT-TYPE
       SYNTAX AcPMMediaRealmBwTxEntry
       MAX-ACCESS not-accessible
       STATUS current
       DESCRIPTION
           ""
       INDEX {acPMMediaRealmBwTxMediaRealmNum,acPMMediaRealmBwTxInterval}
       ::= {acPMMediaRealmBwTxTable 1}



     -- ****************************************
     -- acPMMediaRealmBwTx TABLE
     -- ****************************************
     AcPMMediaRealmBwTxEntry ::= SEQUENCE {
       acPMMediaRealmBwTxMediaRealmNum                 Unsigned32,
       acPMMediaRealmBwTxInterval                      Unsigned32,
       acPMMediaRealmBwTxVal                           Counter32,
       acPMMediaRealmBwTxAverage                       Integer32,
       acPMMediaRealmBwTxMax                           Integer32,
       acPMMediaRealmBwTxMin                           Integer32,
       acPMMediaRealmBwTxTimeBelowLowThreshold         Integer32,
       acPMMediaRealmBwTxTimeBetweenThresholds         Integer32,
       acPMMediaRealmBwTxTimeAboveHighThreshold        Integer32,
       acPMMediaRealmBwTxFullDayAverage                Integer32,
       acPMMediaRealmBwTxTotal                         Counter32
     }



     acPMMediaRealmBwTxMediaRealmNum OBJECT-TYPE
       SYNTAX Unsigned32 (0..63)
       MAX-ACCESS not-accessible
       STATUS current
       DESCRIPTION
           "Media Realm number.
0 is the first Media Realm."
       ::= {acPMMediaRealmBwTxEntry 1}



     acPMMediaRealmBwTxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmBwTxEntry 2}



     acPMMediaRealmBwTxVal OBJECT-TYPE
       SYNTAX Counter32
       MAX-ACCESS read-only
       STATUS current
       DESCRIPTION
           "Value of gauge or counter."
       ::= {acPMMediaRealmBwTxEntry 3}



     acPMMediaRealmBwTxAverage OBJECT-TYPE
       SYNTAX Integer32 (-1..2150000000)
       MAX-ACCESS read-only
       STATUS current
       DESCRIPTION
           "Average value with in the period time."
       ::= {acPMMediaRealmBwTxEntry 4}



     acPMMediaRealmBwTxMax OBJECT-TYPE
       SYNTAX Integer32 (-1..2150000000)
       MAX-ACCESS read-only
       STATUS current
       DESCRIPTION
           "Maximum value with in the period time."
       ::= {acPMMediaRealmBwTxEntry 5}



     acPMMediaRealmBwTxMin OBJECT-TYPE
       SYNTAX Integer32 (-1..2150000000)
       MAX-ACCESS read-only
       STATUS current
       DESCRIPTION
           "Minimum value with in the period time."
       ::= {acPMMediaRealmBwTxEntry 6}



     acPMMediaRealmBwTxTimeBelowLowThreshold OBJECT-TYPE
       SYNTAX Integer32 (-1..100)
       MAX-ACCESS read-only
       STATUS current
       DESCRIPTION
           "Percent of interval time for which gauge is below what was determined
as the low threshold."
       ::= {acPMMediaRealmBwTxEntry 7}



     acPMMediaRealmBwTxTimeBetweenThresholds OBJECT-TYPE
       SYNTAX Integer32 (-1..100)
       MAX-ACCESS read-only
       STATUS current
       DESCRIPTION
           "Percent of interval time for which gauge is above what was determined
as the high threshold."
       ::= {acPMMediaRealmBwTxEntry 8}



     acPMMediaRealmBwTxTimeAboveHighThreshold OBJECT-TYPE
       SYNTAX Integer32 (-1..100)
       MAX-ACCESS read-only
       STATUS current
       DESCRIPTION
           "Percent of interval time for which gauge is between what were
determined as the low and high thresholds."
       ::= {acPMMediaRealmBwTxEntry 9}



     acPMMediaRealmBwTxFullDayAverage OBJECT-TYPE
       SYNTAX Integer32 (-1..2150000000)
       MAX-ACCESS read-only
       STATUS current
       DESCRIPTION
           "The average of full 24 hours."
       ::= {acPMMediaRealmBwTxEntry 10}



     acPMMediaRealmBwTxTotal OBJECT-TYPE
       SYNTAX Counter32
       MAX-ACCESS read-only
       STATUS current
       DESCRIPTION
           "Activity volume."
       ::= {acPMMediaRealmBwTxEntry 11}



     -- ****************************************
     -- acPMMediaRealmPacketLossRx table declaration
     -- ****************************************
     acPMMediaRealmPacketLossRxTable OBJECT-TYPE
       SYNTAX SEQUENCE OF AcPMMediaRealmPacketLossRxEntry
       MAX-ACCESS not-accessible
       STATUS current
       DESCRIPTION
           "Performance Monitoring MediaRealmPacketLossRx"
       ::= {acPMMediaRealm  10}



     -- ****************************************
     -- acPMMediaRealmPacketLossRx table entry
     -- ****************************************
     acPMMediaRealmPacketLossRxEntry OBJECT-TYPE
       SYNTAX AcPMMediaRealmPacketLossRxEntry
       MAX-ACCESS not-accessible
       STATUS current
       DESCRIPTION
           ""
       INDEX {acPMMediaRealmPacketLossRxMediaRealmNum,acPMMediaRealmPacketLossRxInterval}
       ::= {acPMMediaRealmPacketLossRxTable 1}



     -- ****************************************
     -- acPMMediaRealmPacketLossRx TABLE
     -- ****************************************
     AcPMMediaRealmPacketLossRxEntry ::= SEQUENCE {
       acPMMediaRealmPacketLossRxMediaRealmNum         Unsigned32,
       acPMMediaRealmPacketLossRxInterval              Unsigned32,
       acPMMediaRealmPacketLossRxVal                   Counter32,
       acPMMediaRealmPacketLossRxVolume                Counter32
     }



     acPMMediaRealmPacketLossRxMediaRealmNum OBJECT-TYPE
       SYNTAX Unsigned32 (0..63)
       MAX-ACCESS not-accessible
       STATUS current
       DESCRIPTION
           "Media Realm number.
0 is the first Media Realm."
       ::= {acPMMediaRealmPacketLossRxEntry 1}



     acPMMediaRealmPacketLossRxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmPacketLossRxEntry 2}



     acPMMediaRealmPacketLossRxVal OBJECT-TYPE
       SYNTAX Counter32
       MAX-ACCESS read-only
       STATUS current
       DESCRIPTION
           "Value of gauge or counter."
       ::= {acPMMediaRealmPacketLossRxEntry 3}



     acPMMediaRealmPacketLossRxVolume OBJECT-TYPE
       SYNTAX Counter32
       MAX-ACCESS read-only
       STATUS current
       DESCRIPTION
           "Activity volume."
       ::= {acPMMediaRealmPacketLossRxEntry 4}



     -- ****************************************
     -- acPMMediaRealmPacketLossTx table declaration
     -- ****************************************
     acPMMediaRealmPacketLossTxTable OBJECT-TYPE
       SYNTAX SEQUENCE OF AcPMMediaRealmPacketLossTxEntry
       MAX-ACCESS not-accessible
       STATUS current
       DESCRIPTION
           "Performance Monitoring MediaRealmPacketLossTx"
       ::= {acPMMediaRealm  11}



     -- ****************************************
     -- acPMMediaRealmPacketLossTx table entry
     -- ****************************************
     acPMMediaRealmPacketLossTxEntry OBJECT-TYPE
       SYNTAX AcPMMediaRealmPacketLossTxEntry
       MAX-ACCESS not-accessible
       STATUS current
       DESCRIPTION
           ""
       INDEX {acPMMediaRealmPacketLossTxMediaRealmNum,acPMMediaRealmPacketLossTxInterval}
       ::= {acPMMediaRealmPacketLossTxTable 1}



     -- ****************************************
     -- acPMMediaRealmPacketLossTx TABLE
     -- ****************************************
     AcPMMediaRealmPacketLossTxEntry ::= SEQUENCE {
       acPMMediaRealmPacketLossTxMediaRealmNum         Unsigned32,
       acPMMediaRealmPacketLossTxInterval              Unsigned32,
       acPMMediaRealmPacketLossTxVal                   Counter32,
       acPMMediaRealmPacketLossTxVolume                Counter32
     }



     acPMMediaRealmPacketLossTxMediaRealmNum OBJECT-TYPE
       SYNTAX Unsigned32 (0..63)
       MAX-ACCESS not-accessible
       STATUS current
       DESCRIPTION
           "Media Realm number.
0 is the first Media Realm."
       ::= {acPMMediaRealmPacketLossTxEntry 1}



     acPMMediaRealmPacketLossTxInterval OBJECT-TYPE
       SYNTAX Unsigned32 (0..2)
       MAX-ACCESS not-accessible
       STATUS current
       DESCRIPTION
           "Interval index.
0 - current period (incomplete monitoring - mid period).
1 - Last full period.
2 - One before last."
       ::= {acPMMediaRealmPacketLossTxEntry 2}



     acPMMediaRealmPacketLossTxVal OBJECT-TYPE
       SYNTAX Counter32
       MAX-ACCESS read-only
       STATUS current
       DESCRIPTION
           "Value of gauge or counter."
       ::= {acPMMediaRealmPacketLossTxEntry 3}



     acPMMediaRealmPacketLossTxVolume OBJECT-TYPE
       SYNTAX Counter32
       MAX-ACCESS read-only
       STATUS current
       DESCRIPTION
           "Activity volume."
       ::= {acPMMediaRealmPacketLossTxEntry 4}





END
