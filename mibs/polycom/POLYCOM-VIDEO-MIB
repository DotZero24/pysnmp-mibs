-- Polycom Video MIB definitions
--    Version: 2.0
--       Date: 1/7/1998
--       VSX Revision: 1/9/2004

POLYCOM-VIDEO-MIB DEFINITIONS ::= BEGIN

	IMPORTS
		enterprises
			FROM RFC1155-SMI
		OBJECT-TYPE
			FROM RFC-1212
		DisplayString
			FROM RFC1213-MIB
		TRAP-TYPE
			FROM RFC-1215;

	-- - - - - - - - -
	-- Global Defines
	-- - - - - - - - -
	polycom		OBJECT IDENTIFIER ::=	{ enterprises 2684 }
	polycomVideo	OBJECT IDENTIFIER ::=	{ polycom 1 }
	polycomAudio	OBJECT IDENTIFIER ::=	{ polycom 2 }
	polycomData	OBJECT IDENTIFIER ::=	{ polycom 3 }

	-- - - - - - - - -
	-- Audio Products
	-- - - - - - - - -
	-- none defined here

	-- - - - - - - - -
	-- Video Products
	-- - - - - - - - -
	polycomViewStation		OBJECT IDENTIFIER ::=	{ polycomVideo 1 }

	-- - - - - - - - -
	-- Data Products
	-- - - - - - - - -
	-- none defined here

	-- - - - - - - - -
	--
	-- VSX
	--
	-- - - - - - - - -
	polycomVSAuthLocation	OBJECT-TYPE
		SYNTAX		INTEGER
		ACCESS		read-only
		STATUS		mandatory
		DESCRIPTION	"The origin of the last attempted admin login. Valid values are 0(local), 1(ftp), 2(telnet) or 3(web)."
		::=	{ polycomViewStation 1 }

 	polycomVSPhoneNumber	OBJECT-TYPE
		SYNTAX		DisplayString
		ACCESS		read-only
		STATUS		mandatory
		DESCRIPTION	"The far site number."
		::=	{ polycomViewStation 2 }

	polycomVSReason		OBJECT-TYPE
		SYNTAX		DisplayString
		ACCESS		read-only
		STATUS		mandatory
		DESCRIPTION	"The cause code associated with a call disconnecting."
		::=	{ polycomViewStation 3 }

	polycomVSPlead		OBJECT-TYPE
		SYNTAX		DisplayString
		ACCESS		read-only
		STATUS		mandatory
		DESCRIPTION	"The contact phone number for the user who sent the help request to GMS."
		::=	{ polycomViewStation 4 }

	polycomVSMicData		OBJECT-TYPE
		SYNTAX		DisplayString
		ACCESS		read-only
		STATUS		mandatory
		DESCRIPTION	"The current total connected mic count or VTX status."
		::=	{ polycomViewStation 5 }

	polycomVSAutoAnswerSetting		OBJECT-TYPE
		SYNTAX		DisplayString
		ACCESS		read-only
		STATUS		mandatory
		DESCRIPTION	"The current user-specified auto answer setting (i.e. Yes, No, Do_Not_Disturb)."
		::=	{ polycomViewStation 6 }

	polycomVSTimeServerAddress		OBJECT-TYPE
		SYNTAX		DisplayString
		ACCESS		read-only
		STATUS		mandatory
		DESCRIPTION	"The current time server address."
		::=	{ polycomViewStation 7 }

	polycomVSTimeServerSetting		OBJECT-TYPE
		SYNTAX		DisplayString
		ACCESS		read-only
		STATUS		mandatory
		DESCRIPTION	"The current time server setting."
		::=	{ polycomViewStation 8 }

	polycomVSGDSAddress		OBJECT-TYPE
		SYNTAX		DisplayString
		ACCESS		read-only
		STATUS		mandatory
		DESCRIPTION	"The current global directory server address related to a certain GDS event."
		::=	{ polycomViewStation 9 }

	polycomVSGatekeeperAddress		OBJECT-TYPE
		SYNTAX		DisplayString
		ACCESS		read-only
		STATUS		mandatory
		DESCRIPTION	"The current gatekeeper address related to a certain gatekeeper event."
		::=	{ polycomViewStation 10 }

	polycomVSPreviousIPAddress		OBJECT-TYPE
		SYNTAX		DisplayString
		ACCESS		read-only
		STATUS		mandatory
		DESCRIPTION	"The previous IP address."
		::=	{ polycomViewStation 11 }

	polycomVSCurrentIPAddress		OBJECT-TYPE
		SYNTAX		DisplayString
		ACCESS		read-only
		STATUS		mandatory
		DESCRIPTION	"The current IP address."
		::=	{ polycomViewStation 12 }

	polycomVSPreviousNicType		OBJECT-TYPE
		SYNTAX		DisplayString
		ACCESS		read-only
		STATUS		mandatory
		DESCRIPTION	"The previous network interface card type."
		::=	{ polycomViewStation 13 }

	polycomVSCurrentNicType		OBJECT-TYPE
		SYNTAX		DisplayString
		ACCESS		read-only
		STATUS		mandatory
		DESCRIPTION	"The current network interface card type."
		::=	{ polycomViewStation 14 }

	polycomVSNicLineNumber		OBJECT-TYPE
		SYNTAX		DisplayString
		ACCESS		read-only
		STATUS		mandatory
		DESCRIPTION	"The V.35 or ISDN line number related to a certain line event."
		::=	{ polycomViewStation 15 }

	polycomVSPreviousNicLineCount		OBJECT-TYPE
		SYNTAX		DisplayString
		ACCESS		read-only
		STATUS		mandatory
		DESCRIPTION	"The total nic line count (i.e. ISDN Quad BRI = 4 lines)."
		::=	{ polycomViewStation 16 }

	polycomVSCurrentNicLineCount		OBJECT-TYPE
		SYNTAX		DisplayString
		ACCESS		read-only
		STATUS		mandatory
		DESCRIPTION	"The current nic line count (i.e. ISDN Quad BRI = 4 lines)."
		::=	{ polycomViewStation 17 }

	polycomVSV35PortsEnabled		OBJECT-TYPE
		SYNTAX		DisplayString
		ACCESS		read-only
		STATUS		mandatory
		DESCRIPTION	"The current user specified V.35 ports enabled setting (i.e. 1, 1+2, none)."
		::=	{ polycomViewStation 18 }

   	polycomVSAuthClientAddress	OBJECT-TYPE
		SYNTAX		DisplayString
		ACCESS		read-only
		STATUS		mandatory
		DESCRIPTION	"The address of the login client."
		::=	{ polycomViewStation 19 }

   	polycomVSUPnPStatus	OBJECT-TYPE
		SYNTAX		DisplayString
		ACCESS		read-only
		STATUS		mandatory
		DESCRIPTION	"The current status of the UPnP device."
		::=	{ polycomViewStation 20 }

   	polycomVSPercentPacketLoss	OBJECT-TYPE
		SYNTAX		DisplayString
		ACCESS		read-only
		STATUS		mandatory
		DESCRIPTION	"The current combined (audio/video) average percentage packet loss when in an H.323 call."
		::=	{ polycomViewStation 21 }

   	polycomVSJitter	OBJECT-TYPE
		SYNTAX		DisplayString
		ACCESS		read-only
		STATUS		mandatory
		DESCRIPTION	"The current combined (audio/video) cumulative average jitter (in ms) when in an H.323 call."
		::=	{ polycomViewStation 22 }

   	polycomVSLatency	OBJECT-TYPE
		SYNTAX		DisplayString
		ACCESS		read-only
		STATUS		mandatory
		DESCRIPTION	"The current average latency based on round trip delay when in an H.323 call."
		::=	{ polycomViewStation 23 }
	-- - - - - - - - -
	--
	-- Trap Types
	--
	-- - - - - - - - -
	loginOK TRAP-TYPE
		ENTERPRISE	polycomViewStation
		VARIABLES	{ polycomVSAuthLocation, polycomVSAuthClientAddress }
		DESCRIPTION	"Sent when an administrator logs in via embedded UI, ftp, telnet or web."
		::= 1

	loginFail TRAP-TYPE
		ENTERPRISE	polycomViewStation
		VARIABLES	{ polycomVSAuthLocation, polycomVSAuthClientAddress }
		DESCRIPTION	"Sent when an attempt to log in as an administrator fails via embedded UI, ftp, telnet or web."
		::= 2

	lowBattery TRAP-TYPE
		ENTERPRISE	polycomViewStation
		DESCRIPTION	"Sent when the remote has a low battery."
		::= 3

	callUp TRAP-TYPE
		ENTERPRISE	polycomViewStation
		VARIABLES	{ polycomVSPhoneNumber }
		DESCRIPTION	"When a call is successfully connected, this notifies the SNMP manager of the far site number."
		::= 4

	callDown TRAP-TYPE
		ENTERPRISE	polycomViewStation
		VARIABLES	{ polycomVSPhoneNumber }
		DESCRIPTION	"When a call is disconnected with normal call clearing, this notifies the SNMP manager of the far site number."
		::= 5

	callFail TRAP-TYPE
		ENTERPRISE	polycomViewStation
		VARIABLES	{ polycomVSReason, polycomVSPhoneNumber }
		DESCRIPTION	"When a call is disconnected with a cause code other than normal, this notifies the SNMP manager
				of the reason."
		::= 6

	userAssist TRAP-TYPE
		ENTERPRISE	polycomViewStation
		VARIABLES	{ polycomVSPlead }
		DESCRIPTION	"Sent when a user sends a help request to GMS."
		::= 7

	visualConcertUp TRAP-TYPE
		ENTERPRISE	polycomViewStation
		DESCRIPTION	"Sent when a visual concert pod is connected."
		::= 8

	visualConcertOff TRAP-TYPE
		ENTERPRISE	polycomViewStation
		DESCRIPTION	"Sent when a visual concert pod is disconnected."
		::= 9

	micChange TRAP-TYPE
		ENTERPRISE	polycomViewStation
		VARIABLES	{ polycomVSMicData }
		DESCRIPTION	"Sent when a mic pod or VTX is connected or disconnected and includes the total mic count."
		::= 10

	autoAnswerChange TRAP-TYPE
		ENTERPRISE	polycomViewStation
		VARIABLES	{ polycomVSAutoAnswerSetting }
		DESCRIPTION	"Sent when the auto answer setting is changed."
		::= 11

	timeServerUp TRAP-TYPE
		ENTERPRISE	polycomViewStation
		VARIABLES	{ polycomVSTimeServerAddress }
		DESCRIPTION	"Sent when the time server successfully connects."
		::= 12

	timeServerDown TRAP-TYPE
		ENTERPRISE	polycomViewStation
		VARIABLES	{ polycomVSTimeServerAddress }
		DESCRIPTION	"Sent when the time server is enabled but does not connect correctly."
		::= 13

	timeServerOn TRAP-TYPE
		ENTERPRISE	polycomViewStation
		VARIABLES	{ polycomVSTimeServerSetting }
		DESCRIPTION	"Sent when the time server is enabled."
		::= 14

	timeServerOff TRAP-TYPE
		ENTERPRISE	polycomViewStation
		DESCRIPTION	"Sent when the time server is disabled."
		::= 15

	gdsUp TRAP-TYPE
		ENTERPRISE	polycomViewStation
		VARIABLES	{ polycomVSGDSAddress }
		DESCRIPTION	"Sent when a global directory server successfully connects."
		::= 16

	gdsDown TRAP-TYPE
		ENTERPRISE	polycomViewStation
		VARIABLES	{ polycomVSGDSAddress }
		DESCRIPTION	"Sent when a global directory server is enabled, but not connected correctly."
		::= 17

	gdsOff TRAP-TYPE
		ENTERPRISE	polycomViewStation
		VARIABLES	{ polycomVSGDSAddress }
		DESCRIPTION	"Sent when a global directory server is disabled."
		::= 18

	gatekeeperReg TRAP-TYPE
		ENTERPRISE	polycomViewStation
		VARIABLES	{ polycomVSGatekeeperAddress }
		DESCRIPTION	"Sent when a gatekeeper is registered successfully."
		::= 19

	gatekeeperDown TRAP-TYPE
		ENTERPRISE	polycomViewStation
		VARIABLES	{ polycomVSGatekeeperAddress }
		DESCRIPTION	"Sent when a gatekeeper is specified, but not registered successfully."
		::= 20

	gatekeeperOff TRAP-TYPE
		ENTERPRISE	polycomViewStation
		DESCRIPTION	"Sent when a gatekeeper is disabled."
		::= 21

	ipAddressChange TRAP-TYPE
		ENTERPRISE	polycomViewStation
		VARIABLES	{ polycomVSPreviousIPAddress, polycomVSCurrentIPAddress }
		DESCRIPTION	"Sent when the system IP address has changed."
		::= 22

	interfaceTypeChange TRAP-TYPE
		ENTERPRISE	polycomViewStation
		VARIABLES	{ polycomVSPreviousNicType, polycomVSCurrentNicType }
		DESCRIPTION	"Sent when the system network interface card type has changed."
		::= 23

	lineEnabled TRAP-TYPE
		ENTERPRISE	polycomViewStation
		VARIABLES	{ polycomVSNicLineNumber }
		DESCRIPTION	"Sent when a V.35 or ISDN line has been enabled."
		::= 24

	lineDisabled TRAP-TYPE
		ENTERPRISE	polycomViewStation
		VARIABLES	{ polycomVSNicLineNumber }
		DESCRIPTION	"Sent when a V.35 or ISDN line has been disabled."
		::= 25

	lineUp TRAP-TYPE
		ENTERPRISE	polycomViewStation
		VARIABLES	{ polycomVSNicLineNumber }
		DESCRIPTION	"Sent when a V.35 or ISDN line has been enabled and becomes available for placing a call."
		::= 26

	lineDown TRAP-TYPE
		ENTERPRISE	polycomViewStation
		VARIABLES	{ polycomVSNicLineNumber }
		DESCRIPTION	"Sent when a V.35 or ISDN line has been enabled, but is not working correctly."
		::= 27

	v35PortsEnabled TRAP-TYPE
		ENTERPRISE	polycomViewStation
		VARIABLES	{ polycomVSV35PortsEnabled }
		DESCRIPTION	"Sent when the V.35 enabled ports setting has changed."
		::= 28

	lineCountChange TRAP-TYPE
		ENTERPRISE	polycomViewStation
		VARIABLES	{ polycomVSPreviousNicLineCount, polycomVSCurrentNicLineCount }
		DESCRIPTION	"Sent when the total of available V.35 or ISDN lines has changed."
		::= 29

	mainCameraUp TRAP-TYPE
		ENTERPRISE	polycomViewStation
		DESCRIPTION	"Sent when the main camera is working correctly."
		::= 30

	mainCameraDown TRAP-TYPE
		ENTERPRISE	polycomViewStation
		DESCRIPTION	"Sent when the main camera is not working correctly."
		::= 31

	upnpChange TRAP-TYPE
		ENTERPRISE	polycomViewStation
		VARIABLES	{ polycomVSUPnPStatus }
		DESCRIPTION	"Sent when the state of the UPnP device changes."
		::= 32

	percentPacketLossExcessive TRAP-TYPE
		ENTERPRISE	polycomViewStation
		VARIABLES	{ polycomVSPercentPacketLoss }
		DESCRIPTION	"Sent when the combined tx/rx percentage of packet loss exceeds 1 percent based on 1 minute samples."
		::= 33

	jitterExcessive TRAP-TYPE
		ENTERPRISE	polycomViewStation
		VARIABLES	{ polycomVSJitter }
		DESCRIPTION	"Sent when the combined tx/rx average jitter exceeds 35 ms based on 1 minute samples."
		::= 34

	latencyExcessive TRAP-TYPE
		ENTERPRISE	polycomViewStation
		VARIABLES	{ polycomVSLatency }
		DESCRIPTION	"Sent when the combined tx/rx average latency exceeds 150 ms based on 1 minute samples."
		::= 35
END
