--/*
-- *
-- * Copyright (c) 1997 - 2002 by Extreme Networks Inc.
-- *
-- *	  Extreme Networks
-- *      http://www.extremenetworks.com
-- *
-- * extracted from $Extreme_Id: extreme.mib,v 1.24.6.35 2006/01/09 15:15:18 build-sc Exp $
-- *
-- */
-- **********************************************************************
-- * Extreme 802.11f MIB.  Based on IEEE MIB with addition of ifIndex for
-- * demux.
-- **********************************************************************
EXTREMEdot11f-MIB DEFINITIONS ::= BEGIN
	IMPORTS

	MODULE-IDENTITY FROM SNMPv2-SMI
	extremeAP FROM EXTREME-BASE-MIB;


-- **********************************************************************
-- * MODULE IDENTITY
-- **********************************************************************

	extremeDot11f MODULE-IDENTITY
	LAST-UPDATED "0107020000Z"
	ORGANIZATION "Extreme Networks"
	CONTACT-INFO
		" "

	DESCRIPTION
	"This MIB module provides management of IAPP on a set of APs.
	 It is functionally identical to the IAPP MIB from the IEEE
	 with the addition of a new index."
    ::= { extremeAP 22 }

END
