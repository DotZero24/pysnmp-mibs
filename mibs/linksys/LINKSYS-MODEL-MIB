LINKSYS-MODEL-MIB DEFINITIONS ::= BEGIN

internet				OBJECT IDENTIFIER ::= { iso org(3) dod(6) 1 }
directory				OBJECT IDENTIFIER ::= { internet 1 }
mgmt					OBJECT IDENTIFIER ::= { internet 2 }
experimental			OBJECT IDENTIFIER ::= { internet 3 }
private					OBJECT IDENTIFIER ::= { internet 4 }
enterprises				OBJECT IDENTIFIER ::= { private 1 }
linksys					OBJECT IDENTIFIER ::= { enterprises 3955 }
common					OBJECT IDENTIFIER ::= { linksys 1 }
products				OBJECT IDENTIFIER ::= { linksys 2 }
snmpMgt					OBJECT IDENTIFIER ::= { linksys 3 }
commonMgt				OBJECT IDENTIFIER ::= { snmpMgt 1 }
internetAccessMgt		OBJECT IDENTIFIER ::= { snmpMgt 4 }
broadbandGateway		OBJECT IDENTIFIER ::= { internetAccessMgt 1 }



-- the Common Group

commonModelId OBJECT-TYPE
	SYNTAX		OwnerString
	ACCESS		read-only
	STATUS		mandatory
	DESCRIPTION
		" The hardware model ID of this managed node. "

	::= { common 1 }

commonSoftwareVer OBJECT-TYPE
	SYNTAX		OwnerString
	ACCESS		read-only
	STATUS		mandatory
	DESCRIPTION
		" The software version of this managed node. "

	::= { common 2 }

commonFirmwareVer OBJECT-TYPE
	SYNTAX		OwnerString
	ACCESS		read-only
	STATUS		mandatory
	DESCRIPTION
		" The firmware version of this managed node. "

	::= { common 3 }


-- the Common Management Group

mgtWarmStart OBJECT-TYPE
	SYNTAX		INTEGER { disable(0), enable(1) }
	ACCESS		read-write
	STATUS		mandatory
	DESCRIPTION
		" "

	::= { commonMgt 1 }

mgtFactoryReset OBJECT-TYPE
	SYNTAX		INTEGER { disable(0), enable(1) }
	ACCESS		read-write
	STATUS		mandatory
	DESCRIPTION
		" "

	::= { commonMgt 2 }

mgtAdministrator OBJECT-TYPE
	SYNTAX		OwnerString (SIZE(0..64))
	ACCESS		read-write
	STATUS		mandatory
	DESCRIPTION
		" "

	::= { commonMgt 3 }

mgtBootStatus OBJECT-TYPE
	SYNTAX		INTEGER { abnormal(0), normal(1) }
	ACCESS		read-only
	STATUS		mandatory
	DESCRIPTION
		" "

	::= { commonMgt 4 }

mgtRefreshMIB OBJECT-TYPE
	SYNTAX		INTEGER { none(0), apply(1) }
	ACCESS		read-write
	STATUS		mandatory
	DESCRIPTION
		"Refresh Enterprise MIB object data from RAM NV."

	::= { commonMgt 5 }

mgtUpdateNV OBJECT-TYPE
	SYNTAX		INTEGER { none(0), apply(1) }
	ACCESS		read-write
	STATUS		mandatory
	DESCRIPTION
		"Save Enterprise MIB Object data to RAM NV and Flash, and reboot system."

	::= { commonMgt 6 }


-- the Community Table

mgtCommunityTable OBJECT-TYPE
	SYNTAX		SEQUENCE OF MgtCommunityEntry
	ACCESS		not-accessible
	STATUS		mandatory
	DESCRIPTION
		" Table of access community. "

	::= { commonMgt 7 }

mgtCommunityEntry OBJECT-TYPE
	SYNTAX		MgtCommunityEntry
	ACCESS		not-accessible
	STATUS		mandatory
	DESCRIPTION
		" An entry in the table, containing read/write community names. "

	INDEX 		{ mgtCommunityIndex }
	::= { mgtCommunityTable 1 }

MgtCommunityEntry ::=
	SEQUENCE {
		mgtCommunityIndex		INTEGER,
		mgtCommunityName		OwnerString,
		mgtCommunityType		INTEGER
	}

mgtCommunityIndex OBJECT-TYPE
	SYNTAX		INTEGER
	ACCESS		read-only
	STATUS		mandatory
	DESCRIPTION
		" "

	::= { mgtCommunityEntry 1 }

mgtCommunityName OBJECT-TYPE
	SYNTAX		OwnerString (SIZE(0..32))
	ACCESS		read-write
	STATUS		mandatory
	DESCRIPTION
		" "

	::= { mgtCommunityEntry 2 }

mgtCommunityType OBJECT-TYPE
	SYNTAX		INTEGER { read-only(1), read-write(2) }
	ACCESS		read-write
	STATUS		mandatory
	DESCRIPTION
		" "

	::= { mgtCommunityEntry 3 }


-- the BroadBand broadbandGateway Management Group

hostName OBJECT-TYPE
	SYNTAX		OwnerString (SIZE(0..32))
	ACCESS		read-write
	STATUS		mandatory
	DESCRIPTION
		" "

	::= { broadbandGateway 1 }

domainName OBJECT-TYPE
	SYNTAX		OwnerString (SIZE(0..64))
	ACCESS		read-write
	STATUS		mandatory
	DESCRIPTION
		" "

	::= { broadbandGateway 2 }

netAddressLAN OBJECT-TYPE
	SYNTAX		IpAddress
	ACCESS		read-write
	STATUS		mandatory
	DESCRIPTION
		" "

	::= { broadbandGateway 3 }

physicalAddrLAN OBJECT-TYPE
	SYNTAX		PhysAddress
	ACCESS		read-only
	STATUS		mandatory
	DESCRIPTION
		" "

	::= { broadbandGateway 4 }

subnetMaskLAN OBJECT-TYPE
	SYNTAX		IpAddress
	ACCESS		read-write
	STATUS		mandatory
	DESCRIPTION
		" "

	::= { broadbandGateway 5 }

dhcpStatusWAN OBJECT-TYPE
	SYNTAX		INTEGER { specific(1), dynamic(2) }
	ACCESS		read-write
	STATUS		mandatory
	DESCRIPTION
		" "

	::= { broadbandGateway 6 }

netAddressWAN OBJECT-TYPE
	SYNTAX		IpAddress
	ACCESS		read-write
	STATUS		mandatory
	DESCRIPTION
		" "

	::= { broadbandGateway 7 }

physicalAddrWAN OBJECT-TYPE
	SYNTAX		PhysAddress
	ACCESS		read-write
	STATUS		mandatory
	DESCRIPTION
		" "

	::= { broadbandGateway 8 }

subnetMaskWAN OBJECT-TYPE
	SYNTAX		IpAddress
	ACCESS		read-write
	STATUS		mandatory
	DESCRIPTION
		" "

	::= { broadbandGateway 9 }

defaultbroadbandGatewayWAN OBJECT-TYPE
	SYNTAX		IpAddress
	ACCESS		read-write
	STATUS		mandatory
	DESCRIPTION
		" "

	::= { broadbandGateway 10 }

loginStatus OBJECT-TYPE
	SYNTAX		INTEGER { disable(0), pppoe(1), ras(2) }
	ACCESS		read-write
	STATUS		mandatory
	DESCRIPTION
		" "

	::= { broadbandGateway 11 }

loginUserName OBJECT-TYPE
	SYNTAX		OwnerString (SIZE(0..64))
	ACCESS		read-write
	STATUS		mandatory
	DESCRIPTION
		" "

	::= { broadbandGateway 12 }

loginPassword OBJECT-TYPE
	SYNTAX		OwnerString (SIZE(0..64))
	ACCESS		read-write
	STATUS		mandatory
	DESCRIPTION
		" "

	::= { broadbandGateway 13 }

rasPlan OBJECT-TYPE
	SYNTAX		INTEGER { ethernet-512k(0), ethernet-256k(1) }
	ACCESS		read-write
	STATUS		mandatory
	DESCRIPTION
		" "

	::= { broadbandGateway 14 }

connectedState OBJECT-TYPE
	SYNTAX		INTEGER { keepAlive(0), onDemand(1) }
	ACCESS		read-write
	STATUS		mandatory
	DESCRIPTION
		" "

	::= { broadbandGateway 15 }

connectedIdleTime OBJECT-TYPE
	SYNTAX		INTEGER
	ACCESS		read-write
	STATUS		mandatory
	DESCRIPTION
		" "

	::= { broadbandGateway 16 }

dhcpStatusLAN OBJECT-TYPE
	SYNTAX		INTEGER { disable(0), enable(1) }
	ACCESS		read-write
	STATUS		mandatory
	DESCRIPTION
		" "

	::= { broadbandGateway 17 }

dhcpStartNetAddr OBJECT-TYPE
	SYNTAX		IpAddress
	ACCESS		read-write
	STATUS		mandatory
	DESCRIPTION
		" "

	::= { broadbandGateway 18 }

dhcpNumberUsers	 OBJECT-TYPE
	SYNTAX		INTEGER
	ACCESS		read-write
	STATUS		mandatory
	DESCRIPTION
		" "

	::= { broadbandGateway 19 }

workingMode OBJECT-TYPE
	SYNTAX		INTEGER { broadbandGateway(1), router(2) }
	ACCESS		read-write
	STATUS		mandatory
	DESCRIPTION
		" "

	::= { broadbandGateway 20 }

dynamicRoutingTX OBJECT-TYPE
	SYNTAX		INTEGER { disable(0), rip1(1), rip1-compatible(2), rip2(3) }
	ACCESS		read-write
	STATUS		mandatory
	DESCRIPTION
		" "

	::= { broadbandGateway 21 }

dynamicRoutingRX OBJECT-TYPE
	SYNTAX		INTEGER { disable(0), rip1(1), rip2(2) }
	ACCESS		read-write
	STATUS		mandatory
	DESCRIPTION
		" "

	::= { broadbandGateway 22 }

spiStatus OBJECT-TYPE
	SYNTAX		INTEGER { disable(0), enable(1) }
	ACCESS		read-write
	STATUS		mandatory
	DESCRIPTION
		" "

	::= { broadbandGateway 23 }

wanReqBlockStatus OBJECT-TYPE
	SYNTAX		INTEGER { disable(0), enable(1) }
	ACCESS		read-write
	STATUS		mandatory
	DESCRIPTION
		" "

	::= { broadbandGateway 24 }

ipSecPassThroughStatus OBJECT-TYPE
	SYNTAX		INTEGER { disable(0), enable(1) }
	ACCESS		read-write
	STATUS		mandatory
	DESCRIPTION
		" "

	::= { broadbandGateway 25 }

pptpPassThroughStatus OBJECT-TYPE
	SYNTAX		INTEGER { disable(0), enable(1) }
	ACCESS		read-write
	STATUS		mandatory
	DESCRIPTION
		" "

	::= { broadbandGateway 26 }

remoteMgtStatus OBJECT-TYPE
	SYNTAX		INTEGER { disable(0), enable(1) }
	ACCESS		read-write
	STATUS		mandatory
	DESCRIPTION
		" "

	::= { broadbandGateway 27 }

remoteUpgradeStatus OBJECT-TYPE
	SYNTAX		INTEGER { disable(0), enable(1) }
	ACCESS		read-write
	STATUS		mandatory
	DESCRIPTION
		" "

	::= { broadbandGateway 28 }

accessLogStatus OBJECT-TYPE
	SYNTAX		INTEGER { disable(0), enable(1) }
	ACCESS		read-write
	STATUS		mandatory
	DESCRIPTION
		" Trap Status"

	::= { broadbandGateway 29 }

dmzHostIPAddress OBJECT-TYPE
	SYNTAX		IpAddress
	ACCESS		read-write
	STATUS		mandatory
	DESCRIPTION
		" "

	::= { broadbandGateway 30 }

qosStatus OBJECT-TYPE
	SYNTAX		INTEGER { disable(0), enable(1) }
	ACCESS		read-write
	STATUS		mandatory
	DESCRIPTION
		" "

	::= { broadbandGateway 31 }

-- the DHCPActiveTable Group

dhcpActiveTable OBJECT-TYPE
	SYNTAX		SEQUENCE OF DHCPActiveEntry
	ACCESS		not-accessible
	STATUS		mandatory
	DESCRIPTION
		" "

	::= { broadbandGateway 32 }


dhcpActiveEntry OBJECT-TYPE
	SYNTAX		DHCPActiveEntry
	ACCESS		not-accessible
	STATUS		mandatory
	DESCRIPTION
		" "

	INDEX		{ dhcpActiveIndex }
	::= { dhcpActiveTable 1 }

DHCPActiveEntry ::=
	SEQUENCE {
		dhcpActiveIndex			INTEGER,
		dhcpClientHostName		OwnerString,
		dhcpNetAddress			IpAddress,
		dhcpPhysicalAddress		PhysAddress
	}

dhcpActiveIndex OBJECT-TYPE
	SYNTAX		INTEGER
	ACCESS		read-only
	STATUS		mandatory
	DESCRIPTION
		" "

	::= { dhcpActiveEntry 1 }

dhcpClientHostName OBJECT-TYPE
	SYNTAX		OwnerString (SIZE(0..32))
	ACCESS		read-only
	STATUS		mandatory
	DESCRIPTION
		" "

	::= { dhcpActiveEntry 2 }

dhcpNetAddress OBJECT-TYPE
	SYNTAX		IpAddress
	ACCESS		read-only
	STATUS		mandatory
	DESCRIPTION
		" "

	::= { dhcpActiveEntry 3 }

dhcpPhysicalAddress OBJECT-TYPE
	SYNTAX		PhysAddress
	ACCESS		read-only
	STATUS		mandatory
	DESCRIPTION
		" "

	::= { dhcpActiveEntry 4 }

-- the StaticRoutingTable Group

staticRoutingTable OBJECT-TYPE
	SYNTAX		SEQUENCE OF StaticRoutingEntry
	ACCESS		not-accessible
	STATUS		mandatory
	DESCRIPTION
		" "

	::= { broadbandGateway 33 }

staticRoutingEntry OBJECT-TYPE
	SYNTAX		StaticRoutingEntry
	ACCESS		not-accessible
	STATUS		mandatory
	DESCRIPTION
		" "

	INDEX		{ staticRoutingIndex }
	::= { staticRoutingTable 1 }

StaticRoutingEntry ::=
	SEQUENCE {
		staticRoutingIndex			INTEGER,
		destinationNetAddress		IpAddress,
		routingSubnetMask			IpAddress,
		routingDefaultbroadbandGateway		IpAddress,
		routingHopCount				INTEGER,
		routingInterface			INTEGER,
		nFlagStatus					INTEGER
	}

staticRoutingIndex OBJECT-TYPE
	SYNTAX		INTEGER
	ACCESS		read-only
	STATUS		mandatory
	DESCRIPTION
		" "

	::= { staticRoutingEntry 1 }

destinationNetAddress OBJECT-TYPE
	SYNTAX		IpAddress
	ACCESS		read-write
	STATUS		mandatory
	DESCRIPTION
		" "

	::= { staticRoutingEntry 2 }

routingSubnetMask OBJECT-TYPE
	SYNTAX		IpAddress
	ACCESS		read-write
	STATUS		mandatory
	DESCRIPTION
		" "

	::= { staticRoutingEntry 3 }

routingDefaultbroadbandGateway OBJECT-TYPE
	SYNTAX		IpAddress
	ACCESS		read-write
	STATUS		mandatory
	DESCRIPTION
		" "

	::= { staticRoutingEntry 4 }

routingHopCount OBJECT-TYPE
	SYNTAX		INTEGER
	ACCESS		read-write
	STATUS		mandatory
	DESCRIPTION
		" "

	::= { staticRoutingEntry 5 }

routingInterface OBJECT-TYPE
	SYNTAX		INTEGER { lan(1), wan(2) }
	ACCESS		read-write
	STATUS		mandatory
	DESCRIPTION
		" "

	::= { staticRoutingEntry 6 }

nFlagStatus	OBJECT-TYPE
	SYNTAX		INTEGER { free(0), ready(1), active(2) }
	ACCESS		read-write
	STATUS		mandatory
	DESCRIPTION
		" "

	::= { staticRoutingEntry 7 }

-- the FilterIPRangeTable Group

filterIPRangeTable OBJECT-TYPE
	SYNTAX		SEQUENCE OF FilterIPRangeEntry
	ACCESS		not-accessible
	STATUS		mandatory
	DESCRIPTION
		" "

	::= { broadbandGateway 34 }

filterIPRangeEntry OBJECT-TYPE
	SYNTAX		FilterIPRangeEntry
	ACCESS		not-accessible
	STATUS		mandatory
	DESCRIPTION
		" "

	INDEX		{ filterIPRangeIndex }
	::= { filterIPRangeTable 1 }

FilterIPRangeEntry ::=
	SEQUENCE {
		filterIPRangeIndex			INTEGER,
		filterIPStart				IpAddress,
		filterIPEnd					IpAddress
	}

filterIPRangeIndex OBJECT-TYPE
	SYNTAX		INTEGER
	ACCESS		read-only
	STATUS		mandatory
	DESCRIPTION
		" "

	::= { filterIPRangeEntry 1 }

filterIPStart OBJECT-TYPE
	SYNTAX		IpAddress
	ACCESS		read-write
	STATUS		mandatory
	DESCRIPTION
		" "

	::= { filterIPRangeEntry 2 }

filterIPEnd	OBJECT-TYPE
	SYNTAX		IpAddress
	ACCESS		read-write
	STATUS		mandatory
	DESCRIPTION
		" "

	::= { filterIPRangeEntry 3 }

-- the FilterPortRangeTable Group

filterPortRangeTable OBJECT-TYPE
	SYNTAX		SEQUENCE OF FilterPortRangeEntry
	ACCESS		not-accessible
	STATUS		mandatory
	DESCRIPTION
		" "

	::= { broadbandGateway 35 }

filterPortRangeEntry OBJECT-TYPE
	SYNTAX		FilterPortRangeEntry
	ACCESS		not-accessible
	STATUS		mandatory
	DESCRIPTION
		" "

	INDEX		{ filterPortRangeIndex }
	::= { filterPortRangeTable 1 }

FilterPortRangeEntry ::=
	SEQUENCE {
		filterPortRangeIndex		INTEGER,
		filterPortProto				INTEGER,
		filterPortStart				INTEGER,
		filterPortEnd				INTEGER
	}

filterPortRangeIndex OBJECT-TYPE
	SYNTAX		INTEGER
	ACCESS		read-only
	STATUS		mandatory
	DESCRIPTION
		" "

	::= { filterPortRangeEntry 1 }

filterPortProto OBJECT-TYPE
	SYNTAX		INTEGER { both(0), udp(1), tcp(2) }
	ACCESS		read-write
	STATUS		mandatory
	DESCRIPTION
		" "

	::= { filterPortRangeEntry 2 }

filterPortStart OBJECT-TYPE
	SYNTAX		INTEGER
	ACCESS		read-write
	STATUS		mandatory
	DESCRIPTION
		" "

	::= { filterPortRangeEntry 3 }

filterPortEnd OBJECT-TYPE
	SYNTAX		INTEGER
	ACCESS		read-write
	STATUS		mandatory
	DESCRIPTION
		" "

	::= { filterPortRangeEntry 4 }

-- the FilterMACTable Group

filterMACTable OBJECT-TYPE
	SYNTAX		SEQUENCE OF FilterMACEntry
	ACCESS		not-accessible
	STATUS		mandatory
	DESCRIPTION
		" "

	::= { broadbandGateway 36 }

filterMACEntry OBJECT-TYPE
	SYNTAX		FilterMACEntry
	ACCESS		not-accessible
	STATUS		mandatory
	DESCRIPTION
		" "

	INDEX		{ filterMACIndex }
	::= { filterMACTable 1 }

FilterMACEntry ::=
	SEQUENCE {
		filterMACIndex		INTEGER,
		filterMAC			PhysAddress
	}

filterMACIndex OBJECT-TYPE
	SYNTAX		INTEGER
	ACCESS		read-only
	STATUS		mandatory
	DESCRIPTION
		" "

	::= { filterMACEntry 1 }

filterMAC OBJECT-TYPE
	SYNTAX		PhysAddress
	ACCESS		read-write
	STATUS		mandatory
	DESCRIPTION
		" "

	::= { filterMACEntry 2 }

-- the ForwardTable Group

forwardTable OBJECT-TYPE
	SYNTAX		SEQUENCE OF ForwardEntry
	ACCESS		not-accessible
	STATUS		mandatory
	DESCRIPTION
		" "

	::= { broadbandGateway 37 }

forwardEntry OBJECT-TYPE
	SYNTAX		ForwardEntry
	ACCESS		not-accessible
	STATUS		mandatory
	DESCRIPTION
		" "

	INDEX		{ forwardIndex }
	::= { forwardTable 1 }

ForwardEntry ::=
	SEQUENCE {
		forwardIndex		INTEGER,
		servicePortStart	INTEGER,
		servicePortEnd		INTEGER,
		servicePortProto	INTEGER,
		forwardIPAddress	IpAddress
	}

forwardIndex OBJECT-TYPE
	SYNTAX		INTEGER
	ACCESS		read-only
	STATUS		mandatory
	DESCRIPTION
		" "

	::= { forwardEntry 1 }

servicePortStart OBJECT-TYPE
	SYNTAX		INTEGER
	ACCESS		read-write
	STATUS		mandatory
	DESCRIPTION
		" "

	::= { forwardEntry 2 }

servicePortEnd OBJECT-TYPE
	SYNTAX		INTEGER
	ACCESS		read-write
	STATUS		mandatory
	DESCRIPTION
		" "

	::= { forwardEntry 3 }

servicePortProto OBJECT-TYPE
	SYNTAX		INTEGER { both(0), udp(1), tcp(2) }
	ACCESS		read-write
	STATUS		mandatory
	DESCRIPTION
		" "

	::= { forwardEntry 4 }

forwardIPAddress OBJECT-TYPE
	SYNTAX		IpAddress
	ACCESS		read-write
	STATUS		mandatory
	DESCRIPTION
		" "

	::= { forwardEntry 5 }

-- the DnsNetAddressWANTable Group

dnsNetAddressWANTable OBJECT-TYPE
	SYNTAX		SEQUENCE OF DnsNetAddressWANEntry
	ACCESS		not-accessible
	STATUS		mandatory
	DESCRIPTION
		" "

	::= { broadbandGateway 38 }


dnsNetAddressWANEntry OBJECT-TYPE
	SYNTAX		DnsNetAddressWANEntry
	ACCESS		not-accessible
	STATUS		mandatory
	DESCRIPTION
		" "

	INDEX		{ dnsNetAddressWANIndex }
	::= { dnsNetAddressWANTable 1 }

DnsNetAddressWANEntry ::=
	SEQUENCE {
		dnsNetAddressWANIndex		INTEGER,
		dnsNetAddressWAN			IpAddress
	}

dnsNetAddressWANIndex OBJECT-TYPE
	SYNTAX		INTEGER
	ACCESS		read-only
	STATUS		mandatory
	DESCRIPTION
		" "

	::= { dnsNetAddressWANEntry 1 }

dnsNetAddressWAN OBJECT-TYPE
	SYNTAX		IpAddress
	ACCESS		read-write
	STATUS		mandatory
	DESCRIPTION
		" "

	::= { dnsNetAddressWANEntry 2 }

-- the OutingLogTable Group

outgoingLogTable OBJECT-TYPE
	SYNTAX		SEQUENCE OF OutgoingLogEntry
	ACCESS		not-accessible
	STATUS		mandatory
	DESCRIPTION
		" "

	::= { broadbandGateway 39 }

outgoingLogEntry OBJECT-TYPE
	SYNTAX		OutgoingLogEntry
	ACCESS		not-accessible
	STATUS		mandatory
	DESCRIPTION
		" "

	INDEX		{ outgoingLogIndex }
	::= { outgoingLogTable 1 }

OutgoingLogEntry ::=
	SEQUENCE {
		outgoingLogIndex	INTEGER,
		sourceIPLAN			IpAddress,
		destinationIP		IpAddress,
		servicePortNumber	INTEGER
	}

outgoingLogIndex OBJECT-TYPE
	SYNTAX		INTEGER
	ACCESS		read-only
	STATUS		mandatory
	DESCRIPTION
		" "

	::= { outgoingLogEntry 1 }

sourceIPLAN OBJECT-TYPE
	SYNTAX		IpAddress
	ACCESS		read-only
	STATUS		mandatory
	DESCRIPTION
		" "

	::= { outgoingLogEntry 2 }

destinationIP OBJECT-TYPE
	SYNTAX		IpAddress
	ACCESS		read-only
	STATUS		mandatory
	DESCRIPTION
		" "

	::= { outgoingLogEntry 3 }


servicePortNumber OBJECT-TYPE
	SYNTAX		INTEGER
	ACCESS		read-only
	STATUS		mandatory
	DESCRIPTION
		" "

	::= { outgoingLogEntry 4 }

-- the IncomingLogTable Group

incomingLogTable OBJECT-TYPE
	SYNTAX		SEQUENCE OF IncomingLogEntry
	ACCESS		not-accessible
	STATUS		mandatory
	DESCRIPTION
		" "

	::= { broadbandGateway 40 }

incomingLogEntry OBJECT-TYPE
	SYNTAX		IncomingLogEntry
	ACCESS		not-accessible
	STATUS		mandatory
	DESCRIPTION
		" "

	INDEX		{ incomingLogIndex }
	::= { incomingLogTable 1 }

IncomingLogEntry ::=
	SEQUENCE {
		incomingLogIndex		INTEGER,
		sourceIP				IpAddress,
		destinationPortNumber	INTEGER
	}

incomingLogIndex OBJECT-TYPE
	SYNTAX		INTEGER
	ACCESS		read-only
	STATUS		mandatory
	DESCRIPTION
		" "

	::= { incomingLogEntry 1 }

sourceIP OBJECT-TYPE
	SYNTAX		IpAddress
	ACCESS		read-only
	STATUS		mandatory
	DESCRIPTION
		" "

	::= { incomingLogEntry 2 }

destinationPortNumber OBJECT-TYPE
	SYNTAX		INTEGER
	ACCESS		read-only
	STATUS		mandatory
	DESCRIPTION
		" "

	::= { incomingLogEntry 3 }


-- the TrapManagerTable Group

trapManagerTable OBJECT-TYPE
	SYNTAX		SEQUENCE OF TrapManagerEntry
	ACCESS		not-accessible
	STATUS		mandatory
	DESCRIPTION
		" "

	::= { broadbandGateway 41 }

trapManagerEntry OBJECT-TYPE
	SYNTAX		TrapManagerEntry
	ACCESS		not-accessible
	STATUS		mandatory
	DESCRIPTION
		" "

	INDEX		{ trapManagerIndex }
	::= { trapManagerTable 1 }

TrapManagerEntry ::=
	SEQUENCE {
		trapManagerIndex		INTEGER,
		trapMgrNetAddress		IpAddress
	}

trapManagerIndex OBJECT-TYPE
	SYNTAX		INTEGER
	ACCESS		read-only
	STATUS		mandatory
	DESCRIPTION
		" "

	::= { trapManagerEntry 1 }

trapMgrNetAddress OBJECT-TYPE
	SYNTAX		IpAddress
	ACCESS		read-write
	STATUS		mandatory
	DESCRIPTION
		" "

	::= { trapManagerEntry 2 }

-- OoS application Table Group

qosAppTable OBJECT-TYPE
	SYNTAX		SEQUENCE OF QoSAppEntry
	ACCESS		not-accessible
	STATUS		mandatory
	DESCRIPTION
		" "

	::= { broadbandGateway 42 }

qosAppEntry OBJECT-TYPE
	SYNTAX		QoSAppEntry
	ACCESS		not-accessible
	STATUS		mandatory
	DESCRIPTION
		" "

	INDEX		{ qosAppIndex }
	::= { qosAppTable 1 }

QoSAppEntry ::=
	SEQUENCE {
		qosAppIndex				INTEGER,
		appPort					INTEGER,
		appPriority				INTEGER
	}

qosAppIndex OBJECT-TYPE
	SYNTAX		INTEGER
	ACCESS		read-only
	STATUS		mandatory
	DESCRIPTION
		" "

	::= { qosAppEntry 1 }

appPort OBJECT-TYPE
	SYNTAX		INTEGER
	ACCESS		read-write
	STATUS		mandatory
	DESCRIPTION
		" "

	::= { qosAppEntry 2 }

appPriority OBJECT-TYPE
	SYNTAX		INTEGER { disable(0), low(1), high(2) }
	ACCESS		read-write
	STATUS		mandatory
	DESCRIPTION
		" "

	::= { qosAppEntry 3 }

-- OoS Port Table Group

qosPortTable OBJECT-TYPE
	SYNTAX		SEQUENCE OF QoSPortEntry
	ACCESS		not-accessible
	STATUS		mandatory
	DESCRIPTION
		" "

	::= { broadbandGateway 43 }

qosPortEntry OBJECT-TYPE
	SYNTAX		QoSPortEntry
	ACCESS		not-accessible
	STATUS		mandatory
	DESCRIPTION
		" "

	INDEX		{ qosPortIndex }
	::= { qosPortTable 1 }

QoSPortEntry ::=
	SEQUENCE {
		qosPortIndex			INTEGER,
		lanPort					INTEGER,
		portPriority			INTEGER
	}

qosPortIndex OBJECT-TYPE
	SYNTAX		INTEGER
	ACCESS		read-only
	STATUS		mandatory
	DESCRIPTION
		" "

	::= { qosPortEntry 1 }

lanPort OBJECT-TYPE
	SYNTAX		INTEGER
	ACCESS		read-only
	STATUS		mandatory
	DESCRIPTION
		" "

	::= { qosPortEntry 2 }

portPriority OBJECT-TYPE
	SYNTAX		INTEGER { disable(0), low(1), high(2) }
	ACCESS		read-write
	STATUS		mandatory
	DESCRIPTION
		" "

	::= { qosPortEntry 3 }

-- 81 v2.39

multicastPassStatus OBJECT-TYPE
	SYNTAX		INTEGER { disable(0), enable(1) }
	ACCESS		read-write
	STATUS		mandatory
	DESCRIPTION
		" "

	::= { broadbandGateway 44 }


mtuStatus OBJECT-TYPE
	SYNTAX		INTEGER { disable(0), enable(1) }
	ACCESS		read-write
	STATUS		mandatory
	DESCRIPTION
		" "

	::= { broadbandGateway 45 }


mtuSize OBJECT-TYPE
	SYNTAX		INTEGER
	ACCESS		read-write
	STATUS		mandatory
	DESCRIPTION
		" "

	::= { broadbandGateway 46 }


redialPeriod OBJECT-TYPE
	SYNTAX		INTEGER
	ACCESS		read-write
	STATUS		mandatory
	DESCRIPTION
		" "

	::= { broadbandGateway 47 }

-- the Port Triggering Group

portTriggering OBJECT-TYPE
	SYNTAX		SEQUENCE OF PortTriggerEntry
	ACCESS		not-accessible
	STATUS		mandatory
	DESCRIPTION
		" "

	::= { broadbandGateway 48 }

portTriggerEntry OBJECT-TYPE
	SYNTAX		PortTriggerEntry
	ACCESS		not-accessible
	STATUS		mandatory
	DESCRIPTION
		" "

	INDEX		{ portTriggerIndex }
	::= { portTriggering 1 }

PortTriggerEntry ::=
	SEQUENCE {
		portTriggerIndex	INTEGER,
		appName				OwnerString,
		triggerPortStart	INTEGER,
		triggerPortEnd		INTEGER,
		incomingPortStart	INTEGER,
		incomingPortEnd		INTEGER
	}

portTriggerIndex OBJECT-TYPE
	SYNTAX		INTEGER
	ACCESS		read-only
	STATUS		mandatory
	DESCRIPTION
		" "

	::= { portTriggerEntry 1 }

appName OBJECT-TYPE
	SYNTAX		OwnerString (SIZE(0..12))
	ACCESS		read-write
	STATUS		mandatory
	DESCRIPTION
		" "

	::= { portTriggerEntry 2 }

triggerPortStart OBJECT-TYPE
	SYNTAX		INTEGER
	ACCESS		read-write
	STATUS		mandatory
	DESCRIPTION
		" "

	::= { portTriggerEntry 3 }

triggerPortEnd OBJECT-TYPE
	SYNTAX		INTEGER
	ACCESS		read-write
	STATUS		mandatory
	DESCRIPTION
		" "

	::= { portTriggerEntry 4 }

incomingPortStart OBJECT-TYPE
	SYNTAX		INTEGER
	ACCESS		read-write
	STATUS		mandatory
	DESCRIPTION
		" "

	::= { portTriggerEntry 5 }

incomingPortEnd OBJECT-TYPE
	SYNTAX		INTEGER
	ACCESS		read-write
	STATUS		mandatory
	DESCRIPTION
		" "

	::= { portTriggerEntry 6 }



END
