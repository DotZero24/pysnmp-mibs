LINKSYS-WLAN-ACCESS-POINT-REF-MIB DEFINITIONS ::= BEGIN

-- LINKSYS-WLAN-ACCESS-POINT-REF-MIB
-- (C) 2014 Belkin International, Inc. and/or its subsidiaries and affiliates, including Linksys, LLC. All rights reserved.

-- This SNMP Management Information Specification
-- embodies Linksys, LLC. Corporation confidential and proprietary
-- intellectual property.  inksys, LLC. Corporation retains all title
-- and ownership in the Specification including any revisions.

-- This Specification is supplied "AS IS", inksys, LLC. Corporation
-- makes no warranty, either expressed or implied,
-- as to the use, operation, condition, or performance of the
-- Specification.

IMPORTS
	MODULE-IDENTITY,
    enterprises
        FROM SNMPv2-SMI;

    linksys MODULE-IDENTITY
        LAST-UPDATED "201404090000Z"
        ORGANIZATION "Linksys, LLC. Corporation"
        CONTACT-INFO
          "
          Postal:               Linksys International, Inc.
								131 Theory Drive
								Irvine, CA 92617
          Tel:                   +1 949 270 8500"

        DESCRIPTION
          "Wireless-AC Dual Band LAPAC1750PRO Access Point with PoE."

        -- Revision history.
        REVISION
          "201404091200Z" -- 9 April 2014 12:00:00 GMT
        DESCRIPTION
          "Initial release."

    ::= {  enterprises 3955 }

smb OBJECT IDENTIFIER
    ::= { linksys 1000 }

--wap03 OBJECT IDENTIFIER
    --::= { smb 203 }

END
