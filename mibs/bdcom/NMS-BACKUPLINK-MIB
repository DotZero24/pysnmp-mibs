NMS-BACKUPLINK-MIB DEFINITIONS ::= BEGIN

	IMPORTS
		MODULE-IDENTITY, OBJECT-TYPE, Counter32, TimeTicks
			FROM SNMPv2-SMI
		DisplayString, MacAddress, TEXTUAL-CONVENTION, TruthValue, RowStatus
			FROM SNMPv2-TC
		MODULE-COMPLIANCE, OBJECT-GROUP
			FROM SNMPv2-CONF
		InterfaceIndex
			FROM IF-MIB
		PortList
			FROM Q-BRIDGE-MIB
		nmsMgmt
			FROM NMS-SMI;

    BackupLinkState ::= TEXTUAL-CONVENTION
    STATUS  current
    DESCRIPTION
        "The  backupLink port state."
    SYNTAX  INTEGER {
    	up(0),
        down(1),
        nosetting(2)
    }

    PreemptionMode ::= TEXTUAL-CONVENTION
    STATUS  current
    DESCRIPTION
        "The preemption mode of backupLink group."
    SYNTAX  INTEGER {
    	forced(0),
        bandwidth(1),
        nopreemption(2)
    }

    MMU ::= TEXTUAL-CONVENTION
    STATUS  current
    DESCRIPTION
        "MAC-adress move update."
    SYNTAX  INTEGER {
    	transmit(0),
        receive(1),
        no_mmu(2)
    }

    MonitorLinkState ::= TEXTUAL-CONVENTION
    STATUS  current
    DESCRIPTION
        "The  monitorLink port state."
    SYNTAX  INTEGER {
    	up(0),
        down(1),
        nosetting(2)
    }

    NMSBackupLinkMIB MODULE-IDENTITY
        LAST-UPDATED "201104290000Z"
        ORGANIZATION ""
        CONTACT-INFO ""
        DESCRIPTION  "MIB module for backuplink"
        ::= { nmsMgmt 254 }

    NMSBackupLinkGroupTable OBJECT-TYPE
        SYNTAX      SEQUENCE OF NMSBackupLinkGroupEntry
        MAX-ACCESS  not-accessible
        STATUS      current
        ::= { NMSBackupLinkMIB 1 }

    NMSBackupLinkGroupEntry OBJECT-TYPE
        SYNTAX      NMSBackupLinkGroupEntry
        MAX-ACCESS  not-accessible
        STATUS      current
        INDEX { NMSBLGID }
        ::= { NMSBackupLinkGroupTable 1 }

    NMSBackupLinkGroupEntry ::=
    SEQUENCE {
        NMSBLGID
            InterfaceIndex,
        NMSBLGActivePortID
            InterfaceIndex,
        NMSBLGActivePortState
            BackupLinkState,
        NMSBLGActiveFdbUpdate
            MMU,
        NMSBLGBackupPortID
            InterfaceIndex,
        NMSBLGBackupPortState
            BackupLinkState,
        NMSBLGBackupShareLoadVlan
            OCTET STRING,
        NMSBLGBackupVlanState
            BackupLinkState,
        NMSBLGBackupFdbUpdate
            MMU,
        NMSBLGPreemptionMode
            PreemptionMode,
        NMSBLGPreemptionDelay
            INTEGER,
        NMSBLGSwitchCount
            INTEGER,
        NMSBLGFdbUpdateTxCount
            INTEGER,
        NMSBLGRowStatus
        	RowStatus
    }

    NMSBLGID OBJECT-TYPE
        SYNTAX       InterfaceIndex
   		MAX-ACCESS   not-accessible
    	STATUS       current
        DESCRIPTION
            "The BackupLink group id."
    ::= { NMSBackupLinkGroupEntry 1 }

    NMSBLGActivePortID  OBJECT-TYPE
        SYNTAX       InterfaceIndex
   		MAX-ACCESS   read-write
    	STATUS       current
        DESCRIPTION
            "The port id of the BackupLink group active port."
    ::= { NMSBackupLinkGroupEntry 2 }

    NMSBLGActivePortState OBJECT-TYPE
        SYNTAX       BackupLinkState
   		MAX-ACCESS   read-only
    	STATUS       current
        DESCRIPTION
            "The port state of the BackupLink group active port."
    ::= { NMSBackupLinkGroupEntry 3 }

    NMSBLGActiveFdbUpdate OBJECT-TYPE
        SYNTAX       MMU
   		MAX-ACCESS   read-write
    	STATUS       current
        DESCRIPTION
            "The port mmuType of the BackupLink group active port."
    ::= { NMSBackupLinkGroupEntry 4 }

    NMSBLGBackupPortID  OBJECT-TYPE
        SYNTAX       InterfaceIndex
   		MAX-ACCESS   read-write
    	STATUS       current
        DESCRIPTION
            "The port id of the BackupLink group backup port."
    ::= { NMSBackupLinkGroupEntry 5 }

    NMSBLGBackupPortState OBJECT-TYPE
        SYNTAX       BackupLinkState
   		MAX-ACCESS   read-only
    	STATUS       current
        DESCRIPTION
            "The port state of the BackupLink group backup port."
    ::= { NMSBackupLinkGroupEntry 6 }

    NMSBLGBackupFdbUpdate OBJECT-TYPE
        SYNTAX       MMU
   		MAX-ACCESS   read-write
    	STATUS       current
        DESCRIPTION
            "The port mmuType of the BackupLink group backup port."
    ::= { NMSBackupLinkGroupEntry 7 }

    NMSBLGBackupShareLoadVlan OBJECT-TYPE
        SYNTAX       OCTET STRING
   		MAX-ACCESS   read-write
    	STATUS       current
        DESCRIPTION
            "The share load vlan  of the BackupLink group."
    ::= { NMSBackupLinkGroupEntry 8 }

    NMSBLGBackupVlanState OBJECT-TYPE
        SYNTAX       BackupLinkState
   		MAX-ACCESS   read-only
    	STATUS       current
        DESCRIPTION
            "The backup port state of the BackupLink group in the backup vlan."
    ::= { NMSBackupLinkGroupEntry 9 }

    NMSBLGPreemptionMode  OBJECT-TYPE
        SYNTAX       PreemptionMode
   		MAX-ACCESS   read-write
    	STATUS       current
        DESCRIPTION
            "The preemption mode of the BackupLink group."
    ::= { NMSBackupLinkGroupEntry 10 }

    NMSBLGPreemptionDelay    OBJECT-TYPE
        SYNTAX       INTEGER
   		MAX-ACCESS   read-write
    	STATUS       current
        DESCRIPTION
            "The preemption delay timer of the BackupLink group."
    ::= { NMSBackupLinkGroupEntry 11 }

    NMSBLGSwitchCount OBJECT-TYPE
        SYNTAX       INTEGER
   		MAX-ACCESS   read-only
    	STATUS       current
        DESCRIPTION
            "The switch counts of the BackupLink group."
    ::= { NMSBackupLinkGroupEntry 12 }

    NMSBLGFdbUpdateTxCount OBJECT-TYPE
        SYNTAX       INTEGER
   		MAX-ACCESS   read-only
    	STATUS       current
        DESCRIPTION
            "The Tx counts of the BackupLink group."
    ::= { NMSBackupLinkGroupEntry 13 }

    NMSBLGRowStatus OBJECT-TYPE
        SYNTAX       RowStatus
        MAX-ACCESS   read-create
        STATUS       current
        DESCRIPTION
            "Create a new BackupLink group."
    ::= { NMSBackupLinkGroupEntry 14 }

    NMSMonitorLinkUplinkGroupTable OBJECT-TYPE
        SYNTAX      SEQUENCE OF NMSMonitorLinkUplinkGroupEntry
        MAX-ACCESS  not-accessible
        STATUS      current
        ::= { NMSBackupLinkMIB 2 }

    NMSMonitorLinkUplinkGroupEntry OBJECT-TYPE
        SYNTAX      NMSMonitorLinkUplinkGroupEntry
        MAX-ACCESS  not-accessible
        STATUS      current
        INDEX { NMSMLGUplinkPortID }
        ::= { NMSMonitorLinkUplinkGroupTable 1 }

    NMSMonitorLinkUplinkGroupEntry ::=
    SEQUENCE {
        NMSMLGID
            InterfaceIndex,
        NMSMLGUplinkPortID
            InterfaceIndex,
        NMSMLGUplinkPortState
            MonitorLinkState,
        NMSMLGUplinkRowStatus
        	RowStatus
    }

    NMSMLGID OBJECT-TYPE
        SYNTAX       InterfaceIndex
   		MAX-ACCESS   not-accessible
    	STATUS       current
        DESCRIPTION
            "The MonitorLink group id."
    ::= { NMSMonitorLinkUplinkGroupEntry 1 }

    NMSMLGUplinkPortID  OBJECT-TYPE
        SYNTAX       InterfaceIndex
   		MAX-ACCESS   read-write
    	STATUS       current
        DESCRIPTION
            "The port id of the MonitorLink group uplink port."
    ::= { NMSMonitorLinkUplinkGroupEntry 2 }

    NMSMLGUplinkPortState OBJECT-TYPE
        SYNTAX       MonitorLinkState
   		MAX-ACCESS   read-only
    	STATUS       current
        DESCRIPTION
            "The port state of the MonitorLink group uplink port."
    ::= { NMSMonitorLinkUplinkGroupEntry 3 }

    NMSMLGUplinkRowStatus OBJECT-TYPE
        SYNTAX       RowStatus
        MAX-ACCESS   read-create
        STATUS       current
        DESCRIPTION
            "The port linkstate of the MonitorLink group uplink port."
        ::= { NMSMonitorLinkUplinkGroupEntry 4 }

    NMSMonitorLinkDownlinkGroupTable OBJECT-TYPE
        SYNTAX      SEQUENCE OF NMSMonitorLinkDownlinkGroupEntry
        MAX-ACCESS  not-accessible
        STATUS      current
        ::= { NMSBackupLinkMIB 3 }

    NMSMonitorLinkDownlinkGroupEntry OBJECT-TYPE
        SYNTAX      NMSMonitorLinkDownlinkGroupEntry
        MAX-ACCESS  not-accessible
        STATUS      current
        INDEX { nmsMLGID, NMSMLGDownlinkIndex }
        ::= { NMSMonitorLinkDownlinkGroupTable 1 }

    NMSMonitorLinkDownlinkGroupEntry ::=
    SEQUENCE {
        nmsMLGID
            InterfaceIndex,
        NMSMLGDownlinkIndex
            InterfaceIndex,
        NMSMLGDownlinkPortState
            MonitorLinkState,
        NMSMLGDownlinkRowStatus
        	RowStatus
    }

    nmsMLGID OBJECT-TYPE
        SYNTAX       InterfaceIndex
   		MAX-ACCESS   not-accessible
    	STATUS       current
        DESCRIPTION
            "The MonitorLink group id."
    ::= { NMSMonitorLinkDownlinkGroupEntry 1 }

    NMSMLGDownlinkIndex OBJECT-TYPE
        SYNTAX       InterfaceIndex
   		MAX-ACCESS   read-only
    	STATUS       current
        DESCRIPTION
            "The port id of the MonitorLink group downlink port."
    ::= { NMSMonitorLinkDownlinkGroupEntry 2 }

    NMSMLGDownlinkPortState OBJECT-TYPE
        SYNTAX       MonitorLinkState
   		MAX-ACCESS   read-only
    	STATUS       current
        DESCRIPTION
            "The port state of the MonitorLink group downlink port."
    ::= { NMSMonitorLinkDownlinkGroupEntry 3 }

    NMSMLGDownlinkRowStatus OBJECT-TYPE
        SYNTAX       RowStatus
        MAX-ACCESS   read-create
        STATUS       current
        DESCRIPTION
            "The port linkstate of the MonitorLink group downlink port."
    ::= { NMSMonitorLinkDownlinkGroupEntry 4 }
    END
