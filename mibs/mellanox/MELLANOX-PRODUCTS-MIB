MELLANOX-PRODUCTS-MIB DEFINITIONS ::= BEGIN

IMPORTS
	OBJECT-TYPE, MODULE-IDENTITY, Integer32
		FROM SNMPv2-SMI
	mellanoxProducts
		FROM MELLANOX-SMI-MIB;

-- Mellanox Products MIB
--

mellanoxProductsMib MODULE-IDENTITY
	LAST-UPDATED "202008260000Z"
	ORGANIZATION
		"Mellanox Technologies, Inc."
	CONTACT-INFO
		"
		Mellanox Technologies, Inc.
		350 Oakmead Parkway, Suite 100
		Sunnyvale, CA 94085
		Tel: 408-970-3400
		Fax: 408-970-3403
		E-mail: info@mellanox.com
		        "
	DESCRIPTION
		"Mellanox Products MIB"

	REVISION "202008260000Z"
	DESCRIPTION
		"Added 7880"
::= { mellanoxProducts 1 }

switchXFamily        OBJECT IDENTIFIER ::= { mellanoxProductsMib 1 }
ufm                  OBJECT IDENTIFIER ::= { mellanoxProductsMib 2 }
neo                  OBJECT IDENTIFIER ::= { mellanoxProductsMib 3 }

sx1012  OBJECT-TYPE
    SYNTAX     OBJECT IDENTIFIER
    MAX-ACCESS read-only
    STATUS     current
    DESCRIPTION
        "Mellanox SX1012, 12-Port 40GbE Switch System"
    ::= { switchXFamily 1012 }

sx1012x  OBJECT-TYPE
    SYNTAX     OBJECT IDENTIFIER
    MAX-ACCESS read-only
    STATUS     current
    DESCRIPTION
        "Mellanox SX1012X, 12-Port 10GbE Switch System"
    ::= { switchXFamily 10121 }

sx1016  OBJECT-TYPE
	SYNTAX     OBJECT IDENTIFIER
	MAX-ACCESS read-only
	STATUS     current
	DESCRIPTION
		"Mellanox SX1016, 64-Port 10GbE Switch System"
	::= { switchXFamily 1016 }

sx1024  OBJECT-TYPE
	SYNTAX     OBJECT IDENTIFIER
	MAX-ACCESS read-only
	STATUS     current
	DESCRIPTION
		"Mellanox SX1024, 48 port 10GbE + 12 port 40GbE Switch System"
	::= { switchXFamily 1024 }

sx1035  OBJECT-TYPE
	SYNTAX     OBJECT IDENTIFIER
	MAX-ACCESS read-only
	STATUS     current
	DESCRIPTION
		"Mellanox SX1035, 36-Port 40GbE Switch System"
	::= { switchXFamily 1035 }

sx1036  OBJECT-TYPE
	SYNTAX     OBJECT IDENTIFIER
	MAX-ACCESS read-only
	STATUS     current
	DESCRIPTION
		"Mellanox SX1036, 36-Port 40GbE Switch System"
	::= { switchXFamily 1036 }

sx1400  OBJECT-TYPE
	SYNTAX     OBJECT IDENTIFIER
	MAX-ACCESS read-only
	STATUS     current
	DESCRIPTION
		"Mellanox SX1400, 48 port 10GbE + 12 port 40GbE Switch System"
	::= { switchXFamily 1400 }

msx1410  OBJECT-TYPE
	SYNTAX     OBJECT IDENTIFIER
	MAX-ACCESS read-only
	STATUS     current
	DESCRIPTION
		"Mellanox SX1410, 48 port 10GbE + 12 port 40GbE Switch System"
	::= { switchXFamily 1410 }

sx1700  OBJECT-TYPE
	SYNTAX     OBJECT IDENTIFIER
	MAX-ACCESS read-only
	STATUS     current
	DESCRIPTION
		"Mellanox SX1700, 36-Port 40GbE Switch System"
	::= { switchXFamily 1700 }

sx1710  OBJECT-TYPE
	SYNTAX     OBJECT IDENTIFIER
	MAX-ACCESS read-only
	STATUS     current
	DESCRIPTION
		"Mellanox SX1710, 36-Port 40GbE Switch System"
	::= { switchXFamily 1710 }

sn2010  OBJECT-TYPE
     SYNTAX     OBJECT IDENTIFIER
     MAX-ACCESS read-only
     STATUS     current
     DESCRIPTION
           "Mellanox SN2010, 18 port 25GbE + 4 port 100GbE Switch System"
     ::= { switchXFamily 2010 }

sn2100  OBJECT-TYPE
	SYNTAX     OBJECT IDENTIFIER
	MAX-ACCESS read-only
	STATUS     current
	DESCRIPTION
		"Mellanox SN2100, 16-Port 100GbE Switch System"
	::= { switchXFamily 2100 }

sn2100b  OBJECT-TYPE
	SYNTAX     OBJECT IDENTIFIER
	MAX-ACCESS read-only
	STATUS     current
	DESCRIPTION
		"Mellanox SN2100B, 16-Port 40GbE Switch System"
	::= { switchXFamily 2101 }

sn2410  OBJECT-TYPE
	SYNTAX     OBJECT IDENTIFIER
	MAX-ACCESS read-only
	STATUS     current
	DESCRIPTION
		"Mellanox SN2410, 48 port 25GbE + 8 port 100GbE Switch System"
	::= { switchXFamily 2410 }

sn2700  OBJECT-TYPE
	SYNTAX     OBJECT IDENTIFIER
	MAX-ACCESS read-only
	STATUS     current
	DESCRIPTION
		"Mellanox SN2700, 32-Port 100GbE Switch System"
	::= { switchXFamily 2700 }

sn27002 OBJECT-TYPE
	SYNTAX     OBJECT IDENTIFIER
	MAX-ACCESS read-only
	STATUS     current
	DESCRIPTION
		"Mellanox SN2700, 32-Port 100GbE Switch System"
	::= { switchXFamily 27002 }

sn2700b  OBJECT-TYPE
	SYNTAX     OBJECT IDENTIFIER
	MAX-ACCESS read-only
	STATUS     current
	DESCRIPTION
		"Mellanox SN2700B, 32-Port 40GbE Switch System"
	::= { switchXFamily 2701 }

sn2740  OBJECT-TYPE
	SYNTAX     OBJECT IDENTIFIER
	MAX-ACCESS read-only
	STATUS     current
	DESCRIPTION
		"Mellanox MSN2740, 32-Port 100GbE Switch System"
	::= { switchXFamily 2740 }

sn3420  OBJECT-TYPE
	SYNTAX     OBJECT IDENTIFIER
	MAX-ACCESS read-only
	STATUS     current
	DESCRIPTION
		"Mellanox MSN3420, 48 port 25GbE + 12 port 100GbE Switch System"
	::= { switchXFamily 3420 }

sn3700  OBJECT-TYPE
	SYNTAX     OBJECT IDENTIFIER
	MAX-ACCESS read-only
	STATUS     current
	DESCRIPTION
		"Mellanox MSN3700, 32-port 200GbE Switch System"
	::= { switchXFamily 3700 }

sn3700c  OBJECT-TYPE
	SYNTAX     OBJECT IDENTIFIER
	MAX-ACCESS read-only
	STATUS     current
	DESCRIPTION
		"Mellanox MSN3700C, 32-port 100GbE Switch System"
	::= { switchXFamily 370013 }

sn3800  OBJECT-TYPE
	SYNTAX     OBJECT IDENTIFIER
	MAX-ACCESS read-only
	STATUS     current
	DESCRIPTION
		"Mellanox MSN3800, 64-port 100GbE Switch System"
	::= { switchXFamily 3800 }

sn4600  OBJECT-TYPE
	SYNTAX     OBJECT IDENTIFIER
	MAX-ACCESS read-only
	STATUS     current
	DESCRIPTION
		"Mellanox MSN4600 64-port 200GbE Switch System"
	::= { switchXFamily 4600 }

sn4600c  OBJECT-TYPE
	SYNTAX     OBJECT IDENTIFIER
	MAX-ACCESS read-only
	STATUS     current
	DESCRIPTION
		"Mellanox MSN4600C 64-port 100GbE Switch System"
	::= { switchXFamily 460013 }

sn4700  OBJECT-TYPE
	SYNTAX     OBJECT IDENTIFIER
	MAX-ACCESS read-only
	STATUS     current
	DESCRIPTION
		"Mellanox MSN4700, 32 port 100GbE Switch System"
	::= { switchXFamily 4700 }

sx6012  OBJECT-TYPE
	SYNTAX     OBJECT IDENTIFIER
	MAX-ACCESS read-only
	STATUS     current
	DESCRIPTION
		"Mellanox SX6012, 12-Port FDR/FDR10 Switch System"
	::= { switchXFamily 6012 }

sx6018  OBJECT-TYPE
	SYNTAX     OBJECT IDENTIFIER
	MAX-ACCESS read-only
	STATUS     current
	DESCRIPTION
		"Mellanox SX6018, 18-Port FDR/FDR10 Switch System"
	::= { switchXFamily 6018 }

sx6018g  OBJECT-TYPE
    SYNTAX     OBJECT IDENTIFIER
    MAX-ACCESS read-only
    STATUS     current
    DESCRIPTION
        "Mellanox SX6018G, 18-Port Gateway System"
    ::= { switchXFamily 60181 }

sx6036  OBJECT-TYPE
	SYNTAX     OBJECT IDENTIFIER
	MAX-ACCESS read-only
	STATUS     current
	DESCRIPTION
		"Mellanox SX6036, 36-Port FDR/FDR10 Switch System"
	::= { switchXFamily 6036 }

sx6036g  OBJECT-TYPE
	SYNTAX     OBJECT IDENTIFIER
	MAX-ACCESS read-only
	STATUS     current
	DESCRIPTION
		"Mellanox SX6036G, 36-Port Gateway System"
	::= { switchXFamily 60361 }

mtx6100  OBJECT-TYPE
	SYNTAX     OBJECT IDENTIFIER
	MAX-ACCESS read-only
	STATUS     current
	DESCRIPTION
		"Mellanox MTX6100, 6-Port FDR10 Long-haul System"
	::= { switchXFamily 6100 }

mtx6000  OBJECT-TYPE
	SYNTAX     OBJECT IDENTIFIER
	MAX-ACCESS read-only
	STATUS     current
	DESCRIPTION
		"Mellanox MTX6000, 16-Port FDR10 Long-haul System"
	::= { switchXFamily 6000 }

mtx6240  OBJECT-TYPE
	SYNTAX     OBJECT IDENTIFIER
	MAX-ACCESS read-only
	STATUS     current
	DESCRIPTION
		"Mellanox MTX6240 bundle, 2-Port WDM Long-haul System"
	::= { switchXFamily 6240 }

mtx6280  OBJECT-TYPE
	SYNTAX     OBJECT IDENTIFIER
	MAX-ACCESS read-only
	STATUS     current
	DESCRIPTION
		"Mellanox MTX6280 bundle, 1-Port WDM Long-haul System"
	::= { switchXFamily 6280 }

sx6506  OBJECT-TYPE
	SYNTAX     OBJECT IDENTIFIER
	MAX-ACCESS read-only
	STATUS     current
	DESCRIPTION
		"Mellanox SX6506, 108-Port FDR/FDR10 Switch System"
	::= { switchXFamily 6506 }

sx6512  OBJECT-TYPE
	SYNTAX     OBJECT IDENTIFIER
	MAX-ACCESS read-only
	STATUS     current
	DESCRIPTION
		"Mellanox SX6512, 216-Port FDR/FDR10 Switch System"
	::= { switchXFamily 6512 }

sx6518  OBJECT-TYPE
	SYNTAX     OBJECT IDENTIFIER
	MAX-ACCESS read-only
	STATUS     current
	DESCRIPTION
		"Mellanox SX6518, 324-Port FDR/FDR10 Switch System"
	::= { switchXFamily 6518 }

sx6536  OBJECT-TYPE
	SYNTAX     OBJECT IDENTIFIER
	MAX-ACCESS read-only
	STATUS     current
	DESCRIPTION
		"Mellanox SX6536, 648-Port FDR/FDR10 Switch System"
	::= { switchXFamily 6536 }

sx6700  OBJECT-TYPE
	SYNTAX     OBJECT IDENTIFIER
	MAX-ACCESS read-only
	STATUS     current
	DESCRIPTION
		"Mellanox SX6700, 36-Port FDR/FDR10 Switch System"
	::= { switchXFamily 6700 }

sx6710  OBJECT-TYPE
	SYNTAX     OBJECT IDENTIFIER
	MAX-ACCESS read-only
	STATUS     current
	DESCRIPTION
		"Mellanox SX6710, 36-Port FDR/FDR10 Switch System"
	::= { switchXFamily 6710 }

sx6710g  OBJECT-TYPE
     SYNTAX     OBJECT IDENTIFIER
     MAX-ACCESS read-only
     STATUS     current
     DESCRIPTION
           "Mellanox SX6710G, 36-Port Gateway System"
     ::= { switchXFamily 67101 }

sx6720  OBJECT-TYPE
	SYNTAX     OBJECT IDENTIFIER
	MAX-ACCESS read-only
	STATUS     current
	DESCRIPTION
		"Mellanox SX6720, 36-Port FDR/FDR10 Switch System with battery backup units"
	::= { switchXFamily 6720 }

sx6730  OBJECT-TYPE
	SYNTAX     OBJECT IDENTIFIER
	MAX-ACCESS read-only
	STATUS     current
	DESCRIPTION
		"Mellanox SX6730, 36-Port FDR/FDR10 Managed Switch System NEBS Certified"
	::= { switchXFamily 6730 }

cs7500  OBJECT-TYPE
    SYNTAX     OBJECT IDENTIFIER
    MAX-ACCESS read-only
    STATUS     current
    DESCRIPTION
        "Mellanox CS7500, 648-Port EDR Switch System"
    ::= { switchXFamily 7500 }

cs7510  OBJECT-TYPE
    SYNTAX     OBJECT IDENTIFIER
    MAX-ACCESS read-only
    STATUS     current
    DESCRIPTION
        "Mellanox CS7510, 324-Port EDR Switch System"
    ::= { switchXFamily 7510 }

cs7520  OBJECT-TYPE
    SYNTAX     OBJECT IDENTIFIER
    MAX-ACCESS read-only
    STATUS     current
    DESCRIPTION
        "Mellanox CS7520, 216-Port EDR Switch System"
    ::= { switchXFamily 7520 }

sb7700  OBJECT-TYPE
	SYNTAX     OBJECT IDENTIFIER
	MAX-ACCESS read-only
	STATUS     current
	DESCRIPTION
		"Mellanox SB7700, 36-Port EDR Managed Switch System"
	::= { switchXFamily 7700 }

sb7780  OBJECT-TYPE
	SYNTAX     OBJECT IDENTIFIER
	MAX-ACCESS read-only
	STATUS     current
	DESCRIPTION
		"Mellanox SB7780, 36-Port EDR managed InfiniBand Router System"
	::= { switchXFamily 7780 }

sb7800  OBJECT-TYPE
	SYNTAX     OBJECT IDENTIFIER
	MAX-ACCESS read-only
	STATUS     current
	DESCRIPTION
		"Mellanox SB7800, 36-Port EDR managed Switch System"
	::= { switchXFamily 7800 }

sb7880  OBJECT-TYPE
	SYNTAX     OBJECT IDENTIFIER
	MAX-ACCESS read-only
	STATUS     current
	DESCRIPTION
		"Mellanox MSB7880, 36-Port EDR managed InfiniBand Router System"
	::= { switchXFamily 7880 }

mtq8100  OBJECT-TYPE
    SYNTAX     OBJECT IDENTIFIER
    MAX-ACCESS read-only
    STATUS     current
    DESCRIPTION
        "Mellanox MTQ8100, IB long haul switch, 8 ports HDR, dual EDR 10km LH ports"
    ::= { switchXFamily 8100 }

mtq8200  OBJECT-TYPE
    SYNTAX     OBJECT IDENTIFIER
    MAX-ACCESS read-only
    STATUS     current
    DESCRIPTION
        "Mellanox MTQ8200, IB long haul switch, 8 ports HDR, dual EDR 40km LH ports"
    ::= { switchXFamily 8200 }

cs8500  OBJECT-TYPE
    SYNTAX     OBJECT IDENTIFIER
    MAX-ACCESS read-only
    STATUS     current
    DESCRIPTION
        "Mellanox CS8500, 800-port HDR Switch System"
    ::= { switchXFamily 8500 }

mqm8700  OBJECT-TYPE
    SYNTAX     OBJECT IDENTIFIER
    MAX-ACCESS read-only
    STATUS     current
    DESCRIPTION
        "Mellanox MQM8700, 40-Port HDR / 80-Port HDR100 managed Switch System"
    ::= { switchXFamily 8700 }

ufmAppliance  OBJECT-TYPE
	SYNTAX     Integer32
	MAX-ACCESS read-only
	STATUS     current
	DESCRIPTION
		"Mellanox UFM Appliance"
	::= { ufm 1 }

ufmServer  OBJECT-TYPE
	SYNTAX     Integer32
	MAX-ACCESS read-only
	STATUS     current
	DESCRIPTION
		"Mellanox UFM Server Software"
	::= { ufm 2 }

neoAppliance  OBJECT-TYPE
	SYNTAX     Integer32
	MAX-ACCESS read-only
	STATUS     current
	DESCRIPTION
		"Mellanox NEO Appliance"
	::= { neo 1 }
END
