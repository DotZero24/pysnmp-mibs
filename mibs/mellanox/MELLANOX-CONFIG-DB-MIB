MELLANOX-CONFIG-DB-MIB DEFINITIONS ::= BEGIN

IMPORTS
    MODULE-IDENTITY, OBJECT-TYPE, Integer32
        FROM SNMPv2-SMI
	mellanoxConfigDB
		FROM MELLANOX-SMI-MIB;

-- Mellanox Config DB MIB

mellanoxConfigDBMib MODULE-IDENTITY
	LAST-UPDATED "201707250000Z"
	ORGANIZATION
		"Mellanox Technologies, Inc."
	CONTACT-INFO
		"
		Mellanox Technologies, Inc.
		350 Oakmead Parkway, Suite 100
		Sunnyvale, CA 94085
		Tel: 408-970-3400
		Fax: 408-970-3403
		E-mail: info@mellanox.com
		        "
	DESCRIPTION
		"Mellanox Config DB MIB"

	REVISION "201707250000Z"
	DESCRIPTION
		"Fixed syntax errors"
::= { mellanoxConfigDB 1 }

mellanoxConfigDBMibObjects  OBJECT IDENTIFIER ::= { mellanoxConfigDBMib 1 }
mellanoxConfigDBCmd  OBJECT IDENTIFIER ::= { mellanoxConfigDBMibObjects 2 }

mellanoxConfigDBCmdUri  OBJECT-TYPE
	SYNTAX     OCTET STRING
	MAX-ACCESS read-write
	STATUS     current
	DESCRIPTION
		"URI to fetch the configuration file from or upload the file to"
	::= { mellanoxConfigDBCmd 1 }

mellanoxConfigDBCmdFilename  OBJECT-TYPE
	SYNTAX     OCTET STRING
	MAX-ACCESS read-write
	STATUS     current
	DESCRIPTION
		"Filename to save the configuration file to or to upload to a remote location"
	::= { mellanoxConfigDBCmd 2 }

mellanoxConfigDBCmdExecute  OBJECT-TYPE
	SYNTAX     INTEGER {
		mellanoxConfigDBCmdExecuteBinarySwitchTo (1),
		mellanoxConfigDBCmdExecuteTextApply (2),
		mellanoxConfigDBCmdExecuteTextApplyFailContinue (3),
		mellanoxConfigDBCmdExecuteBinaryUpload (4),
		mellanoxConfigDBCmdExecuteTextUpload (5),
		mellanoxConfigDBCmdExecuteConfigWrite (6),
		mellanoxConfigDBCmdExecuteBinaryDelete (7),
		mellanoxConfigDBCmdExecuteTextDelete (8)
	}
	MAX-ACCESS read-write
	STATUS     current
	DESCRIPTION
		"Depending on selected operation -
		BinarySwitchTo          binary file, save to given filename
		TextApply               text file, add to configuration, save to given filename, stop if
                                command fails
		TextApplyFailContinue   text file, add to configuration, save to given filename,
                                continue if command fails
		BinaryUpload            upload configuration file to remote destination
                                ('active' can be used to upload the active configuration)
		TextUpload              upload configuration file to remote destination
		                        ('active-running' and 'active-saved' can be used to upload running or
								startup configuration)
		ConfigWrite             save the running configuration to given filename
		                        ('active' can be used to save as the currently active configuration file)
		BinaryDelete            deletes a saved binary configuration file according to given filename
		TextDelete              deletes a saved textual configuration file according to given filename
	"
	::= { mellanoxConfigDBCmd 3 }

mellanoxConfigDBCmdStatus  OBJECT-TYPE
	SYNTAX     INTEGER
	MAX-ACCESS read-only
	STATUS     current
	DESCRIPTION
		"The status of the configuration operation:
		0: No operation pending
		1-100: progress percentage
		101: success
		>200: failure"
	::= { mellanoxConfigDBCmd 4 }

mellanoxConfigDBCmdStatusString  OBJECT-TYPE
	SYNTAX     OCTET STRING
	MAX-ACCESS read-only
	STATUS     current
	DESCRIPTION
		"String status or error description"
	::= { mellanoxConfigDBCmd 5 }

END
