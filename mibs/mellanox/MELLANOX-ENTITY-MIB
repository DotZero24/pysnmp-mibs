MELLANOX-ENTITY-MIB DEFINITIONS ::= BEGIN

IMPORTS
	OBJECT-TYPE, MODULE-IDENTITY, Integer32
		FROM SNMPv2-SMI
	mellanoxEntity
		FROM MELLANOX-SMI-MIB
	entPhysicalIndex
		FROM ENTITY-MIB;

-- Mellanox ENTITY MIB
--

mellanoxEntityMib MODULE-IDENTITY
	LAST-UPDATED "201306300000Z"
	ORGANIZATION
		"Mellanox Technologies, Inc."
	CONTACT-INFO
		"
		Mellanox Technologies, Inc.
		350 Oakmead Parkway, Suite 100
		Sunnyvale, CA 94085
		Tel: 408-970-3400
		Fax: 408-970-3403
		E-mail: info@mellanox.com
		        "
	DESCRIPTION
		"Mellanox Entity MIB"

	REVISION "201306300000Z"
	DESCRIPTION
		"Initial revision"
::= { mellanoxEntity 1 }


mellanoxPhysicalEntityTable  OBJECT-TYPE
	SYNTAX SEQUENCE OF MellanoxPhysicalEntityEntry
	MAX-ACCESS not-accessible
	STATUS     current
	DESCRIPTION
		"entPhysicalTable extension"
	REFERENCE
		"ENTITY-MIB"
	::= { mellanoxEntityMib 1 }

mellanoxPhysicalEntityEntry  OBJECT-TYPE
	SYNTAX 	MellanoxPhysicalEntityEntry
	MAX-ACCESS not-accessible
	STATUS     current
	DESCRIPTION
		"entPhysical Index"
	INDEX { entPhysicalIndex }
	::= { mellanoxPhysicalEntityTable 1 }

MellanoxPhysicalEntityEntry ::= SEQUENCE {
	mellanoxPhysicalEntityGUID
		OCTET STRING,
	mellanoxPhysicalEntityAsicRev
		Integer32
}

mellanoxPhysicalEntityGUID  OBJECT-TYPE
	SYNTAX     OCTET STRING
	MAX-ACCESS read-only
	STATUS     current
	DESCRIPTION
		"Entity Physical GUID (System or Module GUID)"
	::= { mellanoxPhysicalEntityEntry 1 }

-- Expected values are currently:
--
-- 1 - SwitchX 1
-- 2 - SwitchX 2
--
-- 0 - ASIC Revision N/A

mellanoxPhysicalEntityAsicRev  OBJECT-TYPE
	SYNTAX     Integer32
	MAX-ACCESS read-only
	STATUS     current
	DESCRIPTION
		"ASIC Revision"
	::= { mellanoxPhysicalEntityEntry 2 }
END
