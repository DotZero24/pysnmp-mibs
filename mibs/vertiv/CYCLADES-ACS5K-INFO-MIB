CYCLADES-ACS5K-INFO-MIB DEFINITIONS ::= BEGIN

-- Avocent Vendor MIB OID Tree
-- Release 3.3.0-9 05/24/2011
-- ACS 5000 Enterprise MIB
-- The cyACS5KInfo has the ACS 5000' information MIB) :

IMPORTS
	cyACS5KMgmt
		FROM CYCLADES-ACS5K-MIB
	InterfaceIndex
		FROM IF-MIB
	MODULE-IDENTITY, OBJECT-TYPE,
	Counter32, Integer32
			FROM SNMPv2-SMI
	DisplayString
		FROM SNMPv2-TC;

cyACS5KInfo	MODULE-IDENTITY
	LAST-UPDATED	"201007260000Z"
	ORGANIZATION	"Avocent Corporation"
	CONTACT-INFO	"postal : Avocent Corporation
				47281 Bayside Parkway
				Fremont, CA 94538, USA
				e-mail : Technical Support
					  techsupport@avocent.com"
	DESCRIPTION	"This module defines objects of the ACS/TS/ACS5000 information"
	REVISION	"201007260000Z"
	DESCRIPTION	"First Draft"
::= { cyACS5KMgmt 3 }

cyInfoSerialTable	OBJECT-TYPE
	SYNTAX		SEQUENCE OF CyISPortEntry
	MAX-ACCESS	not-accessible
	STATUS		current
	DESCRIPTION	"This is the information of the specific serial port"
::= { cyACS5KInfo 1 }

cyisPortEntry	OBJECT-TYPE
	SYNTAX		CyISPortEntry
	MAX-ACCESS	not-accessible
	STATUS		current
	DESCRIPTION	"One particular serial port "
	INDEX		{ cyISPortNumber }
::= { cyInfoSerialTable 1 }

CyISPortEntry ::= SEQUENCE  {
	cyISPortNumber	InterfaceIndex,      --  X == ttyX sX.
	cyISPortTty	DisplayString,         -- associate device
	cyISPortName	DisplayString,          -- alias name
	cyISPortSpeed	Integer32,
	cyISPortTxBytes	Counter32,
	cyISPortRXBytes	Counter32,
	cyISPortErrFrame	Counter32,
	cyISPortErrParity	Counter32,
	cyISPortErrBreaks	Counter32,
	cyISPortErrOverrun	Counter32,
	cyISPortSigDTR		INTEGER,
	cyISPortSigCD		INTEGER,
	cyISPortSigDSR		INTEGER,
	cyISPortSigRTS		INTEGER,
	cyISPortSigCTS		INTEGER,
	cyISPortSigRI		INTEGER
 }

cyISPortNumber	OBJECT-TYPE
	SYNTAX		InterfaceIndex
	MAX-ACCESS	read-only
	STATUS		current
	DESCRIPTION	"number to identifier the serial port."
::= { cyisPortEntry 1 }

cyISPortTty		OBJECT-TYPE
	SYNTAX		DisplayString
	MAX-ACCESS	read-only
	STATUS		current
	DESCRIPTION	"The device name for the serial port."
::= { cyisPortEntry 2 }

cyISPortName		OBJECT-TYPE
	SYNTAX		DisplayString
	MAX-ACCESS	read-only
	STATUS		current
	DESCRIPTION	"Alias name given to the server connected to the serial port."
::= { cyisPortEntry 3 }

cyISPortSpeed	OBJECT-TYPE
	SYNTAX		Integer32
	MAX-ACCESS	read-only
	STATUS		current
	DESCRIPTION	"The speed for serial port."
::= { cyisPortEntry 4 }

cyISPortTxBytes	OBJECT-TYPE
	SYNTAX		Counter32
	MAX-ACCESS	read-only
	STATUS		current
	DESCRIPTION	"The number of transmited bytes by the serial port."
::= { cyisPortEntry 5 }

cyISPortRXBytes	OBJECT-TYPE
	SYNTAX		Counter32
	MAX-ACCESS	read-only
	STATUS		current
	DESCRIPTION	"The number of received bytes by the serial port."
::= { cyisPortEntry 6 }

cyISPortErrFrame	OBJECT-TYPE
	SYNTAX		Counter32
	MAX-ACCESS	read-only
	STATUS		current
	DESCRIPTION	"The number of frame error."
::= { cyisPortEntry 7 }

cyISPortErrParity	OBJECT-TYPE
	SYNTAX		Counter32
	MAX-ACCESS	read-only
	STATUS		current
	DESCRIPTION	"The number of parity error."
::= { cyisPortEntry 8 }

cyISPortErrBreaks	OBJECT-TYPE
	SYNTAX		Counter32
	MAX-ACCESS	read-only
	STATUS		current
	DESCRIPTION	"The number of breaks error."
::= { cyisPortEntry 9 }

cyISPortErrOverrun	OBJECT-TYPE
	SYNTAX		Counter32
	MAX-ACCESS	read-only
	STATUS		current
	DESCRIPTION	"The number of overrun error."
::= { cyisPortEntry 10 }

cyISPortSigDTR	OBJECT-TYPE
	SYNTAX		INTEGER	{
				down(0),
				up(1)
			}
	MAX-ACCESS	read-only
	STATUS		current
	DESCRIPTION	"The state of DTR signal."
::= { cyisPortEntry 11 }

cyISPortSigCD	OBJECT-TYPE
	SYNTAX		INTEGER	{
				down(0),
				up(1)
			}
	MAX-ACCESS	read-only
	STATUS		current
	DESCRIPTION	"The state of DCD signal."
::= { cyisPortEntry 12 }

cyISPortSigDSR	OBJECT-TYPE
	SYNTAX		INTEGER {
				down(0),
				up(1)
			}
	MAX-ACCESS	read-only
	STATUS		current
	DESCRIPTION	"The state of DSR signal."
::= { cyisPortEntry 13 }

cyISPortSigRTS	OBJECT-TYPE
	SYNTAX		INTEGER {
				down(0),
				up(1)
			}
	MAX-ACCESS	read-only
	STATUS		current
	DESCRIPTION	"The state of RTS signal."
::= { cyisPortEntry 14 }

cyISPortSigCTS	OBJECT-TYPE
	SYNTAX		INTEGER {
				down(0),
				up(1)
			}
	MAX-ACCESS	read-only
	STATUS		current
	DESCRIPTION	"The state of CTS signal."
::= { cyisPortEntry 15 }

cyISPortSigRI	OBJECT-TYPE
	SYNTAX		INTEGER {
				down(0),
				up(1)
			}
	MAX-ACCESS	read-only
	STATUS		current
	DESCRIPTION	"The state of RI signal."
::= { cyisPortEntry 16 }

END
