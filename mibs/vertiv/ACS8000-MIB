--------------------------------------------------------------------------------
--  Avocent ACS8000 MIB
--  Copyright 2020 Vertiv Co
--  Revision: 2.16.0
--  Last Modified: April 2021
--------------------------------------------------------------------------------

ACS8000-MIB DEFINITIONS ::= BEGIN

IMPORTS
   Gauge,TimeTicks,IpAddress,Counter,NetworkAddress
      FROM RFC1155-SMI
  PhysAddress
      FROM RFC1213-MIB
  enterprises, MODULE-IDENTITY
      FROM SNMPv2-SMI
  OBJECT-TYPE, MODULE-IDENTITY, OBJECT-IDENTITY, Integer32
      FROM SNMPv2-SMI
  DisplayString
      FROM SNMPv2-TC
  InterfaceIndex, InterfaceIndexOrZero
        FROM IF-MIB
   TRAP-TYPE
      FROM RFC-1215;

--------------------------------------------------------------------------------
-- Object Groupings
--------------------------------------------------------------------------------

--@ Note: every product type should be uniquely identified underneath the
--@ acsProducts object group. Each product should report its unique acsProducts
--@ OBJECT IDENTIFIER in mib-2.system.sysObjectID.

-- enterprises  .1.3.6.1.4.1

-- avocent         OBJECT IDENTIFIER ::= { enterprises 10418 }

acs     MODULE-IDENTITY
        LAST-UPDATED    "202104190000Z"
        ORGANIZATION    "Vertiv Co"
        CONTACT-INFO    "e-mail : support.avocent@vertiv.com
                         Web : www.vertiv.com
                         postal : Vertiv Co
                         4991 Corporate Drive
                         Huntsville, AL 35805
                         USA"
        DESCRIPTION "This module defines the MIB extensions to ACS80xx products."
        REVISION    "202104190000Z"
        DESCRIPTION "Added acsScheduledTasksTable."
        REVISION    "202010010000Z"
        DESCRIPTION "Added serial and part number information for PDUs."
        REVISION    "202007010000Z"
        DESCRIPTION "Added support for acsModems. Added support for resetting
        serial port statistics."
        REVISION    "201906010000Z"
        DESCRIPTION "Added support for sensors"
        REVISION    "201805010000Z"
        DESCRIPTION "Dewpoint sensor type"
        REVISION    "201711170000Z"
        DESCRIPTION "Vertiv updates"
        REVISION    "201606170000Z"
        DESCRIPTION "Added UPS support"
        REVISION    "201601060000Z"
        DESCRIPTION "Ported to acs8000 and that product list"
        REVISION    "201010100000Z"
        DESCRIPTION "Extended acsPowerMgmt to support data monitoring and Avocent PM-PDUs"
        REVISION    "200709170000Z"
        DESCRIPTION "First Draft"
::= { enterprises 10418 26 }

acsProducts     OBJECT IDENTIFIER ::= { acs 1 }
acsManagement   OBJECT IDENTIFIER ::= { acs 2 }
--
acs8048         OBJECT IDENTIFIER ::= { acsProducts 1 }    -- 10418.26.1.1
acs8032         OBJECT IDENTIFIER ::= { acsProducts 2 }    -- 10418.26.1.2
acs8016         OBJECT IDENTIFIER ::= { acsProducts 3 }    -- 10418.26.1.3
acs8008         OBJECT IDENTIFIER ::= { acsProducts 4 }    -- 10418.26.1.4
acs808          OBJECT IDENTIFIER ::= { acsProducts 5 }    -- 10418.26.1.5
acs804          OBJECT IDENTIFIER ::= { acsProducts 6 }    -- 10418.26.1.6
acs802          OBJECT IDENTIFIER ::= { acsProducts 7 }    -- 10418.26.1.7

acsAppliance    OBJECT IDENTIFIER ::= { acsManagement 1  }  -- 10418.26.2.1
acsSessions     OBJECT IDENTIFIER ::= { acsManagement 2  }  -- 10418.26.2.2
acsSerialPort   OBJECT IDENTIFIER ::= { acsManagement 3  }  -- 10418.26.2.3
acsPowerMgmt    OBJECT IDENTIFIER ::= { acsManagement 5  }  -- 10418.26.2.5

-- objects under acsPowerMgmt
-- acsPowerMgmtNumSerialPorts       ::=  { acsPowerMgmt 1 }
-- acsPowerMgmtSerialTable          ::=  { acsPowerMgmt 2 }
-- acsPowerMgmtPDUTable             ::=  { acsPowerMgmt 3 }
-- acsPowerMgmtTotalNumberOfOutlets ::= { acsPowerMgmt 4 }
-- acsPowerMgmtOutletsTable         ::= { acsPowerMgmt 5 }
-- acsPowerMgmtNumberOfOutletGroup  ::= { acsPowerMgmt 6 }
-- acsPowerMgmtGroupTable           ::= { acsPowerMgmt 7 }
-- acsPowerMgmtPhasesTable          ::= { acsPowerMgmt 8 }
-- acsPowerMgmtBanksTable           ::= { acsPowerMgmt 9 }
-- acsPowerMgmtEnvMonTable          ::= { acsPowerMgmt 10 }
-- acsPowerMgmtOutElecMonTable      ::= { acsPowerMgmt 11 }

-- acsPowerMgmtUPSTable             ::= { acsPowerMgmt 12 }
-- acsPowerMgmtUPSInputTable        ::= { acsPowerMgmt 13 }
-- acsPowerMgmtUPSBypassTable       ::= { acsPowerMgmt 14 }
-- acsPowerMgmtUPSBatteryTable      ::= { acsPowerMgmt 15 }
-- acsPowerMgmtUPSOutputTable       ::= { acsPowerMgmt 16 }
-- acsPowerMgmtUPSEcoModeTable      ::= { acsPowerMgmt 17 }
-- acsPowerMgmtUPSOutletGroupTable  ::= { acsPowerMgmt 18 }


--
-- Note that traps are defined in a separate trap MIB
--
acsTrapObject   OBJECT IDENTIFIER ::= { acsManagement 6 }  -- 10418.26.2.6

acsSensors      OBJECT IDENTIFIER ::= { acsManagement 7  }  -- 10418.26.2.7
acsModems       OBJECT IDENTIFIER ::= { acsManagement 8  }  -- 10418.26.2.8

--
-- Type Definitions
--

--
-- Each enumeration represents the states of the appliance power supplies.
PowerSupplyState ::= INTEGER
{
        statePowerOn(1),
        statePowerOff(2),
        powerNotInstaled(9999)
}

--
-- Each enumeration represents the speed of the serial port.
SerialPortSpeed ::= INTEGER
{
        speed300bps(300),
        speed600bps(600),
        speed1200bps(1200),
        speed2400bps(2400),
        speed4800bps(4800),
        speed9600bps(9600),
        speed19200bps(19200),
        speed38400bps(38400),
        speed57600bps(57600),
        speed115200bps(115200),
        speed230400bps(230400),
        speed460800bps(460800)
}

--
-- Each enumeration represents the state of the RS-232C signal.
SerialPortSignalState ::=INTEGER
{
        up(1),
        down(2)
}

--
-- Each enumeration represents the RJ-45 pin-out
SerialPortPinOut ::=INTEGER
{
        cyclades(1),
        cisco(2),
        rs422(3),
        rs485(4),
        auto(5)
}

--
-- acsAppliance
-- OBJECT IDENTIFIER ::= { acsManagement 1  }  10418.26.2.1
--
acsHostName OBJECT-TYPE
        SYNTAX             DisplayString ( SIZE (0..32) )
        MAX-ACCESS         read-only
        STATUS             current
        DESCRIPTION
        "The appliance name"
::= { acsAppliance 1 }

acsProductModel OBJECT-TYPE
        SYNTAX             DisplayString ( SIZE (0..50) )
        MAX-ACCESS         read-only
        STATUS             current
        DESCRIPTION
        "The appliance product model"
::= { acsAppliance 2 }

acsPartNumber OBJECT-TYPE
        SYNTAX             DisplayString ( SIZE (0..32) )
        MAX-ACCESS         read-only
        STATUS             current
        DESCRIPTION
        "The part number of this appliance as shown on the label
         attached or imprinted on the appliance."
::= { acsAppliance 3 }

acsSerialNumber OBJECT-TYPE
        SYNTAX             DisplayString ( SIZE (0..32) )
        MAX-ACCESS         read-only
        STATUS             current
        DESCRIPTION
        "The serial number of this appliance as shown on the label
         attached or imprinted on the appliance."
::= { acsAppliance 4 }

acsEIDNumber OBJECT-TYPE
        SYNTAX             DisplayString ( SIZE (0..32) )
        MAX-ACCESS         read-only
        STATUS             current
        DESCRIPTION
        "The electronic ID number (EID) of this appliance as shown on the label
         attached or imprinted on the appliance."
::= { acsAppliance 5 }

acsBootcodeVersion OBJECT-TYPE
        SYNTAX             DisplayString ( SIZE (0..32) )
        MAX-ACCESS         read-only
        STATUS             current
        DESCRIPTION
        "The version of the bootcode of this appliance."
::= { acsAppliance 6 }

acsFirmwareVersion OBJECT-TYPE
        SYNTAX             DisplayString ( SIZE (0..32) )
        MAX-ACCESS         read-only
        STATUS             current
        DESCRIPTION
        "The version of the firmware of this appliance."
::= { acsAppliance 7 }

acsPowerSupply OBJECT-IDENTITY
        STATUS             current
        DESCRIPTION
        "It gives information about Power Supply of this appliance"
::= { acsAppliance 8 }

acsPowerSupplyNumber OBJECT-TYPE
        SYNTAX             Integer32
        MAX-ACCESS         read-only
        STATUS             current
        DESCRIPTION
        "Number of the power supplies of this appliance"
::= { acsPowerSupply 1 }

acsPowerSupplyStatePw1 OBJECT-TYPE
        SYNTAX             PowerSupplyState
        MAX-ACCESS         read-only
        STATUS             current
        DESCRIPTION
        "State of the first power supply"
::= { acsPowerSupply 2 }

acsPowerSupplyStatePw2 OBJECT-TYPE
        SYNTAX             PowerSupplyState
        MAX-ACCESS         read-only
        STATUS             current
        DESCRIPTION
        "State of the second power supply"
::= { acsPowerSupply 3 }

acsReboot OBJECT-TYPE
        SYNTAX INTEGER {
                noAction(1),
                reboot(2)
             }
        MAX-ACCESS         read-write
        STATUS             current
        DESCRIPTION
        "A set value of reboot(2) will reboot the appliance.
         noAction(1) = always returned in a GET. Does nothing if SET.
         reboot(2)   = when SET the appliance immediately reboots."
::= { acsAppliance 9 }

--
-- acsScheduledTasksTable
-- OBJECT IDENTIFIER ::= 10418.26.2.1.10
--

acsScheduledTasksTable OBJECT-TYPE
        SYNTAX             SEQUENCE OF AcsScheduledTasksTableEntry
        MAX-ACCESS         not-accessible
        STATUS             current
        DESCRIPTION
        "This table contains the list of the scheduled tasks."
::= { acsAppliance 10 }

acsScheduledTasksTableEntry        OBJECT-TYPE
        SYNTAX            AcsScheduledTasksTableEntry
        MAX-ACCESS        not-accessible
        STATUS            current
        DESCRIPTION
        "each entry has the information about the scheduled task"
        INDEX        { acsScheduledTasksTableIndex }
::= { acsScheduledTasksTable 1 }

AcsScheduledTasksTableEntry ::= SEQUENCE  {
        acsScheduledTasksTableIndex             InterfaceIndexOrZero,
        acsScheduledTasksTableType              INTEGER,
        acsScheduledTasksTableName              DisplayString,
        acsScheduledTasksTableStatus            INTEGER,
        acsScheduledTasksTableFrequency         INTEGER,
        acsScheduledTasksTableDay               INTEGER,
        acsScheduledTasksTableDate              Integer32,
        acsScheduledTasksTableTime              DisplayString,
        acsScheduledTasksTableLastStarted       DisplayString,
        acsScheduledTasksTableLastResult        DisplayString,
        acsScheduledTasksTableScript            DisplayString,
        acsScheduledTasksTableIpAddress         DisplayString
}

acsScheduledTasksTableIndex OBJECT-TYPE
        SYNTAX             InterfaceIndexOrZero
        MAX-ACCESS         read-only
        STATUS             current
        DESCRIPTION
        "A unique index representing an entry in this table."
::= { acsScheduledTasksTableEntry 1 }

acsScheduledTasksTableType OBJECT-TYPE
        SYNTAX INTEGER {
                custom(1),
                cell-modem-ip-test(2),
                cell-modem-signal-check(3),
                save-config-cli(4)
        }
        MAX-ACCESS     read-only
        STATUS         current
        DESCRIPTION
        "The type of the scheduled task."
::= { acsScheduledTasksTableEntry 2 }

acsScheduledTasksTableName OBJECT-TYPE
        SYNTAX             DisplayString ( SIZE (0..32) )
        MAX-ACCESS         read-only
        STATUS             current
        DESCRIPTION
        "Name of the scheduled task."
::= { acsScheduledTasksTableEntry 3 }

acsScheduledTasksTableStatus OBJECT-TYPE
        SYNTAX INTEGER {
                disabled(1),
                enabled(2)
        }
        MAX-ACCESS         read-write
        STATUS             current
        DESCRIPTION
        "When set to enabled, the task will be run according to the schedule
        defined by acsScheduledTasksTableFrequency."
::= { acsScheduledTasksTableEntry 4 }

acsScheduledTasksTableFrequency OBJECT-TYPE
        SYNTAX INTEGER {
                hourly(1),
                daily(2),
                weekly(3),
                monthly(4)
        }
        MAX-ACCESS     read-write
        STATUS         current
        DESCRIPTION
        "This object defines how often the task will be run.

        When set to hourly(1), the task will be run every hour.

        When set to daily(2), the task will be run every day at the time
        specified by acsScheduledTasksTableTime.

        When set to weekly(3), the task will be run every week on the day
        specified by acsScheduledTasksTableDay, at the time
        specified by acsScheduledTasksTableTime.

        When set to monthly(4), the task will be run every month on the day
        specified by acsScheduledTasksTableDate, at the time
        specified by acsScheduledTasksTableTime.
        "
::= { acsScheduledTasksTableEntry 5 }

acsScheduledTasksTableDay OBJECT-TYPE
        SYNTAX INTEGER {
                sunday(1),
                monday(2),
                tuesday(3),
                wednesday(4),
                thursday(5),
                friday(6),
                saturday(7)
        }
        MAX-ACCESS     read-write
        STATUS         current
        DESCRIPTION
        "Only used if acsScheduledTasksTableFrequency is set to weekly(3).
        The task will be run every week on this day, at the time
        specified by acsScheduledTasksTableTime.
        "
::= { acsScheduledTasksTableEntry 6 }

acsScheduledTasksTableDate OBJECT-TYPE
        SYNTAX             Integer32
        MAX-ACCESS         read-write
        STATUS             current
        DESCRIPTION
        "Only used if acsScheduledTasksTableFrequency is set to monthly(4).
        The task will be run every month on this day, at the time
        specified by acsScheduledTasksTableTime."
::= { acsScheduledTasksTableEntry 7 }

acsScheduledTasksTableTime OBJECT-TYPE
        SYNTAX             DisplayString ( SIZE (0..32) )
        MAX-ACCESS         read-write
        STATUS             current
        DESCRIPTION
        "The time of day the task will run. Format must be HH:MM."
::= { acsScheduledTasksTableEntry 8 }

acsScheduledTasksTableLastStarted OBJECT-TYPE
        SYNTAX             DisplayString ( SIZE (0..32) )
        MAX-ACCESS         read-only
        STATUS             current
        DESCRIPTION
        "The timestamp of the last time the task started running."
::= { acsScheduledTasksTableEntry 9 }

acsScheduledTasksTableLastResult OBJECT-TYPE
        SYNTAX             DisplayString ( SIZE (0..256) )
        MAX-ACCESS         read-only
        STATUS             current
        DESCRIPTION
        "The result of the last time the task was run."
::= { acsScheduledTasksTableEntry 10 }

acsScheduledTasksTableScript OBJECT-TYPE
        SYNTAX             DisplayString ( SIZE (0..128) )
        MAX-ACCESS         read-write
        STATUS             current
        DESCRIPTION
        "The script command used by the task. Only used if
        acsScheduledTasksTableType is set to custom(1)."
::= { acsScheduledTasksTableEntry 11 }

acsScheduledTasksTableIpAddress OBJECT-TYPE
        SYNTAX             DisplayString ( SIZE (0..32) )
        MAX-ACCESS         read-write
        STATUS             current
        DESCRIPTION
        "The IP address used by the cell-modem-ip task. Not used
        by all tasks."
::= { acsScheduledTasksTableEntry 12 }

--
-- acsSessions
-- OBJECT IDENTIFIER ::= { acsManagement 2  }   10418.26.2.2
--
acsActiveSessionsNumberOfSession OBJECT-TYPE
        SYNTAX             Integer32
        MAX-ACCESS         read-only
        STATUS             current
        DESCRIPTION
        "Number of active sessions."
::= { acsSessions 1 }

acsActiveSessionsTable OBJECT-TYPE
        SYNTAX             SEQUENCE OF AcsActiveSessionsTableEntry
        MAX-ACCESS         not-accessible
        STATUS             current
        DESCRIPTION
        "This table contains the list of active sessions."
::= { acsSessions 2 }

acsActiveSessionsTableEntry        OBJECT-TYPE
        SYNTAX            AcsActiveSessionsTableEntry
        MAX-ACCESS        not-accessible
        STATUS            current
        DESCRIPTION
        "each entry has the information about the active session"
        INDEX        { acsActiveSessionsTableIndex }
::= { acsActiveSessionsTable 1 }

AcsActiveSessionsTableEntry ::= SEQUENCE  {
        acsActiveSessionsTableIndex        InterfaceIndexOrZero,
        acsActiveSessionsTableUser         DisplayString, -- user name
        acsActiveSessionsTableGroup        DisplayString, -- group name
        acsActiveSessionsTableType         DisplayString, -- RO/RW-ssh,telnet or web
        acsActiveSessionsTableConnection   DisplayString, -- type + target name
        acsActiveSessionsTableSessionTime  DisplayString, -- time of session
        acsActiveSessionsTableFrom         DisplayString, -- source of the session
        acsActiveSessionsTableKill         INTEGER
}

acsActiveSessionsTableIndex OBJECT-TYPE
        SYNTAX             InterfaceIndexOrZero
        MAX-ACCESS         read-only
        STATUS             current
        DESCRIPTION
        "A unique index representing an entry in this table."
::= { acsActiveSessionsTableEntry 1 }

acsActiveSessionsTableUser OBJECT-TYPE
        SYNTAX             DisplayString ( SIZE (0..32) )
        MAX-ACCESS         read-only
        STATUS             current
        DESCRIPTION
        "The name of the user that opens this session."
::= { acsActiveSessionsTableEntry 2 }

acsActiveSessionsTableGroup OBJECT-TYPE
        SYNTAX             DisplayString ( SIZE (0..32) )
        MAX-ACCESS         read-only
        STATUS             current
        DESCRIPTION
        "The name of the group that the user belongs to."
::= { acsActiveSessionsTableEntry 3 }

acsActiveSessionsTableType OBJECT-TYPE
        SYNTAX             DisplayString ( SIZE (0..32) )
        MAX-ACCESS         read-only
        STATUS             current
        DESCRIPTION
        "The session type."
::= { acsActiveSessionsTableEntry 4 }

acsActiveSessionsTableConnection OBJECT-TYPE
        SYNTAX             DisplayString ( SIZE (0..32) )
        MAX-ACCESS         read-only
        STATUS             current
        DESCRIPTION
        "Connection type."
::= { acsActiveSessionsTableEntry 5 }

acsActiveSessionsTableSessionTime OBJECT-TYPE
        SYNTAX             DisplayString ( SIZE (0..32) )
        MAX-ACCESS         read-only
        STATUS             current
        DESCRIPTION
        "Time of the session"
::= { acsActiveSessionsTableEntry 6 }

acsActiveSessionsTableFrom OBJECT-TYPE
        SYNTAX             DisplayString ( SIZE (0..32) )
        MAX-ACCESS         read-only
        STATUS             current
        DESCRIPTION
        "The source IP address of the session."
::= { acsActiveSessionsTableEntry 7 }

acsActiveSessionsTableKill OBJECT-TYPE
        SYNTAX INTEGER {
                noAction(1),
                killSession(2)
             }
        MAX-ACCESS     read-write
        STATUS         current
        DESCRIPTION
        "A set value of killSession(2) will kill the session.
          noAction(1)   = always returned in a GET. Does nothing if SET.
         killSession(2)= when SET the appliance immediately kills the session."
::= { acsActiveSessionsTableEntry 8 }

--
-- acsSerialPort
-- OBJECT IDENTIFIER ::= { acsManagement 3  }   10418.26.2.3
--

acsSerialPortNumberOfPorts OBJECT-TYPE
        SYNTAX             Integer32
        MAX-ACCESS         read-only
        STATUS             current
        DESCRIPTION
        "Number of Serial Ports (physical serial port plus Aux Port."
::= { acsSerialPort 1 }

acsSerialPortTable OBJECT-TYPE
        SYNTAX             SEQUENCE OF AcsSerialPortTableEntry
        MAX-ACCESS         not-accessible
        STATUS             current
        DESCRIPTION
        "This table contains information about serial ports."
::= { acsSerialPort 2 }

acsSerialPortTableEntry        OBJECT-TYPE
        SYNTAX            AcsSerialPortTableEntry
        MAX-ACCESS        not-accessible
        STATUS            current
        DESCRIPTION
        "each entry has the information about specific serial port."
        INDEX            { acsSerialPortTableNumber }
::= { acsSerialPortTable 1 }

AcsSerialPortTableEntry ::= SEQUENCE  {
        acsSerialPortTableNumber          Integer32,    -- serial port number
        acsSerialPortTableDeviceName      DisplayString, -- associated device name
        acsSerialPortTableStatus          INTEGER,      -- status of serial port
        acsSerialPortTableName            DisplayString, -- associated name
        acsSerialPortTableProfile         INTEGER,      -- configured profile
        acsSerialPortTablePinOut          SerialPortPinOut,      -- configure RJ45 pin-out
        acsSerialPortTableComSpeed        SerialPortSpeed,      -- configured speed
        acsSerialPortTableComParity       INTEGER,      -- configured parity
        acsSerialPortTableComDataSize     Integer32,    -- configured data size
        acsSerialPortTableComStopBits     Integer32,      -- configured stop bits
        acsSerialPortTableComFlowControl  INTEGER,      -- configured flow control
        acsSerialPortTableSignalStateDTR  SerialPortSignalState,      -- state of DTR RS-232C signal
        acsSerialPortTableSignalStateDCD  SerialPortSignalState,      -- state of DCD RS-232C signal
        acsSerialPortTableSignalStateRTS  SerialPortSignalState,      -- state of RTS RS-232C signal
        acsSerialPortTableSignalStateCTS  SerialPortSignalState,      -- state of CTS RS-232C signal
        acsSerialPortTableTxBytes         Integer32,    -- number of transmitted bytes
        acsSerialPortTableRxBytes         Integer32,    -- number of received bytes
        acsSerialPortTableFrameError      Integer32,    -- number of detected frame errors
        acsSerialPortTableParityError     Integer32,    -- number of detected parity errors
        acsSerialPortTableBreak           Integer32,    -- number of detected break
        acsSerialPortTableOverrun         Integer32,    -- number of detected overrun errors
        acsSerialPortTableResetCounters   INTEGER,      -- reset counters for all port statistics
        acsSerialPortTableXcvrStatus      SerialPortSignalState       -- transceiver status
}

acsSerialPortTableNumber OBJECT-TYPE
        SYNTAX             Integer32 (1..49)
        MAX-ACCESS         read-only
        STATUS             current
        DESCRIPTION
        "A unique index representing an entry in this table.
         It is the number of the serial port. For AUX port,
         the number will be the number of physical serial ports plus 1."
::= { acsSerialPortTableEntry 1 }

acsSerialPortTableDeviceName OBJECT-TYPE
        SYNTAX            DisplayString (SIZE (0..25))
        MAX-ACCESS        read-only
        STATUS            current
        DESCRIPTION
        "The associated device name for the serial port."
::= { acsSerialPortTableEntry 2 }

acsSerialPortTableStatus OBJECT-TYPE
        SYNTAX INTEGER {
                        disabled(1),
                        idle(2),
                        inUse(3)
             }
        MAX-ACCESS     read-only
        STATUS         current
        DESCRIPTION
        "The status of the serial port:
         disabled(1) = it was configured as disable.
         idle(2)     = there is not any session opened in this port.
         inUse(3)    = there is session(s) opened in this port."
::= { acsSerialPortTableEntry 3 }

acsSerialPortTableName    OBJECT-TYPE
        SYNTAX            DisplayString (SIZE (0..25))
        MAX-ACCESS        read-only
        STATUS            current
        DESCRIPTION
        "Name associated with this serial port."
::= { acsSerialPortTableEntry 4 }

acsSerialPortTableProfile    OBJECT-TYPE
        SYNTAX  INTEGER {
                        casProfile(1),
                        tsProfile(2),
                        dialInProfile(3),
                        powerProfile(4)
                  }
        MAX-ACCESS        read-only
        STATUS            current
        DESCRIPTION
        "Configured profile for this serial port."
::= { acsSerialPortTableEntry 5 }

acsSerialPortTablePinOut    OBJECT-TYPE
        SYNTAX            SerialPortPinOut
        MAX-ACCESS        read-only
        STATUS            current
        DESCRIPTION
        "RJ45 Pin-out configured for this serial port."
::= { acsSerialPortTableEntry 6 }

acsSerialPortTableComSpeed OBJECT-TYPE
        SYNTAX            SerialPortSpeed
        MAX-ACCESS        read-only
        STATUS            current
        DESCRIPTION
        "Speed configured for this serial port."
::= { acsSerialPortTableEntry 7 }

acsSerialPortTableComParity    OBJECT-TYPE
        SYNTAX  INTEGER {
                        none(1),
                        odd(2),
                        even(3)
                  }
        MAX-ACCESS        read-only
        STATUS            current
        DESCRIPTION
        "Parity configured for this serial port."
::= { acsSerialPortTableEntry 8 }

acsSerialPortTableComDataSize    OBJECT-TYPE
        SYNTAX            Integer32
        MAX-ACCESS        read-only
        STATUS            current
        DESCRIPTION
        "Data Size configured for this serial port."
::= { acsSerialPortTableEntry 9 }

acsSerialPortTableComStopBits    OBJECT-TYPE
        SYNTAX            Integer32
        MAX-ACCESS        read-only
        STATUS            current
        DESCRIPTION
        "Number of Stop Bits configured for this serial port."
::= { acsSerialPortTableEntry 10 }

acsSerialPortTableComFlowControl        OBJECT-TYPE
        SYNTAX  INTEGER {
                        none(1),
                        hardware(2),
                        software(3)
                  }
        MAX-ACCESS        read-only
        STATUS            current
        DESCRIPTION
        "Flow Control configured for this serial port."
::= { acsSerialPortTableEntry 11 }

acsSerialPortTableSignalStateDTR        OBJECT-TYPE
        SYNTAX            SerialPortSignalState
        MAX-ACCESS        read-only
        STATUS            current
        DESCRIPTION
        "State of the DTR RS-232C signal."
::= { acsSerialPortTableEntry 12 }

acsSerialPortTableSignalStateDCD        OBJECT-TYPE
        SYNTAX            SerialPortSignalState
        MAX-ACCESS        read-only
        STATUS            current
        DESCRIPTION
        "State of the DCD RS-232C signal."
::= { acsSerialPortTableEntry 13 }

acsSerialPortTableSignalStateRTS        OBJECT-TYPE
        SYNTAX            SerialPortSignalState
        MAX-ACCESS        read-only
        STATUS            current
        DESCRIPTION
        "State of the RTS RS-232C signal."
::= { acsSerialPortTableEntry 14 }

acsSerialPortTableSignalStateCTS        OBJECT-TYPE
        SYNTAX            SerialPortSignalState
        MAX-ACCESS        read-only
        STATUS            current
        DESCRIPTION
        "State of the CTS RS-232C signal."
::= { acsSerialPortTableEntry 15 }

acsSerialPortTableTxBytes        OBJECT-TYPE
        SYNTAX            Integer32
        MAX-ACCESS        read-only
        STATUS            current
        DESCRIPTION
        "The number of transmited bytes by the serial port."
::= { acsSerialPortTableEntry 16 }

acsSerialPortTableRxBytes        OBJECT-TYPE
        SYNTAX            Integer32
        MAX-ACCESS        read-only
        STATUS            current
        DESCRIPTION
        "The number of received bytes by the serial port."
::= { acsSerialPortTableEntry 17 }

acsSerialPortTableFrameError        OBJECT-TYPE
        SYNTAX            Integer32
        MAX-ACCESS        read-only
        STATUS            current
        DESCRIPTION
        "The number of frame error detected in the serial port."
::= { acsSerialPortTableEntry 18 }

acsSerialPortTableParityError        OBJECT-TYPE
        SYNTAX            Integer32
        MAX-ACCESS        read-only
        STATUS            current
        DESCRIPTION
        "The number of parity error detected in the serial port."
::= { acsSerialPortTableEntry 19 }

acsSerialPortTableBreak        OBJECT-TYPE
        SYNTAX            Integer32
        MAX-ACCESS        read-only
        STATUS            current
        DESCRIPTION
        "The number of break detected in the serial port."
::= { acsSerialPortTableEntry 20 }

acsSerialPortTableOverrun        OBJECT-TYPE
        SYNTAX            Integer32
        MAX-ACCESS        read-only
        STATUS            current
        DESCRIPTION
        "The number of overrun error detected in the serial port."
::= { acsSerialPortTableEntry 21 }

acsSerialPortTableResetCounters        OBJECT-TYPE
        SYNTAX  INTEGER {
                        no-action(1),
                        resetCounters(2)
                  }
        MAX-ACCESS        read-write
        STATUS            current
        DESCRIPTION
        "Resets counters for all statistics for this serial port.
        Resets the countes for TxBytes, RxBytes, frame errors,
        parity errors, breaks, and overrun errors."
::= { acsSerialPortTableEntry 22 }

acsSerialPortTableXcvrStatus        OBJECT-TYPE
        SYNTAX            SerialPortSignalState
        MAX-ACCESS        read-only
        STATUS            current
        DESCRIPTION
        "Activity status of the RS232 transceiver."
::= { acsSerialPortTableEntry 23 }

--
-- acsPowerMgmt
-- OBJECT IDENTIFIER ::= { acsManagement 5  }   10418.26.2.5
--
acsPowerMgmtNumSerialPorts OBJECT-TYPE
      SYNTAX        Integer32
      MAX-ACCESS    read-only
      STATUS        current
      DESCRIPTION
        "The number of Serial Ports that has PDU connected on the appliance."
::= { acsPowerMgmt 1 }

acsPowerMgmtSerialTable OBJECT-TYPE
      SYNTAX        SEQUENCE OF AcsPowerMgmtSerialTableEntry
      MAX-ACCESS    not-accessible
      STATUS        current
      DESCRIPTION
        "Information about each serial port thas has PDU connect."
::= { acsPowerMgmt 2 }

acsPowerMgmtSerialTableEntry    OBJECT-TYPE
        SYNTAX          AcsPowerMgmtSerialTableEntry
        MAX-ACCESS      not-accessible
        STATUS          current
        DESCRIPTION
        "Information about each serial port thas has PDU connect."
        INDEX           { acsPowerMgmtSerialTableIndex }
::= { acsPowerMgmtSerialTable 1 }

AcsPowerMgmtSerialTableEntry ::= SEQUENCE  {
        acsPowerMgmtSerialTableIndex          InterfaceIndex,
        acsPowerMgmtSerialTablePortNumber     Integer32,
        acsPowerMgmtSerialTableDeviceName     DisplayString,
        acsPowerMgmtSerialTableNumberPDUs     Integer32,
        acsPowerMgmtSerialTableNumberUPS      Integer32
}

acsPowerMgmtSerialTableIndex    OBJECT-TYPE
        SYNTAX         InterfaceIndex
        MAX-ACCESS     read-only
        STATUS         current
        DESCRIPTION
        "The index of the register."
::= { acsPowerMgmtSerialTableEntry 1 }

acsPowerMgmtSerialTablePortNumber    OBJECT-TYPE
        SYNTAX         Integer32
        MAX-ACCESS     read-only
        STATUS         current
        DESCRIPTION
        "The number of the serial port when the PDU is connected."
::= { acsPowerMgmtSerialTableEntry 2 }

acsPowerMgmtSerialTableDeviceName  OBJECT-TYPE
        SYNTAX             DisplayString
        MAX-ACCESS         read-only
        STATUS             current
        DESCRIPTION
        "The device name of this serial port."
::= { acsPowerMgmtSerialTableEntry 3 }

acsPowerMgmtSerialTableNumberPDUs        OBJECT-TYPE
      SYNTAX          Integer32
        MAX-ACCESS      read-only
        STATUS          current
        DESCRIPTION
        "Total number of units connected in this serial port."
::= { acsPowerMgmtSerialTableEntry 4 }

acsPowerMgmtSerialTableNumberUPS        OBJECT-TYPE
      SYNTAX          Integer32
        MAX-ACCESS      read-only
        STATUS          current
        DESCRIPTION
        "Total number of UPS devices connected to this serial port."
::= { acsPowerMgmtSerialTableEntry 5 }

acsPowerMgmtPDUTable OBJECT-TYPE
        SYNTAX             SEQUENCE OF AcsPowerMgmtPDUTableEntry
        MAX-ACCESS         not-accessible
        STATUS             current
        DESCRIPTION
        "This table contains the list of detected PDUs."
::= { acsPowerMgmt 3 }

acsPowerMgmtPDUTableEntry        OBJECT-TYPE
        SYNTAX            AcsPowerMgmtPDUTableEntry
        MAX-ACCESS        not-accessible
        STATUS            current
        DESCRIPTION
        "each entry has the information about the PDU."
        INDEX                { acsPowerMgmtPDUTablePortNumber, acsPowerMgmtPDUTablePduIndex }
::= { acsPowerMgmtPDUTable 1 }

AcsPowerMgmtPDUTableEntry ::= SEQUENCE  {
        acsPowerMgmtPDUTablePortNumber        InterfaceIndex,  -- number of serial port
        acsPowerMgmtPDUTablePduIndex          InterfaceIndexOrZero,
        acsPowerMgmtPDUTablePduId             DisplayString,   -- PDU identification
        acsPowerMgmtPDUTablePortName          DisplayString,   -- Serial Port Name
        acsPowerMgmtPDUTableModel             DisplayString,   -- PDU model
        acsPowerMgmtPDUTableVendor            DisplayString,   -- Vendor
        acsPowerMgmtPDUTableFirmwareVersion   DisplayString,   -- Firmware Version
        acsPowerMgmtPDUTableNumberOfOutlets   Integer32,
        acsPowerMgmtPDUTableCurrentNOS        Integer32,        -- OBSOLETED number of current sensors
        acsPowerMgmtPDUTableCurrent1Value     Integer32,        -- OBSOLETED actual value for current of the sensor 1
        acsPowerMgmtPDUTableCurrent1Max       Integer32,        -- OBSOLETED max value for current of the sensor 1
        acsPowerMgmtPDUTableCurrent2Value     Integer32,        -- OBSOLETED actual value for current of the sensor 2
        acsPowerMgmtPDUTableCurrent2Max       Integer32,        -- OBSOLETED max value for current of the sensor 2
        acsPowerMgmtPDUTableCurrent3Value     Integer32,        -- OBSOLETED actual value for current of the sensor 3
        acsPowerMgmtPDUTableCurrent3Max       Integer32,        -- OBSOLETED max value for current of the sensor 3
        acsPowerMgmtPDUTableTemperatureNOS    Integer32,        -- OBSOLETED number of temperature  sensors
        acsPowerMgmtPDUTableTemperature1Value Integer32,        -- OBSOLETED actual value for Temperature 1
        acsPowerMgmtPDUTableTemperature1Max   Integer32,        -- OBSOLETED max value for Temperature 1
        acsPowerMgmtPDUTableTemperature2Value Integer32,        -- OBSOLETED actual value for Temperaturet 2
        acsPowerMgmtPDUTableTemperature2Max   Integer32,        -- OBSOLETED max value for Temperature 2
        acsPowerMgmtPDUTableTemperature3Value Integer32,        -- OBSOLETED actual value for Temperature 3
        acsPowerMgmtPDUTableTemperature3Max   Integer32,        -- OBSOLETED max value for Temperature 3
        acsPowerMgmtPDUTableHumidityNOS       Integer32,        -- OBSOLETED humidity number of humidity sensors
        acsPowerMgmtPDUTableHumidity1Value    Integer32,        -- OBSOLETED actual value for Humidity of the sensor 1
        acsPowerMgmtPDUTableHumidity1Max      Integer32,        -- OBSOLETED max value for Humidityof the sensor 1
        acsPowerMgmtPDUTableHumidity2Value    Integer32,        -- OBSOLETED actual value for Humidity of the sensor 2
        acsPowerMgmtPDUTableHumidity2Max      Integer32,        -- OBSOLETED max value for Humidity of the sensor 2
        acsPowerMgmtPDUTableHumidity3Value    Integer32,        -- OBSOLETED actual value for Humidity of the sensor 3
        acsPowerMgmtPDUTableHumidity3Max      Integer32,        -- OBSOLETED max value for Humidity of the sensor 3
        acsPowerMgmtPDUTableVoltageNOS        Integer32,        -- OBSOLETED number of voltage sensor
        acsPowerMgmtPDUTableVoltage1Value     Integer32,        -- OBSOLETED actual value for Voltage of the sensor 1
        acsPowerMgmtPDUTableVoltage1Max       Integer32,        -- OBSOLETED max value for Voltage of the sensor 1
        acsPowerMgmtPDUTableVoltage2Value     Integer32,        -- OBSOLETED actual value for Voltage of the sensor 2
        acsPowerMgmtPDUTableVoltage2Max       Integer32,        -- OBSOLETED max value for Voltaget of the sensor 2
        acsPowerMgmtPDUTableVoltage3Value     Integer32,        -- OBSOLETED actual value for Voltage of the sensor 3
        acsPowerMgmtPDUTableVoltage3Max       Integer32,        -- OBSOLETED max value for Voltage of the sensor 3
        acsPowerMgmtPDUTableNumberOfPhases    Integer32,        -- number of phases (single or 3-phases)
        acsPowerMgmtPDUTableNumberOfBanks     Integer32,        -- number of banks
        acsPowerMgmtPDUTableCurrentValue      Integer32,        -- actual value of PDU current sensor
        acsPowerMgmtPDUTableCurrentMax        Integer32,        -- max detected value of current sensor
        acsPowerMgmtPDUTableCurrentMin        Integer32,        -- min detected value of current sensor
        acsPowerMgmtPDUTableCurrentAvg        Integer32,        -- average value for current sensor
        acsPowerMgmtPDUTableCurrentReset      INTEGER,          -- reset max, min and avg values
        acsPowerMgmtPDUTableVoltageType       INTEGER,          -- type of PDU voltage
        acsPowerMgmtPDUTableVoltageValue      Integer32,        -- actual value of PDU voltage
        acsPowerMgmtPDUTableVoltageMax        Integer32,        -- max value of voltage sensor
        acsPowerMgmtPDUTableVoltageMin        Integer32,        -- min value of voltage sensor
        acsPowerMgmtPDUTableVoltageAvg        Integer32,        -- avg value of voltage sensor
        acsPowerMgmtPDUTableVoltageReset      INTEGER,          -- reset max, min and avg values
        acsPowerMgmtPDUTablePowerType         INTEGER,          -- type of PDU power consumption
        acsPowerMgmtPDUTablePowerValue        Integer32,        -- actual value of PDU power consumption
        acsPowerMgmtPDUTablePowerMax          Integer32,        -- max value
        acsPowerMgmtPDUTablePowerMin          Integer32,        -- min value
        acsPowerMgmtPDUTablePowerAvg          Integer32,        -- average value
        acsPowerMgmtPDUTablePowerReset        INTEGER,          -- reset max, min and avg values
        acsPowerMgmtPDUTablePowerFactorType   INTEGER,          -- type of PDU power factor
        acsPowerMgmtPDUTablePowerFactorValue  Integer32,        -- actual value of PDU power factor
        acsPowerMgmtPDUTablePowerFactorMax    Integer32,        -- max value for power factor
        acsPowerMgmtPDUTablePowerFactorMin    Integer32,        -- min value for power factor
        acsPowerMgmtPDUTablePowerFactorAvg    Integer32,        -- avg value for power factor
        acsPowerMgmtPDUTablePowerFactorReset  INTEGER,          -- reset max, min and avg values
        acsPowerMgmtPDUTableAlarm             INTEGER,          -- status of PDU alarm
        acsPowerMgmtPDUTableEnvSensors        Integer32,        -- number of environmental sensors
        acsPowerMgmtPDUTableAgentSerialNumber DisplayString,    -- agent serial number
        acsPowerMgmtPDUTablePduModelNumber    DisplayString,    -- PDU model number
        acsPowerMgmtPDUTablePduSerialNumber   DisplayString,    -- PDU serial number
        acsPowerMgmtPDUTablePduPartNumber     DisplayString     -- PDU part number
}

acsPowerMgmtPDUTablePortNumber OBJECT-TYPE
        SYNTAX            InterfaceIndex
        MAX-ACCESS        read-only
        STATUS            current
        DESCRIPTION
        "Number of serial port when the PDU is connected."
::= { acsPowerMgmtPDUTableEntry 1 }

acsPowerMgmtPDUTablePduIndex OBJECT-TYPE
        SYNTAX            InterfaceIndexOrZero
        MAX-ACCESS        read-only
        STATUS            current
        DESCRIPTION
        "A PDU position in the chain."
::= { acsPowerMgmtPDUTableEntry 2 }

acsPowerMgmtPDUTablePduId  OBJECT-TYPE
        SYNTAX             DisplayString
        MAX-ACCESS         read-only
        STATUS             current
        DESCRIPTION
        "PDU identification."
::= { acsPowerMgmtPDUTableEntry 3 }

acsPowerMgmtPDUTablePortName OBJECT-TYPE
        SYNTAX             DisplayString

        MAX-ACCESS         read-only
        STATUS             current
        DESCRIPTION
        "Name of serial port when the PDU is connected."
::= { acsPowerMgmtPDUTableEntry 4 }

acsPowerMgmtPDUTableModel  OBJECT-TYPE
        SYNTAX             DisplayString
        MAX-ACCESS         read-only
        STATUS             current
        DESCRIPTION
        "Model of the PDU."
::= { acsPowerMgmtPDUTableEntry 5 }

acsPowerMgmtPDUTableVendor   OBJECT-TYPE
        SYNTAX             DisplayString
        MAX-ACCESS         read-only
        STATUS             current
        DESCRIPTION
        "Vendor of the PDU."
::= { acsPowerMgmtPDUTableEntry 6 }

acsPowerMgmtPDUTableFirmwareVersion        OBJECT-TYPE
        SYNTAX             DisplayString
        MAX-ACCESS         read-only
        STATUS             current
        DESCRIPTION
        "Version of the PDU firmware."
::= { acsPowerMgmtPDUTableEntry 7 }

acsPowerMgmtPDUTableNumberOfOutlets OBJECT-TYPE
        SYNTAX             Integer32
        MAX-ACCESS         read-only
        STATUS             current
        DESCRIPTION
        "Number of outlets of the PDU."
::= { acsPowerMgmtPDUTableEntry 8 }

acsPowerMgmtPDUTableCurrentNOS OBJECT-TYPE
        SYNTAX             Integer32
        MAX-ACCESS         read-only
        STATUS             obsolete
        DESCRIPTION
        "Number of current sensors in the PDU."
::= { acsPowerMgmtPDUTableEntry 9 }

acsPowerMgmtPDUTableCurrent1Value OBJECT-TYPE
        SYNTAX             Integer32
        MAX-ACCESS         read-only
        STATUS             obsolete
        DESCRIPTION
        "Current of the sensor 1 in this PDU unit in AMP.
         The value of this object is the actual current in
         AMP * 10. You need to translate the readed value
         (Ex. : value is 5, the current is 0.5 AMP.)"
::= { acsPowerMgmtPDUTableEntry 10 }

acsPowerMgmtPDUTableCurrent1Max OBJECT-TYPE
        SYNTAX             Integer32
        MAX-ACCESS         read-write
        STATUS             obsolete
        DESCRIPTION
        "Maximum current of the sensor 1 in this PDU unit in AMP.
         When the PDU does not have support for maximum value,
         the value will be 0.
         The value of this object is the actual current in
         AMP * 10. You need to translate the readed value
         (Ex. : value is 5, the current is 0.5 AMP.)
         Clear this value, set it with Zero value."
::= { acsPowerMgmtPDUTableEntry 11 }

acsPowerMgmtPDUTableCurrent2Value OBJECT-TYPE
        SYNTAX             Integer32
        MAX-ACCESS         read-only
        STATUS             obsolete
        DESCRIPTION
        "Current of the sensor 2 in this PDU unit in AMP.
         The value of this object is the actual current in
         AMP * 10. You need to translate the readed value
         (Ex. : value is 5, the current is 0.5 AMP.)"
::= { acsPowerMgmtPDUTableEntry 12 }

acsPowerMgmtPDUTableCurrent2Max OBJECT-TYPE
        SYNTAX             Integer32
        MAX-ACCESS         read-write
        STATUS             obsolete
        DESCRIPTION
        "Maximum current of the sensor 2 in this PDU unit in AMP.
          When the PDU does not have support for maximum value,
         the value will be 0.
         The value of this object is the actual current in
         AMP * 10. You need to translate the readed value
         (Ex. : value is 5, the current is 0.5 AMP.)
         Clear this value, set it with Zero value."
::= { acsPowerMgmtPDUTableEntry 13}

acsPowerMgmtPDUTableCurrent3Value OBJECT-TYPE
        SYNTAX             Integer32
        MAX-ACCESS         read-only
        STATUS             obsolete
        DESCRIPTION
        "Current of the sensor 3 in this PDU unit in AMP.
         The value of this object is the actual current in
         AMP * 10. You need to translate the readed value
        (Ex. : value is 5, the current is 0.5 AMP.)"
::= { acsPowerMgmtPDUTableEntry 14 }

acsPowerMgmtPDUTableCurrent3Max OBJECT-TYPE
        SYNTAX             Integer32
        MAX-ACCESS         read-write
        STATUS             obsolete
        DESCRIPTION
         "Maximum current of the sensor 3 in this PDU unit in AMP.
         When the PDU does not have support for maximum value,
         the value will be 0.
         The value of this object is the actual current in
         AMP * 10. You need to translate the readed value
         (Ex. : value is 5, the current is 0.5 AMP.)
         Clear this value, set it with Zero value."
::= { acsPowerMgmtPDUTableEntry 15 }

acsPowerMgmtPDUTableTemperatureNOS OBJECT-TYPE
        SYNTAX             Integer32
        MAX-ACCESS         read-only
        STATUS             obsolete
        DESCRIPTION
        "Number of temperature sensors in the PDU."
::= { acsPowerMgmtPDUTableEntry 16 }

acsPowerMgmtPDUTableTemperature1Value OBJECT-TYPE
        SYNTAX             Integer32
        MAX-ACCESS         read-only
        STATUS             obsolete
        DESCRIPTION
        "Temperature of this PM unit in Celsius degrees.
         The value of this object is the actual temperature in
         degrees C * 10. You need to translate the readed value
        (Ex. : value is 240, the temperature is 24 Celsius.)
         If the temperature measurement is not installed this
         value will be 0.
        Valid values are 5 to 999 ( 0.5 to 99.9 Celsius)."
::= { acsPowerMgmtPDUTableEntry 17 }

acsPowerMgmtPDUTableTemperature1Max OBJECT-TYPE
        SYNTAX             Integer32
        MAX-ACCESS         read-write
        STATUS             obsolete
        DESCRIPTION
        "Maximum temperature detected in this PM unit in Celsius degrees.
        The value will be Zero when the PDU does not have support for maximum value.
         The value of this object is the actual temperature in
         degrees C * 10. You need to translate the readed value
        (Ex. : value is 240, the temperature is 24 Celsius.)
         If the temperature measurement is not installed this
         value will be 0.
         Valid values are 5 to 999 ( 0.5 to 99.9 Celsius).
        Set with Zero value to clear the max. temperature."
::= { acsPowerMgmtPDUTableEntry 18 }

acsPowerMgmtPDUTableTemperature2Value OBJECT-TYPE
        SYNTAX             Integer32
        MAX-ACCESS         read-only
        STATUS             obsolete
        DESCRIPTION
        "Temperature of this PM unit in Celsius degrees.
         The value of this object is the actual temperature in
         degrees C * 10. You need to translate the readed value
         (Ex. : value is 240, the temperature is 24 Celsius.)
         If the temperature measurement is not installed this
         value will be 0.
          Valid values are 5 to 999 ( 0.5 to 99.9 Celsius)."
::= { acsPowerMgmtPDUTableEntry 19 }

acsPowerMgmtPDUTableTemperature2Max OBJECT-TYPE
        SYNTAX             Integer32
        MAX-ACCESS         read-write
        STATUS             obsolete
        DESCRIPTION
        "Maximum temperature detected in this PM unit in Celsius degrees.
         The value will be Zero when the PDU does not have support for maximum value.
         The value of this object is the actual temperature in
         degrees C * 10. You need to translate the readed value
         (Ex. : value is 240, the temperature is 24 Celsius.)
         If the temperature measurement is not installed this
         value will be 0.
         Valid values are 5 to 999 ( 0.5 to 99.9 Celsius).
         Set with Zero value to clear the max. temperature."
::= { acsPowerMgmtPDUTableEntry 20 }

acsPowerMgmtPDUTableTemperature3Value OBJECT-TYPE
        SYNTAX             Integer32
        MAX-ACCESS         read-only
        STATUS             obsolete
        DESCRIPTION
        "Temperature of this PM unit in Celsius degrees.
        The value of this object is the actual temperature in
        degrees C * 10. You need to translate the readed value
        (Ex. : value is 240, the temperature is 24 Celsius.)
        If the temperature measurement is not installed this
        value will be 0.
        Valid values are 5 to 999 ( 0.5 to 99.9 Celsius)."
::= { acsPowerMgmtPDUTableEntry 21 }

acsPowerMgmtPDUTableTemperature3Max OBJECT-TYPE
        SYNTAX             Integer32
        MAX-ACCESS         read-write
        STATUS             obsolete
        DESCRIPTION
        "Maximum temperature detected in this PM unit in Celsius degrees.
        The value will be Zero when the PDU does not have support for maximum value.
         The value of this object is the actual temperature in
         degrees C * 10. You need to translate the readed value
         (Ex. : value is 240, the temperature is 24 Celsius.)
         If the temperature measurement is not installed this
         value will be 0.
         Valid values are 5 to 999 ( 0.5 to 99.9 Celsius).
         Set with Zero value to clear the max. temperature."
::= { acsPowerMgmtPDUTableEntry 22 }

acsPowerMgmtPDUTableHumidityNOS OBJECT-TYPE
        SYNTAX             Integer32
        MAX-ACCESS         read-only
        STATUS             obsolete
        DESCRIPTION
        "Number of humidity sensors in the PDU."
::= { acsPowerMgmtPDUTableEntry 23 }

acsPowerMgmtPDUTableHumidity1Value OBJECT-TYPE
        SYNTAX             Integer32
        MAX-ACCESS         read-only
        STATUS             obsolete
        DESCRIPTION
        "Humidity of this PM unit .
         If the humidity measurement is not installed this
         value will be 0."
::= {  acsPowerMgmtPDUTableEntry 24 }

acsPowerMgmtPDUTableHumidity1Max OBJECT-TYPE
        SYNTAX             Integer32
        MAX-ACCESS         read-write
        STATUS             obsolete
        DESCRIPTION
        "Maximum humidity detected in this PM unit.
         If the humidity measurement  is not installed  or the PDU does not have support for maximum value this
         value will be 0.
         Set with Zero value to clear the max. temperature."
::= {  acsPowerMgmtPDUTableEntry 25 }

acsPowerMgmtPDUTableHumidity2Value OBJECT-TYPE
        SYNTAX             Integer32
        MAX-ACCESS         read-only
        STATUS             obsolete
        DESCRIPTION
        "Humidity of this PM unit .
         If the humidity measurement is not installed this
         value will be 0."
::= {  acsPowerMgmtPDUTableEntry 26 }

acsPowerMgmtPDUTableHumidity2Max OBJECT-TYPE
        SYNTAX             Integer32
        MAX-ACCESS         read-write
        STATUS             obsolete
        DESCRIPTION
        "Maximum humidity detected in this PM unit.
         If the humidity measurement  is not installed  or the PDU does not have support for maximum value this
         value will be 0.
         Set with Zero value to clear the max. temperature."
::= {  acsPowerMgmtPDUTableEntry 27 }

acsPowerMgmtPDUTableHumidity3Value OBJECT-TYPE
        SYNTAX             Integer32
        MAX-ACCESS         read-only
        STATUS             obsolete
        DESCRIPTION
        "Humidity of this PM unit .
         If the humidity measurement is not installed this
         value will be 0."
::= {  acsPowerMgmtPDUTableEntry 28 }

acsPowerMgmtPDUTableHumidity3Max OBJECT-TYPE
        SYNTAX             Integer32
        MAX-ACCESS         read-write
        STATUS             obsolete
        DESCRIPTION
        "Maximum humidity detected in this PM unit.
         If the humidity measurement  is not installed  or the PDU does not have support for maximum value this
         value will be 0.
         Set with Zero value to clear the max. temperature."
::= {  acsPowerMgmtPDUTableEntry 29 }

acsPowerMgmtPDUTableVoltageNOS OBJECT-TYPE
        SYNTAX             Integer32
        MAX-ACCESS         read-only
        STATUS             obsolete
        DESCRIPTION
        "Number of voltage sensors in the PDU."
::= { acsPowerMgmtPDUTableEntry 30 }

acsPowerMgmtPDUTableVoltage1Value OBJECT-TYPE
        SYNTAX             Integer32
        MAX-ACCESS         read-only
        STATUS             obsolete
        DESCRIPTION
        "Voltage of this sensor in this PDU unit."
::= { acsPowerMgmtPDUTableEntry 31 }

acsPowerMgmtPDUTableVoltage1Max OBJECT-TYPE
        SYNTAX             Integer32
        MAX-ACCESS         read-write
        STATUS             obsolete
        DESCRIPTION
        "Maximum voltage of this sensor in this PDU unit.
         Set with Zero value to clear the maximum voltage."
::= { acsPowerMgmtPDUTableEntry 32 }

acsPowerMgmtPDUTableVoltage2Value OBJECT-TYPE
        SYNTAX             Integer32
        MAX-ACCESS         read-only
        STATUS             obsolete
        DESCRIPTION
        "Voltage of this sensor in this PDU unit."
::= { acsPowerMgmtPDUTableEntry 33 }

acsPowerMgmtPDUTableVoltage2Max OBJECT-TYPE
        SYNTAX             Integer32
        MAX-ACCESS         read-write
        STATUS             obsolete
        DESCRIPTION
        "Maximum voltage of this sensor in this PDU unit.
         Set with Zero value to clear the maximum voltage."
::= { acsPowerMgmtPDUTableEntry 34 }

acsPowerMgmtPDUTableVoltage3Value OBJECT-TYPE
        SYNTAX             Integer32
        MAX-ACCESS         read-only
        STATUS             obsolete
        DESCRIPTION
        "Voltage of this sensor in this PDU unit."
::= { acsPowerMgmtPDUTableEntry 35 }

acsPowerMgmtPDUTableVoltage3Max OBJECT-TYPE
        SYNTAX             Integer32
        MAX-ACCESS         read-write
        STATUS             obsolete
        DESCRIPTION
        "Maximum voltage of this sensor in this PDU unit.
         Set with Zero value to clear the maximum voltage."
::= { acsPowerMgmtPDUTableEntry 36 }

acsPowerMgmtPDUTableNumberOfPhases OBJECT-TYPE
        SYNTAX       INTEGER {
            single-phase (0),
            three-phase (3)
                    }
        MAX-ACCESS      read-only
        STATUS          current
        DESCRIPTION     "Number of phases of this PDU unit."
::= { acsPowerMgmtPDUTableEntry 37 }

acsPowerMgmtPDUTableNumberOfBanks OBJECT-TYPE
        SYNTAX          Integer32
        MAX-ACCESS      read-only
        STATUS          current
        DESCRIPTION     "Number of banks of this PDU unit."
::= { acsPowerMgmtPDUTableEntry 38 }

acsPowerMgmtPDUTableCurrentValue OBJECT-TYPE
        SYNTAX             Integer32
        MAX-ACCESS         read-only
        STATUS             current
        DESCRIPTION
        "Actual value of current sensor in this PDU.( A x 10 )"
::= { acsPowerMgmtPDUTableEntry 39 }

acsPowerMgmtPDUTableCurrentMax OBJECT-TYPE
        SYNTAX             Integer32
        MAX-ACCESS         read-only
        STATUS             current
        DESCRIPTION
        "Max detected value of current sensor in this PDU.( A x 10 )"
::= { acsPowerMgmtPDUTableEntry 40 }

acsPowerMgmtPDUTableCurrentMin OBJECT-TYPE
        SYNTAX             Integer32
        MAX-ACCESS         read-only
        STATUS             current
        DESCRIPTION
        "Min detected value of current sensor in this PDU.( A x 10 )"
::= { acsPowerMgmtPDUTableEntry 41 }

acsPowerMgmtPDUTableCurrentAvg OBJECT-TYPE
        SYNTAX             Integer32
        MAX-ACCESS         read-only
        STATUS             current
        DESCRIPTION
        "Average value for current sensor in this PDU.( A x 10 )"
::= { acsPowerMgmtPDUTableEntry 42 }

acsPowerMgmtPDUTableCurrentReset OBJECT-TYPE
        SYNTAX       INTEGER {
            no-action (1),
            reset (2)
                    }
        MAX-ACCESS      read-write
        STATUS          current
        DESCRIPTION     "Reset max, min and avg values of current."
::= { acsPowerMgmtPDUTableEntry 43 }

acsPowerMgmtPDUTableVoltageType OBJECT-TYPE
        SYNTAX       INTEGER {
            none-sensor (0),
            estimated (1),
            read (2)
                    }
        MAX-ACCESS      read-only
        STATUS          current
        DESCRIPTION     "Type of voltage values."
::= { acsPowerMgmtPDUTableEntry 44 }

acsPowerMgmtPDUTableVoltageValue OBJECT-TYPE
        SYNTAX             Integer32
        MAX-ACCESS         read-only
        STATUS             current
        DESCRIPTION
        "Actual value of voltage sensor in this PDU unit.( V )"
::= { acsPowerMgmtPDUTableEntry 45 }

acsPowerMgmtPDUTableVoltageMax OBJECT-TYPE
        SYNTAX             Integer32
        MAX-ACCESS         read-only
        STATUS             current
        DESCRIPTION
        "Max detected value of voltage sensor in this PDU unit.( V )"
::= { acsPowerMgmtPDUTableEntry 46 }

acsPowerMgmtPDUTableVoltageMin OBJECT-TYPE
        SYNTAX             Integer32
        MAX-ACCESS         read-only
        STATUS             current
        DESCRIPTION
        "Min detected value of voltage sensor in this PDU unit.( V )"
::= { acsPowerMgmtPDUTableEntry 47 }

acsPowerMgmtPDUTableVoltageAvg OBJECT-TYPE
        SYNTAX             Integer32
        MAX-ACCESS         read-only
        STATUS             current
        DESCRIPTION
        "Average value for voltage sensor in this PDU unit.( V )"
::= { acsPowerMgmtPDUTableEntry 48 }

acsPowerMgmtPDUTableVoltageReset OBJECT-TYPE
        SYNTAX       INTEGER {
            no-action (1),
            reset (2)
                    }
        MAX-ACCESS      read-write
        STATUS          current
        DESCRIPTION     "Reset max, min and avg values of voltage."
::= { acsPowerMgmtPDUTableEntry 49 }

acsPowerMgmtPDUTablePowerType OBJECT-TYPE
        SYNTAX       INTEGER {
            none-sensor (0),
            estimated (1),
            read (2)
                    }
        MAX-ACCESS      read-only
        STATUS          current
        DESCRIPTION     "Type of power consumption values.( W x 10 )"
::= { acsPowerMgmtPDUTableEntry 50 }

acsPowerMgmtPDUTablePowerValue OBJECT-TYPE
        SYNTAX             Integer32
        MAX-ACCESS         read-only
        STATUS             current
        DESCRIPTION
        "Actual value of power consumption in this PDU unit.( W x 10 )"
::= { acsPowerMgmtPDUTableEntry 51 }

acsPowerMgmtPDUTablePowerMax OBJECT-TYPE
        SYNTAX             Integer32
        MAX-ACCESS         read-only
        STATUS             current
        DESCRIPTION
        "Max detected value of power consumption in this PDU unit.( W x 10 )"
::= { acsPowerMgmtPDUTableEntry 52 }

acsPowerMgmtPDUTablePowerMin OBJECT-TYPE
        SYNTAX             Integer32
        MAX-ACCESS         read-only
        STATUS             current
        DESCRIPTION
        "Min detected value of power consumption in this PDU unit.( W x 10 )"
::= { acsPowerMgmtPDUTableEntry 53 }

acsPowerMgmtPDUTablePowerAvg OBJECT-TYPE
        SYNTAX             Integer32
        MAX-ACCESS         read-only
        STATUS             current
        DESCRIPTION
        "Average value for power consumption in this PDU unit.( W x 10 )"
::= { acsPowerMgmtPDUTableEntry 54 }

acsPowerMgmtPDUTablePowerReset OBJECT-TYPE
        SYNTAX       INTEGER {
            no-action (1),
            reset (2)
                    }
        MAX-ACCESS      read-write
        STATUS          current
        DESCRIPTION     "Reset max, min and avg values of power consumption."
::= { acsPowerMgmtPDUTableEntry 55 }

acsPowerMgmtPDUTablePowerFactorType OBJECT-TYPE
        SYNTAX       INTEGER {
            none-sensor (0),
            estimated (1),
            read (2)
                    }
        MAX-ACCESS      read-only
        STATUS          current
        DESCRIPTION     "Type of power factor values."
::= { acsPowerMgmtPDUTableEntry 56 }

acsPowerMgmtPDUTablePowerFactorValue OBJECT-TYPE
        SYNTAX             Integer32
        MAX-ACCESS         read-only
        STATUS             current
        DESCRIPTION
        "Actual value of power factor in this PDU unit.( PF x 100 )"
::= { acsPowerMgmtPDUTableEntry 57 }

acsPowerMgmtPDUTablePowerFactorMax OBJECT-TYPE
        SYNTAX             Integer32
        MAX-ACCESS         read-only
        STATUS             current
        DESCRIPTION
        "Max detected value of power factor in this PDU unit.( PF x 100 )"
::= { acsPowerMgmtPDUTableEntry 58 }

acsPowerMgmtPDUTablePowerFactorMin OBJECT-TYPE
        SYNTAX             Integer32
        MAX-ACCESS         read-only
        STATUS             current
        DESCRIPTION
        "Min detected value of power factor in this PDU unit.( PF x 100 )"
::= { acsPowerMgmtPDUTableEntry 59 }

acsPowerMgmtPDUTablePowerFactorAvg OBJECT-TYPE
        SYNTAX             Integer32
        MAX-ACCESS         read-only
        STATUS             current
        DESCRIPTION
        "Average value for power factor in this PDU unit.( PF x 100 )"
::= { acsPowerMgmtPDUTableEntry 60 }

acsPowerMgmtPDUTablePowerFactorReset OBJECT-TYPE
        SYNTAX       INTEGER {
            no-action (1),
            reset (2)
                    }
        MAX-ACCESS      read-write
        STATUS          current
        DESCRIPTION     "Reset max, min and avg values of power factor."
::= { acsPowerMgmtPDUTableEntry 61 }

acsPowerMgmtPDUTableAlarm OBJECT-TYPE
        SYNTAX       INTEGER {
            normal (1),
            blow-fuse (2),
            hw-ocp (3),
            high-critical (4),
            high-warning (5),
            low-warning (6),
            low-critical (7)
                    }
        MAX-ACCESS      read-only
        STATUS          current
        DESCRIPTION     "Show the PDU alarm status."
::= { acsPowerMgmtPDUTableEntry 62 }

acsPowerMgmtPDUTableEnvSensors OBJECT-TYPE
        SYNTAX             Integer32
        MAX-ACCESS         read-only
        STATUS             current
        DESCRIPTION
        "Number of environmental sensor in this PDU."
::= { acsPowerMgmtPDUTableEntry 63 }

acsPowerMgmtPDUTableAgentSerialNumber  OBJECT-TYPE
        SYNTAX             DisplayString
        MAX-ACCESS         read-only
        STATUS             current
        DESCRIPTION
        "Serial number of the agent."
::= { acsPowerMgmtPDUTableEntry 64 }

acsPowerMgmtPDUTablePduModelNumber  OBJECT-TYPE
        SYNTAX             DisplayString
        MAX-ACCESS         read-only
        STATUS             current
        DESCRIPTION
        "Model number of the PDU."
::= { acsPowerMgmtPDUTableEntry 65 }

acsPowerMgmtPDUTablePduSerialNumber  OBJECT-TYPE
        SYNTAX             DisplayString
        MAX-ACCESS         read-only
        STATUS             current
        DESCRIPTION
        "Serial number of the PDU."
::= { acsPowerMgmtPDUTableEntry 66 }

acsPowerMgmtPDUTablePduPartNumber  OBJECT-TYPE
        SYNTAX             DisplayString
        MAX-ACCESS         read-only
        STATUS             current
        DESCRIPTION
        "Part number of the PDU."
::= { acsPowerMgmtPDUTableEntry 67 }






acsPowerMgmtTotalNumberOfOutlets OBJECT-TYPE
        SYNTAX             Integer32
        MAX-ACCESS         read-only
        STATUS             current
        DESCRIPTION
        "Number of outlets managed by the appliance."
::= { acsPowerMgmt 4 }

acsPowerMgmtOutletsTable OBJECT-TYPE
        SYNTAX             SEQUENCE OF AcsPowerMgmtOutletsTableEntry
        MAX-ACCESS         not-accessible
        STATUS             current
        DESCRIPTION
        "This table contains the information about outlets."
::= { acsPowerMgmt 5 }

acsPowerMgmtOutletsTableEntry  OBJECT-TYPE
        SYNTAX            AcsPowerMgmtOutletsTableEntry
        MAX-ACCESS        not-accessible
        STATUS            current
        DESCRIPTION
        "each entry has the information about the outlet."
        INDEX             { acsPowerMgmtOutletsTablePortNumber,
                            acsPowerMgmtOutletsTablePduNumber,
                            acsPowerMgmtOutletsTableNumber }
::= { acsPowerMgmtOutletsTable 1 }

AcsPowerMgmtOutletsTableEntry ::= SEQUENCE  {
        acsPowerMgmtOutletsTablePortNumber   InterfaceIndex, -- serial port #
        acsPowerMgmtOutletsTablePduNumber    InterfaceIndex,
        acsPowerMgmtOutletsTableNumber       InterfaceIndex, -- outlet number in PDU
        acsPowerMgmtOutletsTableName         DisplayString,  -- outlet name
        acsPowerMgmtOutletsTableStatus       INTEGER,        -- outlet status
        acsPowerMgmtOutletsTablePowerControl INTEGER,        -- manage the outlet
        acsPowerMgmtOutletsTablePortName     DisplayString,  -- serial port name
        acsPowerMgmtOutletsTablePduId        DisplayString  -- PDU ID
}

acsPowerMgmtOutletsTablePortNumber OBJECT-TYPE
        SYNTAX             InterfaceIndex
        MAX-ACCESS         read-only
        STATUS             current
        DESCRIPTION
        "Serial Port number."
::= { acsPowerMgmtOutletsTableEntry 1 }

acsPowerMgmtOutletsTablePduNumber OBJECT-TYPE
        SYNTAX             InterfaceIndex
        MAX-ACCESS         read-only
        STATUS             current
        DESCRIPTION
        "Index."
::= { acsPowerMgmtOutletsTableEntry 2 }

acsPowerMgmtOutletsTableNumber OBJECT-TYPE
        SYNTAX             InterfaceIndex
        MAX-ACCESS         read-only
        STATUS             current
        DESCRIPTION
        "Number of the outlet in the PDU."
::= { acsPowerMgmtOutletsTableEntry 3 }

acsPowerMgmtOutletsTableName OBJECT-TYPE
        SYNTAX             DisplayString
        MAX-ACCESS         read-only
        STATUS             current
        DESCRIPTION
        "Name of the outlet."
::= { acsPowerMgmtOutletsTableEntry 4 }

acsPowerMgmtOutletsTableStatus OBJECT-TYPE
        SYNTAX        INTEGER {
                off(1),
                on(2)
        }
        MAX-ACCESS         read-only
        STATUS             current
        DESCRIPTION
        "Status of the outlet."
::= { acsPowerMgmtOutletsTableEntry 5 }

acsPowerMgmtOutletsTablePowerControl OBJECT-TYPE
        SYNTAX INTEGER {
                noAction(1),
                powerOn(2),
                powerOff(3),
                powerCycle(4),
                powerLock(5),
                powerUnlock(6)
        }
        MAX-ACCESS         read-write
        STATUS             current
        DESCRIPTION
        "A set value of power*(2-6) will send command to PDU.
         noAction(1) = always returned in a GET. Does nothing if SET.
         powerOn(2)  = when SET the power On command is sent to PDU.
         powerOff(3) = when SET the power Off command is sent to PDU.
         powerCycle(4)=when SET the power cycle command is sent to PDU.
         powerLock(5)= when SET the power lock command is sent to PDU.
         powerUnlock(6)=when SET the power unlock command is sent to PDU.
        The powerLock and powerUnlock are valid only for Cyclades-PM PDUs"
::= { acsPowerMgmtOutletsTableEntry 6 }

acsPowerMgmtOutletsTablePortName OBJECT-TYPE
        SYNTAX             DisplayString
        MAX-ACCESS         read-only
        STATUS             current
        DESCRIPTION
        "Serial Port Name where the PDU is connected."
::= { acsPowerMgmtOutletsTableEntry 7 }

acsPowerMgmtOutletsTablePduId        OBJECT-TYPE
        SYNTAX             DisplayString
        MAX-ACCESS         read-only
        STATUS             current
        DESCRIPTION
        "PDU identification."
::= { acsPowerMgmtOutletsTableEntry 8 }

acsPowerMgmtNumberOfOutletGroup OBJECT-TYPE
        SYNTAX             Integer32
        MAX-ACCESS         read-only
        STATUS             current
        DESCRIPTION
        "Number of configured group of outlets."
::= { acsPowerMgmt 6 }

acsPowerMgmtGroupTable OBJECT-TYPE
        SYNTAX             SEQUENCE OF AcsPowerMgmtGroupTableEntry
        MAX-ACCESS         not-accessible
        STATUS             current
        DESCRIPTION
        "This table contains the information about group of outlets."
::= { acsPowerMgmt 7 }

acsPowerMgmtGroupTableEntry  OBJECT-TYPE
        SYNTAX            AcsPowerMgmtGroupTableEntry
        MAX-ACCESS        not-accessible
        STATUS            current
        DESCRIPTION
        "each entry has the information about group of outlets."
        INDEX             { acsPowerMgmtGroupTableIndex }
::= { acsPowerMgmtGroupTable 1 }

AcsPowerMgmtGroupTableEntry ::= SEQUENCE  {
        acsPowerMgmtGroupTableIndex           InterfaceIndexOrZero,
        acsPowerMgmtGroupTableName            DisplayString, -- group name
        acsPowerMgmtGroupTableStatus          INTEGER,            -- group status
        acsPowerMgmtGroupTablePowerControl    INTEGER    -- manage the group
}

acsPowerMgmtGroupTableIndex OBJECT-TYPE
        SYNTAX             InterfaceIndexOrZero
        MAX-ACCESS         read-only
        STATUS             current
        DESCRIPTION
        "Index of the group."
::= { acsPowerMgmtGroupTableEntry 1 }

acsPowerMgmtGroupTableName OBJECT-TYPE
        SYNTAX             DisplayString
        MAX-ACCESS         read-only
        STATUS             current
        DESCRIPTION
        "Name of the group of outlets."
::= { acsPowerMgmtGroupTableEntry 2 }

acsPowerMgmtGroupTableStatus OBJECT-TYPE
        SYNTAX INTEGER {
                off(1),
                on(2)
                }
        MAX-ACCESS         read-only
        STATUS             current
        DESCRIPTION
        "Status of the group of outlet."
::= { acsPowerMgmtGroupTableEntry 3 }

acsPowerMgmtGroupTablePowerControl OBJECT-TYPE
        SYNTAX INTEGER {
                noAction(1),
                powerOn(2),
                powerOff(3),
                powerCycle(4)
        }
        MAX-ACCESS         read-write
        STATUS             current
        DESCRIPTION
        "A set value of power*(2-6) will send command to PDU.
         noAction(1) = always returned in a GET. Does nothing if SET.
         powerOn(2)  = when SET the power On command is sent to PDU.
         powerOff(3) = when SET the power Off command is sent to PDU.
         powerCycle(4)=when SET the power cycle command is sent to PDU."
::= { acsPowerMgmtGroupTableEntry 4 }

acsPowerMgmtPhasesTable OBJECT-TYPE
        SYNTAX             SEQUENCE OF AcsPowerMgmtPhasesTableEntry
        MAX-ACCESS         not-accessible
        STATUS             current
        DESCRIPTION
        "This table contains data monitoring of each detected phase."
::= { acsPowerMgmt 8 }

acsPowerMgmtPhasesTableEntry        OBJECT-TYPE
        SYNTAX            AcsPowerMgmtPhasesTableEntry
        MAX-ACCESS        not-accessible
        STATUS            current
        DESCRIPTION
        "each entry has the data monitoring about phases."
        INDEX  { acsPowerMgmtPhasesTablePortNumber, acsPowerMgmtPhasesTablePduIndex, acsPowerMgmtPhasesTablePhaseIndex }
::= { acsPowerMgmtPhasesTable 1 }

AcsPowerMgmtPhasesTableEntry ::= SEQUENCE  {
    acsPowerMgmtPhasesTablePortNumber        InterfaceIndex,  -- number of serial port
    acsPowerMgmtPhasesTablePduIndex          InterfaceIndexOrZero, -- number of PDU
    acsPowerMgmtPhasesTablePhaseIndex        InterfaceIndexOrZero, -- phase index
    acsPowerMgmtPhasesTablePhaseName         DisplayString,   -- Phase Name
    acsPowerMgmtPhasesTablePduId             DisplayString,   -- PDU identification
    acsPowerMgmtPhasesTablePortName          DisplayString,   -- Serial Port Name
    acsPowerMgmtPhasesTableCurrentValue      Integer32,    -- actual value of Phase current sensor
    acsPowerMgmtPhasesTableCurrentMax        Integer32,    -- max detected value of current sensor
    acsPowerMgmtPhasesTableCurrentMin        Integer32,    -- min detected value of current sensor
    acsPowerMgmtPhasesTableCurrentAvg        Integer32,    -- average value for current sensor
    acsPowerMgmtPhasesTableCurrentReset      INTEGER,      -- reset max, min and avg values
    acsPowerMgmtPhasesTableVoltageType       INTEGER,      -- type of phase voltage
    acsPowerMgmtPhasesTableVoltageValue      Integer32,    -- actual value of phase voltage
    acsPowerMgmtPhasesTableVoltageMax        Integer32,    -- max value of voltage sensor
    acsPowerMgmtPhasesTableVoltageMin        Integer32,    -- min value of voltage sensor
    acsPowerMgmtPhasesTableVoltageAvg        Integer32,    -- avg value of voltage sensor
    acsPowerMgmtPhasesTableVoltageReset      INTEGER,      -- reset max, min and avg values
    acsPowerMgmtPhasesTablePowerType         INTEGER,      -- type of phase power consumption
    acsPowerMgmtPhasesTablePowerValue        Integer32,    -- actual value of phase power consumption
    acsPowerMgmtPhasesTablePowerMax          Integer32,    -- max value
    acsPowerMgmtPhasesTablePowerMin          Integer32,    -- min value
    acsPowerMgmtPhasesTablePowerAvg          Integer32,    -- average value
    acsPowerMgmtPhasesTablePowerReset        INTEGER,      -- reset max, min and avg values
    acsPowerMgmtPhasesTablePowerFactorType   INTEGER,      -- type of phase power factor
    acsPowerMgmtPhasesTablePowerFactorValue  Integer32,    -- actual value of phase power factor
    acsPowerMgmtPhasesTablePowerFactorMax    Integer32,    -- max value for power factor
    acsPowerMgmtPhasesTablePowerFactorMin    Integer32,    -- min value for power factor
    acsPowerMgmtPhasesTablePowerFactorAvg    Integer32,    -- avg value for power factor
    acsPowerMgmtPhasesTablePowerFactorReset  INTEGER,      -- reset max, min and avg values
    acsPowerMgmtPhasesTableAlarm             INTEGER       -- phase alarm status
}

acsPowerMgmtPhasesTablePortNumber OBJECT-TYPE
        SYNTAX            InterfaceIndex
        MAX-ACCESS        read-only
        STATUS            current
        DESCRIPTION
        "Number of serial port when the PDU is connected."
::= { acsPowerMgmtPhasesTableEntry 1 }

acsPowerMgmtPhasesTablePduIndex OBJECT-TYPE
        SYNTAX            InterfaceIndexOrZero
        MAX-ACCESS        read-only
        STATUS            current
        DESCRIPTION
        "A PDU position in the chain."
::= { acsPowerMgmtPhasesTableEntry 2 }

acsPowerMgmtPhasesTablePhaseIndex OBJECT-TYPE
        SYNTAX            InterfaceIndexOrZero
        MAX-ACCESS        read-only
        STATUS            current
        DESCRIPTION
        "phase index in the PDU."
::= { acsPowerMgmtPhasesTableEntry 3 }

acsPowerMgmtPhasesTablePhaseName OBJECT-TYPE
        SYNTAX             DisplayString
        MAX-ACCESS         read-only
        STATUS             current
        DESCRIPTION
        "phase name in the PDU."
::= { acsPowerMgmtPhasesTableEntry 4 }

acsPowerMgmtPhasesTablePduId  OBJECT-TYPE
        SYNTAX             DisplayString
        MAX-ACCESS         read-only
        STATUS             current
        DESCRIPTION
        "PDU identification."
::= { acsPowerMgmtPhasesTableEntry 5 }

acsPowerMgmtPhasesTablePortName OBJECT-TYPE
        SYNTAX             DisplayString
        MAX-ACCESS         read-only
        STATUS             current
        DESCRIPTION
        "Name of serial port when the PDU is connected."
::= { acsPowerMgmtPhasesTableEntry 6 }

acsPowerMgmtPhasesTableCurrentValue OBJECT-TYPE
        SYNTAX             Integer32
        MAX-ACCESS         read-only
        STATUS             current
        DESCRIPTION
        "Actual value of current sensor in this phase.( A x 10 )"
::= { acsPowerMgmtPhasesTableEntry 7 }

acsPowerMgmtPhasesTableCurrentMax OBJECT-TYPE
        SYNTAX             Integer32
        MAX-ACCESS         read-only
        STATUS             current
        DESCRIPTION
        "Max detected value of current sensor in this phase.( A x 10 )"
::= { acsPowerMgmtPhasesTableEntry 8 }

acsPowerMgmtPhasesTableCurrentMin OBJECT-TYPE
        SYNTAX             Integer32
        MAX-ACCESS         read-only
        STATUS             current
        DESCRIPTION
        "Min detected value of current sensor in this phase.( A x 10 )"
::= { acsPowerMgmtPhasesTableEntry 9 }

acsPowerMgmtPhasesTableCurrentAvg OBJECT-TYPE
        SYNTAX             Integer32
        MAX-ACCESS         read-only
        STATUS             current
        DESCRIPTION
        "Average value for current sensor in this phase.( A x 10 )"
::= { acsPowerMgmtPhasesTableEntry 10 }

acsPowerMgmtPhasesTableCurrentReset OBJECT-TYPE
        SYNTAX       INTEGER {
            no-action (1),
            reset (2)
                    }
        MAX-ACCESS      read-write
        STATUS          current
        DESCRIPTION     "Reset max, min and avg values of current."
::= { acsPowerMgmtPhasesTableEntry 11 }

acsPowerMgmtPhasesTableVoltageType OBJECT-TYPE
        SYNTAX       INTEGER {
            none-sensor (0),
            estimated (1),
            read (2)
                    }
        MAX-ACCESS      read-only
        STATUS          current
        DESCRIPTION     "Type of voltage values."
::= { acsPowerMgmtPhasesTableEntry 12 }

acsPowerMgmtPhasesTableVoltageValue OBJECT-TYPE
        SYNTAX             Integer32
        MAX-ACCESS         read-only
        STATUS             current
        DESCRIPTION
        "Actual value of voltage sensor in this phase.( V )"
::= { acsPowerMgmtPhasesTableEntry 13 }

acsPowerMgmtPhasesTableVoltageMax OBJECT-TYPE
        SYNTAX             Integer32
        MAX-ACCESS         read-only
        STATUS             current
        DESCRIPTION
        "Max detected value of voltage sensor in this phase.( V )"
::= { acsPowerMgmtPhasesTableEntry 14 }

acsPowerMgmtPhasesTableVoltageMin OBJECT-TYPE
        SYNTAX             Integer32
        MAX-ACCESS         read-only
        STATUS             current
        DESCRIPTION
        "Min detected value of voltage sensor in this phase.( V )"
::= { acsPowerMgmtPhasesTableEntry 15 }

acsPowerMgmtPhasesTableVoltageAvg OBJECT-TYPE
        SYNTAX             Integer32
        MAX-ACCESS         read-only
        STATUS             current
        DESCRIPTION
        "Average value for voltage sensor in this phase.( V )"
::= { acsPowerMgmtPhasesTableEntry 16 }

acsPowerMgmtPhasesTableVoltageReset OBJECT-TYPE
        SYNTAX       INTEGER {
            no-action (1),
            reset (2)
                    }
        MAX-ACCESS      read-write
        STATUS          current
        DESCRIPTION     "Reset max, min and avg values of voltage."
::= { acsPowerMgmtPhasesTableEntry 17 }

acsPowerMgmtPhasesTablePowerType OBJECT-TYPE
        SYNTAX       INTEGER {
            none-sensor (0),
            estimated (1),
            read (2)
                    }
        MAX-ACCESS      read-only
        STATUS          current
        DESCRIPTION     "Type of power consumption values."
::= { acsPowerMgmtPhasesTableEntry 18 }

acsPowerMgmtPhasesTablePowerValue OBJECT-TYPE
        SYNTAX             Integer32
        MAX-ACCESS         read-only
        STATUS             current
        DESCRIPTION
        "Actual value of power consumption in this phase.( W x 10 )"
::= { acsPowerMgmtPhasesTableEntry 19 }

acsPowerMgmtPhasesTablePowerMax OBJECT-TYPE
        SYNTAX             Integer32
        MAX-ACCESS         read-only
        STATUS             current
        DESCRIPTION
        "Max detected value of power consumption in this phase.( W x 10 )"
::= { acsPowerMgmtPhasesTableEntry 20 }

acsPowerMgmtPhasesTablePowerMin OBJECT-TYPE
        SYNTAX             Integer32
        MAX-ACCESS         read-only
        STATUS             current
        DESCRIPTION
        "Min detected value of power consumption in this phase.( W x 10 )"
::= { acsPowerMgmtPhasesTableEntry 21 }

acsPowerMgmtPhasesTablePowerAvg OBJECT-TYPE
        SYNTAX             Integer32
        MAX-ACCESS         read-only
        STATUS             current
        DESCRIPTION
        "Average value for power consumption in this phase.( W x 10 )"
::= { acsPowerMgmtPhasesTableEntry 22 }

acsPowerMgmtPhasesTablePowerReset OBJECT-TYPE
        SYNTAX       INTEGER {
            no-action (1),
            reset (2)
                    }
        MAX-ACCESS      read-write
        STATUS          current
        DESCRIPTION     "Reset max, min and avg values of power consumption."
::= { acsPowerMgmtPhasesTableEntry 23 }

acsPowerMgmtPhasesTablePowerFactorType OBJECT-TYPE
        SYNTAX       INTEGER {
            none-sensor (0),
            estimated (1),
            read (2)
                    }
        MAX-ACCESS      read-only
        STATUS          current
        DESCRIPTION     "Type of power factor values."
::= { acsPowerMgmtPhasesTableEntry 24 }

acsPowerMgmtPhasesTablePowerFactorValue OBJECT-TYPE
        SYNTAX             Integer32
        MAX-ACCESS         read-only
        STATUS             current
        DESCRIPTION
        "Actual value of power factor in this phase.( PF x 100 )"
::= { acsPowerMgmtPhasesTableEntry 25 }

acsPowerMgmtPhasesTablePowerFactorMax OBJECT-TYPE
        SYNTAX             Integer32
        MAX-ACCESS         read-only
        STATUS             current
        DESCRIPTION
        "Max detected value of power factor in this phase.( PF x 100 )"
::= { acsPowerMgmtPhasesTableEntry 26 }

acsPowerMgmtPhasesTablePowerFactorMin OBJECT-TYPE
        SYNTAX             Integer32
        MAX-ACCESS         read-only
        STATUS             current
        DESCRIPTION
        "Min detected value of power factor in this phase.( PF x 100 )"
::= { acsPowerMgmtPhasesTableEntry 27 }

acsPowerMgmtPhasesTablePowerFactorAvg OBJECT-TYPE
        SYNTAX             Integer32
        MAX-ACCESS         read-only
        STATUS             current
        DESCRIPTION
        "Average value for power factor in this phase.( PF x 100 )"
::= { acsPowerMgmtPhasesTableEntry 28 }

acsPowerMgmtPhasesTablePowerFactorReset OBJECT-TYPE
        SYNTAX       INTEGER {
            no-action (1),
            reset (2)
                    }
        MAX-ACCESS      read-write
        STATUS          current
        DESCRIPTION     "Reset max, min and avg values of power factor."
::= { acsPowerMgmtPhasesTableEntry 29 }

acsPowerMgmtPhasesTableAlarm OBJECT-TYPE
        SYNTAX       INTEGER {
            normal (1),
            blow-fuse (2),
            hw-ocp (3),
            high-critical (4),
            high-warning (5),
            low-warning (6),
            low-critical (7)
                    }
        MAX-ACCESS      read-only
        STATUS          current
        DESCRIPTION     "Show the phase alarm status."
::= { acsPowerMgmtPhasesTableEntry 30 }

acsPowerMgmtBanksTable OBJECT-TYPE
        SYNTAX             SEQUENCE OF AcsPowerMgmtBanksTableEntry
        MAX-ACCESS         not-accessible
        STATUS             current
        DESCRIPTION
        "This table contains data monitoring of each detected bank."
::= { acsPowerMgmt 9 }

acsPowerMgmtBanksTableEntry        OBJECT-TYPE
        SYNTAX            AcsPowerMgmtBanksTableEntry
        MAX-ACCESS        not-accessible
        STATUS            current
        DESCRIPTION
        "each entry has the data monitoring about bank."
        INDEX  { acsPowerMgmtBanksTablePortNumber, acsPowerMgmtBanksTablePduIndex, acsPowerMgmtBanksTableBankIndex }
::= { acsPowerMgmtBanksTable 1 }

AcsPowerMgmtBanksTableEntry ::= SEQUENCE  {
    acsPowerMgmtBanksTablePortNumber        InterfaceIndex,  -- number of serial port
    acsPowerMgmtBanksTablePduIndex          InterfaceIndexOrZero, -- number of PDU
    acsPowerMgmtBanksTableBankIndex         InterfaceIndexOrZero, -- bank index
    acsPowerMgmtBanksTableBankName          DisplayString,   -- Bank Name
    acsPowerMgmtBanksTablePduId             DisplayString,   -- PDU identification
    acsPowerMgmtBanksTablePortName          DisplayString,   -- Serial Port Name
    acsPowerMgmtBanksTableCurrentValue      Integer32,    -- actual value of bank current sensor
    acsPowerMgmtBanksTableCurrentMax        Integer32,    -- max detected value of current sensor
    acsPowerMgmtBanksTableCurrentMin        Integer32,    -- min detected value of current sensor
    acsPowerMgmtBanksTableCurrentAvg        Integer32,    -- average value for current sensor
    acsPowerMgmtBanksTableCurrentReset      INTEGER,      -- reset max, min and avg values
    acsPowerMgmtBanksTableVoltageType       INTEGER,      -- type of bank voltage
    acsPowerMgmtBanksTableVoltageValue      Integer32,    -- actual value of bank voltage
    acsPowerMgmtBanksTableVoltageMax        Integer32,    -- max value of voltage sensor
    acsPowerMgmtBanksTableVoltageMin        Integer32,    -- min value of voltage sensor
    acsPowerMgmtBanksTableVoltageAvg        Integer32,    -- avg value of voltage sensor
    acsPowerMgmtBanksTableVoltageReset      INTEGER,      -- reset max, min and avg values
    acsPowerMgmtBanksTablePowerType         INTEGER,      -- type of bank power consumption
    acsPowerMgmtBanksTablePowerValue        Integer32,    -- actual value of bank power consumption
    acsPowerMgmtBanksTablePowerMax          Integer32,    -- max value
    acsPowerMgmtBanksTablePowerMin          Integer32,    -- min value
    acsPowerMgmtBanksTablePowerAvg          Integer32,    -- average value
    acsPowerMgmtBanksTablePowerReset        INTEGER,      -- reset max, min and avg values
    acsPowerMgmtBanksTablePowerFactorType   INTEGER,      -- type of bank power factor
    acsPowerMgmtBanksTablePowerFactorValue  Integer32,    -- actual value of bank power factor
    acsPowerMgmtBanksTablePowerFactorMax    Integer32,    -- max value for power factor
    acsPowerMgmtBanksTablePowerFactorMin    Integer32,    -- min value for power factor
    acsPowerMgmtBanksTablePowerFactorAvg    Integer32,    -- avg value for power factor
    acsPowerMgmtBanksTablePowerFactorReset  INTEGER,      -- reset max, min and avg values
    acsPowerMgmtBanksTableAlarm             INTEGER       -- status of bank alarm
}

acsPowerMgmtBanksTablePortNumber OBJECT-TYPE
        SYNTAX            InterfaceIndex
        MAX-ACCESS        read-only
        STATUS            current
        DESCRIPTION
        "Number of serial port when the PDU is connected."
::= { acsPowerMgmtBanksTableEntry 1 }

acsPowerMgmtBanksTablePduIndex OBJECT-TYPE
        SYNTAX            InterfaceIndexOrZero
        MAX-ACCESS        read-only
        STATUS            current
        DESCRIPTION
        "A PDU position in the chain."
::= { acsPowerMgmtBanksTableEntry 2 }

acsPowerMgmtBanksTableBankIndex OBJECT-TYPE
        SYNTAX            InterfaceIndexOrZero
        MAX-ACCESS        read-only
        STATUS            current
        DESCRIPTION
        "Bank index in the PDU."
::= { acsPowerMgmtBanksTableEntry 3 }

acsPowerMgmtBanksTableBankName OBJECT-TYPE
        SYNTAX             DisplayString
        MAX-ACCESS         read-only
        STATUS             current
        DESCRIPTION
        "Bank name in the PDU."
::= { acsPowerMgmtBanksTableEntry 4 }

acsPowerMgmtBanksTablePduId  OBJECT-TYPE
        SYNTAX             DisplayString
        MAX-ACCESS         read-only
        STATUS             current
        DESCRIPTION
        "PDU identification."
::= { acsPowerMgmtBanksTableEntry 5 }

acsPowerMgmtBanksTablePortName OBJECT-TYPE
        SYNTAX             DisplayString
        MAX-ACCESS         read-only
        STATUS             current
        DESCRIPTION
        "Name of serial port when the PDU is connected."
::= { acsPowerMgmtBanksTableEntry 6 }

acsPowerMgmtBanksTableCurrentValue OBJECT-TYPE
        SYNTAX             Integer32
        MAX-ACCESS         read-only
        STATUS             current
        DESCRIPTION
        "Actual value of current sensor in this bank.( A x 10 )"
::= { acsPowerMgmtBanksTableEntry 7 }

acsPowerMgmtBanksTableCurrentMax OBJECT-TYPE
        SYNTAX             Integer32
        MAX-ACCESS         read-only
        STATUS             current
        DESCRIPTION
        "Max detected value of current sensor in this bank.( A x 10 )"
::= { acsPowerMgmtBanksTableEntry 8 }

acsPowerMgmtBanksTableCurrentMin OBJECT-TYPE
        SYNTAX             Integer32
        MAX-ACCESS         read-only
        STATUS             current
        DESCRIPTION
        "Min detected value of current sensor in this bank.( A x 10 )"
::= { acsPowerMgmtBanksTableEntry 9 }

acsPowerMgmtBanksTableCurrentAvg OBJECT-TYPE
        SYNTAX             Integer32
        MAX-ACCESS         read-only
        STATUS             current
        DESCRIPTION
        "Average value for current sensor in this bank.( A x 10 )"
::= { acsPowerMgmtBanksTableEntry 10 }

acsPowerMgmtBanksTableCurrentReset OBJECT-TYPE
        SYNTAX       INTEGER {
            no-action (1),
            reset (2)
                    }
        MAX-ACCESS      read-write
        STATUS          current
        DESCRIPTION     "Reset max, min and avg values of current."
::= { acsPowerMgmtBanksTableEntry 11 }

acsPowerMgmtBanksTableVoltageType OBJECT-TYPE
        SYNTAX       INTEGER {
            none-sensor (0),
            estimated (1),
            read (2)
                    }
        MAX-ACCESS      read-only
        STATUS          current
        DESCRIPTION     "Type of voltage values."
::= { acsPowerMgmtBanksTableEntry 12 }

acsPowerMgmtBanksTableVoltageValue OBJECT-TYPE
        SYNTAX             Integer32
        MAX-ACCESS         read-only
        STATUS             current
        DESCRIPTION
        "Actual value of voltage sensor in this bank.( V )"
::= { acsPowerMgmtBanksTableEntry 13 }

acsPowerMgmtBanksTableVoltageMax OBJECT-TYPE
        SYNTAX             Integer32
        MAX-ACCESS         read-only
        STATUS             current
        DESCRIPTION
        "Max detected value of voltage sensor in this bank.( V )"
::= { acsPowerMgmtBanksTableEntry 14 }

acsPowerMgmtBanksTableVoltageMin OBJECT-TYPE
        SYNTAX             Integer32
        MAX-ACCESS         read-only
        STATUS             current
        DESCRIPTION
        "Min detected value of voltage sensor in this bank.( V )"
::= { acsPowerMgmtBanksTableEntry 15 }

acsPowerMgmtBanksTableVoltageAvg OBJECT-TYPE
        SYNTAX             Integer32
        MAX-ACCESS         read-only
        STATUS             current
        DESCRIPTION
        "Average value for voltage sensor in this bank.( V )"
::= { acsPowerMgmtBanksTableEntry 16 }

acsPowerMgmtBanksTableVoltageReset OBJECT-TYPE
        SYNTAX       INTEGER {
            no-action (1),
            reset (2)
                    }
        MAX-ACCESS      read-write
        STATUS          current
        DESCRIPTION     "Reset max, min and avg values of voltage."
::= { acsPowerMgmtBanksTableEntry 17 }

acsPowerMgmtBanksTablePowerType OBJECT-TYPE
        SYNTAX       INTEGER {
            none-sensor (0),
            estimated (1),
            read (2)
                    }
        MAX-ACCESS      read-only
        STATUS          current
        DESCRIPTION     "Type of power consumption values."
::= { acsPowerMgmtBanksTableEntry 18 }

acsPowerMgmtBanksTablePowerValue OBJECT-TYPE
        SYNTAX             Integer32
        MAX-ACCESS         read-only
        STATUS             current
        DESCRIPTION
        "Actual value of power consumption in this bank.( W x 10 )"
::= { acsPowerMgmtBanksTableEntry 19 }

acsPowerMgmtBanksTablePowerMax OBJECT-TYPE
        SYNTAX             Integer32
        MAX-ACCESS         read-only
        STATUS             current
        DESCRIPTION
        "Max detected value of power consumption in this bank.( W x 10 )"
::= { acsPowerMgmtBanksTableEntry 20 }

acsPowerMgmtBanksTablePowerMin OBJECT-TYPE
        SYNTAX             Integer32
        MAX-ACCESS         read-only
        STATUS             current
        DESCRIPTION
        "Min detected value of power consumption in this bank.( W x 10 )"
::= { acsPowerMgmtBanksTableEntry 21 }

acsPowerMgmtBanksTablePowerAvg OBJECT-TYPE
        SYNTAX             Integer32
        MAX-ACCESS         read-only
        STATUS             current
        DESCRIPTION
        "Average value for power consumption in this bank.( W x 10 )"
::= { acsPowerMgmtBanksTableEntry 22 }

acsPowerMgmtBanksTablePowerReset OBJECT-TYPE
        SYNTAX       INTEGER {
            no-action (1),
            reset (2)
                    }
        MAX-ACCESS      read-write
        STATUS          current
        DESCRIPTION     "Reset max, min and avg values of power consumption."
::= { acsPowerMgmtBanksTableEntry 23 }

acsPowerMgmtBanksTablePowerFactorType OBJECT-TYPE
        SYNTAX       INTEGER {
            none-sensor (0),
            estimated (1),
            read (2)
                    }
        MAX-ACCESS      read-only
        STATUS          current
        DESCRIPTION     "Type of power factor values."
::= { acsPowerMgmtBanksTableEntry 24 }

acsPowerMgmtBanksTablePowerFactorValue OBJECT-TYPE
        SYNTAX             Integer32
        MAX-ACCESS         read-only
        STATUS             current
        DESCRIPTION
        "Actual value of power factor in this bank.( PF x 100 )"
::= { acsPowerMgmtBanksTableEntry 25 }

acsPowerMgmtBanksTablePowerFactorMax OBJECT-TYPE
        SYNTAX             Integer32
        MAX-ACCESS         read-only
        STATUS             current
        DESCRIPTION
        "Max detected value of power factor in this bank.( PF x 100 )"
::= { acsPowerMgmtBanksTableEntry 26 }

acsPowerMgmtBanksTablePowerFactorMin OBJECT-TYPE
        SYNTAX             Integer32
        MAX-ACCESS         read-only
        STATUS             current
        DESCRIPTION
        "Min detected value of power factor in this bank.( PF x 100 )"
::= { acsPowerMgmtBanksTableEntry 27 }

acsPowerMgmtBanksTablePowerFactorAvg OBJECT-TYPE
        SYNTAX             Integer32
        MAX-ACCESS         read-only
        STATUS             current
        DESCRIPTION
        "Average value for power factor in this bank.( PF x 100 )"
::= { acsPowerMgmtBanksTableEntry 28 }

acsPowerMgmtBanksTablePowerFactorReset OBJECT-TYPE
        SYNTAX       INTEGER {
            no-action (1),
            reset (2)
                    }
        MAX-ACCESS      read-write
        STATUS          current
        DESCRIPTION     "Reset max, min and avg values of power factor."
::= { acsPowerMgmtBanksTableEntry 29 }

acsPowerMgmtBanksTableAlarm OBJECT-TYPE
        SYNTAX       INTEGER {
            normal (1),
            blow-fuse (2),
            hw-ocp (3),
            high-critical (4),
            high-warning (5),
            low-warning (6),
            low-critical (7)
                    }
        MAX-ACCESS      read-only
        STATUS          current
        DESCRIPTION     "Show the bank alarm status."
::= { acsPowerMgmtBanksTableEntry 30 }

acsPowerMgmtEnvMonTable OBJECT-TYPE
        SYNTAX             SEQUENCE OF AcsPowerMgmtEnvMonTableEntry
        MAX-ACCESS         not-accessible
        STATUS             current
        DESCRIPTION
        "This table contains data monitoring of each detected environmental sensor."
::= { acsPowerMgmt 10 }

acsPowerMgmtEnvMonTableEntry        OBJECT-TYPE
        SYNTAX            AcsPowerMgmtEnvMonTableEntry
        MAX-ACCESS        not-accessible
        STATUS            current
        DESCRIPTION
        "each entry has the data monitoring about environmental sensors."
        INDEX  { acsPowerMgmtEnvMonTablePortNumber, acsPowerMgmtEnvMonTablePduIndex, acsPowerMgmtEnvMonTableIndex }
::= { acsPowerMgmtEnvMonTable 1 }

AcsPowerMgmtEnvMonTableEntry ::= SEQUENCE  {
    acsPowerMgmtEnvMonTablePortNumber    InterfaceIndex,  -- number of serial port
    acsPowerMgmtEnvMonTablePduIndex      InterfaceIndexOrZero, -- number of PDU
    acsPowerMgmtEnvMonTableIndex         InterfaceIndexOrZero, -- index
    acsPowerMgmtEnvMonTableName          DisplayString,   -- sensor name
    acsPowerMgmtEnvMonTablePduId         DisplayString,   -- PDU identification
    acsPowerMgmtEnvMonTablePortName      DisplayString,   -- Serial Port Name
    acsPowerMgmtEnvMonTableType          INTEGER,         -- environmental sensor type
    acsPowerMgmtEnvMonTableStatus        INTEGER,         -- state of digital sensor
    acsPowerMgmtEnvMonTableValue         Integer32,       -- value
    acsPowerMgmtEnvMonTableMaxValue      Integer32        -- max value
}

acsPowerMgmtEnvMonTablePortNumber OBJECT-TYPE
        SYNTAX            InterfaceIndex
        MAX-ACCESS        read-only
        STATUS            current
        DESCRIPTION
        "Number of serial port when the PDU is connected."
::= { acsPowerMgmtEnvMonTableEntry 1 }

acsPowerMgmtEnvMonTablePduIndex OBJECT-TYPE
        SYNTAX            InterfaceIndexOrZero
        MAX-ACCESS        read-only
        STATUS            current
        DESCRIPTION
        "A PDU position in the chain."
::= { acsPowerMgmtEnvMonTableEntry 2 }

acsPowerMgmtEnvMonTableIndex OBJECT-TYPE
        SYNTAX            InterfaceIndexOrZero
        MAX-ACCESS        read-only
        STATUS            current
        DESCRIPTION
        "envmon sensor index."
::= { acsPowerMgmtEnvMonTableEntry 3 }

acsPowerMgmtEnvMonTableName OBJECT-TYPE
        SYNTAX             DisplayString
        MAX-ACCESS         read-only
        STATUS             current
        DESCRIPTION
        "envmon sensor name."
::= { acsPowerMgmtEnvMonTableEntry 4 }

acsPowerMgmtEnvMonTablePduId  OBJECT-TYPE
        SYNTAX             DisplayString
        MAX-ACCESS         read-only
        STATUS             current
        DESCRIPTION
        "PDU identification."
::= { acsPowerMgmtEnvMonTableEntry 5 }

acsPowerMgmtEnvMonTablePortName OBJECT-TYPE
        SYNTAX             DisplayString
        MAX-ACCESS         read-only
        STATUS             current
        DESCRIPTION
        "Name of serial port when the PDU is connected."
::= { acsPowerMgmtEnvMonTableEntry 6 }

acsPowerMgmtEnvMonTableType OBJECT-TYPE
    SYNTAX  INTEGER {
        temp-internal (1),
        temperature (2),
        humidity (3),
        air-flow (4),
        smoke (5),
        dry-contact (6),
        water-level (7),
        motion (8),
        unplugged (9),
        unknown (10),
        air-pressure (11),
        vibration (12),
        vibration-contact (13),
        leak(14),
        door-contact (15),
        dewpoint (16),
        ad-converter(17),
        voltage(18),
        current(19)
    }
    MAX-ACCESS      read-only
    STATUS          current
    DESCRIPTION     "The type of environmental monitor."
::= { acsPowerMgmtEnvMonTableEntry 7 }

acsPowerMgmtEnvMonTableStatus OBJECT-TYPE
    SYNTAX  INTEGER {
        normal(1),
        triggered(2),
        not-applicable(3),
        leak(4),
        cableFault(5)
    }
    MAX-ACCESS      read-only
    STATUS          current
    DESCRIPTION     "Status of digital sensors:
        Dry-Contact, Water level, Smoke sensor, Motion sensor, Door-Contact, Leak, A2D.
        For Door-Contact, normal(1) = closed, triggered(2) = opened.
        For A2D, normal(1) = low, triggered(2) = high.
        For Leak, normal(1) = no leak, leak(4) = leak, cableFault(5) = cable fault."
::= { acsPowerMgmtEnvMonTableEntry 8 }

acsPowerMgmtEnvMonTableValue OBJECT-TYPE
        SYNTAX             Integer32
        MAX-ACCESS         read-only
        STATUS             current
        DESCRIPTION
        "Detected value for envmon sensors. Temperature: C x 10. Humidity: %. Air flow: afu."
::= { acsPowerMgmtEnvMonTableEntry 9 }

acsPowerMgmtEnvMonTableMaxValue OBJECT-TYPE
        SYNTAX             Integer32
        MAX-ACCESS         read-only
        STATUS             current
        DESCRIPTION
        "Max detected value for envmon sensors. Temperature: C x 10. Humidity: %. Air flow: afu.
        Voltage VDC x 100. Current x 100."
::= { acsPowerMgmtEnvMonTableEntry 10 }

acsPowerMgmtOutElecMonTable OBJECT-TYPE
        SYNTAX             SEQUENCE OF AcsPowerMgmtOutElecMonTableEntry
        MAX-ACCESS         not-accessible
        STATUS             current
        DESCRIPTION
        "This table contains the information about data monitoring of outlets."
::= { acsPowerMgmt 11 }

acsPowerMgmtOutElecMonTableEntry  OBJECT-TYPE
        SYNTAX            AcsPowerMgmtOutElecMonTableEntry
        MAX-ACCESS        not-accessible
        STATUS            current
        DESCRIPTION
        "each entry has the information about the outlet."
        INDEX             { acsPowerMgmtOutElecMonTablePortNumber,
                            acsPowerMgmtOutElecMonTablePduNumber,
                            acsPowerMgmtOutElecMonTableNumber }
::= { acsPowerMgmtOutElecMonTable 1 }

AcsPowerMgmtOutElecMonTableEntry ::= SEQUENCE  {
    acsPowerMgmtOutElecMonTablePortNumber       InterfaceIndex, -- serial port #
    acsPowerMgmtOutElecMonTablePduNumber        InterfaceIndex,
    acsPowerMgmtOutElecMonTableNumber           InterfaceIndex, -- outlet number in PDU
    acsPowerMgmtOutElecMonTableCurrentValue     Integer32,      -- actual value for current
    acsPowerMgmtOutElecMonTableCurrentMax       Integer32,      -- max detected value for current
    acsPowerMgmtOutElecMonTableCurrentMin       Integer32,      -- min detected value for current
    acsPowerMgmtOutElecMonTableCurrentAvg       Integer32,      -- average value for current
    acsPowerMgmtOutElecMonTableCurrentReset     INTEGER,        -- reset max, min and avg values of current
    acsPowerMgmtOutElecMonTablePowerValue       Integer32,      -- actual value for power
    acsPowerMgmtOutElecMonTablePowerMax         Integer32,      -- max detected value for power
    acsPowerMgmtOutElecMonTablePowerMin         Integer32,      -- min detected value for power
    acsPowerMgmtOutElecMonTablePowerAvg         Integer32,      -- average value for power
    acsPowerMgmtOutElecMonTablePowerReset       INTEGER,        -- reset max, min and avg values of power
    acsPowerMgmtOutElecMonTableVoltageValue     Integer32,      -- actual value for voltage
    acsPowerMgmtOutElecMonTableVoltageMax       Integer32,      -- max detected value for voltage
    acsPowerMgmtOutElecMonTableVoltageMin       Integer32,      -- min detected value for voltage
    acsPowerMgmtOutElecMonTableVoltageAvg       Integer32,      -- average value for voltage
    acsPowerMgmtOutElecMonTableVoltageReset     INTEGER,        -- reset max, min and avg values of voltage
    acsPowerMgmtOutElecMonTablePowerFactorValue Integer32,      -- actual value for power factor
    acsPowerMgmtOutElecMonTablePowerFactorMax   Integer32,      -- max detected value for power factor
    acsPowerMgmtOutElecMonTablePowerFactorMin   Integer32,      -- min detected value for power factor
    acsPowerMgmtOutElecMonTablePowerFactorAvg   Integer32,      -- avg value for power factor
    acsPowerMgmtOutElecMonTablePowerFactorReset INTEGER,        -- reset max, min and avg values of power factor
    acsPowerMgmtOutElecMonTableAlarm            INTEGER         -- outlet alarm status
}

acsPowerMgmtOutElecMonTablePortNumber OBJECT-TYPE
        SYNTAX             InterfaceIndex
        MAX-ACCESS         read-only
        STATUS             current
        DESCRIPTION
        "Serial Port number."
::= { acsPowerMgmtOutElecMonTableEntry 1 }

acsPowerMgmtOutElecMonTablePduNumber OBJECT-TYPE
        SYNTAX             InterfaceIndex
        MAX-ACCESS         read-only
        STATUS             current
        DESCRIPTION
        "Index."
::= { acsPowerMgmtOutElecMonTableEntry 2 }

acsPowerMgmtOutElecMonTableNumber OBJECT-TYPE
        SYNTAX             InterfaceIndex
        MAX-ACCESS         read-only
        STATUS             current
        DESCRIPTION
        "Number of the outlet in the PDU."
::= { acsPowerMgmtOutElecMonTableEntry 3 }

acsPowerMgmtOutElecMonTableCurrentValue OBJECT-TYPE
        SYNTAX             Integer32
        MAX-ACCESS         read-only
        STATUS             current
        DESCRIPTION
        "Actual value of outlet current sensor.( A x 10 )"
::= { acsPowerMgmtOutElecMonTableEntry 4 }

acsPowerMgmtOutElecMonTableCurrentMax OBJECT-TYPE
        SYNTAX             Integer32
        MAX-ACCESS         read-only
        STATUS             current
        DESCRIPTION
        "Max detected value of outlet current sensor.( A x 10 )"
::= { acsPowerMgmtOutElecMonTableEntry 5 }

acsPowerMgmtOutElecMonTableCurrentMin OBJECT-TYPE
        SYNTAX             Integer32
        MAX-ACCESS         read-only
        STATUS             current
        DESCRIPTION
        "Min detected value of outlet current sensor.( A x 10 )"
::= { acsPowerMgmtOutElecMonTableEntry 6 }

acsPowerMgmtOutElecMonTableCurrentAvg OBJECT-TYPE
        SYNTAX             Integer32
        MAX-ACCESS         read-only
        STATUS             current
        DESCRIPTION
        "Average value for outlet current sensor.( A x 10 )"
::= { acsPowerMgmtOutElecMonTableEntry 7 }

acsPowerMgmtOutElecMonTableCurrentReset OBJECT-TYPE
        SYNTAX        INTEGER {
                noAction(1),
                reset(2)
        }
        MAX-ACCESS         read-write
        STATUS             current
        DESCRIPTION
        "Reset max, min and avertage values of outlet current."
::= { acsPowerMgmtOutElecMonTableEntry 8 }

acsPowerMgmtOutElecMonTablePowerValue OBJECT-TYPE
        SYNTAX             Integer32
        MAX-ACCESS         read-only
        STATUS             current
        DESCRIPTION
        "Actual value of outlet power comsumption sensor.( W x 10 )"
::= { acsPowerMgmtOutElecMonTableEntry 9 }

acsPowerMgmtOutElecMonTablePowerMax OBJECT-TYPE
        SYNTAX             Integer32
        MAX-ACCESS         read-only
        STATUS             current
        DESCRIPTION
        "Max detected value of outlet power comsumption sensor.( W x 10 )"
::= { acsPowerMgmtOutElecMonTableEntry 10 }

acsPowerMgmtOutElecMonTablePowerMin OBJECT-TYPE
        SYNTAX             Integer32
        MAX-ACCESS         read-only
        STATUS             current
        DESCRIPTION
        "Min detected value of outlet power comsumption sensor.( W x 10 )"
::= { acsPowerMgmtOutElecMonTableEntry 11 }

acsPowerMgmtOutElecMonTablePowerAvg OBJECT-TYPE
        SYNTAX             Integer32
        MAX-ACCESS         read-only
        STATUS             current
        DESCRIPTION
        "Average value for outlet power comsumption sensor.( W x 10 )"
::= { acsPowerMgmtOutElecMonTableEntry 12 }

acsPowerMgmtOutElecMonTablePowerReset OBJECT-TYPE
        SYNTAX        INTEGER {
                noAction(1),
                reset(2)
        }
        MAX-ACCESS         read-write
        STATUS             current
        DESCRIPTION
        "Reset max, min and avertage values of outlet power comsumption."
::= { acsPowerMgmtOutElecMonTableEntry 13 }

acsPowerMgmtOutElecMonTableVoltageValue OBJECT-TYPE
        SYNTAX             Integer32
        MAX-ACCESS         read-only
        STATUS             current
        DESCRIPTION
        "Actual value of outlet voltage sensor.( V )"
::= { acsPowerMgmtOutElecMonTableEntry 14 }

acsPowerMgmtOutElecMonTableVoltageMax OBJECT-TYPE
        SYNTAX             Integer32
        MAX-ACCESS         read-only
        STATUS             current
        DESCRIPTION
        "Max detected value of outlet voltage sensor.( V )"
::= { acsPowerMgmtOutElecMonTableEntry 15 }

acsPowerMgmtOutElecMonTableVoltageMin OBJECT-TYPE
        SYNTAX             Integer32
        MAX-ACCESS         read-only
        STATUS             current
        DESCRIPTION
        "Min detected value of outlet voltage sensor.( V )"
::= { acsPowerMgmtOutElecMonTableEntry 16 }

acsPowerMgmtOutElecMonTableVoltageAvg OBJECT-TYPE
        SYNTAX             Integer32
        MAX-ACCESS         read-only
        STATUS             current
        DESCRIPTION
        "Average value for outlet voltage sensor.( V )"
::= { acsPowerMgmtOutElecMonTableEntry 17 }

acsPowerMgmtOutElecMonTableVoltageReset OBJECT-TYPE
        SYNTAX        INTEGER {
                noAction(1),
                reset(2)
        }
        MAX-ACCESS         read-write
        STATUS             current
        DESCRIPTION
        "Reset max, min and avertage values of outlet voltage."
::= { acsPowerMgmtOutElecMonTableEntry 18 }

acsPowerMgmtOutElecMonTablePowerFactorValue OBJECT-TYPE
        SYNTAX             Integer32
        MAX-ACCESS         read-only
        STATUS             current
        DESCRIPTION
        "Actual value of outlet power-factor sensor.( PF x 100 )"
::= { acsPowerMgmtOutElecMonTableEntry 19 }

acsPowerMgmtOutElecMonTablePowerFactorMax OBJECT-TYPE
        SYNTAX             Integer32
        MAX-ACCESS         read-only
        STATUS             current
        DESCRIPTION
        "Max detected value of outlet power-factor sensor.( PF x 100 )"
::= { acsPowerMgmtOutElecMonTableEntry 20 }

acsPowerMgmtOutElecMonTablePowerFactorMin OBJECT-TYPE
        SYNTAX             Integer32
        MAX-ACCESS         read-only
        STATUS             current
        DESCRIPTION
        "Min detected value of outlet power-factor sensor.( PF x 100 )"
::= { acsPowerMgmtOutElecMonTableEntry 21 }

acsPowerMgmtOutElecMonTablePowerFactorAvg OBJECT-TYPE
        SYNTAX             Integer32
        MAX-ACCESS         read-only
        STATUS             current
        DESCRIPTION
        "Average value for outlet power-factor sensor.( PF x 100 )"
::= { acsPowerMgmtOutElecMonTableEntry 22 }

acsPowerMgmtOutElecMonTablePowerFactorReset OBJECT-TYPE
        SYNTAX        INTEGER {
                noAction(1),
                reset(2)
        }
        MAX-ACCESS         read-write
        STATUS             current
        DESCRIPTION
        "Reset max, min and avertage values of outlet power-factor."
::= { acsPowerMgmtOutElecMonTableEntry 23 }

acsPowerMgmtOutElecMonTableAlarm OBJECT-TYPE
        SYNTAX       INTEGER {
            normal (1),
            blow-fuse (2),
            hw-ocp (3),
            high-critical (4),
            high-warning (5),
            low-warning (6),
            low-critical (7)
                    }
        MAX-ACCESS      read-only
        STATUS          current
        DESCRIPTION     "Show the outlet alarm status."
::= { acsPowerMgmtOutElecMonTableEntry 24 }


acsPowerMgmtUPSTable OBJECT-TYPE
        SYNTAX             SEQUENCE OF AcsPowerMgmtUPSTableEntry
        MAX-ACCESS         not-accessible
        STATUS             current
        DESCRIPTION
        "This table contains the list of detected UPSs."
::= { acsPowerMgmt 12 }

acsPowerMgmtUPSTableEntry        OBJECT-TYPE
        SYNTAX            AcsPowerMgmtUPSTableEntry
        MAX-ACCESS        not-accessible
        STATUS            current
        DESCRIPTION
        "Each entry has the information about the UPS."
        INDEX                { acsPowerMgmtUPSTablePortNumber, acsPowerMgmtUPSTableUpsIndex }
::= { acsPowerMgmtUPSTable 1 }

AcsPowerMgmtUPSTableEntry ::= SEQUENCE  {
        acsPowerMgmtUPSTablePortNumber                 InterfaceIndex,  -- number of serial port
        acsPowerMgmtUPSTableUpsIndex                   InterfaceIndexOrZero,
        acsPowerMgmtUPSTableUpsId                      DisplayString,   -- UPS identification
        acsPowerMgmtUPSTablePortName                   DisplayString,   -- Serial Port Name  or IP address if network device
        acsPowerMgmtUPSTableModel                      DisplayString,
        acsPowerMgmtUPSTableVendor                     DisplayString,
        acsPowerMgmtUPSTableFirmwareVersion            DisplayString,
        acsPowerMgmtUPSTableAgentFirmwareVersion       DisplayString,
        acsPowerMgmtUPSTableSystemStatus               DisplayString,
        acsPowerMgmtUPSTableInputBlackOutCount         Integer32,
        acsPowerMgmtUPSTableInputBrownOutCount         Integer32,
        acsPowerMgmtUPSTableInletAirTemperature        DisplayString,
        acsPowerMgmtUPSTableNumberOutletGroups         Integer32,

        acsPowerMgmtUPSTableUPSSerialNumber            DisplayString,
        acsPowerMgmtUPSTableUPSManufactureDate         DisplayString,

        acsPowerMgmtUPSTableAutoRestartDelay           Integer32,
        acsPowerMgmtUPSTableAutoRestartControl         INTEGER,
        acsPowerMgmtUPSTableAudibleAlarmControl        INTEGER,
        acsPowerMgmtUPSTableSilenceAlarm               Integer32,
        acsPowerMgmtUPSTableInverterState              DisplayString,
        acsPowerMgmtUPSTableDCConverterStatus          DisplayString,
        acsPowerMgmtUPSTableShutdownReason             DisplayString,
        acsPowerMgmtUPSTableUPSTopology                DisplayString,
        acsPowerMgmtUPSTableBypassInverterInputConfig  DisplayString

}

acsPowerMgmtUPSTablePortNumber OBJECT-TYPE
        SYNTAX            InterfaceIndex
        MAX-ACCESS        read-only
        STATUS            current
        DESCRIPTION
        "Number of serial port when the UPS is connected."
::= { acsPowerMgmtUPSTableEntry 1 }

acsPowerMgmtUPSTableUpsIndex OBJECT-TYPE
        SYNTAX            InterfaceIndexOrZero
        MAX-ACCESS        read-only
        STATUS            current
        DESCRIPTION
        "A UPS position in the chain."
::= { acsPowerMgmtUPSTableEntry 2 }

 acsPowerMgmtUPSTableUpsId  OBJECT-TYPE
         SYNTAX             DisplayString
         MAX-ACCESS         read-only
         STATUS             current
         DESCRIPTION
         "UPS identification."
 ::= { acsPowerMgmtUPSTableEntry 3 }

acsPowerMgmtUPSTablePortName OBJECT-TYPE
        SYNTAX             DisplayString

        MAX-ACCESS         read-only
        STATUS             current
        DESCRIPTION
        "Name of serial port or IP address if network device"
::= { acsPowerMgmtUPSTableEntry 4 }

acsPowerMgmtUPSTableModel  OBJECT-TYPE
        SYNTAX             DisplayString
        MAX-ACCESS         read-only
        STATUS             current
        DESCRIPTION
        "Model of the UPS."
::= { acsPowerMgmtUPSTableEntry 5 }

acsPowerMgmtUPSTableVendor  OBJECT-TYPE
        SYNTAX             DisplayString
        MAX-ACCESS         read-only
        STATUS             current
        DESCRIPTION
        "Vendor of the UPS."
::= { acsPowerMgmtUPSTableEntry 6 }

acsPowerMgmtUPSTableFirmwareVersion OBJECT-TYPE
        SYNTAX             DisplayString
        MAX-ACCESS         read-only
        STATUS             current
        DESCRIPTION
        "Version of the UPS firmware."
::= { acsPowerMgmtUPSTableEntry 7 }

acsPowerMgmtUPSTableAgentFirmwareVersion OBJECT-TYPE
        SYNTAX             DisplayString
        MAX-ACCESS         read-only
        STATUS             current
        DESCRIPTION
        "Firmware version of the agent card."
::= { acsPowerMgmtUPSTableEntry 8 }

acsPowerMgmtUPSTableSystemStatus OBJECT-TYPE
       SYNTAX             DisplayString
       MAX-ACCESS         read-only
        STATUS             current
        DESCRIPTION
        "System Status of the UPS."
::= { acsPowerMgmtUPSTableEntry 9 }

acsPowerMgmtUPSTableInputBlackOutCount OBJECT-TYPE
        SYNTAX             Integer32
        MAX-ACCESS         read-only
        STATUS             current
        DESCRIPTION
        "The number of occurrences, since the last reset, where the input
        was not qualified to provide power to the system."
::= { acsPowerMgmtUPSTableEntry 10 }

acsPowerMgmtUPSTableInputBrownOutCount OBJECT-TYPE
        SYNTAX             Integer32
        MAX-ACCESS         read-only
        STATUS             current
        DESCRIPTION
        "The number of occurrences, since the last reset, where the system
        input voltage has fallen below a pre-determined threshold for a
        specified amount of time."
::= { acsPowerMgmtUPSTableEntry 11 }

acsPowerMgmtUPSTableInletAirTemperature OBJECT-TYPE
        SYNTAX             DisplayString
        MAX-ACCESS         read-only
        STATUS             current
        DESCRIPTION
        "Temperature of the inlet air."
::= { acsPowerMgmtUPSTableEntry 12 }

acsPowerMgmtUPSTableNumberOutletGroups OBJECT-TYPE
        SYNTAX             Integer32
        MAX-ACCESS         read-only
        STATUS             current
        DESCRIPTION
        "The number of Outlet Groups on this UPS"
::= { acsPowerMgmtUPSTableEntry 13 }

acsPowerMgmtUPSTableUPSSerialNumber OBJECT-TYPE
        SYNTAX             DisplayString
        MAX-ACCESS         read-only
        STATUS             current
        DESCRIPTION
        "System serial number."
::= { acsPowerMgmtUPSTableEntry 14 }

acsPowerMgmtUPSTableUPSManufactureDate OBJECT-TYPE
        SYNTAX             DisplayString
        MAX-ACCESS         read-only
        STATUS             current
        DESCRIPTION
        "Manufacturing date of the system."
::= { acsPowerMgmtUPSTableEntry 15 }

acsPowerMgmtUPSTableAutoRestartDelay OBJECT-TYPE
        SYNTAX             Integer32
        MAX-ACCESS         read-write
        STATUS             current
        DESCRIPTION
        "If power is lost, the control will delay this amount of
        time after power is restored before restarting the unit."
::= { acsPowerMgmtUPSTableEntry 16 }

acsPowerMgmtUPSTableAutoRestartControl OBJECT-TYPE
        SYNTAX INTEGER {
                disabled(1),
                enabled(2)
        }
        MAX-ACCESS         read-write
        STATUS             current
        DESCRIPTION
        "When set to enabled, the UPS will automatically restart the load
        when utility power is restored after a battery discharge."
::= { acsPowerMgmtUPSTableEntry 17 }

acsPowerMgmtUPSTableAudibleAlarmControl OBJECT-TYPE
        SYNTAX INTEGER {
                off(1),
                on(2)
        }
        MAX-ACCESS         read-write
        STATUS             current
        DESCRIPTION
        "Audible alarm control."
::= { acsPowerMgmtUPSTableEntry 18 }

acsPowerMgmtUPSTableSilenceAlarm OBJECT-TYPE
        SYNTAX INTEGER {
                noAction(0),
                silenceAlarm(1)
        }
        MAX-ACCESS         read-write
        STATUS             current
        DESCRIPTION
        "Silence audible alarm."
::= { acsPowerMgmtUPSTableEntry 19 }

acsPowerMgmtUPSTableInverterState OBJECT-TYPE
        SYNTAX             DisplayString
        MAX-ACCESS         read-only
        STATUS             current
        DESCRIPTION
        "Inverter on/off state."
::= { acsPowerMgmtUPSTableEntry 20 }

acsPowerMgmtUPSTableDCConverterStatus OBJECT-TYPE
        SYNTAX             DisplayString
        MAX-ACCESS         read-only
        STATUS             current
        DESCRIPTION
        "The operating state of the dc converter."
::= { acsPowerMgmtUPSTableEntry 21 }

acsPowerMgmtUPSTableShutdownReason OBJECT-TYPE
        SYNTAX             DisplayString
        MAX-ACCESS         read-only
        STATUS             current
        DESCRIPTION
        "The reason for the most recent shutdown."
::= { acsPowerMgmtUPSTableEntry 22 }

acsPowerMgmtUPSTableUPSTopology OBJECT-TYPE
        SYNTAX             DisplayString
        MAX-ACCESS         read-only
        STATUS             current
        DESCRIPTION
        "UPS Topology."
::= { acsPowerMgmtUPSTableEntry 23 }

acsPowerMgmtUPSTableBypassInverterInputConfig OBJECT-TYPE
        SYNTAX             DisplayString
        MAX-ACCESS         read-only
        STATUS             current
        DESCRIPTION
        "Input source configuration for the bypass and inverter."
::= { acsPowerMgmtUPSTableEntry 24 }

--
-- acsPowerMgmtUPSInputTable           ::= { acsPowerMgmt 13 }
--
acsPowerMgmtUPSInputTable OBJECT-TYPE
        SYNTAX             SEQUENCE OF AcsPowerMgmtUPSInputTableEntry
        MAX-ACCESS         not-accessible
        STATUS             current
        DESCRIPTION
        "This table contains the information about UPS inputs."
::= { acsPowerMgmt 13 }

acsPowerMgmtUPSInputTableEntry        OBJECT-TYPE
        SYNTAX            AcsPowerMgmtUPSInputTableEntry
        MAX-ACCESS        not-accessible
        STATUS            current
        DESCRIPTION
        "each entry has the information about the UPS inputs."
        INDEX             { acsPowerMgmtUPSInputTablePortNumber,
                            acsPowerMgmtUPSInputTableUpsIndex }
::= { acsPowerMgmtUPSInputTable 1 }

AcsPowerMgmtUPSInputTableEntry ::= SEQUENCE  {
        acsPowerMgmtUPSInputTablePortNumber       InterfaceIndex, -- serial port #
        acsPowerMgmtUPSInputTableUpsIndex         InterfaceIndex,
        acsPowerMgmtUPSInputTableFrequency        DisplayString,
        acsPowerMgmtUPSInputTableRMSVoltageL1N    DisplayString,
        acsPowerMgmtUPSInputTableRMSVoltageL1L2   DisplayString,
        acsPowerMgmtUPSInputTableRMSVoltageL2N    DisplayString,
        acsPowerMgmtUPSInputTableRMSCurrentL1     DisplayString,
        acsPowerMgmtUPSInputTableRMSCurrentL2     DisplayString,
        acsPowerMgmtUPSInputTableMaxVoltageL1N    DisplayString,
        acsPowerMgmtUPSInputTableMinVoltageL1N    DisplayString,
        acsPowerMgmtUPSInputTableMaxVoltageL2N    DisplayString,
        acsPowerMgmtUPSInputTableMinVoltageL2N    DisplayString,
        acsPowerMgmtUPSInputTableNominalVoltage   DisplayString,
        acsPowerMgmtUPSInputTableNominalFrequency DisplayString,
        acsPowerMgmtUPSInputTableNominalCurrent   DisplayString,
        acsPowerMgmtUPSInputTableEnergy           DisplayString,
        acsPowerMgmtUPSInputTablePowerFactorL1N   DisplayString,
        acsPowerMgmtUPSInputTablePowerFactorL2N   DisplayString
}

acsPowerMgmtUPSInputTablePortNumber OBJECT-TYPE
        SYNTAX             InterfaceIndex
        MAX-ACCESS         read-only
        STATUS             current
        DESCRIPTION
        "Serial Port number."
::= { acsPowerMgmtUPSInputTableEntry 1 }

acsPowerMgmtUPSInputTableUpsIndex OBJECT-TYPE
        SYNTAX             InterfaceIndex
        MAX-ACCESS         read-only
        STATUS             current
        DESCRIPTION
        "Index."
::= { acsPowerMgmtUPSInputTableEntry 2 }

acsPowerMgmtUPSInputTableFrequency OBJECT-TYPE
        SYNTAX             DisplayString
        MAX-ACCESS         read-only
        STATUS             current
        DESCRIPTION
        "Input Frequency."
::= { acsPowerMgmtUPSInputTableEntry 3 }

acsPowerMgmtUPSInputTableRMSVoltageL1N OBJECT-TYPE
        SYNTAX             DisplayString
        MAX-ACCESS         read-only
        STATUS             current
        DESCRIPTION
        "RMS Voltage L1-N."
::= { acsPowerMgmtUPSInputTableEntry 4 }

acsPowerMgmtUPSInputTableRMSVoltageL1L2 OBJECT-TYPE
        SYNTAX             DisplayString
        MAX-ACCESS         read-only
        STATUS             current
        DESCRIPTION
        "RMS Voltage L1L2."
::= { acsPowerMgmtUPSInputTableEntry 5 }

acsPowerMgmtUPSInputTableRMSVoltageL2N OBJECT-TYPE
        SYNTAX             DisplayString
        MAX-ACCESS         read-only
        STATUS             current
        DESCRIPTION
        "RMS Voltage L2N."
::= { acsPowerMgmtUPSInputTableEntry 6 }

acsPowerMgmtUPSInputTableRMSCurrentL1 OBJECT-TYPE
        SYNTAX             DisplayString
        MAX-ACCESS         read-only
        STATUS             current
        DESCRIPTION
        "RMS Current for L1."
::= { acsPowerMgmtUPSInputTableEntry 7 }

acsPowerMgmtUPSInputTableRMSCurrentL2 OBJECT-TYPE
        SYNTAX             DisplayString
        MAX-ACCESS         read-only
        STATUS             current
        DESCRIPTION
        "RMS Current for L2."
::= { acsPowerMgmtUPSInputTableEntry 8 }

acsPowerMgmtUPSInputTableMaxVoltageL1N OBJECT-TYPE
        SYNTAX             DisplayString
        MAX-ACCESS         read-only
        STATUS             current
        DESCRIPTION
        "Input Max Voltage measurement for Line L1-N since the last reset."
::= { acsPowerMgmtUPSInputTableEntry 9 }

acsPowerMgmtUPSInputTableMinVoltageL1N OBJECT-TYPE
        SYNTAX             DisplayString
        MAX-ACCESS         read-only
        STATUS             current
        DESCRIPTION
        "Input Min Voltage measurement for Line L1-N since the last reset."
::= { acsPowerMgmtUPSInputTableEntry 10 }

acsPowerMgmtUPSInputTableMaxVoltageL2N OBJECT-TYPE
        SYNTAX             DisplayString
        MAX-ACCESS         read-only
        STATUS             current
        DESCRIPTION
        "Input Max Voltage measurement for Line L2-N since the last reset."
::= { acsPowerMgmtUPSInputTableEntry 11 }

acsPowerMgmtUPSInputTableMinVoltageL2N OBJECT-TYPE
        SYNTAX             DisplayString
        MAX-ACCESS         read-only
        STATUS             current
        DESCRIPTION
        "Input Min Voltage measurement for Line L1-N since the last reset."
::= { acsPowerMgmtUPSInputTableEntry 12 }

acsPowerMgmtUPSInputTableNominalVoltage OBJECT-TYPE
        SYNTAX             DisplayString
        MAX-ACCESS         read-only
        STATUS             current
        DESCRIPTION
        "Input nominal voltage."
::= { acsPowerMgmtUPSInputTableEntry 13 }

acsPowerMgmtUPSInputTableNominalFrequency OBJECT-TYPE
        SYNTAX             DisplayString
        MAX-ACCESS         read-only
        STATUS             current
        DESCRIPTION
        "Input nominal frequency."
::= { acsPowerMgmtUPSInputTableEntry 14 }

acsPowerMgmtUPSInputTableNominalCurrent OBJECT-TYPE
        SYNTAX             DisplayString
        MAX-ACCESS         read-only
        STATUS             current
        DESCRIPTION
        "Input nominal current."
::= { acsPowerMgmtUPSInputTableEntry 15 }

acsPowerMgmtUPSInputTableEnergy OBJECT-TYPE
        SYNTAX             DisplayString
        MAX-ACCESS         read-only
        STATUS             current
        DESCRIPTION
        "Input Energy."
::= { acsPowerMgmtUPSInputTableEntry 16 }

acsPowerMgmtUPSInputTablePowerFactorL1N OBJECT-TYPE
        SYNTAX             DisplayString
        MAX-ACCESS         read-only
        STATUS             current
        DESCRIPTION
        "Input Power Factor for Line 1."
::= { acsPowerMgmtUPSInputTableEntry 17 }

acsPowerMgmtUPSInputTablePowerFactorL2N OBJECT-TYPE
        SYNTAX             DisplayString
        MAX-ACCESS         read-only
        STATUS             current
        DESCRIPTION
        "Input Power Factor for Line 2."
::= { acsPowerMgmtUPSInputTableEntry 18 }

--
-- acsPowerMgmtUPSBypassTable           ::= { acsPowerMgmt 14 }
--
acsPowerMgmtUPSBypassTable OBJECT-TYPE
        SYNTAX             SEQUENCE OF AcsPowerMgmtUPSBypassTableEntry
        MAX-ACCESS         not-accessible
        STATUS             current
        DESCRIPTION
        "This table contains the information about UPS bypass."
::= { acsPowerMgmt 14 }

acsPowerMgmtUPSBypassTableEntry        OBJECT-TYPE
        SYNTAX            AcsPowerMgmtUPSBypassTableEntry
        MAX-ACCESS        not-accessible
        STATUS            current
        DESCRIPTION
        "each entry has the information about the UPS bypass."
        INDEX             { acsPowerMgmtUPSBypassTablePortNumber,
                            acsPowerMgmtUPSBypassTableUpsIndex }
::= { acsPowerMgmtUPSBypassTable 1 }

AcsPowerMgmtUPSBypassTableEntry ::= SEQUENCE  {
        acsPowerMgmtUPSBypassTablePortNumber      InterfaceIndex, -- serial port #
        acsPowerMgmtUPSBypassTableUpsIndex        InterfaceIndex,
        acsPowerMgmtUPSBypassTableRMSVoltageL1N   DisplayString,
        acsPowerMgmtUPSBypassTableRMSVoltageL1L2  DisplayString,
        acsPowerMgmtUPSBypassTableRMSVoltageL2N   DisplayString,
        acsPowerMgmtUPSBypassTableRMSCurrent      DisplayString,
        acsPowerMgmtUPSBypassTableRMSCurrentL2    DisplayString,
        acsPowerMgmtUPSBypassTableInputFrequency  DisplayString,
        acsPowerMgmtUPSBypassTableNominalVoltage  DisplayString
}

acsPowerMgmtUPSBypassTablePortNumber OBJECT-TYPE
        SYNTAX             InterfaceIndex
        MAX-ACCESS         read-only
        STATUS             current
        DESCRIPTION
        "Serial Port number."
::= { acsPowerMgmtUPSBypassTableEntry 1 }

acsPowerMgmtUPSBypassTableUpsIndex OBJECT-TYPE
        SYNTAX             InterfaceIndex
        MAX-ACCESS         read-only
        STATUS             current
        DESCRIPTION
        "Index."
::= { acsPowerMgmtUPSBypassTableEntry 2 }

acsPowerMgmtUPSBypassTableRMSVoltageL1N OBJECT-TYPE
        SYNTAX             DisplayString
        MAX-ACCESS         read-only
        STATUS             current
        DESCRIPTION
        "RMS Voltage L1N."
::= { acsPowerMgmtUPSBypassTableEntry 3 }

acsPowerMgmtUPSBypassTableRMSVoltageL1L2 OBJECT-TYPE
        SYNTAX             DisplayString
        MAX-ACCESS         read-only
        STATUS             current
        DESCRIPTION
        "RMS Voltage L1L2."
::= { acsPowerMgmtUPSBypassTableEntry 4 }

acsPowerMgmtUPSBypassTableRMSVoltageL2N OBJECT-TYPE
        SYNTAX             DisplayString
        MAX-ACCESS         read-only
        STATUS             current
        DESCRIPTION
        "RMS Voltage L2N."
::= { acsPowerMgmtUPSBypassTableEntry 5 }

acsPowerMgmtUPSBypassTableRMSCurrent OBJECT-TYPE
        SYNTAX             DisplayString
        MAX-ACCESS         read-only
        STATUS             current
        DESCRIPTION
        "RMS Current."
::= { acsPowerMgmtUPSBypassTableEntry 6 }

acsPowerMgmtUPSBypassTableRMSCurrentL2 OBJECT-TYPE
        SYNTAX             DisplayString
        MAX-ACCESS         read-only
        STATUS             current
        DESCRIPTION
        "RMS Current."
::= { acsPowerMgmtUPSBypassTableEntry 7 }

acsPowerMgmtUPSBypassTableInputFrequency OBJECT-TYPE
        SYNTAX             DisplayString
        MAX-ACCESS         read-only
        STATUS             current
        DESCRIPTION
        "Bypass Input Frequency."
::= { acsPowerMgmtUPSBypassTableEntry 8 }

acsPowerMgmtUPSBypassTableNominalVoltage OBJECT-TYPE
        SYNTAX             DisplayString
        MAX-ACCESS         read-only
        STATUS             current
        DESCRIPTION
        "Bypass Nominal Voltage."
::= { acsPowerMgmtUPSBypassTableEntry 9 }


--
-- acsPowerMgmtUPSBatteryTable           ::= { acsPowerMgmt 15 }
--
acsPowerMgmtUPSBatteryTable OBJECT-TYPE
        SYNTAX             SEQUENCE OF AcsPowerMgmtUPSBatteryTableEntry
        MAX-ACCESS         not-accessible
        STATUS             current
        DESCRIPTION
        "This table contains the information about UPS battery."
::= { acsPowerMgmt 15 }

acsPowerMgmtUPSBatteryTableEntry        OBJECT-TYPE
        SYNTAX            AcsPowerMgmtUPSBatteryTableEntry
        MAX-ACCESS        not-accessible
        STATUS            current
        DESCRIPTION
        "each entry has the information about the UPS bypass."
        INDEX             { acsPowerMgmtUPSBatteryTablePortNumber,
                            acsPowerMgmtUPSBatteryTableUpsIndex }
::= { acsPowerMgmtUPSBatteryTable 1 }

AcsPowerMgmtUPSBatteryTableEntry ::= SEQUENCE  {
        acsPowerMgmtUPSBatteryTablePortNumber        InterfaceIndex, -- serial port #
        acsPowerMgmtUPSBatteryTableUpsIndex                  InterfaceIndex,
        acsPowerMgmtUPSBatteryTableDCBusVoltage              DisplayString,
        acsPowerMgmtUPSBatteryTableTimeRemaining             DisplayString,
        acsPowerMgmtUPSBatteryTablePercentageCharge          DisplayString,
        acsPowerMgmtUPSBatteryTableChargeStatus              DisplayString,
        acsPowerMgmtUPSBatteryTableLowBatteryWarningTime     INTEGER,
        acsPowerMgmtUPSBatteryTableTestResult                DisplayString,
        acsPowerMgmtUPSBatteryTableDCBusNominalVoltage       DisplayString,
        acsPowerMgmtUPSBatteryTableNominalBatteryCapacity    DisplayString,
        acsPowerMgmtUPSBatteryTableBatteryFloatVoltage       DisplayString,
        acsPowerMgmtUPSBatteryTableBatteryCabinetType        DisplayString,
        acsPowerMgmtUPSBatteryTableBatteryNumberOfEBC        DisplayString,
        acsPowerMgmtUPSBatteryTableBatteryRating             DisplayString,
        acsPowerMgmtUPSBatteryTableBatteryDischargeTime      DisplayString,
        acsPowerMgmtUPSBatteryTableBatteryChargeCompensating DisplayString,
        acsPowerMgmtUPSBatteryTableBatteryChargerState       DisplayString,
        acsPowerMgmtUPSBatteryTableStartBatteryTest          INTEGER,
        acsPowerMgmtUPSBatteryTableBatteryStatus             DisplayString,
        acsPowerMgmtUPSBatteryTableBatteryTotalDischargeTime DisplayString,
        acsPowerMgmtUPSBatteryTableBatteryDischargeCount     DisplayString,
        acsPowerMgmtUPSBatteryTableBatteryCurrent            DisplayString
}

acsPowerMgmtUPSBatteryTablePortNumber OBJECT-TYPE
        SYNTAX             InterfaceIndex
        MAX-ACCESS         read-only
        STATUS             current
        DESCRIPTION
        "Serial Port number."
::= { acsPowerMgmtUPSBatteryTableEntry 1 }

acsPowerMgmtUPSBatteryTableUpsIndex OBJECT-TYPE
        SYNTAX             InterfaceIndex
        MAX-ACCESS         read-only
        STATUS             current
        DESCRIPTION
        "Index."
::= { acsPowerMgmtUPSBatteryTableEntry 2 }

acsPowerMgmtUPSBatteryTableDCBusVoltage OBJECT-TYPE
        SYNTAX             DisplayString
        MAX-ACCESS         read-only
        STATUS             current
        DESCRIPTION
        "DC Bus Voltage"
::= { acsPowerMgmtUPSBatteryTableEntry 3 }

acsPowerMgmtUPSBatteryTableTimeRemaining OBJECT-TYPE
        SYNTAX             DisplayString
        MAX-ACCESS         read-only
        STATUS             current
        DESCRIPTION
        "The calculated available time on battery."
::= { acsPowerMgmtUPSBatteryTableEntry 4 }

acsPowerMgmtUPSBatteryTablePercentageCharge OBJECT-TYPE
        SYNTAX             DisplayString
        MAX-ACCESS         read-only
        STATUS             current
        DESCRIPTION
        "Battery Percentage Charge."
::= { acsPowerMgmtUPSBatteryTableEntry 5 }

acsPowerMgmtUPSBatteryTableChargeStatus OBJECT-TYPE
        SYNTAX             DisplayString
        MAX-ACCESS         read-only
        STATUS             current
        DESCRIPTION
        "Battery Charge Status."
::= { acsPowerMgmtUPSBatteryTableEntry 6 }

acsPowerMgmtUPSBatteryTableLowBatteryWarningTime OBJECT-TYPE
        SYNTAX             INTEGER  (2..30)
        MAX-ACCESS         read-write
        STATUS             current
        DESCRIPTION
        "When battery time remaining falls to, or below, this value
        (minutes) the low battery alarm is activated."
::= { acsPowerMgmtUPSBatteryTableEntry 7 }

acsPowerMgmtUPSBatteryTableTestResult OBJECT-TYPE
        SYNTAX             DisplayString
        MAX-ACCESS         read-only
        STATUS             current
        DESCRIPTION
        "The outcome of the previous battery test."
::= { acsPowerMgmtUPSBatteryTableEntry 8 }

acsPowerMgmtUPSBatteryTableDCBusNominalVoltage OBJECT-TYPE
        SYNTAX             DisplayString
        MAX-ACCESS         read-only
        STATUS             current
        DESCRIPTION
        "Battery DC Bus Nominal Voltage."
::= { acsPowerMgmtUPSBatteryTableEntry 9 }

acsPowerMgmtUPSBatteryTableNominalBatteryCapacity OBJECT-TYPE
        SYNTAX             DisplayString
        MAX-ACCESS         read-only
        STATUS             current
        DESCRIPTION
        "Nominal Battery Capacity."
::= { acsPowerMgmtUPSBatteryTableEntry 10 }

acsPowerMgmtUPSBatteryTableBatteryFloatVoltage OBJECT-TYPE
        SYNTAX             DisplayString
        MAX-ACCESS         read-only
        STATUS             current
        DESCRIPTION
        "Battery Float Voltage."
::= { acsPowerMgmtUPSBatteryTableEntry 11 }

acsPowerMgmtUPSBatteryTableBatteryCabinetType OBJECT-TYPE
        SYNTAX             DisplayString
        MAX-ACCESS         read-only
        STATUS             current
        DESCRIPTION
        "Battery Cabinet Type."
::= { acsPowerMgmtUPSBatteryTableEntry 12 }

acsPowerMgmtUPSBatteryTableBatteryNumberOfEBC OBJECT-TYPE
        SYNTAX             DisplayString
        MAX-ACCESS         read-only
        STATUS             current
        DESCRIPTION
        "Number of Extended Battery Cabinets installed."
::= { acsPowerMgmtUPSBatteryTableEntry 13 }

acsPowerMgmtUPSBatteryTableBatteryRating OBJECT-TYPE
        SYNTAX             DisplayString
        MAX-ACCESS         read-only
        STATUS             current
        DESCRIPTION
        "Battery Rating."
::= { acsPowerMgmtUPSBatteryTableEntry 14 }

acsPowerMgmtUPSBatteryTableBatteryDischargeTime OBJECT-TYPE
        SYNTAX             DisplayString
        MAX-ACCESS         read-only
        STATUS             current
        DESCRIPTION
        "Time on battery operation for this discharge"
::= { acsPowerMgmtUPSBatteryTableEntry 15 }

acsPowerMgmtUPSBatteryTableBatteryChargeCompensating OBJECT-TYPE
        SYNTAX             DisplayString
        MAX-ACCESS         read-only
        STATUS             current
        DESCRIPTION
        "Battery charge algorithm changed due to battery temperature."
::= { acsPowerMgmtUPSBatteryTableEntry 16 }

acsPowerMgmtUPSBatteryTableBatteryChargerState OBJECT-TYPE
        SYNTAX             DisplayString
        MAX-ACCESS         read-only
        STATUS             current
        DESCRIPTION
        "Battery charger state."
::= { acsPowerMgmtUPSBatteryTableEntry 17 }

acsPowerMgmtUPSBatteryTableStartBatteryTest OBJECT-TYPE
        SYNTAX INTEGER {
                noAction(1),
                start(2)
        }
        MAX-ACCESS         read-write
        STATUS             current
        DESCRIPTION
        "Command to initate a manual battery test."
::= { acsPowerMgmtUPSBatteryTableEntry 18 }

acsPowerMgmtUPSBatteryTableBatteryStatus OBJECT-TYPE
        SYNTAX             DisplayString
        MAX-ACCESS         read-only
        STATUS             current
        DESCRIPTION
        "Battery Status."
::= { acsPowerMgmtUPSBatteryTableEntry 19 }

acsPowerMgmtUPSBatteryTableBatteryTotalDischargeTime OBJECT-TYPE
        SYNTAX             DisplayString
        MAX-ACCESS         read-only
        STATUS             current
        DESCRIPTION
        "Cumulative battery discharge time."
::= { acsPowerMgmtUPSBatteryTableEntry 20 }

acsPowerMgmtUPSBatteryTableBatteryDischargeCount OBJECT-TYPE
        SYNTAX             DisplayString
        MAX-ACCESS         read-only
        STATUS             current
        DESCRIPTION
        " Total number of battery discharges."
::= { acsPowerMgmtUPSBatteryTableEntry 21 }

acsPowerMgmtUPSBatteryTableBatteryCurrent OBJECT-TYPE
        SYNTAX             DisplayString
        MAX-ACCESS         read-only
        STATUS             current
        DESCRIPTION
        " Current at the battery input terminals. In charging mode,
        the current will be a positive value. In discharging mode,
        the current will be a negative value."
::= { acsPowerMgmtUPSBatteryTableEntry 22 }

--
-- acsPowerMgmtUPSOutputTable           ::= { acsPowerMgmt 16 }
--
acsPowerMgmtUPSOutputTable OBJECT-TYPE
        SYNTAX             SEQUENCE OF AcsPowerMgmtUPSOutputTableEntry
        MAX-ACCESS         not-accessible
        STATUS             current
        DESCRIPTION
        "This table contains the information about UPS output."
::= { acsPowerMgmt 16 }

acsPowerMgmtUPSOutputTableEntry        OBJECT-TYPE
        SYNTAX            AcsPowerMgmtUPSOutputTableEntry
        MAX-ACCESS        not-accessible
        STATUS            current
        DESCRIPTION
        "Each entry has the information about the UPS output."
        INDEX             { acsPowerMgmtUPSOutputTablePortNumber,
                            acsPowerMgmtUPSOutputTableUpsIndex }
::= { acsPowerMgmtUPSOutputTable 1 }

AcsPowerMgmtUPSOutputTableEntry ::= SEQUENCE  {
        acsPowerMgmtUPSOutputTablePortNumber                 InterfaceIndex, -- serial port #
        acsPowerMgmtUPSOutputTableUpsIndex                   InterfaceIndex,
        acsPowerMgmtUPSOutputTableApparentPower              DisplayString,
        acsPowerMgmtUPSOutputTableFrequency                  DisplayString,
        acsPowerMgmtUPSOutputTablePercentPower               DisplayString,
        acsPowerMgmtUPSOutputTablePercentPowerL1             DisplayString,
        acsPowerMgmtUPSOutputTablePercentPowerL2             DisplayString,
        acsPowerMgmtUPSOutputTablePower                      DisplayString,
        acsPowerMgmtUPSOutputTableRMSCurrentL1               DisplayString,
        acsPowerMgmtUPSOutputTableRMSCurrentL2               DisplayString,
        acsPowerMgmtUPSOutputTableRMSVoltageL1N              DisplayString,
        acsPowerMgmtUPSOutputTableRMSVoltageL2N              DisplayString,
        acsPowerMgmtUPSOutputTableRMSVoltageL1L2             DisplayString,
        acsPowerMgmtUPSOutputOffDelay                        INTEGER,
        acsPowerMgmtUPSOutputOnDelay                         INTEGER,
        acsPowerMgmtUPSOutputCycleDelay                      INTEGER,
        acsPowerMgmtUPSOutputTableMaxVoltageL1               DisplayString,
        acsPowerMgmtUPSOutputTableMinVoltageL1               DisplayString,
        acsPowerMgmtUPSOutputTableMaxVoltageL2               DisplayString,
        acsPowerMgmtUPSOutputTableMinVoltageL2               DisplayString,
        acsPowerMgmtUPSOutputTableNominalVoltage             DisplayString,
        acsPowerMgmtUPSOutputTablePowerNominalFrequency      DisplayString,
        acsPowerMgmtUPSOutputTablePowerApparentPowerRating   DisplayString,
        acsPowerMgmtUPSOutputTablePowerNominalPowerFactor    DisplayString,
        acsPowerMgmtUPSOutputTablePowerPowerFactorCorrection DisplayString,
        acsPowerMgmtUPSOutputTablePowerL1                    DisplayString,
        acsPowerMgmtUPSOutputTablePowerL2                    DisplayString,
        acsPowerMgmtUPSOutputTableApparentPowerL1            DisplayString,
        acsPowerMgmtUPSOutputTableApparentPowerL2            DisplayString,
        acsPowerMgmtUPSOutputTablePowerFactorL1              DisplayString,
        acsPowerMgmtUPSOutputTablePowerFactorL2              DisplayString
}

acsPowerMgmtUPSOutputTablePortNumber OBJECT-TYPE
        SYNTAX             InterfaceIndex
        MAX-ACCESS         read-only
        STATUS             current
        DESCRIPTION
        "Serial Port number."
::= { acsPowerMgmtUPSOutputTableEntry 1 }

acsPowerMgmtUPSOutputTableUpsIndex OBJECT-TYPE
        SYNTAX             InterfaceIndex
        MAX-ACCESS         read-only
        STATUS             current
        DESCRIPTION
        "Index."
::= { acsPowerMgmtUPSOutputTableEntry 2 }

acsPowerMgmtUPSOutputTableApparentPower OBJECT-TYPE
        SYNTAX             DisplayString
        MAX-ACCESS         read-only
        STATUS             current
        DESCRIPTION
        "DC Bus Voltage"
::= { acsPowerMgmtUPSOutputTableEntry 3 }

acsPowerMgmtUPSOutputTableFrequency OBJECT-TYPE
        SYNTAX             DisplayString
        MAX-ACCESS         read-only
        STATUS             current
        DESCRIPTION
        "Output frequency."
::= { acsPowerMgmtUPSOutputTableEntry 4 }

acsPowerMgmtUPSOutputTablePercentPower OBJECT-TYPE
        SYNTAX             DisplayString
        MAX-ACCESS         read-only
        STATUS             current
        DESCRIPTION
        "The system output power as a percentage of the rated capacity."
::= { acsPowerMgmtUPSOutputTableEntry 5 }

acsPowerMgmtUPSOutputTablePercentPowerL1 OBJECT-TYPE
        SYNTAX             DisplayString
        MAX-ACCESS         read-only
        STATUS             current
        DESCRIPTION
        "The system output power on line L1 as a percentage of the rated capacity."
::= { acsPowerMgmtUPSOutputTableEntry 6 }

acsPowerMgmtUPSOutputTablePercentPowerL2 OBJECT-TYPE
        SYNTAX             DisplayString
        MAX-ACCESS         read-only
        STATUS             current
        DESCRIPTION
        "The system output power on line L2 as a percentage of the rated capacity."
::= { acsPowerMgmtUPSOutputTableEntry 7 }

acsPowerMgmtUPSOutputTablePower OBJECT-TYPE
        SYNTAX             DisplayString
        MAX-ACCESS         read-only
        STATUS             current
        DESCRIPTION
        "The sum total power of all system output phases."
::= { acsPowerMgmtUPSOutputTableEntry 8 }

acsPowerMgmtUPSOutputTableRMSCurrentL1 OBJECT-TYPE
        SYNTAX             DisplayString
        MAX-ACCESS         read-only
        STATUS             current
        DESCRIPTION
        "System output RMS current for line L1."
::= { acsPowerMgmtUPSOutputTableEntry 9 }

acsPowerMgmtUPSOutputTableRMSCurrentL2 OBJECT-TYPE
        SYNTAX             DisplayString
        MAX-ACCESS         read-only
        STATUS             current
        DESCRIPTION
        "System output RMS current for line L2."
::= { acsPowerMgmtUPSOutputTableEntry 10 }

acsPowerMgmtUPSOutputTableRMSVoltageL1N OBJECT-TYPE
        SYNTAX             DisplayString
        MAX-ACCESS         read-only
        STATUS             current
        DESCRIPTION
        "The system output RMS voltage."
::= { acsPowerMgmtUPSOutputTableEntry 11 }

acsPowerMgmtUPSOutputTableRMSVoltageL2N OBJECT-TYPE
        SYNTAX             DisplayString
        MAX-ACCESS         read-only
        STATUS             current
        DESCRIPTION
        "The system output RMS voltage."
::= { acsPowerMgmtUPSOutputTableEntry 12 }

acsPowerMgmtUPSOutputTableRMSVoltageL1L2 OBJECT-TYPE
        SYNTAX             DisplayString
        MAX-ACCESS         read-only
        STATUS             current
        DESCRIPTION
        "The system output RMS voltage."
::= { acsPowerMgmtUPSOutputTableEntry 13 }

acsPowerMgmtUPSOutputOffDelay OBJECT-TYPE
        SYNTAX             INTEGER  (0..300)
        MAX-ACCESS         read-write
        STATUS             current
        DESCRIPTION
        "Turns the UPS output off after the number of seconds specified.
        When a value is written to this object the output will be turned
        off after the specified time has elapsed and the output will
        remain off."
::= { acsPowerMgmtUPSOutputTableEntry 14 }

acsPowerMgmtUPSOutputOnDelay OBJECT-TYPE
        SYNTAX             INTEGER  (0..300)
        MAX-ACCESS         read-write
        STATUS             current
        DESCRIPTION
        "Turns the UPS output on after the number of seconds specified.
        When a value is written to this object the output will be turned
        on after the specified time has elapsed."
::= { acsPowerMgmtUPSOutputTableEntry 15 }

acsPowerMgmtUPSOutputCycleDelay OBJECT-TYPE
        SYNTAX             INTEGER  (0..300)
        MAX-ACCESS         read-write
        STATUS             current
        DESCRIPTION
        "Turns the UPS off and then back on after the number of seconds specified.
        When a value is written to this object the output will turned off immediately
        and then turned back on after the specified time has elapsed."
::= { acsPowerMgmtUPSOutputTableEntry 16 }

acsPowerMgmtUPSOutputTableMaxVoltageL1 OBJECT-TYPE
        SYNTAX             DisplayString
        MAX-ACCESS         read-only
        STATUS             current
        DESCRIPTION
        "The maximum system output voltage measurement for line 1 since the last reset."
::= { acsPowerMgmtUPSOutputTableEntry 17 }

acsPowerMgmtUPSOutputTableMinVoltageL1 OBJECT-TYPE
        SYNTAX             DisplayString
        MAX-ACCESS         read-only
        STATUS             current
        DESCRIPTION
        "The minimum system output voltage measurement for line 1 since the last reset."
::= { acsPowerMgmtUPSOutputTableEntry 18 }

acsPowerMgmtUPSOutputTableMaxVoltageL2 OBJECT-TYPE
        SYNTAX             DisplayString
        MAX-ACCESS         read-only
        STATUS             current
        DESCRIPTION
        "The maximum system output voltage measurement for line 21 since the last reset."
::= { acsPowerMgmtUPSOutputTableEntry 19 }

acsPowerMgmtUPSOutputTableMinVoltageL2 OBJECT-TYPE
        SYNTAX             DisplayString
        MAX-ACCESS         read-only
        STATUS             current
        DESCRIPTION
        "The minimum system output voltage measurement for line 2 since the last reset."
::= { acsPowerMgmtUPSOutputTableEntry 20 }

acsPowerMgmtUPSOutputTableNominalVoltage OBJECT-TYPE
        SYNTAX             DisplayString
        MAX-ACCESS         read-only
        STATUS             current
        DESCRIPTION
        "The nominal (or rated) system output voltage."
::= { acsPowerMgmtUPSOutputTableEntry 21 }

acsPowerMgmtUPSOutputTablePowerNominalFrequency OBJECT-TYPE
        SYNTAX             DisplayString
        MAX-ACCESS         read-only
        STATUS             current
        DESCRIPTION
        "The nominal (or rated) system output frequency."
::= { acsPowerMgmtUPSOutputTableEntry 22 }

acsPowerMgmtUPSOutputTablePowerApparentPowerRating OBJECT-TYPE
        SYNTAX             DisplayString
        MAX-ACCESS         read-only
        STATUS             current
        DESCRIPTION
        "Output apparent power rating."
::= { acsPowerMgmtUPSOutputTableEntry 23 }

acsPowerMgmtUPSOutputTablePowerNominalPowerFactor OBJECT-TYPE
        SYNTAX             DisplayString
        MAX-ACCESS         read-only
        STATUS             current
        DESCRIPTION
        "The nominal (or rated) system power factor."
::= { acsPowerMgmtUPSOutputTableEntry 24 }

acsPowerMgmtUPSOutputTablePowerPowerFactorCorrection OBJECT-TYPE
        SYNTAX             DisplayString
        MAX-ACCESS         read-only
        STATUS             current
        DESCRIPTION
        "The state of the power factor correction circuitry of the system."
::= { acsPowerMgmtUPSOutputTableEntry 25 }

acsPowerMgmtUPSOutputTablePowerL1 OBJECT-TYPE
        SYNTAX             DisplayString
        MAX-ACCESS         read-only
        STATUS             current
        DESCRIPTION
        "The system output power on line 1."
::= { acsPowerMgmtUPSOutputTableEntry 26 }

acsPowerMgmtUPSOutputTablePowerL2 OBJECT-TYPE
        SYNTAX             DisplayString
        MAX-ACCESS         read-only
        STATUS             current
        DESCRIPTION
        "The system output power on line 2."
::= { acsPowerMgmtUPSOutputTableEntry 27 }

acsPowerMgmtUPSOutputTableApparentPowerL1 OBJECT-TYPE
        SYNTAX             DisplayString
        MAX-ACCESS         read-only
        STATUS             current
        DESCRIPTION
        "The system output apparent power on line 1."
::= { acsPowerMgmtUPSOutputTableEntry 28 }

acsPowerMgmtUPSOutputTableApparentPowerL2 OBJECT-TYPE
        SYNTAX             DisplayString
        MAX-ACCESS         read-only
        STATUS             current
        DESCRIPTION
        "The system output apparent power on line 2."
::= { acsPowerMgmtUPSOutputTableEntry 29 }

acsPowerMgmtUPSOutputTablePowerFactorL1 OBJECT-TYPE
        SYNTAX             DisplayString
        MAX-ACCESS         read-only
        STATUS             current
        DESCRIPTION
        "The system output power factor on line 1."
::= { acsPowerMgmtUPSOutputTableEntry 30 }

acsPowerMgmtUPSOutputTablePowerFactorL2 OBJECT-TYPE
        SYNTAX             DisplayString
        MAX-ACCESS         read-only
        STATUS             current
        DESCRIPTION
        "The system output power factor on line 2."
::= { acsPowerMgmtUPSOutputTableEntry 31 }

--
-- acsPowerMgmtUPSEcoModeTable           ::= { acsPowerMgmt 17 }
--
acsPowerMgmtUPSEcoModeTable OBJECT-TYPE
        SYNTAX             SEQUENCE OF AcsPowerMgmtUPSEcoModeTableEntry
        MAX-ACCESS         not-accessible
        STATUS             current
        DESCRIPTION
        "This table contains the information about UPS ECO Mode."
::= { acsPowerMgmt 17 }

acsPowerMgmtUPSEcoModeTableEntry        OBJECT-TYPE
        SYNTAX            AcsPowerMgmtUPSEcoModeTableEntry
        MAX-ACCESS        not-accessible
        STATUS            current
        DESCRIPTION
        "each entry has the information about the UPS ECO Mode."
        INDEX             { acsPowerMgmtUPSBypassTablePortNumber,
                            acsPowerMgmtUPSBypassTableUpsIndex }
::= { acsPowerMgmtUPSEcoModeTable 1 }

AcsPowerMgmtUPSEcoModeTableEntry ::= SEQUENCE  {
        acsPowerMgmtUPSEcoModeTablePortNumber    InterfaceIndex, -- serial port #
        acsPowerMgmtUPSEcoModeTableUpsIndex      InterfaceIndex,
        acsPowerMgmtUPSEcoModeTableStatus        DisplayString,
        acsPowerMgmtUPSEcoModeTableStateControl  INTEGER
}

acsPowerMgmtUPSEcoModeTablePortNumber OBJECT-TYPE
        SYNTAX             InterfaceIndex
        MAX-ACCESS         read-only
        STATUS             current
        DESCRIPTION
        "Serial Port number."
::= { acsPowerMgmtUPSEcoModeTableEntry 1 }

acsPowerMgmtUPSEcoModeTableUpsIndex OBJECT-TYPE
        SYNTAX             InterfaceIndex
        MAX-ACCESS         read-only
        STATUS             current
        DESCRIPTION
        "Index."
::= { acsPowerMgmtUPSEcoModeTableEntry 2 }

acsPowerMgmtUPSEcoModeTableStatus OBJECT-TYPE
        SYNTAX             DisplayString
        MAX-ACCESS         read-only
        STATUS             current
        DESCRIPTION
        "Current ECO Mode Status."
::= { acsPowerMgmtUPSEcoModeTableEntry 3 }

acsPowerMgmtUPSEcoModeTableStateControl OBJECT-TYPE
        SYNTAX             INTEGER {
              noAction(1),
              enable(2),
              disable(3)
        }
        MAX-ACCESS         read-write
        STATUS             current
        DESCRIPTION
        "Enable or disable ECO mode."
::= { acsPowerMgmtUPSEcoModeTableEntry 4 }


--
-- acsPowerMgmtUPSOutletGroupTable           ::= { acsPowerMgmt 18 }
--
acsPowerMgmtUPSOutletGroupTable OBJECT-TYPE
        SYNTAX             SEQUENCE OF AcsPowerMgmtUPSOutletGroupTableEntry
        MAX-ACCESS         not-accessible
        STATUS             current
        DESCRIPTION
        "This table contains the UPS Outlet Group Information."
::= { acsPowerMgmt 18 }

acsPowerMgmtUPSOutletGroupTableEntry        OBJECT-TYPE
        SYNTAX            AcsPowerMgmtUPSOutletGroupTableEntry
        MAX-ACCESS        not-accessible
        STATUS            current
        DESCRIPTION
        "Each entry has the UPS outlet group information."
        INDEX             { acsPowerMgmtUPSOutletGroupTablePortNumber,
                            acsPowerMgmtUPSOutletGroupTableUpsIndex,
                            acsPowerMgmtUPSOutletGroupTableNumber }
::= { acsPowerMgmtUPSOutletGroupTable 1 }

AcsPowerMgmtUPSOutletGroupTableEntry ::= SEQUENCE  {
        acsPowerMgmtUPSOutletGroupTablePortNumber    InterfaceIndex, -- serial port #
        acsPowerMgmtUPSOutletGroupTableUpsIndex      InterfaceIndex,
        acsPowerMgmtUPSOutletGroupTableNumber        InterfaceIndex,
        acsPowerMgmtUPSOutletGroupTableLabel         DisplayString,
        acsPowerMgmtUPSOutletGroupTableState         DisplayString,
        acsPowerMgmtUPSOutletGroupTablePowerControl  INTEGER        -- manage the outlet group
}

acsPowerMgmtUPSOutletGroupTablePortNumber OBJECT-TYPE
        SYNTAX             InterfaceIndex
        MAX-ACCESS         read-only
        STATUS             current
        DESCRIPTION
        "Serial Port number."
::= { acsPowerMgmtUPSOutletGroupTableEntry 1 }

acsPowerMgmtUPSOutletGroupTableUpsIndex OBJECT-TYPE
        SYNTAX             InterfaceIndex
        MAX-ACCESS         read-only
        STATUS             current
        DESCRIPTION
        "Index."
::= { acsPowerMgmtUPSOutletGroupTableEntry 2 }

acsPowerMgmtUPSOutletGroupTableNumber OBJECT-TYPE
        SYNTAX             InterfaceIndex
        MAX-ACCESS         read-only
        STATUS             current
        DESCRIPTION
        "Number of the outletgroup in the UPS."
::= { acsPowerMgmtUPSOutletGroupTableEntry 3 }

acsPowerMgmtUPSOutletGroupTableLabel OBJECT-TYPE
        SYNTAX             DisplayString
        MAX-ACCESS         read-only
        STATUS             current
        DESCRIPTION
        "User-defined label for the outlet group."
::= { acsPowerMgmtUPSOutletGroupTableEntry 4 }

acsPowerMgmtUPSOutletGroupTableState OBJECT-TYPE
        SYNTAX             DisplayString
        MAX-ACCESS         read-only
        STATUS             current
        DESCRIPTION
        "User-defined label for the outlet group."
::= { acsPowerMgmtUPSOutletGroupTableEntry 5 }

acsPowerMgmtUPSOutletGroupTablePowerControl OBJECT-TYPE
        SYNTAX INTEGER {
                noAction(1),
                powerOn(2),
                powerOff(3),
                powerCycle(4)
        }
        MAX-ACCESS         read-write
        STATUS             current
        DESCRIPTION
        "A set value of power(2-6) will send command to the UPS.
         noAction(1) = always returned in a GET. Does nothing if SET.
         powerOn(2)  = when SET the power On command is sent to UPS.
         powerOff(3) = when SET the power Off command is sent to UPS.
         powerCycle(4)=when SET the power cycle command is sent to UPS."
::= { acsPowerMgmtUPSOutletGroupTableEntry 6 }


--
-- acsSensors
-- OBJECT IDENTIFIER ::= { acsManagement 7  }   10418.26.2.7
--
acsSensorsInternalCurrentCPUTemperature OBJECT-TYPE
        SYNTAX        Integer32
        MAX-ACCESS    read-only
        STATUS        current
        DESCRIPTION
        "The current CPU temperature in degrees Celsius."
::= { acsSensors 1 }

acsSensorsInternalMaxCPUTemperature OBJECT-TYPE
        SYNTAX             Integer32
        MAX-ACCESS         read-write
        STATUS             current
        DESCRIPTION
        "The CPU temperature in degrees Celsius that, if exceeded,
        will generate an event notification."
::= { acsSensors 2 }

acsSensorsInternalMaxCPUTemperatureThreshold OBJECT-TYPE
        SYNTAX             Integer32 (0..4)
        MAX-ACCESS         read-write
        STATUS             current
        DESCRIPTION
        "The CPU temperature threshold in degrees Celsius below the
        maximum CPU temperature. When the temperature exceeds the
        Maximum Temperature plus Threshold, an event notification
        will be generated. When the temperature falls below the
        Maximum Temperature minus Threshold, an event notification
        that the console system has returned to normal operating
        temperature will be generated."
::= { acsSensors 3 }

acsSensorsInternalMinCPUTemperature OBJECT-TYPE
        SYNTAX             Integer32
        MAX-ACCESS         read-write
        STATUS             current
        DESCRIPTION
        "The CPU temperature in degrees Celsius that, if the
        CPU temperature falls below, will generate an event notification."
::= { acsSensors 4 }

acsSensorsInternalMinCPUTemperatureThreshold OBJECT-TYPE
        SYNTAX             Integer32 (0..4)
        MAX-ACCESS         read-write
        STATUS             current
        DESCRIPTION
        "The CPU temperature threshold in degrees Celsius above the
        minimum CPU temperature."
::= { acsSensors 5 }

acsSensorsInternalCurrentBoardTemperature OBJECT-TYPE
        SYNTAX        Integer32
        MAX-ACCESS    read-only
        STATUS        current
        DESCRIPTION
        "The current board temperature in degrees Celsius."
::= { acsSensors 6 }

acsSensorsInternalMaxBoardTemperature OBJECT-TYPE
        SYNTAX             Integer32
        MAX-ACCESS         read-write
        STATUS             current
        DESCRIPTION
        "The board temperature in degrees Celsius that, if exceeded,
        will generate an event notification."
::= { acsSensors 7 }

acsSensorsInternalMaxBoardTemperatureThreshold OBJECT-TYPE
        SYNTAX             Integer32 (0..4)
        MAX-ACCESS         read-write
        STATUS             current
        DESCRIPTION
        "The board temperature threshold in degrees Celsius below the
        maximum board temperature. When the temperature exceeds the
        Maximum Temperature plus Threshold, an event notification
        will be generated. When the temperature falls below the
        Maximum Temperature minus Threshold, an event notification
        that the console system has returned to normal operating
        temperature will be generated."
::= { acsSensors 8 }

acsSensorsInternalMinBoardTemperature OBJECT-TYPE
        SYNTAX             Integer32
        MAX-ACCESS         read-write
        STATUS             current
        DESCRIPTION
        "The board temperature in degrees Celsius that, if the
        board temperature falls below, will generate an event notification."
::= { acsSensors 9 }

acsSensorsInternalMinBoardTemperatureThreshold OBJECT-TYPE
        SYNTAX             Integer32 (0..4)
        MAX-ACCESS         read-write
        STATUS             current
        DESCRIPTION
        "The board temperature threshold in degrees Celsius above the
        minimum board temperature."
::= { acsSensors 10 }

acsSensorsVoltagePSInternal OBJECT-TYPE
        SYNTAX             Integer32
        MAX-ACCESS         read-only
        STATUS             current
        DESCRIPTION
        "The PS Internal Supply voltage [0.95v ~ 1.05v] x 100."
::= { acsSensors 11 }

acsSensorsVoltagePLInternal OBJECT-TYPE
        SYNTAX             Integer32
        MAX-ACCESS         read-only
        STATUS             current
        DESCRIPTION
        "The PL Internal Supply voltage [0.95v ~ 1.05v] x 100."
::= { acsSensors 12 }

acsSensorsVoltagePSAuxiliary OBJECT-TYPE
        SYNTAX             Integer32
        MAX-ACCESS         read-only
        STATUS             current
        DESCRIPTION
        "The PS Auxiliary Supply voltage [1.71v ~ 1.89v] x 100."
::= { acsSensors 13 }

acsSensorsVoltagePLAuxiliary OBJECT-TYPE
        SYNTAX             Integer32
        MAX-ACCESS         read-only
        STATUS             current
        DESCRIPTION
        "The PL Auxiliary Supply voltage [1.71v ~ 1.89v] x 100."
::= { acsSensors 14 }

acsSensorsVoltagePSDDR3 OBJECT-TYPE
        SYNTAX             Integer32
        MAX-ACCESS         read-only
        STATUS             current
        DESCRIPTION
        "The PS DDR3 Supply voltage [1.31v ~ 1.39v] x 100."
::= { acsSensors 15 }

acsSensorsVoltagePLBlockRam OBJECT-TYPE
        SYNTAX             Integer32
        MAX-ACCESS         read-only
        STATUS             current
        DESCRIPTION
        "The PL Block RAM Supply voltage [0.95v ~ 1.05v] x 100."
::= { acsSensors 16 }

acsSensorsVoltagePowerSupply1 OBJECT-TYPE
        SYNTAX             Integer32
        MAX-ACCESS         read-only
        STATUS             current
        DESCRIPTION
        "The Power Supply 1 voltage [11.06v ~ 12.98v] x 100."
::= { acsSensors 17 }

acsSensorsVoltagePowerSupply2 OBJECT-TYPE
        SYNTAX             Integer32
        MAX-ACCESS         read-only
        STATUS             current
        DESCRIPTION
        "The Power Supply 2 voltage [11.06v ~ 12.98v] x 100."
::= { acsSensors 18 }

acsSensors1WireUpdateControl OBJECT-TYPE
        SYNTAX INTEGER {
                noAction(1),
                update(2)
        }
        MAX-ACCESS         read-write
        STATUS             current
        DESCRIPTION
        "A set value of update(2) will refresh the 1-wire sensor list."
::= { acsSensors 19 }

acsSensors1WireTable OBJECT-TYPE
        SYNTAX             SEQUENCE OF AcsSensors1WireTableEntry
        MAX-ACCESS         not-accessible
        STATUS             current
        DESCRIPTION
        "This table contains the list of detected external 1-wire sensors."
::= { acsSensors 20 }

acsSensors1WireTableEntry        OBJECT-TYPE
        SYNTAX            AcsSensors1WireTableEntry
        MAX-ACCESS        not-accessible
        STATUS            current
        DESCRIPTION
        "Each entry has the information about the external 1-wire sensor."
        INDEX          { acsSensors1WireTableIndex }
::= { acsSensors1WireTable 1 }

AcsSensors1WireTableEntry ::= SEQUENCE  {
        acsSensors1WireTableIndex              Integer32,
        acsSensors1WireTableName               DisplayString,
        acsSensors1WireTableLocation           DisplayString,
        acsSensors1WireTableAddress            DisplayString,
        acsSensors1WireTableType               INTEGER,
        acsSensors1WireTableUnit               INTEGER,
        acsSensors1WireTableValue              DisplayString,
        acsSensors1WireTableValueMax           Integer32,
        acsSensors1WireTableValueMin           Integer32,
        acsSensors1WireTableValueAvg           Integer32,
        acsSensors1WireTableValueLowWarning    Integer32,
        acsSensors1WireTableValueLowCritical   Integer32,
        acsSensors1WireTableValueHighWarning   Integer32,
        acsSensors1WireTableValueHighCritical  Integer32,
        acsSensors1WireTableReset              INTEGER,
        acsSensors1WireTableAnalogAlarm        INTEGER,
        acsSensors1WireTableContactAlarm1      INTEGER,
        acsSensors1WireTableContactAlarm2      INTEGER,
        acsSensors1WireTableContactAlarm3      INTEGER,
        acsSensors1WireTableLeakFilterTime     INTEGER,
        acsSensors1WireTableLeakAlarm          INTEGER,
        acsSensors1WireTableLeakCableFailAlarm INTEGER
}

acsSensors1WireTableIndex OBJECT-TYPE
        SYNTAX            Integer32 (1..20)
        MAX-ACCESS        read-only
        STATUS            current
        DESCRIPTION
        "Index of detected 1-wire sensor."
::= { acsSensors1WireTableEntry 1 }

acsSensors1WireTableName  OBJECT-TYPE
        SYNTAX             DisplayString
        MAX-ACCESS         read-write
        STATUS             current
        DESCRIPTION
        "Name of the 1-wire sensor."
::= { acsSensors1WireTableEntry 2 }

acsSensors1WireTableLocation  OBJECT-TYPE
        SYNTAX             DisplayString
        MAX-ACCESS         read-write
        STATUS             current
        DESCRIPTION
        "Location of the 1-wire sensor."
::= { acsSensors1WireTableEntry 3 }

acsSensors1WireTableAddress  OBJECT-TYPE
        SYNTAX             DisplayString
        MAX-ACCESS         read-only
        STATUS             current
        DESCRIPTION
        "Address of the 1-wire sensor."
::= { acsSensors1WireTableEntry 4 }

acsSensors1WireTableType OBJECT-TYPE
        SYNTAX  INTEGER {
            sensor-unknown(0),
            external-temperature(1),
            external-humidity(2),
            door-contact(3),
            dry-contact(4),
            leak(5),
            differential-pressure(6)
        }
        MAX-ACCESS      read-only
        STATUS          current
        DESCRIPTION     "Type of 1-wire sensor."
::= { acsSensors1WireTableEntry 5 }

acsSensors1WireTableUnit OBJECT-TYPE
        SYNTAX  INTEGER {
            notApplicable(0),
            celsius(1),
            fahrenheit(2),
            percent(3),
            pa(4)
        }
        MAX-ACCESS      read-only
        STATUS          current
        DESCRIPTION
        "The unit of the 1-wire sensor.
         notApplicable(0) = used for contact or leak sensor
         celsius(1)       = used for temperature sensor
         fahrenheit(2)    = used for temperature sensor
         percent(3)       = used for humidity sensor
         pascal(4)        = used for differential pressure sensor."
::= { acsSensors1WireTableEntry 6 }

acsSensors1WireTableValue OBJECT-TYPE
        SYNTAX          DisplayString
        MAX-ACCESS      read-only
        STATUS          current
        DESCRIPTION     "Current sensor reading."
::= { acsSensors1WireTableEntry 7 }

acsSensors1WireTableValueMax OBJECT-TYPE
        SYNTAX          Integer32
        MAX-ACCESS      read-only
        STATUS          current
        DESCRIPTION     "Maximum sensor reading detected. Unit is specified in acsSensors1WireTableUnit."
::= { acsSensors1WireTableEntry 8 }

acsSensors1WireTableValueMin OBJECT-TYPE
        SYNTAX          Integer32
        MAX-ACCESS      read-only
        STATUS          current
        DESCRIPTION     "Minimum sensor reading detected. Unit is specified in acsSensors1WireTableUnit."
::= { acsSensors1WireTableEntry 9 }

acsSensors1WireTableValueAvg OBJECT-TYPE
        SYNTAX          Integer32
        MAX-ACCESS      read-only
        STATUS          current
        DESCRIPTION     "Average sensor reading detected. Unit is specified in acsSensors1WireTableUnit."
::= { acsSensors1WireTableEntry 10 }

acsSensors1WireTableValueLowWarning OBJECT-TYPE
        SYNTAX          Integer32
        MAX-ACCESS      read-only
        STATUS          current
        DESCRIPTION     "If the sensor value falls below this value, an event notification
        will be generated. Unit is specified in acsSensors1WireTableUnit."
::= { acsSensors1WireTableEntry 11 }

acsSensors1WireTableValueLowCritical OBJECT-TYPE
        SYNTAX          Integer32
        MAX-ACCESS      read-write
        STATUS          current
        DESCRIPTION     "If the sensor value falls below this value, an event notification
        will be generated. Unit is specified in acsSensors1WireTableUnit."
::= { acsSensors1WireTableEntry 12 }

acsSensors1WireTableValueHighWarning OBJECT-TYPE
        SYNTAX          Integer32
        MAX-ACCESS      read-write
        STATUS          current
        DESCRIPTION     "If the sensor value rises above this value, an event notification
        will be generated. Unit is specified in acsSensors1WireTableUnit."
::= { acsSensors1WireTableEntry 13 }

acsSensors1WireTableValueHighCritical OBJECT-TYPE
        SYNTAX          Integer32
        MAX-ACCESS      read-write
        STATUS          current
        DESCRIPTION     "If the sensor value rises above this value, an event notification
        will be generated. Unit is specified in acsSensors1WireTableUnit."
::= { acsSensors1WireTableEntry 14 }

acsSensors1WireTableReset OBJECT-TYPE
        SYNTAX  INTEGER {
            noAction(1),
            reset(2)
        }
        MAX-ACCESS      read-write
        STATUS          current
        DESCRIPTION
        "A set value of update(2) will reset the 1-wire sensor min/max/avg values."
::= { acsSensors1WireTableEntry 15 }

acsSensors1WireTableAnalogAlarm OBJECT-TYPE
        SYNTAX  INTEGER {
            notApplicable(0),
            disabled(1),
            enabled(2)
        }
        MAX-ACCESS      read-write
        STATUS          current
        DESCRIPTION
        "Status of the 1-wire analog sensor alarm.
         Used for temperature, humidity, and differential pressure sensors only.
         For all other sensor types the value notApplicable(0) will be returned."
::= { acsSensors1WireTableEntry 16 }

acsSensors1WireTableContactAlarm1 OBJECT-TYPE
        SYNTAX  INTEGER {
            notApplicable(0),
            disabled(1),
            alarmWhenOpen(2),
            alarmWhenClosed(3)
        }
        MAX-ACCESS      read-write
        STATUS          current
        DESCRIPTION
        "Status of the 1-wire contact sensor alarm.
        Used for door and dry contact sensors only.
        For all other sensor types the value notApplicable(0) will be returned."

::= { acsSensors1WireTableEntry 17 }

acsSensors1WireTableContactAlarm2 OBJECT-TYPE
        SYNTAX  INTEGER {
            notApplicable(0),
            disabled(1),
            alarmWhenOpen(2),
            alarmWhenClosed(3)
        }
        MAX-ACCESS      read-write
        STATUS          current
        DESCRIPTION
       "Status of the 1-wire contact sensor alarm.
        Used for door and dry contact sensors only.
        For all other sensor types the value notApplicable(0) will be returned."
::= { acsSensors1WireTableEntry 18 }

acsSensors1WireTableContactAlarm3 OBJECT-TYPE
        SYNTAX  INTEGER {
            notApplicable(0),
            disabled(1),
            alarmWhenOpen(2),
            alarmWhenClosed(3)
        }
        MAX-ACCESS      read-write
        STATUS          current
        DESCRIPTION
       "Status of the 1-wire contact sensor alarm.
        Used for door and dry contact sensors only.
        For all other sensor types the value notApplicable(0) will be returned."
::= { acsSensors1WireTableEntry 19 }

acsSensors1WireTableLeakFilterTime OBJECT-TYPE
        SYNTAX             INTEGER {
            notApplicable(0),
            filter-time-15(1),
            filter-time-30(2),
            filter-time-60(3),
            filter-time-120(4)
        }
        MAX-ACCESS      read-write
        STATUS          current
        DESCRIPTION
       "Leak filter time in seconds."
::= { acsSensors1WireTableEntry 20 }

acsSensors1WireTableLeakAlarm OBJECT-TYPE
        SYNTAX  INTEGER {
            notApplicable(0),
            disabled(1),
            enabled(2)
        }
        MAX-ACCESS      read-write
        STATUS          current
        DESCRIPTION
        "Status of the leak alarm for the leak sensor.
         Used for leak sensors only.
         For all other sensor types the value notApplicable(0) will be returned."
::= { acsSensors1WireTableEntry 21 }

acsSensors1WireTableLeakCableFailAlarm OBJECT-TYPE
        SYNTAX  INTEGER {
            notApplicable(0),
            disabled(1),
            enabled(2)
        }
        MAX-ACCESS      read-write
        STATUS          current
        DESCRIPTION
        "Status of the cable fail alarm for the leak sensor.
         Used for leak sensors only.
         For all other sensor types the value notApplicable(0) will be returned."
::= { acsSensors1WireTableEntry 22 }

acsSensorsDigitalInTable OBJECT-TYPE
        SYNTAX             SEQUENCE OF AcsSensorsDigitalInTableEntry
        MAX-ACCESS         not-accessible
        STATUS             current
        DESCRIPTION
        "This table contains the list of Digital In sensors."
::= { acsSensors 21 }

acsSensorsDigitalInTableEntry        OBJECT-TYPE
        SYNTAX            AcsSensorsDigitalInTableEntry
        MAX-ACCESS        not-accessible
        STATUS            current
        DESCRIPTION
        "Each entry has the information about the Digital In sensor."
        INDEX          { acsSensorsDigitalInTablePosition }
::= { acsSensorsDigitalInTable 1 }

AcsSensorsDigitalInTableEntry ::= SEQUENCE  {
        acsSensorsDigitalInTablePosition          Integer32,
        acsSensorsDigitalInTableName              DisplayString,
        acsSensorsDigitalInTableLocation          DisplayString,
        acsSensorsDigitalInTableType              INTEGER,
        acsSensorsDigitalInTableValue             INTEGER,
        acsSensorsDigitalInTableAlarm             INTEGER
}

acsSensorsDigitalInTablePosition OBJECT-TYPE
        SYNTAX            Integer32 (1..4)
        MAX-ACCESS        read-only
        STATUS            current
        DESCRIPTION
        "Position of the Digital In sensor."
::= { acsSensorsDigitalInTableEntry 1 }

acsSensorsDigitalInTableName  OBJECT-TYPE
        SYNTAX             DisplayString
        MAX-ACCESS         read-write
        STATUS             current
        DESCRIPTION
        "Name of the Digital In sensor."
::= { acsSensorsDigitalInTableEntry 2 }

acsSensorsDigitalInTableLocation  OBJECT-TYPE
        SYNTAX             DisplayString
        MAX-ACCESS         read-write
        STATUS             current
        DESCRIPTION
        "Location of the Digital In sensor."
::= { acsSensorsDigitalInTableEntry 3 }

acsSensorsDigitalInTableType OBJECT-TYPE
        SYNTAX  INTEGER {
            custom(0),
            vibration(1),
            smoke-ad-s(2),
            leak-sn-l(3),
            door(4),
            motion-ad-im(5)
        }
        MAX-ACCESS      read-write
        STATUS          current
        DESCRIPTION     "Configurable type of Digital In sensor."
::= { acsSensorsDigitalInTableEntry 4 }

acsSensorsDigitalInTableValue OBJECT-TYPE
        SYNTAX  INTEGER {
            undefined(0),
            open(1),
            closed(2)
        }
        MAX-ACCESS      read-only
        STATUS          current
        DESCRIPTION "Value of the Digital In sensor."
::= { acsSensorsDigitalInTableEntry 5 }

acsSensorsDigitalInTableAlarm OBJECT-TYPE
        SYNTAX  INTEGER {
            disabled(1),
            alarmWhenOpen(2),
            alarmWhenClosed(3)
        }
        MAX-ACCESS      read-write
        STATUS          current
        DESCRIPTION "Status of the Digital In sensor alarm."
::= { acsSensorsDigitalInTableEntry 6 }

--
-- acsModems
-- OBJECT IDENTIFIER ::= { acsManagement 8  }   10418.26.2.8
--

acsModemsNumberOfModems OBJECT-TYPE
        SYNTAX             Integer32 (0..64)
        MAX-ACCESS         read-only
        STATUS             current
        DESCRIPTION
        "Number of modems, including auxiliary port built-in modems,
        pluggable USB modems, and serial port modems."
::= { acsModems 1 }

acsModemsTable OBJECT-TYPE
        SYNTAX             SEQUENCE OF AcsModemsTableEntry
        MAX-ACCESS         not-accessible
        STATUS             current
        DESCRIPTION
        "This table contains information about the ACS modems,
        including auxiliary port built-in modem, pluggable USB
        modems, and serial port modems."
::= { acsModems 2 }

acsModemsTableEntry        OBJECT-TYPE
        SYNTAX            AcsModemsTableEntry
        MAX-ACCESS        not-accessible
        STATUS            current
        DESCRIPTION
        "Each entry has the information about a specific modem."
        INDEX            { acsModemsTableNumber }
::= { acsModemsTable 1 }

AcsModemsTableEntry ::= SEQUENCE  {
        acsModemsTableNumber                    Integer32,
        acsModemsTableDeviceName                DisplayString,
        acsModemsTableStatus                    INTEGER,
        acsModemsTableProfile                   INTEGER,
        acsModemsTablePhoneNumber               DisplayString,
        acsModemsTableComSpeed                  INTEGER,
        acsModemsTableInitChat                  DisplayString,
        acsModemsTablePppAddressConfig          INTEGER,
        acsModemsTableLocalIpv4Address          DisplayString,
        acsModemsTableRemoteIpv4Address         DisplayString,
        acsModemsTableLocalIPv6Address          DisplayString,
        acsModemsTableRemoteIPv6Address         DisplayString,
        acsModemsTablePppAuthentication         INTEGER,
        acsModemsTablePppRemoteUsername         DisplayString,
        acsModemsTablePppRemotePassphrase       DisplayString,
        acsModemsTableChapInterval              INTEGER,
        acsModemsTableChapMaxChallenge          INTEGER,
        acsModemsTableChapRestart               INTEGER,
        acsModemsTablePppIdleTimeout            INTEGER,
        acsModemsTableModel                     DisplayString,
        acsModemsTableCellProvider              DisplayString,
        acsModemsTableCellRegistration          DisplayString,
        acsModemsTableCCID                      DisplayString,
        acsModemsTableIMSI                      DisplayString,
        acsModemsTableIMEI                      DisplayString,
        acsModemsTableCellStatus                DisplayString,
        acsModemsTableAPN                       DisplayString,
        acsModemsTableMtuSize                   INTEGER,
        acsModemsTableReplaceDefaultRoute       INTEGER,
        acsModemsTablePersistMode               INTEGER,
        acsModemsTableSignalQualityCheck        INTEGER,
        acsModemsTableSignalQualityDisplay      DisplayString,
        acsModemsTableSIMStatus                 INTEGER,
        acsModemsTableSIMPINEntry               DisplayString,
        acsModemsTableSIMUnlockCodeEntry        DisplayString,
        acsModemsTableCellTestLastStarted       DisplayString,
        acsModemsTableCellTestLastResult        DisplayString
 }

acsModemsTableNumber OBJECT-TYPE
        SYNTAX             Integer32 (1..49)
        MAX-ACCESS         read-only
        STATUS             current
        DESCRIPTION
        "A unique index representing an entry in this table.
        "
::= { acsModemsTableEntry 1 }

acsModemsTableDeviceName OBJECT-TYPE
        SYNTAX            DisplayString (SIZE (0..25))
        MAX-ACCESS        read-only
        STATUS            current
        DESCRIPTION
        "The associated device name for the modem."
::= { acsModemsTableEntry 2 }

acsModemsTableStatus OBJECT-TYPE
        SYNTAX INTEGER {
                disabled(1),
                enabled(2)
        }
        MAX-ACCESS     read-write
        STATUS         current
        DESCRIPTION
        "Enables or disbles the modem."
::= { acsModemsTableEntry 3 }

acsModemsTableProfile OBJECT-TYPE
        SYNTAX INTEGER {
                unconfigured(1),
                dialIn(2),
                dialOut(3)
        }
        MAX-ACCESS         read-write
        STATUS             current
        DESCRIPTION
        "The modem profile. For an integrated cell modem, only dial-out(3) is valid."
::= { acsModemsTableEntry 4 }

acsModemsTablePhoneNumber OBJECT-TYPE
        SYNTAX            DisplayString (SIZE (0..25))
        MAX-ACCESS        read-write
        STATUS            current
        DESCRIPTION
        "The dial-out phone number. Only supported if acsModemsTableProfile is
        set to dial-out(3). Not used for integrated cellular modem."
::= { acsModemsTableEntry 5 }

acsModemsTableComSpeed OBJECT-TYPE
        SYNTAX INTEGER {
                speed1200(1200),
                speed2400(2400),
                speed4800(4800),
                speed9600(9600),
                speed19200(19200),
                speed38400(38400),
                speed57600(57600),
                speed115200(115200),
                speed230400(230400),
                speed460800(460800),
                speed921600(921600)
        }
        MAX-ACCESS         read-write
        STATUS             current
        DESCRIPTION
        "The modem speed. Speeds above 230400 not supported by serial port modems."
::= { acsModemsTableEntry 6 }

acsModemsTableInitChat OBJECT-TYPE
        SYNTAX            DisplayString (SIZE (0..1200))
        MAX-ACCESS        read-write
        STATUS            current
        DESCRIPTION
        "Modem initialization string."
::= { acsModemsTableEntry 7 }

acsModemsTablePppAddressConfig OBJECT-TYPE
        SYNTAX INTEGER {
                notApplicable(0),
                none(1),
                local(2),
                remote(3)
        }
        MAX-ACCESS         read-write
        STATUS             current
        DESCRIPTION
        "Supported only if acsModemsTableProfile is set to dial-out(2).
        If none(1) or remote(3) is set, then the IP address fields will be cleared.
        When at least one IP address is set, this value will be local(2).
        If remote(3) is set, the remote peer should send both IP addresses (local
        and remote) during negotiation."
::= { acsModemsTableEntry 8 }

acsModemsTableLocalIpv4Address OBJECT-TYPE
        SYNTAX            DisplayString (SIZE (0..46))
        MAX-ACCESS        read-write
        STATUS            current
        DESCRIPTION
        "Configures the local IPv4 address for the PPP connection."
::= { acsModemsTableEntry 9 }

acsModemsTableRemoteIpv4Address OBJECT-TYPE
        SYNTAX            DisplayString (SIZE (0..46))
        MAX-ACCESS        read-write
        STATUS            current
        DESCRIPTION
        "Configures the remote IPv4 address for the PPP connection."
::= { acsModemsTableEntry 10 }

acsModemsTableLocalIPv6Address OBJECT-TYPE
        SYNTAX            DisplayString (SIZE (0..46))
        MAX-ACCESS        read-write
        STATUS            current
        DESCRIPTION
        "Configures the local IPv6 address for the PPP connection."
::= { acsModemsTableEntry 11 }

acsModemsTableRemoteIPv6Address OBJECT-TYPE
        SYNTAX            DisplayString (SIZE (0..46))
        MAX-ACCESS        read-write
        STATUS            current
        DESCRIPTION
        "Configures the remote IPv6 address for the PPP connection."
::= { acsModemsTableEntry 12 }

acsModemsTablePppAuthentication OBJECT-TYPE
        SYNTAX INTEGER {
                noAuth(1),
                localPap(2),
                localChap(3),
                localEap(4),
                remoteChap(5),
                remotePap(6)
        }
        MAX-ACCESS         read-write
        STATUS             current
        DESCRIPTION
        "Configure the PPP authentication protocol. If this is set to remoteChap(5) or
        remotePap(6), then you must also set acsModemsTablePppRemoteUsername
        and acsModemsTablePppRemotePassphrase."
::= { acsModemsTableEntry 13 }

acsModemsTablePppRemoteUsername OBJECT-TYPE
        SYNTAX            DisplayString (SIZE (0..32))
        MAX-ACCESS        read-write
        STATUS            current
        DESCRIPTION
        "Only used if acsModemsTablePppAuthentication is set to
        remoteChap(5) or remotePap(6)."
::= { acsModemsTableEntry 14 }

acsModemsTablePppRemotePassphrase OBJECT-TYPE
        SYNTAX            DisplayString (SIZE (0..32))
        MAX-ACCESS        read-write
        STATUS            current
        DESCRIPTION
        "Only used if acsModemsTablePppAuthentication is set to
        remoteChap(5) or remotePap(6)."
::= { acsModemsTableEntry 15 }

acsModemsTableChapInterval    OBJECT-TYPE
        SYNTAX            Integer32
        MAX-ACCESS        read-write
        STATUS            current
        DESCRIPTION
        "CHAP Interval in seconds. Default is 0.
        Not used for integrated cellular modem."
::= { acsModemsTableEntry 16 }

acsModemsTableChapMaxChallenge    OBJECT-TYPE
        SYNTAX            Integer32
        MAX-ACCESS        read-write
        STATUS            current
        DESCRIPTION
        "CHAP Max Challenge value in seconds. Default is 10 seconds.
        Not used for integrated cellular modem."
::= { acsModemsTableEntry 17 }

acsModemsTableChapRestart    OBJECT-TYPE
        SYNTAX            Integer32
        MAX-ACCESS        read-write
        STATUS            current
        DESCRIPTION
        "CHAP Restart value in seconds. Default is 3 seconds.
        Not used for integrated cellular modem."
::= { acsModemsTableEntry 18 }

acsModemsTablePppIdleTimeout    OBJECT-TYPE
        SYNTAX            Integer32
        MAX-ACCESS        read-write
        STATUS            current
        DESCRIPTION
        "PPP idle timeout value in seconds. Default is 0.
        Not used for integrated cellular modem."
::= { acsModemsTableEntry 19 }

acsModemsTableModel OBJECT-TYPE
        SYNTAX            DisplayString (SIZE (0..32))
        MAX-ACCESS        read-only
        STATUS            current
        DESCRIPTION
        "Modem vendor model name. Only used for integrated cellular modem."
::= { acsModemsTableEntry 20 }

acsModemsTableCellProvider OBJECT-TYPE
        SYNTAX            DisplayString (SIZE (0..32))
        MAX-ACCESS        read-only
        STATUS            current
        DESCRIPTION
        "Cellular modem service provider. Only used for integrated cellular modem."
::= { acsModemsTableEntry 21 }

acsModemsTableCellRegistration OBJECT-TYPE
        SYNTAX            DisplayString (SIZE (0..32))
        MAX-ACCESS        read-only
        STATUS            current
        DESCRIPTION
        "Cellular modem network registration. Only used for integrated cellular modem."
::= { acsModemsTableEntry 22 }

acsModemsTableCCID OBJECT-TYPE
        SYNTAX            DisplayString (SIZE (0..32))
        MAX-ACCESS        read-only
        STATUS            current
        DESCRIPTION
        "SIM integrated circuit card identifier. Only used for integrated
        cellular modem."
::= { acsModemsTableEntry 23 }

acsModemsTableIMSI OBJECT-TYPE
        SYNTAX            DisplayString (SIZE (0..32))
        MAX-ACCESS        read-only
        STATUS            current
        DESCRIPTION
        "International mobile subscriber identity. Only used for integrated
        cellular modem."
::= { acsModemsTableEntry 24 }

acsModemsTableIMEI OBJECT-TYPE
        SYNTAX            DisplayString (SIZE (0..32))
        MAX-ACCESS        read-only
        STATUS            current
        DESCRIPTION
        "International mobile equipment identity. Only used for integrated
        cellular modem."
::= { acsModemsTableEntry 25 }

acsModemsTableCellStatus OBJECT-TYPE
        SYNTAX            DisplayString (SIZE (0..80))
        MAX-ACCESS        read-only
        STATUS            current
        DESCRIPTION
        "Shows the status of the cellular modem. Only used for integrated
        cellular modem."
::= { acsModemsTableEntry 26 }

acsModemsTableAPN OBJECT-TYPE
        SYNTAX            DisplayString (SIZE (0..40))
        MAX-ACCESS        read-write
        STATUS            current
        DESCRIPTION
        "Access point name. Only used for integrated cellular modem."
::= { acsModemsTableEntry 27 }

acsModemsTableMtuSize OBJECT-TYPE
        SYNTAX            Integer32
        MAX-ACCESS        read-only
        STATUS            current
        DESCRIPTION
        "The maxiumum transmission unit size for use by the integrated cellular modem."
::= { acsModemsTableEntry 28 }

acsModemsTableReplaceDefaultRoute OBJECT-TYPE
        SYNTAX INTEGER {
                notApplicable(0),
                disabled(1),
                enabled(2)
        }
        MAX-ACCESS     read-write
        STATUS         current
        DESCRIPTION
        "If this is set to enabled(2), then the integrated cellular modem
        becomes the default gateway. Only used for integrated cellular
        modem."
::= { acsModemsTableEntry 29 }

acsModemsTablePersistMode OBJECT-TYPE
        SYNTAX INTEGER {
                notApplicable(0),
                disabled(1),
                enabled(2)
        }
        MAX-ACCESS     read-write
        STATUS         current
        DESCRIPTION
        "If this is set to 'yes' then the integrated cellular modem connection persists.
        Only used for integrated cellular modem."
::= { acsModemsTableEntry 30 }

acsModemsTableSignalQualityCheck OBJECT-TYPE
        SYNTAX       INTEGER {
            notApplicable(0),
            no-action (1),
            signalCheck (2)
        }
        MAX-ACCESS      read-write
        STATUS          current
        DESCRIPTION     "Check the signal quality of the integrated cellular modem. This
        turns on the modem transceiver to get the signal. The signal quality can be read
        in acsModemsTableSignalQualityDisplay."
::= { acsModemsTableEntry 31 }

acsModemsTableSignalQualityDisplay OBJECT-TYPE
        SYNTAX            DisplayString (SIZE (0..80))
        MAX-ACCESS        read-write
        STATUS            current
        DESCRIPTION     "Displays the last read signal quality of the integrated cellular modem.
        To refresh this value write signalCheck(2) to acsModemsTableSignalQualityCheck."
::= { acsModemsTableEntry 32 }

acsModemsTableSIMStatus OBJECT-TYPE
        SYNTAX INTEGER {
                unknown(0),
                ready(1),
                waitingForPIN(2),
                waitingForUnlockCode(3),
                errorReadingSIM(4)
        }
        MAX-ACCESS         read-only
        STATUS             current
        DESCRIPTION
        "Status of the modem SIM card. Only used for integrated cellular modem."
::= { acsModemsTableEntry 33 }

acsModemsTableSIMPINEntry OBJECT-TYPE
        SYNTAX            DisplayString (SIZE (0..80))
        MAX-ACCESS        read-write
        STATUS            current
        DESCRIPTION
        "Modem SIM card PIN/Password entry. Writable only if acsModemsTableSIMStatus
        returns waitingForPIN(2). Only used for integrated cellular modem."
::= { acsModemsTableEntry 34 }

acsModemsTableSIMUnlockCodeEntry OBJECT-TYPE
        SYNTAX            DisplayString (SIZE (0..80))
        MAX-ACCESS        read-write
        STATUS            current
        DESCRIPTION
        "Modem SIM card Unlock Code entry. Writable only if acsModemsTableSIMStatus
        returns waitingForUnlockCode(3). Only used for integrated cellular modem."
::= { acsModemsTableEntry 35 }

acsModemsTableCellTestLastStarted OBJECT-TYPE
        SYNTAX             DisplayString ( SIZE (0..32) )
        MAX-ACCESS         read-only
        STATUS             current
        DESCRIPTION
        "The timestamp of the last time the Cell Modem IP Test started running.
        Only used for integrated cellular modem."
::= { acsModemsTableEntry 36 }

acsModemsTableCellTestLastResult OBJECT-TYPE
        SYNTAX             DisplayString ( SIZE (0..256) )
        MAX-ACCESS         read-only
        STATUS             current
        DESCRIPTION
        "The result of the last time the Cell Modem IP Test was run.
        Only used for integrated cellular modem."
::= { acsModemsTableEntry 37 }

END
