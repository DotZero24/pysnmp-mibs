-- *****************************************************************
-- Meru Networks Enterprise Specific MIB
--
-- Copyright (c) 2005 by Meru Networks
-- All rights reserved
--
-- *****************************************************************

MERU-CONFIG-SECURITYCERT-MIB  DEFINITIONS ::= BEGIN

IMPORTS
    NOTIFICATION-TYPE,
    OBJECT-TYPE,
    MODULE-IDENTITY,
    OBJECT-IDENTITY,
    enterprises,
    Counter32,
    Counter64,
    Gauge32,
    TimeTicks,
    IpAddress,
    Integer32
        FROM SNMPv2-SMI
    Ipv6Address
        FROM IPV6-TC
    TEXTUAL-CONVENTION,
    TimeInterval,
    TimeStamp,
    DateAndTime,
    TruthValue,
    DisplayString,
    MacAddress,
    RowStatus
        FROM SNMPv2-TC
    mwConfiguration
        FROM MERU-SMI
    ;

  mwConfigSecurityCert  MODULE-IDENTITY
    LAST-UPDATED "200506050000Z"
    ORGANIZATION "Meru Networks"
    CONTACT-INFO "support@merunetworks.com"
    DESCRIPTION
        "This MIB defines all the managed objects used to manage the Meru WLAN
         Security Certificate Configuration infrastructure"
    ::= { mwConfiguration 10 }

    mwSslCertInput                           OBJECT IDENTIFIER ::= { mwConfigSecurityCert 2 }
    mwSslCert                                OBJECT IDENTIFIER ::= { mwConfigSecurityCert 3 }


  mwSslCertInputCertificateName  OBJECT-TYPE
    SYNTAX DisplayString(SIZE (0..255))
    MAX-ACCESS read-write
    STATUS     current
    DESCRIPTION
         "This object describes Certificate Path Name"
    ::= { mwSslCertInput    1 }

  mwSslCertInputPfxPassword  OBJECT-TYPE
    SYNTAX DisplayString(SIZE (0..64))
    MAX-ACCESS read-write
    STATUS     current
    DESCRIPTION
         "This object describes Password"
    ::= { mwSslCertInput    2 }

  mwSslCertCertificateName  OBJECT-TYPE
    SYNTAX DisplayString(SIZE (0..255))
    MAX-ACCESS  read-only
    STATUS     current
    DESCRIPTION
         "This object describes Certificate Path Name"
    ::= { mwSslCert    1 }

  mwSslCertCertFormattedText  OBJECT-TYPE
    SYNTAX DisplayString
    MAX-ACCESS  read-only
    STATUS     current
    DESCRIPTION
         "This object describes Certificate Body"
    ::= { mwSslCert    2 }


END
