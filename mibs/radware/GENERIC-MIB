GENERIC-MIB DEFINITIONS ::= BEGIN

-- Title:      RADWARE
--             This Private MIB supports the Vgate
-- Version:    3.0
-- Date:       24 May 2016
-- By:         RMA (Radware MIB Authority)
-- E-mail:     US:            support@radware.com
--             International: support_int@radware.com
--
IMPORTS
       NetworkAddress,
       IpAddress,
       Counter,
       Gauge,
       enterprises
              FROM RFC1155-SMI
       OBJECT-TYPE
              FROM RFC-1212
       DisplayString,
       PhysAddress,
       ipAddrEntry
              FROM RFC1213-MIB
       TRAP-TYPE
                    FROM RFC-1215
       rsGeneric,
       rndErrorDesc,
       rndErrorSeverity,
       rsWSDTelnetParams,
       rsWSDSshParams,
       rsServerDispatcher,
       tftp,
       TruthValue,
       RowStatus,
       FeatureStatus
                    FROM RADWARE-MIB;

    DisplayStatus ::= INTEGER {
         displayed(1),
         hidden(2)
		}

    NetNumber ::=  OCTET STRING (SIZE(4))
-- List of dynamic protocols session types - to be used in other mibs.
    DpsSessionType ::= INTEGER {
        none(0),
        ftpControl(1),
        ftpData(2),
        ftpAll(3),
        tftpControl(4),
        tftpData(5),
        tftpAll(6),
        rshellControl(7),
        rshellErrors(8),
        rshellAll(9),
        rexecControl(10),
        rexecErrors(11),
        rexecAll(12),
		h225Control(13),
		h245Session(14),
		h225All(15),
        sipSignal(16),
        sipMediaControl(17),
        sipAudio(18),
        sipVideo(19),
        sipApplication(20),
        sipOtherMediaType(21),
        sipAll(22)
--        rtspControl(23),       ### FOR NOW RTSP DYNAMIC PROTOCOL IS HIDDEN  ###
--        rtspCombined(24),
--        rtspDataRTP(25),
--        rtspDataRTCP(26),
--        rtspDataRDT(27),
--        rtspAll(28)
        }

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsTunnelingMode OBJECT-TYPE
    SYNTAX FeatureStatus
    ACCESS  read-write
    STATUS  mandatory
    DESCRIPTION "Enabled entails that the tunneled data will be
    treated by the application."
--  DEFVAL  { disable }
    ::= { rsGeneric 1 }

rsIpVersionMode OBJECT-TYPE
    SYNTAX INTEGER {
        ipv4 (1),
        ipv4and6 (2)
    }
    ACCESS  read-write
    STATUS  mandatory
    DESCRIPTION "Enables Ipv6 support"
--  DEFVAL  { ipv4 }
    ::= { rsGeneric 2 }


dpFtpStatus OBJECT-TYPE
    SYNTAX FeatureStatus
    ACCESS  read-write
    STATUS  mandatory
    DESCRIPTION "Enable/disable the dp ftp."
	DEFVAL  { enable }
    ::= { rsGeneric 3 }

dpFtpControlAgingTime OBJECT-TYPE
    SYNTAX  INTEGER (0..65535)
    ACCESS  read-write
    STATUS  mandatory
    DESCRIPTION "ftp control session aging time"
    DEFVAL  { 0 }
    ::= { rsGeneric 4 }

dpFtpDataAgingTime OBJECT-TYPE
    SYNTAX  INTEGER (0..65535)
    ACCESS  read-write
    STATUS  mandatory
    DESCRIPTION "ftp data session aging time"
    DEFVAL  { 0 }
    ::= { rsGeneric 5 }

dpFtpControlPorts OBJECT-TYPE
    SYNTAX DisplayString (SIZE(0..29))
    ACCESS read-only
    STATUS mandatory
    DESCRIPTION
      "Control L4-ports for FTP."
    ::=  { rsGeneric 6 }

dpTftpStatus OBJECT-TYPE
    SYNTAX FeatureStatus
    ACCESS  read-write
    STATUS  mandatory
    DESCRIPTION "Enable/disable the dp tftp."
	DEFVAL  { enable }
    ::= { rsGeneric 7 }

dpTftpDataAgingTime OBJECT-TYPE
    SYNTAX  INTEGER (0..65535)
    ACCESS  read-write
    STATUS  mandatory
    DESCRIPTION "tftp data session aging time"
    DEFVAL  { 0 }
    ::= { rsGeneric 8 }

dpTftpControlPorts OBJECT-TYPE
    SYNTAX DisplayString (SIZE(0..29))
    ACCESS read-only
    STATUS mandatory
    DESCRIPTION
      "Control L4-ports for TFTP."
    ::=  { rsGeneric 9 }

dpRshellStatus OBJECT-TYPE
    SYNTAX FeatureStatus
    ACCESS  read-write
    STATUS  mandatory
    DESCRIPTION "Enable/disable the dp rshell."
	DEFVAL  { enable }
    ::= { rsGeneric 10 }

dpRshellControlAgingTime OBJECT-TYPE
    SYNTAX  INTEGER (0..65535)
    ACCESS  read-write
    STATUS  mandatory
    DESCRIPTION "Rshell control session aging time"
    DEFVAL  { 0 }
    ::= { rsGeneric 11 }

dpRshellDataAgingTime OBJECT-TYPE
    SYNTAX  INTEGER (0..65535)
    ACCESS  read-write
    STATUS  mandatory
    DESCRIPTION "Rshell data session aging time"
    DEFVAL  { 0 }
    ::= { rsGeneric 12 }

dpRshellControlPorts OBJECT-TYPE
    SYNTAX DisplayString (SIZE(0..29))
    ACCESS read-only
    STATUS mandatory
    DESCRIPTION
      "Control L4-ports for Rshell."
    ::=  { rsGeneric 13 }

dpRexecStatus OBJECT-TYPE
    SYNTAX FeatureStatus
    ACCESS  read-write
    STATUS  mandatory
    DESCRIPTION "Enable/disable the dp rexec."
	DEFVAL  { enable }
    ::= { rsGeneric 14 }

dpRexecControlAgingTime OBJECT-TYPE
    SYNTAX  INTEGER (0..65535)
    ACCESS  read-write
    STATUS  mandatory
    DESCRIPTION "Rexec control session aging time"
    DEFVAL  { 0 }
    ::= { rsGeneric 15 }

dpRexecDataAgingTime OBJECT-TYPE
    SYNTAX  INTEGER (0..65535)
    ACCESS  read-write
    STATUS  mandatory
    DESCRIPTION "Rexec data session aging time"
    DEFVAL  { 0 }
    ::= { rsGeneric 16 }

dpRexecControlPorts OBJECT-TYPE
    SYNTAX DisplayString (SIZE(0..29))
    ACCESS read-only
    STATUS mandatory
    DESCRIPTION
      "Control L4-ports for Rexec."
    ::=  { rsGeneric 17 }

dpH225Status OBJECT-TYPE
    SYNTAX FeatureStatus
    ACCESS  read-write
    STATUS  mandatory
    DESCRIPTION "Enable/disable the dp h225."
	DEFVAL  { enable }
    ::= { rsGeneric 18 }

dpH225ControlAgingTime OBJECT-TYPE
    SYNTAX  INTEGER (0..65535)
    ACCESS  read-write
    STATUS  mandatory
    DESCRIPTION "H225 control session aging time"
    DEFVAL  { 0 }
    ::= { rsGeneric 19 }

dpH225DataAgingTime OBJECT-TYPE
    SYNTAX  INTEGER (0..65535)
    ACCESS  read-write
    STATUS  mandatory
    DESCRIPTION "H225 data session aging time"
    DEFVAL  { 0 }
    ::= { rsGeneric 20 }

dpH225ControlPorts OBJECT-TYPE
    SYNTAX DisplayString (SIZE(0..29))
    ACCESS read-only
    STATUS mandatory
    DESCRIPTION
      "Control L4-ports for H225."
    ::=  { rsGeneric 21 }



rsGenericTuning OBJECT IDENTIFIER ::= { rsGeneric 22 }


rsDebugPoliciesTuning OBJECT IDENTIFIER ::= { rsGenericTuning 5 }

rsDEBUGPolicyEntries OBJECT-TYPE
    SYNTAX INTEGER
    ACCESS  read-only
    STATUS  mandatory
    DESCRIPTION
      "Maximum number entries kept for the debug policies table ."
    ::= { rsDebugPoliciesTuning 1 }

rsDEBUGPolicyEntriesAfterReset OBJECT-TYPE
    SYNTAX INTEGER
    ACCESS  read-write
    STATUS  mandatory
    DESCRIPTION
      "Future maximum number of entries kept for the debug policies table ."
    ::=  { rsDebugPoliciesTuning 2 }

dpsSIPCallTableTuning OBJECT IDENTIFIER ::= { rsGenericTuning 2 }

dpSIPCallEntries OBJECT-TYPE
    SYNTAX INTEGER
    ACCESS  read-only
    STATUS  mandatory
    DESCRIPTION
      "Maximum number of SIP calls supported."
    ::= { dpsSIPCallTableTuning 1 }

dpSIPCallEntriesAfterReset OBJECT-TYPE
    SYNTAX INTEGER
    ACCESS  read-write
    STATUS  mandatory
    DESCRIPTION
      "Future maximum number of SIP calls supported."
    ::=  { dpsSIPCallTableTuning 2 }

dpsTCPSegmentsTableTuning OBJECT IDENTIFIER ::= { rsGenericTuning 3 }

dpsTCPSegmentsTableEntries OBJECT-TYPE
    SYNTAX INTEGER
    ACCESS  read-only
    STATUS  mandatory
    DESCRIPTION
      "Maximum number of TCP segments supported."
    ::= { dpsTCPSegmentsTableTuning 1 }

dpsTCPSegmentsTableEntriesAfterReset OBJECT-TYPE
    SYNTAX INTEGER
    ACCESS  read-write
    STATUS  mandatory
    DESCRIPTION
      "Future maximum number of TCP segments supported."
    ::=  { dpsTCPSegmentsTableTuning 2 }

dpsRTSPControlTableTuning OBJECT IDENTIFIER ::= { rsGenericTuning 4 }

dpsRTSPControlTableEntries OBJECT-TYPE
    SYNTAX INTEGER
    ACCESS  read-only
    STATUS  mandatory
    DESCRIPTION
      "Maximum number of TCP segments supported."
    ::= { dpsRTSPControlTableTuning 1 }

dpsRTSPControlTableEntriesAfterReset OBJECT-TYPE
    SYNTAX INTEGER
    ACCESS  read-write
    STATUS  mandatory
    DESCRIPTION
      "Future maximum number of TCP segments supported."
    ::=  { dpsRTSPControlTableTuning 2 }

dpsPendingTableTuning OBJECT IDENTIFIER ::= { rsGenericTuning 1 }

dpsPendingTableEntries OBJECT-TYPE
    SYNTAX INTEGER
    ACCESS  read-only
    STATUS  mandatory
    DESCRIPTION
      "Maximum number entries kept for the pending table ."
    ::= { dpsPendingTableTuning 1 }

dpsPendingTableEntriesAfterReset OBJECT-TYPE
    SYNTAX INTEGER
    ACCESS  read-write
    STATUS  mandatory
    DESCRIPTION
      "Future maximum number of entries kept for the pending table ."
    ::=  { dpsPendingTableTuning 2 }

dpSIPStatus OBJECT-TYPE
    SYNTAX FeatureStatus
    ACCESS  read-write
    STATUS  mandatory
    DESCRIPTION "Enable/disable the dp SIP."
    DEFVAL  { disable }
    ::= { rsGeneric 23 }

dpSIPSignalAgingTime OBJECT-TYPE
    SYNTAX  INTEGER (1..65535)
    ACCESS  read-write
    STATUS  mandatory
    DESCRIPTION "SIP signal session aging time"
    DEFVAL  { 10 }
    ::= { rsGeneric 24 }

dpSIPRTCPAgingTime OBJECT-TYPE
    SYNTAX  INTEGER (0..65535)
    ACCESS  read-write
    STATUS  mandatory
    DESCRIPTION "SIP RTCP session aging time"
    DEFVAL  { 300 }
    ::= { rsGeneric 25 }

dpSIPControlPorts OBJECT-TYPE
    SYNTAX DisplayString (SIZE(0..29))
    ACCESS read-write
    STATUS mandatory
    DESCRIPTION "Control L4-ports for SIP."
    ::=  { rsGeneric 26 }

dpsTCPSegmentAgingTime OBJECT-TYPE
    SYNTAX  INTEGER (0..65535)
    ACCESS  read-write
    STATUS  mandatory
    DESCRIPTION "TCP segments aging time"
    DEFVAL  { 5 }
    ::= { rsGeneric 27 }

dpRTSPStatus OBJECT-TYPE
    SYNTAX FeatureStatus
    ACCESS  read-write
    STATUS  mandatory
    DESCRIPTION "Enable/disable the dp RTSP."
    DEFVAL  { disable }
    ::= { rsGeneric 28 }

dpRTSPControlAgingTime OBJECT-TYPE
    SYNTAX  INTEGER (0..65535)
    ACCESS  read-write
    STATUS  mandatory
    DESCRIPTION "RTSP control session aging time"
    DEFVAL  { 3600 }
    ::= { rsGeneric 29 }

dpRTSPDataAgingTime OBJECT-TYPE
    SYNTAX  INTEGER (0..65535)
    ACCESS  read-write
    STATUS  mandatory
    DESCRIPTION "RTSP data session aging time"
    DEFVAL  { 300 }
    ::= { rsGeneric 30 }

dpRTSPControlPorts OBJECT-TYPE
    SYNTAX DisplayString (SIZE(0..29))
    ACCESS read-write
    STATUS mandatory
    DESCRIPTION "Control L4-ports for RTSP."
    ::=  { rsGeneric 31 }

rsDEBUGPolicyTable OBJECT-TYPE
    SYNTAX SEQUENCE OF RsDEBUGPolicyEntry
    ACCESS not-accessible
    STATUS  mandatory
    DESCRIPTION
      "Table containing the debug policies."
    ::=  {rsGeneric 32}

rsDEBUGPolicyEntry OBJECT-TYPE
    SYNTAX RsDEBUGPolicyEntry
    ACCESS not-accessible
    STATUS  mandatory
    DESCRIPTION
       "The row definition for this table. Each policy defines the way the matching
	    packet should be tracved/logged"
    INDEX {rsDEBUGPolicyName}
    ::=  { rsDEBUGPolicyTable 1 }


RsDEBUGPolicyEntry ::= SEQUENCE {
    rsDEBUGPolicyName DisplayString,
    rsDEBUGPolicyIndex INTEGER,
    rsDEBUGPolicyDescription DisplayString,
    rsDEBUGPolicySource DisplayString,
    rsDEBUGPolicyDestination DisplayString,
    rsDEBUGPolicyRXPortGroup DisplayString,
    rsDEBUGPolicyTXPortGroup DisplayString,
    rsDEBUGPolicyServiceType INTEGER,
    rsDEBUGPolicyService DisplayString,
    rsDEBUGPolicyVlanTagGroupName DisplayString,
    rsDEBUGPolicySrcMacGroupName DisplayString,
    rsDEBUGPolicyDstMacGroupName DisplayString,
    rsDEBUGPolicyIsSnp FeatureStatus,
    rsDEBUGPolicyIsTrace FeatureStatus,
    rsDEBUGPolicyPacketsMaxNum INTEGER,
    rsDEBUGPolicyPacketMaxLen INTEGER,
    rsDEBUGPolicyStatus RowStatus
}

rsDEBUGPolicyName OBJECT-TYPE
    SYNTAX DisplayString  (SIZE(0..64))
    ACCESS  read-only
    STATUS  mandatory
    DESCRIPTION
      "Debug policy name"
    ::=  { rsDEBUGPolicyEntry 1 }

rsDEBUGPolicyIndex OBJECT-TYPE
    SYNTAX INTEGER
    ACCESS  read-write
    STATUS  mandatory
    DESCRIPTION
      "Debug policy index"
    ::=  { rsDEBUGPolicyEntry 2 }

rsDEBUGPolicyDescription OBJECT-TYPE
    SYNTAX DisplayString  (SIZE(0..20))
    ACCESS  read-write
    STATUS  mandatory
    DESCRIPTION
      "The description of this policy. "
    ::=  { rsDEBUGPolicyEntry 3 }

rsDEBUGPolicySource OBJECT-TYPE
    SYNTAX DisplayString  (SIZE(0..20))
    ACCESS  read-write
    STATUS  mandatory
    DESCRIPTION
      "The source address / range of address for the packet, the name is
      defined in the Objects table or can be an IP address."
    ::=  { rsDEBUGPolicyEntry 4 }

rsDEBUGPolicyDestination OBJECT-TYPE
    SYNTAX DisplayString  (SIZE(0..20))
    ACCESS  read-write
    STATUS  mandatory
    DESCRIPTION
      "The destination address / range of address for the packet, the name is
      defined in the Objects table or can be an IP address."
    ::=  { rsDEBUGPolicyEntry 5 }


rsDEBUGPolicyRXPortGroup OBJECT-TYPE
    SYNTAX DisplayString (SIZE(0..30))
    ACCESS  read-write
    STATUS  mandatory
    DESCRIPTION
       "The name of the inbound physical port group for this policy."
	::=  { rsDEBUGPolicyEntry 6 }

rsDEBUGPolicyTXPortGroup OBJECT-TYPE
    SYNTAX DisplayString (SIZE(0..30))
    ACCESS  read-write
    STATUS  mandatory
    DESCRIPTION
       "The name of the outbound physical port group for this policy."
	::=  { rsDEBUGPolicyEntry 7 }

rsDEBUGPolicyServiceType OBJECT-TYPE
    SYNTAX INTEGER {
              none(1),
              basic-filter(2),
              and-group(3),
              or-group(4)}
    ACCESS  read-write
    STATUS  mandatory
    DESCRIPTION
       "The type of the service - i.e. if this is a filter, advanced filter or group."
    DEFVAL  { 1 }
    ::=  { rsDEBUGPolicyEntry 8 }

rsDEBUGPolicyService OBJECT-TYPE
    SYNTAX DisplayString (SIZE(0..30))
    ACCESS  read-write
    STATUS  mandatory
    DESCRIPTION
       "The name of the service for this policy."
	::=  { rsDEBUGPolicyEntry 9 }


rsDEBUGPolicyVlanTagGroupName OBJECT-TYPE
    SYNTAX DisplayString (SIZE(0..30))
    ACCESS  read-write
    STATUS  mandatory
    DESCRIPTION
       "The name of the VLAN tag group for this policy."
	::=  { rsDEBUGPolicyEntry 10 }


rsDEBUGPolicySrcMacGroupName OBJECT-TYPE
    SYNTAX DisplayString (SIZE(0..30))
    ACCESS  read-write
    STATUS  mandatory
    DESCRIPTION
       "The name of the source MAC group for this policy."
	::=  { rsDEBUGPolicyEntry 11 }

rsDEBUGPolicyDstMacGroupName OBJECT-TYPE
    SYNTAX DisplayString (SIZE(0..30))
    ACCESS  read-write
    STATUS  mandatory
    DESCRIPTION
       "The name of the destination MAC group for this policy."
	::=  { rsDEBUGPolicyEntry 12 }


rsDEBUGPolicyIsSnp OBJECT-TYPE
    SYNTAX FeatureStatus
    ACCESS  read-write
    STATUS  mandatory
    DESCRIPTION
       "Snapshot status for this policy."
    DEFVAL  { 1 }
    ::=  { rsDEBUGPolicyEntry 13 }

rsDEBUGPolicyIsTrace OBJECT-TYPE
    SYNTAX FeatureStatus
    ACCESS  read-write
    STATUS  mandatory
    DESCRIPTION
       "Debug trace status for this policy."
    DEFVAL  { 1 }
    ::=  { rsDEBUGPolicyEntry 14 }


rsDEBUGPolicyPacketsMaxNum OBJECT-TYPE
    SYNTAX INTEGER
    ACCESS  read-write
    STATUS  mandatory
    DESCRIPTION
      "Maximal number of packets can be matched by this policy"
    ::=  { rsDEBUGPolicyEntry 15 }

rsDEBUGPolicyPacketMaxLen OBJECT-TYPE
    SYNTAX INTEGER
    ACCESS  read-write
    STATUS  mandatory
    DESCRIPTION
      "Maximal packet length matched by this policy"
    ::=  { rsDEBUGPolicyEntry 16 }


rsDEBUGPolicyStatus OBJECT-TYPE
    SYNTAX RowStatus
    ACCESS  read-write
    STATUS  mandatory
    DESCRIPTION
       "This variable indicates the administrative status of this entry.
        Used to delete an entry of this table."
    ::=  { rsDEBUGPolicyEntry 17 }

rsDebugSnapshotStatus OBJECT-TYPE
    SYNTAX FeatureStatus
    ACCESS  read-write
    STATUS  mandatory
    DESCRIPTION
       "Snapshot Debug Tool status."
    DEFVAL  { 2 }
    ::=  { rsGeneric 33 }

rsDebugSnapshotOutputToFile OBJECT-TYPE
    SYNTAX INTEGER {
              ram-file(1),
              ram(2),
              none(3)}
    ACCESS  read-write
    STATUS  mandatory
    DESCRIPTION
       "Snapshot Debug Tool output to file status."
    DEFVAL  { 1 }
    ::=  { rsGeneric 34 }

rsDebugSnapshotOutputToTerm OBJECT-TYPE
    SYNTAX FeatureStatus
    ACCESS  read-write
    STATUS  mandatory
    DESCRIPTION
       "Snapshot Debug Tool output to terminal status."
    DEFVAL  { 1 }
    ::=  { rsGeneric 35 }

rsDebugSnapshotPortGroup OBJECT-TYPE
    SYNTAX INTEGER {
              on-management-ports(1),
              on-data-ports(2),
              on-management-and-data(3)}
    ACCESS  read-write
    STATUS  mandatory
    DESCRIPTION
       "Snapshot Debug Tool Port Group status"
    DEFVAL  { 2 }
    ::=  { rsGeneric 36 }

rsDebugTraceStatus OBJECT-TYPE
    SYNTAX FeatureStatus
    ACCESS  read-write
    STATUS  mandatory
    DESCRIPTION
       "Packets Trace Debug Tool status."
    DEFVAL  { 2 }
    ::=  { rsGeneric 37 }

rsDebugTraceOutputToFile OBJECT-TYPE
    SYNTAX INTEGER {
              ram-file(1),
              ram(2),
              none(3)}
    ACCESS  read-write
    STATUS  mandatory
    DESCRIPTION
       "Debug trace output to file status."
    DEFVAL  { 1 }
    ::=  { rsGeneric 38 }


rsDebugTraceOutputToTerm OBJECT-TYPE
    SYNTAX FeatureStatus
    ACCESS  read-write
    STATUS  mandatory
    DESCRIPTION
       "Debug trace output to terminal status."
    DEFVAL  { 1 }
    ::=  { rsGeneric 39 }


rsDebugTraceOutputToSysLog OBJECT-TYPE
    SYNTAX FeatureStatus
    ACCESS  read-write
    STATUS  mandatory
    DESCRIPTION
       "Debug trace output to sys-log server status."
    DEFVAL  { 1 }
    ::=  { rsGeneric 40 }


rsDebugTraceMsgFormatDate OBJECT-TYPE
    SYNTAX DisplayStatus
    ACCESS  read-write
    STATUS  mandatory
    DESCRIPTION
       "Display status of date in debug trace message format."
    DEFVAL  { 1 }
    ::=  { rsGeneric 42 }


rsDebugTraceMsgFormatTime OBJECT-TYPE
    SYNTAX DisplayStatus
    ACCESS  read-write
    STATUS  mandatory
    DESCRIPTION
       "Display status of time in debug trace message format."
    DEFVAL  { 1 }
    ::=  { rsGeneric 43 }

rsDebugTraceMsgFormatPlatform OBJECT-TYPE
    SYNTAX DisplayStatus
    ACCESS  read-write
    STATUS  mandatory
    DESCRIPTION
       "Display status of platform in debug trace message format."
    DEFVAL  { 1 }
    ::=  { rsGeneric 44 }

rsDebugTraceMsgFormatFile OBJECT-TYPE
    SYNTAX DisplayStatus
    ACCESS  read-write
    STATUS  mandatory
    DESCRIPTION
       "Display status of file name in debug trace message format."
    DEFVAL  { 1 }
    ::=  { rsGeneric 45 }

rsDebugTraceMsgFormatLine OBJECT-TYPE
    SYNTAX DisplayStatus
    ACCESS  read-write
    STATUS  mandatory
    DESCRIPTION
       "Display status of line number in debug trace message format."
    DEFVAL  { 1 }
    ::=  { rsGeneric 46 }

rsDebugTraceMsgFormatPcktId OBJECT-TYPE
    SYNTAX DisplayStatus
    ACCESS  read-write
    STATUS  mandatory
    DESCRIPTION
       "Display status of packet ID in debug trace message format."
    DEFVAL  { 1 }
    ::=  { rsGeneric 47 }

rsDebugTraceMsgFormatModule OBJECT-TYPE
    SYNTAX DisplayStatus
    ACCESS  read-write
    STATUS  mandatory
    DESCRIPTION
       "Display status of module name number name in debug trace message format."
    DEFVAL  { 1 }
    ::=  { rsGeneric 48 }

rsDebugTraceMsgFormatTask OBJECT-TYPE
    SYNTAX DisplayStatus
    ACCESS  read-write
    STATUS  mandatory
    DESCRIPTION
       "Display status of task name number name in debug trace message format."
    DEFVAL  { 1 }
    ::=  { rsGeneric 49 }


rsDebugTraceApplTable OBJECT-TYPE
    SYNTAX SEQUENCE OF RsDebugTraceApplEntry
    ACCESS not-accessible
    STATUS  mandatory
    DESCRIPTION
      "Table containing information of application bound to debug module."
    ::=  {rsGeneric 50}

rsDebugTraceApplEntry OBJECT-TYPE
    SYNTAX RsDebugTraceApplEntry
    ACCESS not-accessible
    STATUS  mandatory
    DESCRIPTION
       "The row definition for this table."
    INDEX {rsDebugTraceApplName}
    ::=  { rsDebugTraceApplTable 1 }


RsDebugTraceApplEntry ::= SEQUENCE {
    rsDebugTraceApplName DisplayString,
    rsDebugTraceApplStatus FeatureStatus,
    rsDebugTraceApplSeverity INTEGER
}

rsDebugTraceApplName OBJECT-TYPE
    SYNTAX DisplayString  (SIZE(0..20))
    ACCESS  read-only
    STATUS  mandatory
    DESCRIPTION
      "Bound Application name"
    ::=  { rsDebugTraceApplEntry 1 }

rsDebugTraceApplStatus OBJECT-TYPE
    SYNTAX FeatureStatus
    ACCESS  read-write
    STATUS  mandatory
    DESCRIPTION
      "Bound Application status"
    ::=  { rsDebugTraceApplEntry 2 }

rsDebugTraceApplSeverity OBJECT-TYPE
    SYNTAX INTEGER {
              emergency(1),
              alert(2),
              critical(3),
              error(4),
              warning(5),
              notice(6),
              info(7),
              debug(8)}
    ACCESS  read-write
    STATUS  mandatory
    DESCRIPTION
      "Bound Application Tracing Severity. "
    ::=  { rsDebugTraceApplEntry 3 }




rsDebugSnapshotPoint OBJECT-TYPE
    SYNTAX INTEGER {
              on-packet-arrive(1),
              on-packet-send(2),
              both(3),
              on-packet-arrive-inc-decrypt-unit(4),
              on-packet-send-inc-decrypt-unit(5),
              both-inc-decrypt-unit(6),
	      only-decrypt-unit(7)
	      }
    ACCESS  read-write
    STATUS  mandatory
    DESCRIPTION
       ""
    DEFVAL  { 1 }
    ::=  { rsGeneric 51 }



rsDebugFilesTable OBJECT-TYPE
    SYNTAX SEQUENCE OF RsDebugFileEntry
    ACCESS not-accessible
    STATUS  mandatory
    DESCRIPTION
      "Table containing information about files generated by debug tools."
    ::=  {rsGeneric 52}

rsDebugFileEntry OBJECT-TYPE
    SYNTAX RsDebugFileEntry
    ACCESS not-accessible
    STATUS  mandatory
    DESCRIPTION
       "The row definition for this table."
    INDEX {rsDebugFileName}
    ::=  { rsDebugFilesTable 1 }


RsDebugFileEntry ::= SEQUENCE {
    rsDebugFileName DisplayString,
    rsDebugFileSize INTEGER,
    rsDebugFileRowStatus RowStatus
}

rsDebugFileName OBJECT-TYPE
    SYNTAX DisplayString  (SIZE(0..60))
    ACCESS  read-only
    STATUS  mandatory
    DESCRIPTION
      "Debug File name"
    ::=  { rsDebugFileEntry 1 }


rsDebugFileSize OBJECT-TYPE
    SYNTAX INTEGER
    ACCESS  read-only
    STATUS  mandatory
    DESCRIPTION
      "Debug File size"
    ::=  { rsDebugFileEntry 2 }

rsDebugFileRowStatus OBJECT-TYPE
    SYNTAX RowStatus
    ACCESS  read-write
    STATUS  mandatory
    DESCRIPTION
       "This variable indicates the administrative status of this entry.
        Used to delete an entry of this table."
    ::=  { rsDebugFileEntry 3 }

rsDebugFilesFlashTable OBJECT-TYPE
    SYNTAX SEQUENCE OF RsDebugFileFlashEntry
    ACCESS not-accessible
    STATUS  mandatory
    DESCRIPTION
      "Table containing information about files generated by debug tools."
    ::=  {rsGeneric 71}

rsDebugFileFlashEntry OBJECT-TYPE
    SYNTAX RsDebugFileFlashEntry
    ACCESS not-accessible
    STATUS  mandatory
    DESCRIPTION
       "The row definition for this table."
    INDEX {rsDebugFileFlashName}
    ::=  { rsDebugFilesFlashTable 1 }


RsDebugFileFlashEntry ::= SEQUENCE {
    rsDebugFileFlashName DisplayString,
    rsDebugFileFlashSize INTEGER,
    rsDebugFileFlashPathSecret INTEGER,
    rsDebugFileFlashRowStatus RowStatus
}



rsDebugFileFlashName OBJECT-TYPE
    SYNTAX DisplayString  (SIZE(0..60))
    ACCESS  read-only
    STATUS  mandatory
    DESCRIPTION
      "Debug File name"
    ::=  { rsDebugFileFlashEntry 1 }


rsDebugFileFlashSize OBJECT-TYPE
    SYNTAX INTEGER
    ACCESS  read-only
    STATUS  mandatory
    DESCRIPTION
      "Debug File size"
    ::=  { rsDebugFileFlashEntry 2 }



rsDebugFileFlashPathSecret OBJECT-TYPE
    SYNTAX INTEGER {
    ram(1),
    flash(2)}
    ACCESS  read-only
    STATUS  mandatory
    DESCRIPTION
      "Debug File size"
    ::=  { rsDebugFileFlashEntry 3 }



rsDebugFileFlashRowStatus OBJECT-TYPE
    SYNTAX RowStatus
    ACCESS  read-write
    STATUS  mandatory
    DESCRIPTION
       "This variable indicates the administrative status of this entry.
        Used to delete an entry of this table."
    ::=  { rsDebugFileFlashEntry 4 }


rsDebugFilesRamTable OBJECT-TYPE
    SYNTAX SEQUENCE OF RsDebugFileRamEntry
    ACCESS not-accessible
    STATUS  mandatory
    DESCRIPTION
      "Table containing information about files generated by debug tools."
    ::=  {rsGeneric 72}

rsDebugFileRamEntry OBJECT-TYPE
    SYNTAX RsDebugFileRamEntry
    ACCESS not-accessible
    STATUS  mandatory
    DESCRIPTION
       "The row definition for this table."
    INDEX {rsDebugFileRamName}
    ::=  { rsDebugFilesRamTable 1 }


RsDebugFileRamEntry ::= SEQUENCE {
    rsDebugFileRamName DisplayString,
    rsDebugFileRamSize INTEGER,
    rsDebugFileRamPathSecret INTEGER,
    rsDebugFileRamRowStatus RowStatus
}


rsDebugFileRamName OBJECT-TYPE
    SYNTAX DisplayString  (SIZE(0..60))
    ACCESS  read-only
    STATUS  mandatory
    DESCRIPTION
      "Debug File name"
    ::=  { rsDebugFileRamEntry 1 }


rsDebugFileRamSize OBJECT-TYPE
    SYNTAX INTEGER
    ACCESS  read-only
    STATUS  mandatory
    DESCRIPTION
      "Debug File size"
    ::=  { rsDebugFileRamEntry 2 }



rsDebugFileRamPathSecret OBJECT-TYPE
    SYNTAX INTEGER {
    ram(1),
    flash(2)}
    ACCESS  read-only
    STATUS  mandatory
    DESCRIPTION
      "Debug File size"
    ::=  { rsDebugFileRamEntry 3 }



rsDebugFileRamRowStatus OBJECT-TYPE
    SYNTAX RowStatus
    ACCESS  read-write
    STATUS  mandatory
    DESCRIPTION
       "This variable indicates the administrative status of this entry.
        Used to delete an entry of this table."
    ::=  { rsDebugFileRamEntry 4 }

rsDebugFileTFTPSendSrc OBJECT-TYPE
    SYNTAX DisplayString
    ACCESS  read-write
    STATUS  mandatory
    DESCRIPTION
        "The name of the file to be sent to TFTP server."
    ::= { rsGeneric 53 }

rsDebugFileDelete OBJECT-TYPE
    SYNTAX DisplayString
    ACCESS  read-write
    STATUS  mandatory
    DESCRIPTION
        "The name of the file to be deleted."
    ::= { rsGeneric 54 }

rsDebugFileTFTPSendDst OBJECT-TYPE
    SYNTAX DisplayString
    ACCESS  read-write
    STATUS  mandatory
    DESCRIPTION
        "File name where TFTP server should save transfered file."
    ::= { rsGeneric 56 }

rsDebugTraceApplTableInternal OBJECT-TYPE
    SYNTAX SEQUENCE OF RsDebugTraceApplEntryInternal
    ACCESS not-accessible
    STATUS  mandatory
    DESCRIPTION
      "Table containing information of application bound to debug module."
    ::=  {rsGeneric 57}

rsDebugTraceApplEntryInternal OBJECT-TYPE
    SYNTAX RsDebugTraceApplEntryInternal
    ACCESS not-accessible
    STATUS  mandatory
    DESCRIPTION
       "The row definition for this table."
    INDEX {rsDebugTraceApplNameInternal}
    ::=  { rsDebugTraceApplTableInternal 1 }


RsDebugTraceApplEntryInternal ::= SEQUENCE {
    rsDebugTraceApplNameInternal DisplayString,
    rsDebugTraceApplStatusInternal FeatureStatus,
    rsDebugTraceApplSeverityInternal INTEGER
}

rsDebugTraceApplNameInternal OBJECT-TYPE
    SYNTAX DisplayString  (SIZE(0..20))
    ACCESS  read-only
    STATUS  mandatory
    DESCRIPTION
      "Bound Internal Application name"
    ::=  { rsDebugTraceApplEntryInternal 1 }

rsDebugTraceApplStatusInternal OBJECT-TYPE
    SYNTAX FeatureStatus
    ACCESS  read-write
    STATUS  mandatory
    DESCRIPTION
      "Bound Internal Application status"
    ::=  { rsDebugTraceApplEntryInternal 2 }

rsDebugTraceApplSeverityInternal OBJECT-TYPE
    SYNTAX INTEGER {
              emergency(1),
              alert(2),
              critical(3),
              error(4),
              warning(5),
              notice(6),
              info(7),
              debug(8)}
    ACCESS  read-write
    STATUS  mandatory
    DESCRIPTION
      "Bound Internal Application Tracing Severity. "
    ::=  { rsDebugTraceApplEntryInternal 3 }

rsDebugSnapshotMode OBJECT-TYPE
    SYNTAX INTEGER {
              default(1),
              lab(2)}
    ACCESS  read-write
    STATUS  mandatory
    DESCRIPTION
       "The mode in which the diagnostic capture is working"
    DEFVAL  { 1 }
    ::=  { rsGeneric 58 }

rsWSDTelnetSessionTimeout OBJECT-TYPE
   SYNTAX  INTEGER (1..120)
   ACCESS  read-write
   STATUS  mandatory
   DESCRIPTION
        "Telnet session timeout (in minutes)."
   DEFVAL  { 5 }
   ::= { rsWSDTelnetParams 3 }

rsWSDTelnetAuthenticationTimeout OBJECT-TYPE
   SYNTAX  INTEGER (10..60)
   ACCESS  read-write
   STATUS  mandatory
   DESCRIPTION
        "Telnet authentication timeout (in seconds)."
   DEFVAL  { 30 }
   ::= { rsWSDTelnetParams 4 }

rsWSDSshSessionTimeout OBJECT-TYPE
   SYNTAX  INTEGER (1..120)
   ACCESS  read-write
   STATUS  mandatory
   DESCRIPTION
        "SSH session timeout (in minutes)."
   DEFVAL  { 5 }
   ::= { rsWSDSshParams 4 }

rsWSDSshAuthenticationTimeout OBJECT-TYPE
   SYNTAX  INTEGER (10..60)
   ACCESS  read-write
   STATUS  mandatory
   DESCRIPTION
        "SSH authentication timeout (in seconds)."
   DEFVAL  { 30 }
   ::= { rsWSDSshParams 5 }

rsWSDSshManageAlgorithms OBJECT-TYPE
    SYNTAX  DisplayString (SIZE(0..200))
    ACCESS  read-write
    STATUS  mandatory
    DESCRIPTION
         "SSH     encryptions list (in string format)."
    ::= { rsWSDSshParams 6 }

rsSendSupportFile OBJECT-TYPE
    SYNTAX DisplayString
    ACCESS  read-write
    STATUS  mandatory
    DESCRIPTION
        "The file name (including path) where the device will put the
        file containing the output of the 'manage support display' command.
        The destination address is the address of the management station."
    ::= { tftp 7 }

rsIpFragment OBJECT IDENTIFIER ::= { rsGeneric 55 }

rsIpFragmentStatus OBJECT-TYPE
    SYNTAX FeatureStatus
    ACCESS  read-write
    STATUS  mandatory
    DESCRIPTION "Enable/disable Ip Fragmentation."
	DEFVAL  { enable }
    ::= { rsIpFragment 1 }

rsIpFragmentQueuingLimit OBJECT-TYPE
   SYNTAX  INTEGER (0..100)
   ACCESS  read-write
   STATUS  mandatory
   DESCRIPTION
        "Ip Fragmentation Queuing Limit (percent)."
   DEFVAL  { 25 }
   ::= { rsIpFragment 2 }

rsIpFragmentAging OBJECT-TYPE
   SYNTAX  INTEGER (1..255)
   ACCESS  read-write
   STATUS  mandatory
   DESCRIPTION
        "Ip Fragmentation Aging Period (seconds)."
   DEFVAL  { 1 }
   ::= { rsIpFragment 3 }

rsIpFragmentForwardAgedPacket OBJECT-TYPE
    SYNTAX FeatureStatus
    ACCESS  read-write
    STATUS  mandatory
    DESCRIPTION "Enable/disable Ip Fragmentation Aged Packet Forwarding."
	DEFVAL  { enable }
    ::= { rsIpFragment 4 }

rsIpFragmentQueueingStatus OBJECT-TYPE
   SYNTAX  FeatureStatus
   ACCESS  read-write
   STATUS  mandatory
   DESCRIPTION
        "Ip Fragmentation Queueing Status."
   DEFVAL  { enable }
   ::= { rsIpFragment 5 }

rsIpFragmentTuning OBJECT IDENTIFIER ::= { rsGenericTuning 6 }

rsIpFragmentTableEntries OBJECT-TYPE
    SYNTAX INTEGER
    ACCESS  read-only
    STATUS  mandatory
    DESCRIPTION
      "Maximum number entries kept for the ip-fragments table ."
    ::= { rsIpFragmentTuning 1 }

rsIpFragmentTableEntriesAfterReset OBJECT-TYPE
    SYNTAX INTEGER
    ACCESS  read-write
    STATUS  mandatory
    DESCRIPTION
      "Future maximum number of entries kept for the ip-fragments table ."
    ::=  { rsIpFragmentTuning 2 }

rsPortsStatsTable OBJECT-TYPE
	SYNTAX SEQUENCE OF RsPortStatsEntry
	ACCESS not-accessible
    STATUS  mandatory
    DESCRIPTION
      "Table for the device ports statistics per second"
    ::=  {rsGeneric 59}

rsPortStatsEntry OBJECT-TYPE
	SYNTAX RsPortStatsEntry
	ACCESS not-accessible
    STATUS  mandatory
    DESCRIPTION
       "The row definition for this table"
   INDEX { rsPortStatsPortNumber }
    ::=  {rsPortsStatsTable 1}

RsPortStatsEntry ::= SEQUENCE {
  rsPortStatsPortNumber		     INTEGER,
  rsPortStatsInOctetsPerSec        INTEGER,
  rsPortStatsInPktsPerSec        INTEGER,
  rsPortStatsInDiscardsPerSec    INTEGER,
  rsPortStatsInErrorsPerSec      INTEGER,
  rsPortStatsOutOctetsPerSec     INTEGER,
  rsPortStatsOutPktsPerSec       INTEGER,
  rsPortStatsOutDiscardsPerSec   INTEGER,
  rsPortStatsOutErrorsPerSec	 INTEGER,
  rsPortStatsInMbitsPerSec       INTEGER,
  rsPortStatsOutMbitsPerSec      INTEGER
  }

rsPortStatsPortNumber OBJECT-TYPE
	SYNTAX  INTEGER
    ACCESS read-only
    STATUS  mandatory
    DESCRIPTION
      "port number"
    ::=  {rsPortStatsEntry 1}

--Below Field is OBSOLETE, will be removed in Future. Addedd new field rsPortStatsInMbitsPerSec
rsPortStatsInOctetsPerSec OBJECT-TYPE
	SYNTAX  INTEGER
    ACCESS read-only
    STATUS  mandatory
    DESCRIPTION
      "This field is OBSOLETE, instead use rsPortStatsInMbitsPerSec"
    ::=  {rsPortStatsEntry 2}

rsPortStatsInPktsPerSec OBJECT-TYPE
	SYNTAX  INTEGER
    ACCESS read-only
    STATUS  mandatory
    DESCRIPTION
      "amount of input data in packets in the last sec"
    ::=  {rsPortStatsEntry 3}

rsPortStatsInDiscardsPerSec OBJECT-TYPE
	SYNTAX  INTEGER
    ACCESS read-only
    STATUS  mandatory
    DESCRIPTION
      "amount of input data that got discarded in the last sec"
    ::=  {rsPortStatsEntry 4}

rsPortStatsInErrorsPerSec OBJECT-TYPE
	SYNTAX  INTEGER
    ACCESS read-only
    STATUS  mandatory
    DESCRIPTION
      "amount of input data that have error in the last sec"
    ::=  {rsPortStatsEntry 5}

--Below Field is OBSOLETE, will be removed in Future. Addedd new field rsPortStatsOutMbitsPerSec
rsPortStatsOutOctetsPerSec OBJECT-TYPE
	SYNTAX  INTEGER
    ACCESS read-only
    STATUS  mandatory
    DESCRIPTION
      "This field is OBSOLETE, instead use rsPortStatsOutMbitsPerSec"
    ::=  {rsPortStatsEntry 6}

rsPortStatsOutPktsPerSec OBJECT-TYPE
	SYNTAX  INTEGER
    ACCESS read-only
    STATUS  mandatory
    DESCRIPTION
      "amount of output data in packets in the last sec"
    ::=  {rsPortStatsEntry 7}

rsPortStatsOutDiscardsPerSec OBJECT-TYPE
	SYNTAX  INTEGER
    ACCESS read-only
    STATUS  mandatory
    DESCRIPTION
      "amount of output data that got discarded in the last sec"
    ::=  {rsPortStatsEntry 8}

rsPortStatsOutErrorsPerSec OBJECT-TYPE
	SYNTAX  INTEGER
    ACCESS read-only
    STATUS  mandatory
    DESCRIPTION
      "amount of output data that have error in the last sec"
    ::=  {rsPortStatsEntry 9}

--Below Two fields are added as a part of Fix for bug :DE41830
rsPortStatsInMbitsPerSec OBJECT-TYPE
        SYNTAX  INTEGER
    ACCESS read-only
    STATUS  mandatory
    DESCRIPTION
      "amount of input data in Mbits in the last sec"
    ::=  {rsPortStatsEntry 10}

rsPortStatsOutMbitsPerSec OBJECT-TYPE
        SYNTAX  INTEGER
    ACCESS read-only
    STATUS  mandatory
    DESCRIPTION
      "amount of output data in Mbits in the last sec"
    ::=  {rsPortStatsEntry 11}


rsPortStatsTotalInOctetsPerSec OBJECT-TYPE
	SYNTAX  INTEGER
    ACCESS read-only
    STATUS  obsolete
    DESCRIPTION
      "amount of total input in octets on all ports per second"
	::=  {rsGeneric 60 }

rsPortStatsTotalInMbitsPerSec OBJECT-TYPE
	SYNTAX 	INTEGER
	ACCESS	read-only
	STATUS	mandatory
	DESCRIPTION
	  "amount of total input in Mbits on all ports per second"
	::=	{rsGeneric 61 }

rsDebugSnapshotRate OBJECT-TYPE
    SYNTAX  INTEGER (1..10000)
    ACCESS  read-write
    STATUS  mandatory
    DESCRIPTION
       "The rate of packet capturing"
    DEFVAL  { 1 }
    ::=  { rsGeneric 62 }

-- Enterprise-specific traps for RADWARE
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------


rsGenericTablesFull   TRAP-TYPE
       ENTERPRISE  rsGeneric
        VARIABLES  { rndErrorDesc, rndErrorSeverity }
        DESCRIPTION
             "This trap is sent to inform the user about one of the generic tables being full."
       ::=  1

rsDebugTrace TRAP-TYPE
         ENTERPRISE rsGeneric
         VARIABLES { rndErrorDesc, rndErrorSeverity }
         DESCRIPTION
             "This info trap is sent when output to sys log server for debug traces is enabled."
     ::=  2

-- New tunneling support
--rsTunnelingModeProtocol OBJECT-TYPE
--    SYNTAX FeatureStatus
--    ACCESS  read-write
--    STATUS  mandatory
--    DESCRIPTION "Enabled entails that the tunneled data will be
--    treated by the application."
--  DEFVAL  { disable }
--    ::= { rsGeneric 62 }

rsTunnelingModeProtocolGre OBJECT-TYPE
    SYNTAX FeatureStatus
    ACCESS  read-write
    STATUS  mandatory
    DESCRIPTION "Enabled entails that the tunneled by GRE protocol data will be
    treated by the application."
--  DEFVAL  { disable }
    ::= { rsGeneric 63 }

rsTunnelingModeProtocolGtp OBJECT-TYPE
    SYNTAX FeatureStatus
    ACCESS  read-write
    STATUS  mandatory
    DESCRIPTION "Enabled entails that the tunneled by GTP protocol data will be
    treated by the application."
--  DEFVAL  { disable }
    ::= { rsGeneric 64 }
rsTunnelingModeProtocolL2tp OBJECT-TYPE
    SYNTAX FeatureStatus
    ACCESS  read-write
    STATUS  mandatory
    DESCRIPTION "Enabled entails that the tunneled by L2TP protocol data will be
    treated by the application."
--  DEFVAL  { disable }
    ::= { rsGeneric 65 }
rsTunnelingModeProtocolVlan OBJECT-TYPE
    SYNTAX FeatureStatus
    ACCESS  read-write
    STATUS  mandatory
    DESCRIPTION "Enabled entails that the tunneled by VLAN/MPLS data will be
    treated by the application."
--  DEFVAL  { disable }
    ::= { rsGeneric 66 }
rsTunnelingModeProtocolIpInIp OBJECT-TYPE
    SYNTAX FeatureStatus
    ACCESS  read-write
    STATUS  mandatory
    DESCRIPTION "Enabled entails that the tunneled by IpInIp data will be
    treated by the application."
--  DEFVAL  { disable }
    ::= { rsGeneric 67 }
rsTunnelingModeProtocolInner OBJECT-TYPE
    SYNTAX FeatureStatus
    ACCESS  read-write
    STATUS  mandatory
    DESCRIPTION "Enabled entails that the tunneled inner flag are enabled."
--  DEFVAL  { disable }
    ::= { rsGeneric 68 }
rsTunnelingModeProtocolIpsecBypass OBJECT-TYPE
    SYNTAX FeatureStatus
    ACCESS  read-write
    STATUS  mandatory
    DESCRIPTION "Enabled entails that ipsec traffic will be bypassed."
--  DEFVAL  { enable }
    ::= { rsGeneric 69 }

rdwrIntConfSyncConfigTimestamp OBJECT-TYPE
    SYNTAX	INTEGER
    ACCESS	read-only
    STATUS	mandatory
    DESCRIPTION
	"Timestamp of the last configuration change in the machine. used internaly for ICDE sync"
    ::= { rsGeneric 70 }

rsDiagPktCapGlobalStatus OBJECT-TYPE
    SYNTAX FeatureStatus
    ACCESS  read-write
    STATUS  mandatory
    DESCRIPTION
       "Diagnostics Packet Capture Tool Global status."
    DEFVAL  { 1 }
    ::=  { rsGeneric 73 }
  END
