IDS-MIB DEFINITIONS ::= BEGIN

-- Title:      RADWARE
--             This Private MIB supports the Vgate
-- Version:    3.0
-- Date:       17 Jun 2018
-- By:         RMA (Radware MIB Authority)
-- E-mail:     US:            support@radware.com
--             International: support_int@radware.com
--
IMPORTS
       NetworkAddress,
       IpAddress,
       Counter,
       Gauge,
       enterprises
              FROM RFC1155-SMI
       OBJECT-TYPE
              FROM RFC-1212
	   Counter32
              FROM SNMPv2-SMI
	   Counter64
              FROM SNMPv2-SMI
       Ipv6Address
			FROM IPV6-TC
       DisplayString,
       PhysAddress,
       ipAddrEntry
              FROM RFC1213-MIB
       TRAP-TYPE
                    FROM RFC-1215
	   MacAddress
              FROM SNMPv2-TC
       rsIDS,
       rndErrorDesc,
       rndErrorSeverity
                    FROM RADWARE-MIB;

    TruthValue ::= INTEGER {
         true (1),
         false (2)
        }
    RowStatus ::= INTEGER {
        active(1),
        notInService(2),
        notReady(3),
        createAndGo(4),
        createAndWait(5),
        destroy(6)
        }

    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }


 rsIDSTrackingTable OBJECT-TYPE
    SYNTAX SEQUENCE OF RsIDSTrackingEntry
    ACCESS not-accessible
    STATUS  mandatory
    DESCRIPTION
      "Table containing the parameters that are needed to detect intrusions"
    ::=  {rsIDS 1}


rsIDStrackingEntry OBJECT-TYPE
    SYNTAX RsIDSTrackingEntry
    ACCESS not-accessible
    STATUS  mandatory
    DESCRIPTION
       "The row definition for this table."
    INDEX { rsIDSFilterGroupName }
    ::=  { rsIDSTrackingTable 1 }

RsIDSTrackingEntry ::= SEQUENCE {
    rsIDSFilterGroupName DisplayString,
    rsIDSTrackingTime INTEGER,
    rsIDSThreshold INTEGER,
    rsIDSFilterGroupType INTEGER,
    rsIDSTrackingType INTEGER,
    rsIDSStatus    RowStatus,
    rsIDSReportMode INTEGER,
	rsIDSPacketReport INTEGER,
    rsIDSRisk INTEGER
}

rsIDSFilterGroupName OBJECT-TYPE
    SYNTAX DisplayString (SIZE(0..30))
    ACCESS  read-only
    STATUS  mandatory
    DESCRIPTION
      "The Name for the filter/group must be unique.
       that name should be the same as the name of the
       appropriate filter/group"
    ::=  {rsIDStrackingEntry 1}

rsIDSTrackingTime OBJECT-TYPE
    SYNTAX INTEGER
    ACCESS  read-write
    STATUS  mandatory
    DESCRIPTION
       "This variable indicates the time interval, in miliseconds,
        to track a detection"
    DEFVAL  { 1000 }
    ::=  { rsIDStrackingEntry 2 }

rsIDSThreshold OBJECT-TYPE
    SYNTAX INTEGER
    ACCESS  read-write
    STATUS  mandatory
    DESCRIPTION
       "This variable indicates the threshold "
    DEFVAL  { 50 }
    ::=  { rsIDStrackingEntry 3 }

rsIDSFilterGroupType OBJECT-TYPE
    SYNTAX INTEGER {
              filter(1),
              advanced-filter(2) }
    ACCESS  read-write
    STATUS  mandatory
    DESCRIPTION
       "This variable indicates the object type- whether it is a filter or group  "
    ::=  { rsIDStrackingEntry 4}

rsIDSTrackingType OBJECT-TYPE
    SYNTAX INTEGER {
    drop(0),
--    reset(1),
    ncps(2),
    ncpd(3),
    ncpsd(4),
--    ncpf(5),
--    winnuke(6),
    landattack(7),
--    synattackack(8),
--    tcpsyn(9),
--    tcpack(10),
--    tcpsynack(11),
--    tcprst(12),
--    tcpfin(13),
--    tcpelse(14),
      fragments(15),
      ncpsdscan(16),
	  dhcp(17)
    }
    ACCESS  read-write
    STATUS  mandatory
    DESCRIPTION
       "This variable indicates how to count  "
    ::=  { rsIDStrackingEntry 5}

rsIDSStatus OBJECT-TYPE
    SYNTAX RowStatus
    ACCESS  read-write
    STATUS  mandatory
    DESCRIPTION
       "This variable indicates the administrative status of this entry.
        Used to delete an entry of this table."
    ::=  { rsIDStrackingEntry 6 }


rsIDSReportMode OBJECT-TYPE
    SYNTAX INTEGER {
			drop(1),
			forward(2),
			rst-src(3),
     	    rst-dst(4),
    	    rst-bi(5),
			default(6)}
    ACCESS  read-write
    STATUS  mandatory
    DESCRIPTION
       "This variable indicates the attack report mode"
    ::=  { rsIDStrackingEntry 7}

rsIDSPacketReport OBJECT-TYPE
    SYNTAX INTEGER {
			enable(1),
			disable(2)}
    ACCESS  read-write
    STATUS  mandatory
    DESCRIPTION
       "This variable indicates the per-attack packet report"
	DEFVAL  {disable}
    ::=  { rsIDStrackingEntry 8}

rsIDSRisk OBJECT-TYPE
    SYNTAX INTEGER {
	  n-a(1),
	  low(2),
       	  medium(3),
	  high(4)}
    ACCESS  read-write
    STATUS  mandatory
    DESCRIPTION
       "This variable indicates the risk of the attack"
	DEFVAL  {medium}
    ::=  {rsIDStrackingEntry 9}

rsIDSMechanismStatus OBJECT-TYPE
 SYNTAX INTEGER {
      enable(1),
      disable(2)
   }
    ACCESS read-write
    STATUS mandatory
    DESCRIPTION
      "the Application Security trigger"
   DEFVAL  {enable}
    ::= {rsIDS 2}

rsIDSTCPAgingTimeFreq OBJECT-TYPE
 SYNTAX INTEGER
    ACCESS read-write
    STATUS mandatory
    DESCRIPTION
      "the TCP table aging time frequency"
    ::= {rsIDS 3}

rsIDSNCPsAgingTimeFreq OBJECT-TYPE
 SYNTAX INTEGER
    ACCESS read-write
    STATUS mandatory
    DESCRIPTION
      "the NCP's tables aging time frequency"
    ::= {rsIDS 4}

rsIDSStatsAgingTimeFreq OBJECT-TYPE
 SYNTAX INTEGER
    ACCESS read-write
    STATUS mandatory
    DESCRIPTION
      "the statistics table aging time frequency"
    ::= {rsIDS 5}

rsIDSNCPSTableSize OBJECT-TYPE
SYNTAX INTEGER
    ACCESS read-write
    STATUS mandatory
    DESCRIPTION
      "the NCPS table size"
    ::= {rsIDS 6}

rsIDSNCPDTableSize OBJECT-TYPE
 SYNTAX INTEGER
    ACCESS read-write
    STATUS mandatory
    DESCRIPTION
      "the NCPD table size"
    ::= {rsIDS 7}

rsIDSNCPSDTableSize OBJECT-TYPE
 SYNTAX INTEGER
    ACCESS read-write
    STATUS mandatory
    DESCRIPTION
      "the NCPSD table size"
    ::= {rsIDS 8}

rsIDSTCPTableSize OBJECT-TYPE
 SYNTAX INTEGER
    ACCESS read-write
    STATUS mandatory
    DESCRIPTION
      "the TCP table size"
    ::= {rsIDS 9}

rsIDSSTATSTableSize OBJECT-TYPE
 SYNTAX INTEGER
    ACCESS read-write
    STATUS mandatory
    DESCRIPTION
      "the statistics table size"
    ::= {rsIDS 10}

rsIDSBasic OBJECT-TYPE
 SYNTAX INTEGER {
      enable(1),
      disable(2)
   }
    ACCESS read-write
    STATUS mandatory
    DESCRIPTION
      "the basic protection rule trigger"
   DEFVAL  {disable}
    ::= {rsIDS 11}

rsIDSAllServers OBJECT-TYPE
 SYNTAX INTEGER {
      enable(1),
      disable(2)
   }
    ACCESS read-write
    STATUS mandatory
    DESCRIPTION
      "the All servers rule trigger"
   DEFVAL  {disable}
    ::= {rsIDS 12}


rsIDSUNIXServers OBJECT-TYPE
 SYNTAX INTEGER {
      enable(1),
      disable(2)
   }
    ACCESS read-write
    STATUS mandatory
    DESCRIPTION
      "the unix servers rule trigger"
   DEFVAL  {disable}
    ::= {rsIDS 13}

rsIDSLotusServers OBJECT-TYPE
 SYNTAX INTEGER {
      enable(1),
      disable(2)
   }
    ACCESS read-write
    STATUS mandatory
    DESCRIPTION
      "the Lotus servers rule trigger"
   DEFVAL  {disable}
    ::= {rsIDS 14}

rsIDSMSIISServers OBJECT-TYPE
 SYNTAX INTEGER {
      enable(1),
      disable(2)
   }
    ACCESS read-write
    STATUS mandatory
    DESCRIPTION
      "the MS_IIS servers rule trigger"
   DEFVAL  {disable}
    ::= {rsIDS 15}

rsIDSMSFrontPageServers OBJECT-TYPE
 SYNTAX INTEGER {
      enable(1),
      disable(2)
   }
    ACCESS read-write
    STATUS mandatory
    DESCRIPTION
      "the MS front page servers rule trigger"
   DEFVAL  {disable}
    ::= {rsIDS 16}

rsIDSApacheServers OBJECT-TYPE
 SYNTAX INTEGER {
      enable(1),
      disable(2)
   }
    ACCESS read-write
    STATUS mandatory
    DESCRIPTION
      "the Apache servers rule trigger"
   DEFVAL  {disable}
    ::= {rsIDS 17}

rsIDSNetscapeWebServers OBJECT-TYPE
 SYNTAX INTEGER {
      enable(1),
      disable(2)
   }
    ACCESS read-write
    STATUS mandatory
    DESCRIPTION
      "the Netscape_Web servers rule trigger"
   DEFVAL  {disable}
    ::= {rsIDS 18}

rsIDSNovellServers OBJECT-TYPE
 SYNTAX INTEGER {
      enable(1),
      disable(2)
   }
    ACCESS read-write
    STATUS mandatory
    DESCRIPTION
      "the Novell servers rule trigger"
   DEFVAL  {disable}
    ::= {rsIDS 19}

rsIDSOracleServers OBJECT-TYPE
 SYNTAX INTEGER {
      enable(1),
      disable(2)
   }
    ACCESS read-write
    STATUS mandatory
    DESCRIPTION
      "the Oracle servers rule trigger"
   DEFVAL  {disable}
    ::= {rsIDS 20}

rsIDSOmniHTTPDServers OBJECT-TYPE
 SYNTAX INTEGER {
      enable(1),
      disable(2)
   }
    ACCESS read-write
    STATUS mandatory
    DESCRIPTION
      "the OmniHTTPD servers rule trigger"
   DEFVAL  {disable}
    ::= {rsIDS 21}

rsIDSWebSiteServers OBJECT-TYPE
 SYNTAX INTEGER {
      enable(1),
      disable(2)
   }
    ACCESS read-write
    STATUS mandatory
    DESCRIPTION
      "the WebSite_WebSitePro servers rule trigger"
   DEFVAL  {disable}
    ::= {rsIDS 22}

rsIDSColdfusionServers OBJECT-TYPE
 SYNTAX INTEGER {
      enable(1),
      disable(2)
   }
    ACCESS read-write
    STATUS mandatory
    DESCRIPTION
      "the Allaire_Coldfusion servers rule trigger"
   DEFVAL  {disable}
    ::= {rsIDS 23}

rsIDSIRIXServers OBJECT-TYPE
 SYNTAX INTEGER {
      enable(1),
      disable(2)
   }
    ACCESS read-write
    STATUS mandatory
    DESCRIPTION
      "the IRIX servers rule trigger"
   DEFVAL  {disable}
    ::= {rsIDS 24}

rsIDSNCSAServers OBJECT-TYPE
 SYNTAX INTEGER {
      enable(1),
      disable(2)
   }
    ACCESS read-write
    STATUS mandatory
    DESCRIPTION
      "the NCSA servers rule trigger"
   DEFVAL  {disable}
    ::= {rsIDS 25}

rsIDSCompaqServers OBJECT-TYPE
 SYNTAX INTEGER {
      enable(1),
      disable(2)
   }
    ACCESS read-write
    STATUS mandatory
    DESCRIPTION
      "the Compaq_Web_Servers servers rule trigger"
   DEFVAL  {disable}
    ::= {rsIDS 26}

rsIDSbackdoors OBJECT-TYPE
 SYNTAX INTEGER {
      enable(1),
      disable(2)
   }
    ACCESS read-write
    STATUS mandatory
    DESCRIPTION
      "the backdoors rule trigger"
   DEFVAL  {disable}
    ::= {rsIDS 27}

rsIDSTraps OBJECT-TYPE
 SYNTAX INTEGER {
      enable(1),
      disable(2)
   }
    ACCESS read-write
    STATUS mandatory
    DESCRIPTION
      "the traps sending mechanism trigger"
   DEFVAL  {enable}
    ::= {rsIDS 28}

rsIDSStatsTable OBJECT-TYPE
    SYNTAX SEQUENCE OF RsIDSStatsEntry
    ACCESS not-accessible
    STATUS  mandatory
    DESCRIPTION
      "Table containing the intrusion detection statistics"
    ::=  {rsIDS 29}

rsIDSStatsEntry OBJECT-TYPE
    SYNTAX RsIDSStatsEntry
    ACCESS not-accessible
    STATUS  mandatory
    DESCRIPTION
       "The row definition for this table."
    INDEX { rsIDSAttackIndex }
    ::=  { rsIDSStatsTable 1 }

RsIDSStatsEntry ::= SEQUENCE {
    rsIDSAttackIndex   INTEGER,
    rsIDSAttackName    DisplayString,
    rsIDSAttackSrcAddr IpAddress,
    rsIDSAttackDstAddr IpAddress,
    rsIDSAttackStatus  INTEGER,
    rsIDSAttacktime    DisplayString,
    rsIDSStatsStatus   RowStatus,
    rsIDSStatsContext  INTEGER,
    rsIDSStatsSrcPort  INTEGER,
    rsIDSStatsDstPort  INTEGER,
    rsIDSStatsProtocol INTEGER,
    rsIDSStatsPhyPort  INTEGER,
    rsIDSStatsRID      INTEGER,
    rsIDSStatsService  INTEGER,
    rsIDSPolicyName    DisplayString,
    rsIDSStatsPktCount INTEGER,
    rsIDSStatsByteCount INTEGER,
    rsIDSStatsReportMode INTEGER,
    rsIDSStatsRisk INTEGER
}

rsIDSAttackIndex OBJECT-TYPE
    SYNTAX  INTEGER
    ACCESS  read-only
    STATUS  mandatory
    DESCRIPTION
      "The index of the attack that was detected"
    ::=  {rsIDSStatsEntry 1}

rsIDSAttackName OBJECT-TYPE
    SYNTAX DisplayString (SIZE(0..80))
    ACCESS  read-only
    STATUS  mandatory
    DESCRIPTION
      "The Name for the attack"
    ::=  {rsIDSStatsEntry 2}

rsIDSAttackSrcAddr OBJECT-TYPE
    SYNTAX  IpAddress
    ACCESS  read-only
    STATUS  mandatory
    DESCRIPTION
      "The src address of the attack"
    ::=  {rsIDSStatsEntry 3}

rsIDSAttackDstAddr OBJECT-TYPE
    SYNTAX  IpAddress
    ACCESS  read-only
    STATUS  mandatory
    DESCRIPTION
      "The dest address of the attack"
    ::=  {rsIDSStatsEntry 4}

rsIDSAttackStatus OBJECT-TYPE
    SYNTAX INTEGER {
	  -- discrete --
      started(1),
      terminated(2),
			occur(3),
	  -- limited --
      sampled(6),
	  -- aggregated --
      occured(11),
	  -- aggressive --
	  ongoing(16)
   }
    ACCESS  read-only
    STATUS  mandatory
    DESCRIPTION
      "The status of the attack(started/terminated/occured...)"
    ::=  {rsIDSStatsEntry 5}

rsIDSAttacktime OBJECT-TYPE
    SYNTAX DisplayString (SIZE(0..32))
    ACCESS  read-only
    STATUS  mandatory
    DESCRIPTION
      "The time of the attack"
    ::=  {rsIDSStatsEntry 6}

rsIDSStatsStatus OBJECT-TYPE
    SYNTAX RowStatus
    ACCESS  read-write
    STATUS  mandatory
    DESCRIPTION
       "This variable indicates the administrative status of this entry.
        Used to delete an entry of this table."
    ::=  { rsIDSStatsEntry 7 }

rsIDSStatsContext  OBJECT-TYPE
    SYNTAX INTEGER {
    	regular(1),
    	ssl(2)
    }
    ACCESS  read-only
    STATUS  mandatory
    DESCRIPTION
      "The context of the attack"
    ::=  {rsIDSStatsEntry 8}


rsIDSStatsSrcPort  OBJECT-TYPE
    SYNTAX INTEGER
    ACCESS  read-only
    STATUS  mandatory
    DESCRIPTION
      "The src address of the attack"
    ::=  {rsIDSStatsEntry 9}

rsIDSStatsDstPort  OBJECT-TYPE
    SYNTAX INTEGER
    ACCESS  read-only
    STATUS  mandatory
    DESCRIPTION
      "The dst address of the attack"
    ::=  {rsIDSStatsEntry 10}

rsIDSStatsProtocol OBJECT-TYPE
    SYNTAX INTEGER {
    	ip(1),
    	tcp(2),
    	udp(3),
    	icmp(4)
    }
    ACCESS  read-only
    STATUS  mandatory
    DESCRIPTION
      "The protocol of the attack"
    ::=  {rsIDSStatsEntry 11}

rsIDSStatsPhyPort OBJECT-TYPE
    SYNTAX INTEGER
    ACCESS  read-only
    STATUS  mandatory
    DESCRIPTION
      "The phy address of the attack"
    ::=  {rsIDSStatsEntry 12}

rsIDSStatsRID OBJECT-TYPE
    SYNTAX INTEGER
    ACCESS  read-only
    STATUS  mandatory
    DESCRIPTION
      "The Radware ID of the attack"
    ::=  {rsIDSStatsEntry 13}

rsIDSStatsService OBJECT-TYPE
    SYNTAX INTEGER {
      unassigned(1),
      intrusion(2),
      dos(3),
	  anomalies(4),
	  scanning(5)
   }
    ACCESS  read-only
    STATUS  mandatory
    DESCRIPTION
      "The Service/Category related to the event"
    ::=  {rsIDSStatsEntry 14}

rsIDSPolicyName OBJECT-TYPE
    SYNTAX DisplayString (SIZE(0..80))
    ACCESS  read-only
    STATUS  mandatory
    DESCRIPTION
      "The Name for the policy"
    ::=  {rsIDSStatsEntry 15}

rsIDSStatsPktCount OBJECT-TYPE
    SYNTAX INTEGER
    ACCESS  read-only
    STATUS  mandatory
    DESCRIPTION
      "The # of packets that match the attack filter"
    ::=  {rsIDSStatsEntry 16}

rsIDSStatsByteCount OBJECT-TYPE
    SYNTAX INTEGER
    ACCESS  read-only
    STATUS  mandatory
    DESCRIPTION
      "The # of packets that match the attack filter"
    ::=  {rsIDSStatsEntry 17}

rsIDSStatsReportMode OBJECT-TYPE
    SYNTAX INTEGER {
		  drop(1),
		  forward(2),
       	  rst-src(3),
   	      rst-dst(4),
   	      rst-bi(5)}
    ACCESS  read-only
    STATUS  mandatory
    DESCRIPTION
       "This variable indicates the action performed on the attack"
    ::=  {rsIDSStatsEntry 18}

rsIDSStatsRisk OBJECT-TYPE
    SYNTAX INTEGER {
	  n-a(1),
	  low(2),
       	  medium(3),
	  high(4)}
    ACCESS  read-only
    STATUS  mandatory
    DESCRIPTION
       "This variable indicates the risk of the attack"
	DEFVAL  {medium}
    ::=  {rsIDSStatsEntry 19}


rsIDSNCPDTableSizeAfterReset OBJECT-TYPE
    SYNTAX INTEGER
    ACCESS read-write
    STATUS mandatory
    DESCRIPTION
      "the NCPD after-reset table size"
    ::= {rsIDS 30}

rsIDSNCPSDTableSizeAfterReset OBJECT-TYPE
    SYNTAX INTEGER
    ACCESS read-write
    STATUS mandatory
    DESCRIPTION
      "the NCPS after-reset table size"
    ::= {rsIDS 31}

rsIDSTCPTableSizeAfterReset OBJECT-TYPE
    SYNTAX INTEGER
    ACCESS read-write
    STATUS mandatory
    DESCRIPTION
      "the NCPS after-reset table size"
    ::= {rsIDS 32}

 rsIDSSTATSTableSizeAfterReset OBJECT-TYPE
    SYNTAX INTEGER
    ACCESS read-write
    STATUS mandatory
    DESCRIPTION
      "the NCPS after-reset table size"
    ::= {rsIDS 33}

 rsIDSLogfileAgingTimeFreq OBJECT-TYPE
 SYNTAX INTEGER
    ACCESS read-write
    STATUS mandatory
    DESCRIPTION
      "the log file polling time frequency"
    ::= {rsIDS 34}

 rsIDSSendLogFile OBJECT-TYPE
    SYNTAX DisplayString
    ACCESS  read-write
    STATUS  mandatory
    DESCRIPTION
        "The file name include path where the device will put the
         log file. The default destination address will be the sender
         address."
    ::= { rsIDS 35 }

rsIDSUtils OBJECT-TYPE
 SYNTAX INTEGER {
      clrstats(1),
      clrlog(2)
   }
    ACCESS read-write
    STATUS mandatory
    DESCRIPTION
      "IDS miscellaneous utilities"
    ::= { rsIDS 36 }

rsIDSVersion OBJECT-TYPE
    SYNTAX DisplayString
    ACCESS  read-only
    STATUS  mandatory
    DESCRIPTION
        "The current IDS software version."
    ::= { rsIDS 37 }

 rsIDSSLTTrackingTable OBJECT-TYPE
    SYNTAX SEQUENCE OF RsIDSSLTTrackingEntry
    ACCESS not-accessible
    STATUS  mandatory
    DESCRIPTION
      "TempTable containing the temp parameters that are needed to detect
      intrusions"
    ::=  {rsIDS 38}


rsIDSSLTtrackingEntry OBJECT-TYPE
    SYNTAX RsIDSSLTTrackingEntry
    ACCESS not-accessible
    STATUS  mandatory
    DESCRIPTION
       "The row definition for this table."
    INDEX { rsIDSSLTFilterGroupName }
    ::=  { rsIDSSLTTrackingTable 1 }

RsIDSSLTTrackingEntry ::= SEQUENCE {
    rsIDSSLTFilterGroupName DisplayString,
    rsIDSSLTAlertThreshold INTEGER,
    rsIDSSLTActiveThreshold INTEGER,
    rsIDSSLTDropThreshold INTEGER,
    rsIDSSLTTermAlertThreshold INTEGER,
    rsIDSSLTTermThreshold INTEGER,
    rsIDSSLTAgingPeriod INTEGER,
    rsIDSSLTObjectID INTEGER,
    rsIDSSLTAttackState INTEGER,
    rsIDSSLTMsg DisplayString,
    rsIDSSLTStatus    RowStatus,
    rsIDSSLTReportMode INTEGER,
    rsIDSSLTRisk INTEGER
}

rsIDSSLTFilterGroupName OBJECT-TYPE
    SYNTAX DisplayString (SIZE(0..30))
    ACCESS  read-only
    STATUS  mandatory
    DESCRIPTION
      "The Name for the filter/group must be unique.
       that name should be the same as the name of the
       appropriate filter/group"
    ::=  {rsIDSSLTtrackingEntry 1}

rsIDSSLTAlertThreshold OBJECT-TYPE
    SYNTAX INTEGER
    ACCESS  read-write
    STATUS  mandatory
    DESCRIPTION
       "This variable indicates the attack alerting threshold "
    DEFVAL  { 30 }
    ::=  { rsIDSSLTtrackingEntry 2 }

rsIDSSLTActiveThreshold OBJECT-TYPE
    SYNTAX INTEGER
    ACCESS  read-write
    STATUS  mandatory
    DESCRIPTION
       "This variable indicates the activating threshold "
    DEFVAL  { 50 }
    ::=  { rsIDSSLTtrackingEntry 3 }

rsIDSSLTDropThreshold OBJECT-TYPE
    SYNTAX INTEGER
    ACCESS  read-write
    STATUS  mandatory
    DESCRIPTION
       "This variable indicates the dropping threshold "
    DEFVAL  { 50 }
    ::=  { rsIDSSLTtrackingEntry 4 }

rsIDSSLTTermAlertThreshold OBJECT-TYPE
    SYNTAX INTEGER
    ACCESS  read-write
    STATUS  mandatory
    DESCRIPTION
       "This variable indicates the termination alert threshold "
    DEFVAL  { 50 }
    ::=  { rsIDSSLTtrackingEntry 5 }

rsIDSSLTTermThreshold OBJECT-TYPE
    SYNTAX INTEGER
    ACCESS  read-write
    STATUS  mandatory
    DESCRIPTION
       "This variable indicates the termination threshold "
    DEFVAL  { 30 }
    ::=  { rsIDSSLTtrackingEntry 6 }

rsIDSSLTAgingPeriod OBJECT-TYPE
    SYNTAX INTEGER
    ACCESS  read-write
    STATUS  mandatory
    DESCRIPTION
       "This variable indicates the the number of periods before an attack is
       removed "
    DEFVAL  { 5 }
    ::=  { rsIDSSLTtrackingEntry 7 }

rsIDSSLTObjectID OBJECT-TYPE
    SYNTAX INTEGER
    ACCESS  read-write
    STATUS  mandatory
    DESCRIPTION
       "This variable indicates the the index of the object in the temp tracking
       table "
    ::=  { rsIDSSLTtrackingEntry 8 }

rsIDSSLTAttackState OBJECT-TYPE
    SYNTAX INTEGER {
    disable(0),
    sampling(1),
    active(2),
	panic(3) }
    ACCESS  read-write
    STATUS  mandatory
    DESCRIPTION
       "This variable indicates the attack state "
    ::=  { rsIDSSLTtrackingEntry 9}

rsIDSSLTMsg OBJECT-TYPE
    SYNTAX DisplayString (SIZE(0..80))
    ACCESS  read-write
    STATUS  mandatory
    DESCRIPTION
      "The alert that pops up in the terminal when
      there is an attack"
    ::=  {rsIDSSLTtrackingEntry 10}


rsIDSSLTStatus OBJECT-TYPE
    SYNTAX RowStatus
    ACCESS  read-write
    STATUS  mandatory
    DESCRIPTION
       "This variable indicates the administrative status of this entry.
        Used to delete an entry of this table."
    ::=  { rsIDSSLTtrackingEntry 11 }


rsIDSSLTReportMode OBJECT-TYPE
    SYNTAX INTEGER {
			drop(1),
			forward(2),
--       	  rst-src(3),
--     	      rst-dst(4),
--     	      rst-bi(5),
			  default(6)}
    ACCESS  read-write
    STATUS  mandatory
    DESCRIPTION
       "This variable indicates the dos attack report mode"
    ::=  { rsIDSSLTtrackingEntry 12}

rsIDSSLTRisk OBJECT-TYPE
    SYNTAX INTEGER {
	  n-a(1),
	  low(2),
       	  medium(3),
	  high(4)}
    ACCESS  read-write
    STATUS  mandatory
    DESCRIPTION
       "This variable indicates the risk of the dos attack"
	DEFVAL  {medium}
    ::=  {rsIDSSLTtrackingEntry 13}

rsIDSSLTACTTrackingTable OBJECT-TYPE
    SYNTAX SEQUENCE OF RsIDSSLTACTTrackingEntry
    ACCESS not-accessible
    STATUS  mandatory
    DESCRIPTION
      "The table containing the actual parameters that are needed to detect
      intrusions"
    ::=  {rsIDS 39}


rsIDSSLTACTtrackingEntry OBJECT-TYPE
    SYNTAX RsIDSSLTACTTrackingEntry
    ACCESS not-accessible
    STATUS  mandatory
    DESCRIPTION
       "The row definition for this table."
    INDEX { rsIDSSLTACTFilterGroupName }
    ::=  { rsIDSSLTACTTrackingTable 1 }

RsIDSSLTACTTrackingEntry ::= SEQUENCE {
    rsIDSSLTACTFilterGroupName DisplayString,
    rsIDSSLTACTAlertThreshold INTEGER,
    rsIDSSLTACTActiveThreshold INTEGER,
    rsIDSSLTACTDropThreshold INTEGER,
    rsIDSSLTACTTermAlertThreshold INTEGER,
    rsIDSSLTACTTermThreshold INTEGER,
    rsIDSSLTACTAgingPeriod INTEGER,
    rsIDSSLTACTObjectID INTEGER,
    rsIDSSLTACTAttackState INTEGER,
    rsIDSSLTACTMsg      DisplayString,
    rsIDSSLTACTStatus    RowStatus,
    rsIDSSLTACTReportMode INTEGER,
    rsIDSSLTACTRisk INTEGER
}

rsIDSSLTACTFilterGroupName OBJECT-TYPE
    SYNTAX DisplayString (SIZE(0..30))
    ACCESS  read-only
    STATUS  mandatory
    DESCRIPTION
      "The Name for the filter/group must be unique.
       that name should be the same as the name of the
       appropriate filter/group"
    ::=  {rsIDSSLTACTtrackingEntry 1}

rsIDSSLTACTAlertThreshold OBJECT-TYPE
    SYNTAX INTEGER
    ACCESS  read-only
    STATUS  mandatory
    DESCRIPTION
       "This variable indicates the attack alerting threshold "
    ::=  { rsIDSSLTACTtrackingEntry 2 }

rsIDSSLTACTActiveThreshold OBJECT-TYPE
    SYNTAX INTEGER
    ACCESS  read-only
    STATUS  mandatory
    DESCRIPTION
       "This variable indicates the activating threshold "
    DEFVAL  { 50 }
    ::=  { rsIDSSLTACTtrackingEntry 3 }

rsIDSSLTACTDropThreshold OBJECT-TYPE
    SYNTAX INTEGER
    ACCESS  read-only
    STATUS  mandatory
    DESCRIPTION
       "This variable indicates the dropping threshold "
    ::=  { rsIDSSLTACTtrackingEntry 4 }

rsIDSSLTACTTermAlertThreshold OBJECT-TYPE
    SYNTAX INTEGER
    ACCESS  read-only
    STATUS  mandatory
    DESCRIPTION
       "This variable indicates the termination alert threshold "
    ::=  { rsIDSSLTACTtrackingEntry 5 }

rsIDSSLTACTTermThreshold OBJECT-TYPE
    SYNTAX INTEGER
    ACCESS  read-only
    STATUS  mandatory
    DESCRIPTION
       "This variable indicates the termination threshold "
    ::=  { rsIDSSLTACTtrackingEntry 6 }

rsIDSSLTACTAgingPeriod OBJECT-TYPE
    SYNTAX INTEGER
    ACCESS  read-only
    STATUS  mandatory
    DESCRIPTION
       "This variable indicates the the number of periods before an attack is
       removed "
    ::=  { rsIDSSLTACTtrackingEntry 7 }

rsIDSSLTACTObjectID OBJECT-TYPE
    SYNTAX INTEGER
    ACCESS  read-only
    STATUS  mandatory
    DESCRIPTION
       "This variable indicates the the index of the object in the act tracking
       table "
    ::=  { rsIDSSLTACTtrackingEntry 8 }

rsIDSSLTACTAttackState OBJECT-TYPE
    SYNTAX INTEGER {
    disable(0),
    sampling(1),
    active(2),
	panic(3) }
    ACCESS  read-only
    STATUS  mandatory
    DESCRIPTION
       "This variable indicates the attack state "
    ::=  { rsIDSSLTACTtrackingEntry 9}

rsIDSSLTACTMsg OBJECT-TYPE
    SYNTAX DisplayString (SIZE(0..80))
    ACCESS  read-only
    STATUS  mandatory
    DESCRIPTION
      "The alert that pops up in the terminal when
      there is an attack"
    ::=  {rsIDSSLTACTtrackingEntry 10}


rsIDSSLTACTStatus OBJECT-TYPE
    SYNTAX RowStatus
    ACCESS  read-write
    STATUS  mandatory
    DESCRIPTION
       "This variable indicates the administrative status of this entry.
        Used to delete an entry of this table."
    ::=  { rsIDSSLTACTtrackingEntry 11 }

rsIDSSLTACTReportMode OBJECT-TYPE
    SYNTAX INTEGER {
			  drop(1),
			  forward(2),
--       	  rst-src(3),
--     	      rst-dst(4),
--     	      rst-bi(5),
			  default(6)}
    ACCESS  read-write
    STATUS  mandatory
    DESCRIPTION
       "This variable indicates the dos act attack report mode"
    ::=  { rsIDSSLTACTtrackingEntry 12}

rsIDSSLTACTRisk OBJECT-TYPE
    SYNTAX INTEGER {
	  n-a(1),
	  low(2),
       	  medium(3),
	  high(4)}
    ACCESS  read-write
    STATUS  mandatory
    DESCRIPTION
       "This variable indicates the risk of the dos act attack"
	DEFVAL  {medium}
    ::=  {rsIDSSLTACTtrackingEntry 13}

rsIDSSLTNCPFTable OBJECT-TYPE
    SYNTAX SEQUENCE OF RsIDSSLTNCPFEntry
    ACCESS not-accessible
    STATUS  mandatory
    DESCRIPTION
      "The table containing the SLT params"
    ::=  {rsIDS 40}


rsIDSSLTNCPFEntry OBJECT-TYPE
    SYNTAX RsIDSSLTNCPFEntry
    ACCESS not-accessible
    STATUS  mandatory
    DESCRIPTION
       "The row definition for this table."
    INDEX { rsIDSSLTNCPFObjectID, rsIDSSLTNCPFRuleName }
    ::=  { rsIDSSLTNCPFTable 1 }


RsIDSSLTNCPFEntry ::= SEQUENCE {
    rsIDSSLTNCPFObjectID INTEGER,
    rsIDSSLTNCPFRuleName DisplayString,
    rsIDSSLTNCPFSamplingCNT INTEGER,
    rsIDSSLTNCPFActiveCNT INTEGER,
    rsIDSSLTNCPFAlertState INTEGER,
    rsIDSSLTNCPFAttackState INTEGER,
    rsIDSSLTNCPFTermAlertCNT INTEGER,
    rsIDSSLTNCPFTermCNT INTEGER,
    rsIDSSLTAttackTime DisplayString,
    rsIDSSLTAttackDate DisplayString,
    rsIDSSLTAttackTermTime DisplayString,
    rsIDSSLTAttackTermDate DisplayString,
    rsIDSSLTNCPFStatus    RowStatus,
    rsIDSSLTAttackMsg DisplayString,
    rsIDSSLTNCPFPeakCNT INTEGER
}

rsIDSSLTNCPFObjectID OBJECT-TYPE
    SYNTAX INTEGER
    ACCESS  read-only
    STATUS  mandatory
    DESCRIPTION
       "This variable indicates attack's object id "
    ::=  { rsIDSSLTNCPFEntry 1 }

rsIDSSLTNCPFRuleName OBJECT-TYPE
    SYNTAX DisplayString (SIZE(0..20))
    ACCESS  read-only
    STATUS  mandatory
    DESCRIPTION
      "The name of the policy which caught the attack"
    ::=  {rsIDSSLTNCPFEntry 2}

rsIDSSLTNCPFSamplingCNT OBJECT-TYPE
    SYNTAX INTEGER
    ACCESS  read-only
    STATUS  mandatory
    DESCRIPTION
       "This variable indicates the sampling counter"
    ::=  { rsIDSSLTNCPFEntry 3 }

rsIDSSLTNCPFActiveCNT OBJECT-TYPE
    SYNTAX INTEGER
    ACCESS  read-only
    STATUS  mandatory
    DESCRIPTION
       "This variable indicates the active counter"
    ::=  { rsIDSSLTNCPFEntry 4 }

rsIDSSLTNCPFAlertState OBJECT-TYPE
    SYNTAX INTEGER {
              dont(0),
              not(1),
              sent(2),
              act(3),
              drop(4) }
    ACCESS  read-only
    STATUS  mandatory
    DESCRIPTION
       "This variable indicates the attack alerting state "
    ::=  { rsIDSSLTNCPFEntry 5 }

rsIDSSLTNCPFAttackState OBJECT-TYPE
    SYNTAX INTEGER {
              sampling(1),
              active(2) }
    ACCESS  read-only
    STATUS  mandatory
    DESCRIPTION
       "This variable indicates the attack state "
    ::=  { rsIDSSLTNCPFEntry 6 }

rsIDSSLTNCPFTermAlertCNT OBJECT-TYPE
    SYNTAX INTEGER
    ACCESS  read-only
    STATUS  mandatory
    DESCRIPTION
       "This variable indicates the attack termination alert counter "
    ::=  { rsIDSSLTNCPFEntry 7 }

rsIDSSLTNCPFTermCNT OBJECT-TYPE
    SYNTAX INTEGER
    ACCESS  read-only
    STATUS  mandatory
    DESCRIPTION
       "This variable indicates the attack termination counter"
    ::=  { rsIDSSLTNCPFEntry 8 }

rsIDSSLTAttackTime OBJECT-TYPE
    SYNTAX DisplayString (SIZE(0..9))
    ACCESS  read-only
    STATUS  mandatory
    DESCRIPTION
      "The last time the attack took place"
    ::=  {rsIDSSLTNCPFEntry 9}

rsIDSSLTAttackDate OBJECT-TYPE
    SYNTAX DisplayString (SIZE(0..11))
    ACCESS  read-only
    STATUS  mandatory
    DESCRIPTION
      "The last date the attack took place"
    ::=  {rsIDSSLTNCPFEntry 10}

rsIDSSLTAttackTermTime OBJECT-TYPE
    SYNTAX DisplayString (SIZE(0..9))
    ACCESS  read-only
    STATUS  mandatory
    DESCRIPTION
      "The last time the attack terminated"
    ::=  {rsIDSSLTNCPFEntry 11}

rsIDSSLTAttackTermDate OBJECT-TYPE
    SYNTAX DisplayString (SIZE(0..11))
    ACCESS  read-only
    STATUS  mandatory
    DESCRIPTION
      "The last date the attack terminated"
    ::=  {rsIDSSLTNCPFEntry 12}

rsIDSSLTNCPFStatus OBJECT-TYPE
    SYNTAX RowStatus
    ACCESS  read-write
    STATUS  mandatory
    DESCRIPTION
       "This variable indicates the administrative status of this entry.
        Used to delete an entry of this table."
    ::=  { rsIDSSLTNCPFEntry 13 }

rsIDSSLTAttackMsg OBJECT-TYPE
    SYNTAX DisplayString (SIZE(0..80))
    ACCESS  read-only
    STATUS  mandatory
    DESCRIPTION
      "The attack message"
    ::=  {rsIDSSLTNCPFEntry 14}

rsIDSSLTNCPFPeakCNT OBJECT-TYPE
    SYNTAX INTEGER
    ACCESS  read-only
    STATUS  mandatory
    DESCRIPTION
       "This variable indicates the peak counter"
    ::=  { rsIDSSLTNCPFEntry 15 }

rsIDSEmail OBJECT-TYPE
 SYNTAX INTEGER {
      enable(1),
      disable(2)
   }
    ACCESS read-write
    STATUS mandatory
    DESCRIPTION
      "the email sending mechanism trigger"
   DEFVAL  {enable}
    ::= {rsIDS 41}

rsIDSLogging OBJECT-TYPE
 SYNTAX INTEGER {
      enable(1),
      disable(2)
   }
    ACCESS read-write
    STATUS mandatory
    DESCRIPTION
      "the logging mechanism trigger"
   DEFVAL  {enable}
    ::= {rsIDS 42}

rsIDSSLTSamplingTimeFreq OBJECT-TYPE
 SYNTAX INTEGER
 ACCESS read-write
 STATUS mandatory
 DESCRIPTION
   "the SLT sampling time frequency"
   ::= {rsIDS 43}

rsIDSSLTMechStatus OBJECT-TYPE
 SYNTAX INTEGER {
      enable(1),
      disable(2)
   }
    ACCESS read-write
    STATUS mandatory
    DESCRIPTION
      "the DoS Shield trigger"
   DEFVAL  {enable}
    ::= {rsIDS 44}

rsIDSReportStatus OBJECT-TYPE
 SYNTAX INTEGER {
		drop(1),
		forward(2),
       	  rst-src(3),
     	      rst-dst(4),
     	      rst-bi(5)
   }
    ACCESS read-write
    STATUS mandatory
    DESCRIPTION
      "the Application Security reporting mode"
   DEFVAL  {drop}
    ::= {rsIDS 45}

rsIDSSLTReportStatus OBJECT-TYPE
 SYNTAX INTEGER {
		drop(1),
		forward(2)
--       	  rst-src(3),
--     	      rst-dst(4),
--     	      rst-bi(5)
   }
    ACCESS read-write
    STATUS mandatory
    DESCRIPTION
      "the DoS Shield reporting mode"
   DEFVAL  {drop}
    ::= {rsIDS 46}

rsIDSRulesTable OBJECT-TYPE
    SYNTAX SEQUENCE OF RsIDSRulesEntry
    ACCESS not-accessible
    STATUS  mandatory
    DESCRIPTION
      "Table containing the list of rules params for the ids"
    ::=  {rsIDS 47}

rsIDSRulesEntry OBJECT-TYPE
    SYNTAX RsIDSRulesEntry
    ACCESS not-accessible
    STATUS  mandatory
    DESCRIPTION
       "The row definition for this table."
    INDEX { rsIDSRulesIndex }
    ::=  { rsIDSRulesTable 1 }

RsIDSRulesEntry ::= SEQUENCE {
    rsIDSRulesIndex INTEGER,
    rsIDSRulesName DisplayString,
    rsIDSRulesSource DisplayString,
    rsIDSRulesDestination DisplayString,
    rsIDSRulesDirection INTEGER,
    rsIDSRulesPortmask DisplayString,
    rsIDSRulesStatus  RowStatus
}

rsIDSRulesIndex OBJECT-TYPE
    SYNTAX INTEGER
    ACCESS  read-only
    STATUS  mandatory
    DESCRIPTION
       "This variable indicates the administrative index of a line it
       determines the order of the rules."
    ::=  { rsIDSRulesEntry 1 }

rsIDSRulesName OBJECT-TYPE
    SYNTAX DisplayString (SIZE(0..20))
    ACCESS  read-only
    STATUS  mandatory
    DESCRIPTION
      "The Name for the Rule."
    ::=  {rsIDSRulesEntry 2}

rsIDSRulesSource OBJECT-TYPE
    SYNTAX DisplayString (SIZE(0..20))
    ACCESS  read-write
    STATUS  mandatory
    DESCRIPTION
      "The source address / range of address for the packet, the name is
      defined in the Objects table or can be an IP address."
    ::=  {rsIDSRulesEntry 3}

rsIDSRulesDestination OBJECT-TYPE
    SYNTAX DisplayString (SIZE(0..20))
    ACCESS  read-write
    STATUS  mandatory
    DESCRIPTION
      "The destination address / range of address for the packet, the name is
      defined in the Objects table or can be an IP address."
    ::=  {rsIDSRulesEntry 4}

rsIDSRulesDirection OBJECT-TYPE
    SYNTAX INTEGER {
              oneway(1),
              twoway(2) }
    ACCESS  read-write
    STATUS  mandatory
    DESCRIPTION
       "This variable indicates the direction of the incoming packet."
    DEFVAL { 1 }
    ::=  { rsIDSRulesEntry 5 }


rsIDSRulesPortmask OBJECT-TYPE
    SYNTAX DisplayString (SIZE(0..80))
    ACCESS  read-write
    STATUS  mandatory
    DESCRIPTION
       "The mask of the ports, should be in the format
       of 1,2,3,2"
    ::=  { rsIDSRulesEntry 6 }

rsIDSRulesStatus OBJECT-TYPE
    SYNTAX RowStatus
    ACCESS  read-write
    STATUS  mandatory
    DESCRIPTION
       "This variable indicates the administrative status of this entry.
        Used to delete an entry of this table."
    ::=  { rsIDSRulesEntry 7 }

rsIDSRestore OBJECT-TYPE
 SYNTAX INTEGER {
      dflsecgroups(1)
   }
    ACCESS read-write
    STATUS mandatory
    DESCRIPTION
      "Restore Default Configuration"
    ::= { rsIDS 48 }

rsIDSMaxURILength OBJECT-TYPE
    SYNTAX INTEGER (1..65535)
    ACCESS read-write
    STATUS mandatory
    DESCRIPTION
      "Max URI Length"
    DEFVAL  { 500 }
    ::=  { rsIDS 49 }

rsIDSMinFragmentSize OBJECT-TYPE
    SYNTAX INTEGER (0..65535)
    ACCESS read-write
    STATUS mandatory
    DESCRIPTION
      "Min fragmented packet size"
    DEFVAL  { 100 }
    ::=  { rsIDS 50 }

rsIDSMinUrlPktSize OBJECT-TYPE
    SYNTAX INTEGER (0..65535)
    ACCESS read-write
    STATUS mandatory
    DESCRIPTION
      "Min HTTP GET/HEAD/POST fargmented
      packet Length"
    DEFVAL  { 50 }
    ::=  { rsIDS 51 }

rsIDSNewRulesTable OBJECT-TYPE
    SYNTAX SEQUENCE OF RsIDSNewRulesEntry
    ACCESS not-accessible
    STATUS  mandatory
    DESCRIPTION
      "Table containing the list of rules params for the ids"
    ::=  {rsIDS 52}

rsIDSNewRulesEntry OBJECT-TYPE
    SYNTAX RsIDSNewRulesEntry
    ACCESS not-accessible
    STATUS  mandatory
    DESCRIPTION
       "The row definition for this table."
    INDEX { rsIDSNewRulesName }
    ::=  { rsIDSNewRulesTable 1 }

RsIDSNewRulesEntry ::= SEQUENCE {
    rsIDSNewRulesName DisplayString,
    rsIDSServiceName DisplayString, -- obsolete
    rsIDSNewRulesSource DisplayString,
    rsIDSNewRulesDestination DisplayString,
    rsIDSNewRulesDirection INTEGER,
    rsIDSNewRulesPortmask DisplayString,
    rsIDSNewRulesState INTEGER,
    rsIDSNewRulesStatus  RowStatus,
    rsIDSNewRulesVlanTagGroup DisplayString,
    rsIDSNewRulesAction INTEGER,
    rsIDSNewRulesPacketReportingStatus INTEGER,
    rsIDSNewRulesProfileAppsec DisplayString,
    rsIDSNewRulesProfileConlmt DisplayString,
    rsIDSNewRulesProfileStateful DisplayString,
    rsIDSNewRulesProfileScanning DisplayString,
    rsIDSNewRulesProfileNetflood DisplayString,
    rsIDSNewRulesProfileSynprotection DisplayString,
    rsIDSNewRulesProfileServprotection DisplayString,
    rsIDSNewRulesProfilePPS DisplayString,
    rsIDSNewRulesMPLSRDGroup DisplayString,
    rsIDSNewRulesPacketTraceStatus INTEGER,
    rsIDSNewRulesPacketTraceEnforcement INTEGER,
    rsIDSNewRulesPacketReportingEnforcement INTEGER,
    rsIDSNewRulesProfileDNS DisplayString,
    rsIDSQuarantineStatusInPolicy INTEGER,
    rsIDSNewRulesProfileServiceDiscovery DisplayString,
    rsIDSNewRulesInstanceId INTEGER,
    rsIDSNewRulesPriority   INTEGER,
    rsIDSNewRulesProfileTrafficFilters  DisplayString,
    rsIDSNewRulesCdnAction INTEGER,
    rsIDSNewRulesCdnHandling INTEGER
}

-- Orc - 22/2/20120 - Added Instance ID to the Sequence of NewRulesEntry. Moved to bottom of mib sequence.

rsIDSNewRulesName OBJECT-TYPE
    SYNTAX DisplayString (SIZE(1..64))
    ACCESS  read-only
    STATUS  mandatory
    DESCRIPTION
      "The Name for the Rule."
    ::=  {rsIDSNewRulesEntry 1}

rsIDSServiceName OBJECT-TYPE
    SYNTAX DisplayString (SIZE(1..29))
    ACCESS  read-write
    STATUS  mandatory
    DESCRIPTION
      "The Name for the Service."
    ::=  {rsIDSNewRulesEntry 2}

rsIDSNewRulesSource OBJECT-TYPE
    SYNTAX DisplayString (SIZE(0..46))
    ACCESS  read-write
    STATUS  mandatory
    DESCRIPTION
      "The source address / range of address for the packet, the name is
      defined in the Objects table or can be an IP address."
    ::=  {rsIDSNewRulesEntry 3}

rsIDSNewRulesDestination OBJECT-TYPE
    SYNTAX DisplayString (SIZE(0..64))
    ACCESS  read-write
    STATUS  mandatory
    DESCRIPTION
      "The destination address / range of address for the packet, the name is
      defined in the Objects table or can be an IP address."
    ::=  {rsIDSNewRulesEntry 4}

rsIDSNewRulesDirection OBJECT-TYPE
    SYNTAX INTEGER {
              oneway(1),
              twoway(2) }
    ACCESS  read-write
    STATUS  mandatory
    DESCRIPTION
       "This variable indicates the direction of the incoming packet."
    DEFVAL { 1 }
    ::=  { rsIDSNewRulesEntry 5 }


rsIDSNewRulesPortmask OBJECT-TYPE
    SYNTAX DisplayString (SIZE(0..80))
    ACCESS  read-write
    STATUS  mandatory
    DESCRIPTION
       "The Port Group"
    ::=  { rsIDSNewRulesEntry 6 }

 rsIDSNewRulesState OBJECT-TYPE
    SYNTAX INTEGER {
              active(1),
              inactive(2) }
    ACCESS  read-write
    STATUS  mandatory
    DESCRIPTION
       "This variable indicates the state of the rule."
    DEFVAL { 1 }
    ::=  { rsIDSNewRulesEntry 7 }

rsIDSNewRulesStatus OBJECT-TYPE
    SYNTAX RowStatus
    ACCESS  read-write
    STATUS  mandatory
    DESCRIPTION
       "This variable indicates the administrative status of this entry.
        Used to delete an entry of this table."
    ::=  { rsIDSNewRulesEntry 8 }

rsIDSNewRulesVlanTagGroup OBJECT-TYPE
    SYNTAX DisplayString (SIZE(0..80))
    ACCESS  read-write
    STATUS  mandatory
    DESCRIPTION
       "The VLAN tag Group"
    ::=  { rsIDSNewRulesEntry 9 }

rsIDSNewRulesAction OBJECT-TYPE
    SYNTAX INTEGER {
        report(0),
        block(1) }
    ACCESS  read-write
    STATUS  mandatory
    DESCRIPTION
       "This variable indicates the policy action"
    ::=  { rsIDSNewRulesEntry 10 }


rsIDSNewRulesPacketReportingStatus OBJECT-TYPE
    SYNTAX INTEGER {
     enable(1),
     disable(2)
	}
    ACCESS  read-write
    STATUS  mandatory
    DESCRIPTION
       "This variable indicates the packet reporting status for the policy rule"
    ::=  { rsIDSNewRulesEntry 11 }

rsIDSNewRulesProfileAppsec OBJECT-TYPE
    SYNTAX DisplayString (SIZE(0..29))
    ACCESS  read-write
    STATUS  mandatory
    DESCRIPTION
      "Name for the signatures profile."
    ::=  {rsIDSNewRulesEntry 12}

rsIDSNewRulesProfileConlmt OBJECT-TYPE
    SYNTAX DisplayString (SIZE(0..29))
    ACCESS  read-write
    STATUS  mandatory
    DESCRIPTION
      "Name for the connection limiting profile."
    ::=  {rsIDSNewRulesEntry 13}

rsIDSNewRulesProfileStateful OBJECT-TYPE
    SYNTAX DisplayString (SIZE(0..29))
    ACCESS  read-write
    STATUS  mandatory
    DESCRIPTION
      "Name for the stateful inspection profile."
    ::=  {rsIDSNewRulesEntry 14}

rsIDSNewRulesProfileScanning OBJECT-TYPE
    SYNTAX DisplayString (SIZE(0..29))
    ACCESS  read-write
    STATUS  mandatory
    DESCRIPTION
      "Name for the anti scanning profile."
    ::=  {rsIDSNewRulesEntry 15}

rsIDSNewRulesProfileNetflood OBJECT-TYPE
    SYNTAX DisplayString (SIZE(0..29))
    ACCESS  read-write
    STATUS  mandatory
    DESCRIPTION
      "Name for the behavioral dos profile."
    ::=  {rsIDSNewRulesEntry 16}

rsIDSNewRulesProfileSynprotection OBJECT-TYPE
    SYNTAX DisplayString (SIZE(0..29))
    ACCESS  read-write
    STATUS  mandatory
    DESCRIPTION
      "Name for the syn protection profile."
    ::=  {rsIDSNewRulesEntry 17}

rsIDSNewRulesProfileServprotection OBJECT-TYPE
    SYNTAX DisplayString (SIZE(0..29))
    ACCESS  read-write
    STATUS  mandatory
    DESCRIPTION
      "Name for the server protection profile."
    ::=  {rsIDSNewRulesEntry 18}

rsIDSNewRulesProfilePPS OBJECT-TYPE
    SYNTAX DisplayString (SIZE(0..29))
    ACCESS  read-write
    STATUS  mandatory
    DESCRIPTION
      "Name for the PPS limiting profile."
    ::=  {rsIDSNewRulesEntry 19}

rsIDSNewRulesMPLSRDGroup OBJECT-TYPE
    SYNTAX DisplayString (SIZE(0..29))
    ACCESS  read-write
    STATUS  mandatory
    DESCRIPTION
      "Name for the MPLS RD group."
    ::=  {rsIDSNewRulesEntry 20}

rsIDSNewRulesPacketTraceStatus OBJECT-TYPE
    SYNTAX INTEGER {
     enable(1),
     disable(2)
	}
    ACCESS  read-write
    STATUS  mandatory
    DESCRIPTION
       "This variable indicates the packet trace status for the policy rule"
    ::=  { rsIDSNewRulesEntry 21 }

rsIDSNewRulesPacketTraceEnforcement OBJECT-TYPE
    SYNTAX INTEGER {
     enable(1),
     disable(2)
	}
    ACCESS  read-write
    STATUS  mandatory
    DESCRIPTION
       "This variable indicates the packet trace enforcement status for the policy rule"
    ::=  { rsIDSNewRulesEntry 22 }

rsIDSNewRulesPacketReportingEnforcement OBJECT-TYPE
    SYNTAX INTEGER {
     enable(1),
     disable(2)
	}
    ACCESS  read-write
    STATUS  mandatory
    DESCRIPTION
       "This variable indicates the packet reporting enforcement status for the policy rule"
    ::=  { rsIDSNewRulesEntry 23}

rsIDSNewRulesProfileDNS OBJECT-TYPE
    SYNTAX DisplayString (SIZE(0..29))
    ACCESS  read-write
    STATUS  mandatory
    DESCRIPTION
      "Name for the DNS protection profile."
    ::=  {rsIDSNewRulesEntry 24}

rsIDSQuarantineStatusInPolicy OBJECT-TYPE
    SYNTAX INTEGER {
     enable(1),
     disable(2)
	}
    ACCESS  read-write
    STATUS  mandatory
    DESCRIPTION
       "Quarantine Configuration"
    ::=  { rsIDSNewRulesEntry 25}


rsIDSNewRulesProfileServiceDiscovery OBJECT-TYPE
    SYNTAX DisplayString (SIZE(0..29))
    ACCESS  read-write
    STATUS  mandatory
    DESCRIPTION
      "Name for the Service Discovery protection profile."
    ::=  {rsIDSNewRulesEntry 26}


	    -- Orc - 9/2/2012 - Added the Instance ID mib
rsIDSNewRulesInstanceId OBJECT-TYPE
	SYNTAX INTEGER {
              instance0(0),
              instance1(1) }
    ACCESS read-only
    STATUS mandatory
    DESCRIPTION
      "This variable indicates the Instance ID ascription for the policy"
    ::= {rsIDSNewRulesEntry 27}

rsIDSNewRulesPriority OBJECT-TYPE
    SYNTAX INTEGER (0..64000)
    ACCESS read-write
    STATUS mandatory
    DESCRIPTION
      "This variable indicates the Policy Priority."
    DEFVAL  { 0 }
    ::= {rsIDSNewRulesEntry 28}

rsIDSNewRulesProfileTrafficFilters OBJECT-TYPE
    SYNTAX DisplayString (SIZE(0..29))
    ACCESS  read-write
    STATUS  mandatory
    DESCRIPTION
      "Name for the Traffic Filters profile."
    ::=  {rsIDSNewRulesEntry 29}

rsIDSNewRulesCdnAction OBJECT-TYPE
    SYNTAX INTEGER {
        disabled(0),
	http200ok(1),
        http200ok-rst-dst(2),
	http403(3),
        http403-rst-dst(4) }
    ACCESS  read-write
    STATUS  mandatory
    DESCRIPTION
       "This variable indicates the policy CDN action"
    ::=  { rsIDSNewRulesEntry 30 }

rsIDSNewRulesCdnHandling OBJECT-TYPE
    SYNTAX INTEGER {
        disable(2),
		enable(1)
    }
    ACCESS  read-write
    STATUS  mandatory
    DESCRIPTION
       "This variable indicates the policy CDN handling status"
    ::=  { rsIDSNewRulesEntry 31 }

rsIDSRestoreGroup OBJECT-TYPE
    SYNTAX DisplayString
    ACCESS read-write
    STATUS mandatory
    DESCRIPTION
      "Restore Default Group Configuration"
    ::= { rsIDS 53 }

rsIDSStaticGroupTable OBJECT-TYPE
    SYNTAX SEQUENCE OF RsIDSStaticGroupEntry
    ACCESS not-accessible
    STATUS  mandatory
    DESCRIPTION
      "Table containing the parameters that are needed to detect intrusions"
    ::=  {rsIDS 54}


rsIDSStaticGroupEntry OBJECT-TYPE
    SYNTAX RsIDSStaticGroupEntry
    ACCESS not-accessible
    STATUS  mandatory
    DESCRIPTION
       "The row definition for this table."
    INDEX { rsIDSStaticGroupName }
    ::=  { rsIDSStaticGroupTable 1 }

RsIDSStaticGroupEntry ::= SEQUENCE {
    rsIDSStaticGroupName DisplayString
}

rsIDSStaticGroupName OBJECT-TYPE
    SYNTAX DisplayString (SIZE(0..30))
    ACCESS  read-only
    STATUS  mandatory
    DESCRIPTION
      "The Name for the filter/group must be unique.
       that name should be the same as the name of the
       appropriate filter/group"
    ::=  {rsIDSStaticGroupEntry 1}


rsIDSPanicMode OBJECT-TYPE
 SYNTAX INTEGER {
     enable(1),
     disable(2)
   }
    ACCESS read-write
    STATUS mandatory
    DESCRIPTION
      "the Panic Mode status"
   DEFVAL  {disable}
    ::= {rsIDS 55}


rsIDSAttackDBSend OBJECT-TYPE
    SYNTAX DisplayString
    ACCESS  read-write
    STATUS  mandatory
    DESCRIPTION
        "The file name include path where the attack database located."
    ::=  {rsIDS 56}

rsIDSAttackDBVersion OBJECT-TYPE
    SYNTAX DisplayString (SIZE(0..30))
    ACCESS  read-only
    STATUS  mandatory
    DESCRIPTION
      "The version of the Attack database file"
    ::=  {rsIDS 57}

rsIDSAttackDBUpdateRes OBJECT-TYPE
 SYNTAX INTEGER {
     succeeded(1),
     failed(2),
     processing(3),
     reboot-needed(4),
     auth-fail(5)
   }
    ACCESS read-write
    STATUS mandatory
    DESCRIPTION
      "The attack db file update result"
   DEFVAL  {succeeded}
    ::= {rsIDS 58}


rsIDSDHCPTableSize OBJECT-TYPE
 SYNTAX INTEGER
    ACCESS read-write
    STATUS mandatory
    DESCRIPTION
      "the DHCP table size"
    ::= {rsIDS 59}

rsIDSDHCPTableSizeAfterReset OBJECT-TYPE
    SYNTAX INTEGER
    ACCESS read-write
    STATUS mandatory
    DESCRIPTION
      "the DHCP after-reset table size"
    ::= {rsIDS 60}


rsIDSLogDisplay OBJECT-TYPE
    SYNTAX SEQUENCE OF RsIDSLogEntry
    ACCESS not-accessible
    STATUS  mandatory
    DESCRIPTION
      "A table-like display containing security logfile entries"
    ::=  {rsIDS 61}

rsIDSLogEntry OBJECT-TYPE
    SYNTAX RsIDSLogEntry
    ACCESS not-accessible
    STATUS  mandatory
    DESCRIPTION
       "The row definition for the Security logfile."
    INDEX { rsIDSLogIndex }
    ::=  { rsIDSLogDisplay 1 }

RsIDSLogEntry ::= SEQUENCE {
    rsIDSLogIndex		INTEGER,
    rsIDSLogAttackName	DisplayString,
    rsIDSLogSrcAddr		Ipv6Address,
    rsIDSLogDstAddr		Ipv6Address,
    rsIDSLogAttackStatus INTEGER,
    rsIDSLogtime		DisplayString,
	rsIDSLogStatus		RowStatus,
    rsIDSLogContext		INTEGER,
    rsIDSLogSrcPort		INTEGER,
    rsIDSLogDstPort		INTEGER,
    rsIDSLogProtocol	INTEGER,
    rsIDSLogPhyPort		INTEGER,
    rsIDSLogRID			INTEGER,
    rsIDSLogCategory	INTEGER,
    rsIDSLogPolicyName	DisplayString,
    rsIDSLogPktCount	INTEGER,
    rsIDSLogByteCount	INTEGER,
	rsIDSLogReportMode	INTEGER,
	rsIDSLogRisk		INTEGER,
	rsIDSLogVlanTag		INTEGER,
	rsIDSLogMPLSTag		INTEGER,
	rsIDSLogMPLSRD      DisplayString,
        rsIDSLogInstance	INTEGER
}

rsIDSLogIndex OBJECT-TYPE
    SYNTAX  INTEGER
    ACCESS  read-only
    STATUS  mandatory
    DESCRIPTION
      "The index of the attack that was detected"
    ::=  {rsIDSLogEntry 1}

rsIDSLogAttackName OBJECT-TYPE
    SYNTAX DisplayString (SIZE(0..80))
    ACCESS  read-only
    STATUS  mandatory
    DESCRIPTION
      "The Name for the attack"
    ::=  {rsIDSLogEntry 2}

rsIDSLogSrcAddr OBJECT-TYPE
    SYNTAX  Ipv6Address
    ACCESS  read-only
    STATUS  mandatory
    DESCRIPTION
      "The src address of the attack"
    ::=  {rsIDSLogEntry 3}

rsIDSLogDstAddr OBJECT-TYPE
    SYNTAX  Ipv6Address
    ACCESS  read-only
    STATUS  mandatory
    DESCRIPTION
      "The dest address of the attack"
    ::=  {rsIDSLogEntry 4}

rsIDSLogAttackStatus OBJECT-TYPE
    SYNTAX INTEGER {
	  -- discrete --
      started(1),
      terminated(2),
			occur(3),
	  -- limited --
      sampled(6),
	  -- aggregated --
      occured(11),
	  -- aggressive --
	  ongoing(16)
   }
    ACCESS  read-only
    STATUS  mandatory
    DESCRIPTION
      "The status of the attack(started/terminated/occured...)"
    ::=  {rsIDSLogEntry 5}

rsIDSLogtime OBJECT-TYPE
    SYNTAX DisplayString (SIZE(0..32))
    ACCESS  read-only
    STATUS  mandatory
    DESCRIPTION
      "The time of the attack"
    ::=  {rsIDSLogEntry 6}

rsIDSLogStatus OBJECT-TYPE
    SYNTAX RowStatus
    ACCESS  read-write
    STATUS  mandatory
    DESCRIPTION
       "This variable indicates the administrative status of this entry.
        Used to delete an entry of this table."
    ::=  { rsIDSLogEntry 7 }

rsIDSLogContext  OBJECT-TYPE
    SYNTAX INTEGER {
    	regular(1),
    	ssl(2),
		passive-ssl(3)
    }
    ACCESS  read-only
    STATUS  mandatory
    DESCRIPTION
      "The context of the attack"
    ::=  {rsIDSLogEntry 8}


rsIDSLogSrcPort  OBJECT-TYPE
    SYNTAX INTEGER
    ACCESS  read-only
    STATUS  mandatory
    DESCRIPTION
      "The src address of the attack"
    ::=  {rsIDSLogEntry 9}

rsIDSLogDstPort  OBJECT-TYPE
    SYNTAX INTEGER
    ACCESS  read-only
    STATUS  mandatory
    DESCRIPTION
      "The dst address of the attack"
    ::=  {rsIDSLogEntry 10}

rsIDSLogProtocol OBJECT-TYPE
    SYNTAX INTEGER {
    	ip(1),
    	tcp(2),
    	udp(3),
    	icmp(4),
    	nonip(5),
		sctp(6),
    	icmpv6(7)
    }
    ACCESS  read-only
    STATUS  mandatory
    DESCRIPTION
      "The protocol of the attack"
    ::=  {rsIDSLogEntry 11}

rsIDSLogPhyPort OBJECT-TYPE
    SYNTAX INTEGER
    ACCESS  read-only
    STATUS  mandatory
    DESCRIPTION
      "The phy address of the attack"
    ::=  {rsIDSLogEntry 12}

rsIDSLogRID OBJECT-TYPE
    SYNTAX INTEGER
    ACCESS  read-only
    STATUS  mandatory
    DESCRIPTION
      "The Radware ID of the attack"
    ::=  {rsIDSLogEntry 13}

rsIDSLogCategory OBJECT-TYPE
    SYNTAX INTEGER {
      unassigned(1),
      intrusion(2),
      dos(3),
	  	anomalies(4),
	 		scanning(5),
	 		behavioral-doS(6),
  		syn-flood(7),
  		access(8),
		http-flood(9),
		server-protection(10),
		acl(11),
		session-table-protection(12),
		bwm(13),
		dns-protection(14),
		traffic-filters(15)
   }
    ACCESS  read-only
    STATUS  mandatory
    DESCRIPTION
      "The category related to the event"
    ::=  {rsIDSLogEntry 14}

rsIDSLogPolicyName OBJECT-TYPE
    SYNTAX DisplayString (SIZE(0..80))
    ACCESS  read-only
    STATUS  mandatory
    DESCRIPTION
      "The Name for the policy"
    ::=  {rsIDSLogEntry 15}

rsIDSLogPktCount OBJECT-TYPE
    SYNTAX INTEGER
    ACCESS  read-only
    STATUS  mandatory
    DESCRIPTION
      "The # of packets that match the attack filter"
    ::=  {rsIDSLogEntry 16}

rsIDSLogByteCount OBJECT-TYPE
    SYNTAX INTEGER
    ACCESS  read-only
    STATUS  mandatory
    DESCRIPTION
      "The # of packets that match the attack filter"
    ::=  {rsIDSLogEntry 17}

rsIDSLogReportMode OBJECT-TYPE
    SYNTAX INTEGER {
        report-only(0),
		proxy(9),
	    drop(10),
	    rst-src(11),
     	rst-dst(12),
    	rst-bi(13),
		rst-mm7(15),
		quarantine(16),
		drop-and-quarantine(17)}
    ACCESS  read-only
    STATUS  mandatory
    DESCRIPTION
       "This variable indicates the action performed on the attack"
    ::=  {rsIDSLogEntry 18}

rsIDSLogRisk OBJECT-TYPE
    SYNTAX INTEGER {
		  info(1),
		  low(2),
       	  medium(3),
		  high(4)}
    ACCESS  read-only
    STATUS  mandatory
    DESCRIPTION
       "This variable indicates the risk of the attack"
    ::=  {rsIDSLogEntry 19}

rsIDSLogVlanTag OBJECT-TYPE
    SYNTAX INTEGER
    ACCESS  read-only
    STATUS  mandatory
    DESCRIPTION
      "The vlan tag in the packet of the attack"
    ::=  {rsIDSLogEntry 20}

rsIDSLogMPLSTag OBJECT-TYPE
    SYNTAX INTEGER
    ACCESS  read-only
    STATUS  mandatory
    DESCRIPTION
      "The MPLS tag in the packet of the attack"
    ::=  {rsIDSLogEntry 21}

rsIDSLogMPLSRD OBJECT-TYPE
    SYNTAX DisplayString (SIZE(0..30))
    ACCESS  read-only
    STATUS  mandatory
    DESCRIPTION
      "The Name for the policy"
    ::=  {rsIDSLogEntry 22}

rsIDSLogInstance OBJECT-TYPE
    SYNTAX INTEGER
    ACCESS  read-only
    STATUS  mandatory
    DESCRIPTION
      "The active Instance in the packet of the attack"
    ::=  {rsIDSLogEntry 24}


rsIDSGlobalPacketReport OBJECT-TYPE
 SYNTAX INTEGER {
      enable(1),
      disable(2)
   }
    ACCESS not-accessible
    STATUS mandatory
    DESCRIPTION
      "The Application Security global packet-reporting configuration"
   DEFVAL  {disable}
    ::= {rsIDS 62}

rsIDSGroupCategoryTable OBJECT-TYPE
    SYNTAX SEQUENCE OF RsIDSGroupCategoryEntry
    ACCESS not-accessible
    STATUS  mandatory
    DESCRIPTION
      "Table group list and categories."
    ::= { rsIDS 63 }

rsIDSGroupCategoryEntry OBJECT-TYPE
    SYNTAX RsIDSGroupCategoryEntry
    ACCESS not-accessible
    STATUS mandatory
    DESCRIPTION
       "The row definition for this table."
    INDEX {rsIDSGroupCategory, rsIDSGroupCatName }
    ::=  { rsIDSGroupCategoryTable 1 }

RsIDSGroupCategoryEntry ::= SEQUENCE {
    rsIDSGroupCategory INTEGER,
    rsIDSGroupCatName DisplayString
}

rsIDSGroupCategory OBJECT-TYPE
    SYNTAX INTEGER {
        unassigned(1),
        intrusions(2),
        dos(3),
        anomalies(4),
        anti-scanning(5)
    }
    ACCESS read-only
    STATUS mandatory
    DESCRIPTION
      "The group category."
    ::=  { rsIDSGroupCategoryEntry 1 }

rsIDSGroupCatName OBJECT-TYPE
    SYNTAX DisplayString(SIZE(0..30))
    ACCESS read-write
    STATUS mandatory
    DESCRIPTION
      "The name of the group."
    ::=  { rsIDSGroupCategoryEntry 2 }

rsIDSReportingInterval OBJECT-TYPE
    SYNTAX INTEGER (1..65535)
    ACCESS read-write
    STATUS mandatory
    DESCRIPTION
      "Reporting Interval"
    DEFVAL  { 5 }
    ::=  { rsIDS 64 }

rsIDSMaxAlertPerReport OBJECT-TYPE
    SYNTAX INTEGER (1..2000)
    ACCESS read-write
    STATUS mandatory
    DESCRIPTION
      "Maximum Alerts per Report"
    DEFVAL  { 1000 }
    ::=  { rsIDS 65 }

-- obsolete
rsIDSProfilesTable OBJECT-TYPE
    SYNTAX SEQUENCE OF RsIDSProfilesEntry
    ACCESS not-accessible
    STATUS  mandatory
    DESCRIPTION
      "Table containing the list of rules params for the ids"
    ::=  {rsIDS 66}

-- obsolete
rsIDSProfilesEntry OBJECT-TYPE
    SYNTAX RsIDSProfilesEntry
    ACCESS not-accessible
    STATUS  mandatory
    DESCRIPTION
       "The row definition for this table."
    INDEX { rsIDSProfilesName, rsIDSProfileServiceName }
    ::=  { rsIDSProfilesTable 1 }

-- obsolete
RsIDSProfilesEntry ::= SEQUENCE {
    rsIDSProfilesName DisplayString,
    rsIDSProfileServiceName DisplayString,
    rsIDSProfileCategory INTEGER,
    rsIDSProfilesStatus RowStatus,
    rsIDSProfileServiceId INTEGER,
    rsIDSProfileType INTEGER
}

-- obsolete
rsIDSProfilesName OBJECT-TYPE
    SYNTAX DisplayString (SIZE(1..29))
    ACCESS  read-only
    STATUS  mandatory
    DESCRIPTION
      "The Name for the Profile."
    ::=  {rsIDSProfilesEntry 1}

-- obsolete
rsIDSProfileServiceName OBJECT-TYPE
    SYNTAX DisplayString (SIZE(1..29))
    ACCESS  read-only
    STATUS  mandatory
    DESCRIPTION
      "The Name for the Service."
    ::=  {rsIDSProfilesEntry 2}

-- obsolete
rsIDSProfileCategory OBJECT-TYPE
    SYNTAX INTEGER {
        intrusions(2),
        dos(3),
        anomalies(4),
        anti-scanning(5)
    }
    ACCESS read-write
    STATUS mandatory
    DESCRIPTION
      "The profile category."
    ::=  { rsIDSProfilesEntry 3 }

-- obsolete
rsIDSProfilesStatus OBJECT-TYPE
    SYNTAX RowStatus
    ACCESS  read-write
    STATUS  mandatory
    DESCRIPTION
       "This variable indicates the administrative status of this entry.
        Used to delete an entry of this table."
    ::=  { rsIDSProfilesEntry 4 }

-- obsolete
rsIDSProfileServiceId OBJECT-TYPE
    SYNTAX INTEGER
    ACCESS read-write
    STATUS mandatory
    DESCRIPTION
      "The profile service ID. this field should not be visible to the user."
    ::=  { rsIDSProfilesEntry 5 }

-- obsolete
rsIDSProfileType OBJECT-TYPE
    SYNTAX INTEGER {
        user (3),
        static (4)
    }
    ACCESS read-only
    STATUS mandatory
    DESCRIPTION
      "Denotes the type of the filter policy."
    ::=  { rsIDSProfilesEntry 6 }

rsIDSNCPSTableSizeAfterReset OBJECT-TYPE
    SYNTAX INTEGER
    ACCESS read-write
    STATUS mandatory
    DESCRIPTION
      "the NCPS after-reset table size"
    ::= {rsIDS 67}

rsIDSSLTProfilesTable OBJECT-TYPE
    SYNTAX SEQUENCE OF RsIDSSLTProfilesEntry
    ACCESS not-accessible
    STATUS  mandatory
    DESCRIPTION
      "Table containing the list of SLT rules params for the ids"
    ::=  {rsIDS 68}

rsIDSSLTProfilesEntry OBJECT-TYPE
    SYNTAX RsIDSSLTProfilesEntry
    ACCESS not-accessible
    STATUS  mandatory
    DESCRIPTION
       "The row definition for this table."
    INDEX { rsIDSSLTProfilesName, rsIDSSLTProfileServiceName }
    ::=  { rsIDSSLTProfilesTable 1 }

RsIDSSLTProfilesEntry ::= SEQUENCE {
    rsIDSSLTProfilesName DisplayString,
    rsIDSSLTProfileServiceName DisplayString,
	rsIDSSLTProfileCategory INTEGER,
    rsIDSSLTProfilesStatus RowStatus,
	rsIDSSLTProfileServiceId INTEGER,
    rsIDSSLTProfileType INTEGER
}

rsIDSSLTProfilesName OBJECT-TYPE
    SYNTAX DisplayString (SIZE(1..29))
    ACCESS  read-write
    STATUS  mandatory
    DESCRIPTION
      "The Name for the Profile."
    ::=  {rsIDSSLTProfilesEntry 1}

rsIDSSLTProfileServiceName OBJECT-TYPE
    SYNTAX DisplayString (SIZE(1..29))
    ACCESS  read-write
    STATUS  mandatory
    DESCRIPTION
      "The Name for the Service."
    ::=  {rsIDSSLTProfilesEntry 2}

rsIDSSLTProfileCategory OBJECT-TYPE
    SYNTAX INTEGER {
        dos(3)
    }
    ACCESS read-write
    STATUS mandatory
    DESCRIPTION
      "The profile category."
    ::=  { rsIDSSLTProfilesEntry 3 }

rsIDSSLTProfilesStatus OBJECT-TYPE
    SYNTAX RowStatus
    ACCESS  read-write
    STATUS  mandatory
    DESCRIPTION
       "This variable indicates the administrative status of this entry.
        Used to delete an entry of this table."
    ::=  { rsIDSSLTProfilesEntry 4 }

rsIDSSLTProfileServiceId OBJECT-TYPE
    SYNTAX INTEGER
    ACCESS read-write
    STATUS mandatory
    DESCRIPTION
      "The profile service ID. this field should not be visible to the user."
    ::=  { rsIDSSLTProfilesEntry 5 }

rsIDSSLTProfileType OBJECT-TYPE
    SYNTAX INTEGER {
        user (3),
        static (4)
    }
    ACCESS read-only
    STATUS mandatory
    DESCRIPTION
      "Denotes the type of the filter policy."
    ::=  { rsIDSSLTProfilesEntry 6 }


rsIDSSLTNewRulesTable OBJECT-TYPE
    SYNTAX SEQUENCE OF RsIDSSLTNewRulesEntry
    ACCESS not-accessible
    STATUS  mandatory
    DESCRIPTION
      "Table containing the list of rules params for the ids"
    ::=  {rsIDS 69}

rsIDSSLTNewRulesEntry OBJECT-TYPE
    SYNTAX RsIDSSLTNewRulesEntry
    ACCESS not-accessible
    STATUS  mandatory
    DESCRIPTION
       "The row definition for this table."
    INDEX { rsIDSSLTNewRulesName }
    ::=  { rsIDSSLTNewRulesTable 1 }

RsIDSSLTNewRulesEntry ::= SEQUENCE {
    rsIDSSLTNewRulesName DisplayString,
    rsIDSSLTServiceName DisplayString,
    rsIDSSLTNewRulesSource DisplayString,
    rsIDSSLTNewRulesDestination DisplayString,
    rsIDSSLTNewRulesDirection INTEGER,
    rsIDSSLTNewRulesPortmask DisplayString,
    rsIDSSLTNewRulesState INTEGER,
    rsIDSSLTNewRulesStatus  RowStatus,
    rsIDSSLTNewRulesVlanTagGroup DisplayString,
    rsIDSSLTNewRulesAction INTEGER
}

rsIDSSLTNewRulesName OBJECT-TYPE
    SYNTAX DisplayString (SIZE(1..19))
    ACCESS  read-write
    STATUS  mandatory
    DESCRIPTION
      "The Name for the Rule."
    ::=  {rsIDSSLTNewRulesEntry 1}

rsIDSSLTServiceName OBJECT-TYPE
    SYNTAX DisplayString (SIZE(1..29))
    ACCESS  read-write
    STATUS  mandatory
    DESCRIPTION
      "The Name for the Service."
    ::=  {rsIDSSLTNewRulesEntry 2}

rsIDSSLTNewRulesSource OBJECT-TYPE
    SYNTAX DisplayString (SIZE(0..20))
    ACCESS  read-write
    STATUS  mandatory
    DESCRIPTION
      "The source address / range of address for the packet, the name is
      defined in the Objects table or can be an IP address."
    ::=  {rsIDSSLTNewRulesEntry 3}

rsIDSSLTNewRulesDestination OBJECT-TYPE
    SYNTAX DisplayString (SIZE(0..20))
    ACCESS  read-write
    STATUS  mandatory
    DESCRIPTION
      "The destination address / range of address for the packet, the name is
      defined in the Objects table or can be an IP address."
    ::=  {rsIDSSLTNewRulesEntry 4}

rsIDSSLTNewRulesDirection OBJECT-TYPE
    SYNTAX INTEGER {
              oneway(1),
              twoway(2) }
    ACCESS  read-write
    STATUS  mandatory
    DESCRIPTION
       "This variable indicates the direction of the incoming packet."
    DEFVAL { 1 }
    ::=  { rsIDSSLTNewRulesEntry 5 }


rsIDSSLTNewRulesPortmask OBJECT-TYPE
    SYNTAX DisplayString (SIZE(0..80))
    ACCESS  read-write
    STATUS  mandatory
    DESCRIPTION
       "The Port Group"
    ::=  { rsIDSSLTNewRulesEntry 6 }

 rsIDSSLTNewRulesState OBJECT-TYPE
    SYNTAX INTEGER {
              active(1),
              inactive(2) }
    ACCESS  read-write
    STATUS  mandatory
    DESCRIPTION
       "This variable indicates the state of the rule."
    DEFVAL { 1 }
    ::=  { rsIDSSLTNewRulesEntry 7 }

rsIDSSLTNewRulesStatus OBJECT-TYPE
    SYNTAX RowStatus
    ACCESS  read-write
    STATUS  mandatory
    DESCRIPTION
       "This variable indicates the administrative status of this entry.
        Used to delete an entry of this table."
    ::=  { rsIDSSLTNewRulesEntry 8 }

rsIDSSLTNewRulesVlanTagGroup OBJECT-TYPE
    SYNTAX DisplayString (SIZE(0..80))
    ACCESS  read-write
    STATUS  mandatory
    DESCRIPTION
       "The VLAN tag Group"
    ::=  { rsIDSSLTNewRulesEntry 9 }

rsIDSSLTNewRulesAction OBJECT-TYPE
    SYNTAX INTEGER {
        report(0),
        block(1) }
    ACCESS  read-write
    STATUS  mandatory
    DESCRIPTION
       "This variable indicates the policy action"
    ::=  { rsIDSSLTNewRulesEntry 10 }


rsIDSReportTerminalStatus OBJECT-TYPE
 SYNTAX INTEGER {
      enable(1),
      disable(2)
   }
    ACCESS read-write
    STATUS mandatory
    DESCRIPTION
      "configures the terminal echo on security event"
   DEFVAL  {enable}
    ::= {rsIDS 70}

rsIDSReportSysLogStatus OBJECT-TYPE
 SYNTAX INTEGER {
      enable(1),
      disable(2)
   }
    ACCESS read-write
    STATUS mandatory
    DESCRIPTION
      "configures syslog sending status on security event"
   DEFVAL  {enable}
    ::= {rsIDS 71}

rsIDSPacketReportLimit OBJECT-TYPE
    SYNTAX INTEGER
    ACCESS read-write
    STATUS mandatory
    DESCRIPTION
      "the maximum number of reported packets per-report interval"
	DEFVAL  { 100 }
    ::= {rsIDS 72}

rsIDSPacketReportAttackLimit OBJECT-TYPE
    SYNTAX INTEGER
    ACCESS read-write
    STATUS mandatory
    DESCRIPTION
      "the maximum number of reported packets per-attack per-report interval"
	DEFVAL  { 10 }
    ::= {rsIDS 73}

rsIDSReportAggregationTrheshold OBJECT-TYPE
    SYNTAX INTEGER
    ACCESS read-write
    STATUS mandatory
    DESCRIPTION
      "the maximum number of reported packets per-report interval"
	DEFVAL  { 10 }
    ::= {rsIDS 74}

rsIDSFilterEntryTable OBJECT-TYPE
    SYNTAX SEQUENCE OF RsIDSFilterEntry
    ACCESS not-accessible
    STATUS  mandatory
    DESCRIPTION
      "Table containing the filters."
    ::= { rsIDS 75 }

rsIDSFilterEntry OBJECT-TYPE
    SYNTAX RsIDSFilterEntry
    ACCESS not-accessible
    STATUS mandatory
    DESCRIPTION
       "The row definition for this table."
    INDEX { rsIDSFilterName }
    ::=  { rsIDSFilterEntryTable 1 }

RsIDSFilterEntry ::= SEQUENCE {
    rsIDSFilterName DisplayString,
    rsIDSFilterProtocol INTEGER,
    rsIDSFilterOMPCOffset INTEGER,
    rsIDSFilterOMPCMask OCTET STRING,
    rsIDSFilterOMPCPattern OCTET STRING,
    rsIDSFilterOMPCCondition INTEGER,
    rsIDSFilterOMPCLength INTEGER,
    rsIDSFilterContentOffset INTEGER,
    rsIDSFilterContent DisplayString,
    rsIDSFilterContentType INTEGER,
    rsIDSFilterType INTEGER,
    rsIDSFilterStatus RowStatus,
    rsIDSFilterContentEnd INTEGER,
    rsIDSFilterContentData DisplayString,
    rsIDSFilterContentCoding INTEGER,
    rsIDSFilterContentDataCoding INTEGER,
    rsIDSFilterOMPCOffsetBase INTEGER,
    rsIDSFilterSourceAppPortGroup DisplayString,
    rsIDSFilterDestinationAppPortGroup DisplayString,
    rsIDSFilterDistanceRange DisplayString,
    rsIDSFilterRegExpContent INTEGER,
    rsIDSFilterRegExpContentData INTEGER,
	rsIDSFilterPacketSizeType INTEGER,
	rsIDSFilterPacketSizeRange DisplayString
}

rsIDSFilterName OBJECT-TYPE
    SYNTAX DisplayString (SIZE(1..29))
    ACCESS read-only
    STATUS mandatory
    DESCRIPTION
      "The name of the filter object."
    ::=  { rsIDSFilterEntry 1 }

rsIDSFilterProtocol OBJECT-TYPE
    SYNTAX INTEGER {
        ip (1),
        tcp (2),
        udp (3),
        icmp (4),
        nonIp (5),
	icmpv6 (6)
    }
    ACCESS read-write
    STATUS mandatory
    DESCRIPTION
      "The protocol for the filter."
--  DEFVAL  ( 1 )
    ::=  { rsIDSFilterEntry 2 }

rsIDSFilterOMPCOffset OBJECT-TYPE
    SYNTAX INTEGER
    ACCESS read-write
    STATUS mandatory
    DESCRIPTION
      "The offset of the OMPC data."
    ::=  { rsIDSFilterEntry 3 }

rsIDSFilterOMPCMask OBJECT-TYPE
    SYNTAX OCTET STRING (SIZE(4))
    ACCESS read-write
    STATUS mandatory
    DESCRIPTION
      "The mask for the OMPC object."
    ::=  { rsIDSFilterEntry 4 }

rsIDSFilterOMPCPattern OBJECT-TYPE
    SYNTAX OCTET STRING (SIZE(4))
    ACCESS read-write
    STATUS mandatory
    DESCRIPTION
      "The pattern for the OMPC data."
    ::=  { rsIDSFilterEntry 5 }

rsIDSFilterOMPCCondition OBJECT-TYPE
    SYNTAX INTEGER {
        notApplicable (1),
        equal (2),
        notEqual (3),
        greaterThan (4),
        lessThan (5)
    }
    ACCESS read-write
    STATUS mandatory
    DESCRIPTION
      "The condition for the OMPC data check."
    ::=  { rsIDSFilterEntry 6 }

rsIDSFilterOMPCLength OBJECT-TYPE
    SYNTAX INTEGER {
        oneByte (1),
        twoBytes (2),
        threeBytes (3),
        fourBytes (4),
        notApplicable (5)
    }
    ACCESS read-write
    STATUS mandatory
    DESCRIPTION
      "The length of the OMPC."
    ::=  { rsIDSFilterEntry 7 }

rsIDSFilterContentOffset OBJECT-TYPE
    SYNTAX INTEGER
    ACCESS read-write
    STATUS mandatory
    DESCRIPTION
      "The offset for the content."
    ::=  { rsIDSFilterEntry 8 }

rsIDSFilterContent OBJECT-TYPE
    SYNTAX DisplayString (SIZE(0..255))
    ACCESS read-write
    STATUS mandatory
    DESCRIPTION
      "The content to be checked."
    ::=  { rsIDSFilterEntry 9 }

rsIDSFilterContentType OBJECT-TYPE
    SYNTAX INTEGER {
        notApplicable (1),
--        url (2),
        text(3)
--        hostname(4),
--        headertype(5),
--      expression(6),
--        maildomain(7),
--        mailto(8),
--        mailfrom(9),
--        mailsubject(10),
--        filetype(11),
--        cookiedata(12),
--	norm-url(13),
--        pop3user(14),
--	urilength(15),
--	ftpcommand(16),
--	ftpcontent(17),
--	rpc(18),
--	dcerpc(19),
--	http-reply-data(26),
--	http-reply-header(27),
--	mm7-request(29),
--	mm7-file-attachment(30)
    }
    ACCESS read-write
    STATUS mandatory
    DESCRIPTION
      "The type of content. In the case of URL only the url is checked. (No
      offset is used). In the case of text then the entire packet is checked.
      (will make use of the offset)."
    ::=  { rsIDSFilterEntry 10 }

rsIDSFilterType OBJECT-TYPE
    SYNTAX INTEGER {
        user (3),
        static (4)
    }
    ACCESS read-write
    STATUS mandatory
    DESCRIPTION
      "The type of object. This can be regular (user defined), static (defined
      by the application), ids (defined by the user for ids) or idsStatic
      (defined by the application for the ids)."
    ::=  { rsIDSFilterEntry 11 }

rsIDSFilterStatus OBJECT-TYPE
    SYNTAX RowStatus
    ACCESS read-write
    STATUS mandatory
    DESCRIPTION
      "The status of the object."
    ::=  { rsIDSFilterEntry 12 }

rsIDSFilterContentEnd OBJECT-TYPE
    SYNTAX INTEGER
    ACCESS read-write
    STATUS mandatory
    DESCRIPTION
      "End of search data."
    ::=  { rsIDSFilterEntry 13 }


rsIDSFilterContentData OBJECT-TYPE
    SYNTAX DisplayString (SIZE(0..255))
    ACCESS read-write
    STATUS mandatory
    DESCRIPTION
      "The content data to be checked."
    ::=  { rsIDSFilterEntry 14 }

rsIDSFilterContentCoding OBJECT-TYPE
    SYNTAX INTEGER {
        notApplicable (1),
        caseInsensitive (2),
        caseSensitive (3),
        hex (4)
--        international(5)
    }
    ACCESS read-write
    STATUS mandatory
    DESCRIPTION
      "The type of content coding that is used."
    ::=  { rsIDSFilterEntry 15 }

rsIDSFilterContentDataCoding OBJECT-TYPE
    SYNTAX INTEGER {
        notApplicable (1),
        caseInsensitive (2),
        caseSensitive (3),
        hex (4),
        international(5)
    }
    ACCESS read-write
    STATUS mandatory
    DESCRIPTION
      "The type of content coding that is used."
    ::=  { rsIDSFilterEntry 16 }

rsIDSFilterOMPCOffsetBase OBJECT-TYPE
    SYNTAX INTEGER {
	    none (0),
        ipHeader (1),
        ipData (2),
        tcpData (3),
        ethernet (5),
        l4Header (6),
	ipv6Header (7)
    }
    ACCESS read-write
    STATUS mandatory
    DESCRIPTION
      "The base of filter OMPC offset."
    ::=  { rsIDSFilterEntry 17 }

rsIDSFilterSourceAppPortGroup OBJECT-TYPE
    SYNTAX DisplayString (SIZE(0..30))
    ACCESS read-write
    STATUS mandatory
    DESCRIPTION
      "Source port group name."
    ::=  { rsIDSFilterEntry 18 }

rsIDSFilterDestinationAppPortGroup OBJECT-TYPE
    SYNTAX DisplayString (SIZE(0..30))
    ACCESS read-write
    STATUS mandatory
    DESCRIPTION
      "Destination port group name."
    ::=  { rsIDSFilterEntry 19 }

rsIDSFilterDistanceRange OBJECT-TYPE
    SYNTAX DisplayString (SIZE(0..30))
    ACCESS read-write
    STATUS mandatory
    DESCRIPTION
      "Distance."
    ::=  { rsIDSFilterEntry 20 }

rsIDSFilterRegExpContent OBJECT-TYPE
    SYNTAX INTEGER {
        yes (1),
        no (2)
    }
    ACCESS read-write
    STATUS mandatory
    DESCRIPTION
      "Flag that shows whether content is a regular expression"
    DEFVAL { 2 }
    ::=  { rsIDSFilterEntry 21 }

rsIDSFilterRegExpContentData OBJECT-TYPE
    SYNTAX INTEGER {
        yes (1),
        no (2)
    }
    ACCESS read-write
    STATUS mandatory
    DESCRIPTION
      "Flag that shows whether content data is a regular expression"
    DEFVAL { 2 }
    ::=  { rsIDSFilterEntry 22 }

rsIDSFilterPacketSizeType OBJECT-TYPE
    SYNTAX INTEGER {
--	   	l2 (0),
--        l3 (1),
--        l4 (2),
        l7 (3),
        none (255)
    }
    ACCESS read-write
    STATUS mandatory
    DESCRIPTION
      "The packet size type."
    DEFVAL { 255 }
    ::=  { rsIDSFilterEntry 23 }

rsIDSFilterPacketSizeRange OBJECT-TYPE
    SYNTAX DisplayString (SIZE(0..30))
    ACCESS read-write
    STATUS mandatory
    DESCRIPTION
      "Packet Size Range."
    ::=  { rsIDSFilterEntry 24 }

rsIDSAdvancedFilterTable OBJECT-TYPE
    SYNTAX SEQUENCE OF RsIDSAdvancedFilterEntry
    ACCESS not-accessible
    STATUS  mandatory
    DESCRIPTION
      "Table containing groups of filters."
    ::= { rsIDS 76 }

rsIDSAdvancedFilterEntry OBJECT-TYPE
    SYNTAX RsIDSAdvancedFilterEntry
    ACCESS not-accessible
    STATUS mandatory
    DESCRIPTION
       "The row definition for this table."
    INDEX { rsIDSAdvancedFilterEntryName, rsIDSAdvancedFilterEntryBasicName }
    ::=  { rsIDSAdvancedFilterTable 1 }

RsIDSAdvancedFilterEntry ::= SEQUENCE {
    rsIDSAdvancedFilterEntryName DisplayString,
    rsIDSAdvancedFilterEntryBasicName DisplayString,
    rsIDSAdvancedFilterEntryType INTEGER,
    rsIDSAdvancedFilterEntryStatus RowStatus
}

rsIDSAdvancedFilterEntryName OBJECT-TYPE
    SYNTAX DisplayString(SIZE(1..29))
    ACCESS read-only
    STATUS mandatory
    DESCRIPTION
      "The name of the group entry."
    ::=  { rsIDSAdvancedFilterEntry 1 }

rsIDSAdvancedFilterEntryBasicName OBJECT-TYPE
    SYNTAX DisplayString(SIZE(1..29))
    ACCESS read-only
    STATUS mandatory
    DESCRIPTION
      "The name of the filter entry in the group."
    ::=  { rsIDSAdvancedFilterEntry 2 }

rsIDSAdvancedFilterEntryType OBJECT-TYPE
    SYNTAX INTEGER {
        user (3),
        static (4)
    }
    ACCESS read-only
    STATUS mandatory
    DESCRIPTION
      "The type of object. This can be regular (user defined), static (defined
      by the application), ids (defined by the user for ids) or idsStatic
      (defined by the application for the ids)."
    ::=  { rsIDSAdvancedFilterEntry 3 }

rsIDSAdvancedFilterEntryStatus OBJECT-TYPE
    SYNTAX RowStatus
    ACCESS read-write
    STATUS mandatory
    DESCRIPTION
      "The status of the object."
    ::=  { rsIDSAdvancedFilterEntry 4 }



rsIDSGroupTable OBJECT-TYPE
    SYNTAX SEQUENCE OF RsIDSGroupEntry
    ACCESS not-accessible
    STATUS  mandatory
    DESCRIPTION
      "Table containing the set of filters and group filters - used by
      rule."
    ::= { rsIDS 77 }

rsIDSGroupEntry OBJECT-TYPE
    SYNTAX RsIDSGroupEntry
    ACCESS not-accessible
    STATUS mandatory
    DESCRIPTION
       "The row definition for this table."
    INDEX { rsIDSGroupName, rsIDSGroupEntryID }
    ::=  { rsIDSGroupTable 1 }

RsIDSGroupEntry ::= SEQUENCE {
    rsIDSGroupName DisplayString,
    rsIDSGroupEntryID INTEGER,
    rsIDSGroupEntryName DisplayString,
	rsIDSGroupID INTEGER,
    rsIDSGroupType INTEGER,
    rsIDSGroupStatus RowStatus
}

rsIDSGroupName OBJECT-TYPE
    SYNTAX DisplayString(SIZE(1..29))
    ACCESS read-only
    STATUS mandatory
    DESCRIPTION
      "The name of the filter policy."
    ::=  { rsIDSGroupEntry 1 }

rsIDSGroupEntryID OBJECT-TYPE
    SYNTAX INTEGER
    ACCESS read-only
    STATUS mandatory
    DESCRIPTION
       "This variable indicates Attack entry id  "
    ::=  { rsIDSGroupEntry 2}

rsIDSGroupEntryName OBJECT-TYPE
    SYNTAX DisplayString(SIZE(1..29))
    ACCESS read-write
    STATUS mandatory
    DESCRIPTION
      "The name of the filter entry. This can either be a group or a
      filter. The device will resolve the type - i.e. filter or group."
    ::=  { rsIDSGroupEntry 3 }


rsIDSGroupID OBJECT-TYPE
    SYNTAX INTEGER
    ACCESS read-write
    STATUS mandatory
    DESCRIPTION
       "This variable indicates Group id  "
    ::=  { rsIDSGroupEntry 4}

rsIDSGroupType OBJECT-TYPE
    SYNTAX INTEGER {
        user (3),
        static (4)
    }
    ACCESS read-only
    STATUS mandatory
    DESCRIPTION
      "Denotes the type of the filter polciy."
    ::=  { rsIDSGroupEntry 5 }

rsIDSGroupStatus OBJECT-TYPE
    SYNTAX RowStatus
    ACCESS read-write
    STATUS mandatory
    DESCRIPTION
      "The status of the object."
    ::=  { rsIDSGroupEntry 6 }


 rsIDSAsAttackTable OBJECT-TYPE
    SYNTAX SEQUENCE OF RsIDSAsAttackEntry
    ACCESS not-accessible
    STATUS  mandatory
    DESCRIPTION
      "Table containing the parameters that are needed to detect intrusions"
    ::=  {rsIDS 78}


rsIDSAsAttackEntry OBJECT-TYPE
    SYNTAX RsIDSAsAttackEntry
    ACCESS not-accessible
    STATUS  mandatory
    DESCRIPTION
       "The row definition for this table."
    INDEX { rsIDSAsAttackId }
    ::=  { rsIDSAsAttackTable 1 }

RsIDSAsAttackEntry ::= SEQUENCE {
	rsIDSAsAttackId INTEGER,
	rsIDSAsAttackName DisplayString,
	rsIDSAsAttackServiceName DisplayString,
	rsIDSAsAttackServiceType INTEGER,
	rsIDSAsAttackTrackingTime INTEGER,
	rsIDSAsAttackThreshold INTEGER,
	rsIDSAsAttackTrackingType INTEGER,
	rsIDSAsAttackMsg DisplayString,
	rsIDSAsAttackStatus RowStatus,
	rsIDSAsAttackReportMode INTEGER,
	rsIDSAsAttackSourceType INTEGER,
	rsIDSAsAttackPacketReport INTEGER,
    rsIDSAsAttackRisk INTEGER,
	rsIDSAsAttackState INTEGER,
    rsIDSAsAttackDirection INTEGER,
	rsIDSAsAttackSuspendAction INTEGER,
	rsIDSAsAttackDropThreshold INTEGER,
	rsIDSAsAttackTermThreshold INTEGER,
	rsIDSAsAttackExcludeSrcAddr DisplayString,
	rsIDSAsAttackExcludeDestAddr DisplayString,
	rsIDSAsAttackPacketTrace INTEGER,
	rsIDSAsAttackQuarantine INTEGER,
	rsIDSAsAttackAppType INTEGER
}

rsIDSAsAttackId OBJECT-TYPE
    SYNTAX INTEGER
    ACCESS  read-only
    STATUS  mandatory
    DESCRIPTION
       "This variable indicates the object type- whether it is a filter or group  "
    ::=  { rsIDSAsAttackEntry 1}

rsIDSAsAttackName OBJECT-TYPE
    SYNTAX DisplayString (SIZE(1..29))
    ACCESS  read-write
    STATUS  mandatory
    DESCRIPTION
      "The Name for the attack must be unique."
    ::=  {rsIDSAsAttackEntry 2}

rsIDSAsAttackServiceName OBJECT-TYPE
    SYNTAX DisplayString (SIZE(1..29))
    ACCESS  read-write
    STATUS  mandatory
    DESCRIPTION
      "The Name for the filter must be unique."
    ::=  {rsIDSAsAttackEntry 3}

rsIDSAsAttackServiceType OBJECT-TYPE
    SYNTAX INTEGER {
              filter(1),
              advanced-filter(2) }
    ACCESS  read-write
    STATUS  mandatory
    DESCRIPTION
       "This variable indicates the object type- whether it is a filter or group  "
    ::=  { rsIDSAsAttackEntry 4}

rsIDSAsAttackTrackingTime OBJECT-TYPE
    SYNTAX INTEGER
    ACCESS  read-write
    STATUS  mandatory
    DESCRIPTION
       "This variable indicates the time interval, in miliseconds,
        to track a detection"
    DEFVAL  { 1000 }
    ::=  { rsIDSAsAttackEntry 5 }

rsIDSAsAttackThreshold OBJECT-TYPE
    SYNTAX INTEGER
    ACCESS  read-write
    STATUS  mandatory
    DESCRIPTION
       "This variable indicates the threshold "
    DEFVAL  { 50 }
    ::=  { rsIDSAsAttackEntry 6 }


rsIDSAsAttackTrackingType OBJECT-TYPE
    SYNTAX INTEGER {
    drop(0),
--    reset(1),
      ncps(2),
      ncpd(3),
      ncpsd(4),
--    ncpf(5),
--    winnuke(6),
--    landattack(7),
--    synattackack(8),
--    winny(9),
--    tcpack(10),
--    tcpsynack(11),
--    tcprst(12),
--    tcpfin(13),
--    tcpelse(14),
--    fragments(15),
--    ncpsdscan(16),
--    dhcp(17),
--	ftpbounce(18),
--	bobo2k(19),
	sampling(20)
--	ftpbounce6(21)
    }
    ACCESS  read-write
    STATUS  mandatory
    DESCRIPTION
       "This variable indicates how to count  "
    ::=  { rsIDSAsAttackEntry 7}

rsIDSAsAttackMsg OBJECT-TYPE
    SYNTAX DisplayString (SIZE(0..30))
    ACCESS  read-only
    STATUS  mandatory
    DESCRIPTION
      "The Name for the filter must be unique."
    ::=  {rsIDSAsAttackEntry 8}

rsIDSAsAttackStatus OBJECT-TYPE
    SYNTAX RowStatus
    ACCESS  read-write
    STATUS  mandatory
    DESCRIPTION
       "This variable indicates the administrative status of this entry.
        Used to delete an entry of this table."
    ::=  { rsIDSAsAttackEntry 9 }


rsIDSAsAttackReportMode OBJECT-TYPE
    SYNTAX INTEGER {
	    report-only(0),
	    drop(10),
--	    rst-src(11),
     	    rst-dst(12),
--    	    rst-bi(13),
--	    rst-mm7(15),
		http200ok(18),
		http200ok-rst-dst(19),
		http403(20),
		http403-rst-dst(21)
    }
    ACCESS  read-write
    STATUS  mandatory
    DESCRIPTION
       "This variable indicates the attack report mode"
    ::=  { rsIDSAsAttackEntry 10}

rsIDSAsAttackSourceType OBJECT-TYPE
    SYNTAX INTEGER {
        user (3),
        static (4)
    }
    ACCESS read-only
    STATUS mandatory
    DESCRIPTION
      "Denotes the type of the filter polciy."
    ::=  { rsIDSAsAttackEntry 11 }

rsIDSAsAttackPacketReport OBJECT-TYPE
    SYNTAX INTEGER {
			enable(1),
			disable(2)}
    ACCESS  read-write
    STATUS  mandatory
    DESCRIPTION
       "This variable indicates the per-attack packet report"
	DEFVAL  {disable}
    ::=  {rsIDSAsAttackEntry 12}

rsIDSAsAttackRisk OBJECT-TYPE
    SYNTAX INTEGER {
		  info(1),
		  low(2),
       	  medium(3),
		  high(4)}
    ACCESS  read-write
    STATUS  mandatory
    DESCRIPTION
       "This variable indicates the risk of the attack"
	DEFVAL  {low}
    ::=  {rsIDSAsAttackEntry 13}

rsIDSAsAttackState OBJECT-TYPE
    SYNTAX INTEGER {
			enable(1),
			disable(2)}
    ACCESS  read-write
    STATUS  mandatory
    DESCRIPTION
       "This variable indicates whether the attack should be classified or not "
    DEFVAL  { enable }
    ::=  { rsIDSAsAttackEntry 14 }

rsIDSAsAttackDirection OBJECT-TYPE
    SYNTAX INTEGER {
		  inoutbound(0),
       	  inbound(1),
		  outbound(2)}
    ACCESS  read-write
    STATUS  mandatory
    DESCRIPTION
       "This variable indicates the direction of the attack"
	DEFVAL  {inoutbound}
    ::=  {rsIDSAsAttackEntry 15}

rsIDSAsAttackSuspendAction OBJECT-TYPE
    SYNTAX INTEGER {
		  none(0),
       	  sip(1),
		  sipdip(2),
		  sipdprt(3),
		  sipdipdprt(4),
		  sipdipsprtdprt(5)
		  }
    ACCESS  read-write
    STATUS  mandatory
    DESCRIPTION
       "This variable indicates the suspend action type of the attack"
	DEFVAL  {none}
    ::=  {rsIDSAsAttackEntry 16}

rsIDSAsAttackDropThreshold OBJECT-TYPE
    SYNTAX INTEGER
    ACCESS  read-write
    STATUS  mandatory
    DESCRIPTION
       "This variable indicates the drop threshold "
    DEFVAL  { 50 }
    ::=  { rsIDSAsAttackEntry 17 }

rsIDSAsAttackTermThreshold OBJECT-TYPE
    SYNTAX INTEGER
    ACCESS  read-write
    STATUS  mandatory
    DESCRIPTION
       "This variable indicates the term threshold "
    DEFVAL  { 50 }
    ::=  { rsIDSAsAttackEntry 18 }


rsIDSAsAttackExcludeSrcAddr OBJECT-TYPE
    SYNTAX DisplayString (SIZE(0..46))
    ACCESS  read-write
    STATUS  mandatory
    DESCRIPTION
      "The exclude src addr."
    ::=  {rsIDSAsAttackEntry 19}


rsIDSAsAttackExcludeDestAddr OBJECT-TYPE
    SYNTAX DisplayString (SIZE(0..46))
    ACCESS  read-write
    STATUS  mandatory
    DESCRIPTION
      "The exclude dest addr."
    ::=  {rsIDSAsAttackEntry 20}
rsIDSAsAttackPacketTrace OBJECT-TYPE
    SYNTAX INTEGER {
			enable(1),
			disable(2)}
    ACCESS  read-write
    STATUS  mandatory
    DESCRIPTION
       "This variable indicates the per-attack packet trace"
	DEFVAL  {disable}
    ::=  {rsIDSAsAttackEntry 21}

rsIDSAsAttackQuarantine OBJECT-TYPE
    SYNTAX INTEGER {
			enable(1),
			disable(2)}
    ACCESS  read-write
    STATUS  mandatory
    DESCRIPTION
       "This variable indicates if quarantine is relevant for the attack"
	DEFVAL  {disable}
    ::=  {rsIDSAsAttackEntry 22}

rsIDSAsAttackAppType OBJECT-TYPE
    SYNTAX INTEGER {
			appsec(1),
			doss(2)}
    ACCESS  read-write
    STATUS  mandatory
    DESCRIPTION
       "This variable indicates the application type of the attack"
	DEFVAL  {appsec}
    ::=  {rsIDSAsAttackEntry 23}

rsIDSDosAttackTable OBJECT-TYPE
    SYNTAX SEQUENCE OF RsIDSDosAttackEntry
    ACCESS not-accessible
    STATUS  mandatory
    DESCRIPTION
      "Table containing the parameters that are needed to detect intrusions"
    ::=  {rsIDS 79}

rsIDSDosAttackEntry OBJECT-TYPE
    SYNTAX RsIDSDosAttackEntry
    ACCESS not-accessible
    STATUS  mandatory
    DESCRIPTION
       "The row definition for this table."
    INDEX { rsIDSDosAttackId }
    ::=  { rsIDSDosAttackTable 1 }

RsIDSDosAttackEntry ::= SEQUENCE {
	rsIDSDosAttackId INTEGER,
	rsIDSDosAttackName DisplayString,
	rsIDSDosAttackServiceName DisplayString,
	rsIDSDosAttackServiceType INTEGER,
	rsIDSDosAttackAlertThreshold INTEGER,
	rsIDSDosAttackActiveThreshold INTEGER,
	rsIDSDosAttackDropThreshold INTEGER,
	rsIDSDosAttackTermAlertThreshold INTEGER,
	rsIDSDosAttackTermThreshold INTEGER,
	rsIDSDosAttackAgingPeriod INTEGER,
	rsIDSDosAttackMsg DisplayString,
	rsIDSDosAttackPacketReport INTEGER,
	rsIDSDosAttackStatus RowStatus,
	rsIDSDosAttackReportMode INTEGER,
	rsIDSDosAttackSourceType INTEGER,
    rsIDSDosAttackRisk INTEGER
}

rsIDSDosAttackId OBJECT-TYPE
    SYNTAX INTEGER
    ACCESS  read-write
    STATUS  mandatory
    DESCRIPTION
       "This variable indicates the object type- whether it is a filter or group  "
    ::=  { rsIDSDosAttackEntry 1}

rsIDSDosAttackName OBJECT-TYPE
    SYNTAX DisplayString (SIZE(1..29))
    ACCESS  read-write
    STATUS  mandatory
    DESCRIPTION
      "The Name for the attack must be unique."
    ::=  {rsIDSDosAttackEntry 2}

rsIDSDosAttackServiceName OBJECT-TYPE
    SYNTAX DisplayString (SIZE(1..29))
    ACCESS  read-write
    STATUS  mandatory
    DESCRIPTION
      "The Name for the filter must be unique."
    ::=  {rsIDSDosAttackEntry 3}

rsIDSDosAttackServiceType OBJECT-TYPE
    SYNTAX INTEGER {
              filter(1),
              advanced-filter(2) }
    ACCESS  read-write
    STATUS  mandatory
    DESCRIPTION
       "This variable indicates the object type- whether it is a filter or group  "
    ::=  { rsIDSDosAttackEntry 4}

rsIDSDosAttackAlertThreshold OBJECT-TYPE
    SYNTAX INTEGER
    ACCESS  read-write
    STATUS  mandatory
    DESCRIPTION
       "This variable indicates the attack alerting threshold "
    DEFVAL  { 30 }
    ::=  { rsIDSDosAttackEntry 5 }

rsIDSDosAttackActiveThreshold OBJECT-TYPE
    SYNTAX INTEGER
    ACCESS  read-write
    STATUS  mandatory
    DESCRIPTION
       "This variable indicates the activating threshold "
    DEFVAL  { 50 }
    ::=  { rsIDSDosAttackEntry 6 }

rsIDSDosAttackDropThreshold OBJECT-TYPE
    SYNTAX INTEGER
    ACCESS  read-write
    STATUS  mandatory
    DESCRIPTION
       "This variable indicates the dropping threshold "
    DEFVAL  { 50 }
    ::=  { rsIDSDosAttackEntry 7 }

rsIDSDosAttackTermAlertThreshold OBJECT-TYPE
    SYNTAX INTEGER
    ACCESS  read-write
    STATUS  mandatory
    DESCRIPTION
       "This variable indicates the termination alert threshold "
    DEFVAL  { 50 }
    ::=  { rsIDSDosAttackEntry 8 }

rsIDSDosAttackTermThreshold OBJECT-TYPE
    SYNTAX INTEGER
    ACCESS  read-write
    STATUS  mandatory
    DESCRIPTION
       "This variable indicates the termination threshold "
    DEFVAL  { 30 }
    ::=  { rsIDSDosAttackEntry 9 }

rsIDSDosAttackAgingPeriod OBJECT-TYPE
    SYNTAX INTEGER
    ACCESS  read-write
    STATUS  mandatory
    DESCRIPTION
       "This variable indicates the the number of periods before an attack is
       removed "
    DEFVAL  { 5 }
    ::=  { rsIDSDosAttackEntry 10 }

rsIDSDosAttackMsg OBJECT-TYPE
    SYNTAX DisplayString (SIZE(0..30))
    ACCESS  read-write
    STATUS  mandatory
    DESCRIPTION
      "The Name for the filter must be unique."
    ::=  {rsIDSDosAttackEntry 11 }

rsIDSDosAttackPacketReport OBJECT-TYPE
    SYNTAX INTEGER {
			enable(1),
			disable(2)}
    ACCESS  read-write
    STATUS  mandatory
    DESCRIPTION
       "This variable indicates the per-attack packet report"
	DEFVAL  {disable}
    ::=  { rsIDSDosAttackEntry 12 }


rsIDSDosAttackStatus OBJECT-TYPE
    SYNTAX RowStatus
    ACCESS  read-write
    STATUS  mandatory
    DESCRIPTION
       "This variable indicates the administrative status of this entry.
        Used to delete an entry of this table."
    ::=  { rsIDSDosAttackEntry 13 }


rsIDSDosAttackReportMode OBJECT-TYPE
    SYNTAX INTEGER {
	    report-only(0),
	    drop(10)}
    ACCESS  read-write
    STATUS  mandatory
    DESCRIPTION
       "This variable indicates the attack report mode"
    ::=  { rsIDSDosAttackEntry 14 }

rsIDSDosAttackSourceType OBJECT-TYPE
    SYNTAX INTEGER {
        user (3),
        static (4)
    }
    ACCESS read-only
    STATUS mandatory
    DESCRIPTION
      "Denotes the type of the filter polciy."
    ::=  { rsIDSDosAttackEntry 15 }

rsIDSDosAttackRisk OBJECT-TYPE
    SYNTAX INTEGER {
		  low(2),
       	  medium(3),
		  high(4)}
    ACCESS  read-write
    STATUS  mandatory
    DESCRIPTION
       "This variable indicates the risk of the attack"
	DEFVAL  {medium}
    ::=  {rsIDSDosAttackEntry 16}


rsIDSServiceTable OBJECT-TYPE
    SYNTAX SEQUENCE OF RsIDSServiceEntry
    ACCESS not-accessible
    STATUS  mandatory
    DESCRIPTION
      "Table containing the available services."
    ::=  {rsIDS 80}

rsIDSServiceEntry OBJECT-TYPE
    SYNTAX RsIDSServiceEntry
    ACCESS not-accessible
    STATUS  mandatory
    DESCRIPTION
       "The row definition for this table."
    INDEX {rsIDSServiceTableType, rsIDSServiceType, rsIDSServiceID}
    ::=  {rsIDSServiceTable 1}

RsIDSServiceEntry ::= SEQUENCE {
    rsIDSServiceTableType INTEGER,
    rsIDSServiceType INTEGER,
    rsIDSServiceID INTEGER,
    rsIDSServiceEntName DisplayString
}

rsIDSServiceTableType OBJECT-TYPE
    SYNTAX INTEGER {
        filter		(1),
        advanced	(2),
        group		(3),
		dos-attack	(4),
		as-attack	(5)
    }
    ACCESS  read-only
    STATUS  mandatory
    DESCRIPTION
      "The specific table to access."
    ::=  {rsIDSServiceEntry 1}

rsIDSServiceType OBJECT-TYPE
    SYNTAX INTEGER {
        user (3),
        static (4),
        all	(65536)
    }
    ACCESS read-only
    STATUS  mandatory
    DESCRIPTION
       "The type of entry."
    ::=  {rsIDSServiceEntry 2}

rsIDSServiceID OBJECT-TYPE
    SYNTAX INTEGER
    ACCESS read-only
    STATUS mandatory
    DESCRIPTION
      "Attack ID."
    ::=  {rsIDSServiceEntry 3}

rsIDSServiceEntName OBJECT-TYPE
    SYNTAX DisplayString (SIZE(0..30))
    ACCESS read-only
    STATUS mandatory
    DESCRIPTION
      "The filter or advanced or group or attack name (of type rsIDSServiceType)."
    ::=  {rsIDSServiceEntry 4}


rsIDSASAttackNextID OBJECT-TYPE
	SYNTAX INTEGER
    ACCESS read-only
    STATUS mandatory
    DESCRIPTION
		"the next attack id for appsec attack"
    ::= {rsIDS 81}

rsIDSDOSAttackNextID OBJECT-TYPE
	SYNTAX INTEGER
    ACCESS read-only
    STATUS mandatory
    DESCRIPTION
		"the next attack id for dos attack"
    ::= {rsIDS 82}

rsIDSEncoding OBJECT-TYPE
    SYNTAX INTEGER {
	none (0),
	e1250 (1),
	e1251 (2),
	e1252 (3),
	e1253 (4),
	e1254 (5),
	e1255 (6),
	e1256 (7),
	e1257 (8),
	e1258 (9),
	e20127 (10),
	e20261 (11),
	e20866 (12),
	e28591 (13),
	e28592 (14),
	e28605 (15),
	e37 (16),
	e437 (17),
	e500 (18),
	e850 (19),
	e860 (20),
	e861 (21),
	e863 (22),
	e865 (23),
	e874 (24),
	e932 (25),
	e936 (26),
	e949 (27),
	e950 (28)
    }
    ACCESS read-write
    STATUS mandatory
    DESCRIPTION
		"encoding of application server for unicode normalization"
    ::= {rsIDS 83}

rsIDSReportTrapsRisk OBJECT-TYPE
 SYNTAX INTEGER {
 		  info(1),
		  low(2),
       	  medium(3),
		  high(4)
   }
    ACCESS read-write
    STATUS mandatory
    DESCRIPTION
      "configures the minimal risk level for email sending on security event"
   DEFVAL  {low}
    ::= {rsIDS 84}

rsIDSReportEmailRisk OBJECT-TYPE
 SYNTAX INTEGER {
 		  info(1),
		  low(2),
       	  medium(3),
		  high(4)
   }
    ACCESS read-write
    STATUS mandatory
    DESCRIPTION
      "configures the minimal risk level for email sending on security event"
   DEFVAL  {low}
    ::= {rsIDS 85}

rsIDSReportTerminalRisk OBJECT-TYPE
 SYNTAX INTEGER {
 		  info(1),
		  low(2),
       	  medium(3),
		  high(4)
   }
    ACCESS read-write
    STATUS mandatory
    DESCRIPTION
      "configures the minimal risk level for terminal echo on security event"
   DEFVAL  {low}
    ::= {rsIDS 86}

rsIDSReportSysLogRisk OBJECT-TYPE
 SYNTAX INTEGER {
 		  info(1),
		  low(2),
       	  medium(3),
		  high(4)
   }
    ACCESS read-write
    STATUS mandatory
    DESCRIPTION
      "configures the minimal risk level for syslog on security event"
   DEFVAL  {low}
    ::= {rsIDS 87}

rsIDSIpFragments   OBJECT IDENTIFIER ::= { rsIDS 88 }

rsIDSIpFragMinFragmentStatus OBJECT-TYPE
	SYNTAX INTEGER {
			enable(1),
			disable(2)}
    ACCESS read-write
    STATUS mandatory
    DESCRIPTION
		"minimum fragment status"
	DEFVAL { disable }
    ::= { rsIDSIpFragments 1 }

rsIDSIpFragMinFragmentMode OBJECT-TYPE
   SYNTAX INTEGER {
        report-only(0),
	    drop(10)}
    ACCESS read-write
    STATUS mandatory
    DESCRIPTION
		"minimum fragment mode"
	DEFVAL { report-only }
    ::= { rsIDSIpFragments 2 }

rsIDSIpFragReassemblyAgingTimeFreq OBJECT-TYPE
	SYNTAX INTEGER (1..60)
    ACCESS read-write
    STATUS mandatory
    DESCRIPTION
		"reassembly aging timeout"
	DEFVAL { 3 }
    ::= { rsIDSIpFragments 3 }


rsIDSIpFragReassemblyStatus OBJECT-TYPE
	SYNTAX INTEGER {
			enable(1),
			disable(2)}
    ACCESS read-write
    STATUS mandatory
    DESCRIPTION
		"Reassembly status"
	DEFVAL { disable }
    ::= { rsIDSIpFragments 4 }

rsIDSIpFragReassemblyMode OBJECT-TYPE
   SYNTAX INTEGER {
			drop(10),
			forward(0)}
    ACCESS read-write
    STATUS mandatory
    DESCRIPTION
		"Reassembly mode"
	DEFVAL { forward }
    ::= { rsIDSIpFragments 5 }

rsIDSIpFragReassemblyOverlapStatus OBJECT-TYPE
   SYNTAX INTEGER {
			allow(1),
			deny(2)}
    ACCESS read-write
    STATUS mandatory
    DESCRIPTION
		"Reassembly Overlap Status"
	DEFVAL { allow }
    ::= { rsIDSIpFragments 6 }


 rsIDSIpFragReassemblyOverlapMode OBJECT-TYPE
   SYNTAX INTEGER {
		 report-only(0),
	     drop(10)}
    ACCESS read-write
    STATUS mandatory
    DESCRIPTION
		"Reassembly Overlap mode"
	DEFVAL { report-only }
    ::= { rsIDSIpFragments 7 }



rsIDSIpFragmentsTuning OBJECT IDENTIFIER ::= { rsIDS 89}

rsIDSIpFragReassemblyMemorySize OBJECT-TYPE
    SYNTAX INTEGER
    ACCESS  read-only
    STATUS  mandatory
    DESCRIPTION
      "Maximal memory amount used by IP fragmentation support, in MB."
    ::=  { rsIDSIpFragmentsTuning 1 }

rsIDSIpFragReassemblyMemorySizeAfterReset OBJECT-TYPE
    SYNTAX INTEGER
    ACCESS  read-write
    STATUS  mandatory
    DESCRIPTION
      "Future maximal memory amount used by IP fragmentation support,
       in MB."
    ::=  { rsIDSIpFragmentsTuning 2 }


rsIDSTcpReassemblyStatus OBJECT-TYPE
 SYNTAX INTEGER {
      enable(1),
      disable(2)
   }
    ACCESS read-write
    STATUS mandatory
    DESCRIPTION
      "the Application Security Tcp reassembly mechanism status"
   DEFVAL  {disable}
    ::= {rsIDS 90}


rsIDSNonTuneableMemory OBJECT IDENTIFIER ::= { rsIDS 91}

rsIDSNonTunableMemorySize OBJECT-TYPE
    SYNTAX INTEGER
    ACCESS  not-accessible
    STATUS  mandatory
    DESCRIPTION
      ""
    ::=  { rsIDSNonTuneableMemory 1 }

rsIDSNonTunableMemorySizeAfterReset OBJECT-TYPE
    SYNTAX INTEGER
    ACCESS  not-accessible
    STATUS  mandatory
    DESCRIPTION
      ""
    ::=  { rsIDSNonTuneableMemory 2 }


rsIDSUserAttacksDBEntriesTuning OBJECT IDENTIFIER ::= { rsIDS 92}

rsIDSUserAttacksDBEntries OBJECT-TYPE
    SYNTAX INTEGER
    ACCESS read-only
    STATUS mandatory
    DESCRIPTION
      "Tuning parameter for the user defined attacks data-base"
    ::= {rsIDSUserAttacksDBEntriesTuning 1}

rsIDSUserAttacksDBEntriesAfterReset OBJECT-TYPE
    SYNTAX INTEGER
    ACCESS read-write
    STATUS mandatory
    DESCRIPTION
      "Tuning parameter for the user defined attacks data-base after the next reset"
    ::= {rsIDSUserAttacksDBEntriesTuning 2}



rsIDSUserGroupsNumberTuning OBJECT IDENTIFIER ::= { rsIDS 93}

rsIDSUserGroupsNumber OBJECT-TYPE
    SYNTAX INTEGER
    ACCESS read-only
    STATUS mandatory
    DESCRIPTION
      "Tuning parameter for the user groups data-base"
    ::= {rsIDSUserGroupsNumberTuning 1}

rsIDSUserGroupsNumberAfterReset OBJECT-TYPE
    SYNTAX INTEGER
    ACCESS read-write
    STATUS mandatory
    DESCRIPTION
      "Tuning parameter for the user groups data-base after the next reset"
    ::= {rsIDSUserGroupsNumberTuning 2}


rsIDSNCPNFTableSizeTuning OBJECT IDENTIFIER ::= { rsIDS 94}

rsIDSNCPNFTableSize OBJECT-TYPE
    SYNTAX INTEGER
    ACCESS read-only
    STATUS mandatory
    DESCRIPTION
      "Tuning parameter for the NCPNF table size"
    ::= {rsIDSNCPNFTableSizeTuning 1}

rsIDSNCPNFTableSizeAfterReset OBJECT-TYPE
    SYNTAX INTEGER
    ACCESS read-write
    STATUS mandatory
    DESCRIPTION
      "Tuning parameter for the NCPNF table size after the next reset"
    ::= {rsIDSNCPNFTableSizeTuning 2}

rsIDSDropSession OBJECT-TYPE
 SYNTAX INTEGER {
      enable(1),
      disable(2)
   }
    ACCESS read-write
    STATUS mandatory
    DESCRIPTION
      "the Application Security drop-session mechanism status"
   DEFVAL  {enable}
    ::= {rsIDS 95}

rsIDSNetforensics OBJECT IDENTIFIER ::= { rsIDS 96}

rsIDSNetforensicsAgentAddress OBJECT-TYPE
    SYNTAX IpAddress
    ACCESS  read-write
    STATUS  mandatory
    DESCRIPTION
        "The IP Address of the netforensics agent."
    ::= {rsIDSNetforensics 1}

rsIDSNetforensicsAgentPort OBJECT-TYPE
    SYNTAX INTEGER (1..65535)
    ACCESS  read-write
    STATUS  mandatory
    DESCRIPTION
        "The listening port of the netforensics agent."
    ::= {rsIDSNetforensics 2}

rsIDSNetforensicsAgentStatus OBJECT-TYPE
    SYNTAX INTEGER {
      enable(1),
      disable(2)
   }
    ACCESS  read-write
    STATUS  mandatory
    DESCRIPTION
        "netforensics agent reporting status."
    ::= {rsIDSNetforensics 3}

rsIDSSourceTableParams OBJECT IDENTIFIER ::= { rsIDS 97}

rsIDSSourceTableSize OBJECT-TYPE
    SYNTAX INTEGER
    ACCESS read-only
    STATUS mandatory
    DESCRIPTION
      "Tuning parameter for the source table size"
    ::= {rsIDSSourceTableParams 1}

rsIDSSourceTableSizeAfterReset OBJECT-TYPE
    SYNTAX INTEGER
    ACCESS read-write
    STATUS mandatory
    DESCRIPTION
      "Tuning parameter for the source table size after the next reset"
    ::= {rsIDSSourceTableParams 2}


rsIDSSuspendTableParams OBJECT IDENTIFIER ::= { rsIDS 98}

rsIDSSuspendTableMaxSrcIps OBJECT-TYPE
    SYNTAX INTEGER
    ACCESS read-only
    STATUS mandatory
    DESCRIPTION
      "Tuning parameter for the SuspendTable maximal number of SRC-IPs"
    ::= {rsIDSSuspendTableParams 1}

rsIDSSuspendTableMaxSrcIpsAfterReset OBJECT-TYPE
    SYNTAX INTEGER
    ACCESS read-write
    STATUS mandatory
    DESCRIPTION
      "Tuning parameter for the SuspendTable maximal number of SRC-IPs after the next reset"
    ::= {rsIDSSuspendTableParams 2}

rsIDSSuspendTableMinAgingTimeout OBJECT-TYPE
    SYNTAX INTEGER
    ACCESS read-write
    STATUS mandatory
    DESCRIPTION
      "Dynamic blocking min timeout"
    ::= { rsIDSSuspendTableParams 3}

rsIDSSuspendTableMaxAgingTimeout OBJECT-TYPE
    SYNTAX INTEGER
    ACCESS read-write
    STATUS mandatory
    DESCRIPTION
      "Dynamic blocking max timeout"
    ::= {rsIDSSuspendTableParams 4}

rsIDSSuspendTableEntriesPerSrcIP OBJECT-TYPE
    SYNTAX INTEGER
    ACCESS read-write
    STATUS mandatory
    DESCRIPTION
      "Dynamic blocking max same source entries"
    ::= {rsIDSSuspendTableParams 5}

rsIDSSuspendTableNumberOfEntries OBJECT-TYPE
    SYNTAX INTEGER
    ACCESS read-write
    STATUS mandatory
    DESCRIPTION
      "Number of entries"
    ::= {rsIDSSuspendTableParams 6}

rsIDSMinRisk OBJECT-TYPE
    SYNTAX INTEGER {
 	  info(1),
	  low(2),
      medium(3),
	  high(4)}
    ACCESS read-write
    STATUS mandatory
    DESCRIPTION
      "Minimum risk of as attacks to be classified"
    DEFVAL  { low }
    ::=  { rsIDS 99 }


rsIDSScanning OBJECT IDENTIFIER ::= { rsIDS 100 }

rsIDSScanningMechanismStatus OBJECT-TYPE
 SYNTAX INTEGER {
      enable(1),
      disable(2)
   }
    ACCESS read-write
    STATUS mandatory
    DESCRIPTION
      "Scanning Module trigger"
   DEFVAL  {enable}
    ::= {rsIDSScanning 1}

rsIDSScanningProfilesTable OBJECT-TYPE
    SYNTAX SEQUENCE OF RsIDSScanningProfilesEntry
    ACCESS not-accessible
    STATUS  mandatory
    DESCRIPTION
      "Table containing the list of scanning profiles"
    ::=  {rsIDSScanning 2}

rsIDSScanningProfilesEntry OBJECT-TYPE
    SYNTAX RsIDSScanningProfilesEntry
    ACCESS not-accessible
    STATUS  mandatory
    DESCRIPTION
       "The row definition for this table."
    INDEX { rsIDSScanningProfilesName }
    ::=  { rsIDSScanningProfilesTable 1 }

RsIDSScanningProfilesEntry ::= SEQUENCE {
    rsIDSScanningProfilesName DisplayString,
    rsIDSScanningProfilesTCPState INTEGER,
    rsIDSScanningProfilesUDPState INTEGER,
    rsIDSScanningProfilesICMPState INTEGER,
    rsIDSScanningProfilesStatus RowStatus,
    rsIDSScanningProfilesType RowStatus,
    rsIDSScanningProfilesSensitivity INTEGER,
    rsIDSScanningProfilesAccuracyLevel RowStatus,
    rsIDSScanningProfilesSinglePort INTEGER,
    rsIDSScanningProfilesPacketTraceStatus INTEGER,
    rsIDSScanningProfilesHighPortsResp INTEGER,
    rsIDSScanningProfilesAction INTEGER,
    rsIDSScanningProfilesFootprintStrictness INTEGER,
    rsIDSScanningProfilesLowToHighBypass INTEGER
}

rsIDSScanningProfilesName OBJECT-TYPE
    SYNTAX DisplayString (SIZE(1..29))
    ACCESS  read-only
    STATUS  mandatory
    DESCRIPTION
      "The Name for the Profile."
    ::=  {rsIDSScanningProfilesEntry 1}

rsIDSScanningProfilesTCPState OBJECT-TYPE
    SYNTAX INTEGER {
        active(1),
        inactive(2)
    }
    ACCESS read-write
    STATUS mandatory
    DESCRIPTION
      "Scanning profile TCP state."
    DEFVAL {1}
    ::=  { rsIDSScanningProfilesEntry 2 }

rsIDSScanningProfilesUDPState OBJECT-TYPE
    SYNTAX INTEGER {
        active(1),
        inactive(2)
    }
    ACCESS read-write
    STATUS mandatory
    DESCRIPTION
      "Scanning profile UDP state."
    DEFVAL {2}
    ::=  { rsIDSScanningProfilesEntry 3 }

rsIDSScanningProfilesICMPState OBJECT-TYPE
    SYNTAX INTEGER {
        active(1),
        inactive(2)
    }
    ACCESS read-write
    STATUS mandatory
    DESCRIPTION
      "Scanning profile ICMP state."
    DEFVAL {2}
    ::=  { rsIDSScanningProfilesEntry 4 }

rsIDSScanningProfilesStatus OBJECT-TYPE
    SYNTAX RowStatus
    ACCESS  read-write
    STATUS  mandatory
    DESCRIPTION
       "This variable indicates the administrative status of this entry.
        Used to delete an entry of this table."
    ::=  { rsIDSScanningProfilesEntry 5 }

-- obsolete
rsIDSScanningProfilesType OBJECT-TYPE
    SYNTAX RowStatus
    ACCESS read-only
    STATUS deprecated
    DESCRIPTION
      "Scanning profile type."
    DEFVAL {3}
    ::=  { rsIDSScanningProfilesEntry 6 }

rsIDSScanningProfilesSensitivity OBJECT-TYPE
    SYNTAX INTEGER {
      low(1),
      medium(2),
      high(3),
      veryhigh(4)
    }
    ACCESS read-write
    STATUS mandatory
    DESCRIPTION
      "Scanning profile sensitivity."
    DEFVAL {2}
    ::=  { rsIDSScanningProfilesEntry 7 }

rsIDSScanningProfilesAccuracyLevel OBJECT-TYPE
    SYNTAX RowStatus
    ACCESS read-write
    STATUS mandatory
    DESCRIPTION
      "Scanning profile accuracy level."
    DEFVAL {2}
    ::=  { rsIDSScanningProfilesEntry 8 }

rsIDSScanningProfilesSinglePort OBJECT-TYPE
    SYNTAX INTEGER {
        enable(1),
        disable(2)
    }
    ACCESS read-write
    STATUS mandatory
    DESCRIPTION
      "Scanning profile single probed port test."
    DEFVAL {2}
    ::=  { rsIDSScanningProfilesEntry 9 }

rsIDSScanningProfilesPacketTraceStatus OBJECT-TYPE
 SYNTAX INTEGER {
      enable(1),
      disable(2)
   }
    ACCESS read-write
    STATUS mandatory
    DESCRIPTION
      "Scanning profile packet report status"
   DEFVAL  {disable}
    ::= {rsIDSScanningProfilesEntry 10}

rsIDSScanningProfilesHighPortsResp OBJECT-TYPE
 SYNTAX INTEGER {
      enable(1),
      disable(2)
   }
    ACCESS read-write
    STATUS mandatory
    DESCRIPTION
      "Scanning profile high port response"
   DEFVAL  {disable}
    ::= {rsIDSScanningProfilesEntry 11}

rsIDSScanningProfilesAction OBJECT-TYPE
    SYNTAX INTEGER {
        report(0),
        block(1)
    }
    ACCESS  read-write
    STATUS  mandatory
    DESCRIPTION
       "Scanning profile action"
    DEFVAL  {block}
    ::=  { rsIDSScanningProfilesEntry 12 }

rsIDSScanningProfilesFootprintStrictness OBJECT-TYPE
 SYNTAX INTEGER {
      enable(1),
      disable(2)
   }
    ACCESS read-write
    STATUS mandatory
    DESCRIPTION
      "Scanning profile footprint strictness"
   DEFVAL  {disable}
    ::= {rsIDSScanningProfilesEntry 13}


rsIDSScanningProfilesLowToHighBypass OBJECT-TYPE
 SYNTAX INTEGER {
   any(1),
   disable(2),
   tcp(3),
   udp(4)
  }

    ACCESS read-write
    STATUS mandatory
    DESCRIPTION
      "Bypass connections originating from System Ports to Non-System Ports"
   DEFVAL  {any}
    ::= {rsIDSScanningProfilesEntry 14}



-- obsolete
rsIDSScanningPolicyTable OBJECT-TYPE
    SYNTAX SEQUENCE OF RsIDSScanningPolicyEntry
    ACCESS not-accessible
    STATUS  mandatory
    DESCRIPTION
      "Table containing the list of scanning policies"
    ::=  {rsIDSScanning 3}

rsIDSScanningPolicyEntry OBJECT-TYPE
    SYNTAX RsIDSScanningPolicyEntry
    ACCESS not-accessible
    STATUS  mandatory
    DESCRIPTION
       "The row definition for this table."
    INDEX { rsIDSScanningPolicyName }
    ::=  { rsIDSScanningPolicyTable 1 }

RsIDSScanningPolicyEntry ::= SEQUENCE {
    rsIDSScanningPolicyName DisplayString,
    rsIDSScanningPolicyServiceName DisplayString,
    rsIDSScanningPolicyInternal DisplayString,
    rsIDSScanningPolicyExternal DisplayString,
    rsIDSScanningPolicyPortmask DisplayString,
    rsIDSScanningPolicyState INTEGER,
    rsIDSScanningPolicyStatus  RowStatus,
    rsIDSScanningPolicyVlanTagGroup DisplayString,
    rsIDSScanningPolicyAction INTEGER,
    rsIDSScanningPolicyDirection INTEGER
}

rsIDSScanningPolicyName OBJECT-TYPE
    SYNTAX DisplayString (SIZE(1..19))
    ACCESS  read-only
    STATUS  mandatory
    DESCRIPTION
      "The Name for the Rule."
    ::=  {rsIDSScanningPolicyEntry 1}

rsIDSScanningPolicyServiceName OBJECT-TYPE
    SYNTAX DisplayString (SIZE(1..29))
    ACCESS  read-write
    STATUS  mandatory
    DESCRIPTION
      "The Name for the Service."
    ::=  {rsIDSScanningPolicyEntry 2}

rsIDSScanningPolicyInternal OBJECT-TYPE
    SYNTAX DisplayString (SIZE(0..20))
    ACCESS  read-write
    STATUS  mandatory
    DESCRIPTION
      "The source address / range of address for the packet, the name is
      defined in the Objects table or can be an IP address."
    ::=  {rsIDSScanningPolicyEntry 3}

rsIDSScanningPolicyExternal OBJECT-TYPE
    SYNTAX DisplayString (SIZE(0..20))
    ACCESS  read-write
    STATUS  mandatory
    DESCRIPTION
      "The destination address / range of address for the packet, the name is
      defined in the Objects table or can be an IP address."
    ::=  {rsIDSScanningPolicyEntry 4}

rsIDSScanningPolicyPortmask OBJECT-TYPE
    SYNTAX DisplayString (SIZE(0..80))
    ACCESS  read-write
    STATUS  mandatory
    DESCRIPTION
       "The Port Group"
    ::=  { rsIDSScanningPolicyEntry 5 }

 rsIDSScanningPolicyState OBJECT-TYPE
    SYNTAX INTEGER {
              active(1),
              inactive(2) }
    ACCESS  read-write
    STATUS  mandatory
    DESCRIPTION
       "This variable indicates the state of the rule."
    DEFVAL { 1 }
    ::=  { rsIDSScanningPolicyEntry 6 }

rsIDSScanningPolicyStatus OBJECT-TYPE
    SYNTAX RowStatus
    ACCESS  read-write
    STATUS  mandatory
    DESCRIPTION
       "This variable indicates the administrative status of this entry.
        Used to delete an entry of this table."
    ::=  { rsIDSScanningPolicyEntry 7 }

rsIDSScanningPolicyVlanTagGroup OBJECT-TYPE
    SYNTAX DisplayString (SIZE(0..80))
    ACCESS  read-write
    STATUS  mandatory
    DESCRIPTION
       "The VLAN tag Group"
    ::=  { rsIDSScanningPolicyEntry 8 }

rsIDSScanningPolicyAction OBJECT-TYPE
    SYNTAX INTEGER {
        report(0),
        block(1) }
    ACCESS  read-write
    STATUS  mandatory
    DESCRIPTION
       "This variable indicates the policy action"
    ::=  { rsIDSScanningPolicyEntry 9 }

rsIDSScanningPolicyDirection OBJECT-TYPE
    SYNTAX INTEGER {
              oneway(1),
              twoway(2) }
    ACCESS  read-write
    STATUS  mandatory
    DESCRIPTION
       "This variable indicates the direction of the incoming packet."
    DEFVAL { 1 }
    ::=  { rsIDSScanningPolicyEntry 10 }

-- obsolete
rsIDSScanningSensitivity OBJECT-TYPE
 SYNTAX INTEGER {
      low(1),
      medium(2),
      high(3)
   }
    ACCESS read-write
    STATUS mandatory
    DESCRIPTION
      "Scanning Module sensitivity level"
   DEFVAL  {medium}
    ::= {rsIDSScanning 4}

-- obsolete
rsIDSScanningSlowScans OBJECT-TYPE
 SYNTAX INTEGER {
      enable(1),
      disable(2)
   }
    ACCESS read-only
    STATUS deprecated
    DESCRIPTION
      "Scanning Module slow scans flag"
   DEFVAL  {disable}
    ::= {rsIDSScanning 5}


rsIDSScanningMaxIPPairs OBJECT-TYPE
    SYNTAX INTEGER
    ACCESS read-only
    STATUS mandatory
    DESCRIPTION
      "Tuning parameter for the Scanning maximal number of containers for IP pairs"
    ::= {rsIDSScanning 6}

rsIDSScanningMaxIPPairsAfterReset OBJECT-TYPE
    SYNTAX INTEGER
    ACCESS read-write
    STATUS mandatory
    DESCRIPTION
      "Tuning parameter for the Scanning maximal number of containers for IP pairs after the next reset"
    ::= {rsIDSScanning 7}

rsIDSScanningFirewall OBJECT-TYPE
 SYNTAX INTEGER {
      enable(1),
      disable(2)
   }
    ACCESS read-write
    STATUS mandatory
    DESCRIPTION
      "Scanning Module firewall flag"
   DEFVAL  {enable}
    ::= {rsIDSScanning 8}

rsIDSScanningHighPortResp OBJECT-TYPE
 SYNTAX INTEGER {
      enable(1),
      disable(2)
   }
    ACCESS read-write
    STATUS mandatory
    DESCRIPTION
      "Scanning Module high port response"
   DEFVAL  {enable}
    ::= {rsIDSScanning 9}

rsIDSScanningMaxBlockingTime OBJECT-TYPE
 SYNTAX INTEGER (20..3600)
    ACCESS read-write
    STATUS mandatory
    DESCRIPTION
      "Scanning Module maximal blocking duration"
   DEFVAL  {80}
    ::= {rsIDSScanning 10}

rsIDSScanningTrustedPortsTable OBJECT-TYPE
    SYNTAX SEQUENCE OF RsIDSScanningTrustedPorts
    ACCESS not-accessible
    STATUS  mandatory
    DESCRIPTION
      "Table containing the trusted ports for scanning profiles"
    ::=  {rsIDSScanning 11}

rsIDSScanningTrustedPorts OBJECT-TYPE
    SYNTAX RsIDSScanningTrustedPorts
    ACCESS not-accessible
    STATUS  mandatory
    DESCRIPTION
       "The row definition for this table."
    INDEX { rsIDSScanningTrustedPortsProfileName, rsIDSScanningTrustedPortsPort }
    ::=  { rsIDSScanningTrustedPortsTable 1 }

RsIDSScanningTrustedPorts ::= SEQUENCE {
    rsIDSScanningTrustedPortsProfileName DisplayString,
    rsIDSScanningTrustedPortsPort INTEGER,
    rsIDSScanningTrustedPortsStatus  RowStatus,
    rsIDSScanningTrustedPortsDirection INTEGER,
    rsIDSScanningTrustedPortsProtocol INTEGER
}

rsIDSScanningTrustedPortsProfileName OBJECT-TYPE
    SYNTAX DisplayString (SIZE(1..29))
    ACCESS  read-only
    STATUS  mandatory
    DESCRIPTION
      "Profile To be bypassed in the Scanning module"
    ::=  {rsIDSScanningTrustedPorts 1}

rsIDSScanningTrustedPortsPort OBJECT-TYPE
    SYNTAX INTEGER (1..65535)
    ACCESS  read-only
    STATUS  mandatory
    DESCRIPTION
      "Port To be bypassed for the scanning profile"
    ::=  {rsIDSScanningTrustedPorts 2}

rsIDSScanningTrustedPortsStatus OBJECT-TYPE
    SYNTAX RowStatus
    ACCESS  read-write
    STATUS  mandatory
    DESCRIPTION
       "This variable indicates the administrative status of this entry.
        Used to delete an entry of this table."
    ::=  { rsIDSScanningTrustedPorts 3 }

rsIDSScanningTrustedPortsDirection OBJECT-TYPE
    SYNTAX INTEGER {
     destination(1),
     source(2),
     any(3)
	}
    ACCESS  read-write
    STATUS  mandatory
    DESCRIPTION
      "L4 port type - Source or Destination"
	DEFVAL{3}
    ::=  {rsIDSScanningTrustedPorts 4}

rsIDSScanningTrustedPortsProtocol OBJECT-TYPE
    SYNTAX INTEGER {
			tcp(1),
			udp(2),
			any(3)}
    ACCESS read-write
    STATUS mandatory
    DESCRIPTION
      "L4 protocol"
    DEFVAL{3}
    ::=  { rsIDSScanningTrustedPorts 5 }



rsIDSScanningTrustedSourceIPsTable OBJECT-TYPE
    SYNTAX SEQUENCE OF RsIDSScanningTrustedSourceIPs
    ACCESS not-accessible
    STATUS  mandatory
    DESCRIPTION
      "Table containing the trusted Source IPs for scanning profiles"
    ::=  {rsIDSScanning 12}

rsIDSScanningTrustedSourceIPs OBJECT-TYPE
    SYNTAX RsIDSScanningTrustedSourceIPs
    ACCESS not-accessible
    STATUS  mandatory
    DESCRIPTION
       "The row definition for this table."
    INDEX { rsIDSScanningTrustedSourceIPsProfileName, rsIDSScanningTrustedSourceIPsIP }
    ::=  { rsIDSScanningTrustedSourceIPsTable 1 }

RsIDSScanningTrustedSourceIPs ::= SEQUENCE {
    rsIDSScanningTrustedSourceIPsProfileName DisplayString,
    rsIDSScanningTrustedSourceIPsIP Ipv6Address,
    rsIDSScanningTrustedSourceIPsStatus  RowStatus
}

rsIDSScanningTrustedSourceIPsProfileName OBJECT-TYPE
    SYNTAX DisplayString (SIZE(1..29))
    ACCESS  read-only
    STATUS  mandatory
    DESCRIPTION
      "Profile To be bypassed in the Scanning module"
    ::=  {rsIDSScanningTrustedSourceIPs 1}

rsIDSScanningTrustedSourceIPsIP OBJECT-TYPE
    SYNTAX Ipv6Address
    ACCESS  read-only
    STATUS  mandatory
    DESCRIPTION
      "Source IP To be bypassed for the scanning profile"
    ::=  {rsIDSScanningTrustedSourceIPs 2}

rsIDSScanningTrustedSourceIPsStatus OBJECT-TYPE
    SYNTAX RowStatus
    ACCESS  read-write
    STATUS  mandatory
    DESCRIPTION
       "This variable indicates the administrative status of this entry.
        Used to delete an entry of this table."
    ::=  { rsIDSScanningTrustedSourceIPs 3 }


--
-- Nework Floods
--


rsNetFlood OBJECT IDENTIFIER ::= { rsIDS 101 }

-- obsolete
rsNetFloodPolicyTable OBJECT-TYPE
    SYNTAX SEQUENCE OF RsNetFloodPolicyEntry
    ACCESS not-accessible
    STATUS  mandatory
    DESCRIPTION
      "Table containing the list of policies params for the NetFlood inspection"
    ::=  {rsNetFlood 1}

rsNetFloodPolicyEntry OBJECT-TYPE
    SYNTAX RsNetFloodPolicyEntry
    ACCESS not-accessible
    STATUS  mandatory
    DESCRIPTION
       "The row definition for this table."
    INDEX { rsNetFloodPolicyName }
    ::=  { rsNetFloodPolicyTable 1 }

RsNetFloodPolicyEntry ::= SEQUENCE {
    rsNetFloodPolicyName DisplayString,
    rsNetFloodPolicyProfileName DisplayString,
    rsNetFloodPolicySourceNet DisplayString,
    rsNetFloodPolicyDestinationNet DisplayString,
    rsNetFloodPolicyDirection INTEGER,
    rsNetFloodPolicyPhysicalPortGroup DisplayString,
    rsNetFloodPolicyOperationalStatus INTEGER,
    rsNetFloodPolicyStatus  RowStatus,
	rsNetFloodPolicyVlanTagGroup DisplayString,
    rsNetFloodPolicyAction INTEGER,
    rsNetFloodPolicyPacketReportingStatus INTEGER
}

rsNetFloodPolicyName OBJECT-TYPE
    SYNTAX DisplayString (SIZE(0..20))
    ACCESS  read-only
    STATUS  mandatory
    DESCRIPTION
      "The Name for the NetFlood inspection Policy."
    ::=  {rsNetFloodPolicyEntry 1 }

rsNetFloodPolicyProfileName OBJECT-TYPE
    SYNTAX DisplayString (SIZE(0..20))
    ACCESS  read-write
    STATUS  mandatory
    DESCRIPTION
      "The Name of the NetFlood inspection Profile."
    ::=  {rsNetFloodPolicyEntry 2 }

rsNetFloodPolicySourceNet OBJECT-TYPE
    SYNTAX DisplayString (SIZE(0..20))
    ACCESS  read-write
    STATUS  mandatory
    DESCRIPTION
      "The source address / range of address for the packet, the name is
      defined in the Objects table or can be an IP address."
    ::=  {rsNetFloodPolicyEntry 3 }

rsNetFloodPolicyDestinationNet OBJECT-TYPE
    SYNTAX DisplayString (SIZE(0..20))
    ACCESS  read-write
    STATUS  mandatory
    DESCRIPTION
      "The destination address / range of address for the packet, the name is
      defined in the Objects table or can be an IP address."
    ::=  {rsNetFloodPolicyEntry 4 }

rsNetFloodPolicyDirection OBJECT-TYPE
    SYNTAX INTEGER {
              oneway(1),
              twoway(2) }
    ACCESS  read-write
    STATUS  mandatory
    DESCRIPTION
       "This variable indicates the direction of the incoming packet."
    DEFVAL { 1 }
    ::=  { rsNetFloodPolicyEntry 5 }

rsNetFloodPolicyPhysicalPortGroup OBJECT-TYPE
    SYNTAX DisplayString (SIZE(0..20))
    ACCESS  read-write
    STATUS  mandatory
    DESCRIPTION
       "The Port Group"
    ::=  { rsNetFloodPolicyEntry 6 }

 rsNetFloodPolicyOperationalStatus OBJECT-TYPE
    SYNTAX INTEGER {
              active(1),
              inactive(2) }

    ACCESS  read-write
    STATUS  mandatory
    DESCRIPTION
       "This variable indicates the operational status of the policy."
    DEFVAL { 1  }
    ::=  { rsNetFloodPolicyEntry 7 }


rsNetFloodPolicyStatus OBJECT-TYPE
    SYNTAX RowStatus
    ACCESS  read-write
    STATUS  mandatory
    DESCRIPTION
       "This variable indicates the administrative status of this entry.
        Used to delete an entry of this table."
    ::=  { rsNetFloodPolicyEntry 8 }

rsNetFloodPolicyVlanTagGroup OBJECT-TYPE
    SYNTAX DisplayString (SIZE(0..20))
    ACCESS  read-write
    STATUS  mandatory
    DESCRIPTION
       "The Port Group"
    ::=  { rsNetFloodPolicyEntry 9 }

rsNetFloodPolicyAction OBJECT-TYPE
    SYNTAX INTEGER {
        report(0),
        block(1) }
    ACCESS  read-write
    STATUS  mandatory
    DESCRIPTION
       "This variable indicates the policy action"
    ::=  { rsNetFloodPolicyEntry 10 }


rsNetFloodPolicyPacketReportingStatus OBJECT-TYPE
    SYNTAX INTEGER {
     enable(1),
     disable(2)
	}
    ACCESS  read-write
    STATUS  mandatory
    DESCRIPTION
       "This variable indicates the packet reporting status for the policy rule"
    ::=  { rsNetFloodPolicyEntry 11 }


rsNetFloodProfileTable OBJECT-TYPE
    SYNTAX SEQUENCE OF RsNetFloodProfileEntry
    ACCESS not-accessible
    STATUS  mandatory
    DESCRIPTION
      "Table containing the list of profiles params for the NetFlood inspection"
    ::=  {rsNetFlood 2}

rsNetFloodProfileEntry OBJECT-TYPE
    SYNTAX RsNetFloodProfileEntry
    ACCESS not-accessible
    STATUS  mandatory
    DESCRIPTION
       "The row definition for this table."
    INDEX { rsNetFloodProfileName }
    ::=  { rsNetFloodProfileTable 1 }

RsNetFloodProfileEntry ::= SEQUENCE {
    rsNetFloodProfileName DisplayString,
    rsNetFloodProfileTcpStatus INTEGER,
    rsNetFloodProfileTcpSynStatus INTEGER,
    rsNetFloodProfileUdpStatus INTEGER,
    rsNetFloodProfileIgmpStatus INTEGER,
    rsNetFloodProfileIcmpStatus INTEGER,
    rsNetFloodProfileStatus RowStatus,
    rsNetFloodProfileTcpFinAckStatus INTEGER,
    rsNetFloodProfileTcpRstStatus INTEGER,
    rsNetFloodProfileTcpPshAckStatus INTEGER,
    rsNetFloodProfileTcpSynAckStatus INTEGER,
    rsNetFloodProfileTcpFragStatus INTEGER,
    rsNetFloodProfileBandwidthIn INTEGER,
    rsNetFloodProfileBandwidthOut INTEGER,
    rsNetFloodProfileTcpInQuota INTEGER,
    rsNetFloodProfileUdpInQuota INTEGER,
    rsNetFloodProfileIcmpInQuota INTEGER,
    rsNetFloodProfileIgmpInQuota INTEGER,
    rsNetFloodProfileTcpOutQuota INTEGER,
    rsNetFloodProfileUdpOutQuota INTEGER,
    rsNetFloodProfileIcmpOutQuota INTEGER,
    rsNetFloodProfileIgmpOutQuota INTEGER,
    rsNetFloodProfileTransparentOptimization INTEGER,
    rsNetFloodProfileLevelOfReuglarzation INTEGER,
    rsNetFloodProfilePacketReportStatus INTEGER,
    rsNetFloodProfilePacketTraceStatus INTEGER,
    rsNetFloodProfileAction INTEGER,
    rsNetFloodProfileSimulationDuration INTEGER,
    rsNetFloodProfileSimulationStopAtAttackEnd INTEGER,
    rsNetFloodProfileSimulationStabilizationDuration INTEGER,
    rsNetFloodProfileSimulationStartWhenSigChange INTEGER,
    rsNetFloodProfileJointDistributionStatus INTEGER,
    rsNetFloodProfileUdpFragStatus INTEGER,
    rsNetFloodProfileUdpFragInQuota INTEGER,
    rsNetFloodProfileUdpFragOutQuota INTEGER,
    rsNetFloodProfileBurstEnabled INTEGER,
    rsNetFloodProfileNoBurstTimeout INTEGER,
    rsNetFloodProfileBurstAttackThreshold INTEGER,
    rsNetFloodProfileBurstAttackPeriod INTEGER,
    rsNetFloodProfileOverMitigationStatus INTEGER,
     rsNetFloodProfileOverMitigationThreshold INTEGER
}

rsNetFloodProfileName OBJECT-TYPE
    SYNTAX DisplayString (SIZE(0..19))
    ACCESS  read-only
    STATUS  mandatory
    DESCRIPTION
      "The Name for the Profile."
    ::=  {rsNetFloodProfileEntry 1}


rsNetFloodProfileTcpStatus OBJECT-TYPE
    SYNTAX INTEGER {
              active(1),
              inactive(2)}
    ACCESS  read-write
    STATUS  mandatory
    DESCRIPTION
       "This variable indicates whether to check tcp protocol in this policy."
    DEFVAL { 2 }
    ::=  { rsNetFloodProfileEntry 2 }

rsNetFloodProfileTcpSynStatus OBJECT-TYPE
    SYNTAX INTEGER {
              active(1),
              inactive(2)}
    ACCESS  read-write
    STATUS  mandatory
    DESCRIPTION
       "This variable indicates whether to check tcp protocol in this policy."
    DEFVAL { 2 }
    ::=  { rsNetFloodProfileEntry 3 }

rsNetFloodProfileUdpStatus OBJECT-TYPE
    SYNTAX INTEGER {
              active(1),
              inactive(2) }
    ACCESS  read-write
    STATUS  mandatory
    DESCRIPTION
       "This variable indicates whether to check udp protocol in this policy."
    DEFVAL { 2 }
    ::=  { rsNetFloodProfileEntry 4 }

rsNetFloodProfileIgmpStatus OBJECT-TYPE
    SYNTAX INTEGER {
              active(1),
              inactive(2) }
    ACCESS  read-write
    STATUS  mandatory
    DESCRIPTION
       "This variable indicates whether to check igmp protocol in this policy."
    DEFVAL { 2 }
    ::=  { rsNetFloodProfileEntry 5 }


rsNetFloodProfileIcmpStatus OBJECT-TYPE
    SYNTAX INTEGER {
              active(1),
              inactive(2) }
    ACCESS  read-write
    STATUS  mandatory
    DESCRIPTION
       "This variable indicates whether to check icmp protocol in this policy."
    DEFVAL { 2 }
    ::=  { rsNetFloodProfileEntry 6 }

rsNetFloodProfileStatus OBJECT-TYPE
    SYNTAX RowStatus
    ACCESS  read-write
    STATUS  mandatory
    DESCRIPTION
       "This variable indicates the administrative status of this entry.
        Used to delete an entry of this table."
    ::=  { rsNetFloodProfileEntry 7 }

rsNetFloodProfileTcpFinAckStatus OBJECT-TYPE
    SYNTAX INTEGER {
              active(1),
              inactive(2)}
    ACCESS  read-write
    STATUS  mandatory
    DESCRIPTION
       "This variable indicates whether to check tcp fin + ack in this policy."
    DEFVAL { 2 }
    ::=  { rsNetFloodProfileEntry 8 }

rsNetFloodProfileTcpRstStatus OBJECT-TYPE
    SYNTAX INTEGER {
              active(1),
              inactive(2)}
    ACCESS  read-write
    STATUS  mandatory
    DESCRIPTION
       "This variable indicates whether to check tcp reset in this policy."
    DEFVAL { 2 }
    ::=  { rsNetFloodProfileEntry 9 }

rsNetFloodProfileTcpPshAckStatus OBJECT-TYPE
    SYNTAX INTEGER {
              active(1),
              inactive(2)}
    ACCESS  read-write
    STATUS  mandatory
    DESCRIPTION
       "This variable indicates whether to check tcp push + ack in this policy."
    DEFVAL { 2 }
    ::=  { rsNetFloodProfileEntry 10 }

rsNetFloodProfileTcpSynAckStatus OBJECT-TYPE
    SYNTAX INTEGER {
              active(1),
              inactive(2)}
    ACCESS  read-write
    STATUS  mandatory
    DESCRIPTION
       "This variable indicates whether to check tcp syn + ack in this policy."
    DEFVAL { 2 }
    ::=  { rsNetFloodProfileEntry 11 }

rsNetFloodProfileTcpFragStatus OBJECT-TYPE
    SYNTAX INTEGER {
              active(1),
              inactive(2)}
    ACCESS  read-write
    STATUS  mandatory
    DESCRIPTION
       "This variable indicates whether to check tcp fragment in this policy."
    DEFVAL { 2 }
    ::=  { rsNetFloodProfileEntry 12 }

rsNetFloodProfileBandwidthIn OBJECT-TYPE
    SYNTAX INTEGER (1..1342177280)
    ACCESS  read-write
    STATUS  mandatory
    DESCRIPTION
       "network flood bandwidth inbound initial value (in Mgbit) for this policy."
    ::=  { rsNetFloodProfileEntry 13 }

rsNetFloodProfileBandwidthOut OBJECT-TYPE
    SYNTAX INTEGER (1..1342177280)
    ACCESS  read-write
    STATUS  mandatory
    DESCRIPTION
       "network flood bandwidth outbound initial value (in Mgbit) for this policy."
    ::=  { rsNetFloodProfileEntry 14 }

rsNetFloodProfileTcpInQuota OBJECT-TYPE
    SYNTAX INTEGER (0..100)
    ACCESS  read-write
    STATUS  mandatory
    DESCRIPTION
       "Tcp quota inbound value for this policy."
    ::=  { rsNetFloodProfileEntry 15 }

rsNetFloodProfileUdpInQuota OBJECT-TYPE
    SYNTAX INTEGER (0..100)
    ACCESS  read-write
    STATUS  mandatory
    DESCRIPTION
       "Udp quota inbound value for this policy."
    ::=  { rsNetFloodProfileEntry 16 }

rsNetFloodProfileIcmpInQuota OBJECT-TYPE
    SYNTAX INTEGER (0..100)
    ACCESS  read-write
    STATUS  mandatory
    DESCRIPTION
       "Icmp quota inbound value for this policy."
    ::=  { rsNetFloodProfileEntry 17 }

rsNetFloodProfileIgmpInQuota OBJECT-TYPE
    SYNTAX INTEGER (0..100)
    ACCESS  read-write
    STATUS  mandatory
    DESCRIPTION
       "Igmp quota inbound value for this policy."
    ::=  { rsNetFloodProfileEntry 18 }

rsNetFloodProfileTcpOutQuota OBJECT-TYPE
    SYNTAX INTEGER (0..100)
    ACCESS  read-write
    STATUS  mandatory
    DESCRIPTION
       "Tcp quota outbound value for this policy."
    ::=  { rsNetFloodProfileEntry 19 }

rsNetFloodProfileUdpOutQuota OBJECT-TYPE
    SYNTAX INTEGER (0..100)
    ACCESS  read-write
    STATUS  mandatory
    DESCRIPTION
       "Udp quota outbound value for this policy."
    ::=  { rsNetFloodProfileEntry 20 }

rsNetFloodProfileIcmpOutQuota OBJECT-TYPE
    SYNTAX INTEGER (0..100)
    ACCESS  read-write
    STATUS  mandatory
    DESCRIPTION
       "Icmp quota outbound value for this policy."
    ::=  { rsNetFloodProfileEntry 21 }

rsNetFloodProfileIgmpOutQuota OBJECT-TYPE
    SYNTAX INTEGER (0..100)
    ACCESS  read-write
    STATUS  mandatory
    DESCRIPTION
       "Igmp quota outbound value for this policy."
    ::=  { rsNetFloodProfileEntry 22 }

rsNetFloodProfileTransparentOptimization OBJECT-TYPE
     SYNTAX INTEGER {
        yes (1),
        no (2)
    }
    ACCESS  read-write
    STATUS  mandatory
    DESCRIPTION
       "Transparent Optimization process (Don't Blcok during closed feedback iteration)"
	DEFVAL  {no}
    ::=  { rsNetFloodProfileEntry 23 }

rsNetFloodProfileLevelOfReuglarzation OBJECT-TYPE
     SYNTAX INTEGER {
        notApplied (1),
        weak (2),
		middle (3),
		strong (4)
    }
    ACCESS  read-write
    STATUS  mandatory
    DESCRIPTION
       "Level Of Reuglarization"
	DEFVAL  {weak}
    ::=  { rsNetFloodProfileEntry 24 }

rsNetFloodProfilePacketReportStatus OBJECT-TYPE
 SYNTAX INTEGER {
      enable(1),
      disable(2)
   }
    ACCESS read-write
    STATUS mandatory
    DESCRIPTION
      "packet report status"
   DEFVAL  {enable}
    ::= {rsNetFloodProfileEntry 25}

rsNetFloodProfilePacketTraceStatus OBJECT-TYPE
 SYNTAX INTEGER {
      enable(1),
      disable(2)
   }
    ACCESS read-write
    STATUS mandatory
    DESCRIPTION
      "packet trace status"
   DEFVAL  {disable}
    ::= {rsNetFloodProfileEntry 26}

rsNetFloodProfileAction OBJECT-TYPE
    SYNTAX INTEGER {
        report(0),
        block(1),
		report-and-simulate(2),
		block-and-simulate(3)
	}
    ACCESS read-write
    STATUS mandatory
    DESCRIPTION
      "The action of this profile"
	DEFVAL {block}
    ::=  { rsNetFloodProfileEntry 27 }

rsNetFloodProfileSimulationDuration OBJECT-TYPE
    SYNTAX INTEGER (1..60)
    ACCESS read-write
    STATUS mandatory
    DESCRIPTION
      "The pre-defined duration of this simulation (minutes)"
	DEFVAL {10}
    ::=  { rsNetFloodProfileEntry 28 }

rsNetFloodProfileSimulationStopAtAttackEnd OBJECT-TYPE
    SYNTAX INTEGER {
    false(0),
	true(1)
    }
    ACCESS read-write
	STATUS mandatory
    DESCRIPTION
      "A flag indicating if the simulation will stop at the end of the attack or continue the pre-define duration"
    ::=  { rsNetFloodProfileEntry 29 }

rsNetFloodProfileSimulationStabilizationDuration OBJECT-TYPE
    SYNTAX INTEGER (5..60)
    ACCESS read-write
    STATUS mandatory
    DESCRIPTION
      "The number of seconds after the signature is stable, before starting the simulation."
	DEFVAL {10}
    ::=  { rsNetFloodProfileEntry 30 }

rsNetFloodProfileSimulationStartWhenSigChange OBJECT-TYPE
    SYNTAX INTEGER {
    false(0),
	true(1)
    }
    ACCESS read-write
    STATUS mandatory
    DESCRIPTION
      "A flag indicating if the simulation will restart if the signature changed (For BDoS only)"
    ::=  { rsNetFloodProfileEntry 31 }

rsNetFloodProfileJointDistributionStatus OBJECT-TYPE
 SYNTAX INTEGER {
      enable(1),
      disable(2)
   }
    ACCESS read-write
    STATUS mandatory
    DESCRIPTION
      "A flag indicating if the joint distribution statistics will be reported (For BDoS only)"
    ::=  { rsNetFloodProfileEntry 32 }

rsNetFloodProfileUdpFragStatus OBJECT-TYPE
    SYNTAX INTEGER {
              active(1),
              inactive(2)}
    ACCESS  read-write
    STATUS  mandatory
    DESCRIPTION
       "This variable indicates whether to check udp fragment in this policy."
    DEFVAL { 2 }
    ::=  { rsNetFloodProfileEntry 33 }

rsNetFloodProfileUdpFragInQuota OBJECT-TYPE
    SYNTAX INTEGER (0..100)
    ACCESS  read-write
    STATUS  mandatory
    DESCRIPTION
       "Inbound UDP Fragmentation Quota for this policy."
    ::=  { rsNetFloodProfileEntry 34 }

rsNetFloodProfileUdpFragOutQuota OBJECT-TYPE
    SYNTAX INTEGER (0..100)
    ACCESS  read-write
    STATUS  mandatory
    DESCRIPTION
       "Outbound UDP Fragmentation Quota for this policy."
    ::=  { rsNetFloodProfileEntry 35 }

rsNetFloodProfileBurstEnabled OBJECT-TYPE
	SYNTAX INTEGER {
      enable(1),
      disable(2)
    }
    ACCESS read-write
    STATUS mandatory
    DESCRIPTION
      "Burst attack treatment status."
   DEFVAL  {enable}
    ::= {rsNetFloodProfileEntry 36}

rsNetFloodProfileNoBurstTimeout OBJECT-TYPE
    SYNTAX INTEGER (10..10080)
    ACCESS  read-write
    STATUS  mandatory
    DESCRIPTION
       "The maximal interval, in minutes, between two consecutive traffic bursts, that is required in order to identify the attack as a burst-attack."
    ::=  { rsNetFloodProfileEntry 37 }

rsNetFloodProfileBurstAttackThreshold OBJECT-TYPE
    SYNTAX INTEGER (2..50)
    ACCESS  read-write
    STATUS  mandatory
    DESCRIPTION
       "The number of consecutive bursts that causes DefensePro to identify the attack as a burst attack."
    ::=  { rsNetFloodProfileEntry 38 }

rsNetFloodProfileBurstAttackPeriod OBJECT-TYPE
    SYNTAX INTEGER (1..336)
    ACCESS  read-write
    STATUS  mandatory
    DESCRIPTION
       "Maximal lifespan of a burst attack after which DefensePro declares an end of the burst attack."
    ::=  { rsNetFloodProfileEntry 39 }


rsNetFloodProfileOverMitigationStatus OBJECT-TYPE
    SYNTAX INTEGER {
              enable(1),
              disable(2) }
    ACCESS  read-write
    STATUS  mandatory
    DESCRIPTION
       "This variable indicates whether to check for over blocking"
    DEFVAL { 2 }
    ::=  { rsNetFloodProfileEntry 40 }

rsNetFloodProfileOverMitigationThreshold OBJECT-TYPE
     SYNTAX INTEGER (1..100)
    ACCESS  read-write
    STATUS  mandatory
    DESCRIPTION
       "This variable indicates over mitigation threshold"
    DEFVAL { 25 }
    ::=  { rsNetFloodProfileEntry 41 }

rsNetFloodMechStatus OBJECT-TYPE
 SYNTAX INTEGER {
      enable(1),
      disable(2)
   }
    ACCESS read-write
    STATUS mandatory
    DESCRIPTION
      "the Network Flood mudule activation"
   DEFVAL  {enable}
    ::= {rsNetFlood 3}

-- obsolete
rsNetFloodBandwidthIn OBJECT-TYPE
 SYNTAX INTEGER (0..2147483647)
    ACCESS read-only
    STATUS deprecated
    DESCRIPTION
      "network flood bandwidth inbound initial value (in Mgbit)"
    ::= {rsNetFlood 4}


-- obsolete
rsNetFloodBandwidthOut OBJECT-TYPE
 SYNTAX INTEGER (0..2147483647)
    ACCESS read-only
    STATUS deprecated
    DESCRIPTION
      "network flood bandwidth outbound initial value (in Mgbit)"
    ::= {rsNetFlood 5}


rsNetFloodLearningPeriod OBJECT-TYPE
 SYNTAX INTEGER {
    day(1),
    week(2),
    month(3)}
   ACCESS  read-write
   STATUS  mandatory
   DESCRIPTION
       "network flood learning response time "
    ::=  { rsNetFlood 9}

rsNetFloodResetAllLearning OBJECT-TYPE
 SYNTAX INTEGER
   ACCESS  read-write
   STATUS  mandatory
   DESCRIPTION
       "reset learning baseline"
    ::=  { rsNetFlood 10}

rsNetFloodResetPolicyLearning OBJECT-TYPE
   SYNTAX DisplayString(SIZE(0..64))
   ACCESS  read-write
   STATUS  mandatory
   DESCRIPTION
       "reset learning baseline for specific policy"
    ::=  { rsNetFlood 11}

rsNetFloodQuotaTable OBJECT-TYPE
    SYNTAX SEQUENCE OF RsNetFloodQuotaEntry
    ACCESS not-accessible
    STATUS  mandatory
    DESCRIPTION
      "Table containing the list of profiles params for the NetFlood inspection"
    ::=  {rsNetFlood 12}

rsNetFloodLearningSuppressionThreshold OBJECT-TYPE
 SYNTAX INTEGER (0..50)
    ACCESS read-write
    STATUS mandatory
    DESCRIPTION
      "configures the threshold percentage of traffic that cause learning BDoS baselines"
    ::= {rsNetFlood 39}

rsNetFloodUdpFragCtrlStrictLevel OBJECT-TYPE
   SYNTAX INTEGER {
      global(1),
      low(2),
      medium(3),
      high(4)
   }
   ACCESS  read-write
   STATUS  mandatory
   DESCRIPTION
       "Fragmented UDP Controller strictness level"
    ::=  {rsNetFlood 40}

rsNetFloodQuotaEntry OBJECT-TYPE
    SYNTAX RsNetFloodQuotaEntry
    ACCESS not-accessible
    STATUS  mandatory
    DESCRIPTION
       "The row definition for this table."
    INDEX { rsNetFloodQuotaWay }
    ::=  { rsNetFloodQuotaTable 1 }

RsNetFloodQuotaEntry ::= SEQUENCE {
    rsNetFloodQuotaWay INTEGER,
    rsNetFloodTcpQuota INTEGER,
    rsNetFloodUdpQuota INTEGER,
    rsNetFloodIcmpQuota INTEGER,
    rsNetFloodIgmpQuota INTEGER,
    rsNetFloodUdpFragQuota INTEGER
}

rsNetFloodQuotaWay OBJECT-TYPE
    SYNTAX INTEGER {
    inbound(0),
    outbound(1)
    }
    ACCESS  read-only
    STATUS  mandatory
    DESCRIPTION
      "The protection way inbound / outbound."
    ::=  {rsNetFloodQuotaEntry 1}


rsNetFloodTcpQuota OBJECT-TYPE
    SYNTAX INTEGER (1..100)
    ACCESS  read-write
    STATUS  mandatory
    DESCRIPTION
       "Tcp quota value."
    ::=  { rsNetFloodQuotaEntry 2 }


rsNetFloodUdpQuota OBJECT-TYPE
    SYNTAX INTEGER (1..100)
    ACCESS  read-write
    STATUS  mandatory
    DESCRIPTION
       "Udp quota value."
    ::=  { rsNetFloodQuotaEntry 3 }

rsNetFloodIcmpQuota OBJECT-TYPE
    SYNTAX INTEGER (1..100)
    ACCESS  read-write
    STATUS  mandatory
    DESCRIPTION
       "Icmp quota value."
    ::=  { rsNetFloodQuotaEntry 4 }

rsNetFloodIgmpQuota OBJECT-TYPE
    SYNTAX INTEGER (1..100)
    ACCESS  read-write
    STATUS  mandatory
    DESCRIPTION
       "Igmp quota value."
    ::=  { rsNetFloodQuotaEntry 5 }

rsNetFloodUdpFragQuota OBJECT-TYPE
    SYNTAX INTEGER (1..100)
    ACCESS  read-write
    STATUS  mandatory
    DESCRIPTION
       "UDP Fragmentation quota value."
    ::=  { rsNetFloodQuotaEntry 6 }


rsNetFloodSetDefaultQuotas OBJECT-TYPE
 SYNTAX INTEGER
   ACCESS  read-write
   STATUS  mandatory
   DESCRIPTION
       "set the defualt quotas according the configured bandwidth"
    ::=  { rsNetFlood 13}

rsNetFloodBypassTcpTable OBJECT-TYPE
    SYNTAX SEQUENCE OF RsNetFloodBypassTcpEntry
    ACCESS not-accessible
    STATUS  mandatory
    DESCRIPTION
      "Table containing the list of profiles params for the NetFlood inspection"
    ::=  {rsNetFlood 14}

rsNetFloodBypassTcpEntry OBJECT-TYPE
    SYNTAX RsNetFloodBypassTcpEntry
    ACCESS not-accessible
    STATUS  mandatory
    DESCRIPTION
       "The row definition for this table."
    INDEX { rsNetFloodBypassTcpType }
    ::=  { rsNetFloodBypassTcpTable 1 }

RsNetFloodBypassTcpEntry ::= SEQUENCE {
    rsNetFloodBypassTcpType INTEGER,
	rsNetFloodBypassTcpStatus INTEGER,
    rsNetFloodBypassTcpValues DisplayString
}


rsNetFloodBypassTcpType OBJECT-TYPE
    SYNTAX INTEGER {
--  checksum(0),
	sequence-num(1),
    id-num(2),
--  dns-id-num(3),
--  dns-qname(4),
--  dns-subdomain(5),
--	dns-qcount(6),
	source-port(7),
    source-ip(8),
	frag-offset(9),
	flow-label(10),
	tos(11),
	packet-size(12),
	destination-port(13),
    destination-ip(14),
    fragment(15),
--  (16),
--  (17),
--  (18),
--  icmp-igmp-message-type(19),
    ttl(20),
	id-num-ipv6(21),
	frag-offset-ipv6(22),
--	(23),
	packet-size-ipv6(24),
	source-ip-ipv6(25),
	destination-ip-ipv6(26),
--	icmp-message-type-ipv6(27),
	context-tag(28)
    }
    ACCESS  read-write
    STATUS  mandatory
    DESCRIPTION
       "The bypass type"
    ::=  { rsNetFloodBypassTcpEntry 1}

rsNetFloodBypassTcpStatus OBJECT-TYPE
    SYNTAX INTEGER {
    accept(0),
	bypass(1)
    }
    ACCESS  read-write
    STATUS  mandatory
    DESCRIPTION
       "The bypass type"
    ::=  {rsNetFloodBypassTcpEntry 2}

rsNetFloodBypassTcpValues OBJECT-TYPE
    SYNTAX DisplayString
    ACCESS  read-write
    STATUS  mandatory
    DESCRIPTION
      "The values of the bypass."
    ::=  {rsNetFloodBypassTcpEntry 3}

rsNetFloodBypassTcpSynTable OBJECT-TYPE
    SYNTAX SEQUENCE OF RsNetFloodBypassTcpSynEntry
    ACCESS not-accessible
    STATUS  mandatory
    DESCRIPTION
      "Table containing the list of profiles params for the NetFlood inspection"
    ::=  {rsNetFlood 15}

rsNetFloodBypassTcpSynEntry OBJECT-TYPE
    SYNTAX RsNetFloodBypassTcpSynEntry
    ACCESS not-accessible
    STATUS  mandatory
    DESCRIPTION
       "The row definition for this table."
    INDEX { rsNetFloodBypassTcpSynType }
    ::=  { rsNetFloodBypassTcpSynTable 1 }

RsNetFloodBypassTcpSynEntry ::= SEQUENCE {
    rsNetFloodBypassTcpSynType INTEGER,
	rsNetFloodBypassTcpSynStatus INTEGER,
    rsNetFloodBypassTcpSynValues DisplayString
}


rsNetFloodBypassTcpSynType OBJECT-TYPE
    SYNTAX INTEGER {
--  checksum(0),
	sequence-num(1),
    id-num(2),
--  dns-id-num(3),
--  dns-qname(4),
--  dns-subdomain(5),
--	dns-qcount(6),
	source-port(7),
    source-ip(8),
	frag-offset(9),
	flow-label(10),
	tos(11),
	packet-size(12),
	destination-port(13),
    destination-ip(14),
    fragment(15),
--  (16),
--  (17),
--  (18),
--  icmp-igmp-message-type(19),
    ttl(20),
	id-num-ipv6(21),
	frag-offset-ipv6(22),
--	(23),
	packet-size-ipv6(24),
	source-ip-ipv6(25),
	destination-ip-ipv6(26),
--	icmp-message-type-ipv6(27),
	context-tag(28)
    }
    ACCESS  read-write
    STATUS  mandatory
    DESCRIPTION
       "The bypass type"
    ::=  { rsNetFloodBypassTcpSynEntry 1}

rsNetFloodBypassTcpSynStatus OBJECT-TYPE
    SYNTAX INTEGER {
    accept(0),
	bypass(1)
    }
    ACCESS  read-write
    STATUS  mandatory
    DESCRIPTION
       "The bypass type"
    ::=  {rsNetFloodBypassTcpSynEntry 2}

rsNetFloodBypassTcpSynValues OBJECT-TYPE
    SYNTAX DisplayString
    ACCESS  read-write
    STATUS  mandatory
    DESCRIPTION
      "The values of the bypass."
    ::=  {rsNetFloodBypassTcpSynEntry 3}

rsNetFloodBypassUdpTable OBJECT-TYPE
    SYNTAX SEQUENCE OF RsNetFloodBypassUdpEntry
    ACCESS not-accessible
    STATUS  mandatory
    DESCRIPTION
      "Table containing the list of profiles params for the NetFlood inspection"
    ::=  {rsNetFlood 16}

rsNetFloodBypassUdpEntry OBJECT-TYPE
    SYNTAX RsNetFloodBypassUdpEntry
    ACCESS not-accessible
    STATUS  mandatory
    DESCRIPTION
       "The row definition for this table."
    INDEX { rsNetFloodBypassUdpType }
    ::=  { rsNetFloodBypassUdpTable 1 }

RsNetFloodBypassUdpEntry ::= SEQUENCE {
    rsNetFloodBypassUdpType INTEGER,
	rsNetFloodBypassUdpStatus INTEGER,
    rsNetFloodBypassUdpValues DisplayString
}


rsNetFloodBypassUdpType OBJECT-TYPE
    SYNTAX INTEGER {
    checksum(0),
--	sequence-num(1),
    id-num(2),
    dns-id-num(3),
    dns-qname(4),
--  dns-subdomain(5),
    dns-qcount(6),
	source-port(7),
    source-ip(8),
	frag-offset(9),
	flow-label(10),
	tos(11),
	packet-size(12),
	destination-port(13),
    destination-ip(14),
    fragment(15),
--  (16),
--  (17),
--  (18),
--  icmp-igmp-message-type(19),
    ttl(20),
	id-num-ipv6(21),
	frag-offset-ipv6(22),
--	(23),
	packet-size-ipv6(24),
	source-ip-ipv6(25),
	destination-ip-ipv6(26),
--	icmp-message-type-ipv6(27),
	context-tag(28)
    }
    ACCESS  read-write
    STATUS  mandatory
    DESCRIPTION
       "The bypass type"
    ::=  { rsNetFloodBypassUdpEntry 1}

rsNetFloodBypassUdpStatus OBJECT-TYPE
    SYNTAX INTEGER {
    accept(0),
	bypass(1)
    }
    ACCESS  read-write
    STATUS  mandatory
    DESCRIPTION
       "The bypass type"
    ::=  {rsNetFloodBypassUdpEntry 2}

rsNetFloodBypassUdpValues OBJECT-TYPE
    SYNTAX DisplayString
    ACCESS  read-write
    STATUS  mandatory
    DESCRIPTION
      "The values of the bypass."
    ::=  {rsNetFloodBypassUdpEntry 3}

rsNetFloodBypassIcmpTable OBJECT-TYPE
    SYNTAX SEQUENCE OF RsNetFloodBypassIcmpEntry
    ACCESS not-accessible
    STATUS  mandatory
    DESCRIPTION
      "Table containing the list of profiles params for the NetFlood inspection"
    ::=  {rsNetFlood 17}

rsNetFloodBypassIcmpEntry OBJECT-TYPE
    SYNTAX RsNetFloodBypassIcmpEntry
    ACCESS not-accessible
    STATUS  mandatory
    DESCRIPTION
       "The row definition for this table."
    INDEX { rsNetFloodBypassIcmpType }
    ::=  { rsNetFloodBypassIcmpTable 1 }

RsNetFloodBypassIcmpEntry ::= SEQUENCE {
    rsNetFloodBypassIcmpType INTEGER,
	rsNetFloodBypassIcmpStatus INTEGER,
    rsNetFloodBypassIcmpValues DisplayString
}


rsNetFloodBypassIcmpType OBJECT-TYPE
    SYNTAX INTEGER {
    checksum(0),
--	sequence-num(1),
    id-num(2),
--  dns-id-num(3),
--  dns-qname(4),
--  dns-subdomain(5),
--	dns-qcount(6),
--	source-port(7),
    source-ip(8),
	frag-offset(9),
	flow-label(10),
	tos(11),
	packet-size(12),
--	destination-port(13),
    destination-ip(14),
    fragment(15),
--  (16),
--  (17),
--  (18),
    icmp-message-type(19),
    ttl(20),
	id-num-ipv6(21),
	frag-offset-ipv6(22),
--	(23),
	packet-size-ipv6(24),
	source-ip-ipv6(25),
	destination-ip-ipv6(26),
	icmp-message-type-ipv6(27),
	context-tag(28)
    }
    ACCESS  read-write
    STATUS  mandatory
    DESCRIPTION
       "The bypass type"
    ::=  { rsNetFloodBypassIcmpEntry 1}

rsNetFloodBypassIcmpStatus OBJECT-TYPE
    SYNTAX INTEGER {
    accept(0),
	bypass(1)
    }
    ACCESS  read-write
    STATUS  mandatory
    DESCRIPTION
       "The bypass type"
    ::=  {rsNetFloodBypassIcmpEntry 2}

rsNetFloodBypassIcmpValues OBJECT-TYPE
    SYNTAX DisplayString
    ACCESS  read-write
    STATUS  mandatory
    DESCRIPTION
      "The values of the bypass."
    ::=  {rsNetFloodBypassIcmpEntry 3}

rsNetFloodBypassIgmpTable OBJECT-TYPE
    SYNTAX SEQUENCE OF RsNetFloodBypassIgmpEntry
    ACCESS not-accessible
    STATUS  mandatory
    DESCRIPTION
      "Table containing the list of profiles params for the NetFlood inspection"
    ::=  {rsNetFlood 18}

rsNetFloodBypassIgmpEntry OBJECT-TYPE
    SYNTAX RsNetFloodBypassIgmpEntry
    ACCESS not-accessible
    STATUS  mandatory
    DESCRIPTION
       "The row definition for this table."
    INDEX { rsNetFloodBypassIgmpType }
    ::=  { rsNetFloodBypassIgmpTable 1 }

RsNetFloodBypassIgmpEntry ::= SEQUENCE {
    rsNetFloodBypassIgmpType INTEGER,
	rsNetFloodBypassIgmpStatus INTEGER,
    rsNetFloodBypassIgmpValues DisplayString
}


rsNetFloodBypassIgmpType OBJECT-TYPE
    SYNTAX INTEGER {
    checksum(0),
--	sequence-num(1),
    id-num(2),
--  dns-id-num(3),
--  dns-qname(4),
--  dns-subdomain(5),
--	dns-qcount(6),
--	source-port(7),
    source-ip(8),
	frag-offset(9),
	flow-label(10),
	tos(11),
	packet-size(12),
--	destination-port(13),
    destination-ip(14),
    fragment(15),
--  (16),
--  (17),
--  (18),
    igmp-message-type(19),
    ttl(20),
	id-num-ipv6(21),
	frag-offset-ipv6(22),
--	(23),
	packet-size-ipv6(24),
	source-ip-ipv6(25),
	destination-ip-ipv6(26),
--	icmp-message-type-ipv6(27),
	context-tag(28)
    }
    ACCESS  read-write
    STATUS  mandatory
    DESCRIPTION
       "The bypass type"
    ::=  { rsNetFloodBypassIgmpEntry 1}

rsNetFloodBypassIgmpStatus OBJECT-TYPE
    SYNTAX INTEGER {
    accept(0),
	bypass(1)
    }
    ACCESS  read-write
    STATUS  mandatory
    DESCRIPTION
       "The bypass type"
    ::=  {rsNetFloodBypassIgmpEntry 2}

rsNetFloodBypassIgmpValues OBJECT-TYPE
    SYNTAX DisplayString
    ACCESS  read-write
    STATUS  mandatory
    DESCRIPTION
      "The values of the bypass."
    ::=  {rsNetFloodBypassIgmpEntry 3}

rsNetFloodFootprintStrictness OBJECT-TYPE
 SYNTAX INTEGER {
   low(0),
   medium(1),
   high(2)
   }
   ACCESS  read-write
   STATUS  mandatory
   DESCRIPTION
       "configures how accurate must the footprint be in order to be activated"
    ::=  { rsNetFlood 19}

rsNetFloodSamplingStatus OBJECT-TYPE
 SYNTAX INTEGER {
		enable(1),
		disable(2)
		}
   ACCESS  read-write
   STATUS  mandatory
   DESCRIPTION
       "configures whether the netflood sampling is enabled or disabled"
    ::=  { rsNetFlood 20}

rsIDSNetFloodPolicies OBJECT-TYPE
   SYNTAX INTEGER
   ACCESS read-only
   STATUS mandatory
   DESCRIPTION
       "Tuning parameter for the number of netflood policies"
    ::=  { rsNetFlood 21}

rsIDSNetFloodPoliciesAfterReset OBJECT-TYPE
   SYNTAX INTEGER
   ACCESS  read-write
   STATUS  mandatory
   DESCRIPTION
       "Tuning parameter for the number of netflood policies after the next reset"
    ::=  { rsNetFlood 22}

rsNetFloodBypassTcpFragTable OBJECT-TYPE
    SYNTAX SEQUENCE OF RsNetFloodBypassTcpFragEntry
    ACCESS not-accessible
    STATUS  mandatory
    DESCRIPTION
      "Table containing the list of profiles params for the NetFlood inspection"
    ::=  {rsNetFlood 23}

rsNetFloodBypassTcpFragEntry OBJECT-TYPE
    SYNTAX RsNetFloodBypassTcpFragEntry
    ACCESS not-accessible
    STATUS  mandatory
    DESCRIPTION
       "The row definition for this table."
    INDEX { rsNetFloodBypassTcpFragType }
    ::=  { rsNetFloodBypassTcpFragTable 1 }

RsNetFloodBypassTcpFragEntry ::= SEQUENCE {
    rsNetFloodBypassTcpFragType INTEGER,
	rsNetFloodBypassTcpFragStatus INTEGER,
    rsNetFloodBypassTcpFragValues DisplayString
}


rsNetFloodBypassTcpFragType OBJECT-TYPE
    SYNTAX INTEGER {
--  checksum(0),
	sequence-num(1),
    id-num(2),
--  dns-id-num(3),
--  dns-qname(4),
--  dns-subdomain(5),
--	dns-qcount(6),
	source-port(7),
    source-ip(8),
	frag-offset(9),
	flow-label(10),
	tos(11),
	packet-size(12),
	destination-port(13),
    destination-ip(14),
    fragment(15),
--  (16),
--  (17),
--  (18),
--  icmp-igmp-message-type(19),
    ttl(20),
	id-num-ipv6(21),
	frag-offset-ipv6(22),
--	(23),
	packet-size-ipv6(24),
	source-ip-ipv6(25),
	destination-ip-ipv6(26),
--	icmp-message-type-ipv6(27),
	context-tag(28)
    }
    ACCESS  read-write
    STATUS  mandatory
    DESCRIPTION
       "The bypass type"
    ::=  { rsNetFloodBypassTcpFragEntry 1}

rsNetFloodBypassTcpFragStatus OBJECT-TYPE
    SYNTAX INTEGER {
    accept(0),
	bypass(1)
    }
    ACCESS  read-write
    STATUS  mandatory
    DESCRIPTION
       "The bypass type"
    ::=  {rsNetFloodBypassTcpFragEntry 2}

rsNetFloodBypassTcpFragValues OBJECT-TYPE
    SYNTAX DisplayString
    ACCESS  read-write
    STATUS  mandatory
    DESCRIPTION
      "The values of the bypass."
    ::=  {rsNetFloodBypassTcpFragEntry 3}

rsNetFloodBypassTable OBJECT-TYPE
    SYNTAX SEQUENCE OF RsNetFloodBypassEntry
    ACCESS not-accessible
    STATUS  mandatory
    DESCRIPTION
      "Table containing the list of profiles params for the NetFlood inspection"
    ::=  {rsNetFlood 24}


rsNetFloodBypassEntry OBJECT-TYPE
    SYNTAX RsNetFloodBypassEntry
    ACCESS not-accessible
    STATUS  mandatory
    DESCRIPTION
       "The row definition for this table."
    INDEX { rsNetFloodBypassController, rsNetFloodBypassType }
    ::=  { rsNetFloodBypassTable 1 }

RsNetFloodBypassEntry ::= SEQUENCE {
rsNetFloodBypassController INTEGER,
    rsNetFloodBypassType INTEGER,
	rsNetFloodBypassStatus INTEGER,
    rsNetFloodBypassValues DisplayString,
    rsNetFloodBypassRowStatus RowStatus
}

rsNetFloodBypassController OBJECT-TYPE
    SYNTAX INTEGER {
   udp-in(0),
   icmp-in(2),
   igmp-in(4),
   tcp-syn-in(6),
   tcp-rst-in(8),
   tcp-ack-in(10),
   tcp-ack-psh-in(12),
   tcp-ack-fin-in(14),
   tcp-syn-ack-in(16),
   tcp-frag-in(18),
   udp-frag-in(20)
   }
    ACCESS  read-write
    STATUS  mandatory
    DESCRIPTION
       "The bypass controller type"
    ::=  { rsNetFloodBypassEntry 1}


rsNetFloodBypassType OBJECT-TYPE
    SYNTAX INTEGER {
    checksum(0),
	sequence-num(1),
    id-num(2),
      dns-id-num(3),
      dns-qname(4),
--      dns-subdomain(5),
  	dns-qcount(6),
	source-port(7),
    source-ip(8),
	frag-offset(9),
	flow-label(10),
	tos(11),
	packet-size(12),
	destination-port(13),
    destination-ip(14),
    fragment(15),
--  (16),
--  (17),
--  (18),
  icmp-igmp-message-type(19),
    ttl(20),
	id-num-ipv6(21),
	frag-offset-ipv6(22),
--   (23),
	packet-size-ipv6(24),
	source-ip-ipv6(25),
	destination-ip-ipv6(26),
	icmp-message-type-ipv6(27) ,
	context-tag(28)
--   (29),
--	dns-ancount(30),
--	dns-flags(31)
    }
    ACCESS  read-write
    STATUS  mandatory
    DESCRIPTION
       "The bypass type"
    ::=  { rsNetFloodBypassEntry 2}

rsNetFloodBypassStatus OBJECT-TYPE
    SYNTAX INTEGER {
    accept(0),
	bypass(1)
    }
    ACCESS  read-write
    STATUS  mandatory
    DESCRIPTION
       "The bypass type"
    ::=  {rsNetFloodBypassEntry 3}

rsNetFloodBypassValues OBJECT-TYPE
    SYNTAX DisplayString
    ACCESS  read-write
    STATUS  mandatory
    DESCRIPTION
      "The values of the bypass."
    ::=  {rsNetFloodBypassEntry 4}


rsNetFloodBypassRowStatus OBJECT-TYPE
    SYNTAX RowStatus
    ACCESS  read-write
    STATUS  mandatory
    DESCRIPTION
       "This variable indicates the administrative status of this entry.
        Used to delete an entry of this table."
    ::=  { rsNetFloodBypassEntry 5 }


--
-- SuspendTable browsing table
--

rsIDSSuspendTable OBJECT-TYPE
    SYNTAX SEQUENCE OF RsIDSSuspendTableEntry
    ACCESS not-accessible
    STATUS  mandatory
    DESCRIPTION
      "Dynamic Blocking Table"
    ::= { rsIDS 102 }

rsIDSSuspendTableEntry OBJECT-TYPE
    SYNTAX RsIDSSuspendTableEntry
    ACCESS not-accessible
    STATUS mandatory
    DESCRIPTION
       "The row definition for this table."
    INDEX { rsIDSSuspendTableEntrySrcIp, rsIDSSuspendTableEntryDstIp, rsIDSSuspendTableEntryDstPort, rsIDSSuspendTableEntryProtocol}
    ::=  { rsIDSSuspendTable 1 }


RsIDSSuspendTableEntry ::= SEQUENCE {
    rsIDSSuspendTableEntrySrcIp DisplayString,
    rsIDSSuspendTableEntryDstIp DisplayString,
    rsIDSSuspendTableEntryDstPort DisplayString,
    rsIDSSuspendTableEntryProtocol DisplayString,
    rsIDSSuspendTableEntryExpTypeAndTime DisplayString
}


rsIDSSuspendTableEntrySrcIp OBJECT-TYPE
    SYNTAX DisplayString(SIZE(1..15))
    ACCESS read-only
    STATUS mandatory
    DESCRIPTION
      "Source IP"
    ::=  { rsIDSSuspendTableEntry 1 }

rsIDSSuspendTableEntryDstIp OBJECT-TYPE
    SYNTAX DisplayString(SIZE(1..15))
    ACCESS read-only
    STATUS mandatory
    DESCRIPTION
      "Destination IP"
    ::=  { rsIDSSuspendTableEntry 2 }

rsIDSSuspendTableEntryDstPort OBJECT-TYPE
    SYNTAX DisplayString(SIZE(1..5))
    ACCESS read-only
    STATUS mandatory
    DESCRIPTION
      "Destination Port"
    ::=  { rsIDSSuspendTableEntry 3 }


rsIDSSuspendTableEntryProtocol OBJECT-TYPE
    SYNTAX DisplayString(SIZE(1..4))
    ACCESS read-only
    STATUS mandatory
    DESCRIPTION
      "Protocol"
    ::=  { rsIDSSuspendTableEntry 4 }

rsIDSSuspendTableEntryExpTypeAndTime OBJECT-TYPE
    SYNTAX DisplayString(SIZE(1..7))
    ACCESS read-only
    STATUS mandatory
    DESCRIPTION
      "Expiration type. String which will contain one of the following: On demand, Dyn:[time_left], Fix:[time_left], where the time_left designates the amount of time left until the row expires"
    ::=  { rsIDSSuspendTableEntry 5 }

-- Suspend table NEW Mib

rsIDSNewSuspendTable OBJECT-TYPE
    SYNTAX SEQUENCE OF RsIDSNewSuspendTableEntry
    ACCESS not-accessible
    STATUS  mandatory
    DESCRIPTION
      "Dynamic Blocking Table"
    ::= { rsIDS 112 }

rsIDSNewSuspendTableEntry OBJECT-TYPE
    SYNTAX RsIDSNewSuspendTableEntry
    ACCESS not-accessible
    STATUS mandatory
    DESCRIPTION
       "The row definition for this table."
    INDEX { rsIDSNewSuspendTableEntrySrcIp, rsIDSNewSuspendTableEntryDstIp,
	        rsIDSNewSuspendTableEntryDstPort, rsIDSNewSuspendTableEntryProtocol,
			rsIDSNewSuspendTableEntryModule}
    ::=  { rsIDSNewSuspendTable 1 }


RsIDSNewSuspendTableEntry ::= SEQUENCE {
    rsIDSNewSuspendTableEntrySrcIp DisplayString,
    rsIDSNewSuspendTableEntryDstIp DisplayString,
    rsIDSNewSuspendTableEntryDstPort INTEGER,
    rsIDSNewSuspendTableEntryProtocol INTEGER,
	rsIDSNewSuspendTableEntryModule INTEGER,
    rsIDSNewSuspendTableEntryExpType INTEGER,
	rsIDSNewSuspendTableEntryExpTime INTEGER
}


rsIDSNewSuspendTableEntrySrcIp OBJECT-TYPE
    SYNTAX DisplayString(SIZE(1..46))
    ACCESS read-only
    STATUS mandatory
    DESCRIPTION
      "Source IP"
    ::=  { rsIDSNewSuspendTableEntry 1 }

rsIDSNewSuspendTableEntryDstIp OBJECT-TYPE
    SYNTAX DisplayString(SIZE(1..46))
    ACCESS read-only
    STATUS mandatory
    DESCRIPTION
      "Destination IP"
    ::=  { rsIDSNewSuspendTableEntry 2 }

rsIDSNewSuspendTableEntryDstPort OBJECT-TYPE
    SYNTAX INTEGER
    ACCESS read-only
    STATUS mandatory
    DESCRIPTION
      "Destination Port"
    ::=  { rsIDSNewSuspendTableEntry 3 }

rsIDSNewSuspendTableEntryProtocol OBJECT-TYPE
    SYNTAX INTEGER {
			ip(0),
			tcp(1),
			udp(2),
			icmp(3),
			icmpv6(5)}
    ACCESS read-only
    STATUS mandatory
    DESCRIPTION
      "Protocol"
    ::=  { rsIDSNewSuspendTableEntry 4 }

rsIDSNewSuspendTableEntryModule OBJECT-TYPE
    SYNTAX INTEGER {
			signatures(0),
			anti-scanning(1),
			syn-protection(2)}
	ACCESS read-only
    STATUS mandatory
    DESCRIPTION
      "Module"
    ::=  { rsIDSNewSuspendTableEntry 5 }

rsIDSNewSuspendTableEntryExpType OBJECT-TYPE
    SYNTAX INTEGER {
			on-request(0),
			fixed-timeout(1),
			dynamic-timeout(2)}
    ACCESS read-only
    STATUS mandatory
    DESCRIPTION
      "Expiration Type"
    ::=  { rsIDSNewSuspendTableEntry 6 }

rsIDSNewSuspendTableEntryExpTime OBJECT-TYPE
    SYNTAX INTEGER
    ACCESS read-only
    STATUS mandatory
    DESCRIPTION
      "Expiration Time"
    ::=  { rsIDSNewSuspendTableEntry 7 }

-- SYN protection
--
rsIDSSynProtection OBJECT IDENTIFIER ::= { rsIDS 103 }

-- obsolete
rsIDSSynPolicyTable OBJECT-TYPE
    SYNTAX SEQUENCE OF RsIDSSynPolicyEntry
    ACCESS not-accessible
    STATUS  mandatory
    DESCRIPTION
      "Table containing the list of policy params for the syn protection"
    ::=  {rsIDSSynProtection 1}

rsIDSSynPolicyEntry OBJECT-TYPE
    SYNTAX RsIDSSynPolicyEntry
    ACCESS not-accessible
    STATUS  mandatory
    DESCRIPTION
       "The SYN policy  definition for this table."
    INDEX { rsIDSSynPolicyName }
    ::=  { rsIDSSynPolicyTable 1 }

RsIDSSynPolicyEntry ::= SEQUENCE {
    rsIDSSynPolicyName DisplayString,
    rsIDSSynPolicyProfileName DisplayString,
    rsIDSSynPolicySource DisplayString,
    rsIDSSynPolicyDestination DisplayString,
    rsIDSSynPolicyDirection INTEGER,
    rsIDSSynPolicyPortmask DisplayString,
    rsIDSSynPolicyState INTEGER,
    rsIDSSynPolicyStatus  RowStatus,
    rsIDSSynPolicyVlanTagGroup DisplayString,
    rsIDSSynPolicyAction INTEGER
}

rsIDSSynPolicyName OBJECT-TYPE
    SYNTAX DisplayString (SIZE(1..19))
    ACCESS  read-only
    STATUS  mandatory
    DESCRIPTION
      "The Name for the Rule."
    ::=  {rsIDSSynPolicyEntry 1}

rsIDSSynPolicyProfileName OBJECT-TYPE
    SYNTAX DisplayString (SIZE(1..29))
    ACCESS  read-write
    STATUS  mandatory
    DESCRIPTION
      "The Name for the Service."
    ::=  {rsIDSSynPolicyEntry 2}

rsIDSSynPolicySource OBJECT-TYPE
    SYNTAX DisplayString (SIZE(0..20))
    ACCESS  read-write
    STATUS  mandatory
    DESCRIPTION
      "The source address / range of address for the packet, the name is
      defined in the Objects table or can be an IP address."
    ::=  {rsIDSSynPolicyEntry 3}

rsIDSSynPolicyDestination OBJECT-TYPE
    SYNTAX DisplayString (SIZE(0..20))
    ACCESS  read-write
    STATUS  mandatory
    DESCRIPTION
      "The destination address / range of address for the packet, the name is
      defined in the Objects table or can be an IP address."
    ::=  {rsIDSSynPolicyEntry 4}

rsIDSSynPolicyDirection OBJECT-TYPE
    SYNTAX INTEGER {
              oneway(1),
              twoway(2) }
    ACCESS  read-write
    STATUS  mandatory
    DESCRIPTION
       "This variable indicates the direction of the incoming packet."
    DEFVAL { 1 }
    ::=  { rsIDSSynPolicyEntry 5 }


rsIDSSynPolicyPortmask OBJECT-TYPE
    SYNTAX DisplayString (SIZE(0..80))
    ACCESS  read-write
    STATUS  mandatory
    DESCRIPTION
       "The Port Group"
    ::=  { rsIDSSynPolicyEntry 6 }

 rsIDSSynPolicyState OBJECT-TYPE
    SYNTAX INTEGER {
              active(1),
              inactive(2) }
    ACCESS  read-write
    STATUS  mandatory
    DESCRIPTION
       "This variable indicates the state of the rule."
    DEFVAL { 1 }
    ::=  { rsIDSSynPolicyEntry 7 }

rsIDSSynPolicyStatus OBJECT-TYPE
    SYNTAX RowStatus
    ACCESS  read-write
    STATUS  mandatory
    DESCRIPTION
       "This variable indicates the administrative status of this entry.
        Used to delete an entry of this table."
    ::=  { rsIDSSynPolicyEntry 8 }

rsIDSSynPolicyVlanTagGroup OBJECT-TYPE
    SYNTAX DisplayString (SIZE(0..80))
    ACCESS  read-write
    STATUS  mandatory
    DESCRIPTION
       "The VLAN tag Group"
    ::=  { rsIDSSynPolicyEntry 9 }

rsIDSSynPolicyAction OBJECT-TYPE
    SYNTAX INTEGER {
        report(0),
        block(1) }
    ACCESS  read-write
    STATUS  mandatory
    DESCRIPTION
       "This variable indicates the policy action"
    ::=  { rsIDSSynPolicyEntry 10 }


rsIDSSynProfilesTable OBJECT-TYPE
    SYNTAX SEQUENCE OF RsIDSSynProfilesEntry
    ACCESS not-accessible
    STATUS  mandatory
    DESCRIPTION
      "Table containing the list of Syn rules params for the ids"
    ::=  {rsIDSSynProtection 2}

rsIDSSynProfilesEntry OBJECT-TYPE
    SYNTAX RsIDSSynProfilesEntry
    ACCESS not-accessible
    STATUS  mandatory
    DESCRIPTION
       "The row definition for this table."
    INDEX { rsIDSSynProfilesName, rsIDSSynProfileServiceName }
    ::=  { rsIDSSynProfilesTable 1 }

RsIDSSynProfilesEntry ::= SEQUENCE {
    rsIDSSynProfilesName DisplayString,
    rsIDSSynProfileServiceName DisplayString,
    rsIDSSynProfilesStatus RowStatus,
	rsIDSSynProfileServiceId INTEGER,
    rsIDSSynProfileType INTEGER,
    rsIDSSynProfileAction INTEGER
}

rsIDSSynProfilesName OBJECT-TYPE
    SYNTAX DisplayString (SIZE(1..29))
    ACCESS  read-only
    STATUS  mandatory
    DESCRIPTION
      "The Name for the Profile."
    ::=  {rsIDSSynProfilesEntry 1}

rsIDSSynProfileServiceName OBJECT-TYPE
    SYNTAX DisplayString (SIZE(1..29))
    ACCESS  read-only
    STATUS  mandatory
    DESCRIPTION
      "The Name for the Service."
    ::=  {rsIDSSynProfilesEntry 2}


rsIDSSynProfilesStatus OBJECT-TYPE
    SYNTAX RowStatus
    ACCESS  read-write
    STATUS  mandatory
    DESCRIPTION
       "This variable indicates the administrative status of this entry.
        Used to delete an entry of this table."
    ::=  { rsIDSSynProfilesEntry 3 }

rsIDSSynProfileServiceId OBJECT-TYPE
    SYNTAX INTEGER
    ACCESS read-write
    STATUS mandatory
    DESCRIPTION
      "The profile service ID. this field should not be visible to the user."
    ::=  { rsIDSSynProfilesEntry 4 }

rsIDSSynProfileType OBJECT-TYPE
    SYNTAX INTEGER {
        user (3),
        static (4)
    }
    ACCESS read-only
    STATUS mandatory
    DESCRIPTION
      "Denotes the type of the filter policy."
    ::=  { rsIDSSynProfilesEntry 5 }

rsIDSSynProfileAction OBJECT-TYPE
    SYNTAX INTEGER {
        report(0),
        block(1) }
    ACCESS  read-write
    STATUS  mandatory
    DESCRIPTION
       "This variable indicates the profile action"
    ::=  { rsIDSSynProfilesEntry 6 }

rsIDSSYNAttackTable OBJECT-TYPE
    SYNTAX SEQUENCE OF RsIDSSynAttackEntry
    ACCESS not-accessible
    STATUS  mandatory
    DESCRIPTION
      "Table containing the parameters that are needed to detect intrusions"
    ::=  {rsIDSSynProtection 3}


rsIDSSynAttackEntry OBJECT-TYPE
    SYNTAX RsIDSSynAttackEntry
    ACCESS not-accessible
    STATUS  mandatory
    DESCRIPTION
       "The row definition for this table."
    INDEX { rsIDSSYNAttackId }
    ::=  { rsIDSSYNAttackTable 1 }

RsIDSSynAttackEntry ::= SEQUENCE {
	rsIDSSYNAttackId INTEGER,
	rsIDSSYNAttackName DisplayString,
	rsIDSSYNDestinationAppPortGroup  DisplayString,
	rsIDSSYNAttackActivationThreshold INTEGER,
	rsIDSSYNAttackTerminationThreshold INTEGER,
	rsIDSSYNAttackStableThresholdPeriod INTEGER,
	rsIDSSYNAttackPacketReport INTEGER,
	rsIDSSYNAttackStatus RowStatus,
	rsIDSSYNAttackSourceType INTEGER,
    rsIDSSYNAttackRisk INTEGER,
	rsIDSSYNVerificationType INTEGER
}

rsIDSSYNAttackId OBJECT-TYPE
    SYNTAX INTEGER
    ACCESS  read-write
    STATUS  mandatory
    DESCRIPTION
       "This variable indicates the object type- whether it is a filter or group  "
    ::=  { rsIDSSynAttackEntry 1}

rsIDSSYNAttackName OBJECT-TYPE
    SYNTAX DisplayString (SIZE(1..29))
    ACCESS  read-write
    STATUS  mandatory
    DESCRIPTION
      "The Name for the attack must be unique."
    ::=  {rsIDSSynAttackEntry 2}

rsIDSSYNDestinationAppPortGroup OBJECT-TYPE
    SYNTAX DisplayString (SIZE(0..30))
    ACCESS  read-write
    STATUS  mandatory
    DESCRIPTION
      "The Destination Application Port Group."
    ::=  {rsIDSSynAttackEntry 3 }


rsIDSSYNAttackActivationThreshold OBJECT-TYPE
    SYNTAX INTEGER (0..150000)
    ACCESS  read-write
    STATUS  mandatory
    DESCRIPTION
       "This variable indicates the activating threshold "
    DEFVAL  { 2500 }
    ::=  { rsIDSSynAttackEntry 4 }


rsIDSSYNAttackTerminationThreshold OBJECT-TYPE
    SYNTAX INTEGER (0..150000)
    ACCESS  read-write
    STATUS  mandatory
    DESCRIPTION
       "This variable indicates the termination threshold "
    DEFVAL  { 1500 }
    ::=  { rsIDSSynAttackEntry 5 }



rsIDSSYNAttackStableThresholdPeriod OBJECT-TYPE
    SYNTAX INTEGER (0..10)
    ACCESS  read-write
    STATUS  mandatory
    DESCRIPTION
       "This variable indicates the the period before the behaviour as detected as stable "
    DEFVAL  { 5 }
    ::=  { rsIDSSynAttackEntry 6 }



rsIDSSYNAttackPacketReport OBJECT-TYPE
    SYNTAX INTEGER {
			enable(1),
			disable(2)}
    ACCESS  read-write
    STATUS  mandatory
    DESCRIPTION
       "This variable indicates the per-attack packet report"
	DEFVAL  {disable}
    ::=  { rsIDSSynAttackEntry 7 }


rsIDSSYNAttackStatus OBJECT-TYPE
    SYNTAX RowStatus
    ACCESS  read-write
    STATUS  mandatory
    DESCRIPTION
       "This variable indicates the administrative status of this entry.
        Used to delete an entry of this table."
    ::=  { rsIDSSynAttackEntry 8 }



rsIDSSYNAttackSourceType OBJECT-TYPE
    SYNTAX INTEGER {
        user (3),
        static (4)
    }
    ACCESS read-only
    STATUS mandatory
    DESCRIPTION
      "Denotes the type of the attack ."
    ::=  { rsIDSSynAttackEntry 9 }

rsIDSSYNAttackRisk OBJECT-TYPE
    SYNTAX INTEGER {
	      info(1),
		  low(2),
       	  medium(3),
		  high(4)}
    ACCESS  read-write
    STATUS  mandatory
    DESCRIPTION
       "This variable indicates the risk of the attack"
	DEFVAL  {medium}
    ::=  {rsIDSSynAttackEntry 10}

rsIDSSYNVerificationType OBJECT-TYPE
    SYNTAX INTEGER {
		  ack(1),
       	  request(2)}
    ACCESS  read-write
    STATUS  mandatory
    DESCRIPTION
       "This variable indicates the verification type of the attack"
	DEFVAL  {ack}
    ::=  {rsIDSSynAttackEntry 11}


rsIDSSynAttackNextID OBJECT-TYPE
	SYNTAX INTEGER
    ACCESS read-only
    STATUS mandatory
    DESCRIPTION
		"the next attack id for syn attack"
    ::= {rsIDSSynProtection 4}


rsIDSSynProtStatus OBJECT-TYPE
	SYNTAX INTEGER {
			enable(1),
			disable(2)}
    ACCESS read-write
    STATUS mandatory
    DESCRIPTION
		"Syn Protection status"
	DEFVAL { disable }
    ::= { rsIDSSynProtection 5 }

rsIDSSynSrcMonitoring OBJECT-TYPE
	SYNTAX INTEGER (1..100000)
    ACCESS read-write
    STATUS mandatory
    DESCRIPTION
		"Syn Protection source monitoring"
	DEFVAL { 1000 }
    ::= { rsIDSSynProtection 6 }

rsIDSSynSrcSampling OBJECT-TYPE
	SYNTAX INTEGER (1..10000)
    ACCESS read-write
    STATUS mandatory
    DESCRIPTION
		"Syn Protection source monitoring"
	DEFVAL { 100 }
    ::= { rsIDSSynProtection 7 }


rsIDSSynMaliciousTableAging OBJECT-TYPE
	SYNTAX INTEGER (1..300)
    ACCESS read-write
    STATUS mandatory
    DESCRIPTION
		"Syn Protection Malicious table aging"
	DEFVAL { 240 }
    ::= { rsIDSSynProtection 8 }

rsIDSSynTrustedTableAging OBJECT-TYPE
	SYNTAX INTEGER (1..1500)
    ACCESS read-write
    STATUS mandatory
    DESCRIPTION
		"Syn Protection Trusted table aging"
	DEFVAL { 1200 }
    ::= { rsIDSSynProtection 9 }


rsIDSSynServerTableAging OBJECT-TYPE
	SYNTAX INTEGER (1..600)
    ACCESS read-write
    STATUS mandatory
    DESCRIPTION
		"Syn Protection Server table aging"
	DEFVAL { 480 }
    ::= { rsIDSSynProtection 10 }


rsIDSSynSuspeciousToMalicious OBJECT-TYPE
	SYNTAX INTEGER (1..100)
    ACCESS read-write
    STATUS mandatory
    DESCRIPTION
		"Syn Protection SuspeciousToMalicious state detection"
	DEFVAL { 5 }
    ::= { rsIDSSynProtection 11 }


rsIDSSynSuspeciousToTrusted OBJECT-TYPE
	SYNTAX INTEGER (1..100)
    ACCESS read-write
    STATUS mandatory
    DESCRIPTION
		"Syn Protection SuspeciousToTrusted state detection"
	DEFVAL { 1 }
    ::= { rsIDSSynProtection 12 }


rsIDSSynTrustedToMalicious OBJECT-TYPE
	SYNTAX INTEGER (1..100)
    ACCESS read-write
    STATUS mandatory
    DESCRIPTION
		"Syn Protection TrustedToMalicious state detection"
	DEFVAL { 50 }
    ::= { rsIDSSynProtection 13 }


rsIDSSynSessionTableFullPercent OBJECT-TYPE
	SYNTAX INTEGER (1..100)
    ACCESS read-write
    STATUS mandatory
    DESCRIPTION
		"Syn Protection TrustedToMalicious state detection"
	DEFVAL { 80 }
    ::= { rsIDSSynProtection 14 }



rsIDSSYNServersTable OBJECT-TYPE
    SYNTAX SEQUENCE OF RsIDSSynServersEntry
    ACCESS not-accessible
    STATUS  mandatory
    DESCRIPTION
      "Table containing the servers table"
    ::=  {rsIDSSynProtection 15}


rsIDSSynServersEntry OBJECT-TYPE
    SYNTAX RsIDSSynServersEntry
    ACCESS not-accessible
    STATUS  mandatory
    DESCRIPTION
       "The row definition for this table."
    INDEX { rsIDSSYNServerName , rsIDSSYNServerPort }
    ::=  { rsIDSSYNServersTable 1 }

RsIDSSynServersEntry ::= SEQUENCE {
	rsIDSSYNServerName DisplayString,
	rsIDSSYNServerPort  INTEGER,
	rsIDSSYNServerState DisplayString,
	rsIDSSYNServerActivationThreshold INTEGER,
	rsIDSSYNServerTerminationThreshold INTEGER,
	rsIDSSYNServerStableThresholdPeriod INTEGER,
	rsIDSSYNServerStatus RowStatus
}

rsIDSSYNServerName OBJECT-TYPE
    SYNTAX DisplayString (SIZE(1..29))
    ACCESS  read-write
    STATUS  mandatory
    DESCRIPTION
      "The Name for the server ."
    ::=  {rsIDSSynServersEntry 1}

rsIDSSYNServerPort OBJECT-TYPE
    SYNTAX INTEGER
    ACCESS  read-write
    STATUS  mandatory
    DESCRIPTION
       "This variable indicates server port  "
    ::=  { rsIDSSynServersEntry 2}


rsIDSSYNServerState OBJECT-TYPE
    SYNTAX DisplayString (SIZE(0..30))
    ACCESS  read-write
    STATUS  mandatory
    DESCRIPTION
      "The server protection state."
    ::=  {rsIDSSynServersEntry 3 }

rsIDSSYNServerActivationThreshold OBJECT-TYPE
    SYNTAX INTEGER (0..100000)
    ACCESS  read-write
    STATUS  mandatory
    DESCRIPTION
       "This variable indicates the activating threshold "
    DEFVAL  { 2500 }
    ::=  { rsIDSSynServersEntry 4 }


rsIDSSYNServerTerminationThreshold OBJECT-TYPE
    SYNTAX INTEGER (0..100000)
    ACCESS  read-write
    STATUS  mandatory
    DESCRIPTION
       "This variable indicates the termination threshold "
    DEFVAL  { 1500 }
    ::=  { rsIDSSynServersEntry 5 }



rsIDSSYNServerStableThresholdPeriod OBJECT-TYPE
    SYNTAX INTEGER (0..10)
    ACCESS  read-write
    STATUS  mandatory
    DESCRIPTION
       "This variable indicates the the period before the behaviour as detected as stable "
    DEFVAL  { 5 }
    ::=  { rsIDSSynServersEntry 6 }



rsIDSSYNServerStatus OBJECT-TYPE
    SYNTAX RowStatus
    ACCESS  read-write
    STATUS  mandatory
    DESCRIPTION
       "This variable indicates the administrative status of this entry.
        Used to delete an entry of this table."
    ::=  { rsIDSSynServersEntry 7 }

rsIDSSynMaliciousSourceBlockingStatus OBJECT-TYPE
	SYNTAX INTEGER {
			enable(1),
			disable(2)}
    ACCESS read-write
    STATUS mandatory
    DESCRIPTION
		"Syn Protection malicious blocking status"
	DEFVAL { enable }
    ::= { rsIDSSynProtection 16 }

rsIDSSynTrackingTime OBJECT-TYPE
	SYNTAX INTEGER (1..10)
    ACCESS read-write
    STATUS mandatory
    DESCRIPTION
		"Syn Protection global tracking time"
	DEFVAL { 5 }
    ::= { rsIDSSynProtection 17 }


rsIDSSynFpga OBJECT-TYPE
	SYNTAX INTEGER {
			enable(1),
			disable(2)}
    ACCESS read-only
    STATUS mandatory
    DESCRIPTION
		"Syn Protection FPGA status"
	DEFVAL { disable }
    ::= { rsIDSSynProtection 18 }

-- WHITE list
--
rsIDSSynSafeResetLegitRetransmitRangeMin OBJECT-TYPE
	SYNTAX INTEGER (2..14)
    ACCESS read-write
    STATUS mandatory
    DESCRIPTION
		"Syn Protection Safe Reset minimum time interval(in seconds) between reset sending and successful authentication by SYN retransmit"
	DEFVAL { 2 }
    ::= { rsIDSSynProtection 25 }


rsIDSSynSafeResetLegitRetransmitRangeMax OBJECT-TYPE
	SYNTAX INTEGER (3..15)
    ACCESS read-write
    STATUS mandatory
    DESCRIPTION
		"Syn Protection Safe Reset maximum time interval(in seconds) between reset sending and successful authentication by SYN retransmit"
	DEFVAL { 4 }
    ::= { rsIDSSynProtection 26 }
rsWhiteList OBJECT IDENTIFIER ::= { rsIDS 104 }

-- OBSOLETE!!!
rsWhiteListTable OBJECT-TYPE
    SYNTAX SEQUENCE OF RsWhiteListEntry
    ACCESS not-accessible
    STATUS  mandatory
    DESCRIPTION
      "Table containing the white list sources "
    ::=  {rsWhiteList 1}

rsWhiteListEntry OBJECT-TYPE
    SYNTAX RsWhiteListEntry
    ACCESS not-accessible
    STATUS  mandatory
    DESCRIPTION
       "The row definition for this table."
    INDEX { rsWhiteListSource }
    ::=  { rsWhiteListTable 1 }

RsWhiteListEntry ::= SEQUENCE {
    rsWhiteListSource DisplayString,
    rsWhiteListState INTEGER,
    rsWhiteListStatus RowStatus,
    rsWhiteListAllModules INTEGER,
    rsWhiteListDirection INTEGER,
    rsWhiteListSynModule INTEGER,
    rsWhiteListStatefulModule INTEGER,
    rsWhiteListScanningModule INTEGER,
    rsWhiteListSignatureModule INTEGER,
	rsWhiteListHttpFloodModule INTEGER
}

rsWhiteListSource OBJECT-TYPE
    SYNTAX DisplayString (SIZE(1..46))
    ACCESS  read-write
    STATUS  mandatory
    DESCRIPTION
      "The White list source address / range of address for the packet."
    ::=  {rsWhiteListEntry 1}

rsWhiteListState OBJECT-TYPE
    SYNTAX INTEGER {
        active(1),
        inactive(2)
    }
    ACCESS read-write
    STATUS mandatory
    DESCRIPTION
      "The white list source state."
    DEFVAL {1}
    ::=  { rsWhiteListEntry 2 }

rsWhiteListStatus OBJECT-TYPE
    SYNTAX RowStatus
    ACCESS  read-write
    STATUS  mandatory
    DESCRIPTION
       "This variable indicates the administrative status of this entry.
        Used to delete an entry of this table."
    ::=  { rsWhiteListEntry 3 }

rsWhiteListAllModules OBJECT-TYPE
    SYNTAX INTEGER {
        active(1),
        inactive(2)
    }
    ACCESS read-write
    STATUS mandatory
    DESCRIPTION
      "The White list all modules selection."
    DEFVAL {1}
    ::=  { rsWhiteListEntry 4 }

rsWhiteListDirection OBJECT-TYPE
    SYNTAX INTEGER {
        bi-direct(0),
        src(1),
		dest(2)
    }
    ACCESS read-write
    STATUS mandatory
    DESCRIPTION
      "The White list classification direction ."
    DEFVAL {0}
    ::=  { rsWhiteListEntry 5 }

rsWhiteListSynModule OBJECT-TYPE
    SYNTAX INTEGER {
        active(1),
        inactive(2)
    }
    ACCESS read-write
    STATUS mandatory
    DESCRIPTION
      "The White list Syn Protection Module state."
    DEFVAL {1}
    ::=  { rsWhiteListEntry 6 }

rsWhiteListStatefulModule OBJECT-TYPE
    SYNTAX INTEGER {
        active(1),
        inactive(2)
    }
    ACCESS read-write
    STATUS mandatory
    DESCRIPTION
      "The White list Stateful Module state."
    DEFVAL {1}
    ::=  { rsWhiteListEntry 7 }

rsWhiteListScanningModule OBJECT-TYPE
    SYNTAX INTEGER {
        active(1),
        inactive(2)
    }
    ACCESS read-write
    STATUS mandatory
    DESCRIPTION
      "The White list Scanning Module state."
    DEFVAL {1}
    ::=  { rsWhiteListEntry 8 }

rsWhiteListSignatureModule OBJECT-TYPE
    SYNTAX INTEGER {
        active(1),
        inactive(2)
    }
    ACCESS read-write
    STATUS mandatory
    DESCRIPTION
      "The White list Signature Module state."
    DEFVAL {1}
    ::=  { rsWhiteListEntry 9 }

rsWhiteListHttpFloodModule OBJECT-TYPE
    SYNTAX INTEGER {
        active(1),
        inactive(2)
    }
    ACCESS read-write
    STATUS mandatory
    DESCRIPTION
      "The White list Http Flood Module state."
    DEFVAL {1}
    ::=  { rsWhiteListEntry 10 }



rsNewWhiteListTable OBJECT-TYPE
    SYNTAX SEQUENCE OF RsNewWhiteListEntry
    ACCESS not-accessible
    STATUS  mandatory
    DESCRIPTION
      "Table containing the white list sources "
    ::=  {rsWhiteList 2}

rsNewWhiteListEntry OBJECT-TYPE
    SYNTAX RsNewWhiteListEntry
    ACCESS not-accessible
    STATUS  mandatory
    DESCRIPTION
       "The row definition for this table."
    INDEX { rsNewWhiteListName }
    ::=  { rsNewWhiteListTable 1 }

RsNewWhiteListEntry ::= SEQUENCE {
	rsNewWhiteListName DisplayString,
    rsNewWhiteListSrcNetwork DisplayString,
    rsNewWhiteListDstNetwork DisplayString,
    rsNewWhiteListSrcPortGroup DisplayString,
    rsNewWhiteListDstPortGroup DisplayString,
    rsNewWhiteListPhysicalPort DisplayString,
    rsNewWhiteListVLANTag DisplayString,
	rsNewWhiteListProtocol INTEGER,
    rsNewWhiteListState INTEGER,
    rsNewWhiteListDirection INTEGER,
	rsNewWhiteListAction INTEGER,
	rsNewWhiteListReportAction INTEGER,
    rsNewWhiteListDescription DisplayString,
    rsNewWhiteListStatus RowStatus,
    rsNewWhiteListAllModules INTEGER,
    rsNewWhiteListSynModule INTEGER,
    rsNewWhiteListStatefulModule INTEGER,
    rsNewWhiteListScanningModule INTEGER,
    rsNewWhiteListSignatureModule INTEGER,
	rsNewWhiteListHttpFloodModule INTEGER,
	rsNewWhiteListServerCrackingModule INTEGER
}

rsNewWhiteListName OBJECT-TYPE
    SYNTAX DisplayString (SIZE(1..29))
    ACCESS  read-write
    STATUS  mandatory
    DESCRIPTION
      "The White list attack name."
    ::=  {rsNewWhiteListEntry 1}

rsNewWhiteListSrcNetwork OBJECT-TYPE
    SYNTAX DisplayString (SIZE(0..46))
    ACCESS  read-write
    STATUS  mandatory
    DESCRIPTION
      "The White list source address / range of address for the packet."
    DEFVAL { "any" }
    ::=  {rsNewWhiteListEntry 2}

rsNewWhiteListDstNetwork OBJECT-TYPE
    SYNTAX DisplayString (SIZE(0..46))
    ACCESS  read-write
    STATUS  mandatory
    DESCRIPTION
      "The White list destination address / range of address for the packet."
    ::=  {rsNewWhiteListEntry 3}

rsNewWhiteListSrcPortGroup OBJECT-TYPE
    SYNTAX DisplayString (SIZE(0..29))
    ACCESS  read-write
    STATUS  mandatory
    DESCRIPTION
      "The White list source port / port group for the packet."
    ::=  {rsNewWhiteListEntry 4}

rsNewWhiteListDstPortGroup OBJECT-TYPE
    SYNTAX DisplayString (SIZE(0..29))
    ACCESS  read-write
    STATUS  mandatory
    DESCRIPTION
      "The White list destinatin port / port group for the packet."
    ::=  {rsNewWhiteListEntry 5}

rsNewWhiteListPhysicalPort OBJECT-TYPE
    SYNTAX DisplayString (SIZE(0..29))
    ACCESS  read-write
    STATUS  mandatory
    DESCRIPTION
      "The White list physical port group for the packet."
    ::=  {rsNewWhiteListEntry 6}

rsNewWhiteListVLANTag OBJECT-TYPE
    SYNTAX DisplayString (SIZE(0..29))
    ACCESS  read-write
    STATUS  mandatory
    DESCRIPTION
      "The White list VLAN tags group for the packet."
    ::=  {rsNewWhiteListEntry 7}

rsNewWhiteListProtocol OBJECT-TYPE
    SYNTAX INTEGER {
        any(0),
		tcp(1),
		udp(2),
		icmp(3),
		igmp(4),
		sctp(5),
		gre(6),
		icmpv6(7),
		l2tp(8),
		gtp(9),
        ipInip(10)
    }
    ACCESS read-write
    STATUS mandatory
    DESCRIPTION
      "The white list protocol."
    DEFVAL {0}
    ::=  { rsNewWhiteListEntry 8 }

rsNewWhiteListState OBJECT-TYPE
    SYNTAX INTEGER {
        active(1),
        inactive(2)
    }
    ACCESS read-write
    STATUS mandatory
    DESCRIPTION
      "The white list source state."
    DEFVAL {1}
    ::=  { rsNewWhiteListEntry 9 }


rsNewWhiteListDirection OBJECT-TYPE
    SYNTAX INTEGER {
        bi-direct(0),
        one-direct(1)
--		dest(2)
    }
    ACCESS read-write
    STATUS mandatory
    DESCRIPTION
      "The White list classification direction ."
    DEFVAL {1}
    ::=  { rsNewWhiteListEntry 10 }

rsNewWhiteListAction OBJECT-TYPE
    SYNTAX INTEGER {
        bypass(0),
        drop(1)
    }
    ACCESS read-only
    STATUS mandatory
    DESCRIPTION
      "The White list action."
    DEFVAL {0}
    ::=  { rsNewWhiteListEntry 11 }

rsNewWhiteListReportAction OBJECT-TYPE
    SYNTAX INTEGER {
        no-report(0),
        report(1)
    }
    ACCESS read-write
    STATUS mandatory
    DESCRIPTION
      "The White list Report Action."
    DEFVAL {1}
    ::=  { rsNewWhiteListEntry 12 }

rsNewWhiteListDescription OBJECT-TYPE
    SYNTAX DisplayString (SIZE(0..32))
    ACCESS  read-write
    STATUS  mandatory
    DESCRIPTION
      "The White list description."
    ::=  {rsNewWhiteListEntry 13}

rsNewWhiteListStatus OBJECT-TYPE
    SYNTAX RowStatus
    ACCESS  read-write
    STATUS  mandatory
    DESCRIPTION
       "This variable indicates the administrative status of this entry.
        Used to delete an entry of this table."
    ::=  { rsNewWhiteListEntry 14 }

rsNewWhiteListAllModules OBJECT-TYPE
    SYNTAX INTEGER {
        active(1),
        inactive(2)
    }
    ACCESS read-write
    STATUS mandatory
    DESCRIPTION
      "The White list all modules selection."
    DEFVAL {1}
    ::=  { rsNewWhiteListEntry 15 }

rsNewWhiteListSynModule OBJECT-TYPE
    SYNTAX INTEGER {
        active(1),
        inactive(2)
    }
    ACCESS read-write
    STATUS mandatory
    DESCRIPTION
      "The White list Syn Protection Module state."
    DEFVAL {1}
    ::=  { rsNewWhiteListEntry 16 }

rsNewWhiteListStatefulModule OBJECT-TYPE
    SYNTAX INTEGER {
        active(1),
        inactive(2)
    }
    ACCESS read-write
    STATUS mandatory
    DESCRIPTION
      "The White list Stateful Module state."
    DEFVAL {1}
    ::=  { rsNewWhiteListEntry 17 }

rsNewWhiteListScanningModule OBJECT-TYPE
    SYNTAX INTEGER {
        active(1),
        inactive(2)
    }
    ACCESS read-write
    STATUS mandatory
    DESCRIPTION
      "The White list Scanning Module state."
    DEFVAL {1}
    ::=  { rsNewWhiteListEntry 18 }

rsNewWhiteListSignatureModule OBJECT-TYPE
    SYNTAX INTEGER {
        active(1),
        inactive(2)
    }
    ACCESS read-write
    STATUS mandatory
    DESCRIPTION
      "The White list Signature Module state."
    DEFVAL {1}
    ::=  { rsNewWhiteListEntry 19 }

rsNewWhiteListHttpFloodModule OBJECT-TYPE
    SYNTAX INTEGER {
        active(1),
        inactive(2)
    }
    ACCESS read-write
    STATUS mandatory
    DESCRIPTION
      "The White list Http Flood Module state."
    DEFVAL {1}
    ::=  { rsNewWhiteListEntry 20 }

rsNewWhiteListServerCrackingModule OBJECT-TYPE
    SYNTAX INTEGER {
        active(1),
        inactive(2)
    }
    ACCESS read-write
    STATUS mandatory
    DESCRIPTION
      "The White list Server cracking Module state."
    DEFVAL {1}
    ::=  { rsNewWhiteListEntry 21 }


-- BLACK list
--

rsBlackList OBJECT IDENTIFIER ::= { rsIDS 105 }


-- OBSOLETE!!

rsBlackListTable OBJECT-TYPE
    SYNTAX SEQUENCE OF RsBlackListEntry
    ACCESS not-accessible
    STATUS  mandatory
    DESCRIPTION
      "Table containing the Black list sources "
    ::=  {rsBlackList 1}

rsBlackListEntry OBJECT-TYPE
    SYNTAX RsBlackListEntry
    ACCESS not-accessible
    STATUS  mandatory
    DESCRIPTION
       "The row definition for this table."
    INDEX { rsBlackListSource }
    ::=  { rsBlackListTable 1 }

RsBlackListEntry ::= SEQUENCE {
    rsBlackListSource DisplayString,
    rsBlackListState INTEGER,
    rsBlackListStatus RowStatus
}

rsBlackListSource OBJECT-TYPE
    SYNTAX DisplayString (SIZE(1..46))
    ACCESS  read-write
    STATUS  mandatory
    DESCRIPTION
      "The Black list source address / range of address for the packet."
    ::=  {rsBlackListEntry 1}

rsBlackListState OBJECT-TYPE
    SYNTAX INTEGER {
        active(1),
        inactive(2)
    }
    ACCESS read-write
    STATUS mandatory
    DESCRIPTION
      "The Black list source state."
    DEFVAL {1}
    ::=  { rsBlackListEntry 2 }

rsBlackListStatus OBJECT-TYPE
    SYNTAX RowStatus
    ACCESS  read-write
    STATUS  mandatory
    DESCRIPTION
       "This variable indicates the administrative status of this entry.
        Used to delete an entry of this table."
    ::=  { rsBlackListEntry 3 }

rsNewBlackListTable OBJECT-TYPE
    SYNTAX SEQUENCE OF RsNewBlackListEntry
    ACCESS not-accessible
    STATUS  mandatory
    DESCRIPTION
      "Table containing the black list sources "
    ::=  {rsBlackList 2}

rsNewBlackListPacketTraceStatus OBJECT-TYPE
    SYNTAX INTEGER {
      enable(1),
      disable(2)
   }
    ACCESS read-write
    STATUS mandatory
	DESCRIPTION
      "Packet Trace status for Black List entries "
   DEFVAL  {disable}
    ::=  {rsBlackList 3}

rsNewAccessListListsPriority OBJECT-TYPE
    SYNTAX INTEGER {
		whiteListBeforeBlackList(1),
		blackListBeforeWhiteList(2)
	}
    ACCESS  read-write
    STATUS  mandatory
    DESCRIPTION
       "This variable indicates packet reporting status for the black list rule."
	DEFVAL  {whiteListBeforeBlackList}
     ::=  {rsBlackList 4}

rsNewBlackListEntry OBJECT-TYPE
    SYNTAX RsNewBlackListEntry
    ACCESS not-accessible
    STATUS  mandatory
    DESCRIPTION
       "The row definition for this table."
    INDEX { rsNewBlackListName }
    ::=  { rsNewBlackListTable 1 }

RsNewBlackListEntry ::= SEQUENCE {
	rsNewBlackListName DisplayString,
    rsNewBlackListSrcNetwork DisplayString,
    rsNewBlackListDstNetwork DisplayString,
    rsNewBlackListSrcPortGroup DisplayString,
    rsNewBlackListDstPortGroup DisplayString,
    rsNewBlackListPhysicalPort DisplayString,
    rsNewBlackListVLANTag DisplayString,
	rsNewBlackListProtocol INTEGER,
    rsNewBlackListState INTEGER,
    rsNewBlackListDirection INTEGER,
	rsNewBlackListAction INTEGER,
	rsNewBlackListReportAction INTEGER,
	rsNewBlackListDescription DisplayString,
    rsNewBlackListStatus RowStatus,
	rsNewBlackListExpirationHour INTEGER,
	rsNewBlackListExpirationMinute INTEGER,
	rsNewBlackListCDBExpirationTime INTEGER,
	rsNewBlackListDetector DisplayString,
	rsNewBlackListDetectorSecurityModule INTEGER,
	rsNewBlackListDynamicState INTEGER,
    rsNewBlackListPacketReport INTEGER
}

rsNewBlackListName OBJECT-TYPE
    SYNTAX DisplayString (SIZE(1..29))
    ACCESS  read-write
    STATUS  mandatory
    DESCRIPTION
      "The Black list attack name."
    ::=  {rsNewBlackListEntry 1}

rsNewBlackListSrcNetwork OBJECT-TYPE
    SYNTAX DisplayString (SIZE(0..46))
    ACCESS  read-write
    STATUS  mandatory
    DESCRIPTION
      "The Black list source address / range of address for the packet."
    DEFVAL { "any" }
    ::=  {rsNewBlackListEntry 2}

rsNewBlackListDstNetwork OBJECT-TYPE
    SYNTAX DisplayString (SIZE(0..46))
    ACCESS  read-write
    STATUS  mandatory
    DESCRIPTION
      "The Black list destination address / range of address for the packet."
    DEFVAL { "any" }
    ::=  {rsNewBlackListEntry 3}

rsNewBlackListSrcPortGroup OBJECT-TYPE
    SYNTAX DisplayString (SIZE(0..29))
    ACCESS  read-write
    STATUS  mandatory
    DESCRIPTION
      "The Black list source port / port group for the packet."
    ::=  {rsNewBlackListEntry 4}

rsNewBlackListDstPortGroup OBJECT-TYPE
    SYNTAX DisplayString (SIZE(0..29))
    ACCESS  read-write
    STATUS  mandatory
    DESCRIPTION
      "The Black list destinatin port / port group for the packet."
    ::=  {rsNewBlackListEntry 5}

rsNewBlackListPhysicalPort OBJECT-TYPE
    SYNTAX DisplayString (SIZE(0..29))
    ACCESS  read-write
    STATUS  mandatory
    DESCRIPTION
      "The Black list physical port group for the packet."
    ::=  {rsNewBlackListEntry 6}

rsNewBlackListVLANTag OBJECT-TYPE
    SYNTAX DisplayString (SIZE(0..29))
    ACCESS  read-write
    STATUS  mandatory
    DESCRIPTION
      "The Black list VLAN tags group for the packet."
    ::=  {rsNewBlackListEntry 7}

rsNewBlackListProtocol OBJECT-TYPE
    SYNTAX INTEGER {
        any(0),
		tcp(1),
		udp(2),
		icmp(3),
		igmp(4),
		sctp(5),
		gre(6),
		icmpv6(7),
		l2tp(8),
		gtp(9),
        ipInip(10)
    }
    ACCESS read-write
    STATUS mandatory
    DESCRIPTION
      "The Black list protocol."
    DEFVAL {0}
    ::=  { rsNewBlackListEntry 8 }

rsNewBlackListState OBJECT-TYPE
    SYNTAX INTEGER {
        active(1),
        inactive(2)
    }
    ACCESS read-write
    STATUS mandatory
    DESCRIPTION
      "The Black list source state."
    DEFVAL {1}
    ::=  { rsNewBlackListEntry 9 }


rsNewBlackListDirection OBJECT-TYPE
    SYNTAX INTEGER {
        bi-direct(0),
        one-direct(1)
--		dest(2)
    }
    ACCESS read-write
    STATUS mandatory
    DESCRIPTION
      "The Black list classification direction ."
    DEFVAL {1}
    ::=  { rsNewBlackListEntry 10 }

rsNewBlackListAction OBJECT-TYPE
    SYNTAX INTEGER {
        bypass(0),
        drop(1)
    }
    ACCESS read-only
    STATUS mandatory
    DESCRIPTION
      "The Black list action ."
    DEFVAL {1}
    ::=  { rsNewBlackListEntry 11 }

rsNewBlackListReportAction OBJECT-TYPE
    SYNTAX INTEGER {
        no-report(0),
        report(1)
    }
    ACCESS read-write
    STATUS mandatory
    DESCRIPTION
      "The Black list report action ."
    DEFVAL {1}
    ::=  { rsNewBlackListEntry 12 }

rsNewBlackListDescription OBJECT-TYPE
    SYNTAX DisplayString (SIZE(0..32))
    ACCESS  read-write
    STATUS  mandatory
    DESCRIPTION
      "The Black list description."
    ::=  {rsNewBlackListEntry 13 }

rsNewBlackListStatus OBJECT-TYPE
    SYNTAX RowStatus
    ACCESS  read-write
    STATUS  mandatory
    DESCRIPTION
       "This variable indicates the administrative status of this entry.
        Used to delete an entry of this table."
    ::=  { rsNewBlackListEntry 14 }

rsNewBlackListExpirationHour OBJECT-TYPE
    SYNTAX INTEGER (0..2)
    ACCESS  read-write
    STATUS  mandatory
    DESCRIPTION
       "Time out for which this entry should be removed, in hours"
	DEFVAL {0}
    ::=  { rsNewBlackListEntry 15 }

rsNewBlackListExpirationMinute OBJECT-TYPE
    SYNTAX INTEGER (0..59)
    ACCESS  read-write
    STATUS  mandatory
    DESCRIPTION
       "Time out for which this entry should be removed, in minutes"
	DEFVAL {0}
    ::=  { rsNewBlackListEntry 16 }

rsNewBlackListCDBExpirationTime OBJECT-TYPE
    SYNTAX INTEGER
    ACCESS  read-write
    STATUS  mandatory
    DESCRIPTION
       "Time out for which this entry should be removed used internally in CDB"
	DEFVAL {0}
    ::=  { rsNewBlackListEntry 17 }

rsNewBlackListDetector OBJECT-TYPE
    SYNTAX DisplayString (SIZE(0..46))
    ACCESS  read-write
    STATUS  mandatory
    DESCRIPTION
      "The ip address of the device originated the threat sharing alert"
    ::=  {rsNewBlackListEntry 18}


rsNewBlackListDetectorSecurityModule OBJECT-TYPE
    SYNTAX INTEGER {
        admin(0),
		eiq(1),
		serverCrack(2),
		antiScan(3),
		connectionLimit(4),
		applicationSecurity(5),
		synProtection(6),
		httpFlood(7),
		bDoS(8),
		dnsFlood(9)
    }
    ACCESS read-write
    STATUS mandatory
    DESCRIPTION
      "The Module which originated the in-demand request."
    DEFVAL {0}
    ::=  { rsNewBlackListEntry 19}

rsNewBlackListDynamicState OBJECT-TYPE
    SYNTAX INTEGER {
        yes(1),
        no(2)
    }
    ACCESS read-write
    STATUS mandatory
    DESCRIPTION
      "The Black list entry dynamic state."
    DEFVAL {2}
    ::=  { rsNewBlackListEntry 20 }

rsNewBlackListPacketReport OBJECT-TYPE
    SYNTAX INTEGER {
			enable(1),
			disable(2)}
    ACCESS  read-write
    STATUS  mandatory
    DESCRIPTION
       "This variable indicates packet reporting status for the black list rule."
	DEFVAL  {disable}
    ::=  {rsNewBlackListEntry 21}


--
-- Connection Limiting
--

rsIDSConnectionLimit OBJECT IDENTIFIER ::= { rsIDS 106}

-- obsolete
rsIDSConnectionLimitPolicyTable OBJECT-TYPE
    SYNTAX SEQUENCE OF RsIDSConnectionLimitPolicyEntry
    ACCESS not-accessible
    STATUS  mandatory
    DESCRIPTION
      "Table containing the list of rules params for the ids"
    ::=  {rsIDSConnectionLimit 1}

rsIDSConnectionLimitPolicyEntry OBJECT-TYPE
    SYNTAX RsIDSConnectionLimitPolicyEntry
    ACCESS not-accessible
    STATUS  mandatory
    DESCRIPTION
       "The row definition for this table."
    INDEX { rsIDSConnectionLimitPolicyName }
    ::=  { rsIDSConnectionLimitPolicyTable 1 }

RsIDSConnectionLimitPolicyEntry ::= SEQUENCE {
    rsIDSConnectionLimitPolicyName DisplayString,
    rsIDSConnectionLimitPolicyProfileName DisplayString,
    rsIDSConnectionLimitPolicySource DisplayString,
    rsIDSConnectionLimitPolicyDestination DisplayString,
    rsIDSConnectionLimitPolicyDirection INTEGER,
    rsIDSConnectionLimitPolicyPortmask DisplayString,
    rsIDSConnectionLimitPolicyState INTEGER,
    rsIDSConnectionLimitPolicyStatus  RowStatus,
    rsIDSConnectionLimitPolicyVlanTagGroup DisplayString,
    rsIDSConnectionLimitPolicyAction INTEGER,
	rsIDSConnectionLimitPolicyPacketReportingStatus INTEGER
}

rsIDSConnectionLimitPolicyName OBJECT-TYPE
    SYNTAX DisplayString (SIZE(1..19))
    ACCESS  read-only
    STATUS  mandatory
    DESCRIPTION
      "The Name for the Rule."
    ::=  {rsIDSConnectionLimitPolicyEntry 1}

rsIDSConnectionLimitPolicyProfileName OBJECT-TYPE
    SYNTAX DisplayString (SIZE(1..29))
    ACCESS  read-write
    STATUS  mandatory
    DESCRIPTION
      "The Name for the Service."
    ::=  {rsIDSConnectionLimitPolicyEntry 2}

rsIDSConnectionLimitPolicySource OBJECT-TYPE
    SYNTAX DisplayString (SIZE(0..20))
    ACCESS  read-write
    STATUS  mandatory
    DESCRIPTION
      "The source address / range of address for the packet, the name is
      defined in the Objects table or can be an IP address."
    ::=  {rsIDSConnectionLimitPolicyEntry 3}

rsIDSConnectionLimitPolicyDestination OBJECT-TYPE
    SYNTAX DisplayString (SIZE(0..20))
    ACCESS  read-write
    STATUS  mandatory
    DESCRIPTION
      "The destination address / range of address for the packet, the name is
      defined in the Objects table or can be an IP address."
    ::=  {rsIDSConnectionLimitPolicyEntry 4}

rsIDSConnectionLimitPolicyDirection OBJECT-TYPE
    SYNTAX INTEGER {
              oneway(1),
              twoway(2) }
    ACCESS  read-write
    STATUS  mandatory
    DESCRIPTION
       "This variable indicates the direction of the incoming packet."
    DEFVAL { 1 }
    ::=  { rsIDSConnectionLimitPolicyEntry 5 }


rsIDSConnectionLimitPolicyPortmask OBJECT-TYPE
    SYNTAX DisplayString (SIZE(0..80))
    ACCESS  read-write
    STATUS  mandatory
    DESCRIPTION
       "The Port Group"
    ::=  { rsIDSConnectionLimitPolicyEntry 6 }

 rsIDSConnectionLimitPolicyState OBJECT-TYPE
    SYNTAX INTEGER {
              active(1),
              inactive(2) }
    ACCESS  read-write
    STATUS  mandatory
    DESCRIPTION
       "This variable indicates the state of the rule."
    DEFVAL { 1 }
    ::=  { rsIDSConnectionLimitPolicyEntry 7 }

rsIDSConnectionLimitPolicyStatus OBJECT-TYPE
    SYNTAX RowStatus
    ACCESS  read-write
    STATUS  mandatory
    DESCRIPTION
       "This variable indicates the administrative status of this entry.
        Used to delete an entry of this table."
    ::=  { rsIDSConnectionLimitPolicyEntry 8 }

rsIDSConnectionLimitPolicyVlanTagGroup OBJECT-TYPE
    SYNTAX DisplayString (SIZE(0..80))
    ACCESS  read-write
    STATUS  mandatory
    DESCRIPTION
       "The VLAN tag Group"
    ::=  { rsIDSConnectionLimitPolicyEntry 9 }

rsIDSConnectionLimitPolicyAction OBJECT-TYPE
    SYNTAX INTEGER {
        report(0),
        block(1) }
    ACCESS  read-write
    STATUS  mandatory
    DESCRIPTION
       "This variable indicates the policy action"
    ::=  { rsIDSConnectionLimitPolicyEntry 10 }


rsIDSConnectionLimitPolicyPacketReportingStatus OBJECT-TYPE
    SYNTAX INTEGER {
     enable(1),
     disable(2)
	}
    ACCESS  read-write
    STATUS  mandatory
    DESCRIPTION
       "This variable indicates the packet reporting status for the policy rule"
    ::=  { rsIDSConnectionLimitPolicyEntry 11 }


rsIDSConnectionLimitProfileTable OBJECT-TYPE
	SYNTAX SEQUENCE OF RsIDSConnectionLimitProfileEntry
	ACCESS not-accessible
	STATUS  mandatory
    DESCRIPTION
      "Table containing the list of connection limiting profiles"
    ::=  {rsIDSConnectionLimit 2}

rsIDSConnectionLimitProfileEntry OBJECT-TYPE
    SYNTAX RsIDSConnectionLimitProfileEntry
    ACCESS not-accessible
    STATUS  mandatory
    DESCRIPTION
       "The row definition for this table."
    INDEX { rsIDSConnectionLimitProfileName, rsIDSConnectionLimitProfileAttackName }
    ::=  { rsIDSConnectionLimitProfileTable 1 }

RsIDSConnectionLimitProfileEntry ::= SEQUENCE {
    rsIDSConnectionLimitProfileName DisplayString,
    rsIDSConnectionLimitProfileAttackName DisplayString,
   	rsIDSConnectionLimitProfileAttackId INTEGER,
    rsIDSConnectionLimitProfileStatus RowStatus
}

rsIDSConnectionLimitProfileName OBJECT-TYPE
    SYNTAX DisplayString (SIZE(1..29))
    ACCESS  read-only
    STATUS  mandatory
    DESCRIPTION
      "The Name of the Profile."
    ::=  {rsIDSConnectionLimitProfileEntry 1}

rsIDSConnectionLimitProfileAttackName OBJECT-TYPE
    SYNTAX DisplayString (SIZE(1..29))
    ACCESS  read-only
    STATUS  mandatory
    DESCRIPTION
      "The Connection limiting attack Name."
    ::=  {rsIDSConnectionLimitProfileEntry 2}

rsIDSConnectionLimitProfileAttackId OBJECT-TYPE
    SYNTAX INTEGER
    ACCESS read-write
    STATUS mandatory
    DESCRIPTION
      "The profile service ID. this field should not be visible to the user."
    ::=  { rsIDSConnectionLimitProfileEntry 3 }

rsIDSConnectionLimitProfileStatus OBJECT-TYPE
    SYNTAX RowStatus
    ACCESS  read-write
    STATUS  mandatory
    DESCRIPTION
       "This variable indicates the administrative status of this entry.
        Used to delete an entry of this table."
    ::=  { rsIDSConnectionLimitProfileEntry 4 }



rsIDSConnectionLimitAttackTable OBJECT-TYPE
	SYNTAX SEQUENCE OF RsIDSConnectionLimitAttackEntry
	ACCESS not-accessible
	STATUS  mandatory
    DESCRIPTION
      "Table containing the list of connection limiting attacks"
    ::=  {rsIDSConnectionLimit 3}

rsIDSConnectionLimitAttackEntry OBJECT-TYPE
    SYNTAX RsIDSConnectionLimitAttackEntry
    ACCESS not-accessible
    STATUS  mandatory
    DESCRIPTION
       "The row definition for this table."
    INDEX { rsIDSConnectionLimitAttackId }
    ::=  { rsIDSConnectionLimitAttackTable 1 }

RsIDSConnectionLimitAttackEntry ::= SEQUENCE {
	rsIDSConnectionLimitAttackId INTEGER,
	rsIDSConnectionLimitAttackName DisplayString,
	rsIDSConnectionLimitAttackAppPort DisplayString,
	rsIDSConnectionLimitAttackProtocol INTEGER,
	rsIDSConnectionLimitAttackThreshold INTEGER,
	rsIDSConnectionLimitAttackTrackingType INTEGER,
	rsIDSConnectionLimitAttackReportMode INTEGER,
	rsIDSConnectionLimitAttackPacketReport INTEGER,
	rsIDSConnectionLimitAttackRisk INTEGER,
	rsIDSConnectionLimitAttackSuspendAction INTEGER,
	rsIDSConnectionLimitAttackStatus RowStatus
}


rsIDSConnectionLimitAttackId OBJECT-TYPE
    SYNTAX INTEGER
    ACCESS  read-write
    STATUS  mandatory
    DESCRIPTION
       "This variable indicates the object type- whether it is a filter or group  "
    ::=  { rsIDSConnectionLimitAttackEntry 1}

rsIDSConnectionLimitAttackName OBJECT-TYPE
    SYNTAX DisplayString (SIZE(1..29))
    ACCESS  read-write
    STATUS  mandatory
    DESCRIPTION
      "The Name for the attack must be unique."
    ::=  {rsIDSConnectionLimitAttackEntry 2}

rsIDSConnectionLimitAttackAppPort OBJECT-TYPE
    SYNTAX DisplayString (SIZE(0..29))
    ACCESS  read-write
    STATUS  mandatory
    DESCRIPTION
      "The desteantion appliction port on which the attack is defined for."
    ::=  {rsIDSConnectionLimitAttackEntry 3}


rsIDSConnectionLimitAttackProtocol OBJECT-TYPE
    SYNTAX INTEGER {
--        ip (1),
        tcp (2),
        udp (3)
--        icmp (4),
--        nonIp (5)
    }
    ACCESS  read-write
    STATUS  mandatory
    DESCRIPTION
       "This variable indicates the protocol that the application port relate to"
	DEFVAL  {tcp}
    ::=  { rsIDSConnectionLimitAttackEntry 4}

rsIDSConnectionLimitAttackThreshold OBJECT-TYPE
    SYNTAX INTEGER (0..100000000)
    ACCESS  read-write
    STATUS  mandatory
    DESCRIPTION
       "This variable indicates the threshold "
    DEFVAL  { 50 }
    ::=  { rsIDSConnectionLimitAttackEntry 5 }


rsIDSConnectionLimitAttackTrackingType OBJECT-TYPE
    SYNTAX INTEGER {
--    drop(0),
--    reset(1),
    ncps(2),
    ncpd(3),
    ncpsd(4)
--    ncpf(5),
--    winnuke(6),
--		landattack(7),
--    synattackack(8),
--    tcpsyn(9),
--    tcpack(10),
--    tcpsynack(11),
--    tcprst(12),
--    tcpfin(13),
--    tcpelse(14),
--    fragments(15),
--    ncpsdscan(16),
--    dhcp(17),
--		ftpbounce(18),
--		bobo2k(19),
--    sampling(20),
--    ftpbounce(21)
    }
    ACCESS  read-write
    STATUS  mandatory
    DESCRIPTION
       "This variable indicates how to count  "
    ::=  { rsIDSConnectionLimitAttackEntry 6}


rsIDSConnectionLimitAttackReportMode OBJECT-TYPE
    SYNTAX INTEGER {
	    report-only(0),
	    drop(10)
	    }
    ACCESS  read-write
    STATUS  mandatory
    DESCRIPTION
       "This variable indicates the attack report mode"
    ::=  { rsIDSConnectionLimitAttackEntry 7}

rsIDSConnectionLimitAttackPacketReport OBJECT-TYPE
    SYNTAX INTEGER {
			enable(1),
			disable(2)}
    ACCESS  read-write
    STATUS  mandatory
    DESCRIPTION
       "This variable indicates the per-attack packet report"
	DEFVAL  {disable}
    ::=  {rsIDSConnectionLimitAttackEntry 8}

rsIDSConnectionLimitAttackRisk OBJECT-TYPE
    SYNTAX INTEGER {
 		  info(1),
		  low(2),
       	  medium(3),
		  high(4)}
    ACCESS  read-write
    STATUS  mandatory
    DESCRIPTION
       "This variable indicates the risk of the attack"
	DEFVAL  {medium}
    ::=  {rsIDSConnectionLimitAttackEntry 9}

rsIDSConnectionLimitAttackSuspendAction OBJECT-TYPE
    SYNTAX INTEGER {
		  none(0),
 		  sip(1),
		  sipdip(2),
		  sipdipdprt(3),
		  sipdprt(4)
--		  sipdipsprtdprt(5)
		  }
    ACCESS  read-write
    STATUS  mandatory
    DESCRIPTION
       "This variable indicates the suspend action type of the attack"
	DEFVAL  {none}
    ::=  {rsIDSConnectionLimitAttackEntry 10}

rsIDSConnectionLimitAttackStatus OBJECT-TYPE
    SYNTAX RowStatus
    ACCESS  read-write
    STATUS  mandatory
    DESCRIPTION
       "This variable indicates the administrative status of this entry.
        Used to delete an entry of this table."
    ::=  { rsIDSConnectionLimitAttackEntry 11 }


rsIDSConnectionLimitAttackNextID OBJECT-TYPE
	SYNTAX INTEGER
    ACCESS read-only
    STATUS mandatory
    DESCRIPTION
		"the next attack id for connection limit attacks"
    ::= {rsIDSConnectionLimit 4}

--
-- Signatures
--

rsIDSSignatures OBJECT IDENTIFIER ::= { rsIDS 108}

rsIDSSignaturesAttributeTypesTable OBJECT-TYPE
    SYNTAX SEQUENCE OF RsIDSSignaturesAttributeTypesEntry
    ACCESS not-accessible
    STATUS  mandatory
    DESCRIPTION
      "Table containing the list of attribute types for the signatures"
    ::=  {rsIDSSignatures 1}

rsIDSSignaturesAttributeTypesEntry OBJECT-TYPE
    SYNTAX RsIDSSignaturesAttributeTypesEntry
    ACCESS not-accessible
    STATUS  mandatory
    DESCRIPTION
       "The row definition for this table."
    INDEX { rsIDSSignaturesAttributeTypeName }
    ::=  { rsIDSSignaturesAttributeTypesTable 1 }

RsIDSSignaturesAttributeTypesEntry ::= SEQUENCE {
    rsIDSSignaturesAttributeTypeName DisplayString,
	rsIDSSignaturesAttributeTypeMultipleValuesInAttack INTEGER,
	rsIDSSignaturesAttributeTypeMultipleValuesInRule INTEGER,
	rsIDSSignaturesAttributeTypeConfigurableInStatic INTEGER,
	rsIDSSignaturesAttributeTypeMatchMethod INTEGER,
    rsIDSSignaturesAttributeTypeStatus RowStatus
}

rsIDSSignaturesAttributeTypeName OBJECT-TYPE
    SYNTAX DisplayString (SIZE(1..29))
    ACCESS  read-only
    STATUS  mandatory
    DESCRIPTION
      "The Name for the attribute type."
    ::=  {rsIDSSignaturesAttributeTypesEntry 1}

rsIDSSignaturesAttributeTypeMultipleValuesInAttack OBJECT-TYPE
    SYNTAX INTEGER {
        no (0),
        yes (1)
    }
    ACCESS read-only
    STATUS mandatory
    DESCRIPTION
      "Does attribute type allow configuration of multiple values in attack."
    ::=  { rsIDSSignaturesAttributeTypesEntry 2 }

rsIDSSignaturesAttributeTypeMultipleValuesInRule OBJECT-TYPE
    SYNTAX INTEGER {
        no (0),
        yes (1)
    }
    ACCESS read-only
    STATUS mandatory
    DESCRIPTION
      "Does attribute type allow configuration of multiple values in rule."
    ::=  { rsIDSSignaturesAttributeTypesEntry 3 }

rsIDSSignaturesAttributeTypeConfigurableInStatic OBJECT-TYPE
    SYNTAX INTEGER {
        no (0),
        yes (1)
    }
    ACCESS read-only
    STATUS mandatory
    DESCRIPTION
      "Does attribute type support configuration in static attacks."
    ::=  { rsIDSSignaturesAttributeTypesEntry 4 }

rsIDSSignaturesAttributeTypeMatchMethod OBJECT-TYPE
    SYNTAX INTEGER {
        exact (0),
        minimum (1)
    }
    ACCESS read-write
    STATUS mandatory
    DESCRIPTION
      "How attribute of this type are matched."
    ::=  { rsIDSSignaturesAttributeTypesEntry 5 }

rsIDSSignaturesAttributeTypeStatus OBJECT-TYPE
    SYNTAX RowStatus
    ACCESS  read-write
    STATUS  mandatory
    DESCRIPTION
       "This variable indicates the administrative status of this entry.
        Used to delete an entry of this table."
    ::=  { rsIDSSignaturesAttributeTypesEntry 6 }

rsIDSSignaturesAttributesTable OBJECT-TYPE
    SYNTAX SEQUENCE OF RsIDSSignaturesAttributesEntry
    ACCESS not-accessible
    STATUS  mandatory
    DESCRIPTION
      "Table containing the list of attribues for the signatures"
    ::=  {rsIDSSignatures 2}

rsIDSSignaturesAttributesEntry OBJECT-TYPE
    SYNTAX RsIDSSignaturesAttributesEntry
    ACCESS not-accessible
    STATUS  mandatory
    DESCRIPTION
       "The row definition for this table."
    INDEX { rsIDSSignaturesAttributeType,
			rsIDSSignaturesAttributeName }
    ::=  { rsIDSSignaturesAttributesTable 1 }

RsIDSSignaturesAttributesEntry ::= SEQUENCE {
    rsIDSSignaturesAttributeType DisplayString,
    rsIDSSignaturesAttributeName DisplayString,
	rsIDSSignaturesAttributeSource INTEGER,
    rsIDSSignaturesAttributeTypeId INTEGER,
    rsIDSSignaturesAttributeValue INTEGER,
    rsIDSSignaturesAttributeStatus RowStatus
}

rsIDSSignaturesAttributeType OBJECT-TYPE
    SYNTAX DisplayString (SIZE(1..29))
    ACCESS read-write
    STATUS mandatory
    DESCRIPTION
      "The type of the attribute."
    ::=  { rsIDSSignaturesAttributesEntry 1 }

rsIDSSignaturesAttributeName OBJECT-TYPE
    SYNTAX DisplayString (SIZE(1..29))
    ACCESS  read-write
    STATUS  mandatory
    DESCRIPTION
      "The Name for the Attribute."
    ::=  {rsIDSSignaturesAttributesEntry 2}

rsIDSSignaturesAttributeSource OBJECT-TYPE
    SYNTAX INTEGER {
        user (3),
        static (4)
    }
    ACCESS read-only
    STATUS mandatory
    DESCRIPTION
      "Denotes the source of the attribute."
    ::=  { rsIDSSignaturesAttributesEntry 3 }

-- used only for configuration download (where attribute tables may not be available)
rsIDSSignaturesAttributeTypeId OBJECT-TYPE
    SYNTAX INTEGER
    ACCESS read-write
    STATUS mandatory
    DESCRIPTION
      "The id of the type of the attribute."
    DEFVAL { 0 }
    ::=  { rsIDSSignaturesAttributesEntry 4 }

-- used only for configuration download (where attribute tables may not be available)
rsIDSSignaturesAttributeValue OBJECT-TYPE
    SYNTAX INTEGER
    ACCESS read-write
    STATUS mandatory
    DESCRIPTION
      "The value of the attribute."
    DEFVAL { 0 }
    ::=  { rsIDSSignaturesAttributesEntry 5 }

rsIDSSignaturesAttributeStatus OBJECT-TYPE
    SYNTAX RowStatus
    ACCESS  read-write
    STATUS  mandatory
    DESCRIPTION
       "This variable indicates the administrative status of this entry.
        Used to delete an entry of this table."
    ::=  { rsIDSSignaturesAttributesEntry 6 }

rsIDSSignaturesAttackAttributesTable OBJECT-TYPE
    SYNTAX SEQUENCE OF RsIDSSignaturesAttackAttributesEntry
    ACCESS not-accessible
    STATUS  mandatory
    DESCRIPTION
      "Table containing the list of profile params for the signatures"
    ::=  {rsIDSSignatures 3}

rsIDSSignaturesAttackAttributesEntry OBJECT-TYPE
    SYNTAX RsIDSSignaturesAttackAttributesEntry
    ACCESS not-accessible
    STATUS  mandatory
    DESCRIPTION
       "The row definition for this table."
    INDEX { rsIDSSignaturesAttackAttributeAttackId,
			rsIDSSignaturesAttackAttributeType,
			rsIDSSignaturesAttackAttributeName }
    ::=  { rsIDSSignaturesAttackAttributesTable 1 }

RsIDSSignaturesAttackAttributesEntry ::= SEQUENCE {
    rsIDSSignaturesAttackAttributeAttackId INTEGER,
    rsIDSSignaturesAttackAttributeType DisplayString,
    rsIDSSignaturesAttackAttributeName DisplayString,
    rsIDSSignaturesAttackAttributeTypeId INTEGER,
    rsIDSSignaturesAttackAttributeValue INTEGER,
    rsIDSSignaturesAttackAttributeStatus RowStatus
}

rsIDSSignaturesAttackAttributeAttackId OBJECT-TYPE
    SYNTAX INTEGER
    ACCESS read-write
    STATUS mandatory
    DESCRIPTION
      "The attack id."
    ::=  { rsIDSSignaturesAttackAttributesEntry 1 }

rsIDSSignaturesAttackAttributeType OBJECT-TYPE
    SYNTAX DisplayString (SIZE(1..29))
    ACCESS read-write
    STATUS mandatory
    DESCRIPTION
      "The type of the attribute."
    ::=  { rsIDSSignaturesAttackAttributesEntry 2 }

rsIDSSignaturesAttackAttributeName OBJECT-TYPE
    SYNTAX DisplayString (SIZE(1..29))
    ACCESS  read-write
    STATUS  mandatory
    DESCRIPTION
      "The Name for the Attribute."
    ::=  {rsIDSSignaturesAttackAttributesEntry 3}

-- used only for configuration download (where attribute tables may not be available)
rsIDSSignaturesAttackAttributeTypeId OBJECT-TYPE
    SYNTAX INTEGER
    ACCESS read-write
    STATUS mandatory
    DESCRIPTION
      "The id of the type of the attribute."
    DEFVAL { 0 }
    ::=  { rsIDSSignaturesAttackAttributesEntry 4 }

-- used only for configuration download (where attribute tables may not be available)
rsIDSSignaturesAttackAttributeValue OBJECT-TYPE
    SYNTAX INTEGER
    ACCESS read-write
    STATUS mandatory
    DESCRIPTION
      "The value of the attribute."
    DEFVAL { 0 }
    ::=  { rsIDSSignaturesAttackAttributesEntry 5 }

rsIDSSignaturesAttackAttributeStatus OBJECT-TYPE
    SYNTAX RowStatus
    ACCESS  read-write
    STATUS  mandatory
    DESCRIPTION
       "This variable indicates the administrative status of this entry.
        Used to delete an entry of this table."
    ::=  { rsIDSSignaturesAttackAttributesEntry 6 }

rsIDSSignaturesProfilesTable OBJECT-TYPE
    SYNTAX SEQUENCE OF RsIDSSignaturesProfilesEntry
    ACCESS not-accessible
    STATUS  mandatory
    DESCRIPTION
      "Table containing the list of profile params for the signatures"
    ::=  {rsIDSSignatures 4}

rsIDSSignaturesProfilesEntry OBJECT-TYPE
    SYNTAX RsIDSSignaturesProfilesEntry
    ACCESS not-accessible
    STATUS  mandatory
    DESCRIPTION
       "The row definition for this table."
    INDEX { rsIDSSignaturesProfileName,
			rsIDSSignaturesProfileRuleName,
			rsIDSSignaturesProfileRuleAttributeType,
			rsIDSSignaturesProfileRuleAttributeName}
    ::=  { rsIDSSignaturesProfilesTable 1 }

RsIDSSignaturesProfilesEntry ::= SEQUENCE {
    rsIDSSignaturesProfileName DisplayString,
    rsIDSSignaturesProfileRuleName DisplayString,
    rsIDSSignaturesProfileRuleAttributeType DisplayString,
    rsIDSSignaturesProfileRuleAttributeName DisplayString,
	rsIDSSignaturesProfileType INTEGER,
    rsIDSSignaturesProfileRuleAttributeTypeId INTEGER,
    rsIDSSignaturesProfileRuleAttributeValue INTEGER,
    rsIDSSignaturesProfileStatus RowStatus
}

rsIDSSignaturesProfileName OBJECT-TYPE
    SYNTAX DisplayString (SIZE(1..29))
    ACCESS  read-write
    STATUS  mandatory
    DESCRIPTION
      "The Name for the Profile."
    ::=  {rsIDSSignaturesProfilesEntry 1}

rsIDSSignaturesProfileRuleName OBJECT-TYPE
    SYNTAX DisplayString (SIZE(1..29))
    ACCESS read-write
    STATUS mandatory
    DESCRIPTION
      "The name of the rule."
    ::=  { rsIDSSignaturesProfilesEntry 2 }

rsIDSSignaturesProfileRuleAttributeType OBJECT-TYPE
    SYNTAX DisplayString (SIZE(1..29))
    ACCESS read-write
    STATUS mandatory
    DESCRIPTION
      "The type of the attribute."
    ::=  { rsIDSSignaturesProfilesEntry 3 }

rsIDSSignaturesProfileRuleAttributeName OBJECT-TYPE
    SYNTAX DisplayString (SIZE(1..29))
    ACCESS  read-write
    STATUS  mandatory
    DESCRIPTION
      "The value of the attribute."
    ::=  {rsIDSSignaturesProfilesEntry 4}

rsIDSSignaturesProfileType OBJECT-TYPE
    SYNTAX INTEGER {
        user (3),
        static (4)
    }
    ACCESS read-only
    STATUS mandatory
    DESCRIPTION
      "Denotes the type of the profile."
    ::=  { rsIDSSignaturesProfilesEntry 5 }

-- used only for configuration download (where attribute tables may not be available)
rsIDSSignaturesProfileRuleAttributeTypeId OBJECT-TYPE
    SYNTAX INTEGER
    ACCESS read-write
    STATUS mandatory
    DESCRIPTION
      "The id of the type of the attribute."
    DEFVAL { 0 }
    ::=  { rsIDSSignaturesProfilesEntry 6 }

-- used only for configuration download (where attribute tables may not be available)
rsIDSSignaturesProfileRuleAttributeValue OBJECT-TYPE
    SYNTAX INTEGER
    ACCESS read-write
    STATUS mandatory
    DESCRIPTION
      "The value of the attribute."
    DEFVAL { 0 }
    ::=  { rsIDSSignaturesProfilesEntry 7 }

rsIDSSignaturesProfileStatus OBJECT-TYPE
    SYNTAX RowStatus
    ACCESS  read-write
    STATUS  mandatory
    DESCRIPTION
       "This variable indicates the administrative status of this entry.
        Used to delete an entry of this table."
    ::=  { rsIDSSignaturesProfilesEntry 8 }

rsIDSSignaturesProfileAttackListTable OBJECT-TYPE
    SYNTAX SEQUENCE OF RsIDSSignaturesProfileAttackListEntry
    ACCESS not-accessible
    STATUS  mandatory
    DESCRIPTION
      "Table containing the list of attacks included in each profile"
    ::=  {rsIDSSignatures 5}

rsIDSSignaturesProfileAttackListEntry OBJECT-TYPE
    SYNTAX RsIDSSignaturesProfileAttackListEntry
    ACCESS not-accessible
    STATUS  mandatory
    DESCRIPTION
       "The row definition for this table."
    INDEX { rsIDSSignaturesProfileAttackListProfileName,
			rsIDSSignaturesProfileAttackListAttackID }
    ::=  { rsIDSSignaturesProfileAttackListTable 1 }

RsIDSSignaturesProfileAttackListEntry ::= SEQUENCE {
    rsIDSSignaturesProfileAttackListProfileName DisplayString,
    rsIDSSignaturesProfileAttackListAttackID INTEGER,
    rsIDSSignaturesProfileAttackListAttackName DisplayString,
    rsIDSSignaturesProfileAttackListStatus RowStatus
}

rsIDSSignaturesProfileAttackListProfileName OBJECT-TYPE
    SYNTAX DisplayString (SIZE(1..29))
    ACCESS  read-write
    STATUS  mandatory
    DESCRIPTION
      "The Name for the Profile."
    ::=  {rsIDSSignaturesProfileAttackListEntry 1}

rsIDSSignaturesProfileAttackListAttackID OBJECT-TYPE
    SYNTAX INTEGER
    ACCESS read-only
    STATUS mandatory
    DESCRIPTION
      "The unique ID of the attack."
    ::=  { rsIDSSignaturesProfileAttackListEntry 2 }

rsIDSSignaturesProfileAttackListAttackName OBJECT-TYPE
    SYNTAX DisplayString (SIZE(1..29))
    ACCESS  read-write
    STATUS  mandatory
    DESCRIPTION
      "The Name for the attack."
    ::=  {rsIDSSignaturesProfileAttackListEntry 3}

rsIDSSignaturesProfileAttackListStatus OBJECT-TYPE
    SYNTAX RowStatus
    ACCESS  read-write
    STATUS  mandatory
    DESCRIPTION
       "This variable indicates the administrative status of this entry.
        Used to delete an entry of this table."
    ::=  { rsIDSSignaturesProfileAttackListEntry 4 }

rsIDSSignaturesProfileAttackNumberTable OBJECT-TYPE
    SYNTAX SEQUENCE OF RsIDSSignaturesProfileAttackNumberEntry
    ACCESS not-accessible
    STATUS  mandatory
    DESCRIPTION
      "Table containing the number of attacks included in each profile."
    ::=  {rsIDSSignatures 6}

rsIDSSignaturesProfileAttackNumberEntry OBJECT-TYPE
    SYNTAX RsIDSSignaturesProfileAttackNumberEntry
    ACCESS not-accessible
    STATUS  mandatory
    DESCRIPTION
       "The row definition for this table."
    INDEX { rsIDSSignaturesProfileAttackNumberProfileName }
    ::=  { rsIDSSignaturesProfileAttackNumberTable 1 }

RsIDSSignaturesProfileAttackNumberEntry ::= SEQUENCE {
    rsIDSSignaturesProfileAttackNumberProfileName DisplayString,
    rsIDSSignaturesProfileAttackNumberAttackNumber INTEGER,
    rsIDSSignaturesProfileAttackNumberStatus RowStatus
}

rsIDSSignaturesProfileAttackNumberProfileName OBJECT-TYPE
    SYNTAX DisplayString (SIZE(1..29))
    ACCESS  read-write
    STATUS  mandatory
    DESCRIPTION
      "The Name for the Profile."
    ::=  {rsIDSSignaturesProfileAttackNumberEntry 1}

rsIDSSignaturesProfileAttackNumberAttackNumber OBJECT-TYPE
    SYNTAX INTEGER
    ACCESS read-only
    STATUS mandatory
    DESCRIPTION
      "The number of attacks included in the profile."
    ::=  { rsIDSSignaturesProfileAttackNumberEntry 2 }

rsIDSSignaturesProfileAttackNumberStatus OBJECT-TYPE
    SYNTAX RowStatus
    ACCESS  read-write
    STATUS  mandatory
    DESCRIPTION
       "This variable indicates the administrative status of this entry.
        Used to delete an entry of this table."
    ::=  { rsIDSSignaturesProfileAttackNumberEntry 3 }

rsIDSSignaturesRuleAttackListTable OBJECT-TYPE
    SYNTAX SEQUENCE OF RsIDSSignaturesRuleAttackListEntry
    ACCESS not-accessible
    STATUS  mandatory
    DESCRIPTION
      "Table containing the list of attacks included in each profile"
    ::=  {rsIDSSignatures 7}

rsIDSSignaturesRuleAttackListEntry OBJECT-TYPE
    SYNTAX RsIDSSignaturesRuleAttackListEntry
    ACCESS not-accessible
    STATUS  mandatory
    DESCRIPTION
       "The row definition for this table."
    INDEX { rsIDSSignaturesRuleAttackListProfileName,
			rsIDSSignaturesRuleAttackListRuleName,
			rsIDSSignaturesRuleAttackListAttackID }
    ::=  { rsIDSSignaturesRuleAttackListTable 1 }

RsIDSSignaturesRuleAttackListEntry ::= SEQUENCE {
    rsIDSSignaturesRuleAttackListProfileName DisplayString,
    rsIDSSignaturesRuleAttackListRuleName DisplayString,
    rsIDSSignaturesRuleAttackListAttackID INTEGER,
    rsIDSSignaturesRuleAttackListAttackName DisplayString,
    rsIDSSignaturesRuleAttackListStatus RowStatus
}

rsIDSSignaturesRuleAttackListProfileName OBJECT-TYPE
    SYNTAX DisplayString (SIZE(1..29))
    ACCESS  read-write
    STATUS  mandatory
    DESCRIPTION
      "The Name for the Profile."
    ::=  {rsIDSSignaturesRuleAttackListEntry 1}

rsIDSSignaturesRuleAttackListRuleName OBJECT-TYPE
    SYNTAX DisplayString (SIZE(1..29))
    ACCESS read-only
    STATUS mandatory
    DESCRIPTION
      "The name of the rule."
    ::=  { rsIDSSignaturesRuleAttackListEntry 2 }

rsIDSSignaturesRuleAttackListAttackID OBJECT-TYPE
    SYNTAX INTEGER
    ACCESS read-only
    STATUS mandatory
    DESCRIPTION
      "The unique ID of the attack."
    ::=  { rsIDSSignaturesRuleAttackListEntry 3 }

rsIDSSignaturesRuleAttackListAttackName OBJECT-TYPE
    SYNTAX DisplayString (SIZE(1..29))
    ACCESS  read-write
    STATUS  mandatory
    DESCRIPTION
      "The Name for the attack."
    ::=  {rsIDSSignaturesRuleAttackListEntry 4}

rsIDSSignaturesRuleAttackListStatus OBJECT-TYPE
    SYNTAX RowStatus
    ACCESS  read-write
    STATUS  mandatory
    DESCRIPTION
       "This variable indicates the administrative status of this entry.
        Used to delete an entry of this table."
    ::=  { rsIDSSignaturesRuleAttackListEntry 5 }

rsIDSSignaturesRuleAttackNumberTable OBJECT-TYPE
    SYNTAX SEQUENCE OF RsIDSSignaturesRuleAttackNumberEntry
    ACCESS not-accessible
    STATUS  mandatory
    DESCRIPTION
      "Table containing the number of attacks included in each profile."
    ::=  {rsIDSSignatures 8}

rsIDSSignaturesRuleAttackNumberEntry OBJECT-TYPE
    SYNTAX RsIDSSignaturesRuleAttackNumberEntry
    ACCESS not-accessible
    STATUS  mandatory
    DESCRIPTION
       "The row definition for this table."
    INDEX { rsIDSSignaturesRuleAttackNumberProfileName,
			rsIDSSignaturesRuleAttackNumberRuleName }
    ::=  { rsIDSSignaturesRuleAttackNumberTable 1 }

RsIDSSignaturesRuleAttackNumberEntry ::= SEQUENCE {
    rsIDSSignaturesRuleAttackNumberProfileName DisplayString,
    rsIDSSignaturesRuleAttackNumberRuleName DisplayString,
    rsIDSSignaturesRuleAttackNumberAttackNumber INTEGER,
    rsIDSSignaturesRuleAttackNumberStatus RowStatus
}

rsIDSSignaturesRuleAttackNumberProfileName OBJECT-TYPE
    SYNTAX DisplayString (SIZE(1..29))
    ACCESS  read-write
    STATUS  mandatory
    DESCRIPTION
      "The Name for the Profile."
    ::=  {rsIDSSignaturesRuleAttackNumberEntry 1}

rsIDSSignaturesRuleAttackNumberRuleName OBJECT-TYPE
    SYNTAX DisplayString (SIZE(1..29))
    ACCESS read-only
    STATUS mandatory
    DESCRIPTION
      "The ordinal number of the rule."
    ::=  { rsIDSSignaturesRuleAttackNumberEntry 2 }

rsIDSSignaturesRuleAttackNumberAttackNumber OBJECT-TYPE
    SYNTAX INTEGER
    ACCESS read-only
    STATUS mandatory
    DESCRIPTION
      "The number of attacks included in the rule."
    ::=  { rsIDSSignaturesRuleAttackNumberEntry 3 }

rsIDSSignaturesRuleAttackNumberStatus OBJECT-TYPE
    SYNTAX RowStatus
    ACCESS  read-write
    STATUS  mandatory
    DESCRIPTION
       "This variable indicates the administrative status of this entry.
        Used to delete an entry of this table."
    ::=  { rsIDSSignaturesRuleAttackNumberEntry 4 }

rsIDSSignaturesAttributeAttackListTable OBJECT-TYPE
    SYNTAX SEQUENCE OF RsIDSSignaturesAttributeAttackListEntry
    ACCESS not-accessible
    STATUS  mandatory
    DESCRIPTION
      "Table containing the list of attacks configured for each attribute"
    ::=  {rsIDSSignatures 9}

rsIDSSignaturesAttributeAttackListEntry OBJECT-TYPE
    SYNTAX RsIDSSignaturesAttributeAttackListEntry
    ACCESS not-accessible
    STATUS  mandatory
    DESCRIPTION
       "The row definition for this table."
    INDEX { rsIDSSignaturesAttributeAttackListAttributeType,
			rsIDSSignaturesAttributeAttackListAttributeName,
			rsIDSSignaturesAttributeAttackListAttackID }
    ::=  { rsIDSSignaturesAttributeAttackListTable 1 }

RsIDSSignaturesAttributeAttackListEntry ::= SEQUENCE {
    rsIDSSignaturesAttributeAttackListAttributeType DisplayString,
    rsIDSSignaturesAttributeAttackListAttributeName DisplayString,
    rsIDSSignaturesAttributeAttackListAttackID INTEGER,
    rsIDSSignaturesAttributeAttackListAttackName DisplayString,
	rsIDSSignaturesAttributeAttackListAttackSourceType INTEGER,
    rsIDSSignaturesAttributeAttackListStatus RowStatus
}

rsIDSSignaturesAttributeAttackListAttributeType OBJECT-TYPE
    SYNTAX DisplayString (SIZE(1..29))
    ACCESS read-write
    STATUS mandatory
    DESCRIPTION
      "The type of the attribute."
    ::=  { rsIDSSignaturesAttributeAttackListEntry 1}

rsIDSSignaturesAttributeAttackListAttributeName OBJECT-TYPE
    SYNTAX DisplayString (SIZE(1..29))
    ACCESS  read-write
    STATUS  mandatory
    DESCRIPTION
      "The Name for the Attribute."
    ::=  {rsIDSSignaturesAttributeAttackListEntry 2}

rsIDSSignaturesAttributeAttackListAttackID OBJECT-TYPE
    SYNTAX INTEGER
    ACCESS read-only
    STATUS mandatory
    DESCRIPTION
      "The unique ID of the attack."
    ::=  { rsIDSSignaturesAttributeAttackListEntry 3 }

rsIDSSignaturesAttributeAttackListAttackName OBJECT-TYPE
    SYNTAX DisplayString (SIZE(1..29))
    ACCESS  read-write
    STATUS  mandatory
    DESCRIPTION
      "The Name for the attack."
    ::=  {rsIDSSignaturesAttributeAttackListEntry 4}

rsIDSSignaturesAttributeAttackListAttackSourceType OBJECT-TYPE
    SYNTAX INTEGER {
        user (3),
        static (4)
    }
    ACCESS read-only
    STATUS mandatory
    DESCRIPTION
      "Denotes the type of the attack."
    ::=  {rsIDSSignaturesAttributeAttackListEntry 5}

rsIDSSignaturesAttributeAttackListStatus OBJECT-TYPE
    SYNTAX RowStatus
    ACCESS  read-write
    STATUS  mandatory
    DESCRIPTION
       "This variable indicates the administrative status of this entry.
        Used to delete an entry of this table."
    ::=  { rsIDSSignaturesAttributeAttackListEntry 6 }

rsIDSSignaturesAttributeAttackNumberTable OBJECT-TYPE
    SYNTAX SEQUENCE OF RsIDSSignaturesAttributeAttackNumberEntry
    ACCESS not-accessible
    STATUS  mandatory
    DESCRIPTION
      "Table containing the number of attacks configured for each attribute"
    ::=  {rsIDSSignatures 10}

rsIDSSignaturesAttributeAttackNumberEntry OBJECT-TYPE
    SYNTAX RsIDSSignaturesAttributeAttackNumberEntry
    ACCESS not-accessible
    STATUS  mandatory
    DESCRIPTION
       "The row definition for this table."
    INDEX { rsIDSSignaturesAttributeAttackNumberAttributeType,
			rsIDSSignaturesAttributeAttackNumberAttributeName }
    ::=  { rsIDSSignaturesAttributeAttackNumberTable 1 }

RsIDSSignaturesAttributeAttackNumberEntry ::= SEQUENCE {
    rsIDSSignaturesAttributeAttackNumberAttributeType DisplayString,
    rsIDSSignaturesAttributeAttackNumberAttributeName DisplayString,
    rsIDSSignaturesAttributeAttackNumberAttackNumber INTEGER,
    rsIDSSignaturesAttributeAttackNumberStatus RowStatus
}

rsIDSSignaturesAttributeAttackNumberAttributeType OBJECT-TYPE
    SYNTAX DisplayString (SIZE(1..29))
    ACCESS read-write
    STATUS mandatory
    DESCRIPTION
      "The type of the attribute."
    ::=  { rsIDSSignaturesAttributeAttackNumberEntry 1}

rsIDSSignaturesAttributeAttackNumberAttributeName OBJECT-TYPE
    SYNTAX DisplayString (SIZE(1..29))
    ACCESS  read-write
    STATUS  mandatory
    DESCRIPTION
      "The Name for the Attribute."
    ::=  {rsIDSSignaturesAttributeAttackNumberEntry 2}

rsIDSSignaturesAttributeAttackNumberAttackNumber OBJECT-TYPE
    SYNTAX INTEGER
    ACCESS read-only
    STATUS mandatory
    DESCRIPTION
      "The number of attacks included in the attribute."
    ::=  { rsIDSSignaturesAttributeAttackNumberEntry 3 }

rsIDSSignaturesAttributeAttackNumberStatus OBJECT-TYPE
    SYNTAX RowStatus
    ACCESS  read-write
    STATUS  mandatory
    DESCRIPTION
       "This variable indicates the administrative status of this entry.
        Used to delete an entry of this table."
    ::=  { rsIDSSignaturesAttributeAttackNumberEntry 5 }


-- Server protection

rsIDSServProtection OBJECT IDENTIFIER ::= { rsIDS 109 }

rsIDSServProtProfilesTable OBJECT-TYPE
    SYNTAX SEQUENCE OF RsIDSServProtProfilesEntry
    ACCESS not-accessible
    STATUS  mandatory
    DESCRIPTION
      "Table containing the list of ServProt rules params for the ids"
    ::=  {rsIDSServProtection 1}

rsIDSServProtProfilesEntry OBJECT-TYPE
    SYNTAX RsIDSServProtProfilesEntry
    ACCESS not-accessible
    STATUS  mandatory
    DESCRIPTION
       "The row definition for this table."
    INDEX { rsIDSServProtProfilesName, rsIDSServProtProfileServiceName }
    ::=  { rsIDSServProtProfilesTable 1 }

RsIDSServProtProfilesEntry ::= SEQUENCE {
    rsIDSServProtProfilesName DisplayString,
    rsIDSServProtProfileServiceName DisplayString,
    rsIDSServProtProfilesStatus RowStatus,
	rsIDSServProtProfileServiceId INTEGER,
    rsIDSServProtProfileAttackSens INTEGER,
    rsIDSServProtProfileAttackRisk INTEGER,
    rsIDSServProtProfileAction INTEGER,
	rsIDSServProtProfilePacketTraceStatus INTEGER
	}

rsIDSServProtProfilesName OBJECT-TYPE
    SYNTAX DisplayString (SIZE(1..29))
    ACCESS  read-only
    STATUS  mandatory
    DESCRIPTION
      "The Name for the Profile."
    ::=  {rsIDSServProtProfilesEntry 1}

rsIDSServProtProfileServiceName OBJECT-TYPE
    SYNTAX DisplayString (SIZE(1..29))
    ACCESS  read-only
    STATUS  mandatory
    DESCRIPTION
      "The Name for the Service."
    ::=  {rsIDSServProtProfilesEntry 2}


rsIDSServProtProfilesStatus OBJECT-TYPE
    SYNTAX RowStatus
    ACCESS  read-write
    STATUS  mandatory
    DESCRIPTION
       "This variable indicates the administrative status of this entry.
        Used to delete an entry of this table."
    ::=  { rsIDSServProtProfilesEntry 3 }

rsIDSServProtProfileServiceId OBJECT-TYPE
    SYNTAX INTEGER
    ACCESS read-write
    STATUS mandatory
    DESCRIPTION
      "The profile service ID. this field should not be visible to the user."
    ::=  { rsIDSServProtProfilesEntry 4 }

rsIDSServProtProfileAttackSens OBJECT-TYPE
    SYNTAX INTEGER {
		  high(0),
       	  medium(1),
		  low(2),
		  minor(3)
	}
    ACCESS read-write
    STATUS mandatory
    DESCRIPTION
      "The sensitivity of the attack in the profile."
    ::=  { rsIDSServProtProfilesEntry 5 }

rsIDSServProtProfileAttackRisk OBJECT-TYPE
    SYNTAX INTEGER {
		  info(1),
		  low(2),
       	  medium(3),
		  high(4)
	}
    ACCESS read-write
    STATUS mandatory
    DESCRIPTION
      "The risk of the attack in the profile."
    ::=  { rsIDSServProtProfilesEntry 6 }

rsIDSServProtProfileAction OBJECT-TYPE
    SYNTAX INTEGER {
        report(0),
        block(1) }
    ACCESS  read-write
    STATUS  mandatory
    DESCRIPTION
       "This variable indicates the profile action"
    ::=  { rsIDSServProtProfilesEntry 7 }

rsIDSServProtProfilePacketTraceStatus OBJECT-TYPE
 SYNTAX INTEGER {
      enable(1),
      disable(2)
   }
    ACCESS read-write
    STATUS mandatory
    DESCRIPTION
      "packet trace status"
   DEFVAL  {disable}
    ::= {rsIDSServProtProfilesEntry 8}

rsIDSServAttackTable OBJECT-TYPE
    SYNTAX SEQUENCE OF RsIDSServAttackEntry
    ACCESS not-accessible
    STATUS  mandatory
    DESCRIPTION
      "Table containing the list of ServProt rules params for the ids"
    ::=  {rsIDSServProtection 2}

rsIDSServAttackEntry OBJECT-TYPE
    SYNTAX RsIDSServAttackEntry
    ACCESS not-accessible
    STATUS  mandatory
    DESCRIPTION
       "The row definition for this table."
    INDEX { rsSERVAttackId }
    ::=  { rsIDSServAttackTable 1 }

RsIDSServAttackEntry ::= SEQUENCE {
	rsSERVAttackId INTEGER,
	rsSERVAttackName DisplayString,
    rsSERVAttackStatus RowStatus,
	rsSERVAttackReportMode INTEGER,
	rsSERVAttackPacketReport INTEGER,
    rsSERVAttackRisk INTEGER,
	rsSERVAttackState INTEGER,
    rsSERVAttackDirection INTEGER,
	rsSERVAttackSuspendAction INTEGER,
	rsSERVAttackTracingType INTEGER,
	rsSERVAttackCounterType INTEGER,
	rsSERVAttackFuzzyProf INTEGER,
	rsSERVAttackSensProf INTEGER
}

rsSERVAttackId OBJECT-TYPE
    SYNTAX INTEGER
    ACCESS  read-only
    STATUS  mandatory
    DESCRIPTION
       "This variable indicates the object id "
    ::=  { rsIDSServAttackEntry 1}

rsSERVAttackName OBJECT-TYPE
    SYNTAX DisplayString (SIZE(1..29))
    ACCESS  read-only
    STATUS  mandatory
    DESCRIPTION
      "The Name for the attack must be unique."
    ::=  { rsIDSServAttackEntry 2 }

rsSERVAttackStatus OBJECT-TYPE
    SYNTAX RowStatus
    ACCESS  read-only
    STATUS  mandatory
    DESCRIPTION
       "This variable indicates the administrative status of this entry.
        Used to delete an entry of this table."
    ::=  { rsIDSServAttackEntry 3 }


rsSERVAttackReportMode OBJECT-TYPE
    SYNTAX INTEGER {
		 report-only(0),
	     drop(10),
	     rst-src(11),
     	 rst-dst(12),
    	 rst-bi(13)}
    ACCESS  read-only
    STATUS  mandatory
    DESCRIPTION
       "This variable indicates the attack report mode"
    ::=  { rsIDSServAttackEntry 4}

rsSERVAttackPacketReport OBJECT-TYPE
    SYNTAX INTEGER {
			enable(1),
			disable(2)}
    ACCESS  read-only
    STATUS  mandatory
    DESCRIPTION
       "This variable indicates the per-attack packet report"
	DEFVAL  {disable}
    ::=  {rsIDSServAttackEntry 5}

rsSERVAttackRisk OBJECT-TYPE
    SYNTAX INTEGER {
		  info(1),
		  low(2),
       	  medium(3),
		  high(4)}
    ACCESS  read-only
    STATUS  mandatory
    DESCRIPTION
       "This variable indicates the risk of the attack"
	DEFVAL  {medium}
    ::=  {rsIDSServAttackEntry 6}

rsSERVAttackState OBJECT-TYPE
    SYNTAX INTEGER {
			enable(1),
			disable(2)}
    ACCESS  read-only
    STATUS  mandatory
    DESCRIPTION
       "This variable indicates whether the attack should be classified or not "
    DEFVAL  { enable }
    ::=  { rsIDSServAttackEntry 7 }

rsSERVAttackDirection OBJECT-TYPE
    SYNTAX INTEGER {
		  inoutbound(0),
       	  inbound(1),
		  outbound(2)}
    ACCESS  read-only
    STATUS  mandatory
    DESCRIPTION
       "This variable indicates the direction of the attack"
	DEFVAL  {inoutbound}
    ::=  {rsIDSServAttackEntry 8}

rsSERVAttackSuspendAction OBJECT-TYPE
    SYNTAX INTEGER {
		  none(0),
       	  sip(1),
		  sipdip(2),
		  sipdprt(3),
		  sipdipdprt(4),
		  sipdipsprtdprt(5)
		  }
    ACCESS  read-only
    STATUS  mandatory
    DESCRIPTION
       "This variable indicates the suspend action type of the attack"
	DEFVAL  {sipdipsprtdprt}
    ::=  {rsIDSServAttackEntry 9}

rsSERVAttackTracingType OBJECT-TYPE
    SYNTAX INTEGER {
		  ip-only(0),
       	  ip-session(1)
		  }
    ACCESS  read-only
    STATUS  mandatory
    DESCRIPTION
       "This variable indicates the tracing type of the attack"
	DEFVAL  {ip-only}
    ::=  {rsIDSServAttackEntry 10}

rsSERVAttackCounterType OBJECT-TYPE
    SYNTAX INTEGER {
		  linear(0),
       	  iir(1)
		  }
    ACCESS  read-only
    STATUS  mandatory
    DESCRIPTION
       "This variable indicates the counter type of the attack"
	DEFVAL  {linear}
    ::=  {rsIDSServAttackEntry 11}

rsSERVAttackFuzzyProf OBJECT-TYPE
    SYNTAX INTEGER {
		  app-scan(0),
       	  brute-force(1)
		  }
    ACCESS  read-only
    STATUS  mandatory
    DESCRIPTION
       "This variable indicates the fuzzy profile of the attack"
	DEFVAL  {app-scan}
    ::=  {rsIDSServAttackEntry 12}

rsSERVAttackSensProf OBJECT-TYPE
    SYNTAX INTEGER {
		  high(0),
       	  medium(1),
		  low(2),
		  minor(3)
		  }
    ACCESS  read-only
    STATUS  mandatory
    DESCRIPTION
       "This variable indicates the sensitivity of the attack"
	DEFVAL  {high}
    ::=  {rsIDSServAttackEntry 13}


rsIDSServProtCntTableSize OBJECT-TYPE
SYNTAX INTEGER
    ACCESS read-write
    STATUS mandatory
    DESCRIPTION
      "the SERVPROT table size"
    ::= {rsIDSServProtection 3}

rsIDSServProtCntTableSizeAfterReset OBJECT-TYPE
    SYNTAX INTEGER
    ACCESS read-write
    STATUS mandatory
    DESCRIPTION
      "the SERVPROT after-reset table size"
    ::= {rsIDSServProtection 4}

rsIDSServProtSipTrackingType OBJECT-TYPE
    SYNTAX INTEGER {
		sip-uri(1),
		source-ip(2),
		both(3)	}
    ACCESS read-write
    STATUS mandatory
    DESCRIPTION
      "SIP-Crack protection tracking method (SIP-URI Only, IP Only, Both)"
	DEFVAL  {sip-uri}
    ::= {rsIDSServProtection 5}

rsIDSServProtSipResetCode OBJECT-TYPE
    SYNTAX INTEGER {
		forbidden(403),
		not-found(404),
		not-acceptable-error(406),
		temporarily-unavailable(480),
		ambiguous(485),
		busy-here(486),
		request-terminated(487),
		not-acceptable-here(488),
		busy-everywhere(600),
		decline(603),
		not-acceptable-fail(606) }
    ACCESS read-write
    STATUS mandatory
    DESCRIPTION
      "SIP reply code to the attacker during SIP-TCP blocking"
    DEFVAL {not-acceptable-error}
    ::= {rsIDSServProtection 6}

rsIDSServProtSipServerOrig OBJECT-TYPE
    SYNTAX INTEGER {
			enable(1),
			disable(2)
			}
    ACCESS read-write
    STATUS mandatory
    DESCRIPTION
      "SIP Server Originated Sessions"
    DEFVAL {2}
    ::= {rsIDSServProtection 7}

rsIDSServProtSipEnableURIinTCP OBJECT-TYPE
    SYNTAX INTEGER {
			enable(1),
			disable(2)
			}
    ACCESS read-write
    STATUS mandatory
    DESCRIPTION
      "SIP Server Uri in Tcp"
    DEFVAL {2}
    ::= {rsIDSServProtection 8}

-- Immediate Checks

rsIDSImmediateChecks OBJECT IDENTIFIER ::= { rsIDS 110 }

rsIDSImmediateChecksAttackTable OBJECT-TYPE
	SYNTAX SEQUENCE OF RsIDSImmediateChecksAttackEntry
	ACCESS not-accessible
	STATUS  mandatory
    DESCRIPTION
      "Table containing the list of immediate chacks"
    ::=  {rsIDSImmediateChecks 1}

	rsIDSImmediateChecksPacketTraceStatus OBJECT-TYPE
	SYNTAX INTEGER {
			enable(1),
			disable(2)
			}
    ACCESS read-write
    STATUS mandatory
    DESCRIPTION
      "Packet Trace status for Immediate Checks "
    DEFVAL {2}
    ::=  {rsIDSImmediateChecks 2}

rsIDSImmediateChecksAttackEntry OBJECT-TYPE
    SYNTAX RsIDSImmediateChecksAttackEntry
    ACCESS not-accessible
    STATUS  mandatory
    DESCRIPTION
       "The row definition for this table."
    INDEX { rsIDSImmChkId }
    ::=  { rsIDSImmediateChecksAttackTable 1 }

RsIDSImmediateChecksAttackEntry ::= SEQUENCE {
	rsIDSImmChkId INTEGER,
	rsIDSImmChkName DisplayString,
	rsIDSImmChkAction INTEGER,
	rsIDSImmChkRisk INTEGER,
	rsIDSImmChkStatus RowStatus,
	rsIDSImmChkReportAction INTEGER
}

rsIDSImmChkId OBJECT-TYPE
    SYNTAX INTEGER
    ACCESS  read-only
    STATUS  mandatory
    DESCRIPTION
       "This variable idex of the immediate check"
    ::=  { rsIDSImmediateChecksAttackEntry 1}

rsIDSImmChkName OBJECT-TYPE
    SYNTAX DisplayString (SIZE(0..80))
    ACCESS  read-only
    STATUS  mandatory
    DESCRIPTION
      "The Name for the immediate check."
    ::=  {rsIDSImmediateChecksAttackEntry 2}

rsIDSImmChkAction OBJECT-TYPE
    SYNTAX INTEGER {
			no-report(0),
			report(1),
			block(2)}
    ACCESS  read-write
    STATUS  mandatory
    DESCRIPTION
      "The immediate check attack action."
    ::=  {rsIDSImmediateChecksAttackEntry 3}

rsIDSImmChkRisk OBJECT-TYPE
    SYNTAX INTEGER {
	  info(1),
	  low(2),
      medium(3),
	  high(4)}
    ACCESS  read-write
    STATUS  mandatory
    DESCRIPTION
       "The immediate check report mode."
    ::=  {rsIDSImmediateChecksAttackEntry 4}

rsIDSImmChkStatus OBJECT-TYPE
    SYNTAX RowStatus
    ACCESS  read-write
    STATUS  mandatory
    DESCRIPTION
       "This variable indicates the administrative status of this entry."
    ::=  { rsIDSImmediateChecksAttackEntry 5 }

rsIDSImmChkReportAction OBJECT-TYPE
    SYNTAX INTEGER {
			process(0),
			bypass(1)}
    ACCESS  read-write
    STATUS  mandatory
    DESCRIPTION
      "The immediate check report-only action."
    ::=  {rsIDSImmediateChecksAttackEntry 6}


-- EXCLUDE IP list
--

rsExcludeIp OBJECT IDENTIFIER ::= { rsIDS 111 }

rsExcludeIpTable OBJECT-TYPE
    SYNTAX SEQUENCE OF RsExcludeIpEntry
    ACCESS not-accessible
    STATUS  mandatory
    DESCRIPTION
      "Table containing the attack exclude ips  "
    ::=  {rsExcludeIp 1}

rsExcludeIpEntry OBJECT-TYPE
    SYNTAX RsExcludeIpEntry
    ACCESS not-accessible
    STATUS  mandatory
    DESCRIPTION
       "The row definition for this table."
    INDEX { rsExcludeIpAttackId }
    ::=  { rsExcludeIpTable 1 }

RsExcludeIpEntry ::= SEQUENCE {
    rsExcludeIpAttackId   INTEGER,
    rsExcludeIpAttackName DisplayString,
	rsExcludeIpSource     DisplayString,
	rsExcludeIpDest       DisplayString,
    rsExcludeIpStatus     RowStatus
}


rsExcludeIpAttackId OBJECT-TYPE
    SYNTAX INTEGER
    ACCESS read-write
    STATUS mandatory
    DESCRIPTION
      "The exclude address attack id."
    ::=  {rsExcludeIpEntry 1 }

rsExcludeIpAttackName OBJECT-TYPE
    SYNTAX DisplayString (SIZE(0..80))
    ACCESS  read-only
    STATUS  mandatory
    DESCRIPTION
      "The exclude address attack name."
    ::=  {rsExcludeIpEntry 2}

rsExcludeIpSource OBJECT-TYPE
    SYNTAX DisplayString (SIZE(0..46))
    ACCESS  read-write
    STATUS  mandatory
    DESCRIPTION
      "The exclude source address / range of address for the attack."
    ::=  {rsExcludeIpEntry 3}

rsExcludeIpDest OBJECT-TYPE
    SYNTAX DisplayString (SIZE(0..46))
    ACCESS  read-write
    STATUS  mandatory
    DESCRIPTION
      "The exclude destination address / range of address for the attack."
    ::=  {rsExcludeIpEntry 4}

rsExcludeIpStatus OBJECT-TYPE
    SYNTAX RowStatus
    ACCESS  read-write
    STATUS  mandatory
    DESCRIPTION
       "This variable indicates the administrative status of this entry.
        Used to delete an entry of this table."
    ::=  {rsExcludeIpEntry 5 }


-- Generic Signature

rsIDSGenericSignatureParams OBJECT IDENTIFIER ::= { rsIDS 113}

rsIDSGenericSignaturesMaxSize OBJECT-TYPE
SYNTAX INTEGER
    ACCESS read-only
    STATUS mandatory
    DESCRIPTION
      "the generic signnatures size"
    ::= {rsIDSGenericSignatureParams 1}

rsIDSGenericSignaturesMaxSizeAfterReset OBJECT-TYPE
    SYNTAX INTEGER
    ACCESS read-write
    STATUS mandatory
    DESCRIPTION
      "the  generic signnatures after-reset table size"
    ::= {rsIDSGenericSignatureParams 2}


rsIDSCountersReportInfoTuning OBJECT IDENTIFIER ::= { rsIDS 114}

rsIDSCountersReportInfoTableSize OBJECT-TYPE
    SYNTAX INTEGER
    ACCESS  read-only
    STATUS  mandatory
    DESCRIPTION
      "Maximal report info objects for counters use."
    ::=  { rsIDSCountersReportInfoTuning 1 }

rsIDSCountersReportInfoSizeAfterReset OBJECT-TYPE
    SYNTAX INTEGER
    ACCESS  read-write
    STATUS  mandatory
    DESCRIPTION
      "Future maximal report info objects for counters use."
    ::=  { rsIDSCountersReportInfoTuning 2 }


rsIDSSignaturesAttackAttributeStaticTable OBJECT-TYPE
    SYNTAX SEQUENCE OF RsIDSSignaturesAttackAttributeStaticEntry
    ACCESS not-accessible
    STATUS  mandatory
    DESCRIPTION
      "Table containing the number of attacks changed for each attribute"
    ::=  {rsIDSSignatures 11}

rsIDSSignaturesAttackAttributeStaticEntry OBJECT-TYPE
    SYNTAX RsIDSSignaturesAttackAttributeStaticEntry
    ACCESS not-accessible
    STATUS  mandatory
    DESCRIPTION
       "The row definition for this table."
    INDEX { rsIDSSignaturesAttackAttributeStaticAttackId,
			rsIDSSignaturesAttackAttributeStaticAttributeName }
    ::=  { rsIDSSignaturesAttackAttributeStaticTable 1 }

RsIDSSignaturesAttackAttributeStaticEntry ::= SEQUENCE {
    rsIDSSignaturesAttackAttributeStaticAttackId INTEGER,
    rsIDSSignaturesAttackAttributeStaticAttributeName DisplayString,
    rsIDSSignaturesAttackAttributeStaticAttributeId INTEGER,
    rsIDSSignaturesAttackAttributeStaticStatus RowStatus
}

rsIDSSignaturesAttackAttributeStaticAttackId OBJECT-TYPE
    SYNTAX INTEGER
    ACCESS read-write
    STATUS mandatory
    DESCRIPTION
      "The id of the attack."
    ::=  { rsIDSSignaturesAttackAttributeStaticEntry 1}

rsIDSSignaturesAttackAttributeStaticAttributeName OBJECT-TYPE
    SYNTAX DisplayString (SIZE(1..29))
    ACCESS  read-write
    STATUS  mandatory
    DESCRIPTION
      "The Name for the Attribute."
    ::=  {rsIDSSignaturesAttackAttributeStaticEntry 2}

rsIDSSignaturesAttackAttributeStaticAttributeId OBJECT-TYPE
    SYNTAX INTEGER
    ACCESS  read-write
    STATUS  mandatory
    DESCRIPTION
      "The type of the attribute."
    ::=  {rsIDSSignaturesAttackAttributeStaticEntry 3}

rsIDSSignaturesAttackAttributeStaticStatus OBJECT-TYPE
    SYNTAX RowStatus
    ACCESS  read-write
    STATUS  mandatory
    DESCRIPTION
       "This variable indicates the administrative status of this entry.
        Used to delete an entry of this table."
    ::=  { rsIDSSignaturesAttackAttributeStaticEntry 4 }

-- Application-specific traps for IDS
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------
-- obsolete
rdwrIDSNetfloodFootprintTrap TRAP-TYPE
        ENTERPRISE rsIDS
        VARIABLES  { rndErrorDesc, rndErrorSeverity }
        DESCRIPTION
             "Netflood footprint."
		::=  1


rsIDSEventTraps OBJECT IDENTIFIER ::= { rsIDS 107 }

-- Intrusion
rsIDSIntrusionEvent  OBJECT IDENTIFIER ::= { rsIDSEventTraps 1 }

rsIDSIntrusionErrorDesc OBJECT-TYPE
    SYNTAX DisplayString
    ACCESS  read-only
    STATUS  mandatory
    DESCRIPTION
       "A textual description of the enterprise-specific trap sent
        to the Network Management Station by the RND managed device."
    ::= { rsIDSIntrusionEvent 1  }

rsIDSIntrusionErrorSeverity OBJECT-TYPE
    SYNTAX INTEGER
    ACCESS  read-only
    STATUS  mandatory
    DESCRIPTION
      "The severity type of the enterprise-specific trap sent to the
      Network Management Station by the RND managed device."
    ::= { rsIDSIntrusionEvent 2  }

rsIDSIntrusionEventTrap TRAP-TYPE
        ENTERPRISE rsIDSEventTraps
        VARIABLES  { rsIDSIntrusionErrorDesc, rsIDSIntrusionErrorSeverity }
        DESCRIPTION
             "IDS intrusion event traps."
		::=  1

-- Netflood Footprint
rsIDSFootprintEvent  OBJECT IDENTIFIER ::= { rsIDSEventTraps 2 }

rsIDSFootprintErrorDesc OBJECT-TYPE
    SYNTAX DisplayString
    ACCESS  read-only
    STATUS  mandatory
    DESCRIPTION
       "A textual description of the enterprise-specific trap sent
        to the Network Management Station by the RND managed device."
    ::= { rsIDSFootprintEvent 1  }

rsIDSFootprintErrorSeverity OBJECT-TYPE
    SYNTAX INTEGER
    ACCESS  read-only
    STATUS  mandatory
    DESCRIPTION
      "The severity type of the enterprise-specific trap sent to the
      Network Management Station by the RND managed device."
    ::= { rsIDSFootprintEvent 2  }


rsIDSNetfloodFootprintTrap TRAP-TYPE
        ENTERPRISE rsIDSEventTraps
        VARIABLES  { rsIDSFootprintErrorDesc, rsIDSFootprintErrorSeverity }
        DESCRIPTION
             "Netflood footprint."
		::=  2
-- DOS Overload
rsIDSDOSOverloadEvent  OBJECT IDENTIFIER ::= { rsIDSEventTraps 3 }

rsIDSDOSOverloadErrorDesc OBJECT-TYPE
    SYNTAX DisplayString
    ACCESS  read-only
    STATUS  mandatory
    DESCRIPTION
       "A textual description of the enterprise-specific trap sent
        to the Network Management Station by the RND managed device."
    ::= { rsIDSDOSOverloadEvent 1  }

rsIDSDOSOverloadErrorSeverity OBJECT-TYPE
    SYNTAX INTEGER
    ACCESS  read-only
    STATUS  mandatory
    DESCRIPTION
      "The severity type of the enterprise-specific trap sent to the
      Network Management Station by the RND managed device."
    ::= { rsIDSDOSOverloadEvent 2  }


rsIDSDOSOverloadTrap TRAP-TYPE
        ENTERPRISE rsIDSEventTraps
        VARIABLES  { rsIDSDOSOverloadErrorDesc, rsIDSDOSOverloadErrorSeverity }
        DESCRIPTION
             "DOS overload indication."
		::=  3


-- Out of path
rsIDSOutOfPathFootPrintEvent  OBJECT IDENTIFIER ::= { rsIDSEventTraps 4 }

rsIDSOutOfPathFootPrintErrorDesc OBJECT-TYPE
    SYNTAX DisplayString
    ACCESS  read-only
    STATUS  mandatory
    DESCRIPTION
       "A textual description of the enterprise-specific trap sent
        to the Network Management Station by the RND managed device."
    ::= { rsIDSOutOfPathFootPrintEvent 1  }

rsIDSOutOfPathFootPrintErrorSeverity OBJECT-TYPE
    SYNTAX INTEGER
    ACCESS  read-only
    STATUS  mandatory
    DESCRIPTION
      "The severity type of the enterprise-specific trap sent to the
      Network Management Station by the RND managed device."
    ::= { rsIDSOutOfPathFootPrintEvent 2  }

rsIDSOutOfPathFootPrintTrap TRAP-TYPE
        ENTERPRISE rsIDSEventTraps
        VARIABLES  { rsIDSOutOfPathFootPrintErrorDesc, rsIDSOutOfPathFootPrintErrorSeverity }
        DESCRIPTION
             "Out Of Path indication."
		::=  4

-- Netflood warning trap
rsIDSNetfloodWarningEvent  OBJECT IDENTIFIER ::= { rsIDSEventTraps 5 }

rsIDSNetfloodWarningErrorDesc OBJECT-TYPE
    SYNTAX DisplayString
    ACCESS  read-only
    STATUS  mandatory
    DESCRIPTION
       "A textual description of the enterprise-specific trap sent
        to the Network Management Station by the RND managed device."
    ::= { rsIDSNetfloodWarningEvent 1  }

rsIDSNetfloodWarningErrorSeverity OBJECT-TYPE
    SYNTAX INTEGER
    ACCESS  read-only
    STATUS  mandatory
    DESCRIPTION
      "The severity type of the enterprise-specific trap sent to the
      Network Management Station by the RND managed device."
    ::= { rsIDSNetfloodWarningEvent 2  }



rsIDSNetfloodWarningTrap TRAP-TYPE
        ENTERPRISE rsIDSEventTraps
        VARIABLES  { rsIDSNetfloodWarningErrorDesc, rsIDSNetfloodWarningErrorSeverity }
        DESCRIPTION
             "Netflood related warning indication."
		::=  5


-- Anti Fraud
rsIDSAntiFraudEvent  OBJECT IDENTIFIER ::= { rsIDSEventTraps 6 }

rsIDSAntiFraudWarningTrap TRAP-TYPE
        ENTERPRISE rsIDSEventTraps
        VARIABLES  { rndErrorDesc, rndErrorSeverity }
        DESCRIPTION
             "Anti Fraud related warning indication."
		::=  6

rsIDSDnsProtWarningTrap TRAP-TYPE
        ENTERPRISE rsIDSEventTraps
        VARIABLES  { rndErrorDesc, rndErrorSeverity }
        DESCRIPTION
             "DNS protection related warning indication."
		::=  7

rsIDSAuthenticationTableTrap TRAP-TYPE
        ENTERPRISE rsIDSEventTraps
        VARIABLES  { rndErrorDesc, rndErrorSeverity }
        DESCRIPTION
             "Authentication tables related traps."
		::=  8

rsIDSScheduledAclTrap TRAP-TYPE
        ENTERPRISE rsIDSEventTraps
        VARIABLES  { rndErrorDesc, rndErrorSeverity }
        DESCRIPTION
             "scheduled acl related traps."
		::=  9

rsIDSSynProtSslAlteonWarningTrap TRAP-TYPE
        ENTERPRISE rsIDSEventTraps
        VARIABLES  { rndErrorDesc, rndErrorSeverity }
        DESCRIPTION
             "SSL Alteon related warning traps."
		::=  10

rsIDSTrafficExclusionTrap TRAP-TYPE
        ENTERPRISE rsIDSEventTraps
        VARIABLES  { rndErrorDesc, rndErrorSeverity }
        DESCRIPTION
             "Traffic Exclusion related information traps."
		::=  11

rsIDSQuarantineFullTableTrap TRAP-TYPE
        ENTERPRISE rsIDSEventTraps
        VARIABLES  { rndErrorDesc, rndErrorSeverity }
        DESCRIPTION
             "Quarantine related information traps."
		::=  12

rsIDSTrackingTableFullTableTrap TRAP-TYPE
        ENTERPRISE rsIDSEventTraps
        VARIABLES  { rndErrorDesc, rndErrorSeverity }
        DESCRIPTION
             "Tracking table related information traps."
       ::=  13

rsIDSTrackingTableNotFullTableTrap TRAP-TYPE
        ENTERPRISE rsIDSEventTraps
        VARIABLES  { rndErrorDesc, rndErrorSeverity }
        DESCRIPTION
             "Tracking table related information traps."
       ::=  14
rsIDSAntiFraudInfoTrap TRAP-TYPE
        ENTERPRISE rsIDSEventTraps
        VARIABLES  { rndErrorDesc, rndErrorSeverity }
        DESCRIPTION
             "Anti Fraud related info indication."
		::=  15

rsIDSOutOfStatePortTrap TRAP-TYPE
		ENTERPRISE rsIDSEventTraps
        VARIABLES  { rndErrorDesc, rndErrorSeverity }
        DESCRIPTION
             "Out of state related info indication."
		::=  16

-- Orc 07/02/2012 Added a MIB for Black List Any to Any rule warning trap
-- Black List Rules Traps

rsIDSBlackListRuleEvent  OBJECT IDENTIFIER ::= { rsIDSEventTraps 7 }

rsIDSBlackListRuleEventTrap TRAP-TYPE
        ENTERPRISE rsIDSEventTraps
        VARIABLES  { rndErrorDesc, rndErrorSeverity }
        DESCRIPTION
             "IDS black list rule event traps."
	::=  17


-- Service Discovery
rsIDSServiceDiscoveryEvent  OBJECT IDENTIFIER ::= { rsIDSEventTraps 8 }

rsIDSServiceDiscoveryInfoTrap TRAP-TYPE
        ENTERPRISE rsIDSEventTraps
        VARIABLES  { rndErrorDesc, rndErrorSeverity }
        DESCRIPTION
             "Service Discovery related info indication."
		::=  18


rsIDSRestoreDefaultsInfoTrap TRAP-TYPE
        ENTERPRISE rsIDSEventTraps
        VARIABLES  { rndErrorDesc, rndErrorSeverity }
        DESCRIPTION
             "restore-defaults related info indication."
		::=  19

rsIDSServerProtUpgradePerPolicyTrap TRAP-TYPE
	ENTERPRISE rsIDSEventTraps
	VARIABLES  { rndErrorDesc, rndErrorSeverity }
        DESCRIPTION
            "Server Protection Upgrade to Per Policy information trap."
       ::=  21

rsIDSServerProtPolicyInactiveTrap TRAP-TYPE
        ENTERPRISE rsIDSEventTraps
        VARIABLES  { rndErrorDesc, rndErrorSeverity }
        DESCRIPTION
             "Notify user protected server associated with the deleted policy are now disabled"
	::=  22

-- out of state
rsIDSOutOfStateXadTableFullInfoTrap TRAP-TYPE
        ENTERPRISE rsIDSEventTraps
        VARIABLES  { rndErrorDesc, rndErrorSeverity }
        DESCRIPTION
             "Out of state indication that a table is full."
		::=  23
--
-- BDoS Learning suppression
--

rsNetFloodLearningSuppressionThresholdTrap TRAP-TYPE
    ENTERPRISE rsIDSEventTraps
    VARIABLES  { rndErrorDesc, rndErrorSeverity }
    DESCRIPTION
      "Behavioural DoS learning suppression indication."
    ::=  24


rsIDSSuspendTableFullTableTrap TRAP-TYPE
        ENTERPRISE rsIDSEventTraps
        VARIABLES  { rndErrorDesc, rndErrorSeverity }
        DESCRIPTION
             "Suspend table related information traps."
       ::=  25

rsIDSSuspendTableNotFullTableTrap TRAP-TYPE
        ENTERPRISE rsIDSEventTraps
        VARIABLES  { rndErrorDesc, rndErrorSeverity }
        DESCRIPTION
             "Suspend table related information traps."
       ::=  26

-- Network Policy
rsIDSNetworkPolicyEvent  OBJECT IDENTIFIER ::= { rsIDSEventTraps 9 }

rsIDSServProtPolicyInactiveErrorDesc OBJECT-TYPE
    SYNTAX DisplayString
    ACCESS  read-only
    STATUS  mandatory
    DESCRIPTION
       "A textual description of the enterprise-specific trap sent
        to the Network Management Station by the RND managed device."
    ::= { rsIDSNetworkPolicyEvent 1  }

rsIDSServProtPolicyInactiveErrorSeverity OBJECT-TYPE
    SYNTAX INTEGER
    ACCESS  read-only
    STATUS  mandatory
    DESCRIPTION
      "The severity type of the enterprise-specific trap sent to the
      Network Management Station by the RND managed device."
    ::= { rsIDSNetworkPolicyEvent 2  }

--
-- Http Floods
--


rsHttpFlood OBJECT IDENTIFIER ::= { rsIDS 115 }


--- Servers are obsolete!

rsHTTPFServerTable OBJECT-TYPE
    SYNTAX SEQUENCE OF RsHTTPFServerEntry
    ACCESS not-accessible
    STATUS  mandatory
    DESCRIPTION
      "Table containing the server list and configuration for HTTP flood module"
    ::=  {rsHttpFlood 1}

rsHTTPFServerEntry OBJECT-TYPE
    SYNTAX RsHTTPFServerEntry
    ACCESS not-accessible
    STATUS  mandatory
    DESCRIPTION
       "The row definition for this table."
    INDEX { rsHTTPFServerName }
    ::=  { rsHTTPFServerTable 1 }


RsHTTPFServerEntry ::= SEQUENCE {
    rsHTTPFServerName DisplayString,
    rsHTTPFServerIp DisplayString,
    rsHTTPFServerSensitivity INTEGER,
    rsHTTPFServerAction INTEGER,
    rsHTTPFServerPacketReport INTEGER,
    rsHTTPFServerSetManTriggers INTEGER,
    rsHTTPFServerGetPostTrs INTEGER,
    rsHTTPFServerOtherTrs INTEGER,
    rsHTTPFServerOutboundBandwidth INTEGER,
    rsHTTPFServerRequestsPerSource INTEGER,
    rsHTTPFServerRequestsPerConnection INTEGER,
    rsHTTPFServerStatus  RowStatus,
    rsHTTPFServerUriOnlyMitigation INTEGER
}

rsHTTPFServerName OBJECT-TYPE
    SYNTAX DisplayString (SIZE(1..19))
    ACCESS  read-only
    STATUS  mandatory
    DESCRIPTION
      "The Name for the server."
    ::=  {rsHTTPFServerEntry 1}

rsHTTPFServerIp OBJECT-TYPE
    SYNTAX  DisplayString
    ACCESS  read-write
    STATUS  mandatory
    DESCRIPTION
      "The ip address of the server"
    ::=  {rsHTTPFServerEntry 2}


rsHTTPFServerSensitivity OBJECT-TYPE
    SYNTAX INTEGER {
      minor(1),
      low(2),
      medium(3),
      high(4)
    }
    ACCESS read-write
    STATUS mandatory
    DESCRIPTION
      "Http Flood Server detection sensitiviy."
    DEFVAL {3}
    ::=  { rsHTTPFServerEntry 3 }


rsHTTPFServerAction OBJECT-TYPE
    SYNTAX INTEGER {
        report-only(0),
        block(1)
    }
    ACCESS read-write
    STATUS mandatory
    DESCRIPTION
      "Attack Response action."
    DEFVAL {1}
    ::=  { rsHTTPFServerEntry 4 }

rsHTTPFServerPacketReport OBJECT-TYPE
    SYNTAX INTEGER {
			enable(1),
			disable(2)
			}
    ACCESS read-write
    STATUS mandatory
    DESCRIPTION
      "Http Flood Server packet report state."
    DEFVAL {2}
    ::=  { rsHTTPFServerEntry 5 }


rsHTTPFServerSetManTriggers OBJECT-TYPE
    SYNTAX INTEGER {
			active(1),
			inactive(2)
			}
    ACCESS read-write
    STATUS mandatory
    DESCRIPTION
      "Http Flood Server manual triger state."
    DEFVAL {2}
    ::=  { rsHTTPFServerEntry 6 }

rsHTTPFServerGetPostTrs OBJECT-TYPE
    SYNTAX INTEGER
    ACCESS read-write
    STATUS mandatory
    DESCRIPTION
      "Http Flood Server manual threshold of GET/POST requests."
	DEFVAL {0}
    ::=  { rsHTTPFServerEntry 7 }

rsHTTPFServerOtherTrs OBJECT-TYPE
    SYNTAX INTEGER
    ACCESS read-write
    STATUS mandatory
    DESCRIPTION
      "Http Flood Server manual threshold of other requests types."
	DEFVAL {0}
    ::=  { rsHTTPFServerEntry 8 }

rsHTTPFServerOutboundBandwidth OBJECT-TYPE
    SYNTAX INTEGER
    ACCESS read-write
    STATUS mandatory
    DESCRIPTION
      "Http Flood Server manual outbound bandwidth."
	DEFVAL {0}
    ::=  { rsHTTPFServerEntry 9 }

rsHTTPFServerRequestsPerSource OBJECT-TYPE
    SYNTAX INTEGER (1..65535)
    ACCESS read-write
    STATUS mandatory
    DESCRIPTION
      "Http Flood Server manual request per source."
	DEFVAL {10}
    ::=  { rsHTTPFServerEntry 10 }

rsHTTPFServerRequestsPerConnection OBJECT-TYPE
    SYNTAX INTEGER (1..65535)
    ACCESS read-write
    STATUS mandatory
    DESCRIPTION
      "Http Flood Server manual request per connection."
	DEFVAL {5}
    ::=  { rsHTTPFServerEntry 11 }


rsHTTPFServerStatus OBJECT-TYPE
    SYNTAX RowStatus
    ACCESS  read-write
    STATUS  mandatory
    DESCRIPTION
       "This variable indicates the administrative status of this entry.
        Used to delete an entry of this table."
    ::=  { rsHTTPFServerEntry 12 }

rsHTTPFServerUriOnlyMitigation OBJECT-TYPE
    SYNTAX INTEGER {
			enable(1),
			disable(2)
			}
    ACCESS read-write
    STATUS mandatory
    DESCRIPTION
      "Http Flood Server uri-only mitigation state."
    DEFVAL {2}
    ::=  { rsHTTPFServerEntry 13 }


rsHttpFloodMechanismStatus OBJECT-TYPE
 SYNTAX INTEGER {
      enable(1),
      disable(2)
   }
    ACCESS read-write
    STATUS mandatory
    DESCRIPTION
      "Http Flood Module activation"
   DEFVAL  {enable}
    ::= {rsHttpFlood 2}

rsHttpFloodLearnTimeBeforeActive OBJECT-TYPE
 SYNTAX INTEGER
    ACCESS read-write
    STATUS mandatory
    DESCRIPTION
      "Learning time before the http flood will become active"
    ::= {rsHttpFlood 3}

rsHttpFloodLearningMode OBJECT-TYPE
 SYNTAX INTEGER {
      automatic(1),
      continuous-only(2)
   }
    ACCESS read-write
    STATUS mandatory
    DESCRIPTION
      "Http Flood learning mode"
   DEFVAL  {automatic}
    ::= {rsHttpFlood 4}

rsHttpFloodLearningSensitivity OBJECT-TYPE
 SYNTAX INTEGER {
      day(1),
      week(2),
      month(3)
   }
    ACCESS read-write
    STATUS mandatory
    DESCRIPTION
      "Http Flood learning mode"
   DEFVAL  {week}
    ::= {rsHttpFlood 5}

-- obsolete
rsHttpFloodFullBlockModeStatus OBJECT-TYPE
 SYNTAX INTEGER {
      enable(1),
      disable(2)
   }
    ACCESS read-write
    STATUS mandatory
    DESCRIPTION
      "Http Flood Module full blocking mode status"
   DEFVAL  {disable}
    ::= {rsHttpFlood 6}

-- obsolete
rsHttpFloodSourceRateLimit OBJECT-TYPE
	  SYNTAX INTEGER {
      twenty-five(1),
      fifty(2),
      seventy-five(3),
      hundred(4)
   }
    ACCESS read-write
    STATUS mandatory
    DESCRIPTION
      "Http Flood Source rate limit - http connection per second"
   DEFVAL  {4}
    ::= {rsHttpFlood 7}

-- obsolete
rsHttpFloodUriRateLimit OBJECT-TYPE
	  SYNTAX INTEGER {
      twenty-five(1),
      fifty(2),
      seventy-five(3),
      hundred(4)
   }
    ACCESS read-write
    STATUS mandatory
    DESCRIPTION
      "Http Flood rate limit for specific uri's per second"
   DEFVAL  {4}
    ::= {rsHttpFlood 8}

-- obsolete
rsHttpFloodMitigationMode OBJECT-TYPE
     SYNTAX INTEGER {
      automatic(1),
      manual(2)
   }
    ACCESS read-write
    STATUS mandatory
    DESCRIPTION
      "Http Flood mitigation mode"
   DEFVAL  {automatic}
    ::= {rsHttpFlood 9}

-- obsolete
rsHttpFloodManModeSourceRateLimit OBJECT-TYPE
	SYNTAX INTEGER {
      twenty-five(1),
      fifty(2),
      seventy-five(3),
      hundred(4)
   }
    ACCESS read-write
    STATUS mandatory
    DESCRIPTION
      "Http Flood Source rate limit - http connection per second in manual mode"
   DEFVAL  {2}
    ::= {rsHttpFlood 10}

-- obsolete
rsHttpFloodManModeUriRateLimit OBJECT-TYPE
	 SYNTAX INTEGER {
      twenty-five(1),
      fifty(2),
      seventy-five(3),
      hundred(4)
    }
    ACCESS read-write
    STATUS mandatory
    DESCRIPTION
      "Http Flood rate limit for specific uri's per second"
   DEFVAL  {2}
    ::= {rsHttpFlood 11}

rsHttpFloodMitigationFailureCond OBJECT-TYPE
	  SYNTAX INTEGER (1..100)
    ACCESS read-write
    STATUS mandatory
    DESCRIPTION
      "Http Flood number of mitigation failure condition"
   DEFVAL  {3}
    ::= {rsHttpFlood 12}

-- obsolete
rsHttpFloodUriBypassTable OBJECT-TYPE
    SYNTAX SEQUENCE OF RsHttpFloodUriBypassEntry
    ACCESS not-accessible
    STATUS  mandatory
    DESCRIPTION
      "Table containing the parameters that are needed to detect intrusions"
    ::=  {rsHttpFlood 13}

-- obsolete
rsHttpFloodUriBypassEntry OBJECT-TYPE
    SYNTAX RsHttpFloodUriBypassEntry
    ACCESS not-accessible
    STATUS  mandatory
    DESCRIPTION
       "The row definition for this table."
    INDEX { rsHttpFloodUriBypassServerName, rsHttpFloodUriBypassName }
    ::=  { rsHttpFloodUriBypassTable 1 }

-- obsolete
RsHttpFloodUriBypassEntry ::= SEQUENCE {
    rsHttpFloodUriBypassServerName DisplayString,
    rsHttpFloodUriBypassName DisplayString,
    rsHttpFloodUriBypassStatus  RowStatus
}

-- obsolete
rsHttpFloodUriBypassServerName OBJECT-TYPE
    SYNTAX DisplayString (SIZE(1..20))
    ACCESS  read-only
    STATUS  mandatory
    DESCRIPTION
      "Server To be bypassed in the HTTP flood module"
    ::=  {rsHttpFloodUriBypassEntry 1}

-- obsolete
rsHttpFloodUriBypassName OBJECT-TYPE
    SYNTAX DisplayString (SIZE(1..256))
    ACCESS  read-only
    STATUS  mandatory
    DESCRIPTION
      "Uri To be bypassed in the HTTP flood module"
    ::=  {rsHttpFloodUriBypassEntry 2}

-- obsolete
rsHttpFloodUriBypassStatus OBJECT-TYPE
    SYNTAX RowStatus
    ACCESS  read-write
    STATUS  mandatory
    DESCRIPTION
       "This variable indicates the administrative status of this entry.
        Used to delete an entry of this table."
    ::=  { rsHttpFloodUriBypassEntry 3 }

rsHttpFloodLearnedStatTable OBJECT-TYPE
    SYNTAX SEQUENCE OF RsHttpFloodLearnedStatEntry
    ACCESS not-accessible
    STATUS  mandatory
    DESCRIPTION
      "Table containing the parameters that are needed to detect intrusions"
    ::=  {rsHttpFlood 14}

rsHttpFloodLearnedStatEntry OBJECT-TYPE
    SYNTAX RsHttpFloodLearnedStatEntry
    ACCESS not-accessible
    STATUS  mandatory
    DESCRIPTION
       "The row definition for this table."
 		INDEX {rsHttpFloodLearnedStatServerName, rsHttpFloodLearnedStatDate, rsHttpFloodLearnedStatHour}
    ::=  { rsHttpFloodLearnedStatTable 1 }

RsHttpFloodLearnedStatEntry ::= SEQUENCE {
    rsHttpFloodLearnedStatServerName DisplayString,
    rsHttpFloodLearnedStatDate DisplayString,
    rsHttpFloodLearnedStatHour DisplayString,
    rsHttpFloodLearnedGetPostCnt INTEGER,
    rsHttpFloodLearnedOtherCnt INTEGER,
    rsHttpFloodLearnedOutBand INTEGER
}

rsHttpFloodLearnedStatServerName OBJECT-TYPE
    SYNTAX DisplayString (SIZE(1..32))
    ACCESS  read-only
    STATUS  mandatory
    DESCRIPTION
      "The Name of the server."
    ::=  {rsHttpFloodLearnedStatEntry 1}

rsHttpFloodLearnedStatDate OBJECT-TYPE
   SYNTAX DisplayString (SIZE(0..20))
   ACCESS read-only
   STATUS mandatory
   DESCRIPTION
    "The date will be sent in the format dd/mm/yy. The day to display the params on."
    ::=  { rsHttpFloodLearnedStatEntry 2 }

rsHttpFloodLearnedStatHour OBJECT-TYPE
   SYNTAX DisplayString (SIZE(0..6))
   ACCESS read-only
   STATUS mandatory
   DESCRIPTION
    "The hour will be sent in the format hh:00. The hour to display the params on."
    ::=  { rsHttpFloodLearnedStatEntry 3 }

rsHttpFloodLearnedGetPostCnt OBJECT-TYPE
   SYNTAX INTEGER
   ACCESS read-only
   STATUS mandatory
   DESCRIPTION
    "The Get / Post average request rate per second."
    ::=  { rsHttpFloodLearnedStatEntry 4 }

rsHttpFloodLearnedOtherCnt OBJECT-TYPE
   SYNTAX INTEGER
   ACCESS read-only
   STATUS mandatory
   DESCRIPTION
    "The other methods average request rate per second."
    ::=  { rsHttpFloodLearnedStatEntry 5 }

rsHttpFloodLearnedOutBand OBJECT-TYPE
   SYNTAX INTEGER
   ACCESS read-only
   STATUS mandatory
   DESCRIPTION
    "The outbound bandwidth rate per second."
    ::=  { rsHttpFloodLearnedStatEntry 6 }

rsHttpFloodUriBinDistTable OBJECT-TYPE
    SYNTAX SEQUENCE OF RsHttpFloodUriBinDistEntry
    ACCESS not-accessible
    STATUS  mandatory
    DESCRIPTION
      "Table of the uri distribution statistics for http flood"
    ::=  {rsHttpFlood 15}


rsHttpFloodUriBinDistEntry OBJECT-TYPE
    SYNTAX RsHttpFloodUriBinDistEntry
    ACCESS not-accessible
    STATUS  mandatory
    DESCRIPTION
       "The row definition for this table."
 		INDEX {rsHttpFloodUriBinDistServerName, rsHttpFloodUriBinDistMaxBin}
    ::=  { rsHttpFloodUriBinDistTable 1 }

RsHttpFloodUriBinDistEntry ::= SEQUENCE {
    rsHttpFloodUriBinDistServerName DisplayString,
    rsHttpFloodUriBinDistMaxBin INTEGER,
    rsHttpFloodUriBinDistCurrStat DisplayString,
    rsHttpFloodUriBinDistLearnStat DisplayString
}

rsHttpFloodUriBinDistServerName OBJECT-TYPE
    SYNTAX DisplayString (SIZE(1..64))
    ACCESS  read-only
    STATUS  mandatory
    DESCRIPTION
      "The Name of the server."
    ::=  {rsHttpFloodUriBinDistEntry 1}

rsHttpFloodUriBinDistMaxBin OBJECT-TYPE
   SYNTAX INTEGER
   ACCESS read-only
   STATUS mandatory
   DESCRIPTION
    "The maximum bin that is delivered."
    ::=  { rsHttpFloodUriBinDistEntry 2 }

rsHttpFloodUriBinDistCurrStat OBJECT-TYPE
   SYNTAX DisplayString (SIZE(0..255))
   ACCESS read-only
   STATUS mandatory
   DESCRIPTION
    "The current bin distribution statistics (updated every second). This field has 25 integers CSV."
    ::=  { rsHttpFloodUriBinDistEntry 3 }

rsHttpFloodUriBinDistLearnStat OBJECT-TYPE
   SYNTAX DisplayString (SIZE(0..255))
   ACCESS read-only
   STATUS mandatory
   DESCRIPTION
    "The learned bin distribution statistics. This field has 25 integers CSV."
    ::=  { rsHttpFloodUriBinDistEntry 4 }

rsHttpFloodsResetServerLearning OBJECT-TYPE
   SYNTAX DisplayString (SIZE(1..64))
   ACCESS  read-write
   STATUS  mandatory
   DESCRIPTION
       "reset learning baseline for specific server"
    ::=  {rsHttpFlood 16}

rsHTTPFProfileTable OBJECT-TYPE
    SYNTAX SEQUENCE OF RsHTTPFProfileEntry
    ACCESS not-accessible
    STATUS  mandatory
    DESCRIPTION
      "Table containing the profile list and configuration for HTTP flood module"
    ::=  {rsHttpFlood 17 }

rsHTTPFProfileEntry OBJECT-TYPE
    SYNTAX RsHTTPFProfileEntry
    ACCESS not-accessible
    STATUS  mandatory
    DESCRIPTION
       "The row definition for this table."
    INDEX { rsHTTPFProfileName }
    ::=  { rsHTTPFProfileTable 1 }


RsHTTPFProfileEntry ::= SEQUENCE {
    rsHTTPFProfileName DisplayString,
    rsHTTPFProfileSensitivity INTEGER,
    rsHTTPFProfileAction INTEGER,
    rsHTTPFProfilePacketReport INTEGER,
    rsHTTPFProfileSetManTriggers INTEGER,
    rsHTTPFProfileGetPostTrs INTEGER,
    rsHTTPFProfileOtherTrs INTEGER,
    rsHTTPFProfileOutboundBandwidth INTEGER,
    rsHTTPFProfileRequestsPerSource INTEGER,
    rsHTTPFProfileRequestsPerConnection INTEGER,
    rsHTTPFProfileStatus  RowStatus,
    rsHTTPFProfileUriOnlyMitigation INTEGER,
    rsHTTPFProfileSrcSuspTrs INTEGER,
    rsHTTPFProfileConSuspTrs INTEGER,
    rsHTTPFProfilePacketTrace INTEGER,
    rsHttpFloodSourceChallengeStatus INTEGER,
    rsHttpFloodCollectiveChallengeStatus INTEGER,
    rsHttpFloodMitigationBlockingStatus INTEGER,
    rsHttpFloodChallengeMode INTEGER,
	rsHttpFloodOtherEngineStatus INTEGER,
	rsHttpFloodPerSrcEngineStatus INTEGER,
	rsHttpFloodGetPostEngineStatus INTEGER,
	rsHttpFloodOutboundBWEngineStatus INTEGER,
	rsHttpFloodPerConnectionEngineStatus INTEGER
}

rsHTTPFProfileName OBJECT-TYPE
    SYNTAX DisplayString
    ACCESS  read-only
    STATUS  mandatory
    DESCRIPTION
      "The Name for the Profile."
    ::=  {rsHTTPFProfileEntry 1}

rsHTTPFProfileSensitivity OBJECT-TYPE
    SYNTAX INTEGER {
      minor(1),
      low(2),
      medium(3),
      high(4)
    }
    ACCESS read-write
    STATUS mandatory
    DESCRIPTION
      "Http Flood Profile detection sensitiviy."
    DEFVAL {3}
    ::=  { rsHTTPFProfileEntry 2 }


rsHTTPFProfileAction OBJECT-TYPE
    SYNTAX INTEGER {
        report-only(0),
        block(1)
    }
    ACCESS read-write
    STATUS mandatory
    DESCRIPTION
      "Attack Response action."
    DEFVAL {1}
    ::=  { rsHTTPFProfileEntry 3 }

rsHTTPFProfilePacketReport OBJECT-TYPE
    SYNTAX INTEGER {
			enable(1),
			disable(2)
			}
    ACCESS read-write
    STATUS mandatory
    DESCRIPTION
      "Http Flood Profile packet report state."
    DEFVAL {2}
    ::=  { rsHTTPFProfileEntry 4 }


rsHTTPFProfileSetManTriggers OBJECT-TYPE
    SYNTAX INTEGER {
			active(1),
			inactive(2)
			}
    ACCESS read-write
    STATUS mandatory
    DESCRIPTION
      "Http Flood Profile manual triger state."
    DEFVAL {2}
    ::=  { rsHTTPFProfileEntry 5 }

rsHTTPFProfileGetPostTrs OBJECT-TYPE
    SYNTAX INTEGER
    ACCESS read-write
    STATUS mandatory
    DESCRIPTION
      "Http Flood Profile manual threshold of GET/POST requests."
	DEFVAL {0}
    ::=  { rsHTTPFProfileEntry 6 }

rsHTTPFProfileOtherTrs OBJECT-TYPE
    SYNTAX INTEGER
    ACCESS read-write
    STATUS mandatory
    DESCRIPTION
      "Http Flood Profile manual threshold of other requests types."
	DEFVAL {0}
    ::=  { rsHTTPFProfileEntry 7 }

rsHTTPFProfileOutboundBandwidth OBJECT-TYPE
    SYNTAX INTEGER
    ACCESS read-write
    STATUS mandatory
    DESCRIPTION
      "Http Flood Profile manual outbound bandwidth."
	DEFVAL {0}
    ::=  { rsHTTPFProfileEntry 8 }

rsHTTPFProfileRequestsPerSource OBJECT-TYPE
    SYNTAX INTEGER
    ACCESS read-write
    STATUS mandatory
    DESCRIPTION
      "Http Flood Profile manual request per source."
	DEFVAL {0}
    ::=  { rsHTTPFProfileEntry 9 }

rsHTTPFProfileRequestsPerConnection OBJECT-TYPE
    SYNTAX INTEGER
    ACCESS read-write
    STATUS mandatory
    DESCRIPTION
      "Http Flood Profile manual request per connection."
	DEFVAL {0}
    ::=  { rsHTTPFProfileEntry 10 }


rsHTTPFProfileStatus OBJECT-TYPE
    SYNTAX RowStatus
    ACCESS  read-write
    STATUS  mandatory
    DESCRIPTION
       "This variable indicates the administrative status of this entry.
        Used to delete an entry of this table."
    ::=  { rsHTTPFProfileEntry 11 }

rsHTTPFProfileUriOnlyMitigation OBJECT-TYPE
    SYNTAX INTEGER {
			enable(1),
			disable(2)
			}
    ACCESS read-write
    STATUS mandatory
    DESCRIPTION
      "Http Flood Profile uri-only mitigation state."
    DEFVAL {2}
    ::=  { rsHTTPFProfileEntry 12 }

rsHTTPFProfileSrcSuspTrs OBJECT-TYPE
	SYNTAX INTEGER (1..65535)
    ACCESS read-write
    STATUS mandatory
    DESCRIPTION
      "Http Flood Profile threshold of suspect sources."
	DEFVAL {5}
    ::=  { rsHTTPFProfileEntry 13 }

rsHTTPFProfileConSuspTrs OBJECT-TYPE
	SYNTAX INTEGER (1..65535)
    ACCESS read-write
    STATUS mandatory
    DESCRIPTION
      "Http Flood Profile threshold of suspect connection."
	DEFVAL {5}
    ::=  { rsHTTPFProfileEntry 14 }

rsHTTPFProfilePacketTrace OBJECT-TYPE
    SYNTAX INTEGER {
			enable(1),
			disable(2)
			}
    ACCESS read-write
    STATUS mandatory
    DESCRIPTION
      "Http Flood Profile packet trace state."
    DEFVAL {2}
    ::=  { rsHTTPFProfileEntry 15 }

rsHttpFloodSourceChallengeStatus OBJECT-TYPE
   SYNTAX INTEGER {
			enable(1),
			disable(2)
			}
   ACCESS  read-write
   STATUS  mandatory
   DESCRIPTION
       "Http Flood source challenge state"
   DEFVAL  {enable}
    ::= {rsHTTPFProfileEntry 16}

rsHttpFloodCollectiveChallengeStatus OBJECT-TYPE
   SYNTAX INTEGER {
			enable(1),
			disable(2)
			}
   ACCESS  read-write
   STATUS  mandatory
   DESCRIPTION
       "Http Flood source challenge state"
    ::= {rsHTTPFProfileEntry 17}

rsHttpFloodMitigationBlockingStatus OBJECT-TYPE
   SYNTAX INTEGER {
			enable(1),
			disable(2)
			}
   ACCESS  read-write
   STATUS  mandatory
   DESCRIPTION
       "Http Flood source challenge state"
   DEFVAL  {enable}
    ::= {rsHTTPFProfileEntry 18}

rsHttpFloodChallengeMode OBJECT-TYPE
   SYNTAX INTEGER {
			httpRedirect(1),
			javaScript(2)
			}
   ACCESS  read-write
   STATUS  mandatory
   DESCRIPTION
       "Http Flood challenge mode"
   DEFVAL  {httpRedirect}
    ::= {rsHTTPFProfileEntry 19}

rsHttpFloodOtherEngineStatus OBJECT-TYPE
   SYNTAX INTEGER {
			enable(1),
			disable(2)
			}
   ACCESS  read-write
   STATUS  mandatory
   DESCRIPTION
       "Other Request Decision Engine state"
    ::= {rsHTTPFProfileEntry 20}

rsHttpFloodPerSrcEngineStatus OBJECT-TYPE
   SYNTAX INTEGER {
			enable(1),
			disable(2)
			}
   ACCESS  read-write
   STATUS  mandatory
   DESCRIPTION
       "Request per src Decision Engine state"
    ::= {rsHTTPFProfileEntry 21}

rsHttpFloodGetPostEngineStatus OBJECT-TYPE
   SYNTAX INTEGER {
			enable(1),
			disable(2)
			}
   ACCESS  read-write
   STATUS  mandatory
   DESCRIPTION
       "GET+POST Global Requests (FIS1) Decision Engine state"
    ::= {rsHTTPFProfileEntry 22}

rsHttpFloodOutboundBWEngineStatus OBJECT-TYPE
   SYNTAX INTEGER {
			enable(1),
			disable(2)
			}
   ACCESS  read-write
   STATUS  mandatory
   DESCRIPTION
       "Outbound BW (FIS2) Decision Engine state"
    ::= {rsHTTPFProfileEntry 23}

rsHttpFloodPerConnectionEngineStatus OBJECT-TYPE
   SYNTAX INTEGER {
			enable(1),
			disable(2)
			}
   ACCESS  read-write
   STATUS  mandatory
   DESCRIPTION
       "Requests per connection Decision Engine state"
    ::= {rsHTTPFProfileEntry 24}

rsHttpFloodInitialGetPostAverage OBJECT-TYPE
 SYNTAX INTEGER (1..65535)
   ACCESS  read-write
   STATUS  mandatory
   DESCRIPTION
       "Http Flood Initial Get Post Average"
    ::=  { rsHttpFlood 18}

rsHttpFloodInitialGetPostMax OBJECT-TYPE
 SYNTAX INTEGER (1..65535)
   ACCESS  read-write
   STATUS  mandatory
   DESCRIPTION
       "Http Flood Initial Get Post Max"
    ::=  { rsHttpFlood 19}

rsHttpFloodInitialRequestsMax OBJECT-TYPE
 SYNTAX INTEGER (1..65535)
   ACCESS  read-write
   STATUS  mandatory
   DESCRIPTION
       "Http Flood Initial Requests Max"
    ::=  { rsHttpFlood 20}

rsHttpFloodInitialRequestsConnectionMax OBJECT-TYPE
 SYNTAX INTEGER (1..65535)
   ACCESS  read-write
   STATUS  mandatory
   DESCRIPTION
       "Http Flood Initial Requests Connection Max"
    ::=  { rsHttpFlood 21}

rsHttpFloodInitialOutbound OBJECT-TYPE
 SYNTAX INTEGER (1..65535)
   ACCESS  read-write
   STATUS  mandatory
   DESCRIPTION
       "Http Flood Initial Outbound"
    ::=  { rsHttpFlood 22}

rsHttpFloodInitialOutboundMax OBJECT-TYPE
 SYNTAX INTEGER (1..65535)
   ACCESS  read-write
   STATUS  mandatory
   DESCRIPTION
       "Http Flood Initial Outbound Max"
    ::=  { rsHttpFlood 23}

rsHttpFloodGetPostSensitivityHigh OBJECT-TYPE
   SYNTAX INTEGER (1..255)
   ACCESS  read-write
   STATUS  mandatory
   DESCRIPTION
       "Http Flood Get Post High Sensitivity"
    ::=  { rsHttpFlood 24}

rsHttpFloodGetPostSensitivityMedium OBJECT-TYPE
   SYNTAX INTEGER (1..255)
   ACCESS  read-write
   STATUS  mandatory
   DESCRIPTION
       "Http Flood Get Post Medium Sensitivity"
    ::=  { rsHttpFlood 25}

rsHttpFloodGetPostSensitivityLow OBJECT-TYPE
   SYNTAX INTEGER (1..255)
   ACCESS  read-write
   STATUS  mandatory
   DESCRIPTION
       "Http Flood Get Post Low Sensitivity"
    ::=  { rsHttpFlood 26}

rsHttpFloodGetPostSensitivityMinor OBJECT-TYPE
   SYNTAX INTEGER (1..255)
   ACCESS  read-write
   STATUS  mandatory
   DESCRIPTION
       "Http Flood Get Post Minor Sensitivity"
    ::=  { rsHttpFlood 27}

rsHttpFloodOtherSensitivityHigh OBJECT-TYPE
   SYNTAX INTEGER (1..255)
   ACCESS  read-write
   STATUS  mandatory
   DESCRIPTION
       "Http Flood Other High Sensitivity"
    ::=  { rsHttpFlood 28}

rsHttpFloodOtherSensitivityMedium OBJECT-TYPE
   SYNTAX INTEGER (1..255)
   ACCESS  read-write
   STATUS  mandatory
   DESCRIPTION
       "Http Flood Other Medium Sensitivity"
    ::=  { rsHttpFlood 29}

rsHttpFloodOtherSensitivityLow OBJECT-TYPE
   SYNTAX INTEGER (1..255)
   ACCESS  read-write
   STATUS  mandatory
   DESCRIPTION
       "Http Flood Other Low Sensitivity"
    ::=  { rsHttpFlood 30}

rsHttpFloodOtherSensitivityMinor OBJECT-TYPE
   SYNTAX INTEGER (1..255)
   ACCESS  read-write
   STATUS  mandatory
   DESCRIPTION
       "Http Flood Other Minor Sensitivity"
    ::=  { rsHttpFlood 31}

rsHttpFloodOutboundSensitivityHigh OBJECT-TYPE
   SYNTAX INTEGER (1..255)
   ACCESS  read-write
   STATUS  mandatory
   DESCRIPTION
       "Http Flood Outbound High Sensitivity"
    ::=  { rsHttpFlood 32}

rsHttpFloodOutboundSensitivityMedium OBJECT-TYPE
   SYNTAX INTEGER (1..255)
   ACCESS  read-write
   STATUS  mandatory
   DESCRIPTION
       "Http Flood Outbound Medium Sensitivity"
    ::=  { rsHttpFlood 33}

rsHttpFloodOutboundSensitivityLow OBJECT-TYPE
   SYNTAX INTEGER (1..255)
   ACCESS  read-write
   STATUS  mandatory
   DESCRIPTION
       "Http Flood Outbound Low Sensitivity"
    ::=  { rsHttpFlood 34}

rsHttpFloodOutboundSensitivityMinor OBJECT-TYPE
   SYNTAX INTEGER (1..255)
   ACCESS  read-write
   STATUS  mandatory
   DESCRIPTION
       "Http Flood Outbound Minor Sensitivity"
    ::=  { rsHttpFlood 35}

rsHttpFloodOutRPSensitivityHigh OBJECT-TYPE
   SYNTAX INTEGER (1..255)
   ACCESS  read-write
   STATUS  mandatory
   DESCRIPTION
       "Http Flood outbound / requests High Sensitivity"
    ::=  { rsHttpFlood 36}

rsHttpFloodOutRPSensitivityMedium OBJECT-TYPE
   SYNTAX INTEGER (1..255)
   ACCESS  read-write
   STATUS  mandatory
   DESCRIPTION
       "Http Flood outbound / requests Medium Sensitivity"
    ::=  { rsHttpFlood 37}

rsHttpFloodOutRPSensitivityLow OBJECT-TYPE
   SYNTAX INTEGER (1..255)
   ACCESS  read-write
   STATUS  mandatory
   DESCRIPTION
       "Http Flood outbound / requests Low Sensitivity"
    ::=  { rsHttpFlood 38}

rsHttpFloodOutRPSensitivityMinor OBJECT-TYPE
   SYNTAX INTEGER (1..255)
   ACCESS  read-write
   STATUS  mandatory
   DESCRIPTION
       "Http Flood outbound / requests Minor Sensitivity"
    ::=  { rsHttpFlood 39}

rsHttpFloodExpSizeConfidenceHigh OBJECT-TYPE
   SYNTAX INTEGER (1..255)
   ACCESS  read-write
   STATUS  mandatory
   DESCRIPTION
       "Http Flood expected size confidence high sensitivity"
    ::=  { rsHttpFlood 40}

rsHttpFloodExpSizeConfidenceMedium OBJECT-TYPE
   SYNTAX INTEGER (1..255)
   ACCESS  read-write
   STATUS  mandatory
   DESCRIPTION
       "Http Flood expected size confidence medium sensitivity"
    ::=  { rsHttpFlood 41}

rsHttpFloodExpSizeConfidenceLow OBJECT-TYPE
   SYNTAX INTEGER (1..255)
   ACCESS  read-write
   STATUS  mandatory
   DESCRIPTION
       "Http Flood expected size confidence low sensitivity"
    ::=  { rsHttpFlood 42}

rsHttpFloodExpSizeConfidenceMinor OBJECT-TYPE
   SYNTAX INTEGER (1..255)
   ACCESS  read-write
   STATUS  mandatory
   DESCRIPTION
       "Http Flood expected size confidence minor sensitivity"
    ::=  { rsHttpFlood 43}

rsHttpFloodRequestPerConnectionConfidenceHigh OBJECT-TYPE
   SYNTAX INTEGER (1..255)
   ACCESS  read-write
   STATUS  mandatory
   DESCRIPTION
       "Http Flood request per connection confidence high sensitivity"
    ::=  { rsHttpFlood 44}

rsHttpFloodRequestPerConnectionConfidenceMedium OBJECT-TYPE
   SYNTAX INTEGER (1..255)
   ACCESS  read-write
   STATUS  mandatory
   DESCRIPTION
       "Http Flood request per connection confidence medium sensitivity"
    ::=  { rsHttpFlood 45}

rsHttpFloodRequestPerConnectionConfidenceLow OBJECT-TYPE
   SYNTAX INTEGER (1..255)
   ACCESS  read-write
   STATUS  mandatory
   DESCRIPTION
       "Http Flood request per connection confidence low sensitivity"
    ::=  { rsHttpFlood 46}

rsHttpFloodRequestPerConnectionConfidenceMinor OBJECT-TYPE
   SYNTAX INTEGER (1..255)
   ACCESS  read-write
   STATUS  mandatory
   DESCRIPTION
       "Http Flood request per connection confidence minor sensitivity"
    ::=  { rsHttpFlood 47}

rsHttpFloodRequestPerSourceConfidenceHigh OBJECT-TYPE
   SYNTAX INTEGER (1..255)
   ACCESS  read-write
   STATUS  mandatory
   DESCRIPTION
       "Http Flood request per source confidence high sensitivity"
    ::=  { rsHttpFlood 48}

rsHttpFloodRequestPerSourceConfidenceMedium OBJECT-TYPE
   SYNTAX INTEGER (1..255)
   ACCESS  read-write
   STATUS  mandatory
   DESCRIPTION
       "Http Flood request per source confidence medium sensitivity"
    ::=  { rsHttpFlood 49}

rsHttpFloodRequestPerSourceConfidenceLow OBJECT-TYPE
   SYNTAX INTEGER (1..255)
   ACCESS  read-write
   STATUS  mandatory
   DESCRIPTION
       "Http Flood request per source confidence low sensitivity"
    ::=  { rsHttpFlood 50}

rsHttpFloodRequestPerSourceConfidenceMinor OBJECT-TYPE
   SYNTAX INTEGER (1..255)
   ACCESS  read-write
   STATUS  mandatory
   DESCRIPTION
       "Http Flood request per source confidence minor sensitivity"
    ::=  { rsHttpFlood 51}

rsHttpFloodExpSizeSensitivityHigh OBJECT-TYPE
   SYNTAX INTEGER (1..255)
   ACCESS  read-write
   STATUS  mandatory
   DESCRIPTION
       "Http Flood expected size high sensitivity"
    ::=  { rsHttpFlood 52}

rsHttpFloodExpSizeSensitivityMedium OBJECT-TYPE
   SYNTAX INTEGER (1..255)
   ACCESS  read-write
   STATUS  mandatory
   DESCRIPTION
       "Http Flood expected size medium sensitivity"
    ::=  { rsHttpFlood 53}

rsHttpFloodExpSizeSensitivityLow OBJECT-TYPE
   SYNTAX INTEGER (1..255)
   ACCESS  read-write
   STATUS  mandatory
   DESCRIPTION
       "Http Flood expected size low sensitivity"
    ::=  { rsHttpFlood 54}

rsHttpFloodExpSizeSensitivityMinor OBJECT-TYPE
   SYNTAX INTEGER (1..255)
   ACCESS  read-write
   STATUS  mandatory
   DESCRIPTION
       "Http Flood expected size minor sensitivity"
    ::=  { rsHttpFlood 55}

rsHttpFloodRequestPerConnectionSensitivityHigh OBJECT-TYPE
   SYNTAX INTEGER (1..255)
   ACCESS  read-write
   STATUS  mandatory
   DESCRIPTION
       "Http Flood Request Per Connection high sensitivity"
    ::=  { rsHttpFlood 56}

rsHttpFloodRequestPerConnectionSensitivityMedium OBJECT-TYPE
   SYNTAX INTEGER (1..255)
   ACCESS  read-write
   STATUS  mandatory
   DESCRIPTION
       "Http Flood Request Per Connection medium sensitivity"
    ::=  { rsHttpFlood 57}

rsHttpFloodRequestPerConnectionSensitivityLow OBJECT-TYPE
   SYNTAX INTEGER (1..255)
   ACCESS  read-write
   STATUS  mandatory
   DESCRIPTION
       "Http Flood Request Per Connection low sensitivity"
    ::=  { rsHttpFlood 58}

rsHttpFloodRequestPerConnectionSensitivityMinor OBJECT-TYPE
   SYNTAX INTEGER (1..255)
   ACCESS  read-write
   STATUS  mandatory
   DESCRIPTION
       "Http Flood Request Per Connection minor sensitivity"
    ::=  { rsHttpFlood 59}

rsHttpFloodRequestPerSourceSensitivityHigh OBJECT-TYPE
   SYNTAX INTEGER (1..255)
   ACCESS  read-write
   STATUS  mandatory
   DESCRIPTION
       "Http Flood Request Per Source high sensitivity"
    ::=  { rsHttpFlood 60}

rsHttpFloodRequestPerSourceSensitivityMedium OBJECT-TYPE
   SYNTAX INTEGER (1..255)
   ACCESS  read-write
   STATUS  mandatory
   DESCRIPTION
       "Http Flood Request Per Source medium sensitivity"
    ::=  { rsHttpFlood 61}

rsHttpFloodRequestPerSourceSensitivityLow OBJECT-TYPE
   SYNTAX INTEGER (1..255)
   ACCESS  read-write
   STATUS  mandatory
   DESCRIPTION
       "Http Flood Request Per Source low sensitivity"
    ::=  { rsHttpFlood 62}

rsHttpFloodRequestPerSourceSensitivityMinor OBJECT-TYPE
   SYNTAX INTEGER (1..255)
   ACCESS  read-write
   STATUS  mandatory
   DESCRIPTION
       "Http Flood Request Per Source minor sensitivity"
    ::=  { rsHttpFlood 63}

rsHttpFloodMaxSourceConnectionFading OBJECT-TYPE
 SYNTAX INTEGER {
      ten-min(0),
      thirty-min(1),
      sixty-min(2),
      one-day(3)
   }
   ACCESS  read-write
   STATUS  mandatory
   DESCRIPTION
       "Http Flood Max Source Connection Fading"
   DEFVAL  {thirty-min}
   ::=  { rsHttpFlood 64}

rsHttpFloodMinGetPostLearn OBJECT-TYPE
   SYNTAX INTEGER (1..65535)
   ACCESS  read-write
   STATUS  mandatory
   DESCRIPTION
       "Http Flood minimal learned request per second"
    ::=  { rsHttpFlood 65}

rsHttpFloodMinOtherLearn OBJECT-TYPE
   SYNTAX INTEGER (1..65535)
   ACCESS  read-write
   STATUS  mandatory
   DESCRIPTION
       "Http Flood minimal learned other request per second"
    ::=  { rsHttpFlood 66}

rsHttpFloodMinOutboundLearn OBJECT-TYPE
   SYNTAX INTEGER (1..65535)
   ACCESS  read-write
   STATUS  mandatory
   DESCRIPTION
       "Http Flood minimal outbound B/W per second"
    ::=  { rsHttpFlood 67}

rsHttpFloodMinRequestConLearn OBJECT-TYPE
   SYNTAX INTEGER (1..65535)
   ACCESS  read-write
   STATUS  mandatory
   DESCRIPTION
       "Http Flood minimal learned number of HTTP request per connection"
    ::=  { rsHttpFlood 68}

rsHttpFloodMinRequestSrcLearn OBJECT-TYPE
   SYNTAX INTEGER (1..65535)
   ACCESS  read-write
   STATUS  mandatory
   DESCRIPTION
       "Http Flood minimal learned number of HTTP request per session"
    ::=  { rsHttpFlood 69}

rsHttpFloodTrapBufferLowThreshold OBJECT-TYPE
   SYNTAX INTEGER (1..20)
   ACCESS  read-write
   STATUS  mandatory
   DESCRIPTION
       "Http Flood minimum trap-buffer threshold"
    ::=  { rsHttpFlood 70}

rsHttpFloodLowHitRate OBJECT-TYPE
   SYNTAX INTEGER (1..100)
   ACCESS  read-write
   STATUS  mandatory
   DESCRIPTION
       "Http Flood minimum hit-rate threshold percent"
    ::=  { rsHttpFlood 71}

rsHttpFloodHitRate OBJECT-TYPE
   SYNTAX INTEGER (1..100)
   ACCESS  read-write
   STATUS  mandatory
   DESCRIPTION
       "Http Flood hit-rate threshold percent"
    ::=  { rsHttpFlood 72}

rsHttpFloodSingleRqstAttck OBJECT-TYPE
   SYNTAX INTEGER {
			enable(1),
			disable(2)
			}
   ACCESS  read-write
   STATUS  mandatory
   DESCRIPTION
       "Http Flood single-request-attack state"
    ::=  { rsHttpFlood 73}

rsHttpCharPersist OBJECT-TYPE
   SYNTAX INTEGER (2..600)
   ACCESS  read-write
   STATUS  mandatory
   DESCRIPTION
       "Http Flood persistency sub-state time"
   DEFVAL{4}
    ::=  { rsHttpFlood 79}

rsHttpCharExpir OBJECT-TYPE
   SYNTAX INTEGER (2..600)
   ACCESS  read-write
   STATUS  mandatory
   DESCRIPTION
       "Http Flood characterization state expiration time"
   DEFVAL{6}
    ::=  { rsHttpFlood 80}

rsHTTPFClearAuthUserOnNegFeedback OBJECT-TYPE
    SYNTAX INTEGER {
        enable(1),
        disable(2)
    }
    ACCESS read-write
    STATUS mandatory
    DESCRIPTION
      "Clear authenticated user list upon negative feedbacks."
    DEFVAL {2}
    ::=  { rsHttpFlood 81 }

-- Reporting data ip addresses

rsPacketReportData OBJECT IDENTIFIER ::= { rsIDS 116 }

rsIDSReportDataAddressTable OBJECT-TYPE
    SYNTAX SEQUENCE OF RsIDSReportDataAddressEntry
    ACCESS not-accessible
    STATUS  mandatory
    DESCRIPTION
      "Table containing the list of ip addresses for data reports"
    ::=  {rsPacketReportData 1}

rsIDSReportDataAddressEntry OBJECT-TYPE
    SYNTAX RsIDSReportDataAddressEntry
    ACCESS not-accessible
    STATUS  mandatory
    DESCRIPTION
       "The row definition for this table."
    INDEX { rsIDSReportDataAddress }
    ::=  { rsIDSReportDataAddressTable 1 }

RsIDSReportDataAddressEntry ::= SEQUENCE {
    rsIDSReportDataAddress IpAddress,
    rsIDSReportDataStatus RowStatus
}

rsIDSReportDataAddress OBJECT-TYPE
    SYNTAX  IpAddress
    ACCESS  read-only
    STATUS  mandatory
    DESCRIPTION
      "The ip address"
    ::=  {rsIDSReportDataAddressEntry 1}

rsIDSReportDataStatus OBJECT-TYPE
    SYNTAX  RowStatus
    ACCESS  read-write
    STATUS  mandatory
    DESCRIPTION
       "This variable indicates the administrative status of this entry.
        Used to delete an entry of this table."
    ::=  {rsIDSReportDataAddressEntry 2}


rsIDSPacketReportDestPort OBJECT-TYPE
    SYNTAX INTEGER (1..65535)
    ACCESS  read-write
    STATUS  mandatory
    DESCRIPTION
        "The destination port of the packet reporting."
    ::= {rsPacketReportData 2}


rsSystemInternalDataReportMaxPoliciesInSingleIrp OBJECT-TYPE
    SYNTAX INTEGER
    ACCESS  read-write
    STATUS  mandatory
    DESCRIPTION
       "Maximum policies in a single IRP"
    DEFVAL  { 10 }
    ::=  { rsPacketReportData 3}

-- MPLS RD

rsIDSMPLSRDParams OBJECT IDENTIFIER ::= { rsIDS 117 }

rsIDSMPLSRDMechanismStatus OBJECT-TYPE
 SYNTAX INTEGER {
      enable(1),
      disable(2)
   }
    ACCESS read-write
    STATUS mandatory
    DESCRIPTION
      "MPLS RD Module trigger"
   DEFVAL  {disable}
    ::= {rsIDSMPLSRDParams 1}

rsIDSMPLSRDTable OBJECT-TYPE
    SYNTAX SEQUENCE OF RsIDSMPLSRDTableEntry
    ACCESS not-accessible
    STATUS  mandatory
    DESCRIPTION
      "Table containing the table of MPLS-RD entries"
    ::=  {rsIDSMPLSRDParams 2}

rsIDSMPLSRDTableEntry OBJECT-TYPE
    SYNTAX RsIDSMPLSRDTableEntry
    ACCESS not-accessible
    STATUS  mandatory
    DESCRIPTION
       "The row definition for this table."
    INDEX { rsIDSMPLSRDTableRD, rsIDSMPLSRDTableUpperTag, rsIDSMPLSRDTableLowerTag }
    ::=  { rsIDSMPLSRDTable 1 }

RsIDSMPLSRDTableEntry::= SEQUENCE {
    rsIDSMPLSRDTableRD DisplayString,
	rsIDSMPLSRDTableUpperTag INTEGER,
    rsIDSMPLSRDTableLowerTag INTEGER,
    rsIDSMPLSRDTableType INTEGER,
    rsIDSMPLSRDTableStatus RowStatus
}

rsIDSMPLSRDTableRD OBJECT-TYPE
    SYNTAX DisplayString (SIZE(1..30))
    ACCESS read-write
    STATUS mandatory
    DESCRIPTION
      "MPLS RD string."
    ::=  { rsIDSMPLSRDTableEntry 1 }

rsIDSMPLSRDTableUpperTag OBJECT-TYPE
    SYNTAX INTEGER
    ACCESS read-only
    STATUS mandatory
    DESCRIPTION
      "MPLS RD Upper Tag."
    ::=  { rsIDSMPLSRDTableEntry 2 }

rsIDSMPLSRDTableLowerTag OBJECT-TYPE
    SYNTAX INTEGER
    ACCESS read-only
    STATUS mandatory
    DESCRIPTION
      "MPLS RD Lower Tag."
    ::=  { rsIDSMPLSRDTableEntry 3 }

rsIDSMPLSRDTableType OBJECT-TYPE
    SYNTAX INTEGER {
        type0(0),
        type1(1),
		type2(2)
    }
    ACCESS read-write
    STATUS mandatory
    DESCRIPTION
      "MPLS RD Type."
    DEFVAL {0}
    ::=  { rsIDSMPLSRDTableEntry 4 }

rsIDSMPLSRDTableStatus OBJECT-TYPE
    SYNTAX RowStatus
    ACCESS  read-write
    STATUS  mandatory
    DESCRIPTION
       "This variable indicates the administrative status of this entry.
        Used to delete an entry of this table."
    ::=  { rsIDSMPLSRDTableEntry 5 }

rsIDSMPLSRDTableClean OBJECT-TYPE
 SYNTAX INTEGER {
      clearTable(1)
   }
    ACCESS read-write
    STATUS mandatory
    DESCRIPTION
      "MPLS RD Clean Table Command"
   DEFVAL  {1}
    ::= {rsIDSMPLSRDParams 3}

rsIDSMPLSRDGroup OBJECT-TYPE
    SYNTAX SEQUENCE OF RsIDSMPLSRDGroupEntry
    ACCESS not-accessible
    STATUS  mandatory
    DESCRIPTION
      "Table containing MPLS-RD groups"
    ::=  {rsIDSMPLSRDParams 4}

rsIDSMPLSRDGroupEntry OBJECT-TYPE
    SYNTAX RsIDSMPLSRDGroupEntry
    ACCESS not-accessible
    STATUS  mandatory
    DESCRIPTION
       "The row definition for this table."
    INDEX { rsIDSMPLSRDGroupName, rsIDSMPLSRDGroupRDValue }
    ::=  { rsIDSMPLSRDGroup 1 }

RsIDSMPLSRDGroupEntry::= SEQUENCE {
    rsIDSMPLSRDGroupName DisplayString,
    rsIDSMPLSRDGroupRDValue DisplayString,
    rsIDSMPLSRDGroupRDType INTEGER,
    rsIDSMPLSRDGroupStatus RowStatus
}

rsIDSMPLSRDGroupName OBJECT-TYPE
    SYNTAX DisplayString (SIZE(1..30))
    ACCESS read-only
    STATUS mandatory
    DESCRIPTION
      "MPLS RD Group name."
    ::=  { rsIDSMPLSRDGroupEntry 1 }

rsIDSMPLSRDGroupRDValue OBJECT-TYPE
    SYNTAX DisplayString (SIZE(1..30))
    ACCESS read-write
    STATUS mandatory
    DESCRIPTION
      "MPLS RD string."
    ::=  { rsIDSMPLSRDGroupEntry 2 }

rsIDSMPLSRDGroupRDType OBJECT-TYPE
    SYNTAX INTEGER {
        type0(0),
        type1(1),
		type2(2)
    }
    ACCESS read-write
    STATUS mandatory
    DESCRIPTION
      "MPLS RD Type."
    DEFVAL {0}
    ::=  { rsIDSMPLSRDGroupEntry 3 }

rsIDSMPLSRDGroupStatus OBJECT-TYPE
    SYNTAX RowStatus
    ACCESS  read-write
    STATUS  mandatory
    DESCRIPTION
       "This variable indicates the administrative status of this entry.
        Used to delete an entry of this table."
    ::=  { rsIDSMPLSRDGroupEntry 4 }

rsIDSServerTable OBJECT-TYPE
    SYNTAX SEQUENCE OF RsIDSServerTableEntry
    ACCESS not-accessible
    STATUS  mandatory
    DESCRIPTION
      "Table containing server IP entries"
    ::=  {rsIDS 119}

rsIDSServerTableEntry OBJECT-TYPE
    SYNTAX RsIDSServerTableEntry
    ACCESS not-accessible
    STATUS  mandatory
    DESCRIPTION
       "The row definition for this table."
    INDEX { rsIDSServerName }
    ::=  { rsIDSServerTable 1 }

-- Orc - 15/2/2012 - Added PolicyName to Protected Server MIB

RsIDSServerTableEntry::= SEQUENCE {
    rsIDSServerName DisplayString,
    rsIDSServerIPAddress Ipv6Address,
    rsIDSServerSYNProfile DisplayString,
    rsIDSServerHTTPProfile DisplayString,
    rsIDSServerIPSProfile DisplayString,
	rsIDSServerState INTEGER,
    rsIDSServerStatus RowStatus,
	rsIDSServerPacketTraceStatus INTEGER,
    rsIDSServerPacketTraceEnforcement INTEGER,
	rsIDSServerPacketReportStatus INTEGER,
	rsIDSServerPacketReportEnforcement INTEGER,
    rsIDSServerVlanTagGroup DisplayString,
    rsIDSServerIPRange DisplayString,
    rsIDSServerSDiscoveryServerPolicyName DisplayString,
	rsIDSServerSDiscoveryServerStatus		INTEGER,
	rsIDSServerNextReEvaluationTime		DisplayString,
	rsIDSServerLastValidatedTimeStamp		INTEGER,
	rsIDSServerPolicyName DisplayString
}

rsIDSServerName OBJECT-TYPE
    SYNTAX DisplayString (SIZE(1..32))
    ACCESS read-only
    STATUS mandatory
    DESCRIPTION
      "Server name."
    ::=  { rsIDSServerTableEntry 1 }

rsIDSServerIPAddress OBJECT-TYPE
    SYNTAX Ipv6Address
    ACCESS read-write
    STATUS mandatory
    DESCRIPTION
      "Server IP Address."
    ::=  { rsIDSServerTableEntry 2 }

rsIDSServerSYNProfile OBJECT-TYPE
    SYNTAX DisplayString (SIZE(0..30))
    ACCESS read-write
    STATUS mandatory
    DESCRIPTION
      "Server SYN protection profile name."
    ::=  { rsIDSServerTableEntry 3 }

rsIDSServerHTTPProfile OBJECT-TYPE
    SYNTAX DisplayString (SIZE(0..30))
    ACCESS read-write
    STATUS mandatory
    DESCRIPTION
      "Server HTTP profile name."
    ::=  { rsIDSServerTableEntry 4 }

rsIDSServerIPSProfile OBJECT-TYPE
    SYNTAX DisplayString (SIZE(0..30))
    ACCESS read-write
    STATUS mandatory
    DESCRIPTION
      "Server IPS profile name."
    ::=  { rsIDSServerTableEntry 5 }

 rsIDSServerState OBJECT-TYPE
    SYNTAX INTEGER {
              active(1),
              inactive(2) }
    ACCESS  read-write
    STATUS  mandatory
    DESCRIPTION
       "This variable indicates the state of the server."
    DEFVAL { 1 }
    ::=  { rsIDSServerTableEntry 6 }

rsIDSServerStatus OBJECT-TYPE
    SYNTAX RowStatus
    ACCESS  read-write
    STATUS  mandatory
    DESCRIPTION
       "This variable indicates the administrative status of this entry.
        Used to delete an entry of this table."
    ::=  { rsIDSServerTableEntry 7}


rsIDSServerPacketTraceStatus OBJECT-TYPE
    SYNTAX INTEGER {
     enable(1),
     disable(2)
	}
    ACCESS  read-write
    STATUS  mandatory
    DESCRIPTION
       "This variable indicates the packet trace status for the server"
    ::=  { rsIDSServerTableEntry 8 }

rsIDSServerPacketTraceEnforcement OBJECT-TYPE
    SYNTAX INTEGER {
     enable(1),
     disable(2)
	}
    ACCESS  read-write
    STATUS  mandatory
    DESCRIPTION
       "This variable indicates the packet trace enforcement status for the server"
    ::=  { rsIDSServerTableEntry 9}

rsIDSServerPacketReportStatus OBJECT-TYPE
    SYNTAX INTEGER {
     enable(1),
     disable(2)
	}
    ACCESS  read-write
    STATUS  mandatory
    DESCRIPTION
       "This variable indicates the packet report status for the server"
    ::=  { rsIDSServerTableEntry 10 }

rsIDSServerPacketReportEnforcement OBJECT-TYPE
    SYNTAX INTEGER {
     enable(1),
     disable(2)
	}
    ACCESS  read-write
    STATUS  mandatory
    DESCRIPTION
       "This variable indicates the packet report enforcement status for the server"
    ::=  { rsIDSServerTableEntry 11}


rsIDSServerVlanTagGroup OBJECT-TYPE
    SYNTAX DisplayString (SIZE(0..19))
    ACCESS read-write
    STATUS mandatory
    DESCRIPTION
      "Server VLAN-Tag group."
    ::=  { rsIDSServerTableEntry 12 }

rsIDSServerIPRange OBJECT-TYPE
    SYNTAX DisplayString (SIZE(0..46))
    ACCESS read-write
    STATUS mandatory
    DESCRIPTION
      "Server IP Address/range"
    ::=  { rsIDSServerTableEntry 13 }


rsIDSServerSDiscoveryServerPolicyName OBJECT-TYPE
    SYNTAX DisplayString (SIZE(0..30))
    ACCESS read-write
    STATUS mandatory
    DESCRIPTION
      "Service discovery policy related to host name."
    ::=  { rsIDSServerTableEntry 14 }

rsIDSServerSDiscoveryServerStatus OBJECT-TYPE
    SYNTAX INTEGER {
			  static(0),
              ignore (1),
              autoDetected(2),
			  inEvaluation(3),
			  reEvaluation(4)}
    ACCESS  read-write
    STATUS  mandatory
    DESCRIPTION
       "This variable indicates the host state."
    DEFVAL { 0 }
    ::=  { rsIDSServerTableEntry 15 }

rsIDSServerNextReEvaluationTime OBJECT-TYPE
    SYNTAX DisplayString (SIZE(1..30))
    ACCESS read-only
    STATUS mandatory
    DESCRIPTION
      "Time until revalidation of the server."
    ::=  { rsIDSServerTableEntry 16 }

rsIDSServerLastValidatedTimeStamp OBJECT-TYPE
    SYNTAX INTEGER
    ACCESS read-write
    STATUS mandatory
    DESCRIPTION
      "Last Validation Time Stamp."
    ::=  { rsIDSServerTableEntry 17 }

	 rsIDSServerPolicyName OBJECT-TYPE
    SYNTAX DisplayString (SIZE(0..30))
    ACCESS read-write
    STATUS mandatory
    DESCRIPTION
      "The policy name this server is ascribed to."
    ::=  { rsIDSServerTableEntry 18 }


rsIDSServerProtectionTabServers OBJECT-TYPE
    SYNTAX INTEGER
    ACCESS read-only
    STATUS mandatory
    DESCRIPTION
      "Tuning parameter for the server protection tab maximal number of servers"
    ::= {rsIDS 120}

rsIDSServerProtectionTabServersAfterReset OBJECT-TYPE
    SYNTAX INTEGER
    ACCESS read-write
    STATUS mandatory
    DESCRIPTION
      "Tuning parameter for the server protection tab maximal number of servers after the next reset"
    ::= {rsIDS 121}


rsIDSOOPStatus OBJECT-TYPE
 SYNTAX INTEGER {
      enable(1),
      disable(2)
   }
    ACCESS read-write
    STATUS mandatory
    DESCRIPTION
      "the Out-Of-Path trigger"
   DEFVAL  {disable}
    ::= {rsIDS 122}

rsIDSOOPTable OBJECT-TYPE
    SYNTAX SEQUENCE OF RsIDSOOPTableEntry
    ACCESS not-accessible
    STATUS  mandatory
    DESCRIPTION
      "Table containing the parameters that are needed for out-of-path"
    ::=  {rsIDS 123}


rsIDSOOPTableEntry OBJECT-TYPE
    SYNTAX RsIDSOOPTableEntry
    ACCESS not-accessible
    STATUS  mandatory
    DESCRIPTION
       "The row definition for this table."
    INDEX { rsIDSOOPRouterEntryKey }
    ::=  { rsIDSOOPTable 1 }

RsIDSOOPTableEntry::= SEQUENCE {
    rsIDSOOPRouterEntryKey DisplayString,
    rsIDSOOPRouterIPAddress DisplayString,
    rsIDSOOPRouterPassword DisplayString,
    rsIDSOOPRouterProtectedPort DisplayString,
    rsIDSOOPSSHUserName DisplayString,
    rsIDSOOPSSHPassWord DisplayString,
    rsIDSOOPDebugMode INTEGER,
    rsIDSOOPTableStatus RowStatus
}

rsIDSOOPRouterEntryKey OBJECT-TYPE
    SYNTAX  DisplayString
    ACCESS  read-only
    STATUS  mandatory
    DESCRIPTION
      "The Entry Key of the table"
    ::=  {rsIDSOOPTableEntry 1}

rsIDSOOPRouterIPAddress OBJECT-TYPE
    SYNTAX  DisplayString
    ACCESS  read-write
    STATUS  mandatory
    DESCRIPTION
      "The ip address of the router"
    ::=  {rsIDSOOPTableEntry 2}


rsIDSOOPRouterPassword OBJECT-TYPE
    SYNTAX DisplayString (SIZE(1..30))
    ACCESS read-write
    STATUS mandatory
    DESCRIPTION
      "Router's Enable Password."
    ::=  { rsIDSOOPTableEntry 3 }

rsIDSOOPRouterProtectedPort OBJECT-TYPE
    SYNTAX DisplayString (SIZE(1..30))
    ACCESS  read-write
    STATUS  mandatory
    DESCRIPTION
        "The Protected port of the router."
    ::= { rsIDSOOPTableEntry 4}

rsIDSOOPSSHUserName OBJECT-TYPE
    SYNTAX DisplayString
    ACCESS  read-write
    STATUS  mandatory
    DESCRIPTION
        "SSH user name"
    ::= {rsIDSOOPTableEntry 5}

rsIDSOOPSSHPassWord OBJECT-TYPE
    SYNTAX  DisplayString
    ACCESS  read-write
    STATUS  mandatory
    DESCRIPTION
      "SSH Password"
    ::=  {rsIDSOOPTableEntry 6}


rsIDSOOPDebugMode OBJECT-TYPE
    SYNTAX INTEGER {
      on(1),
      off(2)
    }
    ACCESS read-write
    STATUS mandatory
    DESCRIPTION
      "Debug mode of out-pf-path"
    DEFVAL  {off}
    ::= {rsIDSOOPTableEntry 7}

rsIDSOOPTableStatus OBJECT-TYPE
    SYNTAX RowStatus
    ACCESS  read-write
    STATUS  mandatory
    DESCRIPTION
       "This variable indicates the administrative status of this entry.
        Used to delete an entry of this table."
    ::=  { rsIDSOOPTableEntry 8 }


rsAntiFraud OBJECT IDENTIFIER ::= { rsIDS 124 }

rsIDSAntiFraudProtectionStatus OBJECT-TYPE
 SYNTAX INTEGER {
      enable(1),
      disable(2)
   }
    ACCESS read-write
    STATUS mandatory
    DESCRIPTION
      "Anti Fraud Protection module status"
   DEFVAL  {disable}
    ::= {rsAntiFraud 1}

rsIDSAntiFraudPhishingAgingTime OBJECT-TYPE
	SYNTAX INTEGER (1..168)
    ACCESS read-write
    STATUS mandatory
    DESCRIPTION
      "Anti Fraud Protection phishing Attack Duration"
    ::= {rsAntiFraud 2}

rsIDSAntiFraudDropPointsAgingTime OBJECT-TYPE
	SYNTAX INTEGER (1..168)
    ACCESS read-write
    STATUS mandatory
    DESCRIPTION
      "Anti Fraud Protection drop point Attack Duration"
    ::= {rsAntiFraud 3}

rsIDSAntiFraudMalDwnldAgingTime OBJECT-TYPE
	SYNTAX INTEGER (1..168)
    ACCESS read-write
    STATUS mandatory
    DESCRIPTION
      "Anti Fraud Protection mal download Attack Duration"
    ::= {rsAntiFraud 4}

rsIDSAntiFraudCheckForUpdatesFreq OBJECT-TYPE
	SYNTAX INTEGER (1..24)
    ACCESS read-write
    STATUS mandatory
    DESCRIPTION
      "Anti Fraud Protection check for updates frequency - in hours"
    ::= {rsAntiFraud 5}

rsIDSAntiFraudLastUpdate OBJECT-TYPE
    SYNTAX DisplayString
    ACCESS  read-only
    STATUS  mandatory
    DESCRIPTION "Last Anti-Fraud Update"
    ::= { rsAntiFraud 6 }

rsIDSAntiFraudInternalLastUpdate OBJECT-TYPE
    SYNTAX DisplayString
    ACCESS  read-write
    STATUS  mandatory
    DESCRIPTION "Last Anti-Fraud Update internal for Vision only."
    ::= { rsAntiFraud 7 }


rsNetFloodDynamicStateFpTable OBJECT-TYPE
    SYNTAX SEQUENCE OF RsNetFloodDynamicStateFpEntry
    ACCESS not-accessible
    STATUS  mandatory
    DESCRIPTION
      "Table containing the list of profiles params for the NetFlood inspection"
    ::=  {rsNetFlood 25}


rsNetFloodDynamicStateFpEntry OBJECT-TYPE
    SYNTAX RsNetFloodDynamicStateFpEntry
    ACCESS not-accessible
    STATUS  mandatory
    DESCRIPTION
       "The row definition for this table."
    INDEX { rsNetFloodDynamicController, rsNetFloodDynamicFpType }
    ::=  { rsNetFloodDynamicStateFpTable 1 }

RsNetFloodDynamicStateFpEntry ::= SEQUENCE {
	rsNetFloodDynamicController INTEGER,
    rsNetFloodDynamicFpType INTEGER,
	rsNetFloodDynamicState INTEGER,
    rsNetFloodDynamicRowStatus RowStatus
}

rsNetFloodDynamicController OBJECT-TYPE
    SYNTAX INTEGER {
   udp-in(0),
   icmp-in(2),
   igmp-in(4),
   tcp-syn-in(6),
   tcp-rst-in(8),
   tcp-ack-fin-in(14),
   tcp-syn-ack-in(16),
   tcp-frag-in(18)
    }
    ACCESS  read-write
    STATUS  mandatory
    DESCRIPTION
       "The controller type"
    ::=  { rsNetFloodDynamicStateFpEntry 1}


rsNetFloodDynamicFpType OBJECT-TYPE
    SYNTAX INTEGER {
    checksum(0),
	sequence-num(1),
    id-num(2),
   dns-id-num(3),
   dns-qname(4),
   dns-subdomain(5),
	dns-qcount(6),
	source-port(7),
    source-ip(8),
	frag-offset(9),
	flow-label(10),
	tos(11),
	packet-size(12),
	destination-port(13),
    destination-ip(14),
    fragment(15),
--  (16),
--  (17),
--  (18),
  icmp-igmp-message-type(19),
    ttl(20),
	id-num-ipv6(21),
	frag-offset-ipv6(22),
--   (23),
	packet-size-ipv6(24),
	source-ip-ipv6(25),
	destination-ip-ipv6(26),
	icmp-message-type-ipv6(27),
	context-tag(28)
    }
    ACCESS  read-write
    STATUS  mandatory
    DESCRIPTION
       "The dynamic footprint type"
    ::=  { rsNetFloodDynamicStateFpEntry 2}

rsNetFloodDynamicState OBJECT-TYPE
    SYNTAX INTEGER {
    no(0),
	yes(1)
    }
    ACCESS  read-write
    STATUS  mandatory
    DESCRIPTION
       "The dynamic state"
    ::=  { rsNetFloodDynamicStateFpEntry 3 }

rsNetFloodDynamicRowStatus OBJECT-TYPE
    SYNTAX RowStatus
    ACCESS  read-write
    STATUS  mandatory
    DESCRIPTION
       "This variable indicates the administrative status of this entry.
        Used to delete an entry of this table."
    ::=  { rsNetFloodDynamicStateFpEntry 4 }


rsNetFloodDynamicStateTwoTable OBJECT-TYPE
    SYNTAX SEQUENCE OF RsNetFloodDynamicStateTwoEntry
    ACCESS not-accessible
    STATUS  mandatory
    DESCRIPTION
      "Table containing the dynamic state 2 any flag"
    ::=  {rsNetFlood 26}


rsNetFloodDynamicStateTwoEntry OBJECT-TYPE
    SYNTAX RsNetFloodDynamicStateTwoEntry
    ACCESS not-accessible
    STATUS  mandatory
    DESCRIPTION
       "The row definition for this table."
    INDEX { rsNetFloodDynamicStateController }
    ::=  { rsNetFloodDynamicStateTwoTable 1 }

RsNetFloodDynamicStateTwoEntry ::= SEQUENCE {
	rsNetFloodDynamicStateController INTEGER,
	rsNetFloodDynamicStateAnyTypeFlag INTEGER,
	rsNetFloodDynamicStateTypeThreshold INTEGER,
	rsNetFloodDynamicStateValThreshold INTEGER,
    rsNetFloodDynamicStateRowStatus RowStatus
}

rsNetFloodDynamicStateController OBJECT-TYPE
    SYNTAX INTEGER {
   udp-in(0),
   icmp-in(2),
   igmp-in(4),
   tcp-syn-in(6),
   tcp-rst-in(8),
   tcp-ack-fin-in(14),
   tcp-syn-ack-in(16),
   tcp-frag-in(18)
    }
    ACCESS  read-write
    STATUS  mandatory
    DESCRIPTION
       "The controller type"
    ::=  { rsNetFloodDynamicStateTwoEntry 1}


rsNetFloodDynamicStateAnyTypeFlag OBJECT-TYPE
    SYNTAX INTEGER {
    false(0),
	true(1)
    }
    ACCESS  read-write
    STATUS  mandatory
    DESCRIPTION
       "The any type flag"
    ::=  { rsNetFloodDynamicStateTwoEntry 2 }

rsNetFloodDynamicStateTypeThreshold OBJECT-TYPE
    SYNTAX INTEGER
    ACCESS  read-write
    STATUS  mandatory
    DESCRIPTION
       "The type threshold (Th1)"
    ::=  { rsNetFloodDynamicStateTwoEntry 3 }

rsNetFloodDynamicStateValThreshold OBJECT-TYPE
    SYNTAX INTEGER  (1..1000)
    ACCESS  read-write
    STATUS  mandatory
    DESCRIPTION
       "The type threshold (Th2)"
    ::=  { rsNetFloodDynamicStateTwoEntry 4 }

rsNetFloodDynamicStateRowStatus OBJECT-TYPE
    SYNTAX RowStatus
    ACCESS  read-write
    STATUS  mandatory
    DESCRIPTION
       "This variable indicates the administrative status of this entry.
        Used to delete an entry of this table."
    ::=  { rsNetFloodDynamicStateTwoEntry 5 }

rsNetFloodDynamicTermSC2 OBJECT-TYPE
 SYNTAX INTEGER (0..30)
   ACCESS  read-write
   STATUS  mandatory
   DESCRIPTION
       "stability counter for state 2"
    ::=  { rsNetFlood 27}

rsNetFloodDynamicTermSC6 OBJECT-TYPE
 SYNTAX INTEGER (45..300)
   ACCESS  read-write
   STATUS  mandatory
   DESCRIPTION
       "stability counter for state 6"
    ::=  { rsNetFlood 28}

rsNetFloodDynamicTermSC37 OBJECT-TYPE
 SYNTAX INTEGER (45..300)
   ACCESS  read-write
   STATUS  mandatory
   DESCRIPTION
       "stability counter for state 3 & 7"
    ::=  { rsNetFlood 29}

rsNetFloodAvgUdpSzNorm OBJECT-TYPE
 SYNTAX INTEGER (1..65535)
   ACCESS  read-write
   STATUS  mandatory
   DESCRIPTION
       "Avg Udp normal packet size"
    ::=  { rsNetFlood 30}

rsNetFloodAvgUdpSzAttack OBJECT-TYPE
 SYNTAX INTEGER (1..65535)
   ACCESS  read-write
   STATUS  mandatory
   DESCRIPTION
       "Avg Udp normal packet size"
    ::=  { rsNetFlood 31}

rsNetFloodEnableANDrestriction OBJECT-TYPE
    SYNTAX INTEGER {
			enable(1),
			disable(2)}
   ACCESS  read-write
   STATUS  mandatory
   DESCRIPTION
       "maximum fields in AND list"
   DEFVAL  {enable}
    ::=  { rsNetFlood 32}

rsNetFloodExpertTableT2 OBJECT-TYPE
   SYNTAX DisplayString
   ACCESS  read-write
   STATUS  mandatory
   DESCRIPTION
       "Bdos expert table T2 value"
    ::=  { rsNetFlood 33}

rsNetFloodExpertTableT3 OBJECT-TYPE
   SYNTAX DisplayString
   ACCESS  read-write
   STATUS  mandatory
   DESCRIPTION
       "Bdos expert table T3 value"
    ::=  { rsNetFlood 34}

rsNetFloodExpertTableT4 OBJECT-TYPE
   SYNTAX DisplayString
   ACCESS  read-write
   STATUS  mandatory
   DESCRIPTION
       "Bdos expert table T4 value"
    ::=  { rsNetFlood 35}

rsNetFloodExpertTableT6 OBJECT-TYPE
   SYNTAX DisplayString
   ACCESS  read-write
   STATUS  mandatory
   DESCRIPTION
       "Bdos expert table T6 value"
    ::=  { rsNetFlood 36}

rsNetFloodExpertTableT7 OBJECT-TYPE
   SYNTAX DisplayString
   ACCESS  read-write
   STATUS  mandatory
   DESCRIPTION
       "Bdos expert table T7 value"
    ::=  { rsNetFlood 37}

rsNetFloodExpertTableT8 OBJECT-TYPE
   SYNTAX DisplayString
   ACCESS  read-write
   STATUS  mandatory
   DESCRIPTION
       "Bdos expert table T8 value"
    ::=  { rsNetFlood 38}

rsNetFloodOverBlockingGlobalStatus OBJECT-TYPE
    SYNTAX INTEGER {
     enable(1),
     disable(2)
	}
    ACCESS  read-write
    STATUS  mandatory
    DESCRIPTION
       "This variable indicates the over blocking global status"
    ::=  { rsNetFlood 41 }

rsIdsHwaccWarning OBJECT-TYPE
    SYNTAX DisplayString (SIZE(0..255))
    ACCESS  read-only
    STATUS  mandatory
    DESCRIPTION
      "A warning issued in the snmp process of some classes or DP policy, regarding the HW accelerator compatibility"
    ::=  {rsIDS 125}

rsIDSHttpfldSuspectSrcIp OBJECT-TYPE
    SYNTAX INTEGER
    ACCESS read-only
    STATUS mandatory
    DESCRIPTION
      "Tuning parameter for the http-flood maximal number suspect sources"
    ::= {rsIDS 126}

rsIDSHttpfldSuspectSrcIpAfterReset OBJECT-TYPE
    SYNTAX INTEGER
    ACCESS read-write
    STATUS mandatory
    DESCRIPTION
      "Tuning parameter for the http-flood maximal number suspect sources after the next reset"
    ::= {rsIDS 127}

rsIDSPPS OBJECT IDENTIFIER ::= { rsIDS 130}

rsIDSPPSProfileTable OBJECT-TYPE
	SYNTAX SEQUENCE OF RsIDSPPSProfileEntry
	ACCESS not-accessible
	STATUS  mandatory
    DESCRIPTION
      "Table containing the list of connection limiting profiles"
    ::=  {rsIDSPPS 2}

rsIDSPPSProfileEntry OBJECT-TYPE
    SYNTAX RsIDSPPSProfileEntry
    ACCESS not-accessible
    STATUS  mandatory
    DESCRIPTION
       "The row definition for this table."
    INDEX { rsIDSPPSProfileName, rsIDSPPSProfileAttackName }
    ::=  { rsIDSPPSProfileTable 1 }

RsIDSPPSProfileEntry ::= SEQUENCE {
    rsIDSPPSProfileName DisplayString,
    rsIDSPPSProfileAttackName DisplayString,
   	rsIDSPPSProfileAttackId INTEGER,
    rsIDSPPSProfileStatus RowStatus
}

rsIDSPPSProfileName OBJECT-TYPE
    SYNTAX DisplayString (SIZE(1..29))
    ACCESS  read-only
    STATUS  mandatory
    DESCRIPTION
      "The Name of the Profile."
    ::=  {rsIDSPPSProfileEntry 1}

rsIDSPPSProfileAttackName OBJECT-TYPE
    SYNTAX DisplayString (SIZE(1..29))
    ACCESS  read-only
    STATUS  mandatory
    DESCRIPTION
      "The Connection limiting attack Name."
    ::=  {rsIDSPPSProfileEntry 2}

rsIDSPPSProfileAttackId OBJECT-TYPE
    SYNTAX INTEGER
    ACCESS read-write
    STATUS mandatory
    DESCRIPTION
      "The profile service ID. this field should not be visible to the user."
    ::=  { rsIDSPPSProfileEntry 3 }

rsIDSPPSProfileStatus OBJECT-TYPE
    SYNTAX RowStatus
    ACCESS  read-write
    STATUS  mandatory
    DESCRIPTION
       "This variable indicates the administrative status of this entry.
        Used to delete an entry of this table."
    ::=  { rsIDSPPSProfileEntry 4 }

rsIDSPPSAttackTable OBJECT-TYPE
	SYNTAX SEQUENCE OF RsIDSPPSAttackEntry
	ACCESS not-accessible
	STATUS  mandatory
    DESCRIPTION
      "Table containing the list of connection limiting attacks"
    ::=  {rsIDSPPS 3}

rsIDSPPSAttackEntry OBJECT-TYPE
    SYNTAX RsIDSPPSAttackEntry
    ACCESS not-accessible
    STATUS  mandatory
    DESCRIPTION
       "The row definition for this table."
    INDEX { rsIDSPPSAttackId }
    ::=  { rsIDSPPSAttackTable 1 }

RsIDSPPSAttackEntry ::= SEQUENCE {
	rsIDSPPSAttackId INTEGER,
	rsIDSPPSAttackName DisplayString,
	rsIDSPPSAttackAppPort DisplayString,
	rsIDSPPSAttackTrackingType INTEGER,
	rsIDSPPSAttackActThres INTEGER,
	rsIDSPPSAttackTermThres INTEGER,
	rsIDSPPSAttackDropThres INTEGER,
	rsIDSPPSAttackRisk INTEGER,
	rsIDSPPSAttackActionMode INTEGER,
	rsIDSPPSAttackActPeriod INTEGER,
	rsIDSPPSAttackTermPeriod INTEGER,
	rsIDSPPSAttackStatus RowStatus,
	rsIDSPPSAttackPacketTrace INTEGER
}

rsIDSPPSAttackId OBJECT-TYPE
    SYNTAX INTEGER
    ACCESS  read-write
    STATUS  mandatory
    DESCRIPTION
       "This variable indicates the object type- whether it is a filter or group  "
    ::=  { rsIDSPPSAttackEntry 1}

rsIDSPPSAttackName OBJECT-TYPE
    SYNTAX DisplayString (SIZE(1..29))
    ACCESS  read-write
    STATUS  mandatory
    DESCRIPTION
      "The Name for the attack must be unique."
    ::=  {rsIDSPPSAttackEntry 2}

rsIDSPPSAttackAppPort OBJECT-TYPE
    SYNTAX DisplayString (SIZE(0..29))
    ACCESS  read-write
    STATUS  mandatory
    DESCRIPTION
      "The desteantion appliction port on which the attack is defined for."
    ::=  {rsIDSPPSAttackEntry 3}

rsIDSPPSAttackTrackingType OBJECT-TYPE
    SYNTAX INTEGER {
		connection(1)
	}
    ACCESS read-write
    STATUS mandatory
    DESCRIPTION
      "Indicates whether the rate limit is per connection or per source"
	DEFVAL  {connection}
    ::= {rsIDSPPSAttackEntry 4}

rsIDSPPSAttackActThres OBJECT-TYPE
    SYNTAX INTEGER
    ACCESS  read-write
    STATUS  mandatory
    DESCRIPTION
       "This variable indicates connection activiation threshold  "
	DEFVAL{10000}
    ::=  { rsIDSPPSAttackEntry 5}

rsIDSPPSAttackTermThres OBJECT-TYPE
    SYNTAX INTEGER
    ACCESS  read-write
    STATUS  mandatory
    DESCRIPTION
       "This variable indicates connection termination threshold"
	DEFVAL{9000}
    ::=  { rsIDSPPSAttackEntry 6}

rsIDSPPSAttackDropThres OBJECT-TYPE
    SYNTAX INTEGER
    ACCESS  read-write
    STATUS  mandatory
    DESCRIPTION
       "This variable indicates connection drop threshold"
    ::=  {rsIDSPPSAttackEntry 7}

rsIDSPPSAttackRisk OBJECT-TYPE
    SYNTAX INTEGER {
 		  info(1),
		  low(2),
       	  medium(3),
		  high(4)}
    ACCESS  read-write
    STATUS  mandatory
    DESCRIPTION
       "This variable indicates the risk of the attack"
	DEFVAL  {medium}
    ::=  {rsIDSPPSAttackEntry 8}

rsIDSPPSAttackActionMode OBJECT-TYPE
	SYNTAX INTEGER {
	    report-only(0),
	    drop(10)}
    ACCESS  read-write
    STATUS  mandatory
    DESCRIPTION
       "This variable indicates the stable threshold period."
    ::=  { rsIDSPPSAttackEntry 9 }

rsIDSPPSAttackActPeriod OBJECT-TYPE
    SYNTAX INTEGER
    ACCESS  read-write
    STATUS  mandatory
    DESCRIPTION
       "This variable indicates the stable threshold period."
	DEFVAL{1}
    ::=  { rsIDSPPSAttackEntry 10 }

rsIDSPPSAttackTermPeriod OBJECT-TYPE
    SYNTAX INTEGER
    ACCESS  read-write
    STATUS  mandatory
    DESCRIPTION
       "This variable indicates the stable threshold period."
    ::=  { rsIDSPPSAttackEntry 11 }

	rsIDSPPSAttackStatus OBJECT-TYPE
    SYNTAX RowStatus
    ACCESS  read-write
    STATUS  mandatory
    DESCRIPTION
       "This variable indicates the administrative status of this entry. Used to delete an entry of this table."
	DEFVAL{1}
    ::=  { rsIDSPPSAttackEntry 12 }

rsIDSPPSAttackPacketTrace OBJECT-TYPE
    SYNTAX INTEGER {
			enable(1),
			disable(2)}
    ACCESS  read-write
    STATUS  mandatory
    DESCRIPTION
       "This variable indicates the per-attack packet trace"
	DEFVAL  {disable}
    ::=  {rsIDSPPSAttackEntry 13}

rsIDSPPSAttackNextID OBJECT-TYPE
	SYNTAX INTEGER
    ACCESS read-only
    STATUS mandatory
    DESCRIPTION
		"the next attack id for pps attacks"
    ::= {rsIDSPPS 4}

rsIDSPPSMaxPerConnectionAttacks OBJECT-TYPE
    SYNTAX INTEGER
    ACCESS read-write
    STATUS mandatory
    DESCRIPTION
      "Tuning parameter for the PPS max attacked connection after the next reset"
    ::= {rsIDS 131}

rsIDSMAXConnectionIP OBJECT-TYPE
    SYNTAX INTEGER
    ACCESS read-write
    STATUS mandatory
    DESCRIPTION
      "Tuning parameter for the PPS max attacked connection after the next reset"
    ::= {rsIDS 134}

rsIDSPPSMaxSrcIp OBJECT-TYPE
    SYNTAX INTEGER
    ACCESS read-write
    STATUS mandatory
    DESCRIPTION
      "Tuning parameter for the PPS maximal number suspect sources after the next reset"
    ::= {rsIDS 135}

rsIDSPPSMaxTrackedSources OBJECT-TYPE
    SYNTAX INTEGER
    ACCESS read-write
    STATUS mandatory
    DESCRIPTION
      "Tuning parameter for the PPS maximal number suspect sources after the next reset"
    ::= {rsIDS 137}

rsIDSBWMReportTrackTime OBJECT-TYPE
    SYNTAX INTEGER (1..3600)
    ACCESS read-write
    STATUS mandatory
    DESCRIPTION
      "Policy Return to Normal Threshold Sustained Period (in seconds)"
    ::= {rsIDS 138}

rsIDSBWMReportStartThreshold OBJECT-TYPE
    SYNTAX INTEGER (1..100)
    ACCESS read-write
    STATUS mandatory
    DESCRIPTION
      "Policy Exceed Threshold (in %)"
    ::= {rsIDS 139}

rsIDSBWMReportTermThresholdDelta OBJECT-TYPE
    SYNTAX INTEGER (1..100)
    ACCESS read-write
    STATUS mandatory
    DESCRIPTION
      "Policy Return to Normal Threshold (in %). delta from rsIDSBWMReportStartThreshold"
    ::= {rsIDS 140}

rsIDSPacketTrace OBJECT IDENTIFIER ::= { rsIDS 141}

rsIDSPacketTraceStatus OBJECT-TYPE
     SYNTAX INTEGER {
			enable(1),
			disable(2)}
    ACCESS  read-write
    STATUS  mandatory
    DESCRIPTION
       "This variable indicates the packet trace mechanism status"
	DEFVAL  {disable}
    ::=  { rsIDSPacketTrace 1 }

rsIDSPacketTracePort OBJECT-TYPE
	SYNTAX INTEGER
    ACCESS read-write
    STATUS mandatory
    DESCRIPTION
      "The destinated port which will be used to trace traffic"
	  ::=  { rsIDSPacketTrace 2 }

rsIDSPacketTraceMaxPacketRate OBJECT-TYPE
	SYNTAX INTEGER
    ACCESS read-write
    STATUS mandatory
    DESCRIPTION
      "Determines the max bandwidth for trace output in pps"
	  ::=  { rsIDSPacketTrace 3 }

rsIDSPacketTracePacketLength OBJECT-TYPE
	SYNTAX INTEGER
    ACCESS read-write
    STATUS mandatory
    DESCRIPTION
      "The length of the forensic packet"
	  ::=  { rsIDSPacketTrace 4 }


-- Suspend table NEW Mib

rsIDSNewerSuspendTable OBJECT-TYPE
    SYNTAX SEQUENCE OF RsIDSNewerSuspendTableEntry
    ACCESS not-accessible
    STATUS  mandatory
    DESCRIPTION
      "Dynamic Blocking Table"
    ::= { rsIDS 142 }

rsIDSNewerSuspendTableEntry OBJECT-TYPE
    SYNTAX RsIDSNewerSuspendTableEntry
    ACCESS not-accessible
    STATUS mandatory
    DESCRIPTION
       "The row definition for this table."
    INDEX { rsIDSNewerSuspendTableEntryIndex}
    ::=  { rsIDSNewerSuspendTable 1 }


RsIDSNewerSuspendTableEntry ::= SEQUENCE {
    rsIDSNewerSuspendTableEntryIndex INTEGER,
    rsIDSNewerSuspendTableEntrySrcIp DisplayString,
    rsIDSNewerSuspendTableEntryDstIp DisplayString,
    rsIDSNewerSuspendTableEntryDstPort INTEGER,
    rsIDSNewerSuspendTableEntryProtocol INTEGER,
	rsIDSNewerSuspendTableEntryModule INTEGER,
	rsIDSNewerSuspendTableEntryClassType INTEGER,
	rsIDSNewerSuspendTableEntryClassName DisplayString,
    rsIDSNewerSuspendTableEntryExpType INTEGER,
	rsIDSNewerSuspendTableEntryExpTime INTEGER,
	rsIDSNewerSuspendTableEntryAction INTEGER,
	rsIDSNewerSuspendTableEntryAttackID INTEGER
}

rsIDSNewerSuspendTableEntryIndex OBJECT-TYPE
    SYNTAX INTEGER
    ACCESS read-only
    STATUS mandatory
    DESCRIPTION
      "The ID of the current entry"
    ::=  { rsIDSNewerSuspendTableEntry 1 }

rsIDSNewerSuspendTableEntrySrcIp OBJECT-TYPE
    SYNTAX DisplayString(SIZE(1..46))
    ACCESS read-only
    STATUS mandatory
    DESCRIPTION
      "Source IP"
    ::=  { rsIDSNewerSuspendTableEntry 2 }

rsIDSNewerSuspendTableEntryDstIp OBJECT-TYPE
    SYNTAX DisplayString(SIZE(1..46))
    ACCESS read-only
    STATUS mandatory
    DESCRIPTION
      "Destination IP"
    ::=  { rsIDSNewerSuspendTableEntry 3 }

rsIDSNewerSuspendTableEntryDstPort OBJECT-TYPE
    SYNTAX INTEGER
    ACCESS read-only
    STATUS mandatory
    DESCRIPTION
      "Destination Port"
    ::=  { rsIDSNewerSuspendTableEntry 4 }

rsIDSNewerSuspendTableEntryProtocol OBJECT-TYPE
    SYNTAX INTEGER {
			ip(0),
			tcp(1),
			udp(2),
			icmp(3),
			icmpv6(5)}
    ACCESS read-only
    STATUS mandatory
    DESCRIPTION
      "Protocol"
    ::=  { rsIDSNewerSuspendTableEntry 5 }

rsIDSNewerSuspendTableEntryModule OBJECT-TYPE
    SYNTAX INTEGER {
			signatures(0),
			connection-limit(1),
			anti-scanning(2),
			traffic-filters(3)}
	ACCESS read-only
    STATUS mandatory
    DESCRIPTION
      "Module"
    ::=  { rsIDSNewerSuspendTableEntry 6 }

rsIDSNewerSuspendTableEntryClassType OBJECT-TYPE
    SYNTAX INTEGER {
			policy(0),
			server(1)}
	ACCESS read-only
    STATUS mandatory
    DESCRIPTION
      "Classification Object type"
    ::=  { rsIDSNewerSuspendTableEntry 7 }

rsIDSNewerSuspendTableEntryClassName OBJECT-TYPE
    SYNTAX DisplayString(SIZE(1..29))
	ACCESS read-only
    STATUS mandatory
    DESCRIPTION
      "Classification Object name"
    ::=  { rsIDSNewerSuspendTableEntry 8 }

rsIDSNewerSuspendTableEntryExpType OBJECT-TYPE
    SYNTAX INTEGER {
			on-request(0),
			fixed-timeout(1),
			dynamic-timeout(2)}
    ACCESS read-only
    STATUS mandatory
    DESCRIPTION
      "Expiration Type"
    ::=  { rsIDSNewerSuspendTableEntry 9 }

rsIDSNewerSuspendTableEntryExpTime OBJECT-TYPE
    SYNTAX INTEGER
    ACCESS read-only
    STATUS mandatory
    DESCRIPTION
      "Time To Live"
    ::=  { rsIDSNewerSuspendTableEntry 10 }


rsIDSNewerSuspendTableEntryAction OBJECT-TYPE
    SYNTAX INTEGER {
			report(0),
			block(1)}
	ACCESS read-only
    STATUS mandatory
    DESCRIPTION
      "Action"
    ::=  { rsIDSNewerSuspendTableEntry 11}

rsIDSNewerSuspendTableEntryAttackID OBJECT-TYPE
    SYNTAX INTEGER
    ACCESS read-only
    STATUS mandatory
    DESCRIPTION
      "Attack ID"
    ::=  { rsIDSNewerSuspendTableEntry 12 }


rsIDSLoop OBJECT IDENTIFIER ::= { rsIDS 143}

rsIDSLoopGlobalStatus OBJECT-TYPE
     SYNTAX INTEGER {
			enable(1),
			disable(2)}
    ACCESS  read-write
    STATUS  mandatory
    DESCRIPTION
       "This variable indicates the local out-of-path mechanism status"
	DEFVAL  {disable}
    ::=  { rsIDSLoop 1 }

rsIDSLoopConfigurationStatus OBJECT-TYPE
	SYNTAX INTEGER {
    		success(1),
			failure(2)}
    ACCESS read-only
    STATUS  mandatory
    DESCRIPTION
      "This variable indicates the local out-of-path configuration status"
	DEFVAL  {success}
	  ::=  { rsIDSLoop 2 }

rsIDSLoopGlobalDiversionStatus OBJECT-TYPE
	SYNTAX INTEGER {
			started(1),
			manual-ended(2),
			automat-ended(3),
			peacetime(4),
			failed(5),
			manual(6)}
    ACCESS  read-write
    STATUS  mandatory
    DESCRIPTION
       "This variable indicates the local out-of-path diversion status"
	DEFVAL  {peacetime}
    ::=  { rsIDSLoop 3 }

rsIDSLoopGlobalSwitchStatus OBJECT-TYPE
	SYNTAX INTEGER {
			up(1),
			unreachable(2)}
    ACCESS read-only
    STATUS  mandatory
    DESCRIPTION
       "This variable indicates the local out-of-path switch status"
	DEFVAL  {up}
    ::=  { rsIDSLoop 4 }

rsIDSLoopAdvancedMode OBJECT-TYPE
	SYNTAX INTEGER {
			automatic(1),
			manual(2)}
    ACCESS read-write
    STATUS  mandatory
    DESCRIPTION
       "This variable indicates the local out-of-path mode status"
	DEFVAL  {automatic}
    ::=  { rsIDSLoop 5 }


rsIDSLoopConfigurationTable OBJECT-TYPE
    SYNTAX SEQUENCE OF RsIDSLoopConfigurationTableEntry
    ACCESS not-accessible
    STATUS  mandatory
    DESCRIPTION
      "Table containing the LOOP configuration table."
    ::= { rsIDSLoop 6 }

rsIDSLoopConfigurationTableEntry OBJECT-TYPE
    SYNTAX RsIDSLoopConfigurationTableEntry
    ACCESS not-accessible
    STATUS mandatory
    DESCRIPTION
       "The definition for LOOP configuration table entry."
    INDEX { rsLOOPTblEntryPortIndex }
    ::=  { rsIDSLoopConfigurationTable 1 }

RsIDSLoopConfigurationTableEntry ::= SEQUENCE {
    rsLOOPTblEntryPortIndex INTEGER,
   	rsLOOPTblEntryPortName DisplayString,
	rsLOOPTblEntryPortInbound INTEGER,
	rsLOOPTblEntryPortOutbound	INTEGER
}

rsLOOPTblEntryPortIndex OBJECT-TYPE
    SYNTAX INTEGER
    ACCESS read-write
    STATUS mandatory
    DESCRIPTION
      "This variable indicates the index of this entry "
    ::=  { rsIDSLoopConfigurationTableEntry 1 }

rsLOOPTblEntryPortName OBJECT-TYPE
    SYNTAX DisplayString (SIZE(0..40))
    ACCESS  read-write
    STATUS  mandatory
    DESCRIPTION
      "The Name for the entry."
    ::=  { rsIDSLoopConfigurationTableEntry 2 }

rsLOOPTblEntryPortInbound OBJECT-TYPE
    SYNTAX INTEGER
    ACCESS read-write
    STATUS mandatory
    DESCRIPTION
      "The Inbound port value."
    ::=  { rsIDSLoopConfigurationTableEntry 3 }

rsLOOPTblEntryPortOutbound OBJECT-TYPE
    SYNTAX INTEGER
    ACCESS read-write
    STATUS mandatory
    DESCRIPTION
      "The Outbound port value."
    ::=  { rsIDSLoopConfigurationTableEntry 4 }

rsIDSLoopConfigurationDeviceTable OBJECT-TYPE
    SYNTAX SEQUENCE OF RsIDSLoopConfigurationDeviceTableEntry
    ACCESS not-accessible
    STATUS  mandatory
    DESCRIPTION
      "Table containing the LOOP Device configuration table."
    ::= { rsIDSLoop 7 }

rsIDSLoopConfigurationDeviceTableEntry OBJECT-TYPE
    SYNTAX RsIDSLoopConfigurationDeviceTableEntry
    ACCESS not-accessible
    STATUS mandatory
    DESCRIPTION
       "The definition for LOOP configuration table entry."
    INDEX { rsLOOPDeviceTblEntryPortIndex }
    ::=  { rsIDSLoopConfigurationDeviceTable 1 }

RsIDSLoopConfigurationDeviceTableEntry ::= SEQUENCE {
    rsLOOPDeviceTblEntryPortIndex INTEGER,
   	rsLOOPDeviceTblEntryPortName DisplayString,
	rsLOOPDeviceTblEntryPortInbound INTEGER,
	rsLOOPDeviceTblEntryPortOutbound	INTEGER
}

rsLOOPDeviceTblEntryPortIndex OBJECT-TYPE
    SYNTAX INTEGER
    ACCESS read-write
    STATUS mandatory
    DESCRIPTION
      "This variable indicates the index of this entry "
    ::=  { rsIDSLoopConfigurationDeviceTableEntry 1 }

rsLOOPDeviceTblEntryPortName OBJECT-TYPE
    SYNTAX DisplayString (SIZE(0..40))
    ACCESS  read-write
    STATUS  mandatory
    DESCRIPTION
      "The Name for the entry."
    ::=  { rsIDSLoopConfigurationDeviceTableEntry 2 }

rsLOOPDeviceTblEntryPortInbound OBJECT-TYPE
    SYNTAX INTEGER
    ACCESS read-write
    STATUS mandatory
    DESCRIPTION
      "The Inbound port value."
    ::=  { rsIDSLoopConfigurationDeviceTableEntry 3 }

rsLOOPDeviceTblEntryPortOutbound OBJECT-TYPE
    SYNTAX INTEGER
    ACCESS read-write
    STATUS mandatory
    DESCRIPTION
      "The Outbound port value."
    ::=  { rsIDSLoopConfigurationDeviceTableEntry 4 }

rsIDSLoopAdvancedActivationTimeout OBJECT-TYPE
	SYNTAX INTEGER (0..1200)
    ACCESS read-write
    STATUS mandatory
    DESCRIPTION
      "Activatio(Diversion) Timeout in seconds"
	 DEFVAL  {10}
    ::= { rsIDSLoop 8 }

rsIDSLoopAdvancedTerminationTimeout OBJECT-TYPE
    SYNTAX INTEGER (0..1200)
    ACCESS read-write
    STATUS mandatory
    DESCRIPTION
      "Termination Timeout in seconds"
	DEFVAL  {20}
    ::= { rsIDSLoop 9 }

rsIDSLoopAdvancedManualStatus OBJECT-TYPE
   SYNTAX INTEGER {
			start(1),
			stop(2)}
   ACCESS  read-write
   STATUS  mandatory
   DESCRIPTION
      "Manual diversion status."
     ::= { rsIDSLoop 10 }

rsIDSLoopConfigurationMngIPAddr OBJECT-TYPE
	SYNTAX IpAddress
    ACCESS  read-write
    STATUS  mandatory
    DESCRIPTION
        "The IP Address of the Management."
    ::= { rsIDSLoop 11 }

rsIDSLoopConfigurationSSHUser OBJECT-TYPE
   SYNTAX DisplayString (SIZE(1..29))
   ACCESS  read-write
   STATUS  mandatory
   DESCRIPTION
      "SSH user string."
     ::= { rsIDSLoop 12 }

rsIDSLoopConfigurationSSHPassword OBJECT-TYPE
   SYNTAX DisplayString (SIZE(1..29))
   ACCESS  read-write
   STATUS  mandatory
   DESCRIPTION
      "SSH user password."
     ::= { rsIDSLoop 13 }

rsIDSLoopConfigurationUser OBJECT-TYPE
   SYNTAX DisplayString (SIZE(1..29))
   ACCESS  read-write
   STATUS  mandatory
   DESCRIPTION
      "User string."
     ::= { rsIDSLoop 14 }

rsIDSLoopConfigurationPassword OBJECT-TYPE
   SYNTAX DisplayString (SIZE(1..29))
   ACCESS  read-write
   STATUS  mandatory
   DESCRIPTION
      "User password."
     ::= { rsIDSLoop 15 }


rsIDSLoopGlobalLoopDeviceType OBJECT-TYPE
SYNTAX INTEGER {
			netOptics-Director(1),
			netOptics-Director-xStream(2)}
   ACCESS  read-write
   STATUS  mandatory
   DESCRIPTION
      "Loop Device Type."
     ::= { rsIDSLoop 16 }


rsIDSFPRisk OBJECT IDENTIFIER ::= { rsIDS 144}

rsIDSFPRiskStatus OBJECT-TYPE
 SYNTAX INTEGER {
      enable(1),
      disable(2)
   }
    ACCESS read-write
    STATUS mandatory
    DESCRIPTION
      "False Positive Risk Analysis Trigger"
   DEFVAL  {disable}
    ::= {rsIDSFPRisk 1}

rsIDSFPRiskReportPeriod OBJECT-TYPE
 SYNTAX INTEGER (5..100)
    ACCESS read-write
    STATUS mandatory
    DESCRIPTION
      "False Positive Risk Analysis Report period (sec)"
	DEFVAL {10}
    ::= {rsIDSFPRisk 2}

rsIDSFPRiskAttackTable OBJECT-TYPE
	SYNTAX SEQUENCE OF RsIDSFPRiskAttackEntry
	ACCESS not-accessible
	STATUS  mandatory
    DESCRIPTION
      "Table containing the list of latest attacks under signature simulation"
    ::=  {rsIDSFPRisk 3}

rsIDSFPRiskAttackEntry OBJECT-TYPE
    SYNTAX RsIDSFPRiskAttackEntry
    ACCESS not-accessible
    STATUS  mandatory
    DESCRIPTION
       "The row definition for this table."
    INDEX { rsIDSFPRiskAttackType, rsIDSFPRiskAttackReportIdTime, rsIDSFPRiskAttackReportIdCounter }
    ::=  { rsIDSFPRiskAttackTable 1 }

RsIDSFPRiskAttackEntry ::= SEQUENCE {
	rsIDSFPRiskAttackType INTEGER,
	rsIDSFPRiskAttackReportIdTime INTEGER,
	rsIDSFPRiskAttackReportIdCounter INTEGER,
	rsIDSFPRiskAttackRowStatus RowStatus,
	rsIDSFPRiskAttackSimulationDuration INTEGER,
	rsIDSFPRiskAttackSimulationAction INTEGER,
	rsIDSFPRiskAttackSimulationStopAtAttackEnd INTEGER,
	rsIDSFPRiskAttackStabilizationDuration INTEGER,
	rsIDSFPRiskAttackSimulationStartWhenSigChange INTEGER,
	rsIDSFPRiskAttackJointDistributionStatus INTEGER,
	rsIDSFPRiskAttackSimulationStop   INTEGER,
	rsIDSFPRiskAttackSimulationStatus INTEGER,
	rsIDSFPRiskAttackAttackStatus     INTEGER,
	rsIDSFPRiskAttackSimulationRunTime INTEGER,
	rsIDSFPRiskAttackSimulationType INTEGER
}

rsIDSFPRiskAttackType OBJECT-TYPE
    SYNTAX INTEGER {
      behavioral-dos(1),
      dos-shield(2)
	}
    ACCESS read-write
    STATUS mandatory
    DESCRIPTION
      "The type of the attack under simulation"
    ::= {rsIDSFPRiskAttackEntry 1}

rsIDSFPRiskAttackReportIdTime OBJECT-TYPE
    SYNTAX INTEGER
    ACCESS read-write
    STATUS mandatory
    DESCRIPTION
      "The id of the attack under simulation (the time part of the report id)"
    ::= {rsIDSFPRiskAttackEntry 2}

rsIDSFPRiskAttackReportIdCounter OBJECT-TYPE
    SYNTAX INTEGER
    ACCESS read-write
    STATUS mandatory
    DESCRIPTION
      "The id of the attack under simulation (the counter part of the report id)"
    ::= {rsIDSFPRiskAttackEntry 3}

rsIDSFPRiskAttackRowStatus OBJECT-TYPE
    SYNTAX RowStatus
    ACCESS read-write
    STATUS mandatory
    DESCRIPTION
      "The row status of this entry"
    ::= {rsIDSFPRiskAttackEntry 4}

rsIDSFPRiskAttackSimulationDuration OBJECT-TYPE
    SYNTAX INTEGER (1..60)
    ACCESS read-write
    STATUS mandatory
    DESCRIPTION
      "The pre-defined duration of this simulation (minutes)"
	DEFVAL {10}
    ::= {rsIDSFPRiskAttackEntry 5}

rsIDSFPRiskAttackSimulationAction OBJECT-TYPE
    SYNTAX INTEGER {
        report(0),
        block(1),
		report-and-simulate(2),
		block-and-simulate(3)
	}
    ACCESS read-write
    STATUS mandatory
    DESCRIPTION
      "The action of this simulation"
    ::= {rsIDSFPRiskAttackEntry 6}

rsIDSFPRiskAttackSimulationStopAtAttackEnd OBJECT-TYPE
    SYNTAX INTEGER {
    false(0),
	true(1)
    }
    ACCESS read-write
	STATUS mandatory
    DESCRIPTION
      "A flag indicating if the simulation will stop at the end of the attack or continue the pre-define duration"
	DEFVAL {true}
    ::= {rsIDSFPRiskAttackEntry 7}

rsIDSFPRiskAttackStabilizationDuration  OBJECT-TYPE
    SYNTAX INTEGER (5..60)
    ACCESS read-write
    STATUS mandatory
    DESCRIPTION
      "The number of seconds after the signature is stable, before starting the simulation (For BDoS only)"
	DEFVAL {10}
    ::= {rsIDSFPRiskAttackEntry 8}

rsIDSFPRiskAttackSimulationStartWhenSigChange  OBJECT-TYPE
    SYNTAX INTEGER {
    false(0),
	true(1)
    }
    ACCESS read-write
    STATUS mandatory
    DESCRIPTION
      "A flag indicating if the simulation will restart if the signature changed (For BDoS only)"
	DEFVAL {false}
    ::= {rsIDSFPRiskAttackEntry 9}

rsIDSFPRiskAttackJointDistributionStatus OBJECT-TYPE
 SYNTAX INTEGER {
      enable(1),
      disable(2)
   }
    ACCESS read-write
    STATUS mandatory
    DESCRIPTION
      "A flag indicating if the joint distribution statistics will be reported (For BDoS only)"
    ::= {rsIDSFPRiskAttackEntry 10}

rsIDSFPRiskAttackSimulationStop OBJECT-TYPE
    SYNTAX INTEGER {
    false(0),
	true(1)
    }
    ACCESS read-write
    STATUS mandatory
    DESCRIPTION
      "If set to true, the simulation will stop immediately"
    ::= {rsIDSFPRiskAttackEntry 11}

rsIDSFPRiskAttackSimulationStatus OBJECT-TYPE
    SYNTAX INTEGER {
	   ongoing(0),
	   ended(1),
	   suspended(2),
	   not-under-simulation(3)
	}
    ACCESS read-only
    STATUS mandatory
    DESCRIPTION
      "The cuurent status of this attack simulation"
    ::= {rsIDSFPRiskAttackEntry 12}

rsIDSFPRiskAttackAttackStatus OBJECT-TYPE
    SYNTAX INTEGER {
	   ongoing(0),
	   ended(1),
	   unstable(2),
	   anomaly(3)
	}
    ACCESS read-only
    STATUS mandatory
    DESCRIPTION
      "The cuurent status of this attack"
    ::= {rsIDSFPRiskAttackEntry 13}

rsIDSFPRiskAttackSimulationRunTime  OBJECT-TYPE
    SYNTAX INTEGER
    ACCESS read-only
    STATUS mandatory
    DESCRIPTION
      "The number of seconds since the current simulation began"
    ::= {rsIDSFPRiskAttackEntry 14}

rsIDSFPRiskAttackSimulationType  OBJECT-TYPE
    SYNTAX INTEGER {
	   pre-defined(1),
	   real-time(2)
	}
    ACCESS read-only
    STATUS mandatory
    DESCRIPTION
      "The type of this simulation entry"
    ::= {rsIDSFPRiskAttackEntry 15}

rsIDSGeoIPDBVersion OBJECT-TYPE
    SYNTAX DisplayString (SIZE(0..30))
    ACCESS  read-only
    STATUS  mandatory
    DESCRIPTION
      "The version of the current GeoIP database file"
    ::=  {rsIDS 145}

rsIDSGeoIPDBUpdateRes OBJECT-TYPE
 SYNTAX INTEGER {
     succeeded(1),
     failed(2),
     processing(3)
   }
    ACCESS read-only
    STATUS mandatory
    DESCRIPTION
      "The GeoIP db file update result"
    ::= {rsIDS 146}

rsIDSGeoIPDBSend OBJECT-TYPE
    SYNTAX DisplayString
    ACCESS  read-write
    STATUS  mandatory
    DESCRIPTION
        "The file name include path where the geoIP database is located."
    ::=  {rsIDS 147}

rsIDSSignaturesProfileParamsTable OBJECT-TYPE
    SYNTAX SEQUENCE OF RsIDSSignaturesProfileParamsEntry
    ACCESS not-accessible
    STATUS  mandatory
    DESCRIPTION
      "Table containing the list of profile params for the signatures"
    ::=  {rsIDSSignatures 12}

rsIDSSignaturesProfileParamsEntry OBJECT-TYPE
    SYNTAX RsIDSSignaturesProfileParamsEntry
    ACCESS not-accessible
    STATUS  mandatory
    DESCRIPTION
       "The row definition for this table."
    INDEX { rsIDSSignaturesProfileParamsName }
    ::=  { rsIDSSignaturesProfileParamsTable 1 }

RsIDSSignaturesProfileParamsEntry ::= SEQUENCE {
    rsIDSSignaturesProfileParamsName DisplayString,
    rsIDSSignaturesProfileParamsSimulationStatus INTEGER,
    rsIDSSignaturesProfileParamsSimulationDuration INTEGER,
    rsIDSSignaturesProfileParamsSimulationStopAtAttackEnd INTEGER,
    rsIDSSignaturesProfileParamsStatus RowStatus
}

rsIDSSignaturesProfileParamsName OBJECT-TYPE
    SYNTAX DisplayString (SIZE(1..29))
    ACCESS  read-write
    STATUS  mandatory
    DESCRIPTION
      "The Name for the Profile."
    ::=  {rsIDSSignaturesProfileParamsEntry 1}

rsIDSSignaturesProfileParamsSimulationStatus OBJECT-TYPE
    SYNTAX INTEGER {
			enable(1),
			disable(2)}
    ACCESS  read-write
    STATUS  mandatory
    DESCRIPTION
       "This variable indicates the signature simulation status"
	DEFVAL  {disable}
    ::=  { rsIDSSignaturesProfileParamsEntry 2}

rsIDSSignaturesProfileParamsSimulationDuration OBJECT-TYPE
    SYNTAX INTEGER (1..60)
    ACCESS read-write
    STATUS mandatory
    DESCRIPTION
      "The pre-defined duration of this simulation (minutes)"
	DEFVAL {10}
    ::=  { rsIDSSignaturesProfileParamsEntry 3}

rsIDSSignaturesProfileParamsSimulationStopAtAttackEnd OBJECT-TYPE
    SYNTAX INTEGER {
    false(0),
	true(1)
    }
    ACCESS read-write
	STATUS mandatory
    DESCRIPTION
      "A flag indicating if the simulation will stop at the end of the attack or continue the pre-define duration"
    ::=  { rsIDSSignaturesProfileParamsEntry 4}

rsIDSSignaturesProfileParamsStatus OBJECT-TYPE
    SYNTAX RowStatus
    ACCESS read-write
    STATUS mandatory
    DESCRIPTION
      "The row status of this entry"
    ::= {rsIDSSignaturesProfileParamsEntry 5}

rsDnsProt OBJECT IDENTIFIER ::= { rsIDS 148 }

rsDnsProtProfileTable OBJECT-TYPE
    SYNTAX SEQUENCE OF RsDnsProtProfileEntry
    ACCESS not-accessible
    STATUS  mandatory
    DESCRIPTION
      "Table containing the list of profiles params for the DNS protection inspection"
    ::=  {rsDnsProt 1}

rsDnsProtProfileEntry OBJECT-TYPE
    SYNTAX RsDnsProtProfileEntry
    ACCESS not-accessible
    STATUS  mandatory
    DESCRIPTION
       "The row definition for this table."
    INDEX { rsDnsProtProfileName }
    ::=  { rsDnsProtProfileTable 1 }

RsDnsProtProfileEntry ::= SEQUENCE {
    rsDnsProtProfileName DisplayString,
    rsDnsProtProfileDnsAStatus INTEGER,
	rsDnsProtProfileDnsMxStatus INTEGER,
    rsDnsProtProfileDnsPtrStatus INTEGER,
    rsDnsProtProfileDnsAaaaStatus INTEGER,
    rsDnsProtProfileDnsTextStatus INTEGER,
    rsDnsProtProfileDnsSoaStatus INTEGER,
    rsDnsProtProfileDnsNaptrStatus INTEGER,
    rsDnsProtProfileDnsSrvStatus INTEGER,
    rsDnsProtProfileDnsOtherStatus INTEGER,
    rsDnsProtProfileExpectedQps INTEGER,
    rsDnsProtProfileDnsAQuota INTEGER,
    rsDnsProtProfileDnsMxQuota INTEGER,
    rsDnsProtProfileDnsPtrQuota INTEGER,
    rsDnsProtProfileDnsAaaaQuota INTEGER,
    rsDnsProtProfileDnsTextQuota INTEGER,
    rsDnsProtProfileDnsSoaQuota INTEGER,
    rsDnsProtProfileDnsNaptrQuota INTEGER,
    rsDnsProtProfileDnsSrvQuota INTEGER,
    rsDnsProtProfileDnsOtherQuota INTEGER,
	rsDnsProtProfileAction INTEGER,
	rsDnsProtProfileMaxAllowQps INTEGER,
	rsDnsProtProfileSigRateLimTarget INTEGER,
	rsDnsProtProfileManualTriggerStatus INTEGER,
	rsDnsProtProfileManualTriggerActThresh INTEGER,
	rsDnsProtProfileManualTriggerTermThresh INTEGER,
	rsDnsProtProfileManualTriggerMaxQpsTarget INTEGER,
	rsDnsProtProfileManualTriggerActPeriod INTEGER,
	rsDnsProtProfileManualTriggerTermPeriod INTEGER,
	rsDnsProtProfileManualTriggerEscalatePeriod INTEGER,
	rsDnsProtProfilePacketReportStatus INTEGER,
	rsDnsProtProfilePacketTraceStatus INTEGER,
	rsDnsProtProfileQueryNameMonitoringSensitivity INTEGER,
	rsDnsProtProfileStatus RowStatus,
	rsDnsProtProfileSubdomainsWLLearningState INTEGER
	}

rsDnsProtProfileName OBJECT-TYPE
    SYNTAX DisplayString (SIZE(0..19))
    ACCESS  read-only
    STATUS  mandatory
    DESCRIPTION
      "The Name for the DNS protection Profile."
    ::=  {rsDnsProtProfileEntry 1}


rsDnsProtProfileDnsAStatus OBJECT-TYPE
    SYNTAX INTEGER {
              active(1),
              inactive(2)}
    ACCESS  read-write
    STATUS  mandatory
    DESCRIPTION
       "This variable indicates whether to check DNS A protocol in this policy."
    DEFVAL { 2 }
    ::=  { rsDnsProtProfileEntry 2 }

rsDnsProtProfileDnsMxStatus OBJECT-TYPE
    SYNTAX INTEGER {
              active(1),
              inactive(2)}
    ACCESS  read-write
    STATUS  mandatory
    DESCRIPTION
       "This variable indicates whether to check DNS MX protocol in this policy."
    DEFVAL { 2 }
    ::=  { rsDnsProtProfileEntry 3 }

rsDnsProtProfileDnsPtrStatus OBJECT-TYPE
    SYNTAX INTEGER {
              active(1),
              inactive(2) }
    ACCESS  read-write
    STATUS  mandatory
    DESCRIPTION
       "This variable indicates whether to check DNS PTR protocol in this policy."
    DEFVAL { 2 }
    ::=  { rsDnsProtProfileEntry 4 }

rsDnsProtProfileDnsAaaaStatus OBJECT-TYPE
    SYNTAX INTEGER {
              active(1),
              inactive(2) }
    ACCESS  read-write
    STATUS  mandatory
    DESCRIPTION
       "This variable indicates whether to check DNS AAAA protocol in this policy."
    DEFVAL { 2 }
    ::=  { rsDnsProtProfileEntry 5 }

rsDnsProtProfileDnsTextStatus OBJECT-TYPE
    SYNTAX INTEGER {
              active(1),
              inactive(2) }
    ACCESS  read-write
    STATUS  mandatory
    DESCRIPTION
       "This variable indicates whether to check DNS TEXT protocol in this policy."
    DEFVAL { 2 }
    ::=  { rsDnsProtProfileEntry 6 }

rsDnsProtProfileDnsSoaStatus OBJECT-TYPE
    SYNTAX INTEGER {
              active(1),
              inactive(2)}
    ACCESS  read-write
    STATUS  mandatory
    DESCRIPTION
       "This variable indicates whether to check DNS SOA in this policy."
    DEFVAL { 2 }
    ::=  { rsDnsProtProfileEntry 7 }

rsDnsProtProfileDnsNaptrStatus OBJECT-TYPE
    SYNTAX INTEGER {
              active(1),
              inactive(2)}
    ACCESS  read-write
    STATUS  mandatory
    DESCRIPTION
       "This variable indicates whether to check DNS NAPTR in this policy."
    DEFVAL { 2 }
    ::=  { rsDnsProtProfileEntry 8 }

rsDnsProtProfileDnsSrvStatus OBJECT-TYPE
    SYNTAX INTEGER {
              active(1),
              inactive(2)}
    ACCESS  read-write
    STATUS  mandatory
    DESCRIPTION
       "This variable indicates whether to check DNS SRV in this policy."
    DEFVAL { 2 }
    ::=  { rsDnsProtProfileEntry 9 }

rsDnsProtProfileDnsOtherStatus OBJECT-TYPE
    SYNTAX INTEGER {
              active(1),
              inactive(2)}
    ACCESS  read-write
    STATUS  mandatory
    DESCRIPTION
       "This variable indicates whether to check Other DNS protocols in this policy."
    DEFVAL { 2 }
    ::=  { rsDnsProtProfileEntry 10 }

rsDnsProtProfileExpectedQps OBJECT-TYPE
    SYNTAX INTEGER (1..4000000)
    ACCESS  read-write
    STATUS  mandatory
    DESCRIPTION
       "Expected number of queries per second for this policy."
    ::=  { rsDnsProtProfileEntry 11 }

rsDnsProtProfileDnsAQuota OBJECT-TYPE
    SYNTAX INTEGER (0..100)
    ACCESS  read-write
    STATUS  mandatory
    DESCRIPTION
       "DNS A quota inbound value for this policy."
    ::=  { rsDnsProtProfileEntry 12 }

rsDnsProtProfileDnsMxQuota OBJECT-TYPE
    SYNTAX INTEGER (0..100)
    ACCESS  read-write
    STATUS  mandatory
    DESCRIPTION
       "DNS MX quota inbound value for this policy."
    ::=  { rsDnsProtProfileEntry 13 }

rsDnsProtProfileDnsPtrQuota OBJECT-TYPE
    SYNTAX INTEGER (0..100)
    ACCESS  read-write
    STATUS  mandatory
    DESCRIPTION
       "DNS PTR quota inbound value for this policy."
    ::=  { rsDnsProtProfileEntry 14 }

rsDnsProtProfileDnsAaaaQuota OBJECT-TYPE
    SYNTAX INTEGER (0..100)
    ACCESS  read-write
    STATUS  mandatory
    DESCRIPTION
       "DNS AAAA quota inbound value for this policy."
    ::=  { rsDnsProtProfileEntry 15 }

rsDnsProtProfileDnsTextQuota OBJECT-TYPE
    SYNTAX INTEGER (0..100)
    ACCESS  read-write
    STATUS  mandatory
    DESCRIPTION
       "DNS TEXT quota outbound value for this policy."
    ::=  { rsDnsProtProfileEntry 16 }

rsDnsProtProfileDnsSoaQuota OBJECT-TYPE
    SYNTAX INTEGER (0..100)
    ACCESS  read-write
    STATUS  mandatory
    DESCRIPTION
       "DNS SOA quota outbound value for this policy."
    ::=  { rsDnsProtProfileEntry 17 }

rsDnsProtProfileDnsNaptrQuota OBJECT-TYPE
    SYNTAX INTEGER (0..100)
    ACCESS  read-write
    STATUS  mandatory
    DESCRIPTION
       "DNS NAPTR quota outbound value for this policy."
    ::=  { rsDnsProtProfileEntry 18 }

rsDnsProtProfileDnsSrvQuota OBJECT-TYPE
    SYNTAX INTEGER (0..100)
    ACCESS  read-write
    STATUS  mandatory
    DESCRIPTION
       "DNS SRV quota outbound value for this policy."
    ::=  { rsDnsProtProfileEntry 19 }

rsDnsProtProfileDnsOtherQuota OBJECT-TYPE
    SYNTAX INTEGER (0..100)
    ACCESS  read-write
    STATUS  mandatory
    DESCRIPTION
       "DNS Other quota outbound value for this policy."
    ::=  { rsDnsProtProfileEntry 20 }

rsDnsProtProfileAction OBJECT-TYPE
    SYNTAX INTEGER {
        report(0),
        block(1) }
    ACCESS  read-write
    STATUS  mandatory
    DESCRIPTION
       "This variable indicates the profile action"
    ::=  { rsDnsProtProfileEntry 21 }

rsDnsProtProfileMaxAllowQps OBJECT-TYPE
    SYNTAX INTEGER (1..4000000)
    ACCESS  read-write
    STATUS  mandatory
    DESCRIPTION
       "The maximum number of queries per sec per dns type that this profile will forward in collective mode mitigation"
    ::=  { rsDnsProtProfileEntry 22 }

rsDnsProtProfileSigRateLimTarget OBJECT-TYPE
    SYNTAX INTEGER (0..100)
    ACCESS  read-write
    STATUS  mandatory
    DESCRIPTION
       "The Signature rate limit mitigation target, as a percentage of the learned traffic."
	DEFVAL  {0}
    ::=  { rsDnsProtProfileEntry 23 }

rsDnsProtProfileManualTriggerStatus OBJECT-TYPE
	SYNTAX INTEGER {
			enable(1),
			disable(2)}
    ACCESS  read-write
    STATUS  mandatory
    DESCRIPTION
       "Whether to activate manual triggers mode for this profile."
	DEFVAL  {disable}
    ::=  { rsDnsProtProfileEntry 24 }

rsDnsProtProfileManualTriggerActThresh OBJECT-TYPE
    SYNTAX INTEGER (0..4000000)
    ACCESS  read-write
    STATUS  mandatory
    DESCRIPTION
       "Number of QPS for starting the manual triggers mitigation."
	DEFVAL  {0}
    ::=  { rsDnsProtProfileEntry 25 }

rsDnsProtProfileManualTriggerTermThresh OBJECT-TYPE
    SYNTAX INTEGER (0..4000000)
    ACCESS  read-write
    STATUS  mandatory
    DESCRIPTION
       "Number of QPS for terminating the manual triggers mitigation."
	DEFVAL  {0}
    ::=  { rsDnsProtProfileEntry 26 }

rsDnsProtProfileManualTriggerMaxQpsTarget OBJECT-TYPE
    SYNTAX INTEGER (0..4000000)
    ACCESS  read-write
    STATUS  mandatory
    DESCRIPTION
       "The number of QPS that will be forwarded in manual triggers mode"
	DEFVAL  {0}
    ::=  { rsDnsProtProfileEntry 27 }

rsDnsProtProfileManualTriggerActPeriod OBJECT-TYPE
    SYNTAX INTEGER (1..30)
    ACCESS  read-write
    STATUS  mandatory
    DESCRIPTION
       "Number of seconds above the manual triggers activation threshold before starting the mitigation"
	DEFVAL  {3}
    ::=  { rsDnsProtProfileEntry 28 }

rsDnsProtProfileManualTriggerTermPeriod OBJECT-TYPE
    SYNTAX INTEGER (1..30)
    ACCESS  read-write
    STATUS  mandatory
    DESCRIPTION
       "Number of seconds below the manual triggers termination threshold before stopping the mitigation"
	DEFVAL  {3}
    ::=  { rsDnsProtProfileEntry 29 }

rsDnsProtProfileManualTriggerEscalatePeriod OBJECT-TYPE
    SYNTAX INTEGER (0..30)
    ACCESS  read-write
    STATUS  mandatory
    DESCRIPTION
       "Number of seconds with bad feedback before changing the mitigation type in manual triggers mode"
	DEFVAL  {3}
    ::=  { rsDnsProtProfileEntry 30 }

rsDnsProtProfilePacketReportStatus OBJECT-TYPE
 SYNTAX INTEGER {
      enable(1),
      disable(2)
   }
    ACCESS read-write
    STATUS mandatory
    DESCRIPTION
      "packet report status"
   DEFVAL  {enable}
    ::= {rsDnsProtProfileEntry 31}

rsDnsProtProfilePacketTraceStatus OBJECT-TYPE
 SYNTAX INTEGER {
      enable(1),
      disable(2)
   }
    ACCESS read-write
    STATUS mandatory
    DESCRIPTION
      "packet trace status"
   DEFVAL  {disable}
    ::= {rsDnsProtProfileEntry 32}

rsDnsProtProfileQueryNameMonitoringSensitivity OBJECT-TYPE
 SYNTAX INTEGER {
      none(1),
      low(2),
      medium(3),
      high(4)
   }
    ACCESS read-only
    STATUS deprecated
    DESCRIPTION
      "This variable indicates the query name monitoring sensitivity"
   DEFVAL  {none}
    ::= {rsDnsProtProfileEntry 33}

rsDnsProtProfileStatus OBJECT-TYPE
    SYNTAX RowStatus
    ACCESS  read-write
    STATUS  mandatory
    DESCRIPTION
       "This variable indicates the administrative status of this entry.
        Used to delete an entry of this table."
    ::=  { rsDnsProtProfileEntry 34 }

rsDnsProtProfileSubdomainsWLLearningState OBJECT-TYPE
 SYNTAX INTEGER {
      enable(1),
      disable(2)
   }
    ACCESS read-only
    STATUS deprecated
    DESCRIPTION
      "This variable indicates the dns subdomains white list learning state."
   DEFVAL  {enable}
    ::= {rsDnsProtProfileEntry 35}

rsDnsProtResetServerLearning OBJECT-TYPE
   SYNTAX DisplayString(SIZE(0..64))
   ACCESS  read-write
   STATUS  mandatory
   DESCRIPTION
       "reset learning baseline for specific server"
    ::=  { rsDnsProt 2}

rsDnsProtMechStatus OBJECT-TYPE
 SYNTAX INTEGER {
      enable(1),
      disable(2)
   }
    ACCESS read-write
    STATUS mandatory
    DESCRIPTION
      "The DNS Protection module activation"
   DEFVAL  {disable}
    ::= {rsDnsProt 3}

rsDnsProtLearningPeriod OBJECT-TYPE
 SYNTAX INTEGER {
    day(1),
    week(2),
    month(3)}
   ACCESS  read-write
   STATUS  mandatory
   DESCRIPTION
       "DNS protection learning response time "
    ::=  { rsDnsProt 4}

rsDnsProtResetAllLearning OBJECT-TYPE
 SYNTAX INTEGER
   ACCESS  read-write
   STATUS  mandatory
   DESCRIPTION
       "reset learning baseline"
    ::=  { rsDnsProt 5}

rsDnsProtFootprintStrictness OBJECT-TYPE
 SYNTAX INTEGER {
   low(0),
   medium(1),
   high(2)
   }
   ACCESS  read-write
   STATUS  mandatory
   DESCRIPTION
       "configures how accurate must the footprint be in order to be activated"
    ::=  { rsDnsProt 6}

rsDnsProtDynamicTermSC2 OBJECT-TYPE
 SYNTAX INTEGER (1..30)
   ACCESS  read-write
   STATUS  mandatory
   DESCRIPTION
       "stability counter for state 2"
    ::=  { rsDnsProt 8}

rsDnsProtDynamicTermSC6 OBJECT-TYPE
 SYNTAX INTEGER (45..300)
   ACCESS  read-write
   STATUS  mandatory
   DESCRIPTION
       "stability counter for state 6"
    ::=  { rsDnsProt 9}

rsDnsProtDynamicTermSC37 OBJECT-TYPE
 SYNTAX INTEGER (45..300)
   ACCESS  read-write
   STATUS  mandatory
   DESCRIPTION
       "stability counter for state 3"
    ::=  { rsDnsProt 10}

rsDnsProtBypassTable OBJECT-TYPE
    SYNTAX SEQUENCE OF RsDnsProtBypassEntry
    ACCESS not-accessible
    STATUS  mandatory
    DESCRIPTION
      "Table containing the list of profiles params for the DNS Protection inspection"
    ::=  {rsDnsProt 11}

rsDnsProtBypassEntry OBJECT-TYPE
    SYNTAX RsDnsProtBypassEntry
    ACCESS not-accessible
    STATUS  mandatory
    DESCRIPTION
       "The row definition for this table."
    INDEX { rsDnsProtBypassController, rsDnsProtBypassType }
    ::=  { rsDnsProtBypassTable 1 }

RsDnsProtBypassEntry ::= SEQUENCE {
rsDnsProtBypassController INTEGER,
    rsDnsProtBypassType INTEGER,
	rsDnsProtBypassStatus INTEGER,
    rsDnsProtBypassValues DisplayString,
    rsDnsProtBypassRowStatus RowStatus
}

rsDnsProtBypassController OBJECT-TYPE
    SYNTAX INTEGER {
   dns-a(20),
   dns-mx(22),
   dns-ptr(24),
   dns-aaaa(26),
   dns-text(28),
   dns-soa(30),
   dns-naptr(32),
   dns-srv(34),
   dns-other(36)
    }
    ACCESS  read-write
    STATUS  mandatory
    DESCRIPTION
       "The bypass controller type"
    ::=  { rsDnsProtBypassEntry 1}


rsDnsProtBypassType OBJECT-TYPE
    SYNTAX INTEGER {
    checksum(0),
--	sequence-num(1),
    id-num(2),
    dns-id-num(3),
    dns-qname(4),
    dns-subdomain(5),
	dns-qcount(6),
	source-port(7),
    source-ip(8),
--	frag-offset(9),
	flow-label(10),
	tos(11),
	packet-size(12),
--	destination-port(13),
    destination-ip(14),
    fragment(15),
--  (16),
--  (17),
--  (18),
--  icmp-igmp-message-type(19),
    ttl(20),
	id-num-ipv6(21),
	frag-offset-ipv6(22),
--   (23),
	packet-size-ipv6(24),
	source-ip-ipv6(25),
	destination-ip-ipv6(26),
--	icmp-message-type-ipv6(27) ,
	context-tag(28),
--   (29),
	dns-ancount(30),
	dns-flags(31)
    }
    ACCESS  read-write
    STATUS  mandatory
    DESCRIPTION
       "The bypass type"
    ::=  { rsDnsProtBypassEntry 2}

rsDnsProtBypassStatus OBJECT-TYPE
    SYNTAX INTEGER {
    accept(0),
	bypass(1)
    }
    ACCESS  read-write
    STATUS  mandatory
    DESCRIPTION
       "The bypass type"
    ::=  {rsDnsProtBypassEntry 3}

rsDnsProtBypassValues OBJECT-TYPE
    SYNTAX DisplayString
    ACCESS  read-write
    STATUS  mandatory
    DESCRIPTION
      "The values of the bypass."
    ::=  {rsDnsProtBypassEntry 4}

rsDnsProtBypassRowStatus OBJECT-TYPE
    SYNTAX RowStatus
    ACCESS  read-write
    STATUS  mandatory
    DESCRIPTION
       "This variable indicates the administrative status of this entry.
        Used to delete an entry of this table."
    ::=  { rsDnsProtBypassEntry 5 }

rsDnsProtDynamicStateFpTable OBJECT-TYPE
    SYNTAX SEQUENCE OF RsDnsProtDynamicStateFpEntry
    ACCESS not-accessible
    STATUS  mandatory
    DESCRIPTION
      "Table containing the list of profiles params for the NetFlood inspection"
    ::=  {rsDnsProt 12}

rsDnsProtDynamicStateFpEntry OBJECT-TYPE
    SYNTAX RsDnsProtDynamicStateFpEntry
    ACCESS not-accessible
    STATUS  mandatory
    DESCRIPTION
       "The row definition for this table."
    INDEX { rsDnsProtDynamicController, rsDnsProtDynamicFpType }
    ::=  { rsDnsProtDynamicStateFpTable 1 }

RsDnsProtDynamicStateFpEntry ::= SEQUENCE {
	rsDnsProtDynamicController INTEGER,
    rsDnsProtDynamicFpType INTEGER,
	rsDnsProtDynamicState INTEGER,
    rsDnsProtDynamicRowStatus RowStatus
}

rsDnsProtDynamicController OBJECT-TYPE
    SYNTAX INTEGER {
   dns-a(20),
   dns-mx(22),
   dns-ptr(24),
   dns-aaaa(26),
   dns-text(28),
   dns-soa(30),
   dns-naptr(32),
   dns-srv(34),
   dns-other(36)
    }
    ACCESS  read-write
    STATUS  mandatory
    DESCRIPTION
       "The controller type"
    ::=  { rsDnsProtDynamicStateFpEntry 1}


rsDnsProtDynamicFpType OBJECT-TYPE
    SYNTAX INTEGER {
    checksum(0),
--	sequence-num(1),
    id-num(2),
    dns-id-num(3),
    dns-qname(4),
     dns-subdomain(5),
	dns-qcount(6),
	source-port(7),
    source-ip(8),
	frag-offset(9),
	flow-label(10),
	tos(11),
	packet-size(12),
--	destination-port(13),
    destination-ip(14),
    fragment(15),
--  (16),
--  (17),
--  (18),
--  icmp-igmp-message-type(19),
    ttl(20),
	id-num-ipv6(21),
	frag-offset-ipv6(22),
--   (23),
	packet-size-ipv6(24),
	source-ip-ipv6(25),
	destination-ip-ipv6(26),
--	icmp-message-type-ipv6(27) ,
	context-tag(28),
--   (29),
	dns-ancount(30),
	dns-flags(31)
    }
    ACCESS  read-write
    STATUS  mandatory
    DESCRIPTION
       "The dynamic footprint type"
    ::=  { rsDnsProtDynamicStateFpEntry 2}

rsDnsProtDynamicState OBJECT-TYPE
    SYNTAX INTEGER {
    no(0),
	yes(1)
    }
    ACCESS  read-write
    STATUS  mandatory
    DESCRIPTION
       "The dynamic state"
    ::=  { rsDnsProtDynamicStateFpEntry 3 }

rsDnsProtDynamicRowStatus OBJECT-TYPE
    SYNTAX RowStatus
    ACCESS  read-write
    STATUS  mandatory
    DESCRIPTION
       "This variable indicates the administrative status of this entry.
        Used to delete an entry of this table."
    ::=  { rsDnsProtDynamicStateFpEntry 4 }


rsDnsProtDynamicStateTwoTable OBJECT-TYPE
    SYNTAX SEQUENCE OF RsDnsProtDynamicStateTwoEntry
    ACCESS not-accessible
    STATUS  mandatory
    DESCRIPTION
      "Table containing the dynamic state 2 any flag"
    ::=  {rsDnsProt 13}


rsDnsProtDynamicStateTwoEntry OBJECT-TYPE
    SYNTAX RsDnsProtDynamicStateTwoEntry
    ACCESS not-accessible
    STATUS  mandatory
    DESCRIPTION
       "The row definition for this table."
    INDEX { rsDnsProtDynamicStateController }
    ::=  { rsDnsProtDynamicStateTwoTable 1 }

RsDnsProtDynamicStateTwoEntry ::= SEQUENCE {
	rsDnsProtDynamicStateController INTEGER,
	rsDnsProtDynamicStateAnyTypeFlag INTEGER,
	rsDnsProtDynamicStateTypeThreshold INTEGER,
	rsDnsProtDynamicStateValThreshold INTEGER,
    rsDnsProtDynamicStateRowStatus RowStatus
}

rsDnsProtDynamicStateController OBJECT-TYPE
    SYNTAX INTEGER {
   dns-a(20),
   dns-mx(22),
   dns-ptr(24),
   dns-aaaa(26),
   dns-text(28),
   dns-soa(30),
   dns-naptr(32),
   dns-srv(34),
   dns-other(36)
    }
    ACCESS  read-write
    STATUS  mandatory
    DESCRIPTION
       "The controller type"
    ::=  { rsDnsProtDynamicStateTwoEntry 1}


rsDnsProtDynamicStateAnyTypeFlag OBJECT-TYPE
    SYNTAX INTEGER {
    false(0),
	true(1)
    }
    ACCESS  read-write
    STATUS  mandatory
    DESCRIPTION
       "The any type flag"
    ::=  { rsDnsProtDynamicStateTwoEntry 2 }

rsDnsProtDynamicStateTypeThreshold OBJECT-TYPE
    SYNTAX INTEGER
    ACCESS  read-write
    STATUS  mandatory
    DESCRIPTION
       "The type threshold (Th1)"
    ::=  { rsDnsProtDynamicStateTwoEntry 3 }

rsDnsProtDynamicStateValThreshold OBJECT-TYPE
    SYNTAX INTEGER  (1..1000)
    ACCESS  read-write
    STATUS  mandatory
    DESCRIPTION
       "The type threshold (Th2)"
    ::=  { rsDnsProtDynamicStateTwoEntry 4 }

rsDnsProtDynamicStateRowStatus OBJECT-TYPE
    SYNTAX RowStatus
    ACCESS  read-write
    STATUS  mandatory
    DESCRIPTION
       "This variable indicates the administrative status of this entry.
        Used to delete an entry of this table."
    ::=  { rsDnsProtDynamicStateTwoEntry 5 }

rsDnsProtPolicies OBJECT-TYPE
   SYNTAX INTEGER
   ACCESS read-only
   STATUS mandatory
   DESCRIPTION
       "Tuning parameter for the number of DNS protection policies"
    ::=  { rsDnsProt 14}

rsDnsProtPoliciesAfterReset OBJECT-TYPE
   SYNTAX INTEGER
   ACCESS  read-write
   STATUS  mandatory
   DESCRIPTION
       "Tuning parameter for the number of DNS protection after the next reset"
    ::=  { rsDnsProt 15}

rsDnsSDMWhiteListStatus OBJECT-TYPE
   SYNTAX INTEGER {
			enable(1),
			disable(2)}
   ACCESS  read-write
   STATUS  mandatory
   DESCRIPTION
       "DNS SDM authentication list activation status"
    ::=  { rsDnsProt 16}

rsDnsPacketAnomaliesStatus OBJECT-TYPE
   SYNTAX INTEGER {
			enable(1),
			disable(2)}
   ACCESS  read-write
   STATUS  mandatory
   DESCRIPTION
       "DNS Packet anomalies check under attack"
    ::=  { rsDnsProt 17}

rsDnsSDMWhiteListTimeout OBJECT-TYPE
   SYNTAX INTEGER (1..60)
   ACCESS  read-write
   STATUS  mandatory
   DESCRIPTION
       "Timeout for the DNS SDM authentication list (in minutes)"
	DEFVAL  { 20 }
    ::=  { rsDnsProt 18}

rsDnsSDMRetransmitMinTime OBJECT-TYPE
   SYNTAX INTEGER (0..40)
   ACCESS  read-write
   STATUS  mandatory
   DESCRIPTION
       "Minimum time for a legal DNS retransmission (in half seconds)"
	DEFVAL  { 1 }
    ::=  { rsDnsProt 19}

rsDnsSDMRetransmitMaxTime OBJECT-TYPE
   SYNTAX INTEGER (2..120)
   ACCESS  read-write
   STATUS  mandatory
   DESCRIPTION
       "Maximum time for a legal DNS retransmission (in half seconds)"
	DEFVAL  { 16 }
    ::=  { rsDnsProt 20}

rsDnsSDMRetransmitMaxAttackTime OBJECT-TYPE
   SYNTAX INTEGER (2..240)
   ACCESS  read-write
   STATUS  mandatory
   DESCRIPTION
       "Timeout for the DNS retransmission attack (in half seconds)"
	DEFVAL  { 32 }
    ::=  { rsDnsProt 21}

rsDnsSDMTableSize OBJECT-TYPE
   SYNTAX INTEGER {
		small(1),
		medium(2),
		large(3)}
   ACCESS  read-only
   STATUS  mandatory
   DESCRIPTION
       "The current size of the SDM table"
    ::=  { rsDnsProt 22}

rsDnsSDMTableSizeAfterReset OBJECT-TYPE
	SYNTAX INTEGER {
		small(1),
		medium(2),
		large(3)}
   ACCESS  read-write
   STATUS  mandatory
   DESCRIPTION
       "The size of the SDM table after reset"
    ::=  { rsDnsProt 23}

rsDnsMitigationTimeout OBJECT-TYPE
	SYNTAX INTEGER (1..60)
   ACCESS  read-write
   STATUS  mandatory
   DESCRIPTION
       "Timeout (in minutes) before going back from state 6 to state 2 and starting trying to build a new signature"
	DEFVAL  { 10 }
    ::=  { rsDnsProt 24}

rsDnsFootprintRetries OBJECT-TYPE
	SYNTAX INTEGER (1..10)
   ACCESS  read-write
   STATUS  mandatory
   DESCRIPTION
       "Maximum number of times that we will try to find a dynamic footprint, before going to collective mitigation mode."
	DEFVAL  { 3 }
    ::=  { rsDnsProt 25}

rsDnsSignatureChallengeStatus OBJECT-TYPE
 SYNTAX INTEGER {
			enable(1),
			disable(2)}
   ACCESS  read-write
   STATUS  mandatory
   DESCRIPTION
       "Whether the DNS protection Signature-Challenge is enabled."
	DEFVAL  { disable }
    ::=  { rsDnsProt 26}

rsDnsSignatureRateLimitStatus OBJECT-TYPE
 SYNTAX INTEGER {
			enable(1),
			disable(2)}
   ACCESS  read-write
   STATUS  mandatory
   DESCRIPTION
       "Whether the DNS protection Signature-Rate-limit is enabled."
	DEFVAL  { enable }
    ::=  { rsDnsProt 27}

rsDnsCollectiveChallengeStatus OBJECT-TYPE
 SYNTAX INTEGER {
			enable(1),
			disable(2)}
   ACCESS  read-write
   STATUS  mandatory
   DESCRIPTION
       "Whether the DNS protection Collective-Challenge is enabled."
	DEFVAL  { disable }
    ::=  { rsDnsProt 28}

rsDnsCollectiveRateLimitStatus OBJECT-TYPE
 SYNTAX INTEGER {
			enable(1)
--			disable(2)}
}
   ACCESS  read-only
   STATUS  mandatory
   DESCRIPTION
       "Whether the DNS protection Collective-Rate-limit is enabled."
	DEFVAL  { enable }
    ::=  { rsDnsProt 29}

rsDnsProtMitigationStabilityCounter OBJECT-TYPE
	SYNTAX INTEGER (1..30)
   ACCESS  read-write
   STATUS  mandatory
   DESCRIPTION
       "Number of seconds with negative feedback, before trying another mitigation method (not for manual triggers)."
	DEFVAL  { 3 }
    ::=  { rsDnsProt 30}

rsDnsProtSamplingStatus OBJECT-TYPE
 SYNTAX INTEGER {
		enable(1),
		disable(2)
		}
   ACCESS  read-write
   STATUS  mandatory
   DESCRIPTION
       "configures whether the DNS protection sampling is enabled or disabled"
    ::=  { rsDnsProt 31}

rsDnsSDMProtQidTreatment OBJECT-TYPE
 SYNTAX INTEGER {
		strict(0),
		loose(1),
		ignore(2)
		}
   ACCESS  read-write
   STATUS  mandatory
   DESCRIPTION
       "configures how DNS protection treats query ID during SDM authentication process"
   DEFVAL  { strict }
    ::=  { rsDnsProt 32}

rsDnsSDMProtForwardRetransmissions OBJECT-TYPE
    SYNTAX INTEGER {
			enable(1),
			disable(2)}
   ACCESS  read-write
   STATUS  mandatory
   DESCRIPTION
       "configures how DNS protection treats retransmittions - forward all, or only first legal one."
   DEFVAL  { disable }
    ::=  { rsDnsProt 33}

rsDnsProtGlobalAdvancedLearningSuppThreshold OBJECT-TYPE
   SYNTAX INTEGER (0..100)
   ACCESS  read-write
   STATUS  mandatory
   DESCRIPTION
       "reset learning for dns suppression"
    ::=  { rsDnsProt 34}

rsDnsProtComplianceCheckStatus OBJECT-TYPE
   SYNTAX INTEGER {
			enable(1),
			disable(2)}
   ACCESS  read-write
   STATUS  mandatory
   DESCRIPTION
       "dns compliance check status"
    ::=  { rsDnsProt 35}

rsDnsNewSdmTableSize OBJECT-TYPE
   SYNTAX INTEGER {
			size1(1),
			size2(2),
			size3(3),
			size4(4),
			size5(5)}
   ACCESS  read-write
   STATUS  mandatory
   DESCRIPTION
       "The size of the SDM table"
    ::=  { rsDnsProt 36}

rsDnsProtComplianceAllowLargeEdnsPackets OBJECT-TYPE
   SYNTAX INTEGER {
			enable(1),
			disable(2)}
   ACCESS  read-write
   STATUS  mandatory
   DESCRIPTION
       "Specifies whether DNS-protocol-compliance checks allow large EDNS packets"
    ::=  { rsDnsProt 37}

rsTcpAuthenListAging OBJECT-TYPE
    SYNTAX INTEGER (60..3600)
    ACCESS  read-write
    STATUS  mandatory
    DESCRIPTION
        "The aging time of the tcp challenge response authentication table."
    DEFVAL { 1200 }
    ::=  {rsIDS 149}

rsHttpAuthenListAging OBJECT-TYPE
    SYNTAX INTEGER (60..3600)
    ACCESS  read-write
    STATUS  mandatory
    DESCRIPTION
        "The aging time of the http challenge response authentication table."
    DEFVAL { 1200 }
    ::=  {rsIDS 150}

rsTcpAuthenListUtilization OBJECT-TYPE
    SYNTAX INTEGER (0..100)
    ACCESS  read-only
    STATUS  mandatory
    DESCRIPTION
        "The current utilization (%) of the tcp challenge response authentication table."
    ::=  {rsIDS 151}

rsHttpAuthenListUtilization OBJECT-TYPE
    SYNTAX INTEGER (0..100)
    ACCESS  read-only
    STATUS  mandatory
    DESCRIPTION
        "The current utilization (%) of the http challenge response authentication table."
    ::=  {rsIDS 152}

rsDnsAuthenListUtilization OBJECT-TYPE
    SYNTAX INTEGER (0..100)
    ACCESS  read-only
    STATUS  mandatory
    DESCRIPTION
        "The current utilization (%) of the dns challenge response authentication table."
    ::=  {rsIDS 153}

rsTcpAuthenListSize OBJECT-TYPE
    SYNTAX INTEGER
    ACCESS  read-only
    STATUS  mandatory
    DESCRIPTION
        "The allocated size of the tcp challenge response authentication table."
    ::=  {rsIDS 154}

rsHttpAuthenListSize OBJECT-TYPE
    SYNTAX INTEGER
    ACCESS  read-only
    STATUS  mandatory
    DESCRIPTION
        "The allocated size of the http challenge response authentication table."
    ::=  {rsIDS 155}

rsDnsAuthenListSize OBJECT-TYPE
    SYNTAX INTEGER
    ACCESS  read-only
    STATUS  mandatory
    DESCRIPTION
        "The allocated size of the dns challenge response authentication table."
    ::=  {rsIDS 156}

rsTcpAuthenListClean OBJECT-TYPE
    SYNTAX INTEGER {
		clean(1),
		do-nothing(2)
		}
    ACCESS  read-write
    STATUS  mandatory
    DESCRIPTION
        "Clean tcp challenge response authentication table."
    ::=  {rsIDS 157}

rsHttpAuthenListClean OBJECT-TYPE
    SYNTAX INTEGER {
		clean(1),
		do-nothing(2)
		}
    ACCESS  read-write
    STATUS  mandatory
    DESCRIPTION
        "Clean http challenge response authentication table."
    ::=  {rsIDS 158}

rsDnsAuthenListClean OBJECT-TYPE
    SYNTAX INTEGER {
		clean(1),
		do-nothing(2)
		}
    ACCESS  read-write
    STATUS  mandatory
    DESCRIPTION
        "Clean dns challenge response authentication table."
    ::=  {rsIDS 159}

rsHttpAuthenListSizeAfterReset OBJECT-TYPE
	SYNTAX INTEGER
   ACCESS  read-write
   STATUS  mandatory
   DESCRIPTION
       "The size of the HTTP authenticated table after reset"
    ::=  {rsIDS 160}

rsTcpAuthenListSizeAfterReset OBJECT-TYPE
	SYNTAX INTEGER
   ACCESS  read-write
   STATUS  mandatory
   DESCRIPTION
       "The size of the TCP authenticated table after reset"
    ::=  {rsIDS 162}

rsIDSMemoryReservedTuning OBJECT IDENTIFIER ::= { rsIDS 163}

rsIDSDynamicMemoryAfterReset OBJECT-TYPE
    SYNTAX INTEGER
    ACCESS  not-accessible
    STATUS  mandatory
    DESCRIPTION
      "Memory reserved for dynamic allocations."

    ::=  { rsIDSMemoryReservedTuning 1 }

rsIDSDynamicMemory OBJECT-TYPE
    SYNTAX INTEGER (20000000)
    ACCESS  not-accessible
    STATUS  mandatory
    DESCRIPTION "Memory reserved for dynamic allocations."
    ::= { rsIDSMemoryReservedTuning 2 }

rsIDSSynProfilesParamsTable OBJECT-TYPE
    SYNTAX SEQUENCE OF RsIDSSynProfilesParamsEntry
    ACCESS not-accessible
    STATUS  mandatory
    DESCRIPTION
      "Table containing the list of profile params for the syn profile"
    ::=  {rsIDSSynProtection 19}

rsIDSSynProfilesParamsEntry OBJECT-TYPE
    SYNTAX RsIDSSynProfilesParamsEntry
    ACCESS not-accessible
    STATUS  mandatory
    DESCRIPTION
       "The row definition for this table."
    INDEX { rsIDSSynProfilesParamsName }
    ::=  { rsIDSSynProfilesParamsTable 1 }

RsIDSSynProfilesParamsEntry ::= SEQUENCE {
    rsIDSSynProfilesParamsName DisplayString,
    rsIDSSynProfilesParamsAuthType INTEGER,
    rsIDSSynProfilesParamsWebEnable INTEGER,
    rsIDSSynProfilesParamsWebMethod INTEGER,
    rsIDSSynProfileTCPResetStatus  INTEGER,
    rsIDSSynProfilesParamsStatus RowStatus,
    rsIDSSynProfilesSSLMitigationStatus INTEGER
}

rsIDSSynProfilesParamsName OBJECT-TYPE
    SYNTAX DisplayString (SIZE(1..29))
    ACCESS  read-write
    STATUS  mandatory
    DESCRIPTION
      "The Name for the Profile."
    ::=  {rsIDSSynProfilesParamsEntry 1}

rsIDSSynProfilesParamsAuthType OBJECT-TYPE
    SYNTAX INTEGER {
			safe-reset(1)}
    ACCESS  read-write
    STATUS  mandatory
    DESCRIPTION
       "This variable indicates the authentication method"
	DEFVAL  {safe-reset}
    ::=  { rsIDSSynProfilesParamsEntry 2}

rsIDSSynProfilesParamsWebEnable OBJECT-TYPE
    SYNTAX INTEGER {
			enable(1),
			disable(2)}
    ACCESS read-write
    STATUS mandatory
    DESCRIPTION
      "This variable indicates the HTTP authentication status"
	DEFVAL {disable}
    ::=  { rsIDSSynProfilesParamsEntry 3}

rsIDSSynProfilesParamsWebMethod OBJECT-TYPE
    SYNTAX INTEGER {
    redirect(1),
    javaScript(2)
    }
    ACCESS read-write
	STATUS mandatory
    DESCRIPTION
      "This variable indicates the HTTP authentication method"
    DEFVAL {redirect}
    ::=  { rsIDSSynProfilesParamsEntry 4}


rsIDSSynProfileTCPResetStatus OBJECT-TYPE
    SYNTAX INTEGER {
			enable(1),
			disable(2)}
    ACCESS read-write
	STATUS mandatory
    DESCRIPTION
      "This variable indicates the TCP-Reset status"
    DEFVAL {disable}
    ::=  { rsIDSSynProfilesParamsEntry 5}



rsIDSSynProfilesParamsStatus OBJECT-TYPE
    SYNTAX RowStatus
    ACCESS read-write
    STATUS mandatory
    DESCRIPTION
      "The row status of this entry"
    ::= {rsIDSSynProfilesParamsEntry 6}

rsIDSSynProfilesSSLMitigationStatus OBJECT-TYPE
    SYNTAX INTEGER {
			enable(1),
			disable(2)}
    ACCESS read-write
    STATUS mandatory
    DESCRIPTION
      "This variable indicates the SSL-Mitigation status"
    DEFVAL {disable}
    ::= {rsIDSSynProfilesParamsEntry 7}

rsIDSynSSLMitigationTable OBJECT-TYPE
    SYNTAX SEQUENCE OF RsIDSynSSLMitigationEntry
    ACCESS not-accessible
    STATUS  mandatory
    DESCRIPTION
      "Table containing the parameters that are needed for out-of-path"
    ::=  {rsIDSSynProtection 20}


rsIDSynSSLMitigationEntry OBJECT-TYPE
    SYNTAX RsIDSynSSLMitigationEntry
    ACCESS not-accessible
    STATUS  mandatory
    DESCRIPTION
       "The row definition for this table."
    INDEX { rsIDSynSSLMitigationEntryName }
    ::=  { rsIDSynSSLMitigationTable 1 }

RsIDSynSSLMitigationEntry::= SEQUENCE {
    rsIDSynSSLMitigationEntryName DisplayString,
    rsIDSynSSLMitigationEntryrsSSLMitigationVIP DisplayString,
    rsIDSynSSLMitigationEntryADCserverDstIP DisplayString,
    rsIDSynSSLMitigationEntryInboundPort INTEGER,
    rsIDSynSSLMitigationEntryOutboundPort INTEGER,
    rsIDSynSSLMitigationEntryMAC MacAddress,
    rsIDSynSSLMitigationEntryPolicyName DisplayString,
    rsIDSynSSLMitigationEntryState INTEGER,
    rsIDSynSSLMitigationEntryStatus RowStatus
}

 rsIDSynSSLMitigationEntryName OBJECT-TYPE
    SYNTAX  DisplayString (SIZE(0..19))
    ACCESS  read-only
    STATUS  mandatory
    DESCRIPTION
      "The Entry Key of the table VIP for ADC"
    ::=  {rsIDSynSSLMitigationEntry 1}

 rsIDSynSSLMitigationEntryrsSSLMitigationVIP OBJECT-TYPE
    SYNTAX  DisplayString
    ACCESS  read-write
    STATUS  mandatory
    DESCRIPTION
      "The VIP address"
    ::=  {rsIDSynSSLMitigationEntry 2}

 rsIDSynSSLMitigationEntryADCserverDstIP OBJECT-TYPE
    SYNTAX  DisplayString
    ACCESS  read-write
    STATUS  mandatory
    DESCRIPTION
      "The ADC server IP address"
    ::=  {rsIDSynSSLMitigationEntry 3}

rsIDSynSSLMitigationEntryInboundPort OBJECT-TYPE
    SYNTAX INTEGER
    ACCESS  read-write
    STATUS  mandatory
    DESCRIPTION
        "The physical inbound port of ADC."
    ::= { rsIDSynSSLMitigationEntry 4}

rsIDSynSSLMitigationEntryOutboundPort OBJECT-TYPE
    SYNTAX INTEGER
    ACCESS  read-write
    STATUS  mandatory
    DESCRIPTION
        "The physical outbound port of ADC."
    ::= { rsIDSynSSLMitigationEntry 5}

rsIDSynSSLMitigationEntryMAC OBJECT-TYPE
    SYNTAX	MacAddress
    ACCESS  read-write
    STATUS  mandatory
    DESCRIPTION
      "ADC MAC"
    ::=  {rsIDSynSSLMitigationEntry 6}

rsIDSynSSLMitigationEntryPolicyName OBJECT-TYPE
	SYNTAX DisplayString
    ACCESS  read-write
    STATUS  mandatory
    DESCRIPTION
        "The related Policy Name."
    ::= { rsIDSynSSLMitigationEntry 7}

rsIDSynSSLMitigationEntryState OBJECT-TYPE
    SYNTAX INTEGER {
              active(1),
              inactive(2) }
    ACCESS  read-write
    STATUS  mandatory
    DESCRIPTION
       "This variable indicates the state of the entry."
    DEFVAL { 1 }
    ::=  { rsIDSynSSLMitigationEntry 8 }

rsIDSynSSLMitigationEntryStatus OBJECT-TYPE
    SYNTAX RowStatus
    ACCESS  read-write
    STATUS  mandatory
    DESCRIPTION
       "This variable indicates the administrative status of this entry.
        Used to delete an entry of this table."
    ::=  { rsIDSynSSLMitigationEntry 9}

rsIDSWebQuarantineTable OBJECT-TYPE
    SYNTAX SEQUENCE OF RsIDSWebQuarantineEntry
    ACCESS not-accessible
    STATUS  mandatory
    DESCRIPTION
      "Web quarantine entries table"
    ::=  {rsIDS 165}


rsIDSWebQuarantineEntry OBJECT-TYPE
    SYNTAX RsIDSWebQuarantineEntry
    ACCESS not-accessible
    STATUS  mandatory
    DESCRIPTION
       "The row definition for this table."
    INDEX { rsIDSWebQuarantineAddress }
    ::=  { rsIDSWebQuarantineTable 1 }

RsIDSWebQuarantineEntry::= SEQUENCE {
    rsIDSWebQuarantineAddress DisplayString,
	rsIDSWebQuarantinePolicy DisplayString,
	rsIDSWebQuarantineTimeHours INTEGER,
	rsIDSWebQuarantineTimeMin INTEGER,
	rsIDSWebQuarantineAttack DisplayString,
	rsIDSWebQuarantineInsertionTime DisplayString,
    rsIDSWebQuarantineStatus RowStatus
}

 rsIDSWebQuarantineAddress OBJECT-TYPE
    SYNTAX  DisplayString
    ACCESS  read-only
    STATUS  mandatory
    DESCRIPTION
      "Web quarantine address"
    ::=  {rsIDSWebQuarantineEntry 1}

 rsIDSWebQuarantinePolicy OBJECT-TYPE
    SYNTAX  DisplayString
    ACCESS  read-write
    STATUS  mandatory
    DESCRIPTION
      "Web quarantine policy"
    ::=  {rsIDSWebQuarantineEntry 2}

rsIDSWebQuarantineTimeHours OBJECT-TYPE
    SYNTAX  INTEGER	(0..168)
    ACCESS  read-write
    STATUS  mandatory
    DESCRIPTION
      "Aging (Hours)"
    ::=  {rsIDSWebQuarantineEntry 3}

rsIDSWebQuarantineTimeMin OBJECT-TYPE
    SYNTAX  INTEGER	(0..59)
    ACCESS  read-write
    STATUS  mandatory
    DESCRIPTION
      "Aging (Minutes)"
    ::=  {rsIDSWebQuarantineEntry 4}

rsIDSWebQuarantineAttack OBJECT-TYPE
    SYNTAX  DisplayString
    ACCESS  read-only
    STATUS  mandatory
    DESCRIPTION
      "Web quarantine attack"
    ::=  {rsIDSWebQuarantineEntry 5}

rsIDSWebQuarantineInsertionTime OBJECT-TYPE
    SYNTAX  DisplayString
    ACCESS  read-only
    STATUS  mandatory
    DESCRIPTION
      "Quarantine time"
    ::=  {rsIDSWebQuarantineEntry 6}

rsIDSWebQuarantineStatus OBJECT-TYPE
    SYNTAX RowStatus
    ACCESS  read-write
    STATUS  mandatory
    DESCRIPTION
       "This variable indicates the administrative status of this entry. Used to delete an entry of this table."
	DEFVAL{1}
    ::=  { rsIDSWebQuarantineEntry 7 }

rsIDSQuarantineTableActionTable OBJECT-TYPE
    SYNTAX SEQUENCE OF RsIDSQuarantineTableAction
    ACCESS not-accessible
    STATUS  mandatory
    DESCRIPTION
      "Table containing the Web quarantine configuration per policy"
    ::=  {rsIDS 166}


rsIDSQuarantineTableAction OBJECT-TYPE
    SYNTAX RsIDSQuarantineTableAction
    ACCESS not-accessible
    STATUS  mandatory
    DESCRIPTION
       "The row definition for this table."
    INDEX { rsIDSQuarantineActionPolicyName }
    ::=  { rsIDSQuarantineTableActionTable 1 }

RsIDSQuarantineTableAction::= SEQUENCE {
    rsIDSQuarantineActionPolicyName DisplayString,
	rsIDSQuarantineActionType INTEGER,
	rsIDSQuarantineActionRedirect DisplayString,
	rsIDSQuarantineActionMetadata INTEGER,
	rsIDSQuarantineActionTimeoutHour INTEGER,
	rsIDSQuarantineActionTimeoutMin INTEGER,
    rsIDSQuarantineActionStatus RowStatus
}
rsIDSQuarantineActionPolicyName OBJECT-TYPE
    SYNTAX  DisplayString
    ACCESS  read-write
    STATUS  mandatory
    DESCRIPTION
      "Web quarantine configuration policy name"
    ::=  {rsIDSQuarantineTableAction 1}

 rsIDSQuarantineActionType OBJECT-TYPE
    SYNTAX INTEGER {
              default(1),
              redirect(2) }
    ACCESS  read-write
    STATUS  mandatory
    DESCRIPTION
      "Web quarantine action type"
    ::=  {rsIDSQuarantineTableAction 2}

 rsIDSQuarantineActionRedirect OBJECT-TYPE
    SYNTAX  DisplayString
    ACCESS  read-write
    STATUS  mandatory
    DESCRIPTION
      "Redirection web-server"
    ::=  {rsIDSQuarantineTableAction 3}

 rsIDSQuarantineActionMetadata OBJECT-TYPE
    SYNTAX INTEGER {
              enable(1),
              disable(2) }
    ACCESS  read-write
    STATUS  mandatory
    DESCRIPTION
      "Metadata"
	DEFVAL  {disable}
    ::=  {rsIDSQuarantineTableAction 4}

rsIDSQuarantineActionTimeoutHour OBJECT-TYPE
    SYNTAX  INTEGER	(0..168)
    ACCESS  read-write
    STATUS  mandatory
    DESCRIPTION
      "Aging (Hours)"
    ::=  {rsIDSQuarantineTableAction 5}

rsIDSQuarantineActionTimeoutMin OBJECT-TYPE
    SYNTAX  INTEGER	(0..59)
    ACCESS  read-write
    STATUS  mandatory
    DESCRIPTION
      "Aging (Minutes)"
    ::=  {rsIDSQuarantineTableAction 6}

rsIDSQuarantineActionStatus OBJECT-TYPE
    SYNTAX RowStatus
    ACCESS  read-write
    STATUS  mandatory
    DESCRIPTION
       "This variable indicates the administrative status of this entry. Used to delete an entry of this table."
	DEFVAL{1}
    ::=  { rsIDSQuarantineTableAction 7}

rsIDSynSSLMitigationAlteonMngIP OBJECT-TYPE
    SYNTAX  DisplayString (SIZE(0..256))
    ACCESS  read-write
    STATUS  mandatory
    DESCRIPTION
      "The ADC Management IP address"
    ::=  {rsIDSSynProtection 21}

rsIDSynSSLMitigationAlteonStatus OBJECT-TYPE
	SYNTAX INTEGER {
			enable(1),
			disable(2)}
    ACCESS  read-write
    STATUS  mandatory
    DESCRIPTION
      "The ADC status"
	 DEFVAL  {disable}
    ::=  {rsIDSSynProtection 22}

rsIDSynSSLMitigationAlteonPortsTable OBJECT-TYPE
    SYNTAX SEQUENCE OF RsIDSynSSLMitigationAlteonPortsEntry
    ACCESS not-accessible
    STATUS  mandatory
    DESCRIPTION
      "Table containing Alteon ports pair"
    ::=  {rsIDSSynProtection 23}


rsIDSynSSLMitigationAlteonPortsEntry OBJECT-TYPE
    SYNTAX RsIDSynSSLMitigationAlteonPortsEntry
    ACCESS not-accessible
    STATUS  mandatory
    DESCRIPTION
        "The entity stores Alteon ports pair."
	INDEX { rsIDSynSSLMitigationAlteonIndex }
    ::= {rsIDSynSSLMitigationAlteonPortsTable 1}

RsIDSynSSLMitigationAlteonPortsEntry::= SEQUENCE {
	rsIDSynSSLMitigationAlteonIndex		INTEGER,
	rsIDSynSSLMitigationAlteonInboundPort	INTEGER,
    rsIDSynSSLMitigationAlteonOutboundPort	INTEGER
}

rsIDSynSSLMitigationAlteonIndex OBJECT-TYPE
	SYNTAX  INTEGER
    ACCESS  read-write
    STATUS  mandatory
    DESCRIPTION
      "The entry index"
    ::=  {rsIDSynSSLMitigationAlteonPortsEntry 1}

rsIDSynSSLMitigationAlteonInboundPort OBJECT-TYPE
	SYNTAX  INTEGER
    ACCESS  read-write
    STATUS  mandatory
    DESCRIPTION
      "The Alteon Inbound port"
    ::=  {rsIDSynSSLMitigationAlteonPortsEntry 2}

rsIDSynSSLMitigationAlteonOutboundPort OBJECT-TYPE
	SYNTAX  INTEGER
    ACCESS  read-write
    STATUS  mandatory
    DESCRIPTION
      "The Alteon Outbound port"
    ::=  {rsIDSynSSLMitigationAlteonPortsEntry 3}

rsIDSynSSLMitigationAlteonSnmpAlertPort OBJECT-TYPE
    SYNTAX  INTEGER
    ACCESS  read-write
    STATUS  mandatory
    DESCRIPTION
      "The Alteon SNMP alert port"
    DEFVAL{162}
    ::=  {rsIDSSynProtection 24}


rsIDSynSSLMitigationAlteonMac OBJECT-TYPE
    SYNTAX  MacAddress
    ACCESS  read-write
    STATUS  mandatory
    DESCRIPTION
      "The Alteon MAC Address"
    ::=  {rsIDSSynProtection 27}

rsIDSHwPoliciesTable OBJECT-TYPE
    SYNTAX SEQUENCE OF RsIDSHwPoliciesTableEntry
    ACCESS not-accessible
    STATUS  mandatory
    DESCRIPTION
      "Table containing the sizes of the hw accelerator policies"
    ::=  {rsIDS 167}

rsIDSHwPoliciesTableEntry OBJECT-TYPE
    SYNTAX RsIDSHwPoliciesTableEntry
    ACCESS not-accessible
    STATUS  mandatory
    DESCRIPTION
       "The row definition for this table."
    INDEX { rsIDSHwPoliciesTableEntryName,  rsIDSHwPoliciesTableEntryDirection}
    ::=  { rsIDSHwPoliciesTable 1 }

RsIDSHwPoliciesTableEntry::= SEQUENCE {
    rsIDSHwPoliciesTableEntryName DisplayString,
	rsIDSHwPoliciesTableEntryDirection INTEGER,
	rsIDSHwPoliciesTableEntryHwEntriesNum INTEGER,
	rsIDSHwPoliciesTableEntrySubPoliciesNum INTEGER,
    rsIDSHwPoliciesTableEntryStatus RowStatus
}

rsIDSHwPoliciesTableEntryName OBJECT-TYPE
    SYNTAX  DisplayString
    ACCESS  read-only
    STATUS  mandatory
    DESCRIPTION
      "Policy name"
    ::=  {rsIDSHwPoliciesTableEntry 1}

rsIDSHwPoliciesTableEntryDirection OBJECT-TYPE
    SYNTAX INTEGER {
              inbound(1),
              outbound(2),
			  none(3) }
    ACCESS  read-only
    STATUS  mandatory
    DESCRIPTION
      "policy direction"
    ::=  {rsIDSHwPoliciesTableEntry 2}

rsIDSHwPoliciesTableEntryHwEntriesNum OBJECT-TYPE
    SYNTAX  INTEGER
    ACCESS  read-only
    STATUS  mandatory
    DESCRIPTION
      "Number of hw policies required to create this policy."
    ::=  {rsIDSHwPoliciesTableEntry 3}


rsIDSHwPoliciesTableEntrySubPoliciesNum OBJECT-TYPE
    SYNTAX  INTEGER
    ACCESS  read-only
    STATUS  mandatory
    DESCRIPTION
      "Number of sub policies required to create this policy."
    ::=  {rsIDSHwPoliciesTableEntry 4}

rsIDSHwPoliciesTableEntryStatus OBJECT-TYPE
    SYNTAX RowStatus
    ACCESS  read-only
    STATUS  mandatory
    DESCRIPTION
       "This variable indicates the administrative status of this entry."
	DEFVAL{1}
    ::=  { rsIDSHwPoliciesTableEntry 5}

rsIDSTrafficExclusionStatus OBJECT-TYPE
 SYNTAX INTEGER {
		enable(1),
		disable(2)
		}
   ACCESS  read-write
   STATUS  mandatory
   DESCRIPTION
       "configures whether the traffic exclusion is enabled or disabled"
    ::=  { rsIDS 168}

rsIDSMemoryQuarantineTuning OBJECT IDENTIFIER ::= { rsIDS 169}

rsIDSQuarantineMaxIPs OBJECT-TYPE
    SYNTAX INTEGER (1..10000)
    ACCESS  read-only
    STATUS  mandatory
    DESCRIPTION
      "Memory reserved for quarantine table."
	  ::=  { rsIDSMemoryQuarantineTuning 1 }

rsIDSQuarantineMaxIPsAfterReset OBJECT-TYPE
    SYNTAX INTEGER (1..10000)
    ACCESS  read-write
    STATUS  mandatory
    DESCRIPTION
      "Memory reserved for quarantine table."
    ::=  { rsIDSMemoryQuarantineTuning 2 }

rsIDSHwPoliciesTotalNum OBJECT-TYPE
    SYNTAX  INTEGER
    ACCESS  read-only
    STATUS  mandatory
    DESCRIPTION
      "Total number of device policies entries."
    ::=  {rsIDS 170}

rsIDSHwPoliciesSubPoliciesUtilization OBJECT-TYPE
    SYNTAX  INTEGER
    ACCESS  read-only
    STATUS  mandatory
    DESCRIPTION
      "Utilization (percent) of sub policies for the device policies."
    ::=  {rsIDS 171}

rsIDSHwPoliciesHWEntriesUtilization OBJECT-TYPE
    SYNTAX  INTEGER
    ACCESS  read-only
    STATUS  mandatory
    DESCRIPTION
      "Utilization (percent) of hw entries for the device policies."
    ::=  {rsIDS 172}

rsIDSBWMReportRiskLevel OBJECT-TYPE
    SYNTAX INTEGER {
		  info(1),
		  low(2),
       	  medium(3),
		  high(4)}
    ACCESS read-write
    STATUS mandatory
    DESCRIPTION
      "Risk level for BWM reporting"
    DEFVAL  { 1 }
    ::= {rsIDS 173}

rsIDSHttpfldPipelineStatus OBJECT-TYPE
    SYNTAX INTEGER {
			enable(1),
			disable(2)}
    ACCESS  read-write
    STATUS  mandatory
    DESCRIPTION
       "This variable indicates the status of http pipeline in http flood mitigator"
	DEFVAL  {enable}
    ::= {rsHttpFlood 82}

rsIDSQuarantineFileSendTable OBJECT-TYPE
    SYNTAX SEQUENCE OF RsIDSQuarantineFileSend
    ACCESS not-accessible
    STATUS  mandatory
    DESCRIPTION
      "Download HTML File For Quarantine Policy Action"
    ::=  {rsIDS 174}


rsIDSQuarantineFileSend OBJECT-TYPE
    SYNTAX RsIDSQuarantineFileSend
    ACCESS not-accessible
    STATUS  mandatory
    DESCRIPTION
       "The row definition for this table."
    INDEX { rsQuarantineDownloadPolicy }
    ::=  { rsIDSQuarantineFileSendTable 1 }

RsIDSQuarantineFileSend::= SEQUENCE {
	rsQuarantineDownloadPolicy DisplayString,
    rsQuarantineDownloadAddress DisplayString,
	rsQuarantineDownloadfile DisplayString,
	rsQuarantineDownloadStatus RowStatus
}

 rsQuarantineDownloadPolicy OBJECT-TYPE
    SYNTAX  DisplayString
    ACCESS  read-write
    STATUS  mandatory
    DESCRIPTION
      "Quarantine Action Policy Name"
    ::=  {rsIDSQuarantineFileSend 1}

 rsQuarantineDownloadAddress OBJECT-TYPE
    SYNTAX  DisplayString
    ACCESS  read-write
    STATUS  mandatory
    DESCRIPTION
      "Quarantine File Download Remote Server IP Address"
    ::=  {rsIDSQuarantineFileSend 2}

rsQuarantineDownloadfile OBJECT-TYPE
    SYNTAX  DisplayString
    ACCESS  read-write
    STATUS  mandatory
    DESCRIPTION
      "File to Download"
    ::=  {rsIDSQuarantineFileSend 3}

rsQuarantineDownloadStatus OBJECT-TYPE
    SYNTAX RowStatus
    ACCESS  read-write
    STATUS  mandatory
    DESCRIPTION
       "This variable indicates the administrative status of this entry. Used to delete an entry of this table."
	DEFVAL{1}
    ::=  { rsIDSQuarantineFileSend 4 }
rsTrafficUtilization OBJECT IDENTIFIER ::= { rsIDS 188}

rsTrafficUtilizationConcurrentConnectionsTCP OBJECT-TYPE
   SYNTAX INTEGER
   ACCESS  read-only
   STATUS  mandatory
   DESCRIPTION
       "Concurrent Connections TCP Protocol."
   ::= {rsTrafficUtilization 1 }
rsTrafficUtilizationConcurrentConnectionsUDP OBJECT-TYPE
   SYNTAX INTEGER
   ACCESS  read-only
   STATUS  mandatory
   DESCRIPTION
      "Concurrent Connections UDP Protocol."
   ::= {rsTrafficUtilization 2}
rsTrafficUtilizationPerPort OBJECT IDENTIFIER ::= { rsTrafficUtilization 3}
rsTrafficUtilizationPerPortTableUDP 	OBJECT-TYPE
	SYNTAX SEQUENCE OF RsTrafficUtilizationPerPortEntryUDP
	ACCESS  not-accessible
    STATUS  mandatory
    DESCRIPTION
        "A table Traffic Utilization per Policy."
    ::= {rsTrafficUtilizationPerPort 1}
rsTrafficUtilizationPerPortEntryUDP OBJECT-TYPE
	SYNTAX RsTrafficUtilizationPerPortEntryUDP
	ACCESS not-accessible
	STATUS mandatory
	DESCRIPTION
		"An entry of the traffic utilization per Port and Protocol."
	INDEX {rsTrafficUtilizationPortPerPortUDP}
	::= { rsTrafficUtilizationPerPortTableUDP 1}
RsTrafficUtilizationPerPortEntryUDP ::= SEQUENCE {
	rsTrafficUtilizationPortPerPortUDP			INTEGER,
	rsDroppedPacketsPerPortUDP					Counter64,
	rsDroppedBytesPerPortUDP					Counter64,
	rsReceivedPacketsPerPortUDP					Counter64,
	rsReceivedBytesPerPortUDP					Counter64,
	rsExcludedPacketsPerPortUDP					Counter64,
	rsExcludedBytesPerPortUDP					Counter64
}
rsTrafficUtilizationPortPerPortUDP OBJECT-TYPE
   SYNTAX INTEGER
   ACCESS  read-write
   STATUS  mandatory
   DESCRIPTION
       "Port Index of traffic Monitoring table."
   ::= {rsTrafficUtilizationPerPortEntryUDP 1}
rsDroppedPacketsPerPortUDP OBJECT-TYPE
   SYNTAX Counter64
   ACCESS  read-only
   STATUS  mandatory
   DESCRIPTION
       "Concurrent dropped Packets per port and protocol."
   ::= {rsTrafficUtilizationPerPortEntryUDP 2}
rsDroppedBytesPerPortUDP OBJECT-TYPE
   SYNTAX Counter64
   ACCESS  read-only
   STATUS  mandatory
   DESCRIPTION
       "Concurrent dropped Bytes per port and protocol."
   ::= {rsTrafficUtilizationPerPortEntryUDP 3}
rsReceivedPacketsPerPortUDP OBJECT-TYPE
   SYNTAX Counter64
   ACCESS  read-only
   STATUS  mandatory
   DESCRIPTION
       "Concurrent received Packets per port and protocol."
   ::= {rsTrafficUtilizationPerPortEntryUDP 4}
rsReceivedBytesPerPortUDP OBJECT-TYPE
   SYNTAX Counter64
   ACCESS  read-only
   STATUS  mandatory
   DESCRIPTION
       "Concurrent received Bytes per port and protocol."
   ::= {rsTrafficUtilizationPerPortEntryUDP 5}
rsExcludedPacketsPerPortUDP OBJECT-TYPE
   SYNTAX Counter64
   ACCESS  read-only
   STATUS  mandatory
   DESCRIPTION
       "Concurrent excluded Packets per port and protocol."
   ::= {rsTrafficUtilizationPerPortEntryUDP 6}
rsExcludedBytesPerPortUDP OBJECT-TYPE
   SYNTAX Counter64
   ACCESS  read-only
   STATUS  mandatory
   DESCRIPTION
       "Concurrent excluded Bytes per port and protocol."
   ::= {rsTrafficUtilizationPerPortEntryUDP 7}

rsTrafficUtilizationPerPortTableTCP 	OBJECT-TYPE
	SYNTAX SEQUENCE OF RsTrafficUtilizationPerPortEntryTCP
	ACCESS  not-accessible
    STATUS  mandatory
    DESCRIPTION
        "A table Traffic Utilization per Policy."
    ::= {rsTrafficUtilizationPerPort 2}
rsTrafficUtilizationPerPortEntryTCP OBJECT-TYPE
	SYNTAX RsTrafficUtilizationPerPortEntryTCP
	ACCESS not-accessible
	STATUS mandatory
	DESCRIPTION
		"An entry of the traffic utilization per Port and Protocol."
	INDEX {rsTrafficUtilizationPortPerPortTCP}
	::= { rsTrafficUtilizationPerPortTableTCP 1}
RsTrafficUtilizationPerPortEntryTCP ::= SEQUENCE {
	rsTrafficUtilizationPortPerPortTCP			INTEGER,
	rsDroppedPacketsPerPortTCP					Counter64,
	rsDroppedBytesPerPortTCP					Counter64,
	rsReceivedPacketsPerPortTCP					Counter64,
	rsReceivedBytesPerPortTCP					Counter64,
	rsExcludedPacketsPerPortTCP					Counter64,
	rsExcludedBytesPerPortTCP					Counter64
}
rsTrafficUtilizationPortPerPortTCP OBJECT-TYPE
   SYNTAX INTEGER
   ACCESS  read-write
   STATUS  mandatory
   DESCRIPTION
       "Port Index of traffic Monitoring table."
   ::= {rsTrafficUtilizationPerPortEntryTCP 1}
rsDroppedPacketsPerPortTCP OBJECT-TYPE
   SYNTAX Counter64
   ACCESS  read-only
   STATUS  mandatory
   DESCRIPTION
       "Concurrent dropped Packets per port and protocol."
   ::= {rsTrafficUtilizationPerPortEntryTCP 2}
rsDroppedBytesPerPortTCP OBJECT-TYPE
   SYNTAX Counter64
   ACCESS  read-only
   STATUS  mandatory
   DESCRIPTION
       "Concurrent dropped Bytes per port and protocol."
   ::= {rsTrafficUtilizationPerPortEntryTCP 3}
rsReceivedPacketsPerPortTCP OBJECT-TYPE
   SYNTAX Counter64
   ACCESS  read-only
   STATUS  mandatory
   DESCRIPTION
       "Concurrent received Packets per port and protocol."
   ::= {rsTrafficUtilizationPerPortEntryTCP 4}
rsReceivedBytesPerPortTCP OBJECT-TYPE
   SYNTAX Counter64
   ACCESS  read-only
   STATUS  mandatory
   DESCRIPTION
       "Concurrent received Bytes per port and protocol."
   ::= {rsTrafficUtilizationPerPortEntryTCP 5}
rsExcludedPacketsPerPortTCP OBJECT-TYPE
   SYNTAX Counter64
   ACCESS  read-only
   STATUS  mandatory
   DESCRIPTION
       "Concurrent excluded Packets per port and protocol."
   ::= {rsTrafficUtilizationPerPortEntryTCP 6}
rsExcludedBytesPerPortTCP OBJECT-TYPE
   SYNTAX Counter64
   ACCESS  read-only
   STATUS  mandatory
   DESCRIPTION
       "Concurrent excluded Bytes per port and protocol."
   ::= {rsTrafficUtilizationPerPortEntryTCP 7}
 rsTrafficUtilizationPerPortTableICMP 	OBJECT-TYPE
	SYNTAX SEQUENCE OF RsTrafficUtilizationPerPortEntryICMP
	ACCESS  not-accessible
    STATUS  mandatory
    DESCRIPTION
        "A table Traffic Utilization per Policy."
    ::= {rsTrafficUtilizationPerPort 3}
rsTrafficUtilizationPerPortEntryICMP OBJECT-TYPE
	SYNTAX RsTrafficUtilizationPerPortEntryICMP
	ACCESS not-accessible
	STATUS mandatory
	DESCRIPTION
		"An entry of the traffic utilization per Port and Protocol."
	INDEX {rsTrafficUtilizationPortPerPortICMP}
	::= { rsTrafficUtilizationPerPortTableICMP 1}
RsTrafficUtilizationPerPortEntryICMP ::= SEQUENCE {
	rsTrafficUtilizationPortPerPortICMP			INTEGER,
	rsDroppedPacketsPerPortICMP					Counter64,
	rsDroppedBytesPerPortICMP					Counter64,
	rsReceivedPacketsPerPortICMP				Counter64,
	rsReceivedBytesPerPortICMP					Counter64,
	rsExcludedPacketsPerPortICMP				Counter64,
	rsExcludedBytesPerPortICMP					Counter64
}
rsTrafficUtilizationPortPerPortICMP OBJECT-TYPE
   SYNTAX INTEGER
   ACCESS  read-write
   STATUS  mandatory
   DESCRIPTION
       "Port Index of traffic Monitoring table."
   ::= {rsTrafficUtilizationPerPortEntryICMP 1}
rsDroppedPacketsPerPortICMP OBJECT-TYPE
   SYNTAX Counter64
   ACCESS  read-only
   STATUS  mandatory
   DESCRIPTION
       "Concurrent dropped Packets per port and protocol."
   ::= {rsTrafficUtilizationPerPortEntryICMP 2}
rsDroppedBytesPerPortICMP OBJECT-TYPE
   SYNTAX Counter64
   ACCESS  read-only
   STATUS  mandatory
   DESCRIPTION
       "Concurrent dropped Bytes per port and protocol."
   ::= {rsTrafficUtilizationPerPortEntryICMP 3}
rsReceivedPacketsPerPortICMP OBJECT-TYPE
   SYNTAX Counter64
   ACCESS  read-only
   STATUS  mandatory
   DESCRIPTION
       "Concurrent received Packets per port and protocol."
   ::= {rsTrafficUtilizationPerPortEntryICMP 4}
rsReceivedBytesPerPortICMP OBJECT-TYPE
   SYNTAX Counter64
   ACCESS  read-only
   STATUS  mandatory
   DESCRIPTION
       "Concurrent received Bytes per port and protocol."
   ::= {rsTrafficUtilizationPerPortEntryICMP 5}
rsExcludedPacketsPerPortICMP OBJECT-TYPE
   SYNTAX Counter64
   ACCESS  read-only
   STATUS  mandatory
   DESCRIPTION
       "Concurrent excluded Packets per port and protocol."
   ::= {rsTrafficUtilizationPerPortEntryICMP 6}
rsExcludedBytesPerPortICMP OBJECT-TYPE
   SYNTAX Counter64
   ACCESS  read-only
   STATUS  mandatory
   DESCRIPTION
       "Concurrent excluded Bytes per port and protocol."
   ::= {rsTrafficUtilizationPerPortEntryICMP 7}
rsTrafficUtilizationPerPortTableOTHER 	OBJECT-TYPE
	SYNTAX SEQUENCE OF RsTrafficUtilizationPerPortEntryOTHER
	ACCESS  not-accessible
    STATUS  mandatory
    DESCRIPTION
        "A table Traffic Utilization per Policy."
    ::= {rsTrafficUtilizationPerPort 4}
rsTrafficUtilizationPerPortEntryOTHER OBJECT-TYPE
	SYNTAX RsTrafficUtilizationPerPortEntryOTHER
	ACCESS not-accessible
	STATUS mandatory
	DESCRIPTION
		"An entry of the traffic utilization per Port and Protocol."
	INDEX {rsTrafficUtilizationPortPerPortOTHER}
	::= { rsTrafficUtilizationPerPortTableOTHER 1}
RsTrafficUtilizationPerPortEntryOTHER ::= SEQUENCE {
	rsTrafficUtilizationPortPerPortOTHER			INTEGER,
	rsDroppedPacketsPerPortOTHER					Counter64,
	rsDroppedBytesPerPortOTHER					Counter64,
	rsReceivedPacketsPerPortOTHER				Counter64,
	rsReceivedBytesPerPortOTHER					Counter64,
	rsExcludedPacketsPerPortOTHER				Counter64,
	rsExcludedBytesPerPortOTHER					Counter64
}
rsTrafficUtilizationPortPerPortOTHER OBJECT-TYPE
   SYNTAX INTEGER
   ACCESS  read-write
   STATUS  mandatory
   DESCRIPTION
       "Port Index of traffic Monitoring table."
   ::= {rsTrafficUtilizationPerPortEntryOTHER 1}
rsDroppedPacketsPerPortOTHER OBJECT-TYPE
   SYNTAX Counter64
   ACCESS  read-only
   STATUS  mandatory
   DESCRIPTION
       "Concurrent dropped Packets per port and protocol."
   ::= {rsTrafficUtilizationPerPortEntryOTHER 2}
rsDroppedBytesPerPortOTHER OBJECT-TYPE
   SYNTAX Counter64
   ACCESS  read-only
   STATUS  mandatory
   DESCRIPTION
       "Concurrent dropped Bytes per port and protocol."
   ::= {rsTrafficUtilizationPerPortEntryOTHER 3}
rsReceivedPacketsPerPortOTHER OBJECT-TYPE
   SYNTAX Counter64
   ACCESS  read-only
   STATUS  mandatory
   DESCRIPTION
       "Concurrent received Packets per port and protocol."
   ::= {rsTrafficUtilizationPerPortEntryOTHER 4}
rsReceivedBytesPerPortOTHER OBJECT-TYPE
   SYNTAX Counter64
   ACCESS  read-only
   STATUS  mandatory
   DESCRIPTION
       "Concurrent received Bytes per port and protocol."
   ::= {rsTrafficUtilizationPerPortEntryOTHER 5}
rsExcludedPacketsPerPortOTHER OBJECT-TYPE
   SYNTAX Counter64
   ACCESS  read-only
   STATUS  mandatory
   DESCRIPTION
       "Concurrent excluded Packets per port and protocol."
   ::= {rsTrafficUtilizationPerPortEntryOTHER 6}
rsExcludedBytesPerPortOTHER OBJECT-TYPE
   SYNTAX Counter64
   ACCESS  read-only
   STATUS  mandatory
   DESCRIPTION
       "Concurrent excluded Bytes per port and protocol."
   ::= {rsTrafficUtilizationPerPortEntryOTHER 7}
rsTrafficUtilizationPerPortTableSCTP	OBJECT-TYPE
	SYNTAX SEQUENCE OF RsTrafficUtilizationPerPortEntrySCTP
	ACCESS  not-accessible
    STATUS  mandatory
    DESCRIPTION
        "A table Traffic Utilization per Policy."
    ::= {rsTrafficUtilizationPerPort 5}
rsTrafficUtilizationPerPortEntrySCTP OBJECT-TYPE
	SYNTAX RsTrafficUtilizationPerPortEntrySCTP
	ACCESS not-accessible
	STATUS mandatory
	DESCRIPTION
		"An entry of the traffic utilization per Port and Protocol."
	INDEX {rsTrafficUtilizationPortPerPortSCTP}
	::= { rsTrafficUtilizationPerPortTableSCTP 1}
RsTrafficUtilizationPerPortEntrySCTP::= SEQUENCE {
	rsTrafficUtilizationPortPerPortSCTP			INTEGER,
	rsDroppedPacketsPerPortSCTP					Counter64,
	rsDroppedBytesPerPortSCTP					Counter64,
	rsReceivedPacketsPerPortSCTP				Counter64,
	rsReceivedBytesPerPortSCTP					Counter64,
	rsExcludedPacketsPerPortSCTP				Counter64,
	rsExcludedBytesPerPortSCTP					Counter64
}
rsTrafficUtilizationPortPerPortSCTP OBJECT-TYPE
   SYNTAX INTEGER
   ACCESS  read-write
   STATUS  mandatory
   DESCRIPTION
       "Port Index of traffic Monitoring table."
   ::= {rsTrafficUtilizationPerPortEntrySCTP 1}
rsDroppedPacketsPerPortSCTP OBJECT-TYPE
   SYNTAX Counter64
   ACCESS  read-only
   STATUS  mandatory
   DESCRIPTION
       "Concurrent dropped Packets per port and protocol."
   ::= {rsTrafficUtilizationPerPortEntrySCTP 2}
rsDroppedBytesPerPortSCTP OBJECT-TYPE
   SYNTAX Counter64
   ACCESS  read-only
   STATUS  mandatory
   DESCRIPTION
       "Concurrent dropped Bytes per port and protocol."
   ::= {rsTrafficUtilizationPerPortEntrySCTP 3}
rsReceivedPacketsPerPortSCTP OBJECT-TYPE
   SYNTAX Counter64
   ACCESS  read-only
   STATUS  mandatory
   DESCRIPTION
       "Concurrent received Packets per port and protocol."
   ::= {rsTrafficUtilizationPerPortEntrySCTP 4}
rsReceivedBytesPerPortSCTP OBJECT-TYPE
   SYNTAX Counter64
   ACCESS  read-only
   STATUS  mandatory
   DESCRIPTION
       "Concurrent received Bytes per port and protocol."
   ::= {rsTrafficUtilizationPerPortEntrySCTP 5}
rsExcludedPacketsPerPortSCTP OBJECT-TYPE
   SYNTAX Counter64
   ACCESS  read-only
   STATUS  mandatory
   DESCRIPTION
       "Concurrent excluded Packets per port and protocol."
   ::= {rsTrafficUtilizationPerPortEntrySCTP 6}
rsExcludedBytesPerPortSCTP OBJECT-TYPE
   SYNTAX Counter64
   ACCESS  read-only
   STATUS  mandatory
   DESCRIPTION
       "Concurrent excluded Bytes per port and protocol."
   ::= {rsTrafficUtilizationPerPortEntrySCTP 7}

rsTrafficUtilizationPerPortTableIGMP	OBJECT-TYPE
	SYNTAX SEQUENCE OF RsTrafficUtilizationPerPortEntryIGMP
	ACCESS  not-accessible
    STATUS  mandatory
    DESCRIPTION
        "A table Traffic Utilization per Policy."
    ::= {rsTrafficUtilizationPerPort 6}
rsTrafficUtilizationPerPortEntryIGMP OBJECT-TYPE
	SYNTAX RsTrafficUtilizationPerPortEntryIGMP
	ACCESS not-accessible
	STATUS mandatory
	DESCRIPTION
		"An entry of the traffic utilization per Port and Protocol."
	INDEX {rsTrafficUtilizationPortPerPortIGMP}
	::= { rsTrafficUtilizationPerPortTableIGMP 1}
RsTrafficUtilizationPerPortEntryIGMP::= SEQUENCE {
	rsTrafficUtilizationPortPerPortIGMP			INTEGER,
	rsDroppedPacketsPerPortIGMP					Counter64,
	rsDroppedBytesPerPortIGMP					Counter64,
	rsReceivedPacketsPerPortIGMP				Counter64,
	rsReceivedBytesPerPortIGMP					Counter64,
	rsExcludedPacketsPerPortIGMP				Counter64,
	rsExcludedBytesPerPortIGMP					Counter64
}
rsTrafficUtilizationPortPerPortIGMP OBJECT-TYPE
   SYNTAX INTEGER
   ACCESS  read-write
   STATUS  mandatory
   DESCRIPTION
       "Port Index of traffic Monitoring table."
   ::= {rsTrafficUtilizationPerPortEntryIGMP 1}
rsDroppedPacketsPerPortIGMP OBJECT-TYPE
   SYNTAX Counter64
   ACCESS  read-only
   STATUS  mandatory
   DESCRIPTION
       "Concurrent dropped Packets per port and protocol."
   ::= {rsTrafficUtilizationPerPortEntryIGMP 2}
rsDroppedBytesPerPortIGMP OBJECT-TYPE
   SYNTAX Counter64
   ACCESS  read-only
   STATUS  mandatory
   DESCRIPTION
       "Concurrent dropped Bytes per port and protocol."
   ::= {rsTrafficUtilizationPerPortEntryIGMP 3}
rsReceivedPacketsPerPortIGMP OBJECT-TYPE
   SYNTAX Counter64
   ACCESS  read-only
   STATUS  mandatory
   DESCRIPTION
       "Concurrent received Packets per port and protocol."
   ::= {rsTrafficUtilizationPerPortEntryIGMP 4}
rsReceivedBytesPerPortIGMP OBJECT-TYPE
   SYNTAX Counter64
   ACCESS  read-only
   STATUS  mandatory
   DESCRIPTION
       "Concurrent received Bytes per port and protocol."
   ::= {rsTrafficUtilizationPerPortEntryIGMP 5}
rsExcludedPacketsPerPortIGMP OBJECT-TYPE
   SYNTAX Counter64
   ACCESS  read-only
   STATUS  mandatory
   DESCRIPTION
       "Concurrent excluded Packets per port and protocol."
   ::= {rsTrafficUtilizationPerPortEntryIGMP 6}
rsExcludedBytesPerPortIGMP OBJECT-TYPE
   SYNTAX Counter64
   ACCESS  read-only
   STATUS  mandatory
   DESCRIPTION
       "Concurrent excluded Bytes per port and protocol."
   ::= {rsTrafficUtilizationPerPortEntryIGMP 7}
rsTrafficUtilizationPerPolicy OBJECT IDENTIFIER ::= { rsTrafficUtilization 4}

rsTrafficUtilizationPerPolicyTableUDP 	OBJECT-TYPE
	SYNTAX SEQUENCE OF RsTrafficUtilizationPerPolicyEntryUDP
	ACCESS  not-accessible
    STATUS  mandatory
    DESCRIPTION
        "A table of Traffic Utilization Per Policy."
    ::= {rsTrafficUtilizationPerPolicy 1}
rsTrafficUtilizationPerPolicyEntryUDP OBJECT-TYPE
	SYNTAX RsTrafficUtilizationPerPolicyEntryUDP
	ACCESS not-accessible
	STATUS mandatory
	DESCRIPTION
	"An entry of the traffic utilization per Policy and Protocol."
	INDEX {rsPolicyNamePerPolicyUDP}
	::= { rsTrafficUtilizationPerPolicyTableUDP 1}
RsTrafficUtilizationPerPolicyEntryUDP ::= SEQUENCE {
	rsPolicyNamePerPolicyUDP							DisplayString,
	rsNewConnectionsPerPolicyUDP						INTEGER,
	rsConcurConnectionsPerPolicyUDP						INTEGER,
	rsDroppedPacketsPerPolicyUDP						Counter64,
	rsDroppedBytesPerPolicyUDP							Counter64,
	rsReceivedPacketsPerPolicyUDP						Counter64,
	rsReceivedBytesPerPolicyUDP							Counter64
}
rsPolicyNamePerPolicyUDP OBJECT-TYPE
   SYNTAX DisplayString
   ACCESS  read-write
   STATUS  mandatory
   DESCRIPTION
       "Policy name for traffic monitoring utilization table."
   ::= {rsTrafficUtilizationPerPolicyEntryUDP 1}

rsNewConnectionsPerPolicyUDP OBJECT-TYPE
   SYNTAX INTEGER
   ACCESS  read-only
   STATUS  mandatory
   DESCRIPTION
       "New connections per policy."
   ::= {rsTrafficUtilizationPerPolicyEntryUDP 2}

rsConcurConnectionsPerPolicyUDP OBJECT-TYPE
   SYNTAX INTEGER
   ACCESS  read-only
   STATUS  mandatory
   DESCRIPTION
       "Reserved for Concurrent connections per policy UDP."
   ::= {rsTrafficUtilizationPerPolicyEntryUDP 3}

rsDroppedPacketsPerPolicyUDP OBJECT-TYPE
   SYNTAX Counter64
   ACCESS  read-only
   STATUS  mandatory
   DESCRIPTION
       "Concurrent dropped Packets per policy and protocol."
   ::= {rsTrafficUtilizationPerPolicyEntryUDP 4}
rsDroppedBytesPerPolicyUDP OBJECT-TYPE
   SYNTAX Counter64
   ACCESS  read-only
   STATUS  mandatory
   DESCRIPTION
       "Concurrent dropped Bytes per policy and protocol."
   ::= {rsTrafficUtilizationPerPolicyEntryUDP 5}

rsReceivedPacketsPerPolicyUDP OBJECT-TYPE
   SYNTAX Counter64
   ACCESS  read-only
   STATUS  mandatory
   DESCRIPTION
       "Concurrent received Packets per policy and protocol."
   ::= {rsTrafficUtilizationPerPolicyEntryUDP 6}
rsReceivedBytesPerPolicyUDP OBJECT-TYPE
   SYNTAX Counter64
   ACCESS  read-only
   STATUS  mandatory
   DESCRIPTION
       "Concurrent received Bytes per policy and protocol."
   ::= {rsTrafficUtilizationPerPolicyEntryUDP 7}

rsTrafficUtilizationPerPolicyTableTCP 	OBJECT-TYPE
	SYNTAX SEQUENCE OF RsTrafficUtilizationPerPolicyEntryTCP
	ACCESS  not-accessible
    STATUS  mandatory
    DESCRIPTION
        "A table of Traffic Utilization Per Policy."
    ::= {rsTrafficUtilizationPerPolicy 2}
rsTrafficUtilizationPerPolicyEntryTCP OBJECT-TYPE
	SYNTAX RsTrafficUtilizationPerPolicyEntryTCP
	ACCESS not-accessible
	STATUS mandatory
	DESCRIPTION
	"An entry of the traffic utilization per Policy and Protocol."
	INDEX {rsPolicyNamePerPolicyTCP}
	::= { rsTrafficUtilizationPerPolicyTableTCP 1}

RsTrafficUtilizationPerPolicyEntryTCP ::= SEQUENCE {
	rsPolicyNamePerPolicyTCP							DisplayString,
	rsNewConnectionsPerPolicyTCP						INTEGER,
	rsConcurConnectionsPerPolicyTCP						INTEGER,
	rsDroppedPacketsPerPolicyTCP						Counter64,
	rsDroppedBytesPerPolicyTCP							Counter64,
	rsReceivedPacketsPerPolicyTCP						Counter64,
	rsReceivedBytesPerPolicyTCP							Counter64
}
rsPolicyNamePerPolicyTCP OBJECT-TYPE
   SYNTAX DisplayString
   ACCESS  read-write
   STATUS  mandatory
   DESCRIPTION
       "Policy name for traffic monitoring utilization table."
   ::= {rsTrafficUtilizationPerPolicyEntryTCP 1}

rsNewConnectionsPerPolicyTCP OBJECT-TYPE
   SYNTAX INTEGER
   ACCESS  read-only
   STATUS  mandatory
   DESCRIPTION
       "New connections per policy."
   ::= {rsTrafficUtilizationPerPolicyEntryTCP 2}

rsConcurConnectionsPerPolicyTCP OBJECT-TYPE
   SYNTAX INTEGER
   ACCESS  read-only
   STATUS  mandatory
   DESCRIPTION
       "Reserved for Concurrent connections per policy TCP."
   ::= {rsTrafficUtilizationPerPolicyEntryTCP 3}

rsDroppedPacketsPerPolicyTCP OBJECT-TYPE
   SYNTAX Counter64
   ACCESS  read-only
   STATUS  mandatory
   DESCRIPTION
       "Concurrent dropped Packets per policy and protocol."
   ::= {rsTrafficUtilizationPerPolicyEntryTCP 4}

rsDroppedBytesPerPolicyTCP OBJECT-TYPE
   SYNTAX Counter64
   ACCESS  read-only
   STATUS  mandatory
   DESCRIPTION
       "Concurrent dropped Bytes per policy and protocol."
   ::= {rsTrafficUtilizationPerPolicyEntryTCP 5}

rsReceivedPacketsPerPolicyTCP OBJECT-TYPE
   SYNTAX Counter64
   ACCESS  read-only
   STATUS  mandatory
   DESCRIPTION
       "Concurrent received Packets per policy and protocol."
   ::= {rsTrafficUtilizationPerPolicyEntryTCP 6}

rsReceivedBytesPerPolicyTCP OBJECT-TYPE
   SYNTAX Counter64
   ACCESS  read-only
   STATUS  mandatory
   DESCRIPTION
       "Concurrent received Bytes per policy and protocol."
   ::= {rsTrafficUtilizationPerPolicyEntryTCP 7}

rsTrafficUtilizationPerPolicyTableICMP 	OBJECT-TYPE
	SYNTAX SEQUENCE OF RsTrafficUtilizationPerPolicyEntryICMP
	ACCESS  not-accessible
    STATUS  mandatory
    DESCRIPTION
        "A table of Traffic Utilization Per Policy."
    ::= {rsTrafficUtilizationPerPolicy 3}

rsTrafficUtilizationPerPolicyEntryICMP OBJECT-TYPE
	SYNTAX RsTrafficUtilizationPerPolicyEntryICMP
	ACCESS not-accessible
	STATUS mandatory
	DESCRIPTION
	"An entry of the traffic utilization per Policy and Protocol."
	INDEX {rsPolicyNamePerPolicyICMP}
	::= { rsTrafficUtilizationPerPolicyTableICMP 1}
RsTrafficUtilizationPerPolicyEntryICMP ::= SEQUENCE {
	rsPolicyNamePerPolicyICMP								DisplayString,
	rsNewConnectionsPerPolicyICMP							INTEGER,
	rsConcurConnectionsPerPolicyICMP						INTEGER,
	rsDroppedPacketsPerPolicyICMP							Counter64,
	rsDroppedBytesPerPolicyICMP								Counter64,
	rsReceivedPacketsPerPolicyICMP							Counter64,
	rsReceivedBytesPerPolicyICMP							Counter64
}
rsPolicyNamePerPolicyICMP OBJECT-TYPE
   SYNTAX DisplayString
   ACCESS  read-write
   STATUS  mandatory
   DESCRIPTION
       "Policy name for traffic monitoring utilization table."
   ::= {rsTrafficUtilizationPerPolicyEntryICMP 1}

rsNewConnectionsPerPolicyICMP OBJECT-TYPE
   SYNTAX INTEGER
   ACCESS  read-only
   STATUS  mandatory
   DESCRIPTION
       "New connections per policy."
   ::= {rsTrafficUtilizationPerPolicyEntryICMP 2}

rsConcurConnectionsPerPolicyICMP OBJECT-TYPE
   SYNTAX INTEGER
   ACCESS  read-only
   STATUS  mandatory
   DESCRIPTION
       "Reserved for Concurrent connections per policy ICMP."
   ::= {rsTrafficUtilizationPerPolicyEntryICMP 3}


rsDroppedPacketsPerPolicyICMP OBJECT-TYPE
   SYNTAX Counter64
   ACCESS  read-only
   STATUS  mandatory
   DESCRIPTION
       "Concurrent dropped Packets per policy and protocol."
   ::= {rsTrafficUtilizationPerPolicyEntryICMP 4}

rsDroppedBytesPerPolicyICMP OBJECT-TYPE
   SYNTAX Counter64
   ACCESS  read-only
   STATUS  mandatory
   DESCRIPTION
       "Concurrent dropped Bytes per policy and protocol."
   ::= {rsTrafficUtilizationPerPolicyEntryICMP 5}

rsReceivedPacketsPerPolicyICMP OBJECT-TYPE
   SYNTAX Counter64
   ACCESS  read-only
   STATUS  mandatory
   DESCRIPTION
       "Concurrent received Packets per policy and protocol."
   ::= {rsTrafficUtilizationPerPolicyEntryICMP 6}

rsReceivedBytesPerPolicyICMP OBJECT-TYPE
   SYNTAX Counter64
   ACCESS  read-only
   STATUS  mandatory
   DESCRIPTION
       "Concurrent received Bytes per policy and protocol."
   ::= {rsTrafficUtilizationPerPolicyEntryICMP 7}

rsTrafficUtilizationPerPolicyTableOTHER 	OBJECT-TYPE
	SYNTAX SEQUENCE OF RsTrafficUtilizationPerPolicyEntryOTHER
	ACCESS  not-accessible
    STATUS  mandatory
    DESCRIPTION
        "A table of Traffic Utilization Per Policy."
    ::= {rsTrafficUtilizationPerPolicy 4}

rsTrafficUtilizationPerPolicyEntryOTHER OBJECT-TYPE
	SYNTAX RsTrafficUtilizationPerPolicyEntryOTHER
	ACCESS not-accessible
	STATUS mandatory
	DESCRIPTION
	"An entry of the traffic utilization per Policy and Protocol."
	INDEX {rsPolicyNamePerPolicyOTHER}
	::= { rsTrafficUtilizationPerPolicyTableOTHER 1}

RsTrafficUtilizationPerPolicyEntryOTHER ::= SEQUENCE {
	rsPolicyNamePerPolicyOTHER							DisplayString,
	rsNewConnectionsPerPolicyOTHER						INTEGER,
	rsConcurConnectionsPerPolicyOTHER					INTEGER,
	rsDroppedPacketsPerPolicyOTHER						Counter64,
	rsDroppedBytesPerPolicyOTHER						Counter64,
	rsReceivedPacketsPerPolicyOTHER						Counter64,
	rsReceivedBytesPerPolicyOTHER						Counter64
}
rsPolicyNamePerPolicyOTHER OBJECT-TYPE
   SYNTAX DisplayString
   ACCESS  read-write
   STATUS  mandatory
   DESCRIPTION
       "Policy name for traffic monitoring utilization table."
   ::= {rsTrafficUtilizationPerPolicyEntryOTHER 1}

rsNewConnectionsPerPolicyOTHER OBJECT-TYPE
   SYNTAX INTEGER
   ACCESS  read-only
   STATUS  mandatory
   DESCRIPTION
       "New connections per policy."
   ::= {rsTrafficUtilizationPerPolicyEntryOTHER 2}

rsConcurConnectionsPerPolicyOTHER OBJECT-TYPE
   SYNTAX INTEGER
   ACCESS  read-only
   STATUS  mandatory
   DESCRIPTION
       "Reserved for Concurrent connections per policy OTHER."
   ::= {rsTrafficUtilizationPerPolicyEntryOTHER 3}

rsDroppedPacketsPerPolicyOTHER OBJECT-TYPE
   SYNTAX Counter64
   ACCESS  read-only
   STATUS  mandatory
   DESCRIPTION
       "Concurrent dropped Packets per policy and protocol."
   ::= {rsTrafficUtilizationPerPolicyEntryOTHER 4}

rsDroppedBytesPerPolicyOTHER OBJECT-TYPE
   SYNTAX Counter64
   ACCESS  read-only
   STATUS  mandatory
   DESCRIPTION
       "Concurrent dropped Bytes per policy and protocol."
   ::= {rsTrafficUtilizationPerPolicyEntryOTHER 5}

rsReceivedPacketsPerPolicyOTHER OBJECT-TYPE
   SYNTAX Counter64
   ACCESS  read-only
   STATUS  mandatory
   DESCRIPTION
       "Concurrent received Packets per policy and protocol."
   ::= {rsTrafficUtilizationPerPolicyEntryOTHER 6}

rsReceivedBytesPerPolicyOTHER OBJECT-TYPE
   SYNTAX Counter64
   ACCESS  read-only
   STATUS  mandatory
   DESCRIPTION
       "Concurrent received Bytes per policy and protocol."
   ::= {rsTrafficUtilizationPerPolicyEntryOTHER 7}

rsTrafficUtilizationPerPolicyTableSCTP 	OBJECT-TYPE
	SYNTAX SEQUENCE OF RsTrafficUtilizationPerPolicyEntrySCTP
	ACCESS  not-accessible
    STATUS  mandatory
    DESCRIPTION
        "A table of Traffic Utilization Per Policy."
    ::= {rsTrafficUtilizationPerPolicy 5}

rsTrafficUtilizationPerPolicyEntrySCTP OBJECT-TYPE
	SYNTAX RsTrafficUtilizationPerPolicyEntrySCTP
	ACCESS not-accessible
	STATUS mandatory
	DESCRIPTION
	"An entry of the traffic utilization per Policy and Protocol."
	INDEX {rsPolicyNamePerPolicySCTP}
	::= { rsTrafficUtilizationPerPolicyTableSCTP 1}

RsTrafficUtilizationPerPolicyEntrySCTP ::= SEQUENCE {
	rsPolicyNamePerPolicySCTP							DisplayString,
	rsNewConnectionsPerPolicySCTP						INTEGER,
	rsConcurConnectionsPerPolicySCTP					INTEGER,
	rsDroppedPacketsPerPolicySCTP						Counter64,
	rsDroppedBytesPerPolicySCTP							Counter64,
	rsReceivedPacketsPerPolicySCTP						Counter64,
	rsReceivedBytesPerPolicySCTP						Counter64
}
rsPolicyNamePerPolicySCTP OBJECT-TYPE
   SYNTAX DisplayString
   ACCESS  read-write
   STATUS  mandatory
   DESCRIPTION
       "Policy name for traffic monitoring utilization table."
   ::= {rsTrafficUtilizationPerPolicyEntrySCTP 1}

rsNewConnectionsPerPolicySCTP OBJECT-TYPE
   SYNTAX INTEGER
   ACCESS  read-only
   STATUS  mandatory
   DESCRIPTION
       "New connections per policy."
   ::= {rsTrafficUtilizationPerPolicyEntrySCTP 2}

rsConcurConnectionsPerPolicySCTP OBJECT-TYPE
   SYNTAX INTEGER
   ACCESS  read-only
   STATUS  mandatory
   DESCRIPTION
       "Reserved for Concurrent connections per policy SCTP."
   ::= {rsTrafficUtilizationPerPolicyEntrySCTP 3}

rsDroppedPacketsPerPolicySCTP OBJECT-TYPE
   SYNTAX Counter64
   ACCESS  read-only
   STATUS  mandatory
   DESCRIPTION
       "Concurrent dropped Packets per policy and protocol."
   ::= {rsTrafficUtilizationPerPolicyEntrySCTP 4}

rsDroppedBytesPerPolicySCTP OBJECT-TYPE
   SYNTAX Counter64
   ACCESS  read-only
   STATUS  mandatory
   DESCRIPTION
       "Concurrent dropped Bytes per policy and protocol."
   ::= {rsTrafficUtilizationPerPolicyEntrySCTP 5}

rsReceivedPacketsPerPolicySCTP OBJECT-TYPE
   SYNTAX Counter64
   ACCESS  read-only
   STATUS  mandatory
   DESCRIPTION
       "Concurrent received Packets per policy and protocol."
   ::= {rsTrafficUtilizationPerPolicyEntrySCTP 6}

rsReceivedBytesPerPolicySCTP OBJECT-TYPE
   SYNTAX Counter64
   ACCESS  read-only
   STATUS  mandatory
   DESCRIPTION
       "Concurrent received Bytes per policy and protocol."
   ::= {rsTrafficUtilizationPerPolicyEntrySCTP 7}

rsTrafficUtilizationPerPolicyTableIGMP 	OBJECT-TYPE
	SYNTAX SEQUENCE OF RsTrafficUtilizationPerPolicyEntryIGMP
	ACCESS  not-accessible
    STATUS  mandatory
    DESCRIPTION
        "A table of Traffic Utilization Per Policy."
    ::= {rsTrafficUtilizationPerPolicy 6}

rsTrafficUtilizationPerPolicyEntryIGMP OBJECT-TYPE
	SYNTAX RsTrafficUtilizationPerPolicyEntryIGMP
	ACCESS not-accessible
	STATUS mandatory
	DESCRIPTION
	"An entry of the traffic utilization per Policy and Protocol."
	INDEX {rsPolicyNamePerPolicyIGMP}
	::= { rsTrafficUtilizationPerPolicyTableIGMP 1}

RsTrafficUtilizationPerPolicyEntryIGMP ::= SEQUENCE {
	rsPolicyNamePerPolicyIGMP							DisplayString,
	rsNewConnectionsPerPolicyIGMP						INTEGER,
	rsConcurConnectionsPerPolicyIGMP					INTEGER,
	rsDroppedPacketsPerPolicyIGMP						Counter64,
	rsDroppedBytesPerPolicyIGMP							Counter64,
	rsReceivedPacketsPerPolicyIGMP						Counter64,
	rsReceivedBytesPerPolicyIGMP						Counter64
}
rsPolicyNamePerPolicyIGMP OBJECT-TYPE
   SYNTAX DisplayString
   ACCESS  read-write
   STATUS  mandatory
   DESCRIPTION
       "Policy name for traffic monitoring utilization table."
   ::= {rsTrafficUtilizationPerPolicyEntryIGMP 1}

rsNewConnectionsPerPolicyIGMP OBJECT-TYPE
   SYNTAX INTEGER
   ACCESS  read-only
   STATUS  mandatory
   DESCRIPTION
       "New connections per policy."
   ::= {rsTrafficUtilizationPerPolicyEntryIGMP 2}

rsConcurConnectionsPerPolicyIGMP OBJECT-TYPE
   SYNTAX INTEGER
   ACCESS  read-only
   STATUS  mandatory
   DESCRIPTION
       "Reserved for Concurrent connections per policy IGMP."
   ::= {rsTrafficUtilizationPerPolicyEntryIGMP 3}

rsDroppedPacketsPerPolicyIGMP OBJECT-TYPE
   SYNTAX Counter64
   ACCESS  read-only
   STATUS  mandatory
   DESCRIPTION
       "Concurrent dropped Packets per policy and protocol."
   ::= {rsTrafficUtilizationPerPolicyEntryIGMP 4}

rsDroppedBytesPerPolicyIGMP OBJECT-TYPE
   SYNTAX Counter64
   ACCESS  read-only
   STATUS  mandatory
   DESCRIPTION
       "Concurrent dropped Bytes per policy and protocol."
   ::= {rsTrafficUtilizationPerPolicyEntryIGMP 5}

rsReceivedPacketsPerPolicyIGMP OBJECT-TYPE
   SYNTAX Counter64
   ACCESS  read-only
   STATUS  mandatory
   DESCRIPTION
       "Concurrent received Packets per policy and protocol."
   ::= {rsTrafficUtilizationPerPolicyEntryIGMP 6}

rsReceivedBytesPerPolicyIGMP OBJECT-TYPE
   SYNTAX Counter64
   ACCESS  read-only
   STATUS  mandatory
   DESCRIPTION
       "Concurrent received Bytes per policy and protocol."
   ::= {rsTrafficUtilizationPerPolicyEntryIGMP 7}

   rsHTTPFReportsContinuousLearningStatisticsTable OBJECT-TYPE
    SYNTAX SEQUENCE OF RsHTTPFReportsContinuousLearningStatisticsEntry
    ACCESS not-accessible
    STATUS  mandatory
    DESCRIPTION
      "Table containing the Continuous Learning Statistics Table"
    ::=  {rsHttpFlood 83}
rsHTTPFReportsContinuousLearningStatisticsEntry OBJECT-TYPE
    SYNTAX RsHTTPFReportsContinuousLearningStatisticsEntry
    ACCESS not-accessible
    STATUS  mandatory
    DESCRIPTION
       "The row definition for this table."
    INDEX { rsHTTPFReportsContinuousLearningStatisticsServerName }
    ::=  { rsHTTPFReportsContinuousLearningStatisticsTable 1 }
RsHTTPFReportsContinuousLearningStatisticsEntry ::= SEQUENCE {
    rsHTTPFReportsContinuousLearningStatisticsServerName 					DisplayString,
	rsHTTPFReportsContinuousLearningStatisticsGETAndPOSTRequestsRate 		INTEGER,
    rsHTTPFReportsContinuousLearningStatisticsOtherRequestsRate				INTEGER,
    rsHTTPFReportsContinuousLearningStatisticsRequestsRatePerSource 		INTEGER,
	rsHTTPFReportsContinuousLearningStatisticsRequestsRatePerConn		    INTEGER,
    rsHTTPFReportsContinuousLearningStatisticsOutboundBandwidthKbps			INTEGER
}
rsHTTPFReportsContinuousLearningStatisticsServerName OBJECT-TYPE
    SYNTAX DisplayString (SIZE(1..30))
    ACCESS read-only
    STATUS mandatory
    DESCRIPTION
      "Server Name."
    ::=  { rsHTTPFReportsContinuousLearningStatisticsEntry 1 }
rsHTTPFReportsContinuousLearningStatisticsGETAndPOSTRequestsRate OBJECT-TYPE
    SYNTAX INTEGER
    ACCESS  read-only
    STATUS  mandatory
    DESCRIPTION
        "GET and POST Requests Rate."
    ::= {rsHTTPFReportsContinuousLearningStatisticsEntry  2}
rsHTTPFReportsContinuousLearningStatisticsOtherRequestsRate OBJECT-TYPE
    SYNTAX INTEGER
    ACCESS  read-only
    STATUS  mandatory
    DESCRIPTION
        "Other Requests Rate."
    ::= {rsHTTPFReportsContinuousLearningStatisticsEntry  3}
rsHTTPFReportsContinuousLearningStatisticsRequestsRatePerSource OBJECT-TYPE
    SYNTAX INTEGER
    ACCESS  read-only
    STATUS  mandatory
    DESCRIPTION
        "Requests Rate Per Source."
    ::= {rsHTTPFReportsContinuousLearningStatisticsEntry  4}
rsHTTPFReportsContinuousLearningStatisticsRequestsRatePerConn OBJECT-TYPE
    SYNTAX INTEGER
    ACCESS  read-only
    STATUS  mandatory
    DESCRIPTION
        "Requests Rate Per Connection."
    ::= {rsHTTPFReportsContinuousLearningStatisticsEntry  5}
rsHTTPFReportsContinuousLearningStatisticsOutboundBandwidthKbps OBJECT-TYPE
    SYNTAX INTEGER
    ACCESS  read-only
    STATUS  mandatory
    DESCRIPTION
        "Outbound Bandwidth."
    ::= {rsHTTPFReportsContinuousLearningStatisticsEntry  6}

rsServiceDiscovery OBJECT IDENTIFIER ::= { rsIDS 175}

rsServiceDiscoveryGlobalStatus OBJECT-TYPE
    SYNTAX INTEGER {
			enable(1),
			disable(2)}
    ACCESS  read-write
    STATUS  mandatory
    DESCRIPTION
       "This variable indicates the status of service discovery mechanism"
	DEFVAL  {enable}
    ::= {rsServiceDiscovery 1}

rsServiceDiscoveryGlobalTrackingTime OBJECT-TYPE
    SYNTAX INTEGER (1..60)
    ACCESS  read-write
    STATUS  mandatory
    DESCRIPTION
        "Tracking Time in Minutes."
	DEFVAL { 5 }
    ::= {rsServiceDiscovery 2}

rsServiceDiscoveryGlobalReValidTime OBJECT-TYPE
    SYNTAX INTEGER (0..365)
    ACCESS  read-write
    STATUS  mandatory
    DESCRIPTION
        "Re-Evaluation time in days."
	DEFVAL { 7 }
    ::= {rsServiceDiscovery 3}


rsServiceDiscoveryProfileTable OBJECT-TYPE
    SYNTAX SEQUENCE OF RsServiceDiscoveryProfileEntry
    ACCESS not-accessible
    STATUS  mandatory
    DESCRIPTION
      "Table containing service discovery profile parameters"
    ::=  {rsServiceDiscovery 4}


rsServiceDiscoveryProfileEntry OBJECT-TYPE
    SYNTAX RsServiceDiscoveryProfileEntry
    ACCESS not-accessible
    STATUS  mandatory
    DESCRIPTION
       "The row definition for this table."
    INDEX { rsServiceDiscoveryProfileName }
    ::=  { rsServiceDiscoveryProfileTable 1 }

RsServiceDiscoveryProfileEntry ::= SEQUENCE {
	rsServiceDiscoveryProfileName DisplayString,
	rsServiceDiscoveryHTTPProfileName DisplayString,
	rsServiceDiscoveryResponseRate	INTEGER,
	rsServiceDiscoveryAutoRemoval	INTEGER,
	rsServiceDiscoveryProfileStatus RowStatus
}

rsServiceDiscoveryProfileName OBJECT-TYPE
    SYNTAX DisplayString (SIZE(1..30))
    ACCESS read-write
    STATUS mandatory
    DESCRIPTION
      "Service discovery profile name."
    ::=  { rsServiceDiscoveryProfileEntry 1 }

rsServiceDiscoveryHTTPProfileName OBJECT-TYPE
    SYNTAX DisplayString (SIZE(0..30))
    ACCESS read-write
    STATUS mandatory
    DESCRIPTION
      "Service discovery HTTP profile name."
    ::=  { rsServiceDiscoveryProfileEntry 2 }

rsServiceDiscoveryResponseRate OBJECT-TYPE
    SYNTAX INTEGER (1..5000)
    ACCESS  read-write
    STATUS  mandatory
    DESCRIPTION
        "Response Rate Threshold."
	DEFVAL { 100 }
    ::= {rsServiceDiscoveryProfileEntry 3}

rsServiceDiscoveryAutoRemoval OBJECT-TYPE
    SYNTAX INTEGER {
              yes(1),
			  no(2)}
    ACCESS  read-write
    STATUS  mandatory
    DESCRIPTION
       "Automatic removal of hosts status."
    DEFVAL { 1 }
    ::=  { rsServiceDiscoveryProfileEntry 4 }

rsServiceDiscoveryProfileStatus OBJECT-TYPE
    SYNTAX RowStatus
    ACCESS  read-write
    STATUS  mandatory
    DESCRIPTION
       "This variable indicates the administrative status of this entry. Used to delete an entry of this table."
	DEFVAL{1}
    ::=  { rsServiceDiscoveryProfileEntry 5 }



rsIdsDeployment OBJECT IDENTIFIER ::= { rsIDS 176}

rsIdsDeploymentBackToDefault OBJECT-TYPE
    SYNTAX  INTEGER {
       defaultCP(1)
     }
    ACCESS  read-write
    STATUS  mandatory
    DESCRIPTION
      "This variable enables the operator to perform back-to-defaults
      operation on the device, depending on its current deployment."
   ::= { rsIdsDeployment 1  }


rsSslMitigation OBJECT IDENTIFIER ::= { rsIDS 177 }

rsSSLMitigationGlobalStatus OBJECT-TYPE
	SYNTAX INTEGER {
			disable(0),
			external(1),
            on-device(2)}
    ACCESS  read-write
    STATUS  mandatory
    DESCRIPTION
      "The SSL mitigation status"
	 DEFVAL  {disable}
    ::=  {rsSslMitigation 1}

rsProtectedSslObjTable OBJECT-TYPE
    SYNTAX SEQUENCE OF RsProtectedSslObjEntry
    ACCESS not-accessible
    STATUS  mandatory
    DESCRIPTION
      "Table containing the parameters that are needed to detect intrusions"
    ::=  {rsSslMitigation 2 }


rsProtectedSslObjEntry OBJECT-TYPE
   SYNTAX RsProtectedSslObjEntry
   ACCESS not-accessible
   STATUS  mandatory
   DESCRIPTION
      "The row definition for this table."
   INDEX { rsProtectedObjName }
   ::=  { rsProtectedSslObjTable 1 }


RsProtectedSslObjEntry ::= SEQUENCE {
   rsProtectedObjName      DisplayString,
   rsProtectedObjEnable     		        INTEGER,
   rsProtectedObjIpAddr    			Ipv6Address,
   rsProtectedObjApplPort			INTEGER,
   rsProtectedObjAddCertificate			DisplayString,
   rsProtectedObjRemoveCertificate	        DisplayString,
   rsProtectedObjDefaultSNICertificate	        DisplayString,
   rsProtectedObjSSLV3Enable			INTEGER,
   rsProtectedObjTLS10Enable			INTEGER,
   rsProtectedObjTLS11Enable			INTEGER,
   rsProtectedObjTLS12Enable			INTEGER,
   rsProtectedObjCipherSuiteSystemEnable	INTEGER,
   rsProtectedObjUserCipher	        	DisplayString,
   rsProtectedObjRowStatus    			RowStatus
}

rsProtectedObjName OBJECT-TYPE
   SYNTAX DisplayString (SIZE(1..60))
   ACCESS  read-only
   STATUS  mandatory
   DESCRIPTION
     "The Name for the protected SSL object"
   ::=  {rsProtectedSslObjEntry 1}


rsProtectedObjEnable OBJECT-TYPE
   SYNTAX INTEGER {
             enable(1),
             disable(2) }
   ACCESS  read-write
   STATUS  mandatory
   DESCRIPTION
      "Protected SSL object enable(can send traffic) /disable."
   DEFVAL { 2 }
   ::=  {rsProtectedSslObjEntry 2}

rsProtectedObjIpAddr OBJECT-TYPE
    SYNTAX  Ipv6Address
   ACCESS  read-write
   STATUS  mandatory
   DESCRIPTION
            "The IP address of the protected SSL object."
   ::=  {rsProtectedSslObjEntry 3}


rsProtectedObjApplPort OBJECT-TYPE
   SYNTAX INTEGER
   ACCESS  read-write
   STATUS  mandatory
   DESCRIPTION
      "The application port of  the protected SSL object. default 443"
      DEFVAL { 443 }
   ::=  {rsProtectedSslObjEntry 4}

rsProtectedObjAddCertificate OBJECT-TYPE
   SYNTAX DisplayString (SIZE(0..64))
   ACCESS  read-write
   STATUS  mandatory
   DESCRIPTION
     "The server certificate to be added to the protected SSL object, on get it's 0."
   ::=  {rsProtectedSslObjEntry 5}

rsProtectedObjRemoveCertificate OBJECT-TYPE
   SYNTAX DisplayString (SIZE(0..64))
   ACCESS  read-write
   STATUS  mandatory
   DESCRIPTION
     "The server certificate to be removed from the protected SSL object, on get it's 0"
   ::=  {rsProtectedSslObjEntry 6}

rsProtectedObjDefaultSNICertificate OBJECT-TYPE
   SYNTAX DisplayString (SIZE(0..64))
   ACCESS  read-write
   STATUS  mandatory
   DESCRIPTION
     "The default server SNI certificate."
   ::=  {rsProtectedSslObjEntry 7}

rsProtectedObjSSLV3Enable   OBJECT-TYPE
   SYNTAX INTEGER {
             enable(1),
             disable(2) }
   ACCESS  read-write
   STATUS  mandatory
   DESCRIPTION
      "SSLV3 enable/disable."
   DEFVAL { 2 }
   ::=  {rsProtectedSslObjEntry 8}

rsProtectedObjTLS10Enable OBJECT-TYPE
   SYNTAX INTEGER {
             enable(1),
             disable(2) }
   ACCESS  read-write
   STATUS  mandatory
   DESCRIPTION
      "TLS 1.0 enable/disable."
   DEFVAL { 2 }
   ::=  {rsProtectedSslObjEntry 9}

rsProtectedObjTLS11Enable OBJECT-TYPE
   SYNTAX INTEGER {
             enable(1),
             disable(2) }
   ACCESS  read-write
   STATUS  mandatory
   DESCRIPTION
      "TLS 1.1 enable/disable."
   DEFVAL { 1 }
   ::=  {rsProtectedSslObjEntry 10}

rsProtectedObjTLS12Enable OBJECT-TYPE
   SYNTAX INTEGER {
             enable(1),
             disable(2) }
   ACCESS  read-write
   STATUS  mandatory
   DESCRIPTION
      "TLS 1.2 enable/disable."
   DEFVAL { 1 }
   ::=  {rsProtectedSslObjEntry 11}

rsProtectedObjCipherSuiteSystemEnable OBJECT-TYPE
   SYNTAX INTEGER {
             system(1),
             user(2) }
   ACCESS  read-write
   STATUS  mandatory
   DESCRIPTION
      "cipher suite system or user."
   DEFVAL { 1 }
   ::=  {rsProtectedSslObjEntry 12}

rsProtectedObjUserCipher OBJECT-TYPE
   SYNTAX DisplayString (SIZE(0..255))
   ACCESS  read-write
   STATUS  mandatory
   DESCRIPTION
     "The user cipher."
   ::=  {rsProtectedSslObjEntry 13}

rsProtectedObjRowStatus OBJECT-TYPE
    SYNTAX RowStatus
    ACCESS  read-write
    STATUS  mandatory
    DESCRIPTION
       "This variable indicates the administrative status of this entry. Used to delete/add/modify an entry of this table."
	DEFVAL{1}
    ::=  { rsProtectedSslObjEntry 14 }

--Protected Objects Certificates association Table (alphanumeric key indexed)
rsProtectedSslObjCertificatesTable OBJECT-TYPE
    SYNTAX  SEQUENCE OF RsProtectedSslObjCertificatesEntry
    ACCESS not-accessible
    STATUS  mandatory
    DESCRIPTION
        "The table of certificates per group."
    ::= { rsSslMitigation 3 }

rsProtectedSslObjCertificatesEntry OBJECT-TYPE
    SYNTAX  RsProtectedSslObjCertificatesEntry
    ACCESS not-accessible
    STATUS  mandatory
    DESCRIPTION
        "A row in the Certificates Protected Object table."
    INDEX   { rsProtectedSslObjName,rsCertificatesName}
    ::= { rsProtectedSslObjCertificatesTable 1 }

RsProtectedSslObjCertificatesEntry ::= SEQUENCE {
    rsProtectedSslObjName         DisplayString,
    rsCertificatesName        	  DisplayString,
    rsCertificatesDefault         INTEGER,
    rsCertificatesRowStatus         RowStatus
    }

rsProtectedSslObjName OBJECT-TYPE
    SYNTAX DisplayString (SIZE(1..60))
    ACCESS  read-only
    STATUS  mandatory
    DESCRIPTION
        "The protected object name."
    ::= { rsProtectedSslObjCertificatesEntry 1 }

rsCertificatesName OBJECT-TYPE
    SYNTAX DisplayString (SIZE(0..64))
    ACCESS  read-only
    STATUS  mandatory
    DESCRIPTION
        "The certificates  friendly name."
    ::= { rsProtectedSslObjCertificatesEntry 2 }

rsCertificatesDefault OBJECT-TYPE
   SYNTAX INTEGER {
             on(1),
             off(2) }
   ACCESS  read-write
   STATUS  mandatory
   DESCRIPTION
      "Default certificate."
   DEFVAL { 2 }
   ::= { rsProtectedSslObjCertificatesEntry 3 }

rsCertificatesRowStatus OBJECT-TYPE
    SYNTAX RowStatus
    ACCESS  read-write
    STATUS  mandatory
    DESCRIPTION
       "This variable indicates the administrative status of this entry. Used to delete/add/modify an entry of this table."
	DEFVAL{1}
   ::= { rsProtectedSslObjCertificatesEntry 4 }

--Associated Protected Objects with Network Protection Policy
rsAssociatedProtectedSSLObjectTable OBJECT-TYPE
    SYNTAX  SEQUENCE OF RsAssociatedProtectedSSLObjectEntry
    ACCESS not-accessible
    STATUS  mandatory
    DESCRIPTION
        "The table of protected objects associated with a polciy."
    ::= { rsSslMitigation 4 }

rsAssociatedProtectedSSLObjectEntry OBJECT-TYPE
    SYNTAX  RsAssociatedProtectedSSLObjectEntry
    ACCESS not-accessible
    STATUS  mandatory
    DESCRIPTION
        "A row in the policy associated Protected Object table."
    INDEX   { rsAssociatedProtectedSslPolicy, rsAssociatedProtectedSslLine }
    ::= { rsAssociatedProtectedSSLObjectTable 1 }

RsAssociatedProtectedSSLObjectEntry ::= SEQUENCE {
    rsAssociatedProtectedSslPolicy          DisplayString,
    rsAssociatedProtectedSslLine            INTEGER,
    rsAssociatedProtectedSslObjName         DisplayString,
    rsAssociatedProtectedSslObjIpAddr    	Ipv6Address,
    rsAssociatedProtectedSslObjCertName     DisplayString,
    rsAssociatedProtectedSslObjSniStatus    INTEGER,
    rsAssociatedProtectedSslObjProtocol     DisplayString
    }

rsAssociatedProtectedSslPolicy OBJECT-TYPE
   SYNTAX DisplayString (SIZE(1..60))
   ACCESS  read-only
   STATUS  mandatory
   DESCRIPTION
     "The name of the policy"
   ::=  {rsAssociatedProtectedSSLObjectEntry 1}

rsAssociatedProtectedSslLine OBJECT-TYPE
    SYNTAX INTEGER
    ACCESS  read-only
    STATUS  mandatory
    DESCRIPTION
       "Protected object line #"
   ::=  {rsAssociatedProtectedSSLObjectEntry 2}

rsAssociatedProtectedSslObjName OBJECT-TYPE
   SYNTAX DisplayString (SIZE(1..60))
   ACCESS  read-only
   STATUS  mandatory
   DESCRIPTION
     "The name of the protected SSL object"
   ::=  {rsAssociatedProtectedSSLObjectEntry 3}

rsAssociatedProtectedSslObjIpAddr OBJECT-TYPE
    SYNTAX  Ipv6Address
   ACCESS  read-only
   STATUS  mandatory
   DESCRIPTION
            "The IP address of the protected SSL object."
   ::=  {rsAssociatedProtectedSSLObjectEntry 4}

rsAssociatedProtectedSslObjCertName OBJECT-TYPE
    SYNTAX DisplayString (SIZE(0..64))
    ACCESS  read-only
    STATUS  mandatory
    DESCRIPTION
        "The certificates friendly name."
   ::=  {rsAssociatedProtectedSSLObjectEntry 5}

rsAssociatedProtectedSslObjSniStatus OBJECT-TYPE
   SYNTAX INTEGER {
            on(1),
            off(2) }
   ACCESS  read-only
   STATUS  mandatory
   DESCRIPTION
      "Uses SNI."
   DEFVAL { 2 }
   ::=  {rsAssociatedProtectedSSLObjectEntry 6}

rsAssociatedProtectedSslObjProtocol OBJECT-TYPE
    SYNTAX DisplayString (SIZE(0..16))
    ACCESS  read-only
    STATUS  mandatory
    DESCRIPTION
        "The protected object protocol."
   ::=  {rsAssociatedProtectedSSLObjectEntry 7}

-- Signaling
--

rsSignaling OBJECT IDENTIFIER ::= { rsIDS 338 }

rsSignalingStatus OBJECT-TYPE
    SYNTAX INTEGER {
      enabled(1),
      disabled(2)
   }
    ACCESS read-write
    STATUS mandatory
	DESCRIPTION
      "Signaling status"
   DEFVAL  {disabled}
    ::=  {rsSignaling 1}

rsSignalingTable OBJECT-TYPE
    SYNTAX SEQUENCE OF RsSignalingPolicyEntry
    ACCESS not-accessible
    STATUS  mandatory
    DESCRIPTION
      "Table containing the signaling policies "
    ::=  {rsSignaling 2}

rsSignalingPolicyEntry OBJECT-TYPE
    SYNTAX RsSignalingPolicyEntry
    ACCESS not-accessible
    STATUS  mandatory
    DESCRIPTION
       "The row definition for this table."
    INDEX { rsSignalingPolicyId }
    ::=  { rsSignalingTable 1 }

RsSignalingPolicyEntry ::= SEQUENCE {
	rsSignalingPolicyId							INTEGER,
	rsSignalingPolicyRowStatus					RowStatus,
	rsSignalingPolicyStatus 					INTEGER,
    rsSignalingPolicyName						DisplayString,
	rsSignalingPolicySourceNwPoliciesAll		INTEGER,
    rsSignalingPolicySourceNwPolicyGroupId 		INTEGER,
	rsSignalingPolicySourceServersAll			INTEGER,
    rsSignalingPolicySourceServerGroupId 		INTEGER,
	rsSignalingPolicyMode						INTEGER,
	rsSignalingPolicyCustomerName				DisplayString,
	rsSignalingPolicyCustomerInformation		DisplayString,
	rsSignalingPolicyPipeSize					INTEGER,
	rsSignalingPolicyBdosCategory				INTEGER,
	rsSignalingPolicyDnsCategory				INTEGER,
	rsSignalingPolicyAntiscanCategory			INTEGER,
	rsSignalingPolicySigprotCategory			INTEGER,
	rsSignalingPolicyConlimitCategory			INTEGER,
	rsSignalingPolicySynfloodCategory			INTEGER,
	rsSignalingPolicyPpsCategory				INTEGER,
	rsSignalingPolicyHttpfloodCategory			INTEGER,
	rsSignalingPolicyCrackingCategory			INTEGER,
	rsSignalingPolicyOosCategory				INTEGER,
	rsSignalingPolicyAccessCategory				INTEGER,
	rsSignalingPolicySyslogServer				DisplayString
}

rsSignalingPolicyId OBJECT-TYPE
    SYNTAX INTEGER
    ACCESS  read-only
    STATUS  mandatory
    DESCRIPTION
       "Signaling Policy unique Id"
    ::=  { rsSignalingPolicyEntry 1 }

rsSignalingPolicyRowStatus OBJECT-TYPE
    SYNTAX RowStatus
    ACCESS  read-write
    STATUS  mandatory
    DESCRIPTION
       "This variable indicates the administrative status of this entry.
        Used to delete an entry of this table."
    ::=  { rsSignalingPolicyEntry 2 }

rsSignalingPolicyStatus  OBJECT-TYPE
    SYNTAX INTEGER {
		enabled(1),
		disabled(2)
	}
    ACCESS  read-write
    STATUS mandatory
    DESCRIPTION
      "Signaling Policy Enabled Status."
	DEFVAL  {enabled}
	::=  { rsSignalingPolicyEntry 3 }

rsSignalingPolicyName  OBJECT-TYPE
    SYNTAX DisplayString (SIZE(1..80))
    ACCESS  read-write
    STATUS mandatory
    DESCRIPTION
      "Signaling Policy Name."
    ::=  { rsSignalingPolicyEntry 4 }

rsSignalingPolicySourceNwPoliciesAll  OBJECT-TYPE
	SYNTAX INTEGER {
		for-all(1),
		specific(2)
    }
    ACCESS  read-write
    STATUS mandatory
    DESCRIPTION
      "Signaling Network Policies Source - FOR ALL indicator."
	DEFVAL  {for-all}
    ::=  { rsSignalingPolicyEntry 5 }

rsSignalingPolicySourceNwPolicyGroupId  OBJECT-TYPE
    SYNTAX INTEGER
    ACCESS  read-write
    STATUS mandatory
    DESCRIPTION
      "Signaling Network Policies Source Group Id."
    ::=  { rsSignalingPolicyEntry 6 }

rsSignalingPolicySourceServersAll  OBJECT-TYPE
	SYNTAX INTEGER {
		for-all(1),
		specific(2)
}
    ACCESS  read-write
    STATUS mandatory
    DESCRIPTION
      "Signaling Servers Source - FOR ALL indicator."
	DEFVAL  {for-all}
    ::=  { rsSignalingPolicyEntry 7 }

rsSignalingPolicySourceServerGroupId  OBJECT-TYPE
    SYNTAX INTEGER
    ACCESS  read-write
    STATUS mandatory
    DESCRIPTION
      "Signaling Servers Source Group Id."
    ::=  { rsSignalingPolicyEntry 8 }

rsSignalingPolicyMode  OBJECT-TYPE
    SYNTAX INTEGER {
		events-and-data(1),
		events-only(2)
	}
    ACCESS  read-write
    STATUS mandatory
    DESCRIPTION
      "Signaling Policy Mode."
	DEFVAL  {events-and-data}
	::=  { rsSignalingPolicyEntry 9 }

rsSignalingPolicyCustomerName  OBJECT-TYPE
    SYNTAX DisplayString (SIZE(1..32))
    ACCESS  read-write
    STATUS mandatory
    DESCRIPTION
      "Signaling Policy Customer Name."
    ::=  { rsSignalingPolicyEntry 10 }

rsSignalingPolicyCustomerInformation  OBJECT-TYPE
    SYNTAX DisplayString (SIZE(1..100))
    ACCESS  read-write
    STATUS mandatory
    DESCRIPTION
      "Signaling Policy Customer Information."
    ::=  { rsSignalingPolicyEntry 11 }

rsSignalingPolicyPipeSize  OBJECT-TYPE
    SYNTAX INTEGER
    ACCESS  read-write
    STATUS mandatory
    DESCRIPTION
      "Signaling Source Pipe Size."
    ::=  { rsSignalingPolicyEntry 12 }

rsSignalingPolicyBdosCategory  OBJECT-TYPE
    SYNTAX INTEGER {
		enabled(1),
		disabled(2)
	}
    ACCESS  read-write
    STATUS mandatory
    DESCRIPTION
      "Signaling Policy BDoS Category Indicator."
	DEFVAL  {enabled}
	::=  { rsSignalingPolicyEntry 13 }

rsSignalingPolicyDnsCategory  OBJECT-TYPE
    SYNTAX INTEGER {
		enabled(1),
		disabled(2)
	}
    ACCESS  read-write
    STATUS mandatory
    DESCRIPTION
      "Signaling Policy DNS Category Indicator."
	DEFVAL  {enabled}
	::=  { rsSignalingPolicyEntry 14 }

rsSignalingPolicyAntiscanCategory  OBJECT-TYPE
    SYNTAX INTEGER {
		enabled(1),
		disabled(2)
	}
    ACCESS  read-write
    STATUS mandatory
    DESCRIPTION
      "Signaling Policy Anti Scan Category Indicator."
	DEFVAL  {enabled}
	::=  { rsSignalingPolicyEntry 15 }

rsSignalingPolicySigprotCategory  OBJECT-TYPE
    SYNTAX INTEGER {
		enabled(1),
		disabled(2)
	}
    ACCESS  read-write
    STATUS mandatory
    DESCRIPTION
      "Signaling Policy Signature Protection Category Indicator."
	DEFVAL  {enabled}
	::=  { rsSignalingPolicyEntry 16 }

rsSignalingPolicyConlimitCategory  OBJECT-TYPE
    SYNTAX INTEGER {
		enabled(1),
		disabled(2)
	}
    ACCESS  read-write
    STATUS mandatory
    DESCRIPTION
      "Signaling Policy Connection Limit Category Indicator."
	DEFVAL  {enabled}
	::=  { rsSignalingPolicyEntry 17 }

rsSignalingPolicySynfloodCategory  OBJECT-TYPE
    SYNTAX INTEGER {
		enabled(1),
		disabled(2)
	}
    ACCESS  read-write
    STATUS mandatory
    DESCRIPTION
      "Signaling Policy SYN Flood Category Indicator."
	DEFVAL  {enabled}
	::=  { rsSignalingPolicyEntry 18 }

rsSignalingPolicyPpsCategory  OBJECT-TYPE
    SYNTAX INTEGER {
		enabled(1),
		disabled(2)
	}
    ACCESS  read-write
    STATUS mandatory
    DESCRIPTION
      "Signaling Policy PPS Category Indicator."
	DEFVAL  {enabled}
	::=  { rsSignalingPolicyEntry 19 }

rsSignalingPolicyHttpfloodCategory  OBJECT-TYPE
    SYNTAX INTEGER {
		enabled(1),
		disabled(2)
	}
    ACCESS  read-write
    STATUS mandatory
    DESCRIPTION
      "Signaling Policy HTTP Flood Category Indicator."
	DEFVAL  {enabled}
	::=  { rsSignalingPolicyEntry 20 }

rsSignalingPolicyCrackingCategory  OBJECT-TYPE
    SYNTAX INTEGER {
		enabled(1),
		disabled(2)
	}
    ACCESS  read-write
    STATUS mandatory
    DESCRIPTION
      "Signaling Policy Cracking Category Indicator."
	DEFVAL  {enabled}
	::=  { rsSignalingPolicyEntry 21 }

rsSignalingPolicyOosCategory  OBJECT-TYPE
    SYNTAX INTEGER {
		enabled(1),
		disabled(2)
	}
    ACCESS  read-write
    STATUS mandatory
    DESCRIPTION
      "Signaling Policy OOS Category Indicator."
	DEFVAL  {enabled}
	::=  { rsSignalingPolicyEntry 22 }

rsSignalingPolicyAccessCategory  OBJECT-TYPE
    SYNTAX INTEGER {
		enabled(1),
		disabled(2)
	}
    ACCESS  read-write
    STATUS mandatory
    DESCRIPTION
      "Signaling Policy Access Category Indicator."
	DEFVAL  {enabled}
	::=  { rsSignalingPolicyEntry 23 }

rsSignalingPolicySyslogServer  OBJECT-TYPE
    SYNTAX DisplayString
    ACCESS  read-write
    STATUS mandatory
    DESCRIPTION
      "Signaling Policy Syslog Server."
	::=  { rsSignalingPolicyEntry 24 }

-- Signaling Reports : Total Traffic
--

rsSigReportTotalTrafficTable OBJECT-TYPE
    SYNTAX SEQUENCE OF RsSigReportTotalTrafficEntry
    ACCESS not-accessible
    STATUS  mandatory
    DESCRIPTION
      "Table containing the situational signal for Total Traffic report "
    ::=  {rsSignaling 4}

rsSigReportTotalTrafficEntry OBJECT-TYPE
    SYNTAX RsSigReportTotalTrafficEntry
    ACCESS not-accessible
    STATUS  mandatory
    DESCRIPTION
       "The row definition for this table."
	INDEX { rsSigReportTtlTrffcDeviceName	 }
    ::=  { rsSigReportTotalTrafficTable 1 }

RsSigReportTotalTrafficEntry ::= SEQUENCE {
	rsSigReportTtlTrffcDeviceName				DisplayString,
	rsSigReportPollingTimestamp					DisplayString,
	rsSigReportTtlTrffcCurrtBw					INTEGER,
	rsSigReportTtlTrffcAvrgBw					INTEGER,
	rsSigReportTtlTrffcAvrgDiscardBw			INTEGER,
	rsSigReportTtlTrffcCurrPackets				INTEGER,
    rsSigReportTtlTrffcAvrgPackets				INTEGER,
	rsSigReportTtlTrffcAvrgDiscardPackets		INTEGER,
	rsSigReportTtlTrffcCurrentCons				INTEGER,
	rsSigReportTtlTrffcAvrgCons					INTEGER
}

rsSigReportTtlTrffcDeviceName  OBJECT-TYPE
    SYNTAX DisplayString (SIZE(1..30))
    ACCESS  read-only
    STATUS mandatory
    DESCRIPTION
      "Network Device Name."
    ::=  { rsSigReportTotalTrafficEntry 1 }

rsSigReportPollingTimestamp  OBJECT-TYPE
    SYNTAX DisplayString (SIZE(1..30))
    ACCESS  read-only
    STATUS mandatory
    DESCRIPTION
      "Current Timestamp."
    ::=  { rsSigReportTotalTrafficEntry 2 }

rsSigReportTtlTrffcCurrtBw  OBJECT-TYPE
    SYNTAX INTEGER
    ACCESS  read-only
    STATUS mandatory
    DESCRIPTION
      "Curent BW."
    ::=  { rsSigReportTotalTrafficEntry 3 }

rsSigReportTtlTrffcAvrgBw  OBJECT-TYPE
    SYNTAX INTEGER
    ACCESS  read-only
    STATUS mandatory
    DESCRIPTION
      "Cumulative BW."
    ::=  { rsSigReportTotalTrafficEntry 4 }

rsSigReportTtlTrffcAvrgDiscardBw  OBJECT-TYPE
    SYNTAX INTEGER
    ACCESS  read-only
    STATUS mandatory
    DESCRIPTION
      "Discareded BW."
    ::=  { rsSigReportTotalTrafficEntry 5 }

rsSigReportTtlTrffcCurrPackets  OBJECT-TYPE
    SYNTAX INTEGER
    ACCESS  read-only
    STATUS mandatory
    DESCRIPTION
      "Current packets."
    ::=  { rsSigReportTotalTrafficEntry 6 }

rsSigReportTtlTrffcAvrgPackets  OBJECT-TYPE
    SYNTAX INTEGER
    ACCESS  read-only
    STATUS mandatory
    DESCRIPTION
      "Cumulative packets."
    ::=  { rsSigReportTotalTrafficEntry 7 }

rsSigReportTtlTrffcAvrgDiscardPackets  OBJECT-TYPE
    SYNTAX INTEGER
    ACCESS  read-only
    STATUS mandatory
    DESCRIPTION
      "Discarded packets."
    ::=  { rsSigReportTotalTrafficEntry 8 }

rsSigReportTtlTrffcCurrentCons  OBJECT-TYPE
    SYNTAX INTEGER
    ACCESS  read-only
    STATUS mandatory
    DESCRIPTION
      "Current connections."
    ::=  { rsSigReportTotalTrafficEntry 9 }

rsSigReportTtlTrffcAvrgCons  OBJECT-TYPE
    SYNTAX INTEGER
    ACCESS  read-only
    STATUS mandatory
    DESCRIPTION
      "Cumulative connections PPS."
    ::=  { rsSigReportTotalTrafficEntry 10 }

-- Signaling Reports : Total Utilizaition
--

rsSignalingTotalUtilTable OBJECT-TYPE
    SYNTAX SEQUENCE OF RsSignalingTotalUtilEntry
    ACCESS not-accessible
    STATUS  mandatory
    DESCRIPTION
      "Table containing System Utilization report."
    ::=  {rsSignaling 5}

rsSignalingTotalUtilEntry OBJECT-TYPE
    SYNTAX RsSignalingTotalUtilEntry
    ACCESS not-accessible
    STATUS  mandatory
    DESCRIPTION
       "The row definition for this table."
	INDEX { rsSignalingUtilTimestamp	 }
    ::=  { rsSignalingTotalUtilTable 1 }

RsSignalingTotalUtilEntry ::= SEQUENCE {
	rsSignalingUtilTimestamp				DisplayString,
	rsSignalingTotalUtil					INTEGER
}

rsSignalingUtilTimestamp  OBJECT-TYPE
    SYNTAX DisplayString (SIZE(1..30))
    ACCESS  read-only
    STATUS mandatory
    DESCRIPTION
      "Current Timestamp."
    ::=  { rsSignalingTotalUtilEntry 1 }

rsSignalingTotalUtil  OBJECT-TYPE
    SYNTAX INTEGER
    ACCESS  read-only
    STATUS mandatory
    DESCRIPTION
      "System Utilization"
    ::=  { rsSignalingTotalUtilEntry 2 }

-- Signaling Reports : BDoS Statistics
--

rsSignalingReportBdosTable OBJECT-TYPE
    SYNTAX SEQUENCE OF RsSignalingReportBdosEntry
    ACCESS not-accessible
    STATUS  mandatory
    DESCRIPTION
      "Table containing System BDoS statistics report."
    ::=  {rsSignaling 6}

rsSignalingReportBdosEntry OBJECT-TYPE
    SYNTAX RsSignalingReportBdosEntry
    ACCESS not-accessible
    STATUS  mandatory
    DESCRIPTION
       "The row definition for this table."
	INDEX { rsSigRprtBdosNwPolicyName	 }
    ::=  { rsSignalingReportBdosTable 1 }

RsSignalingReportBdosEntry ::= SEQUENCE {
	rsSigRprtBdosNwPolicyName			DisplayString,
	rsSigRprtBdosDeviceName				DisplayString,
	rsSigRprtBdosTimestamp				DisplayString,

	rsSigRprtBdosCustomerName			DisplayString,
	rsSigRprtBdosCustomerDesc			DisplayString,
	rsSigRprtBdosProtectedNw			DisplayString,

	rsSigRprtBdosUdpInXml				DisplayString,
	rsSigRprtBdosUdpOutXml				DisplayString,
	rsSigRprtBdosIcmpInXml				DisplayString,
	rsSigRprtBdosIcmpOutXml				DisplayString,

	rsSigRprtBdosIgmpInXml				DisplayString,
	rsSigRprtBdosIgmpOutXml				DisplayString,
	rsSigRprtBdosSynInXml				DisplayString,
	rsSigRprtBdosSynOutXml				DisplayString,

	rsSigRprtBdosRstInXml				DisplayString,
	rsSigRprtBdosRstOutXml				DisplayString,
	rsSigRprtBdosAckInXml				DisplayString,
	rsSigRprtBdosAckOutXml				DisplayString,

	rsSigRprtBdosAckPushInXml			DisplayString,
	rsSigRprtBdosAckPushOutXml			DisplayString,
	rsSigRprtBdosAckFinInXml			DisplayString,
	rsSigRprtBdosAckFinOutXml			DisplayString,

	rsSigRprtBdosSynAckInXml			DisplayString,
	rsSigRprtBdosSynAckOutXml			DisplayString,
	rsSigRprtBdosTcpFragInXml			DisplayString,
	rsSigRprtBdosTcpFragOutXml			DisplayString
}

rsSigRprtBdosNwPolicyName  OBJECT-TYPE
    SYNTAX DisplayString (SIZE(1..30))
    ACCESS  read-only
    STATUS mandatory
    DESCRIPTION
      "Network Policy Name."
    ::=  { rsSignalingReportBdosEntry 1 }

rsSigRprtBdosDeviceName  OBJECT-TYPE
    SYNTAX DisplayString (SIZE(1..30))
    ACCESS  read-only
    STATUS mandatory
    DESCRIPTION
      "Device Name."
    ::=  { rsSignalingReportBdosEntry 2 }

rsSigRprtBdosTimestamp  OBJECT-TYPE
    SYNTAX DisplayString (SIZE(1..30))
    ACCESS  read-only
    STATUS mandatory
    DESCRIPTION
      "Current Timestamp."
    ::=  { rsSignalingReportBdosEntry 3 }

rsSigRprtBdosCustomerName  OBJECT-TYPE
    SYNTAX DisplayString (SIZE(1..32))
    ACCESS  read-only
    STATUS mandatory
    DESCRIPTION
      "Customer Name."
    ::=  { rsSignalingReportBdosEntry 4 }

rsSigRprtBdosCustomerDesc  OBJECT-TYPE
    SYNTAX DisplayString (SIZE(1..100))
    ACCESS  read-only
    STATUS mandatory
    DESCRIPTION
      "Customer Description."
    ::=  { rsSignalingReportBdosEntry 5 }

rsSigRprtBdosProtectedNw  OBJECT-TYPE
    SYNTAX DisplayString (SIZE(1..30))
    ACCESS  read-only
    STATUS mandatory
    DESCRIPTION
      "Protected Network."
    ::=  { rsSignalingReportBdosEntry 6 }

rsSigRprtBdosUdpInXml  OBJECT-TYPE
    SYNTAX DisplayString (SIZE(1..255))
    ACCESS  read-only
    STATUS mandatory
    DESCRIPTION
      "UDP In Statistics XML."
    ::=  { rsSignalingReportBdosEntry 7 }

rsSigRprtBdosUdpOutXml  OBJECT-TYPE
    SYNTAX DisplayString (SIZE(1..255))
    ACCESS  read-only
    STATUS mandatory
    DESCRIPTION
      "UDP Out Statistics XML."
    ::=  { rsSignalingReportBdosEntry 8 }

rsSigRprtBdosIcmpInXml  OBJECT-TYPE
    SYNTAX DisplayString (SIZE(1..255))
    ACCESS  read-only
    STATUS mandatory
    DESCRIPTION
      "ICMP In Statistics XML."
    ::=  { rsSignalingReportBdosEntry 9 }

rsSigRprtBdosIcmpOutXml  OBJECT-TYPE
    SYNTAX DisplayString (SIZE(1..255))
    ACCESS  read-only
    STATUS mandatory
    DESCRIPTION
      "ICMP Out Statistics XML."
    ::=  { rsSignalingReportBdosEntry 10 }

rsSigRprtBdosIgmpInXml  OBJECT-TYPE
    SYNTAX DisplayString (SIZE(1..255))
    ACCESS  read-only
    STATUS mandatory
    DESCRIPTION
      "IGMP In Statistics XML."
    ::=  { rsSignalingReportBdosEntry 11 }

rsSigRprtBdosIgmpOutXml  OBJECT-TYPE
    SYNTAX DisplayString (SIZE(1..255))
    ACCESS  read-only
    STATUS mandatory
    DESCRIPTION
      "IGMP Out Statistics XML."
    ::=  { rsSignalingReportBdosEntry 12 }

rsSigRprtBdosSynInXml  OBJECT-TYPE
    SYNTAX DisplayString (SIZE(1..255))
    ACCESS  read-only
    STATUS mandatory
    DESCRIPTION
      "SYN In Statistics XML."
    ::=  { rsSignalingReportBdosEntry 13 }

rsSigRprtBdosSynOutXml  OBJECT-TYPE
    SYNTAX DisplayString (SIZE(1..255))
    ACCESS  read-only
    STATUS mandatory
    DESCRIPTION
      "SYN Out Statistics XML."
    ::=  { rsSignalingReportBdosEntry 14 }

rsSigRprtBdosRstInXml  OBJECT-TYPE
    SYNTAX DisplayString (SIZE(1..255))
    ACCESS  read-only
    STATUS mandatory
    DESCRIPTION
      "RST In Statistics XML."
    ::=  { rsSignalingReportBdosEntry 15 }

rsSigRprtBdosRstOutXml  OBJECT-TYPE
    SYNTAX DisplayString (SIZE(1..255))
    ACCESS  read-only
    STATUS mandatory
    DESCRIPTION
      "RST Out Statistics XML."
    ::=  { rsSignalingReportBdosEntry 16 }

rsSigRprtBdosAckInXml  OBJECT-TYPE
    SYNTAX DisplayString (SIZE(1..255))
    ACCESS  read-only
    STATUS mandatory
    DESCRIPTION
      "ACK In Statistics XML."
    ::=  { rsSignalingReportBdosEntry 17 }

rsSigRprtBdosAckOutXml  OBJECT-TYPE
    SYNTAX DisplayString (SIZE(1..255))
    ACCESS  read-only
    STATUS mandatory
    DESCRIPTION
      "ACK Out Statistics XML."
    ::=  { rsSignalingReportBdosEntry 18 }

rsSigRprtBdosAckPushInXml  OBJECT-TYPE
    SYNTAX DisplayString (SIZE(1..255))
    ACCESS  read-only
    STATUS mandatory
    DESCRIPTION
      "ACK-PUSH In Statistics XML."
    ::=  { rsSignalingReportBdosEntry 19 }

rsSigRprtBdosAckPushOutXml  OBJECT-TYPE
    SYNTAX DisplayString (SIZE(1..255))
    ACCESS  read-only
    STATUS mandatory
    DESCRIPTION
      "ACK-PUSH Out Statistics XML."
    ::=  { rsSignalingReportBdosEntry 20 }

rsSigRprtBdosAckFinInXml  OBJECT-TYPE
    SYNTAX DisplayString (SIZE(1..255))
    ACCESS  read-only
    STATUS mandatory
    DESCRIPTION
      "ACK-FIN In Statistics XML."
    ::=  { rsSignalingReportBdosEntry 21 }

rsSigRprtBdosAckFinOutXml  OBJECT-TYPE
    SYNTAX DisplayString (SIZE(1..255))
    ACCESS  read-only
    STATUS mandatory
    DESCRIPTION
      "ACK-FIN Out Statistics XML."
    ::=  { rsSignalingReportBdosEntry 22 }

rsSigRprtBdosSynAckInXml  OBJECT-TYPE
    SYNTAX DisplayString (SIZE(1..255))
    ACCESS  read-only
    STATUS mandatory
    DESCRIPTION
      "SYN-ACK In Statistics XML."
    ::=  { rsSignalingReportBdosEntry 23 }

rsSigRprtBdosSynAckOutXml  OBJECT-TYPE
    SYNTAX DisplayString (SIZE(1..255))
    ACCESS  read-only
    STATUS mandatory
    DESCRIPTION
      "SYN-ACK Out Statistics XML."
    ::=  { rsSignalingReportBdosEntry 24 }

rsSigRprtBdosTcpFragInXml  OBJECT-TYPE
    SYNTAX DisplayString (SIZE(1..255))
    ACCESS  read-only
    STATUS mandatory
    DESCRIPTION
      "TCP-FRAG In Statistics XML."
    ::=  { rsSignalingReportBdosEntry 25 }

rsSigRprtBdosTcpFragOutXml  OBJECT-TYPE
    SYNTAX DisplayString (SIZE(1..255))
    ACCESS  read-only
    STATUS mandatory
    DESCRIPTION
      "TCP-FRAG Out Statistics XML."
    ::=  { rsSignalingReportBdosEntry 26 }

-- Signaling Reports : HTTP-Flood Statistics
--

rsSignalingReportHttpTable OBJECT-TYPE
    SYNTAX SEQUENCE OF RsSignalingReportHttpEntry
    ACCESS not-accessible
    STATUS  mandatory
    DESCRIPTION
      "Table containing System HTTP-Flood statistics report."
    ::=  {rsSignaling 7}

rsSignalingReportHttpEntry OBJECT-TYPE
    SYNTAX RsSignalingReportHttpEntry
    ACCESS not-accessible
    STATUS  mandatory
    DESCRIPTION
       "The row definition for this table."
	INDEX { rsSigRprtHttpServerName	 }
    ::=  { rsSignalingReportHttpTable 1 }

RsSignalingReportHttpEntry ::= SEQUENCE {
	rsSigRprtHttpServerName				DisplayString,
	rsSigRprtHttpDeviceName				DisplayString,
	rsSigRprtHttpTimestamp				DisplayString,

	rsSigRprtHttpCustomerName			DisplayString,
	rsSigRprtHttpCustomerDesc			DisplayString,
	rsSigRprtHttpProtectedNw			DisplayString,

	rsSigRprtHttpLastSecXml				DisplayString,
	rsSigRprtHttpNormalXml				DisplayString,
	rsSigRprtHttpPeakXml				DisplayString
}

rsSigRprtHttpServerName  OBJECT-TYPE
    SYNTAX DisplayString (SIZE(1..30))
    ACCESS  read-only
    STATUS mandatory
    DESCRIPTION
      "Server Name."
    ::=  { rsSignalingReportHttpEntry 1 }

rsSigRprtHttpDeviceName  OBJECT-TYPE
    SYNTAX DisplayString (SIZE(1..30))
    ACCESS  read-only
    STATUS mandatory
    DESCRIPTION
      "Device Name."
    ::=  { rsSignalingReportHttpEntry 2 }

rsSigRprtHttpTimestamp  OBJECT-TYPE
    SYNTAX DisplayString (SIZE(1..30))
    ACCESS  read-only
    STATUS mandatory
    DESCRIPTION
      "Current Timestamp."
    ::=  { rsSignalingReportHttpEntry 3 }

rsSigRprtHttpCustomerName  OBJECT-TYPE
    SYNTAX DisplayString (SIZE(1..32))
    ACCESS  read-only
    STATUS mandatory
    DESCRIPTION
      "Customer Name."
    ::=  { rsSignalingReportHttpEntry 4 }

rsSigRprtHttpCustomerDesc  OBJECT-TYPE
    SYNTAX DisplayString (SIZE(1..100))
    ACCESS  read-only
    STATUS mandatory
    DESCRIPTION
      "Customer Description."
    ::=  { rsSignalingReportHttpEntry 5 }

rsSigRprtHttpProtectedNw  OBJECT-TYPE
    SYNTAX DisplayString (SIZE(1..30))
    ACCESS  read-only
    STATUS mandatory
    DESCRIPTION
      "Protected Network."
    ::=  { rsSignalingReportHttpEntry 6 }

rsSigRprtHttpLastSecXml  OBJECT-TYPE
    SYNTAX DisplayString (SIZE(1..255))
    ACCESS  read-only
    STATUS mandatory
    DESCRIPTION
      "HTTP-Flood Last Second Statistics XML."
    ::=  { rsSignalingReportHttpEntry 7 }

rsSigRprtHttpNormalXml  OBJECT-TYPE
    SYNTAX DisplayString (SIZE(1..255))
    ACCESS  read-only
    STATUS mandatory
    DESCRIPTION
      "HTTP-Flood Baseline Statistics XML."
    ::=  { rsSignalingReportHttpEntry 8 }

rsSigRprtHttpPeakXml  OBJECT-TYPE
    SYNTAX DisplayString (SIZE(1..255))
    ACCESS  read-only
    STATUS mandatory
    DESCRIPTION
      "HTTP-Flood Peak Statistics XML."
    ::=  { rsSignalingReportHttpEntry 9 }


-- Signaling Reports : DNS Statistics
--

rsSignalingReportDnsTable OBJECT-TYPE
    SYNTAX SEQUENCE OF RsSignalingReportDnsEntry
    ACCESS not-accessible
    STATUS  mandatory
    DESCRIPTION
      "Table containing System DNS statistics report."
    ::=  {rsSignaling 8}

rsSignalingReportDnsEntry OBJECT-TYPE
    SYNTAX RsSignalingReportDnsEntry
    ACCESS not-accessible
    STATUS  mandatory
    DESCRIPTION
       "The row definition for this table."
	INDEX { rsSigRprtDnsNwPolicyName	 }
    ::=  { rsSignalingReportDnsTable 1 }

RsSignalingReportDnsEntry ::= SEQUENCE {
	rsSigRprtDnsNwPolicyName			DisplayString,
	rsSigRprtDnsDeviceName				DisplayString,
	rsSigRprtDnsTimestamp				DisplayString,

	rsSigRprtDnsCustomerName			DisplayString,
	rsSigRprtDnsCustomerDesc			DisplayString,
	rsSigRprtDnsProtectedNw				DisplayString,

	rsSigRprtDnsAInXml					DisplayString,
	rsSigRprtDnsMxInXml					DisplayString,

	rsSigRprtDnsPtrInXml				DisplayString,
	rsSigRprtDnsAaaaInXml				DisplayString,

	rsSigRprtDnsTextInXml				DisplayString,
	rsSigRprtDnsSoaInXml				DisplayString,

	rsSigRprtDnsNaptrInXml				DisplayString,
	rsSigRprtDnsSrvInXml				DisplayString,

	rsSigRprtDnsOtherInXml				DisplayString
}

rsSigRprtDnsNwPolicyName  OBJECT-TYPE
    SYNTAX DisplayString (SIZE(1..30))
    ACCESS  read-only
    STATUS mandatory
    DESCRIPTION
      "Network Policy Name."
    ::=  { rsSignalingReportDnsEntry 1 }

rsSigRprtDnsDeviceName  OBJECT-TYPE
    SYNTAX DisplayString (SIZE(1..30))
    ACCESS  read-only
    STATUS mandatory
    DESCRIPTION
      "Device Name."
    ::=  { rsSignalingReportDnsEntry 2 }

rsSigRprtDnsTimestamp  OBJECT-TYPE
    SYNTAX DisplayString (SIZE(1..30))
    ACCESS  read-only
    STATUS mandatory
    DESCRIPTION
      "Current Timestamp."
    ::=  { rsSignalingReportDnsEntry 3 }

rsSigRprtDnsCustomerName  OBJECT-TYPE
    SYNTAX DisplayString (SIZE(1..32))
    ACCESS  read-only
    STATUS mandatory
    DESCRIPTION
      "Customer Name."
    ::=  { rsSignalingReportDnsEntry 4 }

rsSigRprtDnsCustomerDesc  OBJECT-TYPE
    SYNTAX DisplayString (SIZE(1..100))
    ACCESS  read-only
    STATUS mandatory
    DESCRIPTION
      "Customer Description."
    ::=  { rsSignalingReportDnsEntry 5 }

rsSigRprtDnsProtectedNw  OBJECT-TYPE
    SYNTAX DisplayString (SIZE(1..30))
    ACCESS  read-only
    STATUS mandatory
    DESCRIPTION
      "Protected Network."
    ::=  { rsSignalingReportDnsEntry 6 }

rsSigRprtDnsAInXml  OBJECT-TYPE
    SYNTAX DisplayString (SIZE(1..255))
    ACCESS  read-only
    STATUS mandatory
    DESCRIPTION
      "A Statistics XML."
    ::=  { rsSignalingReportDnsEntry 7 }

rsSigRprtDnsMxInXml  OBJECT-TYPE
    SYNTAX DisplayString (SIZE(1..255))
    ACCESS  read-only
    STATUS mandatory
    DESCRIPTION
      "MX Statistics XML."
    ::=  { rsSignalingReportDnsEntry 8 }

rsSigRprtDnsPtrInXml  OBJECT-TYPE
    SYNTAX DisplayString (SIZE(1..255))
    ACCESS  read-only
    STATUS mandatory
    DESCRIPTION
      "PTR Statistics XML."
    ::=  { rsSignalingReportDnsEntry 9 }

rsSigRprtDnsAaaaInXml  OBJECT-TYPE
    SYNTAX DisplayString (SIZE(1..255))
    ACCESS  read-only
    STATUS mandatory
    DESCRIPTION
      "AAAA Statistics XML."
    ::=  { rsSignalingReportDnsEntry 10 }

rsSigRprtDnsTextInXml  OBJECT-TYPE
    SYNTAX DisplayString (SIZE(1..255))
    ACCESS  read-only
    STATUS mandatory
    DESCRIPTION
      "TEXT Statistics XML."
    ::=  { rsSignalingReportDnsEntry 11 }

rsSigRprtDnsSoaInXml  OBJECT-TYPE
    SYNTAX DisplayString (SIZE(1..255))
    ACCESS  read-only
    STATUS mandatory
    DESCRIPTION
      "SOA Statistics XML."
    ::=  { rsSignalingReportDnsEntry 12 }

rsSigRprtDnsNaptrInXml  OBJECT-TYPE
    SYNTAX DisplayString (SIZE(1..255))
    ACCESS  read-only
    STATUS mandatory
    DESCRIPTION
      "NAPTR Statistics XML."
    ::=  { rsSignalingReportDnsEntry 13 }

rsSigRprtDnsSrvInXml  OBJECT-TYPE
    SYNTAX DisplayString (SIZE(1..255))
    ACCESS  read-only
    STATUS mandatory
    DESCRIPTION
      "SRV Statistics XML."
    ::=  { rsSignalingReportDnsEntry 14 }

rsSigRprtDnsOtherInXml  OBJECT-TYPE
    SYNTAX DisplayString (SIZE(1..255))
    ACCESS  read-only
    STATUS mandatory
    DESCRIPTION
      "OTHER Statistics XML."
    ::=  { rsSignalingReportDnsEntry 15 }

-- Signaling Source Group - Network Policies
--

rsSignalingNwSourcesTable OBJECT-TYPE
    SYNTAX SEQUENCE OF RsSignalingNwSrcGroupEntry
    ACCESS not-accessible
    STATUS  mandatory
    DESCRIPTION
      "Table containing the signaling source groups for Network Policies."
    ::=  {rsSignaling 9}

rsSignalingNwSrcGroupEntry OBJECT-TYPE
    SYNTAX RsSignalingNwSrcGroupEntry
    ACCESS not-accessible
    STATUS  mandatory
    DESCRIPTION
       "The row definition for this table."
    INDEX { rsSignalingNwSrcGroupId,
			rsSignalingNwSrcName }
    ::=  { rsSignalingNwSourcesTable 1 }

RsSignalingNwSrcGroupEntry ::= SEQUENCE {
	rsSignalingNwSrcGroupId				INTEGER,
	rsSignalingNwSrcGroupRowStatus		RowStatus,
    rsSignalingNwSrcName				DisplayString
}

rsSignalingNwSrcGroupId OBJECT-TYPE
    SYNTAX INTEGER
    ACCESS  read-only
    STATUS  mandatory
    DESCRIPTION
       "Signaling Network Policies Source Group Id"
    ::=  { rsSignalingNwSrcGroupEntry 1 }

rsSignalingNwSrcGroupRowStatus OBJECT-TYPE
    SYNTAX RowStatus
    ACCESS  read-write
    STATUS  mandatory
    DESCRIPTION
       "Signaling Network Policies Source Group Row Status"
    ::=  { rsSignalingNwSrcGroupEntry 2 }

rsSignalingNwSrcName  OBJECT-TYPE
    SYNTAX DisplayString (SIZE(1..19))
    ACCESS  read-write
    STATUS mandatory
    DESCRIPTION
      "Signaling Network Policy Name."
    ::=  { rsSignalingNwSrcGroupEntry 3 }

-- Signaling Source Group - Servers
--

rsSignalingServerSourcesTable OBJECT-TYPE
    SYNTAX SEQUENCE OF RsSignalingServerSrcGroupEntry
    ACCESS not-accessible
    STATUS  mandatory
    DESCRIPTION
      "Table containing the signaling source groups for Servers."
    ::=  {rsSignaling 10}

rsSignalingServerSrcGroupEntry OBJECT-TYPE
    SYNTAX RsSignalingServerSrcGroupEntry
    ACCESS not-accessible
    STATUS  mandatory
    DESCRIPTION
       "The row definition for this table."
    INDEX { rsSignalingServerSrcGroupId,
			rsSignalingServerSrcName }
    ::=  { rsSignalingServerSourcesTable 1 }

RsSignalingServerSrcGroupEntry ::= SEQUENCE {
	rsSignalingServerSrcGroupId				INTEGER,
	rsSignalingServerSrcGroupRowStatus		RowStatus,
    rsSignalingServerSrcName				DisplayString
}

rsSignalingServerSrcGroupId OBJECT-TYPE
    SYNTAX INTEGER
    ACCESS  read-only
    STATUS  mandatory
    DESCRIPTION
       "Signaling Servers Source Group Id"
    ::=  { rsSignalingServerSrcGroupEntry 1 }

rsSignalingServerSrcGroupRowStatus OBJECT-TYPE
    SYNTAX RowStatus
    ACCESS  read-write
    STATUS  mandatory
    DESCRIPTION
       "Signaling Servers Source Group Row Status"
    ::=  { rsSignalingServerSrcGroupEntry 2 }

rsSignalingServerSrcName  OBJECT-TYPE
    SYNTAX DisplayString (SIZE(1..32))
    ACCESS  read-write
    STATUS mandatory
    DESCRIPTION
      "Signaling Server Name."
    ::=  { rsSignalingServerSrcGroupEntry 3 }



rsUpdatePolicies OBJECT IDENTIFIER ::= { rsIDS 181 }

rdwrPoliciesIsolationMode OBJECT-TYPE
 SYNTAX INTEGER {
      mitigate(1),
      bypass(2),
      drop(3)
   }
    ACCESS read-write
    STATUS mandatory
    DESCRIPTION
      "Update Policies Isolation Mode status"
   DEFVAL  {bypass}
    ::= {rsUpdatePolicies 1}

rdwrUpdatePoliciesRequired OBJECT-TYPE
    SYNTAX INTEGER {
    	no(0),
		yes(1)
    }
    ACCESS read-only
    STATUS mandatory
    DESCRIPTION
      "Derermines if an Update Policies operation is required"
   DEFVAL  {no}
    ::= {rsUpdatePolicies 2}

rsUpdatePoliciesInProgress OBJECT-TYPE
    SYNTAX INTEGER {
    	no(0),
		yes(1)
    }
    ACCESS read-only
    STATUS mandatory
    DESCRIPTION
      "Derermines if an Update Policies operation is in progress"
   DEFVAL  {no}
    ::= {rsUpdatePolicies 3}

rsImportExport OBJECT IDENTIFIER ::= { rsIDS 183 }

-- BDoS Export Baseline
--

	rsExportBaselineBdosEntry OBJECT-TYPE
    SYNTAX DisplayString (SIZE(1..64))
    ACCESS  read-write
    STATUS  mandatory
    DESCRIPTION
       "Export BDoS Baseline Network Policy Name"
    ::=  {  rsImportExport 1 }

-- DNS Export Baseline
--


	rsExportBaselineDnsEntry OBJECT-TYPE
    SYNTAX DisplayString (SIZE(1..64))
    ACCESS  read-write
    STATUS  mandatory
    DESCRIPTION
       "Export DNS Baseline Network Policy Name"
    ::=  { rsImportExport 2}


-- HTTP Export Baseline
--

rsExportBaselineHttpEntry OBJECT-TYPE
    SYNTAX DisplayString (SIZE(1..20))
    ACCESS  read-write
    STATUS  mandatory
    DESCRIPTION
       "Export HTTP Baseline Server Name"
    ::=  { rsImportExport 3 }


-- BDoS Import Baseline
--


rsImportBaselineBdosTable OBJECT-TYPE
    SYNTAX SEQUENCE OF RsImportBaselineBdosEntry
    ACCESS not-accessible
    STATUS  mandatory
    DESCRIPTION
      "Table containing the baseline import request."
    ::=  {rsImportExport 4}

rsImportBaselineBdosEntry OBJECT-TYPE
    SYNTAX RsImportBaselineBdosEntry
    ACCESS not-accessible
    STATUS  mandatory
    DESCRIPTION
       "The row definition for this table."
    INDEX { rsImportBaselineBdosName }
    ::=  { rsImportBaselineBdosTable 1 }

RsImportBaselineBdosEntry ::= SEQUENCE {
    rsImportBaselineBdosName				DisplayString,

	rsImportBaselineBdosIcmpInBpsIpv4		Counter64,
	rsImportBaselineBdosIcmpOutBpsIpv4		Counter64,
	rsImportBaselineBdosTcpInBpsIpv4		Counter64,
	rsImportBaselineBdosTcpOutBpsIpv4		Counter64,

	rsImportBaselineBdosUdpInBpsIpv4		Counter64,
	rsImportBaselineBdosUdpOutBpsIpv4		Counter64,
	rsImportBaselineBdosIgmpInBpsIpv4		Counter64,
	rsImportBaselineBdosIgmpOutBpsIpv4		Counter64,

	rsImportBaselineBdosTcpSynInBpsIpv4		Counter64,
	rsImportBaselineBdosTcpSynOutBpsIpv4		Counter64,
	rsImportBaselineBdosTcpRstInBpsIpv4		Counter64,
	rsImportBaselineBdosTcpRstOutBpsIpv4		Counter64,

	rsImportBaselineBdosTcpAckInBpsIpv4		Counter64,
	rsImportBaselineBdosTcpAckOutBpsIpv4		Counter64,
	rsImportBaselineBdosTcpAckPshInBpsIpv4		Counter64,
	rsImportBaselineBdosTcpAckPshOutBpsIpv4		Counter64,
	rsImportBaselineBdosTcpAckFinInBpsIpv4		Counter64,
	rsImportBaselineBdosTcpAckFinOutBpsIpv4		Counter64,

	rsImportBaselineBdosTcpSynAckInBpsIpv4		Counter64,
	rsImportBaselineBdosTcpSynAckOutBpsIpv4		Counter64,
	rsImportBaselineBdosTcpFragInBpsIpv4		Counter64,
	rsImportBaselineBdosTcpFragOutBpsIpv4		Counter64,

	rsImportBaselineBdosIcmpInPpsIpv4		Counter64,
	rsImportBaselineBdosIcmpOutPpsIpv4		Counter64,
	rsImportBaselineBdosTcpInPpsIpv4		Counter64,
	rsImportBaselineBdosTcpOutPpsIpv4		Counter64,

	rsImportBaselineBdosUdpInPpsIpv4		Counter64,
	rsImportBaselineBdosUdpOutPpsIpv4		Counter64,
	rsImportBaselineBdosIgmpInPpsIpv4		Counter64,
	rsImportBaselineBdosIgmpOutPpsIpv4		Counter64,

	rsImportBaselineBdosTcpSynInPpsIpv4		Counter64,
	rsImportBaselineBdosTcpSynOutPpsIpv4		Counter64,
	rsImportBaselineBdosTcpRstInPpsIpv4		Counter64,
	rsImportBaselineBdosTcpRstOutPpsIpv4		Counter64,

	rsImportBaselineBdosTcpAckInPpsIpv4		Counter64,
	rsImportBaselineBdosTcpAckOutPpsIpv4		Counter64,
	rsImportBaselineBdosTcpAckPshInPpsIpv4		Counter64,
	rsImportBaselineBdosTcpAckPshOutPpsIpv4		Counter64,
	rsImportBaselineBdosTcpAckFinInPpsIpv4		Counter64,
	rsImportBaselineBdosTcpAckFinOutPpsIpv4		Counter64,

	rsImportBaselineBdosTcpSynAckInPpsIpv4		Counter64,
	rsImportBaselineBdosTcpSynAckOutPpsIpv4		Counter64,
	rsImportBaselineBdosTcpFragInPpsIpv4		Counter64,
	rsImportBaselineBdosTcpFragOutPpsIpv4		Counter64,



	rsImportBaselineBdosIcmpInBpsIpv6		Counter64,
	rsImportBaselineBdosIcmpOutBpsIpv6		Counter64,
	rsImportBaselineBdosTcpInBpsIpv6		Counter64,
	rsImportBaselineBdosTcpOutBpsIpv6		Counter64,

	rsImportBaselineBdosUdpInBpsIpv6		Counter64,
	rsImportBaselineBdosUdpOutBpsIpv6		Counter64,
	rsImportBaselineBdosIgmpInBpsIpv6		Counter64,
	rsImportBaselineBdosIgmpOutBpsIpv6		Counter64,

	rsImportBaselineBdosTcpSynInBpsIpv6		Counter64,
	rsImportBaselineBdosTcpSynOutBpsIpv6		Counter64,
	rsImportBaselineBdosTcpRstInBpsIpv6		Counter64,
	rsImportBaselineBdosTcpRstOutBpsIpv6		Counter64,

	rsImportBaselineBdosTcpAckInBpsIpv6		Counter64,
	rsImportBaselineBdosTcpAckOutBpsIpv6		Counter64,
	rsImportBaselineBdosTcpAckPshInBpsIpv6		Counter64,
	rsImportBaselineBdosTcpAckPshOutBpsIpv6		Counter64,
	rsImportBaselineBdosTcpAckFinInBpsIpv6		Counter64,
	rsImportBaselineBdosTcpAckFinOutBpsIpv6		Counter64,

	rsImportBaselineBdosTcpSynAckInBpsIpv6		Counter64,
	rsImportBaselineBdosTcpSynAckOutBpsIpv6		Counter64,
	rsImportBaselineBdosTcpFragInBpsIpv6		Counter64,
	rsImportBaselineBdosTcpFragOutBpsIpv6		Counter64,

	rsImportBaselineBdosIcmpInPpsIpv6		Counter64,
	rsImportBaselineBdosIcmpOutPpsIpv6		Counter64,
	rsImportBaselineBdosTcpInPpsIpv6		Counter64,
	rsImportBaselineBdosTcpOutPpsIpv6		Counter64,

	rsImportBaselineBdosUdpInPpsIpv6		Counter64,
	rsImportBaselineBdosUdpOutPpsIpv6		Counter64,
	rsImportBaselineBdosIgmpInPpsIpv6		Counter64,
	rsImportBaselineBdosIgmpOutPpsIpv6		Counter64,

	rsImportBaselineBdosTcpSynInPpsIpv6		Counter64,
	rsImportBaselineBdosTcpSynOutPpsIpv6		Counter64,
	rsImportBaselineBdosTcpRstInPpsIpv6		Counter64,
	rsImportBaselineBdosTcpRstOutPpsIpv6		Counter64,

	rsImportBaselineBdosTcpAckInPpsIpv6		Counter64,
	rsImportBaselineBdosTcpAckOutPpsIpv6		Counter64,
	rsImportBaselineBdosTcpAckPshInPpsIpv6		Counter64,
	rsImportBaselineBdosTcpAckPshOutPpsIpv6		Counter64,
	rsImportBaselineBdosTcpAckFinInPpsIpv6		Counter64,
	rsImportBaselineBdosTcpAckFinOutPpsIpv6		Counter64,

	rsImportBaselineBdosTcpSynAckInPpsIpv6		Counter64,
	rsImportBaselineBdosTcpSynAckOutPpsIpv6		Counter64,
	rsImportBaselineBdosTcpFragInPpsIpv6		Counter64,
	rsImportBaselineBdosTcpFragOutPpsIpv6		Counter64,

	rsImportBaselineBdosUdpFragInBpsIpv4		Counter64,
	rsImportBaselineBdosUdpFragOutBpsIpv4		Counter64,
	rsImportBaselineBdosUdpFragInPpsIpv4		Counter64,
	rsImportBaselineBdosUdpFragOutPpsIpv4		Counter64,
	rsImportBaselineBdosUdpFragInBpsIpv6		Counter64,
	rsImportBaselineBdosUdpFragOutBpsIpv6		Counter64,
	rsImportBaselineBdosUdpFragInPpsIpv6		Counter64,
	rsImportBaselineBdosUdpFragOutPpsIpv6		Counter64
}

rsImportBaselineBdosName OBJECT-TYPE
    SYNTAX DisplayString (SIZE(1..64))
    ACCESS  read-write
    STATUS  mandatory
    DESCRIPTION
       "Import BDoS Baseline Network Policy Name"
    ::=  { rsImportBaselineBdosEntry 1 }


rsImportBaselineBdosIcmpInBpsIpv4 OBJECT-TYPE
    SYNTAX Counter64
    ACCESS  read-write
    STATUS  mandatory
    DESCRIPTION
       "Import BDoS Baseline ICMP-In-IPv4 Controller (Bps)"
    ::=  { rsImportBaselineBdosEntry 2 }

rsImportBaselineBdosIcmpOutBpsIpv4 OBJECT-TYPE
    SYNTAX Counter64
    ACCESS  read-write
    STATUS  mandatory
    DESCRIPTION
       "Import BDoS Baseline ICMP-Out-IPv4 Controller (Bps)"
    ::=  { rsImportBaselineBdosEntry 3 }

rsImportBaselineBdosTcpInBpsIpv4 OBJECT-TYPE
    SYNTAX Counter64
    ACCESS  read-write
    STATUS  mandatory
    DESCRIPTION
       "Import BDoS Baseline TCP-In-IPv4 Controller (Bps)"
    ::=  { rsImportBaselineBdosEntry 4 }

rsImportBaselineBdosTcpOutBpsIpv4 OBJECT-TYPE
    SYNTAX Counter64
    ACCESS  read-write
    STATUS  mandatory
    DESCRIPTION
       "Import BDoS Baseline TCP-Out-IPv4 Controller (Bps)"
    ::=  { rsImportBaselineBdosEntry 5 }

rsImportBaselineBdosUdpInBpsIpv4 OBJECT-TYPE
    SYNTAX Counter64
    ACCESS  read-write
    STATUS  mandatory
    DESCRIPTION
       "Import BDoS Baseline UDP-In-IPv4 Controller (Bps)"
    ::=  { rsImportBaselineBdosEntry 6 }

rsImportBaselineBdosUdpOutBpsIpv4 OBJECT-TYPE
    SYNTAX Counter64
    ACCESS  read-write
    STATUS  mandatory
    DESCRIPTION
       "Import BDoS Baseline UDP-Out-IPv4 Controller (Bps)"
    ::=  { rsImportBaselineBdosEntry 7 }

rsImportBaselineBdosIgmpInBpsIpv4 OBJECT-TYPE
    SYNTAX Counter64
    ACCESS  read-write
    STATUS  mandatory
    DESCRIPTION
       "Import BDoS Baseline IGMP-In-IPv4 Controller (Bps)"
    ::=  { rsImportBaselineBdosEntry 8 }

rsImportBaselineBdosIgmpOutBpsIpv4 OBJECT-TYPE
    SYNTAX Counter64
    ACCESS  read-write
    STATUS  mandatory
    DESCRIPTION
       "Import BDoS Baseline IGMP-Out-IPv4 Controller (Bps)"
    ::=  { rsImportBaselineBdosEntry 9 }



rsImportBaselineBdosTcpSynInBpsIpv4 OBJECT-TYPE
    SYNTAX Counter64
    ACCESS  read-write
    STATUS  mandatory
    DESCRIPTION
       "Import BDoS Baseline TCP-SYN-In-IPv4 Controller (Bps)"
    ::=  { rsImportBaselineBdosEntry 10 }

rsImportBaselineBdosTcpSynOutBpsIpv4 OBJECT-TYPE
    SYNTAX Counter64
    ACCESS  read-write
    STATUS  mandatory
    DESCRIPTION
       "Import BDoS Baseline TCP-SYN-Out-IPv4 Controller (Bps)"
    ::=  { rsImportBaselineBdosEntry 11 }

rsImportBaselineBdosTcpRstInBpsIpv4 OBJECT-TYPE
    SYNTAX Counter64
    ACCESS  read-write
    STATUS  mandatory
    DESCRIPTION
       "Import BDoS Baseline TCP-RST-In-IPv4 Controller (Bps)"
    ::=  { rsImportBaselineBdosEntry 12 }

rsImportBaselineBdosTcpRstOutBpsIpv4 OBJECT-TYPE
    SYNTAX Counter64
    ACCESS  read-write
    STATUS  mandatory
    DESCRIPTION
       "Import BDoS Baseline TCP-RST-Out-IPv4 Controller (Bps)"
    ::=  { rsImportBaselineBdosEntry 13 }




rsImportBaselineBdosTcpAckInBpsIpv4 OBJECT-TYPE
    SYNTAX Counter64
    ACCESS  read-write
    STATUS  mandatory
    DESCRIPTION
       "Import BDoS Baseline TCP-ACK-In-IPv4 Controller (Bps)"
    ::=  { rsImportBaselineBdosEntry 14 }

rsImportBaselineBdosTcpAckOutBpsIpv4 OBJECT-TYPE
    SYNTAX Counter64
    ACCESS  read-write
    STATUS  mandatory
    DESCRIPTION
       "Import BDoS Baseline TCP-ACK-Out-IPv4 Controller (Bps)"
    ::=  { rsImportBaselineBdosEntry 15 }

rsImportBaselineBdosTcpAckPshInBpsIpv4 OBJECT-TYPE
    SYNTAX Counter64
    ACCESS  read-write
    STATUS  mandatory
    DESCRIPTION
       "Import BDoS Baseline TCP-ACK-PSH-In-IPv4 Controller (Bps)"
    ::=  { rsImportBaselineBdosEntry 16 }

rsImportBaselineBdosTcpAckPshOutBpsIpv4 OBJECT-TYPE
    SYNTAX Counter64
    ACCESS  read-write
    STATUS  mandatory
    DESCRIPTION
       "Import BDoS Baseline TCP-ACK-PSH-Out-IPv4 Controller (Bps)"
    ::=  { rsImportBaselineBdosEntry 17 }

rsImportBaselineBdosTcpAckFinInBpsIpv4 OBJECT-TYPE
    SYNTAX Counter64
    ACCESS  read-write
    STATUS  mandatory
    DESCRIPTION
       "Import BDoS Baseline TCP-ACK-FIN-In-IPv4 Controller (Bps)"
    ::=  { rsImportBaselineBdosEntry 18 }

rsImportBaselineBdosTcpAckFinOutBpsIpv4 OBJECT-TYPE
    SYNTAX Counter64
    ACCESS  read-write
    STATUS  mandatory
    DESCRIPTION
       "Import BDoS Baseline TCP-ACK-FIN-Out-IPv4 Controller (Bps)"
    ::=  { rsImportBaselineBdosEntry 19 }

rsImportBaselineBdosTcpSynAckInBpsIpv4 OBJECT-TYPE
    SYNTAX Counter64
    ACCESS  read-write
    STATUS  mandatory
    DESCRIPTION
       "Import BDoS Baseline TCP-SYN-ACK-In-IPv4 Controller (Bps)"
    ::=  { rsImportBaselineBdosEntry 20 }

rsImportBaselineBdosTcpSynAckOutBpsIpv4 OBJECT-TYPE
    SYNTAX Counter64
    ACCESS  read-write
    STATUS  mandatory
    DESCRIPTION
       "Import BDoS Baseline TCP-SYN-ACK-Out-IPv4 Controller (Bps)"
    ::=  { rsImportBaselineBdosEntry 21 }

rsImportBaselineBdosTcpFragInBpsIpv4 OBJECT-TYPE
    SYNTAX Counter64
    ACCESS  read-write
    STATUS  mandatory
    DESCRIPTION
       "Import BDoS Baseline TCP-FRAG-In-IPv4 Controller (Bps)"
    ::=  { rsImportBaselineBdosEntry 22 }

rsImportBaselineBdosTcpFragOutBpsIpv4 OBJECT-TYPE
    SYNTAX Counter64
    ACCESS  read-write
    STATUS  mandatory
    DESCRIPTION
       "Import BDoS Baseline TCP-FRAG-Out-IPv4 Controller (Bps)"
    ::=  { rsImportBaselineBdosEntry 23 }




rsImportBaselineBdosIcmpInPpsIpv4 OBJECT-TYPE
    SYNTAX Counter64
    ACCESS  read-write
    STATUS  mandatory
    DESCRIPTION
       "Import BDoS Baseline ICMP-In-IPv4 Controller (Pps)"
    ::=  { rsImportBaselineBdosEntry 24 }

rsImportBaselineBdosIcmpOutPpsIpv4 OBJECT-TYPE
    SYNTAX Counter64
    ACCESS  read-write
    STATUS  mandatory
    DESCRIPTION
       "Import BDoS Baseline ICMP-Out-IPv4 Controller (Pps)"
    ::=  { rsImportBaselineBdosEntry 25 }

rsImportBaselineBdosTcpInPpsIpv4 OBJECT-TYPE
    SYNTAX Counter64
    ACCESS  read-write
    STATUS  mandatory
    DESCRIPTION
       "Import BDoS Baseline TCP-In-IPv4 Controller (Pps)"
    ::=  { rsImportBaselineBdosEntry 26 }

rsImportBaselineBdosTcpOutPpsIpv4 OBJECT-TYPE
    SYNTAX Counter64
    ACCESS  read-write
    STATUS  mandatory
    DESCRIPTION
       "Import BDoS Baseline TCP-Out-IPv4 Controller (Pps)"
    ::=  { rsImportBaselineBdosEntry 27 }

rsImportBaselineBdosUdpInPpsIpv4 OBJECT-TYPE
    SYNTAX Counter64
    ACCESS  read-write
    STATUS  mandatory
    DESCRIPTION
       "Import BDoS Baseline UDP-In-IPv4 Controller (Pps)"
    ::=  { rsImportBaselineBdosEntry 28 }

rsImportBaselineBdosUdpOutPpsIpv4 OBJECT-TYPE
    SYNTAX Counter64
    ACCESS  read-write
    STATUS  mandatory
    DESCRIPTION
       "Import BDoS Baseline UDP-Out-IPv4 Controller (Pps)"
    ::=  { rsImportBaselineBdosEntry 29 }

rsImportBaselineBdosIgmpInPpsIpv4 OBJECT-TYPE
    SYNTAX Counter64
    ACCESS  read-write
    STATUS  mandatory
    DESCRIPTION
       "Import BDoS Baseline IGMP-In-IPv4 Controller (Pps)"
    ::=  { rsImportBaselineBdosEntry 30 }

rsImportBaselineBdosIgmpOutPpsIpv4 OBJECT-TYPE
    SYNTAX Counter64
    ACCESS  read-write
    STATUS  mandatory
    DESCRIPTION
       "Import BDoS Baseline IGMP-Out-IPv4 Controller (Pps)"
    ::=  { rsImportBaselineBdosEntry 31 }



rsImportBaselineBdosTcpSynInPpsIpv4 OBJECT-TYPE
    SYNTAX Counter64
    ACCESS  read-write
    STATUS  mandatory
    DESCRIPTION
       "Import BDoS Baseline TCP-SYN-In-IPv4 Controller (Pps)"
    ::=  { rsImportBaselineBdosEntry 32 }

rsImportBaselineBdosTcpSynOutPpsIpv4 OBJECT-TYPE
    SYNTAX Counter64
    ACCESS  read-write
    STATUS  mandatory
    DESCRIPTION
       "Import BDoS Baseline TCP-SYN-Out-IPv4 Controller (Pps)"
    ::=  { rsImportBaselineBdosEntry 33 }

rsImportBaselineBdosTcpRstInPpsIpv4 OBJECT-TYPE
    SYNTAX Counter64
    ACCESS  read-write
    STATUS  mandatory
    DESCRIPTION
       "Import BDoS Baseline TCP-RST-In-IPv4 Controller (Pps)"
    ::=  { rsImportBaselineBdosEntry 34 }

rsImportBaselineBdosTcpRstOutPpsIpv4 OBJECT-TYPE
    SYNTAX Counter64
    ACCESS  read-write
    STATUS  mandatory
    DESCRIPTION
       "Import BDoS Baseline TCP-RST-Out-IPv4 Controller (Pps)"
    ::=  { rsImportBaselineBdosEntry 35 }



rsImportBaselineBdosTcpAckInPpsIpv4 OBJECT-TYPE
    SYNTAX Counter64
    ACCESS  read-write
    STATUS  mandatory
    DESCRIPTION
       "Import BDoS Baseline TCP-ACK-In-IPv4 Controller (Pps)"
    ::=  { rsImportBaselineBdosEntry 36 }

rsImportBaselineBdosTcpAckOutPpsIpv4 OBJECT-TYPE
    SYNTAX Counter64
    ACCESS  read-write
    STATUS  mandatory
    DESCRIPTION
       "Import BDoS Baseline TCP-ACK-Out-IPv4 Controller (Pps)"
    ::=  { rsImportBaselineBdosEntry 37 }

rsImportBaselineBdosTcpAckPshInPpsIpv4 OBJECT-TYPE
    SYNTAX Counter64
    ACCESS  read-write
    STATUS  mandatory
    DESCRIPTION
       "Import BDoS Baseline TCP-ACK-PSH-In-IPv4 Controller (Pps)"
    ::=  { rsImportBaselineBdosEntry 38 }

rsImportBaselineBdosTcpAckPshOutPpsIpv4 OBJECT-TYPE
    SYNTAX Counter64
    ACCESS  read-write
    STATUS  mandatory
    DESCRIPTION
       "Import BDoS Baseline TCP-ACK-PSH-Out-IPv4 Controller (Pps)"
    ::=  { rsImportBaselineBdosEntry 39 }

rsImportBaselineBdosTcpAckFinInPpsIpv4 OBJECT-TYPE
    SYNTAX Counter64
    ACCESS  read-write
    STATUS  mandatory
    DESCRIPTION
       "Import BDoS Baseline TCP-ACK-FIN-In-IPv4 Controller (Pps)"
    ::=  { rsImportBaselineBdosEntry 40 }

rsImportBaselineBdosTcpAckFinOutPpsIpv4 OBJECT-TYPE
    SYNTAX Counter64
    ACCESS  read-write
    STATUS  mandatory
    DESCRIPTION
       "Import BDoS Baseline TCP-ACK-FIN-Out-IPv4 Controller (Pps)"
    ::=  { rsImportBaselineBdosEntry 41 }



rsImportBaselineBdosTcpSynAckInPpsIpv4 OBJECT-TYPE
    SYNTAX Counter64
    ACCESS  read-write
    STATUS  mandatory
    DESCRIPTION
       "Import BDoS Baseline TCP-SYN-ACK-In-IPv4 Controller (Pps)"
    ::=  { rsImportBaselineBdosEntry 42 }

rsImportBaselineBdosTcpSynAckOutPpsIpv4 OBJECT-TYPE
    SYNTAX Counter64
    ACCESS  read-write
    STATUS  mandatory
    DESCRIPTION
       "Import BDoS Baseline TCP-SYN-ACK-In-IPv4 Controller (Pps)"
    ::=  { rsImportBaselineBdosEntry 43 }

rsImportBaselineBdosTcpFragInPpsIpv4 OBJECT-TYPE
    SYNTAX Counter64
    ACCESS  read-write
    STATUS  mandatory
    DESCRIPTION
       "Import BDoS Baseline TCP-FRAG-In-IPv4 Controller (Pps)"
    ::=  { rsImportBaselineBdosEntry 44 }

rsImportBaselineBdosTcpFragOutPpsIpv4 OBJECT-TYPE
    SYNTAX Counter64
    ACCESS  read-write
    STATUS  mandatory
    DESCRIPTION
       "Import BDoS Baseline TCP-FRAG-In-IPv4 Controller (Pps)"
    ::=  { rsImportBaselineBdosEntry 45 }



rsImportBaselineBdosIcmpInBpsIpv6 OBJECT-TYPE
    SYNTAX Counter64
    ACCESS  read-write
    STATUS  mandatory
    DESCRIPTION
       "Import BDoS Baseline ICMP-In-IPv6 Controller (Bps)"
    ::=  { rsImportBaselineBdosEntry 46 }

rsImportBaselineBdosIcmpOutBpsIpv6 OBJECT-TYPE
    SYNTAX Counter64
    ACCESS  read-write
    STATUS  mandatory
    DESCRIPTION
       "Import BDoS Baseline ICMP-Out-IPv6 Controller (Bps)"
    ::=  { rsImportBaselineBdosEntry 47 }

rsImportBaselineBdosTcpInBpsIpv6 OBJECT-TYPE
    SYNTAX Counter64
    ACCESS  read-write
    STATUS  mandatory
    DESCRIPTION
       "Import BDoS Baseline TCP-In-IPv6 Controller (Bps)"
    ::=  { rsImportBaselineBdosEntry 48 }

rsImportBaselineBdosTcpOutBpsIpv6 OBJECT-TYPE
    SYNTAX Counter64
    ACCESS  read-write
    STATUS  mandatory
    DESCRIPTION
       "Import BDoS Baseline TCP-Out-IPv6 Controller (Bps)"
    ::=  { rsImportBaselineBdosEntry 49 }

rsImportBaselineBdosUdpInBpsIpv6 OBJECT-TYPE
    SYNTAX Counter64
    ACCESS  read-write
    STATUS  mandatory
    DESCRIPTION
       "Import BDoS Baseline UDP-In-IPv6 Controller (Bps)"
    ::=  { rsImportBaselineBdosEntry 50 }

rsImportBaselineBdosUdpOutBpsIpv6 OBJECT-TYPE
    SYNTAX Counter64
    ACCESS  read-write
    STATUS  mandatory
    DESCRIPTION
       "Import BDoS Baseline UDP-Out-IPv6 Controller (Bps)"
    ::=  { rsImportBaselineBdosEntry 51 }

rsImportBaselineBdosIgmpInBpsIpv6 OBJECT-TYPE
    SYNTAX Counter64
    ACCESS  read-write
    STATUS  mandatory
    DESCRIPTION
       "Import BDoS Baseline IGMP-In-IPv6 Controller (Bps)"
    ::=  { rsImportBaselineBdosEntry 52 }

rsImportBaselineBdosIgmpOutBpsIpv6 OBJECT-TYPE
    SYNTAX Counter64
    ACCESS  read-write
    STATUS  mandatory
    DESCRIPTION
       "Import BDoS Baseline IGMP-Out-IPv6 Controller (Bps)"
    ::=  { rsImportBaselineBdosEntry 53 }




rsImportBaselineBdosTcpSynInBpsIpv6 OBJECT-TYPE
    SYNTAX Counter64
    ACCESS  read-write
    STATUS  mandatory
    DESCRIPTION
       "Import BDoS Baseline TCP-SYN-In-IPv6 Controller (Bps)"
    ::=  { rsImportBaselineBdosEntry 54 }

rsImportBaselineBdosTcpSynOutBpsIpv6 OBJECT-TYPE
    SYNTAX Counter64
    ACCESS  read-write
    STATUS  mandatory
    DESCRIPTION
       "Import BDoS Baseline TCP-SYN-Out-IPv6 Controller (Bps)"
    ::=  { rsImportBaselineBdosEntry 55 }

rsImportBaselineBdosTcpRstInBpsIpv6 OBJECT-TYPE
    SYNTAX Counter64
    ACCESS  read-write
    STATUS  mandatory
    DESCRIPTION
       "Import BDoS Baseline TCP-RST-In-IPv6 Controller (Bps)"
    ::=  { rsImportBaselineBdosEntry 56 }

rsImportBaselineBdosTcpRstOutBpsIpv6 OBJECT-TYPE
    SYNTAX Counter64
    ACCESS  read-write
    STATUS  mandatory
    DESCRIPTION
       "Import BDoS Baseline TCP-RST-Out-IPv6 Controller (Bps)"
    ::=  { rsImportBaselineBdosEntry 57 }



rsImportBaselineBdosTcpAckInBpsIpv6 OBJECT-TYPE
    SYNTAX Counter64
    ACCESS  read-write
    STATUS  mandatory
    DESCRIPTION
       "Import BDoS Baseline TCP-ACK-In-IPv6 Controller (Bps)"
    ::=  { rsImportBaselineBdosEntry 58 }

rsImportBaselineBdosTcpAckOutBpsIpv6 OBJECT-TYPE
    SYNTAX Counter64
    ACCESS  read-write
    STATUS  mandatory
    DESCRIPTION
       "Import BDoS Baseline TCP-ACK-Out-IPv6 Controller (Bps)"
    ::=  { rsImportBaselineBdosEntry 59 }

rsImportBaselineBdosTcpAckPshInBpsIpv6 OBJECT-TYPE
    SYNTAX Counter64
    ACCESS  read-write
    STATUS  mandatory
    DESCRIPTION
       "Import BDoS Baseline TCP-ACK-PSH-In-IPv6 Controller (Bps)"
    ::=  { rsImportBaselineBdosEntry 60 }

rsImportBaselineBdosTcpAckPshOutBpsIpv6 OBJECT-TYPE
    SYNTAX Counter64
    ACCESS  read-write
    STATUS  mandatory
    DESCRIPTION
       "Import BDoS Baseline TCP-ACK-PSH-Out-IPv6 Controller (Bps)"
    ::=  { rsImportBaselineBdosEntry 61 }

rsImportBaselineBdosTcpAckFinInBpsIpv6 OBJECT-TYPE
    SYNTAX Counter64
    ACCESS  read-write
    STATUS  mandatory
    DESCRIPTION
       "Import BDoS Baseline TCP-ACK-FIN-In-IPv6 Controller (Bps)"
    ::=  { rsImportBaselineBdosEntry 62 }

rsImportBaselineBdosTcpAckFinOutBpsIpv6 OBJECT-TYPE
    SYNTAX Counter64
    ACCESS  read-write
    STATUS  mandatory
    DESCRIPTION
       "Import BDoS Baseline TCP-ACK-FIN-Out-IPv6 Controller (Bps)"
    ::=  { rsImportBaselineBdosEntry 63 }


rsImportBaselineBdosTcpSynAckInBpsIpv6 OBJECT-TYPE
    SYNTAX Counter64
    ACCESS  read-write
    STATUS  mandatory
    DESCRIPTION
       "Import BDoS Baseline TCP-SYN-ACK-In-IPv6 Controller (Bps)"
    ::=  { rsImportBaselineBdosEntry 64 }

rsImportBaselineBdosTcpSynAckOutBpsIpv6 OBJECT-TYPE
    SYNTAX Counter64
    ACCESS  read-write
    STATUS  mandatory
    DESCRIPTION
       "Import BDoS Baseline TCP-SYN-ACK-Out-IPv6 Controller (Bps)"
    ::=  { rsImportBaselineBdosEntry 65 }

rsImportBaselineBdosTcpFragInBpsIpv6 OBJECT-TYPE
    SYNTAX Counter64
    ACCESS  read-write
    STATUS  mandatory
    DESCRIPTION
       "Import BDoS Baseline TCP-FRAG-In-IPv6 Controller (Bps)"
    ::=  { rsImportBaselineBdosEntry 66 }

rsImportBaselineBdosTcpFragOutBpsIpv6 OBJECT-TYPE
    SYNTAX Counter64
    ACCESS  read-write
    STATUS  mandatory
    DESCRIPTION
       "Import BDoS Baseline TCP-FRAG-Out-IPv6 Controller (Bps)"
    ::=  { rsImportBaselineBdosEntry 67 }



rsImportBaselineBdosIcmpInPpsIpv6 OBJECT-TYPE
    SYNTAX Counter64
    ACCESS  read-write
    STATUS  mandatory
    DESCRIPTION
       "Import BDoS Baseline ICMP-In-IPv6 Controller (Pps)"
    ::=  { rsImportBaselineBdosEntry 68 }

rsImportBaselineBdosIcmpOutPpsIpv6 OBJECT-TYPE
    SYNTAX Counter64
    ACCESS  read-write
    STATUS  mandatory
    DESCRIPTION
       "Import BDoS Baseline ICMP-Out-IPv6 Controller (Pps)"
    ::=  { rsImportBaselineBdosEntry 69 }

rsImportBaselineBdosTcpInPpsIpv6 OBJECT-TYPE
    SYNTAX Counter64
    ACCESS  read-write
    STATUS  mandatory
    DESCRIPTION
       "Import BDoS Baseline TCP-In-IPv6 Controller (Pps)"
    ::=  { rsImportBaselineBdosEntry 70 }

rsImportBaselineBdosTcpOutPpsIpv6 OBJECT-TYPE
    SYNTAX Counter64
    ACCESS  read-write
    STATUS  mandatory
    DESCRIPTION
       "Import BDoS Baseline TCP-Out-IPv6 Controller (Pps)"
    ::=  { rsImportBaselineBdosEntry 71 }

rsImportBaselineBdosUdpInPpsIpv6 OBJECT-TYPE
    SYNTAX Counter64
    ACCESS  read-write
    STATUS  mandatory
    DESCRIPTION
       "Import BDoS Baseline UDP-In-IPv6 Controller (Pps)"
    ::=  { rsImportBaselineBdosEntry 72 }

rsImportBaselineBdosUdpOutPpsIpv6 OBJECT-TYPE
    SYNTAX Counter64
    ACCESS  read-write
    STATUS  mandatory
    DESCRIPTION
       "Import BDoS Baseline UDP-Outn-IPv6 Controller (Pps)"
    ::=  { rsImportBaselineBdosEntry 73 }

rsImportBaselineBdosIgmpInPpsIpv6 OBJECT-TYPE
    SYNTAX Counter64
    ACCESS  read-write
    STATUS  mandatory
    DESCRIPTION
       "Import BDoS Baseline IGMP-In-IPv6 Controller (Pps)"
    ::=  { rsImportBaselineBdosEntry 74 }

rsImportBaselineBdosIgmpOutPpsIpv6 OBJECT-TYPE
    SYNTAX Counter64
    ACCESS  read-write
    STATUS  mandatory
    DESCRIPTION
       "Import BDoS Baseline IGMP-Out-IPv6 Controller (Pps)"
    ::=  { rsImportBaselineBdosEntry 75 }


rsImportBaselineBdosTcpSynInPpsIpv6 OBJECT-TYPE
    SYNTAX Counter64
    ACCESS  read-write
    STATUS  mandatory
    DESCRIPTION
       "Import BDoS Baseline TCP-SYN-In-IPv6 Controller (Pps)"
    ::=  { rsImportBaselineBdosEntry 76 }

rsImportBaselineBdosTcpSynOutPpsIpv6 OBJECT-TYPE
    SYNTAX Counter64
    ACCESS  read-write
    STATUS  mandatory
    DESCRIPTION
       "Import BDoS Baseline TCP-SYN-Out-IPv6 Controller (Pps)"
    ::=  { rsImportBaselineBdosEntry 77 }

rsImportBaselineBdosTcpRstInPpsIpv6 OBJECT-TYPE
    SYNTAX Counter64
    ACCESS  read-write
    STATUS  mandatory
    DESCRIPTION
       "Import BDoS Baseline TCP-RST-In-IPv6 Controller (Pps)"
    ::=  { rsImportBaselineBdosEntry 78 }

rsImportBaselineBdosTcpRstOutPpsIpv6 OBJECT-TYPE
    SYNTAX Counter64
    ACCESS  read-write
    STATUS  mandatory
    DESCRIPTION
       "Import BDoS Baseline TCP-RST-Out-IPv6 Controller (Pps)"
    ::=  { rsImportBaselineBdosEntry 79 }

rsImportBaselineBdosTcpAckInPpsIpv6 OBJECT-TYPE
    SYNTAX Counter64
    ACCESS  read-write
    STATUS  mandatory
    DESCRIPTION
       "Import BDoS Baseline TCP-ACK-In-IPv4 Controller (Pps)"
    ::=  { rsImportBaselineBdosEntry 80 }

rsImportBaselineBdosTcpAckOutPpsIpv6 OBJECT-TYPE
    SYNTAX Counter64
    ACCESS  read-write
    STATUS  mandatory
    DESCRIPTION
       "Import BDoS Baseline TCP-ACK-Out-IPv4 Controller (Pps)"
    ::=  { rsImportBaselineBdosEntry 81 }

rsImportBaselineBdosTcpAckPshInPpsIpv6 OBJECT-TYPE
    SYNTAX Counter64
    ACCESS  read-write
    STATUS  mandatory
    DESCRIPTION
       "Import BDoS Baseline TCP-ACK-PSH-In-IPv6 Controller (Pps)"
    ::=  { rsImportBaselineBdosEntry 82 }

rsImportBaselineBdosTcpAckPshOutPpsIpv6 OBJECT-TYPE
    SYNTAX Counter64
    ACCESS  read-write
    STATUS  mandatory
    DESCRIPTION
       "Import BDoS Baseline TCP-ACK-PSH-Out-IPv6 Controller (Pps)"
    ::=  { rsImportBaselineBdosEntry 83 }

rsImportBaselineBdosTcpAckFinInPpsIpv6 OBJECT-TYPE
    SYNTAX Counter64
    ACCESS  read-write
    STATUS  mandatory
    DESCRIPTION
       "Import BDoS Baseline TCP-ACK-FIN-In-IPv6 Controller (Pps)"
    ::=  { rsImportBaselineBdosEntry 84 }

rsImportBaselineBdosTcpAckFinOutPpsIpv6 OBJECT-TYPE
    SYNTAX Counter64
    ACCESS  read-write
    STATUS  mandatory
    DESCRIPTION
       "Import BDoS Baseline TCP-ACK-FIN-Out-IPv6 Controller (Pps)"
    ::=  { rsImportBaselineBdosEntry 85 }


rsImportBaselineBdosTcpSynAckInPpsIpv6 OBJECT-TYPE
    SYNTAX Counter64
    ACCESS  read-write
    STATUS  mandatory
    DESCRIPTION
       "Import BDoS Baseline TCP-SYN-ACK-In-IPv6 Controller (Pps)"
    ::=  { rsImportBaselineBdosEntry 86 }

rsImportBaselineBdosTcpSynAckOutPpsIpv6 OBJECT-TYPE
    SYNTAX Counter64
    ACCESS  read-write
    STATUS  mandatory
    DESCRIPTION
       "Import BDoS Baseline TCP-SYN-ACK-Out-IPv6 Controller (Pps)"
    ::=  { rsImportBaselineBdosEntry 87 }

rsImportBaselineBdosTcpFragInPpsIpv6 OBJECT-TYPE
    SYNTAX Counter64
    ACCESS  read-write
    STATUS  mandatory
    DESCRIPTION
       "Import BDoS Baseline TCP-FRAG-In-IPv6 Controller (Pps)"
    ::=  { rsImportBaselineBdosEntry 88 }

rsImportBaselineBdosTcpFragOutPpsIpv6 OBJECT-TYPE
    SYNTAX Counter64
    ACCESS  read-write
    STATUS  mandatory
    DESCRIPTION
       "Import BDoS Baseline TCP-FRAG-Out-IPv6 Controller (Pps)"
    ::=  { rsImportBaselineBdosEntry 89 }


rsImportBaselineBdosUdpFragInBpsIpv4 OBJECT-TYPE
    SYNTAX Counter64
    ACCESS  read-write
    STATUS  mandatory
    DESCRIPTION
       "Import BDoS Baseline UDP-FRAG-In-IPv4 Controller (Bps)"
    ::=  { rsImportBaselineBdosEntry 90 }

rsImportBaselineBdosUdpFragOutBpsIpv4 OBJECT-TYPE
    SYNTAX Counter64
    ACCESS  read-write
    STATUS  mandatory
    DESCRIPTION
       "Import BDoS Baseline UDP-FRAG-Out-IPv4 Controller (Bps)"
    ::=  { rsImportBaselineBdosEntry 91 }

rsImportBaselineBdosUdpFragInPpsIpv4 OBJECT-TYPE
    SYNTAX Counter64
    ACCESS  read-write
    STATUS  mandatory
    DESCRIPTION
       "Import BDoS Baseline UDP-FRAG-In-IPv4 Controller (Pps)"
    ::=  { rsImportBaselineBdosEntry 92 }

rsImportBaselineBdosUdpFragOutPpsIpv4 OBJECT-TYPE
    SYNTAX Counter64
    ACCESS  read-write
    STATUS  mandatory
    DESCRIPTION
       "Import BDoS Baseline UDP-FRAG-Out-IPv4 Controller (Pps)"
    ::=  { rsImportBaselineBdosEntry 93 }

rsImportBaselineBdosUdpFragInBpsIpv6 OBJECT-TYPE
    SYNTAX Counter64
    ACCESS  read-write
    STATUS  mandatory
    DESCRIPTION
       "Import BDoS Baseline UDP-FRAG-In-IPv6 Controller (Bps)"
    ::=  { rsImportBaselineBdosEntry 94 }

rsImportBaselineBdosUdpFragOutBpsIpv6 OBJECT-TYPE
    SYNTAX Counter64
    ACCESS  read-write
    STATUS  mandatory
    DESCRIPTION
       "Import BDoS Baseline UDP-FRAG-Out-IPv6 Controller (Bps)"
    ::=  { rsImportBaselineBdosEntry 95 }

rsImportBaselineBdosUdpFragInPpsIpv6 OBJECT-TYPE
    SYNTAX Counter64
    ACCESS  read-write
    STATUS  mandatory
    DESCRIPTION
       "Import BDoS Baseline UDP-FRAG-In-IPv6 Controller (Pps)"
    ::=  { rsImportBaselineBdosEntry 96 }

rsImportBaselineBdosUdpFragOutPpsIpv6 OBJECT-TYPE
    SYNTAX Counter64
    ACCESS  read-write
    STATUS  mandatory
    DESCRIPTION
       "Import BDoS Baseline UDP-FRAG-Out-IPv6 Controller (Pps)"
    ::=  { rsImportBaselineBdosEntry 97 }


-- DNS Import Baseline
--


rsImportBaselineDnsTable OBJECT-TYPE
    SYNTAX SEQUENCE OF RsImportBaselineDnsEntry
    ACCESS not-accessible
    STATUS  mandatory
    DESCRIPTION
      "Table containing the baseline import request."
    ::=  {rsImportExport 5}

rsImportBaselineDnsEntry OBJECT-TYPE
    SYNTAX RsImportBaselineDnsEntry
    ACCESS not-accessible
    STATUS  mandatory
    DESCRIPTION
       "The row definition for this table."
    INDEX { rsImportBaselineDnsName }
    ::=  { rsImportBaselineDnsTable 1 }

RsImportBaselineDnsEntry ::= SEQUENCE {

    rsImportBaselineDnsName				DisplayString,

	rsImportBaselineDnsMxInIpv4			INTEGER,
	rsImportBaselineDnsMxOutIpv4			INTEGER,

	rsImportBaselineDnsPtrInIpv4			INTEGER,
	rsImportBaselineDnsPtrOutIpv4			INTEGER,

	rsImportBaselineDnsAaaaInIpv4			INTEGER,
	rsImportBaselineDnsAaaaOutIpv4			INTEGER,

	rsImportBaselineDnsTextInIpv4			INTEGER,
	rsImportBaselineDnsTextOutIpv4			INTEGER,

	rsImportBaselineDnsSoaInIpv4			INTEGER,
	rsImportBaselineDnsSoaOutIpv4			INTEGER,

	rsImportBaselineDnsNaptrInIpv4			INTEGER,
	rsImportBaselineDnsNaptrOutIpv4			INTEGER,

	rsImportBaselineDnsSrcInIpv4			INTEGER,
	rsImportBaselineDnsSrcOutIpv4			INTEGER,

	rsImportBaselineDnsOtherInIpv4			INTEGER,
	rsImportBaselineDnsOtherOutIpv4			INTEGER,

	rsImportBaselineDnsAInIpv4			INTEGER,
	rsImportBaselineDnsAOutIpv4			INTEGER,


	rsImportBaselineDnsMxInIpv6			INTEGER,
	rsImportBaselineDnsMxOutIpv6			INTEGER,

	rsImportBaselineDnsPtrInIpv6			INTEGER,
	rsImportBaselineDnsPtrOutIpv6			INTEGER,

	rsImportBaselineDnsAaaaInIpv6			INTEGER,
	rsImportBaselineDnsAaaaOutIpv6			INTEGER,

	rsImportBaselineDnsTextInIpv6			INTEGER,
	rsImportBaselineDnsTextOutIpv6			INTEGER,

	rsImportBaselineDnsSoaInIpv6			INTEGER,
	rsImportBaselineDnsSoaOutIpv6			INTEGER,

	rsImportBaselineDnsNaptrInIpv6				INTEGER,
	rsImportBaselineDnsNaptrOutIpv6			INTEGER,

	rsImportBaselineDnsSrcInIpv6			INTEGER,
	rsImportBaselineDnsSrcOutIpv6			INTEGER,

	rsImportBaselineDnsOtherInIpv6			INTEGER,
	rsImportBaselineDnsOtherOutIpv6			INTEGER,

	rsImportBaselineDnsAInIpv6			INTEGER,
	rsImportBaselineDnsAOutIpv6			INTEGER,

	rsImportBaselineDnsMxInPpsIpv4			INTEGER,
	rsImportBaselineDnsMxOutPpsIpv4			INTEGER,

	rsImportBaselineDnsPtrInPpsIpv4			INTEGER,
	rsImportBaselineDnsPtrOutPpsIpv4		INTEGER,

	rsImportBaselineDnsAaaaInPpsIpv4		INTEGER,
	rsImportBaselineDnsAaaaOutPpsIpv4		INTEGER,

	rsImportBaselineDnsTextInPpsIpv4		INTEGER,
	rsImportBaselineDnsTextOutPpsIpv4		INTEGER,

	rsImportBaselineDnsSoaInPpsIpv4			INTEGER,
	rsImportBaselineDnsSoaOutPpsIpv4		INTEGER,

	rsImportBaselineDnsNaptrInPpsIpv4		INTEGER,
	rsImportBaselineDnsNaptrOutPpsIpv4		INTEGER,

	rsImportBaselineDnsSrcInPpsIpv4			INTEGER,
	rsImportBaselineDnsSrcOutPpsIpv4		INTEGER,

	rsImportBaselineDnsOtherInPpsIpv4		INTEGER,
	rsImportBaselineDnsOtherOutPpsIpv4		INTEGER,

	rsImportBaselineDnsAInPpsIpv4			INTEGER,
	rsImportBaselineDnsAOutPpsIpv4			INTEGER,

	rsImportBaselineDnsMxInPpsIpv6			INTEGER,
	rsImportBaselineDnsMxOutPpsIpv6			INTEGER,

	rsImportBaselineDnsPtrInPpsIpv6			INTEGER,
	rsImportBaselineDnsPtrOutPpsIpv6		INTEGER,

	rsImportBaselineDnsAaaaInPpsIpv6		INTEGER,
	rsImportBaselineDnsAaaaOutPpsIpv6		INTEGER,

	rsImportBaselineDnsTextInPpsIpv6		INTEGER,
	rsImportBaselineDnsTextOutPpsIpv6		INTEGER,

	rsImportBaselineDnsSoaInPpsIpv6			INTEGER,
	rsImportBaselineDnsSoaOutPpsIpv6		INTEGER,

	rsImportBaselineDnsNaptrInPpsIpv6		INTEGER,
	rsImportBaselineDnsNaptrOutPpsIpv6		INTEGER,

	rsImportBaselineDnsSrcInPpsIpv6			INTEGER,
	rsImportBaselineDnsSrcOutPpsIpv6		INTEGER,

	rsImportBaselineDnsOtherInPpsIpv6		INTEGER,
	rsImportBaselineDnsOtherOutPpsIpv6		INTEGER,

	rsImportBaselineDnsAInPpsIpv6			INTEGER,
	rsImportBaselineDnsAOutPpsIpv6			INTEGER

}


rsImportBaselineDnsName OBJECT-TYPE
    SYNTAX DisplayString (SIZE(1..64))
    ACCESS  read-write
    STATUS  mandatory
    DESCRIPTION
       "Import DNS Baseline Network Policy Name"
    ::=  { rsImportBaselineDnsEntry 1 }


rsImportBaselineDnsMxInIpv4 OBJECT-TYPE
    SYNTAX INTEGER
    ACCESS  read-write
    STATUS  mandatory
    DESCRIPTION
       "Import DNS Baseline MX-In-IPv4 Controller (Bps)"
    ::=  { rsImportBaselineDnsEntry 2 }

rsImportBaselineDnsMxOutIpv4 OBJECT-TYPE
    SYNTAX INTEGER
    ACCESS  read-write
    STATUS  mandatory
    DESCRIPTION
       "Import DNS Baseline MX-Out-IPv4 Controller (Bps)"
    ::=  { rsImportBaselineDnsEntry 3 }


rsImportBaselineDnsPtrInIpv4 OBJECT-TYPE
    SYNTAX INTEGER
    ACCESS  read-write
    STATUS  mandatory
    DESCRIPTION
       "Import DNS Baseline PTR-In-IPv4 Controller (Bps)"
    ::=  { rsImportBaselineDnsEntry 4 }

rsImportBaselineDnsPtrOutIpv4 OBJECT-TYPE
    SYNTAX INTEGER
    ACCESS  read-write
    STATUS  mandatory
    DESCRIPTION
       "Import DNS Baseline PTR-Out-IPv4 Controller (Bps)"
    ::=  { rsImportBaselineDnsEntry 5 }


rsImportBaselineDnsAaaaInIpv4 OBJECT-TYPE
    SYNTAX INTEGER
    ACCESS  read-write
    STATUS  mandatory
    DESCRIPTION
       "Import DNS Baseline AAAA-In-IPv4 Controller (Bps)"
    ::=  { rsImportBaselineDnsEntry 6 }

rsImportBaselineDnsAaaaOutIpv4 OBJECT-TYPE
    SYNTAX INTEGER
    ACCESS  read-write
    STATUS  mandatory
    DESCRIPTION
       "Import DNS Baseline AAAA-Out-IPv4 Controller (Bps)"
    ::=  { rsImportBaselineDnsEntry 7 }


rsImportBaselineDnsTextInIpv4 OBJECT-TYPE
    SYNTAX INTEGER
    ACCESS  read-write
    STATUS  mandatory
    DESCRIPTION
       "Import DNS Baseline TEXT-In-IPv4 Controller (Bps)"
    ::=  { rsImportBaselineDnsEntry 8 }

rsImportBaselineDnsTextOutIpv4 OBJECT-TYPE
    SYNTAX INTEGER
    ACCESS  read-write
    STATUS  mandatory
    DESCRIPTION
       "Import DNS Baseline TEXT-Out-IPv4 Controller (Bps)"
    ::=  { rsImportBaselineDnsEntry 9 }

rsImportBaselineDnsSoaInIpv4 OBJECT-TYPE
    SYNTAX INTEGER
    ACCESS  read-write
    STATUS  mandatory
    DESCRIPTION
       "Import DNS Baseline SOA-In-IPv4 Controller (Bps)"
    ::=  { rsImportBaselineDnsEntry 10 }

rsImportBaselineDnsSoaOutIpv4 OBJECT-TYPE
    SYNTAX INTEGER
    ACCESS  read-write
    STATUS  mandatory
    DESCRIPTION
       "Import DNS Baseline SOA-Out-IPv4 Controller (Bps)"
    ::=  { rsImportBaselineDnsEntry 11 }


rsImportBaselineDnsNaptrInIpv4 OBJECT-TYPE
    SYNTAX INTEGER
    ACCESS  read-write
    STATUS  mandatory
    DESCRIPTION
       "Import DNS Baseline NAPTR-In-IPv4 Controller (Bps)"
    ::=  { rsImportBaselineDnsEntry 12 }

rsImportBaselineDnsNaptrOutIpv4 OBJECT-TYPE
    SYNTAX INTEGER
    ACCESS  read-write
    STATUS  mandatory
    DESCRIPTION
       "Import DNS Baseline NAPTR-Out-IPv4 Controller (Bps)"
    ::=  { rsImportBaselineDnsEntry 13 }



rsImportBaselineDnsSrcInIpv4 OBJECT-TYPE
    SYNTAX INTEGER
    ACCESS  read-write
    STATUS  mandatory
    DESCRIPTION
       "Import DNS Baseline SRC-In-IPv4 Controller (Bps)"
    ::=  { rsImportBaselineDnsEntry 14 }

rsImportBaselineDnsSrcOutIpv4 OBJECT-TYPE
    SYNTAX INTEGER
    ACCESS  read-write
    STATUS  mandatory
    DESCRIPTION
       "Import DNS Baseline SRC-Out-IPv4 Controller (Bps)"
    ::=  { rsImportBaselineDnsEntry 15 }

rsImportBaselineDnsOtherInIpv4 OBJECT-TYPE
    SYNTAX INTEGER
    ACCESS  read-write
    STATUS  mandatory
    DESCRIPTION
       "Import DNS Baseline OTHER-In-IPv4 Controller (Bps)"
    ::=  { rsImportBaselineDnsEntry 16 }

rsImportBaselineDnsOtherOutIpv4 OBJECT-TYPE
    SYNTAX INTEGER
    ACCESS  read-write
    STATUS  mandatory
    DESCRIPTION
       "Import DNS Baseline OTHER-Out-IPv4 Controller (Bps)"
    ::=  { rsImportBaselineDnsEntry 17 }


rsImportBaselineDnsAInIpv4 OBJECT-TYPE
    SYNTAX INTEGER
    ACCESS  read-write
    STATUS  mandatory
    DESCRIPTION
       "Import DNS Baseline A-In-IPv4 Controller (Bps)"
    ::=  { rsImportBaselineDnsEntry 18 }

rsImportBaselineDnsAOutIpv4 OBJECT-TYPE
    SYNTAX INTEGER
    ACCESS  read-write
    STATUS  mandatory
    DESCRIPTION
       "Import DNS Baseline A-Out-IPv4 Controller (Bps)"
    ::=  { rsImportBaselineDnsEntry 19 }


rsImportBaselineDnsMxInIpv6 OBJECT-TYPE
    SYNTAX INTEGER
    ACCESS  read-write
    STATUS  mandatory
    DESCRIPTION
       "Import DNS Baseline MX-In-IPv6 Controller (Bps)"
    ::=  { rsImportBaselineDnsEntry 20 }

rsImportBaselineDnsMxOutIpv6 OBJECT-TYPE
    SYNTAX INTEGER
    ACCESS  read-write
    STATUS  mandatory
    DESCRIPTION
       "Import DNS Baseline MX-Out-IPv6 Controller (Bps)"
    ::=  { rsImportBaselineDnsEntry 21 }


rsImportBaselineDnsPtrInIpv6 OBJECT-TYPE
    SYNTAX INTEGER
    ACCESS  read-write
    STATUS  mandatory
    DESCRIPTION
       "Import DNS Baseline PTR-In-IPv6 Controller (Bps)"
    ::=  { rsImportBaselineDnsEntry 22 }

rsImportBaselineDnsPtrOutIpv6 OBJECT-TYPE
    SYNTAX INTEGER
    ACCESS  read-write
    STATUS  mandatory
    DESCRIPTION
       "Import DNS Baseline PTR-Out-IPv6 Controller (Bps)"
    ::=  { rsImportBaselineDnsEntry 23 }


rsImportBaselineDnsAaaaInIpv6 OBJECT-TYPE
    SYNTAX INTEGER
    ACCESS  read-write
    STATUS  mandatory
    DESCRIPTION
       "Import DNS Baseline AAAA-In-IPv6 Controller (Bps)"
    ::=  { rsImportBaselineDnsEntry 24 }

rsImportBaselineDnsAaaaOutIpv6 OBJECT-TYPE
    SYNTAX INTEGER
    ACCESS  read-write
    STATUS  mandatory
    DESCRIPTION
       "Import DNS Baseline AAAA-Out-IPv6 Controller (Bps)"
    ::=  { rsImportBaselineDnsEntry 25 }


rsImportBaselineDnsTextInIpv6 OBJECT-TYPE
    SYNTAX INTEGER
    ACCESS  read-write
    STATUS  mandatory
    DESCRIPTION
       "Import DNS Baseline TEXT-In-IPv6 Controller (Bps)"
    ::=  { rsImportBaselineDnsEntry 26 }

rsImportBaselineDnsTextOutIpv6 OBJECT-TYPE
    SYNTAX INTEGER
    ACCESS  read-write
    STATUS  mandatory
    DESCRIPTION
       "Import DNS Baseline TEXT-Out-IPv6 Controller (Bps)"
    ::=  { rsImportBaselineDnsEntry 27}



rsImportBaselineDnsSoaInIpv6 OBJECT-TYPE
    SYNTAX INTEGER
    ACCESS  read-write
    STATUS  mandatory
    DESCRIPTION
       "Import DNS Baseline SOA-In-IPv6 Controller (Bps)"
    ::=  { rsImportBaselineDnsEntry 28 }

rsImportBaselineDnsSoaOutIpv6 OBJECT-TYPE
    SYNTAX INTEGER
    ACCESS  read-write
    STATUS  mandatory
    DESCRIPTION
       "Import DNS Baseline SOA-Out-IPv6 Controller (Bps)"
    ::=  { rsImportBaselineDnsEntry 29 }


rsImportBaselineDnsNaptrInIpv6 OBJECT-TYPE
    SYNTAX INTEGER
    ACCESS  read-write
    STATUS  mandatory
    DESCRIPTION
       "Import DNS Baseline NAPTR-In-IPv6 Controller (Bps)"
    ::=  { rsImportBaselineDnsEntry 30 }

rsImportBaselineDnsNaptrOutIpv6 OBJECT-TYPE
    SYNTAX INTEGER
    ACCESS  read-write
    STATUS  mandatory
    DESCRIPTION
       "Import DNS Baseline NAPTR-Out-IPv6 Controller (Bps)"
    ::=  { rsImportBaselineDnsEntry 31 }



rsImportBaselineDnsSrcInIpv6 OBJECT-TYPE
    SYNTAX INTEGER
    ACCESS  read-write
    STATUS  mandatory
    DESCRIPTION
       "Import DNS Baseline SRC-In-IPv6 Controller (Bps)"
    ::=  { rsImportBaselineDnsEntry 32 }

rsImportBaselineDnsSrcOutIpv6 OBJECT-TYPE
    SYNTAX INTEGER
    ACCESS  read-write
    STATUS  mandatory
    DESCRIPTION
       "Import DNS Baseline SRC-Out-IPv6 Controller (Bps)"
    ::=  { rsImportBaselineDnsEntry 33 }



rsImportBaselineDnsOtherInIpv6 OBJECT-TYPE
    SYNTAX INTEGER
    ACCESS  read-write
    STATUS  mandatory
    DESCRIPTION
       "Import DNS Baseline OTHER-In-IPv6 Controller (Bps)"
    ::=  { rsImportBaselineDnsEntry 34 }

rsImportBaselineDnsOtherOutIpv6 OBJECT-TYPE
    SYNTAX INTEGER
    ACCESS  read-write
    STATUS  mandatory
    DESCRIPTION
       "Import DNS Baseline OTHER-Out-IPv6 Controller (Bps)"
    ::=  { rsImportBaselineDnsEntry 35 }



rsImportBaselineDnsAInIpv6 OBJECT-TYPE
    SYNTAX INTEGER
    ACCESS  read-write
    STATUS  mandatory
    DESCRIPTION
       "Import DNS Baseline A-In-IPv6 Controller (Bps)"
    ::=  { rsImportBaselineDnsEntry 36 }

rsImportBaselineDnsAOutIpv6 OBJECT-TYPE
    SYNTAX INTEGER
    ACCESS  read-write
    STATUS  mandatory
    DESCRIPTION
       "Import DNS Baseline A-Out-IPv6 Controller (Bps)"
    ::=  { rsImportBaselineDnsEntry 37 }

rsImportBaselineDnsMxInPpsIpv4 OBJECT-TYPE
    SYNTAX INTEGER
    ACCESS  read-write
    STATUS  mandatory
    DESCRIPTION
       "Import DNS Baseline MX-In-IPv4 Controller (Qps)"
    ::=  { rsImportBaselineDnsEntry 38 }

rsImportBaselineDnsMxOutPpsIpv4 OBJECT-TYPE
    SYNTAX INTEGER
    ACCESS  read-write
    STATUS  mandatory
    DESCRIPTION
       "Import DNS Baseline MX-Out-IPv4 Controller (Qps)"
    ::=  { rsImportBaselineDnsEntry 39 }


rsImportBaselineDnsPtrInPpsIpv4 OBJECT-TYPE
    SYNTAX INTEGER
    ACCESS  read-write
    STATUS  mandatory
    DESCRIPTION
       "Import DNS Baseline PTR-In-IPv4 Controller (Qps)"
    ::=  { rsImportBaselineDnsEntry 40 }

rsImportBaselineDnsPtrOutPpsIpv4 OBJECT-TYPE
    SYNTAX INTEGER
    ACCESS  read-write
    STATUS  mandatory
    DESCRIPTION
       "Import DNS Baseline PTR-Out-IPv4 Controller (Qps)"
    ::=  { rsImportBaselineDnsEntry 41 }


rsImportBaselineDnsAaaaInPpsIpv4 OBJECT-TYPE
    SYNTAX INTEGER
    ACCESS  read-write
    STATUS  mandatory
    DESCRIPTION
       "Import DNS Baseline AAAA-In-IPv4 Controller (Qps)"
    ::=  { rsImportBaselineDnsEntry 42 }

rsImportBaselineDnsAaaaOutPpsIpv4 OBJECT-TYPE
    SYNTAX INTEGER
    ACCESS  read-write
    STATUS  mandatory
    DESCRIPTION
       "Import DNS Baseline AAAA-Out-IPv4 Controller (Qps)"
    ::=  { rsImportBaselineDnsEntry 43 }


rsImportBaselineDnsTextInPpsIpv4 OBJECT-TYPE
    SYNTAX INTEGER
    ACCESS  read-write
    STATUS  mandatory
    DESCRIPTION
       "Import DNS Baseline TEXT-In-IPv4 Controller (Qps)"
    ::=  { rsImportBaselineDnsEntry 44 }

rsImportBaselineDnsTextOutPpsIpv4 OBJECT-TYPE
    SYNTAX INTEGER
    ACCESS  read-write
    STATUS  mandatory
    DESCRIPTION
       "Import DNS Baseline TEXT-Out-IPv4 Controller (Qps)"
    ::=  { rsImportBaselineDnsEntry 45 }

rsImportBaselineDnsSoaInPpsIpv4 OBJECT-TYPE
    SYNTAX INTEGER
    ACCESS  read-write
    STATUS  mandatory
    DESCRIPTION
       "Import DNS Baseline SOA-In-IPv4 Controller (Qps)"
    ::=  { rsImportBaselineDnsEntry 46 }

rsImportBaselineDnsSoaOutPpsIpv4 OBJECT-TYPE
    SYNTAX INTEGER
    ACCESS  read-write
    STATUS  mandatory
    DESCRIPTION
       "Import DNS Baseline SOA-Out-IPv4 Controller (Qps)"
    ::=  { rsImportBaselineDnsEntry 47 }


rsImportBaselineDnsNaptrInPpsIpv4 OBJECT-TYPE
    SYNTAX INTEGER
    ACCESS  read-write
    STATUS  mandatory
    DESCRIPTION
       "Import DNS Baseline NAPTR-In-IPv4 Controller (Qps)"
    ::=  { rsImportBaselineDnsEntry 48 }

rsImportBaselineDnsNaptrOutPpsIpv4 OBJECT-TYPE
    SYNTAX INTEGER
    ACCESS  read-write
    STATUS  mandatory
    DESCRIPTION
       "Import DNS Baseline NAPTR-Out-IPv4 Controller (Qps)"
    ::=  { rsImportBaselineDnsEntry 49 }



rsImportBaselineDnsSrcInPpsIpv4 OBJECT-TYPE
    SYNTAX INTEGER
    ACCESS  read-write
    STATUS  mandatory
    DESCRIPTION
       "Import DNS Baseline SRC-In-IPv4 Controller (Qps)"
    ::=  { rsImportBaselineDnsEntry 50 }

rsImportBaselineDnsSrcOutPpsIpv4 OBJECT-TYPE
    SYNTAX INTEGER
    ACCESS  read-write
    STATUS  mandatory
    DESCRIPTION
       "Import DNS Baseline SRC-Out-IPv4 Controller (Qps)"
    ::=  { rsImportBaselineDnsEntry 51 }

rsImportBaselineDnsOtherInPpsIpv4 OBJECT-TYPE
    SYNTAX INTEGER
    ACCESS  read-write
    STATUS  mandatory
    DESCRIPTION
       "Import DNS Baseline OTHER-In-IPv4 Controller (Qps)"
    ::=  { rsImportBaselineDnsEntry 52 }

rsImportBaselineDnsOtherOutPpsIpv4 OBJECT-TYPE
    SYNTAX INTEGER
    ACCESS  read-write
    STATUS  mandatory
    DESCRIPTION
       "Import DNS Baseline OTHER-Out-IPv4 Controller (Qps)"
    ::=  { rsImportBaselineDnsEntry 53 }


rsImportBaselineDnsAInPpsIpv4 OBJECT-TYPE
    SYNTAX INTEGER
    ACCESS  read-write
    STATUS  mandatory
    DESCRIPTION
       "Import DNS Baseline A-In-IPv4 Controller (Qps)"
    ::=  { rsImportBaselineDnsEntry 54 }

rsImportBaselineDnsAOutPpsIpv4 OBJECT-TYPE
    SYNTAX INTEGER
    ACCESS  read-write
    STATUS  mandatory
    DESCRIPTION
       "Import DNS Baseline A-Out-IPv4 Controller (Qps)"
    ::=  { rsImportBaselineDnsEntry 55 }



rsImportBaselineDnsMxInPpsIpv6 OBJECT-TYPE
    SYNTAX INTEGER
    ACCESS  read-write
    STATUS  mandatory
    DESCRIPTION
       "Import DNS Baseline MX-In-IPv6 Controller (Qps)"
    ::=  { rsImportBaselineDnsEntry 56 }

rsImportBaselineDnsMxOutPpsIpv6 OBJECT-TYPE
    SYNTAX INTEGER
    ACCESS  read-write
    STATUS  mandatory
    DESCRIPTION
       "Import DNS Baseline MX-Out-IPv6 Controller (Qps)"
    ::=  { rsImportBaselineDnsEntry 57 }


rsImportBaselineDnsPtrInPpsIpv6 OBJECT-TYPE
    SYNTAX INTEGER
    ACCESS  read-write
    STATUS  mandatory
    DESCRIPTION
       "Import DNS Baseline PTR-In-IPv6 Controller (Qps)"
    ::=  { rsImportBaselineDnsEntry 58 }

rsImportBaselineDnsPtrOutPpsIpv6 OBJECT-TYPE
    SYNTAX INTEGER
    ACCESS  read-write
    STATUS  mandatory
    DESCRIPTION
       "Import DNS Baseline PTR-Out-IPv6 Controller (Qps)"
    ::=  { rsImportBaselineDnsEntry 59 }


rsImportBaselineDnsAaaaInPpsIpv6 OBJECT-TYPE
    SYNTAX INTEGER
    ACCESS  read-write
    STATUS  mandatory
    DESCRIPTION
       "Import DNS Baseline AAAA-In-IPv6 Controller (Qps)"
    ::=  { rsImportBaselineDnsEntry 60 }

rsImportBaselineDnsAaaaOutPpsIpv6 OBJECT-TYPE
    SYNTAX INTEGER
    ACCESS  read-write
    STATUS  mandatory
    DESCRIPTION
       "Import DNS Baseline AAAA-Out-IPv6 Controller (Qps)"
    ::=  { rsImportBaselineDnsEntry 61 }


rsImportBaselineDnsTextInPpsIpv6 OBJECT-TYPE
    SYNTAX INTEGER
    ACCESS  read-write
    STATUS  mandatory
    DESCRIPTION
       "Import DNS Baseline TEXT-In-IPv6 Controller (Qps)"
    ::=  { rsImportBaselineDnsEntry 62 }

rsImportBaselineDnsTextOutPpsIpv6 OBJECT-TYPE
    SYNTAX INTEGER
    ACCESS  read-write
    STATUS  mandatory
    DESCRIPTION
       "Import DNS Baseline TEXT-Out-IPv6 Controller (Qps)"
    ::=  { rsImportBaselineDnsEntry 63 }

rsImportBaselineDnsSoaInPpsIpv6 OBJECT-TYPE
    SYNTAX INTEGER
    ACCESS  read-write
    STATUS  mandatory
    DESCRIPTION
       "Import DNS Baseline SOA-In-IPv6 Controller (Qps)"
    ::=  { rsImportBaselineDnsEntry 64 }

rsImportBaselineDnsSoaOutPpsIpv6 OBJECT-TYPE
    SYNTAX INTEGER
    ACCESS  read-write
    STATUS  mandatory
    DESCRIPTION
       "Import DNS Baseline SOA-Out-IPv6 Controller (Qps)"
    ::=  { rsImportBaselineDnsEntry 65 }


rsImportBaselineDnsNaptrInPpsIpv6 OBJECT-TYPE
    SYNTAX INTEGER
    ACCESS  read-write
    STATUS  mandatory
    DESCRIPTION
       "Import DNS Baseline NAPTR-In-IPv6 Controller (Qps)"
    ::=  { rsImportBaselineDnsEntry 66 }

rsImportBaselineDnsNaptrOutPpsIpv6 OBJECT-TYPE
    SYNTAX INTEGER
    ACCESS  read-write
    STATUS  mandatory
    DESCRIPTION
       "Import DNS Baseline NAPTR-Out-IPv6 Controller (Qps)"
    ::=  { rsImportBaselineDnsEntry 67 }



rsImportBaselineDnsSrcInPpsIpv6 OBJECT-TYPE
    SYNTAX INTEGER
    ACCESS  read-write
    STATUS  mandatory
    DESCRIPTION
       "Import DNS Baseline SRC-In-IPv6 Controller (Qps)"
    ::=  { rsImportBaselineDnsEntry 68 }

rsImportBaselineDnsSrcOutPpsIpv6 OBJECT-TYPE
    SYNTAX INTEGER
    ACCESS  read-write
    STATUS  mandatory
    DESCRIPTION
       "Import DNS Baseline SRC-Out-IPv6 Controller (Qps)"
    ::=  { rsImportBaselineDnsEntry 69 }

rsImportBaselineDnsOtherInPpsIpv6 OBJECT-TYPE
    SYNTAX INTEGER
    ACCESS  read-write
    STATUS  mandatory
    DESCRIPTION
       "Import DNS Baseline OTHER-In-IPv6 Controller (Qps)"
    ::=  { rsImportBaselineDnsEntry 70 }

rsImportBaselineDnsOtherOutPpsIpv6 OBJECT-TYPE
    SYNTAX INTEGER
    ACCESS  read-write
    STATUS  mandatory
    DESCRIPTION
       "Import DNS Baseline OTHER-Out-IPv6 Controller (Qps)"
    ::=  { rsImportBaselineDnsEntry 71 }


rsImportBaselineDnsAInPpsIpv6 OBJECT-TYPE
    SYNTAX INTEGER
    ACCESS  read-write
    STATUS  mandatory
    DESCRIPTION
       "Import DNS Baseline A-In-IPv6 Controller (Qps)"
    ::=  { rsImportBaselineDnsEntry 72 }

rsImportBaselineDnsAOutPpsIpv6 OBJECT-TYPE
    SYNTAX INTEGER
    ACCESS  read-write
    STATUS  mandatory
    DESCRIPTION
       "Import DNS Baseline A-Out-IPv6 Controller (Qps)"
    ::=  { rsImportBaselineDnsEntry 73 }




-- HTTP Import Baseline
--


rsImportBaselineHttpTable OBJECT-TYPE
    SYNTAX SEQUENCE OF RsImportBaselineHttpEntry
    ACCESS not-accessible
    STATUS  mandatory
    DESCRIPTION
      "Table containing the baseline import request."
    ::=  {rsImportExport 6}

rsImportBaselineHttpEntry OBJECT-TYPE
    SYNTAX RsImportBaselineHttpEntry
    ACCESS not-accessible
    STATUS  mandatory
    DESCRIPTION
       "The row definition for this table."
    INDEX { rsImportBaselineHttpName }
    ::=  { rsImportBaselineHttpTable 1 }

RsImportBaselineHttpEntry ::= SEQUENCE {

    rsImportBaselineHttpName				DisplayString,

	rsImportBaselineHttpAvrgGetpost			INTEGER,
	rsImportBaselineHttpAvrgOther			INTEGER,
	rsImportBaselineHttpAvrgOutband			INTEGER,

	rsImportBaselineHttpPeakGetpost			INTEGER,
	rsImportBaselineHttpPeakOther			INTEGER,
	rsImportBaselineHttpPeakOutband			INTEGER,

	rsImportBaselineHttpLearnInitGetpost	INTEGER,
	rsImportBaselineHttpLearnInitOther		INTEGER,
	rsImportBaselineHttpLearnInitOutband	INTEGER,

	rsImportBaselineHttpMaxGetPerSession	INTEGER,
	rsImportBaselineHttpMaxGetPerSrc		INTEGER,

	rsImportBaselineHttpCreDay				INTEGER,

	rsImportBaselineHttpReqConInit			INTEGER,
	rsImportBaselineHttpReqSrcInit			INTEGER,

	rsImportBaselineHttpGetpostLongTerm1	DisplayString,
	rsImportBaselineHttpGetpostLongTerm2	DisplayString,
	rsImportBaselineHttpGetpostLongTerm3	DisplayString,
	rsImportBaselineHttpGetpostLongTerm4	DisplayString,
	rsImportBaselineHttpGetpostLongTerm5	DisplayString,
	rsImportBaselineHttpGetpostLongTerm6	DisplayString,
	rsImportBaselineHttpGetpostLongTerm7	DisplayString,
	rsImportBaselineHttpGetpostLongTerm8	DisplayString,
	rsImportBaselineHttpGetpostLongTerm9	DisplayString,
	rsImportBaselineHttpGetpostLongTerm10	DisplayString

}


rsImportBaselineHttpName OBJECT-TYPE
    SYNTAX DisplayString (SIZE(1..33))
    ACCESS  read-write
    STATUS  mandatory
    DESCRIPTION
       "Import HTTP Baseline Server Name"
    ::=  { rsImportBaselineHttpEntry 1 }

rsImportBaselineHttpAvrgGetpost OBJECT-TYPE
    SYNTAX INTEGER
    ACCESS  read-write
    STATUS  mandatory
    DESCRIPTION
       "Import HTTP Baseline Avrg-Getpost"
    ::=  { rsImportBaselineHttpEntry 2 }

rsImportBaselineHttpAvrgOther OBJECT-TYPE
    SYNTAX INTEGER
    ACCESS  read-write
    STATUS  mandatory
    DESCRIPTION
       "Import HTTP Baseline Avrg-Other"
    ::=  { rsImportBaselineHttpEntry 3 }

rsImportBaselineHttpAvrgOutband OBJECT-TYPE
    SYNTAX INTEGER
    ACCESS  read-write
    STATUS  mandatory
    DESCRIPTION
       "Import HTTP Baseline Avrg-Outband"
    ::=  { rsImportBaselineHttpEntry 4 }




rsImportBaselineHttpPeakGetpost OBJECT-TYPE
    SYNTAX INTEGER
    ACCESS  read-write
    STATUS  mandatory
    DESCRIPTION
       "Import HTTP Baseline Peak-Getpost"
    ::=  { rsImportBaselineHttpEntry 5 }

rsImportBaselineHttpPeakOther OBJECT-TYPE
    SYNTAX INTEGER
    ACCESS  read-write
    STATUS  mandatory
    DESCRIPTION
       "Import HTTP Baseline Peak-Other"
    ::=  { rsImportBaselineHttpEntry 6 }

rsImportBaselineHttpPeakOutband OBJECT-TYPE
    SYNTAX INTEGER
    ACCESS  read-write
    STATUS  mandatory
    DESCRIPTION
       "Import HTTP Baseline Peak-Outband"
    ::=  { rsImportBaselineHttpEntry 7 }





rsImportBaselineHttpLearnInitGetpost OBJECT-TYPE
    SYNTAX INTEGER
    ACCESS  read-write
    STATUS  mandatory
    DESCRIPTION
       "Import HTTP Baseline LearnInit-Getpost"
    ::=  { rsImportBaselineHttpEntry 8 }

rsImportBaselineHttpLearnInitOther OBJECT-TYPE
    SYNTAX INTEGER
    ACCESS  read-write
    STATUS  mandatory
    DESCRIPTION
       "Import HTTP Baseline LearnInit-Other"
    ::=  { rsImportBaselineHttpEntry 9 }

rsImportBaselineHttpLearnInitOutband OBJECT-TYPE
    SYNTAX INTEGER
    ACCESS  read-write
    STATUS  mandatory
    DESCRIPTION
       "Import HTTP Baseline LearnInit-Outband"
    ::=  { rsImportBaselineHttpEntry 10 }





rsImportBaselineHttpMaxGetPerSession OBJECT-TYPE
    SYNTAX INTEGER
    ACCESS  read-write
    STATUS  mandatory
    DESCRIPTION
       "Import HTTP Baseline Max Get per Session"
    ::=  { rsImportBaselineHttpEntry 11 }

rsImportBaselineHttpMaxGetPerSrc OBJECT-TYPE
    SYNTAX INTEGER
    ACCESS  read-write
    STATUS  mandatory
    DESCRIPTION
      "Import HTTP Baseline Max Get per Source"
    ::=  { rsImportBaselineHttpEntry 12 }



rsImportBaselineHttpCreDay OBJECT-TYPE
    SYNTAX INTEGER
    ACCESS  read-write
    STATUS  mandatory
    DESCRIPTION
      "Import HTTP Baseline Creation Day"
    ::=  { rsImportBaselineHttpEntry 13 }



rsImportBaselineHttpReqConInit OBJECT-TYPE
    SYNTAX INTEGER
    ACCESS  read-write
    STATUS  mandatory
    DESCRIPTION
       "Import HTTP Baseline Connections Request Init"
    ::=  { rsImportBaselineHttpEntry 14 }

rsImportBaselineHttpReqSrcInit OBJECT-TYPE
    SYNTAX INTEGER
    ACCESS  read-write
    STATUS  mandatory
    DESCRIPTION
      "Import HTTP Baseline Source Request Init"
    ::=  { rsImportBaselineHttpEntry 15 }

rsImportBaselineHttpGetpostLongTerm1 OBJECT-TYPE
    SYNTAX DisplayString
    ACCESS  read-write
    STATUS  mandatory
    DESCRIPTION
      "Import HTTP Baseline Getpost Long Term"
    ::=  { rsImportBaselineHttpEntry 16 }

rsImportBaselineHttpGetpostLongTerm2 OBJECT-TYPE
    SYNTAX DisplayString
    ACCESS  read-write
    STATUS  mandatory
    DESCRIPTION
      "Import HTTP Baseline Getpost Long Term"
    ::=  { rsImportBaselineHttpEntry 17 }

rsImportBaselineHttpGetpostLongTerm3 OBJECT-TYPE
    SYNTAX DisplayString
    ACCESS  read-write
    STATUS  mandatory
    DESCRIPTION
      "Import HTTP Baseline Getpost Long Term"
    ::=  { rsImportBaselineHttpEntry 18 }

rsImportBaselineHttpGetpostLongTerm4 OBJECT-TYPE
    SYNTAX DisplayString
    ACCESS  read-write
    STATUS  mandatory
    DESCRIPTION
      "Import HTTP Baseline Getpost Long Term"
    ::=  { rsImportBaselineHttpEntry 19 }

rsImportBaselineHttpGetpostLongTerm5 OBJECT-TYPE
    SYNTAX DisplayString
    ACCESS  read-write
    STATUS  mandatory
    DESCRIPTION
      "Import HTTP Baseline Getpost Long Term"
    ::=  { rsImportBaselineHttpEntry 20 }

rsImportBaselineHttpGetpostLongTerm6 OBJECT-TYPE
    SYNTAX DisplayString
    ACCESS  read-write
    STATUS  mandatory
    DESCRIPTION
      "Import HTTP Baseline Getpost Long Term"
    ::=  { rsImportBaselineHttpEntry 21 }

rsImportBaselineHttpGetpostLongTerm7 OBJECT-TYPE
    SYNTAX DisplayString
    ACCESS  read-write
    STATUS  mandatory
    DESCRIPTION
      "Import HTTP Baseline Getpost Long Term"
    ::=  { rsImportBaselineHttpEntry 22 }

rsImportBaselineHttpGetpostLongTerm8 OBJECT-TYPE
    SYNTAX DisplayString
    ACCESS  read-write
    STATUS  mandatory
    DESCRIPTION
      "Import HTTP Baseline Getpost Long Term"
    ::=  { rsImportBaselineHttpEntry 23 }

rsImportBaselineHttpGetpostLongTerm9 OBJECT-TYPE
    SYNTAX DisplayString
    ACCESS  read-write
    STATUS  mandatory
    DESCRIPTION
      "Import HTTP Baseline Getpost Long Term"
    ::=  { rsImportBaselineHttpEntry 24 }

rsImportBaselineHttpGetpostLongTerm10 OBJECT-TYPE
    SYNTAX DisplayString
    ACCESS  read-write
    STATUS  mandatory
    DESCRIPTION
      "Import HTTP Baseline Getpost Long Term"
    ::=  { rsImportBaselineHttpEntry 25 }



-- Import Policy
--


rsImportPolicyTable OBJECT-TYPE
    SYNTAX SEQUENCE OF RsImportPolicyEntry
    ACCESS not-accessible
    STATUS  mandatory
    DESCRIPTION
      "Table containing the Network Policy import request."
    ::=  {rsImportExport 7}


rsImportPolicyEntry OBJECT-TYPE
    SYNTAX RsImportPolicyEntry
    ACCESS not-accessible
    STATUS  mandatory
    DESCRIPTION
       "The row definition for this table."
    INDEX { rsImportPolicyFile }
    ::=  { rsImportPolicyTable 1 }

RsImportPolicyEntry ::= SEQUENCE {

	rsImportPolicyFile			DisplayString,
	rsImportPolicyUpdate		INTEGER,
	rsImportPolicyOverride		INTEGER
}

rsImportPolicyFile OBJECT-TYPE
   SYNTAX DisplayString (SIZE(0..255))
    ACCESS read-write
    STATUS mandatory
	DESCRIPTION
      "Import File Name"
    ::=  {rsImportPolicyEntry 1}


rsImportPolicyUpdate OBJECT-TYPE
    SYNTAX INTEGER {
      yes(1),
      no(2)
   }
    ACCESS  read-write
    STATUS  mandatory
    DESCRIPTION
       "Import Policy Update-Policies Indicator"
    DEFVAL  {yes}
    ::=  { rsImportPolicyEntry 2}

rsImportPolicyOverride OBJECT-TYPE
    SYNTAX INTEGER {
      yes(1),
      no(2)
   }
    ACCESS  read-write
    STATUS  mandatory
    DESCRIPTION
       "Import Policy Override-Existing Indicator"
    DEFVAL  {yes}
    ::=  { rsImportPolicyEntry 3}


-- Export Policy
--


rsExportPolicyTable OBJECT-TYPE
    SYNTAX SEQUENCE OF RsExportPolicyEntry
    ACCESS not-accessible
    STATUS  mandatory
    DESCRIPTION
      "Table containing the Network Policy export request."
    ::=  {rsImportExport 8}


rsExportPolicyEntry OBJECT-TYPE
    SYNTAX RsExportPolicyEntry
    ACCESS not-accessible
    STATUS  mandatory
    DESCRIPTION
       "The row definition for this table."
    INDEX { rsExportPolicyName }
    ::=  { rsExportPolicyTable 1 }

RsExportPolicyEntry ::= SEQUENCE {

    rsExportPolicyName			DisplayString,

	rsExportPolicyConfiguration		INTEGER,
	rsExportPolicyBaselineBdos		INTEGER,
	rsExportPolicyBaselineDns		INTEGER,
	rsExportPolicySigUserProfile		INTEGER,
	rsExportPolicyTrafficFilterProfile	INTEGER,
	rsExportPolicyAntiScanWhitelists	INTEGER
}

rsExportPolicyName OBJECT-TYPE
    SYNTAX DisplayString (SIZE(1..64))
    ACCESS  read-write
    STATUS  mandatory
    DESCRIPTION
       "Export Network Policy Name"
    ::=  { rsExportPolicyEntry 1 }

rsExportPolicyConfiguration OBJECT-TYPE
    SYNTAX INTEGER {
      yes(1),
      no(2)
   }
    ACCESS  read-write
    STATUS  mandatory
    DESCRIPTION
       "Export Policy Configuration Indicator"
    DEFVAL  {yes}
    ::=  { rsExportPolicyEntry 2 }

rsExportPolicyBaselineBdos OBJECT-TYPE
    SYNTAX INTEGER {
      yes(1),
      no(2)
   }
    ACCESS  read-write
    STATUS  mandatory
    DESCRIPTION
       "Export Policy Baseline BDoS Indicator"
    DEFVAL  {yes}
    ::=  { rsExportPolicyEntry 3 }

rsExportPolicyBaselineDns OBJECT-TYPE
    SYNTAX INTEGER {
      yes(1),
      no(2)
   }
    ACCESS  read-write
    STATUS  mandatory
    DESCRIPTION
       "Export Policy Baseline DNS Indicator"
    DEFVAL  {yes}
    ::=  { rsExportPolicyEntry 4 }

rsExportPolicySigUserProfile OBJECT-TYPE
			    SYNTAX INTEGER {
      yes(1),
      no(2)
   }
    ACCESS  read-write
    STATUS  mandatory
    DESCRIPTION
       "Export Signature User Profile "
    DEFVAL  {yes}
    ::=  { rsExportPolicyEntry 5 }

rsExportPolicyTrafficFilterProfile OBJECT-TYPE
			    SYNTAX INTEGER {
      yes(1),
      no(2)
   }
    ACCESS  read-write
    STATUS  mandatory
    DESCRIPTION
       "Export Traffic Filter Profile "
    DEFVAL  {yes}
    ::=  { rsExportPolicyEntry 6 }

rsExportPolicyAntiScanWhitelists OBJECT-TYPE
   SYNTAX INTEGER {
      yes(1),
      no(2)
   }
    ACCESS  read-write
    STATUS  mandatory
    DESCRIPTION
       "Export Anti-Scanning Whitelisted Objects"
    DEFVAL  {yes}
    ::=  { rsExportPolicyEntry 7 }


-- Import Server
--


rsImportServerTable OBJECT-TYPE
    SYNTAX SEQUENCE OF RsImportServerEntry
    ACCESS not-accessible
    STATUS  mandatory
    DESCRIPTION
      "Table containing the Network Server import request."
    ::=  {rsImportExport 9}


rsImportServerEntry OBJECT-TYPE
    SYNTAX RsImportServerEntry
    ACCESS not-accessible
    STATUS  mandatory
    DESCRIPTION
       "The row definition for this table."
    INDEX { rsImportServerFile }
    ::=  { rsImportServerTable 1 }

RsImportServerEntry ::= SEQUENCE {

	rsImportServerFile			DisplayString,
	rsImportServerUpdate		INTEGER,
	rsImportServerOverride		INTEGER
}

rsImportServerFile OBJECT-TYPE
   SYNTAX DisplayString (SIZE(0..255))
    ACCESS read-write
    STATUS mandatory
	DESCRIPTION
      "Import File Name"
    ::=  {rsImportServerEntry 1}


rsImportServerUpdate OBJECT-TYPE
    SYNTAX INTEGER {
      yes(1),
      no(2)
   }
    ACCESS  read-write
    STATUS  mandatory
    DESCRIPTION
       "Import Server Update-Policies Indicator"
    DEFVAL  {no}
    ::=  { rsImportServerEntry 2 }

rsImportServerOverride OBJECT-TYPE
    SYNTAX INTEGER {
      yes(1),
      no(2)
   }
    ACCESS  read-write
    STATUS  mandatory
    DESCRIPTION
       "Import Server Override-Existing Indicator"
    DEFVAL  {no}
    ::=  { rsImportServerEntry 3 }

-- Export Server
--


rsExportServerTable OBJECT-TYPE
    SYNTAX SEQUENCE OF RsExportServerEntry
    ACCESS not-accessible
    STATUS  mandatory
    DESCRIPTION
      "Table containing the Server export request."
    ::=  {rsImportExport 10}


rsExportServerEntry OBJECT-TYPE
    SYNTAX RsExportServerEntry
    ACCESS not-accessible
    STATUS  mandatory
    DESCRIPTION
       "The row definition for this table."
    INDEX { rsExportServerName }
    ::=  { rsExportServerTable 1 }

RsExportServerEntry ::= SEQUENCE {

    rsExportServerName			DisplayString,

	rsExportServerConfiguration	INTEGER,
	rsExportServerBaselineHttp	INTEGER
}

rsExportServerName OBJECT-TYPE
    SYNTAX DisplayString (SIZE(1..20))
    ACCESS  read-write
    STATUS  mandatory
    DESCRIPTION
       "Export Server Name"
    ::=  { rsExportServerEntry 1 }

rsExportServerConfiguration OBJECT-TYPE
    SYNTAX INTEGER {
      yes(1),
      no(2)
   }
    ACCESS  read-write
    STATUS  mandatory
    DESCRIPTION
       "Export Server Configuration Indicator"
    DEFVAL  {no}
    ::=  { rsExportServerEntry 2 }

rsExportServerBaselineHttp OBJECT-TYPE
    SYNTAX INTEGER {
      yes(1),
      no(2)
   }
    ACCESS  read-write
    STATUS  mandatory
    DESCRIPTION
       "Export Server Baseline HTTP Indicator"
    DEFVAL  {no}
    ::=  { rsExportServerEntry 3 }


-- Delete Policy
--


rsDeletePolicyTable OBJECT-TYPE
    SYNTAX SEQUENCE OF RsDeletePolicyEntry
    ACCESS not-accessible
    STATUS  mandatory
    DESCRIPTION
      "Table containing the Network Policy delete request."
    ::=  {rsImportExport 11}


rsDeletePolicyEntry OBJECT-TYPE
    SYNTAX RsDeletePolicyEntry
    ACCESS not-accessible
    STATUS  mandatory
    DESCRIPTION
       "The row definition for this table."
    INDEX { rsDeletePolicyName }
    ::=  { rsDeletePolicyTable 1 }

RsDeletePolicyEntry ::= SEQUENCE {

    rsDeletePolicyName			DisplayString,
	rsDeletePolicyUpdate		INTEGER
}

rsDeletePolicyName OBJECT-TYPE
    SYNTAX DisplayString (SIZE(1..64))
    ACCESS  read-write
    STATUS  mandatory
    DESCRIPTION
       "Delete Network Policy Name"
    ::=  { rsDeletePolicyEntry 1 }

rsDeletePolicyUpdate OBJECT-TYPE
    SYNTAX INTEGER {
      yes(1),
      no(2)
   }
    ACCESS  read-write
    STATUS  mandatory
    DESCRIPTION
       "Delete Policy Update-Policies Indicator"
    DEFVAL  {yes}
    ::=  { rsDeletePolicyEntry 2 }


-- Delete Server
--

rsDeleteServerTable OBJECT-TYPE
    SYNTAX SEQUENCE OF RsDeleteServerEntry
    ACCESS not-accessible
    STATUS  mandatory
    DESCRIPTION
      "Table containing the Network Server delete request."
    ::=  {rsImportExport 12}


rsDeleteServerEntry OBJECT-TYPE
    SYNTAX RsDeleteServerEntry
    ACCESS not-accessible
    STATUS  mandatory
    DESCRIPTION
       "The row definition for this table."
    INDEX { rsDeleteServerName }
    ::=  { rsDeleteServerTable 1 }

RsDeleteServerEntry ::= SEQUENCE {

    rsDeleteServerName			DisplayString,
	rsDeleteServerUpdate		INTEGER
}

rsDeleteServerName OBJECT-TYPE
    SYNTAX DisplayString (SIZE(1..33))
    ACCESS  read-write
    STATUS  mandatory
    DESCRIPTION
       "Delete Server Name"
    ::=  { rsDeleteServerEntry 1 }

rsDeleteServerUpdate OBJECT-TYPE
    SYNTAX INTEGER {
      yes(1),
      no(2)
   }
    ACCESS  read-write
    STATUS  mandatory
    DESCRIPTION
       "Delete Server Update-Policies Indicator"
    DEFVAL  {no}
    ::=  { rsDeleteServerEntry 2 }


rsNewTrafficFilter OBJECT IDENTIFIER ::= { rsIDS 184 }


-- OBSOLETE!!


rsNewTrafficFilterTable OBJECT-TYPE
    SYNTAX SEQUENCE OF RsNewTrafficFilterEntry
    ACCESS not-accessible
    STATUS  mandatory
    DESCRIPTION
      "Table containing the manual rules sources "
    ::=  {rsNewTrafficFilter 1}


rsNewTrafficFilterEntry OBJECT-TYPE
    SYNTAX RsNewTrafficFilterEntry
    ACCESS not-accessible
    STATUS  mandatory
    DESCRIPTION
       "The row definition for this table."
    INDEX { rsNewTrafficFilterProfileName, rsNewTrafficFilterName }
    ::=  { rsNewTrafficFilterTable 1 }

RsNewTrafficFilterEntry ::= SEQUENCE {
	rsNewTrafficFilterProfileName 	DisplayString,
	rsNewTrafficFilterName 		DisplayString,
	rsNewTrafficFilterID		INTEGER,
	rsNewTrafficFilterState 	INTEGER,
	rsNewTrafficFilterPriority	INTEGER,
	rsNewTrafficFilterMatchCriteria INTEGER,
	rsNewTrafficFilterSrcNetwork 	DisplayString,
	rsNewTrafficFilterSrcPort	DisplayString,
	rsNewTrafficFilterDstNetwork 	DisplayString,
	rsNewTrafficFilterDstPort	DisplayString,
	rsNewTrafficFilterProtocol INTEGER,
	rsNewTrafficFilterPacketSize DisplayString,
	rsNewTrafficFilterTCPFlagsSyn INTEGER,
	rsNewTrafficFilterTCPFlagsAck INTEGER,
	rsNewTrafficFilterTCPFlagsRst INTEGER,
	rsNewTrafficFilterTCPFlagsSynAck INTEGER,
	rsNewTrafficFilterTCPFlagsFinAck INTEGER,
	rsNewTrafficFilterTCPFlagsPshAck INTEGER,
	rsNewTrafficFilterDnsQueryName DisplayString,
	rsNewTrafficFilterDnsTypeA INTEGER,
	rsNewTrafficFilterDnsTypeAAAA INTEGER,
	rsNewTrafficFilterDnsTypeMX INTEGER,
	rsNewTrafficFilterDnsTypePTR INTEGER,
	rsNewTrafficFilterDnsTypeCNAME INTEGER,
	rsNewTrafficFilterDnsTypeNS INTEGER,
	rsNewTrafficFilterDnsTypeTXT INTEGER,
	rsNewTrafficFilterDnsTypeANY INTEGER,
	rsNewTrafficFilterDnsTypeSOA INTEGER,
	rsNewTrafficFilterThresholdPPS Counter64,
	rsNewTrafficFilterThresholdBPS Counter64,
	rsNewTrafficFilterPacketReport INTEGER,
	rsNewTrafficFilterRowStatus RowStatus,
	rsNewTrafficFilterThresholdUsed INTEGER,
	rsNewTrafficFilterTTL DisplayString,
	rsNewTrafficFilterSequenceNum DisplayString,
	rsNewTrafficFilterFragId DisplayString,
	rsNewTrafficFilterFragOffset	DisplayString,
	rsNewTrafficFilterAttackTrackingType INTEGER,
	rsNewTrafficFilterRegex DisplayString,
	rsNewTrafficFilterTOS DisplayString,
	rsNewTrafficFilterVLAN DisplayString
}

rsNewTrafficFilterProfileName OBJECT-TYPE
    SYNTAX DisplayString (SIZE(1..29))
    ACCESS  read-write
    STATUS  mandatory
    DESCRIPTION
      "The traffic filter profile name."
    ::=  {rsNewTrafficFilterEntry 1}

rsNewTrafficFilterName OBJECT-TYPE
    SYNTAX DisplayString (SIZE(1..29))
    ACCESS  read-write
    STATUS  mandatory
    DESCRIPTION
      "The traffic filter name."
    ::=  {rsNewTrafficFilterEntry 2}

rsNewTrafficFilterID OBJECT-TYPE
    SYNTAX INTEGER
    ACCESS read-write
    STATUS mandatory
    DESCRIPTION
      "This variable indicates the traffic filter ID."
    ::= {rsNewTrafficFilterEntry 3}

rsNewTrafficFilterState OBJECT-TYPE
	SYNTAX INTEGER {
	enable(1),
	disable(2)
	}
    ACCESS read-write
    STATUS mandatory
    DESCRIPTION
      "The traffic filter admin status"
   DEFVAL  {enable}
    ::=  { rsNewTrafficFilterEntry 4 }

rsNewTrafficFilterPriority OBJECT-TYPE
    SYNTAX INTEGER (0..14)
    ACCESS read-only
    STATUS mandatory
    DESCRIPTION
      "This variable indicates the traffic filter Priority."
    ::= {rsNewTrafficFilterEntry 5}

rsNewTrafficFilterMatchCriteria OBJECT-TYPE
	SYNTAX INTEGER {
	match(1),
	not-match(2)
	}
	ACCESS read-write
	STATUS mandatory
	DESCRIPTION
	"The traffic filter matching criteria"
	DEFVAL  {1}
	::=  { rsNewTrafficFilterEntry 6 }

rsNewTrafficFilterSrcNetwork OBJECT-TYPE
    SYNTAX DisplayString (SIZE(0..46))
    ACCESS  read-write
    STATUS  mandatory
    DESCRIPTION
      "The source address / range of address for the packet, the name is
      defined in the Objects table or can be an IP address."
    ::=  {rsNewTrafficFilterEntry 7}

rsNewTrafficFilterSrcPort OBJECT-TYPE
    SYNTAX DisplayString (SIZE(0..30))
    ACCESS  read-write
    STATUS  mandatory
    DESCRIPTION
      "The traffic filter source port for the packet."
    ::=  {rsNewTrafficFilterEntry 8}

rsNewTrafficFilterDstNetwork OBJECT-TYPE
    SYNTAX DisplayString (SIZE(0..46))
    ACCESS  read-write
    STATUS  mandatory
    DESCRIPTION
      "The destination address / range of address for the packet, the name is
      defined in the Objects table or can be an IP address."
    ::=  {rsNewTrafficFilterEntry 9}

rsNewTrafficFilterDstPort OBJECT-TYPE
    SYNTAX DisplayString (SIZE(0..30))
    ACCESS  read-write
    STATUS  mandatory
    DESCRIPTION
      "The traffic filter destinatin port for the packet."
    ::=  {rsNewTrafficFilterEntry 10}

rsNewTrafficFilterProtocol OBJECT-TYPE
    SYNTAX INTEGER {
        any(0),
		tcp(1),
		udp(2),
		icmp(3),
		igmp(4),
		sctp(5),
		icmpv6(6)
    }
    ACCESS read-write
    STATUS mandatory
    DESCRIPTION
      "The traffic filter protocol."
    DEFVAL {0}
    ::=  { rsNewTrafficFilterEntry 11 }

rsNewTrafficFilterPacketSize OBJECT-TYPE
    SYNTAX DisplayString (SIZE(0..255))
    ACCESS read-write
    STATUS mandatory
    DESCRIPTION
      "The traffic filter size of packet."
    ::=  { rsNewTrafficFilterEntry 12 }

rsNewTrafficFilterTCPFlagsSyn OBJECT-TYPE
    SYNTAX INTEGER {
              active(1),
              inactive(2)}
    ACCESS  read-write
    STATUS  mandatory
    DESCRIPTION
       "This variable indicates whether to check TCP SYN Flag in this filter"
    DEFVAL { 2 }
    ::=  { rsNewTrafficFilterEntry 13 }

rsNewTrafficFilterTCPFlagsAck OBJECT-TYPE
    SYNTAX INTEGER {
              active(1),
              inactive(2)}
    ACCESS  read-write
    STATUS  mandatory
    DESCRIPTION
       "This variable indicates whether to check TCP ACK Flag in this filter"
    DEFVAL { 2 }
    ::=  { rsNewTrafficFilterEntry 14 }

rsNewTrafficFilterTCPFlagsRst OBJECT-TYPE
    SYNTAX INTEGER {
              active(1),
              inactive(2)}
    ACCESS  read-write
    STATUS  mandatory
    DESCRIPTION
       "This variable indicates whether to check TCP RST Flag in this filter"
    DEFVAL { 2 }
    ::=  { rsNewTrafficFilterEntry 15 }


rsNewTrafficFilterTCPFlagsSynAck OBJECT-TYPE
    SYNTAX INTEGER {
              active(1),
              inactive(2)}
    ACCESS  read-write
    STATUS  mandatory
    DESCRIPTION
       "This variable indicates whether to check TCP SYN-ACK Flag in this filter"
    DEFVAL { 2 }
    ::=  { rsNewTrafficFilterEntry 16 }

rsNewTrafficFilterTCPFlagsFinAck OBJECT-TYPE
    SYNTAX INTEGER {
              active(1),
              inactive(2)}
    ACCESS  read-write
    STATUS  mandatory
    DESCRIPTION
       "This variable indicates whether to check TCP FIN-ACK Flag in this filter"
    DEFVAL { 2 }
    ::=  { rsNewTrafficFilterEntry 17 }

rsNewTrafficFilterTCPFlagsPshAck OBJECT-TYPE
    SYNTAX INTEGER {
              active(1),
              inactive(2)}
    ACCESS  read-write
    STATUS  mandatory
    DESCRIPTION
       "This variable indicates whether to check TCP PSH-ACK Flag in this filter"
    DEFVAL { 2 }
    ::=  { rsNewTrafficFilterEntry 18 }


rsNewTrafficFilterDnsQueryName OBJECT-TYPE
  SYNTAX DisplayString (SIZE(0..255))
    ACCESS  read-write
    STATUS  mandatory
    DESCRIPTION
      "The traffic filter DNS query name."
    ::=  {rsNewTrafficFilterEntry 19}

rsNewTrafficFilterDnsTypeA OBJECT-TYPE
    SYNTAX INTEGER {
              active(1),
              inactive(2)}
    ACCESS  read-write
    STATUS  mandatory
    DESCRIPTION
       "This variable indicates whether to check DNS Query Type A in this filter"
    DEFVAL { 2 }
    ::=  { rsNewTrafficFilterEntry 20 }

rsNewTrafficFilterDnsTypeAAAA OBJECT-TYPE
    SYNTAX INTEGER {
              active(1),
              inactive(2)}
    ACCESS  read-write
    STATUS  mandatory
    DESCRIPTION
       "This variable indicates whether to check DNS Query Type AAAA in this filter"
    DEFVAL { 2 }
    ::=  { rsNewTrafficFilterEntry 21 }

    rsNewTrafficFilterDnsTypeMX OBJECT-TYPE
    SYNTAX INTEGER {
              active(1),
              inactive(2)}
    ACCESS  read-write
    STATUS  mandatory
    DESCRIPTION
       "This variable indicates whether to check DNS Query Type MX in this filter"
    DEFVAL { 2 }
    ::=  { rsNewTrafficFilterEntry 22 }

rsNewTrafficFilterDnsTypePTR OBJECT-TYPE
    SYNTAX INTEGER {
              active(1),
              inactive(2)}
    ACCESS  read-write
    STATUS  mandatory
    DESCRIPTION
       "This variable indicates whether to check DNS Query Type PTR in this filter"
    DEFVAL { 2 }
    ::=  { rsNewTrafficFilterEntry 23 }

rsNewTrafficFilterDnsTypeCNAME OBJECT-TYPE
    SYNTAX INTEGER {
              active(1),
              inactive(2)}
    ACCESS  read-write
    STATUS  mandatory
    DESCRIPTION
       "This variable indicates whether to check DNS Query Type CNAME in this filter"
    DEFVAL { 2 }
    ::=  { rsNewTrafficFilterEntry 24 }

rsNewTrafficFilterDnsTypeNS OBJECT-TYPE
    SYNTAX INTEGER {
              active(1),
              inactive(2)}
    ACCESS  read-write
    STATUS  mandatory
    DESCRIPTION
       "This variable indicates whether to check DNS Query Type NS in this filter"
    DEFVAL { 2 }
    ::=  { rsNewTrafficFilterEntry 25 }

rsNewTrafficFilterDnsTypeTXT OBJECT-TYPE
    SYNTAX INTEGER {
              active(1),
              inactive(2)}
    ACCESS  read-write
    STATUS  mandatory
    DESCRIPTION
       "This variable indicates whether to check DNS Query Type TXT in this filter"
    DEFVAL { 2 }
    ::=  { rsNewTrafficFilterEntry 26 }

rsNewTrafficFilterDnsTypeANY OBJECT-TYPE
    SYNTAX INTEGER {
              active(1),
              inactive(2)}
    ACCESS  read-write
    STATUS  mandatory
    DESCRIPTION
       "This variable indicates whether to check DNS Query Type ANY in this filter"
    DEFVAL { 2 }
    ::=  { rsNewTrafficFilterEntry 27 }

rsNewTrafficFilterDnsTypeSOA OBJECT-TYPE
    SYNTAX INTEGER {
              active(1),
              inactive(2)}
    ACCESS  read-write
    STATUS  mandatory
    DESCRIPTION
       "This variable indicates whether to check DNS Query Type SOA in this filter"
    DEFVAL { 2 }
    ::=  { rsNewTrafficFilterEntry 28 }

rsNewTrafficFilterThresholdPPS OBJECT-TYPE
    SYNTAX Counter64
    ACCESS read-write
    STATUS mandatory
    DESCRIPTION
      "The traffic filter threshold Packets Per Second."
    ::=  { rsNewTrafficFilterEntry 29 }

rsNewTrafficFilterThresholdBPS OBJECT-TYPE
    SYNTAX Counter64
    ACCESS read-write
    STATUS mandatory
    DESCRIPTION
      "The traffic filter threshold Packets Per Second."
    ::=  { rsNewTrafficFilterEntry 30 }

rsNewTrafficFilterPacketReport OBJECT-TYPE
	SYNTAX INTEGER {
	enable(1),
	disable(2)
	}
    ACCESS read-write
    STATUS mandatory
    DESCRIPTION
      "The traffic filter Packet Report status"
   DEFVAL  {disable}
    ::=  { rsNewTrafficFilterEntry 31 }

rsNewTrafficFilterRowStatus OBJECT-TYPE
    SYNTAX RowStatus
    ACCESS  read-write
    STATUS  mandatory
    DESCRIPTION
       "This variable indicates the administrative status of this entry.
       Used to delete an entry of this table."
    ::=  { rsNewTrafficFilterEntry 32 }

rsNewTrafficFilterThresholdUsed OBJECT-TYPE
	SYNTAX INTEGER {
	empty(0),
	kbps(1),
	pps(2)
	}
    ACCESS read-write
    STATUS mandatory
    DESCRIPTION
      "The traffic filter admin status"
   DEFVAL  {pps}
    ::=  { rsNewTrafficFilterEntry 33 }

rsNewTrafficFilterTTL OBJECT-TYPE
    SYNTAX DisplayString (SIZE(0..255))
    ACCESS  read-write
    STATUS  mandatory
    DESCRIPTION
       "This variable indicates the value of TTL in this filter."
    ::=  { rsNewTrafficFilterEntry 34 }

rsNewTrafficFilterSequenceNum OBJECT-TYPE
    SYNTAX DisplayString (SIZE(0..255))
    ACCESS  read-write
    STATUS  mandatory
    DESCRIPTION
       "The TCP Sequence number criteria in this filter."
    ::=  { rsNewTrafficFilterEntry 35 }

rsNewTrafficFilterFragId OBJECT-TYPE
    SYNTAX DisplayString (SIZE(0..255))
    ACCESS  read-write
    STATUS  mandatory
    DESCRIPTION
       "This variable indicates the fragment id in this filter."
    ::=  { rsNewTrafficFilterEntry 36 }


rsNewTrafficFilterFragOffset	OBJECT-TYPE
    SYNTAX DisplayString (SIZE(0..255))
    ACCESS  read-write
    STATUS  mandatory
    DESCRIPTION
       "This variable indicates the fragment offset in this filter."
    ::=  { rsNewTrafficFilterEntry 37 }

rsNewTrafficFilterAttackTrackingType OBJECT-TYPE
    SYNTAX INTEGER {
    drop(0),
    ncps(2),
    ncpd(3),
    ncpsd(4),
    reversedncps(5)
    }
    ACCESS  read-write
    STATUS  mandatory
    DESCRIPTION
       "This variable indicates how to count Traffic Filters"
    ::=  { rsNewTrafficFilterEntry 38}

rsNewTrafficFilterRegex OBJECT-TYPE
    SYNTAX DisplayString (SIZE(0..252))
    ACCESS  read-write
    STATUS  mandatory
    DESCRIPTION
       "This variable indicates the value of regex in this filter."
    ::=  { rsNewTrafficFilterEntry 39 }

 rsNewTrafficFilterTOS	OBJECT-TYPE
    SYNTAX DisplayString (SIZE(0..255))
    ACCESS  read-write
    STATUS  mandatory
    DESCRIPTION
       "This variable indicates the Type Of Service (TOS) in this filter."
    ::=  { rsNewTrafficFilterEntry 40 }

 rsNewTrafficFilterVLAN	OBJECT-TYPE
    SYNTAX DisplayString (SIZE(0..20))
    ACCESS  read-write
    STATUS  mandatory
    DESCRIPTION
       "This variable indicates the VLAN ID in this filter."
    ::=  { rsNewTrafficFilterEntry 41 }

-- Traffic Filter MIB split  rsNewTrafficFilterTableOne


rsNewTrafficFilterTableOne OBJECT-TYPE
    SYNTAX SEQUENCE OF RsNewTrafficFilterEntryOne
    ACCESS not-accessible
    STATUS  mandatory
    DESCRIPTION
      "Table containing the manual rules sources "
    ::=  {rsNewTrafficFilter 4}



rsNewTrafficFilterEntryOne OBJECT-TYPE
    SYNTAX RsNewTrafficFilterEntryOne
    ACCESS not-accessible
    STATUS  mandatory
    DESCRIPTION
       "The row definition for this table."
    INDEX { rsNewTrafficFilterProfileNameOne, rsNewTrafficFilterNameOne }
    ::=  { rsNewTrafficFilterTableOne 1 }

RsNewTrafficFilterEntryOne ::= SEQUENCE {
	rsNewTrafficFilterProfileNameOne 	DisplayString,
	rsNewTrafficFilterNameOne 		DisplayString,
	rsNewTrafficFilterDnsQueryNameOne	DisplayString,
	rsNewTrafficFilterPacketSizeOne		DisplayString,
	rsNewTrafficFilterSrcNetworkOne 	DisplayString,
	rsNewTrafficFilterSrcPortOne		DisplayString,
	rsNewTrafficFilterDstNetworkOne 	DisplayString,
	rsNewTrafficFilterDstPortOne		DisplayString,
	rsNewTrafficFilterThresholdPPSOne 	Counter64,
	rsNewTrafficFilterStateOne 		INTEGER,
	rsNewTrafficFilterProtocolOne		INTEGER,
	rsNewTrafficFilterRowStatusOne	 	RowStatus
}


rsNewTrafficFilterProfileNameOne OBJECT-TYPE
    SYNTAX DisplayString (SIZE(1..20))
    ACCESS  read-write
    STATUS  mandatory
    DESCRIPTION
      "The traffic filter profile name."
    ::=  {rsNewTrafficFilterEntryOne 1}

rsNewTrafficFilterNameOne OBJECT-TYPE
    SYNTAX DisplayString (SIZE(1..20))
    ACCESS  read-write
    STATUS  mandatory
    DESCRIPTION
      "The traffic filter name."
    ::=  {rsNewTrafficFilterEntryOne 2}


rsNewTrafficFilterDnsQueryNameOne OBJECT-TYPE
  SYNTAX DisplayString (SIZE(0..255))
    ACCESS  read-write
    STATUS  mandatory
    DESCRIPTION
      "The traffic filter DNS query name."
    ::=  {rsNewTrafficFilterEntryOne 3}


rsNewTrafficFilterPacketSizeOne OBJECT-TYPE
    SYNTAX DisplayString (SIZE(0..255))
    ACCESS read-write
    STATUS mandatory
    DESCRIPTION
      "The traffic filter size of packet."
    ::=  { rsNewTrafficFilterEntryOne 4 }

rsNewTrafficFilterSrcNetworkOne OBJECT-TYPE
    SYNTAX DisplayString (SIZE(0..46))
    ACCESS  read-write
    STATUS  mandatory
    DESCRIPTION
      "The source address / range of address for the packet, the name is
      defined in the Objects table or can be an IP address."
    ::=  {rsNewTrafficFilterEntryOne 5}

rsNewTrafficFilterSrcPortOne OBJECT-TYPE
    SYNTAX DisplayString (SIZE(0..30))
    ACCESS  read-write
    STATUS  mandatory
    DESCRIPTION
      "The traffic filter source port for the packet."
    ::=  {rsNewTrafficFilterEntryOne 6}

rsNewTrafficFilterDstNetworkOne OBJECT-TYPE
    SYNTAX DisplayString (SIZE(0..46))
    ACCESS  read-write
    STATUS  mandatory
    DESCRIPTION
      "The destination address / range of address for the packet, the name is
      defined in the Objects table or can be an IP address."
    ::=  {rsNewTrafficFilterEntryOne 7}

rsNewTrafficFilterDstPortOne OBJECT-TYPE
    SYNTAX DisplayString (SIZE(0..30))
    ACCESS  read-write
    STATUS  mandatory
    DESCRIPTION
      "The traffic filter destinatin port for the packet."
    ::=  {rsNewTrafficFilterEntryOne 8}

rsNewTrafficFilterThresholdPPSOne OBJECT-TYPE
    SYNTAX Counter64
    ACCESS read-write
    STATUS mandatory
    DESCRIPTION
      "The traffic filter threshold Packets Per Second."
    ::=  { rsNewTrafficFilterEntryOne 9 }


rsNewTrafficFilterStateOne OBJECT-TYPE
	SYNTAX INTEGER {
	enable(1),
	disable(2)
	}
    ACCESS read-write
    STATUS mandatory
    DESCRIPTION
      "The traffic filter admin status"
   DEFVAL  {enable}
    ::=  { rsNewTrafficFilterEntryOne 10 }

rsNewTrafficFilterProtocolOne OBJECT-TYPE
    SYNTAX INTEGER {
        any(0),
		tcp(1),
		udp(2),
		icmp(3),
		igmp(4),
		sctp(5),
		icmpv6(6)
    }
    ACCESS read-write
    STATUS mandatory
    DESCRIPTION
      "The traffic filter protocol."
    DEFVAL {0}
    ::=  { rsNewTrafficFilterEntryOne 11 }


rsNewTrafficFilterRowStatusOne OBJECT-TYPE
    SYNTAX RowStatus
    ACCESS  read-write
    STATUS  mandatory
    DESCRIPTION
       "This variable indicates the administrative status of this entry.
       Used to delete an entry of this table."
    ::=  { rsNewTrafficFilterEntryOne 12 }

-- Traffic Filter MIB split  rsNewTrafficFilterTableTwo


rsNewTrafficFilterTableTwo OBJECT-TYPE
    SYNTAX SEQUENCE OF RsNewTrafficFilterEntryTwo
    ACCESS not-accessible
    STATUS  mandatory
    DESCRIPTION
      "Table containing the manual rules sources "
    ::=  {rsNewTrafficFilter 5}



rsNewTrafficFilterEntryTwo OBJECT-TYPE
    SYNTAX RsNewTrafficFilterEntryTwo
    ACCESS not-accessible
    STATUS  mandatory
    DESCRIPTION
       "The row definition for this table."
    INDEX { rsNewTrafficFilterProfileNameTwo, rsNewTrafficFilterNameTwo }
    ::=  { rsNewTrafficFilterTableTwo 1 }

RsNewTrafficFilterEntryTwo ::= SEQUENCE {
	rsNewTrafficFilterProfileNameTwo 	DisplayString,
	rsNewTrafficFilterNameTwo 		DisplayString,
	rsNewTrafficFilterTCPFlagsSynTwo	INTEGER,
	rsNewTrafficFilterTCPFlagsAckTwo 	INTEGER,
	rsNewTrafficFilterTCPFlagsRstTwo 	INTEGER,
	rsNewTrafficFilterTCPFlagsSynAckTwo 	INTEGER,
	rsNewTrafficFilterTCPFlagsFinAckTwo 	INTEGER,
	rsNewTrafficFilterTCPFlagsPshAckTwo 	INTEGER,
	rsNewTrafficFilterRowStatusTwo	 	RowStatus
}


rsNewTrafficFilterProfileNameTwo OBJECT-TYPE
    SYNTAX DisplayString (SIZE(1..20))
    ACCESS  read-write
    STATUS  mandatory
    DESCRIPTION
      "The traffic filter profile name."
    ::=  {rsNewTrafficFilterEntryTwo 1}

rsNewTrafficFilterNameTwo OBJECT-TYPE
    SYNTAX DisplayString (SIZE(1..20))
    ACCESS  read-write
    STATUS  mandatory
    DESCRIPTION
      "The traffic filter name."
    ::=  {rsNewTrafficFilterEntryTwo 2}



rsNewTrafficFilterTCPFlagsSynTwo OBJECT-TYPE
    SYNTAX INTEGER {
              active(1),
              inactive(2)}
    ACCESS  read-write
    STATUS  mandatory
    DESCRIPTION
       "This variable indicates whether to check TCP SYN Flag in this filter"
    DEFVAL { 2 }
    ::=  { rsNewTrafficFilterEntryTwo 3 }

rsNewTrafficFilterTCPFlagsAckTwo OBJECT-TYPE
    SYNTAX INTEGER {
              active(1),
              inactive(2)}
    ACCESS  read-write
    STATUS  mandatory
    DESCRIPTION
       "This variable indicates whether to check TCP ACK Flag in this filter"
    DEFVAL { 2 }
    ::=  { rsNewTrafficFilterEntryTwo 4 }

rsNewTrafficFilterTCPFlagsRstTwo OBJECT-TYPE
    SYNTAX INTEGER {
              active(1),
              inactive(2)}
    ACCESS  read-write
    STATUS  mandatory
    DESCRIPTION
       "This variable indicates whether to check TCP RST Flag in this filter"
    DEFVAL { 2 }
    ::=  { rsNewTrafficFilterEntryTwo 5 }


rsNewTrafficFilterTCPFlagsSynAckTwo OBJECT-TYPE
    SYNTAX INTEGER {
              active(1),
              inactive(2)}
    ACCESS  read-write
    STATUS  mandatory
    DESCRIPTION
       "This variable indicates whether to check TCP SYN-ACK Flag in this filter"
    DEFVAL { 2 }
    ::=  { rsNewTrafficFilterEntryTwo 6 }

rsNewTrafficFilterTCPFlagsFinAckTwo OBJECT-TYPE
    SYNTAX INTEGER {
              active(1),
              inactive(2)}
    ACCESS  read-write
    STATUS  mandatory
    DESCRIPTION
       "This variable indicates whether to check TCP FIN-ACK Flag in this filter"
    DEFVAL { 2 }
    ::=  { rsNewTrafficFilterEntryTwo 7 }

rsNewTrafficFilterTCPFlagsPshAckTwo OBJECT-TYPE
    SYNTAX INTEGER {
              active(1),
              inactive(2)}
    ACCESS  read-write
    STATUS  mandatory
    DESCRIPTION
       "This variable indicates whether to check TCP PSH-ACK Flag in this filter"
    DEFVAL { 2 }
    ::=  { rsNewTrafficFilterEntryTwo 8 }


rsNewTrafficFilterRowStatusTwo OBJECT-TYPE
    SYNTAX RowStatus
    ACCESS  read-write
    STATUS  mandatory
    DESCRIPTION
       "This variable indicates the administrative status of this entry.
       Used to delete an entry of this table."
    ::=  { rsNewTrafficFilterEntryTwo 9 }


-- Traffic Filter MIB split  rsNewTrafficFilterTableThree



rsNewTrafficFilterTableThree OBJECT-TYPE
    SYNTAX SEQUENCE OF RsNewTrafficFilterEntryThree
    ACCESS not-accessible
    STATUS  mandatory
    DESCRIPTION
      "Table containing the manual rules sources "
    ::=  {rsNewTrafficFilter 6}



rsNewTrafficFilterEntryThree OBJECT-TYPE
    SYNTAX RsNewTrafficFilterEntryThree
    ACCESS not-accessible
    STATUS  mandatory
    DESCRIPTION
       "The row definition for this table."
    INDEX { rsNewTrafficFilterProfileNameThree, rsNewTrafficFilterNameThree }
    ::=  { rsNewTrafficFilterTableThree 1 }

RsNewTrafficFilterEntryThree ::= SEQUENCE {
	rsNewTrafficFilterProfileNameThree 	DisplayString,
	rsNewTrafficFilterNameThree 		DisplayString,
	rsNewTrafficFilterDnsTypeAThree		INTEGER,
	rsNewTrafficFilterDnsTypeAAAAThree INTEGER,
	rsNewTrafficFilterDnsTypeMXThree INTEGER,
	rsNewTrafficFilterDnsTypePTRThree INTEGER,
	rsNewTrafficFilterDnsTypeCNAMEThree INTEGER,
	rsNewTrafficFilterDnsTypeNSThree INTEGER,
	rsNewTrafficFilterDnsTypeTXTThree INTEGER,
	rsNewTrafficFilterDnsTypeANYThree INTEGER,
	rsNewTrafficFilterDnsTypeSOAThree INTEGER,
	rsNewTrafficFilterRowStatusThree 	RowStatus
}


rsNewTrafficFilterProfileNameThree OBJECT-TYPE
    SYNTAX DisplayString (SIZE(1..20))
    ACCESS  read-write
    STATUS  mandatory
    DESCRIPTION
      "The traffic filter profile name."
    ::=  {rsNewTrafficFilterEntryThree 1}

rsNewTrafficFilterNameThree OBJECT-TYPE
    SYNTAX DisplayString (SIZE(1..20))
    ACCESS  read-write
    STATUS  mandatory
    DESCRIPTION
      "The traffic filter name."
    ::=  {rsNewTrafficFilterEntryThree 2}


rsNewTrafficFilterDnsTypeAThree OBJECT-TYPE
    SYNTAX INTEGER {
              active(1),
              inactive(2)}
    ACCESS  read-write
    STATUS  mandatory
    DESCRIPTION
       "This variable indicates whether to check DNS Query Type A in this filter"
    DEFVAL { 2 }
    ::=  { rsNewTrafficFilterEntryThree 3}


rsNewTrafficFilterDnsTypeAAAAThree OBJECT-TYPE
    SYNTAX INTEGER {
              active(1),
              inactive(2)}
    ACCESS  read-write
    STATUS  mandatory
    DESCRIPTION
       "This variable indicates whether to check DNS Query Type AAAA in this filter"
    DEFVAL { 2 }
    ::=  { rsNewTrafficFilterEntryThree 4}

    rsNewTrafficFilterDnsTypeMXThree OBJECT-TYPE
    SYNTAX INTEGER {
              active(1),
              inactive(2)}
    ACCESS  read-write
    STATUS  mandatory
    DESCRIPTION
       "This variable indicates whether to check DNS Query Type MX in this filter"
    DEFVAL { 2 }
    ::=  { rsNewTrafficFilterEntryThree 5}

rsNewTrafficFilterDnsTypePTRThree OBJECT-TYPE
    SYNTAX INTEGER {
              active(1),
              inactive(2)}
    ACCESS  read-write
    STATUS  mandatory
    DESCRIPTION
       "This variable indicates whether to check DNS Query Type PTR in this filter"
    DEFVAL { 2 }
    ::=  { rsNewTrafficFilterEntryThree 6}

rsNewTrafficFilterDnsTypeCNAMEThree OBJECT-TYPE
    SYNTAX INTEGER {
              active(1),
              inactive(2)}
    ACCESS  read-write
    STATUS  mandatory
    DESCRIPTION
       "This variable indicates whether to check DNS Query Type CNAME in this filter"
    DEFVAL { 2 }
    ::=  { rsNewTrafficFilterEntryThree 7}

rsNewTrafficFilterDnsTypeNSThree OBJECT-TYPE
    SYNTAX INTEGER {
              active(1),
              inactive(2)}
    ACCESS  read-write
    STATUS  mandatory
    DESCRIPTION
       "This variable indicates whether to check DNS Query Type NS in this filter"
    DEFVAL { 2 }
    ::=  { rsNewTrafficFilterEntryThree 8}

rsNewTrafficFilterDnsTypeTXTThree OBJECT-TYPE
    SYNTAX INTEGER {
              active(1),
              inactive(2)}
    ACCESS  read-write
    STATUS  mandatory
    DESCRIPTION
       "This variable indicates whether to check DNS Query Type TXT in this filter"
    DEFVAL { 2 }
    ::=  { rsNewTrafficFilterEntryThree 9}

rsNewTrafficFilterDnsTypeANYThree OBJECT-TYPE
    SYNTAX INTEGER {
              active(1),
              inactive(2)}
    ACCESS  read-write
    STATUS  mandatory
    DESCRIPTION
       "This variable indicates whether to check DNS Query Type ANY in this filter"
    DEFVAL { 2 }
    ::=  { rsNewTrafficFilterEntryThree 10}

rsNewTrafficFilterDnsTypeSOAThree OBJECT-TYPE
    SYNTAX INTEGER {
              active(1),
              inactive(2)}
    ACCESS  read-write
    STATUS  mandatory
    DESCRIPTION
       "This variable indicates whether to check DNS Query Type SOA in this filter"
    DEFVAL { 2 }
    ::=  { rsNewTrafficFilterEntryThree 11}


rsNewTrafficFilterRowStatusThree OBJECT-TYPE
    SYNTAX RowStatus
    ACCESS  read-write
    STATUS  mandatory
    DESCRIPTION
       "This variable indicates the administrative status of this entry.
       Used to delete an entry of this table."
    ::=  { rsNewTrafficFilterEntryThree 12 }


-- Traffic Filter MIB split  rsNewTrafficFilterTableFour


rsNewTrafficFilterTableFour OBJECT-TYPE
    SYNTAX SEQUENCE OF RsNewTrafficFilterEntryFour
    ACCESS not-accessible
    STATUS  mandatory
    DESCRIPTION
      "Table containing the manual rules sources "
    ::=  {rsNewTrafficFilter 7}



rsNewTrafficFilterEntryFour OBJECT-TYPE
    SYNTAX RsNewTrafficFilterEntryFour
    ACCESS not-accessible
    STATUS  mandatory
    DESCRIPTION
       "The row definition for this table."
    INDEX { rsNewTrafficFilterProfileNameFour, rsNewTrafficFilterNameFour }
    ::=  { rsNewTrafficFilterTableFour 1 }

RsNewTrafficFilterEntryFour ::= SEQUENCE {
	rsNewTrafficFilterProfileNameFour 	DisplayString,
	rsNewTrafficFilterNameFour 		DisplayString,
	rsNewTrafficFilterThresholdBPSFour	 Counter64,
	rsNewTrafficFilterPacketReportFour 	INTEGER,
	rsNewTrafficFilterThresholdUsedFour 	INTEGER,
	rsNewTrafficFilterIDFour		INTEGER,
	rsNewTrafficFilterPriorityFour		INTEGER,
	rsNewTrafficFilterMatchCriteriaFour 	INTEGER,
	rsNewTrafficFilterRowStatusFour RowStatus
}


rsNewTrafficFilterProfileNameFour OBJECT-TYPE
    SYNTAX DisplayString (SIZE(1..20))
    ACCESS  read-write
    STATUS  mandatory
    DESCRIPTION
      "The traffic filter profile name."
    ::=  {rsNewTrafficFilterEntryFour 1}

rsNewTrafficFilterNameFour OBJECT-TYPE
    SYNTAX DisplayString (SIZE(1..20))
    ACCESS  read-write
    STATUS  mandatory
    DESCRIPTION
      "The traffic filter name."
    ::=  {rsNewTrafficFilterEntryFour 2}


rsNewTrafficFilterThresholdBPSFour OBJECT-TYPE
    SYNTAX Counter64
    ACCESS read-write
    STATUS mandatory
    DESCRIPTION
      "The traffic filter threshold Packets Per Second."
    ::=  { rsNewTrafficFilterEntryFour 3 }

rsNewTrafficFilterPacketReportFour OBJECT-TYPE
	SYNTAX INTEGER {
	enable(1),
	disable(2)
	}
    ACCESS read-write
    STATUS mandatory
    DESCRIPTION
      "The traffic filter Packet Report status"
   DEFVAL  {disable}
    ::=  { rsNewTrafficFilterEntryFour 4 }


rsNewTrafficFilterThresholdUsedFour OBJECT-TYPE
	SYNTAX INTEGER {
	empty(0),
	kbps(1),
	pps(2)
	}
    ACCESS read-write
    STATUS mandatory
    DESCRIPTION
      "The traffic filter admin status"
   DEFVAL  {pps}
    ::=  { rsNewTrafficFilterEntryFour 5 }


rsNewTrafficFilterIDFour OBJECT-TYPE
    SYNTAX INTEGER
    ACCESS read-write
    STATUS mandatory
    DESCRIPTION
      "This variable indicates the traffic filter ID."
    ::= {rsNewTrafficFilterEntryFour 6 }



rsNewTrafficFilterPriorityFour OBJECT-TYPE
    SYNTAX INTEGER (0..14)
    ACCESS read-write
    STATUS mandatory
    DESCRIPTION
      "This variable indicates the traffic filter Priority."
    ::= {rsNewTrafficFilterEntryFour 7  }

rsNewTrafficFilterMatchCriteriaFour OBJECT-TYPE
	SYNTAX INTEGER {
	match(1),
	not-match(2)
	}
	ACCESS read-write
	STATUS mandatory
	DESCRIPTION
	"The traffic filter matching criteria"
	DEFVAL  {1}
	::=  { rsNewTrafficFilterEntryFour 8 }


rsNewTrafficFilterRowStatusFour OBJECT-TYPE
    SYNTAX RowStatus
    ACCESS  read-write
    STATUS  mandatory
    DESCRIPTION
       "This variable indicates the administrative status of this entry.
       Used to delete an entry of this table."
    ::=  { rsNewTrafficFilterEntryFour 9 }

--
-- Trafic_filter Profile definition
--

rsNewTrafficProfileTable OBJECT-TYPE
    SYNTAX SEQUENCE OF RsNewTrafficProfileEntry
    ACCESS not-accessible
    STATUS  mandatory
    DESCRIPTION
      "Table containing the Traffic Profiles"
    ::=  {rsNewTrafficFilter 2}

rsNewTrafficProfileEntry OBJECT-TYPE
    SYNTAX RsNewTrafficProfileEntry
    ACCESS not-accessible
    STATUS  mandatory
    DESCRIPTION
       "The row definition for the profile table."
    INDEX { rsNewTrafficProfileName }
    ::=  { rsNewTrafficProfileTable 1 }

RsNewTrafficProfileEntry ::= SEQUENCE {
	rsNewTrafficProfileName DisplayString,
	rsNewTrafficProfileNumOfRules INTEGER,
	rsNewTrafficProfileAction INTEGER,
	rsNewTrafficProfileRowStatus RowStatus
}

rsNewTrafficProfileName OBJECT-TYPE
    SYNTAX DisplayString (SIZE(1..29))
    ACCESS  read-write
    STATUS  mandatory
    DESCRIPTION
      "The traffic_filter profile name."
    ::=  {rsNewTrafficProfileEntry 1}

rsNewTrafficProfileNumOfRules OBJECT-TYPE
    SYNTAX INTEGER
    ACCESS read-only
    STATUS mandatory
    DESCRIPTION
      "The number of rules in a trafic filter profile."
      DEFVAL {0}
    ::=  { rsNewTrafficProfileEntry 2 }

rsNewTrafficProfileAction OBJECT-TYPE
    SYNTAX INTEGER {
	    report-only(0),
	    drop(1)}
    ACCESS  read-write
    STATUS  mandatory
    DESCRIPTION
       "This variable indicates the profile action"
	   DEFVAL {0}
    ::=  { rsNewTrafficProfileEntry 3 }

rsNewTrafficProfileRowStatus OBJECT-TYPE
    SYNTAX RowStatus
    ACCESS  read-write
    STATUS  mandatory
    DESCRIPTION
       "This variable indicates the administrative status of this entry.
       Used to delete an entry of this table."
    ::=  { rsNewTrafficProfileEntry 4 }

--
-- Trafic_filter filters Priority auxiliary table definitions.
--


rsNewTrafficFiltersPriorityAuxTable OBJECT-TYPE
    SYNTAX SEQUENCE OF RsNewTrafficFiltersPriorityEntry
    ACCESS not-accessible
    STATUS  mandatory
    DESCRIPTION
      "Table containing the Traffic Profiles"
    ::=  {rsNewTrafficFilter 3}

rsNewTrafficFiltersPriorityEntry OBJECT-TYPE
    SYNTAX RsNewTrafficFiltersPriorityEntry
    ACCESS not-accessible
    STATUS  mandatory
    DESCRIPTION
       "The row definition for the profile table."
    INDEX { rsNewTrafficFilterPriorityProfileName }
    ::=  { rsNewTrafficFiltersPriorityAuxTable 1 }

RsNewTrafficFiltersPriorityEntry ::= SEQUENCE {
	rsNewTrafficFilterPriorityProfileName   DisplayString,
	rsNewTrafficFiltersPriorityList DisplayString,
	rsNewTrafficFilterPriorityRowStatus RowStatus
}

rsNewTrafficFilterPriorityProfileName OBJECT-TYPE
    SYNTAX DisplayString (SIZE(1..29))
    ACCESS  read-write
    STATUS  mandatory
    DESCRIPTION
      "The traffic_filter profile name."
    ::=  {rsNewTrafficFiltersPriorityEntry 1}

rsNewTrafficFiltersPriorityList OBJECT-TYPE
    SYNTAX DisplayString (SIZE(1..255))
    ACCESS  read-write
    STATUS  mandatory
    DESCRIPTION
      "The list of filters (rule IDs) representing priority in descending order."
    ::=  {rsNewTrafficFiltersPriorityEntry 2}

rsNewTrafficFilterPriorityRowStatus OBJECT-TYPE
    SYNTAX RowStatus
    ACCESS  read-write
    STATUS  mandatory
    DESCRIPTION
       "This variable indicates the administrative status of this entry.
       Used to delete an entry of this table."
    ::=  { rsNewTrafficFiltersPriorityEntry 3 }

--
-- Trafic_filter filters Aux table, used by VISION to support link from attack details to configuration.
--


rsNewTrafficFiltersAttackDetailsLinkAuxTable OBJECT-TYPE
    SYNTAX SEQUENCE OF RsNewTrafficFiltersAttackDetailsLinkAuxEntry
    ACCESS not-accessible
    STATUS  mandatory
    DESCRIPTION
      "Table containing the Traffic Profiles"
    ::=  {rsNewTrafficFilter 8}

rsNewTrafficFiltersAttackDetailsLinkAuxEntry OBJECT-TYPE
    SYNTAX RsNewTrafficFiltersAttackDetailsLinkAuxEntry
    ACCESS not-accessible
    STATUS  mandatory
    DESCRIPTION
       "Aux MIB used by VISION to support link from attack details to profile configuration."
    INDEX { rsPolicyeName,rsFilterID }
    ::=  { rsNewTrafficFiltersAttackDetailsLinkAuxTable 1 }

RsNewTrafficFiltersAttackDetailsLinkAuxEntry ::= SEQUENCE {
	rsPolicyeName   DisplayString,
	rsFilterID INTEGER,
	rsFilterName DisplayString,
	rsProfileName DisplayString,
	rsRowStatus RowStatus
}

rsPolicyeName OBJECT-TYPE
    SYNTAX DisplayString (SIZE(1..29))
    ACCESS  read-write
    STATUS  mandatory
    DESCRIPTION
      "The policy name which attack occured on. first part of the key"
    ::=  {rsNewTrafficFiltersAttackDetailsLinkAuxEntry 1}


rsFilterID OBJECT-TYPE
    SYNTAX INTEGER
    ACCESS read-only
    STATUS mandatory
    DESCRIPTION
      "The file ID. second part of the key to find the filter."
      DEFVAL {0}
    ::=  { rsNewTrafficFiltersAttackDetailsLinkAuxEntry 2 }



rsFilterName OBJECT-TYPE
    SYNTAX DisplayString (SIZE(1..29))
    ACCESS  read-only
    STATUS  mandatory
    DESCRIPTION
      "The filter name that attack occured on."
    ::=  {rsNewTrafficFiltersAttackDetailsLinkAuxEntry 3}


rsProfileName OBJECT-TYPE
    SYNTAX DisplayString (SIZE(1..29))
    ACCESS  read-write
    STATUS  mandatory
    DESCRIPTION
      "The policy name which attack occured on. first part of the key"
    ::=  {rsNewTrafficFiltersAttackDetailsLinkAuxEntry 4}



rsRowStatus OBJECT-TYPE
    SYNTAX RowStatus
    ACCESS  read-write
    STATUS  mandatory
    DESCRIPTION
       "This variable indicates the administrative status of this entry.
       Used to delete an entry of this table."
    ::=  { rsNewTrafficFiltersAttackDetailsLinkAuxEntry 5 }



rsNewTrafficFilterNextID OBJECT-TYPE
	SYNTAX INTEGER
    ACCESS read-only
    STATUS mandatory
    DESCRIPTION
		"the next filter id for Traffic Filters"
    ::= {rsNewTrafficFilter 9}

-- NOTE: there is a MIB gap between 178 <-> 180,182 and 185 and above Please use it.

END
