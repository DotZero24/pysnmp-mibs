ACC-MIB DEFINITIONS ::= BEGIN

-- Title:      RADWARE
--             This Private MIB supports the Vgate
-- Version:    3.0
-- Date:       24 May 2016
-- By:         RMA (Radware MIB Authority)
-- E-mail:     US:            support@radware.com
--             International: support_int@radware.com
--
IMPORTS
       NetworkAddress,
       IpAddress,
       Counter,
       Gauge,
       enterprises
              FROM RFC1155-SMI
       OBJECT-TYPE
              FROM RFC-1212
       DisplayString,
       PhysAddress,
       ipAddrEntry
              FROM RFC1213-MIB
       TRAP-TYPE
                    FROM RFC-1215
       rsACC,
       rndErrorDesc,
       rndErrorSeverity,
       TruthValue,
       RowStatus,
       FeatureStatus
                    FROM RADWARE-MIB;

    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rsACCStatTable OBJECT-TYPE
    SYNTAX SEQUENCE OF RsACCStatEntry
    ACCESS not-accessible
    STATUS  mandatory
    DESCRIPTION
      "Table for the accelerator statistics table"
    ::=  {rsACC 1}

rsACCStatEntry OBJECT-TYPE
    SYNTAX RsACCStatEntry
    ACCESS not-accessible
    STATUS  mandatory
    DESCRIPTION
       "the row definition for this table"
   INDEX { rsACCStatId }
    ::=  {rsACCStatTable 1}

RsACCStatEntry ::= SEQUENCE {
  rsACCStatId        INTEGER,
  rsACCStatValue     INTEGER
  }

rsACCStatId OBJECT-TYPE
    SYNTAX INTEGER {
		received(0),
		discardImmediate(1),
		masterImmediate(2),
		macDiscard(3),
		masterNoFlow(4),
		discardBrgLimit(5),
		discardRtrLimit(6),
		masterBrgLimit(7),
		masterRtrLimit(8),
		bridgeDiscard(9),
		routerDiscard(10),
		masterBridge(11),
		masterRouter(12),
		bridgeForward(13),
		routerForward(14),
		bindSyn(15),
		ackForSyn(16),
		cookieData(17),
		invalidCookie(18),
		cookieNotFirst(19),
		bypassAcc(20),
		bypassMaster(21),
		bypassAccBytes(22),
		bypassMasterBytes(23),
		forwardImmediate(24),
		toSmeSent(25),
		toSmeErrors(26),
		fromSmeReceived(27),
		fromSmeBadConfigId(28),
		fromSmeTooManyResults(29),
		fromSmeHwError(30),
		fromSmeTrackingError(31),
		fromSmeToMaster(32),
		fromSmeForward(33),
		fromSmeBypass(34),
		fromSmeDiscard(35),
		fromSmeMatches(36),
		ipFragsToMaster(37),
		ipFragsDiscard(38),
		httpRplyTotal(39),
		httpRplyClassify(40),
		httpRplyAccMarked(41),
		httpRplyAccUnmarked(42),
		httpRplySmeMarked(43),
		debugToMaster(44),
        smeBypassErr(45),
        smeBypassFlow(46),
        smeBypassMarked(47),
        queuedPackets(48),
        fromSmeBadCompileId(49),
        accessListDiscard(50),
        accessListBypass(51),
        accessListToMaster(52),
        fromSmeNFAError(53),
        webCookiesDiscard(54),
        webCookiesForward(55),
        safeRstChallenge(56),
	tcpRstChallenge(57)
	}
    ACCESS  read-only
    STATUS  mandatory
    DESCRIPTION
      "accelerator's statistics id"
    ::=  {rsACCStatEntry 1}

rsACCStatValue OBJECT-TYPE
    SYNTAX  INTEGER
    ACCESS  read-only
    STATUS  mandatory
    DESCRIPTION
      "accelerator's statistic value"
    ::=  {rsACCStatEntry 2}

rsACCUseFlowTable OBJECT-TYPE
    SYNTAX FeatureStatus
    ACCESS  read-write
    STATUS  mandatory
    DESCRIPTION "Traffic that is not added to the flow table will be
    sent to the master CPU."
--  DEFVAL {enable}
    ::= {rsACC 2}

rsACCResourceTable OBJECT-TYPE
    SYNTAX SEQUENCE OF RsACCResourceEntry
    ACCESS not-accessible
    STATUS  mandatory
    DESCRIPTION
      "Table for the accelerator resource table"
    ::=  {rsACC 3}

rsACCResourceEntry OBJECT-TYPE
    SYNTAX RsACCResourceEntry
    ACCESS not-accessible
    STATUS  mandatory
    DESCRIPTION
       "the row definition for this table"
   INDEX {rsACCCPUId}
    ::=  {rsACCResourceTable 1}

RsACCResourceEntry ::= SEQUENCE {
  rsACCInstanceId   INTEGER,
  rsACCId           INTEGER,
  rsACCCPUId        INTEGER,
  rsACCFlow         INTEGER,
  rsACCOther        INTEGER,
  rsACCIdle         INTEGER
  }

rsACCInstanceId OBJECT-TYPE
    SYNTAX INTEGER
    ACCESS  read-only
    STATUS  obsolete
    DESCRIPTION
      "platform instance id the accelerator is in"
    ::=  {rsACCResourceEntry 1}


rsACCId OBJECT-TYPE
    SYNTAX INTEGER
    ACCESS  read-only
    STATUS  obsolete
    DESCRIPTION
      "accelerator id"
    ::=  {rsACCResourceEntry 2}

rsACCCPUId OBJECT-TYPE
    SYNTAX INTEGER
    ACCESS  read-only
    STATUS  mandatory
    DESCRIPTION
      "cpu id"
    ::=  {rsACCResourceEntry 3}

rsACCFlow OBJECT-TYPE
    SYNTAX INTEGER
    ACCESS  read-only
    STATUS  mandatory
    DESCRIPTION
      "Utilization percentage of flow task"
    ::=  {rsACCResourceEntry 4}

rsACCOther OBJECT-TYPE
    SYNTAX INTEGER
    ACCESS  read-only
    STATUS  mandatory
    DESCRIPTION
      "Utilization percentage of the other tasks"
    ::=  {rsACCResourceEntry 5}

rsACCIdle OBJECT-TYPE
    SYNTAX INTEGER
    ACCESS  read-only
    STATUS  mandatory
    DESCRIPTION
      "Percentage of the idle time"
    ::=  {rsACCResourceEntry 6}


rsACCFFTRouteIgnore OBJECT-TYPE
    SYNTAX FeatureStatus
    ACCESS  read-write
    STATUS  mandatory
    DESCRIPTION "The source MAC address will be learnt from the packet
    received and not through the routing table."
--  DEFVAL {enable}
    ::= {rsACC 4}

rsACCHardwareClassification OBJECT-TYPE
    SYNTAX FeatureStatus
    ACCESS  read-write
    STATUS  mandatory
    DESCRIPTION "Indicates if hardware classification is enabled."
--  DEFVAL {enable}
    ::= {rsACC 5}

rsACCSMEStatisticsTable OBJECT-TYPE
    SYNTAX SEQUENCE OF RsACCSMEStatisticsEntry
    ACCESS not-accessible
    STATUS  mandatory
    DESCRIPTION
      "Table for the accelerator SME statistics table"
    ::=  {rsACC 6}

rsACCSMEStatisticsEntry OBJECT-TYPE
    SYNTAX RsACCSMEStatisticsEntry
    ACCESS not-accessible
    STATUS  mandatory
    DESCRIPTION
       "the row definition for this table"
   INDEX { rsACCSMEId }
    ::=  {rsACCSMEStatisticsTable 1}

RsACCSMEStatisticsEntry ::= SEQUENCE {
  rsACCSMEId                    INTEGER,
  rsACCSMEResultsReceived       INTEGER,
  rsACCSMEResultsForward        INTEGER,
  rsACCSMEResultsDiscarded      INTEGER,
  rsACCSMEResultsNext           INTEGER,
  rsACCSMEResultsFree           INTEGER,
  rsACCSMERequestSent           INTEGER,
  rsACCSMERequestInvalidData    INTEGER,
  rsACCSMERequestFailed         INTEGER,
  rsACCSMEDiscard               INTEGER,
  rsACCSMETooManyResults        INTEGER,
  rsACCSMEHWHWProblem           INTEGER,
  rsACCSMEFragmented            INTEGER
}

rsACCSMEId OBJECT-TYPE
    SYNTAX INTEGER
    ACCESS  read-only
    STATUS  mandatory
    DESCRIPTION
      "The SME id"
    ::=  {rsACCSMEStatisticsEntry 1}

rsACCSMEResultsReceived OBJECT-TYPE
    SYNTAX INTEGER
    ACCESS  read-only
    STATUS  mandatory
    DESCRIPTION
      "The number of results received"
    ::=  {rsACCSMEStatisticsEntry 2}

rsACCSMEResultsForward OBJECT-TYPE
    SYNTAX INTEGER
    ACCESS  read-only
    STATUS  mandatory
    DESCRIPTION
      "The number of results forwarded"
    ::=  {rsACCSMEStatisticsEntry 3}

rsACCSMEResultsDiscarded OBJECT-TYPE
    SYNTAX INTEGER
    ACCESS  read-only
    STATUS  mandatory
    DESCRIPTION
      "The number of results discarded"
    ::=  {rsACCSMEStatisticsEntry 4}

rsACCSMEResultsNext OBJECT-TYPE
    SYNTAX INTEGER
    ACCESS  read-only
    STATUS  mandatory
    DESCRIPTION
      "The number of results processed by another task"
    ::=  {rsACCSMEStatisticsEntry 5}

rsACCSMEResultsFree OBJECT-TYPE
    SYNTAX INTEGER
    ACCESS  read-only
    STATUS  mandatory
    DESCRIPTION
      "The number of results freed"
    ::=  {rsACCSMEStatisticsEntry 6}

rsACCSMERequestSent OBJECT-TYPE
    SYNTAX INTEGER
    ACCESS  read-only
    STATUS  mandatory
    DESCRIPTION
      "The number of requests sent"
    ::=  {rsACCSMEStatisticsEntry 7}

rsACCSMERequestInvalidData OBJECT-TYPE
    SYNTAX INTEGER
    ACCESS  read-only
    STATUS  mandatory
    DESCRIPTION
      "The number of invaild data sent"
    ::=  {rsACCSMEStatisticsEntry 8}

rsACCSMERequestFailed OBJECT-TYPE
    SYNTAX INTEGER
    ACCESS  read-only
    STATUS  mandatory
    DESCRIPTION
      "The number of falied requests"
    ::=  {rsACCSMEStatisticsEntry 9}

rsACCSMEDiscard OBJECT-TYPE
    SYNTAX INTEGER
    ACCESS  read-only
    STATUS  mandatory
    DESCRIPTION
      "The number of SME discards"
    ::=  {rsACCSMEStatisticsEntry 10}

rsACCSMETooManyResults OBJECT-TYPE
    SYNTAX INTEGER
    ACCESS  read-only
    STATUS  mandatory
    DESCRIPTION
      "Too many matched found by SME"
    ::=  {rsACCSMEStatisticsEntry 11}

rsACCSMEHWHWProblem OBJECT-TYPE
    SYNTAX INTEGER
    ACCESS  read-only
    STATUS  mandatory
    DESCRIPTION
      "SME hardware problem"
    ::=  {rsACCSMEStatisticsEntry 12}

rsACCSMEFragmented OBJECT-TYPE
    SYNTAX INTEGER
    ACCESS  read-only
    STATUS  mandatory
    DESCRIPTION
      "Fragmentation detected"
    ::=  {rsACCSMEStatisticsEntry 13}

rsACCSwitchMode OBJECT-TYPE
    SYNTAX INTEGER {
        layer3 (1),
        layer4 (2)
    }
    ACCESS  read-write
    STATUS  mandatory
    DESCRIPTION "The mode of persistency for the switch."
--  DEFVAL {layer3}
    ::= {rsACC 7}

rsACCTrunkMode OBJECT-TYPE
    SYNTAX INTEGER {
        static(1),
        dynamic(2)
    }
    ACCESS  read-write
    STATUS  mandatory
    DESCRIPTION "Enables the user to set internal trunk mode to be static or dynamic"
--  DEFVAL {dynamic}
    ::= {rsACC 8}

rsACCWorkingMode OBJECT-TYPE
    SYNTAX INTEGER {
        standard(1),
        single(2),
        dual(3)
    }
    ACCESS  read-only
    STATUS  mandatory
    DESCRIPTION "Two accelerators working modes."
--  DEFVAL {standard}
    ::= {rsACC 9}


rsSystemSmeEngineUtilizationTable OBJECT-TYPE
    SYNTAX SEQUENCE OF RsSmeEngineUtilizationEntry
    ACCESS not-accessible
    STATUS  mandatory
    DESCRIPTION "SME engines utilization"
    ::=  {rsACC 10}

rsSmeEngineUtilizationEntry OBJECT-TYPE
    SYNTAX RsSmeEngineUtilizationEntry
    ACCESS not-accessible
    STATUS  mandatory
    DESCRIPTION "The SME engines utilization"
    INDEX { rsSmeUtilizationInstanceId, rsSMEEnginesUtilId }
    ::=  {rsSystemSmeEngineUtilizationTable 1}

RsSmeEngineUtilizationEntry ::= SEQUENCE {
  rsSmeUtilizationInstanceId            INTEGER,
  rsSMEEnginesUtilId			INTEGER,
  rsSmeNfaUtilization			INTEGER,
  rsSmeDfaUtilization			INTEGER,
  rsSmeDMaUtilization			INTEGER,
  rsSmeCntTotalTime				DisplayString,
  rsSmeDfaBusy					DisplayString,
  rsSmeDfaBusyDmaDataStarve		DisplayString,
  rsSmeDfaBusyNfaDataStall		DisplayString,
  rsSmeDfaMemStall				DisplayString,
  rsSmeNfaBusyReadState			DisplayString,
  rsSmeNfaStateProcessed		DisplayString,
  rsSmeNfaBytesProcessed		DisplayString,
  rsSmeCntTotalBytes			DisplayString,
  rsSmeNfaMemStall				DisplayString,
  rsSmeNfaStatesAverage			INTEGER,
  rsSmeNfaMemStallsPerByteProc	INTEGER,
  rsSmeNfaSatesWhenNfaBusy		INTEGER
}

rsSmeUtilizationInstanceId OBJECT-TYPE
    SYNTAX	INTEGER
    ACCESS  read-only
    STATUS  mandatory
    DESCRIPTION
      "Platform instance id the SME is on"
    ::=  {rsSmeEngineUtilizationEntry 1}

rsSMEEnginesUtilId OBJECT-TYPE
    SYNTAX	INTEGER
    ACCESS  read-only
    STATUS  mandatory
    DESCRIPTION
      "The SME id"
    ::=  {rsSmeEngineUtilizationEntry 2}

rsSmeNfaUtilization OBJECT-TYPE
    SYNTAX	INTEGER
    ACCESS  read-only
    STATUS  mandatory
    DESCRIPTION
      "The SME NFA utilization"
    ::=  {rsSmeEngineUtilizationEntry 3}

rsSmeDfaUtilization OBJECT-TYPE
    SYNTAX	INTEGER
    ACCESS  read-only
    STATUS  mandatory
    DESCRIPTION
      "The SME DFA utilization"
    ::=  {rsSmeEngineUtilizationEntry 4}

rsSmeDMaUtilization OBJECT-TYPE
    SYNTAX	INTEGER
    ACCESS  read-only
    STATUS  mandatory
    DESCRIPTION
      "The SME DMA utilization"
    ::=  {rsSmeEngineUtilizationEntry 5}

rsSmeCntTotalTime OBJECT-TYPE
    SYNTAX	DisplayString (SIZE(0..128))
    ACCESS  read-only
    STATUS  mandatory
    DESCRIPTION
      "Total time counter"
    ::=  {rsSmeEngineUtilizationEntry 6}

rsSmeDfaBusy OBJECT-TYPE
    SYNTAX	DisplayString (SIZE(0..128))
    ACCESS  read-only
    STATUS  mandatory
    DESCRIPTION
      "DFA Busy"
    ::=  {rsSmeEngineUtilizationEntry 7}

rsSmeDfaBusyDmaDataStarve OBJECT-TYPE
    SYNTAX	DisplayString (SIZE(0..128))
    ACCESS  read-only
    STATUS  mandatory
    DESCRIPTION
      "DFA Busy DMA data starve"
    ::=  {rsSmeEngineUtilizationEntry 8}

rsSmeDfaBusyNfaDataStall OBJECT-TYPE
    SYNTAX	DisplayString (SIZE(0..128))
    ACCESS  read-only
    STATUS  mandatory
    DESCRIPTION
      "DFA Busy NFA data stall"
    ::=  {rsSmeEngineUtilizationEntry 9}

rsSmeDfaMemStall OBJECT-TYPE
    SYNTAX	DisplayString (SIZE(0..128))
    ACCESS  read-only
    STATUS  mandatory
    DESCRIPTION
      "DFA mem stall"
    ::=  {rsSmeEngineUtilizationEntry 10}

rsSmeNfaBusyReadState OBJECT-TYPE
    SYNTAX	DisplayString (SIZE(0..128))
    ACCESS  read-only
    STATUS  mandatory
    DESCRIPTION
      "NFA Busy read state"
    ::=  {rsSmeEngineUtilizationEntry 11}

rsSmeNfaStateProcessed OBJECT-TYPE
    SYNTAX	DisplayString (SIZE(0..128))
    ACCESS  read-only
    STATUS  mandatory
    DESCRIPTION
      "NFA state processed"
    ::=  {rsSmeEngineUtilizationEntry 12}

rsSmeNfaBytesProcessed OBJECT-TYPE
    SYNTAX	DisplayString (SIZE(0..128))
    ACCESS  read-only
    STATUS  mandatory
    DESCRIPTION
      "NFA bytes processed"
    ::=  {rsSmeEngineUtilizationEntry 13}

rsSmeCntTotalBytes OBJECT-TYPE
    SYNTAX	DisplayString (SIZE(0..128))
    ACCESS  read-only
    STATUS  mandatory
    DESCRIPTION
      "Total bytes"
    ::=  {rsSmeEngineUtilizationEntry 14}

rsSmeNfaMemStall OBJECT-TYPE
    SYNTAX	DisplayString (SIZE(0..128))
    ACCESS  read-only
    STATUS  mandatory
    DESCRIPTION
      "NFA mem stall"
    ::=  {rsSmeEngineUtilizationEntry 15}

rsSmeNfaStatesAverage OBJECT-TYPE
    SYNTAX	INTEGER
    ACCESS  read-only
    STATUS  mandatory
    DESCRIPTION
      "NFA states average"
    ::=  {rsSmeEngineUtilizationEntry 16}

rsSmeNfaMemStallsPerByteProc OBJECT-TYPE
    SYNTAX	INTEGER
    ACCESS  read-only
    STATUS  mandatory
    DESCRIPTION
      "Number of NFA memory stalls per byte processed"
    ::=  {rsSmeEngineUtilizationEntry 17}

rsSmeNfaSatesWhenNfaBusy OBJECT-TYPE
    SYNTAX	INTEGER
    ACCESS  read-only
    STATUS  mandatory
    DESCRIPTION
      "NFA sates when NFA busy"
    ::=  {rsSmeEngineUtilizationEntry 18}

-- Enterprise-specific traps for RADWARE
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsACCFlowTableFull TRAP-TYPE
   ENTERPRISE rsACC
   VARIABLES { rndErrorDesc, rndErrorSeverity }
   DESCRIPTION
      "The flow table is full."
   ::= 1

rsACCFlowEntryExists TRAP-TYPE
   ENTERPRISE rsACC
   VARIABLES { rndErrorDesc, rndErrorSeverity }
   DESCRIPTION
      "The flow entry already exists."
   ::= 2

rsACCFlowEntryNotFound TRAP-TYPE
   ENTERPRISE rsACC
   VARIABLES { rndErrorDesc, rndErrorSeverity }
   DESCRIPTION
      "The flow entry was not found."
   ::= 3

  END
