-- COPYRIGHT NOTICE
-- Copyright (c) Radware Ltd. 2009
-- All rights reserved

ALTEON-CHEETAH-SWITCH-MIB DEFINITIONS ::= BEGIN

IMPORTS
    MODULE-IDENTITY, OBJECT-TYPE, Integer32, Counter32, Gauge32,
    Counter64, IpAddress, TimeTicks
        FROM SNMPv2-SMI
    DisplayString
        FROM RFC1213-MIB
    PhysAddress
        FROM SNMPv2-TC
    aws-switch
        FROM ALTEON-ROOT-MIB
    ipAddrEntry
        FROM RFC1213-MIB
	;
    FeatureStatus ::= INTEGER {
            enable(1),
	    disable(2)
	    }

agent MODULE-IDENTITY
    LAST-UPDATED "200908050000Z" --  5 August, 2009
    ORGANIZATION "Radware Ltd."
    CONTACT-INFO "Lobby 1 (Visitors) and Lobby 2 (Deliveries)
                  575 Corporate Drive
                  Mahwah, NJ 07430
                  support@radware.com"
    DESCRIPTION
        "The MIB module for the Alteon OS Switch."
    REVISION  "200908050000Z" --  5 August, 2009
    DESCRIPTION
        "Added revision clause for SMIv2 compliance."
    ::= { aws-switch 1 }

agentConfig       OBJECT IDENTIFIER ::= { agent 1 }
agentStats        OBJECT IDENTIFIER ::= { agent 2 }
agentInfo         OBJECT IDENTIFIER ::= { agent 3 }
agentOper         OBJECT IDENTIFIER ::= { agent 4 }

agSystem          OBJECT IDENTIFIER ::= { agentConfig 1 }
agPortConfig      OBJECT IDENTIFIER ::= { agentConfig 2 }
agRadiusConfig    OBJECT IDENTIFIER ::= { agentConfig 3 }
agNTP	          OBJECT IDENTIFIER ::= { agentConfig 4 }
agSyslog          OBJECT IDENTIFIER ::= { agentConfig 5 }
agTrapHost        OBJECT IDENTIFIER ::= { agentConfig 6 }
agTftp            OBJECT IDENTIFIER ::= { agentConfig 7 }
agApply           OBJECT IDENTIFIER ::= { agentConfig 8 }
agMgmt            OBJECT IDENTIFIER ::= { agentConfig 9 }
agSslproc         OBJECT IDENTIFIER ::= { agentConfig 10 }
agTacacsConfig    OBJECT IDENTIFIER ::= { agentConfig 11 }
agMgmtNetConfig   OBJECT IDENTIFIER ::= { agentConfig 12 }
agSecurity        OBJECT IDENTIFIER ::= { agentConfig 14 }
agPortAccessCfg   OBJECT IDENTIFIER ::= { agentConfig 16 }
agSave		  OBJECT IDENTIFIER ::= { agentConfig 17 }
agFileTransfer	  OBJECT IDENTIFIER ::= { agentConfig 18 }
agAccess	  OBJECT IDENTIFIER ::= { agentConfig 19 }


agSnmpSetFail          OBJECT IDENTIFIER ::= { agentConfig 22 }

agAlertThreshold       OBJECT IDENTIFIER ::= { agentConfig 23 }

agVLANAccessCfg   OBJECT IDENTIFIER ::= { agentConfig 24 }

agPgroup          OBJECT IDENTIFIER ::= { agSecurity 1 }
ipAclCfg          OBJECT IDENTIFIER ::= { agSecurity 3 }
udpBlastCfg       OBJECT IDENTIFIER ::= { agSecurity 4 }

secGeneralCfg     OBJECT IDENTIFIER ::= { agSecurity 5 }
dosAttackPrevCfg  OBJECT IDENTIFIER ::= { agSecurity 6 }
ipDstAclCfg       OBJECT IDENTIFIER ::= { agSecurity 7 }
bogonCfg          OBJECT IDENTIFIER ::= { agSecurity 9 }
secSignalingCfg   OBJECT IDENTIFIER ::= { agSecurity 10 }
ipRepCfg          OBJECT IDENTIFIER ::= { agSecurity 11 }


pktStats	  OBJECT IDENTIFIER ::= { agentStats 1 }
mpCpuStats	  OBJECT IDENTIFIER ::= { agentStats 2 }
portStats	  OBJECT IDENTIFIER ::= { agentStats 3 }
spStats	          OBJECT IDENTIFIER ::= { agentStats 4 }
mgmtStats	  OBJECT IDENTIFIER ::= { agentStats 5 }
securityStats	  OBJECT IDENTIFIER ::= { agentStats 6 }
agClearStats	  OBJECT IDENTIFIER ::= { agentStats 7 }
mpMemStats        OBJECT IDENTIFIER ::= { agentStats 8 }
ntpStats          OBJECT IDENTIFIER ::= { agentStats 9 }
portMirrorStats   OBJECT IDENTIFIER ::= { agentStats 11 }
capacityUsageStats  OBJECT IDENTIFIER ::= { agentStats 12 }

spGAStats           OBJECT IDENTIFIER ::= { agentStats 13 }
vlanStats           OBJECT IDENTIFIER ::= { agentStats 14 }
systemMemStats        OBJECT IDENTIFIER ::= { agentStats 15 }

vatdStats	          OBJECT IDENTIFIER ::= { agentStats 16 }
countersStats        OBJECT IDENTIFIER ::= { agentStats 17 }

ipRepCountStats	      OBJECT IDENTIFIER ::= { agentStats 18 }

hardware          OBJECT IDENTIFIER ::= { agentInfo 1 }
portInfo          OBJECT IDENTIFIER ::= { agentInfo 2 }
swKeyInfo         OBJECT IDENTIFIER ::= { agentInfo 3 }
agDiff            OBJECT IDENTIFIER ::= { agentInfo 4 }
agCfgDump         OBJECT IDENTIFIER ::= { agentInfo 5 }
mgmtInfo          OBJECT IDENTIFIER ::= { agentInfo 6 }
securityInfo      OBJECT IDENTIFIER ::= { agentInfo 7 }
capacityInfo      OBJECT IDENTIFIER ::= { agentInfo 9 }

agNTPOper         OBJECT IDENTIFIER ::= { agentOper 2 }

agLicenseInfo     OBJECT IDENTIFIER ::= { agentInfo 10 }
agLicenseOper     OBJECT IDENTIFIER ::= { agentOper 3 }
agLicenseConfig   OBJECT IDENTIFIER ::= { agentConfig 21 }

agSysPeerConfig   OBJECT IDENTIFIER ::= { agentConfig 25 }


agSysApmConfig   OBJECT IDENTIFIER ::= { agentConfig 26 }

agSysDiskConfig  OBJECT IDENTIFIER ::= { agentConfig 27 }

-- License Manager
agLMLicenseInfo     OBJECT IDENTIFIER ::= { agentInfo 19 }
agLMLicenseOper     OBJECT IDENTIFIER ::= { agentOper 12 }
agLMLicenseConfig   OBJECT IDENTIFIER ::= { agentConfig 28 }

agSecIpAclOper    OBJECT IDENTIFIER ::= { agentOper 4 }
agUserPasswdOper  OBJECT IDENTIFIER ::= { agentOper 5 }
agSyslogOper      OBJECT IDENTIFIER ::= { agentOper 6 }
agPeerSyncOper    OBJECT IDENTIFIER ::= { agentOper 8 }
agVadcVrrpOper    OBJECT IDENTIFIER ::= { agentOper 9 }

agAppLogOper    OBJECT IDENTIFIER ::= { agentOper 10 }
agAppLogConfigOper OBJECT IDENTIFIER ::= { agentOper 11 }

-- There are two configuration blocks for Alteon switches.
-- The "current_config" reflects the configuration parameters that the
-- switch is operating on and it is read-only.  The objects with "CurCfg"
-- in the name are reflect to this configuration block.
--
-- The "new_config" accepts user configurations on set.  The objects with
-- "NewCfg" in the name are reflect to this configuration block.
--
-- The newly set configurations will not take effect until a "apply"
-- command has been issued (See agApplyConfiguration object defined in
-- ALTEON-PRIVATE-MIBS).
--
-- The newly set configurations will not be saved through next restarting
-- of the switch unless a "save" command has been issued (See
-- agSaveConfiguration object defined in ALTEON-PRIVATE-MIBS).

-- Hardware Information

hwTemperatureStatus OBJECT-TYPE
    SYNTAX  INTEGER {
        notRelevant(0),
        ok(1),
        exceed(2)
        }
    MAX-ACCESS  read-only
    STATUS  current
    DESCRIPTION
	"The status of the temperature sensor."
    ::= { hardware 3 }

hwFanStatus OBJECT-TYPE
    SYNTAX  INTEGER {
        notRelevant(0),
        ok(1),
        fail(2),
        unplug(3)
        }
    MAX-ACCESS  read-only
    STATUS  current
    DESCRIPTION
	"The status of the fan."
    ::= { hardware 4 }


switchCapL2Info          OBJECT IDENTIFIER ::= { capacityInfo  1 }
switchCapL3Info          OBJECT IDENTIFIER ::= { capacityInfo  2 }
switchCapSlbInfo         OBJECT IDENTIFIER ::= { capacityInfo  3 }
switchCapSlbPortInfo     OBJECT IDENTIFIER ::= { capacityInfo  4 }
switchCapBwmInfo         OBJECT IDENTIFIER ::= { capacityInfo  5 }
switchCapSecInfo         OBJECT IDENTIFIER ::= { capacityInfo  6 }
switchCapGeneralInfo     OBJECT IDENTIFIER ::= { capacityInfo  7 }
switchCapPbladeInfo      OBJECT IDENTIFIER ::= { capacityInfo  8 }

switchCapFDBMaxEnt OBJECT-TYPE
    SYNTAX Integer32
    MAX-ACCESS read-only
    STATUS current
    DESCRIPTION
        "Maximum number of entries for FDB in device."
    ::= { switchCapL2Info 1 }

switchCapFDBCurrEnt OBJECT-TYPE
    SYNTAX Integer32
    MAX-ACCESS read-only
    STATUS current
    DESCRIPTION
        "Current number of entries for FDB in device."
    ::= { switchCapL2Info 2 }

switchCapFDBPerSPMaxEnt OBJECT-TYPE
    SYNTAX Integer32
    MAX-ACCESS read-only
    STATUS current
    DESCRIPTION
        "Maximun number of entries for FDB per SP in device."
    ::= { switchCapL2Info 3 }

switchCapVlanMaxEnt OBJECT-TYPE
    SYNTAX Integer32
    MAX-ACCESS read-only
    STATUS current
    DESCRIPTION
        "Maximum number of entries for vlan in device."
    ::= { switchCapL2Info 4 }

switchCapVlanCurrEnt OBJECT-TYPE
    SYNTAX DisplayString
    MAX-ACCESS read-only
    STATUS current
    DESCRIPTION
        "Current number of entries for vlan in device, the value
         is in the form x(y) where 'x' indicates number of current
         entries and 'y' indicates number of enabled entries only."
    ::= { switchCapL2Info 5 }

switchCapStaticTrunkGrpsMaxEnt OBJECT-TYPE
    SYNTAX Integer32
    MAX-ACCESS read-only
    STATUS current
    DESCRIPTION
        "Maximum number of entries for static trunk groups in device."
    ::= { switchCapL2Info 6 }

switchCapStaticTrunkGrpsCurrEnt OBJECT-TYPE
    SYNTAX DisplayString
    MAX-ACCESS read-only
    STATUS current
    DESCRIPTION
        "Current number of entries for static trunk groups
         in device, the value is in the form x(y) where 'x'
         indicates number of current entries and 'y' indicates
         number of enabled entries only."
    ::= { switchCapL2Info 7 }

switchCapLACPTrunkGRs OBJECT-TYPE
    SYNTAX Integer32
    MAX-ACCESS read-only
    STATUS current
    DESCRIPTION
        "LACP Trunk groups in device."
    ::= { switchCapL2Info 8 }

switchCapTrunksperTrunkGR OBJECT-TYPE
    SYNTAX Integer32
    MAX-ACCESS read-only
    STATUS current
    DESCRIPTION
        "Trunks per trunk group in device."
    ::= { switchCapL2Info 9 }

switchCapSTGsMaxEnt OBJECT-TYPE
    SYNTAX Integer32
    MAX-ACCESS read-only
    STATUS  current
    DESCRIPTION
        "Maximum number of entries for STG in device."
    ::= { switchCapL2Info 10 }

switchCapSTGsCurrEnt OBJECT-TYPE
    SYNTAX DisplayString
    MAX-ACCESS read-only
    STATUS current
    DESCRIPTION
        "Current number of entries for STG in device, the
         value is in the form x(y) where 'x' indicates number
         of current entries and 'y' indicates number of
         enabled entries only."
    ::= { switchCapL2Info 11 }

switchCapPortTeamsMaxEnt OBJECT-TYPE
    SYNTAX Integer32
    MAX-ACCESS read-only
    STATUS  current
    DESCRIPTION
        "Maximum number of entries for port teams in device."
    ::= { switchCapL2Info 12 }

switchCapPortTeamsCurrEnt OBJECT-TYPE
    SYNTAX DisplayString
    MAX-ACCESS read-only
    STATUS current
    DESCRIPTION
        "Current number of entries for port teams in device, the
         value is in the form x(y) where 'x' indicates number
         of current entries and 'y' indicates number of
         enabled entries only."
    ::= { switchCapL2Info 13 }

switchCapMonitorPorts OBJECT-TYPE
    SYNTAX Integer32
    MAX-ACCESS read-only
    STATUS current
    DESCRIPTION
        "Maximum number of monitor ports."
    ::= { switchCapL2Info 14 }

switchCapIpIntfMaxEnt OBJECT-TYPE
    SYNTAX Integer32
    MAX-ACCESS read-only
    STATUS current
    DESCRIPTION
        "Maximum number of entries for interfaces in device."
    ::= { switchCapL3Info 1 }

switchCapIpIntfCurrEnt OBJECT-TYPE
    SYNTAX DisplayString
    MAX-ACCESS read-only
    STATUS current
    DESCRIPTION
        "Current number of entries for interfaces in device, the
         value is in the form x(y) where 'x' indicates number
         of current entries and 'y' indicates number of
         enabled entries only."
    ::= { switchCapL3Info 2 }

switchCapIpGWMaxEnt OBJECT-TYPE
    SYNTAX DisplayString
    MAX-ACCESS read-only
    STATUS current
    DESCRIPTION
        "Maximum number of entries for gateways in device, the
         value is in the form x+y where 'x' indicates number
         of default gateways and 'y' indicates number of
         VLAN gateways."
    ::= { switchCapL3Info 3 }

switchCapIpGWCurrEnt OBJECT-TYPE
    SYNTAX DisplayString
    MAX-ACCESS read-only
    STATUS current
    DESCRIPTION
        "Current number of entries for gateways in device, the
         value is in the form x+y(a+b) where 'x' indicates number
         of current default gateways, 'y' indicates number of
         current VLAN gateways, 'a' indicates number
         of  enabled default gateways, 'b' indicates number of
         enabled VLAN gateways only."
    ::= { switchCapL3Info 4 }

switchCapIpRoutesMaxEnt OBJECT-TYPE
    SYNTAX Integer32
    MAX-ACCESS read-only
    STATUS current
    DESCRIPTION
        "Maximum number of entries for routes in device."
    ::= { switchCapL3Info 5 }

switchCapIpRoutesCurrEnt OBJECT-TYPE
    SYNTAX Integer32
    MAX-ACCESS read-only
    STATUS current
    DESCRIPTION
        "Current number of entries for routes in device."
    ::= { switchCapL3Info 6 }

switchCapIpStaticRoutesMaxEnt OBJECT-TYPE
    SYNTAX Integer32
    MAX-ACCESS read-only
    STATUS current
    DESCRIPTION
        "Maximum number of entries for static routes in device."
    ::= { switchCapL3Info 7 }

switchCapIpStaticRoutesCurrEnt OBJECT-TYPE
    SYNTAX Integer32
    MAX-ACCESS read-only
    STATUS current
    DESCRIPTION
        "Current number of entries for static routes in device."
    ::= { switchCapL3Info 8 }

switchCapIpARPMaxEnt OBJECT-TYPE
    SYNTAX Integer32
    MAX-ACCESS read-only
    STATUS current
    DESCRIPTION
        "Maximum number of entries for ARP in device."
    ::= { switchCapL3Info 9 }

switchCapIpARPCurrEnt OBJECT-TYPE
    SYNTAX Integer32
    MAX-ACCESS read-only
    STATUS current
    DESCRIPTION
        "Current number of entries for ARP in device."
    ::= { switchCapL3Info 10 }

switchCapIpStaticARPMaxEnt OBJECT-TYPE
    SYNTAX Integer32
    MAX-ACCESS read-only
    STATUS current
    DESCRIPTION
        "Maximum number of entries for static ARP in device."
    ::= { switchCapL3Info 11 }

switchCapIpStaticARPCurrEnt OBJECT-TYPE
    SYNTAX Integer32
    MAX-ACCESS read-only
    STATUS current
    DESCRIPTION
        "Current number of entries for static ARP in device."
    ::= { switchCapL3Info 12 }

switchCapLocNetsMaxEnt OBJECT-TYPE
    SYNTAX Integer32
    MAX-ACCESS read-only
    STATUS current
    DESCRIPTION
        "Maximum number of entries for local nets in device."
    ::= { switchCapL3Info 13 }

switchCapLocNetsCurrEnt OBJECT-TYPE
    SYNTAX Integer32
    MAX-ACCESS read-only
    STATUS current
    DESCRIPTION
        "Current number of entries for local nets in device."
    ::= { switchCapL3Info 14 }

switchCapDNSSerMaxEnt OBJECT-TYPE
    SYNTAX Integer32
    MAX-ACCESS read-only
    STATUS current
    DESCRIPTION
        "Maximum number of entries for DNS servers in device."
    ::= { switchCapL3Info 15 }

switchCapDNSSerCurrEnt OBJECT-TYPE
    SYNTAX Integer32
    MAX-ACCESS read-only
    STATUS current
    DESCRIPTION
        "Current number of entries for DNS servers in device."
    ::= { switchCapL3Info 16 }

switchCapBootpSerMaxEnt OBJECT-TYPE
    SYNTAX Integer32
    MAX-ACCESS read-only
    STATUS current
    DESCRIPTION
        "Maximum number of entries for BOOTP servers in device."
    ::= { switchCapL3Info 17 }

switchCapBootpSerCurrEnt OBJECT-TYPE
    SYNTAX Integer32
    MAX-ACCESS read-only
    STATUS current
    DESCRIPTION
        "Current number of entries for BOOTP servers in device."
    ::= { switchCapL3Info 18 }

switchCapRIPIntfMaxEnt OBJECT-TYPE
    SYNTAX Integer32
    MAX-ACCESS read-only
    STATUS current
    DESCRIPTION
        "Maximum number of entries of RIP interfaces in device."
    ::= { switchCapL3Info 19 }

switchCapRIPIntfCurrEnt OBJECT-TYPE
    SYNTAX Integer32
    MAX-ACCESS read-only
    STATUS current
    DESCRIPTION
        "Current number of entries of RIP interfaces in device."
    ::= { switchCapL3Info 20 }

switchCapOSPFIntfMaxEnt OBJECT-TYPE
    SYNTAX Integer32
    MAX-ACCESS read-only
    STATUS current
    DESCRIPTION
        "Maximum number of entries for OSPF interfaces in device."
    ::= { switchCapL3Info 21 }

switchCapOSPFIntfCurrEnt OBJECT-TYPE
    SYNTAX DisplayString
    MAX-ACCESS read-only
    STATUS current
    DESCRIPTION
        "Current number of entries for OSPF interfaces in device, the
         value is in the form x(y) where 'x' indicates number
         of current entries and 'y' indicates number of
         enabled entries only."
    ::= { switchCapL3Info 22 }

switchCapOSPFAreasMaxEnt OBJECT-TYPE
    SYNTAX Integer32
    MAX-ACCESS read-only
    STATUS current
    DESCRIPTION
        "Maximum number of entries for OSPF areas in device."
    ::= { switchCapL3Info 23}

switchCapOSPFAreasCurrEnt OBJECT-TYPE
    SYNTAX DisplayString
    MAX-ACCESS read-only
    STATUS  current
    DESCRIPTION
        "Current number of entries for OSPF areas in device, the
         value is in the form x(y) where 'x' indicates number
         of current entries and 'y' indicates number of
         enabled entries only."
    ::= { switchCapL3Info 24 }

switchCapOSPFSummaryRangesMaxEnt OBJECT-TYPE
    SYNTAX Integer32
    MAX-ACCESS read-only
    STATUS current
    DESCRIPTION
        "Maximum number of entries for OSPF summary ranges in device."
    ::= { switchCapL3Info 25 }

switchCapOSPFSummaryRangesCurrEnt OBJECT-TYPE
    SYNTAX DisplayString
    MAX-ACCESS read-only
    STATUS current
    DESCRIPTION
        "Current number of entries for OSPF summary ranges in
         device, the value is in the form x(y) where 'x' indicates
         number of current entries and 'y' indicates number of
         enabled entries only."
    ::= { switchCapL3Info 26 }

switchCapOSPFVirtLinksMaxEnt OBJECT-TYPE
    SYNTAX Integer32
    MAX-ACCESS read-only
    STATUS current
    DESCRIPTION
        "Maximum number of entries for OSPF virtual links in device."
    ::= { switchCapL3Info 27 }

switchCapOSPFVirtLinksCurrEnt OBJECT-TYPE
    SYNTAX DisplayString
    MAX-ACCESS read-only
    STATUS current
    DESCRIPTION
        "Current number of entries for OSPF virtual links in device,
         the value is in the form x(y) where 'x' indicates number
         of current entries and 'y' indicates number of
         enabled entries only."
    ::= { switchCapL3Info 28 }

switchCapOSPFHostsMaxEnt OBJECT-TYPE
    SYNTAX Integer32
    MAX-ACCESS read-only
    STATUS current
    DESCRIPTION
        "Maximum number of entries for OSPF hosts in device."
    ::= { switchCapL3Info 29 }

switchCapOSPFHostsCurrEnt OBJECT-TYPE
    SYNTAX DisplayString
    MAX-ACCESS read-only
    STATUS current
    DESCRIPTION
        "Current number of entries for OSPF hosts in device, the
         value is in the form x(y) where 'x' indicates number
         of current entries and 'y' indicates number of
         enabled entries only."
    ::= { switchCapL3Info 30 }

switchCapLSDBLimit OBJECT-TYPE
    SYNTAX Integer32
    MAX-ACCESS read-only
    STATUS current
    DESCRIPTION
        "LSDB limit in device."
    ::= { switchCapL3Info 31 }

switchCapBGPPeersMaxEnt OBJECT-TYPE
    SYNTAX Integer32
    MAX-ACCESS read-only
    STATUS current
    DESCRIPTION
        "Maximum number of entries for BGP peers in device."
    ::= { switchCapL3Info 32 }

switchCapBGPPeersCurrEnt OBJECT-TYPE
    SYNTAX DisplayString
    MAX-ACCESS read-only
    STATUS current
    DESCRIPTION
        "Current number of entries for BGP peers in device, the
         value is in the form x(y) where 'x' indicates number
         of current entries and 'y' indicates number of
         enabled entries only."
    ::= { switchCapL3Info 33 }

switchCapBGPRouteAggrsMaxEnt OBJECT-TYPE
    SYNTAX Integer32
    MAX-ACCESS read-only
    STATUS current
    DESCRIPTION
        "Maximum number of entries for BGP route aggregators in device."
    ::= { switchCapL3Info 34 }

switchCapBGPRouteAggrsCurrEnt OBJECT-TYPE
    SYNTAX DisplayString
    MAX-ACCESS read-only
    STATUS current
    DESCRIPTION
        "Current number of entries for BGP route aggregators in
         device, the value is in the form x(y) where 'x' indicates
         number of current entries and 'y' indicates number of
         enabled entries only."
    ::= { switchCapL3Info 35 }

switchCapRouteMapsMaxEnt OBJECT-TYPE
    SYNTAX Integer32
    MAX-ACCESS read-only
    STATUS current
    DESCRIPTION
        "Maximum number of entries for route maps in device."
    ::= { switchCapL3Info 36 }

switchCapRouteMapsCurrEnt OBJECT-TYPE
    SYNTAX DisplayString
    MAX-ACCESS read-only
    STATUS current
    DESCRIPTION
        "Current number of entries for route maps in device, the
         value is in the form x(y) where 'x' indicates number
         of current entries and 'y' indicates number of
         enabled entries only."
    ::= { switchCapL3Info 37 }

switchCapNwkFltsMaxEnt OBJECT-TYPE
    SYNTAX Integer32
    MAX-ACCESS read-only
    STATUS current
    DESCRIPTION
        "Maximum number of entries for network filters in device."
    ::= { switchCapL3Info 38 }

switchCapNwkFltsCurrEnt OBJECT-TYPE
    SYNTAX DisplayString
    MAX-ACCESS read-only
    STATUS current
    DESCRIPTION
        "Current number of entries for network filters in device, the
         value is in the form x(y) where 'x' indicates number
         of current entries and 'y' indicates number of
         enabled entries only."
    ::= { switchCapL3Info 39 }

switchCapASFlts OBJECT-TYPE
    SYNTAX Integer32
    MAX-ACCESS read-only
    STATUS current
    DESCRIPTION
        "Maximum number of entries for AS filters in device."
    ::= { switchCapL3Info 40 }

switchCapVRRPRtrsMaxEnt OBJECT-TYPE
    SYNTAX Integer32
    MAX-ACCESS read-only
    STATUS current
    DESCRIPTION
        "Maximum number of entries for VRRP routers in device."
    ::= { switchCapL3Info 41 }

switchCapVRRPRtrsCurrEnt OBJECT-TYPE
    SYNTAX DisplayString
    MAX-ACCESS read-only
    STATUS current
    DESCRIPTION
        "Current number of entries for VRRP routers in device, the
         value is in the form x(y) where 'x' indicates number
         of current entries and 'y' indicates number of
         enabled entries only."
    ::= { switchCapL3Info 42 }

switchCapVRRPRtrGRsMaxEnt OBJECT-TYPE
    SYNTAX Integer32
    MAX-ACCESS read-only
    STATUS current
    DESCRIPTION
        "Maximum number of entries for VRRP router groups in device."
    ::= { switchCapL3Info 43 }

switchCapVRRPRtrGRsCurrEnt OBJECT-TYPE
    SYNTAX DisplayString
    MAX-ACCESS read-only
    STATUS current
    DESCRIPTION
        "Current number of entries for VRRP router groups in device,the
         value is in the form x(y) where 'x' indicates number
         of current entries and 'y' indicates number of
         enabled entries only."
    ::= { switchCapL3Info 44 }

switchCapVRRPIntfsMaxEnt OBJECT-TYPE
    SYNTAX Integer32
    MAX-ACCESS read-only
    STATUS current
    DESCRIPTION
        "Maximum number of entries for VRRP interfaces in device."
    ::= { switchCapL3Info 45 }

switchCapVRRPIntfsCurrEnt OBJECT-TYPE
    SYNTAX Integer32
    MAX-ACCESS read-only
    STATUS current
    DESCRIPTION
        "Current number of entries for VRRP interfaces in device."
    ::= { switchCapL3Info 46 }

switchCapOSPFv3IntfMaxEnt OBJECT-TYPE
    SYNTAX Integer32
    MAX-ACCESS read-only
    STATUS current
    DESCRIPTION
        "Maximum number of entries for OSPFV3 interfaces in device."
    ::= { switchCapL3Info 47 }

switchCapOSPFv3IntfCurrEnt OBJECT-TYPE
    SYNTAX DisplayString
    MAX-ACCESS read-only
    STATUS current
    DESCRIPTION
        "Current number of entries for OSPFV3 interfaces in device, the
         value is in the form x(y) where 'x' indicates number
         of current entries and 'y' indicates number of
         enabled entries only."
    ::= { switchCapL3Info 48 }

switchCapOSPFv3AreasMaxEnt OBJECT-TYPE
    SYNTAX Integer32
    MAX-ACCESS read-only
    STATUS current
    DESCRIPTION
        "Maximum number of entries for OSPFV3 areas in device."
    ::= { switchCapL3Info 49}

switchCapOSPFv3AreasCurrEnt OBJECT-TYPE
    SYNTAX DisplayString
    MAX-ACCESS read-only
    STATUS  current
    DESCRIPTION
        "Current number of entries for OSPFV3 areas in device, the
         value is in the form x(y) where 'x' indicates number
         of current entries and 'y' indicates number of
         enabled entries only."
    ::= { switchCapL3Info 50 }

switchCapOSPFv3SummaryRangesMaxEnt OBJECT-TYPE
    SYNTAX Integer32
    MAX-ACCESS read-only
    STATUS current
    DESCRIPTION
        "Maximum number of entries for OSPFV3 summary ranges in device."
    ::= { switchCapL3Info 51 }

switchCapOSPFv3SummaryRangesCurrEnt OBJECT-TYPE
    SYNTAX DisplayString
    MAX-ACCESS read-only
    STATUS current
    DESCRIPTION
        "Current number of entries for OSPFV3 summary ranges in
         device, the value is in the form x(y) where 'x' indicates
         number of current entries and 'y' indicates number of
         enabled entries only."
    ::= { switchCapL3Info 52 }

switchCapOSPFv3VirtLinksMaxEnt OBJECT-TYPE
    SYNTAX Integer32
    MAX-ACCESS read-only
    STATUS current
    DESCRIPTION
        "Maximum number of entries for OSPFV3 virtual links in device."
    ::= { switchCapL3Info 53 }

switchCapOSPFv3VirtLinksCurrEnt OBJECT-TYPE
    SYNTAX DisplayString
    MAX-ACCESS read-only
    STATUS current
    DESCRIPTION
        "Current number of entries for OSPFV3 virtual links in device,
         the value is in the form x(y) where 'x' indicates number
         of current entries and 'y' indicates number of
         enabled entries only."
    ::= { switchCapL3Info 54 }

switchCapOSPFv3HostsMaxEnt OBJECT-TYPE
    SYNTAX Integer32
    MAX-ACCESS read-only
    STATUS current
    DESCRIPTION
        "Maximum number of entries for OSPFV3 hosts in device."
    ::= { switchCapL3Info 55 }

switchCapOSPFv3HostsCurrEnt OBJECT-TYPE
    SYNTAX DisplayString
    MAX-ACCESS read-only
    STATUS current
    DESCRIPTION
        "Current number of entries for OSPFV3 hosts in device, the
         value is in the form x(y) where 'x' indicates number
         of current entries and 'y' indicates number of
         enabled entries only."
    ::= { switchCapL3Info 56 }

switchCapASFltsCurr OBJECT-TYPE
    SYNTAX DisplayString
    MAX-ACCESS read-only
    STATUS current
    DESCRIPTION
        "Current number of entries for AS filters in device created and enable."
    ::= { switchCapL3Info 57 }


switchCapRealSersMaxEnt OBJECT-TYPE
    SYNTAX Integer32
    MAX-ACCESS read-only
    STATUS current
    DESCRIPTION
        "Maximum number of entries for real servers in device."
    ::= { switchCapSlbInfo 1 }

switchCapRealSersCurrEnt OBJECT-TYPE
    SYNTAX DisplayString
    MAX-ACCESS read-only
    STATUS current
    DESCRIPTION
        "Current number of entries for real servers in device, the
         value is in the form x(y) where 'x' indicates number
         of current entries and 'y' indicates number of
         enabled entries only."
    ::= { switchCapSlbInfo 2 }

switchCapSerGRsMaxEnt OBJECT-TYPE
    SYNTAX Integer32
    MAX-ACCESS read-only
    STATUS current
    DESCRIPTION
        "Maximum number of entries for real server groups in device."
    ::= { switchCapSlbInfo 3 }

switchCapSerGRsCurrEnt OBJECT-TYPE
    SYNTAX Integer32
    MAX-ACCESS read-only
    STATUS current
    DESCRIPTION
        "Current number of entries for real server groups in device."
    ::= { switchCapSlbInfo 4 }

switchCapVirtSersMaxEnt OBJECT-TYPE
    SYNTAX Integer32
    MAX-ACCESS read-only
    STATUS current
    DESCRIPTION
        "Maximum number of entries for virtual servers in device."
    ::= { switchCapSlbInfo 5 }

switchCapVirtSersCurrEnt OBJECT-TYPE
    SYNTAX DisplayString
    MAX-ACCESS read-only
    STATUS current
    DESCRIPTION
        "Current number of entries for virtual servers in device, the
         value is in the form x(y) where 'x' indicates number
         of current entries and 'y' indicates number of
         enabled entries only."
    ::= { switchCapSlbInfo 6 }

switchCapVirtServicesEnt OBJECT-TYPE
    SYNTAX Integer32
    MAX-ACCESS read-only
    STATUS current
    DESCRIPTION
        "Maximum number of entries for virtual services in device."
    ::= { switchCapSlbInfo 7 }

switchCapRealServicesEnt OBJECT-TYPE
    SYNTAX Integer32
    MAX-ACCESS read-only
    STATUS current
    DESCRIPTION
        "Current number of entries for real services in device."
    ::= { switchCapSlbInfo 8 }

switchCapRealIDSSer OBJECT-TYPE
    SYNTAX Integer32
    MAX-ACCESS read-only
    STATUS current
    DESCRIPTION
        "Maximum number of entries for real IDS servers."
    ::= { switchCapSlbInfo 9 }

switchCapIDSSerGRs OBJECT-TYPE
    SYNTAX Integer32
    MAX-ACCESS read-only
    STATUS current
    DESCRIPTION
        "Maximum number of entries for IDS server groups."
    ::= { switchCapSlbInfo 10 }

switchCapGSLBDomainsMaxEnt OBJECT-TYPE
    SYNTAX Integer32
    MAX-ACCESS read-only
    STATUS current
    DESCRIPTION
        "Maximum number of entries for global SLB domains in device."
    ::= { switchCapSlbInfo 11 }

switchCapGSLBDomainsCurrEnt OBJECT-TYPE
    SYNTAX DisplayString
    MAX-ACCESS read-only
    STATUS current
    DESCRIPTION
        "Current number of entries for global SLB domains in
         device, the value is in the form x(y) where 'x' indicates
         number of current entries and 'y' indicates number of
         enabled entries only."
    ::= { switchCapSlbInfo 12 }

switchCapGSLBServicesMaxEnt OBJECT-TYPE
    SYNTAX Integer32
    MAX-ACCESS read-only
    STATUS current
    DESCRIPTION
        "Maximum number of entries for global SLB services in device."
    ::= { switchCapSlbInfo 13 }

switchCapGSLBServicesCurrEnt OBJECT-TYPE
    SYNTAX DisplayString
    MAX-ACCESS read-only
    STATUS current
    DESCRIPTION
        "Current number of entries for global SLB services in device, the
         value is in the form x(y) where 'x' indicates number
         of current entries and 'y' indicates number of
         enabled entries only."
    ::= { switchCapSlbInfo 14 }

switchCapGSLBLocSersMaxEnt OBJECT-TYPE
    SYNTAX Integer32
    MAX-ACCESS read-only
    STATUS current
    DESCRIPTION
        "Maximum number of entries for global SLB local servers in device."
    ::= { switchCapSlbInfo 15 }

switchCapGSLBLocSersCurrEnt OBJECT-TYPE
    SYNTAX DisplayString
    MAX-ACCESS read-only
    STATUS current
    DESCRIPTION
        "Current number of entries for global SLB local servers
         in device, the value is in the form x(y) where 'x' indicates
         number of current entries and 'y' indicates number of
         enabled entries only."
    ::= { switchCapSlbInfo 16 }

switchCapGSLBRemSersMaxEnt OBJECT-TYPE
    SYNTAX Integer32
    MAX-ACCESS read-only
    STATUS current
    DESCRIPTION
        "Maximum number of entries for global SLB remote servers in device."
    ::= { switchCapSlbInfo 17 }

switchCapGSLBRemSersCurrEnt OBJECT-TYPE
    SYNTAX DisplayString
    MAX-ACCESS read-only
    STATUS current
    DESCRIPTION
        "Current number of entries for global SLB remote servers
         in device, the value is in the form x(y) where 'x' indicates
         number of current entries and 'y' indicates number of
         enabled entries only."
    ::= { switchCapSlbInfo 18 }

switchCapGSLBRemSitesMaxEnt OBJECT-TYPE
    SYNTAX Integer32
    MAX-ACCESS read-only
    STATUS current
    DESCRIPTION
        "Maximum number of entries for global SLB sites in device."
    ::= { switchCapSlbInfo 19 }

switchCapGSLBRemSitesCurrEnt OBJECT-TYPE
    SYNTAX DisplayString
    MAX-ACCESS read-only
    STATUS current
    DESCRIPTION
        "Current number of entries for global SLB sites in device, the
         value is in the form x(y) where 'x' indicates number of current
         entries and 'y' indicates number of enabled entries only."
    ::= { switchCapSlbInfo 20 }

switchCapGSLBFailoversPerRemSiteMaxEnt OBJECT-TYPE
    SYNTAX Integer32
    MAX-ACCESS read-only
    STATUS current
    DESCRIPTION
        "Maximum number of entries for global SLB failovers
         per site in device."
    ::= { switchCapSlbInfo 21 }

switchCapGSLBFailoversPerRemSiteCurrEnt OBJECT-TYPE
    SYNTAX DisplayString
    MAX-ACCESS read-only
    STATUS current
    DESCRIPTION
        "Current number of entries for global SLB failovers per site in
         device, the value is in the form x(y) where 'x' indicates number
         of current entries and 'y' indicates number of
         enabled entries only."
    ::= { switchCapSlbInfo 22 }

switchCapGSLBNetworksMaxEnt OBJECT-TYPE
    SYNTAX Integer32
    MAX-ACCESS read-only
    STATUS current
    DESCRIPTION
        "Maximum number of entries for global SLB networks in device."
    ::= { switchCapSlbInfo 23 }

switchCapGSLBNetworksCurrEnt OBJECT-TYPE
    SYNTAX DisplayString
    MAX-ACCESS read-only
    STATUS current
    DESCRIPTION
        "Current number of entries for global SLB networks in device, the
         value is in the form x(y) where 'x' indicates number of current
         entries and 'y' indicates number of enabled entries only."
    ::= { switchCapSlbInfo 24 }

switchCapGSLBGeographicalRegionsMaxEnt OBJECT-TYPE
    SYNTAX Integer32
    MAX-ACCESS read-only
    STATUS current
    DESCRIPTION
        "Maximum number of entries for global geographical regions in device."
    ::= { switchCapSlbInfo 25 }

switchCapGSLBGeographicalRegionsCurrEnt OBJECT-TYPE
    SYNTAX DisplayString
    MAX-ACCESS read-only
    STATUS current
    DESCRIPTION
        "Current number of entries for global geographical regions in device,
         the value is in the form x(y) where 'x' indicates number of current
         entries and 'y' indicates number of enabled entries only."
    ::= { switchCapSlbInfo 26 }

switchCapGSLBRulesMaxEnt OBJECT-TYPE
    SYNTAX Integer32
    MAX-ACCESS read-only
    STATUS current
    DESCRIPTION
        "Maximum number of entries for global SLB rules in device."
    ::= { switchCapSlbInfo 27 }

switchCapGSLBRulesCurrEnt OBJECT-TYPE
    SYNTAX DisplayString
    MAX-ACCESS read-only
    STATUS current
    DESCRIPTION
        "Current number of entries for global SLB rules in device, the
         value is in the form x(y) where 'x' indicates number of current
         entries and 'y' indicates number of enabled entries only."
    ::= { switchCapSlbInfo 28 }

switchCapGSLBMetricsPerRuleMaxEnt OBJECT-TYPE
    SYNTAX Integer32
    MAX-ACCESS read-only
    STATUS current
    DESCRIPTION
        "Maximum number of entries for global SLB metrics per rule in device."
    ::= { switchCapSlbInfo 29 }

switchCapGSLBMetricPerRuleCurrEnt OBJECT-TYPE
    SYNTAX DisplayString
    MAX-ACCESS read-only
    STATUS current
    DESCRIPTION
        "Current number of entries for global SLB metrics per rule in device,
         the value is in the form x(y) where 'x' indicates number of current
         entries and 'y' indicates number of enabled entries only."
    ::= { switchCapSlbInfo 30 }

switchCapGSLBDNSPersCacheMaxEnt OBJECT-TYPE
    SYNTAX Integer32
    MAX-ACCESS read-only
    STATUS current
    DESCRIPTION
        "Maximum number of entries for global SLB DNS persistence cache in device."
    ::= { switchCapSlbInfo 31 }

switchCapGSLBDNSPersCacheCurrEnt  OBJECT-TYPE
    SYNTAX DisplayString
    MAX-ACCESS read-only
    STATUS current
    DESCRIPTION
        "Current number of entries for global SLB DNS persistence cache in device,
         the value is in the form x(y) where 'x' indicates number of current
         entries and 'y' indicates number of enabled entries only."
    ::= { switchCapSlbInfo 32 }

switchCapFltsMaxEnt OBJECT-TYPE
    SYNTAX Integer32
    MAX-ACCESS read-only
    STATUS current
    DESCRIPTION
        "Maximum number of entries for filters in device."
    ::= { switchCapSlbInfo 33 }

switchCapFltsCurrEnt OBJECT-TYPE
    SYNTAX DisplayString
    MAX-ACCESS read-only
    STATUS current
    DESCRIPTION
        "Current number of entries for filters in device, the
         value is in the form x(y) where 'x' indicates number of current
         entries and 'y' indicates number of enabled entries only."
    ::= { switchCapSlbInfo 34 }

switchCapPIPsMaxEnt OBJECT-TYPE
    SYNTAX Integer32
    MAX-ACCESS read-only
    STATUS current
    DESCRIPTION
        "Maximum number of entries for PIPs in device."
    ::= { switchCapSlbInfo 35 }

switchCapPIPsCurrEnt OBJECT-TYPE
    SYNTAX Integer32
    MAX-ACCESS read-only
    STATUS current
    DESCRIPTION
        "Current number of entries for pips in device."
    ::= { switchCapSlbInfo 36 }

switchCapScriptHealthChecksMaxEnt OBJECT-TYPE
    SYNTAX Integer32
    MAX-ACCESS read-only
    STATUS current
    DESCRIPTION
        "Maximum number of entries for scriptable health checks in device."
    ::= { switchCapSlbInfo 37 }

switchCapScriptHealthChecksCurrEnt OBJECT-TYPE
    SYNTAX Integer32
    MAX-ACCESS read-only
    STATUS current
    DESCRIPTION
        "Current number of entries for scriptable health checks in device."
    ::= { switchCapSlbInfo 38 }

switchCapSNMPHealthChecksMaxEnt OBJECT-TYPE
    SYNTAX Integer32
    MAX-ACCESS read-only
    STATUS current
    DESCRIPTION
        "Maximum number of entries for SNMP health checks in device."
    ::= { switchCapSlbInfo 39 }

switchCapSNMPHealthChecksCurrEnt OBJECT-TYPE
    SYNTAX Integer32
    MAX-ACCESS  read-only
    STATUS current
    DESCRIPTION
        "Current number of entries for snmp health checks in device."
    ::= { switchCapSlbInfo 40 }

switchCapRulesforURLParsingMaxEnt OBJECT-TYPE
    SYNTAX Integer32
    MAX-ACCESS read-only
    STATUS current
    DESCRIPTION
        "Maximum number of entries for rules for URL parsing in device."
    ::= { switchCapSlbInfo 41 }

switchCapRulesforURLParsingCurrEnt OBJECT-TYPE
    SYNTAX Integer32
    MAX-ACCESS read-only
    STATUS current
    DESCRIPTION
        "Current number of entries for rules for URL parsing in device."
    ::= { switchCapSlbInfo 42 }

switchCapSLBSessionsMaxEnt OBJECT-TYPE
    SYNTAX Integer32
    MAX-ACCESS read-only
    STATUS current
    DESCRIPTION
        "Maximum number of entries for SLB sessions in device."
    ::= { switchCapSlbInfo 43 }

switchCapSLBSessionsCurrEnt OBJECT-TYPE
    SYNTAX Integer32
    MAX-ACCESS read-only
    STATUS current
    DESCRIPTION
        "Current number of entries for SLB sessions in device."
    ::= { switchCapSlbInfo 44 }

switchCapNumofRportstoVport OBJECT-TYPE
    SYNTAX Integer32
    MAX-ACCESS read-only
    STATUS current
    DESCRIPTION
        "Maximum number of rports to vport."
    ::= { switchCapSlbInfo 45 }

switchCapDomianRecordsMaxEnt OBJECT-TYPE
    SYNTAX Integer32
    MAX-ACCESS read-only
    STATUS current
    DESCRIPTION
        "Maximum number of entries for domain records in device."
    ::= { switchCapSlbInfo 46 }

switchCapDomainRecordsCurrEnt OBJECT-TYPE
    SYNTAX DisplayString
    MAX-ACCESS read-only
    STATUS current
    DESCRIPTION
        "Current number of entries for domain records in device, the
         value is in the form x(y) where 'x' indicates number of current
         entries and 'y' indicates number of enabled entries only."
    ::= { switchCapSlbInfo 47 }

switchCapMappingPerDomainrecord OBJECT-TYPE
    SYNTAX Integer32
    MAX-ACCESS read-only
    STATUS current
    DESCRIPTION
        "Maximum number of entries for mapping per domain record in device."
    ::= { switchCapSlbInfo 48 }

switchCapNetworkClassesMaxEnt OBJECT-TYPE
    SYNTAX Integer32
    MAX-ACCESS read-only
    STATUS current
    DESCRIPTION
        "Maximum number of entries for network classes in device."
    ::= { switchCapSlbInfo 49 }

switchCapNetworkClassesCurrEnt OBJECT-TYPE
    SYNTAX Integer32
    MAX-ACCESS read-only
    STATUS current
    DESCRIPTION
        "Current number of entries for network classes in device."
    ::= { switchCapSlbInfo 50 }

switchCapNetworkElementsMaxEnt OBJECT-TYPE
    SYNTAX Integer32
    MAX-ACCESS read-only
    STATUS current
    DESCRIPTION
        "Maximum number of entries for network elements in device."
    ::= { switchCapSlbInfo 51 }

switchCapNetworkElementsCurrEnt OBJECT-TYPE
    SYNTAX Integer32
    MAX-ACCESS read-only
    STATUS current
    DESCRIPTION
        "Current number of entries for network elements in device."
    ::= { switchCapSlbInfo 52 }

switchCapAppShapeMaxEnt OBJECT-TYPE
    SYNTAX Integer32
    MAX-ACCESS read-only
    STATUS current
    DESCRIPTION
        "Maximum number of AppShape++ scripts in device."
    ::= { switchCapSlbInfo 53 }

switchCapAppShapeCurrEnt OBJECT-TYPE
    SYNTAX DisplayString
    MAX-ACCESS read-only
    STATUS current
    DESCRIPTION
        "Current number of AppShape++ scripts in device."
    ::= { switchCapSlbInfo 54 }

switchCapDataClassClassesMaxEnt OBJECT-TYPE
    SYNTAX Integer32
    MAX-ACCESS read-only
    STATUS current
    DESCRIPTION
        "Maximum number of Data Classes in device."
    ::= { switchCapSlbInfo 55 }

switchCapDataClassClassesCurEnt OBJECT-TYPE
    SYNTAX Integer32
    MAX-ACCESS read-only
    STATUS current
    DESCRIPTION
        "Current number of Data Classes in device."
    ::= { switchCapSlbInfo 56 }


switchCapDataClassManualEntriesPerClassMaxEnt OBJECT-TYPE
    SYNTAX Integer32
    MAX-ACCESS read-only
    STATUS current
    DESCRIPTION
        "Maximum number of Data Classes manual entries per class."
    ::= { switchCapSlbInfo 59 }

switchCapDataClassManualEntriesMaxEnt OBJECT-TYPE
    SYNTAX Integer32
    MAX-ACCESS read-only
    STATUS current
    DESCRIPTION
        "Maximum number of Data Classes manual entries in device."
    ::= { switchCapSlbInfo 60 }

switchCapDataClassManualEntriesCurEnt OBJECT-TYPE
    SYNTAX Integer32
    MAX-ACCESS read-only
    STATUS current
    DESCRIPTION
        "Current number of Data Classes manual entries in device."
    ::= { switchCapSlbInfo 61 }

switchCapDataClassMemMaxSize OBJECT-TYPE
    SYNTAX Integer32
    MAX-ACCESS read-only
    STATUS current
    DESCRIPTION
        "Maximum size of memory used by Data Classes in bytes."
    ::= { switchCapSlbInfo 62 }

switchCapDataClassMemCurSize OBJECT-TYPE
    SYNTAX Integer32
    MAX-ACCESS read-only
    STATUS current
    DESCRIPTION
         "Current size of memory used by Data Classes in bytes."
    ::= { switchCapSlbInfo 63 }


switchCapDynamicDataStoreMaxSize OBJECT-TYPE
    SYNTAX Integer32
    MAX-ACCESS read-only
    STATUS current
    DESCRIPTION
        "Maximum size of Dyanmic Data Store in 512B blocks."
    ::= { switchCapSlbInfo 64 }

switchCapDynamicDataStoreCurSize OBJECT-TYPE
    SYNTAX Integer32
    MAX-ACCESS read-only
    STATUS current
    DESCRIPTION
        "Current size of Dyanmic Data Store in 512B blocks."
    ::= { switchCapSlbInfo 65 }

switchCapCachePolMaxEnt OBJECT-TYPE
    SYNTAX Integer32
    MAX-ACCESS read-only
    STATUS current
    DESCRIPTION
        "Maximum number of cache policies that can be configured."
    ::= { switchCapSlbInfo 66 }

switchCapCachePolCurrEnt OBJECT-TYPE
    SYNTAX DisplayString
    MAX-ACCESS read-only
    STATUS current
    DESCRIPTION
        "Current number of cache policies which are enable."
    ::= { switchCapSlbInfo 67 }

switchCapCacheRuleMaxEnt OBJECT-TYPE
    SYNTAX Integer32
    MAX-ACCESS read-only
    STATUS current
    DESCRIPTION
        "Maximum number of cache rules that can be configured."
    ::= { switchCapSlbInfo 68 }

switchCapCacheRuleCurrEnt OBJECT-TYPE
    SYNTAX DisplayString
    MAX-ACCESS read-only
    STATUS current
    DESCRIPTION
        "Current number of cache rules which are enable."
    ::= { switchCapSlbInfo 69 }

switchCapCacheRuleListMaxEnt OBJECT-TYPE
    SYNTAX Integer32
    MAX-ACCESS read-only
    STATUS current
    DESCRIPTION
        "Maximum number of cache rule lists that can be configured."
    ::= { switchCapSlbInfo 70 }

switchCapCacheRuleListCurrEnt OBJECT-TYPE
    SYNTAX DisplayString
    MAX-ACCESS read-only
    STATUS current
    DESCRIPTION
        "Current number of cache rule lists which are enable."
    ::= { switchCapSlbInfo 71 }

switchCapKeysMaxEnt OBJECT-TYPE
    SYNTAX Integer32
    MAX-ACCESS read-only
    STATUS current
    DESCRIPTION
        "Maximum number of Keys that can be configured."
    ::= { switchCapSlbInfo 72 }

switchCapKeysCurrEnt OBJECT-TYPE
    SYNTAX Integer32
    MAX-ACCESS read-only
    STATUS current
    DESCRIPTION
        "Current number of Keys that which are enable."
    ::= { switchCapSlbInfo 73 }

switchCapCertSignReqMaxEnt OBJECT-TYPE
    SYNTAX Integer32
    MAX-ACCESS read-only
    STATUS current
    DESCRIPTION
        "Maximum number of Certifiate signing requests that can be configured."
    ::= { switchCapSlbInfo 74 }

switchCapCertSignReqCurrEnt OBJECT-TYPE
    SYNTAX Integer32
    MAX-ACCESS read-only
    STATUS current
    DESCRIPTION
        "Current number of Certifiate signing requests which are enable."
    ::= { switchCapSlbInfo 75 }

switchCapServerCertMaxEnt OBJECT-TYPE
    SYNTAX Integer32
    MAX-ACCESS read-only
    STATUS current
    DESCRIPTION
        "Maximum number of server certificates that can be configured."
    ::= { switchCapSlbInfo 76 }

switchCapServerCertCurrEnt OBJECT-TYPE
    SYNTAX Integer32
    MAX-ACCESS read-only
    STATUS current
    DESCRIPTION
        "Current number of server certificates which are enable."
    ::= { switchCapSlbInfo 77 }

switchCapTrusCACertMaxEnt OBJECT-TYPE
    SYNTAX Integer32
    MAX-ACCESS read-only
    STATUS current
    DESCRIPTION
        "Maximum number of Trusted CA certificates that can be configured."
    ::= { switchCapSlbInfo 78 }

switchCapTrusCACertCurrEnt OBJECT-TYPE
    SYNTAX Integer32
    MAX-ACCESS read-only
    STATUS current
    DESCRIPTION
        "Current number of trusted CA certificates which are enable."
    ::= { switchCapSlbInfo 79 }

switchCapInterCACertMaxEnt OBJECT-TYPE
    SYNTAX Integer32
    MAX-ACCESS read-only
    STATUS current
    DESCRIPTION
        "Maximum number of intermediate CA certificates that can be configured."
    ::= { switchCapSlbInfo 80 }

switchCapInterCACertCurrEnt OBJECT-TYPE
    SYNTAX Integer32
    MAX-ACCESS read-only
    STATUS current
    DESCRIPTION
        "Current number of intermediate CA certificates which are enable."
    ::= { switchCapSlbInfo 81 }

switchCapCertGroupMaxEnt OBJECT-TYPE
    SYNTAX Integer32
    MAX-ACCESS read-only
    STATUS current
    DESCRIPTION
        "Maximum number of certificate Groups that can be configured."
    ::= { switchCapSlbInfo 82 }

switchCapCertGroupCurrEnt OBJECT-TYPE
    SYNTAX Integer32
    MAX-ACCESS read-only
    STATUS current
    DESCRIPTION
        "Current number of Certificate Groups which are enable."
    ::= { switchCapSlbInfo 83 }

switchCapSecurityPolicyMaxEnt OBJECT-TYPE
    SYNTAX Integer32
    MAX-ACCESS read-only
    STATUS current
    DESCRIPTION
        "Maximum number of security policies that can be configured."
    ::= { switchCapSlbInfo 84 }

switchCapSecurityPolicyCurrEnt OBJECT-TYPE
    SYNTAX DisplayString
    MAX-ACCESS read-only
    STATUS current
    DESCRIPTION
        "Current number of enabled security policies."
    ::= { switchCapSlbInfo 85 }

switchCapSmartNatMaxEnt OBJECT-TYPE
    SYNTAX Integer32
    MAX-ACCESS read-only
    STATUS current
    DESCRIPTION
        "Maximum number of Smart NAT entries that can be configured."
    ::= { switchCapSlbInfo 86 }

switchCapSmartNatCurrEnt OBJECT-TYPE
    SYNTAX Integer32
    MAX-ACCESS read-only
    STATUS current
    DESCRIPTION
        "Current number of enabled Smart NAT entries ."
    ::= { switchCapSlbInfo 87 }

switchCapSlbPortInfoTable OBJECT-TYPE
    SYNTAX  SEQUENCE OF SwitchCapSlbPortInfoTableEntry
    MAX-ACCESS  not-accessible
    STATUS  current
    DESCRIPTION
        "The table of slb port information."
    ::= { switchCapSlbPortInfo 1 }

switchCapSlbPortInfoTableEntry OBJECT-TYPE
    SYNTAX SwitchCapSlbPortInfoTableEntry
    MAX-ACCESS not-accessible
    STATUS current
    DESCRIPTION
        "A row in the slb port information table."
    INDEX  { switchCapSlbPortInfoIndx}
    ::= { switchCapSlbPortInfoTable 1 }

SwitchCapSlbPortInfoTableEntry ::= SEQUENCE {
    switchCapSlbPortInfoIndx         Integer32,
    switchCapSlbPortClientState      INTEGER,
    switchCapSlbPortSerState         INTEGER,
    switchCapSlbPortFltState         DisplayString,
    switchCapSlbPortRTSState         INTEGER
    }

switchCapSlbPortInfoIndx OBJECT-TYPE
    SYNTAX Integer32
    MAX-ACCESS read-only
    STATUS current
    DESCRIPTION
        "Index of switch port."
    ::= { switchCapSlbPortInfoTableEntry 1 }

switchCapSlbPortClientState OBJECT-TYPE
    SYNTAX INTEGER {
        enabled(1),
        disabled(2)
        }
    MAX-ACCESS read-only
    STATUS current
    DESCRIPTION
        "Client state on the switch port."
    ::= { switchCapSlbPortInfoTableEntry 2 }

switchCapSlbPortSerState OBJECT-TYPE
    SYNTAX INTEGER {
        enabled(1),
        disabled(2)
        }
    MAX-ACCESS read-only
    STATUS current
    DESCRIPTION
        "Server state on the switch port."
    ::= { switchCapSlbPortInfoTableEntry 3 }

switchCapSlbPortFltState OBJECT-TYPE
    SYNTAX DisplayString
    MAX-ACCESS read-only
    STATUS current
    DESCRIPTION
        "It is in the form E(x) where filter is enabled on the port and
         x is the number of filters configured for port. Otherwise disable."
    ::= { switchCapSlbPortInfoTableEntry 4 }

switchCapSlbPortRTSState OBJECT-TYPE
    SYNTAX INTEGER {
        enabled(1),
        disabled(2)
        }
    MAX-ACCESS read-only
    STATUS current
    DESCRIPTION
        "RTS processing state on the switch port."
    ::= { switchCapSlbPortInfoTableEntry 5 }

bwmPoliciesMaxEnt OBJECT-TYPE
    SYNTAX Integer32
    MAX-ACCESS read-only
    STATUS current
    DESCRIPTION
        "Maximum number of entries for bwm policies in device ."
    ::= { switchCapBwmInfo 1 }

bwmPoliciesCurrEnt OBJECT-TYPE
    SYNTAX Integer32
    MAX-ACCESS  read-only
    STATUS current
    DESCRIPTION
        "Current number of entries for bwm policies in device."
    ::= { switchCapBwmInfo 2 }

bwmContsMaxEnt OBJECT-TYPE
    SYNTAX Integer32
    MAX-ACCESS read-only
    STATUS current
    DESCRIPTION
        "Maximum number of entries for bwm contracts  in device."
    ::= { switchCapBwmInfo 3 }

bwmContsCurrEnt OBJECT-TYPE
    SYNTAX DisplayString
    MAX-ACCESS  read-only
    STATUS current
    DESCRIPTION
        "Current number of entries for bwm contracts  in device, the
         value is in the form x(y) where 'x' indicates number of current
         entries and 'y' indicates number of enabled entries only."
    ::= { switchCapBwmInfo 4 }

bwmGRsMaxEnt OBJECT-TYPE
    SYNTAX Integer32
    MAX-ACCESS read-only
    STATUS current
    DESCRIPTION
        "Maximum number of entries for bwm groups  in device."
    ::= { switchCapBwmInfo 5 }

bwmGRsCurrEnt OBJECT-TYPE
    SYNTAX Integer32
    MAX-ACCESS read-only
    STATUS current
    DESCRIPTION
        "Current number of entries for bwm groups  in device."
    ::= { switchCapBwmInfo 6 }

bwmContsPerGRs OBJECT-TYPE
    SYNTAX Integer32
    MAX-ACCESS read-only
    STATUS current
    DESCRIPTION
        "Maximum number of entries for bwm contracts per group in device."
    ::= { switchCapBwmInfo  7 }

bwmTimePoliciesPerCont OBJECT-TYPE
    SYNTAX Integer32
    MAX-ACCESS read-only
    STATUS current
    DESCRIPTION
        "Current number of entries for  bwm time policies per contract."
    ::= { switchCapBwmInfo  8 }

configSrcIPACLsMaxEnt OBJECT-TYPE
    SYNTAX Integer32
    MAX-ACCESS read-only
    STATUS current
    DESCRIPTION
        "Maximum number of entries for configuration source IP ACLs."
    ::= { switchCapSecInfo 1 }

configSrcIPACLsCurrEnt OBJECT-TYPE
    SYNTAX Integer32
    MAX-ACCESS read-only
    STATUS current
    DESCRIPTION
        "Current number of entries for configuration source IP ACLs."
    ::= { switchCapSecInfo 2 }

bogonSrcIPACLsMaxEnt OBJECT-TYPE
    SYNTAX Integer32
    MAX-ACCESS read-only
    STATUS current
    DESCRIPTION
        "Maximum number of entries for bogon source IP ACLs."
    ::= { switchCapSecInfo 3 }

bogonSrcIPACLsCurrEnt OBJECT-TYPE
    SYNTAX Integer32
    MAX-ACCESS read-only
    STATUS current
    DESCRIPTION
        "Current number of entries for bogon source IP ACLs."
    ::= { switchCapSecInfo 4 }

operSrcIPACLsMaxEnt OBJECT-TYPE
    SYNTAX Integer32
    MAX-ACCESS read-only
    STATUS current
    DESCRIPTION
        "Maximum number of entries for operation source IP ACLs."
    ::= { switchCapSecInfo 5 }

operSrcIPACLsCurrEnt OBJECT-TYPE
    SYNTAX Integer32
    MAX-ACCESS read-only
    STATUS current
    DESCRIPTION
        "Current number of entries for operaion source IP ACLs."
    ::= { switchCapSecInfo 6 }

totalSrcIPACLsMaxEnt OBJECT-TYPE
    SYNTAX Integer32
    MAX-ACCESS read-only
    STATUS current
    DESCRIPTION
        "Maximum number of entries for total source IP ACLs."
    ::= { switchCapSecInfo 7 }

totalSrcIPACLsCurrEnt OBJECT-TYPE
    SYNTAX Integer32
    MAX-ACCESS read-only
    STATUS current
    DESCRIPTION
        "Current number of entries for total source IP ACLs."
    ::= { switchCapSecInfo 8 }

configDstIPACLsMaxEnt OBJECT-TYPE
    SYNTAX Integer32
    MAX-ACCESS read-only
    STATUS current
    DESCRIPTION
        "Maximum number of entries for configuration destination  IP ACLs."
    ::= { switchCapSecInfo 9 }

configDstIPACLsCurrEnt OBJECT-TYPE
    SYNTAX Integer32
    MAX-ACCESS read-only
    STATUS current
    DESCRIPTION
        "Current number of entries for configuration destination IP ACLs."
    ::= { switchCapSecInfo 10 }

operDstIPACLsMaxEnt OBJECT-TYPE
    SYNTAX Integer32
    MAX-ACCESS read-only
    STATUS current
    DESCRIPTION
        "Maximum number of entries for operation destination IP ACLs."
    ::= { switchCapSecInfo 11 }

operDstIPACLsCurrEnt OBJECT-TYPE
    SYNTAX Integer32
    MAX-ACCESS read-only
    STATUS current
    DESCRIPTION
        "Current number of entries for operaion destination IP ACLs."
    ::= { switchCapSecInfo 12 }

totalDstIPACLsMaxEnt OBJECT-TYPE
    SYNTAX Integer32
    MAX-ACCESS read-only
    STATUS current
    DESCRIPTION
        "Maximum number of entries for total destination IP ACLs."
    ::= { switchCapSecInfo 13 }

totalDstIPACLsCurrEnt OBJECT-TYPE
    SYNTAX Integer32
    MAX-ACCESS read-only
    STATUS current
    DESCRIPTION
        "Current number of entries for total destination IP ACLs."
    ::= { switchCapSecInfo 14 }
ipDosAtkPrevention OBJECT-TYPE
    SYNTAX Integer32
    MAX-ACCESS read-only
    STATUS current
    DESCRIPTION
        "Maximum number of entries for IP DOS attack prevention."
    ::= { switchCapSecInfo 15 }

tcpDosAtkPrevention OBJECT-TYPE
    SYNTAX Integer32
    MAX-ACCESS read-only
    STATUS current
    DESCRIPTION
        "Maximum number of entries for TCP DOS attack prevention."
    ::= { switchCapSecInfo 16 }

udpDosAtkPrevention OBJECT-TYPE
    SYNTAX Integer32
    MAX-ACCESS read-only
    STATUS current
    DESCRIPTION
        "Maximum number of entries for UDP DOS attack prevention."
    ::= { switchCapSecInfo 17 }

icmpDosAtkPrevention OBJECT-TYPE
    SYNTAX Integer32
    MAX-ACCESS read-only
    STATUS current
    DESCRIPTION
        "Maximum number of entries for ICMP DOS attack prevention."
    ::= { switchCapSecInfo 18 }

igmpDosAtkPrevention OBJECT-TYPE
    SYNTAX Integer32
    MAX-ACCESS read-only
    STATUS current
    DESCRIPTION
        "Maximum number of entries for IGMP DOS attack prevention."
    ::= { switchCapSecInfo 19 }

arpDosAtkPrevention OBJECT-TYPE
    SYNTAX Integer32
    MAX-ACCESS read-only
    STATUS current
    DESCRIPTION
        "Maximum number of entries for ARP DOS attack prevention."
    ::= { switchCapSecInfo 20 }

ipv6DosAtkPrevention OBJECT-TYPE
    SYNTAX Integer32
    MAX-ACCESS read-only
    STATUS current
    DESCRIPTION
        "Maximum number of entries for ipv6 DOS attack prevention."
    ::= { switchCapSecInfo 21 }

totalDosAtkPrevention OBJECT-TYPE
    SYNTAX Integer32
    MAX-ACCESS read-only
    STATUS current
    DESCRIPTION
        "Total number of entries for DOS attack preventions."
    ::= { switchCapSecInfo 22 }
udpBlastProtection OBJECT-TYPE
    SYNTAX Integer32
    MAX-ACCESS read-only
    STATUS current
    DESCRIPTION
        "Specifies UDP ports for UDP blast protection."
    ::= { switchCapSecInfo 23 }

syslogHostMaxEnt OBJECT-TYPE
    SYNTAX Integer32
    MAX-ACCESS read-only
    STATUS current
    DESCRIPTION
        "Maximum number of entries for syslog hosts  in device."
    ::= { switchCapGeneralInfo 1 }

syslogHostCurrEnt OBJECT-TYPE
    SYNTAX Integer32
    MAX-ACCESS read-only
    STATUS current
    DESCRIPTION
        "Current number of entries for syslog hosts in device."
    ::= { switchCapGeneralInfo 2 }

radiusSerMaxEnt OBJECT-TYPE
    SYNTAX Integer32
    MAX-ACCESS read-only
    STATUS current
    DESCRIPTION
        "Maximum number of entries for radius servers in device ."
    ::= { switchCapGeneralInfo 3 }

radiusSerCurrEnt OBJECT-TYPE
    SYNTAX Integer32
    MAX-ACCESS read-only
    STATUS current
    DESCRIPTION
        "Current number of entries for radius servers in device."
    ::= { switchCapGeneralInfo 4 }

tacacsSerMaxEnt OBJECT-TYPE
    SYNTAX Integer32
    MAX-ACCESS read-only
    STATUS current
    DESCRIPTION
        "Maximum number of entries for tacacs+ server in device."
    ::= { switchCapGeneralInfo 5 }

tacacsSerCurrEnt OBJECT-TYPE
    SYNTAX Integer32
    MAX-ACCESS read-only
    STATUS current
    DESCRIPTION
        "Current number of entries for tacacs+ server in device."
    ::= { switchCapGeneralInfo 6 }

ntpSerMaxEnt OBJECT-TYPE
    SYNTAX Integer32
    MAX-ACCESS read-only
    STATUS current
    DESCRIPTION
        "Maximum number of entries for ntp servers in device ."
    ::= { switchCapGeneralInfo 7 }

ntpSerCurrEnt OBJECT-TYPE
    SYNTAX Integer32
    MAX-ACCESS read-only
    STATUS current
    DESCRIPTION
        "Current number of entries for ntp servers in device."
    ::= { switchCapGeneralInfo 8 }

smtpHostsMaxEnt OBJECT-TYPE
    SYNTAX Integer32
    MAX-ACCESS read-only
    STATUS current
    DESCRIPTION
        "Maximum number of entries for smtp hosts in device."
    ::= { switchCapGeneralInfo 9 }

smtpHostsCurrEnt OBJECT-TYPE
    SYNTAX Integer32
    MAX-ACCESS read-only
    STATUS current
    DESCRIPTION
        "Current number of entries for smtp hosts in device."
    ::= { switchCapGeneralInfo 10 }

mgmtNetworksMaxEnt OBJECT-TYPE
    SYNTAX Integer32
    MAX-ACCESS read-only
    STATUS current
    DESCRIPTION
        "Maximum number of entries for management networks in device ."
    ::= { switchCapGeneralInfo 11 }

mgmtNetworksCurrEnt OBJECT-TYPE
    SYNTAX Integer32
    MAX-ACCESS read-only
    STATUS current
    DESCRIPTION
        "Current number of entries for management networks in device."
    ::= { switchCapGeneralInfo 12 }

endUsers OBJECT-TYPE
    SYNTAX Integer32
    MAX-ACCESS read-only
    STATUS current
    DESCRIPTION
        "Maximum number of entries for end users in device."
    ::= { switchCapGeneralInfo 13 }

panicDumps OBJECT-TYPE
    SYNTAX Integer32
    MAX-ACCESS read-only
    STATUS current
    DESCRIPTION
        "Maximum panic dumps in device."
    ::= { switchCapGeneralInfo 14 }


snmpv3UsersMaxEnt OBJECT-TYPE
    SYNTAX Integer32
    MAX-ACCESS read-only
    STATUS current
    DESCRIPTION
        "Maximum number of entries for snmpv3 users in device."
    ::= { switchCapGeneralInfo 17 }

snmpv3UsersCurrEnt OBJECT-TYPE
    SYNTAX Integer32
    MAX-ACCESS read-only
    STATUS current
    DESCRIPTION
        "Current number of entries for snmpv3 users in device."
    ::= { switchCapGeneralInfo 18 }

snmpv3ViewsMaxEnt OBJECT-TYPE
    SYNTAX Integer32
    MAX-ACCESS read-only
    STATUS current
    DESCRIPTION
        "Maximum number of entries for snmpv3 views in device."
    ::= { switchCapGeneralInfo 19 }

snmpv3ViewsCurrEnt OBJECT-TYPE
    SYNTAX Integer32
    MAX-ACCESS read-only
    STATUS current
    DESCRIPTION
        "Current number of entries for snmpv3 views in device."
    ::= { switchCapGeneralInfo 20 }

snmpv3AccessGRsMaxEnt OBJECT-TYPE
    SYNTAX Integer32
    MAX-ACCESS read-only
    STATUS current
    DESCRIPTION
        "Maximum number of entries for snmpv3 access groups in device."
    ::= { switchCapGeneralInfo 21 }

snmpv3AccessGRsCurrEnt OBJECT-TYPE
    SYNTAX Integer32
    MAX-ACCESS read-only
    STATUS current
    DESCRIPTION
        "Current number of entries for snmpv3 access groups in device."
    ::= { switchCapGeneralInfo 22 }

snmpv3TargetAddrMaxEnt OBJECT-TYPE
    SYNTAX Integer32
    MAX-ACCESS read-only
    STATUS current
    DESCRIPTION
        "Maximum number of entries for snmpv3 target addresses in device."
    ::= { switchCapGeneralInfo 23 }

snmpv3TargetAddrCurrEnt OBJECT-TYPE
    SYNTAX Integer32
    MAX-ACCESS read-only
    STATUS current
    DESCRIPTION
        "Current number of entries for snmpv3 target addresses in device."
    ::= { switchCapGeneralInfo 24 }

snmpv3TargetParamsMaxEnt OBJECT-TYPE
    SYNTAX Integer32
    MAX-ACCESS read-only
    STATUS current
    DESCRIPTION
        "Maximum number of entries for snmpv3 target parameters in device."
    ::= { switchCapGeneralInfo 25 }

snmpv3TargetParamsCurrEnt OBJECT-TYPE
    SYNTAX Integer32
    MAX-ACCESS read-only
    STATUS current
    DESCRIPTION
        "Current number of entries for snmpv3 target parameters in device."
    ::= { switchCapGeneralInfo 26 }



ramSize OBJECT-TYPE
    SYNTAX Integer32
    MAX-ACCESS read-only
    STATUS current
    DESCRIPTION
        "RAM Size (GB)."
    ::= { switchCapGeneralInfo 27 }

hardDiskMax OBJECT-TYPE
    SYNTAX Integer32
    MAX-ACCESS read-only
    STATUS current
    DESCRIPTION
        "Hard Disk Maximum Capicity (GB)."
    ::= { switchCapGeneralInfo 28 }

hardDiskCur OBJECT-TYPE
    SYNTAX Integer32
    MAX-ACCESS read-only
    STATUS current
    DESCRIPTION
        "Hard Disk In Use (GB)."
    ::= { switchCapGeneralInfo 29 }

cacheUsageMaxEnt OBJECT-TYPE
    SYNTAX Integer32
    MAX-ACCESS read-only
    STATUS current
    DESCRIPTION
        "Total Cache available in MB."
    ::= { switchCapGeneralInfo 30 }

cacheUsageCurrEnt OBJECT-TYPE
    SYNTAX Integer32
    MAX-ACCESS read-only
    STATUS current
    DESCRIPTION
        "Current Cache Usage in MB."
    ::= { switchCapGeneralInfo 31 }

ramSizeCurr OBJECT-TYPE
    SYNTAX Integer32
    MAX-ACCESS read-only
    STATUS current
    DESCRIPTION
        "Current Used RAM Size (GB)."
    ::= { switchCapGeneralInfo 32 }


capacityUnitsMax OBJECT-TYPE
    SYNTAX Integer32
    MAX-ACCESS read-only
    STATUS current
    DESCRIPTION
        "Maximum capacitry units assigned to all vadc's."
    ::= { switchCapGeneralInfo 33 }

capacityUnitsCurr OBJECT-TYPE
    SYNTAX Integer32
    MAX-ACCESS read-only
    STATUS current
    DESCRIPTION
        "capacitry units used by vAdc's."
    ::= { switchCapGeneralInfo 34 }

vAdcMax OBJECT-TYPE
    SYNTAX Integer32
    MAX-ACCESS read-only
    STATUS current
    DESCRIPTION
        "Maximum number of vAdc's licence enabled for vadc's configuration."
    ::= { switchCapGeneralInfo 35 }

vAdcCurr OBJECT-TYPE
    SYNTAX Integer32
    MAX-ACCESS read-only
    STATUS current
    DESCRIPTION
        "Number of vAdc's Configured."
    ::= { switchCapGeneralInfo 36 }

-- Pblade Capacity info table
switchCapPbladeInfoTable OBJECT-TYPE
    SYNTAX  SEQUENCE OF SwitchCapPbladeInfoTableEntry
    MAX-ACCESS  not-accessible
    STATUS  current
    DESCRIPTION
        "Pblade Capacity information table"
    ::= { switchCapPbladeInfo 1 }

switchCapPbladeInfoTableEntry OBJECT-TYPE
    SYNTAX  SwitchCapPbladeInfoTableEntry
    MAX-ACCESS  not-accessible
    STATUS  current
    DESCRIPTION
        "A row in the Pblade Capacity information table"
    INDEX  { switchCapPbladeInfoPbladeId }
    ::= { switchCapPbladeInfoTable 1 }

SwitchCapPbladeInfoTableEntry ::= SEQUENCE {
    switchCapPbladeInfoPbladeId         INTEGER,
    switchCapPbladeInfoRamMax           INTEGER,
    switchCapPbladeInfoRamCur           INTEGER
    }

switchCapPbladeInfoPbladeId OBJECT-TYPE
    SYNTAX  INTEGER (3..6)
    MAX-ACCESS  read-only
    STATUS  current
    DESCRIPTION
        "Pblade slot number"
    ::= { switchCapPbladeInfoTableEntry 1 }

switchCapPbladeInfoRamMax OBJECT-TYPE
    SYNTAX  INTEGER
    MAX-ACCESS  read-only
    STATUS  current
    DESCRIPTION
        "Pblade total RAM size (GB)"
    ::= { switchCapPbladeInfoTableEntry 2 }

switchCapPbladeInfoRamCur OBJECT-TYPE
    SYNTAX  INTEGER
    MAX-ACCESS  read-only
    STATUS  current
    DESCRIPTION
        "Pblade used RAM size (GB)"
    ::= { switchCapPbladeInfoTableEntry 3 }

agLicenseInfoTable OBJECT-TYPE
    SYNTAX  SEQUENCE OF AgLicenseInfoTableEntry
    MAX-ACCESS  not-accessible
    STATUS  current
    DESCRIPTION
        "The table of license Information."
    ::= { agLicenseInfo 1 }

agLicenseInfoTableEntry OBJECT-TYPE
    SYNTAX  AgLicenseInfoTableEntry
    MAX-ACCESS not-accessible
    STATUS  current
    DESCRIPTION
        "A row in the license Information table."
    INDEX  { licenseInfoIdx }
    ::= { agLicenseInfoTable 1 }

AgLicenseInfoTableEntry ::=
    SEQUENCE {
        licenseInfoIdx                        Integer32,
        softwareKey                           DisplayString,
        licenseType                           INTEGER,
        remainingDays                         INTEGER,
        remainingDaysLeft                     DisplayString,
        licenseSize                           Integer32,
        licenseAllocated                      Integer32,
        timeBasedLicenseStatus                DisplayString
    }

licenseInfoIdx OBJECT-TYPE
    SYNTAX Integer32
    MAX-ACCESS  read-only
    STATUS  current
    DESCRIPTION
        " The license index."
    ::= { agLicenseInfoTableEntry 1 }

softwareKey OBJECT-TYPE
    SYNTAX DisplayString(SIZE(0..31))
    MAX-ACCESS  read-only
    STATUS  current
    DESCRIPTION
        "The Sofware Key."
    ::= { agLicenseInfoTableEntry 2 }

licenseType OBJECT-TYPE
    SYNTAX INTEGER {
        permanent(1),
        temporary(2),
        removed(3),
        expired(4),
        subscription(5)
        }
    MAX-ACCESS  read-only
    STATUS  current
    DESCRIPTION
        "The License Type information."
    ::= { agLicenseInfoTableEntry 3 }

remainingDays OBJECT-TYPE
    SYNTAX INTEGER
    MAX-ACCESS  read-only
    STATUS  current
    DESCRIPTION
        "The number of days left for temporary license."
    ::= { agLicenseInfoTableEntry 4 }

remainingDaysLeft OBJECT-TYPE
SYNTAX DisplayString(SIZE(0..255))
    MAX-ACCESS  read-only
    STATUS  current
    DESCRIPTION
    "The number of days/hours left for temporary license."
    ::= { agLicenseInfoTableEntry 5 }

licenseSize OBJECT-TYPE
    SYNTAX Integer32
    MAX-ACCESS  read-only
    STATUS  current
    DESCRIPTION
        "The available size of license. Value -1 defines unlimited license."
    ::= { agLicenseInfoTableEntry 6 }

licenseAllocated OBJECT-TYPE
    SYNTAX Integer32
    MAX-ACCESS  read-only
    STATUS  current
    DESCRIPTION
        "The totally allocated license to vADC's. Value -1 defines unlimited license"
    ::= { agLicenseInfoTableEntry 7 }

timeBasedLicenseStatus OBJECT-TYPE
    SYNTAX DisplayString(SIZE(0..255))
    MAX-ACCESS  read-only
    STATUS  current
    DESCRIPTION
        "The time based license status"
    ::= { agLicenseInfoTableEntry 8 }

agLicenseInfoConvStatus OBJECT-TYPE
    SYNTAX  INTEGER {
	licConvDone(0),
        licCookieConvPending(1)
        }
    MAX-ACCESS  read-only
    STATUS  current
    DESCRIPTION
        "This object, when read, gives the information to the user
         whether auto conversion is needed or not."
    ::= { agLicenseInfo 2 }

agLicenseCapacityInfoTable OBJECT-TYPE
    SYNTAX  SEQUENCE OF AgLicenseCapacityInfoTableEntry
    MAX-ACCESS  not-accessible
    STATUS  current
    DESCRIPTION
        "The table of license Capacity Information."
    ::= { agLicenseInfo 3 }

agLicenseCapacityInfoTableEntry OBJECT-TYPE
    SYNTAX  AgLicenseCapacityInfoTableEntry
    MAX-ACCESS not-accessible
    STATUS  current
    DESCRIPTION
        "A row in the license Capacity Information table."
    INDEX  { licenseCapacityInfoIdx }
    ::= { agLicenseCapacityInfoTable 1 }

AgLicenseCapacityInfoTableEntry ::=
    SEQUENCE {
        licenseCapacityInfoIdx                Integer32,
        licenseCapacitySize                   Integer32,
        licenseCapacityAllocated              Integer32,
        licenseCapacityPeakUsage              DisplayString,
        licenseCapacityCurrUsage              DisplayString,
        licenseCapacityPeakTimeStamp          Integer32
    }

licenseCapacityInfoIdx OBJECT-TYPE
    SYNTAX Integer32
    MAX-ACCESS  read-only
    STATUS  current
    DESCRIPTION
        " The capacity license table index."
    ::= { agLicenseCapacityInfoTableEntry 1 }


licenseCapacitySize OBJECT-TYPE
    SYNTAX Integer32
    MAX-ACCESS  read-only
    STATUS  current
    DESCRIPTION
        "The available size of license. Value -1 defines unlimited license"
    ::= { agLicenseCapacityInfoTableEntry 2 }

licenseCapacityAllocated OBJECT-TYPE
    SYNTAX Integer32
    MAX-ACCESS  read-only
    STATUS  current
    DESCRIPTION
        "The totally allocated license to vADC's. Value -1 defines unlimited license"
    ::= { agLicenseCapacityInfoTableEntry 3 }

licenseCapacityPeakUsage OBJECT-TYPE
    SYNTAX DisplayString(SIZE(0..31))
    MAX-ACCESS  read-only
    STATUS  current
    DESCRIPTION
        "Capacity License Peak Usage"
    ::= { agLicenseCapacityInfoTableEntry 4 }

licenseCapacityCurrUsage OBJECT-TYPE
    SYNTAX DisplayString(SIZE(0..31))
    MAX-ACCESS  read-only
    STATUS  current
    DESCRIPTION
        "Capacity License Current Usage"
    ::= { agLicenseCapacityInfoTableEntry 5 }

licenseCapacityPeakTimeStamp OBJECT-TYPE
    SYNTAX Integer32
    MAX-ACCESS  read-only
    STATUS  current
    DESCRIPTION
        "Capacity License Peak Usage Collecting Time Stamp (in seconds since the Epoch)"
    ::= { agLicenseCapacityInfoTableEntry 6 }

licenseKey OBJECT-TYPE
    SYNTAX DisplayString(SIZE(0..108))
    MAX-ACCESS  read-write
    STATUS  current
    DESCRIPTION
     "Current License key."
    ::= {agLicenseOper 1}

licenseDelete OBJECT-TYPE
    SYNTAX INTEGER {
        deleteGlobal(1),
        deleteBwm(2),
        deleteSecurity(4),
        deleteLlb(5),
        deleteItm(6),
        deleteCookie(7),
        deleteSymantec(8),
        deleteSlb(9),
        other(10),
        deleteServices(11),
        deletevADC(12),
        deleteNg(13),
        deleteNgPlus(14),
        deleteLp(15)
        }
    MAX-ACCESS  read-create
    STATUS  current
    DESCRIPTION
     "This is an action object to delete specific feature license
     other(10) is returned always when read."
    ::= {agLicenseOper 2}

automaticConvType OBJECT-TYPE
    SYNTAX INTEGER {
        other(1),
        automatic(2)
        }
    MAX-ACCESS  read-write
    STATUS  current
    DESCRIPTION
     "License- Conversion type Automatic."
    ::= {agLicenseOper 3}

automaticConvStatus OBJECT-TYPE
    SYNTAX DisplayString(SIZE(0..64))
    MAX-ACCESS  read-only
    STATUS  current
    DESCRIPTION
    "Automatic License Conversion status."
    ::= {agLicenseOper 4}


throPutLicenseKey OBJECT-TYPE
    SYNTAX DisplayString(SIZE(0..108))
    MAX-ACCESS  read-only
    STATUS  current
    DESCRIPTION
    "Throughput License key."
    ::= {agLicenseOper 5 }

sslLicenseKey OBJECT-TYPE
    SYNTAX DisplayString(SIZE(0..108))
    MAX-ACCESS  read-only
    STATUS  current
    DESCRIPTION
    "SSL License key."
    ::= {agLicenseOper 6 }

compressionLicenseKey OBJECT-TYPE
    SYNTAX DisplayString(SIZE(0..108))
    MAX-ACCESS  read-only
    STATUS  current
    DESCRIPTION
    "Compression License key."
    ::= {agLicenseOper 7 }

vaLicenseKey OBJECT-TYPE
    SYNTAX DisplayString(SIZE(0..108))
    MAX-ACCESS  read-only
    STATUS  current
    DESCRIPTION
    "VA License key."
    ::= {agLicenseOper 8 }

vADCLicenseKey OBJECT-TYPE
    SYNTAX DisplayString(SIZE(1..108))
    MAX-ACCESS  read-only
    STATUS  current
    DESCRIPTION
    "vADC License key."
    ::= {agLicenseOper 9 }

fastviewLicenseKey OBJECT-TYPE
    SYNTAX DisplayString(SIZE(0..108))
    MAX-ACCESS  read-only
    STATUS  current
    DESCRIPTION
    "fastview License key."
    ::= {agLicenseOper 10 }

apmLicenseKey OBJECT-TYPE
    SYNTAX DisplayString(SIZE(0..108))
    MAX-ACCESS  read-only
    STATUS  current
    DESCRIPTION
    "apm License key."
    ::= {agLicenseOper 11 }
wafLicenseKey OBJECT-TYPE
    SYNTAX DisplayString(SIZE(0..108))
    MAX-ACCESS  read-only
    STATUS  current
    DESCRIPTION
    "waf License key."
    ::= {agLicenseOper 12 }

authLicenseKey OBJECT-TYPE
    SYNTAX DisplayString(SIZE(0..108))
    MAX-ACCESS  read-only
    STATUS  current
    DESCRIPTION
    "authentication License key."
    ::= {agLicenseOper 13 }


ipBasedLicenseV4 OBJECT-TYPE
    SYNTAX DisplayString(SIZE(0..108))
    MAX-ACCESS  read-only
    STATUS  current
    DESCRIPTION
    "IP address from type V4. This is the IP on which the licenses can be based on."
    ::= {agLicenseOper 14 }

ipBasedLicenseV6 OBJECT-TYPE
    SYNTAX DisplayString(SIZE(0..108))
    MAX-ACCESS  read-only
    STATUS  current
    DESCRIPTION
    "IP address from type V6. This is the IP on which the licenses can be based on."
    ::= {agLicenseOper 15}



fastviewLicenseKeyNext OBJECT-TYPE
    SYNTAX DisplayString(SIZE(0..108))
    MAX-ACCESS  read-only
    STATUS  current
    DESCRIPTION
    "fastview next License key."
    ::= {agLicenseOper 16 }

apmLicenseKeyNext OBJECT-TYPE
    SYNTAX DisplayString(SIZE(0..108))
    MAX-ACCESS  read-only
    STATUS  current
    DESCRIPTION
    "apm next License key."
    ::= {agLicenseOper 17 }


wafLicenseKeyNext OBJECT-TYPE
    SYNTAX DisplayString(SIZE(0..108))
    MAX-ACCESS  read-only
    STATUS  current
    DESCRIPTION
    "waf next License key."
    ::= {agLicenseOper 18 }

additionalLicenseKey OBJECT-TYPE
    SYNTAX DisplayString(SIZE(0..108))
    MAX-ACCESS  read-only
    STATUS  current
    DESCRIPTION
     "Additional License key."
    ::= {agLicenseOper 19}

iprepLicenseKey OBJECT-TYPE
    SYNTAX DisplayString(SIZE(0..108))
    MAX-ACCESS  read-only
    STATUS  current
    DESCRIPTION
    "IP Reputation License key."
    ::= {agLicenseOper 20 }

iprepLicenseKeyNext OBJECT-TYPE
    SYNTAX DisplayString(SIZE(0..108))
    MAX-ACCESS  read-only
    STATUS  current
    DESCRIPTION
    "IP Reputation next License key."
    ::= {agLicenseOper 21 }

urlfilterLicenseKey OBJECT-TYPE
    SYNTAX DisplayString(SIZE(0..108))
    MAX-ACCESS  read-only
    STATUS  current
    DESCRIPTION
    "URL Filtering License key."
    ::= {agLicenseOper 22 }

urlfilterLicenseKeyNext OBJECT-TYPE
    SYNTAX DisplayString(SIZE(0..108))
    MAX-ACCESS  read-only
    STATUS  current
    DESCRIPTION
    "URL Filtering next License key."
    ::= {agLicenseOper 23 }


licenseKeyRLM OBJECT-TYPE
    SYNTAX DisplayString(SIZE(0..108))
    MAX-ACCESS  read-write
    STATUS  current
    DESCRIPTION
     "Current License key set via RLM."
    ::= {agLicenseOper 24}

licenseDeleteKeyRLM OBJECT-TYPE
    SYNTAX DisplayString(SIZE(0..108))
    MAX-ACCESS  read-write
    STATUS  current
    DESCRIPTION
     "Current License key removed via RLM."
    ::= {agLicenseOper 25}

agUserNewPasswdOper OBJECT-TYPE
    SYNTAX  DisplayString (SIZE(0..128))
    MAX-ACCESS  read-only
    STATUS  current
    DESCRIPTION
      "Enter New User Password."
    ::= { agUserPasswdOper 1 }

--IP ACL Oper
agSecIpAclOperAdd        OBJECT IDENTIFIER ::= { agSecIpAclOper 1 }
agSecIpAclOperRem        OBJECT IDENTIFIER ::= { agSecIpAclOper 2 }
agSecIpAclOperRemAll     OBJECT-TYPE
    SYNTAX  INTEGER {
        ok(1),
        remove(2)
        }
    MAX-ACCESS  read-write
    STATUS  current
    DESCRIPTION
      "This is an action object to Remove all operations
       source IP Address/Mask. When set to a value of remove(2) it
       removes All source IPACL entries.
       ok(1) is returned when the object is read."
    ::= { agSecIpAclOper 3 }
agSecIpAclOperDestAdd    OBJECT IDENTIFIER ::= { agSecIpAclOper 4 }
agSecIpAclOperDestRem    OBJECT IDENTIFIER ::= { agSecIpAclOper 5 }
agSecIpAclOperDestRemAll OBJECT-TYPE
    SYNTAX  INTEGER {
        ok(1),
        remove(2)
        }
    MAX-ACCESS  read-write
    STATUS  current
    DESCRIPTION
      "This is an action object to Remove all destination IP Address/Mask.
       When set to a value of remove(2) it removes All destination
       IPACL entries. ok(1) is returned when the object is read."
    ::= { agSecIpAclOper 6 }
agSecIpAclOperList       OBJECT IDENTIFIER ::= { agSecIpAclOper 7 }

agSecIpAclOperAddSrcIp OBJECT-TYPE
    SYNTAX  IpAddress
    MAX-ACCESS  read-write
    STATUS  current
    DESCRIPTION
     "Add IP ACL source IP Address"
    ::= { agSecIpAclOperAdd 1 }

agSecIpAclOperAddMask OBJECT-TYPE
    SYNTAX  IpAddress
    MAX-ACCESS  read-write
    STATUS  current
    DESCRIPTION
      "Add IP ACL source Netmask."
    ::= { agSecIpAclOperAdd 2 }

agSecIpAclOperAddTimeOut OBJECT-TYPE
    SYNTAX  INTEGER (1..10080)
    MAX-ACCESS  read-write
    STATUS  current
    DESCRIPTION
      "timeout in minutes"
    ::= { agSecIpAclOperAdd 3 }

agSecIpAclOperAddIp OBJECT-TYPE
    SYNTAX  INTEGER {
        ok(1),
        add(2)
        }
    MAX-ACCESS  read-write
    STATUS  current
    DESCRIPTION
        "This is an action object ,when set to a value of add(2),
         it  Add operations source IP Address/Mask.Ok(1) is returned
         when object is read."
    ::= { agSecIpAclOperAdd 4 }

agSecIpAclOperRemIp OBJECT-TYPE
    SYNTAX  IpAddress
    MAX-ACCESS  read-write
    STATUS  current
    DESCRIPTION
     "Enter source IP Address for Remove operations"
    ::= { agSecIpAclOperRem 1 }

agSecIpAclOperRemMask OBJECT-TYPE
    SYNTAX  IpAddress
    MAX-ACCESS  read-write
    STATUS  current
    DESCRIPTION
      "Enter source Netmask for Remove operations."
    ::= { agSecIpAclOperRem 2 }

agSecIpAclOperRemove OBJECT-TYPE
    SYNTAX  INTEGER {
        ok(1),
        remove(2)
        }
    MAX-ACCESS  read-write
    STATUS  current
    DESCRIPTION
        "This is an action object ,when set to a value of remove(2),
         it  Remove operations source IP Address/Mask.
         Ok(1) is returned when object is read."
    ::= { agSecIpAclOperRem 3 }

agSecIpAclOperDestAddIpAddr OBJECT-TYPE
    SYNTAX  IpAddress
    MAX-ACCESS  read-write
    STATUS  current
    DESCRIPTION
     "Add IP ACL Operations destination IP Address"
    ::= { agSecIpAclOperDestAdd 1 }

agSecIpAclOperDestAddMask OBJECT-TYPE
    SYNTAX  IpAddress
    MAX-ACCESS  read-write
    STATUS  current
    DESCRIPTION
      "Add IP ACL Operations destination Netmask."
    ::= { agSecIpAclOperDestAdd 2 }

agSecIpAclOperDestAddTimeOut OBJECT-TYPE
    SYNTAX  INTEGER (1..10080)
    MAX-ACCESS  read-write
    STATUS  current
    DESCRIPTION
      "destination timeout in minutes"
    ::= { agSecIpAclOperDestAdd 3 }

agSecIpAclOperDestAddIp OBJECT-TYPE
    SYNTAX  INTEGER {
        ok(1),
        add(2)
        }
    MAX-ACCESS  read-write
    STATUS  current
    DESCRIPTION
        "This is an action object ,when set to a value of add(2),
         it  Add operations destination IP Address/Mask.Ok(1) is returned
         when object is read."
    ::= { agSecIpAclOperDestAdd 4 }


agSecIpAclOperDestRemIp OBJECT-TYPE
    SYNTAX  IpAddress
    MAX-ACCESS  read-write
    STATUS  current
    DESCRIPTION
     "Enter destination IP Address for Remove operations"
    ::= { agSecIpAclOperDestRem 1 }

agSecIpAclOperDestRemMask OBJECT-TYPE
    SYNTAX  IpAddress
    MAX-ACCESS  read-write
    STATUS  current
    DESCRIPTION
      "Enter destination IP Netmask for Remove operations."
    ::= { agSecIpAclOperDestRem 2 }

agSecIpAclOperDestRemove OBJECT-TYPE
    SYNTAX  INTEGER {
        ok(1),
        remove(2)
        }
    MAX-ACCESS  read-write
    STATUS  current
    DESCRIPTION
        "This is an action object ,when set to a value of add(2),
         it  remove operations destination IP Address/Mask.
         Ok(1) is returned when object is read."
    ::= { agSecIpAclOperDestRem 4 }

agSecIpAclOperListSumm OBJECT IDENTIFIER ::= { agSecIpAclOperList 1 }

agSecIpAclOperListSummCfgSrc OBJECT-TYPE
    SYNTAX  Integer32
    MAX-ACCESS  read-only
    STATUS  current
    DESCRIPTION
      "Configuration source IP ACL Summary."
    ::= { agSecIpAclOperListSumm 1 }

agSecIpAclOperListSummCfgDst  OBJECT-TYPE
    SYNTAX  Integer32
    MAX-ACCESS  read-only
    STATUS  current
    DESCRIPTION
      "Configuration Destination IP ACL Summary."
    ::= { agSecIpAclOperListSumm 2 }

agSecIpAclOperListSummOperSrc OBJECT-TYPE
    SYNTAX  Integer32
    MAX-ACCESS  read-only
    STATUS  current
    DESCRIPTION
      "Operations source IP ACL Summary."
    ::= { agSecIpAclOperListSumm 3 }
agSecIpAclOperListSummOperDst  OBJECT-TYPE
    SYNTAX  Integer32
    MAX-ACCESS  read-only
    STATUS  current
    DESCRIPTION
      "Operations Destination IP ACL Summary."
    ::= { agSecIpAclOperListSumm 4 }

agSecIpAclOperListSummBogonSrc OBJECT-TYPE
    SYNTAX  Integer32
    MAX-ACCESS  read-only
    STATUS  current
    DESCRIPTION
      "Bogon source IP ACL Summary."
    ::= { agSecIpAclOperListSumm 5 }

agSecIpAclOperListSummTotSrc OBJECT-TYPE
    SYNTAX  Integer32
    MAX-ACCESS  read-only
    STATUS  current
    DESCRIPTION
      "Total source IP ACL Summary."
    ::= { agSecIpAclOperListSumm 6 }

agSecIpAclOperListSummTotDst  OBJECT-TYPE
    SYNTAX  Integer32
    MAX-ACCESS  read-only
    STATUS  current
    DESCRIPTION
      "Total Destination IP ACL Summary."
    ::= { agSecIpAclOperListSumm 7 }

--Ip Acl Oper Src Ip Table

agSecIpAclOperSrcTable OBJECT-TYPE
    SYNTAX  SEQUENCE OF AgSecIpAclOperListSrcTableEntry
    MAX-ACCESS  not-accessible
    STATUS  current
    DESCRIPTION
        "The table of IP ACL Oper Config Source Ip."
    ::= { agSecIpAclOperList 2 }

agSecIpAclOperSrcTableEntry OBJECT-TYPE
    SYNTAX AgSecIpAclOperListSrcTableEntry
    MAX-ACCESS  not-accessible
    STATUS  current
    DESCRIPTION
        "A row in the agSecIpAclOperSrcTable table."
    INDEX   { agSecIpAclOperListSrcIndx }
    ::= { agSecIpAclOperSrcTable 1 }

AgSecIpAclOperListSrcTableEntry ::=
    SEQUENCE {
        agSecIpAclOperListSrcIndx
            Integer32,
        agSecIpAclOperListSrcAddr
            IpAddress,
        agSecIpAclOperListSrcMask
            IpAddress,
        agSecIpAclOperListSrcTimeOut
            Integer32
}
agSecIpAclOperListSrcIndx OBJECT-TYPE
    SYNTAX  Integer32
    MAX-ACCESS  read-only
    STATUS  current
    DESCRIPTION
        "The IP ACL Oper Config Source Group index."
    ::= { agSecIpAclOperSrcTableEntry 1 }

agSecIpAclOperListSrcAddr OBJECT-TYPE
    SYNTAX  IpAddress
    MAX-ACCESS  read-only
    STATUS  current
    DESCRIPTION
            "Oper IP ACL Config Source IP Address."
    ::= { agSecIpAclOperSrcTableEntry 2 }

agSecIpAclOperListSrcMask OBJECT-TYPE
    SYNTAX  IpAddress
    MAX-ACCESS  read-only
    STATUS  current
    DESCRIPTION
            "Oper IP ACL Config Source NetMask."
    ::= { agSecIpAclOperSrcTableEntry 3 }

agSecIpAclOperListSrcTimeOut OBJECT-TYPE
    SYNTAX  Integer32
    MAX-ACCESS  read-only
    STATUS  current
    DESCRIPTION
            "Config Source Ip Timeout."
    ::= { agSecIpAclOperSrcTableEntry 4 }

--Ip ACL Oper Destination IP Table

agSecIpAclOperDstTable OBJECT-TYPE
    SYNTAX  SEQUENCE OF AgSecIpAclOperDstTableEntry
    MAX-ACCESS  not-accessible
    STATUS  current
    DESCRIPTION
        "The table of Operations Source IP ACL."
    ::= { agSecIpAclOperList 3 }

agSecIpAclOperDstTableEntry OBJECT-TYPE
    SYNTAX  AgSecIpAclOperDstTableEntry
    MAX-ACCESS  not-accessible
    STATUS  current
    DESCRIPTION
        "A row in the agSecIpAclOperDstTable table."
    INDEX   { agSecIpAclOperDstIndx }
    ::= { agSecIpAclOperDstTable 1 }

AgSecIpAclOperDstTableEntry ::=
    SEQUENCE {
        agSecIpAclOperDstIndx
            Integer32,
        agSecIpAclOperDstAddr
            IpAddress,
        agSecIpAclOperDstMask
            IpAddress,
        agSecIpAclOperDstTimeout
            Integer32
}
agSecIpAclOperDstIndx OBJECT-TYPE
    SYNTAX  Integer32
    MAX-ACCESS  read-only
    STATUS  current
    DESCRIPTION
        "The IP ACL Oper Destination IP Group index."
    ::= { agSecIpAclOperDstTableEntry 1 }

agSecIpAclOperDstAddr OBJECT-TYPE
    SYNTAX  IpAddress
    MAX-ACCESS  read-only
    STATUS  current
    DESCRIPTION
            "IP ACL Operations Destination IP Address."
    ::= { agSecIpAclOperDstTableEntry 2 }

agSecIpAclOperDstMask OBJECT-TYPE
    SYNTAX  IpAddress
    MAX-ACCESS  read-only
    STATUS  current
    DESCRIPTION
            "IP ACL Operations Destination NetMask."
    ::= { agSecIpAclOperDstTableEntry 3 }

agSecIpAclOperDstTimeout OBJECT-TYPE
    SYNTAX  Integer32
    MAX-ACCESS  read-only
    STATUS  current
    DESCRIPTION
            "IP ACL Operations Destination Ip Timeout."
    ::= { agSecIpAclOperDstTableEntry 4 }

--Displaying syslog messages to telnet/ssh sessions

agSyslogOperDispLog OBJECT-TYPE
    SYNTAX  INTEGER {
        enable(1),
        disable(2)
        }
    MAX-ACCESS  read-write
    STATUS  current
    DESCRIPTION
      "This an action object which is used to enable/disable
       displaying syslog messages to telnet/ssh sessions."
    ::= { agSyslogOper 1 }

-- Port operation table
agPortOperTable OBJECT-TYPE
    SYNTAX  SEQUENCE OF AgPortOperTableEntry
    MAX-ACCESS  not-accessible
    STATUS  current
    DESCRIPTION
        "The table of port operations."
    ::= { agentOper 1 }

agPortOperTableEntry OBJECT-TYPE
    SYNTAX  AgPortOperTableEntry
    MAX-ACCESS  not-accessible
    STATUS  current
    DESCRIPTION
        "A row in the port operations table."
    INDEX   { portOperIdx }
    ::= { agPortOperTable 1 }

AgPortOperTableEntry ::=
    SEQUENCE {
	portOperIdx	    Integer32,
	portOperRmon	    INTEGER,
	portOperState	    INTEGER
    }

portOperIdx OBJECT-TYPE
    SYNTAX  Integer32
    MAX-ACCESS  read-only
    STATUS  current
    DESCRIPTION
        "The port index."
    ::= { agPortOperTableEntry 1 }

portOperState OBJECT-TYPE
    SYNTAX  INTEGER {
        enabled(1),
        disabled(2)
        }
    MAX-ACCESS  read-write
    STATUS  current
    DESCRIPTION
        "Enable/Disable port."
    ::= { agPortOperTableEntry 2 }

portOperRmon OBJECT-TYPE
    SYNTAX  INTEGER {
        enabled(1),
        disabled(2)
        }
    MAX-ACCESS  read-write
    STATUS  current
    DESCRIPTION
        "Enable/Disable RMON for port."
        ::= { agPortOperTableEntry 3 }

agClearAppLog OBJECT-TYPE
    SYNTAX INTEGER {
        ok(1),
        clear(2)
    }
    MAX-ACCESS read-write
    STATUS current
    DESCRIPTION
        "This is an action object.When set to a value of clear(2)
         application services trace Logs will be cleared.
         ok(1) is returned when read."
    ::= { agentOper 7 }

ntpOperSendReq OBJECT-TYPE
    SYNTAX  INTEGER {
        no(1),
        yes(2)
        }
    MAX-ACCESS  read-write
    STATUS  current
    DESCRIPTION
        "Allows the user to send requests to the NTP server."
    ::= { agNTPOper 1 }

agPeerSyncConfigOper OBJECT-TYPE
    SYNTAX  INTEGER {
        other(1),
	sync(2)
        }
    MAX-ACCESS  read-write
    STATUS  current
    DESCRIPTION
        "Allows the user to send oper sync requests.
        Note:This mib is supported only in VX instance on Virtualization. "
    ::= { agPeerSyncOper 1 }

agVadcVrrpOperTable OBJECT-TYPE
    SYNTAX  SEQUENCE OF AgVadcVrrpOperTableEntry
    MAX-ACCESS  not-accessible
    STATUS  current
    DESCRIPTION
        "The table of vADC operations."
    ::= { agVadcVrrpOper 1 }

agVadcVrrpOperTableEntry OBJECT-TYPE
    SYNTAX  AgVadcVrrpOperTableEntry
    MAX-ACCESS  not-accessible
    STATUS  current
    DESCRIPTION
        "A row in the vADC operations table."
    INDEX   { vadcVrrpOperIdx }
    ::= { agVadcVrrpOperTable 1 }

AgVadcVrrpOperTableEntry ::=
    SEQUENCE {
        vadcVrrpOperIdx         Integer32,
        vadcVrrpOperBackup       INTEGER
    }

vadcVrrpOperIdx OBJECT-TYPE
    SYNTAX  Integer32
    MAX-ACCESS  read-only
    STATUS  current
    DESCRIPTION
        "The vadc index."
    ::= { agVadcVrrpOperTableEntry 1 }

vadcVrrpOperBackup OBJECT-TYPE
    SYNTAX  INTEGER {
        ok(1),
        backup(2)
        }
    MAX-ACCESS  read-write
    STATUS  current
    DESCRIPTION
        "When set to a value of 'backup(2)' it forces the specified
         vADC master virtual router into backup mode.
         'ok(1)' is returned when the object is read."
    ::= { agVadcVrrpOperTableEntry 2 }

-- Application Services Trace Logging

agAppLogAppShape OBJECT-TYPE
    SYNTAX  INTEGER {
        enabled(1),
        disabled(2)
        }
    MAX-ACCESS  read-write
    STATUS  current
    DESCRIPTION
        "Enable or disable AppShape++ Trace Logging."
    ::= { agAppLogOper 1 }

agAppLogCaching OBJECT-TYPE
    SYNTAX  INTEGER {
        enabled(1),
        disabled(2)
        }
    MAX-ACCESS  read-write
    STATUS  current
    DESCRIPTION
        "Enable or disable Caching Trace Logging."
    ::= { agAppLogOper 2 }

agAppLogCompression OBJECT-TYPE
    SYNTAX  INTEGER {
        enabled(1),
        disabled(2)
        }
    MAX-ACCESS  read-write
    STATUS  current
    DESCRIPTION
        "Enable or disable Compression Trace Logging."
    ::= { agAppLogOper 3 }

agAppLogContentClass OBJECT-TYPE
    SYNTAX  INTEGER {
        enabled(1),
        disabled(2)
        }
    MAX-ACCESS  read-write
    STATUS  current
    DESCRIPTION
        "Enable or disable Content Class Trace Logging."
    ::= { agAppLogOper 4 }

agAppLogHTTP OBJECT-TYPE
    SYNTAX  INTEGER {
        enabled(1),
        disabled(2)
        }
    MAX-ACCESS  read-write
    STATUS  current
    DESCRIPTION
        "Enable or disable HTTP Trace Logging."
    ::= { agAppLogOper 5 }

agAppLogHTTPModification OBJECT-TYPE
    SYNTAX  INTEGER {
        enabled(1),
        disabled(2)
        }
    MAX-ACCESS  read-write
    STATUS  current
    DESCRIPTION
        "Enable or disable HTTP Modification Trace Logging."
    ::= { agAppLogOper 6 }

agAppLogSSL OBJECT-TYPE
    SYNTAX  INTEGER {
        enabled(1),
        disabled(2)
        }
    MAX-ACCESS  read-write
    STATUS  current
    DESCRIPTION
        "Enable or disable SSL Trace Logging."
    ::= { agAppLogOper 7 }

agAppLogTCP OBJECT-TYPE
    SYNTAX  INTEGER {
        enabled(1),
        disabled(2)
        }
    MAX-ACCESS  read-write
    STATUS  current
    DESCRIPTION
        "Enable or disable TCP Trace Logging."
    ::= { agAppLogOper 8 }

agAppLogDataTable OBJECT-TYPE
    SYNTAX  INTEGER {
        enabled(1),
        disabled(2)
        }
    MAX-ACCESS  read-write
    STATUS  current
    DESCRIPTION
        "Enable or disable Data Table Trace Logging."
    ::= { agAppLogOper 9 }

agAppLogMemory OBJECT-TYPE
    SYNTAX  INTEGER {
        enabled(1),
        disabled(2)
        }
    MAX-ACCESS  read-write
    STATUS  current
    DESCRIPTION
        "Enable or disable Memory Trace Logging."
    ::= { agAppLogOper 10 }

agAppLogFastview OBJECT-TYPE
    SYNTAX  INTEGER {
        enabled(1),
        disabled(2)
        }
    MAX-ACCESS  read-write
    STATUS  current
    DESCRIPTION
        "Enable or disable Fastview Trace Logging."
    ::= { agAppLogOper 11 }

agAppLogFastviewSmf OBJECT-TYPE
    SYNTAX  INTEGER {
        enabled(1),
        disabled(2)
        }
    MAX-ACCESS  read-write
    STATUS  current
    DESCRIPTION
        "Enable or disable Fastview SMF Trace Logging."
    ::= { agAppLogOper 12 }

agAppLogExternalFetcher OBJECT-TYPE
    SYNTAX  INTEGER {
        enabled(1),
        disabled(2)
        }
    MAX-ACCESS  read-write
    STATUS  current
    DESCRIPTION
        "Enable or disable External Fetcher Trace Logging."
    ::= { agAppLogOper 13 }

agAppLogConfigFlushFreq OBJECT-TYPE
    SYNTAX  INTEGER (0..1000)
    MAX-ACCESS  read-write
    STATUS  current
    DESCRIPTION
        "Set the disk flush frequency when writing to the applog files"
    ::= { agAppLogConfigOper 1 }


agAppLogConfigMaxFiles OBJECT-TYPE
    SYNTAX  INTEGER (1..50)
    MAX-ACCESS  read-write
    STATUS  current
    DESCRIPTION
        "Set the maximum number of applog files"
    ::= { agAppLogConfigOper 2 }


agAppLogConfigMaxSize OBJECT-TYPE
    SYNTAX  INTEGER (1..50)
    MAX-ACCESS  read-write
    STATUS  current
    DESCRIPTION
        "Set the maximum size of a single applog file"
    ::= { agAppLogConfigOper 3 }


-- Port information table

portInfoTable OBJECT-TYPE
    SYNTAX  SEQUENCE OF PortInfoTableEntry
    MAX-ACCESS  not-accessible
    STATUS  current
    DESCRIPTION
        "The table of port information."
    ::= { portInfo 1 }

portInfoTableEntry OBJECT-TYPE
    SYNTAX  PortInfoTableEntry
    MAX-ACCESS  not-accessible
    STATUS  current
    DESCRIPTION
        "A row in the port information table."
    INDEX   { portInfoIndx }
    ::= { portInfoTable 1 }

PortInfoTableEntry ::= SEQUENCE {
    portInfoIndx        	Integer32,
    portInfoSpeed       	INTEGER,
    portInfoMode        	INTEGER,
    portInfoFlowCtrl    	INTEGER,
    portInfoLink        	INTEGER,
    portInfoPhyIfDescr  	DisplayString,
    portInfoPhyIfType   	INTEGER,
    portInfoPhyIfMtu    	Integer32,
    portInfoPhyIfPhysAddress  	PhysAddress,
    portInfoPhyIfOperStatus	INTEGER,
    portInfoPhyIfLastChange	TimeTicks,
    portInfoPhyConnType   	INTEGER,
    portInfoPreferred	   	INTEGER,
    portInfoBackup	  	INTEGER,
    portInfoSFPName	  	DisplayString,
    portInfoSFPType		INTEGER,
    portInfoShared		INTEGER
    ,portInfoVADC		INTEGER,
    portInfoVADCs               DisplayString
    }

portInfoIndx OBJECT-TYPE
    SYNTAX  Integer32
    MAX-ACCESS  read-only
    STATUS  current
    DESCRIPTION
        "The port index."
    ::= { portInfoTableEntry 1 }

portInfoSpeed OBJECT-TYPE
    SYNTAX  INTEGER {
        mbs10(2),
        mbs100(3),
        mbs1000(4),
        any(5),
        mbs10000(6),
        mbs40000(7),
        auto(8),
        mbs100000(9),
	mbs25000(10)
        }
    MAX-ACCESS  read-only
    STATUS  current
    DESCRIPTION
        "The current operational speed of the port."
    ::= { portInfoTableEntry 2 }

portInfoMode OBJECT-TYPE
    SYNTAX  INTEGER {
        full-duplex(2),
        half-duplex(3),
        any(4)
        }
    MAX-ACCESS  read-only
    STATUS  current
    DESCRIPTION
        "The current operational mode of the port."
    ::= { portInfoTableEntry 3 }

portInfoFlowCtrl OBJECT-TYPE
    SYNTAX  INTEGER {
        transmit(2),
        receive(3),
        both(4),
        none(5)
        }
    MAX-ACCESS  read-only
    STATUS  current
    DESCRIPTION
        "The current operational flow control of the port."
    ::= { portInfoTableEntry 4 }

portInfoLink OBJECT-TYPE
    SYNTAX  INTEGER {
        up(1),
        down(2),
        disabled(3),
        inoperative(4) -- unrecognized PCI device
        }
     MAX-ACCESS  read-only
     STATUS  current
     DESCRIPTION
         "The current operational link status of the port."
     ::= { portInfoTableEntry 5 }

portInfoPhyIfDescr OBJECT-TYPE
    SYNTAX  DisplayString (SIZE (0..255))
    MAX-ACCESS  read-only
    STATUS  current
    DESCRIPTION
	    "A textual string containing information about the
	    interface.  This string should include the name of
	    the manufacturer, the product name and the version
	    of the hardware interface."
    ::= { portInfoTableEntry 6 }

portInfoPhyIfType OBJECT-TYPE
    SYNTAX  INTEGER {
		other(1),          -- none of the following
		regular1822(2),
		hdh1822(3),
		ddn-x25(4),
		rfc877-x25(5),
		ethernet-csmacd(6),
		iso88023-csmacd(7),
		iso88024-tokenBus(8),
		iso88025-tokenRing(9),
		iso88026-man(10),
		starLan(11),
		proteon-10Mbit(12),
		proteon-80Mbit(13),
		hyperchannel(14),
		fddi(15),
		lapb(16),
		sdlc(17),
		ds1(18),           -- T-1
		e1(19),            -- european equiv. of T-1
		basicISDN(20),
		primaryISDN(21),   -- proprietary serial
		propPointToPointSerial(22),
		ppp(23),
		softwareLoopback(24),
		eon(25),            -- CLNP over IP [11]
		ethernet-3Mbit(26),
		nsip(27),           -- XNS over IP
		slip(28),           -- generic SLIP
		ultra(29),          -- ULTRA technologies
		ds3(30),            -- T-3
		sip(31),            -- SMDS
		frame-relay(32)
	    }
    MAX-ACCESS  read-only
    STATUS  current
    DESCRIPTION
	    "The type of interface, distinguished according to
	    the physical/link protocol(s) immediately `below'
	    the network layer in the protocol stack."
    ::= { portInfoTableEntry 7 }

portInfoPhyIfMtu OBJECT-TYPE
    SYNTAX  Integer32
    MAX-ACCESS  read-only
    STATUS  current
    DESCRIPTION
	    "The size of the largest datagram which can be
	    sent/received on the interface, specified in
	    octets.  For interfaces that are used for
	    transmitting network datagrams, this is the size
	    of the largest network datagram that can be sent
	    on the interface."
    ::= { portInfoTableEntry 8 }

portInfoPhyIfPhysAddress OBJECT-TYPE
    SYNTAX  PhysAddress
    MAX-ACCESS  read-only
    STATUS  current
    DESCRIPTION
	    "The interface's address at the protocol layer
	    immediately `below' the network layer in the
	    protocol stack.  For interfaces which do not have
	    such an address (e.g., a serial line), this object
	    should contain an octet string of zero length."
    ::= { portInfoTableEntry 9 }

portInfoPhyIfOperStatus OBJECT-TYPE
    SYNTAX  INTEGER {
	up(1),       -- ready to pass packets
	down(2),
	testing(3)   -- in some test mode
	}
    MAX-ACCESS  read-only
    STATUS  current
    DESCRIPTION
	    "The current operational state of the interface.
	    The testing(3) state indicates that no operational
	    packets can be passed."
    ::= { portInfoTableEntry 10 }

portInfoPhyIfLastChange OBJECT-TYPE
    SYNTAX  TimeTicks
    MAX-ACCESS  read-only
    STATUS  current
    DESCRIPTION
	    "The value of sysUpTime at the time the interface
	    entered its current operational state.  If the
	    current state was entered prior to the last re-
	    initialization of the local network management
	    subsystem, then this object contains a zero
	    value."
    ::= { portInfoTableEntry 11 }

portInfoPhyConnType OBJECT-TYPE
    SYNTAX  INTEGER {
		feCopper(1),
		geCopper(2),
		geSFP(3),
		unknown(4),
		xGeSFP(5),
		xGeQSFP(6), -- 40G port
		xGeQSFP28(7), -- 100G port
		xGeSFP28(8) -- 25G port
	    }
    MAX-ACCESS  read-only
    STATUS  current
    DESCRIPTION
	    "The physical connection type, i.e. copper or SFP port."
    ::= { portInfoTableEntry 12 }

portInfoPreferred OBJECT-TYPE
    SYNTAX  INTEGER {
		invalid(1),
		copper(2),
		sfp(3)
	    }
    MAX-ACCESS  read-only
    STATUS  current
    DESCRIPTION
	    "The port preferred connection type. For dual ports only"
    ::= { portInfoTableEntry 13 }

portInfoBackup OBJECT-TYPE
    SYNTAX  INTEGER {
		invalid(1),
		none(2),
		copper(3),
		sfp(4)
	    }
    MAX-ACCESS  read-only
    STATUS  current
    DESCRIPTION
	    "The port backup setting. For dual ports only"
    ::= { portInfoTableEntry 14 }

portInfoSFPName OBJECT-TYPE
    SYNTAX  DisplayString (SIZE (0..255))
    MAX-ACCESS  read-only
    STATUS  current
    DESCRIPTION
	    "A textual string containing information about the
	    SFP manufacturer. For valid ports only."
    ::= { portInfoTableEntry 15 }

portInfoSFPType OBJECT-TYPE
    SYNTAX  INTEGER {
		invalid(1),
		sfpTypeSX(2),
		sfpTypeLX(3),
		sfpTypeCX(4),
		sfpTypeCopper(5)
	    }
    MAX-ACCESS  read-only
    STATUS  current
    DESCRIPTION
	    "The inserted SFP type. For valid ports only."
    ::= { portInfoTableEntry 17 }

portInfoShared OBJECT-TYPE
    SYNTAX  INTEGER {
		enabled(1),
		disabled(2)
	    }
    MAX-ACCESS  read-only
    STATUS  current
    DESCRIPTION
	    "Indicates if the port is shared or not."
    ::= { portInfoTableEntry 18 }

portInfoVADC OBJECT-TYPE
    SYNTAX  INTEGER
    MAX-ACCESS  read-only
    STATUS  current
    DESCRIPTION
	    " The vADC number that the port belongs to.
              Note:This mib is supported only in VX and vADC instance"
    ::= { portInfoTableEntry 19 }
portInfoVADCs OBJECT-TYPE
    SYNTAX  DisplayString
    MAX-ACCESS  read-only
    STATUS  current
    DESCRIPTION
            " The Range of vADCS that the port belongs to.
              Note:This mib is supported only in VX and vADC instance"
    ::= { portInfoTableEntry 20 }


agEnabledSwFeatures OBJECT-TYPE
    SYNTAX  DisplayString
    MAX-ACCESS  read-only
    STATUS  current
    DESCRIPTION
        "The software features that are enabled on the switch."
    ::= { swKeyInfo 1 }

agEnabledGslbKey OBJECT-TYPE
    SYNTAX  INTEGER {
        enabled(1),
        disabled(2)
        }
    MAX-ACCESS  read-only
    STATUS  current
    DESCRIPTION
        "Query if software key Global slb enabled on switch."
    ::= { swKeyInfo 2 }

agEnabledBwmKey OBJECT-TYPE
    SYNTAX  INTEGER {
        enabled(1),
        disabled(2)
        }
    MAX-ACCESS  read-only
    STATUS  current
    DESCRIPTION
        "Query if software key Bandwidth Mgmt. enabled on switch."
    ::= { swKeyInfo 3 }

agEnabledSecurityKey OBJECT-TYPE
    SYNTAX  INTEGER {
        enabled(1),
        disabled(2)
        }
    MAX-ACCESS  read-only
    STATUS  current
    DESCRIPTION
        "Query if software key Security enabled on switch."
    ::= { swKeyInfo 4 }

agEnabledLinklbKey OBJECT-TYPE
    SYNTAX  INTEGER {
        enabled(1),
        disabled(2)
        }
    MAX-ACCESS  read-only
    STATUS  current
    DESCRIPTION
        "Query if software key Inbound Linklb is enabled on switch."
    ::= { swKeyInfo 6 }

agEnabledOtbKey OBJECT-TYPE
    SYNTAX  INTEGER {
        enabled(1),
        disabled(2)
        }
    MAX-ACCESS  read-only
    STATUS  current
    DESCRIPTION
        "Query if software key OTB is enabled on switch."
    ::= { swKeyInfo 7 }

agEnabledGeoKey OBJECT-TYPE
    SYNTAX  INTEGER {
        enabled(1),
        disabled(2),
        expired(3)
        }
    MAX-ACCESS  read-only
    STATUS  current
    DESCRIPTION
        "Query if software key Geo-location is enabled on switch."
    ::= { swKeyInfo 8 }


-- Agent System Group
-- This group of objects take effect on the 'SET' request.
-- There is no need to 'apply' or 'save'.

agApplyConfiguration OBJECT-TYPE
    SYNTAX  INTEGER {
        other(1),
        apply(2)
        ,applyVadc(3)
        }
    MAX-ACCESS  read-write
    STATUS  current
    DESCRIPTION
        "This is an action object to apply the changes made to configuration
         of the switch. By setting the value to apply(2), all the changes
         made since the last apply are written to the new_config block.If applyVadc(3) is set, any
         configuration change in the running vadc instances get applied
         If applyVadc(3) is set, any configuration change in the running
         vadc instances get applied.
         other(1) is returned when this object ie read. "
    ::= { agSystem 2 }

agSavePending OBJECT-TYPE
    SYNTAX  INTEGER {
        saveNeeded(1),
        noSaveNeeded(2)
        }
    MAX-ACCESS  read-only
    STATUS  current
    DESCRIPTION
        "This object, when read, gives the user information
         whether an save action is needed and that the configuration
         has been applied but not saved to the flash."
    ::= { agSystem 3 }

agSaveConfiguration OBJECT-TYPE
    SYNTAX  INTEGER {
        ok(1),
        saveActive(2),
        notSaveActive(3)

        ,saveVadc(4)
        }
    MAX-ACCESS  read-write
    STATUS  current
    DESCRIPTION
        "This is an action object to write current configuration to
         nonvolatile storage.

         When issued with the saveActive, the active configuration
         in flash is saved to backup in flash and then the new
         configuration is saved to the active configuration in flash.

         When issued with notSaveActive, the active configuration
         is NOT saved to the flash and the active configuration is
         overwritten with the new configuration.

         When saveVadc(4) is issued all unsaved configuration in the active vadc(s)
         will get saved.

         When saveVadc(4) is issued all unsaved configuration in the active vadc(s)
         will get saved.

         ok(1) is returned always when read."
    ::= { agSystem 4 }

agRevert OBJECT-TYPE
    SYNTAX  INTEGER {
        other(1),
        revert(2)
        }
    MAX-ACCESS  read-write
    STATUS  current
    DESCRIPTION
        "This is an action object to revert the unapplied changes
         made to the switch. By setting the value to revert(2),
         all the unapplied changes will be reverted. This action
         will copy the current_config to the new_config block.

         other(1) is returned when this object is read. "
    ::= { agSystem 5 }

agRevertApply OBJECT-TYPE
    SYNTAX  INTEGER {
        other(1),
        revertApply(2)
        }
    MAX-ACCESS  read-write
    STATUS  current
    DESCRIPTION
        "This is an action object to revert the unsaved changes
         made to the switch. By setting the value to revertApply(2),
         all the unsaved as well as unapplied changes will be
         reverted.

         other(1) is returned when this object is read. "
    ::= { agSystem 6 }

agReset OBJECT-TYPE
    SYNTAX  INTEGER {
        other(1),
        reset(2)
        }
    MAX-ACCESS  read-write
    STATUS  current
    DESCRIPTION
        "This is an action object to reboot the switch or a pblade.
         other(1) is returned always when read."
    ::= { agSystem 7 }

agConfigForNxtReset OBJECT-TYPE
    SYNTAX  INTEGER {
        active(2),
        backup(3),
        default(4)
        }
    MAX-ACCESS  read-write
    STATUS  current
    DESCRIPTION
        "The configuration information to be loaded from at next reset.

          The following values are writable:
              active(2)...active configuration block
              backup(3)...backup configuration block
              default(4)..default configuration block"
    ::= { agSystem 8 }

agImageForNxtReset OBJECT-TYPE
    SYNTAX  INTEGER (2..11)
    MAX-ACCESS  read-write
    STATUS  current
    DESCRIPTION
        "The software image to be booted from at next reset.

         The following values are writable:
             image1(2)...image 1
             image2(3)...image 2
	     ..."
    ::= { agSystem 9 }

agSoftwareVersion OBJECT-TYPE
    SYNTAX  DisplayString (SIZE(0..16))
    MAX-ACCESS  read-only
    STATUS  current
    DESCRIPTION
        "The version of the software image that is currently running on the
         system in the form of 'major.minor.maintenance.bugfix'.  A zero
         length string is returned if version is not available."
    ::= { agSystem 10 }

agBootVer OBJECT-TYPE
    SYNTAX  DisplayString (SIZE(0..16))
    MAX-ACCESS  read-only
    STATUS  current
    DESCRIPTION
        "The version of the boot code in the form of 'major.minor.bugfix'.
         A zero length string is returned if version is not available."
    ::= { agSystem 11 }

agImage1Ver OBJECT-TYPE
    SYNTAX  DisplayString (SIZE(0..128))
    MAX-ACCESS  read-only
    STATUS  current
    DESCRIPTION
        "The version of the software image stored in image 1 storage in the
         form of 'major.minor.maintenance.bugfix'.  A zero length string is returned if
         version is not available or there is no valid software image."
    ::= { agSystem 12 }

agImage2Ver OBJECT-TYPE
    SYNTAX  DisplayString (SIZE(0..128))
    MAX-ACCESS  read-only
    STATUS  current
    DESCRIPTION
        "The version of the software image stored in image 2 storage in the
         form of 'major.minor.maintenance.bugfix'.  A zero length string is returned if
         version is not available or there is no valid software image."
    ::= { agSystem 13 }

agRtcDate OBJECT-TYPE
    SYNTAX  DisplayString (SIZE(0..16))
    MAX-ACCESS  read-write
    STATUS  current
    DESCRIPTION
        "The date on the real time clock in the form of 'mm/dd/yy'.
         A zero length string is returned if date is not available."
    ::= { agSystem 14 }

agRtcTime OBJECT-TYPE
    SYNTAX  DisplayString (SIZE(0..16))
    MAX-ACCESS  read-write
    STATUS  current
    DESCRIPTION
        "The time on the real time clock in the form of 'hh:mm:ss'.
         A zero length string is returned if time is not available."
    ::= { agSystem 15 }

agLastSetErrorReason   OBJECT-TYPE
    SYNTAX  DisplayString (SIZE(0..255))
    MAX-ACCESS  read-only
    STATUS  current
    DESCRIPTION
        "The error reason of the last SET failure."
    ::= { agSystem 16 }

agCurCfgHttpServerPort OBJECT-TYPE
    SYNTAX  INTEGER (1..65535)
    MAX-ACCESS  read-only
    STATUS  current
    DESCRIPTION
        "The TCP port number that the HTTP server is listening to
         in the current_configuration block."
    ::= { agSystem 17 }

agNewCfgHttpServerPort OBJECT-TYPE
    SYNTAX  INTEGER (1..65535)
    MAX-ACCESS  read-write
    STATUS  current
    DESCRIPTION
        "The TCP port number that the HTTP server is listening to
         in the new_configuration block."
    ::= { agSystem 18 }

agCurCfgLoginBanner OBJECT-TYPE
    SYNTAX  DisplayString (SIZE(0..79))
    MAX-ACCESS  read-only
    STATUS  current
    DESCRIPTION
        "The user defined login banner."
    ::= { agSystem 19 }

agNewCfgLoginBanner OBJECT-TYPE
    SYNTAX  DisplayString (SIZE(0..79))
    MAX-ACCESS  read-write
    STATUS  current
    DESCRIPTION
        "The user defined login banner."
    ::= { agSystem 20 }

agCurCfgSmtpHost OBJECT-TYPE
    SYNTAX  DisplayString (SIZE(0..127))
    MAX-ACCESS  read-only
    STATUS  current
    DESCRIPTION
        "The user defined SMTP host."
    ::= { agSystem 21 }

agNewCfgSmtpHost OBJECT-TYPE
    SYNTAX  DisplayString (SIZE(0..127))
    MAX-ACCESS  read-write
    STATUS  current
    DESCRIPTION
        "The user defined SMTP host. If it is a host name then please configure agNewCfgSmtpHostIPVersion.
         By default IPv4 version will be choosen.
         If IPv4 or Ipv6 address is configured than no need to configure agNewCfgSmtpHostIPVersion,
         this will be filled accordingly. "
    ::= { agSystem 22 }


agCurCfgConsole OBJECT-TYPE
    SYNTAX  INTEGER {
        enabled(1),
        disabled(2)
        }
    MAX-ACCESS  read-only
    STATUS  current
    DESCRIPTION
        "Enable or disable console output of syslog messages."
    ::= { agSystem 23 }

agNewCfgConsole OBJECT-TYPE
    SYNTAX  INTEGER {
        enabled(1),
        disabled(2)
        }
    MAX-ACCESS  read-write
    STATUS  current
    DESCRIPTION
        "Enable or disable console output of syslog messages."
    ::= { agSystem 24 }


agCurCfgBootp OBJECT-TYPE
    SYNTAX  INTEGER {
        enabled(2),
        disabled(3)
        }
    MAX-ACCESS  read-only
    STATUS  current
    DESCRIPTION
        "Enable or disable the use of BootP, as currently configured in the
         current_configuration block."
    ::= { agSystem 29 }

agNewCfgBootp OBJECT-TYPE
    SYNTAX  INTEGER {
        enabled(2),
        disabled(3)
        }
    MAX-ACCESS  read-write
    STATUS  current
    DESCRIPTION
        "Enable or disable the use of BootP, in the new_configuration block."
    ::= { agSystem 30 }


agCurCfgSnmpTimeout OBJECT-TYPE
    SYNTAX  INTEGER (1..30)
    MAX-ACCESS  read-only
    STATUS  current
    DESCRIPTION
        "Once SNMP operations like agApplyConfig, agDiffState and
         agDumpState, which use the state machine are done the resources
         used by these operations need to be freed by setting the state
         back to 'idle' so others can issue the commands via SNMP.
         agSnmpTimeout indicates the number of minutes before the resources
         are freed and the state set back to 'idle' if this operation is not
         performed by the user."
    ::= { agSystem 32 }

agNewCfgSnmpTimeout OBJECT-TYPE
    SYNTAX  INTEGER (1..30)
    MAX-ACCESS  read-write
    STATUS  current
    DESCRIPTION
        "Once SNMP operations like agApplyConfig, agDiffState and
         agDumpState, which use the state machine are done the resources
         used by these operations need to be freed by setting the state
         back to 'idle' so others can issue the commands via SNMP.
         agSnmpTimeout indicates the number of minutes before the resources
         are freed and the state set back to 'idle' if this operation is not
         performed by the user."
    ::= { agSystem 33 }

agCurCfgTelnetServerPort OBJECT-TYPE
    SYNTAX  INTEGER (1..65535)
    MAX-ACCESS  read-only
    STATUS  current
    DESCRIPTION
        "The TCP port number that the telnet server listens for telnet
         sessions."
    ::= { agSystem 34 }

agNewCfgTelnetServerPort OBJECT-TYPE
    SYNTAX  INTEGER (1..65535)
    MAX-ACCESS  read-write
    STATUS  current
    DESCRIPTION
        "The TCP port number that the telnet server listens for telnet
         sessions."
    ::= { agSystem 35 }

agClearFlashDump OBJECT-TYPE
    SYNTAX  INTEGER {
        ok(1),
        clear(2)
        }
    MAX-ACCESS  read-write
    STATUS  current
    DESCRIPTION
        "This is an action object to clear the FLASH dump.
         ok(1) is returned when this object is read. "
    ::= { agSystem 36 }


agCurCfgTrapSrcIf OBJECT-TYPE
    SYNTAX  Integer32
    MAX-ACCESS  read-only
    STATUS  current
    DESCRIPTION
        "The SNMP trap source interface number."
    ::= { agSystem 39 }

agNewCfgTrapSrcIf OBJECT-TYPE
    SYNTAX  Integer32
    MAX-ACCESS  read-write
    STATUS  current
    DESCRIPTION
        "The SNMP trap source interface number."
    ::= { agSystem 40 }

agCurCfgARPMaxRate OBJECT-TYPE
    SYNTAX  INTEGER (0..65535)
    MAX-ACCESS  read-only
    STATUS  current
    DESCRIPTION
        "The maximum allowed rate of MP-destined ARP packets."
    ::= { agSystem 41 }

agNewCfgARPMaxRate OBJECT-TYPE
    SYNTAX  INTEGER (0..65535)
    MAX-ACCESS  read-write
    STATUS  current
    DESCRIPTION
        "The maximum allowed rate of MP-destined ARP packets."
    ::= { agSystem 42 }

agCurCfgICMPMaxRate OBJECT-TYPE
    SYNTAX  INTEGER (0..65535)
    MAX-ACCESS  read-only
    STATUS  current
    DESCRIPTION
        "The maximum allowed rate of MP-destined ICMP packets."
    ::= { agSystem 43 }

agNewCfgICMPMaxRate OBJECT-TYPE
    SYNTAX  INTEGER (0..65535)
    MAX-ACCESS  read-write
    STATUS  current
    DESCRIPTION
        "The maximum allowed rate of MP-destined ICMP packets."
    ::= { agSystem 44 }

agCurCfgTCPMaxRate OBJECT-TYPE
    SYNTAX  INTEGER (0..65535)
    MAX-ACCESS  read-only
    STATUS  current
    DESCRIPTION
        "The maximum allowed rate of MP-destined TCP packets."
    ::= { agSystem 45 }

agNewCfgTCPMaxRate OBJECT-TYPE
    SYNTAX  INTEGER (0..65535)
    MAX-ACCESS  read-write
    STATUS  current
    DESCRIPTION
        "The maximum allowed rate of MP-destined TCP packets."
    ::= { agSystem 46 }

agCurCfgUDPMaxRate OBJECT-TYPE
    SYNTAX  INTEGER (0..65535)
    MAX-ACCESS  read-only
    STATUS  current
    DESCRIPTION
        "The maximum allowed rate of MP-destined UDP packets."
    ::= { agSystem 47 }

agNewCfgUDPMaxRate OBJECT-TYPE
    SYNTAX  INTEGER (0..65535)
    MAX-ACCESS  read-write
    STATUS  current
    DESCRIPTION
        "The maximum allowed rate of MP-destined UDP packets."
    ::= { agSystem 48 }

agCurCfgHttpsServerPort OBJECT-TYPE
    SYNTAX  INTEGER (1..65535)
    MAX-ACCESS  read-only
    STATUS  current
    DESCRIPTION
        "The TCP port number that the HTTPS server is listening to
         in the current_configuration block."
    ::= { agSystem 49 }

agNewCfgHttpsServerPort OBJECT-TYPE
    SYNTAX  INTEGER (1..65535)
    MAX-ACCESS  read-write
    STATUS  current
    DESCRIPTION
        "The TCP port number that the HTTPS server is listening to
         in the new_configuration block."
    ::= { agSystem 50 }


agCurDaylightSavings   OBJECT-TYPE
    SYNTAX  INTEGER {
    none(0),
    africa-Algeria(1),
    africa-Angola(2),
    africa-Benin(3),
    africa-Botswana(4),
    africa-Burkina-Faso(5),
    africa-Burundi(6),
    africa-Cameroon(7),
    africa-Central-African-Rep(8),
    africa-Chad(9),
    africa-Congo-WestDemRepCongo(10),
    africa-Congo-EastDemRepCongo(11),
    africa-Congo-Rep(12),
    africa-Cote-dIvoire(13),
    africa-Djibouti(14),
    africa-Egypt(15),
    africa-Equatorial-Guinea(16),
    africa-Eritrea(17),
    africa-Ethiopia(18),
    africa-Gabon(19),
    africa-Gambia(20),
    africa-Ghana(21),
    africa-Guinea(22),
    africa-Guinea-Bissau(23),
    africa-Kenya(24),
    africa-Lesotho(25),
    africa-Liberia(26),
    africa-Libya(27),
    africa-Malawi(28),
    africa-Mali-SouthWestMali(29),
    africa-Mali-NorthEastMali(30),
    africa-Mauritania(31),
    africa-Morocco(32),
    africa-Mozambique(33),
    africa-Namibia(34),
    africa-Niger(35),
    africa-Nigeria(36),
    africa-Rwanda(37),
    africa-SaoTome-And-Principe(38),
    africa-Senegal(39),
    africa-SierraLeone(40),
    africa-Somalia(41),
    africa-SouthAfrica(42),
    europe-Spain-Mainland(43),
    africa-Spain-CeutaMelilla(44),
    atlanticOcean-Spain-CanaryIslands(45),
    africa-Sudan(46),
    africa-Swaziland(47),
    africa-Tanzania(48),
    africa-Togo(49),
    africa-Tunisia(50),
    africa-Uganda(51),
    africa-Western-Sahara(52),
    africa-Zambia(53),
    africa-Zimbabwe(54),
    americas-Anguilla(55),
    americas-Antigua-Barbuda(56),
    americas-Argentina-EArgentina(57),
    americas-Argentina-MostLocations(58),
    americas-Argentina-Jujuy(59),
    americas-Argentina-Catamarca(60),
    americas-Argentina-Mendoza(61),
    americas-Aruba(62),
    americas-Bahamas(63),
    americas-Barbados(64),
    americas-Belize(65),
    americas-Bolivia(66),
    americas-Brazil-AtlanticIslands(67),
    americas-Brazil-AmapaEPara(68),
    americas-Brazil-NEBrazil(69),
    americas-Brazil-Pernambuco(70),
    americas-Brazil-Tocantins(71),
    americas-Brazil-AlagoasSergipe(72),
    americas-Brazil-SSEBrazil(73),
    americas-Brazil-MatoGrossoDoSul(74),
    americas-Brazil-WParaRondonia(75),
    americas-Brazil-Roraima(76),
    americas-Brazil-EAmazonas(77),
    americas-Brazil-WAmazonas(78),
    americas-Brazil-Acre(79),
    americas-Canada-NewfoundlandIsland(80),
    americas-Canada-AtlanTime-NovaScotia(81),
    americas-Canada-AtlanTime-ELabrador(82),
    americas-Canada-EastTime-OntarioMostlocation(83),
    americas-Canada-EastTime-ThunderBay(84),
    americas-Canada-EastStdTime-PangnirtungNunavut(85),
    americas-Canada-EastStdTime-EastNunavut(86),
    americas-Canada-EastStdTime-CenNunavut(87),
    americas-Canada-CenTime-ManitobaWestOntario(88),
    americas-Canada-CenTime-RainyRiver(89),
    americas-Canada-CenTime-WestNunavut(90),
    americas-Canada-CenStdTime-SaskatchewanMostlocation(91),
    americas-Canada-CenStdTime-SaskatchewanMidwest(92),
    americas-Canada-MountTime-AlbertaEastBritishColumbia(93),
    americas-Canada-MountTime-CentralNorthwestTerritories(94),
    americas-Canada-MountTime-WestNorthwestTerritories(95),
    americas-Canada-MountStdTime-DawsonCrkStJohnBritColumbia(96),
    americas-Canada-PacificTime-WestBritishColumbia(97),
    americas-Canada-PacificTime-SouthYukon(98),
    americas-Canada-PacificTime-NorthYukon(99),
    americas-CaymanIslands(100),
    americas-Chile-MostLocation(101),
    americas-Chile-EasterIsland(102),
    americas-Colombia(103),
    americas-CostaRica(104),
    americas-Cuba(105),
    americas-Dominica(106),
    americas-DominicanRepublic (107),
    americas-Ecuador(108),
    americas-ElSalvado(109),
    americas-FrenchGuiana(110),
    americas-Greenland-MostLocation(111),
    americas-Greenland-EastCoastNorthScoresbysund(112),
    americas-Greenland-ScoresbysundIttoqqortoormiit(113),
    americas-Greenland-ThulePituffik(114),
    americas-Grenada(115),
    americas-Guadeloupe(116),
    americas-Guatemala(117),
    americas-Guyana(118),
    americas-Haiti(119),
    americas-Honduras(120),
    americas-Jamaica(121),
    americas-Martinique(122),
    americas-Mexico-CentTime-Mostlocations(123),
    americas-Mexico-CentTime-QuintanaRoo(124),
    americas-Mexico-CentTime-CampecheYucatan(125),
    americas-Mexico-CTime-CoahuilaDurangoNuevoLeonTamaulipas(126),
    americas-Mexico-MountTime-SBajaNayaritSinaloa(127),
    americas-Mexico-MountTime-Chihuahua(128),
    americas-Mexico-MountStdTime-Sonora(129),
    americas-Mexico-PacificTime(130),
    americas-Montserrat(131),
    americas-NetherlandsAntilles(132),
    americas-Nicaragua(133),
    americas-Panama(134),
    americas-Paraguay(135),
    americas-Peru(136),
    americas-PuertoRico(137),
    americas-StKittsAndNevis(138),
    americas-StLucia(139),
    americas-StPierreAndMiquelon(140),
    americas-StVincent(141),
    americas-Suriname(142),
    americas-TrinidadAndTobago(143),
    americas-TurksAndCaicosIs(144),
    americas-USA-EastTime(145),
    americas-USA-EastTime-MichiganMostLocation(146),
    americas-USA-EastTime-KentuckyLouisvilleArea(147),
    americas-USA-EastTime-KentuckyWayneCounty(148),
    americas-USA-EastStdTime-IndianaMostLocations(149),
    americas-USA-EastStdTime-IndianaCrawfordCounty(150),
    americas-USA-EastStdTime-IndianaStarkeCounty(151),
    americas-USA-EastStdTime-IndianaSwitzerlandCounty(152),
    americas-USA-CentTime(153),
    americas-USA-CentTime-MichiganWisconsinborder(154),
    americas-USA-CentTime-NorthDakotaOliverCounty(155),
    americas-USA-MountTime(156),
    americas-USA-MountTime-SouthIdahoAndEastOregon(157),
    americas-USA-MountTime-Navajo(158),
    americas-USA-MountStdTime-Arizona(159),
    americas-USA-PacificTime(160),
    americas-USA-AlaskaTime(161),
    americas-USA-AlaskaTime-AlaskaPanhandle(162),
    americas-USA-AlaskaTime-AlaskaPanhandleNeck(163),
    americas-USA-AlaskaTime-WestAlaska(164),
    americas-USA-AleutianIslands(165),
    americas-USA-Hawaii(166),
    americas-Uruguay(167),
    americas-Venezuela(168),
    americas-VirginIslands-UK(169),
    americas-VirginIslands-US(170),
    antarctica-McMurdoStationRossIsland(171),
    antarctica-Amundsen-ScottStationSouthPole(172),
    antarctica-PalmerStationAnversIsland(173),
    antarctica-MawsonStationHolmeBay(174),
    antarctica-DavisStationVestfoldHills(175),
    antarctica-CaseyStationBaileyPeninsula(176),
    antarctica-VostokStationSMagneticPole(177),
    antarctica-Dumont-dUrvilleBaseTerreAdelie(178),
    antarctica-SyowaStationEOngulI(179),
    arcticOcean-Svalbard(180),
    arcticOcean-JanMayen(181),
    asia-Afghanistan(182),
    asia-Armenia(183),
    asia-Azerbaijan(184),
    asia-Bahrain(185),
    asia-Bangladesh(186),
    asia-Bhutan(187),
    asia-Brunei(188),
    asia-Cambodia(189),
    asia-China-EastChinaBeijingGuangdongShanghai(190),
    asia-China-Heilongjiang(191),
    asia-China-CentralChinaGansuGuizhouSichuanYunnan(192),
    asia-China-TibetmostofXinjiangUyghur(193),
    asia-China-SouthwestXinjiangUyghur(194),
    asia-Cyprus(195),
    asia-EastTimor(196),
    asia-Georgia(197),
    asia-HongKong(198),
    asia-India(199),
    asia-Indonesia-JavaAndSumatra(200),
    asia-Indonesia-WestCentralBorneo(201),
    asia-Indonesia-EstSthBorneoCelebsBaliNusaTengaraWstTimor(202),
    asia-Indonesia-IrianJayaAndMoluccas(203),
    asia-Iran(204),
    asia-Iraq(205),
    asia-Israel(206),
    asia-Japan(207),
    asia-Jordan(208),
    asia-Kazakhstan-MostLocations(209),
    asia-Kazakhstan-QyzylordaKyzylorda(210),
    asia-Kazakhstan-Aqtobe(211),
    asia-Kazakhstan-AtyrauMangghystau(212),
    asia-Kazakhstan-WestKazakhstan(213),
    asia-Korea-North(214),
    asia-Korea-South(215),
    asia-Kuwait(216),
    asia-Kyrgyzstan(217),
    asia-Laos(218),
    asia-Lebanon(219),
    asia-Macau(220),
    asia-Malaysia-PeninsularMalaysia(221),
    asia-Malaysia-SabahSarawak(222),
    asia-Mongolia-MostLocations(223),
    asia-Mongolia-BayanOlgiyGoviAltaiHovdUvsZavkhan(224),
    asia-Mongolia-DornodSukhbaatar(225),
    asia-Myanmar(226),
    asia-Nepal(227),
    asia-Oman(228),
    asia-Pakistan(229),
    asia-Palestine(230),
    asia-Philippines(231),
    asia-Qatar(232),
    asia-Russia-Moscow-01Kaliningrad(233),
    asia-Russia-Moscow00WestRussia(234),
    asia-Russia-Moscow01CaspianSea(235),
    asia-Russia-Moscow02Urals(236),
    asia-Russia-Moscow03WestSiberia(237),
    asia-Russia-Moscow03Novosibirsk(238),
    asia-Russia-Moscow04YeniseiRiver(239),
    asia-Russia-Moscow05LakeBaikal(240),
    asia-Russia-Moscow06LenaRiver(241),
    asia-Russia-Moscow07AmurRiver(242),
    asia-Russia-Moscow07SakhalinIsland(243),
    asia-Russia-Moscow08Magadan(244),
    asia-Russia-Moscow09Kamchatka(245),
    asia-Russia-Moscow10BeringSea(246),
    asia-SaudiArabia(247),
    asia-Singapore(248),
    asia-SriLanka(249),
    asia-Syria(250),
    asia-Taiwan(251),
    asia-Tajikistan(252),
    asia-Thailand(253),
    asia-Turkmenistan(254),
    asia-UnitedArabEmirates(255),
    asia-Uzbekistan-WestUzbekistan(256),
    asia-Uzbekistan-EastUzbekistan(257),
    asia-Vietnam(258),
    asia-Yemen(259),
    atlanticOcean-Bermuda(260),
    atlanticOcean-CapeVerde(261),
    atlanticOcean-FaeroeIslands(262),
    atlanticOcean-FalklandIslands(263),
    atlanticOcean-Iceland(264),
    atlanticOcean-Portugal-Mainland(265),
    atlanticOcean-Portugal-MadeiraIslands(266),
    atlanticOcean-Portugal-Azores(267),
    atlanticOcean-SouthGeorgia-SouthSandwichIslands(268),
    atlanticOcean-StHelena(269),
    atlanticOcean-Svalbard-JanMayen(270),
    australia-LordHoweIsland(271),
    australia-Tasmania(272),
    australia-Victoria(273),
    australia-NewSouthWales-MostLocations(274),
    australia-NewSouthWales-Yancowinna(275),
    australia-Queensland-MostLocations(276),
    australia-Queensland-HolidayIslands(277),
    australia-SouthAustralia(278),
    australia-NorthernTerritory(279),
    australia-WesternAustralia(280),
    europe-Albania(281),
    europe-Andorra(282),
    europe-Austria(283),
    europe-Belarus(284),
    europe-Belgium(285),
    europe-BosniaHerzegovina(286),
    europe-Britain-UKGreatBritain(287),
    europe-Britain-UKNorthernIreland(288),
    europe-Bulgaria(289),
    europe-Croatia(290),
    europe-CzechRepublic(291),
    europe-Denmark(292),
    europe-Estonia(293),
    europe-Finland(294),
    europe-France(295),
    europe-Germany(296),
    europe-Gibraltar(297),
    europe-Greece(298),
    europe-Hungary(299),
    europe-Ireland(300),
    europe-Italy(301),
    europe-Latvia(302),
    europe-Liechtenstein(303),
    europe-Lithuania(304),
    europe-Luxembourg(305),
    europe-Macedonia(306),
    europe-Malta(307),
    europe-Moldova(308),
    europe-Monaco(309),
    europe-Netherlands(310),
    europe-Norway(311),
    europe-Poland(312),
    europe-Portugal-Mainland(313),
    europe-Portugal-MadeiraIslands(314),
    europe-Portugal-Azores(315),
    europe-Romania(316),
    europe-Russia-Moscow-01Kaliningrad(317),
    europe-Russia-Moscow00WestRussia(318),
    europe-Russia-Moscow01CaspianSea(319),
    europe-Russia-Moscow02Urals(320),
    europe-Russia-Moscow03WestSiberia(321),
    europe-Russia-Moscow03Novosibirsk(322),
    europe-Russia-Moscow04YeniseiRiver(323),
    europe-Russia-Moscow05LakeBaikal(324),
    europe-Russia-Moscow06LenaRiver(325),
    europe-Russia-Moscow07AmurRiver(326),
    europe-Russia-Moscow07SakhalinIsland(327),
    europe-Russia-Moscow08Magadan(328),
    europe-Russia-Moscow09Kamchatka(329),
    europe-Russia-Moscow10BeringSea(330),
    europe-SanMarino(331),
    europe-Slovakia(332),
    europe-Slovenia(333),
    europe-Sweden(334),
    europe-Switzerland(335),
    europe-Turkey(336),
    europe-Ukraine-MostLocations(337),
    europe-Ukraine-Ruthenia(338),
    europe-Ukraine-Zaporozhye-ELugansk(339),
    europe-Ukraine-CentralCrimea(340),
    europe-VaticanCity(341),
    europe-Yugoslavia(342),
    indianOcean-BritishIndianOceanTerritory(343),
    indianOcean-ChristmasIsland(344),
    indianOcean-CocosOrKeelingIslands(345),
    indianOcean-Comoros(346),
    indianOcean-FrenchSouthernAndAntarcticLands(347),
    indianOcean-Madagascar(348),
    indianOcean-Maldives(349),
    indianOcean-Mauritius(350),
    indianOcean-Mayotte(351),
    indianOcean-Reunion(352),
    indianOcean-Seychelles(353),
    pacificOcean-Chile-MostLocations(354),
    pacificOcean-Chile-EasterIslandSalayGomez(355),
    pacificOcean-CookIslands(356),
    pacificOcean-Ecuador(357),
    pacificOcean-Fiji(358),
    pacificOcean-FrenchPolynesia-SocietyIslands(359),
    pacificOcean-FrenchPolynesia-MarquesasIslands(360),
    pacificOcean-FrenchPolynesia-GambierIslands(361),
    pacificOcean-Guam(362),
    pacificOcean-Kiribati-GilbertIslands(363),
    pacificOcean-Kiribati-PhoenixIslands(364),
    pacificOcean-Kiribati-LineIslands(365),
    pacificOcean-MarshallIslands-MostLocations(366),
    pacificOcean-MarshallIslands-Kwajalein(367),
    pacificOcean-Micronesia-Yap(368),
    pacificOcean-Micronesia-TrukOrChuuk(369),
    pacificOcean-Micronesia-PonapeOrPohnpei(370),
    pacificOcean-Micronesia-Kosrae(371),
    pacificOcean-Nauru(372),
    pacificOcean-NewCaledonia(373),
    pacificOcean-NewZealand-MostLocations(374),
    pacificOcean-NewZealand-ChathamIslands(375),
    pacificOcean-Niue(376),
    pacificOcean-NorfolkIsland(377),
    pacificOcean-NorthernMarianaIslands(378),
    pacificOcean-Palau(379),
    pacificOcean-PapuaNewGuinea(380),
    pacificOcean-Pitcairn(381),
    pacificOcean-SamoaAmerican(382),
    pacificOcean-SamoaWestern(383),
    pacificOcean-SolomonIslands(384),
    pacificOcean-Tokelau(385),
    pacificOcean-Tonga(386),
    pacificOcean-Tuvalu(387),
    pacificOceanUSA-EastTime(388),
    pacificOceanUSA-EastTime-MichiganMostLocations(389),
    pacificOceanUSA-EastTime-KentuckyLouisvilleArea(390),
    pacificOceanUSA-EastTime-KentuckyWayneCounty(391),
    pacificOceanUSA-EastStdTime-IndianaMostLocations(392),
    pacificOceanUSA-EastStdTime-IndianaCrawfordCounty(393),
    pacificOceanUSA-EastStdTime-IndianaStarkeCounty(394),
    pacificOceanUSA-EastStdTime-IndianaSwitzerlandCounty(395),
    pacificOceanUSA-CentTime(396),
    pacificOceanUSA-CentTime-MichiganWisconsinborder(397),
    pacificOceanUSA-CentTime-NorthDakotaOliverCounty(398),
    pacificOceanUSA-MountTime(399),
    pacificOceanUSA-MountTime-SouthIdahoAndEastOregon(400),
    pacificOceanUSA-MountTime-Navajo(401),
    pacificOceanUSA-MountStdTime-Arizona(402),
    pacificOceanUSA-PacificTime(403),
    pacificOceanUSA-AlaskaTime(404),
    pacificOceanUSA-AlaskaTime-AlaskaPanhandle(405),
    pacificOceanUSA-AlaskaTime-AlaskaPanhandleNeck(406),
    pacificOceanUSA-AlaskaTime-WestAlaska(407),
    pacificOceanUSA-AleutianIslands(408),
    pacificOceanUSA-Hawaii(409),
    pacificOcean-USMinorOutlyingIslands-JohnstonAtoll(410),
    pacificOcean-USMinorOutlyingIslands-MidwayIslands(411),
    pacificOcean-USMinorOutlyingIslands-WakeIsland(412),
    pacificOcean-Vanuatu(413),
    pacificOcean-WallisAndFutuna(414)
	}
    MAX-ACCESS read-only
    STATUS  current
    DESCRIPTION
        "The daylight savings location."
    ::= { agSystem 55 }

agNewDaylightSavings   OBJECT-TYPE
    SYNTAX  INTEGER  {
    none(0),
    africa-Algeria(1),
    africa-Angola(2),
    africa-Benin(3),
    africa-Botswana(4),
    africa-Burkina-Faso(5),
    africa-Burundi(6),
    africa-Cameroon(7),
    africa-Central-African-Rep(8),
    africa-Chad(9),
    africa-Congo-WestDemRepCongo(10),
    africa-Congo-EastDemRepCongo(11),
    africa-Congo-Rep(12),
    africa-Cote-dIvoire(13),
    africa-Djibouti(14),
    africa-Egypt(15),
    africa-Equatorial-Guinea(16),
    africa-Eritrea(17),
    africa-Ethiopia(18),
    africa-Gabon(19),
    africa-Gambia(20),
    africa-Ghana(21),
    africa-Guinea(22),
    africa-Guinea-Bissau(23),
    africa-Kenya(24),
    africa-Lesotho(25),
    africa-Liberia(26),
    africa-Libya(27),
    africa-Malawi(28),
    africa-Mali-SouthWestMali(29),
    africa-Mali-NorthEastMali(30),
    africa-Mauritania(31),
    africa-Morocco(32),
    africa-Mozambique(33),
    africa-Namibia(34),
    africa-Niger(35),
    africa-Nigeria(36),
    africa-Rwanda(37),
    africa-SaoTome-And-Principe(38),
    africa-Senegal(39),
    africa-SierraLeone(40),
    africa-Somalia(41),
    africa-SouthAfrica(42),
    europe-Spain-Mainland(43),
    africa-Spain-CeutaMelilla(44),
    atlanticOcean-Spain-CanaryIslands(45),
    africa-Sudan(46),
    africa-Swaziland(47),
    africa-Tanzania(48),
    africa-Togo(49),
    africa-Tunisia(50),
    africa-Uganda(51),
    africa-Western-Sahara(52),
    africa-Zambia(53),
    africa-Zimbabwe(54),
    americas-Anguilla(55),
    americas-Antigua-Barbuda(56),
    americas-Argentina-EArgentina(57),
    americas-Argentina-MostLocations(58),
    americas-Argentina-Jujuy(59),
    americas-Argentina-Catamarca(60),
    americas-Argentina-Mendoza(61),
    americas-Aruba(62),
    americas-Bahamas(63),
    americas-Barbados(64),
    americas-Belize(65),
    americas-Bolivia(66),
    americas-Brazil-AtlanticIslands(67),
    americas-Brazil-AmapaEPara(68),
    americas-Brazil-NEBrazil(69),
    americas-Brazil-Pernambuco(70),
    americas-Brazil-Tocantins(71),
    americas-Brazil-AlagoasSergipe(72),
    americas-Brazil-SSEBrazil(73),
    americas-Brazil-MatoGrossoDoSul(74),
    americas-Brazil-WParaRondonia(75),
    americas-Brazil-Roraima(76),
    americas-Brazil-EAmazonas(77),
    americas-Brazil-WAmazonas(78),
    americas-Brazil-Acre(79),
    americas-Canada-NewfoundlandIsland(80),
    americas-Canada-AtlanTime-NovaScotia(81),
    americas-Canada-AtlanTime-ELabrador(82),
    americas-Canada-EastTime-OntarioMostlocation(83),
    americas-Canada-EastTime-ThunderBay(84),
    americas-Canada-EastStdTime-PangnirtungNunavut(85),
    americas-Canada-EastStdTime-EastNunavut(86),
    americas-Canada-EastStdTime-CenNunavut(87),
    americas-Canada-CenTime-ManitobaWestOntario(88),
    americas-Canada-CenTime-RainyRiver(89),
    americas-Canada-CenTime-WestNunavut(90),
    americas-Canada-CenStdTime-SaskatchewanMostlocation(91),
    americas-Canada-CenStdTime-SaskatchewanMidwest(92),
    americas-Canada-MountTime-AlbertaEastBritishColumbia(93),
    americas-Canada-MountTime-CentralNorthwestTerritories(94),
    americas-Canada-MountTime-WestNorthwestTerritories(95),
    americas-Canada-MountStdTime-DawsonCrkStJohnBritColumbia(96),
    americas-Canada-PacificTime-WestBritishColumbia(97),
    americas-Canada-PacificTime-SouthYukon(98),
    americas-Canada-PacificTime-NorthYukon(99),
    americas-CaymanIslands(100),
    americas-Chile-MostLocation(101),
    americas-Chile-EasterIsland(102),
    americas-Colombia(103),
    americas-CostaRica(104),
    americas-Cuba(105),
    americas-Dominica(106),
    americas-DominicanRepublic (107),
    americas-Ecuador(108),
    americas-ElSalvado(109),
    americas-FrenchGuiana(110),
    americas-Greenland-MostLocation(111),
    americas-Greenland-EastCoastNorthScoresbysund(112),
    americas-Greenland-ScoresbysundIttoqqortoormiit(113),
    americas-Greenland-ThulePituffik(114),
    americas-Grenada(115),
    americas-Guadeloupe(116),
    americas-Guatemala(117),
    americas-Guyana(118),
    americas-Haiti(119),
    americas-Honduras(120),
    americas-Jamaica(121),
    americas-Martinique(122),
    americas-Mexico-CentTime-Mostlocations(123),
    americas-Mexico-CentTime-QuintanaRoo(124),
    americas-Mexico-CentTime-CampecheYucatan(125),
    americas-Mexico-CTime-CoahuilaDurangoNuevoLeonTamaulipas(126),
    americas-Mexico-MountTime-SBajaNayaritSinaloa(127),
    americas-Mexico-MountTime-Chihuahua(128),
    americas-Mexico-MountStdTime-Sonora(129),
    americas-Mexico-PacificTime(130),
    americas-Montserrat(131),
    americas-NetherlandsAntilles(132),
    americas-Nicaragua(133),
    americas-Panama(134),
    americas-Paraguay(135),
    americas-Peru(136),
    americas-PuertoRico(137),
    americas-StKittsAndNevis(138),
    americas-StLucia(139),
    americas-StPierreAndMiquelon(140),
    americas-StVincent(141),
    americas-Suriname(142),
    americas-TrinidadAndTobago(143),
    americas-TurksAndCaicosIs(144),
    americas-USA-EastTime(145),
    americas-USA-EastTime-MichiganMostLocation(146),
    americas-USA-EastTime-KentuckyLouisvilleArea(147),
    americas-USA-EastTime-KentuckyWayneCounty(148),
    americas-USA-EastStdTime-IndianaMostLocations(149),
    americas-USA-EastStdTime-IndianaCrawfordCounty(150),
    americas-USA-EastStdTime-IndianaStarkeCounty(151),
    americas-USA-EastStdTime-IndianaSwitzerlandCounty(152),
    americas-USA-CentTime(153),
    americas-USA-CentTime-MichiganWisconsinborder(154),
    americas-USA-CentTime-NorthDakotaOliverCounty(155),
    americas-USA-MountTime(156),
    americas-USA-MountTime-SouthIdahoAndEastOregon(157),
    americas-USA-MountTime-Navajo(158),
    americas-USA-MountStdTime-Arizona(159),
    americas-USA-PacificTime(160),
    americas-USA-AlaskaTime(161),
    americas-USA-AlaskaTime-AlaskaPanhandle(162),
    americas-USA-AlaskaTime-AlaskaPanhandleNeck(163),
    americas-USA-AlaskaTime-WestAlaska(164),
    americas-USA-AleutianIslands(165),
    americas-USA-Hawaii(166),
    americas-Uruguay(167),
    americas-Venezuela(168),
    americas-VirginIslands-UK(169),
    americas-VirginIslands-US(170),
    antarctica-McMurdoStationRossIsland(171),
    antarctica-Amundsen-ScottStationSouthPole(172),
    antarctica-PalmerStationAnversIsland(173),
    antarctica-MawsonStationHolmeBay(174),
    antarctica-DavisStationVestfoldHills(175),
    antarctica-CaseyStationBaileyPeninsula(176),
    antarctica-VostokStationSMagneticPole(177),
    antarctica-Dumont-dUrvilleBaseTerreAdelie(178),
    antarctica-SyowaStationEOngulI(179),
    arcticOcean-Svalbard(180),
    arcticOcean-JanMayen(181),
    asia-Afghanistan(182),
    asia-Armenia(183),
    asia-Azerbaijan(184),
    asia-Bahrain(185),
    asia-Bangladesh(186),
    asia-Bhutan(187),
    asia-Brunei(188),
    asia-Cambodia(189),
    asia-China-EastChinaBeijingGuangdongShanghai(190),
    asia-China-Heilongjiang(191),
    asia-China-CentralChinaGansuGuizhouSichuanYunnan(192),
    asia-China-TibetmostofXinjiangUyghur(193),
    asia-China-SouthwestXinjiangUyghur(194),
    asia-Cyprus(195),
    asia-EastTimor(196),
    asia-Georgia(197),
    asia-HongKong(198),
    asia-India(199),
    asia-Indonesia-JavaAndSumatra(200),
    asia-Indonesia-WestCentralBorneo(201),
    asia-Indonesia-EstSthBorneoCelebsBaliNusaTengaraWstTimor(202),
    asia-Indonesia-IrianJayaAndMoluccas(203),
    asia-Iran(204),
    asia-Iraq(205),
    asia-Israel(206),
    asia-Japan(207),
    asia-Jordan(208),
    asia-Kazakhstan-MostLocations(209),
    asia-Kazakhstan-QyzylordaKyzylorda(210),
    asia-Kazakhstan-Aqtobe(211),
    asia-Kazakhstan-AtyrauMangghystau(212),
    asia-Kazakhstan-WestKazakhstan(213),
    asia-Korea-North(214),
    asia-Korea-South(215),
    asia-Kuwait(216),
    asia-Kyrgyzstan(217),
    asia-Laos(218),
    asia-Lebanon(219),
    asia-Macau(220),
    asia-Malaysia-PeninsularMalaysia(221),
    asia-Malaysia-SabahSarawak(222),
    asia-Mongolia-MostLocations(223),
    asia-Mongolia-BayanOlgiyGoviAltaiHovdUvsZavkhan(224),
    asia-Mongolia-DornodSukhbaatar(225),
    asia-Myanmar(226),
    asia-Nepal(227),
    asia-Oman(228),
    asia-Pakistan(229),
    asia-Palestine(230),
    asia-Philippines(231),
    asia-Qatar(232),
    asia-Russia-Moscow-01Kaliningrad(233),
    asia-Russia-Moscow00WestRussia(234),
    asia-Russia-Moscow01CaspianSea(235),
    asia-Russia-Moscow02Urals(236),
    asia-Russia-Moscow03WestSiberia(237),
    asia-Russia-Moscow03Novosibirsk(238),
    asia-Russia-Moscow04YeniseiRiver(239),
    asia-Russia-Moscow05LakeBaikal(240),
    asia-Russia-Moscow06LenaRiver(241),
    asia-Russia-Moscow07AmurRiver(242),
    asia-Russia-Moscow07SakhalinIsland(243),
    asia-Russia-Moscow08Magadan(244),
    asia-Russia-Moscow09Kamchatka(245),
    asia-Russia-Moscow10BeringSea(246),
    asia-SaudiArabia(247),
    asia-Singapore(248),
    asia-SriLanka(249),
    asia-Syria(250),
    asia-Taiwan(251),
    asia-Tajikistan(252),
    asia-Thailand(253),
    asia-Turkmenistan(254),
    asia-UnitedArabEmirates(255),
    asia-Uzbekistan-WestUzbekistan(256),
    asia-Uzbekistan-EastUzbekistan(257),
    asia-Vietnam(258),
    asia-Yemen(259),
    atlanticOcean-Bermuda(260),
    atlanticOcean-CapeVerde(261),
    atlanticOcean-FaeroeIslands(262),
    atlanticOcean-FalklandIslands(263),
    atlanticOcean-Iceland(264),
    atlanticOcean-Portugal-Mainland(265),
    atlanticOcean-Portugal-MadeiraIslands(266),
    atlanticOcean-Portugal-Azores(267),
    atlanticOcean-SouthGeorgia-SouthSandwichIslands(268),
    atlanticOcean-StHelena(269),
    atlanticOcean-Svalbard-JanMayen(270),
    australia-LordHoweIsland(271),
    australia-Tasmania(272),
    australia-Victoria(273),
    australia-NewSouthWales-MostLocations(274),
    australia-NewSouthWales-Yancowinna(275),
    australia-Queensland-MostLocations(276),
    australia-Queensland-HolidayIslands(277),
    australia-SouthAustralia(278),
    australia-NorthernTerritory(279),
    australia-WesternAustralia(280),
    europe-Albania(281),
    europe-Andorra(282),
    europe-Austria(283),
    europe-Belarus(284),
    europe-Belgium(285),
    europe-BosniaHerzegovina(286),
    europe-Britain-UKGreatBritain(287),
    europe-Britain-UKNorthernIreland(288),
    europe-Bulgaria(289),
    europe-Croatia(290),
    europe-CzechRepublic(291),
    europe-Denmark(292),
    europe-Estonia(293),
    europe-Finland(294),
    europe-France(295),
    europe-Germany(296),
    europe-Gibraltar(297),
    europe-Greece(298),
    europe-Hungary(299),
    europe-Ireland(300),
    europe-Italy(301),
    europe-Latvia(302),
    europe-Liechtenstein(303),
    europe-Lithuania(304),
    europe-Luxembourg(305),
    europe-Macedonia(306),
    europe-Malta(307),
    europe-Moldova(308),
    europe-Monaco(309),
    europe-Netherlands(310),
    europe-Norway(311),
    europe-Poland(312),
    europe-Portugal-Mainland(313),
    europe-Portugal-MadeiraIslands(314),
    europe-Portugal-Azores(315),
    europe-Romania(316),
    europe-Russia-Moscow-01Kaliningrad(317),
    europe-Russia-Moscow00WestRussia(318),
    europe-Russia-Moscow01CaspianSea(319),
    europe-Russia-Moscow02Urals(320),
    europe-Russia-Moscow03WestSiberia(321),
    europe-Russia-Moscow03Novosibirsk(322),
    europe-Russia-Moscow04YeniseiRiver(323),
    europe-Russia-Moscow05LakeBaikal(324),
    europe-Russia-Moscow06LenaRiver(325),
    europe-Russia-Moscow07AmurRiver(326),
    europe-Russia-Moscow07SakhalinIsland(327),
    europe-Russia-Moscow08Magadan(328),
    europe-Russia-Moscow09Kamchatka(329),
    europe-Russia-Moscow10BeringSea(330),
    europe-SanMarino(331),
    europe-Slovakia(332),
    europe-Slovenia(333),
    europe-Sweden(334),
    europe-Switzerland(335),
    europe-Turkey(336),
    europe-Ukraine-MostLocations(337),
    europe-Ukraine-Ruthenia(338),
    europe-Ukraine-Zaporozhye-ELugansk(339),
    europe-Ukraine-CentralCrimea(340),
    europe-VaticanCity(341),
    europe-Yugoslavia(342),
    indianOcean-BritishIndianOceanTerritory(343),
    indianOcean-ChristmasIsland(344),
    indianOcean-CocosOrKeelingIslands(345),
    indianOcean-Comoros(346),
    indianOcean-FrenchSouthernAndAntarcticLands(347),
    indianOcean-Madagascar(348),
    indianOcean-Maldives(349),
    indianOcean-Mauritius(350),
    indianOcean-Mayotte(351),
    indianOcean-Reunion(352),
    indianOcean-Seychelles(353),
    pacificOcean-Chile-MostLocations(354),
    pacificOcean-Chile-EasterIslandSalayGomez(355),
    pacificOcean-CookIslands(356),
    pacificOcean-Ecuador(357),
    pacificOcean-Fiji(358),
    pacificOcean-FrenchPolynesia-SocietyIslands(359),
    pacificOcean-FrenchPolynesia-MarquesasIslands(360),
    pacificOcean-FrenchPolynesia-GambierIslands(361),
    pacificOcean-Guam(362),
    pacificOcean-Kiribati-GilbertIslands(363),
    pacificOcean-Kiribati-PhoenixIslands(364),
    pacificOcean-Kiribati-LineIslands(365),
    pacificOcean-MarshallIslands-MostLocations(366),
    pacificOcean-MarshallIslands-Kwajalein(367),
    pacificOcean-Micronesia-Yap(368),
    pacificOcean-Micronesia-TrukOrChuuk(369),
    pacificOcean-Micronesia-PonapeOrPohnpei(370),
    pacificOcean-Micronesia-Kosrae(371),
    pacificOcean-Nauru(372),
    pacificOcean-NewCaledonia(373),
    pacificOcean-NewZealand-MostLocations(374),
    pacificOcean-NewZealand-ChathamIslands(375),
    pacificOcean-Niue(376),
    pacificOcean-NorfolkIsland(377),
    pacificOcean-NorthernMarianaIslands(378),
    pacificOcean-Palau(379),
    pacificOcean-PapuaNewGuinea(380),
    pacificOcean-Pitcairn(381),
    pacificOcean-SamoaAmerican(382),
    pacificOcean-SamoaWestern(383),
    pacificOcean-SolomonIslands(384),
    pacificOcean-Tokelau(385),
    pacificOcean-Tonga(386),
    pacificOcean-Tuvalu(387),
    pacificOceanUSA-EastTime(388),
    pacificOceanUSA-EastTime-MichiganMostLocations(389),
    pacificOceanUSA-EastTime-KentuckyLouisvilleArea(390),
    pacificOceanUSA-EastTime-KentuckyWayneCounty(391),
    pacificOceanUSA-EastStdTime-IndianaMostLocations(392),
    pacificOceanUSA-EastStdTime-IndianaCrawfordCounty(393),
    pacificOceanUSA-EastStdTime-IndianaStarkeCounty(394),
    pacificOceanUSA-EastStdTime-IndianaSwitzerlandCounty(395),
    pacificOceanUSA-CentTime(396),
    pacificOceanUSA-CentTime-MichiganWisconsinborder(397),
    pacificOceanUSA-CentTime-NorthDakotaOliverCounty(398),
    pacificOceanUSA-MountTime(399),
    pacificOceanUSA-MountTime-SouthIdahoAndEastOregon(400),
    pacificOceanUSA-MountTime-Navajo(401),
    pacificOceanUSA-MountStdTime-Arizona(402),
    pacificOceanUSA-PacificTime(403),
    pacificOceanUSA-AlaskaTime(404),
    pacificOceanUSA-AlaskaTime-AlaskaPanhandle(405),
    pacificOceanUSA-AlaskaTime-AlaskaPanhandleNeck(406),
    pacificOceanUSA-AlaskaTime-WestAlaska(407),
    pacificOceanUSA-AleutianIslands(408),
    pacificOceanUSA-Hawaii(409),
    pacificOcean-USMinorOutlyingIslands-JohnstonAtoll(410),
    pacificOcean-USMinorOutlyingIslands-MidwayIslands(411),
    pacificOcean-USMinorOutlyingIslands-WakeIsland(412),
    pacificOcean-Vanuatu(413),
    pacificOcean-WallisAndFutuna(414)
	}
    MAX-ACCESS read-write
    STATUS  current
    DESCRIPTION
        "The daylight savings location."
    ::= { agSystem 56 }

agCurCfgIdleCLITimeout OBJECT-TYPE
    SYNTAX  INTEGER (1..10080)
    MAX-ACCESS  read-only
    STATUS  current
    DESCRIPTION
        "Set idle CLI sessions timeout."
    ::= { agSystem 57 }

agNewCfgIdleCLITimeout OBJECT-TYPE
    SYNTAX INTEGER (1..10080)
    MAX-ACCESS  read-write
    STATUS  current
    DESCRIPTION
        "Set idle CLI sessions timeout."
        ::= { agSystem 58 }

agCurCfgXMLCfgServerPort OBJECT-TYPE
    SYNTAX  INTEGER (1..65535)
    MAX-ACCESS  read-only
    STATUS  current
    DESCRIPTION
    "The TCP port number that the XML config server is listening to
    in the current_configuration block. If HTTPS is also enabled then
    the port numbers should be the same"
    ::= { agSystem 59 }

agNewCfgXMLCfgServerPort OBJECT-TYPE
    SYNTAX  INTEGER (1..65535)
    MAX-ACCESS  read-write
    STATUS  current
    DESCRIPTION
    "The TCP port number that the XML config server is listening to
    in the new_configuration block. If HTTPS is also enabled then
    the port numbers should be the same"
    ::= { agSystem 60 }

agCurCfgLoginNotice OBJECT-TYPE
    SYNTAX  DisplayString (SIZE(0..255))
    MAX-ACCESS  read-only
    STATUS  current
    DESCRIPTION
        "The user defined login notice."
    ::= { agSystem 75 }

agNewCfgLoginNotice OBJECT-TYPE
    SYNTAX  DisplayString (SIZE(0..255))
    MAX-ACCESS  read-write
    STATUS  current
    DESCRIPTION
        "The user defined login notice."
    ::= { agSystem 76 }

agPlatformIdentifier OBJECT-TYPE
    SYNTAX  DisplayString (SIZE(0..255))
    MAX-ACCESS  read-only
    STATUS  current
    DESCRIPTION
        "An administratively-assigned value that identifies managed device platform."
    ::= { agSystem 77 }

agFormFactor OBJECT-TYPE
    SYNTAX  DisplayString (SIZE(0..255))
    MAX-ACCESS  read-only
    STATUS  current
    DESCRIPTION
        "An administratively-assigned value that identifies managed device form-factor."
    ::= { agSystem 78 }


agCurCfgTputInterval OBJECT-TYPE
    SYNTAX  INTEGER (1..60)
    MAX-ACCESS  read-only
    STATUS  current
    DESCRIPTION
        "Set throughput interval."
    ::= { agSystem 62 }

agNewCfgTputInterval OBJECT-TYPE
    SYNTAX INTEGER (1..60)
    MAX-ACCESS  read-write
    STATUS  current
    DESCRIPTION
        "Set throughput interval."
    ::= { agSystem 63 }

agCurCfgTputThreshold OBJECT-TYPE
    SYNTAX  INTEGER (0..99)
    MAX-ACCESS  read-only
    STATUS  current
    DESCRIPTION
        "Set throughput threshold."
    ::= { agSystem 64 }

agNewCfgTputThreshold OBJECT-TYPE
    SYNTAX INTEGER (0..99)
    MAX-ACCESS  read-write
    STATUS  current
    DESCRIPTION
        "Set throughput threshold."
    ::= { agSystem 65 }


agMgmtGlobalState OBJECT-TYPE
    SYNTAX  INTEGER {
        disabled(1),
        enabled(2)
        }
    MAX-ACCESS  read-write
    STATUS  current
    DESCRIPTION
        "This is an action object to globally enable or disable management port access on port 6."
    ::= { agSystem 66 }


agCurCfgBootVAID OBJECT-TYPE
    SYNTAX  INTEGER (1..1024)
    MAX-ACCESS  read-only
    STATUS  current
    DESCRIPTION
        "Alteon unique VA identifier is used to set its traffic virtual MAC."
    ::= { agSystem 67 }

agNewCfgCfgBootVAID OBJECT-TYPE
    SYNTAX INTEGER (1..1024)
    MAX-ACCESS  read-write
    STATUS  current
    DESCRIPTION
        "Alteon unique VA identifier is used to set its traffic virtual MAC.
        To avoid MAC collisions, it is required to set a unique identifier on each VA on a network.
        SET will fail if the old_vaid is same as new_vaid."
    ::= { agSystem 68 }

agCurCfgPrompt OBJECT-TYPE
    SYNTAX  INTEGER {
        enabled(1),
        disabled(2)
        }
    MAX-ACCESS  read-only
    STATUS  current
    DESCRIPTION
        "Enable or disable the hostname display in CLI."
    ::= { agSystem 69 }

agNewCfgPrompt OBJECT-TYPE
    SYNTAX  INTEGER {
        enabled(1),
        disabled(2)
        }
    MAX-ACCESS  read-write
    STATUS  current
    DESCRIPTION
        "Standard(2) or Hostname(1) on CLI prompt."
    ::= { agSystem 70 }

-- Vision Driver file
agVisionDriverActiveName OBJECT-TYPE
    SYNTAX  DisplayString (SIZE(0..100))
    MAX-ACCESS  read-only
    STATUS  current
    DESCRIPTION
        "The name of the active vision driver stored on the device."
    ::= { agSystem 71 }

agVisionDriverRestoreFromBackup OBJECT-TYPE
    SYNTAX  INTEGER {
        activate(1)
        }
    MAX-ACCESS  read-write
    STATUS  current
    DESCRIPTION
        "Restores the backup vision driver."
    ::= { agSystem 72 }

agCurCfgHCTCPServState OBJECT-TYPE
    SYNTAX  INTEGER {
        enabled(1),
        disabled(2)
        }
    MAX-ACCESS  read-only
    STATUS  current
    DESCRIPTION
        "Enable or disable the TCP health services."
    ::= { agSystem 73 }

agNewCfgHCTCPServState OBJECT-TYPE
    SYNTAX  INTEGER {
        enabled(1),
        disabled(2)
        }
    MAX-ACCESS  read-write
    STATUS  current
    DESCRIPTION
        "Enable or disable the TCP health services."
    ::= { agSystem 74 }

agCfgHcTcpPortNxtIdx OBJECT-TYPE
    SYNTAX INTEGER (1..10)
    MAX-ACCESS read-only
    STATUS current
    DESCRIPTION
        "The next free TCP port index.It returns 0 when all 10 ports are configured."
    ::= { agSystem 79 }

agHcTcpPortTable  OBJECT IDENTIFIER ::= { agSystem 80 }

agCurCfgHcTcpPortTable OBJECT-TYPE
    SYNTAX  SEQUENCE OF AgCurCfgHcTcpPortTableEntry
    MAX-ACCESS  not-accessible
    STATUS  current
    DESCRIPTION
        "The table of TCP services listen for health check in the current config block."
    ::= { agHcTcpPortTable 1 }

agCurCfgHcTcpPortTableEntry OBJECT-TYPE
    SYNTAX  AgCurCfgHcTcpPortTableEntry
    MAX-ACCESS  not-accessible
    STATUS  current
    DESCRIPTION
        "A row in the table of TCP services listen for health check."
    INDEX { agCurCfgHcTcpPortIndx }
    ::= { agCurCfgHcTcpPortTable 1 }

AgCurCfgHcTcpPortTableEntry ::= SEQUENCE {
    agCurCfgHcTcpPortIndx         Integer32,
    agCurCfgHcTcpPortNum          INTEGER
    }

agCurCfgHcTcpPortIndx OBJECT-TYPE
    SYNTAX  Integer32 (1..10)
    MAX-ACCESS  read-only
    STATUS  current
    DESCRIPTION
        "The Health check TCP Services table index."
    ::= { agCurCfgHcTcpPortTableEntry 1 }


agCurCfgHcTcpPortNum OBJECT-TYPE
    SYNTAX  INTEGER (2..65535)
    MAX-ACCESS  read-only
    STATUS  current
    DESCRIPTION
        "The TCP Port number which listen for health check."
    ::= { agCurCfgHcTcpPortTableEntry 2 }

agNewCfgHcTcpPortTable OBJECT-TYPE
    SYNTAX  SEQUENCE OF AgNewCfgHcTcpPortTableEntry
    MAX-ACCESS  not-accessible
    STATUS  current
    DESCRIPTION
        "The table of TCP services listen for health check in the new config block."
    ::= { agHcTcpPortTable 2 }

agNewCfgHcTcpPortTableEntry OBJECT-TYPE
    SYNTAX  AgNewCfgHcTcpPortTableEntry
    MAX-ACCESS  not-accessible
    STATUS  current
    DESCRIPTION
        "A row in the table of TCP services listen for health check."
    INDEX   { agNewCfgHcTcpPortIndx }
    ::= { agNewCfgHcTcpPortTable 1 }

AgNewCfgHcTcpPortTableEntry ::= SEQUENCE {
    agNewCfgHcTcpPortIndx         Integer32,
    agNewCfgHcTcpPortNum          INTEGER,
    agNewCfgHcTcpPortNumDelete    INTEGER
    }

agNewCfgHcTcpPortIndx OBJECT-TYPE
    SYNTAX  Integer32 (1..10)
    MAX-ACCESS  read-only
    STATUS  current
    DESCRIPTION
        "The Health check TCP Services table index."
    ::= { agNewCfgHcTcpPortTableEntry 1 }

agNewCfgHcTcpPortNum OBJECT-TYPE
    SYNTAX  INTEGER (2..65535)
    MAX-ACCESS  read-create
    STATUS  current
    DESCRIPTION
        "The TCP Port number which listen for health check."
    ::= { agNewCfgHcTcpPortTableEntry 2 }

agNewCfgHcTcpPortNumDelete OBJECT-TYPE
    SYNTAX  INTEGER {
        other(1),
        delete(2)
    }
    MAX-ACCESS  read-create
    STATUS  current
    DESCRIPTION
        "When set to the value of 2 (delete), the entire row is deleted.
         When read, other(1) is returned."
    ::= { agNewCfgHcTcpPortTableEntry 3 }

agImageTables   OBJECT IDENTIFIER ::= { agSystem 82 }

agImageAdcTable OBJECT-TYPE
    SYNTAX  SEQUENCE OF AgImageAdcEntry
    MAX-ACCESS  not-accessible
    STATUS  current
    DESCRIPTION
        "The table of ADC Software Images"
    ::= { agImageTables 1 }

agImageAdcEntry OBJECT-TYPE
    SYNTAX  AgImageAdcEntry
    MAX-ACCESS  not-accessible
    STATUS  current
    DESCRIPTION
        "A row in the ADC Software Image table"
    INDEX   { agImageAdcIndex }
    ::= { agImageAdcTable 1 }

AgImageAdcEntry ::= SEQUENCE {
    agImageAdcIndex              INTEGER,
    agImageAdcVersion            DisplayString,
    agImageAdcDownloadTime       DisplayString,
    agImageAdcAssignedVadcs      OCTET STRING,
    agImageAdcStatus             INTEGER,
    agImageAdcAdd                INTEGER,
    agImageAdcRemove             INTEGER,
    agImageAdcBmap               OCTET STRING,
    agImageAdcDefault            INTEGER,
    agImageAdcFvStatus           INTEGER
    }

agImageAdcIndex OBJECT-TYPE
    SYNTAX  INTEGER (1..10)
    MAX-ACCESS  read-only
    STATUS  current
    DESCRIPTION
        "The ADC Software Image ID"
    ::= { agImageAdcEntry 1 }

agImageAdcVersion OBJECT-TYPE
    SYNTAX  DisplayString (SIZE(0..128))
    MAX-ACCESS  read-only
    STATUS  current
    DESCRIPTION
        "The ADC Software Image Version"
    ::= { agImageAdcEntry 2 }

agImageAdcDownloadTime OBJECT-TYPE
    SYNTAX  DisplayString (SIZE(0..128))
    MAX-ACCESS  read-only
    STATUS  current
    DESCRIPTION
        "The ADC Software Image Download Time"
    ::= { agImageAdcEntry 3 }

agImageAdcAssignedVadcs OBJECT-TYPE
    SYNTAX  OCTET STRING
    MAX-ACCESS  read-write
    STATUS  current
    DESCRIPTION
        "List of vadc ids that will use this image on reboot"
    ::= { agImageAdcEntry 4 }

agImageAdcStatus OBJECT-TYPE
    SYNTAX  INTEGER {
        idle(0),
        active(1),
        assigned(2),
        incompatible(3)
        }
    MAX-ACCESS read-only
    STATUS  current
    DESCRIPTION
        "The ADC Software Image status"
    ::= { agImageAdcEntry 5 }

agImageAdcAdd OBJECT-TYPE
    SYNTAX  INTEGER (0..28)
    MAX-ACCESS read-write
    STATUS  current
    DESCRIPTION
        "Add VADc to use this Software Image (whwre 0 is No Operation)"
    ::= { agImageAdcEntry 6 }

agImageAdcRemove OBJECT-TYPE
    SYNTAX  INTEGER (0..28)
    MAX-ACCESS read-write
    STATUS  current
    DESCRIPTION
        "Remove VADc from using this Software Image (whwre 0 is No Operation)"
    ::= { agImageAdcEntry 7 }

agImageAdcBmap  OBJECT-TYPE
    SYNTAX  OCTET STRING
    MAX-ACCESS  read-only
    STATUS  current
    DESCRIPTION
        "Bitmap of vadc that will use this image on reboot"
    ::= { agImageAdcEntry 8 }

agImageAdcDefault OBJECT-TYPE
    SYNTAX  INTEGER {
        yes(1),
	no(2)
    }
    MAX-ACCESS  read-write
    STATUS  current
    DESCRIPTION
        "Set the image as default image."
    ::= { agImageAdcEntry 9 }

agImageAdcFvStatus OBJECT-TYPE
    SYNTAX  INTEGER {
        compressed(1),
	extracted(2),
	na(3)
    }
    MAX-ACCESS  read-only
    STATUS  current
    DESCRIPTION
        "Get the FastView Status."
    ::= { agImageAdcEntry 10}

agImageVxTable OBJECT-TYPE
    SYNTAX  SEQUENCE OF AgImageVxEntry
    MAX-ACCESS  not-accessible
    STATUS  current
    DESCRIPTION
        "The table of ADC-VX Software Images"
    ::= { agImageTables 2 }

agImageVxEntry OBJECT-TYPE
    SYNTAX  AgImageVxEntry
    MAX-ACCESS  not-accessible
    STATUS  current
    DESCRIPTION
        "A row in the ADC-VX Software Image table"
    INDEX   { agImageVxIndex }
    ::= { agImageVxTable 1 }

AgImageVxEntry ::= SEQUENCE {
    agImageVxIndex              INTEGER,
    agImageVxVersion            DisplayString,
    agImageVxDownloadTime       DisplayString,
    agImageVxStatus             INTEGER
    }

agImageVxIndex OBJECT-TYPE
    SYNTAX  INTEGER (1..4)
    MAX-ACCESS  read-only
    STATUS  current
    DESCRIPTION
        "The ADC-VX Software Image ID"
    ::= { agImageVxEntry 1 }

agImageVxVersion OBJECT-TYPE
    SYNTAX  DisplayString (SIZE(0..128))
    MAX-ACCESS  read-only
    STATUS  current
    DESCRIPTION
        "The ADC-VX Software Image Version"
    ::= { agImageVxEntry 2 }

agImageVxDownloadTime OBJECT-TYPE
    SYNTAX  DisplayString (SIZE(0..128))
    MAX-ACCESS  read-only
    STATUS  current
    DESCRIPTION
        "The ADC-VX Software Image Download Time"
    ::= { agImageVxEntry 3 }

agImageVxStatus OBJECT-TYPE
    SYNTAX  INTEGER {
        idle(0),
        active(1)
        }
    MAX-ACCESS read-only
    STATUS  current
    DESCRIPTION
        "The ADC-VX Software Image status"
    ::= { agImageVxEntry 4 }


agImageTrasform OBJECT-TYPE
    SYNTAX  INTEGER {
        no(0),
        yes(1)
        }
    MAX-ACCESS  read-write
    STATUS  current
    DESCRIPTION
        "The transformation action restarts the device to switch between
         ADC-VX and Standalone images.
         The following values should also be set for the transformation action.
          1) agImageTransformID for next boot image.
          2) agImageTransformBootOption for next configuration block."
    ::= { agSystem 83 }

agImageTransformBootOption OBJECT-TYPE
    SYNTAX  INTEGER {
        factoryDefault(1),
        lastKnownCfg(2),
        factoryWithMgmtPortCfg(3)
        }
    MAX-ACCESS  read-write
    STATUS  current
    DESCRIPTION
        "The configuration mode in which the transformed image should load.
         factoryDefault(1)         - factory default,
         lastKnownCfg(2)           - Active configuration,
         factoryWithMgmtPortCfg(3) - factory default with retaining current
                                     management port configuration.
         When read, value factoryDefault(1) is returned."
    ::= { agSystem 84 }

agImageTransformID OBJECT-TYPE
    SYNTAX  INTEGER (1..10)
    MAX-ACCESS  read-write
    STATUS  current
    DESCRIPTION
        "The Image ID of the image to load after transform.
         When read, value 0 is returned."
    ::= { agSystem 85 }

agCurCfgIdleCUAlloc OBJECT-TYPE
    SYNTAX INTEGER { limit( 0 ) , share( 1 ) }
    MAX-ACCESS read-only
    STATUS current
    DESCRIPTION
        "limit(0) - Limit vADC to the max allowed by the assigned CUs.
         share(1) - Share unused resources across vADCs."
    ::= { agSystem 86 }

agNewCfgIdleCUAlloc OBJECT-TYPE
    SYNTAX INTEGER { limit( 0 ) , share( 1 ) }
    MAX-ACCESS read-write
    STATUS current
    DESCRIPTION
        "limit(0) - Limit vADC to the max allowed by the assigned CUs.
         share(1) - Share unused resources across vADCs."
    ::= { agSystem 87 }

agActiveConfigBlk OBJECT-TYPE
    SYNTAX  DisplayString (SIZE(0..32))
    MAX-ACCESS  read-only
    STATUS  current
    DESCRIPTION
        "The configuration block which is active right now.This object can have
        either one of these values Active Configuration, Backup configuration,
        Default configuration."
    ::= { agSystem 88 }

agDefaultImageID OBJECT-TYPE
    SYNTAX  INTEGER (1..10)
    MAX-ACCESS  read-write
    STATUS  current
    DESCRIPTION
        "The Image ID of the image to assign vADCs"
    ::= { agSystem 89 }

agDefaultImageVer OBJECT-TYPE
    SYNTAX  DisplayString (SIZE(0..128))
    MAX-ACCESS  read-only
    STATUS  current
    DESCRIPTION
        "The default image version."
    ::= { agSystem 90 }

agMgmtConfigForNxtReset OBJECT-TYPE
    SYNTAX  INTEGER {
        erase(1),
        keep(2)
        }
    MAX-ACCESS  read-write
    STATUS  current
    DESCRIPTION
         "The management port configuration option for next reset.

          The following values are writable:
        erase(1)...remove management port configuration
        keep(2) ...keep management port configuration"
    ::= { agSystem 91 }

agActiveImageName OBJECT-TYPE
    SYNTAX  DisplayString (SIZE(0..255))
    MAX-ACCESS  read-only
    STATUS  current
    DESCRIPTION
         "The image name which is active right now."
    ::= { agSystem 92 }


agCurCfgSmtpHostIPVersion OBJECT-TYPE
    SYNTAX  INTEGER {
        ipv4(4),
        ipv6(6)
        }
    MAX-ACCESS  read-only
    STATUS  current
    DESCRIPTION
        "IP version for SMTP host name(agNewCfgSmtpHost)."
    ::= { agSystem 93 }

agNewCfgSmtpHostIPVersion OBJECT-TYPE
    SYNTAX  INTEGER {
        ipv4(4),
        ipv6(6)
        }
    MAX-ACCESS  read-write
    STATUS  current
    DESCRIPTION
        "IP version for SMTP host name(agNewCfgSmtpHost). Always, first SET the SMTP hostname and this object."
    ::= { agSystem 94 }

agCurCfgVassign OBJECT-TYPE
    SYNTAX  INTEGER {
        vadc(0),
        cu(1)
        }
    MAX-ACCESS read-only
    STATUS current
    DESCRIPTION
        "Automatic vADC payload assignment
         vadc(0) - Assign vADCs to payload blade with the fewest active vADCs
         cu(1) - Assign vADCs to payload blade with the most available CUs"
    ::= { agSystem 95 }

agNewCfgVassign OBJECT-TYPE
    SYNTAX  INTEGER {
        vadc(0),
        cu(1)
        }
    MAX-ACCESS read-write
    STATUS current
    DESCRIPTION
        "Automatic vADC payload assignment
         vadc(0) - Assign vADCs to payload blade with the fewest active vADCs
         cu(1) - Assign vADCs to payload blade with the most available CUs"
    ::= { agSystem 96 }


agMgmtCurGlobalState OBJECT-TYPE
    SYNTAX  INTEGER {
        disabled(1),
        enabled(2)
        }
    MAX-ACCESS  read-only
    STATUS  current
    DESCRIPTION
        "This object gives the current global status (enabled or disabled) of management port."
    ::= { agSystem 97 }


agSshKeysForNxtReset OBJECT-TYPE
    SYNTAX  INTEGER {
        erase(1),
        keep(2)
        }
    MAX-ACCESS  read-write
    STATUS  current
    DESCRIPTION
         "The SSH Keys generated should be erased or retained for next reset.

          The following values are writable:
             erase(1)...remove SSH Keys generated
             keep(2) ...keep SSH Keys generated (default)"
    ::= { agSystem 98 }
agCurStatReportConnPort OBJECT-TYPE
    SYNTAX  INTEGER  (2020..3030)
    MAX-ACCESS  read-only
    STATUS  current
    DESCRIPTION
        "The current port dedicated for statistics report-protocol. Default value: 3030"
    ::= { agSystem 99 }

agNewStatReportConnPort OBJECT-TYPE
    SYNTAX  INTEGER  (0..10000)
    MAX-ACCESS  read-write
    STATUS  current
    DESCRIPTION
        "This object sets the port dedicated for statistics report-protocol."
    ::= { agSystem 100 }

agCurStatReportStatus OBJECT-TYPE
    SYNTAX  INTEGER {
        disabled(1),
        enabled(2)
        }
    MAX-ACCESS  read-only
    STATUS  current
    DESCRIPTION
        "The current status of the statistics report-protocol. ON - statstics is available, OFF - otherwise."
    ::= { agSystem 101 }

agNewStatReportStatus OBJECT-TYPE
    SYNTAX  INTEGER {
        disabled(1),
        enabled(2)
        }
    MAX-ACCESS  read-write
    STATUS  current
    DESCRIPTION
        "Sets the status of the statistics report-protocol. ON - statstics is available, OFF - otherwise."
    ::= { agSystem 102 }

agStatReportProtocolVer OBJECT-TYPE
    SYNTAX  INTEGER  (1..2)
    MAX-ACCESS  read-write
    STATUS  current
    DESCRIPTION
        "This object gives the current version of statistics report-protocol the user requested to use."
    ::= { agSystem 103 }

agStatReportRstCounters OBJECT-TYPE
    SYNTAX  INTEGER {
        other(1),
        reset(2)
        }
    MAX-ACCESS  read-write
    STATUS  current
    DESCRIPTION
        "By this object you can reset the counters used for report-protocol statistics."
    ::= { agSystem 104 }

agStatReportError OBJECT-TYPE
    SYNTAX  DisplayString (SIZE(0..255))
    MAX-ACCESS  read-write
    STATUS  current
    DESCRIPTION
        "By this object you can send an error string to Alteon regarding the report-protocol.
	 The string can be up to 255 characters.This action will close the connection."
    ::= { agSystem 105 }

agStatReportNaming OBJECT-TYPE
    SYNTAX  INTEGER {
        disabled(1),
        enabled(2)
        }
    MAX-ACCESS  read-write
    STATUS  current
    DESCRIPTION
        "By this object you can choose whether you want the naming part (conf) in the report xml, or not."
    ::= { agSystem 106 }

agStatReportInterval OBJECT-TYPE
    SYNTAX  INTEGER  (15..20)
    MAX-ACCESS  read-write
    STATUS  current
    DESCRIPTION
        "By this object you can choose the time interval in which we calculate the statistics."
    ::= { agSystem 107 }

agStatReportClientIPv4Addr OBJECT-TYPE
    SYNTAX  IpAddress
    MAX-ACCESS  read-write
    STATUS  current
    DESCRIPTION
        "The IPv4 address of the Client which is allowed to open a connection and get
	the statistics via the Reporting-Protocol."
    ::= { agSystem 108 }

agShutdown OBJECT-TYPE
    SYNTAX  INTEGER {
        other(1),
        shutdown(2)
        }
    MAX-ACCESS  read-write
    STATUS  current
    DESCRIPTION
        "This is an action object to shutdown the switch.
         other(1) is returned always when read."
    ::= { agSystem 109 }

agCurCfgLimitCUAlloc OBJECT-TYPE
    SYNTAX INTEGER { disable(0) , enable(1) }
    MAX-ACCESS read-write
    STATUS current
    DESCRIPTION
        "disable(0) - Enables sharing an SP that holds unassigned CUs among assigned vADCs.
         enable(1)  - Disallows vADCs to consume resources not allocated to them, regardless of other available resources."
    ::= { agSystem 110 }

agNewCfgLimitCUAlloc OBJECT-TYPE
    SYNTAX INTEGER { disable(0) , enable(1) }
    MAX-ACCESS read-write
    STATUS current
    DESCRIPTION
        "disable(0) - Enables sharing an SP that holds unassigned CUs among assigned vADCs.
         enable(1)  - Disallows vADCs to consume resources not allocated to them, regardless of other available resources."
    ::= { agSystem 111 }

agNewIdByNum OBJECT-TYPE
    SYNTAX  INTEGER {
        disabled(1),
        enabled(2)
        }
    MAX-ACCESS  read-write
    STATUS  current
    DESCRIPTION
        "Enable/Disable Id by number for backward compatibility(relevant if using vDirect, AppShape or APM =only)."
    ::= { agSystem 112 }

agCurIdByNum OBJECT-TYPE
    SYNTAX  INTEGER {
        disabled(1),
        enabled(2)
        }
    MAX-ACCESS  read-only
    STATUS  current
    DESCRIPTION
        "Enable/Disable Id by number for backward compatibility(relevant if using vDirect, AppShape or APM =only)."
    ::= { agSystem 113 }

agSysIdByNum OBJECT-TYPE
    SYNTAX  INTEGER {
        byNumber(1),
        byName(2)
        }
    MAX-ACCESS  read-only
    STATUS  current
    DESCRIPTION
        "The current system mode of operation
         byNumber(1) -  support the Id by number behavior of one to one mapping of numerical
                      indexes to config block.
         byName(2)    - support Id by name, the Id by number behavior
                      as specified above won't be supported."
    ::= { agSystem 114 }

agLastSyncErrorReason   OBJECT-TYPE
    SYNTAX  DisplayString (SIZE(0..255))
    MAX-ACCESS  read-only
    STATUS  current
    DESCRIPTION
        "The error reason of the synchronization failure."
    ::= { agSystem 115 }

agSyncStatus OBJECT-TYPE
    SYNTAX  INTEGER {
        idle(0),
        inprogress(1),
        success(2),
        failure(3)
        }
    MAX-ACCESS  read-only
    STATUS  current
    DESCRIPTION
        "The current configuration synchronization status."
    ::= { agSystem 116 }

connmngStatsFIPSCard OBJECT-TYPE
   SYNTAX  INTEGER {
	notexist(1),
	zeroized(2),
	initialized(3),
	trusted(4),
	error(5)
	}
   MAX-ACCESS  read-only
   STATUS  current
   DESCRIPTION
       "FIPS card status"
   ::= {agSystem 117}


agCurCfgBPDUMaxRate OBJECT-TYPE
    SYNTAX  INTEGER (0..65535)
    MAX-ACCESS  read-only
    STATUS  current
    DESCRIPTION
        "The maximum allowed rate of BPDU."
    ::= { agSystem 118 }
agNewCfgBPDUMaxRate OBJECT-TYPE
    SYNTAX  INTEGER (0..65535)
    MAX-ACCESS  read-write
    STATUS  current
    DESCRIPTION
        "The maximum allowed rate of BPDU."
    ::= { agSystem 119 }
agCurCfgZeroTtlMaxRate OBJECT-TYPE
    SYNTAX  INTEGER (0..65535)
    MAX-ACCESS  read-only
    STATUS  current
    DESCRIPTION
        "The maximum allowed rate of Zero Ttl."
    ::= { agSystem 120 }

agNewCfgZeroTtlMaxRate OBJECT-TYPE
    SYNTAX  INTEGER (0..65535)
    MAX-ACCESS  read-write
    STATUS  current
    DESCRIPTION
        "The maximum allowed rate of Zero Ttl."
    ::= { agSystem 121 }


agImageUploadStatus OBJECT-TYPE
   SYNTAX  INTEGER {
        ok(0),
        inProgressFail(1),
        inProgress(2),
        inProgressSuccessful(3),
        wrriteToFlashFail(4),
        wrriteToFlashSuccessful(5),
        verificationFail(6),
        verificationSuccessful(7),
        instalattionFail(8),
        installationSuccessful(9),
	inProgressOfRmimgFail(10)
        }
   MAX-ACCESS  read-only
   STATUS  current
   DESCRIPTION
      "Display current image upload status in device."
   ::= {agSystem 122}

agSyncNeeded OBJECT-TYPE
    SYNTAX  INTEGER {
	syncNeeded(1),
        syncNotNeeded(2)
	}
    MAX-ACCESS  read-only
    STATUS  current
    DESCRIPTION
        "Is cfg sync needed?."
    ::= { agSystem 123 }

agMaxRules OBJECT-TYPE
    SYNTAX  INTEGER
    MAX-ACCESS  read-only
    STATUS  current
    DESCRIPTION
        "The maximum number of DNS rules allowed."
    ::= { agSystem 139 }

agMaxNetworks OBJECT-TYPE
    SYNTAX  INTEGER
    MAX-ACCESS  read-only
    STATUS  current
    DESCRIPTION
        "The maximum number of networks allowed."
    ::= { agSystem 140 }

agCurCfgGlobalLanguage OBJECT-TYPE
    SYNTAX INTEGER{
	english(0),
	chinese(1),
	korean(2),
	japanese(3)
	}
    MAX-ACCESS  read-only
    STATUS  current
    DESCRIPTION
        "Set default Web UI display language."
    ::= { agSystem 141 }

agNewCfgGlobalLanguage OBJECT-TYPE
    SYNTAX INTEGER{
	english(0),
	chinese(1),
	korean(2),
	japanese(3)
	}
    MAX-ACCESS  read-write
    STATUS  current
    DESCRIPTION
        "Set default Web UI display language."
        ::= { agSystem 142 }

agLpMode OBJECT-TYPE
     SYNTAX  INTEGER {
         none(0),
         module(1),
         standalone(2)
     }
     MAX-ACCESS  read-only
     STATUS current
     DESCRIPTION
          "Return the module according to the license installation."
     ::= { agSystem 143 }

bootResourcesTDVCPUs OBJECT-TYPE
	SYNTAX INTEGER(0..256)
	MAX-ACCESS read-write
	STATUS current
	DESCRIPTION
		"Number of allocated TDs. (Value must be 2^X).
		Note: This MIB is only supported on VA platform."
	::= { agSystem 144 }

bootResourcesMINTDVCPUs OBJECT-TYPE
	SYNTAX INTEGER(0..1)
	MAX-ACCESS read-only
	STATUS current
	DESCRIPTION
		"Minimum allocated TD number.(In Mellanox it's 1, In NON-Mellanox it's 0).
		Note: This MIB is only supported on VA platform."
	::= { agSystem 145 }

bootResourcesMAXTDVCPUs OBJECT-TYPE
	SYNTAX INTEGER(0..256)
	MAX-ACCESS read-only
	STATUS current
	DESCRIPTION
		"Maximum allocated TD number.
		Note: This MIB is only supported on VA platform."
	::= { agSystem 146 }

agCurCfgApmSamp OBJECT-TYPE
    SYNTAX  INTEGER (1..100)
    MAX-ACCESS  read-only
    STATUS  current
    DESCRIPTION
        "Current maximum apm sampling rate percentage."
    ::= { agSystem 147 }

agNewCfgApmSamp OBJECT-TYPE
    SYNTAX  INTEGER (1..100)
    MAX-ACCESS  read-write
    STATUS  current
    DESCRIPTION
        "Set apm sampling rate percentage between 1 to 100."
    ::= { agSystem 148 }



bootResourcesTDCHECKBOX OBJECT-TYPE
	SYNTAX INTEGER(0..1)
	MAX-ACCESS read-only
	STATUS current
	DESCRIPTION
		"Should TD allocation checkbox be checked.
		Note: This MIB is only supported on VA platform."
	::= { agSystem 149 }


agCurPerformanceMonitorInterval OBJECT-TYPE
    SYNTAX  INTEGER  (1..1440)
    MAX-ACCESS  read-only
    STATUS  current
    DESCRIPTION
        "The current performance monitor interval in minutes. Default value: 60"
    ::= { agSystem 150 }

agNewPerformanceMonitorInterval OBJECT-TYPE
    SYNTAX  INTEGER  (1..1440)
    MAX-ACCESS  read-write
    STATUS  current
    DESCRIPTION
        "Set performance monitor interval in minutes. Default value: 60"
    ::= { agSystem 151 }

agCurPerformanceMonitorMaxEntries OBJECT-TYPE
    SYNTAX  INTEGER  (1000..20000)
    MAX-ACCESS  read-only
    STATUS  current
    DESCRIPTION
        "The current performance monitor max entries per file. Default value: 10,000"
    ::= { agSystem 152 }

agNewPerformanceMonitorMaxEntries OBJECT-TYPE
    SYNTAX  INTEGER  (1000..20000)
    MAX-ACCESS  read-write
    STATUS  current
    DESCRIPTION
        "Set performance monitor max entries per file. Default value: 10,000"
    ::= { agSystem 153 }

agCurPerformanceMonitorState OBJECT-TYPE
    SYNTAX  INTEGER  (1..2)
    MAX-ACCESS  read-only
    STATUS  current
    DESCRIPTION
        "The current performance monitor state."
    ::= { agSystem 154 }

agNewPerformanceMonitorState OBJECT-TYPE
    SYNTAX  INTEGER  (1..2)
    MAX-ACCESS  read-write
    STATUS  current
    DESCRIPTION
        "Set performance monitor state."
    ::= { agSystem 155 }

agCurCfgSmtpHost2IPVersion OBJECT-TYPE
    SYNTAX  INTEGER {
        ipv4(4),
        ipv6(6)
        }
    MAX-ACCESS  read-only
    STATUS  current
    DESCRIPTION
        "IP version for SMTP host2 name(agNewCfgSmtpHost2)."
    ::= { agSystem 156 }

agNewCfgSmtpHost2IPVersion OBJECT-TYPE
    SYNTAX  INTEGER {
        ipv4(4),
        ipv6(6)
        }
    MAX-ACCESS  read-write
    STATUS  current
    DESCRIPTION
        "IP version for SMTP host2 name(agNewCfgSmtpHost2). Always, first SET the SMTP hostname2 and this object."
    ::= { agSystem 157 }

agCurCfgSmtpHost2 OBJECT-TYPE
    SYNTAX  DisplayString (SIZE(0..127))
    MAX-ACCESS  read-only
    STATUS  current
    DESCRIPTION
        "The user defined second SMTP host."
    ::= { agSystem 158 }

agNewCfgSmtpHost2 OBJECT-TYPE
    SYNTAX  DisplayString (SIZE(0..127))
    MAX-ACCESS  read-write
    STATUS  current
    DESCRIPTION
        "The user defined second SMTP host. If it is a host name then please configure agNewCfgSmtpHost2IPVersion.
         By default IPv4 version will be choosen.
         If IPv4 or Ipv6 address is configured than no need to configure agNewCfgSmtpHost2IPVersion,
         this will be filled accordingly. "
    ::= { agSystem 159 }


--agCurCfgIdleDashboardTimeout OBJECT-TYPE
--    SYNTAX  INTEGER (1..10080)
--    MAX-ACCESS  read-only
--    STATUS  current
--    DESCRIPTION
--        "Set idle Webui Dashboard timeout."
--    ::= { agSystem 160 }

--agNewCfgIdleDashboardTimeout OBJECT-TYPE
--    SYNTAX INTEGER (1..10080)
--    MAX-ACCESS  read-write
--    STATUS  current
--    DESCRIPTION
--        "Set idle Webui Dashboard timeout."
--        ::= { agSystem 161 }

agFipsSecurityLevel OBJECT-TYPE
    SYNTAX INTEGER{
	none(0),
	level2(2)
	}
    MAX-ACCESS  read-only
    STATUS  current
    DESCRIPTION
        "FIPS 140-2 security level indication."
    ::= { agSystem 162 }

agFipsNonApprovedMode OBJECT-TYPE
    SYNTAX  DisplayString (SIZE(0..255))
    MAX-ACCESS  read-only
    STATUS  current
    DESCRIPTION
        "Fips non-approved/error state indication."
    ::= { agSystem 163 }

agCurSecurityReportingServer OBJECT-TYPE
    SYNTAX  INTEGER {
        enabled(1),
        disabled(2)
        }
    MAX-ACCESS  read-only
    STATUS  current
    DESCRIPTION
        "Enable or disable ip rep service."
    ::= { agSystem 164 }

agNewSecurityReportingServer OBJECT-TYPE
    SYNTAX  INTEGER {
        enabled(1),
        disabled(2)
        }
    MAX-ACCESS  read-write
    STATUS  current
    DESCRIPTION
        "Enable or disable security reporting service."
    ::= { agSystem 165 }

agCurSecurityReportingServerAddr OBJECT-TYPE
    SYNTAX  IpAddress
    MAX-ACCESS  read-only
    STATUS  current
    DESCRIPTION
        "IPv4 address of security reporting server."
    ::= { agSystem 166 }

agNewSecurityReportingServerAddr OBJECT-TYPE
    SYNTAX  IpAddress
    MAX-ACCESS  read-write
    STATUS  current
    DESCRIPTION
        "IPv4 address of Vision server."
    ::= { agSystem 167 }

-- singleip status

agCurCfgSingleip OBJECT-TYPE
    SYNTAX  INTEGER {
        unsupported(0),
        enabled(1),
        disabled(2)
    }
    MAX-ACCESS  read-only
    STATUS  current
    DESCRIPTION
        "The current singleip state."
    ::= { agSystem 168 }

agCurSingleIPonSingleNIC  OBJECT-TYPE
    SYNTAX  INTEGER {
        unsupported(0),
        enabled(1),
        disabled(2)
    }
    MAX-ACCESS  read-only
    STATUS  current
    DESCRIPTION
        "The state of whether singleip is enabled on single NIC device."
    ::= { agSystem 169 }

agAppwallVersion OBJECT-TYPE
    SYNTAX  DisplayString (SIZE(0..16))
    MAX-ACCESS  read-only
    STATUS  current
    DESCRIPTION
        "The version of the Appwall that is currently running on the system."
    ::= { agSystem 170 }

-- azure properties

agCurCfgAzureSubscriptionId OBJECT-TYPE
    SYNTAX  DisplayString (SIZE(0..127))
    MAX-ACCESS  read-only
    STATUS  current
    DESCRIPTION
        "Azure Subscription Id.
         Note: This MIB is only supported on VA platform."
    ::= { agSystem 171 }

agNewCfgAzureSubscriptionId OBJECT-TYPE
    SYNTAX  DisplayString (SIZE(0..127))
    MAX-ACCESS  read-write
    STATUS  current
    DESCRIPTION
        "Azure Subscription Id.
         Note: This MIB is only supported on VA platform."
    ::= { agSystem 172 }

agCurCfgAzureAdClientId OBJECT-TYPE
    SYNTAX  DisplayString (SIZE(0..127))
    MAX-ACCESS  read-only
    STATUS  current
    DESCRIPTION
        "Azure credentials Client ID.
         Note: This MIB is only supported on VA platform."
    ::= { agSystem 173 }

agNewCfgAzureAdClientId OBJECT-TYPE
    SYNTAX  DisplayString (SIZE(0..127))
    MAX-ACCESS  read-write
    STATUS  current
    DESCRIPTION
        "Azure credentials Client ID.
         Note: This MIB is only supported on VA platform."
    ::= { agSystem 174 }

agCurCfgAzureAdClientSecret OBJECT-TYPE
    SYNTAX  DisplayString (SIZE(0..255))
    MAX-ACCESS  read-only
    STATUS  current
    DESCRIPTION
        "Azure credentials  Client secret.
         Note: This MIB is only supported on VA platform."
    ::= { agSystem 175 }

agNewCfgAzureAdClientSecret OBJECT-TYPE
    SYNTAX  DisplayString (SIZE(0..255))
    MAX-ACCESS  read-write
    STATUS  current
    DESCRIPTION
        "Azure credentials  Client secret.
         Note: This MIB is only supported on VA platform."
    ::= { agSystem 176 }

agCurCfgAzureAdTenantId OBJECT-TYPE
    SYNTAX  DisplayString (SIZE(0..127))
    MAX-ACCESS  read-only
    STATUS  current
    DESCRIPTION
        "Azure tenant ID.
         Note: This MIB is only supported on VA platform."
    ::= { agSystem 177 }

agNewCfgAzureAdTenantId OBJECT-TYPE
    SYNTAX  DisplayString (SIZE(0..127))
    MAX-ACCESS  read-write
    STATUS  current
    DESCRIPTION
        "Azure tenant ID.
         Note: This MIB is only supported on VA platform."
    ::= { agSystem 178 }

agCurCfgAzureResourceGroupName OBJECT-TYPE
    SYNTAX  DisplayString (SIZE(0..127))
    MAX-ACCESS  read-only
    STATUS  current
    DESCRIPTION
        "Azure resource group name.
         Note: This MIB is only supported on VA platform."
    ::= { agSystem 179 }

agNewCfgAzureResourceGroupName OBJECT-TYPE
    SYNTAX  DisplayString (SIZE(0..127))
    MAX-ACCESS  read-write
    STATUS  current
    DESCRIPTION
        "Azure resource group name.
         Note: This MIB is only supported on VA platform."
    ::= { agSystem 180 }

agCurCfgAzureDeviceNicName OBJECT-TYPE
    SYNTAX  DisplayString (SIZE(0..127))
    MAX-ACCESS  read-only
    STATUS  current
    DESCRIPTION
        "Azure VM network interface resource name.
         Note: This MIB is only supported on VA platform."
    ::= { agSystem 181 }

agNewCfgAzureDeviceNicName OBJECT-TYPE
    SYNTAX  DisplayString (SIZE(0..127))
    MAX-ACCESS  read-write
    STATUS  current
    DESCRIPTION
        "Azure VM network interface resource name.
         Note: This MIB is only supported on VA platform."
    ::= { agSystem 182 }

agCurCfgAzurePrimaryPublicIpName OBJECT-TYPE
    SYNTAX  DisplayString (SIZE(0..127))
    MAX-ACCESS  read-only
    STATUS  current
    DESCRIPTION
        "Azure VM primary public IP resource name.
         Note: This MIB is only supported on VA platform."
    ::= { agSystem 183 }

agNewCfgAzurePrimaryPublicIpName OBJECT-TYPE
    SYNTAX  DisplayString (SIZE(0..127))
    MAX-ACCESS  read-write
    STATUS  current
    DESCRIPTION
        "Azure VM primary public IP resource name.
         Note: This MIB is only supported on VA platform."
    ::= { agSystem 184 }

agCurCfgAzurePeerDeviceNicName OBJECT-TYPE
    SYNTAX  DisplayString (SIZE(0..127))
    MAX-ACCESS  read-only
    STATUS  current
    DESCRIPTION
        "Azure HA peer VM network interface resource name.
         Note: This MIB is only supported on VA platform."
    ::= { agSystem 185 }

agNewCfgAzurePeerDeviceNicName OBJECT-TYPE
    SYNTAX  DisplayString (SIZE(0..127))
    MAX-ACCESS  read-write
    STATUS  current
    DESCRIPTION
        "Azure HA peer VM network interface resource name.
         Note: This MIB is only supported on VA platform."
    ::= { agSystem 186 }

agCurCfgAzureSecondaryPublicIpName OBJECT-TYPE
    SYNTAX  DisplayString (SIZE(0..127))
    MAX-ACCESS  read-only
    STATUS  current
    DESCRIPTION
        "Azure VM secondary public IP resource name.
         Note: This MIB is only supported on VA platform."
    ::= { agSystem 187 }

agNewCfgAzureSecondaryPublicIpName OBJECT-TYPE
    SYNTAX  DisplayString (SIZE(0..127))
    MAX-ACCESS  read-write
    STATUS  current
    DESCRIPTION
        "Azure VM secondary public IP resource name.
         Note: This MIB is only supported on VA platform."
    ::= { agSystem 188 }

agIsAzure OBJECT-TYPE
    SYNTAX  DisplayString (SIZE(0..15))
    MAX-ACCESS  read-only
    STATUS  current
    DESCRIPTION
        "An administratively-assigned value that identifies if managed device is Azure platform.
         Note: This MIB is only supported on VA platform."
    ::= { agSystem 189 }


-- although this is an Azure property, due to current mechanism, it should be exposed to all platforms

agNewCfgAzureGlobalNicName OBJECT-TYPE
    SYNTAX  DisplayString (SIZE(0..80))
    MAX-ACCESS  read-write
    STATUS  current
    DESCRIPTION
        "Azure VM global NIC name holder."
    ::= { agSystem 207 }

agAccCardSupport OBJECT-TYPE
   SYNTAX  INTEGER {
        notexist(1),
        cavium(2),
        caviumfips(3),
        qat(4)
        }
   MAX-ACCESS  read-only
   STATUS  current
   DESCRIPTION
       "supported acceleration card type"
   ::= {agSystem 190 }

agDeviceLicMode OBJECT-TYPE
   SYNTAX INTEGER {
        none(0),
        ng(1),
        ngplus(2),
        deliver(3),
        perform(4),
        secure(5)
   }
   MAX-ACCESS  read-only
   STATUS  current
   DESCRIPTION
       "Device license mode."
   ::= {agSystem 191 }



-- MIBs Added for Upgrade Tool Support

agUpgradeJarVersion OBJECT-TYPE
    SYNTAX  DisplayString (SIZE(0..40))
    MAX-ACCESS  read-only
    STATUS  current
    DESCRIPTION
    "Version Number of upgradeTool.Jar File for Upgrade Advisor Tool"
    ::= { agSystem 192 }

agUpgradeRuleVersion OBJECT-TYPE
    SYNTAX  DisplayString (SIZE(0..40))
    MAX-ACCESS  read-only
    STATUS  current
    DESCRIPTION
    "Version Number of Rules.dat File for Upgrade Advisor Tool"
    ::= { agSystem 193 }

agUpgradeLog4Version OBJECT-TYPE
    SYNTAX  DisplayString (SIZE(0..40))
    MAX-ACCESS  read-only
    STATUS  current
    DESCRIPTION
    "Version Number of Log4.properties File for Upgrade Advisor Tool"
    ::= { agSystem 194 }

agCurStatReportUid OBJECT-TYPE
    SYNTAX  DisplayString (SIZE(0..33))
    MAX-ACCESS  read-only
    STATUS  current
    DESCRIPTION
    "The Alteon identification for reporting."
    ::= { agSystem 195 }

agSystemAws        OBJECT IDENTIFIER ::= { agSystem 201 }

agCurCfgGeoDbAutoUpdate OBJECT-TYPE
    SYNTAX  INTEGER {
        enabled(1),
        disabled(2)
        }
    MAX-ACCESS  read-only
    STATUS  current
    DESCRIPTION
        "Enable or disable automatic geolocation database update."
    ::= { agSystem 202 }

agNewCfgGeoDbAutoUpdate OBJECT-TYPE
    SYNTAX  INTEGER {
        enabled(1),
        disabled(2)
        }
    MAX-ACCESS  read-write
    STATUS  current
    DESCRIPTION
        "Set automatic geolocation database update as enable or disable."
    ::= { agSystem 203 }


-- aws properties

agIsAws OBJECT-TYPE
    SYNTAX  DisplayString (SIZE(0..15))
    MAX-ACCESS  read-only
    STATUS  current
    DESCRIPTION
        "An administratively-assigned value that identifies if managed device is AWS platform.
         Note: This MIB is only supported on VA platform."
    ::= {agSystem 204 }

agSslVisiReportProtocolVer OBJECT-TYPE
    SYNTAX INTEGER(1..10)
    MAX-ACCESS read-only
    STATUS current
    DESCRIPTION
	"Get Ssl Visibility report protocol Version,
	 used in identifying the json data version
	 used."
    ::= {agSystem 205 }

agImageForNxtResetNew OBJECT-TYPE
    SYNTAX  INTEGER (1..10)
    MAX-ACCESS  read-write
    STATUS  current
    DESCRIPTION
        "The software image to be booted from at next reset.

         The following values are writable:
             image1(1)...image 1
             image2(2)...image 2
             ..."
    ::= { agSystem 206 }



agSessSyncState OBJECT-TYPE
    SYNTAX  DisplayString (SIZE(0..60))
    MAX-ACCESS  read-only
    STATUS  current
    DESCRIPTION
        "The session synchronization status."
    ::= { agSystem 210 }

--Ports combination MIBS
agCurCfgPortsComb OBJECT-TYPE
    SYNTAX  INTEGER (0..3)
    MAX-ACCESS  read-write
    STATUS  current
    DESCRIPTION
        "Ports combination."
    ::= { agSystem 211 }

agNewCfgPortsComb OBJECT-TYPE
    SYNTAX INTEGER (0..3)
    MAX-ACCESS  read-write
    STATUS  current
    DESCRIPTION
        "Ports combination."
        ::= { agSystem 212 }

agCurCfgHwHealthMonitoring OBJECT-TYPE
    SYNTAX  INTEGER {
        enabled(1),
        disabled(2)
        }
    MAX-ACCESS  read-only
    STATUS  current
    DESCRIPTION
        "Enable/disable hardware health monitoring data collection."
    ::= { agSystem 213 }

agNewCfgHwHealthMonitoring OBJECT-TYPE
    SYNTAX  INTEGER {
        enabled(1),
        disabled(2)
        }
    MAX-ACCESS  read-write
    STATUS  current
    DESCRIPTION
        "Enable/disable hardware health monitoring data collection."
    ::= { agSystem 214 }

agAppwallWebUIMode OBJECT-TYPE
    SYNTAX  INTEGER {
        java(0),
        nodejs(1)
        }
    MAX-ACCESS  read-write
    STATUS  current
    DESCRIPTION
        "AppWall webUI mode."
    ::= { agSystem 215 }


-- IPV6 MIBS
agMgmtCurCfgIpv6Addr OBJECT-TYPE
    SYNTAX  DisplayString (SIZE(0..40))
    MAX-ACCESS  read-only
    STATUS  current
    DESCRIPTION
    "  The IPV6 address of the management port.
    Address should be 4-byte haxadecimal colon notation.
    Valid IPv6 address should be in any of the following forms xxxx:xxxx:xxxx:xxxx:xxxx:xxxx:xxxx:xxxx
    or xxxx::xxxx:xxxx:xxxx:xxxx or ::xxxx"
    ::= { agMgmt 75 }

agMgmtNewCfgIpv6Addr OBJECT-TYPE
    SYNTAX DisplayString (SIZE(0..40))
    MAX-ACCESS  read-write
    STATUS  current
    DESCRIPTION
    "  The IPV6 address of the management port.
    Address should be 4-byte haxadecimal colon notation.
    Valid IPv6 address should be in any of the following forms xxxx:xxxx:xxxx:xxxx:xxxx:xxxx:xxxx:xxxx
    or xxxx::xxxx:xxxx:xxxx:xxxx or ::xxxx"
    ::= { agMgmt 76 }

agMgmtCurCfgIpv6PrefixLen OBJECT-TYPE
    SYNTAX  INTEGER  (0..128)
    MAX-ACCESS  read-only
    STATUS  current
    DESCRIPTION
    "  The IPV6 prefix length of the management port. "
    ::= { agMgmt 77 }

agMgmtNewCfgIpv6PrefixLen OBJECT-TYPE
    SYNTAX  INTEGER  (0..128)
    MAX-ACCESS  read-write
    STATUS  current
    DESCRIPTION
    "  The IPV6 prefix length of the management port. "
    ::= { agMgmt 78 }

agMgmtCurCfgIpv6Gateway OBJECT-TYPE
    SYNTAX DisplayString (SIZE(0..40))
    MAX-ACCESS  read-only
    STATUS  current
    DESCRIPTION
    "  The IPV6 Gateway of the management port.
    Address should be 4-byte haxadecimal colon notation.
    Valid IPv6 address should be in any of the following forms xxxx:xxxx:xxxx:xxxx:xxxx:xxxx:xxxx:xxxx
    or xxxx::xxxx:xxxx:xxxx:xxxx or ::xxxx"
    ::= { agMgmt 79 }

agMgmtNewCfgIpv6Gateway OBJECT-TYPE
    SYNTAX DisplayString (SIZE(0..40))
    MAX-ACCESS  read-write
    STATUS  current
    DESCRIPTION
    "  The IPV6 Gateway of the management port.
    Address should be 4-byte haxadecimal colon notation.
    Valid IPv6 address should be in any of the following forms xxxx:xxxx:xxxx:xxxx:xxxx:xxxx:xxxx:xxxx
    or xxxx::xxxx:xxxx:xxxx:xxxx or ::xxxx "
    ::= { agMgmt 80 }

agMgmtCurCfgIpv6Addr2 OBJECT-TYPE
    SYNTAX DisplayString (SIZE(0..40))
    MAX-ACCESS  read-only
    STATUS  current
    DESCRIPTION
    "  The IPV6 address2 of the management port.
    Address should be 4-byte haxadecimal colon notation.
    Valid IPv6 address should be in any of the following forms xxxx:xxxx:xxxx:xxxx:xxxx:xxxx:xxxx:xxxx
    or xxxx::xxxx:xxxx:xxxx:xxxx or ::xxxx "
    ::= { agMgmt 81 }

agMgmtNewCfgIpv6Addr2 OBJECT-TYPE
    SYNTAX DisplayString (SIZE(0..40))
    MAX-ACCESS  read-write
    STATUS  current
    DESCRIPTION
    "  The IPV6 address2 of the management port.
    Address should be 4-byte haxadecimal colon notation.
    Valid IPv6 address should be in any of the following forms xxxx:xxxx:xxxx:xxxx:xxxx:xxxx:xxxx:xxxx
    or xxxx::xxxx:xxxx:xxxx:xxxx or ::xxxx "
    ::= { agMgmt 82 }

agMgmtCurCfgIpv6PrefixLen2 OBJECT-TYPE
    SYNTAX  INTEGER  (0..128)
    MAX-ACCESS  read-only
    STATUS  current
    DESCRIPTION
    "  The IPV6 prefix length2 of the management port. "
    ::= { agMgmt 83 }

agMgmtNewCfgIpv6PrefixLen2 OBJECT-TYPE
    SYNTAX  INTEGER  (0..128)
    MAX-ACCESS  read-write
    STATUS  current
    DESCRIPTION
    "  The IPV6 prefix length2 of the management port. "
    ::= { agMgmt 84 }

agMgmtCurCfgIpv6Gateway2 OBJECT-TYPE
    SYNTAX DisplayString (SIZE(0..40))
    MAX-ACCESS  read-only
    STATUS  current
    DESCRIPTION
    "  The IPV6 Gateway2 of the management port.
    Address should be 4-byte haxadecimal colon notation.
    Valid IPv6 address should be in any of the following forms xxxx:xxxx:xxxx:xxxx:xxxx:xxxx:xxxx:xxxx
    or xxxx::xxxx:xxxx:xxxx:xxxx or ::xxxx "
    ::= { agMgmt 85 }

agMgmtNewCfgIpv6Gateway2 OBJECT-TYPE
    SYNTAX DisplayString (SIZE(0..40))
    MAX-ACCESS  read-write
    STATUS  current
    DESCRIPTION
    "  The IPV6 Gateway2 of the management port.
    Address should be 4-byte haxadecimal colon notation.
    Valid IPv6 address should be in any of the following forms xxxx:xxxx:xxxx:xxxx:xxxx:xxxx:xxxx:xxxx
    or xxxx::xxxx:xxxx:xxxx:xxxx or ::xxxx "
    ::= { agMgmt 86 }

agMgmtCurCfgArpState OBJECT-TYPE
    SYNTAX  INTEGER {
        enabled(1),
        disabled(2)
        }
    MAX-ACCESS  read-only
    STATUS  current
    DESCRIPTION
        "Enable/disable ARP/Neighbor Discovery only health check for management gateway"
   ::= { agMgmt 87 }

agMgmtNewCfgArpState OBJECT-TYPE
    SYNTAX  INTEGER {
        enabled(1),
        disabled(2)
        }
    MAX-ACCESS  read-write
    STATUS  current
    DESCRIPTION
        "Enable/disable ARP/Neighbor Discovery only health check for management gateway"
   ::= { agMgmt 88 }

agMgmtCurCfgWsRadius OBJECT-TYPE
    SYNTAX  INTEGER {
        data(1),
        mgmt(2)
        }
    MAX-ACCESS  read-only
    STATUS  current
    DESCRIPTION
        "Specifies Web Security RADIUS access is over management port or data port."
   ::= { agMgmt 89 }

agMgmtNewCfgWsRadius OBJECT-TYPE
    SYNTAX  INTEGER {
        data(1),
        mgmt(2)
        }
    MAX-ACCESS  read-write
    STATUS  current
    DESCRIPTION
        "Specifies Web Security RADIUS access is over management port or data port."
   ::= { agMgmt 90 }

agMgmtCurCfgWsLdap OBJECT-TYPE
    SYNTAX  INTEGER {
        data(1),
        mgmt(2)
        }
    MAX-ACCESS  read-only
    STATUS  current
    DESCRIPTION
        "Specifies Web Security LDAP access is over management port or data port."
   ::= { agMgmt 91 }

agMgmtNewCfgWsLdap OBJECT-TYPE
    SYNTAX  INTEGER {
        data(1),
        mgmt(2)
        }
    MAX-ACCESS  read-write
    STATUS  current
    DESCRIPTION
        "Specifies Web Security LDAP access is over management port or data port."
   ::= { agMgmt 92 }


agMgmtCurCfgDefensePro OBJECT-TYPE
    SYNTAX  INTEGER {
        data(1),
        mgmt(2)
        }
    MAX-ACCESS  read-only
    STATUS  current
    DESCRIPTION
        "Specifies DefensePro signaling access is over management port or data port."
   ::= { agMgmt 93 }

agMgmtNewCfgDefensePro OBJECT-TYPE
    SYNTAX  INTEGER {
        data(1),
        mgmt(2)
        }
    MAX-ACCESS  read-write
    STATUS  current
    DESCRIPTION
        "Specifies DefensePro signaling access is over management port or data port."
   ::= { agMgmt 94 }

agMgmtCurCfgLinkBonding OBJECT-TYPE
    SYNTAX  INTEGER {
        enabled(1),
        disabled(2)
        }
    MAX-ACCESS  read-only
    STATUS  current
    DESCRIPTION
        "Enable/disable Management Port Bonding."
   ::= { agMgmt 95 }

agMgmtNewCfgLinkBonding OBJECT-TYPE
    SYNTAX  INTEGER {
        enabled(1),
        disabled(2)
        }
    MAX-ACCESS  read-write
    STATUS  current
    DESCRIPTION
        "Enable/disable Management Port Bonding."
   ::= { agMgmt 96 }



-- system Peer Configurarion Menu

agSysPeerCurCfgTable OBJECT-TYPE
    SYNTAX  SEQUENCE OF AgSysPeerCurCfgEntry
    MAX-ACCESS  not-accessible
    STATUS  current
    DESCRIPTION
        "The table of system peer sync configuration in the current Configuration Block."
    ::= { agSysPeerConfig 1 }

agSysPeerCurCfgEntry OBJECT-TYPE
    SYNTAX  AgSysPeerCurCfgEntry
    MAX-ACCESS  not-accessible
    STATUS  current
    DESCRIPTION
        "A row in the system peer table"
    INDEX   { agSysPeerCurCfgIndex }
    ::= { agSysPeerCurCfgTable 1 }

AgSysPeerCurCfgEntry ::= SEQUENCE {
    agSysPeerCurCfgIndex         Integer32,
    agSysPeerCurCfgAddr          IpAddress,
    agSysPeerCurCfgState         INTEGER,
    agSysPeerCurCfgVadcBmap      OCTET STRING,
    agSysPeerCurCfgAddrType	 INTEGER,
    agSysPeerCurCfgIpv6Addr	 DisplayString
    }

agSysPeerCurCfgIndex OBJECT-TYPE
    SYNTAX  Integer32
    MAX-ACCESS  read-only
    STATUS  current
    DESCRIPTION
        "The system peer number for which the IP information is related."
    ::= { agSysPeerCurCfgEntry 1 }

agSysPeerCurCfgAddr OBJECT-TYPE
    SYNTAX  IpAddress
    MAX-ACCESS  read-only
    STATUS  current
    DESCRIPTION
        "The IPv4 address of the system peer."
    ::= { agSysPeerCurCfgEntry 2 }

agSysPeerCurCfgState OBJECT-TYPE
    SYNTAX  INTEGER {
        enabled(2),
        disabled(3)
        }
    MAX-ACCESS  read-only
    STATUS  current
    DESCRIPTION
        "The state of the system peer."
    ::= { agSysPeerCurCfgEntry 3 }

agSysPeerCurCfgVadcBmap OBJECT-TYPE
    SYNTAX  OCTET STRING
    MAX-ACCESS read-only
    STATUS  current
    DESCRIPTION
        "The vAdcs added to the system peer."
    ::= { agSysPeerCurCfgEntry 4 }

agSysPeerCurCfgAddrType OBJECT-TYPE
    SYNTAX  INTEGER {
        ipv4(4),
        ipv6(6)
        }
    MAX-ACCESS  read-only
    STATUS  current
    DESCRIPTION
        "The type of the IP address of the peer (IPv4 | IPv6)"
    ::= { agSysPeerCurCfgEntry 5 }

agSysPeerCurCfgIpv6Addr OBJECT-TYPE
   SYNTAX DisplayString (SIZE(0..40))
    MAX-ACCESS  read-only
    STATUS  current
    DESCRIPTION
    " The IPV6 address of the peer identified by the instance of agSysPeerCurCfgIndex field.
       Address should be 4-byte haxadecimal colon notation. Valid IPv6 address should be in
       any of the following forms xxxx:xxxx:xxxx:xxxx:xxxx:xxxx:xxxx:xxxx or xxxx::xxxx:xxxx:xxxx:xxxx or ::xxxx "
   ::= { agSysPeerCurCfgEntry 6 }



agSysPeerNewCfgTable OBJECT-TYPE
    SYNTAX  SEQUENCE OF AgSysPeerNewCfgEntry
    MAX-ACCESS  not-accessible
    STATUS  current
    DESCRIPTION
        "The table of peer sync configuration in the New Configuration Block."
    ::= { agSysPeerConfig 2 }

agSysPeerNewCfgEntry OBJECT-TYPE
    SYNTAX  AgSysPeerNewCfgEntry
    MAX-ACCESS  not-accessible
    STATUS  current
    DESCRIPTION
        "A row in the system peer table"
    INDEX   { agSysPeerNewCfgIndex }
    ::= { agSysPeerNewCfgTable 1 }

AgSysPeerNewCfgEntry ::= SEQUENCE {
    agSysPeerNewCfgIndex         Integer32,
    agSysPeerNewCfgAddr          IpAddress,
    agSysPeerNewCfgState         INTEGER,
    agSysPeerNewCfgVadcBmap      OCTET STRING,
    agSysPeerNewCfgDelete        INTEGER,
    agSysPeerNewCfgVadcAdd       INTEGER,
    agSysPeerNewCfgVadcRemove    INTEGER,
    agSysPeerNewCfgAddrType	 INTEGER,
    agSysPeerNewCfgIpv6Addr      DisplayString
    }

agSysPeerNewCfgIndex OBJECT-TYPE
    SYNTAX  Integer32
    MAX-ACCESS  read-only
    STATUS  current
    DESCRIPTION
        "The system peer number for which the IP information is related."
    ::= { agSysPeerNewCfgEntry 1 }

agSysPeerNewCfgAddr OBJECT-TYPE
    SYNTAX  IpAddress
    MAX-ACCESS  read-create
    STATUS  current
    DESCRIPTION
        "The IPv4 address of the system peer."
    ::= { agSysPeerNewCfgEntry 2 }

agSysPeerNewCfgState OBJECT-TYPE
    SYNTAX  INTEGER {
        enabled(2),
        disabled(3)
        }
    MAX-ACCESS  read-create
    STATUS  current
    DESCRIPTION
        "The state of the system peer."
    ::= { agSysPeerNewCfgEntry 3 }

agSysPeerNewCfgVadcBmap OBJECT-TYPE
    SYNTAX  OCTET STRING
    MAX-ACCESS read-only
    STATUS  current
    DESCRIPTION
        "The vAdcs that belongs to system peer."
    ::= { agSysPeerNewCfgEntry 4 }

agSysPeerNewCfgDelete OBJECT-TYPE
    SYNTAX  INTEGER {
        other(1),
        delete(2)
        }
    MAX-ACCESS  read-create
    STATUS  current
    DESCRIPTION
        "When set to the value of 2 (delete), the entire row is deleted.
         When read, other(1) is returned. Setting the value to anything
         other than 2(delete) has no effect on the state of the row."
    ::= { agSysPeerNewCfgEntry 5 }

agSysPeerNewCfgVadcAdd OBJECT-TYPE
    SYNTAX  INTEGER (0..256)
    MAX-ACCESS read-write
    STATUS  current
    DESCRIPTION
        "Add VADc to the system peer"
    ::= { agSysPeerNewCfgEntry 6 }

agSysPeerNewCfgVadcRemove OBJECT-TYPE
    SYNTAX  INTEGER (0..256)
    MAX-ACCESS read-write
    STATUS  current
    DESCRIPTION
        "Remove VADc from the system peer"
    ::= { agSysPeerNewCfgEntry 7 }

agSysPeerNewCfgAddrType OBJECT-TYPE
    SYNTAX  INTEGER {
        ipv4(4),
        ipv6(6)
        }
    MAX-ACCESS  read-write
    STATUS  current
    DESCRIPTION
        "The type of the IP address of the peer (IPv4 | IPv6)"
    ::= { agSysPeerNewCfgEntry 8 }

agSysPeerNewCfgIpv6Addr OBJECT-TYPE
   SYNTAX DisplayString (SIZE(0..40))
    MAX-ACCESS  read-write
    STATUS  current
    DESCRIPTION
    " The IPV6 address of the peer identified by the instance of agSysPeerNewCfgIndex field.
       Address should be 4-byte haxadecimal colon notation. Valid IPv6 address should be in
       any of the following forms xxxx:xxxx:xxxx:xxxx:xxxx:xxxx:xxxx:xxxx or xxxx::xxxx:xxxx:xxxx:xxxx or ::xxxx "
   ::= { agSysPeerNewCfgEntry 9 }

agSysCurSyncPasswordMode OBJECT-TYPE
    SYNTAX  INTEGER{
        admin(1),
        passphrase(2)
        }
    MAX-ACCESS  read-only
    STATUS  current
    DESCRIPTION
        "The password mode used for authentication in config sync.
         Only passphrase mode is currently supported."
    ::= { agSysPeerConfig 3 }

agSysNewSyncPasswordMode OBJECT-TYPE
    SYNTAX  INTEGER{
        admin(1),
        passphrase(2)
        }
    MAX-ACCESS  read-write
    STATUS  current
    DESCRIPTION
        "The password mode used for authentication in config sync.
         Only passphrase mode is currently supported."
    ::= { agSysPeerConfig 4 }

agSysSyncPassphrase OBJECT-TYPE
    SYNTAX  DisplayString (SIZE(4..128))
    MAX-ACCESS  read-write
    STATUS  current
    DESCRIPTION
        "Set passphrase to replace the admin password for authentication at the peer device. VX part."
    ::= { agSysPeerConfig 5 }

agSysCurSyncAutosync OBJECT-TYPE
    SYNTAX  INTEGER {
        enabled(1),
        disabled(2)
        }
    MAX-ACCESS  read-only
    STATUS  current
    DESCRIPTION
        "Enable or disable automatic syncing of configuration."
    ::= { agSysPeerConfig 6 }

agSysNewSyncAutosync OBJECT-TYPE
    SYNTAX  INTEGER {
        enabled(1),
        disabled(2)
        }
    MAX-ACCESS  read-write
    STATUS  current
    DESCRIPTION
        "Enable or disable automatic syncing of configuration."
    ::= { agSysPeerConfig 7 }

-- End system Peer Sync Configuration


agCurCfgAPMServerId OBJECT-TYPE
    SYNTAX  DisplayString (SIZE(1..28))
    MAX-ACCESS  read-only
    STATUS  current
    DESCRIPTION
        "The id of the APM server."
    ::= { agSysApmConfig 1 }

agNewCfgAPMServerId OBJECT-TYPE
    SYNTAX  DisplayString (SIZE(1..28))
    MAX-ACCESS  read-write
    STATUS  current
    DESCRIPTION
        "The id of the APM server."
    ::= { agSysApmConfig 2 }

agCurCfgAPMServerDataIpAddr OBJECT-TYPE
    SYNTAX  IpAddress
    MAX-ACCESS  read-only
    STATUS  current
    DESCRIPTION
        "The The APM server data IP address."
    ::= { agSysApmConfig 3 }

agNewCfgAPMServerDataIpAddr OBJECT-TYPE
    SYNTAX  IpAddress
    MAX-ACCESS  read-write
    STATUS  current
    DESCRIPTION
        "The The APM server data IP address."
    ::= { agSysApmConfig 4 }

agCurCfgAPMServerDataPort OBJECT-TYPE
    SYNTAX  INTEGER (2..65534)
    MAX-ACCESS  read-only
    STATUS  current
    DESCRIPTION
        "The port number of the apm server"
    ::= { agSysApmConfig 5 }

agNewCfgAPMServerDataPort OBJECT-TYPE
    SYNTAX  INTEGER (2..65534)
    MAX-ACCESS  read-write
    STATUS  current
    DESCRIPTION
        "The port number of the apm server"
    ::= { agSysApmConfig 6 }

agCurCfgAPMServerMgmtIpAddr OBJECT-TYPE
    SYNTAX  IpAddress
    MAX-ACCESS  read-only
    STATUS  current
    DESCRIPTION
        "The APM server management IP address."
    ::= { agSysApmConfig 7 }

agNewCfgAPMServerMgmtIpAddr OBJECT-TYPE
    SYNTAX  IpAddress
    MAX-ACCESS  read-write
    STATUS  current
    DESCRIPTION
        "The APM server management IP address."
    ::= { agSysApmConfig 8 }

agCurCfgAPMMgmtOrDataPort OBJECT-TYPE
    SYNTAX  INTEGER{
        mgmt(1),
        data(2)
        }
    MAX-ACCESS  read-only
    STATUS  obsolete
    DESCRIPTION
        "The port that is used for the APM server configurtation."
    ::= { agSysApmConfig 9 }

agNewCfgAPMMgmtOrDataPort OBJECT-TYPE
    SYNTAX  INTEGER{
        mgmt(1),
        data(2)
        }
    MAX-ACCESS  read-write
    STATUS  obsolete
    DESCRIPTION
        "The port that is used for the APM server configurtation."
    ::= { agSysApmConfig 10 }

agCurCfgAPMServerBkupIpAddr OBJECT-TYPE
    SYNTAX  IpAddress
    MAX-ACCESS  read-only
    STATUS  obsolete
    DESCRIPTION
        "The APM backup server IP address."
    ::= { agSysApmConfig 11 }

agNewCfgAPMServerBkupIpAddr OBJECT-TYPE
    SYNTAX  IpAddress
    MAX-ACCESS  read-write
    STATUS  obsolete
    DESCRIPTION
        "The APM backup server IP address."
    ::= { agSysApmConfig 12 }

agNewCfgAPMServerDelete OBJECT-TYPE
    SYNTAX  INTEGER {
        other(1),
        delete(2)
        }
    MAX-ACCESS  read-write
    STATUS  current
    DESCRIPTION
        "When set to the value of 2 (delete), the APM server is deleted.
         When read, other(1) is returned. Setting the value to anything
         other than 2(delete) has no effect."
    ::= { agSysApmConfig 13 }

agCurCfgAPMSharepathConfigStatus OBJECT-TYPE
    SYNTAX  INTEGER {
        inProgress(1),
        idleSucceeded (2),
        idleFailed (3)
        }
    MAX-ACCESS  read-only
    STATUS  current
    DESCRIPTION
        "Sharedpath server configuration status."
    ::= { agSysApmConfig 15 }

-- Syslog Configuration
agCurCfgSyslogHost OBJECT-TYPE
    SYNTAX  IpAddress
    MAX-ACCESS  read-only
    STATUS  current
    DESCRIPTION
        "The syslog host IP address, as currently configured in
         the current_configuration block."
    ::= { agSyslog 1 }

agNewCfgSyslogHost OBJECT-TYPE
    SYNTAX  IpAddress
    MAX-ACCESS  read-write
    STATUS  current
    DESCRIPTION
        "The syslog host IP address, in the new_configuration block."
    ::= { agSyslog 2 }

agCurCfgSyslog2Host OBJECT-TYPE
    SYNTAX  IpAddress
    MAX-ACCESS  read-only
    STATUS  current
    DESCRIPTION
        "The second syslog host IP address, as currently configured in
         the current_configuration block."
    ::= { agSyslog 3 }

agNewCfgSyslog2Host OBJECT-TYPE
    SYNTAX  IpAddress
    MAX-ACCESS  read-write
    STATUS  current
    DESCRIPTION
        "The second syslog host IP address, in the new_configuration block."
    ::= { agSyslog 4 }

agCurCfgSyslogFac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog1 host in the current_configuration block."
    ::= { agSyslog 5 }

agNewCfgSyslogFac   OBJECT-TYPE
    SYNTAX  INTEGER  {
	local0(1),
	local1(2),
	local2(3),
	local3(4),
	local4(5),
	local5(6),
        local6(7),
	local7(8)
	}
    MAX-ACCESS  read-write
    STATUS  current
    DESCRIPTION
        "The facility of syslog1 host in the new_configuration block."
    ::= { agSyslog 6 }

agCurCfgSyslog2Fac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog2 host in the current_configuration block."
    ::= { agSyslog 7 }

agNewCfgSyslog2Fac   OBJECT-TYPE
    SYNTAX  INTEGER  {
	local0(1),
	local1(2),
	local2(3),
	local3(4),
        local4(5),
	local5(6),
        local6(7),
	local7(8)
	}
    MAX-ACCESS  read-write
    STATUS  current
    DESCRIPTION
        "The facility of syslog2 host in the new_configuration block."
    ::= { agSyslog 8 }

agCurCfgSyslogSev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog1 host in the current configuration block."
    ::= { agSyslog 13 }

agNewCfgSyslogSev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslog1 host in the new configuration block."
    ::= { agSyslog 14 }

agCurCfgSyslog2Sev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog2 host in the current configuration block."
    ::= { agSyslog 15 }

agNewCfgSyslog2Sev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslog2 host in the new configuration block."
    ::= { agSyslog 16 }

agClrSyslogMsgs OBJECT-TYPE
    SYNTAX  INTEGER {
        other(1),
        reset(2)
        }
    MAX-ACCESS  read-write
    STATUS  current
    DESCRIPTION
        "Clears all current Syslog messages."
    ::= { agSyslog 9 }


agSyslogMsgTableMaxSize OBJECT-TYPE
    SYNTAX  Integer32
    MAX-ACCESS  read-only
    STATUS  current
    DESCRIPTION
        "The maximum number of rows in the syslog message table."
    ::= { agSyslog 10 }

-- Dont remove below placeholder. Real defenition is 500 rows below
--agSyslogMsgTable OBJECT-TYPE
--    SYNTAX  SEQUENCE OF AgSyslogMsgTableEntry
--    MAX-ACCESS  not-accessible
--    STATUS  current
--    DESCRIPTION
--        "The table of syslog messages."
--    ::= { agSyslog 11 }

agCurCfgSyslog3Host OBJECT-TYPE
    SYNTAX  IpAddress
    MAX-ACCESS  read-only
    STATUS  current
    DESCRIPTION
        "The third syslog host IP address, as currently configured in
         the current_configuration block."
    ::= { agSyslog 17 }

agNewCfgSyslog3Host OBJECT-TYPE
    SYNTAX  IpAddress
    MAX-ACCESS  read-write
    STATUS  current
    DESCRIPTION
        "The third syslog host IP address, in the new_configuration block."
    ::= { agSyslog 18 }

agCurCfgSyslog4Host OBJECT-TYPE
    SYNTAX  IpAddress
    MAX-ACCESS  read-only
    STATUS  current
    DESCRIPTION
        "The fourth syslog host IP address, as currently configured in
         the current_configuration block."
    ::= { agSyslog 19 }

agNewCfgSyslog4Host OBJECT-TYPE
    SYNTAX  IpAddress
    MAX-ACCESS  read-write
    STATUS  current
    DESCRIPTION
        "The fourth syslog host IP address, in the new_configuration block."
    ::= { agSyslog 20 }

agCurCfgSyslog5Host OBJECT-TYPE
    SYNTAX  IpAddress
    MAX-ACCESS  read-only
    STATUS  current
    DESCRIPTION
        "The fifth syslog host IP address, as currently configured in
         the current_configuration block."
    ::= { agSyslog 21 }

agNewCfgSyslog5Host OBJECT-TYPE
    SYNTAX  IpAddress
    MAX-ACCESS  read-write
    STATUS  current
    DESCRIPTION
        "The fifth syslog host IP address, in the new_configuration block."
    ::= { agSyslog 22 }

agCurCfgSyslog3Fac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog3 host in the current_configuration block."
    ::= { agSyslog 23 }

agNewCfgSyslog3Fac   OBJECT-TYPE
    SYNTAX  INTEGER  {
	local0(1),
	local1(2),
	local2(3),
	local3(4),
    local4(5),
	local5(6),
    local6(7),
	local7(8)
	}
    MAX-ACCESS  read-write
    STATUS  current
    DESCRIPTION
        "The facility of syslog3 host in the new_configuration block."
    ::= { agSyslog 24 }

agCurCfgSyslog4Fac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog4 host in the current_configuration block."
    ::= { agSyslog 25 }

agNewCfgSyslog4Fac   OBJECT-TYPE
    SYNTAX  INTEGER  {
	local0(1),
	local1(2),
	local2(3),
	local3(4),
    local4(5),
	local5(6),
    local6(7),
	local7(8)
	}
    MAX-ACCESS  read-write
    STATUS  current
    DESCRIPTION
        "The facility of syslog4 host in the new_configuration block."
    ::= { agSyslog 26 }

agCurCfgSyslog5Fac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of syslog5 host in the current_configuration block."
    ::= { agSyslog 27 }

agNewCfgSyslog5Fac   OBJECT-TYPE
    SYNTAX  INTEGER  {
	local0(1),
	local1(2),
	local2(3),
	local3(4),
    local4(5),
    local5(6),
    local6(7),
	local7(8)
	}
    MAX-ACCESS  read-write
    STATUS  current
    DESCRIPTION
        "The facility of syslog5 host in the new_configuration block."
    ::= { agSyslog 28 }

agCurCfgSyslog3Sev   OBJECT-TYPE
    SYNTAX  INTEGER  {
    emerg0(1),
	alert1(2),
	crit2(3),
	err3(4),
	warning4(5),
	notice5(6),
	info6(7),
	debug7(8)
	}
    MAX-ACCESS  read-only
    STATUS  current
    DESCRIPTION
        "The severity of syslog3 host in the current configuration block."
    ::= { agSyslog 29 }

agNewCfgSyslog3Sev   OBJECT-TYPE
    SYNTAX  INTEGER  {
    emerg0(1),
	alert1(2),
	crit2(3),
	err3(4),
	warning4(5),
	notice5(6),
	info6(7),
	debug7(8)
	}
    MAX-ACCESS  read-write
    STATUS  current
    DESCRIPTION
        "The severity of syslog3 host in the new configuration block."
    ::= { agSyslog 30 }

agCurCfgSyslog4Sev   OBJECT-TYPE
    SYNTAX  INTEGER  {
    emerg0(1),
	alert1(2),
	crit2(3),
	err3(4),
	warning4(5),
	notice5(6),
	info6(7),
	debug7(8)
	}
    MAX-ACCESS  read-only
    STATUS  current
    DESCRIPTION
        "The severity of syslog4 host in the current configuration block."
    ::= { agSyslog 31 }

agNewCfgSyslog4Sev   OBJECT-TYPE
    SYNTAX  INTEGER  {
    emerg0(1),
	alert1(2),
	crit2(3),
	err3(4),
	warning4(5),
	notice5(6),
	info6(7),
	debug7(8)
	}
    MAX-ACCESS  read-write
    STATUS  current
    DESCRIPTION
        "The severity of syslog4 host in the new configuration block."
    ::= { agSyslog 32 }

agCurCfgSyslog5Sev   OBJECT-TYPE
    SYNTAX  INTEGER  {
    emerg0(1),
	alert1(2),
	crit2(3),
	err3(4),
	warning4(5),
	notice5(6),
	info6(7),
	debug7(8)
	}
    MAX-ACCESS  read-only
    STATUS  current
    DESCRIPTION
        "The severity of syslog5 host in the current configuration block."
    ::= { agSyslog 33 }

agNewCfgSyslog5Sev   OBJECT-TYPE
    SYNTAX  INTEGER  {
    emerg0(1),
	alert1(2),
	crit2(3),
	err3(4),
	warning4(5),
	notice5(6),
	info6(7),
	debug7(8)
	}
    MAX-ACCESS  read-write
    STATUS  current
    DESCRIPTION
        "The severity of syslog5 host in the new configuration block."
    ::= { agSyslog 34 }

agCurCfgAuditTrail OBJECT-TYPE
    SYNTAX  INTEGER {
        enabled(1),
        disabled(2)
        }
    MAX-ACCESS  read-only
    STATUS  current
    DESCRIPTION
        "Enable or disable Configuration Audit. Enable will log configuration
	 changes in brief alongwith the user identity."
    ::= { agSyslog 35 }

agNewCfgAuditTrail OBJECT-TYPE
    SYNTAX  INTEGER {
        enabled(1),
        disabled(2)
        }
    MAX-ACCESS  read-write
    STATUS  current
    DESCRIPTION
        "Enable or disable Configuration Audit."
    ::= { agSyslog 36 }

agCurCfgSyslogHostv6 OBJECT-TYPE
    SYNTAX DisplayString (SIZE(0..40))
    MAX-ACCESS  read-only
    STATUS  current
    DESCRIPTION
    "The syslog host IPv6 address, as currently configured in
    the current_configuration block."
    ::= { agSyslog 37 }

agNewCfgSyslogHostv6 OBJECT-TYPE
    SYNTAX DisplayString (SIZE(0..40))
    MAX-ACCESS  read-write
    STATUS  current
    DESCRIPTION
    "The syslog host IPv6 address, in the new_configuration block."
    ::= { agSyslog 38 }

agCurCfgSyslog2Hostv6 OBJECT-TYPE
    SYNTAX DisplayString (SIZE(0..40))
    MAX-ACCESS  read-only
    STATUS  current
    DESCRIPTION
    "The second syslog host IPv6 address, as currently configured in
    the current_configuration block."
    ::= { agSyslog 39 }

agNewCfgSyslog2Hostv6 OBJECT-TYPE
    SYNTAX DisplayString (SIZE(0..40))
    MAX-ACCESS  read-write
    STATUS  current
    DESCRIPTION
    "The second syslog host IPv6 address, in the new_configuration block."
    ::= { agSyslog 40 }


agCurCfgSyslog3Hostv6 OBJECT-TYPE
    SYNTAX  DisplayString (SIZE(0..40))
    MAX-ACCESS  read-only
    STATUS  current
    DESCRIPTION
    "The third syslog host IPv6 address, as currently configured in
    the current_configuration block."
    ::= { agSyslog 41 }

agNewCfgSyslog3Hostv6 OBJECT-TYPE
    SYNTAX DisplayString (SIZE(0..40))
    MAX-ACCESS  read-write
    STATUS  current
    DESCRIPTION
    "The third syslog host IPv6 address, in the new_configuration block."
    ::= { agSyslog 42 }

agCurCfgSyslog4Hostv6 OBJECT-TYPE
    SYNTAX  DisplayString (SIZE(0..40))
    MAX-ACCESS  read-only
    STATUS  current
    DESCRIPTION
    "The fourth syslog host IPv6 address, as currently configured in
    the current_configuration block."
    ::= { agSyslog 43 }

agNewCfgSyslog4Hostv6 OBJECT-TYPE
    SYNTAX  DisplayString (SIZE(0..40))
    MAX-ACCESS  read-write
    STATUS  current
    DESCRIPTION
    "The fourth syslog host IPv6 address, in the new_configuration block."
    ::= { agSyslog 44 }

agCurCfgSyslog5Hostv6 OBJECT-TYPE
    SYNTAX DisplayString (SIZE(0..40))
    MAX-ACCESS  read-only
    STATUS  current
    DESCRIPTION
    "The fifth syslog host IPv6 address, as currently configured in
    the current_configuration block."
    ::= { agSyslog 45 }

agNewCfgSyslog5Hostv6 OBJECT-TYPE
    SYNTAX  DisplayString (SIZE(0..40))
    MAX-ACCESS  read-write
    STATUS  current
    DESCRIPTION
    "The fifth syslog host IPv6 address, in the new_configuration block."
    ::= { agSyslog 46 }

agSyslogMsgTable OBJECT-TYPE
    SYNTAX  SEQUENCE OF AgSyslogMsgTableEntry
    MAX-ACCESS  not-accessible
    STATUS  current
    DESCRIPTION
        "The table of syslog messages."
    ::= { agSyslog 11 }

agSyslogMsgTableEntry OBJECT-TYPE
    SYNTAX  AgSyslogMsgTableEntry
    MAX-ACCESS  not-accessible
    STATUS  current
    DESCRIPTION
        "A syslog message stored on the switch."
    INDEX   { agSyslogMsgIndex }
    ::= { agSyslogMsgTable 1 }

AgSyslogMsgTableEntry ::= SEQUENCE {
    agSyslogMsgIndex          Integer32,
    agSyslogMessage           DisplayString,
    agSyslogMessageDate       DisplayString,
    agSyslogMessageSeverity   DisplayString,
    agSyslogMessageOnly       DisplayString
    }

agSyslogMsgIndex OBJECT-TYPE
    SYNTAX  Integer32
    MAX-ACCESS  read-only
    STATUS  current
    DESCRIPTION
        "The syslog message table index."
    ::= { agSyslogMsgTableEntry 1 }

agSyslogMessage OBJECT-TYPE
    SYNTAX  DisplayString (SIZE(0..128))
    MAX-ACCESS  read-only
    STATUS  current
    DESCRIPTION
        "The syslog message."
    ::= { agSyslogMsgTableEntry 2 }

agSyslogMessageDate OBJECT-TYPE
    SYNTAX  DisplayString (SIZE(0..64))
    MAX-ACCESS  read-only
    STATUS  current
    DESCRIPTION
        "The syslog message date."
    ::= { agSyslogMsgTableEntry 3 }

agSyslogMessageSeverity OBJECT-TYPE
    SYNTAX  DisplayString (SIZE(0..32))
    MAX-ACCESS  read-only
    STATUS  current
    DESCRIPTION
        "The syslog message severity."
    ::= { agSyslogMsgTableEntry 4 }

agSyslogMessageOnly OBJECT-TYPE
    SYNTAX  DisplayString (SIZE(0..128))
    MAX-ACCESS  read-only
    STATUS  current
    DESCRIPTION
        "The syslog message plain message."
    ::= { agSyslogMsgTableEntry 5 }

--Dont remove this placeholder, real definition is below
--agSyslogSavedMsgTable OBJECT-TYPE
--    SYNTAX  SEQUENCE OF AgSyslogSavedMsgTableEntry
--    MAX-ACCESS  not-accessible
--    STATUS  current
--    DESCRIPTION
--        "The table of syslog messages saved in Flash."
--    ::= { agSyslog 47 }

agCurCfgSyslogSessLog OBJECT-TYPE
    SYNTAX  INTEGER {
	enabled(1),
	disabled(2)
    }
    MAX-ACCESS  read-only
    STATUS  current
    DESCRIPTION
       "Enable or Disable Session Logging globally."
    ::= { agSyslog 48 }

agNewCfgSyslogSessLog OBJECT-TYPE
    SYNTAX  INTEGER {
	enabled(1),
	disabled(2)
    }
    MAX-ACCESS  read-write
    STATUS  current
    DESCRIPTION
       "Enable or Disable Session Logging globally."
    ::= { agSyslog 49 }

agCurCfgSyslogSessLogFieldReal OBJECT-TYPE
    SYNTAX  INTEGER {
	enabled(1),
	disabled(2)
    }
    MAX-ACCESS  read-only
    STATUS  current
    DESCRIPTION
        "Enable or Disable Logging real server data."
::= { agSyslog 50 }

agNewCfgSyslogSessLogFieldReal OBJECT-TYPE
    SYNTAX  INTEGER {
	enabled(1),
	disabled(2)
    }
    MAX-ACCESS  read-write
    STATUS  current
    DESCRIPTION
        "Enable or Disable Logging real server data."
::= { agSyslog 51 }

agCurCfgSyslogSessLogFieldNat OBJECT-TYPE
    SYNTAX  INTEGER {
	enabled(1),
	disabled(2)
    }
    MAX-ACCESS  read-only
    STATUS  current
    DESCRIPTION
       "Enable or Disable Logging NAT data."
::= { agSyslog 52 }

agNewCfgSyslogSessLogFieldNat OBJECT-TYPE
    SYNTAX  INTEGER {
	enabled(1),
	disabled(2)
    }
    MAX-ACCESS  read-write
    STATUS  current
    DESCRIPTION
       "Enable or Disable Logging NAT data."
::= { agSyslog 53 }

agSyslogSavedMsgTable OBJECT-TYPE
    SYNTAX  SEQUENCE OF AgSyslogSavedMsgTableEntry
    MAX-ACCESS  not-accessible
    STATUS  current
    DESCRIPTION
        "The table of syslog messages saved in Flash."
    ::= { agSyslog 47 }

agSyslogSavedMsgTableEntry OBJECT-TYPE
    SYNTAX  AgSyslogSavedMsgTableEntry
    MAX-ACCESS  not-accessible
    STATUS  current
    DESCRIPTION
        "A syslog messages saved in FLASH."
    INDEX   { agSyslogMsgSavedIndex }
    ::= { agSyslogSavedMsgTable 1 }

AgSyslogSavedMsgTableEntry ::= SEQUENCE {
    agSyslogMsgSavedIndex          Integer32,
    agSyslogSavedMessage           DisplayString
    }

agSyslogMsgSavedIndex OBJECT-TYPE
    SYNTAX  Integer32
    MAX-ACCESS  read-only
    STATUS  current
    DESCRIPTION
        "The syslog Saved message table index."
    ::= { agSyslogSavedMsgTableEntry 1 }

agSyslogSavedMessage OBJECT-TYPE
    SYNTAX  DisplayString (SIZE(0..128))
    MAX-ACCESS  read-only
    STATUS  current
    DESCRIPTION
        "The syslog messages saved in FLASH."
    ::= { agSyslogSavedMsgTableEntry 2 }


agCurCfgSyslogEmail OBJECT-TYPE
    SYNTAX  INTEGER {
        enabled(1),
        disabled(2)
        }
    MAX-ACCESS  read-only
    STATUS  current
    DESCRIPTION
        "Enable or disable Log Emaling Configuration."
    ::= { agSyslog 54 }

agNewCfgSyslogEmail OBJECT-TYPE
    SYNTAX  INTEGER {
        enabled(1),
        disabled(2)
        }
    MAX-ACCESS  read-write
    STATUS  current
    DESCRIPTION
        "Enable or disable Log Emaling Configuration."
    ::= { agSyslog 55 }

agCurCfgSyslogEmailSev   OBJECT-TYPE
    SYNTAX  INTEGER  {
        emerg0(1),
	alert1(2),
	crit2(3),
	err3(4),
	warning4(5),
	notice5(6),
	info6(7),
	debug7(8)
	}
    MAX-ACCESS  read-only
    STATUS  current
    DESCRIPTION
        "The severity of syslog Emailing."
    ::= { agSyslog 56 }

agNewCfgSyslogEmailSev   OBJECT-TYPE
    SYNTAX  INTEGER  {
        emerg0(1),
	alert1(2),
	crit2(3),
	err3(4),
	warning4(5),
	notice5(6),
	info6(7),
	debug7(8)
	}
    MAX-ACCESS  read-write
    STATUS  current
    DESCRIPTION
        "The severity of syslog Emailing."
    ::= { agSyslog 57 }

agCurCfgSyslogEmailToAddress OBJECT-TYPE
    SYNTAX DisplayString (SIZE(0..256))
    MAX-ACCESS  read-only
    STATUS  current
    DESCRIPTION
    "The TO address field of the syslog  Email."
    ::= { agSyslog 58 }

agNewCfgSyslogEmailToAddress  OBJECT-TYPE
    SYNTAX DisplayString (SIZE(0..256))
    MAX-ACCESS  read-write
    STATUS  current
    DESCRIPTION
    "The TO address field of the syslog  Email."
    ::= { agSyslog 59 }

agCurCfgSyslogEmailFromAddress OBJECT-TYPE
    SYNTAX DisplayString (SIZE(0..128))
    MAX-ACCESS  read-only
    STATUS  current
    DESCRIPTION
    "The FROM address field of the syslog  Email."
    ::= { agSyslog 60 }

agNewCfgSyslogEmailFromAddress  OBJECT-TYPE
    SYNTAX DisplayString (SIZE(0..128))
    MAX-ACCESS  read-write
    STATUS  current
    DESCRIPTION
    "The FROM address field of the syslog  Email."
    ::= { agSyslog 61 }

agCurCfgSecSyslogHost OBJECT-TYPE
    SYNTAX  IpAddress
    MAX-ACCESS  read-only
    STATUS  current
    DESCRIPTION
        "The security syslog host IP address, as currently configured in
         the current_configuration block."
    ::= { agSyslog 62 }

agNewCfgSecSyslogHost OBJECT-TYPE
    SYNTAX  IpAddress
    MAX-ACCESS  read-write
    STATUS  current
    DESCRIPTION
        "The security syslog host IP address, in the new_configuration block."
    ::= { agSyslog 63 }

agCurCfgSecSyslogHostv6 OBJECT-TYPE
    SYNTAX  DisplayString (SIZE(0..40))
    MAX-ACCESS  read-only
    STATUS  current
    DESCRIPTION
    "The security syslog host IPv6 address, as currently configured in
    the current_configuration block."
    ::= { agSyslog 64 }

agNewCfgSecSyslogHostv6 OBJECT-TYPE
    SYNTAX DisplayString (SIZE(0..40))
    MAX-ACCESS  read-write
    STATUS  current
    DESCRIPTION
    "The security syslog host IPv6 address, in the new_configuration block."
    ::= { agSyslog 65 }

agCurCfgSecSyslogFac   OBJECT-TYPE
    SYNTAX  INTEGER  {
	local0(1),
	local1(2),
	local2(3),
	local3(4),
	local4(5),
	local5(6),
	local6(7),
	local7(8)
	}
    MAX-ACCESS  read-only
    STATUS  current
    DESCRIPTION
        "The facility of security syslog host in the current_configuration block."
    ::= { agSyslog 66 }

agNewCfgSecSyslogFac   OBJECT-TYPE
    SYNTAX  INTEGER  {
	local0(1),
	local1(2),
	local2(3),
	local3(4),
	local4(5),
	local5(6),
	local6(7),
	local7(8)
	}
    MAX-ACCESS  read-write
    STATUS  current
    DESCRIPTION
        "The facility of security syslog host in the new_configuration block."
    ::= { agSyslog 67 }

agCurCfgSecSyslogSev   OBJECT-TYPE
    SYNTAX  INTEGER  {
	emerg0(1),
	alert1(2),
	crit2(3),
	err3(4),
	warning4(5),
	notice5(6),
	info6(7),
	debug7(8)
	}
    MAX-ACCESS  read-only
    STATUS  current
    DESCRIPTION
        "The severity of security syslog host in the current configuration block."
    ::= { agSyslog 68 }

agNewCfgSecSyslogSev   OBJECT-TYPE
    SYNTAX  INTEGER  {
	emerg0(1),
	alert1(2),
	crit2(3),
	err3(4),
	warning4(5),
	notice5(6),
	info6(7),
	debug7(8)
	}
    MAX-ACCESS  read-write
    STATUS  current
    DESCRIPTION
        "The severity of security syslog host in the new configuration block."
    ::= { agSyslog 69 }

agCurCfgSyslogFeature   OBJECT-TYPE
    SYNTAX  INTEGER {
	all(1),
        grpmng(2),
	grpsys(3),
	grpnw(4),
	grpslb(5),
	grpsec(6),
	fastview(7),
	ha(8),
	appsvc(9),
	bgp(10),
	filter(11),
	gslb(12),
        ip(13),
        ipv6(14),
	ospf(15),
        ospfv3(16),
        ratelim(17),
        rmon(18),
        security(19),
        slb(20),
        slbatk(21),
	synatk(22),
	vlan(23),
        vrrp(24),
	cli(25),
	console(26),
	console(26),
	mgmt(27),
	ntp(28),
	ssh(29),
	stp(30),
	 stp(30),
	system(31),
	web(32),
	audit(33)
        }
    MAX-ACCESS  read-only
    STATUS  current
    DESCRIPTION
        "The Module Type of syslog1 host in the current configuration block."
    ::= { agSyslog 70 }

agNewCfgSyslogFeature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-write
    STATUS  current
    DESCRIPTION
        "The Module Type of syslog1 host in the new configuration block."
    ::= { agSyslog 71 }

agCurCfgSyslog2Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-only
    STATUS  current
    DESCRIPTION
        "The Module Type of syslog2 host in the current configuration block."
    ::= { agSyslog 72 }

agNewCfgSyslog2Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-write
    STATUS  current
    DESCRIPTION
        "The Module Type of syslog2 host in the new configuration block."
    ::= { agSyslog 73 }

agCurCfgSyslog3Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-only
    STATUS  current
    DESCRIPTION
        "The Module Type of syslog3 host in the current configuration block."
    ::= { agSyslog 74 }

agNewCfgSyslog3Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-write
    STATUS  current
    DESCRIPTION
        "The Module Type of syslog3 host in the new configuration block."
    ::= { agSyslog 75 }

agCurCfgSyslog4Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-only
    STATUS  current
    DESCRIPTION
        "The Module Type of syslog4 host in the current configuration block."
    ::= { agSyslog 76 }

agNewCfgSyslog4Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-write
    STATUS  current
    DESCRIPTION
        "The Module Type of syslog4 host in the new configuration block."
    ::= { agSyslog 77 }

agCurCfgSyslog5Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-only
    STATUS  current
    DESCRIPTION
        "The Module Type of syslog5 host in the current configuration block."
    ::= { agSyslog 78 }

agNewCfgSyslog5Feature   OBJECT-TYPE
    SYNTAX  INTEGER {
        all(1),
        grpmng(2),
        grpsys(3),
        grpnw(4),
        grpslb(5),
        grpsec(6),
        fastview(7),
        ha(8),
        appsvc(9),
        bgp(10),
        filter(11),
        gslb(12),
        ip(13),
        ipv6(14),
        ospf(15),
        ospfv3(16),
        ratelim(17),
        rmon(18),
        security(19),
        slb(20),
        slbatk(21),
        synatk(22),
        vlan(23),
        vrrp(24),
	cli(25),
        console(26),
        console(26),
        mgmt(27),
        ntp(28),
        ssh(29),
        stp(30),
         stp(30),
        system(31),
        web(32),
        audit(33)
        }
    MAX-ACCESS  read-write
    STATUS  current
    DESCRIPTION
        "The Module Type of syslog5 host in the new configuration block."
    ::= { agSyslog 79 }


agCurCfgSyslogPort OBJECT-TYPE
    SYNTAX  INTEGER (0..65535)
    MAX-ACCESS  read-only
    STATUS  current
    DESCRIPTION
        "The syslog host port number, as currently configured in
         the current_configuration block."
    ::= { agSyslog 80 }

agNewCfgSyslogPort OBJECT-TYPE
    SYNTAX  INTEGER (0..65535)
    MAX-ACCESS  read-write
    STATUS  current
    DESCRIPTION
        "The syslog host port number, in the new_configuration block."
    ::= { agSyslog 81 }


agCurCfgSyslog2Port OBJECT-TYPE
    SYNTAX  INTEGER (0..65535)
    MAX-ACCESS  read-only
    STATUS  current
    DESCRIPTION
        "The second syslog host port number, as currently configured in
         the current_configuration block."
    ::= { agSyslog 82 }

agNewCfgSyslog2Port OBJECT-TYPE
    SYNTAX  INTEGER (0..65535)
    MAX-ACCESS  read-write
    STATUS  current
    DESCRIPTION
        "The second syslog host port number, in the new_configuration block."
    ::= { agSyslog 83 }


agCurCfgSyslog3Port OBJECT-TYPE
    SYNTAX  INTEGER (0..65535)
    MAX-ACCESS  read-only
    STATUS  current
    DESCRIPTION
        "The third syslog host port number, as currently configured in
         the current_configuration block."
    ::= { agSyslog 84 }

agNewCfgSyslog3Port OBJECT-TYPE
    SYNTAX  INTEGER (0..65535)
    MAX-ACCESS  read-write
    STATUS  current
    DESCRIPTION
        "The third syslog host port number, in the new_configuration block."
    ::= { agSyslog 85 }


agCurCfgSyslog4Port OBJECT-TYPE
    SYNTAX  INTEGER (0..65535)
    MAX-ACCESS  read-only
    STATUS  current
    DESCRIPTION
        "The fourth syslog host port number, as currently configured in
         the current_configuration block."
    ::= { agSyslog 86 }

agNewCfgSyslog4Port OBJECT-TYPE
    SYNTAX  INTEGER (0..65535)
    MAX-ACCESS  read-write
    STATUS  current
    DESCRIPTION
        "The fourth syslog host port number, in the new_configuration block."
    ::= { agSyslog 87 }


agCurCfgSyslog5Port OBJECT-TYPE
    SYNTAX  INTEGER (0..65535)
    MAX-ACCESS  read-only
    STATUS  current
    DESCRIPTION
        "The fifth syslog host port number, as currently configured in
         the current_configuration block."
    ::= { agSyslog 88 }

agNewCfgSyslog5Port OBJECT-TYPE
    SYNTAX  INTEGER (0..65535)
    MAX-ACCESS  read-write
    STATUS  current
    DESCRIPTION
        "The fifth syslog host port number, in the new_configuration block."
    ::= { agSyslog 89 }

agCurCfgSyslogExtdlog OBJECT-TYPE
    SYNTAX  INTEGER {
        enabled(1),
        disabled(2)
        }
    MAX-ACCESS  read-only
    STATUS  current
    DESCRIPTION
        "Enable or disable syslog extended information. Upon enable, UTC standard
         is used for time format in syslog messages."
    ::= { agSyslog 90 }

agNewCfgSyslogExtdlog OBJECT-TYPE
    SYNTAX  INTEGER {
        enabled(1),
        disabled(2)
        }
    MAX-ACCESS  read-write
    STATUS  current
    DESCRIPTION
        "Enable or disable syslog extended information. Upon enable, UTC standard
         is used for time format in syslog messages."
    ::= { agSyslog 91 }

agCurCfgSyslogSessLogFieldMilliSec OBJECT-TYPE
    SYNTAX  INTEGER {
	enabled(1),
	disabled(2)
    }
    MAX-ACCESS  read-only
    STATUS  current
    DESCRIPTION
       "Enable or Disable millisecond time granularity."
::= { agSyslog 92 }

agNewCfgSyslogSessLogFieldMilliSec OBJECT-TYPE
    SYNTAX  INTEGER {
	enabled(1),
	disabled(2)
    }
    MAX-ACCESS  read-write
    STATUS  current
    DESCRIPTION
       "Enable or Disable millisecond time granularity."
::= { agSyslog 93 }

agNewCfgSyslogSessLogMode OBJECT-TYPE
    SYNTAX  INTEGER {
        syslog(1),
        disk(2),
        both(3)
        }
    MAX-ACCESS  read-write
    STATUS  current
    DESCRIPTION
        "This object is used to select syslog session mode.
        syslog(1)  - send the session log details to syslog server only.
        disk(2)    - write the session log details to disk(file).
        both(3)    - session log details send to syslog server and write to disk(file)"
    ::= { agSyslog 94 }

agCurCfgSyslogSessLogMode OBJECT-TYPE
    SYNTAX  INTEGER {
        syslog(1),
        disk(2),
        both(3)
        }
    MAX-ACCESS  read-only
    STATUS  current
    DESCRIPTION
        "This object is used to select syslog session mode.
        syslog(1)  - send the session log details to syslog server only.
        disk(2)    - write the session log details to disk(file).
        both(3)    - session log details send to syslog server and write to disk(file)"
    ::= { agSyslog 95 }

agLog OBJECT IDENTIFIER ::= { agSyslog 12 }
agNewCfgSyslogTrapConsole OBJECT-TYPE
    SYNTAX  INTEGER {
        enabled(1),
        disabled(2)
        }
    MAX-ACCESS  read-write
    STATUS  current
    DESCRIPTION
        "Enable or disable console syslog and SNMP trap, in the
         new_configuration block."
    ::= { agLog 1 }

agCurCfgSyslogTrapConsole OBJECT-TYPE
    SYNTAX  INTEGER {
        enabled(1),
        disabled(2)
        }
    MAX-ACCESS  read-only
    STATUS  current
    DESCRIPTION
        "Enable or disable console syslog and SNMP trap, as currently
         configured in the current_configuration block."
    ::= { agLog 2 }

agNewCfgSyslogTrapSystem OBJECT-TYPE
    SYNTAX  INTEGER {
        enabled(1),
        disabled(2)
        }
    MAX-ACCESS  read-write
    STATUS  current
    DESCRIPTION
        "Enable or disable system level syslog and SNMP trap, in the
         new_configuration block."
    ::= { agLog 3 }

agCurCfgSyslogTrapSystem OBJECT-TYPE
    SYNTAX  INTEGER {
        enabled(1),
        disabled(2)
        }
    MAX-ACCESS  read-only
    STATUS  current
    DESCRIPTION
        "Enable or disable system level syslog and SNMP trap, as currently
         configured in the current_configuration block."
    ::= { agLog 4 }

agNewCfgSyslogTrapMgmt OBJECT-TYPE
    SYNTAX  INTEGER {
        enabled(1),
        disabled(2)
        }
    MAX-ACCESS  read-write
    STATUS  current
    DESCRIPTION
        "Enable or disable management(flash, config, login) syslog and SNMP
         trap, in the new_configuration block."
    ::= { agLog 5 }

agCurCfgSyslogTrapMgmt OBJECT-TYPE
    SYNTAX  INTEGER {
        enabled(1),
        disabled(2)
        }
    MAX-ACCESS  read-only
    STATUS  current
    DESCRIPTION
        "Enable or disable management(flash, config, login) syslog and SNMP
         trap, as currently configured in the current_configuration block."
    ::= { agLog 6 }

agNewCfgSyslogTrapCli OBJECT-TYPE
    SYNTAX  INTEGER {
        enabled(1),
        disabled(2)
        }
    MAX-ACCESS  read-write
    STATUS  current
    DESCRIPTION
        "Enable or disable CLI generated error syslog and SNMP trap, in the
	 new_configuration block."
    ::= { agLog 7 }

agCurCfgSyslogTrapCli OBJECT-TYPE
    SYNTAX  INTEGER {
        enabled(1),
        disabled(2)
        }
    MAX-ACCESS  read-only
    STATUS  current
    DESCRIPTION
        "Enable or disable CLI generated error syslog and SNMP trap, as
         currently configured in the current_configuration block."
    ::= { agLog 8 }
agNewCfgSyslogTrapStp OBJECT-TYPE
    SYNTAX  INTEGER {
        enabled(1),
        disabled(2)
        }
    MAX-ACCESS  read-write
    STATUS  current
    DESCRIPTION
        "Enable or disable spanning tree syslog and SNMP trap, in the
         new_configuration block."
    ::= { agLog 9 }

agCurCfgSyslogTrapStp OBJECT-TYPE
    SYNTAX  INTEGER {
        enabled(1),
        disabled(2)
        }
    MAX-ACCESS  read-only
    STATUS  current
    DESCRIPTION
        "Enable or disable spanning tree syslog and SNMP trap, as currently
         configured in the current_configuration block."
    ::= { agLog 10 }

agNewCfgSyslogTrapVlan OBJECT-TYPE
    SYNTAX  INTEGER {
        enabled(1),
        disabled(2)
        }
    MAX-ACCESS  read-write
    STATUS  current
    DESCRIPTION
        "Enable or disable VLAN syslog and SNMP trap, in the new_configuration
         block."
    ::= { agLog 11 }

agCurCfgSyslogTrapVlan OBJECT-TYPE
    SYNTAX  INTEGER {
        enabled(1),
        disabled(2)
        }
    MAX-ACCESS  read-only
    STATUS  current
    DESCRIPTION
        "Enable or disable VLAN syslog and SNMP trap, as currently configured
         in the current_configuration block."
    ::= { agLog 12 }

agNewCfgSyslogTrapSlb OBJECT-TYPE
    SYNTAX  INTEGER {
        enabled(1),
        disabled(2)
        }
    MAX-ACCESS  read-write
    STATUS  current
    DESCRIPTION
        "Enable or disable SLB syslog and SNMP trap, in the new_configuration
         block."
    ::= { agLog 13 }

agCurCfgSyslogTrapSlb OBJECT-TYPE
    SYNTAX  INTEGER {
        enabled(1),
        disabled(2)
        }
    MAX-ACCESS  read-only
    STATUS  current
    DESCRIPTION
        "Enable or disable SLB syslog and SNMP trap, as currently configured
         in the current_configuration block."
    ::= { agLog 14 }

agNewCfgSyslogTrapGslb OBJECT-TYPE
    SYNTAX  INTEGER {
        enabled(1),
        disabled(2)
        }
    MAX-ACCESS  read-write
    STATUS  current
    DESCRIPTION
        "Enable or disable GSLB syslog and SNMP trap, in the new_configuration
         block."
    ::= { agLog 15 }

agCurCfgSyslogTrapGslb OBJECT-TYPE
    SYNTAX  INTEGER {
        enabled(1),
        disabled(2)
        }
    MAX-ACCESS  read-only
    STATUS  current
    DESCRIPTION
        "Enable or disable GSLB syslog and SNMP trap, as currently configured
         in the current_configuration block."
    ::= { agLog 16 }

agNewCfgSyslogTrapFilter OBJECT-TYPE
    SYNTAX  INTEGER {
        enabled(1),
        disabled(2)
        }
    MAX-ACCESS  read-write
    STATUS  current
    DESCRIPTION
        "Enable or disable filter syslog and SNMP trap, in the
         new_configuration block."
    ::= { agLog 17 }

agCurCfgSyslogTrapFilter OBJECT-TYPE
    SYNTAX  INTEGER {
        enabled(1),
        disabled(2)
        }
    MAX-ACCESS  read-only
    STATUS  current
    DESCRIPTION
        "Enable or disable filter syslog and SNMP trap, as currently
         configured in the current_configuration block."
    ::= { agLog 18 }

agNewCfgSyslogTrapSsh OBJECT-TYPE
    SYNTAX  INTEGER {
        enabled(1),
        disabled(2)
        }
    MAX-ACCESS  read-write
    STATUS  current
    DESCRIPTION
        "Enable or disable SSH, RADIUS syslog and SNMP trap, in the
         new_configuration block."
    ::= { agLog 19 }

agCurCfgSyslogTrapSsh OBJECT-TYPE
    SYNTAX  INTEGER {
        enabled(1),
        disabled(2)
        }
    MAX-ACCESS  read-only
    STATUS  current
    DESCRIPTION
        "Enable or disable SSH, RADIUS syslog and SNMP trap, as currently
         configured in the current_configuration block."
    ::= { agLog 20 }

agNewCfgSyslogTrapVrrp OBJECT-TYPE
    SYNTAX  INTEGER {
        enabled(1),
        disabled(2)
        }
    MAX-ACCESS  read-write
    STATUS  current
    DESCRIPTION
        "Enable or disable VRRP syslog and SNMP trap, in the new_configuration
         block."
    ::= { agLog 21 }

agCurCfgSyslogTrapVrrp OBJECT-TYPE
    SYNTAX  INTEGER {
        enabled(1),
        disabled(2)
        }
    MAX-ACCESS  read-only
    STATUS  current
    DESCRIPTION
        "Enable or disable VRRP syslog and SNMP trap, as currently configured
         in the current_configuration block."
    ::= { agLog 22 }

agNewCfgSyslogTrapBgp OBJECT-TYPE
    SYNTAX  INTEGER {
        enabled(1),
        disabled(2)
        }
    MAX-ACCESS  read-write
    STATUS  current
    DESCRIPTION
        "Enable or disable BGP syslog and SNMP trap, in the new_configuration
         block."
    ::= { agLog 23 }

agCurCfgSyslogTrapBgp OBJECT-TYPE
    SYNTAX  INTEGER {
        enabled(1),
        disabled(2)
        }
    MAX-ACCESS  read-only
    STATUS  current
    DESCRIPTION
        "Enable or disable BGP syslog and SNMP trap, as currently configured
         in the current_configuration block."
    ::= { agLog 24 }

agNewCfgSyslogTrapNtp OBJECT-TYPE
    SYNTAX  INTEGER {
        enabled(1),
        disabled(2)
        }
    MAX-ACCESS  read-write
    STATUS  current
    DESCRIPTION
        "Enable or disable NTP syslog and SNMP trap, in the new_configuration
         block."
    ::= { agLog 25 }

agCurCfgSyslogTrapNtp OBJECT-TYPE
    SYNTAX  INTEGER {
        enabled(1),
        disabled(2)
        }
    MAX-ACCESS  read-only
    STATUS  current
    DESCRIPTION
        "Enable or disable NTP syslog and SNMP trap, as currently configured
         in the current_configuration block."
    ::= { agLog 26 }

agNewCfgSyslogTrapIp OBJECT-TYPE
    SYNTAX  INTEGER {
        enabled(1),
        disabled(2)
        }
    MAX-ACCESS  read-write
    STATUS  current
    DESCRIPTION
        "Enable or disable IP related syslog and SNMP trap, in the
         new_configuration block."
    ::= { agLog 31 }

agCurCfgSyslogTrapIp OBJECT-TYPE
    SYNTAX  INTEGER {
        enabled(1),
        disabled(2)
        }
    MAX-ACCESS  read-only
    STATUS  current
    DESCRIPTION
        "Enable or disable IP related syslog and SNMP trap, as currently
         configured in the current_configuration block."
    ::= { agLog 32 }

agNewCfgSyslogTrapWeb OBJECT-TYPE
    SYNTAX  INTEGER {
        enabled(1),
        disabled(2)
        }
    MAX-ACCESS  read-write
    STATUS  current
    DESCRIPTION
        "Enable or disable WEBUI related syslog and SNMP trap, in the
         new_configuration block."
    ::= { agLog 35 }

agCurCfgSyslogTrapWeb OBJECT-TYPE
    SYNTAX  INTEGER {
        enabled(1),
        disabled(2)
        }
    MAX-ACCESS  read-only
    STATUS  current
    DESCRIPTION
        "Enable or disable WEBUI related syslog and SNMP trap, as currently
         configured in the current_configuration block."
    ::= { agLog 36 }

agNewCfgSyslogTrapSynAtk OBJECT-TYPE
    SYNTAX  INTEGER {
        enabled(1),
        disabled(2)
        }
    MAX-ACCESS  read-write
    STATUS  current
    DESCRIPTION
        "Enable or disable SYN attack detection related syslog and SNMP trap,
         in the new_configuration block."
    ::= { agLog 37 }

agCurCfgSyslogTrapSynAtk OBJECT-TYPE
    SYNTAX  INTEGER {
        enabled(1),
        disabled(2)
        }
    MAX-ACCESS  read-only
    STATUS  current
    DESCRIPTION
        "Enable or disable SYN attack detection related syslog and SNMP trap,
         as currently configured in the current_configuration block."
    ::= { agLog 38 }

agNewCfgSyslogTrapTcpLim OBJECT-TYPE
    SYNTAX  INTEGER {
        enabled(1),
        disabled(2)
        }
    MAX-ACCESS  read-write
    STATUS  current
    DESCRIPTION
        "Enable or disable TCP rate limiting related syslog and SNMP trap,
         in the new_configuration block."
    ::= { agLog 39 }

agCurCfgSyslogTrapTcpLim OBJECT-TYPE
    SYNTAX  INTEGER {
        enabled(1),
        disabled(2)
        }
    MAX-ACCESS  read-only
    STATUS  current
    DESCRIPTION
        "Enable or disable TCP rate limiting related syslog and SNMP trap,
         as currently configured in the current_configuration block."
    ::= { agLog 40 }

agNewCfgSyslogTrapOspf OBJECT-TYPE
    SYNTAX  INTEGER {
        enabled(1),
        disabled(2)
        }
    MAX-ACCESS  read-write
    STATUS  current
    DESCRIPTION
        "Enable or disable OSPF related syslog and SNMP trap,
         in the new_configuration block."
    ::= { agLog 41 }

agCurCfgSyslogTrapOspf OBJECT-TYPE
    SYNTAX  INTEGER {
        enabled(1),
        disabled(2)
        }
    MAX-ACCESS  read-only
    STATUS  current
    DESCRIPTION
        "Enable or disable OSPF related syslog and SNMP trap,
         as currently configured in the current_configuration block."
    ::= { agLog 42 }

agNewCfgSyslogTrapSecurity OBJECT-TYPE
    SYNTAX  INTEGER {
        enabled(1),
        disabled(2)
        }
    MAX-ACCESS  read-write
    STATUS  current
    DESCRIPTION
        "Enable or disable Security pack related syslog and SNMP trap,
         in the new_configuration block."
    ::= { agLog 43 }

agCurCfgSyslogTrapSecurity OBJECT-TYPE
    SYNTAX  INTEGER {
        enabled(1),
        disabled(2)
        }
    MAX-ACCESS  read-only
    STATUS  current
    DESCRIPTION
        "Enable or disable Security pack related syslog and SNMP trap,
         as currently configured in the current_configuration block."
    ::= { agLog 44 }

agNewCfgSyslogTrapRmon OBJECT-TYPE
    SYNTAX  INTEGER {
        enabled(1),
        disabled(2)
        }
    MAX-ACCESS  read-write
    STATUS  current
    DESCRIPTION
        "Enable or disable rmon related syslog and SNMP trap,
         in the new_configuration block."
    ::= { agLog 45 }

agCurCfgSyslogTrapRmon OBJECT-TYPE
    SYNTAX  INTEGER {
        enabled(1),
        disabled(2)
        }
    MAX-ACCESS  read-only
    STATUS  current
    DESCRIPTION
        "Enable or disable rmon related syslog and SNMP trap,
         as currently configured in the current_configuration block."
    ::= { agLog 46 }

agNewCfgSyslogTrapSlbAtk OBJECT-TYPE
    SYNTAX  INTEGER {
        enabled(1),
        disabled(2)
        }
    MAX-ACCESS  read-write
    STATUS  current
    DESCRIPTION
        "Enable or disable SLB ATK related syslog and SNMP trap,
         in the new_configuration block."
    ::= { agLog 47 }

agCurCfgSyslogTrapSlbAtk  OBJECT-TYPE
    SYNTAX  INTEGER {
        enabled(1),
        disabled(2)
        }
    MAX-ACCESS  read-only
    STATUS  current
    DESCRIPTION
        "Enable or disable SLB ATK related syslog and SNMP trap,
         as currently configured in the current_configuration block."
    ::= { agLog 48 }

agNewCfgSyslogTrapIpv6 OBJECT-TYPE
    SYNTAX  INTEGER {
        enabled(1),
        disabled(2)
        }
    MAX-ACCESS  read-write
    STATUS  current
    DESCRIPTION
        "Enable or disable IPV6 related syslog and SNMP trap,
         in the new_configuration block."
    ::= { agLog 49 }

agCurCfgSyslogTrapIpv6  OBJECT-TYPE
    SYNTAX  INTEGER {
        enabled(1),
        disabled(2)
        }
    MAX-ACCESS  read-only
    STATUS  current
    DESCRIPTION
        "Enable or disable IPV6 related syslog and SNMP trap,
         as currently configured in the current_configuration block."
    ::= { agLog 50 }

agNewCfgSyslogTrapAppSvc OBJECT-TYPE
    SYNTAX  INTEGER {
        enabled(1),
        disabled(2)
        }
    MAX-ACCESS  read-write
    STATUS  current
    DESCRIPTION
        "Enable or disable Application service related syslog and SNMP trap,
         in the new_configuration block."
    ::= { agLog 51 }

agCurCfgSyslogTrapAppSvc  OBJECT-TYPE
    SYNTAX  INTEGER {
        enabled(1),
        disabled(2)
        }
    MAX-ACCESS  read-only
    STATUS  current
    DESCRIPTION
        "Enable or disable Application service related syslog and SNMP trap,
         as currently configured in the current_configuration block."
    ::= { agLog 52 }

agNewCfgSyslogTrapFastView OBJECT-TYPE
    SYNTAX  INTEGER {
        enabled(1),
        disabled(2)
        }
    MAX-ACCESS  read-write
    STATUS  current
    DESCRIPTION
        "Enable or disable FastView related syslog and SNMP trap,
         in the new_configuration block."
    ::= { agLog 53 }

agCurCfgSyslogTrapFastView  OBJECT-TYPE
    SYNTAX  INTEGER {
        enabled(1),
        disabled(2)
        }
    MAX-ACCESS  read-only
    STATUS  current
    DESCRIPTION
        "Enable or disable FastView related syslog and SNMP trap,
         as currently configured in the current_configuration block."
    ::= { agLog 54 }

agNewCfgSyslogTrapHA OBJECT-TYPE
    SYNTAX  INTEGER {
        enabled(1),
        disabled(2)
        }
    MAX-ACCESS  read-write
    STATUS  current
    DESCRIPTION
        "Enable or disable HA related syslog and SNMP trap,
         in the new_configuration block."
    ::= { agLog 55 }

agCurCfgSyslogTrapHA  OBJECT-TYPE
    SYNTAX  INTEGER {
        enabled(1),
        disabled(2)
        }
    MAX-ACCESS  read-only
    STATUS  current
    DESCRIPTION
        "Enable or disable HA related syslog and SNMP trap,
         as currently configured in the current_configuration block."
    ::= { agLog 56 }

agNewCfgSyslogTrapOspfv3 OBJECT-TYPE
    SYNTAX  INTEGER {
        enabled(1),
        disabled(2)
        }
    MAX-ACCESS  read-write
    STATUS  current
    DESCRIPTION
        "Enable or disable Ospfv3 related syslog and SNMP trap,
         in the new_configuration block."
    ::= { agLog 57 }

agCurCfgSyslogTrapOspfv3  OBJECT-TYPE
    SYNTAX  INTEGER {
        enabled(1),
        disabled(2)
        }
    MAX-ACCESS  read-only
    STATUS  current
    DESCRIPTION
        "Enable or disable Ospfv3 related syslog and SNMP trap,
         as currently configured in the current_configuration block."
    ::= { agLog 58 }
agNewCfgSyslogTrapAudit OBJECT-TYPE
    SYNTAX  INTEGER {
        enabled(1),
        disabled(2)
        }
    MAX-ACCESS  read-write
    STATUS  current
    DESCRIPTION
        "Enable or disable Audit related syslog and SNMP trap,
         in the new_configuration block."
    ::= { agLog 59 }

agCurCfgSyslogTrapAudit  OBJECT-TYPE
    SYNTAX  INTEGER {
        enabled(1),
        disabled(2)
        }
    MAX-ACCESS  read-only
    STATUS  current
    DESCRIPTION
        "Enable or disable Audit related syslog and SNMP trap,
         as currently configured in the current_configuration block."
    ::= { agLog 60 }

agNewCfgSyslogUrlf OBJECT-TYPE
    SYNTAX  INTEGER {
        enabled(1),
        disabled(2)
        }
    MAX-ACCESS  read-write
    STATUS  current
    DESCRIPTION
        "Enable or disable URLF related syslog ,
         in the new_configuration block."
    ::= { agLog 61 }

agCurCfgSyslogUrlf  OBJECT-TYPE
    SYNTAX  INTEGER {
        enabled(1),
        disabled(2)
        }
    MAX-ACCESS  read-only
    STATUS  current
    DESCRIPTION
        "Enable or disable URLF related syslog,
         as currently configured in the current_configuration block."
    ::= { agLog 62 }

agNewCfgSyslogTrapIprep OBJECT-TYPE
    SYNTAX  INTEGER {
        enabled(1),
        disabled(2)
        }
    MAX-ACCESS  read-write
    STATUS  current
    DESCRIPTION
        "Enable or disable IP REP related syslog ,
         in the new_configuration block."
    ::= { agLog 63 }

agCurCfgSyslogTrapIprep  OBJECT-TYPE
    SYNTAX  INTEGER {
        enabled(1),
        disabled(2)
        }
    MAX-ACCESS  read-only
    STATUS  current
    DESCRIPTION
        "Enable or disable IP REP related syslog,
         as currently configured in the current_configuration block."
    ::= { agLog 64 }

-- Trap host table
agTrapHostTableMaxEnt OBJECT-TYPE
    SYNTAX  Integer32
    MAX-ACCESS  read-only
    STATUS  current
    DESCRIPTION
        "The maximum number of rows in the trap host table."
    ::= { agTrapHost 1 }

agCurCfgTrapHostTable OBJECT-TYPE
    SYNTAX  SEQUENCE OF AgCurCfgTrapHostEntry
    MAX-ACCESS  not-accessible
    STATUS  current
    DESCRIPTION
        "The table of trap hosts which to send SNMP traps in the
         current_configuration block."
    ::= { agTrapHost 2 }

agCurCfgTrapHostEntry OBJECT-TYPE
    SYNTAX  AgCurCfgTrapHostEntry
    MAX-ACCESS  not-accessible
    STATUS  current
    DESCRIPTION
        "A row in the trap host table in the current_configuration block."
    INDEX   { agCurCfgTrapHostIndx }
    ::= { agCurCfgTrapHostTable 1 }

AgCurCfgTrapHostEntry ::= SEQUENCE {
    agCurCfgTrapHostIndx            Integer32,
    agCurCfgTrapHostIpAddr          IpAddress,
    agCurCfgTrapHostCommString      DisplayString
    }

agCurCfgTrapHostIndx OBJECT-TYPE
    SYNTAX  Integer32
    MAX-ACCESS  read-only
    STATUS  current
    DESCRIPTION
        "The index of the row in trap host table."
    ::= { agCurCfgTrapHostEntry 1 }

agCurCfgTrapHostIpAddr OBJECT-TYPE
    SYNTAX  IpAddress
    MAX-ACCESS  read-only
    STATUS  current
    DESCRIPTION
        "The IP address of a trap host."
    ::= { agCurCfgTrapHostEntry 2 }

agCurCfgTrapHostCommString OBJECT-TYPE
    SYNTAX  DisplayString (SIZE (0..32))
    MAX-ACCESS  read-only
    STATUS  current
    DESCRIPTION
        "The SNMP community string to use with the trap host"
    ::= { agCurCfgTrapHostEntry 3 }

agNewCfgTrapHostTable OBJECT-TYPE
    SYNTAX  SEQUENCE OF AgNewCfgTrapHostEntry
    MAX-ACCESS  not-accessible
    STATUS  current
    DESCRIPTION
        "The table of trap hosts which to send SNMP traps in the
          new_configuration block."
    ::= { agTrapHost 3 }

agNewCfgTrapHostEntry OBJECT-TYPE
    SYNTAX  AgNewCfgTrapHostEntry
    MAX-ACCESS  not-accessible
    STATUS  current
    DESCRIPTION
        "A row in the trap host table in the new_configuration block."
    INDEX   { agNewCfgTrapHostIndx }
    ::= { agNewCfgTrapHostTable 1 }

AgNewCfgTrapHostEntry ::= SEQUENCE {
    agNewCfgTrapHostIndx            Integer32,
    agNewCfgTrapHostIpAddr          IpAddress,
    agNewCfgTrapHostCommString      DisplayString
    }

agNewCfgTrapHostIndx OBJECT-TYPE
    SYNTAX  Integer32
    MAX-ACCESS  read-only
    STATUS  current
    DESCRIPTION
        "The index of the row in trap host table."
    ::= { agNewCfgTrapHostEntry 1 }

agNewCfgTrapHostIpAddr OBJECT-TYPE
    SYNTAX  IpAddress
    MAX-ACCESS  read-write
    STATUS  current
    DESCRIPTION
        "The IP address of a trap host."
    ::= { agNewCfgTrapHostEntry 2 }

agNewCfgTrapHostCommString OBJECT-TYPE
    SYNTAX  DisplayString (SIZE (0..32))
    MAX-ACCESS  read-write
    STATUS  current
    DESCRIPTION
        "The SNMP community string to use with the trap host"
    ::= { agNewCfgTrapHostEntry 3 }

-- TFTP Config
agTftpServer OBJECT-TYPE
    SYNTAX  DisplayString (SIZE(0..128))
    MAX-ACCESS  read-write
    STATUS  current
    DESCRIPTION
        "The TFTP server IP address or domain name."
    ::= { agTftp 1 }


agTftpImage OBJECT-TYPE
    SYNTAX  INTEGER {
        image1(2),
        image2(3)
        }
    MAX-ACCESS  read-write
    STATUS  current
    DESCRIPTION
        "Whether the image file should be loaded in image1 or image2 in flash."
    ::= { agTftp 2 }


agTftpImageFileName OBJECT-TYPE
    SYNTAX  DisplayString (SIZE(0..128))
    MAX-ACCESS  read-write
    STATUS  current
    DESCRIPTION
        "The image file name to be downloaded."
    ::= { agTftp 3 }

agTftpCfgFileName OBJECT-TYPE
    SYNTAX  DisplayString (SIZE(0..128))
    MAX-ACCESS  read-write
    STATUS  current
    DESCRIPTION
        "The configuration file name."
    ::= { agTftp 4 }

agTftpDumpFileName OBJECT-TYPE
    SYNTAX  DisplayString (SIZE(0..128))
    MAX-ACCESS  read-write
    STATUS  current
    DESCRIPTION
        "The file name for core dump."
    ::= { agTftp 5 }

agTftpAction OBJECT-TYPE
    SYNTAX  INTEGER {
        other(1),
        img-get(2),
        cfg-get(3),
        cfg-put(4),
        dump-put(5),
        bkpdump-put(6),
        tsdump-put(8),
        bogon-get(9)
        ,xml-get(14)
        ,applog-export(15)
        ,cert-export(16)
        ,cert-import(17)
        ,put-techdata(18)
        ,sesslog-export(19)
        ,sshkey-export(20)
        ,sshkey-import(21)
        }
    MAX-ACCESS  read-write
    STATUS  current
    DESCRIPTION
        "This is an action object to perform various TFTP Get or Put functions.
         The TFTP sever is specified in agTftpServer object.
	 img-get(2)    - Download switch image from a specified image
                         file (agTftpImageFileName) on the TFTP server to
	                 the destinated storage (agTftpImage).
	 cfg-get(3)    - Download switch configuration from a specified
                         file (agTftpCfgFileName) on the TFTP server.
	 cfg-put(4)    - Upload switch configuration to a specified
                         file (agTftpCfgFileName) on the TFTP server.
	 dump-put(5)   - Download switch core dump to a specified
                         file (agTftpDumpFileName) on the TFTP server.
	 bkpdump-put(6)- Download switch backup core dump to a specified
                         file (agTftpDumpFileName) on the TFTP server.
         tsdump-put(8) - Download switch tech support dump to a specified
                         file (agTftpTSDumpFileName) on the TFTP server.
	 bogon-get(9)  - Download bogon config file from a specified bogon
                         file (uses agTftpImageFileName) on the TFTP server.
         xml-get(14)   - Import XML client certificate to a specified
                         file (agTftpCfgFileName) on the TFTP server.
         put-techdata(18) - Upload full tech support data via FTP/TFTP/SCP.
         sesslog-export(19) - Export the session log to a specific file (tftpSessLogFile)
                         to the FTP/SCP server
         sshkey-export(20) - Export the session log to a specific file (tftpSshKeyFile)
                         to the FTP/SCP server
         sshkey-import(21) - Import the session log from a specific file (tftpSshKeyFile)
                         on FTP/SCP.
         other(1) is returned always when read."
    ::= { agTftp 6 }

agTftpLastActionStatus OBJECT-TYPE
    SYNTAX  DisplayString (SIZE(0..256))
    MAX-ACCESS  read-only
    STATUS  current
    DESCRIPTION
        "The recorded status of the previous TFTP activity."
    ::= { agTftp 7 }

agTftpPort OBJECT-TYPE
    SYNTAX  INTEGER {
        data(1),
        mgmt(2)
        }
    MAX-ACCESS  read-write
    STATUS  current
    DESCRIPTION
        "Specify whether the TFTP operation should be performed over the
         data port or the management port.In the case of Admin context only
         mgmt(2) is valid.Setting with data(1) will return an error"
    ::= { agTftp 8 }

agTftpUserName OBJECT-TYPE
    SYNTAX  DisplayString (SIZE(0..128))
    MAX-ACCESS  read-write
    STATUS  current
    DESCRIPTION
        "The username for FTP server or blank for TFTP server."
    ::= { agTftp 9 }

agTftpPassword OBJECT-TYPE
    SYNTAX  DisplayString (SIZE(0..128))
    MAX-ACCESS  read-write
    STATUS  current
    DESCRIPTION
        "The password for FTP server."
    ::= { agTftp 10 }

agTftpTSDumpFileName OBJECT-TYPE
    SYNTAX  DisplayString (SIZE(0..128))
    MAX-ACCESS  read-write
    STATUS  current
    DESCRIPTION
        "The file name for TS dump."
    ::= { agTftp 11 }

agTftpTechDataFileName OBJECT-TYPE
    SYNTAX  DisplayString (SIZE(0..128))
    MAX-ACCESS  read-write
    STATUS  current
    DESCRIPTION
        "The file name for Tech Data."
    ::= { agTftp 12 }



agTftpVersionPass OBJECT-TYPE
    SYNTAX  DisplayString (SIZE(0..8))
    MAX-ACCESS  read-write
    STATUS  current
    DESCRIPTION
        "The password for upgraded version."
    ::= { agTftp 14 }

agTftpMode OBJECT-TYPE
   SYNTAX  INTEGER {
    tftp(1),
    ftp(2),
    scp(3)
    }
   MAX-ACCESS  read-write
   STATUS  current
   DESCRIPTION
        "Wheather the mode of operation should be TFTP or FTP or SCP."
   ::= { agTftp 15 }

agTftpConfigOption OBJECT-TYPE
   SYNTAX  INTEGER {
    all(1),
    global(2),
    vADC(3),
    pvadc(4)
    }
   MAX-ACCESS  read-write
   STATUS  current
   DESCRIPTION
        "Wheather the put or get configuration option should be all or global or vADC configurations.
         Note:This mib is supported only in VX instance on Virtualization."
   ::= { agTftp 16 }
agTftpConfigOptionvADC OBJECT-TYPE
   SYNTAX DisplayString (SIZE(0..64))
   MAX-ACCESS  read-write
   STATUS  current
   DESCRIPTION
        "The vADC's indexes for put or get vADC configuration option. It should be
	 string all or separated with comma(,) or hypen(-).
	 Example:
	   all
	   2,5,28
	   3-7
           Note:This mib is supported only in VX instance on Virtualization."
   ::= { agTftp 17 }
agTftpConfigTypevADC OBJECT-TYPE
   SYNTAX  INTEGER {
    all(1),
    vadmin(2)
    }
   MAX-ACCESS  read-write
   STATUS  current
   DESCRIPTION
        "The vADC's type for put or get vADC configuration option.
         Note:This mib is supported only in VX instance on Virtualization."
   ::= { agTftp 18 }

agTftpImageAdc OBJECT-TYPE
    SYNTAX  INTEGER (1..10)
    MAX-ACCESS  read-write
    STATUS  current
    DESCRIPTION
        "The Image ID in which to load the new image"
    ::= { agTftp 19 }

agTftpImageVx OBJECT-TYPE
    SYNTAX  INTEGER (1..4)
    MAX-ACCESS  read-write
    STATUS  current
    DESCRIPTION
        "The Image ID in which to load the new VX image"
    ::= { agTftp 20 }

agTftpSSLCertType OBJECT-TYPE
   SYNTAX  INTEGER {
    key(1),
    srvrcert(2),
    cert-key(3),
    request(4),
    intermca(5),
    trustca(6),
    crl(7)
    }
   MAX-ACCESS  read-write
   STATUS  current
   DESCRIPTION
        "The type of certificate component to import/export."
   ::= { agTftp 21 }

agTftpSSLCertId OBJECT-TYPE
   SYNTAX  DisplayString (SIZE(0..128))
   MAX-ACCESS  read-write
   STATUS  current
   DESCRIPTION
        "The type of certificate component to import/export."
   ::= { agTftp 22 }

agTftpSSLCertKeyPassphrase OBJECT-TYPE
   SYNTAX  DisplayString (SIZE(4..40))
   MAX-ACCESS  read-write
   STATUS  current
   DESCRIPTION
        "The Passphrase key which is used for key import/export."
   ::= { agTftp 23 }

agTftpSSLCertFileName OBJECT-TYPE
    SYNTAX  DisplayString (SIZE(0..128))
    MAX-ACCESS  read-write
    STATUS  current
    DESCRIPTION
        "The file name for SSL Certificate\Key dump."
    ::= { agTftp 24 }

agTftpPrivateKeys OBJECT-TYPE
    SYNTAX  INTEGER {
        yes(1),
        no(2)
        }
    MAX-ACCESS  read-write
    STATUS  current
    DESCRIPTION
        "Include Private Keys. If 'yes', requires pass phrase to be entered
         by the user. By Default, private keys are not included."
    ::= { agTftp 25 }

agTftpPrivateKeyPassPhrase OBJECT-TYPE
    SYNTAX  DisplayString (SIZE(4..40))
    MAX-ACCESS  read-write
    STATUS  current
    DESCRIPTION
        "Pass phrase for including private keys in the config file."
    ::= { agTftp 26 }

agTftpPrivateKeyConfPassPhrase OBJECT-TYPE
    SYNTAX  DisplayString (SIZE(4..40))
    MAX-ACCESS  read-write
    STATUS  current
    DESCRIPTION
        "Confirm private key pass phrase."
    ::= { agTftp 27 }

agTftpAllowedNetworks OBJECT-TYPE
    SYNTAX  INTEGER {
       yes(1),
       no(2)
       }
    MAX-ACCESS  read-write
    STATUS  current
    DESCRIPTION
        "Configure allowed networks. If yes, configure allowed networks
         by the user. By default no, allowed networks not configured."
    ::= { agTftp 28 }

agCfgTftpHostIPVersion OBJECT-TYPE
    SYNTAX  INTEGER {
        ipv4(4),
        ipv6(6)
        }
    MAX-ACCESS  read-write
    STATUS  current
    DESCRIPTION
        "IP version for TFTP host name(agTftpServer). Always, first SET the TFTP hostname and this object."
    ::= { agTftp 29 }

agTftpImageType OBJECT-TYPE
    SYNTAX  INTEGER {
        other(0),
        vx(1),
        adc(2),
        vxAdc(3)
        }
    MAX-ACCESS  read-write
    STATUS  current
    DESCRIPTION
        "Image type to be downloaded."
    ::= { agTftp 30 }

agTftpImageDownloadStatus OBJECT-TYPE
    SYNTAX  INTEGER {
        unKnown(0),
        failed(1),
        inProgress(2),
        successful(3)
        }
    MAX-ACCESS  read-only
    STATUS  current
    DESCRIPTION
        "Last Image Download status."
    ::= { agTftp 31 }

agTftpManSync OBJECT-TYPE
    SYNTAX  INTEGER {
        none(1),
        mansync(2)
        }
    MAX-ACCESS  read-write
    STATUS  current
    DESCRIPTION
        "Allows the user to send mansync option in getcfg and ptcfg."
    ::= { agTftp 32 }

agTftpPrevArchSessLogFile OBJECT-TYPE
    SYNTAX  INTEGER {
        yes(1),
        no(2)
        }
    MAX-ACCESS  read-write
    STATUS  current
    DESCRIPTION
        "Export previously archived session Log File. If 'yes', export the already archived session log file.
            By Default, create new session log archive file."
    ::= { agTftp 33 }

agTftpSessLogFileName OBJECT-TYPE
    SYNTAX  DisplayString (SIZE(0..128))
    MAX-ACCESS  read-write
    STATUS  current
    DESCRIPTION
        "The export file name for session log."
    ::= { agTftp 34 }

agTftpSshKeyFileName OBJECT-TYPE
    SYNTAX  DisplayString (SIZE(0..128))
    MAX-ACCESS  read-write
    STATUS  current
    DESCRIPTION
        "The import/export file name for ssh public key."
    ::= { agTftp 35 }


-- Agent Port Table

agPortTableMaxEnt OBJECT-TYPE
    SYNTAX  Integer32
    MAX-ACCESS  read-only
    STATUS  current
    DESCRIPTION
        "The maximum number of rows in the port configuration host table.
        Note: This mib is only supported in VX instance of Virtualization."
    ::= { agPortConfig 1 }

agPortCurCfgTable OBJECT-TYPE
    SYNTAX  SEQUENCE OF AgPortCurCfgTableEntry
    MAX-ACCESS  not-accessible
    STATUS  current
    DESCRIPTION
        "The table of port configuration in the current_configuration block.
        Note: This table is only supported in VX instance of Virtualization."
    ::= { agPortConfig 2 }

agPortCurCfgTableEntry OBJECT-TYPE
    SYNTAX  AgPortCurCfgTableEntry
    MAX-ACCESS  not-accessible
    STATUS  current
    DESCRIPTION
        "A row in the port table in the current_configuration block."
    INDEX   { agPortCurCfgIndx }
    ::= { agPortCurCfgTable 1 }

AgPortCurCfgTableEntry ::= SEQUENCE {
    agPortCurCfgIndx             Integer32,
    agPortCurCfgState            INTEGER,
    agPortCurCfgVlanTag          INTEGER,
    agPortCurCfgRmon             INTEGER,
    agPortCurCfgPVID             Integer32,
    agPortCurCfgFastEthAutoNeg   INTEGER,
    agPortCurCfgFastEthSpeed     INTEGER,
    agPortCurCfgFastEthMode      INTEGER,
    agPortCurCfgFastEthFctl      INTEGER,
    agPortCurCfgGigEthAutoNeg    INTEGER,
    agPortCurCfgGigEthFctl       INTEGER,
    agPortCurCfgBwmContract      Integer32,
    agPortCurCfgDiscardNonIPs    INTEGER,
    agPortCurCfgLinkTrap         INTEGER,
    agPortCurCfgPreferred        INTEGER,
    agPortCurCfgBackup           INTEGER,
    agPortCurCfgEgressBW         DisplayString,
    agPortCurCfgNonIPBwmContract Integer32,
    agPortCurCfgGigEthSpeed      INTEGER,
    agPortCurCfgGigEthMode       INTEGER,
    agPortCurCfgPortAlias        DisplayString,
    agPortCurCfgPortName         DisplayString,
    agPortCurCfgPortStp          INTEGER,
    agPortCurCfgPortIpFwd        INTEGER
    }

agPortCurCfgIndx OBJECT-TYPE
    SYNTAX  Integer32
    MAX-ACCESS  read-only
    STATUS  current
    DESCRIPTION
        "The index of the row in port configurations table.
        Note: This mib is only supported in VX instance of Virtualization."
    ::= { agPortCurCfgTableEntry 1 }

agPortCurCfgState OBJECT-TYPE
    SYNTAX  INTEGER {
        enabled(2),
        disabled(3),
	blocked(4)
	}
    MAX-ACCESS  read-only
    STATUS  current
    DESCRIPTION
        "This is the state of the port."
    ::= { agPortCurCfgTableEntry 2 }

agPortCurCfgVlanTag OBJECT-TYPE
    SYNTAX  INTEGER {
        tagged(2),
        untagged(3)
        }
    MAX-ACCESS  read-only
    STATUS  current
    DESCRIPTION
        "This is VLAN tag state of the port"
    ::= { agPortCurCfgTableEntry 3 }

agPortCurCfgRmon OBJECT-TYPE
    SYNTAX  INTEGER {
        on(2),
        off(3)
        }
    MAX-ACCESS  read-only
    STATUS  current
    DESCRIPTION
        "This object is used to turn RMON on or off on the port."
   ::= { agPortCurCfgTableEntry 5 }

agPortCurCfgPVID OBJECT-TYPE
    SYNTAX  Integer32
    MAX-ACCESS  read-only
    STATUS  current
    DESCRIPTION
        "The default VLAN ID for the port."
    ::= { agPortCurCfgTableEntry 6 }

agPortCurCfgFastEthAutoNeg OBJECT-TYPE
    SYNTAX  INTEGER {
        on(2),
        off(3),
	auto(4)
        }
    MAX-ACCESS  read-only
    STATUS  current
    DESCRIPTION
        "This object is used to turn the autonegotiation on or off
         for fast Ethernet connection."
    ::= { agPortCurCfgTableEntry 7 }

agPortCurCfgFastEthSpeed OBJECT-TYPE
    SYNTAX  INTEGER {
        mbs10(2),
        mbs100(3),
        any(4),
        mbs1000(5),
        mbs10000(6),
        mbs40000(7),
        auto(8),
        mbs100000(9),
	mbs25000(10)
        }
    MAX-ACCESS  read-only
    STATUS  current
    DESCRIPTION
        "Selects the port speed for fast Ethernet connection."
    ::= { agPortCurCfgTableEntry 8 }

agPortCurCfgFastEthMode OBJECT-TYPE
    SYNTAX  INTEGER {
        full-duplex(2),
        half-duplex(3),
        full-or-half-duplex(4)
        }
    MAX-ACCESS  read-only
    STATUS  current
    DESCRIPTION
        "This object is used to select port mode for fast Ethernet connection."
    ::= { agPortCurCfgTableEntry 9 }

agPortCurCfgFastEthFctl OBJECT-TYPE
    SYNTAX  INTEGER {
        transmit(2),
        receive(3),
        both(4),
        none(5)
        }
    MAX-ACCESS  read-only
    STATUS  current
    DESCRIPTION
        "Selects the port flow control for fast Ethernet connection."
    ::= { agPortCurCfgTableEntry 10 }

agPortCurCfgGigEthAutoNeg OBJECT-TYPE
    SYNTAX  INTEGER {
        on(2),
        off(3)
        }
    MAX-ACCESS  read-only
    STATUS  current
    DESCRIPTION
        "This object is used to turn the autonegotiation on or off
         for gigabit Ethernet connection."
    ::= { agPortCurCfgTableEntry 11 }

agPortCurCfgGigEthFctl OBJECT-TYPE
    SYNTAX  INTEGER {
        transmit(2),
        receive(3),
        both(4),
        none(5)
        }
    MAX-ACCESS  read-only
    STATUS  current
    DESCRIPTION
        "This object is used to select port flow control for
         gigabit Ethernet connection."
    ::= { agPortCurCfgTableEntry 12 }

agPortCurCfgPortName	OBJECT-TYPE
    SYNTAX  DisplayString (SIZE(0..63))
    MAX-ACCESS  read-only
    STATUS  current
    DESCRIPTION
        "The switch port name."
    ::= { agPortCurCfgTableEntry 13 }

agPortCurCfgBwmContract OBJECT-TYPE
    SYNTAX  Integer32
    MAX-ACCESS  read-only
    STATUS  current
    DESCRIPTION
        "The switch port Bandwidth Management contract number."
    ::= { agPortCurCfgTableEntry 14 }

agPortCurCfgDiscardNonIPs OBJECT-TYPE
    SYNTAX  INTEGER {
        enabled(2),
        disabled(3)
        }
    MAX-ACCESS  read-only
    STATUS  current
    DESCRIPTION
        "Enable or disable to discard all non-IP traffic on the switch port."
    ::= { agPortCurCfgTableEntry 15 }

agPortCurCfgLinkTrap OBJECT-TYPE
    SYNTAX  INTEGER {
	enabled(1),
	disabled(2)
    }
    MAX-ACCESS  read-only
    STATUS  current
    DESCRIPTION
        "Indicates whether linkUp/linkDown traps should be
        generated for this interface.

        By default, this object should have the value
        enabled(1) for interfaces which do not operate on
        'top' of any other interface (as defined in the
        ifStackTable), and disabled(2) otherwise."
    ::= { agPortCurCfgTableEntry 16 }

agPortCurCfgPreferred OBJECT-TYPE
    SYNTAX  INTEGER {
        copper(1),
        sfp(2)
        }
    MAX-ACCESS  read-only
    STATUS  current
    DESCRIPTION
        "This object is used to set the preferred port. Valid only on dual ports."
   ::= { agPortCurCfgTableEntry 17 }

agPortCurCfgBackup OBJECT-TYPE
    SYNTAX  INTEGER {
	none(2),
        copper(3),
        sfp(4)
        }
    MAX-ACCESS  read-only
    STATUS  current
    DESCRIPTION
        "This object is used to set the backup port. Valid only on dual ports."
   ::= { agPortCurCfgTableEntry 18 }

agPortCurCfgEgressBW OBJECT-TYPE
    SYNTAX DisplayString (SIZE(0..9))
    MAX-ACCESS read-only
    STATUS current
    DESCRIPTION
        "The configured egress bandwidth limit for this port. This is the
         maximum egress bandwidth available to this port if BWM is on."
    ::= { agPortCurCfgTableEntry 19 }

agPortCurCfgNonIPBwmContract OBJECT-TYPE
    SYNTAX  Integer32
    MAX-ACCESS  read-only
    STATUS  current
    DESCRIPTION
        "The BWM contract for non-IP traffic."
    ::= { agPortCurCfgTableEntry 20 }

agPortCurCfgGigEthSpeed OBJECT-TYPE
    SYNTAX  INTEGER {
        mbs10(2),
        mbs100(3),
        any(4),
        mbs1000(5)
        ,mbs10000(6)
        ,mbs40000(7)
        ,mbs100000(9)
	,mbs25000(10)
        }
    MAX-ACCESS  read-only
    STATUS  current
    DESCRIPTION
        "Selects the port speed for Gigabit Ethernet connection."
    ::= { agPortCurCfgTableEntry 21 }

agPortCurCfgGigEthMode OBJECT-TYPE
    SYNTAX  INTEGER {
        full-duplex(2),
        half-duplex(3),
        full-or-half-duplex(4)
        }
    MAX-ACCESS  read-only
    STATUS  current
    DESCRIPTION
        "This object is used to select port mode for Gigabit Ethernet connection."
    ::= { agPortCurCfgTableEntry 22 }


agPortCurCfgPortAlias    OBJECT-TYPE
    SYNTAX  DisplayString (SIZE(0..15))
    MAX-ACCESS  read-only
    STATUS  current
    DESCRIPTION
        "The switch port alias."
    ::= { agPortCurCfgTableEntry 24 }

agPortCurCfgPortStp OBJECT-TYPE
    SYNTAX  INTEGER {
        on(1),
        off(2)
        }
    MAX-ACCESS  read-only
    STATUS  current
    DESCRIPTION
        "This is the state of the Spanning Tree."
    ::= { agPortCurCfgTableEntry 26 }

agPortCurCfgPortIpFwd OBJECT-TYPE
    SYNTAX  INTEGER {
        enabled(1),
        disabled(2)
        }
    MAX-ACCESS  read-only
    STATUS  current
    DESCRIPTION
        "This is the state of the IP Forwarding."
    ::= { agPortCurCfgTableEntry 27 }

agPortNewCfgTable OBJECT-TYPE
    SYNTAX  SEQUENCE OF AgPortNewCfgTableEntry
    MAX-ACCESS  not-accessible
    STATUS  current
    DESCRIPTION
        "The table of port configuration in the new_configuration block."
    ::= { agPortConfig 3 }

agPortNewCfgTableEntry OBJECT-TYPE
    SYNTAX  AgPortNewCfgTableEntry
    MAX-ACCESS  not-accessible
    STATUS  current
    DESCRIPTION
        "A row in the port configuration table in the new_configuration block."
    INDEX   { agPortNewCfgIndx }
    ::= { agPortNewCfgTable 1 }

AgPortNewCfgTableEntry ::= SEQUENCE {
    agPortNewCfgIndx             Integer32,
    agPortNewCfgState            INTEGER,
    agPortNewCfgVlanTag          INTEGER,
    agPortNewCfgRmon             INTEGER,
    agPortNewCfgPVID             Integer32,
    agPortNewCfgFastEthAutoNeg   INTEGER,
    agPortNewCfgFastEthSpeed     INTEGER,
    agPortNewCfgFastEthMode      INTEGER,
    agPortNewCfgFastEthFctl      INTEGER,
    agPortNewCfgGigEthAutoNeg    INTEGER,
    agPortNewCfgGigEthFctl       INTEGER,
    agPortNewCfgPortName         DisplayString,
    agPortNewCfgBwmContract      Integer32,
    agPortNewCfgDiscardNonIPs    INTEGER,
    agPortNewCfgLinkTrap         INTEGER,
    agPortNewCfgPreferred        INTEGER,
    agPortNewCfgBackup           INTEGER,
    agPortNewCfgEgressBW         DisplayString,
    agPortNewCfgNonIPBwmContract Integer32,
    agPortNewCfgGigEthSpeed      INTEGER,
    agPortNewCfgGigEthMode       INTEGER,
    agPortNewCfgPortAlias        DisplayString,
    agPortNewCfgPortName         DisplayString,
    agPortNewCfgPortStp          INTEGER,
    agPortNewCfgPortIpFwd        INTEGER
    }

agPortNewCfgIndx OBJECT-TYPE
    SYNTAX  Integer32
    MAX-ACCESS  read-only
    STATUS  current
    DESCRIPTION
        "The index of the row in port configurations table."
    ::= { agPortNewCfgTableEntry 1 }

agPortNewCfgState OBJECT-TYPE
    SYNTAX  INTEGER {
        enabled(2),
        disabled(3)
        }
    MAX-ACCESS  read-write
    STATUS  current
    DESCRIPTION
        "This is the state of the port."
    ::= { agPortNewCfgTableEntry 2 }

agPortNewCfgVlanTag OBJECT-TYPE
    SYNTAX  INTEGER {
        tagged(2),
        untagged(3)
        }
    MAX-ACCESS  read-write
    STATUS  current
    DESCRIPTION
        "This is VLAN tag state of the port"
    ::= { agPortNewCfgTableEntry 3 }

agPortNewCfgRmon OBJECT-TYPE
    SYNTAX  INTEGER {
        on(2),
        off(3)
        }
    MAX-ACCESS  read-write
    STATUS  current
    DESCRIPTION
        "This object is used to turn RMON on or off on the port."
    ::= { agPortNewCfgTableEntry 5 }

agPortNewCfgPVID OBJECT-TYPE
    SYNTAX  Integer32
    MAX-ACCESS  read-write
    STATUS  current
    DESCRIPTION
        "The default VLAN ID for the port."
    ::= { agPortNewCfgTableEntry 6 }

agPortNewCfgFastEthAutoNeg OBJECT-TYPE
    SYNTAX  INTEGER {
        on(2),
        off(3),
	auto(4)
        }
    MAX-ACCESS  read-write
    STATUS  current
    DESCRIPTION
        "This object is used to turn the autonegotiation on or off
         for fast Ethernet connection."
    ::= { agPortNewCfgTableEntry 7 }

agPortNewCfgFastEthSpeed OBJECT-TYPE
    SYNTAX  INTEGER {
        mbs10(2),
        mbs100(3),
        any(4),
        mbs1000(5),
        mbs10000(6),
		mbs40000(7),
        auto(8),
        mbs100000(9),
	mbs25000(10)
        }
    MAX-ACCESS  read-write
    STATUS  current
    DESCRIPTION
        "Selects the port speed for fast Ethernet connection."
    ::= { agPortNewCfgTableEntry 8 }

agPortNewCfgFastEthMode OBJECT-TYPE
    SYNTAX  INTEGER {
        full-duplex(2),
        half-duplex(3),
        full-or-half-duplex(4)
        }
    MAX-ACCESS  read-write
    STATUS  current
    DESCRIPTION
        "This object is used to select port mode for fast Ethernet connection."
    ::= { agPortNewCfgTableEntry 9 }

agPortNewCfgFastEthFctl OBJECT-TYPE
    SYNTAX  INTEGER {
        transmit(2),
        receive(3),
        both(4),
        none(5)
        }
    MAX-ACCESS  read-write
    STATUS  current
    DESCRIPTION
        "Selects the port flow control for fast Ethernet connection."
    ::= { agPortNewCfgTableEntry 10 }

agPortNewCfgGigEthAutoNeg OBJECT-TYPE
    SYNTAX  INTEGER {
        on(2),
        off(3)
        }
    MAX-ACCESS  read-write
    STATUS  current
    DESCRIPTION
        "This object is used to turn the autonegotiation on or off
         for gigabit Ethernet connection."
    ::= { agPortNewCfgTableEntry 11 }

agPortNewCfgGigEthFctl OBJECT-TYPE
    SYNTAX  INTEGER {
        transmit(2),
        receive(3),
        both(4),
        none(5)
       }
    MAX-ACCESS  read-write
    STATUS  current
    DESCRIPTION
        "This object is used to select port flow control for
         gigabit Ethernet connection."
    ::= { agPortNewCfgTableEntry 12 }

agPortNewCfgPortName	OBJECT-TYPE
    SYNTAX  DisplayString (SIZE(0..63))
    MAX-ACCESS  read-write
    STATUS  current
    DESCRIPTION
        "The switch port name."
    ::= { agPortNewCfgTableEntry 13 }

agPortNewCfgBwmContract OBJECT-TYPE
    SYNTAX  Integer32
    MAX-ACCESS  read-write
    STATUS  current
    DESCRIPTION
        "The switch port Bandwidth Management contract number."
    ::= { agPortNewCfgTableEntry 14 }

agPortNewCfgDiscardNonIPs OBJECT-TYPE
    SYNTAX  INTEGER {
        enabled(2),
        disabled(3)
        }
    MAX-ACCESS  read-write
    STATUS  current
    DESCRIPTION
        "Enable or disable to discard all non-IP traffic on the switch port."
    ::= { agPortNewCfgTableEntry 15 }

agPortNewCfgLinkTrap OBJECT-TYPE
    SYNTAX  INTEGER {
	enabled(1),
	disabled(2)
    }
    MAX-ACCESS  read-write
    STATUS  current
    DESCRIPTION
        "Indicates whether linkUp/linkDown traps should be
        generated for this interface.

        By default, this object should have the value
        enabled(1) for interfaces which do not operate on
        'top' of any other interface (as defined in the
        ifStackTable), and disabled(2) otherwise."
    ::= { agPortNewCfgTableEntry 16 }

agPortNewCfgPreferred OBJECT-TYPE
    SYNTAX  INTEGER {
        copper(1),
        sfp(2)
    }
    MAX-ACCESS  read-write
    STATUS  current
    DESCRIPTION
        "This object is used to set the preferred port. Valid only on dual ports."
   ::= { agPortNewCfgTableEntry 17 }

agPortNewCfgBackup OBJECT-TYPE
    SYNTAX  INTEGER {
	none(1),
        copper(2),
        sfp(3)
    }
    MAX-ACCESS  read-write
    STATUS  current
    DESCRIPTION
        "This object is used to set the backup port. Valid only on dual ports."
   ::= { agPortNewCfgTableEntry 18 }

agPortNewCfgEgressBW OBJECT-TYPE
    SYNTAX DisplayString (SIZE(0..9))
    MAX-ACCESS read-write
    STATUS current
    DESCRIPTION
        "The configured egress bandwidth limit for this port. This is the
         maximum egress bandwidth available to this port if BWM is on."
    ::= { agPortNewCfgTableEntry 19 }

agPortNewCfgNonIPBwmContract OBJECT-TYPE
    SYNTAX  Integer32
    MAX-ACCESS  read-write
    STATUS  current
    DESCRIPTION
        "The BWM contract for non-IP traffic"
    ::= { agPortNewCfgTableEntry 20 }

agPortNewCfgGigEthSpeed OBJECT-TYPE
    SYNTAX  INTEGER {
        mbs10(2),
        mbs100(3),
        any(4),
        mbs1000(5)
       ,mbs10000(6)
       ,mbs40000(7)
       ,mbs100000(9)
       ,mbs25000(10)
        }
    MAX-ACCESS  read-write
    STATUS  current
    DESCRIPTION
        "Selects the port speed for Gigabit Ethernet connection."
    ::= { agPortNewCfgTableEntry 21 }

agPortNewCfgGigEthMode OBJECT-TYPE
    SYNTAX  INTEGER {
        full-duplex(2),
        half-duplex(3),
        full-or-half-duplex(4)
        }
    MAX-ACCESS  read-write
    STATUS  current
    DESCRIPTION
        "This object is used to select port mode for Gigabit Ethernet connection."
    ::= { agPortNewCfgTableEntry 22 }


agPortNewCfgPortAlias    OBJECT-TYPE
    SYNTAX  DisplayString (SIZE(0..15))
    MAX-ACCESS  read-write
    STATUS  current
    DESCRIPTION
        "The switch port alias."
    ::= { agPortNewCfgTableEntry 24 }

agPortNewCfgPortStp OBJECT-TYPE
    SYNTAX  INTEGER {
        on(1),
        off(2)
        }
    MAX-ACCESS  read-write
    STATUS  current
    DESCRIPTION
        "This is the state of the spanning tree."
    ::= { agPortNewCfgTableEntry 26 }

agPortNewCfgPortIpFwd OBJECT-TYPE
    SYNTAX  INTEGER {
        enabled(1),
        disabled(2)
        }
    MAX-ACCESS  read-write
    STATUS  current
    DESCRIPTION
        "This is the state of the IP Forwarding."
    ::= { agPortNewCfgTableEntry 27 }

-- Agent Fast Forwarding Port Table

-- RADIUS Configuration

radCurCfgPrimaryIpAddr OBJECT-TYPE
    SYNTAX  IpAddress
    MAX-ACCESS  read-only
    STATUS  current
    DESCRIPTION
        "The IP address of the Primary RADIUS server."
    ::= { agRadiusConfig 1 }

radNewCfgPrimaryIpAddr OBJECT-TYPE
    SYNTAX  IpAddress
    MAX-ACCESS  read-write
    STATUS  current
    DESCRIPTION
        "The IP address of the Primary RADIUS server."
    ::= { agRadiusConfig 2 }

radCurCfgSecondaryIpAddr OBJECT-TYPE
    SYNTAX  IpAddress
    MAX-ACCESS  read-only
    STATUS  current
    DESCRIPTION
        "The IP address of the Secondary RADIUS server."
    ::= { agRadiusConfig 3 }

radNewCfgSecondaryIpAddr OBJECT-TYPE
    SYNTAX  IpAddress
    MAX-ACCESS  read-write
    STATUS  current
    DESCRIPTION
        "The IP address of the Secondary RADIUS server."
    ::= { agRadiusConfig 4 }

radCurCfgPort OBJECT-TYPE
    SYNTAX  INTEGER  (1500..3000)
    MAX-ACCESS  read-only
    STATUS  current
    DESCRIPTION
        "Specify the RADIUS port number."
    ::= { agRadiusConfig 5 }

radNewCfgPort OBJECT-TYPE
    SYNTAX  INTEGER  (1500..3000)
    MAX-ACCESS  read-write
    STATUS  current
    DESCRIPTION
        "Specify the RADIUS port number."
    ::= { agRadiusConfig 6 }

radCurCfgTimeout OBJECT-TYPE
    SYNTAX  INTEGER  (1..60)
    MAX-ACCESS  read-only
    STATUS  current
    DESCRIPTION
        "The maximum number of seconds before resending authentication
         to RADIUS server."
    ::= { agRadiusConfig 7 }

radNewCfgTimeout OBJECT-TYPE
    SYNTAX  INTEGER  (1..60)
    MAX-ACCESS  read-write
    STATUS  current
    DESCRIPTION
        "The maximum number of seconds before resending authentication
         to RADIUS server."
    ::= { agRadiusConfig 8 }

radCurCfgRetries OBJECT-TYPE
    SYNTAX  INTEGER  (1..3)
    MAX-ACCESS  read-only
    STATUS  current
    DESCRIPTION
        "Number of retries to the RADIUS server."
    ::= { agRadiusConfig 9 }

radNewCfgRetries OBJECT-TYPE
    SYNTAX  INTEGER  (1..3)
    MAX-ACCESS  read-write
    STATUS  current
    DESCRIPTION
        "Number of retries to the RADIUS server."
    ::= { agRadiusConfig 10 }

radCurCfgState OBJECT-TYPE
    SYNTAX  INTEGER {
        enabled(2),
        disabled(3)
        }
    MAX-ACCESS  read-only
    STATUS  current
    DESCRIPTION
        "Enable or disbale RADIUS authentication."
    ::= { agRadiusConfig 11 }

radNewCfgState OBJECT-TYPE
    SYNTAX  INTEGER {
        enabled(2),
        disabled(3)
        }
    MAX-ACCESS  read-write
    STATUS  current
    DESCRIPTION
        "Enable or disable RADIUS authentication."
    ::= { agRadiusConfig 12 }

radCurCfgAuthenString OBJECT-TYPE
    SYNTAX  DisplayString (SIZE(0..32))
    MAX-ACCESS  read-only
    STATUS  current
    DESCRIPTION
        "The RADIUS authentication string."
    ::= { agRadiusConfig 13 }

radNewCfgAuthenString OBJECT-TYPE
    SYNTAX  DisplayString (SIZE(0..32))
    MAX-ACCESS  read-write
    STATUS  current
    DESCRIPTION
        "The RADIUS authentication string."
    ::= { agRadiusConfig 14 }

radCurCfgTelnet OBJECT-TYPE
    SYNTAX  INTEGER {
        enabled(1),
        disabled(2)
        }
    MAX-ACCESS  read-only
    STATUS  current
    DESCRIPTION
        "Enable or disbale RADIUS backdoor for telnet."
    ::= { agRadiusConfig 15 }

radNewCfgTelnet OBJECT-TYPE
    SYNTAX  INTEGER {
        enabled(1),
        disabled(2)
        }
    MAX-ACCESS  read-write
    STATUS  current
    DESCRIPTION
        "Enable or disable RADIUS backdoor for telnet."
    ::= { agRadiusConfig 16 }

radCurCfgAuthenSecondString OBJECT-TYPE
    SYNTAX  DisplayString (SIZE(0..32))
    MAX-ACCESS  read-only
    STATUS  current
    DESCRIPTION
        "The second RADIUS authentication string."
    ::= { agRadiusConfig 17 }

radNewCfgAuthenSecondString OBJECT-TYPE
    SYNTAX  DisplayString (SIZE(0..32))
    MAX-ACCESS  read-write
    STATUS  current
    DESCRIPTION
        "The second RADIUS authentication string."
    ::= { agRadiusConfig 18 }

radCurCfgSecBd OBJECT-TYPE
    SYNTAX  INTEGER {
        enabled(1),
        disabled(2)
        }
    MAX-ACCESS  read-only
    STATUS  current
    DESCRIPTION
        "Enable or disbale RADIUS secure backdoor for telnet."
    ::= { agRadiusConfig 19 }

radNewCfgSecBd OBJECT-TYPE
    SYNTAX  INTEGER {
        enabled(1),
        disabled(2)
        }
    MAX-ACCESS  read-write
    STATUS  current
    DESCRIPTION
        "Enable or disable RADIUS secure backdoor for telnet."
    ::= { agRadiusConfig 20 }

radCurCfgPrimaryIpv6Addr OBJECT-TYPE
    SYNTAX DisplayString (SIZE(0..40))
    MAX-ACCESS read-only
    STATUS current
    DESCRIPTION
        "The IPv6 address of the Primary RADIUS server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agRadiusConfig 21 }

radNewCfgPrimaryIpv6Addr OBJECT-TYPE
    SYNTAX DisplayString (SIZE(0..40))
    MAX-ACCESS read-write
    STATUS current
    DESCRIPTION
        "The IPv6 address of the Primary RADIUS server.
        Address should be 16-byte haxadecimal colon notation.
        Valid IPv6 address should be in any of the following forms
        xxxx:xxxx:xxxx:xxxx:xxxx:xxxx:xxxx:xxxx or
        xxxx::xxxx:xxxx:xxxx:xxxx or ::xxxx"
    ::= { agRadiusConfig 22 }

radCurCfgSecondaryIpv6Addr OBJECT-TYPE
    SYNTAX DisplayString (SIZE(0..40))
    MAX-ACCESS read-only
    STATUS current
    DESCRIPTION
        "The IPv6 address of the Secondary RADIUS server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agRadiusConfig 23 }

radNewCfgSecondaryIpv6Addr OBJECT-TYPE
    SYNTAX DisplayString (SIZE(0..40))
    MAX-ACCESS read-write
    STATUS current
    DESCRIPTION
        "The IPv6 address of the Secondary RADIUS server.
        Address should be 16-byte haxadecimal colon notation.
        Valid IPv6 address should be in any of the following forms
        xxxx:xxxx:xxxx:xxxx:xxxx:xxxx:xxxx:xxxx or
        xxxx::xxxx:xxxx:xxxx:xxxx or ::xxxx"
    ::= { agRadiusConfig 24 }

radCurCfgOtp OBJECT-TYPE
    SYNTAX  INTEGER {
        enabled(1),
        disabled(2)
        }
    MAX-ACCESS  read-only
    STATUS  current
    DESCRIPTION
        "Enable/Disable Radius OTP User Server Configuration."
    ::= { agRadiusConfig 25 }

radNewCfgOtp OBJECT-TYPE
    SYNTAX  INTEGER {
        enabled(1),
        disabled(2)
        }
    MAX-ACCESS  read-write
    STATUS  current
    DESCRIPTION
        "Enable/Disable Radius OTP User Server Configuration."
    ::= { agRadiusConfig 26 }

radCurCfgLocalAuth OBJECT-TYPE
    SYNTAX  INTEGER {
        localFirst(1),
        disabled(2)
        }
    MAX-ACCESS  read-only
    STATUS  current
    DESCRIPTION
        "Enable or disbale RADIUS local user authentication."
    ::= { agRadiusConfig 27 }

radNewCfgLocalAuth OBJECT-TYPE
    SYNTAX  INTEGER {
        localFirst(1),
        disabled(2)
        }
    MAX-ACCESS  read-write
    STATUS  current
    DESCRIPTION
        "Enable or disable RADIUS local user authentication."
    ::= { agRadiusConfig 28 }



-- GEL License manager Oper
lmLicOperPendingEntitlementId OBJECT-TYPE
    SYNTAX  DisplayString (SIZE(0..255))
    MAX-ACCESS  read-write
    STATUS  current
    DESCRIPTION
        "GEL: set pending entitlement ID."
    ::= { agLMLicenseOper 1 }

lmLicOperThroughput OBJECT-TYPE
    SYNTAX  INTEGER
    MAX-ACCESS  read-write
    STATUS  current
    DESCRIPTION
        "GEL: set pending throughput (Mbps)."
    ::= { agLMLicenseOper 2 }

lmLicOperSubscrAddOn OBJECT-TYPE
     SYNTAX  INTEGER {
         ignore(0),
         perform(2),
         secure(3)
        }
     MAX-ACCESS  read-write
     STATUS  current
     DESCRIPTION
         "GEL: set/ignore pending subsciption add-on."
     ::= { agLMLicenseOper 5}

lmLicOperRmkey OBJECT-TYPE
    SYNTAX  INTEGER {
        all(0),
        perform(2),
        secure(3)
--        idle(6),
--        inprogress(7),
--        complete(8),
--        failed(9)
       }
    MAX-ACCESS  read-write
    STATUS  current
    DESCRIPTION
        "GEL: Enter software feature to be removed."
    ::= { agLMLicenseOper 3}

lmLicOperSynclic OBJECT-TYPE
    SYNTAX  INTEGER  {
        start(0)
--        idle(1),
--        inprogress(2),
--        complete(3),
--        failed(4)
       }
    MAX-ACCESS  read-write
    STATUS  current
    DESCRIPTION
        "GEL: Synchronize license with the license server (use new features configured via SNMP if exist)."
--         When this object is read the current state is returned.
--         'idle' indicates that there is no communication with license server in progess.
--         'complete' indicates that the last operation is completed.
--         Setting the value to 'start', will write all the changes if found, and start new syncronize.
--         If succesfull will return the state 'complete' else it will return 'failed'.
--         TBD_LM - In case of failure, to read the reason for failure use the lmLicOperStateTable.
--         Once the operation is completed or the agLicOperStatusTable is read in case
--         of failure, the reason buffer needs to be freed and the lmLicOperState
--         should be set back to 'idle' state so others can issue the sync command via SNMP."
    ::= { agLMLicenseOper 4}
-- GEL License manager Oper end

-- GEL License Manager Configuration
curCfgLmLicInterval OBJECT-TYPE
    SYNTAX  INTEGER  (1..86400)
    MAX-ACCESS  read-only
    STATUS  current
    DESCRIPTION
        "Specify the time interval to check with the license server the validity of the checked out licenses."
    ::= { agLMLicenseConfig 1 }

newCfgLmLicInterval OBJECT-TYPE
    SYNTAX  INTEGER  (1..86400)
    MAX-ACCESS  read-write
    STATUS  current
    DESCRIPTION
        "Specify the time interval to check with the license server the validity of the checked out licenses."
    ::= { agLMLicenseConfig 2 }

curCfgLmLicEnable OBJECT-TYPE
    SYNTAX  INTEGER {
        enabled(1),
        disabled(2)
        }
    MAX-ACCESS  read-only
    STATUS  current
    DESCRIPTION
        "Enable or disable license server integration."
    ::= { agLMLicenseConfig 3 }

newCfgLmLicEnable OBJECT-TYPE
    SYNTAX  INTEGER {
        enabled(1),
        disabled(2)
        }
    MAX-ACCESS  read-write
    STATUS  current
    DESCRIPTION
        "Enable or disable license server integration."
    ::= { agLMLicenseConfig 4 }

curCfgLmLicRetryInterval OBJECT-TYPE
    SYNTAX  INTEGER  (1..3600)
    MAX-ACCESS  read-only
    STATUS  current
    DESCRIPTION
        "Specify the retry interval in case of communication failure with the license server."
    ::= { agLMLicenseConfig 5 }

newCfgLmLicRetryInterval OBJECT-TYPE
    SYNTAX  INTEGER  (1..3600)
    MAX-ACCESS  read-write
    STATUS  current
    DESCRIPTION
        "Specify the retry interval in case of communication failure with the license server."
    ::= { agLMLicenseConfig 6 }

curCfgLmLicPrimaryURL OBJECT-TYPE
    SYNTAX  DisplayString (SIZE(0..255))
    MAX-ACCESS  read-only
    STATUS  current
    DESCRIPTION
        "Set primary license server URL."
    ::= { agLMLicenseConfig 7 }

newCfgLmLicPrimaryURL OBJECT-TYPE
    SYNTAX  DisplayString (SIZE(0..255))
    MAX-ACCESS  read-write
    STATUS  current
    DESCRIPTION
        "Set primary license server URL."
    ::= { agLMLicenseConfig 8 }

curCfgLmLicRetries OBJECT-TYPE
    SYNTAX  INTEGER  (1..100)
    MAX-ACCESS  read-only
    STATUS  current
    DESCRIPTION
        "Set number of retries for determining communication failure."
    ::= { agLMLicenseConfig 9 }

newCfgLmLicRetries OBJECT-TYPE
    SYNTAX  INTEGER  (1..100)
    MAX-ACCESS  read-write
    STATUS  current
    DESCRIPTION
        "Set number of retries for determining communication failure."
    ::= { agLMLicenseConfig 10 }

curCfgLmLicSecondaryURL OBJECT-TYPE
    SYNTAX  DisplayString (SIZE(0..255))
    MAX-ACCESS  read-only
    STATUS  current
    DESCRIPTION
        "Set secondary license server URL."
    ::= { agLMLicenseConfig 11 }

newCfgLmLicSecondaryURL OBJECT-TYPE
    SYNTAX  DisplayString (SIZE(0..255))
    MAX-ACCESS  read-write
    STATUS  current
    DESCRIPTION
        "Set secondary license server URL."
    ::= { agLMLicenseConfig 12 }

-- All below code is out of 32.2, so excluding it
-- curCfgLmLicETLEnable OBJECT-TYPE
--     SYNTAX  INTEGER {
--         enabled(1),
--         disabled(2)
--         }
--     MAX-ACCESS  read-only
--     STATUS  current
--     DESCRIPTION
--         "Enable or disable elastic throughput license."
--     ::= { agLMLicenseConfig 13 }

--newCfgLmLicETLEnable OBJECT-TYPE
--    SYNTAX  INTEGER {
--        enabled(1),
--        disabled(2)
--        }
--    MAX-ACCESS  read-write
--    STATUS  current
--    DESCRIPTION
--        "Enable or disable elastic throughput license."
--    ::= { agLMLicenseConfig 14 }

--curCfgLmLicETLPercent OBJECT-TYPE
--    SYNTAX  INTEGER  (1..3600)
--    MAX-ACCESS  read-only
--    STATUS  current
--    DESCRIPTION
--        "Set percent of the sustained throughput beyond the threshold."
--    ::= { agLMLicenseConfig 15 }

--newCfgLmLicETLPercent OBJECT-TYPE
--    SYNTAX  INTEGER  (1..3600)
--    MAX-ACCESS  read-write
--    STATUS  current
--    DESCRIPTION
--        "Set percent of the sustained throughput beyond the threshold."
--    ::= { agLMLicenseConfig 16 }

--curCfgLmLicETLUpThreshold OBJECT-TYPE
--    SYNTAX  INTEGER  (1..3600)
--    MAX-ACCESS  read-only
--    STATUS  current
--    DESCRIPTION
--        "Set scale-up throughput license threshold."
--    ::= { agLMLicenseConfig 17 }

--newCfgLmLicETLUpThreshold OBJECT-TYPE
--    SYNTAX  INTEGER  (1..3600)
--    MAX-ACCESS  read-write
--    STATUS  current
--    DESCRIPTION
--        "Set scale-up throughput license threshold."
--    ::= { agLMLicenseConfig 18}


--curCfgLmLicETLDownThreshold OBJECT-TYPE
--    SYNTAX  INTEGER  (1..3600)
--    MAX-ACCESS  read-only
--    STATUS  current
--    DESCRIPTION
--        "Set scale-down throughput license threshold."
--    ::= { agLMLicenseConfig 19 }

--newCfgLmLicETLDownThreshold OBJECT-TYPE
--    SYNTAX  INTEGER  (1..3600)
--    MAX-ACCESS  read-write
--    STATUS  current
--    DESCRIPTION
--        "Set scale-down throughput license threshold."
--    ::= { agLMLicenseConfig 20}

--curCfgLmLicETLUpime OBJECT-TYPE
--    SYNTAX  INTEGER  (1..3600)
--    MAX-ACCESS  read-only
--    STATUS  current
--    DESCRIPTION
--        "Set scale-up sustained time."
--    ::= { agLMLicenseConfig 21 }

--newCfgLmLicETLUpTime OBJECT-TYPE
--    SYNTAX  INTEGER  (1..3600)
--    MAX-ACCESS  read-write
--    STATUS  current
--    DESCRIPTION
--       "Set scale-up sustained time."
--    ::= { agLMLicenseConfig 22}

--curCfgLmLicETLDownime OBJECT-TYPE
--    SYNTAX  INTEGER  (1..3600)
--    MAX-ACCESS  read-only
--    STATUS  current
--   DESCRIPTION
--        "Set scale-down sustained time."
--    ::= { agLMLicenseConfig 23 }

--newCfgLmLicETLDownTime OBJECT-TYPE
--    SYNTAX  INTEGER  (1..3600)
--    MAX-ACCESS  read-write
--    STATUS  current
--    DESCRIPTION
--        "Set scale-down sustained time."
--    ::= { agLMLicenseConfig 24}

--curCfgLmLicETLMaxTput OBJECT-TYPE
--    SYNTAX  INTEGER  (1..3600)
--    MAX-ACCESS  read-only
--    STATUS  current
--    DESCRIPTION
--        "Set maximum throughput license."
--    ::= { agLMLicenseConfig 25 }

--newCfgLmLicETLMaxTput OBJECT-TYPE
--    SYNTAX  INTEGER  (1..3600)
--    MAX-ACCESS  read-write
--    STATUS  current
--    DESCRIPTION
--        "Set maximum throughput license."
--    ::= { agLMLicenseConfig 26}

--curCfgLmLicETLMinTput OBJECT-TYPE
--    SYNTAX  INTEGER  (1..3600)
--    MAX-ACCESS  read-only
--    STATUS  current
--   DESCRIPTION
--        "Set minimum throughput license."
--    ::= { agLMLicenseConfig 27 }

--newCfgLmLicETLMinTput OBJECT-TYPE
--    SYNTAX  INTEGER  (1..3600)
--    MAX-ACCESS  read-write
--    STATUS  current
--    DESCRIPTION
--        "Set minimum throughput license."
--    ::= { agLMLicenseConfig 28}

-- License manager END

-- GEL License Manager Info
lmLicInfoPrimaryTimestamp OBJECT-TYPE
    SYNTAX  DisplayString (SIZE(0..255))
    MAX-ACCESS  read-only
    STATUS  current
    DESCRIPTION
        "GEL: get last communication with Primary server timestamp."
    ::= { agLMLicenseInfo 1 }

lmLicInfoSecondaryTimestamp OBJECT-TYPE
    SYNTAX  DisplayString (SIZE(0..255))
    MAX-ACCESS  read-only
    STATUS  current
    DESCRIPTION
        "GEL: get last communication with Secondary server timestamp."
    ::= { agLMLicenseInfo 2 }

lmLicInfoHostId OBJECT-TYPE
    SYNTAX  DisplayString (SIZE(0..255))
    MAX-ACCESS  read-only
    STATUS  current
    DESCRIPTION
        "GEL: get host ID."
    ::= { agLMLicenseInfo 3 }

lmLicInfoDeviceName OBJECT-TYPE
    SYNTAX  DisplayString (SIZE(0..65))
    MAX-ACCESS  read-only
    STATUS  current
    DESCRIPTION
        "GEL: get device name."
    ::= { agLMLicenseInfo 4 }

lmLicInfoCurEntitlementId OBJECT-TYPE
    SYNTAX  DisplayString (SIZE(0..255))
    MAX-ACCESS  read-only
    STATUS  current
    DESCRIPTION
        "GEL: get current entitlement ID."
    ::= { agLMLicenseInfo 5 }

lmLicInfoPendingEntitlementId OBJECT-TYPE
    SYNTAX  DisplayString (SIZE(0..255))
    MAX-ACCESS  read-only
    STATUS  current
    DESCRIPTION
        "GEL: get pending entitlement ID."
    ::= { agLMLicenseInfo 6 }

lmLicInfoRejectedEntitlementId OBJECT-TYPE
    SYNTAX  DisplayString (SIZE(0..255))
    MAX-ACCESS  read-only
    STATUS  current
    DESCRIPTION
        "GEL: get rejected entitlement ID."
    ::= { agLMLicenseInfo 7 }

lmLicInfoPrimaryAttemptTimestamp OBJECT-TYPE
    SYNTAX  DisplayString (SIZE(0..255))
    MAX-ACCESS  read-only
    STATUS  current
    DESCRIPTION
        "GEL: get last communication attempt with Primary server timestamp."
    ::= { agLMLicenseInfo 8 }

lmLicInfoSecondaryAttemptTimestamp OBJECT-TYPE
    SYNTAX  DisplayString (SIZE(0..255))
    MAX-ACCESS  read-only
    STATUS  current
    DESCRIPTION
        "GEL: get last communication attempt with Secondary server timestamp."
    ::= { agLMLicenseInfo 9 }

--lmLicInfoProductsTable OBJECT-TYPE
--    SYNTAX  SEQUENCE OF lmLicInfoProductsEntry
--    MAX-ACCESS  not-accessible
--    STATUS  current
--    DESCRIPTION
--        "The table of Global Elastic License features."
--    ::= { agLMLicenseInfo 10 }

--lmLicInfoProductsEntry OBJECT-TYPE
--    SYNTAX  lmLicInfoProductsEntry
--    MAX-ACCESS  not-accessible
--    STATUS  current
--    DESCRIPTION
--        "Information about a particular license Manager Product configuration."
--    INDEX   { lmLicInfoProductId }
--    ::= { lmLicInfoProductsTable 1 }

--lmLicInfoProductsEntry ::= SEQUENCE {
--    lmLicInfoProductId                 DisplayString,
--    lmLicInfoProductQty                INTEGER,
--    lmLicInfoProductExpiration         DisplayString,
--    lmLicInfoProductLastValidated      DisplayString,
--    lmLicInfoProductStatus             DisplayString
--    }

--lmLicInfoProductId OBJECT-TYPE
--    SYNTAX DisplayString (SIZE(1..43))
--    MAX-ACCESS  read-only
--    STATUS  current
--    DESCRIPTION
--        "GEL: get feature's name"
--    ::= { lmLicInfoProductsEntry 1 }

--lmLicInfoProductQty OBJECT-TYPE
--    SYNTAX  INTEGER
--    MAX-ACCESS  read-only
--    STATUS  current
--    DESCRIPTION
--        "GEL: get feature's active quantity."
--    ::= { lmLicInfoProductsEntry 2 }

--lmLicInfoProductExpiration OBJECT-TYPE
--    SYNTAX  DisplayString (SIZE(1..255))
--    MAX-ACCESS  read-only
--    STATUS  current
--    DESCRIPTION
--        "GEL: get feature's expiration date."
--    ::= { lmLicInfoProductsEntry 3 }

--lmLicInfoProductLastValidated OBJECT-TYPE
--    SYNTAX  DisplayString (SIZE(1..255))
--    MAX-ACCESS  read-only
--    STATUS  current
--    DESCRIPTION
--        "GEL: get feature's last validation timestamp."
--    ::= { lmLicInfoProductsEntry 4 }

--lmLicInfoProductStatus OBJECT-TYPE
--    SYNTAX  DisplayString (SIZE(1..255))
--    MAX-ACCESS  read-only
--    STATUS  current
--    DESCRIPTION
--        "GEL: get feature's status."
--    ::= { lmLicInfoProductsEntry 5 }
-- GEL License manager Info

-- NTP Configuration
agCurCfgNTPServer OBJECT-TYPE
    SYNTAX  IpAddress
    MAX-ACCESS  read-only
    STATUS  current
    DESCRIPTION
        "The NTP Server Address."
    ::= { agNTP 1 }

agNewCfgNTPServer OBJECT-TYPE
    SYNTAX  IpAddress
    MAX-ACCESS  read-write
    STATUS  current
    DESCRIPTION
        "The NTP Server Address."
    ::= { agNTP 2 }

agCurCfgNTPResyncInterval OBJECT-TYPE
    SYNTAX  INTEGER (1..44640)
    MAX-ACCESS  read-only
    STATUS  current
    DESCRIPTION
        "The NTP Server resync interval in minutes."
    ::= { agNTP 3 }

agNewCfgNTPResyncInterval OBJECT-TYPE
    SYNTAX  INTEGER (1..44640)
    MAX-ACCESS  read-write
    STATUS  current
    DESCRIPTION
        "The NTP Server resync interval in minutes."
    ::= { agNTP 4 }

agCurCfgNTPTzoneHHMM OBJECT-TYPE
    SYNTAX  DisplayString (SIZE(0..6))
    MAX-ACCESS  read-only
    STATUS  current
    DESCRIPTION
        "The NTP Server timezone offset from GMT formatted as (+/-)HH:MM."
    ::= { agNTP 5 }

agNewCfgNTPTzoneHHMM OBJECT-TYPE
    SYNTAX  DisplayString (SIZE(0..6))
    MAX-ACCESS  read-write
    STATUS  current
    DESCRIPTION
        "The NTP Server timezone offset from GMT formatted as (+/-)HH:MM.
         The valid range is from -12:59 to +12:59."
    ::= { agNTP 6 }

agCurCfgNTPDlight OBJECT-TYPE
    SYNTAX  INTEGER {
        enabled(1),
        disabled(2)
        }
    MAX-ACCESS  read-only
    STATUS  current
    DESCRIPTION
        "Enable/disable daylight savings time."
    ::= { agNTP 7 }

agNewCfgNTPDlight OBJECT-TYPE
    SYNTAX  INTEGER {
        enabled(1),
        disabled(2)
        }
    MAX-ACCESS  read-write
    STATUS  current
    DESCRIPTION
        "Enable/disable daylight savings time."
    ::= { agNTP 8 }

agCurCfgNTPService OBJECT-TYPE
    SYNTAX  INTEGER {
        enabled(1),
        disabled(2)
        }
    MAX-ACCESS  read-only
    STATUS  current
    DESCRIPTION
        "Enable/disable NTP Service."
    ::= { agNTP 9 }

agNewCfgNTPService OBJECT-TYPE
    SYNTAX  INTEGER {
        enabled(1),
        disabled(2)
        }
    MAX-ACCESS  read-write
    STATUS  current
    DESCRIPTION
        "Enable/disable NTP Service."
    ::= { agNTP 10 }

agCurCfgNTPSecServer OBJECT-TYPE
    SYNTAX  IpAddress
    MAX-ACCESS  read-only
    STATUS  current
    DESCRIPTION
        "The Secondary NTP Server Address."
    ::= { agNTP 11 }

agNewCfgNTPSecServer OBJECT-TYPE
    SYNTAX  IpAddress
    MAX-ACCESS  read-write
    STATUS  current
    DESCRIPTION
        "The Secondary NTP Server Address."
    ::= { agNTP 12 }

agCurCfgNTPServerIpv6Addr OBJECT-TYPE
    SYNTAX DisplayString (SIZE(0..40))
    MAX-ACCESS read-only
    STATUS current
    DESCRIPTION
        "The IPv6 address of the Primary NTP server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agNTP 13 }

agNewCfgNTPServerIpv6Addr OBJECT-TYPE
    SYNTAX DisplayString (SIZE(0..40))
    MAX-ACCESS read-write
    STATUS current
    DESCRIPTION
        "The IPv6 address of the Primary NTP server.
        Address should be 16-byte haxadecimal colon notation.
        Valid IPv6 address should be in any of the following forms
        xxxx:xxxx:xxxx:xxxx:xxxx:xxxx:xxxx:xxxx or
        xxxx::xxxx:xxxx:xxxx:xxxx or ::xxxx"
    ::= { agNTP 14 }

agCurCfgNTPSecServerIpv6Addr OBJECT-TYPE
    SYNTAX DisplayString (SIZE(0..40))
    MAX-ACCESS read-only
    STATUS current
    DESCRIPTION
        "The IPv6 address of the Secondary NTP server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agNTP 15 }

agNewCfgNTPSecServerIpv6Addr OBJECT-TYPE
    SYNTAX DisplayString (SIZE(0..40))
    MAX-ACCESS read-write
    STATUS current
    DESCRIPTION
        "The IPv6 address of the Secondary NTP server.
        Address should be 16-byte haxadecimal colon notation.
        Valid IPv6 address should be in any of the following forms
        xxxx:xxxx:xxxx:xxxx:xxxx:xxxx:xxxx:xxxx or
        xxxx::xxxx:xxxx:xxxx:xxxx or ::xxxx"
    ::= { agNTP 16 }

-- APPLY Configuration
agApplyPending OBJECT-TYPE
    SYNTAX  INTEGER {
        applyNeeded(2),
        noApplyNeeded(3)
        }
    MAX-ACCESS  read-only
    STATUS  current
    DESCRIPTION
        "This object, when read, gives the user information
         whether an apply action is needed and that the configuration
         has been chaged by the user actions. The user then can
         apply the changes by setting proper value to the object
         agApplyConfiguration described above."
    ::= { agApply 1 }

agApplyConfig OBJECT-TYPE
    SYNTAX  INTEGER {
        apply(1),
        idle(2),
        inprogress(3),
        complete(4),
        failed(5)
        }
    MAX-ACCESS  read-write
    STATUS  current
    DESCRIPTION
         "When this object is read the current state is returned.
          idle(2) indicates that there is no apply in progess.
          complete(4) indicates that the last apply operation is completed.
          Setting the value to apply(1), will write all the changes made
          since the last apply to the current configuration block.
	  If the apply is successful this variable will return the state
          'complete' else it will return 'failed'. In case of failure,
          to read the reason for failure use the agApplyTable.
          Once the operation is completed or the agApplyTable is read in case
          of failure, the apply buffer needs to be freed and the agApplyState
          should be set back to 'idle' state so others can issue the apply
          command via SNMP."
    ::= { agApply 2 }

agApplyTableSize OBJECT-TYPE
    SYNTAX  Integer32
    MAX-ACCESS  read-only
    STATUS  current
    DESCRIPTION
        "The number of strings in the apply table."
    ::= { agApply 4 }

agApplyTable OBJECT-TYPE
    SYNTAX  SEQUENCE OF AgApplyTableEntry
    MAX-ACCESS  not-accessible
    STATUS  current
    DESCRIPTION
        "The table of URL path for URL load balancing in the current_config."
    ::= { agApply 5 }

agApplyTableEntry OBJECT-TYPE
    SYNTAX  AgApplyTableEntry
    MAX-ACCESS  not-accessible
    STATUS  current
    DESCRIPTION
        "Information about an URL path for URL load balancing."
    INDEX   { agApplyIndex }
    ::= { agApplyTable 1 }

AgApplyTableEntry ::= SEQUENCE {
    agApplyIndex      Integer32,
    agApplyString     DisplayString
    }

agApplyIndex OBJECT-TYPE
    SYNTAX  Integer32
    MAX-ACCESS  read-only
    STATUS  current
    DESCRIPTION
        "The table index."
    ::= { agApplyTableEntry 1 }

agApplyString OBJECT-TYPE
    SYNTAX  DisplayString
    MAX-ACCESS  read-only
    STATUS  current
    DESCRIPTION
        "A string in the apply table."
    ::= { agApplyTableEntry 2 }

-- Mgmt Port Config

agMgmtCurCfgIpAddr OBJECT-TYPE
    SYNTAX  IpAddress
    MAX-ACCESS  read-only
    STATUS  current
    DESCRIPTION
        "The IP address of the management port."
    ::= { agMgmt 1 }

agMgmtNewCfgIpAddr OBJECT-TYPE
    SYNTAX  IpAddress
    MAX-ACCESS  read-write
    STATUS  current
    DESCRIPTION
        "The IP address of the management port."
    ::= { agMgmt 2 }

agMgmtCurCfgMask OBJECT-TYPE
    SYNTAX  IpAddress
    MAX-ACCESS  read-only
    STATUS  current
    DESCRIPTION
        "The subnet mask of the management port."
    ::= { agMgmt 3 }

agMgmtNewCfgMask OBJECT-TYPE
    SYNTAX  IpAddress
    MAX-ACCESS  read-write
    STATUS  current
    DESCRIPTION
        "The subnet mask of the management port."
    ::= { agMgmt 4 }

agMgmtCurCfgGateway OBJECT-TYPE
    SYNTAX  IpAddress
    MAX-ACCESS  read-only
    STATUS  current
    DESCRIPTION
        "The default gateway for the management port."
    ::= { agMgmt 7 }

agMgmtNewCfgGateway OBJECT-TYPE
    SYNTAX  IpAddress
    MAX-ACCESS  read-write
    STATUS  current
    DESCRIPTION
        "The default gateway for the management port."
    ::= { agMgmt 8 }

agMgmtCurCfgState OBJECT-TYPE
    SYNTAX  INTEGER {
        enabled(1),
        disabled(2)
        }
    MAX-ACCESS  read-only
    STATUS  current
    DESCRIPTION
        "Enable/disable management port."
   ::= { agMgmt 9 }

agMgmtNewCfgState OBJECT-TYPE
    SYNTAX  INTEGER {
        enabled(1),
        disabled(2)
        }
    MAX-ACCESS  read-write
    STATUS  current
    DESCRIPTION
        "Enable/disable management port."
   ::= { agMgmt 10 }

agMgmtCurCfgNtp OBJECT-TYPE
    SYNTAX  INTEGER {
        data(1),
        mgmt(2)
        }
    MAX-ACCESS  read-only
    STATUS  current
    DESCRIPTION
        "Specifies NTP access is over management port or data port."
   ::= { agMgmt 11 }

agMgmtNewCfgNtp OBJECT-TYPE
    SYNTAX  INTEGER {
        data(1),
        mgmt(2)
        }
    MAX-ACCESS  read-write
    STATUS  current
    DESCRIPTION
        "Specifies NTP access is over management port or data port."
   ::= { agMgmt 12 }

agMgmtCurCfgRadius OBJECT-TYPE
    SYNTAX  INTEGER {
        data(1),
        mgmt(2)
        }
    MAX-ACCESS  read-only
    STATUS  current
    DESCRIPTION
        "Specifies RADIUS server access is over management port or data port."
   ::= { agMgmt 13 }

agMgmtNewCfgRadius OBJECT-TYPE
    SYNTAX  INTEGER {
        data(1),
        mgmt(2)
        }
    MAX-ACCESS  read-write
    STATUS  current
    DESCRIPTION
        "Specifies RADIUS server access is over management port or data port."
   ::= { agMgmt 14 }

agMgmtCurCfgSmtp OBJECT-TYPE
    SYNTAX  INTEGER {
        data(1),
        mgmt(2)
        }
    MAX-ACCESS  read-only
    STATUS  current
    DESCRIPTION
        "Specifies SMTP access is over management port or data port."
   ::= { agMgmt 15 }

agMgmtNewCfgSmtp OBJECT-TYPE
    SYNTAX  INTEGER {
        data(1),
        mgmt(2)
        }
    MAX-ACCESS  read-write
    STATUS  current
    DESCRIPTION
        "Specifies SMTP access is over management port or data port."
   ::= { agMgmt 16 }

agMgmtCurCfgSnmp OBJECT-TYPE
    SYNTAX  INTEGER {
        data(1),
        mgmt(2)
        }
    MAX-ACCESS  read-only
    STATUS  current
    DESCRIPTION
        "Specifies SNMP trap host access is over management port or data port."
   ::= { agMgmt 17 }

agMgmtNewCfgSnmp OBJECT-TYPE
    SYNTAX  INTEGER {
        data(1),
        mgmt(2)
        }
    MAX-ACCESS  read-write
    STATUS  current
    DESCRIPTION
        "Specifies SNMP trap host access is over management port or data port."
   ::= { agMgmt 18 }

agMgmtCurCfgSyslog OBJECT-TYPE
    SYNTAX  INTEGER {
        data(1),
        mgmt(2)
        }
    MAX-ACCESS  read-only
    STATUS  current
    DESCRIPTION
        "Specifies syslog host access is over management port or data port."
   ::= { agMgmt 19 }

agMgmtNewCfgSyslog OBJECT-TYPE
    SYNTAX  INTEGER {
        data(1),
        mgmt(2)
        }
    MAX-ACCESS  read-write
    STATUS  current
    DESCRIPTION
        "Specifies syslog host access is over management port or data port."
   ::= { agMgmt 20 }

agMgmtCurCfgTftp OBJECT-TYPE
    SYNTAX  INTEGER {
        data(1),
        mgmt(2)
        }
    MAX-ACCESS  read-only
    STATUS  current
    DESCRIPTION
        "Specifies TFTP access is over management port or data port."
   ::= { agMgmt 21 }

agMgmtNewCfgTftp OBJECT-TYPE
    SYNTAX  INTEGER {
        data(1),
        mgmt(2)
        }
    MAX-ACCESS  read-write
    STATUS  current
    DESCRIPTION
        "Specifies TFTP access is over management port or data port."
   ::= { agMgmt 22 }

agMgmtCurCfgDns OBJECT-TYPE
    SYNTAX  INTEGER {
        data(1),
        mgmt(2)
        }
    MAX-ACCESS  read-only
    STATUS  current
    DESCRIPTION
        "Specifies DNS access is over management port or data port."
   ::= { agMgmt 24 }

agMgmtNewCfgDns OBJECT-TYPE
    SYNTAX  INTEGER {
        data(1),
        mgmt(2)
        }
    MAX-ACCESS  read-write
    STATUS  current
    DESCRIPTION
        "Specifies DNS access is over management port or data port."
   ::= { agMgmt 25 }

agMgmtCurCfgTacacs OBJECT-TYPE
    SYNTAX  INTEGER {
        data(1),
        mgmt(2)
        }
    MAX-ACCESS  read-only
    STATUS  current
    DESCRIPTION
        "Specifies TACACS+ server access is over management port or data port."
   ::= { agMgmt 26 }

agMgmtNewCfgTacacs OBJECT-TYPE
    SYNTAX  INTEGER {
        data(1),
        mgmt(2)
        }
    MAX-ACCESS  read-write
    STATUS  current
    DESCRIPTION
        "Specifies TACACS+ server access is over management port or data port."
   ::= { agMgmt 27 }

agMgmtCurCfgIntr OBJECT-TYPE
    SYNTAX  INTEGER (0..60)
    MAX-ACCESS  read-only
    STATUS  current
    DESCRIPTION
        "The management port gateway health check interval (in seconds)."
   ::= { agMgmt 28 }

agMgmtNewCfgIntr OBJECT-TYPE
    SYNTAX  INTEGER (0..60)
    MAX-ACCESS  read-write
    STATUS  current
    DESCRIPTION
        "The management port gateway health check interval (in seconds)."
   ::= { agMgmt 29 }

agMgmtCurCfgRetry OBJECT-TYPE
    SYNTAX  INTEGER (1..120)
    MAX-ACCESS  read-only
    STATUS  current
    DESCRIPTION
        "The management port gateway retries before out of service."
   ::= { agMgmt 30 }

agMgmtNewCfgRetry OBJECT-TYPE
    SYNTAX  INTEGER (1..120)
    MAX-ACCESS  read-write
    STATUS  current
    DESCRIPTION
        "The management port gateway retries before out of service."
   ::= { agMgmt 31 }

agMgmtCurCfgWlm OBJECT-TYPE
    SYNTAX  INTEGER {
        data(1),
        mgmt(2)
        }
    MAX-ACCESS  read-only
    STATUS  current
    DESCRIPTION
        "Specifies WLM SASP is over management port or data port."
   ::= { agMgmt 34 }

agMgmtNewCfgWlm OBJECT-TYPE
    SYNTAX  INTEGER {
        data(1),
        mgmt(2)
        }
    MAX-ACCESS  read-write
    STATUS  current
    DESCRIPTION
        "Specifies WLM SASP is over management port or data port."
   ::= { agMgmt 35 }

agMgmtCurCfgReport OBJECT-TYPE
    SYNTAX  INTEGER {
        data(1),
        mgmt(2)
        }
    MAX-ACCESS  read-only
    STATUS  current
    DESCRIPTION
        "Specifies reporting server is over management port or data port."
   ::= { agMgmt 36 }

agMgmtNewCfgReport OBJECT-TYPE
    SYNTAX  INTEGER {
        data(1),
        mgmt(2)
        }
    MAX-ACCESS  read-write
    STATUS  current
    DESCRIPTION
        "Specifies reporting server is over management port or data port."
   ::= { agMgmt 37 }

agMgmtCurCfgIpAddr2 OBJECT-TYPE
    SYNTAX  IpAddress
    MAX-ACCESS  read-only
    STATUS  current
    DESCRIPTION
        "The IP address of the management port."
    ::= { agMgmt 38 }

agMgmtNewCfgIpAddr2 OBJECT-TYPE
    SYNTAX  IpAddress
    MAX-ACCESS  read-write
    STATUS  current
    DESCRIPTION
        "The IP address of the management port."
    ::= { agMgmt 39 }

agMgmtCurCfgMask2 OBJECT-TYPE
    SYNTAX  IpAddress
    MAX-ACCESS  read-only
    STATUS  current
    DESCRIPTION
        "The subnet mask of the management port."
    ::= { agMgmt 40 }

agMgmtNewCfgMask2 OBJECT-TYPE
    SYNTAX  IpAddress
    MAX-ACCESS  read-write
    STATUS  current
    DESCRIPTION
        "The subnet mask of the management port."
    ::= { agMgmt 41 }

agMgmtCurCfgGateway2 OBJECT-TYPE
    SYNTAX  IpAddress
    MAX-ACCESS  read-only
    STATUS  current
    DESCRIPTION
        "The default gateway for the management port."
    ::= { agMgmt 44 }

agMgmtNewCfgGateway2 OBJECT-TYPE
    SYNTAX  IpAddress
    MAX-ACCESS  read-write
    STATUS  current
    DESCRIPTION
        "The default gateway for the management port."
    ::= { agMgmt 45 }

agMgmtCurCfgState2 OBJECT-TYPE
    SYNTAX  INTEGER {
        enabled(1),
        disabled(2)
        }
    MAX-ACCESS  read-only
    STATUS  current
    DESCRIPTION
        "Enable/disable management port."
   ::= { agMgmt 46 }

agMgmtNewCfgState2 OBJECT-TYPE
    SYNTAX  INTEGER {
        enabled(1),
        disabled(2)
        }
    MAX-ACCESS  read-write
    STATUS  current
    DESCRIPTION
        "Enable/disable management port."
   ::= { agMgmt 47 }
agMgmtCurCfgCdp OBJECT-TYPE
    SYNTAX  INTEGER {
        data(1),
        mgmt(2)
        }
    MAX-ACCESS  read-only
    STATUS  current
    DESCRIPTION
        "Specifies CDP access is over management port or data port."
   ::= { agMgmt 48 }

agMgmtNewCfgCdp OBJECT-TYPE
    SYNTAX  INTEGER {
        data(1),
        mgmt(2)
        }
    MAX-ACCESS  read-write
    STATUS  current
    DESCRIPTION
        "Specifies CDP access is over management port or data port."
   ::= { agMgmt 49 }
agMgmtCurCfgOcsp OBJECT-TYPE
    SYNTAX  INTEGER {
        data(1),
        mgmt(2)
        }
    MAX-ACCESS  read-only
    STATUS  current
    DESCRIPTION
        "Specifies OCSP access is over management port or data port."
   ::= { agMgmt 50 }

agMgmtNewCfgOcsp OBJECT-TYPE
    SYNTAX  INTEGER {
        data(1),
        mgmt(2)
        }
    MAX-ACCESS  read-write
    STATUS  current
    DESCRIPTION
        "Specifies OCSP access is over management port or data port."
   ::= { agMgmt 51 }

agMgmtCurCfgDHCPMode OBJECT-TYPE
    SYNTAX  INTEGER {
        enabled(1),
        disabled(2)
        }
    MAX-ACCESS  read-only
    STATUS  current
    DESCRIPTION
        "Enabled/disable DHCP.
        Note: This MIB is only supported on VA platform."
   ::= { agMgmt 52 }
agMgmtNewCfgDHCPMode OBJECT-TYPE
    SYNTAX  INTEGER {
        enabled(1),
        disabled(2)
        }
    MAX-ACCESS  read-write
    STATUS  current
    DESCRIPTION
        "Enabled/disable DHCP.
        Note: This MIB is only supported on VA platform."
   ::= { agMgmt 53 }
agMgmtCurCfgDHCPTimeout OBJECT-TYPE
    SYNTAX  INTEGER (4..60)
    MAX-ACCESS  read-only
    STATUS  current
    DESCRIPTION
        "DHCP Timeout.
        Note: This MIB is only supported on VA platform."
    ::= { agMgmt 54 }
agMgmtNewCfgDHCPTimeout OBJECT-TYPE
    SYNTAX  INTEGER (4..60)
    MAX-ACCESS  read-write
    STATUS  current
    DESCRIPTION
        "DHCP Timeout.
        Note: This MIB is only supported on VA platform."
    ::= { agMgmt 55 }

agMgmtPort   OBJECT IDENTIFIER ::= { agMgmt 23 }

agMgmtPortCurCfgSpeed OBJECT-TYPE
    SYNTAX  INTEGER {
        mbs10(1),
        mbs100(2),
        mbs1000(3),
        any(4)
        }
    MAX-ACCESS  read-only
    STATUS  current
    DESCRIPTION
        "Set Management port link speed."
   ::= { agMgmtPort 1 }

agMgmtPortNewCfgSpeed OBJECT-TYPE
    SYNTAX  INTEGER {
        mbs10(1),
        mbs100(2),
        mbs1000(3),
        any(4)
        }
    MAX-ACCESS  read-write
    STATUS  current
    DESCRIPTION
        "Set Management port link speed."
   ::= { agMgmtPort 2 }

agMgmtPortCurCfgMode OBJECT-TYPE
    SYNTAX  INTEGER {
        full(1),
        half(2),
        any(3)
        }
    MAX-ACCESS  read-only
    STATUS  current
    DESCRIPTION
        "Set Management port full or half duplex mode."
   ::= { agMgmtPort 3 }

agMgmtPortNewCfgMode OBJECT-TYPE
    SYNTAX  INTEGER {
        full(1),
        half(2),
        any(3)
        }
    MAX-ACCESS  read-write
    STATUS  current
    DESCRIPTION
        "Set Management port full or half duplex mode."
   ::= { agMgmtPort 4 }

agMgmtPortCurCfgAuto OBJECT-TYPE
    SYNTAX  INTEGER {
        on(1),
        off(2)
        }
    MAX-ACCESS  read-only
    STATUS  current
    DESCRIPTION
        "Set Management port autonegotiation."
   ::= { agMgmtPort 5 }

agMgmtPortNewCfgAuto OBJECT-TYPE
    SYNTAX  INTEGER {
        on(1),
        off(2)
        }
    MAX-ACCESS  read-write
    STATUS  current
    DESCRIPTION
        "Set Management port autonegotiation."
   ::= { agMgmtPort 6 }

agMgmtPortCurCfgSpeed2 OBJECT-TYPE
    SYNTAX  INTEGER {
        mbs10(1),
        mbs100(2),
        mbs1000(3),
        any(4)
        }
    MAX-ACCESS  read-only
    STATUS  current
    DESCRIPTION
        "Set Management port2 link speed."
   ::= { agMgmtPort 7 }

agMgmtPortNewCfgSpeed2 OBJECT-TYPE
    SYNTAX  INTEGER {
        mbs10(1),
        mbs100(2),
        mbs1000(3),
        any(4)
        }
    MAX-ACCESS  read-write
    STATUS  current
    DESCRIPTION
        "Set Management port2 link speed."
   ::= { agMgmtPort 8 }

agMgmtPortCurCfgMode2 OBJECT-TYPE
    SYNTAX  INTEGER {
        full(1),
        half(2),
        any(3)
        }
    MAX-ACCESS  read-only
    STATUS  current
    DESCRIPTION
        "Set Management port2 full or half duplex mode."
   ::= { agMgmtPort 9 }

agMgmtPortNewCfgMode2 OBJECT-TYPE
    SYNTAX  INTEGER {
        full(1),
        half(2),
        any(3)
        }
    MAX-ACCESS  read-write
    STATUS  current
    DESCRIPTION
        "Set Management port2 full or half duplex mode."
   ::= { agMgmtPort 10 }

agMgmtPortCurCfgAuto2 OBJECT-TYPE
    SYNTAX  INTEGER {
        on(1),
        off(2)
        }
    MAX-ACCESS  read-only
    STATUS  current
    DESCRIPTION
        "Set Management port2 autonegotiation."
   ::= { agMgmtPort 11 }

agMgmtPortNewCfgAuto2 OBJECT-TYPE
    SYNTAX  INTEGER {
        on(1),
        off(2)
        }
    MAX-ACCESS  read-write
    STATUS  current
    DESCRIPTION
        "Set Management port2 autonegotiation."
   ::= { agMgmtPort 12 }


-- SSL Processor Config

agSslprocCurCfgIpAddr OBJECT-TYPE
    SYNTAX  IpAddress
    MAX-ACCESS  read-only
    STATUS  current
    DESCRIPTION
        "The SSL cluster management IP."
    ::= { agSslproc 1 }

agSslprocNewCfgIpAddr OBJECT-TYPE
    SYNTAX  IpAddress
    MAX-ACCESS  read-write
    STATUS  current
    DESCRIPTION
        "The SSL cluster management IP."
    ::= { agSslproc 2 }

agSslprocCurCfgPort OBJECT-TYPE
    SYNTAX  INTEGER (1..65535)
    MAX-ACCESS  read-only
    STATUS  current
    DESCRIPTION
        "The SSL cluster management port."
    ::= { agSslproc 3 }

agSslprocNewCfgPort OBJECT-TYPE
    SYNTAX  INTEGER (1..65535)
    MAX-ACCESS  read-write
    STATUS  current
    DESCRIPTION
        "The SSL cluster management port."
    ::= { agSslproc 4 }

agSslprocCurCfgRts OBJECT-TYPE
    SYNTAX  INTEGER {
        enabled(1),
        disabled(2)
        }
    MAX-ACCESS  read-only
    STATUS  current
    DESCRIPTION
        "Enable/disable RTS processing."
   ::= { agSslproc 5 }

agSslprocNewCfgRts OBJECT-TYPE
    SYNTAX  INTEGER {
        enabled(1),
        disabled(2)
        }
    MAX-ACCESS  read-write
    STATUS  current
    DESCRIPTION
        "Enabled/disable RTS processing."
   ::= { agSslproc 6 }

agSslprocCurCfgFilt OBJECT-TYPE
    SYNTAX  INTEGER {
        enabled(1),
        disabled(2)
        }
    MAX-ACCESS  read-only
    STATUS  current
    DESCRIPTION
        "Enable/disable filtering."
   ::= { agSslproc 7 }

agSslprocNewCfgFilt OBJECT-TYPE
    SYNTAX  INTEGER {
        enabled(1),
        disabled(2)
        }
    MAX-ACCESS  read-write
    STATUS  current
    DESCRIPTION
        "Enabled/disable filtering."
   ::= { agSslproc 8 }

-- TACACS+ Configuration

tacCurCfgPrimaryIpAddr OBJECT-TYPE
    SYNTAX  IpAddress
    MAX-ACCESS  read-only
    STATUS  current
    DESCRIPTION
        "The IP address of the Primary TACACS+ server."
    ::= { agTacacsConfig 1 }

tacNewCfgPrimaryIpAddr OBJECT-TYPE
    SYNTAX  IpAddress
    MAX-ACCESS  read-write
    STATUS  current
    DESCRIPTION
        "The IP address of the Primary TACACS+ server."
    ::= { agTacacsConfig 2 }

tacCurCfgSecondaryIpAddr OBJECT-TYPE
    SYNTAX  IpAddress
    MAX-ACCESS  read-only
    STATUS  current
    DESCRIPTION
        "The IP address of the Secondary TACSACS server."
    ::= { agTacacsConfig 3 }
tacNewCfgSecondaryIpAddr OBJECT-TYPE
    SYNTAX  IpAddress
    MAX-ACCESS  read-write
    STATUS  current
    DESCRIPTION
        "The IP address of the Secondary TACACS+ server."
    ::= { agTacacsConfig 4 }


tacCurCfgPort OBJECT-TYPE
    SYNTAX  INTEGER  (1..65000)
    MAX-ACCESS  read-only
    STATUS  current
    DESCRIPTION
        "Specify the TACACS+ port number."
    ::= { agTacacsConfig 5 }

tacNewCfgPort OBJECT-TYPE
    SYNTAX  INTEGER  (1..65000)
    MAX-ACCESS  read-write
    STATUS  current
    DESCRIPTION
        "Specify the TACACS+ port number."
    ::= { agTacacsConfig 6 }

tacCurCfgTimeout OBJECT-TYPE
    SYNTAX  INTEGER  (1..15)
    MAX-ACCESS  read-only
    STATUS  current
    DESCRIPTION
        "The maximum number of seconds before resending authentication
         to TACACS+ server."
    ::= { agTacacsConfig 7 }

tacNewCfgTimeout OBJECT-TYPE
    SYNTAX  INTEGER  (1..15)
    MAX-ACCESS  read-write
    STATUS  current
    DESCRIPTION
        "The maximum number of seconds before resending authentication
         to TACACS+ server."
    ::= { agTacacsConfig 8 }

tacCurCfgRetries OBJECT-TYPE
    SYNTAX  INTEGER  (1..3)
    MAX-ACCESS  read-only
    STATUS  current
    DESCRIPTION
        "Number of retries to the TACACS+ server."
    ::= { agTacacsConfig 9 }

tacNewCfgRetries OBJECT-TYPE
    SYNTAX  INTEGER  (1..3)
    MAX-ACCESS  read-write
    STATUS  current
    DESCRIPTION
        "Number of retries to the TACACS+ server."
    ::= { agTacacsConfig 10 }

tacCurCfgState OBJECT-TYPE
    SYNTAX  INTEGER {
        enabled(2),
        disabled(3)
        }
    MAX-ACCESS  read-only
    STATUS  current
    DESCRIPTION
        "Enable or disbale TACACS+ authentication."
    ::= { agTacacsConfig 11 }

tacNewCfgState OBJECT-TYPE
    SYNTAX  INTEGER {
        enabled(2),
        disabled(3)
        }
    MAX-ACCESS  read-write
    STATUS  current
    DESCRIPTION
        "Enable or disable TACACS+ authentication."
    ::= { agTacacsConfig 12 }

tacCurCfgAuthenString OBJECT-TYPE
    SYNTAX  DisplayString (SIZE(0..32))
    MAX-ACCESS  read-only
    STATUS  current
    DESCRIPTION
        "The TACACS+ authentication string."
    ::= { agTacacsConfig 13 }

tacNewCfgAuthenString OBJECT-TYPE
    SYNTAX  DisplayString (SIZE(0..32))
    MAX-ACCESS  read-write
    STATUS  current
    DESCRIPTION
        "The TACACS+ authentication string."
    ::= { agTacacsConfig 14 }

tacCurCfgTelnet OBJECT-TYPE
    SYNTAX  INTEGER {
        enabled(1),
        disabled(2)
        }
    MAX-ACCESS  read-only
    STATUS  current
    DESCRIPTION
        "Enable or disbale TACACS+ backdoor for telnet."
    ::= { agTacacsConfig 15 }

tacNewCfgTelnet OBJECT-TYPE
    SYNTAX  INTEGER {
        enabled(1),
        disabled(2)
        }
    MAX-ACCESS  read-write
    STATUS  current
    DESCRIPTION
        "Enable or disable TACACS+ backdoor for telnet."
    ::= { agTacacsConfig 16 }

tacCurCfgAuthenSecondString OBJECT-TYPE
    SYNTAX  DisplayString (SIZE(0..32))
    MAX-ACCESS  read-only
    STATUS  current
    DESCRIPTION
        "The second TACACS+ authentication string."
    ::= { agTacacsConfig 17 }

tacNewCfgAuthenSecondString OBJECT-TYPE
    SYNTAX  DisplayString (SIZE(0..32))
    MAX-ACCESS  read-write
    STATUS  current
    DESCRIPTION
        "The second TACACS+ authentication string."
    ::= { agTacacsConfig 18 }

tacCurCfgCmdAuthor OBJECT-TYPE
    SYNTAX  INTEGER {
        enabled(1),
        disabled(2)
        }
    MAX-ACCESS  read-only
    STATUS  current
    DESCRIPTION
        "Enable or disbale TACACS+ command authorization."
    ::= { agTacacsConfig 19 }

tacNewCfgCmdAuthor OBJECT-TYPE
    SYNTAX  INTEGER {
        enabled(1),
        disabled(2)
        }
    MAX-ACCESS  read-write
    STATUS  current
    DESCRIPTION
        "Enable or disable TACACS+ command authorization."
    ::= { agTacacsConfig 20 }

tacCurCfgCmdLogging OBJECT-TYPE
    SYNTAX  INTEGER {
        enabled(1),
        disabled(2)
        }
    MAX-ACCESS  read-only
    STATUS  current
    DESCRIPTION
        "Enable or disbale TACACS+ command logging."
    ::= { agTacacsConfig 21 }

tacNewCfgCmdLogging OBJECT-TYPE
    SYNTAX  INTEGER {
        enabled(1),
        disabled(2)
        }
    MAX-ACCESS  read-write
    STATUS  current
    DESCRIPTION
        "Enable or disable TACACS+ command logging."
    ::= { agTacacsConfig 22 }

tacCurCfgClogname OBJECT-TYPE
    SYNTAX  INTEGER {
        admin(1),
        accounting(2)
        }
    MAX-ACCESS  read-only
    STATUS  current
    DESCRIPTION
        "TACACS+ Cisco Secure ACS server command logging type [admin\accounting]"
    ::= { agTacacsConfig 33 }

tacNewCfgClogname OBJECT-TYPE
    SYNTAX  INTEGER {
        admin(1),
        accounting(2)
        }
    MAX-ACCESS  read-write
    STATUS  current
    DESCRIPTION
        "TACACS+ Cisco Secure ACS server command logging type [admin\accounting]"
    ::= { agTacacsConfig 34 }


tacCurCfgSecBd OBJECT-TYPE
    SYNTAX  INTEGER {
        enabled(1),
        disabled(2)
        }
    MAX-ACCESS  read-only
    STATUS  current
    DESCRIPTION
        "Enable or disbale TACACS+ secure backdoor for telnet."
    ::= { agTacacsConfig 23 }

tacNewCfgSecBd OBJECT-TYPE
    SYNTAX  INTEGER {
        enabled(1),
        disabled(2)
        }
    MAX-ACCESS  read-write
    STATUS  current
    DESCRIPTION
        "Enable or disable TACACS+ secure backdoor for telnet."
    ::= { agTacacsConfig 24 }
tacCurCfgCmap OBJECT-TYPE
    SYNTAX  INTEGER {
        enabled(1),
        disabled(2)
        }
    MAX-ACCESS  read-only
    STATUS  current
    DESCRIPTION
        "Enable/Disable Tacacs+ new privilege level mapping."
    ::= { agTacacsConfig 25 }

tacNewCfgCmap OBJECT-TYPE
    SYNTAX  INTEGER {
        enabled(1),
        disabled(2)
        }
    MAX-ACCESS  read-write
    STATUS  current
    DESCRIPTION
        "Enable/Disable Tacacs+ new privilege level mapping."
    ::= { agTacacsConfig 26 }

tacCurCfgPrimaryIpv6Addr OBJECT-TYPE
    SYNTAX DisplayString (SIZE(0..40))
    MAX-ACCESS read-only
    STATUS current
    DESCRIPTION
        "The IPv6 address of the Primary TACACS server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agTacacsConfig 29 }

tacNewCfgPrimaryIpv6Addr OBJECT-TYPE
    SYNTAX DisplayString (SIZE(0..40))
    MAX-ACCESS read-write
    STATUS current
    DESCRIPTION
        "The IPv6 address of the Primary TACACS server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agTacacsConfig 30 }

tacCurCfgSecondaryIpv6Addr OBJECT-TYPE
    SYNTAX DisplayString (SIZE(0..40))
    MAX-ACCESS read-only
    STATUS current
    DESCRIPTION
        "The IPv6 address of the Secondary TACACS server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agTacacsConfig 31 }

tacNewCfgSecondaryIpv6Addr OBJECT-TYPE
    SYNTAX DisplayString (SIZE(0..40))
    MAX-ACCESS read-write
    STATUS current
    DESCRIPTION
        "The IPv6 address of the Secondary TACACS server.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agTacacsConfig 32 }

tacCurCfgOtp OBJECT-TYPE
    SYNTAX  INTEGER {
        enabled(1),
        disabled(2)
        }
    MAX-ACCESS  read-only
    STATUS  current
    DESCRIPTION
        "Enable/Disable Tacacs+ OTP User Server Configuration."
    ::= { agTacacsConfig 35 }

tacNewCfgOtp OBJECT-TYPE
    SYNTAX  INTEGER {
        enabled(1),
        disabled(2)
        }
    MAX-ACCESS  read-write
    STATUS  current
    DESCRIPTION
        "Enable/Disable Tacacs+ OTP User Server Configuration."
    ::= { agTacacsConfig 36 }


tacCurCfgLocalAuth OBJECT-TYPE
    SYNTAX  INTEGER {
        localFirst(1),
        disabled(2)
        }
    MAX-ACCESS  read-only
    STATUS  current
    DESCRIPTION
        "Enable/Disable Tacacs+ local user authentication."
    ::= { agTacacsConfig 37 }

tacNewCfgLocalAuth OBJECT-TYPE
    SYNTAX  INTEGER {
        localFirst(1),
        disabled(2)
        }
    MAX-ACCESS  read-write
    STATUS  current
    DESCRIPTION
        "Enable/Disable Tacacs+ local user authentication."
    ::= { agTacacsConfig 38 }


-- Multiple Management network MIB objects
agMgmtNetTableMaxSize OBJECT-TYPE
    SYNTAX  Integer32
    MAX-ACCESS  read-only
    STATUS  current
    DESCRIPTION
        "The maximum number of entries in the Management
         Network Table."
    ::= { agMgmtNetConfig 1 }

agCurCfgMgmtNetTable OBJECT-TYPE
    SYNTAX  SEQUENCE OF AgCurCfgMgmtNetEntry
    MAX-ACCESS  not-accessible
    STATUS  current
    DESCRIPTION
        "The table for Management Network definitions
         in the current configuration block."
    ::= { agMgmtNetConfig 2 }

agCurCfgMgmtNetEntry OBJECT-TYPE
    SYNTAX  AgCurCfgMgmtNetEntry
    MAX-ACCESS  not-accessible
    STATUS  current
    DESCRIPTION
        "A row in the management network definition table."
    INDEX   {  agCurCfgMgmtNetIndex }
    ::= { agCurCfgMgmtNetTable 1 }

AgCurCfgMgmtNetEntry ::= SEQUENCE {
    agCurCfgMgmtNetIndex  	Integer32,
    agCurCfgMgmtNetSubnet       IpAddress,
    agCurCfgMgmtNetMask         IpAddress,
    agCurCfgMgmtNetProtocol     INTEGER
    }

agCurCfgMgmtNetIndex OBJECT-TYPE
    SYNTAX  Integer32
    MAX-ACCESS  read-only
    STATUS  current
    DESCRIPTION
        "The index of the Management Network Definition table."
    ::= { agCurCfgMgmtNetEntry 1 }

agCurCfgMgmtNetSubnet OBJECT-TYPE
    SYNTAX  IpAddress
    MAX-ACCESS  read-only
    STATUS  current
    DESCRIPTION
        "The Management Network Address in the current_configuration
         block."
    ::= { agCurCfgMgmtNetEntry 2 }

agCurCfgMgmtNetMask OBJECT-TYPE
    SYNTAX  IpAddress
    MAX-ACCESS  read-only
    STATUS  current
    DESCRIPTION
        "The Management Network Mask in the current_configuration
         block."
    ::= { agCurCfgMgmtNetEntry 3 }

agCurCfgMgmtNetProtocol OBJECT-TYPE
    SYNTAX  INTEGER {
        ssh(1),
        telnet(2),
        sshTelnet(3),
        http(4),
        sshHttp(5),
        telnetHttp(6),
        sshTelnetHttp(7),
        https(8),
        sshHttps(9),
        httpsTelnet(10),
        sshTelnetHttps(11),
        httpHttps(12),
        sshHttpHttps(13),
        telnetHttpHttps(14),
        sshTelnetHttpHttps(15),
        snmp(16),
        sshSnmp(17),
        telnetSnmp(18),
        sshTelnetSnmp(19),
        httpSnmp(20),
        sshHttpSnmp(21),
        telnetHttpSnmp(22),
        sshTelnetHttpSnmp(23),
        httpsSnmp(24),
        sshHttpsSnmp(25),
        telnetHttpsSnmp(26),
        sshTelnetHttpsSnmp(27),
        httpHttpsSnmp(28),
        sshHttpHttpsSnmp(29),
        telnetHttpHttpsSnmp(30),
        sshTelnetHttpHttpsSnmp(31),
        report(32),
        sshreport(33),
        telnetreport(34),
        sshTelnetreport(35),
        httpreport(36),
        sshHttpreport(37),
        telnetHttpreport(38),
        sshTelnetHttpreport(39),
        httpsreport(40),
        sshHttpsreport(41),
        httpsTelnetreport(42),
        sshTelnetHttpsreport(43),
        httpHttpsreport(44),
        sshHttpHttpsreport(45),
        telnetHttpHttpsreport(46),
        sshTelnetHttpHttpsreport(47),
        snmpreport(48),
        sshSnmpreport(49),
        telnetSnmpreport(50),
        sshTelnetSnmpreport(51),
        httpSnmpreport(52),
        sshHttpSnmpreport(53),
        telnetHttpSnmpreport(54),
        sshTelnetHttpSnmpreport(55),
        httpsSnmpreport(56),
        sshHttpsSnmpreport(57),
        telnetHttpsSnmpreport(58),
        sshTelnetHttpsSnmpreport(59),
        httpHttpsSnmpreport(60),
        sshHttpHttpsSnmpreport(61),
        telnetHttpHttpsSnmpreport(62),
        sshTelnetHttpHttpsSnmpreport(63),
        none(64)
        }
    MAX-ACCESS  read-only
    STATUS  current
    DESCRIPTION
        "The Management Network Protocol access in the current_configuration
         block.

        1  - Ssh
        2  - Telnet
        3  - Ssh + Telnet
        4  - Http
        5  - Ssh + Http
        6  - Telnet + Http
        7  - Ssh + Telnet + Http
        8  - Https
        9  - Ssh + Https
        10 - Https + Telnet
        11 - Ssh + Telnet + Https
        12 - Http + Https
        13 - Ssh + Http + Https
        14 - Telnet + Http + Https
        15 - Ssh + Telnet + Http + Https
        16 - Snmp
        17 - Ssh + Snmp
        18 - Telnet + Snmp
        19 - Ssh + Telnet + Snmp
        20 - Http + Snmp
        21 - Ssh + Http + Snmp
        22 - Telnet + Http + Snmp
        23 - Ssh + Telnet + Http + Snmp
        24 - Https + Snmp
        25 - Ssh + Https + Snmp
        26 - Telnet + Https + Snmp
        27 - Ssh + Telnet + Https + Snmp
        28 - Http + Https + Snmp
        29 - Ssh + Http + Https + Snmp
        30 - Telnet + Http + Https + Snmp
        31 - Ssh + Telnet + Http + Https + Snmp
        32 - Report
        33 - Ssh + Report
        34 - Telnet + Report
        35 - Ssh + Telnet + Report
        36 - Http + Report
        37 - Ssh + Http + Report
        38 - Telnet + Http + Report
        39 - Ssh + Telnet + Http + Report
        40 - Https + Report
        41 - Ssh + Https + Report
        42 - Telnet + Https + Report
        43 - Ssh + Telnet + Https + Report
        44 - Telnet + Http + Https + Report
        45 - Ssh + Http + Https + Report
        46 - Telnet + Http + Https + Report
        47 - Ssh + Telnet + Http + Https + Report
        48 - Snmp + Report
        49 - Ssh + Snmp + Report
        50 - Telnet + Snmp + Report
        51 - Ssh + Telnet + Snmp + Report
        52 - Http + Snmp + Report
        53 - Ssh + Http + Snmp + Report
        54 - Telnet + Http + Snmp + Report
        55 - Ssh + Telnet + Http + Snmp + Report
        56 - Https + Snmp + Report
        57 - Ssh + Https + Snmp + Report
        58 - Telnet + Https + Snmp + Report
        59 - Ssh + Telnet + Https + Snmp + Report
        60 - Http + Https + Snmp + Report
        61 - Ssh + Http + Https + Snmp + Report
        62 - Telnet + Http + Https + Snmp + Report
        63 - Ssh + Telnet + Http + Https + Snmp + Report
        64 - none
	 "
    ::= { agCurCfgMgmtNetEntry 4 }

agCurCfgMgmtNet6Table OBJECT-TYPE
    SYNTAX  SEQUENCE OF AgCurCfgMgmtNet6Entry
    MAX-ACCESS  not-accessible
    STATUS  current
    DESCRIPTION
        "The table for Management Network definitions
         in the current configuration block."
    ::= { agMgmtNetConfig 4 }

agCurCfgMgmtNet6Entry OBJECT-TYPE
    SYNTAX  AgCurCfgMgmtNet6Entry
    MAX-ACCESS  not-accessible
    STATUS  current
    DESCRIPTION
        "A row in the management network definition table."
    INDEX   {  agCurCfgMgmtNet6Index }
    ::= { agCurCfgMgmtNet6Table 1 }

AgCurCfgMgmtNet6Entry ::= SEQUENCE {
    agCurCfgMgmtNet6Index    Integer32,
    agCurCfgMgmtNet6Subnet      DisplayString,
    agCurCfgMgmtNet6Prefix      INTEGER,
    agCurCfgMgmtNet6Protocol    INTEGER
    }

agCurCfgMgmtNet6Index OBJECT-TYPE
    SYNTAX  Integer32
    MAX-ACCESS  read-only
    STATUS  current
    DESCRIPTION
        "The index of the Management Network Definition table."
    ::= { agCurCfgMgmtNet6Entry 1 }

agCurCfgMgmtNet6Subnet OBJECT-TYPE
    SYNTAX DisplayString (SIZE(0..40))
    MAX-ACCESS  read-only
    STATUS  current
    DESCRIPTION
    "  The IPV6 address of the allowed network over management port.
    Address should be 16-byte haxadecimal colon notation.
    Valid IPv6 address should be in any of the following forms xxxx:xxxx:xxxx:xxxx:xxxx:xxxx:xxxx:xxxx
    or xxxx::xxxx:xxxx:xxxx:xxxx or ::xxxx"
    ::= { agCurCfgMgmtNet6Entry 2 }

agCurCfgMgmtNet6Prefix OBJECT-TYPE
    SYNTAX  INTEGER  (1..128)
    MAX-ACCESS  read-only
    STATUS  current
    DESCRIPTION
    "  The IPV6 prefix length of the allowed networks on management port. "
    ::= { agCurCfgMgmtNet6Entry 3 }

agCurCfgMgmtNet6Protocol OBJECT-TYPE
    SYNTAX  INTEGER {
        ssh(1),
        telnet(2),
        sshTelnet(3),
        http(4),
        sshHttp(5),
        telnetHttp(6),
        sshTelnetHttp(7),
        https(8),
        sshHttps(9),
        httpsTelnet(10),
        sshTelnetHttps(11),
        httpHttps(12),
        sshHttpHttps(13),
        telnetHttpHttps(14),
        sshTelnetHttpHttps(15),
        snmp(16),
        sshSnmp(17),
        telnetSnmp(18),
        sshTelnetSnmp(19),
        httpSnmp(20),
        sshHttpSnmp(21),
        telnetHttpSnmp(22),
        sshTelnetHttpSnmp(23),
        httpsSnmp(24),
        sshHttpsSnmp(25),
        telnetHttpsSnmp(26),
        sshTelnetHttpsSnmp(27),
        httpHttpsSnmp(28),
        sshHttpHttpsSnmp(29),
        telnetHttpHttpsSnmp(30),
        sshTelnetHttpHttpsSnmp(31),
        report(32),
        sshreport(33),
        telnetreport(34),
        sshTelnetreport(35),
        httpreport(36),
        sshHttpreport(37),
        telnetHttpreport(38),
        sshTelnetHttpreport(39),
        httpsreport(40),
        sshHttpsreport(41),
        httpsTelnetreport(42),
        sshTelnetHttpsreport(43),
        httpHttpsreport(44),
        sshHttpHttpsreport(45),
        telnetHttpHttpsreport(46),
        sshTelnetHttpHttpsreport(47),
        snmpreport(48),
        sshSnmpreport(49),
        telnetSnmpreport(50),
        sshTelnetSnmpreport(51),
        httpSnmpreport(52),
        sshHttpSnmpreport(53),
        telnetHttpSnmpreport(54),
        sshTelnetHttpSnmpreport(55),
        httpsSnmpreport(56),
        sshHttpsSnmpreport(57),
        telnetHttpsSnmpreport(58),
        sshTelnetHttpsSnmpreport(59),
        httpHttpsSnmpreport(60),
        sshHttpHttpsSnmpreport(61),
        telnetHttpHttpsSnmpreport(62),
        sshTelnetHttpHttpsSnmpreport(63),
        none(64)
        }
    MAX-ACCESS  read-only
    STATUS  current
    DESCRIPTION
        "The Management Network Protocol access in the current_configuration
         block.

        1  - Ssh
        2  - Telnet
        3  - Ssh + Telnet
        4  - Http
        5  - Ssh + Http
        6  - Telnet + Http
        7  - Ssh + Telnet + Http
        8  - Https
        9  - Ssh + Https
        10 - Https + Telnet
        11 - Ssh + Telnet + Https
        12 - Http + Https
        13 - Ssh + Http + Https
        14 - Telnet + Http + Https
        15 - Ssh + Telnet + Http + Https
        16 - Snmp
        17 - Ssh + Snmp
        18 - Telnet + Snmp
        19 - Ssh + Telnet + Snmp
        20 - Http + Snmp
        21 - Ssh + Http + Snmp
        22 - Telnet + Http + Snmp
        23 - Ssh + Telnet + Http + Snmp
        24 - Https + Snmp
        25 - Ssh + Https + Snmp
        26 - Telnet + Https + Snmp
        27 - Ssh + Telnet + Https + Snmp
        28 - Http + Https + Snmp
        29 - Ssh + Http + Https + Snmp
        30 - Telnet + Http + Https + Snmp
        31 - Ssh + Telnet + Http + Https + Snmp
        32 - Report
        33 - Ssh + Report
        34 - Telnet + Report
        35 - Ssh + Telnet + Report
        36 - Http + Report
        37 - Ssh + Http + Report
        38 - Telnet + Http + Report
        39 - Ssh + Telnet + Http + Report
        40 - Https + Report
        41 - Ssh + Https + Report
        42 - Telnet + Https + Report
        43 - Ssh + Telnet + Https + Report
        44 - Telnet + Http + Https + Report
        45 - Ssh + Http + Https + Report
        46 - Telnet + Http + Https + Report
        47 - Ssh + Telnet + Http + Https + Report
        48 - Snmp + Report
        49 - Ssh + Snmp + Report
        50 - Telnet + Snmp + Report
        51 - Ssh + Telnet + Snmp + Report
        52 - Http + Snmp + Report
        53 - Ssh + Http + Snmp + Report
        54 - Telnet + Http + Snmp + Report
        55 - Ssh + Telnet + Http + Snmp + Report
        56 - Https + Snmp + Report
        57 - Ssh + Https + Snmp + Report
        58 - Telnet + Https + Snmp + Report
        59 - Ssh + Telnet + Https + Snmp + Report
        60 - Http + Https + Snmp + Report
        61 - Ssh + Http + Https + Snmp + Report
        62 - Telnet + Http + Https + Snmp + Report
        63 - Ssh + Telnet + Http + Https + Snmp + Report
        64 - none
     "
    ::= { agCurCfgMgmtNet6Entry 4 }

agNewCfgMgmtNetTable OBJECT-TYPE
    SYNTAX  SEQUENCE OF AgNewCfgMgmtNetEntry
    MAX-ACCESS  not-accessible
    STATUS  current
    DESCRIPTION
        "The table for Management Network definitions
         in the new configuration block."
    ::= { agMgmtNetConfig 3 }

agNewCfgMgmtNetEntry OBJECT-TYPE
    SYNTAX  AgNewCfgMgmtNetEntry
    MAX-ACCESS  not-accessible
    STATUS  current
    DESCRIPTION
        "A row in the management network definition table."
    INDEX   {  agNewCfgMgmtNetIndex }
    ::= { agNewCfgMgmtNetTable 1 }

AgNewCfgMgmtNetEntry ::= SEQUENCE {
    agNewCfgMgmtNetIndex  	Integer32,
    agNewCfgMgmtNetSubnet       IpAddress,
    agNewCfgMgmtNetMask         IpAddress,
    agNewCfgMgmtNetDelete       INTEGER,
    agNewCfgMgmtNetProtocol     INTEGER
    }

agNewCfgMgmtNetIndex OBJECT-TYPE
    SYNTAX  Integer32
    MAX-ACCESS  read-only
    STATUS  current
    DESCRIPTION
        "The index of the Management Network Definition table."
    ::= { agNewCfgMgmtNetEntry 1 }

agNewCfgMgmtNetSubnet OBJECT-TYPE
    SYNTAX  IpAddress
    MAX-ACCESS  read-create
    STATUS  current
    DESCRIPTION
        "The Management Network Address in the new_configuration
         block."
    ::= { agNewCfgMgmtNetEntry 2 }

agNewCfgMgmtNetMask OBJECT-TYPE
    SYNTAX  IpAddress
    MAX-ACCESS  read-create
    STATUS  current
    DESCRIPTION
        "The Management Network Mask in the new_configuration
         block."
    ::= { agNewCfgMgmtNetEntry 3 }

agNewCfgMgmtNetDelete OBJECT-TYPE
    SYNTAX  INTEGER {
        other(1),
        delete(2)
        }
    MAX-ACCESS  read-create
    STATUS  current
    DESCRIPTION
        "By setting the value to delete(2), the entire row is deleted."
    ::= { agNewCfgMgmtNetEntry 4 }

agNewCfgMgmtNetProtocol OBJECT-TYPE
    SYNTAX  INTEGER {
        ssh(1),
        telnet(2),
        sshTelnet(3),
        http(4),
        sshHttp(5),
        telnetHttp(6),
        sshTelnetHttp(7),
        https(8),
        sshHttps(9),
        httpsTelnet(10),
        sshTelnetHttps(11),
        httpHttps(12),
        sshHttpHttps(13),
        telnetHttpHttps(14),
        sshTelnetHttpHttps(15),
        snmp(16),
        sshSnmp(17),
        telnetSnmp(18),
        sshTelnetSnmp(19),
        httpSnmp(20),
        sshHttpSnmp(21),
        telnetHttpSnmp(22),
        sshTelnetHttpSnmp(23),
        httpsSnmp(24),
        sshHttpsSnmp(25),
        telnetHttpsSnmp(26),
        sshTelnetHttpsSnmp(27),
        httpHttpsSnmp(28),
        sshHttpHttpsSnmp(29),
        telnetHttpHttpsSnmp(30),
        sshTelnetHttpHttpsSnmp(31),
        report(32),
        sshreport(33),
        telnetreport(34),
        sshTelnetreport(35),
        httpreport(36),
        sshHttpreport(37),
        telnetHttpreport(38),
        sshTelnetHttpreport(39),
        httpsreport(40),
        sshHttpsreport(41),
        httpsTelnetreport(42),
        sshTelnetHttpsreport(43),
        httpHttpsreport(44),
        sshHttpHttpsreport(45),
        telnetHttpHttpsreport(46),
        sshTelnetHttpHttpsreport(47),
        snmpreport(48),
        sshSnmpreport(49),
        telnetSnmpreport(50),
        sshTelnetSnmpreport(51),
        httpSnmpreport(52),
        sshHttpSnmpreport(53),
        telnetHttpSnmpreport(54),
        sshTelnetHttpSnmpreport(55),
        httpsSnmpreport(56),
        sshHttpsSnmpreport(57),
        telnetHttpsSnmpreport(58),
        sshTelnetHttpsSnmpreport(59),
        httpHttpsSnmpreport(60),
        sshHttpHttpsSnmpreport(61),
        telnetHttpHttpsSnmpreport(62),
        sshTelnetHttpHttpsSnmpreport(63),
        none(64)
        }
    MAX-ACCESS  read-create
    STATUS  current
    DESCRIPTION
        "The Management Network Protocol access in the new_configuration
         block.

        1  - Ssh
        2  - Telnet
        3  - Ssh + Telnet
        4  - Http
        5  - Ssh + Http
        6  - Telnet + Http
        7  - Ssh + Telnet + Http
        8  - Https
        9  - Ssh + Https
        10 - Https + Telnet
        11 - Ssh + Telnet + Https
        12 - Http + Https
        13 - Ssh + Http + Https
        14 - Telnet + Http + Https
        15 - Ssh + Telnet + Http + Https
        16 - Snmp
        17 - Ssh + Snmp
        18 - Telnet + Snmp
        19 - Ssh + Telnet + Snmp
        20 - Http + Snmp
        21 - Ssh + Http + Snmp
        22 - Telnet + Http + Snmp
        23 - Ssh + Telnet + Http + Snmp
        24 - Https + Snmp
        25 - Ssh + Https + Snmp
        26 - Telnet + Https + Snmp
        27 - Ssh + Telnet + Https + Snmp
        28 - Http + Https + Snmp
        29 - Ssh + Http + Https + Snmp
        30 - Telnet + Http + Https + Snmp
        31 - Ssh + Telnet + Http + Https + Snmp
        32 - Report
        33 - Ssh + Report
        34 - Telnet + Report
        35 - Ssh + Telnet + Report
        36 - Http + Report
        37 - Ssh + Http + Report
        38 - Telnet + Http + Report
        39 - Ssh + Telnet + Http + Report
        40 - Https + Report
        41 - Ssh + Https + Report
        42 - Telnet + Https + Report
        43 - Ssh + Telnet + Https + Report
        44 - Telnet + Http + Https + Report
        45 - Ssh + Http + Https + Report
        46 - Telnet + Http + Https + Report
        47 - Ssh + Telnet + Http + Https + Report
        48 - Snmp + Report
        49 - Ssh + Snmp + Report
        50 - Telnet + Snmp + Report
        51 - Ssh + Telnet + Snmp + Report
        52 - Http + Snmp + Report
        53 - Ssh + Http + Snmp + Report
        54 - Telnet + Http + Snmp + Report
        55 - Ssh + Telnet + Http + Snmp + Report
        56 - Https + Snmp + Report
        57 - Ssh + Https + Snmp + Report
        58 - Telnet + Https + Snmp + Report
        59 - Ssh + Telnet + Https + Snmp + Report
        60 - Http + Https + Snmp + Report
        61 - Ssh + Http + Https + Snmp + Report
        62 - Telnet + Http + Https + Snmp + Report
        63 - Ssh + Telnet + Http + Https + Snmp + Report
        64 - none
	 "
    ::= { agNewCfgMgmtNetEntry 5 }

agNewCfgMgmtNet6Table OBJECT-TYPE
    SYNTAX  SEQUENCE OF AgNewCfgMgmtNet6Entry
    MAX-ACCESS  not-accessible
    STATUS  current
    DESCRIPTION
        "The table for Management Network definitions
         in the new configuration block."
    ::= { agMgmtNetConfig 5 }

agNewCfgMgmtNet6Entry OBJECT-TYPE
    SYNTAX  AgNewCfgMgmtNet6Entry
    MAX-ACCESS  not-accessible
    STATUS  current
    DESCRIPTION
        "A row in the management network definition table."
    INDEX   {  agNewCfgMgmtNet6Index }
    ::= { agNewCfgMgmtNet6Table 1 }

AgNewCfgMgmtNet6Entry ::= SEQUENCE {
    agNewCfgMgmtNet6Index    Integer32,
    agNewCfgMgmtNet6Subnet      DisplayString,
    agNewCfgMgmtNet6Prefix      INTEGER,
    agNewCfgMgmtNet6Protocol    INTEGER,
    agNewCfgMgmtNet6Delete      INTEGER
    }

agNewCfgMgmtNet6Index OBJECT-TYPE
    SYNTAX  Integer32
    MAX-ACCESS  read-only
    STATUS  current
    DESCRIPTION
        "The index of the Management Network Definition table."
    ::= { agNewCfgMgmtNet6Entry 1 }

agNewCfgMgmtNet6Subnet OBJECT-TYPE
    SYNTAX DisplayString (SIZE(0..40))
    MAX-ACCESS  read-create
    STATUS  current
    DESCRIPTION
    "  The IPV6 address of the allowed network over management port.
    Address should be 16-byte haxadecimal colon notation.
    Valid IPv6 address should be in any of the following forms xxxx:xxxx:xxxx:xxxx:xxxx:xxxx:xxxx:xxxx
    or xxxx::xxxx:xxxx:xxxx:xxxx or ::xxxx"
    ::= { agNewCfgMgmtNet6Entry 2 }

agNewCfgMgmtNet6Prefix OBJECT-TYPE
    SYNTAX  INTEGER  (1..128)
    MAX-ACCESS  read-create
    STATUS  current
    DESCRIPTION
        "The IPV6 prefix length of the allowed network management port. "
    ::= { agNewCfgMgmtNet6Entry 3 }

agNewCfgMgmtNet6Protocol OBJECT-TYPE
    SYNTAX  INTEGER {
        ssh(1),
        telnet(2),
        sshTelnet(3),
        http(4),
        sshHttp(5),
        telnetHttp(6),
        sshTelnetHttp(7),
        https(8),
        sshHttps(9),
        httpsTelnet(10),
        sshTelnetHttps(11),
        httpHttps(12),
        sshHttpHttps(13),
        telnetHttpHttps(14),
        sshTelnetHttpHttps(15),
        snmp(16),
        sshSnmp(17),
        telnetSnmp(18),
        sshTelnetSnmp(19),
        httpSnmp(20),
        sshHttpSnmp(21),
        telnetHttpSnmp(22),
        sshTelnetHttpSnmp(23),
        httpsSnmp(24),
        sshHttpsSnmp(25),
        telnetHttpsSnmp(26),
        sshTelnetHttpsSnmp(27),
        httpHttpsSnmp(28),
        sshHttpHttpsSnmp(29),
        telnetHttpHttpsSnmp(30),
        sshTelnetHttpHttpsSnmp(31),
        report(32),
        sshreport(33),
        telnetreport(34),
        sshTelnetreport(35),
        httpreport(36),
        sshHttpreport(37),
        telnetHttpreport(38),
        sshTelnetHttpreport(39),
        httpsreport(40),
        sshHttpsreport(41),
        httpsTelnetreport(42),
        sshTelnetHttpsreport(43),
        httpHttpsreport(44),
        sshHttpHttpsreport(45),
        telnetHttpHttpsreport(46),
        sshTelnetHttpHttpsreport(47),
        snmpreport(48),
        sshSnmpreport(49),
        telnetSnmpreport(50),
        sshTelnetSnmpreport(51),
        httpSnmpreport(52),
        sshHttpSnmpreport(53),
        telnetHttpSnmpreport(54),
        sshTelnetHttpSnmpreport(55),
        httpsSnmpreport(56),
        sshHttpsSnmpreport(57),
        telnetHttpsSnmpreport(58),
        sshTelnetHttpsSnmpreport(59),
        httpHttpsSnmpreport(60),
        sshHttpHttpsSnmpreport(61),
        telnetHttpHttpsSnmpreport(62),
        sshTelnetHttpHttpsSnmpreport(63),
        none(64)
        }
    MAX-ACCESS  read-create
    STATUS  current
    DESCRIPTION
        "The Management Network Protocol access in the current_configuration
         block.

        1  - Ssh
        2  - Telnet
        3  - Ssh + Telnet
        4  - Http
        5  - Ssh + Http
        6  - Telnet + Http
        7  - Ssh + Telnet + Http
        8  - Https
        9  - Ssh + Https
        10 - Https + Telnet
        11 - Ssh + Telnet + Https
        12 - Http + Https
        13 - Ssh + Http + Https
        14 - Telnet + Http + Https
        15 - Ssh + Telnet + Http + Https
        16 - Snmp
        17 - Ssh + Snmp
        18 - Telnet + Snmp
        19 - Ssh + Telnet + Snmp
        20 - Http + Snmp
        21 - Ssh + Http + Snmp
        22 - Telnet + Http + Snmp
        23 - Ssh + Telnet + Http + Snmp
        24 - Https + Snmp
        25 - Ssh + Https + Snmp
        26 - Telnet + Https + Snmp
        27 - Ssh + Telnet + Https + Snmp
        28 - Http + Https + Snmp
        29 - Ssh + Http + Https + Snmp
        30 - Telnet + Http + Https + Snmp
        31 - Ssh + Telnet + Http + Https + Snmp
        32 - Report
        33 - Ssh + Report
        34 - Telnet + Report
        35 - Ssh + Telnet + Report
        36 - Http + Report
        37 - Ssh + Http + Report
        38 - Telnet + Http + Report
        39 - Ssh + Telnet + Http + Report
        40 - Https + Report
        41 - Ssh + Https + Report
        42 - Telnet + Https + Report
        43 - Ssh + Telnet + Https + Report
        44 - Telnet + Http + Https + Report
        45 - Ssh + Http + Https + Report
        46 - Telnet + Http + Https + Report
        47 - Ssh + Telnet + Http + Https + Report
        48 - Snmp + Report
        49 - Ssh + Snmp + Report
        50 - Telnet + Snmp + Report
        51 - Ssh + Telnet + Snmp + Report
        52 - Http + Snmp + Report
        53 - Ssh + Http + Snmp + Report
        54 - Telnet + Http + Snmp + Report
        55 - Ssh + Telnet + Http + Snmp + Report
        56 - Https + Snmp + Report
        57 - Ssh + Https + Snmp + Report
        58 - Telnet + Https + Snmp + Report
        59 - Ssh + Telnet + Https + Snmp + Report
        60 - Http + Https + Snmp + Report
        61 - Ssh + Http + Https + Snmp + Report
        62 - Telnet + Http + Https + Snmp + Report
        63 - Ssh + Telnet + Http + Https + Snmp + Report
        64 - none
     "
    ::= { agNewCfgMgmtNet6Entry 4 }

agNewCfgMgmtNet6Delete OBJECT-TYPE
    SYNTAX  INTEGER {
        other(1),
        delete(2)
        }
    MAX-ACCESS  read-create
    STATUS  current
    DESCRIPTION
        "By setting the value to delete(2), the entire row is deleted."
    ::= { agNewCfgMgmtNet6Entry 5 }


-- Pattern Matching Group MIB objects
agPgrpMatchTableMaxSize OBJECT-TYPE
    SYNTAX  Integer32
    MAX-ACCESS  read-only
    STATUS  current
    DESCRIPTION
        "The maximum number of entries in the Pattern
         Match Group Table.
         Note:This mib is not supported for VX instance of Virtualization."
    ::= { agPgroup 1 }

agCurCfgPgrpMatchTable OBJECT-TYPE
    SYNTAX  SEQUENCE OF AgCurCfgPgrpMatchEntry
    MAX-ACCESS  not-accessible
    STATUS  current
    DESCRIPTION
        "The table for Pattern Match Group definitions
         in the current configuration block.
         Note:This table is not supported for VX instance of Virtualization."
    ::= { agPgroup 2 }

agCurCfgPgrpMatchEntry OBJECT-TYPE
    SYNTAX  AgCurCfgPgrpMatchEntry
    MAX-ACCESS  not-accessible
    STATUS  current
    DESCRIPTION
        "A row in the Pattern Match Group table."
    INDEX   {  agCurCfgPgrpMatchIndex }
    ::= { agCurCfgPgrpMatchTable 1 }

AgCurCfgPgrpMatchEntry ::= SEQUENCE {
    agCurCfgPgrpMatchIndex  	Integer32,
    agCurCfgPgrpName		DisplayString,
    agCurCfgPgrpMatchBmap       OCTET STRING
    }

agCurCfgPgrpMatchIndex OBJECT-TYPE
    SYNTAX  Integer32
    MAX-ACCESS  read-only
    STATUS  current
    DESCRIPTION
        "The index of the Pattern Match Group Definition table.
        Note:This mib is not supported for VX instance of Virtualization."
    ::= { agCurCfgPgrpMatchEntry 1 }

agCurCfgPgrpName OBJECT-TYPE
    SYNTAX  DisplayString (SIZE(0..31))
    MAX-ACCESS  read-only
    STATUS  current
    DESCRIPTION
        "The name for the Pattern Match Group."
    ::= { agCurCfgPgrpMatchEntry 2 }

agCurCfgPgrpMatchBmap OBJECT-TYPE
    SYNTAX  OCTET STRING
    MAX-ACCESS  read-only
    STATUS  current
    DESCRIPTION
        "The pattern matching rules applied to the port.  The pattern rules
         are presented in bitmap format.

         in receiving order:

	     OCTET 1  OCTET 2  .....
             xxxxxxxx xxxxxxxx .....
             ||    || |_ string 9
             ||    ||
             ||    ||___ string 8
             ||    |____ string 7
             ||      .    .   .
             ||_________ string 2
             |__________ string 1 (as index to slbCurCfgUrlLbPathTable)

         where x : 1 - The represented string matching rule applied
		   0 - The represented string matching rule applied"
    ::= { agCurCfgPgrpMatchEntry 3 }

agNewCfgPgrpMatchTable OBJECT-TYPE
    SYNTAX  SEQUENCE OF AgNewCfgPgrpMatchEntry
    MAX-ACCESS  not-accessible
    STATUS  current
    DESCRIPTION
        "The table for Pattern Match Group definitions
         in the new configuration block.
         Note:This table is not supported for VX instance of Virtualization."
    ::= { agPgroup 3 }

agNewCfgPgrpMatchEntry OBJECT-TYPE
    SYNTAX  AgNewCfgPgrpMatchEntry
    MAX-ACCESS  not-accessible
    STATUS  current
    DESCRIPTION
        "A row in the Pattern Match Group definition table."
    INDEX   {  agNewCfgPgrpMatchIndex }
    ::= { agNewCfgPgrpMatchTable 1 }

AgNewCfgPgrpMatchEntry ::= SEQUENCE {
    agNewCfgPgrpMatchIndex  	Integer32,
    agNewCfgPgrpName		DisplayString,
    agNewCfgPgrpMatchAdd        Integer32,
    agNewCfgPgrpMatchRem        Integer32,
    agNewCfgPgrpMatchBmap       OCTET STRING,
    agNewCfgPgrpDelete          INTEGER
    }

agNewCfgPgrpMatchIndex OBJECT-TYPE
    SYNTAX  Integer32
    MAX-ACCESS  read-only
    STATUS  current
    DESCRIPTION
        "The index of the Pattern Match Group Definition table.
        Note:This mib is not supported for VX instance of Virtualization."
    ::= { agNewCfgPgrpMatchEntry 1 }

agNewCfgPgrpName OBJECT-TYPE
    SYNTAX  DisplayString (SIZE(0..31))
    MAX-ACCESS  read-create
    STATUS  current
    DESCRIPTION
        "The name for the Pattern Match Group."
    ::= { agNewCfgPgrpMatchEntry 2 }

agNewCfgPgrpMatchAdd OBJECT-TYPE
    SYNTAX  Integer32
    MAX-ACCESS  read-create
    STATUS  current
    DESCRIPTION
        "The Pattern Match Group String added in the new_configuration
         block."
    ::= { agNewCfgPgrpMatchEntry 3 }

agNewCfgPgrpMatchRem OBJECT-TYPE
    SYNTAX  Integer32
    MAX-ACCESS  read-create
    STATUS  current
    DESCRIPTION
        "The Pattern Match Group String removed in the new_configuration
         block."
    ::= { agNewCfgPgrpMatchEntry 4 }

agNewCfgPgrpMatchBmap OBJECT-TYPE
    SYNTAX  OCTET STRING
    MAX-ACCESS  read-only
    STATUS  current
    DESCRIPTION
        "The pattern matching rules applied to the port.  The pattern rules
         are presented in bitmap format.

         in receiving order:

	     OCTET 1  OCTET 2  .....
             xxxxxxxx xxxxxxxx .....
             ||    || |_ string 9
             ||    ||
             ||    ||___ string 8
             ||    |____ string 7
             ||      .    .   .
             ||_________ string 2
             |__________ string 1 (as index to slbCurCfgUrlLbPathTable)

         where x : 1 - The represented string matching rule applied
		   0 - The represented string matching rule applied"
    ::= { agNewCfgPgrpMatchEntry 5 }

agNewCfgPgrpDelete OBJECT-TYPE
    SYNTAX  INTEGER {
        other(1),
        delete(2)
        }
    MAX-ACCESS  read-create
    STATUS  current
    DESCRIPTION
        "By setting the value to delete(2), the entire row is deleted."
    ::= { agNewCfgPgrpMatchEntry 6 }

agCfgSecurityPortTable OBJECT-TYPE
    SYNTAX  SEQUENCE OF AgCfgSecurityPortTableEntry
    MAX-ACCESS  not-accessible
    STATUS  current
    DESCRIPTION
        "The table of Security related features enabled/disabled for this port.
        Note:This table is not supported for VX instance of Virtualization."
    ::= { agSecurity 2 }

agCfgSecurityPortTableEntry OBJECT-TYPE
    SYNTAX  AgCfgSecurityPortTableEntry
    MAX-ACCESS  not-accessible
    STATUS  current
    DESCRIPTION
        "A row in the Security related in the current configuration block."
    INDEX   { agCfgSecurityPortIndx }
    ::= { agCfgSecurityPortTable 1 }

AgCfgSecurityPortTableEntry ::=
    SEQUENCE {
	agCfgSecurityPortIndx
	    Integer32,
	agCurCfgSecurityDosState
	    INTEGER,
	agNewCfgSecurityDosState
	    INTEGER,
        agCurCfgSecurityIpAclState
            INTEGER,
        agNewCfgSecurityIpAclState
            INTEGER,
        agCurCfgSecurityUbState
            INTEGER,
        agNewCfgSecurityUbState
            INTEGER,
        agCurCfgSecurityBogonState
            INTEGER,
        agCurCfgSecurityAttacksBmap
            OCTET STRING,
        agNewCfgSecurityAttacksBmap
            OCTET STRING,
        agNewCfgSecurityAddAttack
            INTEGER,
        agNewCfgSecurityRemAttack
            INTEGER,
        agNewCfgSecurityDoSAttacks
            INTEGER,
        agNewCfgSecurityBogonState
            INTEGER
    }

agCfgSecurityPortIndx OBJECT-TYPE
    SYNTAX  Integer32
    MAX-ACCESS  read-only
    STATUS  current
    DESCRIPTION
        "The port index.
        Note:This mib is not supported for VX instance of Virtualization."
    ::= { agCfgSecurityPortTableEntry 1 }

agCurCfgSecurityDosState OBJECT-TYPE
    SYNTAX  INTEGER {
        enabled(1),
        disabled(2)
        }
    MAX-ACCESS  read-only
    STATUS  current
    DESCRIPTION
        "Enable/Disable DOS attack per port."
    ::= { agCfgSecurityPortTableEntry 2 }

agNewCfgSecurityDosState OBJECT-TYPE
    SYNTAX  INTEGER {
        enabled(1),
        disabled(2)
        }
    MAX-ACCESS  read-write
    STATUS  current
    DESCRIPTION
        "Enable/Disable DOS attack per port."
    ::= { agCfgSecurityPortTableEntry 3 }

agCurCfgSecurityIpAclState OBJECT-TYPE
    SYNTAX  INTEGER {
        enabled(1),
        disabled(2)
        }
    MAX-ACCESS  read-only
    STATUS  current
    DESCRIPTION
        "Enable/Disable IP ACL per port."
    ::= { agCfgSecurityPortTableEntry 4 }

agNewCfgSecurityIpAclState OBJECT-TYPE
    SYNTAX  INTEGER {
        enabled(1),
        disabled(2)
        }
    MAX-ACCESS  read-write
    STATUS  current
    DESCRIPTION
        "Enable/Disable IP ACL per port."
    ::= { agCfgSecurityPortTableEntry 5 }

agCurCfgSecurityUbState OBJECT-TYPE
    SYNTAX  INTEGER {
        enabled(1),
        disabled(2)
        }
    MAX-ACCESS  read-only
    STATUS  current
    DESCRIPTION
        "Enable/Disable UDP Blast per port."
    ::= { agCfgSecurityPortTableEntry 6 }

agNewCfgSecurityUbState OBJECT-TYPE
    SYNTAX  INTEGER {
        enabled(1),
        disabled(2)
        }
    MAX-ACCESS  read-write
    STATUS  current
    DESCRIPTION
        "Enable/Disable UDP Blast per port."
    ::= { agCfgSecurityPortTableEntry 7 }

agCurCfgSecurityBogonState OBJECT-TYPE
    SYNTAX  INTEGER {
        enabled(1),
        disabled(2)
        }
    MAX-ACCESS  read-only
    STATUS  current
    DESCRIPTION
        "Enable/Disable Bogon IP ACL per port."
    ::= { agCfgSecurityPortTableEntry 8 }

agNewCfgSecurityBogonState OBJECT-TYPE
    SYNTAX  INTEGER {
        enabled(1),
        disabled(2)
        }
    MAX-ACCESS  read-write
    STATUS  current
    DESCRIPTION
        "Enable/Disable Bogon IP ACL per port."
    ::= { agCfgSecurityPortTableEntry 9 }

-- MIBs for perPort DoS Attacks add/rem

agCurCfgSecurityAttacksBmap OBJECT-TYPE
    SYNTAX  OCTET STRING
    MAX-ACCESS  read-only
    STATUS  current
    DESCRIPTION
        "The DoS Attacks added/removed for this port.
        The selected DoS Attacks are presented in a bitmap format.

         in receiving order:

             OCTET 1  OCTET 2  .....
             xxxxxxxx xxxxxxxx .....
             ||    || |_______  9
             ||    ||
             ||    ||_________  8
             ||    |__________  7
             ||      .    .   .
             ||________________ 2
             |________________  1

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

        where x :      1 - The represented DoS Attack is enabled
                       0 - The represented DoS Attack is disabled"
    ::= { agCfgSecurityPortTableEntry 10 }

agNewCfgSecurityAttacksBmap OBJECT-TYPE
    SYNTAX  OCTET STRING
    MAX-ACCESS  read-only
    STATUS  current
    DESCRIPTION
        "The DoS Attacks added/removed for this port.
        The selected DoS Attacks are presented in a bitmap format.

         in receiving order:

             OCTET 1  OCTET 2  .....
             xxxxxxxx xxxxxxxx .....
             ||    || |______  9
             ||    ||
             ||    ||________  8
             ||    |_________  7
             ||      .    .   .
             ||_______________ 2
             |________________ 1

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

        where x :      1 - The represented DoS Attack is enabled
                       0 - The represented DoS Attack is disabled"
    ::= { agCfgSecurityPortTableEntry 11 }

agNewCfgSecurityAddAttack OBJECT-TYPE
    SYNTAX  INTEGER {
        iplen(1),
        ipversion(2),
        broadcast(3),
        loopback(4),
        land(5),
        ipreserved(6),
        ipttl(7),
        ipprot(8),
        ipoptlen(9),
        fragmoredont(10),
        fragdata(11),
        fragboundary(12),
        fraglast(13),
        fragdontoff(14),
        fragopt(15),
        fragoff(16),
        fragoversize(17),
        tcplen(18),
        tcpportzero(19),
        blat(20),
        tcpreserved(21),
        nullscan(22),
        fullxmasscan(23),
        finscan(24),
        vecnascan(25),
        xmassscan(26),
        synfinscan(27),
        flagabnormal(28),
        syndata(29),
        synfrag(30),
        ftpport(31),
        dnsport(32),
        seqzero(33),
        ackzero(34),
        tcpoptlen(35),
        udplen(36),
        udpportzero(37),
        fraggle(38),
        pepsi(39),
        rc8(40),
        snmpnull(41),
        icmplen(42),
        smurf(43),
        icmpdata(44),
        icmpoff(45),
        icmptype(46),
        igmplen(47),
        igmpfrag(48),
        igmptype(49),
        arplen(50),
        arpnbcast(51),
        arpnucast(52),
        arpspoof(53),
        garp(54),
        ip6len(55),
        ip6version(56)
        }
    MAX-ACCESS  read-write
    STATUS  current
    DESCRIPTION
        "This is an action object to add a DoS Attack to a port. The value
         specified with this object is number given in this description.

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

            When read, the value '0' is returned always."
    ::= { agCfgSecurityPortTableEntry 12 }

agNewCfgSecurityRemAttack  OBJECT-TYPE
    SYNTAX  INTEGER {
        iplen(1),
        ipversion(2),
        broadcast(3),
        loopback(4),
        land(5),
        ipreserved(6),
        ipttl(7),
        ipprot(8),
        ipoptlen(9),
        fragmoredont(10),
        fragdata(11),
        fragboundary(12),
        fraglast(13),
        fragdontoff(14),
        fragopt(15),
        fragoff(16),
        fragoversize(17),
        tcplen(18),
        tcpportzero(19),
        blat(20),
        tcpreserved(21),
        nullscan(22),
        fullxmasscan(23),
        finscan(24),
        vecnascan(25),
        xmassscan(26),
        synfinscan(27),
        flagabnormal(28),
        syndata(29),
        synfrag(30),
        ftpport(31),
        dnsport(32),
        seqzero(33),
        ackzero(34),
        tcpoptlen(35),
        udplen(36),
        udpportzero(37),
        fraggle(38),
        pepsi(39),
        rc8(40),
        snmpnull(41),
        icmplen(42),
        smurf(43),
        icmpdata(44),
        icmpoff(45),
        icmptype(46),
        igmplen(47),
        igmpfrag(48),
        igmptype(49),
        arplen(50),
        arpnbcast(51),
        arpnucast(52),
        arpspoof(53),
        garp(54),
        ip6len(55),
        ip6version(56)
        }
    MAX-ACCESS  read-write
    STATUS  current
    DESCRIPTION
        "This is an action object to remove a DoS attack for a port. The
         value specified with this object is number given in this description.

        1  - IPLen
        2  - IPVersion
        3  - Broadcast
        4  - Loopback
        5  - Land
        6  - IPReserved
        7  - IPTTL
        8  - IPProt
        9  - IPOptLen
        10 - FragMoreDont
        11 - FragData
        12 - FragBoundary
        13 - FragLast
        14 - FragDontOff
        15 - FragOpt
        16 - FragOff
        17 - FragOversize
        18 - TCPLen
        19 - TCPPortZero
        20 - BlatAttack
        21 - TCPReserved
        22 - NullScanAttack
        23 - FullXmasScan
        24 - FinScan
        25 - VecnaScan
        26 - XmasScanAttack
        27 - SynFinScan
        28 - FlagAbnormal
        29 - SYNData
        30 - SYNFrag
        31 - FTPPort
        32 - DNSPort
        33 - SeqZero
        34 - AckZero
        35 - TCPOptLen
        36 - UDPLen
        37 - UDPPortZero
        38 - FraggleAttack
        39 - Pepsi
        40 - Rc8
        41 - SNMPNull
        42 - ICMPLen
        43 - SmurfAttack
        44 - ICMPData
        45 - ICMPOff
        46 - ICMPType
        47 - IGMPLen
        48 - IGMPFrag
        49 - IGMPType
        50 - ARPLen
        51 - ARPNbCast
        52 - ARPNuCast
        53 - ARPSpoof
        54 - GARP
        55 - IP6Len
        56 - IP6Version

            When read, the value '0' is returned always."
    ::= { agCfgSecurityPortTableEntry 13 }

agNewCfgSecurityDoSAttacks OBJECT-TYPE
    SYNTAX  INTEGER {
	ok(1),
	addall(2),
	remall(3)
    }
    MAX-ACCESS  read-write
    STATUS  current
    DESCRIPTION
	"Add all DoS attacks to the port by setting the value to '2'.
	 Remove all DoS attacks from the port by setting the value to '3'.
	 Do nothing by setting the value to '1'.
 	 When read, the value '0' is returned always."
    ::= { agCfgSecurityPortTableEntry 14 }

--
-- IP Reputation configuration
--

-- enable / disable feature, max values & actions

ipRepEnableCurCfg OBJECT-TYPE
    SYNTAX  INTEGER {
        disable(0),
        enable(1)
        }
    MAX-ACCESS  read-only
    STATUS  current
    DESCRIPTION
        "Enable/disable IP reputation feature"
    ::= { ipRepCfg 1 }

ipRepEnableNewCfg OBJECT-TYPE
    SYNTAX  INTEGER{
        disable(0),
        enable(1)
        }
    MAX-ACCESS  read-write
    STATUS  current
    DESCRIPTION
        "Enable/disable IP reputation feature"
    ::= { ipRepCfg 2 }

ipRepWhiteListTableMaxSize OBJECT-TYPE
    SYNTAX  Integer32
    MAX-ACCESS  read-only
    STATUS  current
    DESCRIPTION
        "The maximum number of rows in the IP reputation white list table."
    ::= { ipRepCfg 3 }

ipRepCountriesTableMaxSize OBJECT-TYPE
    SYNTAX  Integer32
    MAX-ACCESS  read-only
    STATUS  current
    DESCRIPTION
        "The maximum number of rows in the IP reputation countries/geolocations table."
    ::= { ipRepCfg 4 }

ipRepNewCfgActionsErtTorLow OBJECT-TYPE
    SYNTAX  INTEGER {
        allow(1),
        block(2),
        alarm(3)
       }
    MAX-ACCESS  read-write
    STATUS  current
    DESCRIPTION
        "Action for Ert_tor category of Low severity."
    ::= { ipRepCfg 5}

ipRepCurCfgActionsErtTorLow OBJECT-TYPE
    SYNTAX  INTEGER {
        allow(1),
        block(2),
        alarm(3)
       }
    MAX-ACCESS  read-only
    STATUS  current
    DESCRIPTION
        "Action for Ert_tor category of Low severity."
    ::= { ipRepCfg 6}

ipRepNewCfgActionsErtTorMedium OBJECT-TYPE
    SYNTAX  INTEGER {
        allow(1),
        block(2),
        alarm(3)
       }
    MAX-ACCESS  read-write
    STATUS  current
    DESCRIPTION
        "Action for Ert_tor category of Medium severity."
    ::= { ipRepCfg 7}

ipRepCurCfgActionsErtTorMedium OBJECT-TYPE
    SYNTAX  INTEGER {
        allow(1),
        block(2),
        alarm(3)
       }
    MAX-ACCESS  read-only
    STATUS  current
    DESCRIPTION
        "Action for Ert_tor category of Medium severity."
    ::= { ipRepCfg 8}

ipRepNewCfgActionsErtTorHigh OBJECT-TYPE
    SYNTAX  INTEGER {
        allow(1),
        block(2),
        alarm(3)
       }
    MAX-ACCESS  read-write
    STATUS  current
    DESCRIPTION
        "Action for Ert_tor category of High severity."
    ::= { ipRepCfg 9}

ipRepCurCfgActionsErtTorHigh OBJECT-TYPE
    SYNTAX  INTEGER {
        allow(1),
        block(2),
        alarm(3)
       }
    MAX-ACCESS  read-only
    STATUS  current
    DESCRIPTION
        "Action for Ert_tor category of High severity."
    ::= { ipRepCfg 10}

ipRepNewCfgActionsErtMaliciousLow OBJECT-TYPE
    SYNTAX  INTEGER {
        allow(1),
        block(2),
        alarm(3)
       }
    MAX-ACCESS  read-write
    STATUS  current
    DESCRIPTION
        "Action for Ert_Malicious category of Low severity."
    ::= { ipRepCfg 11}

ipRepCurCfgActionsErtMaliciousLow OBJECT-TYPE
    SYNTAX  INTEGER {
        allow(1),
        block(2),
        alarm(3)
       }
    MAX-ACCESS  read-only
    STATUS  current
    DESCRIPTION
        "Action for Ert_Malicious category of Low severity."
    ::= { ipRepCfg 12}

ipRepNewCfgActionsErtMaliciousMedium OBJECT-TYPE
    SYNTAX  INTEGER {
        allow(1),
        block(2),
        alarm(3)
       }
    MAX-ACCESS  read-write
    STATUS  current
    DESCRIPTION
        "Action for Ert_Malicious category of Medium severity."
    ::= { ipRepCfg 13}

ipRepCurCfgActionsErtMaliciousMedium OBJECT-TYPE
    SYNTAX  INTEGER {
        allow(1),
        block(2),
        alarm(3)
       }
    MAX-ACCESS  read-only
    STATUS  current
    DESCRIPTION
        "Action for Ert_Malicious category of Medium severity."
    ::= { ipRepCfg 14}

ipRepNewCfgActionsErtMaliciousHigh OBJECT-TYPE
    SYNTAX  INTEGER {
        allow(1),
        block(2),
        alarm(3)
       }
    MAX-ACCESS  read-write
    STATUS  current
    DESCRIPTION
        "Action for Ert_Malicious category of High severity."
    ::= { ipRepCfg 15}

ipRepCurCfgActionsErtMaliciousHigh OBJECT-TYPE
    SYNTAX  INTEGER {
        allow(1),
        block(2),
        alarm(3)
       }
    MAX-ACCESS  read-only
    STATUS  current
    DESCRIPTION
        "Action for Ert_Malicious category of High severity."
    ::= { ipRepCfg 16}

ipRepCurCfgCountriesMap OBJECT-TYPE
    SYNTAX OCTET STRING
    MAX-ACCESS read-only
    STATUS current
    DESCRIPTION
        "Bit map of blocked countries/geolocations in IP reputation feature

         as follows:

         OCTET 1  OCTET 2  .....
         xxxxxxxx xxxxxxxx .....
         ||    || |_ Rmap 9
         ||    ||
         ||    ||___ Country #8
         ||    |____ Country #7
         ||      .    .   .
         ||_________ Country #2
         |__________ Country #1

         where x : 1 - The represented country is selected
         0 - The represented country is not selected"
    ::= { ipRepCfg 17 }

ipRepNewCfgCountriesMap OBJECT-TYPE
    SYNTAX OCTET STRING
    MAX-ACCESS read-only
    STATUS current
    DESCRIPTION
        "Bit map of blocked countries/geolocations in IP reputation feature

         as follows:

         OCTET 1  OCTET 2  .....
         xxxxxxxx xxxxxxxx .....
         ||    || |_ Rmap 9
         ||    ||
         ||    ||___ Country #8
         ||    |____ Country #7
         ||      .    .   .
         ||_________ Country #2
         |__________ Country #1

         where x : 1 - The represented country is selected
         0 - The represented country is not selected"
    ::= { ipRepCfg 18 }

ipRepNewCfgCountriesMapAddCountry OBJECT-TYPE
    SYNTAX INTEGER
    MAX-ACCESS read-write
    STATUS current
    DESCRIPTION
	"The country/geolocation to be added into countries/geolocations bit map. When read, empty string is returned."
    ::= { ipRepCfg 19 }

ipRepNewCfgCountriesMapRemCountry OBJECT-TYPE
    SYNTAX INTEGER
    MAX-ACCESS read-write
    STATUS current
    DESCRIPTION
	"The country/geolocation to be removed from countries/geolocations bit map. When read,
         empty string is returned."
    ::= { ipRepCfg 20 }


ipRepBaselineLastUpdate OBJECT-TYPE
    SYNTAX DisplayString
    MAX-ACCESS read-only
    STATUS current
    DESCRIPTION
	"Time stamp of last IP reputation baseline update."
    ::= { ipRepCfg 21 }

ipRepBaselineLastUpdateStatus OBJECT-TYPE
    SYNTAX DisplayString
    MAX-ACCESS read-only
    STATUS current
    DESCRIPTION
	"Status of last IP reputation baseline update."
    ::= { ipRepCfg 22 }

ipRepDeltaLastUpdate OBJECT-TYPE
    SYNTAX DisplayString
    MAX-ACCESS read-only
    STATUS current
    DESCRIPTION
	"Time stamp of last IP reputation delta update."
    ::= { ipRepCfg 23 }

ipRepDeltaLastUpdateStatus OBJECT-TYPE
    SYNTAX DisplayString
    MAX-ACCESS read-only
    STATUS current
    DESCRIPTION
	"Status of last IP reputation delta update."
    ::= { ipRepCfg 24 }

ipRepVisionUrlCurCfg OBJECT-TYPE
    SYNTAX DisplayString(SIZE(0..255))
    MAX-ACCESS  read-only
    STATUS  current
    DESCRIPTION
        "Vision URL for IP reputation feature"
    ::= { ipRepCfg 29 }

ipRepVisionUrlNewCfg OBJECT-TYPE
    SYNTAX DisplayString(SIZE(0..255))
    MAX-ACCESS  read-write
    STATUS  current
    DESCRIPTION
        "Vision URL for IP reputation feature"
    ::= { ipRepCfg 30 }

ipRepIndirectCurCfg OBJECT-TYPE
    SYNTAX  INTEGER{
        direct(0),
        indirect(1)
        }
    MAX-ACCESS  read-only
    STATUS  current
    DESCRIPTION
        "Feed Download Location"
    ::= { ipRepCfg 31 }

ipRepIndirectNewCfg OBJECT-TYPE
    SYNTAX  INTEGER{
        direct(0),
        indirect(1)
        }
    MAX-ACCESS  read-write
    STATUS  current
    DESCRIPTION
        "Feed Download Location"
    ::= { ipRepCfg 32 }

-- white list

ipRepNewWhiteListTable OBJECT-TYPE
    SYNTAX  SEQUENCE OF IpRepNewWhiteListTableEntry
    MAX-ACCESS  not-accessible
    STATUS  current
    DESCRIPTION
        "The IP reputation white list table (new configuration block).
        Note:This table is not supported for VX instance of Virtualization."
    ::= { ipRepCfg 25 }

    ipRepNewWhiteListTableEntry OBJECT-TYPE
    SYNTAX  IpRepNewWhiteListTableEntry
    MAX-ACCESS  not-accessible
    STATUS  current
    DESCRIPTION
        "A row in the IP reputation white list table."
    INDEX   { ipRepNewWhiteListIndex }
    ::= { ipRepNewWhiteListTable 1 }

IpRepNewWhiteListTableEntry ::= SEQUENCE {
    ipRepNewWhiteListIndex           INTEGER,
    ipRepNewWhiteListIP              IpAddress,
    ipRepNewWhiteListMask            IpAddress,
    ipRepNewWhiteListAction          INTEGER
    }

ipRepNewWhiteListIndex OBJECT-TYPE
    SYNTAX  INTEGER
    MAX-ACCESS  read-only
    STATUS  current
    DESCRIPTION
        "index of IP address in white list of IP reputation.
        Note:This mib is not supported for VX instance of Virtualization."
    ::= { ipRepNewWhiteListTableEntry 1}

ipRepNewWhiteListIP OBJECT-TYPE
    SYNTAX  IpAddress
    MAX-ACCESS  read-create
    STATUS  current
    DESCRIPTION
        "IP address in the white list of IP reputation."
    ::= { ipRepNewWhiteListTableEntry 2}

ipRepNewWhiteListMask OBJECT-TYPE
    SYNTAX  IpAddress
    MAX-ACCESS  read-create
    STATUS  current
    DESCRIPTION
        "mask of IP address in the white list of IP reputation."
    ::= { ipRepNewWhiteListTableEntry 3}

ipRepNewWhiteListAction OBJECT-TYPE
    SYNTAX  INTEGER{
        other(1),
        delete(2)
        }
    MAX-ACCESS  read-create
    STATUS  current
    DESCRIPTION
        "action flag of IP address in white list of IP reputation (2 - delete, 1 - do nothing)."
    ::= { ipRepNewWhiteListTableEntry 4}

ipRepCurWhiteListTable OBJECT-TYPE
    SYNTAX  SEQUENCE OF IpRepCurWhiteListTableEntry
    MAX-ACCESS  not-accessible
    STATUS  current
    DESCRIPTION
        "The IP reputation white list table (current configuration block).
        Note:This table is not supported for VX instance of Virtualization."
    ::= { ipRepCfg 26 }

    ipRepCurWhiteListTableEntry OBJECT-TYPE
    SYNTAX  IpRepCurWhiteListTableEntry
    MAX-ACCESS  not-accessible
    STATUS  current
    DESCRIPTION
        "A row in the IP reputation white list table."
    INDEX   { ipRepCurWhiteListIndex }
    ::= { ipRepCurWhiteListTable 1 }

IpRepCurWhiteListTableEntry ::= SEQUENCE {
    ipRepCurWhiteListIndex           INTEGER,
    ipRepCurWhiteListIP              IpAddress,
    ipRepCurWhiteListMask            IpAddress
    }

ipRepCurWhiteListIndex OBJECT-TYPE
    SYNTAX  INTEGER
    MAX-ACCESS  read-write
    STATUS  current
    DESCRIPTION
        "index of IP address in white list of IP reputation.
        Note:This mib is not supported for VX instance of Virtualization."
    ::= { ipRepCurWhiteListTableEntry 1}

ipRepCurWhiteListIP OBJECT-TYPE
    SYNTAX  IpAddress
    MAX-ACCESS  read-only
    STATUS  current
    DESCRIPTION
        "IP address in the white list of IP reputation."
    ::= { ipRepCurWhiteListTableEntry 2}

ipRepCurWhiteListMask OBJECT-TYPE
    SYNTAX  IpAddress
    MAX-ACCESS  read-only
    STATUS  current
    DESCRIPTION
        "mask of IP address in the white list of IP reputation."
    ::= { ipRepCurWhiteListTableEntry 3}

-- countries

ipRepNewCountriesTable OBJECT-TYPE
    SYNTAX  SEQUENCE OF IpRepNewCountriesTableEntry
    MAX-ACCESS  not-accessible
    STATUS  current
    DESCRIPTION
        "The IP reputation countries/geolocations table (new configuration block).
        Note:This table is not supported for VX instance of Virtualization."
    ::= { ipRepCfg 27 }

    ipRepNewCountriesTableEntry OBJECT-TYPE
    SYNTAX  IpRepNewCountriesTableEntry
    MAX-ACCESS  not-accessible
    STATUS  current
    DESCRIPTION
        "A row in the IP reputation countries/geolocations table."
    INDEX   { ipRepNewCfgCountriesIndex }
    ::= { ipRepNewCountriesTable 1 }

IpRepNewCountriesTableEntry ::= SEQUENCE {
    ipRepNewCfgCountriesIndex         INTEGER,
    ipRepNewCfgCountriesCountry       DisplayString
    }

ipRepNewCfgCountriesIndex OBJECT-TYPE
    SYNTAX  INTEGER
    MAX-ACCESS  read-only
    STATUS  current
    DESCRIPTION
        "index of country/geolocation in the blocked countries/geolocations list of IP reputation.
        Note:This mib is not supported for VX instance of Virtualization."
    ::= { ipRepNewCountriesTableEntry 1}

ipRepNewCfgCountriesCountry OBJECT-TYPE
    SYNTAX  DisplayString (SIZE(0..50))
    MAX-ACCESS  read-only
    STATUS  current
    DESCRIPTION
        "Country/Geolocation in the blocked countries/geolocations list of IP reputation."
    ::= { ipRepNewCountriesTableEntry 2}

ipRepCurCountriesTable OBJECT-TYPE
    SYNTAX  SEQUENCE OF IpRepCurCountriesTableEntry
    MAX-ACCESS  not-accessible
    STATUS  current
    DESCRIPTION
        "The IP reputation countries/geolocations table (current configuration block).
        Note:This table is not supported for VX instance of Virtualization."
    ::= { ipRepCfg 28 }

    ipRepCurCountriesTableEntry OBJECT-TYPE
    SYNTAX  IpRepCurCountriesTableEntry
    MAX-ACCESS  not-accessible
    STATUS  current
    DESCRIPTION
        "A row in the IP reputation countries/geolocations table."
    INDEX   { ipRepCurCfgCountriesIndex }
    ::= { ipRepCurCountriesTable 1 }

IpRepCurCountriesTableEntry ::= SEQUENCE {
    ipRepCurCfgCountriesIndex      INTEGER,
    ipRepCurCfgCountriesCountry    DisplayString
    }

ipRepCurCfgCountriesIndex OBJECT-TYPE
    SYNTAX  INTEGER
    MAX-ACCESS  read-only
    STATUS  current
    DESCRIPTION
        "index of country/geolocation in the blocked countries/geolocations list of IP reputation.
        Note:This mib is not supported for VX instance of Virtualization."
    ::= { ipRepCurCountriesTableEntry 1}

ipRepCurCfgCountriesCountry OBJECT-TYPE
    SYNTAX  DisplayString (SIZE(0..50))
    MAX-ACCESS  read-only
    STATUS  current
    DESCRIPTION
        "Country/Geolocation in the blocked countries/geolocations list of IP reputation."
    ::= { ipRepCurCountriesTableEntry 2}
--
-- IP_ACL: IP Address ACL Configuration
--

ipAclTableMaxSize OBJECT-TYPE
    SYNTAX  Integer32
    MAX-ACCESS  read-only
    STATUS  current
    DESCRIPTION
        "The maximum number of rows in the IP ACL table."
    ::= { ipAclCfg 1 }

ipAclCurCfgTable OBJECT-TYPE
    SYNTAX  SEQUENCE OF IpAclCurCfgEntry
    MAX-ACCESS  not-accessible
    STATUS  current
    DESCRIPTION
        "The table of IP ACL in the current configuration block.
        Note: This table is not supported in VX instance of Virtualization."
    ::= { ipAclCfg 2 }

ipAclCurCfgEntry OBJECT-TYPE
    SYNTAX  IpAclCurCfgEntry
    MAX-ACCESS  not-accessible
    STATUS  current
    DESCRIPTION
        "A row in the IP ACL table"
    INDEX   { ipAclCurCfgIndx }
    ::= { ipAclCurCfgTable 1 }

IpAclCurCfgEntry ::= SEQUENCE {
    ipAclCurCfgIndx             Integer32,
    ipAclCurCfgIp               IpAddress,
    ipAclCurCfgMask             IpAddress
    }

ipAclCurCfgIndx OBJECT-TYPE
    SYNTAX  Integer32
    MAX-ACCESS  read-only
    STATUS  current
    DESCRIPTION
        "The index of the IP ACL table.
        Note: This mib is not supported in VX instance of Virtualization."
    ::= { ipAclCurCfgEntry 1}

ipAclCurCfgIp OBJECT-TYPE
    SYNTAX  IpAddress
    MAX-ACCESS  read-only
    STATUS  current
    DESCRIPTION
        "The IP address of the entry."
    ::= { ipAclCurCfgEntry 2}

ipAclCurCfgMask OBJECT-TYPE
    SYNTAX  IpAddress
    MAX-ACCESS  read-only
    STATUS  current
    DESCRIPTION
        "The IP address Mask of the entry.
        Note: This mib is not supported in VX instance of Virtualization."
    ::= { ipAclCurCfgEntry 3}

ipAclNewCfgTable OBJECT-TYPE
    SYNTAX  SEQUENCE OF IpAclNewCfgEntry
    MAX-ACCESS  not-accessible
    STATUS  current
    DESCRIPTION
        "The table of IP ACL in the new configuration block.
        Note: This table is not supported in VX instance of Virtualization."
    ::= { ipAclCfg 3 }

ipAclNewCfgEntry OBJECT-TYPE
    SYNTAX  IpAclNewCfgEntry
    MAX-ACCESS  not-accessible
    STATUS  current
    DESCRIPTION
        "A row in the IP ACL table.
        Note: This table is not supported in VX instance of Virtualization."
    INDEX   { ipAclNewCfgIndx }
    ::= { ipAclNewCfgTable 1 }

IpAclNewCfgEntry ::= SEQUENCE {
    ipAclNewCfgIndx             Integer32,
    ipAclNewCfgIp               IpAddress,
    ipAclNewCfgAction           INTEGER,
    ipAclNewCfgMask             IpAddress
    }

ipAclNewCfgIndx OBJECT-TYPE
    SYNTAX  Integer32
    MAX-ACCESS  read-only
    STATUS  current
    DESCRIPTION
        "The index of the IP ACL table.
        Note: This table is not supported in VX instance of Virtualization."
    ::= { ipAclNewCfgEntry 1}

ipAclNewCfgIp OBJECT-TYPE
    SYNTAX  IpAddress
    MAX-ACCESS  read-create
    STATUS  current
    DESCRIPTION
        "The IP address of the entry."
    ::= { ipAclNewCfgEntry 2}

ipAclNewCfgAction OBJECT-TYPE
    SYNTAX  INTEGER {
        other(1),
        delete(2)
       }
    MAX-ACCESS  read-create
    STATUS  current
    DESCRIPTION
        "When set to the value of 2 (delete), the entire row is deleted.
         When read, other is returned. Setting the value to anything other
         than 2(delete) has no effect on the state of the row."
    ::= { ipAclNewCfgEntry 3 }

ipAclNewCfgMask OBJECT-TYPE
    SYNTAX  IpAddress
    MAX-ACCESS  read-create
    STATUS  current
    DESCRIPTION
        "The IP address Mask of the entry."
    ::= { ipAclNewCfgEntry 4}


-- UDP_BLAST: UDP Blast Protection

udpBlastudpPortTableMaxSize OBJECT-TYPE
    SYNTAX  Integer32
    MAX-ACCESS  read-only
    STATUS  current
    DESCRIPTION
        "The maximum number of rows in the UDP Blast Port table.
        Note: This mib is not supported in VX instance of Virtualization."
    ::= { udpBlastCfg 1 }

udpBlastCurCfgudpPortPacketLimit OBJECT-TYPE
    SYNTAX  INTEGER(1..20000000)
    MAX-ACCESS  read-only
    STATUS  current
    DESCRIPTION
        "The default packet limit in the current configuration block."
    ::= { udpBlastCfg 2 }

udpBlastCurCfgudpPortTable OBJECT-TYPE
    SYNTAX  SEQUENCE OF UdpBlastCurCfgudpPortEntry
    MAX-ACCESS  not-accessible
    STATUS  current
    DESCRIPTION
        "The UDP Blast port table in the current configuration block.
        Note: This table is not supported in VX instance of Virtualization."
    ::= { udpBlastCfg 3 }

udpBlastCurCfgudpPortEntry OBJECT-TYPE
    SYNTAX  UdpBlastCurCfgudpPortEntry
    MAX-ACCESS  not-accessible
    STATUS  current
    DESCRIPTION
        "A row in the UDP Blast UDP Port table"
    INDEX   { udpBlastCurCfgudpPortLowIndx, udpBlastCurCfgudpPortHighIndx}
    ::= { udpBlastCurCfgudpPortTable 1 }

UdpBlastCurCfgudpPortEntry ::= SEQUENCE {
    udpBlastCurCfgudpPortLowIndx              INTEGER,
    udpBlastCurCfgudpPortHighIndx             INTEGER,
    udpBlastCurCfgudpPortEntryPacketLimit     INTEGER
    }

udpBlastCurCfgudpPortLowIndx OBJECT-TYPE
    SYNTAX  INTEGER(1..65535)
    MAX-ACCESS  read-only
    STATUS  current
    DESCRIPTION
        "The low UDP port number of UDP port range in the UDP Port table.
        Note: This mib is not supported in VX instance of Virtualization."
    ::= { udpBlastCurCfgudpPortEntry 1}

udpBlastCurCfgudpPortHighIndx OBJECT-TYPE
    SYNTAX  INTEGER(1..65535)
    MAX-ACCESS  read-only
    STATUS  current
    DESCRIPTION
        "The high UDP port number of UDP port range in the UDP Port table.
         If highIndx and lowIndx are set to the same, it is considered a
         single port instead of range
         Note: This mib is not supported in VX instance of Virtualization."
    ::= { udpBlastCurCfgudpPortEntry 2}

udpBlastCurCfgudpPortEntryPacketLimit OBJECT-TYPE
    SYNTAX  INTEGER(1..20000000)
    MAX-ACCESS  read-only
    STATUS  current
    DESCRIPTION
        "The Packet Limit of the UDP Port Entry."
    ::= { udpBlastCurCfgudpPortEntry 3}

udpBlastNewCfgudpPortPacketLimit OBJECT-TYPE
    SYNTAX  INTEGER(1..20000000)
    MAX-ACCESS  read-write
    STATUS  current
    DESCRIPTION
        "The default packet limit in the new configuration block."
    ::= { udpBlastCfg 4 }

udpBlastNewCfgudpPortTable OBJECT-TYPE
    SYNTAX  SEQUENCE OF UdpBlastNewCfgudpPortEntry
    MAX-ACCESS  not-accessible
    STATUS  current
    DESCRIPTION
        "The UDP Blast table in the new configuration block.
        Note: This table is not supported in VX instance of Virtualization."
    ::= { udpBlastCfg 5 }

udpBlastNewCfgudpPortEntry OBJECT-TYPE
    SYNTAX  UdpBlastNewCfgudpPortEntry
    MAX-ACCESS  not-accessible
    STATUS  current
    DESCRIPTION
        "A row in the UDP Blast UDP Port table"
    INDEX   { udpBlastNewCfgudpPortLowIndx, udpBlastNewCfgudpPortHighIndx}
    ::= { udpBlastNewCfgudpPortTable 1 }

UdpBlastNewCfgudpPortEntry ::= SEQUENCE {
    udpBlastNewCfgudpPortLowIndx              INTEGER,
    udpBlastNewCfgudpPortHighIndx             INTEGER,
    udpBlastNewCfgudpPortEntryDelete          INTEGER,
    udpBlastNewCfgudpPortEntryPacketLimit     INTEGER
    }

udpBlastNewCfgudpPortLowIndx OBJECT-TYPE
    SYNTAX  INTEGER(1..65535)
    MAX-ACCESS  read-only
    STATUS  current
    DESCRIPTION
        "The low UDP port number of UDP port range in the UDP Port table.
         The difference between the minimum of all the  low UDP port
         number specified and the maximum of all the high UDP port number
         specified can't exceed 5000.
         Note: This table is not supported in VX instance of Virtualization."
    ::= { udpBlastNewCfgudpPortEntry 1}

udpBlastNewCfgudpPortHighIndx OBJECT-TYPE
    SYNTAX  INTEGER(1..65535)
    MAX-ACCESS  read-only
    STATUS  current
    DESCRIPTION
        "The high UDP port number of UDP port range in the UDP Port table.
         The difference between the minimum of all the  low UDP port
         number specified and the maximum of all the high UDP port number
         specified can't exceed 5000.
         If highIndx and lowIndx are set to the same, it is considered a
         single port instead of range.
         Note: This table is not supported in VX instance of Virtualization."
    ::= { udpBlastNewCfgudpPortEntry 2}

udpBlastNewCfgudpPortEntryDelete OBJECT-TYPE
    SYNTAX  INTEGER {
        other(1),
        delete(2)
       }
    MAX-ACCESS  read-create
    STATUS  current
    DESCRIPTION
        "This deletes the UDP port entry from lowIndx to highIndx."
    ::= { udpBlastNewCfgudpPortEntry 3}

udpBlastNewCfgudpPortEntryPacketLimit OBJECT-TYPE
    SYNTAX  INTEGER(1..20000000)
    MAX-ACCESS  read-create
    STATUS  current
    DESCRIPTION
        "The Packet Limit of the UDP Port Entry."
    ::= { udpBlastNewCfgudpPortEntry 4}


-- General Security MIB objects

secCurCfgSecurityLogThreshold OBJECT-TYPE
    SYNTAX  INTEGER(0..1048576)
    MAX-ACCESS  read-only
    STATUS  current
    DESCRIPTION
        "The rate threshold for security logging in packets/sec. Rate zero indicates no rate threshold."
    ::= { secGeneralCfg 1 }

secNewCfgSecurityLogThreshold OBJECT-TYPE
    SYNTAX  INTEGER(0..1048576)
    MAX-ACCESS  read-write
    STATUS  current
    DESCRIPTION
        "The rate threshold for security logging in packets/sec. Rate zero indicates no rate threshold."
    ::= { secGeneralCfg 2 }

secCurCfgPacketDepth OBJECT-TYPE
    SYNTAX  INTEGER(0..255)
    MAX-ACCESS  read-only
    STATUS  current
    DESCRIPTION
        "Depth of match for pattern matching, in units of packets.
	 A value of 0 means match all packets in the stream."
    ::= { secGeneralCfg 5 }

secNewCfgPacketDepth OBJECT-TYPE
    SYNTAX  INTEGER(0..255)
    MAX-ACCESS  read-write
    STATUS  current
    DESCRIPTION
        "Depth of match for pattern matching, in units of packets.
	 A value of 0 means match all packets in the stream."
    ::= { secGeneralCfg 6 }

secCurCfgIpAclSyslogThreshold OBJECT-TYPE
    SYNTAX INTEGER(1..10080)
    MAX-ACCESS read-only
    STATUS  current
    DESCRIPTION
        "Display syslog when threshold number of ACL's have been hit."
    ::= {secGeneralCfg 7 }

secNewCfgIpAclSyslogThreshold OBJECT-TYPE
    SYNTAX INTEGER(1..10080)
    MAX-ACCESS  read-write
    STATUS  current
    DESCRIPTION
        "Display syslog when threshold number of ACL's have been hit."
    ::= {secGeneralCfg 8 }

secCurCfgIpAclSyslogTime OBJECT-TYPE
    SYNTAX INTEGER(1..10080)
    MAX-ACCESS read-only
    STATUS  current
    DESCRIPTION
        "Display syslog after specified number of minutes have passed."
    ::= { secGeneralCfg 9}

secNewCfgIpAclSyslogTime OBJECT-TYPE
    SYNTAX INTEGER(1..10080)
    MAX-ACCESS  read-write
    STATUS  current
    DESCRIPTION
        "Display syslog after specified number of minutes have passed."
    ::= { secGeneralCfg 10}

secCurCfgIpAclSyslogSendMode OBJECT-TYPE
    SYNTAX  INTEGER {
        none(1),
        threshold(2),
        time(3)
        }
    MAX-ACCESS  read-only
    STATUS  current
    DESCRIPTION
        "Syslog sending mode among none, threshold and time."
    ::= { secGeneralCfg 11}

secNewCfgIpAclSyslogSendMode OBJECT-TYPE
    SYNTAX  INTEGER {
        none(1),
        threshold(2),
        time(3)
        }
    MAX-ACCESS  read-create
    STATUS  current
    DESCRIPTION
        "Syslog sending mode among none, threshold and time."
    ::= { secGeneralCfg 12}


-- DoS Attack Prevention MIB objects

dosCurCfgIPTTL OBJECT-TYPE
    SYNTAX  INTEGER(0..255)
    MAX-ACCESS  read-only
    STATUS  current
    DESCRIPTION
        "The smallest allowable IP ttl."
    ::= { dosAttackPrevCfg 1 }

dosNewCfgIPTTL OBJECT-TYPE
    SYNTAX  INTEGER(0..255)
    MAX-ACCESS  read-write
    STATUS  current
    DESCRIPTION
        "The smallest allowable IP ttl."
    ::= { dosAttackPrevCfg 2 }

dosCurCfgIPProt OBJECT-TYPE
    SYNTAX  INTEGER(0..255)
    MAX-ACCESS  read-only
    STATUS  current
    DESCRIPTION
        "The highest allowable IP protocol."
    ::= { dosAttackPrevCfg 3 }

dosNewCfgIPProt OBJECT-TYPE
    SYNTAX  INTEGER(0..255)
    MAX-ACCESS  read-write
    STATUS  current
    DESCRIPTION
        "The highest allowable IP protocol."
    ::= { dosAttackPrevCfg 4 }

dosCurCfgFragdata OBJECT-TYPE
    SYNTAX  INTEGER(16..248)
    MAX-ACCESS  read-only
    STATUS  current
    DESCRIPTION
        "The smallest allowable IP fragment payload."
    ::= { dosAttackPrevCfg 5 }

dosNewCfgFragdata OBJECT-TYPE
    SYNTAX  INTEGER(16..248)
    MAX-ACCESS  read-write
    STATUS  current
    DESCRIPTION
        "The smallest allowable IP fragment payload."
    ::= { dosAttackPrevCfg 6 }

dosCurCfgFragoff OBJECT-TYPE
    SYNTAX  INTEGER(1..255)
    MAX-ACCESS  read-only
    STATUS  current
    DESCRIPTION
        "The smallest allowable IP fragment offset."
    ::= { dosAttackPrevCfg 7 }

dosNewCfgFragoff OBJECT-TYPE
    SYNTAX  INTEGER(1..255)
    MAX-ACCESS  read-write
    STATUS  current
    DESCRIPTION
        "The smallest allowable IP fragment offset.Should be multiple of 8 bytes"
    ::= { dosAttackPrevCfg 8 }

dosCurCfgSYNdata OBJECT-TYPE
    SYNTAX  INTEGER(0..255)
    MAX-ACCESS  read-only
    STATUS  current
    DESCRIPTION
        "The largest allowable TCP SYN payload."
    ::= { dosAttackPrevCfg 9 }

dosNewCfgSYNdata OBJECT-TYPE
    SYNTAX  INTEGER(0..255)
    MAX-ACCESS  read-write
    STATUS  current
    DESCRIPTION
        "The largest allowable TCP SYN payload."
    ::= { dosAttackPrevCfg 10 }

dosCurCfgICMPdata OBJECT-TYPE
    SYNTAX  INTEGER(1..9026)
    MAX-ACCESS  read-only
    STATUS  current
    DESCRIPTION
        "The largest allowable ICMP payload."
    ::= { dosAttackPrevCfg 11 }

dosNewCfgICMPdata OBJECT-TYPE
    SYNTAX  INTEGER(1..9026)
    MAX-ACCESS  read-write
    STATUS  current
    DESCRIPTION
        "The largest allowable ICMP payload."
    ::= { dosAttackPrevCfg 12 }

dosCurCfgICMPoff OBJECT-TYPE
    SYNTAX  INTEGER(1..8190)
    MAX-ACCESS  read-only
    STATUS  current
    DESCRIPTION
        "The largest allowable ICMP fragment offset."
    ::= { dosAttackPrevCfg 13 }

dosNewCfgICMPoff OBJECT-TYPE
    SYNTAX  INTEGER(1..8190)
    MAX-ACCESS  read-write
    STATUS  current
    DESCRIPTION
        "The largest allowable ICMP fragment offset."
    ::= { dosAttackPrevCfg 14 }


-- DST_IP_ACL: IP DST Address ACL Configuration

ipDstAclTableMaxSize OBJECT-TYPE
    SYNTAX  Integer32
    MAX-ACCESS  read-only
    STATUS  current
    DESCRIPTION
        "The maximum number of rows in the DST IP ACL table."
    ::= { ipDstAclCfg 1 }

ipDstAclCurCfgTable OBJECT-TYPE
    SYNTAX  SEQUENCE OF IpDstAclCurCfgEntry
    MAX-ACCESS  not-accessible
    STATUS  current
    DESCRIPTION
        "The table of DST IP ACL in the current configuration block."
    ::= { ipDstAclCfg 2 }

ipDstAclCurCfgEntry OBJECT-TYPE
    SYNTAX  IpDstAclCurCfgEntry
    MAX-ACCESS  not-accessible
    STATUS  current
    DESCRIPTION
        "A row in the DST IP ACL table"
    INDEX   { ipDstAclCurCfgIndx }
    ::= { ipDstAclCurCfgTable 1 }

IpDstAclCurCfgEntry ::= SEQUENCE {
    ipDstAclCurCfgIndx             Integer32,
    ipDstAclCurCfgIp               IpAddress,
    ipDstAclCurCfgMask             IpAddress
    }

ipDstAclCurCfgIndx OBJECT-TYPE
    SYNTAX  Integer32
    MAX-ACCESS  read-only
    STATUS  current
    DESCRIPTION
        "The index of the DST IP ACL table."
    ::= { ipDstAclCurCfgEntry 1}

ipDstAclCurCfgIp OBJECT-TYPE
    SYNTAX  IpAddress
    MAX-ACCESS  read-only
    STATUS  current
    DESCRIPTION
        "The IP address of the entry."
    ::= { ipDstAclCurCfgEntry 2}

ipDstAclCurCfgMask OBJECT-TYPE
    SYNTAX  IpAddress
    MAX-ACCESS  read-only
    STATUS  current
    DESCRIPTION
        "The IP address Mask of the entry."
    ::= { ipDstAclCurCfgEntry 3}

ipDstAclNewCfgTable OBJECT-TYPE
    SYNTAX  SEQUENCE OF IpDstAclNewCfgEntry
    MAX-ACCESS  not-accessible
    STATUS  current
    DESCRIPTION
        "The table of DST IP ACL in the new configuration block."
    ::= { ipDstAclCfg 3 }

ipDstAclNewCfgEntry OBJECT-TYPE
    SYNTAX  IpDstAclNewCfgEntry
    MAX-ACCESS  not-accessible
    STATUS  current
    DESCRIPTION
        "A row in the DST IP ACL table"
    INDEX   { ipDstAclNewCfgIndx }
    ::= { ipDstAclNewCfgTable 1 }

IpDstAclNewCfgEntry ::= SEQUENCE {
    ipDstAclNewCfgIndx             Integer32,
    ipDstAclNewCfgIp               IpAddress,
    ipDstAclNewCfgAction           INTEGER,
    ipDstAclNewCfgMask             IpAddress
    }

ipDstAclNewCfgIndx OBJECT-TYPE
    SYNTAX  Integer32
    MAX-ACCESS  read-only
    STATUS  current
    DESCRIPTION
        "The index of the DST IP ACL table."
    ::= { ipDstAclNewCfgEntry 1}

ipDstAclNewCfgIp OBJECT-TYPE
    SYNTAX  IpAddress
    MAX-ACCESS  read-create
    STATUS  current
    DESCRIPTION
        "The IP address of the entry."
    ::= { ipDstAclNewCfgEntry 2}

ipDstAclNewCfgAction OBJECT-TYPE
    SYNTAX  INTEGER {
        other(1),
        delete(2)
       }
    MAX-ACCESS  read-create
    STATUS  current
    DESCRIPTION
        "When set to the value of 2 (delete), the entire row is deleted.
         When read, other is returned. Setting the value to anything other
         than 2(delete) has no effect on the state of the row."
    ::= { ipDstAclNewCfgEntry 3 }

ipDstAclNewCfgMask OBJECT-TYPE
    SYNTAX  IpAddress
    MAX-ACCESS  read-create
    STATUS  current
    DESCRIPTION
        "The IP address Mask of the entry."
    ::= { ipDstAclNewCfgEntry 4}


agBogonFileSeqNumber OBJECT-TYPE
    SYNTAX  Integer32
    MAX-ACCESS  read-write
    STATUS  current
    DESCRIPTION
        "bogon file sequence number."
    ::= { bogonCfg 1 }

-- Security signaling (DP signals) MIB objects

secSignalingEnableCurCfg OBJECT-TYPE
    SYNTAX  INTEGER {
        enable(1),
        disable(2)
        }
    MAX-ACCESS  read-only
    STATUS  current
    DESCRIPTION
        "Enable/disable security signaling feature
        Note:This mib is not supported for VX instance of Virtualization."
    ::= { secSignalingCfg 1 }

secSignalingEnableNewCfg OBJECT-TYPE
    SYNTAX  INTEGER{
        enable(1),
        disable(2)
        }
    MAX-ACCESS  read-write
    STATUS  current
    DESCRIPTION
        "Enable/disable security signaling feature
        Note:This mib is not supported for VX instance of Virtualization."
    ::= { secSignalingCfg 2 }

secSignalingPeriodCurCfg OBJECT-TYPE
    SYNTAX  INTEGER(0..60)
    MAX-ACCESS  read-only
    STATUS  current
    DESCRIPTION
        "The period for security logging
        Note:This mib is not supported for VX instance of Virtualization."
    ::= { secSignalingCfg 3 }

secSignalingPeriodNewCfg OBJECT-TYPE
    SYNTAX  INTEGER(0..60)
    MAX-ACCESS  read-write
    STATUS  current
    DESCRIPTION
        "The period for security logging
        Note:This mib is not supported for VX instance of Virtualization."
    ::= { secSignalingCfg 4 }

secSignalingCurSyslogHostCfg OBJECT-TYPE
    SYNTAX  IpAddress
    MAX-ACCESS  read-only
    STATUS  current
    DESCRIPTION
        "The security syslog host IP address, as currently configured in
         the current_configuration block.
         Note:This mib is not supported for VX instance of Virtualization."
    ::= { secSignalingCfg 5 }

secSignalingNewSyslogHostCfg OBJECT-TYPE
    SYNTAX  IpAddress
    MAX-ACCESS  read-write
    STATUS  current
    DESCRIPTION
        "The security syslog host IP address, in the new_configuration block.
        Note:This mib is not supported for VX instance of Virtualization."
    ::= { secSignalingCfg 6 }

secSignalingCurSyslogHostCfgv6 OBJECT-TYPE
    SYNTAX DisplayString (SIZE(0..40))
    MAX-ACCESS  read-only
    STATUS  current
    DESCRIPTION
    "The security syslog host IPv6 address, as currently configured in
    the current_configuration block.
    Note:This mib is not supported for VX instance of Virtualization."
    ::= { secSignalingCfg 7 }

secSignalingNewSyslogHostCfgv6 OBJECT-TYPE
    SYNTAX DisplayString (SIZE(0..40))
    MAX-ACCESS  read-write
    STATUS  current
    DESCRIPTION
    "The security syslog host IPv6 address, in the new_configuration block.
    Note:This mib is not supported for VX instance of Virtualization."
    ::= { secSignalingCfg 8 }

secSignalingCurTrapHostCfg OBJECT-TYPE
    SYNTAX  IpAddress
    MAX-ACCESS  read-only
    STATUS  current
    DESCRIPTION
        "The security trap host IP address, as currently configured in
         the current_configuration block.
         Note:This mib is not supported for VX instance of Virtualization."
    ::= { secSignalingCfg 9 }

secSignalingNewTrapHostCfg OBJECT-TYPE
    SYNTAX  IpAddress
    MAX-ACCESS  read-write
    STATUS  current
    DESCRIPTION
        "The security trap host IP address, in the new_configuration block.
        Note:This mib is not supported for VX instance of Virtualization."
    ::= { secSignalingCfg 10 }

secSignalingCurTrapHostCfgv6 OBJECT-TYPE
    SYNTAX DisplayString (SIZE(0..40))
    MAX-ACCESS  read-only
    STATUS  current
    DESCRIPTION
    "The security trap host IPv6 address, as currently configured in
    the current_configuration block.
    Note:This mib is not supported for VX instance of Virtualization."
    ::= { secSignalingCfg 11 }

secSignalingNewTrapHostCfgv6 OBJECT-TYPE
    SYNTAX DisplayString (SIZE(0..40))
    MAX-ACCESS  read-write
    STATUS  current
    DESCRIPTION
    "The security trap host IPv6 address, in the new_configuration block.
    Note:This mib is not supported for VX instance of Virtualization."
    ::= { secSignalingCfg 12}

secSignalingCurSyslogHostSev OBJECT-TYPE
    SYNTAX  INTEGER  {
	emerg0(1),
	alert1(2),
	crit2(3),
	err3(4),
	warning4(5),
	notice5(6),
	info6(7),
	debug7(8)
	}
    MAX-ACCESS  read-only
    STATUS  current
    DESCRIPTION
        "The severity of security syslog host in the current configuration block.
        Note:This mib is not supported for VX instance of Virtualization."
    ::= {  secSignalingCfg 13 }

secSignalingNewSyslogHostSev OBJECT-TYPE
    SYNTAX  INTEGER  {
	emerg0(1),
	alert1(2),
	crit2(3),
	err3(4),
	warning4(5),
	notice5(6),
	info6(7),
	debug7(8)
	}
    MAX-ACCESS  read-write
    STATUS  current
    DESCRIPTION
        "The severity of security syslog host in the new configuration block.
        Note:This mib is not supported for VX instance of Virtualization."
    ::= { secSignalingCfg 14 }

secSignalingCurSyslogHostFac OBJECT-TYPE
    SYNTAX  INTEGER  {
        local0(1),
        local1(2),
        local2(3),
        local3(4),
        local4(5),
        local5(6),
        local6(7),
        local7(8)
    }
    MAX-ACCESS  read-only
    STATUS  current
    DESCRIPTION
        "The facility of security syslog host in the current_configuration block.
        Note:This mib is not supported for VX instance of Virtualization."
    ::= { secSignalingCfg 15 }

secSignalingNewSyslogHostFac OBJECT-TYPE
    SYNTAX  INTEGER  {
        local0(1),
        local1(2),
        local2(3),
        local3(4),
        local4(5),
        local5(6),
        local6(7),
        local7(8)
    }
    MAX-ACCESS  read-write
    STATUS  current
    DESCRIPTION
        "The facility of security syslog host in the new_configuration block.
        Note:This mib is not supported for VX instance of Virtualization."
    ::= { secSignalingCfg 16 }

--
-- Security Port statistics table
--
agDosPortStatsTable OBJECT-TYPE
    SYNTAX  SEQUENCE OF AgDosPortStatsTableEntry
    MAX-ACCESS  not-accessible
    STATUS  current
    DESCRIPTION
        "The table of DOS port statistics.
        Note: This MIB table is not supported for VX instance of Virtualization."
    ::= { securityStats 1 }

agDosPortStatsTableEntry OBJECT-TYPE
    SYNTAX  AgDosPortStatsTableEntry
    MAX-ACCESS  not-accessible
    STATUS  current
    DESCRIPTION
        "A row in the port stats table."
    INDEX   { agDosPortStatsIndx }
    ::= { agDosPortStatsTable 1 }

AgDosPortStatsTableEntry ::=
    SEQUENCE {
	agDosPortStatsIndx
	    Integer32,
        agDosPortStatsIPLen
            Counter32,
        agDosPortStatsIPVersion
            Counter32,
        agDosPortStatsBroadcast
            Counter32,
        agDosPortStatsLoopback
            Counter32,
	agDosPortStatsLand
	    Counter32,
        agDosPortStatsIPReserved
            Counter32,
        agDosPortStatsIPTTL
            Counter32,
        agDosPortStatsIPProt
            Counter32,
        agDosPortStatsIPOptLen
            Counter32,
        agDosPortStatsFragMoreDont
            Counter32,
        agDosPortStatsFragData
            Counter32,
        agDosPortStatsFragBoundary
            Counter32,
        agDosPortStatsFragLast
            Counter32,
        agDosPortStatsFragDontOff
            Counter32,
        agDosPortStatsFragOpt
            Counter32,
        agDosPortStatsFragOff
            Counter32,
        agDosPortStatsFragOversize
            Counter32,
        agDosPortStatsTCPLen
            Counter32,
        agDosPortStatsTCPPortZero
            Counter32,
	agDosPortStatsBlatAttack
	    Counter32,
        agDosPortStatsTCPReserved
            Counter32,
	agDosPortStatsNullScanAttack
	    Counter32,
        agDosPortStatsFullXmasScan
            Counter32,
        agDosPortStatsFinScan
            Counter32,
        agDosPortStatsVecnaScan
            Counter32,
	agDosPortStatsXmasScanAttack
	    Counter32,
	agDosPortStatsSynFinScan
	    Counter32,
        agDosPortStatsFlagAbnormal
            Counter32,
        agDosPortStatsSYNData
            Counter32,
        agDosPortStatsSYNFrag
            Counter32,
        agDosPortStatsFTPPort
            Counter32,
        agDosPortStatsDNSPort
            Counter32,
        agDosPortStatsSeqZero
            Counter32,
        agDosPortStatsAckZero
            Counter32,
        agDosPortStatsTCPOptLen
            Counter32,
        agDosPortStatsUDPLen
            Counter32,
        agDosPortStatsUDPPortZero
            Counter32,
	agDosPortStatsFraggleAttack
	    Counter32,
        agDosPortStatsPepsi
            Counter32,
        agDosPortStatsRc8
            Counter32,
        agDosPortStatsSNMPNull
            Counter32,
        agDosPortStatsICMPLen
            Counter32,
	agDosPortStatsSmurfAttack
	    Counter32,
        agDosPortStatsICMPData
            Counter32,
        agDosPortStatsICMPOff
            Counter32,
        agDosPortStatsICMPType
            Counter32,
        agDosPortStatsIGMPLen
            Counter32,
        agDosPortStatsIGMPFrag
            Counter32,
        agDosPortStatsIGMPType
            Counter32,
        agDosPortStatsARPLen
            Counter32,
        agDosPortStatsARPNbCast
            Counter32,
        agDosPortStatsARPNuCast
            Counter32,
        agDosPortStatsARPSpoof
            Counter32,
        agDosPortStatsGARP
            Counter32,
        agDosPortStatsIP6Len
            Counter32,
        agDosPortStatsIP6Version
            Counter32
    }

agDosPortStatsIndx OBJECT-TYPE
    SYNTAX  Integer32
    MAX-ACCESS  read-only
    STATUS  current
    DESCRIPTION
        "The port index."
    ::= { agDosPortStatsTableEntry 1 }

agDosPortStatsIPLen OBJECT-TYPE
    SYNTAX  Counter32
    MAX-ACCESS  read-only
    STATUS  current
    DESCRIPTION
	"IPv4 packets with bad IP header or payload length."
    ::= { agDosPortStatsTableEntry 10 }

agDosPortStatsIPVersion OBJECT-TYPE
    SYNTAX  Counter32
    MAX-ACCESS  read-only
    STATUS  current
    DESCRIPTION
	"IPv4 packets with IP version not 4."
    ::= { agDosPortStatsTableEntry 11 }

agDosPortStatsBroadcast OBJECT-TYPE
    SYNTAX  Counter32
    MAX-ACCESS  read-only
    STATUS  current
    DESCRIPTION
	"IPv4 packets with broadcast source or destination
	IP [0.0.0.0,255.255.255.255]."
    ::= { agDosPortStatsTableEntry 12 }

agDosPortStatsLoopback OBJECT-TYPE
    SYNTAX  Counter32
    MAX-ACCESS  read-only
    STATUS  current
    DESCRIPTION
	"IPv4 packets with loopback source or destination
	IP [127.0.0.0/8]."
    ::= { agDosPortStatsTableEntry 13 }

agDosPortStatsLand OBJECT-TYPE
    SYNTAX  Counter32
    MAX-ACCESS  read-only
    STATUS  current
    DESCRIPTION
	"IPv4 Packets with source IP equal to destination IP."
    ::= { agDosPortStatsTableEntry 14 }

agDosPortStatsIPReserved OBJECT-TYPE
    SYNTAX  Counter32
    MAX-ACCESS  read-only
    STATUS  current
    DESCRIPTION
	"IPv4 packets with IP reserved bit is set."
    ::= { agDosPortStatsTableEntry 15 }

agDosPortStatsIPTTL OBJECT-TYPE
    SYNTAX  Counter32
    MAX-ACCESS  read-only
    STATUS  current
    DESCRIPTION
	"IPv4 packets with small IP TTL."
    ::= { agDosPortStatsTableEntry 16 }

agDosPortStatsIPProt OBJECT-TYPE
    SYNTAX  Counter32
    MAX-ACCESS  read-only
    STATUS  current
    DESCRIPTION
	"IPv4 packets with IP protocol is unassigned or reserved."
    ::= { agDosPortStatsTableEntry 17 }

agDosPortStatsIPOptLen OBJECT-TYPE
    SYNTAX  Counter32
    MAX-ACCESS  read-only
    STATUS  current
    DESCRIPTION
	"IPv4 packets with bad IP options length."
    ::= { agDosPortStatsTableEntry 18 }

agDosPortStatsFragMoreDont OBJECT-TYPE
    SYNTAX  Counter32
    MAX-ACCESS  read-only
    STATUS  current
    DESCRIPTION
	"IPv4 packets with more fragments and don't fragment bits are set."
    ::= { agDosPortStatsTableEntry 19 }

agDosPortStatsFragData OBJECT-TYPE
    SYNTAX  Counter32
    MAX-ACCESS  read-only
    STATUS  current
    DESCRIPTION
	"IPv4 packets with more fragments bit is set and small payload."
    ::= { agDosPortStatsTableEntry 20 }

agDosPortStatsFragBoundary OBJECT-TYPE
    SYNTAX  Counter32
    MAX-ACCESS  read-only
    STATUS  current
    DESCRIPTION
	"IPv4 packets with more fragments bit is set and
         payload not at 8-byte boundary."
    ::= { agDosPortStatsTableEntry 21 }

agDosPortStatsFragLast OBJECT-TYPE
    SYNTAX  Counter32
    MAX-ACCESS  read-only
    STATUS  current
    DESCRIPTION
	"IPv4 packets last fragment without payload."
    ::= { agDosPortStatsTableEntry 22 }

agDosPortStatsFragDontOff OBJECT-TYPE
    SYNTAX  Counter32
    MAX-ACCESS  read-only
    STATUS  current
    DESCRIPTION
	"IPv4 packets with non-zero fragment offset and don't
	fragment bits are set."
    ::= { agDosPortStatsTableEntry 23 }

agDosPortStatsFragOpt OBJECT-TYPE
    SYNTAX  Counter32
    MAX-ACCESS  read-only
    STATUS  current
    DESCRIPTION
	"IPv4 packets with non-zero fragment offset and IP options."
    ::= { agDosPortStatsTableEntry 24 }

agDosPortStatsFragOff OBJECT-TYPE
    SYNTAX  Counter32
    MAX-ACCESS  read-only
    STATUS  current
    DESCRIPTION
	"IPv4 packets with small non-zero fragment offset."
    ::= { agDosPortStatsTableEntry 25 }

agDosPortStatsFragOversize OBJECT-TYPE
    SYNTAX  Counter32
    MAX-ACCESS  read-only
    STATUS  current
    DESCRIPTION
	"IPv4 packets with non-zero fragment offset and oversize payload."
    ::= { agDosPortStatsTableEntry 26 }

agDosPortStatsTCPLen OBJECT-TYPE
    SYNTAX  Counter32
    MAX-ACCESS  read-only
    STATUS  current
    DESCRIPTION
	"TCP packets with bad TCP header length."
    ::= { agDosPortStatsTableEntry 27 }

agDosPortStatsTCPPortZero OBJECT-TYPE
    SYNTAX  Counter32
    MAX-ACCESS  read-only
    STATUS  current
    DESCRIPTION
	"TCP packets with source or destination port is zero."
    ::= { agDosPortStatsTableEntry 28 }

agDosPortStatsBlatAttack OBJECT-TYPE
    SYNTAX  Counter32
    MAX-ACCESS  read-only
    STATUS  current
    DESCRIPTION
	"TCP packets source IP not equal to destination IP and source port
	equal to destination port."
    ::= { agDosPortStatsTableEntry 29 }

agDosPortStatsTCPReserved OBJECT-TYPE
    SYNTAX  Counter32
    MAX-ACCESS  read-only
    STATUS  current
    DESCRIPTION
	"TCP packets with TCP reserved bit is set."
    ::= { agDosPortStatsTableEntry 30 }

agDosPortStatsNullScanAttack OBJECT-TYPE
    SYNTAX  Counter32
    MAX-ACCESS  read-only
    STATUS  current
    DESCRIPTION
	"TCP packets were the TCP sequence number is zero and all control
	bits are zeroes."
    ::= { agDosPortStatsTableEntry 31 }

agDosPortStatsFullXmasScan OBJECT-TYPE
    SYNTAX  Counter32
    MAX-ACCESS  read-only
    STATUS  current
    DESCRIPTION
	"TCP packets with all control bits are set."
    ::= { agDosPortStatsTableEntry 32 }

agDosPortStatsFinScan OBJECT-TYPE
    SYNTAX  Counter32
    MAX-ACCESS  read-only
    STATUS  current
    DESCRIPTION
	"TCP packets with only FIN bit is set."
    ::= { agDosPortStatsTableEntry 33 }

agDosPortStatsVecnaScan OBJECT-TYPE
    SYNTAX  Counter32
    MAX-ACCESS  read-only
    STATUS  current
    DESCRIPTION
	"TCP packets with only URG or PUSH or URG|FIN or
         PSH|FIN or URG|PSH bits are set."
    ::= { agDosPortStatsTableEntry 34 }

agDosPortStatsXmasScanAttack OBJECT-TYPE
    SYNTAX  Counter32
    MAX-ACCESS  read-only
    STATUS  current
    DESCRIPTION
	"TCP packets were the TCP sequence number is zero and FIN,
	URG and PSH bits are set."
    ::= { agDosPortStatsTableEntry 35 }

agDosPortStatsSynFinScan OBJECT-TYPE
    SYNTAX  Counter32
    MAX-ACCESS  read-only
    STATUS  current
    DESCRIPTION
	"TCP packets were SYN and FIN bits are set."
    ::= { agDosPortStatsTableEntry 36 }

agDosPortStatsFlagAbnormal OBJECT-TYPE
    SYNTAX  Counter32
    MAX-ACCESS  read-only
    STATUS  current
    DESCRIPTION
	"TCP packets with abnormal control bits combination."
    ::= { agDosPortStatsTableEntry 37 }

agDosPortStatsSYNData OBJECT-TYPE
    SYNTAX  Counter32
    MAX-ACCESS  read-only
    STATUS  current
    DESCRIPTION
	"TCP packets with SYN bit is set and with payload."
    ::= { agDosPortStatsTableEntry 38 }

agDosPortStatsSYNFrag OBJECT-TYPE
    SYNTAX  Counter32
    MAX-ACCESS  read-only
    STATUS  current
    DESCRIPTION
	"TCP packets with SYN bit is set and more fragments bit is set."
    ::= { agDosPortStatsTableEntry 39 }

agDosPortStatsFTPPort OBJECT-TYPE
    SYNTAX  Counter32
    MAX-ACCESS  read-only
    STATUS  current
    DESCRIPTION
	"TCP packets with SPORT=20, DPORT<1024 and SYN bit is set."
    ::= { agDosPortStatsTableEntry 40 }

agDosPortStatsDNSPort OBJECT-TYPE
    SYNTAX  Counter32
    MAX-ACCESS  read-only
    STATUS  current
    DESCRIPTION
	"TCP packets with SPORT=53, DPORT<1024 and SYN bit is set."
    ::= { agDosPortStatsTableEntry 41 }

agDosPortStatsSeqZero OBJECT-TYPE
    SYNTAX  Counter32
    MAX-ACCESS  read-only
    STATUS  current
    DESCRIPTION
	"TCP packets with sequence number is zero."
    ::= { agDosPortStatsTableEntry 42 }

agDosPortStatsAckZero OBJECT-TYPE
    SYNTAX  Counter32
    MAX-ACCESS  read-only
    STATUS  current
    DESCRIPTION
	"TCP packets with acknowledgement number is zero and
	ACK bit is set."
    ::= { agDosPortStatsTableEntry 43 }

agDosPortStatsTCPOptLen OBJECT-TYPE
    SYNTAX  Counter32
    MAX-ACCESS  read-only
    STATUS  current
    DESCRIPTION
	"TCP packets with bad TCP options length."
    ::= { agDosPortStatsTableEntry 44 }

agDosPortStatsUDPLen OBJECT-TYPE
    SYNTAX  Counter32
    MAX-ACCESS  read-only
    STATUS  current
    DESCRIPTION
	"UDP packets with bad UDP header length."
    ::= { agDosPortStatsTableEntry 45 }

agDosPortStatsUDPPortZero OBJECT-TYPE
    SYNTAX  Counter32
    MAX-ACCESS  read-only
    STATUS  current
    DESCRIPTION
	"UDP packets with source or destination port is zero."
    ::= { agDosPortStatsTableEntry 46 }

agDosPortStatsFraggleAttack OBJECT-TYPE
    SYNTAX  Counter32
    MAX-ACCESS  read-only
    STATUS  current
    DESCRIPTION
	"UDP packets sent to a broadcast destination IP (x.x.x.255)."
    ::= { agDosPortStatsTableEntry 47 }

agDosPortStatsPepsi OBJECT-TYPE
    SYNTAX  Counter32
    MAX-ACCESS  read-only
    STATUS  current
    DESCRIPTION
	"UDP packets with SPORT=19, DPORT=7 or SPORT=7, DPORT=19."
    ::= { agDosPortStatsTableEntry 48 }

agDosPortStatsRc8 OBJECT-TYPE
    SYNTAX  Counter32
    MAX-ACCESS  read-only
    STATUS  current
    DESCRIPTION
        "UDP packets with SPORT=7 and DPORT=7."
    ::= { agDosPortStatsTableEntry 49 }

agDosPortStatsSNMPNull OBJECT-TYPE
    SYNTAX  Counter32
    MAX-ACCESS  read-only
    STATUS  current
    DESCRIPTION
	"UDP packets with DPORT=161 and without payload."
    ::= { agDosPortStatsTableEntry 50 }

agDosPortStatsICMPLen OBJECT-TYPE
    SYNTAX  Counter32
    MAX-ACCESS  read-only
    STATUS  current
    DESCRIPTION
	"ICMP packets with bad ICMP header length."
    ::= { agDosPortStatsTableEntry 51 }

agDosPortStatsSmurfAttack OBJECT-TYPE
    SYNTAX  Counter32
    MAX-ACCESS  read-only
    STATUS  current
    DESCRIPTION
	"ICMP ping request to a broadcast destination IP x.x.x.255."
    ::= { agDosPortStatsTableEntry 52 }

agDosPortStatsICMPData OBJECT-TYPE
    SYNTAX  Counter32
    MAX-ACCESS  read-only
    STATUS  current
    DESCRIPTION
	"ICMP packets with non-zero fragment offset and large payload."
    ::= { agDosPortStatsTableEntry 53 }

agDosPortStatsICMPOff OBJECT-TYPE
    SYNTAX  Counter32
    MAX-ACCESS  read-only
    STATUS  current
    DESCRIPTION
        "ICMP packets with large fragment offset."
    ::= { agDosPortStatsTableEntry 54 }

agDosPortStatsICMPType OBJECT-TYPE
    SYNTAX  Counter32
    MAX-ACCESS  read-only
    STATUS  current
    DESCRIPTION
        "ICMP packets with type is reserved."
    ::= { agDosPortStatsTableEntry 55 }

agDosPortStatsIGMPLen OBJECT-TYPE
    SYNTAX  Counter32
    MAX-ACCESS  read-only
    STATUS  current
    DESCRIPTION
	"IGMP packets with bad IGMP header length."
    ::= { agDosPortStatsTableEntry 56 }

agDosPortStatsIGMPFrag OBJECT-TYPE
    SYNTAX  Counter32
    MAX-ACCESS  read-only
    STATUS  current
    DESCRIPTION
	"IGMP packets with more fragments bit is set."
    ::= { agDosPortStatsTableEntry 57 }

agDosPortStatsIGMPType OBJECT-TYPE
    SYNTAX  Counter32
    MAX-ACCESS  read-only
    STATUS  current
    DESCRIPTION
        "IGMP packets with type is reserved."
    ::= { agDosPortStatsTableEntry 58 }

agDosPortStatsARPLen OBJECT-TYPE
    SYNTAX  Counter32
    MAX-ACCESS  read-only
    STATUS  current
    DESCRIPTION
	"ARP request or reply packets with bad length."
    ::= { agDosPortStatsTableEntry 59 }

agDosPortStatsARPNbCast OBJECT-TYPE
    SYNTAX  Counter32
    MAX-ACCESS  read-only
    STATUS  current
    DESCRIPTION
	"ARP request packets with non broadcast destination MAC."
    ::= { agDosPortStatsTableEntry 60 }

agDosPortStatsARPNuCast OBJECT-TYPE
    SYNTAX  Counter32
    MAX-ACCESS  read-only
    STATUS  current
    DESCRIPTION
        "ARP reply packets with non unicast destination MAC."
    ::= { agDosPortStatsTableEntry 61 }

agDosPortStatsARPSpoof OBJECT-TYPE
    SYNTAX  Counter32
    MAX-ACCESS  read-only
    STATUS  current
    DESCRIPTION
	"ARP request or reply packets with mismatch source with
	 sender MACs or destination with target MACs."
    ::= { agDosPortStatsTableEntry 62 }

agDosPortStatsGARP OBJECT-TYPE
    SYNTAX  Counter32
    MAX-ACCESS  read-only
    STATUS  current
    DESCRIPTION
        "ARP request or reply packets with same
         source and destination IP."
    ::= { agDosPortStatsTableEntry 63 }

agDosPortStatsIP6Len OBJECT-TYPE
    SYNTAX  Counter32
    MAX-ACCESS  read-only
    STATUS  current
    DESCRIPTION
	"IPv6 packets with bad header length."
    ::= { agDosPortStatsTableEntry 64 }

agDosPortStatsIP6Version OBJECT-TYPE
    SYNTAX  Counter32
    MAX-ACCESS  read-only
    STATUS  current
    DESCRIPTION
	"IPv6 packets with IP version not 6."
    ::= { agDosPortStatsTableEntry 65 }

agSecurityPgrpStatsTable OBJECT-TYPE
    SYNTAX  SEQUENCE OF AgSecurityPgrpStatsTableEntry
    MAX-ACCESS  not-accessible
    STATUS  current
    DESCRIPTION
        "The table of pattern group statistics.
        Note: This MIB table is not supported for VX instance of Virtualization."
    ::= { securityStats 2 }

agSecurityPgrpStatsTableEntry OBJECT-TYPE
    SYNTAX  AgSecurityPgrpStatsTableEntry
    MAX-ACCESS  not-accessible
    STATUS  current
    DESCRIPTION
        "A row in the port stats table."
    INDEX   { agSecurityPgrpStatsIndx }
    ::= { agSecurityPgrpStatsTable 1 }

AgSecurityPgrpStatsTableEntry ::=
    SEQUENCE {
	agSecurityPgrpStatsIndx
	    Integer32,
	agSecurityPgrpStatsName
	    DisplayString,
	agSecurityPgrpStatsHits
	    Counter32
}

agSecurityPgrpStatsIndx OBJECT-TYPE
    SYNTAX  Integer32
    MAX-ACCESS  read-only
    STATUS  current
    DESCRIPTION
        "The Pattern Group index."
    ::= { agSecurityPgrpStatsTableEntry 1 }

agSecurityPgrpStatsName OBJECT-TYPE
    SYNTAX  DisplayString
    MAX-ACCESS  read-only
    STATUS  current
    DESCRIPTION
	    "The name of the Pattern Group."
    ::= { agSecurityPgrpStatsTableEntry 2 }

agSecurityPgrpStatsHits OBJECT-TYPE
    SYNTAX  Counter32
    MAX-ACCESS  read-only
    STATUS  current
    DESCRIPTION
	    "The total hits for this Pattern Group."
    ::= { agSecurityPgrpStatsTableEntry 3 }

-- UDP_BLAST statistics
agSecurityUbStatsTable OBJECT-TYPE
    SYNTAX  SEQUENCE OF AgSecurityUbStatsTableEntry
    MAX-ACCESS  not-accessible
    STATUS  current
    DESCRIPTION
        "The table of UDP Blast statistics.
        Note: This MIB table is not supported for VX instance of Virtualization."
    ::= { securityStats 3 }

agSecurityUbStatsTableEntry OBJECT-TYPE
    SYNTAX  AgSecurityUbStatsTableEntry
    MAX-ACCESS  not-accessible
    STATUS  current
    DESCRIPTION
        "A row in the UDP Blast stats table."
    INDEX   { agSecurityUbStatsIndx }
    ::= { agSecurityUbStatsTable 1 }

AgSecurityUbStatsTableEntry ::=
    SEQUENCE {
        agSecurityUbStatsIndx
            Integer32,
        agSecurityUbStatsPort
            Integer32,
        agSecurityUbStatsBlockedPacket
            Counter32,
        agSecurityUbStatsPacketRate
            Counter32
}

agSecurityUbStatsIndx OBJECT-TYPE
    SYNTAX  Integer32
    MAX-ACCESS  read-only
    STATUS  current
    DESCRIPTION
        "The UDP Blast Statistics Group index."
    ::= { agSecurityUbStatsTableEntry 1 }

agSecurityUbStatsPort OBJECT-TYPE
    SYNTAX  Integer32
    MAX-ACCESS  read-only
    STATUS  current
    DESCRIPTION
            "UDP Port Number."
    ::= { agSecurityUbStatsTableEntry 2 }

agSecurityUbStatsBlockedPacket OBJECT-TYPE
    SYNTAX  Counter32
    MAX-ACCESS  read-only
    STATUS  current
    DESCRIPTION
            "Total blocked packet."
    ::= { agSecurityUbStatsTableEntry 3 }

agSecurityUbStatsPacketRate OBJECT-TYPE
    SYNTAX  Counter32
    MAX-ACCESS  read-only
    STATUS  current
    DESCRIPTION
            "Current Packet rate per second."
    ::= { agSecurityUbStatsTableEntry 4 }


-- IP_ACL statistics
agSecurityIpAclStatsTable OBJECT-TYPE
    SYNTAX  SEQUENCE OF AgSecurityIpAclStatsTableEntry
    MAX-ACCESS  not-accessible
    STATUS  current
    DESCRIPTION
        "The table of IP ACL statistics.
        Note: This MIB table is not supported for VX instance of Virtualization."
    ::= { securityStats 4 }

agSecurityIpAclStatsTableEntry OBJECT-TYPE
    SYNTAX  AgSecurityIpAclStatsTableEntry
    MAX-ACCESS  not-accessible
    STATUS  current
    DESCRIPTION
        "A row in the IP ACL stats table."
    INDEX   { agSecurityIpAclStatsIndx }
    ::= { agSecurityIpAclStatsTable 1 }

AgSecurityIpAclStatsTableEntry ::=
    SEQUENCE {
        agSecurityIpAclStatsIndx
            Integer32,
        agSecurityIpAclStatsAddress
            IpAddress,
        agSecurityIpAclStatsBlockedPacket
            Counter32
}

agSecurityIpAclStatsIndx OBJECT-TYPE
    SYNTAX  Integer32
    MAX-ACCESS  read-only
    STATUS  current
    DESCRIPTION
        "The IP ACL Statistics Group index."
    ::= { agSecurityIpAclStatsTableEntry 1 }

agSecurityIpAclStatsAddress OBJECT-TYPE
    SYNTAX  IpAddress
    MAX-ACCESS  read-only
    STATUS  current
    DESCRIPTION
            "IP ACL IP Address."
    ::= { agSecurityIpAclStatsTableEntry 2 }

agSecurityIpAclStatsBlockedPacket OBJECT-TYPE
    SYNTAX  Counter32
    MAX-ACCESS  read-only
    STATUS  current
    DESCRIPTION
            "Total blocked packet."
    ::= { agSecurityIpAclStatsTableEntry 3 }

-- DST_IP_ACL statistics
agSecurityIpDstAclStatsTable OBJECT-TYPE
    SYNTAX  SEQUENCE OF AgSecurityIpDstAclStatsTableEntry
    MAX-ACCESS  not-accessible
    STATUS  current
    DESCRIPTION
        "The table of DST IP ACL statistics.
        Note: This MIB table is not supported for VX instance of Virtualization."
    ::= { securityStats 5 }

agSecurityIpDstAclStatsTableEntry OBJECT-TYPE
    SYNTAX  AgSecurityIpDstAclStatsTableEntry
    MAX-ACCESS  not-accessible
    STATUS  current
    DESCRIPTION
        "A row in the DST IP ACL stats table."
    INDEX   { agSecurityIpDstAclStatsIndx }
    ::= { agSecurityIpDstAclStatsTable 1 }

AgSecurityIpDstAclStatsTableEntry ::=
    SEQUENCE {
        agSecurityIpDstAclStatsIndx
            Integer32,
        agSecurityIpDstAclStatsAddress
            IpAddress,
        agSecurityIpDstAclStatsBlockedPacket
            Counter32
}

agSecurityIpDstAclStatsIndx OBJECT-TYPE
    SYNTAX  Integer32
    MAX-ACCESS  read-only
    STATUS  current
    DESCRIPTION
        "The DST IP ACL Statistics Group index."
    ::= { agSecurityIpDstAclStatsTableEntry 1 }

agSecurityIpDstAclStatsAddress OBJECT-TYPE
    SYNTAX  IpAddress
    MAX-ACCESS  read-only
    STATUS  current
    DESCRIPTION
            "DST IP ACL IP Address."
    ::= { agSecurityIpDstAclStatsTableEntry 2 }

agSecurityIpDstAclStatsBlockedPacket OBJECT-TYPE
    SYNTAX  Counter32
    MAX-ACCESS  read-only
    STATUS  current
    DESCRIPTION
            "Total blocked packet."
    ::= { agSecurityIpDstAclStatsTableEntry 3 }


-- Port access

agPortAccessTableMaxSize OBJECT-TYPE
    SYNTAX  Integer32
    MAX-ACCESS  read-only
    STATUS  current
    DESCRIPTION
        "The maximum number of entries in Port Access Table."
    ::= { agPortAccessCfg 1 }

agCurCfgPortAccessTable OBJECT-TYPE
    SYNTAX  SEQUENCE OF AgCurCfgPortAccessEntry
    MAX-ACCESS  not-accessible
    STATUS  current
    DESCRIPTION
       "The table of ports and their access states"
    ::= { agPortAccessCfg 2 }

agCurCfgPortAccessEntry OBJECT-TYPE
    SYNTAX  AgCurCfgPortAccessEntry
    MAX-ACCESS  not-accessible
    STATUS  current
    DESCRIPTION
        "A row in the port access table"
    INDEX   { agCurCfgPortAccessIndex }
    ::= { agCurCfgPortAccessTable 1 }

AgCurCfgPortAccessEntry ::= SEQUENCE {
    agCurCfgPortAccessIndex           Integer32,
    agCurCfgPortAccessState           INTEGER
    }

agCurCfgPortAccessIndex OBJECT-TYPE
    SYNTAX  Integer32
    MAX-ACCESS  read-only
    STATUS  current
    DESCRIPTION
        "The port number in the table."
    ::= { agCurCfgPortAccessEntry 1 }

agCurCfgPortAccessState OBJECT-TYPE
    SYNTAX  INTEGER {
        deny(0),
        allow(1)
        }
    MAX-ACCESS  read-only
    STATUS  current
    DESCRIPTION
        "The port access state of the port.
         deny(0)            - port does not have management access
         allow(1)           - port has management access"
    ::= { agCurCfgPortAccessEntry 2 }

agNewCfgPortAccessTable OBJECT-TYPE
    SYNTAX  SEQUENCE OF AgNewCfgPortAccessEntry
    MAX-ACCESS  not-accessible
    STATUS  current
    DESCRIPTION
        "The table of ports and their access states"
    ::= { agPortAccessCfg 3 }

agNewCfgPortAccessEntry OBJECT-TYPE
    SYNTAX  AgNewCfgPortAccessEntry
    MAX-ACCESS  not-accessible
    STATUS  current
    DESCRIPTION
        "A row in the port access table."
    INDEX   { agNewCfgPortAccessIndex }
    ::= { agNewCfgPortAccessTable 1 }

AgNewCfgPortAccessEntry ::= SEQUENCE {
    agNewCfgPortAccessIndex           Integer32,
    agNewCfgPortAccessState           INTEGER
    }

agNewCfgPortAccessIndex OBJECT-TYPE
    SYNTAX  Integer32
    MAX-ACCESS  read-only
    STATUS  current
    DESCRIPTION
        "The port number in the table."
    ::= { agNewCfgPortAccessEntry 1 }

agNewCfgPortAccessState OBJECT-TYPE
    SYNTAX  INTEGER {
        deny(0),
        allow(1)
        }
    MAX-ACCESS  read-write
    STATUS  current
    DESCRIPTION
        "The port access state of the port.
         deny(0)            - port does not have management access
         allow(1)           - port has management access"
    ::= { agNewCfgPortAccessEntry 2 }

-- VLAN access

agVLANAccessTableMaxSize OBJECT-TYPE
    SYNTAX  Integer32
    MAX-ACCESS  read-only
    STATUS  current
    DESCRIPTION
        "The maximum number of entries in VLAN Access Table.
        Note:This mib is not supported for VX instance of Virtualization."
    ::= { agVLANAccessCfg 1 }

agCurCfgVLANAccessTable OBJECT-TYPE
    SYNTAX  SEQUENCE OF AgCurCfgVLANAccessEntry
    MAX-ACCESS  not-accessible
    STATUS  current
    DESCRIPTION
       "The table of VLAN's and their access states
       Note:This table is not supported for VX instance of Virtualization."
    ::= { agVLANAccessCfg 2 }

agCurCfgVLANAccessEntry OBJECT-TYPE
    SYNTAX  AgCurCfgVLANAccessEntry
    MAX-ACCESS  not-accessible
    STATUS  current
    DESCRIPTION
        "A row in the VLAN access table"
    INDEX   { agCurCfgVLANAccessIndex }
    ::= { agCurCfgVLANAccessTable 1 }

AgCurCfgVLANAccessEntry ::= SEQUENCE {
    agCurCfgVLANAccessIndex           Integer32,
    agCurCfgVLANAccessState           INTEGER
    }

agCurCfgVLANAccessIndex OBJECT-TYPE
    SYNTAX  Integer32
    MAX-ACCESS  read-only
    STATUS  current
    DESCRIPTION
        "The VLAN number in the table.
        Note:This mib is not supported for VX instance of Virtualization."
    ::= { agCurCfgVLANAccessEntry 1 }

agCurCfgVLANAccessState OBJECT-TYPE
    SYNTAX  INTEGER {
        deny(0),
        allow(1)
        }
    MAX-ACCESS  read-only
    STATUS  current
    DESCRIPTION
        "The VLAN access state of the port.
         deny(0)            - VLAN does not have management access
         allow(1)           - VLAN has management access"
    ::= { agCurCfgVLANAccessEntry 2 }

agNewCfgVLANAccessTable OBJECT-TYPE
    SYNTAX  SEQUENCE OF AgNewCfgVLANAccessEntry
    MAX-ACCESS  not-accessible
    STATUS  current
    DESCRIPTION
        "The table of VLAN's and their access states
        Note:This table is not supported for VX instance of Virtualization."
    ::= { agVLANAccessCfg 3 }

agNewCfgVLANAccessEntry OBJECT-TYPE
    SYNTAX  AgNewCfgVLANAccessEntry
    MAX-ACCESS  not-accessible
    STATUS  current
    DESCRIPTION
        "A row in the VLAN access table."
    INDEX   { agNewCfgVLANAccessIndex }
    ::= { agNewCfgVLANAccessTable 1 }

AgNewCfgVLANAccessEntry ::= SEQUENCE {
    agNewCfgVLANAccessIndex           Integer32,
    agNewCfgVLANAccessState           INTEGER
    }

agNewCfgVLANAccessIndex OBJECT-TYPE
    SYNTAX  Integer32
    MAX-ACCESS  read-only
    STATUS  current
    DESCRIPTION
        "The VLAN number in the table.
        Note:This mib is not supported for VX instance of Virtualization."
    ::= { agNewCfgVLANAccessEntry 1 }

agNewCfgVLANAccessState OBJECT-TYPE
    SYNTAX  INTEGER {
        deny(0),
        allow(1)
        }
    MAX-ACCESS  read-write
    STATUS  current
    DESCRIPTION
        "The VLAN access state of the port.
         deny(0)            - VLAN does not have management access
         allow(1)           - VLAN has management access"
    ::= { agNewCfgVLANAccessEntry 2 }

-- SAVE Configuration

agSaveConfig OBJECT-TYPE
    SYNTAX  INTEGER {
        save(1),
        idle(2),
        inprogress(3),
        complete(4),
        failed(5),
	saveNoBackup(6)
        }
    MAX-ACCESS  read-write
    STATUS  current
    DESCRIPTION
        "When this object is read the current state is returned.
        idle(2) indicates that there is no save in progess.
        complete(4) indicates that the last save operation is completed.
        Setting the value to save(1), will write the current config block
        since the last save to the flash memory with backup, for saving
	without backup saveNoBackup(6) can be used.
	If the save is successful this variable will return the state
        'complete' else it will return 'failed'. In case of failure,
        to read the reason for failure use the agSaveTable.
        Once the operation is completed or the agSaveTable is read ,
        the save buffer needs to be freed and the agSaveState
        should be set back to 'idle' state so others can issue the save
        command via SNMP."
    ::= { agSave 1 }

agSaveTableSize OBJECT-TYPE
    SYNTAX  Integer32
    MAX-ACCESS  read-only
    STATUS  current
    DESCRIPTION
        "The number of strings in the save table."
    ::= { agSave 2 }

agSaveTable OBJECT-TYPE
    SYNTAX  SEQUENCE OF AgSaveTableEntry
    MAX-ACCESS  not-accessible
    STATUS  current
    DESCRIPTION
        "The table of error messages for asynchrnous save operation."
    ::= { agSave 3 }

agSaveTableEntry OBJECT-TYPE
    SYNTAX  AgSaveTableEntry
    MAX-ACCESS  not-accessible
    STATUS  current
    DESCRIPTION
        "Error Strings generated while asynchronous save operation."
    INDEX   { agSaveIndex }
    ::= { agSaveTable 1 }

AgSaveTableEntry ::= SEQUENCE {
    agSaveIndex      Integer32,
    agSaveString     OCTET STRING
    }

agSaveIndex OBJECT-TYPE
    SYNTAX  Integer32
    MAX-ACCESS  read-only
    STATUS  current
    DESCRIPTION
        "The table index for save."
    ::= { agSaveTableEntry 1 }

agSaveString OBJECT-TYPE
    SYNTAX  OCTET STRING
    MAX-ACCESS  read-only
    STATUS  current
    DESCRIPTION
        "A string in the Save table."
    ::= { agSaveTableEntry 2 }

-- SNMP File Transfer
agFileSize OBJECT-TYPE
    SYNTAX  Integer32
    MAX-ACCESS  read-write
    STATUS  current
    DESCRIPTION
        "This is the number of octets in the file. This is set to indicate
        the total size of the file that is being transfered. The value is
	set in bytes. File size range for Bogon File Transfer 1 - 2097152
        and for Symantec Signature 1 - 178176"
    ::= { agFileTransfer 1 }

agFileTransferState OBJECT-TYPE
    SYNTAX  INTEGER {
        idle(1),
        transfer(2),
        inprogress(3),
	missingrows(4),
        complete(5),
	error(6),
	endoftransfer(7)
        }
    MAX-ACCESS  read-write
    STATUS  current
    DESCRIPTION
        "When this object is read the current state is returned.
        idle(1) indicates that there is no transfer in progess.
        Any user must verify the state machine is in state idle before
        setting the state to transfer(2).Before setting transfer(2) state
        agFileSize and agFileType should be set and then transition
        changes to inprogress(3). While in this state, the agFileTable
        should be populated with all the rows needed to transfer the files
        entire contents. endoftransfer(7) should be set inorder to notify
	the agent that contents are transfered. If all the contents are
	received, then the state transitions to complete(5). If there are
        any missing rows, the agent will transition to the state
        missingrows(4). The user must either populate the missing rows,
        and give a endoftransfer(7) state, or give up the transfer by
        setting the state to idle(1). When the idle(1) state is set,
        the string with missing rows is cleared and the buffer is written
        to the file, state goes complete(5) to upon successful completion.
	Any transition to idle(1) will free any resources associated with
	the file transfer, that are no longer needed. The agFileTable will
	contain 0 rows. While in state missingrows(4), agFileTableMissingRows
	will contain a parseable string of missing row indexes seperated
	by a comma."
    ::= { agFileTransfer 2 }

agFileTableMissingRows OBJECT-TYPE
    SYNTAX OCTET STRING (SIZE(0..1024))
    MAX-ACCESS  read-only
    STATUS  current
    DESCRIPTION
        "A string representing the missing rows of data for the file
        transfer. This is only valid while agFileTransferState is
        in the missingrows(4) state. The string will be numbers
	representing the missing row indexes seperated by
        commas e.g.  13,25,99"
    ::= { agFileTransfer 3 }

agFileType OBJECT-TYPE
    SYNTAX  INTEGER {
        bogon(1),
        symantecSignature(2)
        }
    MAX-ACCESS  read-write
    STATUS  current
    DESCRIPTION
        "This identifies the file type that is being transfered."
    ::= { agFileTransfer 4 }


agFileTableSize OBJECT-TYPE
    SYNTAX  Integer32
    MAX-ACCESS  read-only
    STATUS  current
    DESCRIPTION
        "The number of rows in the file table."
    ::= { agFileTransfer 5 }

agFileTable OBJECT-TYPE
    SYNTAX  SEQUENCE OF AgFileTableEntry
    MAX-ACCESS  not-accessible
    STATUS  current
    DESCRIPTION
        "The table of octets that when combined create a file."
    ::= { agFileTransfer 6 }

agFileTableEntry OBJECT-TYPE
    SYNTAX  AgFileTableEntry
    MAX-ACCESS  not-accessible
    STATUS  current
    DESCRIPTION
        "An entry in the file table."
    INDEX   { agFileIndex }
    ::= { agFileTable 1 }

AgFileTableEntry ::= SEQUENCE {
    agFileIndex      Integer32,
    agFileString     OCTET STRING
    }

agFileIndex OBJECT-TYPE
    SYNTAX  Integer32
    MAX-ACCESS  read-only
    STATUS  current
    DESCRIPTION
        "The table index."
    ::= { agFileTableEntry 1 }

agFileString OBJECT-TYPE
    SYNTAX  OCTET STRING (SIZE(0..1024))
    MAX-ACCESS  read-write
    STATUS  current
    DESCRIPTION
        "A string with bogon ip/mask pair."
    ::= { agFileTableEntry 2 }
-- End of SNMP FT

agFileErrorTableSize OBJECT-TYPE
    SYNTAX  Integer32
    MAX-ACCESS  read-only
    STATUS  current
    DESCRIPTION
        "The number of strings in the snmp file transfer error table."
    ::= { agFileTransfer 7 }

agFileErrorTable OBJECT-TYPE
    SYNTAX  SEQUENCE OF AgFileErrorTableEntry
    MAX-ACCESS  not-accessible
    STATUS  current
    DESCRIPTION
        "The table of error messages for asynchrnous snmp file transfer
       operation."
    ::= { agFileTransfer 8 }

agFileErrorTableEntry OBJECT-TYPE
    SYNTAX  AgFileErrorTableEntry
    MAX-ACCESS  not-accessible
    STATUS  current
    DESCRIPTION
        "Error Strings generated while asynchronous snmp file transfer
       operation."
    INDEX   { agFileErrorIndex }
    ::= { agFileErrorTable 1 }

AgFileErrorTableEntry ::= SEQUENCE {
    agFileErrorIndex      Integer32,
    agFileErrorString     DisplayString
    }

agFileErrorIndex OBJECT-TYPE
    SYNTAX  Integer32
    MAX-ACCESS  read-only
    STATUS  current
    DESCRIPTION
        "The table index for snmp file transfer error table."
    ::= { agFileErrorTableEntry 1 }

agFileErrorString OBJECT-TYPE
    SYNTAX  DisplayString
    MAX-ACCESS  read-only
    STATUS  current
    DESCRIPTION
        "A string in the snmp file transfer error table."
    ::= { agFileErrorTableEntry 2 }


agAccessUser         OBJECT IDENTIFIER ::= { agAccess 1 }
agAccessUid          OBJECT IDENTIFIER ::= { agAccessUser 1 }

agAccessUserCurCfgTable OBJECT-TYPE
    SYNTAX  SEQUENCE OF AgAccessUserCurCfgTableEntry
    MAX-ACCESS  not-accessible
    STATUS  current
    DESCRIPTION
        "The table of Access user configuration."
    ::= { agAccessUid 1 }

agAccessUserCurCfgTableEntry OBJECT-TYPE
    SYNTAX  AgAccessUserCurCfgTableEntry
    MAX-ACCESS  not-accessible
    STATUS  current
    DESCRIPTION
        "A row in the Access user configuration table."
    INDEX  { agAccessUserCurCfgUId }
    ::= { agAccessUserCurCfgTable 1 }

AgAccessUserCurCfgTableEntry ::= SEQUENCE {
    agAccessUserCurCfgUId 	Integer32,
    agAccessUserCurCos 		INTEGER,
    agAccessUserCurCfgName 	DisplayString,
    agAccessUserCurCfgAdminPswd   DisplayString,
    agAccessUserCurCfgPswd 	DisplayString,
    agAccessUserCurCfgConfPswd    DisplayString,
    agAccessUserCurCfgBackDoor   INTEGER,
    agAccessUserCurCfgCrtMng     INTEGER,
    agAccessUserCurCfgReal  DisplayString,
    agAccessUserCurCfgState	INTEGER,
    agAccessUserCurCfgBmap      OCTET STRING,
    agAccessUserCurCfgLanguage	INTEGER,
    agAccessUserCurCfgSshkey    DisplayString
    }

agAccessUserCurCfgUId OBJECT-TYPE
    SYNTAX Integer32
    MAX-ACCESS  read-only
    STATUS  current
    DESCRIPTION
        "The User identifier."
    ::= { agAccessUserCurCfgTableEntry 1 }


agAccessUserCurCos OBJECT-TYPE
    SYNTAX  INTEGER {
        user(0),
        crtadmin(1),
        slboper(2),
        l4oper(3),
        oper(4),
        slbadmin(5),
        l4admin(6),
        admin(7),
	slbview(8),
        l3oper(9),
        l3admin(10),
        l1oper(11),
        l2oper(12),
	wsadmin(13),
	wsowner(14),
	wsview(15)
        }
    MAX-ACCESS  read-only
    STATUS  current
    DESCRIPTION
        "The user class of service.The COS applicable for users in
         a) Admin Context - user(0),l1oper(11),l2oper(12),oper(4) & admin(7)
         b) vADC - All except l1oper(11) & l2oper(12)
         c) Standalone ADC - All except l3oper(9),l3admin(10),l1oper(11) &
                             l2oper(12)
	 d) AW only wsadmin(13),wsowner(14),wsview(15)."

    ::= { agAccessUserCurCfgTableEntry 2 }

agAccessUserCurCfgName OBJECT-TYPE
    SYNTAX  DisplayString (SIZE(0..8))
    MAX-ACCESS  read-only
    STATUS  current
    DESCRIPTION
        "The user name."
    ::= { agAccessUserCurCfgTableEntry 3 }

agAccessUserCurCfgAdminPswd OBJECT-TYPE
    SYNTAX  DisplayString (SIZE(0..160))
    MAX-ACCESS  read-only
    STATUS  current
    DESCRIPTION
        "The character string representing the admin password."
    ::= { agAccessUserCurCfgTableEntry 4 }

agAccessUserCurCfgPswd OBJECT-TYPE
    SYNTAX  DisplayString (SIZE(0..160))
    MAX-ACCESS  read-only
    STATUS  current
    DESCRIPTION
        "The character string representing the user password."
    ::= { agAccessUserCurCfgTableEntry 5 }

agAccessUserCurCfgConfPswd OBJECT-TYPE
    SYNTAX  DisplayString (SIZE(0..160))
    MAX-ACCESS  read-only
    STATUS  current
    DESCRIPTION
        "The character string is used to confirm the user password."
    ::= { agAccessUserCurCfgTableEntry 6 }

agAccessUserCurCfgBackDoor OBJECT-TYPE
    SYNTAX  INTEGER  {
        enabled(2),
        disabled(3)
        }
    MAX-ACCESS  read-only
    STATUS  current
    DESCRIPTION
        "Enable or disable User backdoor Access."
    ::= { agAccessUserCurCfgTableEntry 7 }

agAccessUserCurCfgCrtMng OBJECT-TYPE
    SYNTAX  INTEGER  {
        enabled(2),
        disabled(3)
        }
    MAX-ACCESS  read-only
    STATUS  current
    DESCRIPTION
        "Enable or disable certificate management permissions."
    ::= { agAccessUserCurCfgTableEntry 8 }

agAccessUserCurCfgReal OBJECT-TYPE
    SYNTAX  DisplayString (SIZE(0..255))
    MAX-ACCESS  read-only
    STATUS  current
    DESCRIPTION
        "The user real servers."
    ::= { agAccessUserCurCfgTableEntry 9 }

agAccessUserCurCfgState OBJECT-TYPE
    SYNTAX  INTEGER  {
	enabled(2),
	disabled(3)
	}
    MAX-ACCESS  read-only
    STATUS  current
    DESCRIPTION
        "Enable or disable a user."
    ::= { agAccessUserCurCfgTableEntry 10 }

agAccessUserCurCfgBmap OBJECT-TYPE
    SYNTAX  OCTET STRING
    MAX-ACCESS  read-only
    STATUS  current
    DESCRIPTION
        "The real servers added to this user.
         The selected real servers are presented in a bitmap format.
         in receiving order:

             OCTET 1  OCTET 2  .....
             xxxxxxxx xxxxxxxx .....
             ||    || |_ Real Server 9
             ||    ||
             ||    ||___ Real Server 8
             ||    |____ Real Server 7
             ||      .    .   .
             ||_________ Real Server 2
             |__________ Real Server 1

             where x : 1 - The represented Real Server is added
                       0 - The represented Real Server is not added"
    ::= { agAccessUserCurCfgTableEntry 11 }

agAccessUserCurCfgLanguage OBJECT-TYPE
    SYNTAX  INTEGER  {
        english(0),
        chinese(1),
	korean(2),
	japanese(3)
        }
    MAX-ACCESS  read-only
    STATUS  current
    DESCRIPTION
        "Set Web UI user display language."
    ::= { agAccessUserCurCfgTableEntry 12 }

agAccessUserCurCfgSshkey OBJECT-TYPE
    SYNTAX  DisplayString (SIZE(0..32))
    MAX-ACCESS  read-only
    STATUS  current
    DESCRIPTION
        "The SSH Public Key ID"
    ::= { agAccessUserCurCfgTableEntry 13 }

agAccessUserNewCfgTable OBJECT-TYPE
    SYNTAX  SEQUENCE OF AgAccessUserNewCfgTableEntry
    MAX-ACCESS  not-accessible
    STATUS  current
    DESCRIPTION
        "The table of Access user configuration."
    ::= { agAccessUid 2 }

agAccessUserNewCfgTableEntry OBJECT-TYPE
    SYNTAX  AgAccessUserNewCfgTableEntry
    MAX-ACCESS  not-accessible
    STATUS  current
    DESCRIPTION
        "A row in the Access user configuration table."
    INDEX  { agAccessUserNewCfgUId }
    ::= { agAccessUserNewCfgTable 1 }

AgAccessUserNewCfgTableEntry ::= SEQUENCE {
    agAccessUserNewCfgUId 	    Integer32,
    agAccessUserNewCos  		INTEGER,
    agAccessUserNewCfgName   	DisplayString,
    agAccessUserNewCfgAdminPswd     DisplayString,
    agAccessUserNewCfgPswd 	    DisplayString,
    agAccessUserNewCfgConfPswd      DisplayString,
    agAccessUserNewCfgBackDoor  INTEGER,
    agAccessUserNewCfgCrtMng    INTEGER,
    agAccessUserNewCfgRealAdd   INTEGER,
    agAccessUserNewCfgRealRem   INTEGER,
    agAccessUserNewCfgState	    INTEGER,
    agAccessUserNewCfgDelete    INTEGER,
    agAccessUserNewCfgBmap    OCTET STRING,
    agAccessUserNewCfgEnhRealAdd DisplayString,
    agAccessUserNewCfgEnhRealRem DisplayString,
    agAccessUserNewCfgLanguage	INTEGER,
    agAccessUserNewCfgSshkey    DisplayString
    }

agAccessUserNewCfgUId OBJECT-TYPE
    SYNTAX Integer32
    MAX-ACCESS  read-only
    STATUS  current
    DESCRIPTION
        "The User identifier."
    ::= { agAccessUserNewCfgTableEntry 1 }

agAccessUserNewCos OBJECT-TYPE
    SYNTAX  INTEGER {
        user(0),
        crtadmin(1),
        slboper(2),
        l4oper(3),
        oper(4),
        slbadmin(5),
        l4admin(6),
        admin(7),
	slbview(8),
        l3oper(9),
        l3admin(10),
        l1oper(11),
        l2oper(12),
	wsadmin(13),
	wsowner(14),
	wsview(15)

        }
    MAX-ACCESS  read-create
    STATUS  current
    DESCRIPTION
        "The user class of service.The COS applicable for users in
         a) Admin Context - user(0),l1oper(11),l2oper(12),oper(4) & admin(7)
         b) vADC - All except l1oper(11) & l2oper(12)
         c) Standalone ADC - All except l3oper(9),l3admin(10),l1oper(11) &
                             l2oper(12)
	  d) AW only wsadmin(13),wsowner(14),wsview(15)."
    ::= { agAccessUserNewCfgTableEntry 2 }

agAccessUserNewCfgName OBJECT-TYPE
    SYNTAX  DisplayString (SIZE(0..8))
    MAX-ACCESS  read-create
    STATUS  current
    DESCRIPTION
        "The user name."
    ::= { agAccessUserNewCfgTableEntry 3 }

agAccessUserNewCfgAdminPswd OBJECT-TYPE
    SYNTAX  DisplayString (SIZE(0..160))
    MAX-ACCESS  read-create
    STATUS  current
    DESCRIPTION
        "The character string representing the admin password."
    ::= { agAccessUserNewCfgTableEntry 4 }

agAccessUserNewCfgPswd OBJECT-TYPE
    SYNTAX  DisplayString (SIZE(0..160))
    MAX-ACCESS  read-create
    STATUS  current
    DESCRIPTION
        "The character string representing the user password."
    ::= { agAccessUserNewCfgTableEntry 5 }

agAccessUserNewCfgConfPswd OBJECT-TYPE
    SYNTAX  DisplayString (SIZE(0..160))
    MAX-ACCESS  read-create
    STATUS  current
    DESCRIPTION
        "This character string is used to confirm the user password."
    ::= { agAccessUserNewCfgTableEntry 6 }

agAccessUserNewCfgBackDoor OBJECT-TYPE
    SYNTAX  INTEGER  {
        enabled(2),
        disabled(3)
        }
    MAX-ACCESS  read-create
    STATUS  current
    DESCRIPTION
        "Enable or disable User backdoor access."
    ::= { agAccessUserNewCfgTableEntry 7 }

agAccessUserNewCfgCrtMng OBJECT-TYPE
    SYNTAX  INTEGER  {
        enabled(2),
        disabled(3)
        }
    MAX-ACCESS  read-create
    STATUS  current
    DESCRIPTION
        "Enable or disable a certificate management permissions."
    ::= { agAccessUserNewCfgTableEntry 8 }

agAccessUserNewCfgRealAdd OBJECT-TYPE
    SYNTAX  INTEGER (1..4096)
    MAX-ACCESS  read-create
    STATUS  current
    DESCRIPTION
        "Add user real server."
    ::= { agAccessUserNewCfgTableEntry 9 }

agAccessUserNewCfgRealRem OBJECT-TYPE
    SYNTAX  INTEGER (1..4096)
    MAX-ACCESS  read-create
    STATUS  current
    DESCRIPTION
        "Remove user real server."
    ::= { agAccessUserNewCfgTableEntry 10 }

agAccessUserNewCfgState OBJECT-TYPE
    SYNTAX  INTEGER  {
	enabled(2),
	disabled(3)
	}
    MAX-ACCESS  read-create
    STATUS  current
    DESCRIPTION
        "Enable or disable a user."
    ::= { agAccessUserNewCfgTableEntry 11 }

agAccessUserNewCfgDelete OBJECT-TYPE
    SYNTAX  INTEGER  {
        other(1),
        delete(2)
        }
    MAX-ACCESS  read-create
    STATUS  current
    DESCRIPTION
        "This is an action object to create or delete a User.
         other(1) is returned always when read.
         The following values are writable: delete(2)...to delete a User"
    ::= { agAccessUserNewCfgTableEntry 12 }

agAccessUserNewCfgBmap OBJECT-TYPE
    SYNTAX  OCTET STRING
    MAX-ACCESS  read-only
    STATUS  current
    DESCRIPTION
        "The real servers added to this user.
         The selected real servers are presented in a bitmap format.
         in receiving order:

             OCTET 1  OCTET 2  .....
             xxxxxxxx xxxxxxxx .....
             ||    || |_ Real Server 9
             ||    ||
             ||    ||___ Real Server 8
             ||    |____ Real Server 7
             ||      .    .   .
             ||_________ Real Server 2
             |__________ Real Server 1

             where x : 1 - The represented Real Server is added
                       0 - The represented Real Server is not added"
    ::= { agAccessUserNewCfgTableEntry 13 }

agAccessUserNewCfgEnhRealAdd OBJECT-TYPE
    SYNTAX  DisplayString (SIZE(1..255))
    MAX-ACCESS  read-create
    STATUS  current
    DESCRIPTION
        "Add user real server name."
    ::= { agAccessUserNewCfgTableEntry 14 }

agAccessUserNewCfgEnhRealRem OBJECT-TYPE
    SYNTAX DisplayString (SIZE(1..255))
    MAX-ACCESS  read-create
    STATUS  current
    DESCRIPTION
        "Remove user real server name."
    ::= { agAccessUserNewCfgTableEntry 15 }

agAccessUserNewCfgLanguage OBJECT-TYPE
    SYNTAX  INTEGER  {
        english(0),
        chinese(1),
	korean(2),
	japanese(3)
        }
    MAX-ACCESS  read-create
    STATUS  current
    DESCRIPTION
        "Set Web UI user display language."
    ::= { agAccessUserNewCfgTableEntry 16 }

agAccessUserNewCfgSshkey OBJECT-TYPE
    SYNTAX  DisplayString (SIZE(0..32))
    MAX-ACCESS  read-create
    STATUS  current
    DESCRIPTION
        "The SSH Public Key ID"
    ::= { agAccessUserNewCfgTableEntry 17 }

agAccessUserEnhRealsTable OBJECT-TYPE
    SYNTAX  SEQUENCE OF AgAccessUserEnhRealsTableEntry
    MAX-ACCESS  not-accessible
    STATUS  current
    DESCRIPTION
        "The table of Access user configuration."
    ::= { agAccessUid 3 }

agAccessUserEnhRealsTableEntry OBJECT-TYPE
    SYNTAX  AgAccessUserEnhRealsTableEntry
    MAX-ACCESS  not-accessible
    STATUS  current
    DESCRIPTION
        "A row in the Access user configuration table."
    INDEX  { agAccessUserIndex, agAccessUserEnhRealIndex }
    ::= { agAccessUserEnhRealsTable 1 }

AgAccessUserEnhRealsTableEntry ::= SEQUENCE {
  agAccessUserIndex            Integer32,
  agAccessUserEnhRealIndex     DisplayString
  }

agAccessUserIndex OBJECT-TYPE
    SYNTAX Integer32
    MAX-ACCESS  read-only
    STATUS  current
    DESCRIPTION
        "The User identifier."
    ::= { agAccessUserEnhRealsTableEntry 1 }

agAccessUserEnhRealIndex OBJECT-TYPE
    SYNTAX  DisplayString (SIZE(1..255))
    MAX-ACCESS  read-only
    STATUS  current
    DESCRIPTION
        "Reaser server index added to the user."
    ::= { agAccessUserEnhRealsTableEntry 2 }

agAccessCurCfgEnhUserRealTable OBJECT-TYPE
    SYNTAX  SEQUENCE OF AgAccessCurCfgEnhUserRealTableEntry
    MAX-ACCESS  not-accessible
    STATUS  current
    DESCRIPTION
        "The table of Access user configuration."
    ::= { agAccessUid 4 }

agAccessCurCfgEnhUserRealTableEntry OBJECT-TYPE
    SYNTAX  AgAccessCurCfgEnhUserRealTableEntry
    MAX-ACCESS  not-accessible
    STATUS  current
    DESCRIPTION
        "A row in the Access user configuration table."
    INDEX  { agAccessCurCfgEnhUserRealIndex, agAccessCurCfgEnhUserRealServ }
    ::= { agAccessCurCfgEnhUserRealTable 1 }

AgAccessCurCfgEnhUserRealTableEntry ::= SEQUENCE {
  agAccessCurCfgEnhUserRealIndex    Integer32,
  agAccessCurCfgEnhUserRealServ     DisplayString,
  agAccessCurCfgEnhUserIdState     INTEGER
  }

agAccessCurCfgEnhUserRealIndex OBJECT-TYPE
    SYNTAX Integer32
    MAX-ACCESS  read-only
    STATUS  current
    DESCRIPTION
        "The User identifier."
    ::= { agAccessCurCfgEnhUserRealTableEntry 1 }

agAccessCurCfgEnhUserRealServ OBJECT-TYPE
    SYNTAX  DisplayString (SIZE(0..255))
    MAX-ACCESS  read-only
    STATUS  current
    DESCRIPTION
        "Add user real server name."
    ::= { agAccessCurCfgEnhUserRealTableEntry 2 }

agAccessCurCfgEnhUserIdState OBJECT-TYPE
    SYNTAX  INTEGER {
        enabled(1),
        disabled(2)
        }
    MAX-ACCESS  read-only
    STATUS  current
    DESCRIPTION
      "Enable/disable status of used configure."
    ::= { agAccessCurCfgEnhUserRealTableEntry 3 }

agAccessNewCfgEnhUserRealTable OBJECT-TYPE
    SYNTAX  SEQUENCE OF AgAccessNewCfgEnhUserRealTableEntry
    MAX-ACCESS  not-accessible
    STATUS  current
    DESCRIPTION
        "The table of Access user configuration."
    ::= { agAccessUid 5 }

agAccessNewCfgEnhUserRealTableEntry OBJECT-TYPE
    SYNTAX  AgAccessNewCfgEnhUserRealTableEntry
    MAX-ACCESS  not-accessible
    STATUS  current
    DESCRIPTION
        "A row in the Access user configuration table."
    INDEX  { agAccessNewCfgEnhUserRealIndex, agAccessNewCfgEnhUserRealServ }
    ::= { agAccessNewCfgEnhUserRealTable 1 }

AgAccessNewCfgEnhUserRealTableEntry ::= SEQUENCE {
  agAccessNewCfgEnhUserRealIndex    Integer32,
  agAccessNewCfgEnhUserRealServ     DisplayString,
  agAccessNewCfgEnhUserIdState     INTEGER
  }

agAccessNewCfgEnhUserRealIndex OBJECT-TYPE
    SYNTAX Integer32
    MAX-ACCESS  read-only
    STATUS  current
    DESCRIPTION
        "The User identifier."
    ::= { agAccessNewCfgEnhUserRealTableEntry 1 }

agAccessNewCfgEnhUserRealServ OBJECT-TYPE
    SYNTAX  DisplayString (SIZE(0..255))
    MAX-ACCESS  read-only
    STATUS  current
    DESCRIPTION
        "Add user real server name."
    ::= { agAccessNewCfgEnhUserRealTableEntry 2 }

agAccessNewCfgEnhUserIdState OBJECT-TYPE
    SYNTAX  INTEGER {
        enabled(1),
        disabled(2)
        }
    MAX-ACCESS  read-create
    STATUS  current
    DESCRIPTION
        "Enable/disable a real server per user basis."
    ::= { agAccessNewCfgEnhUserRealTableEntry 3 }


agAccessUsrPasswd OBJECT-TYPE
    SYNTAX  DisplayString (SIZE(0..160))
    MAX-ACCESS  read-write
    STATUS  current
    DESCRIPTION
        "The character string representing the user password."
    ::= { agAccessUser 2 }

agAccessSlbOperPasswd OBJECT-TYPE
    SYNTAX  DisplayString (SIZE(0..160))
    MAX-ACCESS  read-write
    STATUS  current
    DESCRIPTION
        "The character string representing the SLB operator(slboper)
         password."
    ::= { agAccessUser 3 }

agAccessL4OperPasswd OBJECT-TYPE
    SYNTAX  DisplayString (SIZE(0..160))
    MAX-ACCESS  read-write
    STATUS  current
    DESCRIPTION
        "The character string representing the L4 operator(l4oper)
        password."
    ::= { agAccessUser 4 }

agAccessOperPasswd OBJECT-TYPE
    SYNTAX  DisplayString (SIZE(0..160))
    MAX-ACCESS  read-write
    STATUS  current
    DESCRIPTION
        "The character string representing the Operator(oper) password."
    ::= { agAccessUser 5 }

agAccessSlbAdminPasswd OBJECT-TYPE
    SYNTAX  DisplayString (SIZE(0..160))
    MAX-ACCESS  read-write
    STATUS  current
    DESCRIPTION
        "The character string representing the Slb Admin (slbadmin)
         password."
    ::= { agAccessUser 6 }

agAccessL4AdminPasswd OBJECT-TYPE
    SYNTAX  DisplayString (SIZE(0..160))
    MAX-ACCESS  read-write
    STATUS  current
    DESCRIPTION
        "The character string representing the L4 Admin(l4admin)
         password."
    ::= { agAccessUser 7 }

agAccessAdminPasswd OBJECT-TYPE
    SYNTAX  DisplayString (SIZE(0..160))
    MAX-ACCESS  read-write
    STATUS  current
    DESCRIPTION
        "The character string representing the current Administrator(admin)
         password."
    ::= { agAccessUser 8 }

agAccessAdminNewPasswd OBJECT-TYPE
    SYNTAX  DisplayString (SIZE(0..160))
    MAX-ACCESS  read-write
    STATUS  current
    DESCRIPTION
        "The character string representing the Administrator(admin)
         New password."
    ::= { agAccessUser 9 }

agAccessAdminConfNewPasswd OBJECT-TYPE
    SYNTAX  DisplayString (SIZE(0..160))
    MAX-ACCESS  read-write
    STATUS  current
    DESCRIPTION
        "The character string is used to confirm the Administrator(admin)
         New password."
    ::= { agAccessUser 11 }

agAccessSlbViewerPasswd OBJECT-TYPE
    SYNTAX  DisplayString (SIZE(0..160))
    MAX-ACCESS  read-write
    STATUS  current
    DESCRIPTION
        "The character string representing the Slb Viewer password (slbviewer)."
    ::= { agAccessUser 12 }

------------------AW---------------------------------------------

agUidAppwall          OBJECT IDENTIFIER ::= { agAccessUser 13 }

agUidAwWebAppIdCurTable OBJECT-TYPE
    SYNTAX  SEQUENCE OF AgUidAwWebAppIdCurTableEntry
    MAX-ACCESS  not-accessible
    STATUS  current
    DESCRIPTION
        "The table of Appwall Web App Id User Configuration."
    ::= { agUidAppwall 1 }

agUidAwWebAppIdCurTableEntry OBJECT-TYPE
    SYNTAX  AgUidAwWebAppIdCurTableEntry
    MAX-ACCESS  not-accessible
    STATUS  current
    DESCRIPTION
        "A row in the Appwall Web App User Table"
    INDEX  { agAccessCurUserIdx,  agAccessCurUserAwWebAppIdx}
    ::= { agUidAwWebAppIdCurTable 1 }



AgUidAwWebAppIdCurTableEntry ::= SEQUENCE{

    agAccessCurUserIdx			       INTEGER,
    agAccessCurUserAwWebAppIdx		       DisplayString,
    agAccessCurUserAwWebAppAddDelete	       INTEGER
    }


agAccessCurUserIdx OBJECT-TYPE
    SYNTAX   INTEGER
    MAX-ACCESS  read-only
    STATUS  current
    DESCRIPTION
        "first index of appwall web app user tbl"
    ::= { agUidAwWebAppIdCurTableEntry 1 }

agAccessCurUserAwWebAppIdx OBJECT-TYPE
    SYNTAX   DisplayString (SIZE (0..33))
    MAX-ACCESS  read-only
    STATUS  current
    DESCRIPTION
        "second index of appwall web app user tbl"
    ::= { agUidAwWebAppIdCurTableEntry 2 }

agAccessCurUserAwWebAppAddDelete OBJECT-TYPE
    SYNTAX  INTEGER {
        delete(0),
        add(1)
        }
    MAX-ACCESS  read-only
    STATUS  current
    DESCRIPTION
        "add/delete aw web app to user"
   ::= { agUidAwWebAppIdCurTableEntry 3 }


agUidAwWebAppIdNewTable OBJECT-TYPE
    SYNTAX  SEQUENCE OF AgUidAwWebAppIdNewTableEntry
    MAX-ACCESS  not-accessible
    STATUS  current
    DESCRIPTION
        "The table of Appwall Web App Id User Configuration."
    ::= { agUidAppwall 2 }

agUidAwWebAppIdNewTableEntry OBJECT-TYPE
    SYNTAX  AgUidAwWebAppIdNewTableEntry
    MAX-ACCESS  not-accessible
    STATUS  current
    DESCRIPTION
        "A row in the Appwall Web App User Table"
    INDEX  { agAccessNewUserIdx,  agAccessNewUserAwWebAppIdx}
    ::= { agUidAwWebAppIdNewTable 1 }



AgUidAwWebAppIdNewTableEntry ::= SEQUENCE{

    agAccessNewUserIdx			       INTEGER,
    agAccessNewUserAwWebAppIdx		       DisplayString,
    agAccessNewUserAwWebAppAddDelete	       INTEGER
    }


agAccessNewUserIdx OBJECT-TYPE
    SYNTAX   INTEGER
    MAX-ACCESS  read-only
    STATUS  current
    DESCRIPTION
        "first index of appwall web app user tbl"
    ::= { agUidAwWebAppIdNewTableEntry 1 }

agAccessNewUserAwWebAppIdx OBJECT-TYPE
    SYNTAX   DisplayString (SIZE (0..33))
    MAX-ACCESS  read-only
    STATUS  current
    DESCRIPTION
        "second index of appwall web app user tbl"
    ::= { agUidAwWebAppIdNewTableEntry 2 }

agAccessNewUserAwWebAppAddDelete OBJECT-TYPE
    SYNTAX  INTEGER {
        delete(2),
        add(1)
        }
    MAX-ACCESS  read-write
    STATUS  current
    DESCRIPTION
        "add/delete aw web app to user"
   ::= { agUidAwWebAppIdNewTableEntry 3 }

agAccessWsAdminPasswd OBJECT-TYPE
    SYNTAX  DisplayString (SIZE(0..160))
    MAX-ACCESS  read-write
    STATUS  current
    DESCRIPTION
        "The character string representing the Web Security Administrator password (wsadmin)."
    ::= { agAccessUser 14 }
--------------------------------------------------------------------------------
agAccessTelnet OBJECT-TYPE
    SYNTAX  INTEGER  {
        enabled(2),
        disabled(3)
        }
    MAX-ACCESS  read-write
    STATUS  current
    DESCRIPTION
        "Enable or disable Telnet server access."
    ::= { agAccess 2 }

agAccessHttp OBJECT-TYPE
    SYNTAX  INTEGER  {
        enabled(2),
        disabled(3)
        }
    MAX-ACCESS  read-write
    STATUS  current
    DESCRIPTION
        "Enable or disable HTTP (Web) server access."
    ::= { agAccess 3 }

agAccessHttps         OBJECT IDENTIFIER ::= { agAccess 4 }

agAccessCurCfgHttpsState OBJECT-TYPE
    SYNTAX  INTEGER  {
        enabled(2),
        disabled(3)
        }
    MAX-ACCESS  read-only
    STATUS  current
    DESCRIPTION
        "Enable or disable HTTPS server access."
    ::= { agAccessHttps 1 }

agAccessNewCfgHttpsState OBJECT-TYPE
    SYNTAX  INTEGER  {
        enabled(2),
        disabled(3)
        }
    MAX-ACCESS  read-write
    STATUS  current
    DESCRIPTION
        "Enable or disable HTTPS server access."
    ::= { agAccessHttps 2 }

agAccessCurCfgHttpsPort OBJECT-TYPE
    SYNTAX  INTEGER (1..65535)
    MAX-ACCESS  read-only
    STATUS  current
    DESCRIPTION
        "Enter HTTPS server port number."
    ::= { agAccessHttps 3 }

agAccessNewCfgHttpsPort OBJECT-TYPE
    SYNTAX  INTEGER (1..65535)
    MAX-ACCESS  read-write
    STATUS  current
    DESCRIPTION
        "Enter HTTPS server port number."
    ::= { agAccessHttps 4 }

agAccessCurCfgHttpsCert OBJECT-TYPE
    SYNTAX DisplayString (SIZE(0..128))
    MAX-ACCESS  read-only
    STATUS  current
    DESCRIPTION
        "Association of HTTPS server certificate from certificate repository."
    ::= { agAccessHttps 5 }

agAccessNewCfgHttpsCert OBJECT-TYPE
    SYNTAX DisplayString (SIZE(0..128))
    MAX-ACCESS  read-write
    STATUS  current
    DESCRIPTION
        "Association of HTTPS server certificate from certificate repository."
    ::= { agAccessHttps 6 }

-- Dont remove this placeholder. Definition is below
--agAccessHttpsCfgCertsTable OBJECT-TYPE
--    SYNTAX  SEQUENCE OF AgAccessHttpsCfgCertsEntry
--    MAX-ACCESS  not-accessible
--    STATUS  current
--    DESCRIPTION
--        "."
--    ::= { agAccessHttps 7 }

agAccessCurCfgHttpsIntermcaChainName OBJECT-TYPE
    SYNTAX   DisplayString (SIZE(0..128))
    MAX-ACCESS  read-only
    STATUS  current
    DESCRIPTION
        "Intermediate CA certificate chain name."
    ::= { agAccessHttps 8 }

agAccessNewCfgHttpsIntermcaChainName OBJECT-TYPE
    SYNTAX   DisplayString (SIZE(0..128))
    MAX-ACCESS  read-write
    STATUS  current
    DESCRIPTION
        "Intermediate CA certificate chain name."
    ::= { agAccessHttps 9 }

agAccessCurCfgHttpsIntermcaChainType OBJECT-TYPE
    SYNTAX   DisplayString (SIZE(0..6))
    MAX-ACCESS  read-only
    STATUS  current
    DESCRIPTION
        "Intermediate CA certificate chain type certificate=cert,Group=group,None=empty string."
    ::= { agAccessHttps 10 }

agAccessNewCfgHttpsIntermcaChainType OBJECT-TYPE
    SYNTAX   DisplayString (SIZE(0..6))
    MAX-ACCESS  read-write
    STATUS  current
    DESCRIPTION
        "Intermediate CA certificate chain type certificate=cert,Group=group,None=empty string."
    ::= { agAccessHttps 11 }

agAccessCurTls10State OBJECT-TYPE
    SYNTAX  INTEGER  {
        enabled(2),
        disabled(3)
        }
    MAX-ACCESS  read-only
    STATUS  current
    DESCRIPTION
        "Enable or disable tls1.0."
    ::= { agAccessHttps 16 }

agAccessNewTls10State OBJECT-TYPE
    SYNTAX  INTEGER  {
        enabled(2),
        disabled(3)
        }
    MAX-ACCESS  read-write
    STATUS  current
    DESCRIPTION
        "Enable or disable tls1.0."
    ::= { agAccessHttps 17 }

agAccessCurTls11State OBJECT-TYPE
    SYNTAX  INTEGER  {
        enabled(2),
        disabled(3)
        }
    MAX-ACCESS  read-only
    STATUS  current
    DESCRIPTION
        "Enable or disable tls1.1."
    ::= { agAccessHttps 18 }

agAccessNewTls11State OBJECT-TYPE
    SYNTAX  INTEGER  {
        enabled(2),
        disabled(3)
        }
    MAX-ACCESS  read-write
    STATUS  current
    DESCRIPTION
        "Enable or disable tls1.1."
    ::= { agAccessHttps 19 }

agAccessCurTls12State OBJECT-TYPE
    SYNTAX  INTEGER  {
        enabled(2),
        disabled(3)
        }
    MAX-ACCESS  read-only
    STATUS  current
    DESCRIPTION
        "Enable or disable tls1.2."
    ::= { agAccessHttps 20 }

agAccessNewTls12State OBJECT-TYPE
    SYNTAX  INTEGER  {
        enabled(2),
        disabled(3)
        }
    MAX-ACCESS  read-write
    STATUS  current
    DESCRIPTION
        "Enable or disable tls1.2."
    ::= { agAccessHttps 21 }

agAccessCurTls13State OBJECT-TYPE
    SYNTAX  INTEGER  {
        enabled(2),
        disabled(3)
        }
    MAX-ACCESS  read-only
    STATUS  current
    DESCRIPTION
        "Enable or disable tls1.3."
    ::= { agAccessHttps 22 }

agAccessNewTls13State OBJECT-TYPE
    SYNTAX  INTEGER  {
        enabled(2),
        disabled(3)
        }
    MAX-ACCESS  read-write
    STATUS  current
    DESCRIPTION
        "Enable or disable tls1.3."
    ::= { agAccessHttps 23 }


agAccessHttpsCfgCertsTable OBJECT-TYPE
    SYNTAX  SEQUENCE OF AgAccessHttpsCfgCertsEntry
    MAX-ACCESS  not-accessible
    STATUS  current
    DESCRIPTION
        "."
    ::= { agAccessHttps 7 }

agAccessHttpsCfgCertsEntry OBJECT-TYPE
    SYNTAX  AgAccessHttpsCfgCertsEntry
    MAX-ACCESS  not-accessible
    STATUS  current
    DESCRIPTION
        "."
    INDEX   { agAccessHttpsCfgCertsID }
    ::= { agAccessHttpsCfgCertsTable 1 }

AgAccessHttpsCfgCertsEntry ::= SEQUENCE {
    agAccessHttpsCfgCertsID                    INTEGER,
    agAccessHttpsCfgCertsName                  DisplayString,
    agAccessHttpsCfgCertsKeySize               INTEGER,
    agAccessHttpsCfgCertsExpiry               DisplayString,
    agAccessHttpsCfgCertsCommonName            DisplayString,
    agAccessHttpsCfgCertsHashAlgo              INTEGER,
    agAccessHttpsCfgCertsCountryName           DisplayString,
    agAccessHttpsCfgCertsProvinceName          DisplayString,
    agAccessHttpsCfgCertsLocalityName          DisplayString,
    agAccessHttpsCfgCertsOrganizationName      DisplayString,
    agAccessHttpsCfgCertsOrganizationUnitName  DisplayString,
    agAccessHttpsCfgCertsEMail                 DisplayString,
    agAccessHttpsCfgCertsValidityPeriod        INTEGER,
    agAccessHttpsCfgCertsDelete                INTEGER,
    agAccessHttpsCfgCertsGenerate              INTEGER,
    agAccessHttpsCfgCertsStatus                INTEGER
    }

agAccessHttpsCfgCertsID OBJECT-TYPE
    SYNTAX   INTEGER (1)
    MAX-ACCESS  read-only
    STATUS  current
    DESCRIPTION
        " "
    ::= { agAccessHttpsCfgCertsEntry  1 }

agAccessHttpsCfgCertsName  OBJECT-TYPE
    SYNTAX  DisplayString (SIZE(0..32))
    MAX-ACCESS  read-write
      STATUS  current
      DESCRIPTION
          "Certificate name"
      ::= { agAccessHttpsCfgCertsEntry  3 }

agAccessHttpsCfgCertsKeySize  OBJECT-TYPE
    SYNTAX  INTEGER {
                     ks512(1),
                     ks1024(2),
                     ks2048(3),
                     ks4096(4),
                     unknown(6)
                    }
    MAX-ACCESS  read-create
      STATUS  current
      DESCRIPTION
          "Key size for the generated certificate"
      ::= { agAccessHttpsCfgCertsEntry  4 }

agAccessHttpsCfgCertsExpiry  OBJECT-TYPE
    SYNTAX  DisplayString
    MAX-ACCESS  read-only
      STATUS  current
      DESCRIPTION
          "Certificate expiry date"
      ::= { agAccessHttpsCfgCertsEntry  5 }

agAccessHttpsCfgCertsCommonName  OBJECT-TYPE
    SYNTAX  DisplayString (SIZE(0..85))
      MAX-ACCESS  read-create
      STATUS  current
      DESCRIPTION
          "Your website address should be provided here"
      ::= { agAccessHttpsCfgCertsEntry  6 }

agAccessHttpsCfgCertsHashAlgo  OBJECT-TYPE
    SYNTAX  INTEGER {
                     md5(1),
                     sha1(2),
                     sha256(3),
                     sha384(4),
                     sha512(5),
                     unknown(6)
                    }
    MAX-ACCESS  read-create
    STATUS  current
    DESCRIPTION
        "Hash algorithm for cert generation"
    ::= { agAccessHttpsCfgCertsEntry  7 }

agAccessHttpsCfgCertsCountryName  OBJECT-TYPE
    SYNTAX  DisplayString (SIZE(0..85))
    MAX-ACCESS  read-create
    STATUS  current
    DESCRIPTION
        "Certificate details"
    ::= { agAccessHttpsCfgCertsEntry  8 }

agAccessHttpsCfgCertsProvinceName  OBJECT-TYPE
    SYNTAX  DisplayString (SIZE(0..149))
    MAX-ACCESS  read-create
    STATUS  current
    DESCRIPTION
        "Certificate details"
    ::= { agAccessHttpsCfgCertsEntry  9 }

agAccessHttpsCfgCertsLocalityName  OBJECT-TYPE
    SYNTAX  DisplayString (SIZE(0..149))
    MAX-ACCESS  read-create
    STATUS  current
    DESCRIPTION
        "Certificate details"
    ::= { agAccessHttpsCfgCertsEntry  10 }

agAccessHttpsCfgCertsOrganizationName  OBJECT-TYPE
    SYNTAX  DisplayString (SIZE(0..85))
    MAX-ACCESS  read-create
    STATUS  current
    DESCRIPTION
        "Certificate details"
    ::= { agAccessHttpsCfgCertsEntry  11 }

agAccessHttpsCfgCertsOrganizationUnitName  OBJECT-TYPE
    SYNTAX  DisplayString (SIZE(0..85))
    MAX-ACCESS  read-create
    STATUS  current
    DESCRIPTION
        "Certificate details"
    ::= { agAccessHttpsCfgCertsEntry  12 }

agAccessHttpsCfgCertsEMail  OBJECT-TYPE
    SYNTAX  DisplayString (SIZE(0..149))
    MAX-ACCESS  read-create
    STATUS  current
    DESCRIPTION
        "Certificate details"
    ::= { agAccessHttpsCfgCertsEntry  13 }

agAccessHttpsCfgCertsValidityPeriod  OBJECT-TYPE
    SYNTAX  INTEGER  (1..3650)
    MAX-ACCESS  read-create
    STATUS  current
    DESCRIPTION
        "Period for which this certificate is valid"
    ::= { agAccessHttpsCfgCertsEntry  14 }

agAccessHttpsCfgCertsDelete OBJECT-TYPE
    SYNTAX  INTEGER {
        other(1),
        delete(2)
        }
    MAX-ACCESS  read-write
    STATUS  current
    DESCRIPTION
        "Delete certificate."
    ::= { agAccessHttpsCfgCertsEntry 15 }

agAccessHttpsCfgCertsGenerate OBJECT-TYPE
    SYNTAX  INTEGER {
        other(1),
        generate(2)
        }
    MAX-ACCESS  read-write
    STATUS  current
    DESCRIPTION
        "By setting the value to generate(2), the Certificate will be generated."
    ::= { agAccessHttpsCfgCertsEntry 16 }

agAccessHttpsCfgCertsStatus OBJECT-TYPE
    SYNTAX  INTEGER {
        generated(1),
        notGenerated(2)
        }
    MAX-ACCESS  read-only
    STATUS  current
    DESCRIPTION
        "Shows if the current certificate is generated."
    ::= { agAccessHttpsCfgCertsEntry 17 }


agAccessCurHttpsCfgIntermCertsTable OBJECT-TYPE
    SYNTAX  SEQUENCE OF AgAccessCurHttpsCfgIntermCertsEntry
    MAX-ACCESS  not-accessible
    STATUS  current
    DESCRIPTION
        "."
    ::= { agAccessHttps 12 }

agAccessCurHttpsCfgIntermCertsEntry OBJECT-TYPE
    SYNTAX  AgAccessCurHttpsCfgIntermCertsEntry
    MAX-ACCESS  not-accessible
    STATUS  current
    DESCRIPTION
        "."
    INDEX   { agAccessCurHttpsCfgIntermCertsID, agAccessCurHttpsCfgIntermCertsType }
    ::= { agAccessCurHttpsCfgIntermCertsTable 1 }

AgAccessCurHttpsCfgIntermCertsEntry ::= SEQUENCE {
    agAccessCurHttpsCfgIntermCertsID                    DisplayString,
    agAccessCurHttpsCfgIntermCertsType                  INTEGER,
    agAccessCurHttpsCfgIntermCertsName                  DisplayString,
    agAccessCurHttpsCfgIntermCertsKeySize               INTEGER,
    agAccessCurHttpsCfgIntermCertsExpiry               DisplayString,
    agAccessCurHttpsCfgIntermCertsCommonName            DisplayString,
    agAccessCurHttpsCfgIntermCertsHashAlgo              INTEGER,
    agAccessCurHttpsCfgIntermCertsCountryName           DisplayString,
    agAccessCurHttpsCfgIntermCertsProvinceName          DisplayString,
    agAccessCurHttpsCfgIntermCertsLocalityName          DisplayString,
    agAccessCurHttpsCfgIntermCertsOrganizationName      DisplayString,
    agAccessCurHttpsCfgIntermCertsOrganizationUnitName  DisplayString,
    agAccessCurHttpsCfgIntermCertsEMail                 DisplayString,
    agAccessCurHttpsCfgIntermCertsValidityPeriod        INTEGER,
    agAccessCurHttpsCfgIntermCertsStatus                INTEGER,
    agAccessCurHttpsCfgIntermCertsGenerate              INTEGER,
    agAccessCurHttpsCfgIntermCertsKeyType               INTEGER,
    agAccessCurHttpsCfgIntermCertsKeySizeEc             INTEGER,
    agAccessCurHttpsCfgIntermCurveNameEc                INTEGER,
    agAccessCurHttpsCfgIntermCertsKeySizeCommon         INTEGER
    }

agAccessCurHttpsCfgIntermCertsID OBJECT-TYPE
    SYNTAX   DisplayString (SIZE(0..32))
    MAX-ACCESS  read-only
    STATUS  current
    DESCRIPTION
        "."
    ::= { agAccessCurHttpsCfgIntermCertsEntry  1 }

agAccessCurHttpsCfgIntermCertsType  OBJECT-TYPE
    SYNTAX  INTEGER {
                     intermediateCertificate(5)
                    }
    MAX-ACCESS  read-only
    STATUS  current
    DESCRIPTION
        "."
    ::= { agAccessCurHttpsCfgIntermCertsEntry  2 }

agAccessCurHttpsCfgIntermCertsName  OBJECT-TYPE
    SYNTAX  DisplayString (SIZE(0..32))
    MAX-ACCESS  read-only
    STATUS  current
    DESCRIPTION
        "."
    ::= { agAccessCurHttpsCfgIntermCertsEntry  3 }

agAccessCurHttpsCfgIntermCertsKeySize  OBJECT-TYPE
    SYNTAX  INTEGER {
                     ks512(1),
                     ks1024(2),
                     ks2048(3),
                     ks4096(4),
                     unknown(6)
                    }
    MAX-ACCESS  read-only
    STATUS  current
    DESCRIPTION
        "."
    ::= { agAccessCurHttpsCfgIntermCertsEntry  4 }

agAccessCurHttpsCfgIntermCertsExpiry  OBJECT-TYPE
    SYNTAX  DisplayString
    MAX-ACCESS  read-only
    STATUS  current
    DESCRIPTION
        "."
    ::= { agAccessCurHttpsCfgIntermCertsEntry  5 }

agAccessCurHttpsCfgIntermCertsCommonName  OBJECT-TYPE
    SYNTAX  DisplayString (SIZE(0..64))
    MAX-ACCESS  read-only
    STATUS  current
    DESCRIPTION
        "."
    ::= { agAccessCurHttpsCfgIntermCertsEntry  6 }

agAccessCurHttpsCfgIntermCertsHashAlgo  OBJECT-TYPE
    SYNTAX  INTEGER {
                     md5(1),
                     sha1(2),
                     sha256(3),
                     sha384(4),
                     sha512(5),
                     unknown(6)
                    }
    MAX-ACCESS  read-only
    STATUS  current
    DESCRIPTION
        "."
    ::= { agAccessCurHttpsCfgIntermCertsEntry  7 }

agAccessCurHttpsCfgIntermCertsCountryName  OBJECT-TYPE
    SYNTAX  DisplayString (SIZE (2))
    MAX-ACCESS  read-only
    STATUS  current
    DESCRIPTION
        "."
    ::= { agAccessCurHttpsCfgIntermCertsEntry  8 }

agAccessCurHttpsCfgIntermCertsProvinceName  OBJECT-TYPE
    SYNTAX  DisplayString (SIZE(0..128))
    MAX-ACCESS  read-only
    STATUS  current
    DESCRIPTION
        "."
    ::= { agAccessCurHttpsCfgIntermCertsEntry  9 }

agAccessCurHttpsCfgIntermCertsLocalityName  OBJECT-TYPE
    SYNTAX  DisplayString (SIZE(0..128))
    MAX-ACCESS  read-only
    STATUS  current
    DESCRIPTION
        "."
    ::= { agAccessCurHttpsCfgIntermCertsEntry  10 }

agAccessCurHttpsCfgIntermCertsOrganizationName  OBJECT-TYPE
    SYNTAX  DisplayString (SIZE(0..64))
    MAX-ACCESS  read-only
    STATUS  current
    DESCRIPTION
        "."
    ::= { agAccessCurHttpsCfgIntermCertsEntry  11 }

agAccessCurHttpsCfgIntermCertsOrganizationUnitName  OBJECT-TYPE
    SYNTAX  DisplayString (SIZE(0..64))
    MAX-ACCESS  read-only
    STATUS  current
    DESCRIPTION
        "."
    ::= { agAccessCurHttpsCfgIntermCertsEntry  12 }

agAccessCurHttpsCfgIntermCertsEMail  OBJECT-TYPE
    SYNTAX  DisplayString (SIZE(0..128))
    MAX-ACCESS  read-only
    STATUS  current
    DESCRIPTION
        "."
    ::= { agAccessCurHttpsCfgIntermCertsEntry  13 }

agAccessCurHttpsCfgIntermCertsValidityPeriod  OBJECT-TYPE
    SYNTAX  INTEGER  (1..3650)
    MAX-ACCESS  read-only
    STATUS  current
    DESCRIPTION
        "."
    ::= { agAccessCurHttpsCfgIntermCertsEntry  14 }

agAccessCurHttpsCfgIntermCertsStatus OBJECT-TYPE
    SYNTAX  INTEGER {
        generated(1),
        notGenerated(2)
    }
    MAX-ACCESS  read-only
    STATUS  current
    DESCRIPTION
        "."
    ::= { agAccessCurHttpsCfgIntermCertsEntry 15 }

agAccessCurHttpsCfgIntermCertsGenerate OBJECT-TYPE
    SYNTAX  INTEGER {
        other(1),
        generate(2),
        idle(3),
        inprogress(4),
        generated(5),
        notGenerated(6)
        }
    MAX-ACCESS  read-only
    STATUS  current
    DESCRIPTION
        "When this object is read the current state is returned.
         Setting the value to generate(2),the Certificate will be generated.
         idle(3) indicates that there is no Certificate generate is in progess.
         generated(5) indicates that the last certificate generate operation is completed.
         If the generate is successful this variable will return the state
         'generated' else it will return 'notGenerated'. In case of failure('notGenerated')
         we should set this variable back to 'idle' state so others can issue the generate
         command via SNMP."
    ::= { agAccessCurHttpsCfgIntermCertsEntry 16 }

agAccessCurHttpsCfgIntermCertsKeyType  OBJECT-TYPE
    SYNTAX  INTEGER {
                     rsa(1),
                     ec(2),
                     unknown(6)
                    }
    MAX-ACCESS  read-only
    STATUS  current
    DESCRIPTION
        "Algorithm to generate the key."
    ::= { agAccessCurHttpsCfgIntermCertsEntry  17 }

agAccessCurHttpsCfgIntermCertsKeySizeEc  OBJECT-TYPE
    SYNTAX  INTEGER {
                     ks0(0),
                     ks192(1),
                     ks224(2),
                     ks256(3),
                     ks384(4),
                     ks521(5),
                     unknown(6)
                    }
    MAX-ACCESS  read-only
    STATUS  current
    DESCRIPTION
        "EC key size."
    ::= { agAccessCurHttpsCfgIntermCertsEntry  18 }

agAccessCurHttpsCfgIntermCurveNameEc OBJECT-TYPE
    SYNTAX  INTEGER {
secp112r1(1),
secp112r2(2),
secp128r1(3),
secp128r2(4),
secp160k1(5),
secp160r1(6),
secp160r2(7),
secp192k1(8),
secp224k1(9),
secp224r1(10),
secp256k1(11),
secp384r1(12),
secp521r1(13),
prime192v1(14),
prime192v2(15),
prime192v3(16),
prime239v1(17),
prime239v2(18),
prime239v3(19),
prime256v1(20),
sect113r1(21),
sect113r2(22),
sect131r1(23),
sect131r2(24),
sect163k1(25),
sect163r1(26),
sect163r2(27),
sect193r1(28),
sect193r2(29),
sect233k1(30),
sect233r1(31),
sect239k1(32),
sect283k1(33),
sect283r1(34),
sect409k1(35),
sect409r1(36),
sect571k1(37),
sect571r1(38),
c2pnb163v1(39),
c2pnb163v2(40),
c2pnb163v3(41),
c2pnb176v1(42),
c2tnb191v1(43),
c2tnb191v2(44),
c2tnb191v3(45),
c2pnb208w1(46),
c2tnb239v1(47),
c2tnb239v2(48),
c2tnb239v3(49),
c2pnb272w1(50),
c2pnb304w1(51),
c2tnb359v1(52),
c2pnb368w1(53),
c2tnb431r1(54),
wtls1(55),
wtls3(56),
wtls4(57),
wtls5(58),
wtls6(59),
wtls7(60),
wtls8(61),
wtls9(62),
wtls10(63),
wtls11(64),
wtls12(65),
unknown(0)
                    }
    MAX-ACCESS  read-only
      STATUS  current
      DESCRIPTION
          "EC curve name."
      ::= { agAccessCurHttpsCfgIntermCertsEntry 19 }

agAccessCurHttpsCfgIntermCertsKeySizeCommon  OBJECT-TYPE
    SYNTAX  INTEGER  (0..4096)
    MAX-ACCESS  read-only
    STATUS  current
    DESCRIPTION
        "Current config Read-Only Key size common for both RSA and EC"
    ::= { agAccessCurHttpsCfgIntermCertsEntry  20 }

agAccessNewHttpsCfgIntermCertsTable OBJECT-TYPE
    SYNTAX  SEQUENCE OF AgAccessNewHttpsCfgIntermCertsEntry
    MAX-ACCESS  not-accessible
    STATUS  current
    DESCRIPTION
        "."
    ::= { agAccessHttps 13 }

agAccessNewHttpsCfgIntermCertsEntry OBJECT-TYPE
    SYNTAX  AgAccessNewHttpsCfgIntermCertsEntry
    MAX-ACCESS  not-accessible
    STATUS  current
    DESCRIPTION
        "."
    INDEX   { agAccessNewHttpsCfgIntermCertsID, agAccessNewHttpsCfgIntermCertsType }
    ::= { agAccessNewHttpsCfgIntermCertsTable 1 }

AgAccessNewHttpsCfgIntermCertsEntry ::= SEQUENCE {
    agAccessNewHttpsCfgIntermCertsID                    DisplayString,
    agAccessNewHttpsCfgIntermCertsType                  INTEGER,
    agAccessNewHttpsCfgIntermCertsName                  DisplayString,
    agAccessNewHttpsCfgIntermCertsKeySize               INTEGER,
    agAccessNewHttpsCfgIntermCertsExpiry               DisplayString,
    agAccessNewHttpsCfgIntermCertsCommonName            DisplayString,
    agAccessNewHttpsCfgIntermCertsHashAlgo              INTEGER,
    agAccessNewHttpsCfgIntermCertsCountryName           DisplayString,
    agAccessNewHttpsCfgIntermCertsProvinceName          DisplayString,
    agAccessNewHttpsCfgIntermCertsLocalityName          DisplayString,
    agAccessNewHttpsCfgIntermCertsOrganizationName      DisplayString,
    agAccessNewHttpsCfgIntermCertsOrganizationUnitName  DisplayString,
    agAccessNewHttpsCfgIntermCertsEMail                 DisplayString,
    agAccessNewHttpsCfgIntermCertsValidityPeriod        INTEGER,
    agAccessNewHttpsCfgIntermCertsDelete                INTEGER,
    agAccessNewHttpsCfgIntermCertsGenerate              INTEGER,
    agAccessNewHttpsCfgIntermCertsStatus                INTEGER,
    agAccessNewHttpsCfgIntermCertsKeyType               INTEGER,
    agAccessNewHttpsCfgIntermCertsKeySizeEc             INTEGER,
    agAccessNewHttpsCfgIntermCurveNameEc                INTEGER,
    agAccessNewHttpsCfgIntermCertsKeySizeCommon         INTEGER
    }

agAccessNewHttpsCfgIntermCertsID OBJECT-TYPE
    SYNTAX   DisplayString (SIZE(0..32))
    MAX-ACCESS  read-only
    STATUS  current
    DESCRIPTION
        "Certificate ID."
    ::= { agAccessNewHttpsCfgIntermCertsEntry  1 }
agAccessNewHttpsCfgIntermCertsType  OBJECT-TYPE
    SYNTAX  INTEGER {
                     intermediateCertificate(5)
                     }
    MAX-ACCESS  read-only
    STATUS  current
    DESCRIPTION
        "Certificate type."
    ::= { agAccessNewHttpsCfgIntermCertsEntry  2 }

agAccessNewHttpsCfgIntermCertsName  OBJECT-TYPE
    SYNTAX  DisplayString (SIZE(0..32))
    MAX-ACCESS  read-write
      STATUS  current
      DESCRIPTION
          "Certificate name."
      ::= { agAccessNewHttpsCfgIntermCertsEntry  3 }

agAccessNewHttpsCfgIntermCertsKeySize  OBJECT-TYPE
    SYNTAX  INTEGER {
                     ks512(1),
                     ks1024(2),
                     ks2048(3),
                     ks4096(4),
                     unknown(6)
                    }
    MAX-ACCESS  read-create
      STATUS  current
      DESCRIPTION
          "Certificate key size."
      ::= { agAccessNewHttpsCfgIntermCertsEntry  4 }

agAccessNewHttpsCfgIntermCertsExpiry  OBJECT-TYPE
    SYNTAX  DisplayString
    MAX-ACCESS  read-only
      STATUS  current
      DESCRIPTION
          "Certificate expiry."
      ::= { agAccessNewHttpsCfgIntermCertsEntry  5 }

agAccessNewHttpsCfgIntermCertsCommonName  OBJECT-TYPE
    SYNTAX  DisplayString (SIZE(0..64))
      MAX-ACCESS  read-create
      STATUS  current
      DESCRIPTION
          "Certificate common name."
      ::= { agAccessNewHttpsCfgIntermCertsEntry  6 }

agAccessNewHttpsCfgIntermCertsHashAlgo  OBJECT-TYPE
    SYNTAX  INTEGER {
                     md5(1),
                     sha1(2),
                     sha256(3),
                     sha384(4),
                     sha512(5),
                     unknown(6)
                    }
    MAX-ACCESS  read-create
    STATUS  current
    DESCRIPTION
        "Certificate hash algorithm."
    ::= { agAccessNewHttpsCfgIntermCertsEntry  7 }

agAccessNewHttpsCfgIntermCertsCountryName  OBJECT-TYPE
    SYNTAX  DisplayString (SIZE (2))
    MAX-ACCESS  read-create
    STATUS  current
    DESCRIPTION
        "Certificate country name."
    ::= { agAccessNewHttpsCfgIntermCertsEntry  8 }

agAccessNewHttpsCfgIntermCertsProvinceName  OBJECT-TYPE
    SYNTAX  DisplayString (SIZE(0..128))
    MAX-ACCESS  read-create
    STATUS  current
    DESCRIPTION
        "Certificate province name."
    ::= { agAccessNewHttpsCfgIntermCertsEntry  9 }

agAccessNewHttpsCfgIntermCertsLocalityName  OBJECT-TYPE
    SYNTAX  DisplayString (SIZE(0..128))
    MAX-ACCESS  read-create
    STATUS  current
    DESCRIPTION
        "certificate locality name."
    ::= { agAccessNewHttpsCfgIntermCertsEntry  10 }

agAccessNewHttpsCfgIntermCertsOrganizationName  OBJECT-TYPE
    SYNTAX  DisplayString (SIZE(0..64))
    MAX-ACCESS  read-create
    STATUS  current
    DESCRIPTION
        "Certificate organization name."
    ::= { agAccessNewHttpsCfgIntermCertsEntry  11 }

agAccessNewHttpsCfgIntermCertsOrganizationUnitName  OBJECT-TYPE
    SYNTAX  DisplayString (SIZE(0..64))
    MAX-ACCESS  read-create
    STATUS  current
    DESCRIPTION
        "Certificate organization unit name."
    ::= { agAccessNewHttpsCfgIntermCertsEntry  12 }

agAccessNewHttpsCfgIntermCertsEMail  OBJECT-TYPE
    SYNTAX  DisplayString (SIZE(0..128))
    MAX-ACCESS  read-create
    STATUS  current
    DESCRIPTION
        "Email address."
    ::= { agAccessNewHttpsCfgIntermCertsEntry  13 }

agAccessNewHttpsCfgIntermCertsValidityPeriod  OBJECT-TYPE
    SYNTAX  INTEGER  (1..3650)
    MAX-ACCESS  read-create
    STATUS  current
    DESCRIPTION
        "Certificate validity period."
    ::= { agAccessNewHttpsCfgIntermCertsEntry  14 }

agAccessNewHttpsCfgIntermCertsDelete OBJECT-TYPE
    SYNTAX  INTEGER {
        other(1),
        delete(2)
        }
    MAX-ACCESS  read-write
    STATUS  current
    DESCRIPTION
        "Delete certificate."
    ::= { agAccessNewHttpsCfgIntermCertsEntry 15 }

agAccessNewHttpsCfgIntermCertsGenerate OBJECT-TYPE
    SYNTAX  INTEGER {
        other(1),
        generate(2),
        idle(3),
        inprogress(4),
        generated(5),
        notGenerated(6)
        }
    MAX-ACCESS  read-write
    STATUS  current
    DESCRIPTION
        "When this object is read the current state is returned.
         Setting the value to generate(2),the Certificate will be generated.
         idle(3) indicates that there is no Certificate generate is in progess.
         generated(5) indicates that the last certificate generate operation is completed.
         If the generate is successful this variable will return the state
         'generated' else it will return 'notGenerated'. In case of failure('notGenerated')
         we should set this variable back to 'idle' state so others can issue the generate
         command via SNMP."
    ::= { agAccessNewHttpsCfgIntermCertsEntry 16 }

agAccessNewHttpsCfgIntermCertsStatus OBJECT-TYPE
    SYNTAX  INTEGER {
        generated(1),
            notGenerated(2),
            inProgress(3)
    }
    MAX-ACCESS  read-only
    STATUS  current
    DESCRIPTION
        "Shows if the current certificate is generated."
    ::= { agAccessNewHttpsCfgIntermCertsEntry 17 }

agAccessNewHttpsCfgIntermCertsKeyType OBJECT-TYPE
    SYNTAX  INTEGER {
                     rsa(1),
                     ec(2),
                     unknown(6)
                    }
    MAX-ACCESS  read-create
    STATUS  current
    DESCRIPTION
        "Algorithm to generate the key."
    ::= { agAccessNewHttpsCfgIntermCertsEntry 18 }

agAccessNewHttpsCfgIntermCertsKeySizeEc  OBJECT-TYPE
    SYNTAX  INTEGER {
                     ks0(0),
                     ks192(1),
                     ks224(2),
                     ks256(3),
                     ks384(4),
                     ks521(5),
                     unknown(6)
                    }
    MAX-ACCESS  read-create
      STATUS  current
      DESCRIPTION
          "EC key size."
      ::= { agAccessNewHttpsCfgIntermCertsEntry  19 }

agAccessNewHttpsCfgIntermCurveNameEc OBJECT-TYPE
    SYNTAX  INTEGER {
secp112r1(1),
secp112r2(2),
secp128r1(3),
secp128r2(4),
secp160k1(5),
secp160r1(6),
secp160r2(7),
secp192k1(8),
secp224k1(9),
secp224r1(10),
secp256k1(11),
secp384r1(12),
secp521r1(13),
prime192v1(14),
prime192v2(15),
prime192v3(16),
prime239v1(17),
prime239v2(18),
prime239v3(19),
prime256v1(20),
sect113r1(21),
sect113r2(22),
sect131r1(23),
sect131r2(24),
sect163k1(25),
sect163r1(26),
sect163r2(27),
sect193r1(28),
sect193r2(29),
sect233k1(30),
sect233r1(31),
sect239k1(32),
sect283k1(33),
sect283r1(34),
sect409k1(35),
sect409r1(36),
sect571k1(37),
sect571r1(38),
c2pnb163v1(39),
c2pnb163v2(40),
c2pnb163v3(41),
c2pnb176v1(42),
c2tnb191v1(43),
c2tnb191v2(44),
c2tnb191v3(45),
c2pnb208w1(46),
c2tnb239v1(47),
c2tnb239v2(48),
c2tnb239v3(49),
c2pnb272w1(50),
c2pnb304w1(51),
c2tnb359v1(52),
c2pnb368w1(53),
c2tnb431r1(54),
wtls1(55),
wtls3(56),
wtls4(57),
wtls5(58),
wtls6(59),
wtls7(60),
wtls8(61),
wtls9(62),
wtls10(63),
wtls11(64),
wtls12(65),
                     unknown(0)
                    }
    MAX-ACCESS  read-create
      STATUS  current
      DESCRIPTION
          "EC curve name."
      ::= { agAccessNewHttpsCfgIntermCertsEntry 20 }

agAccessNewHttpsCfgIntermCertsKeySizeCommon  OBJECT-TYPE
    SYNTAX  INTEGER  (0..4096)
    MAX-ACCESS  read-only
    STATUS  current
    DESCRIPTION
        "New config Read-Only Key size common for both RSA and EC"
    ::= { agAccessNewHttpsCfgIntermCertsEntry  21 }


agAccessCurHttpsCfgGroupsTable OBJECT-TYPE
    SYNTAX  SEQUENCE OF AgAccessCurHttpsCfgGroupsEntry
    MAX-ACCESS  not-accessible
    STATUS  current
    DESCRIPTION
        "."
    ::= { agAccessHttps 14 }

agAccessCurHttpsCfgGroupsEntry OBJECT-TYPE
    SYNTAX  AgAccessCurHttpsCfgGroupsEntry
    MAX-ACCESS  not-accessible
    STATUS  current
    DESCRIPTION
        "."
    INDEX   { agAccessCurHttpsCfgGroupsID }
    ::= { agAccessCurHttpsCfgGroupsTable 1 }

AgAccessCurHttpsCfgGroupsEntry ::= SEQUENCE {
    agAccessCurHttpsCfgGroupsID          DisplayString,
    agAccessCurHttpsCfgGroupsCertBmap    OCTET STRING
    }

agAccessCurHttpsCfgGroupsID OBJECT-TYPE
    SYNTAX   DisplayString (SIZE(0..32))
    MAX-ACCESS  read-only
    STATUS  current
    DESCRIPTION
        "."
    ::= { agAccessCurHttpsCfgGroupsEntry  1 }

agAccessCurHttpsCfgGroupsCertBmap OBJECT-TYPE
    SYNTAX  OCTET STRING
    MAX-ACCESS  read-only
    STATUS  current
    DESCRIPTION
         "List of Certificates the group holds - Selected certificates
         are presented in a bitmap format.
         Receiving order is as:

         OCTET 1  OCTET 2  .....
         xxxxxxxx xxxxxxxx .....
         ||    || |_ Cert 9
         ||    ||
         ||    ||___ Cert 4
         ||    |____ Cert 3
         ||      .    .   .
         ||_________ Cert 2
         |__________ Cert 1

         where x : 1 - The represented certficate is selected
         0 - The represented certificate is not selected."
    ::= { agAccessCurHttpsCfgGroupsEntry  5 }

agAccessNewHttpsCfgGroupsTable OBJECT-TYPE
    SYNTAX  SEQUENCE OF AgAccessNewHttpsCfgGroupsEntry
    MAX-ACCESS  not-accessible
    STATUS  current
    DESCRIPTION
        "."
    ::= { agAccessHttps 15 }

agAccessNewHttpsCfgGroupsEntry OBJECT-TYPE
    SYNTAX  AgAccessNewHttpsCfgGroupsEntry
    MAX-ACCESS  not-accessible
    STATUS  current
    DESCRIPTION
        "."
    INDEX   { agAccessNewHttpsCfgGroupsID }
    ::= { agAccessNewHttpsCfgGroupsTable 1 }

AgAccessNewHttpsCfgGroupsEntry ::= SEQUENCE {
    agAccessNewHttpsCfgGroupsID          DisplayString,
    agAccessNewHttpsCfgGroupsName        DisplayString,
    agAccessNewHttpsCfgGroupsType        INTEGER,
    agAccessNewHttpsCfgGroupsDelete      INTEGER,
    agAccessNewHttpsCfgGroupsDefaultCert DisplayString,
    agAccessNewHttpsCfgGroupsAddCert     DisplayString,
    agAccessNewHttpsCfgGroupsRemCert     DisplayString,
    agAccessNewHttpsCfgGroupsCertBmap    OCTET STRING
    }

agAccessNewHttpsCfgGroupsID OBJECT-TYPE
    SYNTAX   DisplayString (SIZE(0..32))
    MAX-ACCESS  read-only
    STATUS  current
    DESCRIPTION
        "."
    ::= { agAccessNewHttpsCfgGroupsEntry  1 }

agAccessNewHttpsCfgGroupsName  OBJECT-TYPE
    SYNTAX  DisplayString (SIZE(0..32))
    MAX-ACCESS  read-write
      STATUS  current
      DESCRIPTION
          "."
      ::= { agAccessNewHttpsCfgGroupsEntry  2 }

agAccessNewHttpsCfgGroupsType  OBJECT-TYPE
    SYNTAX  INTEGER {
                     intermediateCertificate(5)
                    }
    MAX-ACCESS  read-write
    STATUS  current
    DESCRIPTION
        "."
    ::= { agAccessNewHttpsCfgGroupsEntry  3 }

agAccessNewHttpsCfgGroupsDelete OBJECT-TYPE
    SYNTAX  INTEGER {
        other(1),
        delete(2)
        }
    MAX-ACCESS  read-write
    STATUS  current
    DESCRIPTION
        "Delete certificate group."
    ::= { agAccessNewHttpsCfgGroupsEntry 4 }

agAccessNewHttpsCfgGroupsDefaultCert OBJECT-TYPE
    SYNTAX  DisplayString (SIZE(0..32))
    MAX-ACCESS  read-write
      STATUS  current
      DESCRIPTION
          "."
      ::= { agAccessNewHttpsCfgGroupsEntry  5 }

agAccessNewHttpsCfgGroupsAddCert  OBJECT-TYPE
    SYNTAX  DisplayString (SIZE(0..32))
    MAX-ACCESS  read-write
    STATUS  current
    DESCRIPTION
        "Add certificate to the group"
    ::= { agAccessNewHttpsCfgGroupsEntry  6 }

agAccessNewHttpsCfgGroupsRemCert  OBJECT-TYPE
    SYNTAX  DisplayString (SIZE(0..32))
    MAX-ACCESS  read-write
    STATUS  current
    DESCRIPTION
        "Remove certificate from the group"
    ::= { agAccessNewHttpsCfgGroupsEntry  7 }

agAccessNewHttpsCfgGroupsCertBmap OBJECT-TYPE
    SYNTAX  OCTET STRING
    MAX-ACCESS  read-only
    STATUS  current
    DESCRIPTION
         "List of Certificates the group holds - Selected certificates
         are presented in a bitmap format.
         Receiving order is as:

         OCTET 1  OCTET 2  .....
         xxxxxxxx xxxxxxxx .....
         ||    || |_ Cert 9
         ||    ||
         ||    ||___ Cert 4
         ||    |____ Cert 3
         ||      .    .   .
         ||_________ Cert 2
         |__________ Cert 1

         where x : 1 - The represented certficate is selected
         0 - The represented certificate is not selected."
    ::= { agAccessNewHttpsCfgGroupsEntry  8 }


agAccessSnmp        OBJECT IDENTIFIER ::= { agAccess 5 }
agAccessSsh         OBJECT IDENTIFIER ::= { agAccess 6 }
agAccessXml         OBJECT IDENTIFIER ::= { agAccess 7 }
agAccessSnmpV3      OBJECT IDENTIFIER ::= { agAccess 8 }

agAccessCurCfgSnmpAccess OBJECT-TYPE
    SYNTAX  INTEGER  {
        read-only(1),
        read-write(2),
        disabled(3)
        }
    MAX-ACCESS  read-only
    STATUS  current
    DESCRIPTION
        "Set SNMP access control."
    ::= { agAccessSnmp 1 }

agAccessNewCfgSnmpAccess OBJECT-TYPE
    SYNTAX  INTEGER  {
        read-only(1),
        read-write(2),
        disabled(3)
        }
    MAX-ACCESS  read-write
    STATUS  current
    DESCRIPTION
        "Set SNMP access control."
    ::= { agAccessSnmp 2 }

agAccessCurCfgSnmpReadComm OBJECT-TYPE
    SYNTAX  DisplayString (SIZE(0..32))
    MAX-ACCESS  read-only
    STATUS  current
    DESCRIPTION
        "SNMP Read community string."
    ::= { agAccessSnmp 3 }

agAccessNewCfgSnmpReadComm OBJECT-TYPE
    SYNTAX  DisplayString (SIZE(0..32))
    MAX-ACCESS  read-write
    STATUS  current
    DESCRIPTION
        "SNMP Read community string."
    ::= { agAccessSnmp 4 }

agAccessCurCfgSnmpWriteComm OBJECT-TYPE
    SYNTAX  DisplayString (SIZE(0..32))
    MAX-ACCESS  read-only
    STATUS  current
    DESCRIPTION
        "SNMP Write community string."
    ::= { agAccessSnmp 5 }

agAccessNewCfgSnmpWriteComm OBJECT-TYPE
    SYNTAX  DisplayString (SIZE(0..32))
    MAX-ACCESS  read-write
    STATUS  current
    DESCRIPTION
        "SNMP Write community string."
    ::= { agAccessSnmp 6 }

agAccessCurCfgSnmpTrap1 OBJECT-TYPE
    SYNTAX IpAddress
    MAX-ACCESS  read-only
    STATUS  current
    DESCRIPTION
        "First Snmp Trap Host IP Address."
    ::= { agAccessSnmp 7 }

agAccessNewCfgSnmpTrap1 OBJECT-TYPE
    SYNTAX IpAddress
    MAX-ACCESS  read-write
    STATUS  current
    DESCRIPTION
        "First Snmp Trap Host IP Address."
    ::= { agAccessSnmp 8 }

agAccessCurCfgSnmpTrap2 OBJECT-TYPE
    SYNTAX IpAddress
    MAX-ACCESS  read-only
    STATUS  current
    DESCRIPTION
        "Second Snmp Trap Host IP Address."
    ::= { agAccessSnmp 9 }

agAccessNewCfgSnmpTrap2 OBJECT-TYPE
    SYNTAX IpAddress
    MAX-ACCESS  read-write
    STATUS  current
    DESCRIPTION
        "Second Snmp Trap Host IP Address."
    ::= { agAccessSnmp 10 }

agAccessCurCfgSnmpTrap1Ipv6Addr OBJECT-TYPE
    SYNTAX DisplayString (SIZE(0..40))
    MAX-ACCESS read-only
    STATUS current
    DESCRIPTION
         "The IPv6 address of the first Snmp Trap Host.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agAccessSnmp 11 }

agAccessNewCfgSnmpTrap1Ipv6Addr OBJECT-TYPE
    SYNTAX DisplayString (SIZE(0..40))
    MAX-ACCESS read-write
    STATUS current
    DESCRIPTION
         "The IPv6 address of the first Snmp Trap Host.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agAccessSnmp 12 }


agAccessCurCfgSnmpTrap2Ipv6Addr OBJECT-TYPE
    SYNTAX DisplayString (SIZE(0..40))
    MAX-ACCESS read-only
    STATUS current
    DESCRIPTION
         "The IPv6 address of the first Snmp Trap Host.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agAccessSnmp 13 }

agAccessNewCfgSnmpTrap2Ipv6Addr OBJECT-TYPE
    SYNTAX DisplayString (SIZE(0..40))
    MAX-ACCESS read-write
    STATUS current
    DESCRIPTION
         "The IPv6 address of the first Snmp Trap Host.
         Address should be 16-byte haxadecimal colon notation.
         Valid IPv6 address should be in any of the following forms
         xxxx:xxxx:xxxx:xxxx:xxxx:xxxx:xxxx:xxxx or
         xxxx::xxxx:xxxx:xxxx:xxxx or ::xxxx"
    ::= { agAccessSnmp 14 }


agAccessCurCfgSshPort OBJECT-TYPE
    SYNTAX  INTEGER (1..65535)
    MAX-ACCESS  read-only
    STATUS  current
    DESCRIPTION
        "Ssh server port number."
    ::= { agAccessSsh 1 }

agAccessNewCfgSshPort OBJECT-TYPE
    SYNTAX  INTEGER (1..65535)
    MAX-ACCESS  read-write
    STATUS  current
    DESCRIPTION
        "Ssh server port number."
    ::= { agAccessSsh 2 }

agAccessCurCfgSshV1 OBJECT-TYPE
    SYNTAX  INTEGER  {
        enabled(1),
        disabled(2)
        }
    MAX-ACCESS  read-only
    STATUS  current
    DESCRIPTION
        "Enable or disable SSH V1 Support."
    ::= { agAccessSsh 3 }

agAccessNewCfgSshV1 OBJECT-TYPE
    SYNTAX  INTEGER  {
        enabled(1),
        disabled(2)
        }
    MAX-ACCESS  read-write
    STATUS  current
    DESCRIPTION
        "Enable or disable SSH V1 Support."
    ::= { agAccessSsh 4 }

agAccessCurCfgSshScp OBJECT-TYPE
    SYNTAX  INTEGER  {
        enabled(1),
        disabled(2)
        }
    MAX-ACCESS  read-only
    STATUS  current
    DESCRIPTION
        "Enable or disable SCP apply and save."
    ::= { agAccessSsh 5 }

agAccessNewCfgSshScp OBJECT-TYPE
    SYNTAX  INTEGER  {
        enabled(1),
        disabled(2)
        }
    MAX-ACCESS  read-write
    STATUS  current
    DESCRIPTION
        "Enable or disable SCP apply and save."
    ::= { agAccessSsh 6 }

agAccessCurCfgSshState OBJECT-TYPE
    SYNTAX  INTEGER  {
        enabled(1),
        disabled(2)
        }
    MAX-ACCESS  read-only
    STATUS  current
    DESCRIPTION
        "Enable or disable SSH Server."
    ::= { agAccessSsh 7 }

agAccessNewCfgSshState OBJECT-TYPE
    SYNTAX  INTEGER  {
        enabled(1),
        disabled(2)
        }
    MAX-ACCESS  read-write
    STATUS  current
    DESCRIPTION
        "Enable or disable SSH Server."
    ::= { agAccessSsh 8 }

-- SSH Public Key

agAccessSshPubKey          OBJECT IDENTIFIER ::= { agAccessSsh 9 }

agAccessCurCfgSshPubKeyTable OBJECT-TYPE
    SYNTAX  SEQUENCE OF AgAccessCurCfgSshPubKeyEntry
    MAX-ACCESS  not-accessible
    STATUS  current
    DESCRIPTION
        "."
    ::= { agAccessSshPubKey 1 }

agAccessCurCfgSshPubKeyEntry OBJECT-TYPE
    SYNTAX  AgAccessCurCfgSshPubKeyEntry
    MAX-ACCESS  not-accessible
    STATUS  current
    DESCRIPTION
        "."
    INDEX   { agAccessCurCfgSshPubKeyID }
    ::= { agAccessCurCfgSshPubKeyTable 1 }

AgAccessCurCfgSshPubKeyEntry ::= SEQUENCE {
    agAccessCurCfgSshPubKeyID                    DisplayString,
    agAccessCurCfgSshPubKeyName                  DisplayString
    }

agAccessCurCfgSshPubKeyID OBJECT-TYPE
    SYNTAX   DisplayString (SIZE(0..32))
    MAX-ACCESS  read-only
    STATUS  current
    DESCRIPTION
        "SSH Public Key ID"
    ::= { agAccessCurCfgSshPubKeyEntry  1 }

agAccessCurCfgSshPubKeyName  OBJECT-TYPE
    SYNTAX  DisplayString (SIZE(0..32))
    MAX-ACCESS  read-only
    STATUS  current
    DESCRIPTION
        "SSH Public Key Name"
    ::= { agAccessCurCfgSshPubKeyEntry  2 }

agAccessNewCfgSshPubKeyTable OBJECT-TYPE
    SYNTAX  SEQUENCE OF AgAccessNewCfgSshPubKeyEntry
    MAX-ACCESS  not-accessible
    STATUS  current
    DESCRIPTION
        "."
    ::= { agAccessSshPubKey 2 }

agAccessNewCfgSshPubKeyEntry OBJECT-TYPE
    SYNTAX  AgAccessNewCfgSshPubKeyEntry
    MAX-ACCESS  not-accessible
    STATUS  current
    DESCRIPTION
        "."
    INDEX   { agAccessNewCfgSshPubKeyID }
    ::= { agAccessNewCfgSshPubKeyTable 1 }

AgAccessNewCfgSshPubKeyEntry ::= SEQUENCE {
    agAccessNewCfgSshPubKeyID                    DisplayString,
    agAccessNewCfgSshPubKeyName                  DisplayString,
    agAccessNewCfgSshPubKeyDelete                INTEGER
    }

agAccessNewCfgSshPubKeyID OBJECT-TYPE
    SYNTAX   DisplayString (SIZE(0..32))
    MAX-ACCESS  read-only
    STATUS  current
    DESCRIPTION
        "SSH Public Key ID"
    ::= { agAccessNewCfgSshPubKeyEntry  1 }

agAccessNewCfgSshPubKeyName  OBJECT-TYPE
    SYNTAX  DisplayString (SIZE(0..32))
    MAX-ACCESS  read-write
    STATUS  current
    DESCRIPTION
        "SSH Public Key Name"
    ::= { agAccessNewCfgSshPubKeyEntry  2 }

agAccessNewCfgSshPubKeyDelete OBJECT-TYPE
    SYNTAX  INTEGER {
        other(1),
        delete(2)
        }
    MAX-ACCESS  read-write
    STATUS  current
    DESCRIPTION
        "Delete SSH Public Key."
    ::= { agAccessNewCfgSshPubKeyEntry  3 }

agCurCfgXMLCfgState OBJECT-TYPE
    SYNTAX  INTEGER {
        enabled(1),
        disabled(2)
        }
    MAX-ACCESS  read-only
    STATUS  current
    DESCRIPTION
        "Enable or disable XML config access."
    ::= { agAccessXml 1 }

agNewCfgXMLCfgState OBJECT-TYPE
    SYNTAX  INTEGER {
        enabled(1),
        disabled(2)
        }
    MAX-ACCESS  read-write
    STATUS  current
    DESCRIPTION
        "Enable or disable XML config access."
    ::= { agAccessXml 2 }

agCfgXMLCertExpire OBJECT-TYPE
    SYNTAX DisplayString (SIZE(0..255))
    MAX-ACCESS  read-only
    STATUS  current
    DESCRIPTION
        "Certificate expire."
    ::= { agAccessXml 3 }

agCfgXMLCertSubjectCountry OBJECT-TYPE
    SYNTAX DisplayString (SIZE(0..85))
    MAX-ACCESS  read-only
    STATUS  current
    DESCRIPTION
        "Certificate subject country."
    ::= { agAccessXml 4 }

agCfgXMLCertSubjectState OBJECT-TYPE
    SYNTAX DisplayString (SIZE(0..149))
    MAX-ACCESS  read-only
    STATUS  current
    DESCRIPTION
        "Certificate subject state."
    ::= { agAccessXml 5 }

agCfgXMLCertSubjectLocality OBJECT-TYPE
    SYNTAX DisplayString (SIZE(0..149))
    MAX-ACCESS  read-only
    STATUS  current
    DESCRIPTION
        "Certificate subject locality."
    ::= { agAccessXml 6 }

agCfgXMLCertSubjectOrg OBJECT-TYPE
    SYNTAX DisplayString (SIZE(0..85))
    MAX-ACCESS  read-only
    STATUS  current
    DESCRIPTION
        "Certificate subject organization."
    ::= { agAccessXml 7 }

agCfgXMLCertSubjectOrgUnit OBJECT-TYPE
    SYNTAX DisplayString (SIZE(0..85))
    MAX-ACCESS  read-only
    STATUS  current
    DESCRIPTION
        "Certificate subject organization unit."
    ::= { agAccessXml 8 }

agCfgXMLCertSubjectCommonName OBJECT-TYPE
    SYNTAX DisplayString (SIZE(0..85))
    MAX-ACCESS  read-only
    STATUS  current
    DESCRIPTION
        "Certificate subject common name."
    ::= { agAccessXml 9 }

agCfgXMLCertSubjectEmail OBJECT-TYPE
    SYNTAX DisplayString (SIZE(0..149))
    MAX-ACCESS  read-only
    STATUS  current
    DESCRIPTION
        "Certificate subject email."
    ::= { agAccessXml 10 }

agCfgXMLCertSignatureAlg OBJECT-TYPE
    SYNTAX DisplayString (SIZE(0..40))
    MAX-ACCESS  read-only
    STATUS  current
    DESCRIPTION
        "Signature algorithm."
    ::= { agAccessXml 11 }

agCfgXMLClientCertName OBJECT-TYPE
    SYNTAX DisplayString (SIZE(0..40))
    MAX-ACCESS  read-only
    STATUS  current
    DESCRIPTION
        "Certificate Name."
    ::= { agAccessXml 12 }

agCfgXMLClientCertDelete OBJECT-TYPE
    SYNTAX  INTEGER {
        other(1),
        delete(2)
        }
    MAX-ACCESS  read-write
    STATUS  current
    DESCRIPTION
        "Delete certificate."
    ::= { agAccessXml 13 }



agAccessUserLock      OBJECT IDENTIFIER ::= { agAccess 9 }

agAccessCurCfgUserAutolock OBJECT-TYPE
    SYNTAX  INTEGER {
        enabled(2),
        disabled(3)
        }
    MAX-ACCESS  read-only
    STATUS  current
    DESCRIPTION
        "Enable/disable user lockout on failed login attempts. Default disabled (for backward compatibility).
	 Set the locking of a user account after consecutive failed attempts to log in that exceed the specified Lockout Threshold."
    ::= { agAccessUserLock 1 }

agAccessNewCfgUserAutolock OBJECT-TYPE
    SYNTAX  INTEGER {
        enabled(2),
        disabled(3)
        }
	MAX-ACCESS  read-write
    STATUS  current
    DESCRIPTION
        "Enable/disable user lockout on failed login attempts. Default disabled (for backward compatibility).
	 Set the locking of a user account after consecutive failed attempts to log in that exceed the specified Lockout Threshold."
    ::= { agAccessUserLock 2 }

agAccessCurCfgUserLockTreshld   OBJECT-TYPE
    SYNTAX  INTEGER  (3..100)
    MAX-ACCESS  read-only
    STATUS  current
    DESCRIPTION
        "Number of failed login attempts: 3-100 attempts  default 5.
		a) Number of failed login attempts before that user is locked.
		b) In case the duration value is different than 0 - Failed login attempts must be made within a span defined by the Lockout Duration setting."
    ::= { agAccessUserLock 3 }

agAccessNewCfgUserLockTreshld OBJECT-TYPE
    SYNTAX INTEGER  (3..100)
	MAX-ACCESS  read-write
    STATUS  current
    DESCRIPTION
        "Number of failed login attempts: 3-100 attempts  default 5.
		a) Number of failed login attempts before that user is locked.
		b) In case the duration value is different than 0 - Failed login attempts must be made within a span defined by the Lockout Duration setting."
    ::= { agAccessUserLock 4 }

agAccessCurCfgUserLockDuration OBJECT-TYPE
    SYNTAX  INTEGER  (0..3600)
    MAX-ACCESS  read-only
    STATUS  current
    DESCRIPTION
        "Lockout Duration: 0-3600 minutes - default 10 minutes.
		a) Number of minutes that a user remains locked out in response to several invalid login attempts within the amount
		   of time specified by the Lockout Reset Duration.
		b) A value of 0 specifies that the user will be locked out until an administrator explicitly unlocks."
    ::= { agAccessUserLock 5 }

agAccessNewCfgUserLockDuration OBJECT-TYPE
    SYNTAX INTEGER  (0..3600)
	MAX-ACCESS  read-write
    STATUS  current
    DESCRIPTION
        "Lockout Duration: 0-3600 minutes - default 10 minutes.
		a) Number of minutes that a user remains locked out in response to several invalid login attempts within the amount
		   of time specified by the Lockout Reset Duration.
		b) A value of 0 specifies that the user will be locked out until an administrator explicitly unlocks."
    ::= { agAccessUserLock 6 }

agAccessCurCfgUserLockResetTime OBJECT-TYPE
    SYNTAX  INTEGER  (1..60)
    MAX-ACCESS  read-only
    STATUS  current
    DESCRIPTION
        "Lockout Reset Duration: 1-60 minutes,  default 10.
		a) Number of minutes within which failed login attempts must occur in order for the use to be locked.
		b) A user is locked if the number of invalid login attempts defined in the Lockout Threshold happens
		   within the amount of time defined by this attribute. For example, if the value in Lockout Reset
		   Duration attribute is 5 minutes, the Lockout Threshold is 3, and 3 invalid login attempts are made
		   within a 6 minute interval, then the account is not locked. If 3 invalid login attempts are made
		   within a 5 minute period, however, then the account is locked."
    ::= { agAccessUserLock 7 }

agAccessNewCfgUserLockResetTime OBJECT-TYPE
    SYNTAX INTEGER  (1..60)
	MAX-ACCESS  read-write
    STATUS  current
    DESCRIPTION
        "Lockout Reset Duration: 1-60 minutes,  default 10.
		a) Number of minutes within which failed login attempts must occur in order for the use to be locked.
		b) A user is locked if the number of invalid login attempts defined in the Lockout Threshold happens
		   within the amount of time defined by this attribute. For example, if the value in Lockout Reset
		   Duration attribute is 5 minutes, the Lockout Threshold is 3, and 3 invalid login attempts are made
		   within a 6 minute interval, then the account is not locked. If 3 invalid login attempts are made
		   within a 5 minute period, however, then the account is locked."
    ::= { agAccessUserLock 8 }


targetAddrCurCfgTable  OBJECT-TYPE
    SYNTAX       SEQUENCE OF TargetAddrCurCfgEntry
    MAX-ACCESS   not-accessible
    STATUS       current
    DESCRIPTION
        "The table of target addresses configured."
    ::= { agAccessSnmpV3 1 }

targetAddrCurCfgEntry  OBJECT-TYPE
    SYNTAX       TargetAddrCurCfgEntry
    MAX-ACCESS   not-accessible
    STATUS       current
    DESCRIPTION
        "An entry in the target address table."
    INDEX {
        targetAddrCurCfgIndex
    }
    ::= { targetAddrCurCfgTable 1 }

TargetAddrCurCfgEntry ::= SEQUENCE {
    targetAddrCurCfgIndex            Integer32,
    targetAddrCurCfgName             DisplayString,
    targetAddrCurCfgTransIp          IpAddress,
    targetAddrCurCfgTransPort        INTEGER,
    targetAddrCurCfgTagList          DisplayString,
    targetAddrCurCfgParamsName       DisplayString,
    targetAddrCurCfgTransIpv6        DisplayString,
    targetAddrCurCfgIpVer            INTEGER,
    targetAddrCurCfgTrapBmap         OCTET STRING
}

targetAddrCurCfgIndex  OBJECT-TYPE
    SYNTAX       Integer32
    MAX-ACCESS   read-only
    STATUS       current
    DESCRIPTION
        "Target Address table Identifier."
    ::= { targetAddrCurCfgEntry 1 }

targetAddrCurCfgName      OBJECT-TYPE
    SYNTAX       DisplayString (SIZE(0..32))
    MAX-ACCESS   read-only
    STATUS       current
    DESCRIPTION
        "A human readable string representing the name of
         the target address."
    ::= { targetAddrCurCfgEntry 2 }

targetAddrCurCfgTransIp OBJECT-TYPE
    SYNTAX  IpAddress
    MAX-ACCESS  read-only
    STATUS  current
    DESCRIPTION
        "Target transport address IP."
    ::= { targetAddrCurCfgEntry 3 }

targetAddrCurCfgTransPort OBJECT-TYPE
    SYNTAX  INTEGER (1..65535)
    MAX-ACCESS  read-only
    STATUS  current
    DESCRIPTION
    "Target transport address port."
    ::= { targetAddrCurCfgEntry 4 }

targetAddrCurCfgTagList OBJECT-TYPE
    SYNTAX  DisplayString (SIZE(0..255))
    MAX-ACCESS  read-only
    STATUS  current
    DESCRIPTION
        "Tag List."
    ::= { targetAddrCurCfgEntry 5 }

targetAddrCurCfgParamsName OBJECT-TYPE
    SYNTAX  DisplayString (SIZE(0..32))
    MAX-ACCESS  read-only
    STATUS  current
    DESCRIPTION
        "The target parameter name."
    ::= { targetAddrCurCfgEntry 6 }

targetAddrCurCfgTransIpv6 OBJECT-TYPE
    SYNTAX DisplayString ( SIZE ( 0 .. 40 ) )
    MAX-ACCESS read-only
    STATUS current
    DESCRIPTION
        "Target transport Ipv6 address.Address should be 16-byte
         hexadecimal colon notation. Valid IPv6 address should be in
         any of the following forms xxxx:xxxx:xxxx:xxxx:xxxx:xxxx:xxxx:xxxx
         or xxxx::xxxx:xxxx:xxxx:xxxx or ::xxxx."
    ::= { targetAddrCurCfgEntry 7 }

targetAddrCurCfgIpVer OBJECT-TYPE
    SYNTAX INTEGER {
        ipv4 ( 1 ) ,
        ipv6 ( 2 )
    }
    MAX-ACCESS read-only
    STATUS current
    DESCRIPTION
        "Version of the targer Ip Address."
    ::= { targetAddrCurCfgEntry 8 }

targetAddrCurCfgTrapBmap OBJECT-TYPE
    SYNTAX  OCTET STRING
    MAX-ACCESS  read-only
    STATUS  current
    DESCRIPTION
        "Enable/disable traps for selected features.
         Traps for selected features in bitmap format.

         in receiving order:

      OCTET 1               OCTET 2                   OCTET 3                     OCTET4                    OCTET5
      xxxx xxxx             xxxx xxxx                 xxxx xxxx                   xxxx xxxx                 xxxx xxxx
      |||| ||||_ gslb       |||| ||||__ Ip            |||| ||||___ Security       |||| ||||___ ospfv3       |||| ||||___ not used
      |||| |||__ slb        |||| |||___ Port-Mirror   |||| |||____ slb_atk        |||| |||____ not used     |||| |||____ not used
      |||| ||___ vlan       |||| |||___ Isd           |||| ||_____ http-err       |||| ||_____ not used     |||| ||_____ not used
      |||| |____ stp        |||| |_____ ntp           |||| |______ ospf           |||| |______ appsvc       |||| |______ not used
      ||||______ cli        ||||_______ bgp           ||||________ ratelim        ||||________ Ip6          ||||________ HA
      |||_______ mgmt       |||________ vrrp          |||_________ Synk-atk       |||_________ log-UFDFO    |||_________ audit
      ||________ System     ||_________ ssh           ||__________ web            ||__________ not used     ||__________ FastView
      |_________ Console    |__________ filter        |___________ Dps            |___________ rmon         |___________ vautoip

    where x : 1 - Trap is Enabled
              0 - Trap is Disabled."
    ::= { targetAddrCurCfgEntry 9 }


targetAddrNewCfgTable  OBJECT-TYPE
    SYNTAX       SEQUENCE OF TargetAddrNewCfgEntry
    MAX-ACCESS   not-accessible
    STATUS       current
    DESCRIPTION
    "The table of target addresses configured."
    ::= { agAccessSnmpV3 2 }

targetAddrNewCfgEntry  OBJECT-TYPE
    SYNTAX       TargetAddrNewCfgEntry
    MAX-ACCESS   not-accessible
    STATUS       current
    DESCRIPTION
    "An entry in the target address table."
    INDEX {
        targetAddrNewCfgIndex
    }
::= { targetAddrNewCfgTable 1 }

TargetAddrNewCfgEntry ::= SEQUENCE {
    targetAddrNewCfgIndex            Integer32,
    targetAddrNewCfgName             DisplayString,
    targetAddrNewCfgTransIp          IpAddress,
    targetAddrNewCfgTransPort        INTEGER,
    targetAddrNewCfgTagList          DisplayString,
    targetAddrNewCfgParamsName       DisplayString,
    targetAddrNewCfgEnaTrap          INTEGER,
    targetAddrNewCfgDisTrap          INTEGER,
    targetAddrNewCfgDelete           INTEGER,
    targetAddrNewCfgTransIpv6        DisplayString,
    targetAddrNewCfgIpVer            INTEGER,
    targetAddrNewCfgTrapBmap         OCTET STRING
}

targetAddrNewCfgIndex  OBJECT-TYPE
    SYNTAX       Integer32
    MAX-ACCESS   read-create
    STATUS       current
    DESCRIPTION
        "Target Address table Identifier."
    ::= { targetAddrNewCfgEntry 1 }

targetAddrNewCfgName      OBJECT-TYPE
    SYNTAX       DisplayString (SIZE(0..32))
    MAX-ACCESS   read-create
    STATUS       current
    DESCRIPTION
        "A human readable string representing the name of
         the target address."
    ::= { targetAddrNewCfgEntry 2 }

targetAddrNewCfgTransIp OBJECT-TYPE
    SYNTAX  IpAddress
    MAX-ACCESS  read-create
    STATUS  current
    DESCRIPTION
        "Target transport address IP."
    ::= { targetAddrNewCfgEntry 3 }

targetAddrNewCfgTransPort OBJECT-TYPE
    SYNTAX  INTEGER (1..65535)
    MAX-ACCESS  read-create
    STATUS  current
    DESCRIPTION
    "Target transport address port."
    ::= { targetAddrNewCfgEntry 4 }

targetAddrNewCfgTagList OBJECT-TYPE
    SYNTAX  DisplayString (SIZE(0..255))
    MAX-ACCESS  read-create
    STATUS  current
    DESCRIPTION
        "The Tag List."
    ::= { targetAddrNewCfgEntry 5 }

targetAddrNewCfgParamsName OBJECT-TYPE
    SYNTAX  DisplayString (SIZE(0..32))
    MAX-ACCESS  read-create
    STATUS  current
    DESCRIPTION
        "The target parameter name."
    ::= { targetAddrNewCfgEntry 6 }

targetAddrNewCfgEnaTrap OBJECT-TYPE
    SYNTAX  INTEGER {
        console(1),
        system(2),
        mgmt(3),
        cli(4),
        stp(5),
        vlan(6),
        slb(7),
        gslb(8),
        filter(9),
        ssh(10),
        vrrp(11),
        bgp(12),
        ntp(13),
        ip(16),
        synatk(19),
        tcplim(20),
        ospf(21),
        slbatk(23),
        security(24),
        rmon(25),
        ip6(28),
        appsvc(29),
        ospfv3(32),
	web(18),
        vautoip(33),
	fastview(34),
	audit(35),
	ha(36)
    }
    MAX-ACCESS read-create
    STATUS current
    DESCRIPTION
        "This is an action object to enable Trap to a particular target address.
         The value specified with this object is number given in this description.
         1 - Console, 2 - System, 3 - Mgmt, 4 - Cli ,5 - Stp, 6 - Vlan, 7 - Slb,
         8 - Gslb, 9 - Filter, 10 - Ssh, 11 - Vrrp, 12 - Bgp, 13 - Ntp, 16 - Ip,
         18 - Web, 19 - Syn-atk, 20 - Tcp Limit, 21 - Ospf, 23 - Slb Attack,
         24 - Security, 25 - Rmon, 28 - Ip6, 29 - AppSvc, 32 - Ospfv3, 33 - vautoip,
         34 - fastview, 35 - audit, 36 - ha.
         When read this object, the value '0' is returned always."
    ::= { targetAddrNewCfgEntry 7 }

    targetAddrNewCfgDisTrap OBJECT-TYPE
    SYNTAX  INTEGER {
        console(1),
        system(2),
        mgmt(3),
        cli(4),
        stp(5),
        vlan(6),
        slb(7),
        gslb(8),
        filter(9),
        ssh(10),
        vrrp(11),
        bgp(12),
        ntp(13),
        ip(16),
        synatk(19),
        tcplim(20),
        ospf(21),
        slbatk(23),
        security(24),
        rmon(25),
        ip6(28),
        appsvc(29),
        ospfv3(32),
	web(18),
        vautoip(33),
	fastview(34),
	audit(35),
	ha(36)
    }
    MAX-ACCESS read-create
    STATUS current
    DESCRIPTION
        "This is an action object to disable Trap to a particular target address.
         The value specified with this object is number given in this description.
         1 - Console, 2 - System, 3 - Mgmt, 4 - Cli ,5 - Stp, 6 - Vlan, 7 - Slb,
         8 - Gslb, 9 - Filter, 10 - Ssh, 11 - Vrrp, 12 - Bgp, 13 - Ntp, 16 - Ip,
         18 - Web, 19 - Syn-atk, 20 - Tcp Limit, 21 - Ospf, 23 - Slb Attack,
         24 - Security, 25 - Rmon, 28 - Ip6, 29 - AppSvc, 32 - Ospfv3, 33 - vautoip,
         34 - fastview, 35 - audit, 36 - ha.
         When read this object, the value '0' is returned always."
  ::= { targetAddrNewCfgEntry 8 }


targetAddrNewCfgDelete OBJECT-TYPE
    SYNTAX  INTEGER {
        other(1),
        delete(2)
    }
    MAX-ACCESS  read-create
    STATUS  current
    DESCRIPTION
        "This is an action object to create or delete a User.
         other(1) is returned always when read. The following
         values are writable: delete(2)...to delete a User"
    ::= { targetAddrNewCfgEntry 9 }

targetAddrNewCfgTransIpv6 OBJECT-TYPE
    SYNTAX DisplayString  ( SIZE ( 0 .. 40  ) )
    MAX-ACCESS read-create
    STATUS current
    DESCRIPTION
        "Target transport Ipv6 address.
         Address should be 16-byte hexadecimal colon notation.
         Valid IPv6 address should be in any of the following forms
         xxxx:xxxx:xxxx:xxxx:xxxx:xxxx:xxxx:xxxx or
         xxxx::xxxx:xxxx:xxxx:xxxx or ::xxxx"
    ::= { targetAddrNewCfgEntry 10 }

targetAddrNewCfgIpVer OBJECT-TYPE
    SYNTAX INTEGER {
        ipv4 ( 1 ) ,
        ipv6 ( 2 )
    }
    MAX-ACCESS read-only
    STATUS current
    DESCRIPTION
        "Version of the targer Ip Address."
    ::= { targetAddrNewCfgEntry 11 }

targetAddrNewCfgTrapBmap OBJECT-TYPE
    SYNTAX  OCTET STRING
    MAX-ACCESS  read-only
    STATUS  current
    DESCRIPTION
        "Enable/disable traps for selected features.
        Traps for selected features in bitmap format.

        in receiving order:

      OCTET 1               OCTET 2                   OCTET 3                     OCTET4                    OCTET5
      xxxx xxxx             xxxx xxxx                 xxxx xxxx                   xxxx xxxx                 xxxx xxxx
      |||| ||||_ gslb       |||| ||||__ Ip            |||| ||||___ Security       |||| ||||___ ospfv3       |||| ||||___ not used
      |||| |||__ slb        |||| |||___ Port-Mirror   |||| |||____ slb_atk        |||| |||____ not used     |||| |||____ not used
      |||| ||___ vlan       |||| |||___ Isd           |||| ||_____ http-err       |||| ||_____ not used     |||| ||_____ not used
      |||| |____ stp        |||| |_____ ntp           |||| |______ ospf           |||| |______ appsvc       |||| |______ not used
      ||||______ cli        ||||_______ bgp           ||||________ ratelim        ||||________ Ip6          ||||________ HA
      |||_______ mgmt       |||________ vrrp          |||_________ Synk-atk       |||_________ log-UFDFO    |||_________ audit
      ||________ System     ||_________ ssh           ||__________ web            ||__________ not used     ||__________ FastView
      |_________ Console    |__________ filter        |___________ Dps            |___________ rmon         |___________ vautoip

    where x : 1 - Trap is Enabled
              0 - Trap is Disabled."
    ::= { targetAddrNewCfgEntry 12 }


agAccessCurCfgSnmpV1V2Access OBJECT-TYPE
    SYNTAX INTEGER {
        enabled(1),
        disabled(2)
    }
    MAX-ACCESS read-only
    STATUS current
    DESCRIPTION
        "Enable or disable V1/V2 access in the current configuration
        block."
    ::= { agAccessSnmpV3 3 }

agAccessNewCfgSnmpV1V2Access OBJECT-TYPE
    SYNTAX INTEGER {
        enabled(1),
        disabled(2)
    }
    MAX-ACCESS read-write
    STATUS current
    DESCRIPTION
    "Enable or disable V1/V2 access in the new configuration. Value enabled(1) will open V1 and V2 access in addition to V3
    block."
    ::= { agAccessSnmpV3 4 }

agCurCfgThresholdInterval OBJECT-TYPE
    SYNTAX  INTEGER (1..1440)
    MAX-ACCESS  read-only
    STATUS  current
    DESCRIPTION
        "Threshold detection interval."
    ::= { agAlertThreshold 1 }

agNewCfgThresholdInterval OBJECT-TYPE
    SYNTAX  INTEGER (1..1440)
    MAX-ACCESS  read-write
    STATUS  current
    DESCRIPTION
        "Threshold detection interval."
    ::= { agAlertThreshold 2 }

agCurCfgThresholdThrput OBJECT-TYPE
    SYNTAX  INTEGER (0..99)
    MAX-ACCESS  read-only
    STATUS  current
    DESCRIPTION
        "Throughput license alert threshold."
    ::= { agAlertThreshold 3 }

agNewCfgThresholdThrput OBJECT-TYPE
    SYNTAX  INTEGER (0..99)
    MAX-ACCESS  read-write
    STATUS  current
    DESCRIPTION
        "Throughput license alert threshold."
    ::= { agAlertThreshold 4 }

agCurCfgThresholdSSLCps OBJECT-TYPE
    SYNTAX  INTEGER (0..99)
    MAX-ACCESS  read-only
    STATUS  current
    DESCRIPTION
        "SSL CPS license percentage for threshold alert."
    ::= { agAlertThreshold 5 }

agNewCfgThresholdSSLCps OBJECT-TYPE
    SYNTAX  INTEGER (0..99)
    MAX-ACCESS  read-write
    STATUS  current
    DESCRIPTION
        "SSL CPS license percentage for threshold alert."
    ::= { agAlertThreshold 6 }

agCurCfgThresholdCompress OBJECT-TYPE
    SYNTAX  INTEGER (0..99)
    MAX-ACCESS  read-only
    STATUS  current
    DESCRIPTION
        "Compression license percentage for threshold alert."
    ::= { agAlertThreshold 7 }

agNewCfgThresholdCompress OBJECT-TYPE
    SYNTAX  INTEGER (0..99)
    MAX-ACCESS  read-write
    STATUS  current
    DESCRIPTION
        "Compression license percentage for threshold alert."
    ::= { agAlertThreshold 8 }

agCurCfgThresholdApm OBJECT-TYPE
    SYNTAX  INTEGER (0..99)
    MAX-ACCESS  read-only
    STATUS  current
    DESCRIPTION
        "APM license percentage for threshold alert."
    ::= { agAlertThreshold 9 }

agNewCfgThresholdApm OBJECT-TYPE
    SYNTAX  INTEGER (0..99)
    MAX-ACCESS  read-write
    STATUS  current
    DESCRIPTION
        "APM license percentage for threshold alert."
    ::= { agAlertThreshold 10 }

agCurCfgThresholdSPCpu OBJECT-TYPE
    SYNTAX  INTEGER (0..99)
    MAX-ACCESS  read-only
    STATUS  current
    DESCRIPTION
        "High SP CPU Utilization detection."
    ::= { agAlertThreshold 11 }

agNewCfgThresholdSPCpu OBJECT-TYPE
    SYNTAX  INTEGER (0..99)
    MAX-ACCESS  read-write
    STATUS  current
    DESCRIPTION
        "Set high SP CPU Utilization detection."
    ::= { agAlertThreshold 12 }

agCurCfgThresholdMPCpu OBJECT-TYPE
    SYNTAX  INTEGER (0..99)
    MAX-ACCESS  read-only
    STATUS  current
    DESCRIPTION
        "High MP CPU Utilization detection."
    ::= { agAlertThreshold 13 }

agNewCfgThresholdMPCpu OBJECT-TYPE
    SYNTAX  INTEGER (0..99)
    MAX-ACCESS  read-write
    STATUS  current
    DESCRIPTION
        "Set high MP CPU Utilization detection."
    ::= { agAlertThreshold 14 }

agCurCfgThresholdSPClrCpu OBJECT-TYPE
    SYNTAX  INTEGER (0..99)
    MAX-ACCESS  read-only
    STATUS  current
    DESCRIPTION
        "High SP Clear CPU Utilization detection."
    ::= { agAlertThreshold 15 }

agCurCfgThresholdMPClrCpu OBJECT-TYPE
    SYNTAX  INTEGER (0..99)
    MAX-ACCESS  read-only
    STATUS  current
    DESCRIPTION
        "High MP Clear CPU Utilization detection."
    ::= { agAlertThreshold 16 }

agCurCfgThresholdSessTblCritical OBJECT-TYPE
    SYNTAX  INTEGER (1..100)
    MAX-ACCESS  read-only
    STATUS  current
    DESCRIPTION
        "Critical threshold for session table utilization."
    ::= { agAlertThreshold 17 }

agNewCfgThresholdSessTblCritical OBJECT-TYPE
    SYNTAX  INTEGER (1..100)
    MAX-ACCESS  read-write
    STATUS  current
    DESCRIPTION
        "Set critical threshold for session table utilization."
    ::= { agAlertThreshold 18 }

agCurCfgThresholdSessTblHigh OBJECT-TYPE
    SYNTAX  INTEGER (1..100)
    MAX-ACCESS  read-only
    STATUS  current
    DESCRIPTION
        "High threshold for session table utilization."
    ::= { agAlertThreshold 19 }

agNewCfgThresholdSessTblHigh OBJECT-TYPE
    SYNTAX  INTEGER (1..100)
    MAX-ACCESS  read-write
    STATUS  current
    DESCRIPTION
        "Set high threshold for session table utilization."
    ::= { agAlertThreshold 20 }

agCurCfgThresholdPrximityTblHigh OBJECT-TYPE
    SYNTAX  INTEGER (0..99)
    MAX-ACCESS  read-only
    STATUS  current
    DESCRIPTION
        "High threshold for proximity table utilization."
    ::= { agAlertThreshold 21 }

agNewCfgThresholdPrximityTblHigh OBJECT-TYPE
    SYNTAX  INTEGER (0..99)
    MAX-ACCESS  read-write
    STATUS  current
    DESCRIPTION
        "Set high threshold for proximity table utilization."
    ::= { agAlertThreshold 22 }

licCompanyName OBJECT-TYPE
    SYNTAX DisplayString (SIZE(0..255))
    MAX-ACCESS  read-write
    STATUS  current
    DESCRIPTION
        "Company Name Detalis."
    ::= { agLicenseConfig 1 }

licSwitchLocation OBJECT-TYPE
    SYNTAX DisplayString (SIZE(0..255))
    MAX-ACCESS  read-write
    STATUS  current
    DESCRIPTION
        "Switch Location Details."
    ::= { agLicenseConfig 2 }

licContact OBJECT-TYPE
    SYNTAX DisplayString (SIZE(0..255))
    MAX-ACCESS  read-write
    STATUS  current
    DESCRIPTION
        "Contact Details."
    ::= { agLicenseConfig 3 }


licCookie OBJECT-TYPE
    SYNTAX INTEGER  {
        enabled(1),
        disabled(2)
        }
    MAX-ACCESS  read-only
    STATUS  current
    DESCRIPTION
        "PBind Cookie Configuration."
    ::= { agLicenseConfig 4 }



agSnmpErrorRequestId OBJECT-TYPE
    SYNTAX  INTEGER
    MAX-ACCESS read-only
    STATUS current
    DESCRIPTION
      "The requestId of the request which caused the last error."
    ::=  {agSnmpSetFail 1}

agSnmpErrorTbTable OBJECT-TYPE
    SYNTAX SEQUENCE OF AgSnmpErrorTbEntry
    MAX-ACCESS not-accessible
    STATUS current
    DESCRIPTION
      "Table containing the list of errors occured"
    ::=  {agSnmpSetFail 2}

agSnmpErrorTbEntry OBJECT-TYPE
    SYNTAX AgSnmpErrorTbEntry
    MAX-ACCESS not-accessible
    STATUS current
    DESCRIPTION
       "The row definition for this table."
    INDEX { agSnmpErrorTbRequestId }
    ::=  { agSnmpErrorTbTable 1 }

AgSnmpErrorTbEntry ::= SEQUENCE {
        agSnmpErrorTbRequestId                  INTEGER,
        agSnmpErrorTbVarId                      OBJECT IDENTIFIER,
        agSnmpErrorTbDescription                DisplayString,
        agSnmpErrorTbErrorIndex                 INTEGER,
        agSnmpErrorTbType                       INTEGER,
        agSnmpErrorTbStatus                     INTEGER,
        agSnmpErrorTbFieldInEntry               DisplayString,
        agSnmpErrorTbTime                       DisplayString,
        agSnmpErrorTbDate                       DisplayString
}

agSnmpErrorTbRequestId OBJECT-TYPE
    SYNTAX INTEGER
    MAX-ACCESS read-only
    STATUS current
    DESCRIPTION
       "This variable indicates the requestId of the request which caused the error."
    ::=  { agSnmpErrorTbEntry 1 }

agSnmpErrorTbVarId OBJECT-TYPE
    SYNTAX OBJECT IDENTIFIER
    MAX-ACCESS read-only
    STATUS current
    DESCRIPTION
       "This variable indicates the variable Oid"
    ::=  { agSnmpErrorTbEntry 2 }

agSnmpErrorTbDescription OBJECT-TYPE
    SYNTAX DisplayString (SIZE(0..255))
    MAX-ACCESS read-only
    STATUS current
    DESCRIPTION
       "This variable indicates the description of the error"
    ::=  { agSnmpErrorTbEntry 3 }

agSnmpErrorTbErrorIndex OBJECT-TYPE
    SYNTAX INTEGER
    MAX-ACCESS read-only
    STATUS current
    DESCRIPTION
       "This variable indicates the index of the field in the PDU which caused the error (start at 1)"
    ::=  { agSnmpErrorTbEntry 4 }

agSnmpErrorTbType OBJECT-TYPE
    SYNTAX INTEGER {
            ok(0),
            application(1),
            internalRange(2),
            internalGeneral(3)}
    MAX-ACCESS read-only
    STATUS current
    DESCRIPTION
       "This variable indicates the type of error."
    ::=  { agSnmpErrorTbEntry 5 }

agSnmpErrorTbStatus OBJECT-TYPE
    SYNTAX INTEGER {
            ok(0),
            tooBig(1),
            noSuchName(2),
            badValue(3),
            readOnly(4),
            genErr(5),
            noAccess(6),
            wrongType(7),
            wrongLength(8),
            wrongEncoding(9),
            wrongValue(10),
            noCreation(11),
            inconsitentValue(12),
            resourceUnavailable(13),
            commitFailed(14),
            undoFailed(15),
            authorizationErr(16),
            notWritable(17),
            inconsitentName(18),
            lastErr(19)}
    MAX-ACCESS read-only
    STATUS current
    DESCRIPTION
       "This variable indicates the status of error."
    ::=  { agSnmpErrorTbEntry 6 }

agSnmpErrorTbFieldInEntry OBJECT-TYPE
    SYNTAX DisplayString (SIZE(0..255))
    MAX-ACCESS read-only
    STATUS current
    DESCRIPTION
       "This variable indicates the index of the field in an entry (0 for scalar)"
    ::=  { agSnmpErrorTbEntry 7 }

agSnmpErrorTbTime  OBJECT-TYPE
   SYNTAX DisplayString (SIZE(9))
   MAX-ACCESS read-only
   STATUS current
   DESCRIPTION
    "This variable indicates the time the error occurred, the time will be in the format hh:mm:ss"
   ::= { agSnmpErrorTbEntry 8 }

agSnmpErrorTbDate  OBJECT-TYPE
   SYNTAX DisplayString (SIZE(11))
   MAX-ACCESS read-only
   STATUS current
   DESCRIPTION
     "This variable indicates the time the error occurred, the date will be in the format dd/mm/yyyy"
    ::= { agSnmpErrorTbEntry 9 }

-- Statistics Group

-- Packet Statistics Group
-- This group represents Packet Statistics information

pktStatsAllocs OBJECT-TYPE
    SYNTAX  Counter32
    MAX-ACCESS  read-only
    STATUS  current
    DESCRIPTION
        "Total number of packet allocations from the packet buffer pool by
         the TCP/IP protocol stack."
    ::= { pktStats 1 }

pktStatsFrees OBJECT-TYPE
    SYNTAX  Counter32
    MAX-ACCESS  read-only
    STATUS  current
    DESCRIPTION
        "Total number of times the packet buffers are freed(released) to the
         packet buffer pool by the TCP/IP protocol stack."
    ::= { pktStats 2 }

pktStatsAllocFails OBJECT-TYPE
    SYNTAX  Counter32
    MAX-ACCESS  read-only
    STATUS  current
    DESCRIPTION
        "Total number of packet allocation failures from the packet buffer
         pool by the TCP/IP protocol stack."
    ::= { pktStats 3}

pktStatsMediums OBJECT-TYPE
    SYNTAX  Gauge32
    MAX-ACCESS  read-only
    STATUS  current
    DESCRIPTION
        "Total number of packet allocations with size greater than 128 bytes
         and less than or equal to 1536 bytes from the packet buffer pool by
         the TCP/IP protocol stack."
    ::= { pktStats 4}

pktStatsJumbos OBJECT-TYPE
    SYNTAX  Gauge32
    MAX-ACCESS  read-only
    STATUS  current
    DESCRIPTION
        "Total number of packet allocations with size larger than 1536 bytes
         from the packet buffer pool by the TCP/IP protocol stack."
    ::= { pktStats 5}

pktStatsSmalls OBJECT-TYPE
    SYNTAX  Gauge32
    MAX-ACCESS  read-only
    STATUS  current
    DESCRIPTION
        "Total number of packet allocations with size less than or eqaul to
         128 bytes from the packet buffer pool by the TCP/IP protocol stack."
    ::= { pktStats 6}

pktStatsMediumsHiWatermark OBJECT-TYPE
    SYNTAX  Counter32
    MAX-ACCESS  read-only
    STATUS  current
    DESCRIPTION
        "The highest number of packet allocations with size greater than
         128 bytes and less than or equal to 1536 bytes from the packet
         buffer pool by the TCP/IP protocol stack."
    ::= { pktStats 7}

pktStatsJumbosHiWatermark OBJECT-TYPE
    SYNTAX  Counter32
    MAX-ACCESS  read-only
    STATUS  current
    DESCRIPTION
        "The highest number of packet allocations with size larger than
         1536 bytes from the packet buffer pool by the TCP/IP protocol stack."
    ::= { pktStats 8}

pktStatsSmallsHiWatermark OBJECT-TYPE
    SYNTAX  Counter32
    MAX-ACCESS  read-only
    STATUS  current
    DESCRIPTION
        "The highest number of packet allocations with size less than or
         eqaul to 128 bytes from the packet buffer pool by the TCP/IP
         protocol stack."
    ::= { pktStats 9}

pktStatsDiscards OBJECT-TYPE
    SYNTAX  Counter32
    MAX-ACCESS  read-only
    STATUS  current
    DESCRIPTION
        "The total number of packets which were chosen to be discarded because
         the number of buffers available in the packet buffer pool is low."
    ::= { pktStats 10}

pktStatsDynAllocated OBJECT-TYPE
    SYNTAX  Counter32
    MAX-ACCESS  read-only
    STATUS  current
    DESCRIPTION
        "Total number of packet allocations with size greater than 9216 bytes
         and less than or equal to 21504 bytes from the packet buffer pool (used by OSPF v2/v3)"
    ::= { pktStats 11}

pktStatsDynFreed OBJECT-TYPE
    SYNTAX  Counter32
    MAX-ACCESS  read-only
    STATUS  current
    DESCRIPTION
        "Total number of packet freed with size greater than 9216 bytes and less than or
         equal to 21504 bytes from the packet buffer pool (used by OSPF v2/v3)."
    ::= { pktStats 12}

pktStatsDynInUse OBJECT-TYPE
    SYNTAX  Counter32
    MAX-ACCESS  read-only
    STATUS  current
    DESCRIPTION
        "Total number of packets in use with size greater than 9216 bytes and less than or
         equal to 21504 bytes from the packet buffer pool (used by OSPF v2/v3)."
    ::= { pktStats 13}

pktStatsDynAllocFails OBJECT-TYPE
    SYNTAX  Counter32
    MAX-ACCESS  read-only
    STATUS  current
    DESCRIPTION
        "Total number of packet allocation failures with size greater than 9216 bytes and less
         equal to 21504 bytes from the packet buffer pool (used by OSPF v2/v3)."
    ::= { pktStats 14}

-- MP CPU Statisitics Group

mpCpuStatsUtil1Second OBJECT-TYPE
    SYNTAX  Integer32
    MAX-ACCESS  read-only
    STATUS  current
    DESCRIPTION
        "The utilization of MP CPU over 1 second. It shows the percentage."
    ::= { mpCpuStats 1}

mpCpuStatsUtil4Seconds OBJECT-TYPE
    SYNTAX  Integer32
    MAX-ACCESS  read-only
    STATUS  current
    DESCRIPTION
        "The utilization of MP CPU  over 4 seconds.
	 It shows the percentage."
    ::= { mpCpuStats 2}

mpCpuStatsUtil64Seconds OBJECT-TYPE
    SYNTAX  Integer32
    MAX-ACCESS  read-only
    STATUS  current
    DESCRIPTION
        "The utilization of MP CPU over 64 seconds.
	 It shows the percentage."
    ::= { mpCpuStats 3}

--
-- Port statistics table
--
portStatsTable OBJECT-TYPE
    SYNTAX  SEQUENCE OF PortStatsTableEntry
    MAX-ACCESS  not-accessible
    STATUS  current
    DESCRIPTION
        "The table of port statistics."
    ::= { portStats 1 }

portStatsTableEntry OBJECT-TYPE
    SYNTAX  PortStatsTableEntry
    MAX-ACCESS  not-accessible
    STATUS  current
    DESCRIPTION
        "A row in the port stats table."
    INDEX   { portStatsIndx }
    ::= { portStatsTable 1 }

PortStatsTableEntry ::=
    SEQUENCE {
	portStatsIndx
	    Integer32,
	portStatsPhyIfInOctets
	    Counter64,
	portStatsPhyIfInUcastPkts
	    Counter64,
	portStatsPhyIfInNUcastPkts
	    Counter64,
	portStatsPhyIfInDiscards
	    Counter32,
	portStatsPhyIfInErrors
	    Counter32,
	portStatsPhyIfInUnknownProtos
	    Counter32,
	portStatsPhyIfOutOctets
	    Counter64,
	portStatsPhyIfOutUcastPkts
	    Counter64,
	portStatsPhyIfOutNUcastPkts
	    Counter64,
	portStatsPhyIfOutDiscards
	    Counter32,
	portStatsPhyIfOutErrors
	    Counter32,
	portStatsPhyIfOutQLen
	    Gauge32,
        portStatsPhyIfInBroadcastPkts
            Counter64,
        portStatsPhyIfOutBroadcastPkts
            Counter64,
	portStatsClear
            INTEGER,
        portStatsPhyIfInMcastPkts
            Counter64,
        portStatsPhyIfOutMcastPkts
            Counter64
    }

portStatsIndx OBJECT-TYPE
    SYNTAX  Integer32
    MAX-ACCESS  read-only
    STATUS  current
    DESCRIPTION
        "The port index."
    ::= { portStatsTableEntry 1 }

portStatsPhyIfInOctets OBJECT-TYPE
    SYNTAX  Counter64
    MAX-ACCESS  read-only
    STATUS  current
    DESCRIPTION
	    "The total number of octets received on the
	    interface, including framing characters."
    ::= { portStatsTableEntry 2 }

portStatsPhyIfInUcastPkts OBJECT-TYPE
    SYNTAX  Counter64
    MAX-ACCESS  read-only
    STATUS  current
    DESCRIPTION
	    "The number of subnetwork-unicast packets
	    delivered to a higher-layer protocol."
    ::= { portStatsTableEntry 3 }

portStatsPhyIfInNUcastPkts OBJECT-TYPE
    SYNTAX  Counter64
    MAX-ACCESS  read-only
    STATUS  current
    DESCRIPTION
	    "The number of non-unicast (i.e., subnetwork-
	    broadcast or subnetwork-multicast) packets
	    delivered to a higher-layer protocol."
    ::= { portStatsTableEntry 4 }

portStatsPhyIfInDiscards OBJECT-TYPE
    SYNTAX  Counter32
    MAX-ACCESS  read-only
    STATUS  current
    DESCRIPTION
	    "The number of inbound packets which were chosen
	    to be discarded even though no errors had been
	    detected to prevent their being deliverable to a
	    higher-layer protocol.  One possible reason for
	    discarding such a packet could be to free up
	    buffer space."
    ::= { portStatsTableEntry 5 }

portStatsPhyIfInErrors OBJECT-TYPE
    SYNTAX  Counter32
    MAX-ACCESS  read-only
    STATUS  current
    DESCRIPTION
	    "The number of inbound packets that contained
	    errors preventing them from being deliverable to a
	    higher-layer protocol."
    ::= { portStatsTableEntry 6 }

portStatsPhyIfInUnknownProtos OBJECT-TYPE
    SYNTAX  Counter32
    MAX-ACCESS  read-only
    STATUS  current
    DESCRIPTION
	    "The number of packets received via the interface
	    which were discarded because of an unknown or
	    unsupported protocol."
    ::= { portStatsTableEntry 7 }

portStatsPhyIfOutOctets OBJECT-TYPE
    SYNTAX  Counter64
    MAX-ACCESS  read-only
    STATUS  current
    DESCRIPTION
	    "The total number of octets transmitted out of the
	    interface, including framing characters."
    ::= { portStatsTableEntry 8 }

portStatsPhyIfOutUcastPkts OBJECT-TYPE
    SYNTAX  Counter64
    MAX-ACCESS  read-only
    STATUS  current
    DESCRIPTION
	    "The total number of packets that higher-level
	    protocols requested be transmitted to a
	    subnetwork-unicast address, including those that
	    were discarded or not sent."
    ::= { portStatsTableEntry 9 }

portStatsPhyIfOutNUcastPkts OBJECT-TYPE
    SYNTAX  Counter64
    MAX-ACCESS  read-only
    STATUS  current
    DESCRIPTION
	    "The total number of packets that higher-level
	    protocols requested be transmitted to a non-
	    unicast (i.e., a subnetwork-broadcast or
	    subnetwork-multicast) address, including those
	    that were discarded or not sent."
    ::= { portStatsTableEntry 10 }

portStatsPhyIfOutDiscards OBJECT-TYPE
    SYNTAX  Counter32
    MAX-ACCESS  read-only
    STATUS  current
    DESCRIPTION
	    "The number of outbound packets which were chosen
	    to be discarded even though no errors had been
	    detected to prevent their being transmitted.  One
	    possible reason for discarding such a packet could
	    be to free up buffer space."
    ::= { portStatsTableEntry 11 }

portStatsPhyIfOutErrors OBJECT-TYPE
    SYNTAX  Counter32
    MAX-ACCESS  read-only
    STATUS  current
    DESCRIPTION
	    "The number of outbound packets that could not be
	    transmitted because of errors."
    ::= { portStatsTableEntry 12 }

portStatsPhyIfOutQLen OBJECT-TYPE
    SYNTAX  Gauge32
    MAX-ACCESS  read-only
    STATUS  current
    DESCRIPTION
	    "The length of the output packet queue (in
	    packets)."
    ::= { portStatsTableEntry 13 }

portStatsPhyIfInBroadcastPkts OBJECT-TYPE
    SYNTAX  Counter64
    MAX-ACCESS  read-only
    STATUS  current
    DESCRIPTION
            "The number of packets, delivered by this sub-layer to
            a higher (sub-)layer, which were addressed to a
            broadcast address at this sub-layer."
    ::= { portStatsTableEntry 14 }

portStatsPhyIfOutBroadcastPkts OBJECT-TYPE
    SYNTAX  Counter64
    MAX-ACCESS  read-only
    STATUS  current
    DESCRIPTION
	    "The total number of packets that higher-level
            protocols requested be transmitted, and which were
            addressed to a broadcast address at this sub-layer,
            including those that were discarded or not sent."
    ::= { portStatsTableEntry 15 }

portStatsClear OBJECT-TYPE
    SYNTAX  INTEGER {
        ok(1),
        clear(2)
        }
    MAX-ACCESS  read-write
    STATUS  current
    DESCRIPTION
	    "Setting this value to clear(2) clears the stats for this port."
    ::= { portStatsTableEntry 16 }

portStatsPhyIfInMcastPkts OBJECT-TYPE
    SYNTAX  Counter64
    MAX-ACCESS  read-only
    STATUS  current
    DESCRIPTION
        "The number of packets, delivered by this sub-layer to
         a higher (sub-)layer, which were addressed to a
         multicast address at this sub-layer"
    ::= { portStatsTableEntry 17 }

portStatsPhyIfOutMcastPkts OBJECT-TYPE
    SYNTAX  Counter64
    MAX-ACCESS  read-only
    STATUS  current
    DESCRIPTION
        "The total number of packets that higher-level protocols
         requested be transmitted, and which were addressed to
         a multicast address at this sub-layer, including those
         that were discarded or not sent."
    ::= { portStatsTableEntry 18 }

portMirrorStatsTable OBJECT-TYPE
    SYNTAX  SEQUENCE OF PortMirrorStatsTableEntry
    MAX-ACCESS  not-accessible
    STATUS  current
    DESCRIPTION
        "The table of port mirror statistics.
        Note: This MIB table is not supported for VX instance of Virtualization."
    ::= { portMirrorStats 1 }

portMirrorStatsTableEntry OBJECT-TYPE
    SYNTAX  PortMirrorStatsTableEntry
    MAX-ACCESS  not-accessible
    STATUS  current
    DESCRIPTION
        "A row in the port mirror stats table."
    INDEX   { portMirrorStatsIndx }
    ::= { portMirrorStatsTable 1 }

PortMirrorStatsTableEntry ::= SEQUENCE {
    portMirrorStatsIndx          Integer32,
    portMirrorStatsIngress       Integer32,
    portMirrorStatsEgress        Integer32
    }

portMirrorStatsIndx OBJECT-TYPE
    SYNTAX  Integer32
    MAX-ACCESS  read-only
    STATUS  current
    DESCRIPTION
        "The port index."
    ::= { portMirrorStatsTableEntry 1 }

portMirrorStatsIngress OBJECT-TYPE
    SYNTAX Integer32
    MAX-ACCESS  read-only
    STATUS  current
    DESCRIPTION
        "Specifies number of bytes mirrored in ingress port."
    ::= { portMirrorStatsTableEntry 2 }

portMirrorStatsEgress  OBJECT-TYPE
    SYNTAX Integer32
    MAX-ACCESS  read-only
    STATUS  current
    DESCRIPTION
        "Specifies number of bytes mirrored in egress port."
    ::= { portMirrorStatsTableEntry 3 }

portMirrorClear  OBJECT IDENTIFIER ::= { portMirrorStats 2 }

portMirrorStatsClear OBJECT-TYPE
    SYNTAX  INTEGER {
        ok(1),
        clear(2)
        }
    MAX-ACCESS  read-write
    STATUS  current
    DESCRIPTION
        "Setting this value to clear(2) clears the mirror stats."
    ::= { portMirrorClear 1 }

-- Capacity Usage Statistics

peakThroughputUsage OBJECT-TYPE
    SYNTAX  Counter64
    MAX-ACCESS read-only
    STATUS  current
    DESCRIPTION
      "Peak throughput of ports in bits per second."
    ::=  { capacityUsageStats 1 }

curThroughputUsage OBJECT-TYPE
    SYNTAX  Counter64
    MAX-ACCESS read-only
    STATUS  current
    DESCRIPTION
      "Current throughput of ports in bits per second."
    ::=  { capacityUsageStats 2 }

peakSslCapUsage  OBJECT-TYPE
    SYNTAX  DisplayString (SIZE(0..30))
    MAX-ACCESS read-only
    STATUS  current
    DESCRIPTION
      "Peak SSL capacity usage in CPS."
    ::=  { capacityUsageStats 3 }

curSslCapUsage  OBJECT-TYPE
    SYNTAX  DisplayString (SIZE(0..30))
    MAX-ACCESS read-only
    STATUS  current
    DESCRIPTION
      "Current SSL capacity usage in CPS."
    ::=  { capacityUsageStats 4 }

peakComprsnCapUsage OBJECT-TYPE
    SYNTAX  DisplayString (SIZE(0..30))
    MAX-ACCESS read-only
    STATUS  current
    DESCRIPTION
      "Peak compression capacity usage in Mbps."
    ::=  { capacityUsageStats 5 }

curComprsnCapUsage OBJECT-TYPE
    SYNTAX  DisplayString (SIZE(0..30))
    MAX-ACCESS read-only
    STATUS  current
    DESCRIPTION
      "Current compression capacity usage in Mbps."
    ::=  { capacityUsageStats 6 }


clearCapacityUsageStats OBJECT-TYPE
    SYNTAX  INTEGER {
        ok(1),
        clear(2)
        }
    MAX-ACCESS read-write
    STATUS current
    DESCRIPTION
        "Setting this value to clear(2) clears the capacity usage stats."
    ::= { capacityUsageStats 7 }

peakApmCapUsage OBJECT-TYPE
    SYNTAX  DisplayString (SIZE(0..30))
    MAX-ACCESS read-only
    STATUS  current
    DESCRIPTION
      "Peak APM capacity usage in PgPM."
    ::=  { capacityUsageStats 8 }

curApmCapUsage OBJECT-TYPE
    SYNTAX  DisplayString (SIZE(0..30))
    MAX-ACCESS read-only
    STATUS  current
    DESCRIPTION
      "Current APM capacity usage in PgPM."
    ::=  { capacityUsageStats 9 }


-- MP Memory Statisitics
mpMemStatsTotal OBJECT-TYPE
    SYNTAX Counter64
    MAX-ACCESS read-only
    STATUS current
    DESCRIPTION
        "Total RAM (system memory) information in KB."
    ::= { mpMemStats 1 }

mpMemStatsFree OBJECT-TYPE
    SYNTAX Counter64
    MAX-ACCESS read-only
    STATUS current
    DESCRIPTION
        "Free RAM (system memory) information in KB."
    ::= { mpMemStats 3 }

mpMemStatsVirtual OBJECT-TYPE
    SYNTAX DisplayString
    MAX-ACCESS read-only
    STATUS current
    DESCRIPTION
        "MP Virtual memory in KB"
    ::= { mpMemStats 4 }

mpMemStatsRss OBJECT-TYPE
    SYNTAX DisplayString
    MAX-ACCESS read-only
    STATUS current
    DESCRIPTION
        "MP Resident(RSS Linux) memory in KB"
    ::= { mpMemStats 5 }

-- NTP Statisitics

ntpPrimaryServerReqSent OBJECT-TYPE
    SYNTAX Integer32
    MAX-ACCESS read-only
    STATUS current
    DESCRIPTION
        "The total number of NTP requests sent to Primary NTP Server."
    ::= { ntpStats 1 }

ntpPrimaryServerRespRcvd OBJECT-TYPE
    SYNTAX Integer32
    MAX-ACCESS read-only
    STATUS current
    DESCRIPTION
        "The total number of NTP responses received from Primary NTP Server."
    ::= { ntpStats 2 }

ntpPrimaryServerUpdates OBJECT-TYPE
    SYNTAX Integer32
    MAX-ACCESS read-only
    STATUS current
    DESCRIPTION
        "The total number of NTP Updates by Primary NTP Server."
    ::= { ntpStats 3 }

ntpSecondaryServerReqSent OBJECT-TYPE
    SYNTAX Integer32
    MAX-ACCESS read-only
    STATUS current
    DESCRIPTION
        "The total number of NTP requests sent to Secondary NTP Server."
    ::= { ntpStats 4 }

ntpSecondaryServerRespRcvd OBJECT-TYPE
    SYNTAX Integer32
    MAX-ACCESS read-only
    STATUS current
    DESCRIPTION
        "The total number of NTP responses received from Secondary NTP Server."
    ::= { ntpStats 5 }

ntpSecondaryServerUpdates OBJECT-TYPE
    SYNTAX Integer32
    MAX-ACCESS read-only
    STATUS current
    DESCRIPTION
        "The total number of NTP Updates by Secondary NTP Server."
    ::= { ntpStats 6 }

ntpLastUpdateServer OBJECT-TYPE
    SYNTAX  INTEGER {
        none(0),
        primary(1),
        secondary(2)
        }
    MAX-ACCESS read-only
    STATUS current
    DESCRIPTION
        "The type of ntp server updated last time."
    ::= { ntpStats 7 }

ntpLastUpdateTime OBJECT-TYPE
    SYNTAX  DisplayString (SIZE(0..127))
    MAX-ACCESS  read-only
    STATUS  current
    DESCRIPTION
        "The last time updated by ntp server."
    ::= { ntpStats 8 }

ntpClearStats OBJECT-TYPE
    SYNTAX  INTEGER {
        ok(1),
        clear(2)
        }
    MAX-ACCESS read-write
    STATUS current
    DESCRIPTION
        "Setting this value to clear(2) clears the stats for ntp."
    ::= { ntpStats 9 }

ntpSystemCurrentTime OBJECT-TYPE
    SYNTAX  DisplayString (SIZE(0..127))
    MAX-ACCESS  read-only
    STATUS  current
    DESCRIPTION
        "The current system time."
    ::= { ntpStats 10 }

-- Clear Statistics
snmpClearStats OBJECT-TYPE
    SYNTAX  INTEGER {
	ok(1),
	clear(2)
	}
    MAX-ACCESS  read-write
    STATUS  current
    DESCRIPTION
        "Setting this to clear(2) results in clearing the SNMP statistics."
    ::= { agClearStats 1 }

agDiffState OBJECT-TYPE
    SYNTAX  INTEGER {
        diff(1),
        flashdiff(2),
        idle(3),
        inprogress(4),
        complete(5)
        }
    MAX-ACCESS  read-write
    STATUS  current
    DESCRIPTION
         "When this object is read the current state is returned.
          idle(3) indicates that there is no diff in progess.
          complete(5) indicates that the last diff operation is completed.
          Setting the value to diff(1), will start a new diff operation
          Diff compares the new configuration with the current configuration
          and shows the pending configuration changes.
          Setting the value to flashdiff(1), will start a new diff operation.
          flashdiff compares new configuration with the flash configuration.
          To read the configuration changes use the agDiffTable once the
          state of this variable returns complete.
          Once the agDiffTable is read the state should be set back to 'idle'
          which frees the diff buffer and others can issue a diff command via
          SNMP."
    ::= { agDiff 2 }

agDiffTableSize OBJECT-TYPE
    SYNTAX  Integer32
    MAX-ACCESS  read-only
    STATUS  current
    DESCRIPTION
        "The number of strings in the diff table."
    ::= { agDiff 3 }

agDiffTable OBJECT-TYPE
    SYNTAX  SEQUENCE OF AgDiffTableEntry
    MAX-ACCESS  not-accessible
    STATUS  current
    DESCRIPTION
        "The table of diff strings."
    ::= { agDiff 4 }

agDiffTableEntry OBJECT-TYPE
    SYNTAX  AgDiffTableEntry
    MAX-ACCESS  not-accessible
    STATUS  current
    DESCRIPTION
        "An entry in the diff table."
    INDEX   { agDiffIndex }
    ::= { agDiffTable 1 }

AgDiffTableEntry ::= SEQUENCE {
    agDiffIndex      Integer32,
    agDiffString     OCTET STRING
    }

agDiffIndex OBJECT-TYPE
    SYNTAX  Integer32
    MAX-ACCESS  read-only
    STATUS  current
    DESCRIPTION
        "The table index."
    ::= { agDiffTableEntry 1 }

agDiffString OBJECT-TYPE
    SYNTAX  OCTET STRING
    MAX-ACCESS  read-only
    STATUS  current
    DESCRIPTION
        "A string in the diff table."
    ::= { agDiffTableEntry 2 }

-- Config Dump
agCfgDumpState OBJECT-TYPE
    SYNTAX  INTEGER {
        dump(1),
        idle(2),
        inprogress(3),
        complete(4)
        }
    MAX-ACCESS  read-write
    STATUS  current
    DESCRIPTION
         "When this object is read the current state is returned.
          idle(2) indicates that there is no dump in progess.
          complete(4) indicates that the last dump operation is completed.
          Setting the value to dump(1), will start a new dump operation
          By default Dump will show the current configuration with out Private Keys.
          To include private keys, set 'agTftpPrivateKeys' under 'agTftp'.
          To read the configuration dump use the agCfgDumpTable once the
          state of this variable returns complete.
          Once the agCfgDumpTable is read the state should be set back to
          'idle' which frees the dump buffer and others can issue a dump
          command via SNMP."
    ::= { agCfgDump 2 }

agCfgDumpTableSize OBJECT-TYPE
    SYNTAX  Integer32
    MAX-ACCESS  read-only
    STATUS  current
    DESCRIPTION
        "The number of strings in the dump table."
    ::= { agCfgDump 3 }

agCfgDumpTable OBJECT-TYPE
    SYNTAX  SEQUENCE OF AgCfgDumpTableEntry
    MAX-ACCESS  not-accessible
    STATUS  current
    DESCRIPTION
        "The table of dump strings."
    ::= { agCfgDump 4 }

agCfgDumpTableEntry OBJECT-TYPE
    SYNTAX  AgCfgDumpTableEntry
    MAX-ACCESS  not-accessible
    STATUS  current
    DESCRIPTION
        "An entry in the dump table."
    INDEX   { agCfgDumpIndex }
    ::= { agCfgDumpTable 1 }

AgCfgDumpTableEntry ::= SEQUENCE {
    agCfgDumpIndex      Integer32,
    agCfgDumpString     OCTET STRING
    }

agCfgDumpIndex OBJECT-TYPE
    SYNTAX  Integer32
    MAX-ACCESS  read-only
    STATUS  current
    DESCRIPTION
        "The table index."
    ::= { agCfgDumpTableEntry 1 }

agCfgDumpString OBJECT-TYPE
    SYNTAX  OCTET STRING
    MAX-ACCESS  read-only
    STATUS  current
    DESCRIPTION
        "A string in the dump table."
    ::= { agCfgDumpTableEntry 2 }

-- SP Statistics for GA

-- SP CPU utilization table

spGAStatsCpuUtilTable OBJECT-TYPE
    SYNTAX  SEQUENCE OF SpGAStatsCpuUtilTableEntry
    MAX-ACCESS  not-accessible
    STATUS  current
    DESCRIPTION
        "The table of SP CPU utilization shown in GA.
        Note: This MIB table is supported only for Virtualization."
    ::= { spGAStats 1 }

spGAStatsCpuUtilTableEntry OBJECT-TYPE
    SYNTAX  SpGAStatsCpuUtilTableEntry
    MAX-ACCESS  not-accessible
    STATUS  current
    DESCRIPTION
        "A row in the SP CPU utilization table."
    INDEX   { spGAStatsCpuUtilSpIndex }
    ::= { spGAStatsCpuUtilTable 1 }

SpGAStatsCpuUtilTableEntry ::= SEQUENCE {
    spGAStatsCpuUtilSpIndex    Integer32,
    spGAStatsCpuUtilvADC       DisplayString,
    spGAStatsCpuUtil1Second    Integer32,
    spGAStatsCpuUtil4Seconds   Integer32,
    spGAStatsCpuUtil64Seconds  Integer32
    }

spGAStatsCpuUtilSpIndex OBJECT-TYPE
    SYNTAX  Integer32
    MAX-ACCESS  read-only
    STATUS  current
    DESCRIPTION
        "The SP index."
    ::= { spGAStatsCpuUtilTableEntry 1 }

spGAStatsCpuUtilvADC OBJECT-TYPE
    SYNTAX  DisplayString
    MAX-ACCESS  read-only
    STATUS  current
    DESCRIPTION
        "vADC's running in this core."
    ::= { spGAStatsCpuUtilTableEntry 2 }

spGAStatsCpuUtil1Second OBJECT-TYPE
    SYNTAX  Integer32
    MAX-ACCESS  read-only
    STATUS  current
    DESCRIPTION
        "The utilization of this SP over 1 second. It shows the percentage."
    ::= { spGAStatsCpuUtilTableEntry 3 }

spGAStatsCpuUtil4Seconds OBJECT-TYPE
    SYNTAX  Integer32
    MAX-ACCESS  read-only
    STATUS  current
    DESCRIPTION
        "The utilization of this SP over 4 seconds. It shows the percentage."
    ::= { spGAStatsCpuUtilTableEntry 4 }

spGAStatsCpuUtil64Seconds OBJECT-TYPE
    SYNTAX  Integer32
    MAX-ACCESS  read-only
    STATUS  current
    DESCRIPTION
        "The utilization of this SP over 64 seconds. It shows the percentage."
    ::= { spGAStatsCpuUtilTableEntry 5 }



-- VLAN Statistics

vlanStatsTable OBJECT-TYPE
    SYNTAX  SEQUENCE OF VlanStatsTableEntry
    MAX-ACCESS  not-accessible
    STATUS  current
    DESCRIPTION
        "VLAN statistics table."
    ::= { vlanStats 1 }

vlanStatsTableEntry OBJECT-TYPE
    SYNTAX  VlanStatsTableEntry
    MAX-ACCESS  not-accessible
    STATUS  current
    DESCRIPTION
        "A row in VLAN statistics table."
    INDEX   { vlanStatsIndex }
    ::= { vlanStatsTable 1 }

VlanStatsTableEntry ::= SEQUENCE {
    vlanStatsIndex      Integer32,
    vlanStatsClear      INTEGER,
    vlanRealIndex       Integer32
    }

vlanStatsIndex OBJECT-TYPE
    SYNTAX  Integer32
    MAX-ACCESS  read-only
    STATUS  current
    DESCRIPTION
        "VLAN statistics table index."
    ::= { vlanStatsTableEntry 1 }

vlanStatsClear OBJECT-TYPE
    SYNTAX  INTEGER {
        ok(1),
        clear(2)
        }
    MAX-ACCESS  read-write
    STATUS  current
    DESCRIPTION
            "Clear VLAN statistics of a given VLAN ID."
    ::= { vlanStatsTableEntry 2 }

vlanRealIndex OBJECT-TYPE
    SYNTAX  Integer32
    MAX-ACCESS  read-only
    STATUS  current
    DESCRIPTION
        "The Real VLAN index(InterfaceIndex - 1000)."
    ::= { vlanStatsTableEntry 3 }

-- System Memory Statisitics START

systemMemStatsTotalMemory   OBJECT-TYPE
    SYNTAX  Counter32
    MAX-ACCESS  read-only
    STATUS  current
    DESCRIPTION
        "Total RAM(Mb).
        Note: This MIB is not supported for VX instance of Virtualization."
    ::= { systemMemStats 1 }

systemMemStatsInitConfigMemory   OBJECT-TYPE
    SYNTAX  Counter32
    MAX-ACCESS  read-only
    STATUS  current
    DESCRIPTION
        "Initial configured memory(Mb).
        Note: This MIB is not supported for VX instance of Virtualization."
    ::= { systemMemStats 2 }

systemMemStatsNumOfSPs   OBJECT-TYPE
    SYNTAX  Counter32
    MAX-ACCESS  read-only
    STATUS  current
    DESCRIPTION
        "Number of SPs.
        Note: This MIB is not supported for VX instance of Virtualization."
    ::= { systemMemStats 3 }

systemMemStatsInitFreeRam   OBJECT-TYPE
    SYNTAX  Counter32
    MAX-ACCESS  read-only
    STATUS  current
    DESCRIPTION
        "Initial free RAM(Mb).
        Note: This MIB is not supported for VX instance of Virtualization."
    ::= { systemMemStats 4 }

systemMemStatsInitCachedRam   OBJECT-TYPE
    SYNTAX  Counter32
    MAX-ACCESS  read-only
    STATUS  current
    DESCRIPTION
        "Initial cached RAM(Mb).
        Note: This MIB is not supported for VX instance of Virtualization."
    ::= { systemMemStats 5 }

systemMemStatsSafetyMargin1   OBJECT-TYPE
    SYNTAX  Counter32
    MAX-ACCESS  read-only
    STATUS  current
    DESCRIPTION
        "Safety margin (1st watermark %).
        Note: This MIB is not supported for VX instance of Virtualization."
    ::= { systemMemStats 6 }

systemMemStatsSafetyMargin2   OBJECT-TYPE
    SYNTAX  Counter32
    MAX-ACCESS  read-only
    STATUS  current
    DESCRIPTION
        "Safety margin (2nd watermark %).
        Note: This MIB is not supported for VX instance of Virtualization."
    ::= { systemMemStats 7 }

systemMemStatsMemoryLimitEna   OBJECT-TYPE
	SYNTAX INTEGER {
		enabled(1),
		disabled(0)
		}
    MAX-ACCESS  read-only
    STATUS  current
    DESCRIPTION
        "Memory limit module Enable/Disable.
        Note: This MIB is not supported for VX instance of Virtualization."
    ::= { systemMemStats 8 }

systemMemStatsMemoryTrapsEna   OBJECT-TYPE
	SYNTAX INTEGER {
		enabled(1),
		disabled(0)
		}
    MAX-ACCESS  read-only
    STATUS  current
    DESCRIPTION
        "Memory traps module Enable/Disable.
        Note: This MIB is not supported for VX instance of Virtualization."
    ::= { systemMemStats 9 }

-- SP Memory Statisitics END


-- Counters Statisitics START

errorCountersTable OBJECT-TYPE
    SYNTAX  SEQUENCE OF ErrorCountersTableEntry
    MAX-ACCESS  not-accessible
    STATUS  current
    DESCRIPTION
        "Error counters table."
    ::= { countersStats 1 }

errorCountersTableEntry OBJECT-TYPE
    SYNTAX  ErrorCountersTableEntry
    MAX-ACCESS  not-accessible
    STATUS  current
    DESCRIPTION
        "A row in error counters table."
    INDEX   { errorCountersIndex }
    ::= { errorCountersTable 1 }

ErrorCountersTableEntry ::= SEQUENCE {
    errorCountersIndex      	Integer32,
    errorCountersStrName	DisplayString,
    errorCountersBaseVal	Integer32,
    errorCountersHistVal15sec	Integer32,
    errorCountersHistVal30sec	Integer32,
    errorCountersHistVal45sec	Integer32,
    errorCountersHistVal60sec	Integer32,
    errorCountersHistVal75sec	Integer32
    }

errorCountersIndex OBJECT-TYPE
    SYNTAX  Integer32
    MAX-ACCESS  read-only
    STATUS  current
    DESCRIPTION
        "Error counter table index."
    ::= { errorCountersTableEntry 1 }


errorCountersStrName OBJECT-TYPE
    SYNTAX  DisplayString (SIZE(0..60))
    MAX-ACCESS  read-only
    STATUS  current
    DESCRIPTION
        "Error counter string name."
    ::= { errorCountersTableEntry 2 }


errorCountersBaseVal OBJECT-TYPE
    SYNTAX  Integer32
    MAX-ACCESS  read-only
    STATUS  current
    DESCRIPTION
        "Error counter base value."
    ::= { errorCountersTableEntry 3 }


errorCountersHistVal15sec OBJECT-TYPE
    SYNTAX  Integer32
    MAX-ACCESS  read-only
    STATUS  current
    DESCRIPTION
        "Error counter history value - 15 seconds."
    ::= { errorCountersTableEntry 4 }


errorCountersHistVal30sec OBJECT-TYPE
    SYNTAX  Integer32
    MAX-ACCESS  read-only
    STATUS  current
    DESCRIPTION
        "Error counter history value - 30 seconds."
    ::= { errorCountersTableEntry 5 }


errorCountersHistVal45sec OBJECT-TYPE
    SYNTAX  Integer32
    MAX-ACCESS  read-only
    STATUS  current
    DESCRIPTION
        "Error counter history value - 45 seconds."
    ::= { errorCountersTableEntry 6 }


errorCountersHistVal60sec OBJECT-TYPE
    SYNTAX  Integer32
    MAX-ACCESS  read-only
    STATUS  current
    DESCRIPTION
        "Error counter history value - 60 seconds."
    ::= { errorCountersTableEntry 7 }


errorCountersHistVal75sec OBJECT-TYPE
    SYNTAX  Integer32
    MAX-ACCESS  read-only
    STATUS  current
    DESCRIPTION
        "Error counter history value - 75 seconds."
    ::= { errorCountersTableEntry 8 }


eventCountersTable OBJECT-TYPE
    SYNTAX  SEQUENCE OF EventCountersTableEntry
    MAX-ACCESS  not-accessible
    STATUS  current
    DESCRIPTION
        "Event counters statistics table."
    ::= { countersStats 2 }

eventCountersTableEntry OBJECT-TYPE
    SYNTAX  EventCountersTableEntry
    MAX-ACCESS  not-accessible
    STATUS  current
    DESCRIPTION
        "A row in event counters table."
    INDEX   { eventCountersIndex }
    ::= { eventCountersTable 1 }

EventCountersTableEntry ::= SEQUENCE {
    eventCountersIndex      	Integer32,
    eventCountersStrName	DisplayString,
    eventCountersBaseVal	Integer32,
    eventCountersHistVal15sec	Integer32,
    eventCountersHistVal30sec	Integer32,
    eventCountersHistVal45sec	Integer32,
    eventCountersHistVal60sec	Integer32,
    eventCountersHistVal75sec	Integer32
    }

eventCountersIndex OBJECT-TYPE
    SYNTAX  Integer32
    MAX-ACCESS  read-only
    STATUS  current
    DESCRIPTION
        "Event counter table index."
    ::= { eventCountersTableEntry 1 }


eventCountersStrName OBJECT-TYPE
    SYNTAX  DisplayString (SIZE(0..60))
    MAX-ACCESS  read-only
    STATUS  current
    DESCRIPTION
        "Event counter string name."
    ::= { eventCountersTableEntry 2 }


eventCountersBaseVal OBJECT-TYPE
    SYNTAX  Integer32
    MAX-ACCESS  read-only
    STATUS  current
    DESCRIPTION
        "Event counter base value."
    ::= { eventCountersTableEntry 3 }


eventCountersHistVal15sec OBJECT-TYPE
    SYNTAX  Integer32
    MAX-ACCESS  read-only
    STATUS  current
    DESCRIPTION
        "Event counter history value - 15 seconds."
    ::= { eventCountersTableEntry 4 }


eventCountersHistVal30sec OBJECT-TYPE
    SYNTAX  Integer32
    MAX-ACCESS  read-only
    STATUS  current
    DESCRIPTION
        "Event counter history value - 30 seconds."
    ::= { eventCountersTableEntry 5 }


eventCountersHistVal45sec OBJECT-TYPE
    SYNTAX  Integer32
    MAX-ACCESS  read-only
    STATUS  current
    DESCRIPTION
        "Event counter history value - 45 seconds."
    ::= { eventCountersTableEntry 6 }


eventCountersHistVal60sec OBJECT-TYPE
    SYNTAX  Integer32
    MAX-ACCESS  read-only
    STATUS  current
    DESCRIPTION
        "Event counter history value - 60 seconds."
    ::= { eventCountersTableEntry 7 }


eventCountersHistVal75sec OBJECT-TYPE
    SYNTAX  Integer32
    MAX-ACCESS  read-only
    STATUS  current
    DESCRIPTION
        "Event counter history value - 75 seconds."
    ::= { eventCountersTableEntry 8 }

errorCountersSpTable OBJECT-TYPE
    SYNTAX  SEQUENCE OF ErrorCountersSpTableEntry
    MAX-ACCESS  not-accessible
    STATUS  current
    DESCRIPTION
        "Error counters for SP - statistics table."
    ::= { countersStats 3 }

errorCountersSpTableEntry OBJECT-TYPE
    SYNTAX  ErrorCountersSpTableEntry
    MAX-ACCESS  not-accessible
    STATUS  current
    DESCRIPTION
        "A row in error counters table for SP."
    INDEX   { errorCountersSpIndex,  errorCountersSpCntrIndex}
    ::= { errorCountersSpTable 1 }

ErrorCountersSpTableEntry ::= SEQUENCE {
    errorCountersSpIndex      	Integer32,
    errorCountersSpCntrIndex  	Integer32,
    errorCountersSpStrName	DisplayString,
    errorCountersSpBaseVal	Integer32
    }

errorCountersSpIndex OBJECT-TYPE
    SYNTAX  Integer32
    MAX-ACCESS  read-only
    STATUS  current
    DESCRIPTION
        "Error counter SP index."
    ::= { errorCountersSpTableEntry 1 }

errorCountersSpCntrIndex OBJECT-TYPE
    SYNTAX  Integer32
    MAX-ACCESS  read-only
    STATUS  current
    DESCRIPTION
        "Error counter index."
    ::= { errorCountersSpTableEntry 2 }

errorCountersSpStrName OBJECT-TYPE
    SYNTAX  DisplayString (SIZE(0..60))
    MAX-ACCESS  read-only
    STATUS  current
    DESCRIPTION
        "The SP error counter string name."
    ::= { errorCountersSpTableEntry 3 }


errorCountersSpBaseVal OBJECT-TYPE
    SYNTAX  Integer32
    MAX-ACCESS  read-only
    STATUS  current
    DESCRIPTION
        "Error counter SP base value."
    ::= { errorCountersSpTableEntry 4 }


eventCountersSpTable OBJECT-TYPE
    SYNTAX  SEQUENCE OF EventCountersSpTableEntry
    MAX-ACCESS  not-accessible
    STATUS  current
    DESCRIPTION
        "Event counters for SP - statistics table."
    ::= { countersStats 4 }

eventCountersSpTableEntry OBJECT-TYPE
    SYNTAX  EventCountersSpTableEntry
    MAX-ACCESS  not-accessible
    STATUS  current
    DESCRIPTION
        "A row in event counters table for SP."
    INDEX   { eventCountersSpIndex,  eventCountersSpCntrIndex}
    ::= { eventCountersSpTable 1 }

EventCountersSpTableEntry ::= SEQUENCE {
    eventCountersSpIndex      	Integer32,
    eventCountersSpCntrIndex	Integer32,
    eventCountersSpStrName	DisplayString,
    eventCountersSpBaseVal	Integer32
    }

eventCountersSpIndex OBJECT-TYPE
    SYNTAX  Integer32
    MAX-ACCESS  read-only
    STATUS  current
    DESCRIPTION
        "Event counter SP index."
    ::= { eventCountersSpTableEntry 1 }

eventCountersSpCntrIndex OBJECT-TYPE
    SYNTAX  Integer32
    MAX-ACCESS  read-only
    STATUS  current
    DESCRIPTION
        "Event counter index."
    ::= { eventCountersSpTableEntry 2 }

eventCountersSpStrName OBJECT-TYPE
    SYNTAX  DisplayString (SIZE(0..60))
    MAX-ACCESS  read-only
    STATUS  current
    DESCRIPTION
        "The SP event counter string name."
    ::= { eventCountersSpTableEntry 3 }


eventCountersSpBaseVal OBJECT-TYPE
    SYNTAX  Integer32
    MAX-ACCESS  read-only
    STATUS  current
    DESCRIPTION
        "Event counter SP base value."
    ::= { eventCountersSpTableEntry 4 }


-- Counters Statisitics END


-- SP Statistics

-- SP CPU utilization table

spStatsCpuUtilTable OBJECT-TYPE
    SYNTAX  SEQUENCE OF SpStatsCpuUtilTableEntry
    MAX-ACCESS  not-accessible
    STATUS  current
    DESCRIPTION
        "The table of SP CPU utilization.
        Note: This MIB table is not supported for VX instance of Virtualization."
    ::= { spStats 1 }

spStatsCpuUtilTableEntry OBJECT-TYPE
    SYNTAX  SpStatsCpuUtilTableEntry
    MAX-ACCESS  not-accessible
    STATUS  current
    DESCRIPTION
        "A row in the SP CPU utilization table."
    INDEX   { spStatsCpuUtilSpIndex }
    ::= { spStatsCpuUtilTable 1 }

SpStatsCpuUtilTableEntry ::= SEQUENCE {
    spStatsCpuUtilSpIndex    Integer32,
    spStatsCpuUtil1Second    Integer32,
    spStatsCpuUtil4Seconds   Integer32,
    spStatsCpuUtil64Seconds  Integer32
    }

spStatsCpuUtilSpIndex OBJECT-TYPE
    SYNTAX  Integer32
    MAX-ACCESS  read-only
    STATUS  current
    DESCRIPTION
        "The SP index."
    ::= { spStatsCpuUtilTableEntry 1 }

spStatsCpuUtil1Second OBJECT-TYPE
    SYNTAX  Integer32
    MAX-ACCESS  read-only
    STATUS  current
    DESCRIPTION
        "The utilization of this SP over 1 second. It shows the percentage."
    ::= { spStatsCpuUtilTableEntry 2 }

spStatsCpuUtil4Seconds OBJECT-TYPE
    SYNTAX  Integer32
    MAX-ACCESS  read-only
    STATUS  current
    DESCRIPTION
        "The utilization of this SP over 4 seconds. It shows the percentage."
    ::= { spStatsCpuUtilTableEntry 3 }

spStatsCpuUtil64Seconds OBJECT-TYPE
    SYNTAX  Integer32
    MAX-ACCESS  read-only
    STATUS  current
    DESCRIPTION
        "The utilization of this SP over 64 seconds. It shows the percentage."
    ::= { spStatsCpuUtilTableEntry 4 }

-- SP Maintenance Statistics

spMaintStatsTable OBJECT-TYPE
    SYNTAX  SEQUENCE OF SpMaintStatsTableEntry
    MAX-ACCESS  not-accessible
    STATUS  current
    DESCRIPTION
        "The table of SP maintenance statistics.
        Note: This MIB table is not supported for VX instance of Virtualization."
    ::= { spStats 2 }

spMaintStatsTableEntry OBJECT-TYPE
    SYNTAX  SpMaintStatsTableEntry
    MAX-ACCESS  not-accessible
    STATUS  current
    DESCRIPTION
        "A row in the SP maintenance statistics table."
    INDEX   { spMaintStatsSpIndex }
    ::= { spMaintStatsTable 1 }

SpMaintStatsTableEntry ::= SEQUENCE {
    spMaintStatsSpIndex           Integer32,
    spMaintStatsResolveErrNoddw   Counter32,
    spMaintStatsLearnErrNoddw     Counter32,
    spMaintStatsAgeMPNoddw        Counter32,
    spMaintStatsDeleteMiss        Counter32,
    spMaintStatsRecvLetErrorsMP   Counter32,
    spMaintStatsRecvLetErrorsSP1  Counter32,
    spMaintStatsRecvLetErrorsSP2  Counter32,
    spMaintStatsRecvLetErrorsSP3  Counter32,
    spMaintStatsRecvLetErrorsSP4  Counter32,
    spMaintStatsSendLetFailsMP    Counter32,
    spMaintStatsSendLetFailsSP1   Counter32,
    spMaintStatsSendLetFailsSP2   Counter32,
    spMaintStatsSendLetFailsSP3   Counter32,
    spMaintStatsSendLetFailsSP4   Counter32,
    spMaintStatsRecvLetSuccessMP  Counter32,
    spMaintStatsRecvLetSuccessSP1 Counter32,
    spMaintStatsRecvLetSuccessSP2 Counter32,
    spMaintStatsRecvLetSuccessSP3 Counter32,
    spMaintStatsRecvLetSuccessSP4 Counter32,
    spMaintStatsSendLetSuccessMP  Counter32,
    spMaintStatsSendLetSuccessSP1 Counter32,
    spMaintStatsSendLetSuccessSP2 Counter32,
    spMaintStatsSendLetSuccessSP3 Counter32,
    spMaintStatsSendLetSuccessSP4 Counter32,
    spMaintStatsRecvLetErrorsSP5  Counter32,
    spMaintStatsRecvLetErrorsSP6  Counter32,
    spMaintStatsRecvLetErrorsSP7  Counter32,
    spMaintStatsSendLetFailsSP5   Counter32,
    spMaintStatsSendLetFailsSP6   Counter32,
    spMaintStatsSendLetFailsSP7   Counter32,
    spMaintStatsRecvLetSuccessSP5 Counter32,
    spMaintStatsRecvLetSuccessSP6 Counter32,
    spMaintStatsRecvLetSuccessSP7 Counter32,
    spMaintStatsSendLetSuccessSP5 Counter32,
    spMaintStatsSendLetSuccessSP6 Counter32,
    spMaintStatsSendLetSuccessSP7 Counter32,
    spMaintStatsRateLimitArpDrops Counter32,
    spMaintStatsRateLimitIcmpDrops Counter32,
    spMaintStatsRateLimitTcpDrops Counter32,
    spMaintStatsRateLimitUdpDrops Counter32,
    spMaintStatsPfdbFreeEmpty     Counter32,
    spMaintStatsClear             INTEGER
    }

spMaintStatsSpIndex OBJECT-TYPE
    SYNTAX  Integer32
    MAX-ACCESS  read-only
    STATUS  current
    DESCRIPTION
        "The SP index."
    ::= { spMaintStatsTableEntry 1 }

spMaintStatsPfdbFreeEmpty OBJECT-TYPE
    SYNTAX  Counter32
    MAX-ACCESS  read-only
    STATUS  current
    DESCRIPTION
        "The number of times the attempts were made to add entries to an
         already full FDB."
    ::= { spMaintStatsTableEntry 2 }

spMaintStatsResolveErrNoddw OBJECT-TYPE
    SYNTAX  Counter32
    MAX-ACCESS  read-only
    STATUS  current
    DESCRIPTION
        "The number of times MAC address resolution failed because there were
         no DMA descriptors."
    ::= { spMaintStatsTableEntry 3 }

spMaintStatsLearnErrNoddw OBJECT-TYPE
    SYNTAX  Counter32
    MAX-ACCESS  read-only
    STATUS  current
    DESCRIPTION
        "The number of times MAC address learn failed because there were
         no DMA descriptors."
    ::= { spMaintStatsTableEntry 4 }

spMaintStatsAgeMPNoddw OBJECT-TYPE
    SYNTAX  Counter32
    MAX-ACCESS  read-only
    STATUS  current
    DESCRIPTION
        "The number of times MAC address aging failed because there were
         no DMA descriptors."
    ::= { spMaintStatsTableEntry 5 }

spMaintStatsDeleteMiss OBJECT-TYPE
    SYNTAX  Counter32
    MAX-ACCESS  read-only
    STATUS  current
    DESCRIPTION
        "The number of times MAC address could not be found."
    ::= { spMaintStatsTableEntry 6 }

spMaintStatsRecvLetErrorsMP OBJECT-TYPE
    SYNTAX  Counter32
    MAX-ACCESS  read-only
    STATUS  current
    DESCRIPTION
        "The number of receive letter errors from MP."
    ::= { spMaintStatsTableEntry 7 }

spMaintStatsRecvLetErrorsSP1 OBJECT-TYPE
    SYNTAX  Counter32
    MAX-ACCESS  read-only
    STATUS  current
    DESCRIPTION
        "The number of receive letter errors from SP1.
         If the current table index is the same as the SP number then a value
         of 0 is returned."
    ::= { spMaintStatsTableEntry 8 }

spMaintStatsRecvLetErrorsSP2 OBJECT-TYPE
    SYNTAX  Counter32
    MAX-ACCESS  read-only
    STATUS  current
    DESCRIPTION
        "The number of receive letter errors from SP2.
         If the current table index is the same as the SP number then a value
         of 0 is returned.
         Note: This MIB is not supported on platforms with less than 2 SPs."
    ::= { spMaintStatsTableEntry 9 }

spMaintStatsRecvLetErrorsSP3 OBJECT-TYPE
    SYNTAX  Counter32
    MAX-ACCESS  read-only
    STATUS  current
    DESCRIPTION
        "The number of receive letter errors from SP3.
         If the current table index is the same as the SP number then a value
         of 0 is returned.
         Note: This MIB is not supported on platforms with less than 3 SPs."
    ::= { spMaintStatsTableEntry 10 }

spMaintStatsRecvLetErrorsSP4 OBJECT-TYPE
    SYNTAX  Counter32
    MAX-ACCESS  read-only
    STATUS  current
    DESCRIPTION
        "The number of receive letter errors from SP4.
         If the current table index is the same as the SP number then a value
         of 0 is returned.
         Note: This MIB is not supported on platforms with less than 4 SPs."
    ::= { spMaintStatsTableEntry 11 }

spMaintStatsSendLetFailsMP OBJECT-TYPE
    SYNTAX  Counter32
    MAX-ACCESS  read-only
    STATUS  current
    DESCRIPTION
        "The number of send letter failures to MP."
    ::= { spMaintStatsTableEntry 12 }

spMaintStatsSendLetFailsSP1 OBJECT-TYPE
    SYNTAX  Counter32
    MAX-ACCESS  read-only
    STATUS  current
    DESCRIPTION
        "The number of send letter failures to SP1.
         If the current table index is the same as the SP number then a value
         of 0 is returned."
    ::= { spMaintStatsTableEntry 13 }

spMaintStatsSendLetFailsSP2 OBJECT-TYPE
    SYNTAX  Counter32
    MAX-ACCESS  read-only
    STATUS  current
    DESCRIPTION
        "The number of send letter failures to SP2.
         If the current table index is the same as the SP number then a value
         of 0 is returned.
         Note: This MIB is not supported on platforms with less than 2 SPs."
    ::= { spMaintStatsTableEntry 14 }

spMaintStatsSendLetFailsSP3 OBJECT-TYPE
    SYNTAX  Counter32
    MAX-ACCESS  read-only
    STATUS  current
    DESCRIPTION
        "The number of send letter failures to SP3.
         If the current table index is the same as the SP number then a value
         of 0 is returned.
         Note: This MIB is not supported on platforms with less than 3 SPs."
    ::= { spMaintStatsTableEntry 15 }

spMaintStatsSendLetFailsSP4 OBJECT-TYPE
    SYNTAX  Counter32
    MAX-ACCESS  read-only
    STATUS  current
    DESCRIPTION
        "The number of send letter failures to SP4.
         If the current table index is the same as the SP number then a value
         of 0 is returned.
         Note: This MIB is not supported on platforms with less than 4 SPs."
    ::= { spMaintStatsTableEntry 16 }

spMaintStatsRecvLetSuccessMP OBJECT-TYPE
    SYNTAX  Counter32
    MAX-ACCESS  read-only
    STATUS  current
    DESCRIPTION
        "The number of receive letter success from MP."
    ::= { spMaintStatsTableEntry 17 }

spMaintStatsRecvLetSuccessSP1 OBJECT-TYPE
    SYNTAX  Counter32
    MAX-ACCESS  read-only
    STATUS  current
    DESCRIPTION
        "The number of receive letter success from SP1.
         If the current table index is the same as the SP number then a value
         of 0 is returned."
    ::= { spMaintStatsTableEntry 18 }

spMaintStatsRecvLetSuccessSP2 OBJECT-TYPE
    SYNTAX  Counter32
    MAX-ACCESS  read-only
    STATUS  current
    DESCRIPTION
        "The number of receive letter success from SP2.
         If the current table index is the same as the SP number then a value
         of 0 is returned.
         Note: This MIB is not supported on platforms with less than 2 SPs."
    ::= { spMaintStatsTableEntry 19 }

spMaintStatsRecvLetSuccessSP3 OBJECT-TYPE
    SYNTAX  Counter32
    MAX-ACCESS  read-only
    STATUS  current
    DESCRIPTION
        "The number of receive letter success from SP3.
         If the current table index is the same as the SP number then a value
         of 0 is returned.
         Note: This MIB is not supported on platforms with less than 3 SPs."
    ::= { spMaintStatsTableEntry 20 }

spMaintStatsRecvLetSuccessSP4 OBJECT-TYPE
    SYNTAX  Counter32
    MAX-ACCESS  read-only
    STATUS  current
    DESCRIPTION
        "The number of receive letter success from SP4.
         If the current table index is the same as the SP number then a value
         of 0 is returned.
         Note: This MIB is not supported on platforms with less than 4 SPs."
    ::= { spMaintStatsTableEntry 21 }

spMaintStatsSendLetSuccessMP OBJECT-TYPE
    SYNTAX  Counter32
    MAX-ACCESS  read-only
    STATUS  current
    DESCRIPTION
        "The number of send letter success to MP."
    ::= { spMaintStatsTableEntry 22 }

spMaintStatsSendLetSuccessSP1 OBJECT-TYPE
    SYNTAX  Counter32
    MAX-ACCESS  read-only
    STATUS  current
    DESCRIPTION
        "The number of send letter success to SP1.
         If the current table index is the same as the SP number then a value
         of 0 is returned."
    ::= { spMaintStatsTableEntry 23 }

spMaintStatsSendLetSuccessSP2 OBJECT-TYPE
    SYNTAX  Counter32
    MAX-ACCESS  read-only
    STATUS  current
    DESCRIPTION
        "The number of send letter success to SP2.
         If the current table index is the same as the SP number then a value
         of 0 is returned.
         Note: This MIB is not supported on platforms with less than 2 SPs."
    ::= { spMaintStatsTableEntry 24 }

spMaintStatsSendLetSuccessSP3 OBJECT-TYPE
    SYNTAX  Counter32
    MAX-ACCESS  read-only
    STATUS  current
    DESCRIPTION
        "The number of send letter success to SP3.
         If the current table index is the same as the SP number then a value
         of 0 is returned.
         Note: This MIB is not supported on platforms with less than 3 SPs."
    ::= { spMaintStatsTableEntry 25 }

spMaintStatsSendLetSuccessSP4 OBJECT-TYPE
    SYNTAX  Counter32
    MAX-ACCESS  read-only
    STATUS  current
    DESCRIPTION
        "The number of send letter success to SP4.
         If the current table index is the same as the SP number then a value
         of 0 is returned.
         Note: This MIB is not supported on platforms with less than 4 SPs."
    ::= { spMaintStatsTableEntry 26 }

spMaintStatsRateLimitArpDrops OBJECT-TYPE
    SYNTAX  Counter32
    MAX-ACCESS  read-only
    STATUS  current
    DESCRIPTION
        "The total number of ARP packets dropped due to rate limiting."
    ::= { spMaintStatsTableEntry 27 }

spMaintStatsRateLimitIcmpDrops OBJECT-TYPE
    SYNTAX  Counter32
    MAX-ACCESS  read-only
    STATUS  current
    DESCRIPTION
        "The total number of ICMP packets are dropped due to rate limiting."
    ::= { spMaintStatsTableEntry 28 }

spMaintStatsRateLimitTcpDrops OBJECT-TYPE
    SYNTAX  Counter32
    MAX-ACCESS  read-only
    STATUS  current
    DESCRIPTION
        "The total number of TCP packets are dropped due to rate limiting."
    ::= { spMaintStatsTableEntry 29 }

spMaintStatsRateLimitUdpDrops OBJECT-TYPE
    SYNTAX  Counter32
    MAX-ACCESS  read-only
    STATUS  current
    DESCRIPTION
        "The total number of UDP packets are dropped due to rate limiting."
    ::= { spMaintStatsTableEntry 30 }

spMaintStatsRecvLetErrorsSP5 OBJECT-TYPE
    SYNTAX  Counter32
    MAX-ACCESS  read-only
    STATUS  current
    DESCRIPTION
        "The number of receive letter errors from SP5.
         If the current table index is the same as the SP number then a value
         of 0 is returned.
         Note: This MIB is not supported on platforms with less than 5 SPs."
    ::= { spMaintStatsTableEntry 31 }

spMaintStatsRecvLetErrorsSP6 OBJECT-TYPE
    SYNTAX  Counter32
    MAX-ACCESS  read-only
    STATUS  current
    DESCRIPTION
        "The number of receive letter errors from SP6.
         If the current table index is the same as the SP number then a value
         of 0 is returned.
         Note: This MIB is not supported on platforms with less than 6 SPs."
    ::= { spMaintStatsTableEntry 32 }

spMaintStatsRecvLetErrorsSP7 OBJECT-TYPE
    SYNTAX  Counter32
    MAX-ACCESS  read-only
    STATUS  current
    DESCRIPTION
        "The number of receive letter errors from SP7.
         If the current table index is the same as the SP number then a value
         of 0 is returned.
         Note: This MIB is not supported on platforms with less than 7 SPs."
    ::= { spMaintStatsTableEntry 33 }

spMaintStatsSendLetFailsSP5 OBJECT-TYPE
    SYNTAX  Counter32
    MAX-ACCESS  read-only
    STATUS  current
    DESCRIPTION
        "The number of send letter failures to SP5.
         If the current table index is the same as the SP number then a value
         of 0 is returned.
         Note: This MIB is not supported on platforms with less than 5 SPs."
    ::= { spMaintStatsTableEntry 34 }

spMaintStatsSendLetFailsSP6 OBJECT-TYPE
    SYNTAX  Counter32
    MAX-ACCESS  read-only
    STATUS  current
    DESCRIPTION
        "The number of send letter failures to SP6.
         If the current table index is the same as the SP number then a value
         of 0 is returned.
         Note: This MIB is not supported on platforms with less than 6 SPs."
    ::= { spMaintStatsTableEntry 35 }

spMaintStatsSendLetFailsSP7 OBJECT-TYPE
    SYNTAX  Counter32
    MAX-ACCESS  read-only
    STATUS  current
    DESCRIPTION
        "The number of send letter failures to SP7.
         If the current table index is the same as the SP number then a value
         of 0 is returned.
         Note: This MIB is not supported on platforms with less than 7 SPs."
    ::= { spMaintStatsTableEntry 36 }

spMaintStatsRecvLetSuccessSP5 OBJECT-TYPE
    SYNTAX  Counter32
    MAX-ACCESS  read-only
    STATUS  current
    DESCRIPTION
        "The number of receive letter success from SP5.
         If the current table index is the same as the SP number then a value
         of 0 is returned.
         Note: This MIB is not supported on platforms with less than 5 SPs."
    ::= { spMaintStatsTableEntry 37 }

spMaintStatsRecvLetSuccessSP6 OBJECT-TYPE
    SYNTAX  Counter32
    MAX-ACCESS  read-only
    STATUS  current
    DESCRIPTION
        "The number of receive letter success from SP6.
         If the current table index is the same as the SP number then a value
         of 0 is returned.
         Note: This MIB is not supported on platforms less than 6 SPs."
    ::= { spMaintStatsTableEntry 38 }

spMaintStatsRecvLetSuccessSP7 OBJECT-TYPE
    SYNTAX  Counter32
    MAX-ACCESS  read-only
    STATUS  current
    DESCRIPTION
        "The number of receive letter success from SP7.
         If the current table index is the same as the SP number then a value
         of 0 is returned.
         Note: This MIB is not supported on platforms with less than 7 SPs."
    ::= { spMaintStatsTableEntry 39 }

spMaintStatsSendLetSuccessSP5 OBJECT-TYPE
    SYNTAX  Counter32
    MAX-ACCESS  read-only
    STATUS  current
    DESCRIPTION
        "The number of send letter success to SP5.
         If the current table index is the same as the SP number then a value
         of 0 is returned.
         Note: This MIB is not supported on platforms with less than 5 SPs."
    ::= { spMaintStatsTableEntry 40 }

spMaintStatsSendLetSuccessSP6 OBJECT-TYPE
    SYNTAX  Counter32
    MAX-ACCESS  read-only
    STATUS  current
    DESCRIPTION
        "The number of send letter success to SP6.
         If the current table index is the same as the SP number then a value
         of 0 is returned.
         Note: This MIB is not supported on platforms with less than 6 SPs."
    ::= { spMaintStatsTableEntry 41 }

spMaintStatsSendLetSuccessSP7 OBJECT-TYPE
    SYNTAX  Counter32
    MAX-ACCESS  read-only
    STATUS  current
    DESCRIPTION
        "The number of send letter success to SP7.
         If the current table index is the same as the SP number then a value
         of 0 is returned.
         Note: This MIB is not supported on platforms with less than 7 SPs."
    ::= { spMaintStatsTableEntry 42 }

spMaintStatsClear OBJECT-TYPE
    SYNTAX INTEGER {
         ok(1),
         clear(2)
         }
    MAX-ACCESS read-write
    STATUS current
    DESCRIPTION
        "This is an action object to clear maintenance statistics
         on the particular SP.
         ok(1) is returned when read."
    ::= { spMaintStatsTableEntry 43 }


spMemUsageStatsTable OBJECT-TYPE
    SYNTAX  SEQUENCE OF SpMemUsageStatsTableEntry
    MAX-ACCESS  not-accessible
    STATUS  current
    DESCRIPTION
        "The table of SP memory statistics.
        Note: This MIB table is not supported for VX instance of Virtualization."
    ::= { spStats 4 }

spMemUsageStatsTableEntry OBJECT-TYPE
    SYNTAX  SpMemUsageStatsTableEntry
    MAX-ACCESS  not-accessible
    STATUS  current
    DESCRIPTION
        "A row in the SP memory statistics table."
    INDEX   { spMemUsageStatsIndex }
    ::= { spMemUsageStatsTable 1 }

SpMemUsageStatsTableEntry ::= SEQUENCE {
    spMemUsageStatsIndex             Integer32,
    spMemUsageStatsCurrentMemory     Integer32,
    spMemUsageStatsHiWaterMark       Integer32,
    spMemUsageStatsMaxMemory       Integer32
    }

spMemUsageStatsIndex OBJECT-TYPE
    SYNTAX  Integer32
    MAX-ACCESS  read-only
    STATUS  obsolete
    DESCRIPTION
        "The SP index."
    ::= { spMemUsageStatsTableEntry 1 }

spMemUsageStatsCurrentMemory OBJECT-TYPE
    SYNTAX  Integer32
    MAX-ACCESS  read-only
    STATUS  obsolete
    DESCRIPTION
        "The current memory usage of SP in KiloBytes."
    ::= { spMemUsageStatsTableEntry 2 }

spMemUsageStatsHiWaterMark OBJECT-TYPE
    SYNTAX  Integer32
    MAX-ACCESS  read-only
    STATUS  obsolete
    DESCRIPTION
        "The high watermark of memory usage in KiloBytes."
    ::= { spMemUsageStatsTableEntry 3 }

spMemUsageStatsMaxMemory   OBJECT-TYPE
    SYNTAX  Integer32
    MAX-ACCESS  read-only
    STATUS  obsolete
    DESCRIPTION
        "Allowed Max in KiloBytes."
    ::= { spMemUsageStatsTableEntry 4 }

-- SP mem usage start

spMemUseStatsTable OBJECT-TYPE
    SYNTAX  SEQUENCE OF SpMemUseStatsTableEntry
    MAX-ACCESS  not-accessible
    STATUS  current
    DESCRIPTION
        "The table of SP memory statistics.
        Note: This MIB table is not supported for VX instance of Virtualization."
    ::= { spStats 5 }

spMemUseStatsTableEntry OBJECT-TYPE
    SYNTAX  SpMemUseStatsTableEntry
    MAX-ACCESS  not-accessible
    STATUS  current
    DESCRIPTION
        "A row in the SP memory statistics table."
    INDEX   { spMemUseStatsIndex }
    ::= { spMemUseStatsTable 1 }

SpMemUseStatsTableEntry ::= SEQUENCE {
	spMemUseStatsIndex             	Integer32,
	spMemUseStatsInitProcessSize 	Counter32,
	spMemUseStatsInitMaxProcessSize Counter32,
	spMemUseStatsInitSizeTo1Margin  Counter32,
	spMemUseStatsInitSizeTo2Margin  Integer32,
	spMemUseStatsAllowMemIncrease   Counter32,
	spMemUseStatsCurProcSize     	Counter32,
	spMemUseStatsCurProcShareSize  	Counter32,
	spMemUseStatsCurProcResidentSize  Counter32,
	spMemUseStatsCurFrontEndSessions  Counter32,
	spMemUseStatsAvgFrontEndSessions  Counter32,
	spMemUseStatsPeakUsageFrom1stMargin  	Counter32,
	spMemUseStatsMemPressStat		Counter32,
	spMemUseStatsMemUseFrom1stMargin	Counter32,
	spMemUseStatsCurProcCacheRelativeSize 	Counter32,
	spMemUseStatsCurProcDynCertRelativeSize Counter32,
	spMemUseStatsMemPressActiveTime		Counter32,
	spMemUseStatsMaxAllowConnections	Counter32,
	spMemUseStatsProcOver1stMargin		INTEGER,
	spMemUseStatsProcOver2ndMargin		INTEGER,
	spMemUseStatsMemTo2ndMargin		Integer32,
        spMemUseStatsCurExtraProcessRelativeSize Counter32,
        spMemUseStatsCurQatSlabsRelativeSize 	Counter32
    }

spMemUseStatsIndex OBJECT-TYPE
    SYNTAX  Integer32
    MAX-ACCESS  read-only
    STATUS  current
    DESCRIPTION
        "The SP index."
    ::= { spMemUseStatsTableEntry 1 }

-- Memory stats per SP

spMemUseStatsInitProcessSize   OBJECT-TYPE
    SYNTAX  Counter32
    MAX-ACCESS  read-only
    STATUS  current
    DESCRIPTION
        "Initial process size (RES-SHR)(Mb)."
    ::= { spMemUseStatsTableEntry 2 }

spMemUseStatsInitMaxProcessSize   OBJECT-TYPE
    SYNTAX  Counter32
    MAX-ACCESS  read-only
    STATUS  current
    DESCRIPTION
        "Initial max allowed process size(Mb)."
    ::= { spMemUseStatsTableEntry 3 }

spMemUseStatsInitSizeTo1Margin   OBJECT-TYPE
    SYNTAX  Counter32
    MAX-ACCESS  read-only
    STATUS  current
    DESCRIPTION
        "Initial size to 1st watermark(Mb)."
    ::= { spMemUseStatsTableEntry 4 }

spMemUseStatsInitSizeTo2Margin   OBJECT-TYPE
    SYNTAX  Integer32
    MAX-ACCESS  read-only
    STATUS  current
    DESCRIPTION
        "Initial size to 2nd watermark(Mb)."
    ::= { spMemUseStatsTableEntry 5 }

spMemUseStatsAllowMemIncrease   OBJECT-TYPE
    SYNTAX  Counter32
    MAX-ACCESS  read-only
    STATUS  current
    DESCRIPTION
        "Allowed memory increase before drop(Mb)."
    ::= { spMemUseStatsTableEntry 6 }

spMemUseStatsCurProcSize   OBJECT-TYPE
    SYNTAX  Counter32
    MAX-ACCESS  read-only
    STATUS  current
    DESCRIPTION
        "Current process size (RES-SHR+CACHE)(Mb)."
    ::= { spMemUseStatsTableEntry 7 }

spMemUseStatsCurProcShareSize   OBJECT-TYPE
    SYNTAX  Counter32
    MAX-ACCESS  read-only
    STATUS  current
    DESCRIPTION
        "Current process shared size (SHR)(Mb)."
    ::= { spMemUseStatsTableEntry 8 }

spMemUseStatsCurProcResidentSize   OBJECT-TYPE
    SYNTAX  Counter32
    MAX-ACCESS  read-only
    STATUS  current
    DESCRIPTION
        "Current process resident size (RES)(Mb)."
    ::= { spMemUseStatsTableEntry 9 }

spMemUseStatsCurFrontEndSessions   OBJECT-TYPE
    SYNTAX  Counter32
    MAX-ACCESS  read-only
    STATUS  current
    DESCRIPTION
        "Current front-end sessions."
    ::= { spMemUseStatsTableEntry 10 }

spMemUseStatsAvgFrontEndSessions   OBJECT-TYPE
    SYNTAX  Counter32
    MAX-ACCESS  read-only
    STATUS  current
    DESCRIPTION
        "Average front-end session size(Kb)."
    ::= { spMemUseStatsTableEntry 11 }

spMemUseStatsPeakUsageFrom1stMargin   OBJECT-TYPE
    SYNTAX  Counter32
    MAX-ACCESS  read-only
    STATUS  current
    DESCRIPTION
        "Peak memory used from 1st watermark(%)."
    ::= { spMemUseStatsTableEntry 12 }

spMemUseStatsMemPressStat   OBJECT-TYPE
    SYNTAX  Counter32
    MAX-ACCESS  read-only
    STATUS  current
    DESCRIPTION
        "Memory pressure status (On/Off)."
    ::= { spMemUseStatsTableEntry 13 }

spMemUseStatsMemUseFrom1stMargin   OBJECT-TYPE
    SYNTAX  Counter32
    MAX-ACCESS  read-only
    STATUS  current
    DESCRIPTION
        "Memory used from 1st watermark (%)."
    ::= { spMemUseStatsTableEntry 14 }

spMemUseStatsCurProcCacheRelativeSize   OBJECT-TYPE
    SYNTAX  Counter32
    MAX-ACCESS  read-only
    STATUS  current
    DESCRIPTION
        "Current process cache relative size (Mb)."
    ::= { spMemUseStatsTableEntry 15 }

spMemUseStatsCurProcDynCertRelativeSize   OBJECT-TYPE
    SYNTAX  Counter32
    MAX-ACCESS  read-only
    STATUS  current
    DESCRIPTION
        "Current process dynamic certs relative size (Mb)."
    ::= { spMemUseStatsTableEntry 16 }

spMemUseStatsMemPressActiveTime   OBJECT-TYPE
    SYNTAX  Counter32
    MAX-ACCESS  read-only
    STATUS  current
    DESCRIPTION
        "Memory pressure active time(sec)."
    ::= { spMemUseStatsTableEntry 17 }

spMemUseStatsMaxAllowConnections   OBJECT-TYPE
    SYNTAX  Counter32
    MAX-ACCESS  read-only
    STATUS  current
    DESCRIPTION
        "Max allowed front-end sessions."
    ::= { spMemUseStatsTableEntry 18 }

spMemUseStatsProcOver1stMargin  OBJECT-TYPE
	SYNTAX INTEGER {
		over(1),
		below(0)
		}
    MAX-ACCESS  read-only
    STATUS  current
    DESCRIPTION
        "Process over the 1st watermark."
    ::= { spMemUseStatsTableEntry 19 }

spMemUseStatsProcOver2ndMargin  OBJECT-TYPE
	SYNTAX INTEGER {
		over(1),
		below(0)
		}
    MAX-ACCESS  read-only
    STATUS  current
    DESCRIPTION
        "Process over the 2nd watermark."
    ::= { spMemUseStatsTableEntry 20 }

spMemUseStatsMemTo2ndMargin   OBJECT-TYPE
    SYNTAX  Integer32
    MAX-ACCESS  read-only
    STATUS  current
    DESCRIPTION
        "Mem below \ over the 2nd watermark - minus represent memory crossed 2nd watermark (Mb)."
    ::= { spMemUseStatsTableEntry 21 }

spMemUseStatsCurExtraProcessRelativeSize  OBJECT-TYPE
    SYNTAX  Counter32
    MAX-ACCESS  read-only
    STATUS  current
    DESCRIPTION
        "Current process extra process relative size (Mb)."
    ::= { spMemUseStatsTableEntry 22 }

spMemUseStatsCurQatSlabsRelativeSize   OBJECT-TYPE
    SYNTAX  Counter32
    MAX-ACCESS  read-only
    STATUS  current
    DESCRIPTION
        "Current process QAT slabs relative size (Mb)."
    ::= { spMemUseStatsTableEntry 23 }

-- SP mem usage end



-- Management Port Statistics

mgmtStatsRxpackets OBJECT-TYPE
    SYNTAX  Counter32
    MAX-ACCESS  read-only
    STATUS  current
    DESCRIPTION
        "Total number of packet allocations from the packet buffer pool by
         the TCP/IP protocol stack."
    ::= { mgmtStats 1 }

mgmtStatsRxErrors OBJECT-TYPE
    SYNTAX  Counter32
    MAX-ACCESS  read-only
    STATUS  current
    DESCRIPTION
	    "The number of inbound packets that contained
	     errors preventing them from being deliverable to a
	     higher-layer protocol."
    ::= { mgmtStats 2 }

mgmtStatsRxDropped OBJECT-TYPE
    SYNTAX  Counter32
    MAX-ACCESS  read-only
    STATUS  current
    DESCRIPTION
	    "The number of inbound packets that were dropped."
    ::= { mgmtStats 3 }

mgmtStatsRxOverruns OBJECT-TYPE
    SYNTAX  Counter32
    MAX-ACCESS  read-only
    STATUS  current
    DESCRIPTION
	    "The number of data overruns over this link."
    ::= { mgmtStats 4 }

mgmtStatsRxFrame OBJECT-TYPE
    SYNTAX  Counter32
    MAX-ACCESS  read-only
    STATUS  current
    DESCRIPTION
	    "The number of frames received on this link."
    ::= { mgmtStats 5 }

mgmtStatsTxpackets OBJECT-TYPE
    SYNTAX  Counter32
    MAX-ACCESS  read-only
    STATUS  current
    DESCRIPTION
        "Total number of packet allocations from the packet buffer pool by
         the TCP/IP protocol stack."
    ::= { mgmtStats 6 }

mgmtStatsTxErrors OBJECT-TYPE
    SYNTAX  Counter32
    MAX-ACCESS  read-only
    STATUS  current
    DESCRIPTION
	    "The number of outbound packets that contained
	     errors preventing them from being deliverable to a
	     higher-layer protocol."
    ::= { mgmtStats 7 }

mgmtStatsTxDropped OBJECT-TYPE
    SYNTAX  Counter32
    MAX-ACCESS  read-only
    STATUS  current
    DESCRIPTION
	    "The number of outbound packets that were dropped."
    ::= { mgmtStats 8 }

mgmtStatsTxOverruns OBJECT-TYPE
    SYNTAX  Counter32
    MAX-ACCESS  read-only
    STATUS  current
    DESCRIPTION
	    "The number of data overruns over this link."
    ::= { mgmtStats 9 }

mgmtStatsTxCarrier OBJECT-TYPE
    SYNTAX  Counter32
    MAX-ACCESS  read-only
    STATUS  current
    DESCRIPTION
 	"The number of times that the carrier sense
         condition was lost or never asserted when
         attempting to transmit a frame on a this
         interface."
    ::= { mgmtStats 10 }

mgmtStatsTxCollisions OBJECT-TYPE
    SYNTAX  Counter32
    MAX-ACCESS  read-only
    STATUS  current
    DESCRIPTION
	    "The number of collisions on this outbound segment."
    ::= { mgmtStats 11 }

mgmtStatsTxQueueLen OBJECT-TYPE
    SYNTAX  Counter32
    MAX-ACCESS  read-only
    STATUS  current
    DESCRIPTION
	    "The length of the TCP transmit queue."
    ::= { mgmtStats 12 }

mgmtStatsRxBytes OBJECT-TYPE
    SYNTAX  Counter32
    MAX-ACCESS  read-only
    STATUS  current
    DESCRIPTION
            "The total number of bytes received."
    ::= { mgmtStats 13 }

mgmtStatsRxMulticast OBJECT-TYPE
    SYNTAX  Counter32
    MAX-ACCESS  read-only
    STATUS  current
    DESCRIPTION
            "The total number of multicast packets received."
    ::= { mgmtStats 14 }

mgmtStatsTxBytes OBJECT-TYPE
    SYNTAX  Counter32
    MAX-ACCESS  read-only
    STATUS  current
    DESCRIPTION
            "The total number of bytes transmitted."
    ::= { mgmtStats 15 }

-- IP ACL Bogon Info
ipAclBogonInfo OBJECT IDENTIFIER ::= { securityInfo 1 }

ipAclBogonInfoTableMaxSize OBJECT-TYPE
    SYNTAX  Integer32
    MAX-ACCESS  read-only
    STATUS  current
    DESCRIPTION
        "The number of bogon IPs in IP ACL table.
        Note: This MIB is not supported for VX instance of Virtualization."
    ::= { ipAclBogonInfo 1 }

ipAclBogonInfoTable OBJECT-TYPE
    SYNTAX  SEQUENCE OF IpAclBogonInfoTableEntry
    MAX-ACCESS  not-accessible
    STATUS  current
    DESCRIPTION
        "The table of bogons.
        Note: This MIB table is not supported for VX instance of Virtualization."
    ::= { ipAclBogonInfo 2 }

ipAclBogonInfoTableEntry OBJECT-TYPE
    SYNTAX  IpAclBogonInfoTableEntry
    MAX-ACCESS  not-accessible
    STATUS  current
    DESCRIPTION
        "An entry in the bogon IP ACL table."
    INDEX   { ipAclBogonInfoIndex }
    ::= { ipAclBogonInfoTable 1 }

IpAclBogonInfoTableEntry ::= SEQUENCE {
    ipAclBogonInfoIndex      Integer32,
    ipAclBogonInfoIp         IpAddress,
    ipAclBogonInfoMask       IpAddress
    }

ipAclBogonInfoIndex OBJECT-TYPE
    SYNTAX  Integer32
    MAX-ACCESS  read-only
    STATUS  current
    DESCRIPTION
        "The table index."
    ::= { ipAclBogonInfoTableEntry 1 }

ipAclBogonInfoIp OBJECT-TYPE
    SYNTAX  IpAddress
    MAX-ACCESS  read-only
    STATUS  current
    DESCRIPTION
        "Bogon IP Address."
    ::= { ipAclBogonInfoTableEntry 2 }

ipAclBogonInfoMask OBJECT-TYPE
    SYNTAX  IpAddress
    MAX-ACCESS  read-only
    STATUS  current
    DESCRIPTION
        "Mask for the bogon IP."
    ::= { ipAclBogonInfoTableEntry 3 }
-- End of Bogon Info


-- Management Port Infor
mgmtPortInfoSpeed OBJECT-TYPE
    SYNTAX  INTEGER {
        mbs10(1),
        mbs100(2),
        any(3)
        }
    MAX-ACCESS  read-only
    STATUS  current
    DESCRIPTION
        "The current operational speed of the management port."
    ::= { mgmtInfo 1 }

mgmtPortInfoMode OBJECT-TYPE
    SYNTAX  INTEGER {
        full-duplex(1),
        half-duplex(2),
        any(3)
        }
    MAX-ACCESS  read-only
    STATUS  current
    DESCRIPTION
        "The current operational mode of the management port."
    ::= { mgmtInfo 2 }

mgmtPortInfoLink OBJECT-TYPE
    SYNTAX  INTEGER {
        up(1),
        down(2),
        disabled(3)
        }
     MAX-ACCESS  read-only
     STATUS  current
     DESCRIPTION
         "The current operational link status of the management port."
     ::= { mgmtInfo 3 }

hwMainBoardNumber OBJECT-TYPE
    SYNTAX  DisplayString (SIZE(0..16))
    MAX-ACCESS  read-only
    STATUS  current
    DESCRIPTION
        "The hardware main board number of the Alteon Switch."
    ::= { hardware 6 }

hwMainBoardRevision OBJECT-TYPE
    SYNTAX DisplayString (SIZE(0..16))
    MAX-ACCESS read-only
    STATUS current
    DESCRIPTION
        "The hardware main board revision.  If the revision is not
         available, a zero length string should be returned."
    ::= { hardware 7 }

hwEthernetBoardNumber OBJECT-TYPE
    SYNTAX  DisplayString (SIZE(0..16))
    MAX-ACCESS  read-only
    STATUS  current
    DESCRIPTION
        "The hardware ethernet board number of the Alteon Switch."
    ::= { hardware 8 }

hwEthernetBoardRevision OBJECT-TYPE
    SYNTAX DisplayString (SIZE(0..16))
    MAX-ACCESS read-only
    STATUS current
    DESCRIPTION
        "The hardware ethernet board revision.  If the revision is not
         available, a zero length string should be returned."
    ::= { hardware 9 }


hwMACAddress OBJECT-TYPE
    SYNTAX DisplayString (SIZE(0..48))
    MAX-ACCESS read-only
    STATUS current
    DESCRIPTION
	"The MAC address."
    ::= { hardware 13 }

hwLicMACAddress OBJECT-TYPE
    SYNTAX DisplayString (SIZE(0..48))
    MAX-ACCESS read-only
    STATUS current
    DESCRIPTION
	"The License Generation MAC address."
    ::= { hardware 14 }

hwFABNumber OBJECT-TYPE
    SYNTAX DisplayString (SIZE(0..48))
    MAX-ACCESS read-only
    STATUS current
    DESCRIPTION
	"The FAB number."
    ::= { hardware 17 }

hwSerialNumber OBJECT-TYPE
    SYNTAX DisplayString (SIZE(0..48))
    MAX-ACCESS read-only
    STATUS current
    DESCRIPTION
	"The switch serial number."
    ::= { hardware 18 }

hwManufacturingDate OBJECT-TYPE
    SYNTAX DisplayString (SIZE(0..48))
    MAX-ACCESS read-only
    STATUS current
    DESCRIPTION
	"The date of manufacturing."
    ::= { hardware 19 }

hwPLDFirmwareVersion OBJECT-TYPE
    SYNTAX DisplayString (SIZE(0..48))
    MAX-ACCESS read-only
    STATUS current
    DESCRIPTION
	"The PLD Firmware Version."
    ::= { hardware 21 }

hwTemperatureSensor1 OBJECT-TYPE
    SYNTAX DisplayString (SIZE(0..48))
    MAX-ACCESS read-only
    STATUS current
    DESCRIPTION
	"The temperature sensor 1."
    ::= { hardware 22 }

hwTemperatureSensor2 OBJECT-TYPE
    SYNTAX DisplayString (SIZE(0..48))
    MAX-ACCESS read-only
    STATUS current
    DESCRIPTION
	"The temperature sensor 2."
    ::= { hardware 23 }

hwUpgradeLicense OBJECT-TYPE
    SYNTAX DisplayString (SIZE(0..256))
    MAX-ACCESS read-only
    STATUS current
    DESCRIPTION
	"The upgrade license generation MAC address or Entitlement ID."
    ::= { hardware 24 }

-- Start of AAS

hwDRAMSize OBJECT-TYPE
   SYNTAX  INTEGER
   MAX-ACCESS  read-only
   STATUS  current
   DESCRIPTION
    "DRAM Size"
        ::= {hardware 25}

hwFlashSize OBJECT-TYPE
   SYNTAX  INTEGER
   MAX-ACCESS  read-only
   STATUS  current
   DESCRIPTION
        "Flash Size"
        ::= {hardware 26}

hwNumberOfHD OBJECT-TYPE
   SYNTAX INTEGER
   MAX-ACCESS read-only
   STATUS current
   DESCRIPTION
    "The number of hard drives."
    ::= { hardware 27}

hwTemperatureThreshold OBJECT IDENTIFIER ::= {hardware 28 }

hwTemperatureWarningThresholdGet OBJECT-TYPE
   SYNTAX INTEGER
   MAX-ACCESS read-only
   STATUS current
   DESCRIPTION
           "get the temperature warning threshold"
    ::= { hwTemperatureThreshold 1}

hwTemperatureShutdownThresholdGet OBJECT-TYPE
   SYNTAX INTEGER
   MAX-ACCESS read-only
   STATUS current
   DESCRIPTION
           "get the temperature shutdown threshold"
   ::= { hwTemperatureThreshold 2}

hwTemperatureThresholdStatusCPU1Get OBJECT-TYPE
   SYNTAX INTEGER {
        notRelevant(0),
        normal(1),
        warning(2),
        critical(3)
    }
   MAX-ACCESS read-only
   STATUS current
   DESCRIPTION
           "get the threshold status of CPU1
            warning - if the warning threshold exceeded
            critical - if the shutdown threshold exceeded"
   ::= { hwTemperatureThreshold 3}

hwTemperatureThresholdStatusCPU2Get OBJECT-TYPE
   SYNTAX INTEGER {
        notRelevant(0),
        normal(1),
        warning(2),
        critical(3)
    }
   MAX-ACCESS read-only
   STATUS current
   DESCRIPTION
           "get the threshold status of CPU2
            warning - if the warning threshold exceeded
            critical - if the shutdown threshold exceeded"
   ::= { hwTemperatureThreshold 4}

hwDualPowerSupplyParams OBJECT IDENTIFIER ::= { hardware 29 }

hwPowerSupplyTrapStatus  OBJECT-TYPE
   SYNTAX FeatureStatus
   MAX-ACCESS read-write
   STATUS current
   DESCRIPTION
    "Enables the user to disable the sending of traps for the power supply status"
   ::= { hwDualPowerSupplyParams 1 }

hwPowerSupplyStatus  OBJECT-TYPE
   SYNTAX INTEGER {
      notRelevant(0),
      singlePowerSupplyOk(1),
      firstPowerSupplyFailed(2),
      secondPowerSupplyFailed(3),
      doublePowerSupplyOk(4),
      unknownPowerSupplyFailed(5),
      singlePowerSupplyFailed(6),
      singlePowerSupplyConnected(7)
   }
   MAX-ACCESS read-only
   STATUS current
   DESCRIPTION
    "The status of the power supply, the values 1,4,5 and 7 are relevant where -
    Value 1 refers to power supply ok on a platform with single PS.
    Value 4 refers to power supply ok on a platform with dual PS.
    Value 5 refers to failure while fetching the status (Please try later).
    value 7 refers only one PS unit operational, on the platform with dual PS."
   ::= { hwDualPowerSupplyParams 2 }

hwVersion OBJECT-TYPE
   SYNTAX  DisplayString
   MAX-ACCESS  read-only
   STATUS  current
   DESCRIPTION
        "Defines the HW version of the product."
   ::= { hardware 30 }

-- fan slot information table

hwFanInfoTable OBJECT-TYPE
    SYNTAX  SEQUENCE OF HwFanInfoTableEntry
    MAX-ACCESS  not-accessible
    STATUS  current
    DESCRIPTION
        "The table of fan slot information."
    ::= { hardware 31 }

hwFanInfoTableEntry OBJECT-TYPE
    SYNTAX  HwFanInfoTableEntry
    MAX-ACCESS  not-accessible
    STATUS  current
    DESCRIPTION
        "A row in the fan information table."
    INDEX   { hwFanInfoIndex }
    ::= { hwFanInfoTable 1 }

HwFanInfoTableEntry ::= SEQUENCE {
    hwFanInfoIndex              Integer32,
    hwFanInfoStatus		INTEGER,
    hwFanInfoTotalCount		INTEGER,
    hwFanInfoCountFailed	INTEGER,
    hwFanInfoIsCritical     INTEGER
}

hwFanInfoIndex OBJECT-TYPE
    SYNTAX  Integer32
    MAX-ACCESS  read-only
    STATUS  current
    DESCRIPTION
        "fan slot index."
    ::= { hwFanInfoTableEntry 1 }

hwFanInfoStatus OBJECT-TYPE
    SYNTAX  INTEGER {
        notRelevant(0),
        ok(1),
        failed(2),
        unplugged(3),
		empty(4)
        }
    MAX-ACCESS  read-only
    STATUS  current
    DESCRIPTION
		"The status of the fan slot."
    ::= { hwFanInfoTableEntry 2 }

hwFanInfoTotalCount OBJECT-TYPE
    SYNTAX  INTEGER
    MAX-ACCESS  read-only
    STATUS  current
    DESCRIPTION
		"The total count of fans per slot."
    ::= { hwFanInfoTableEntry 3 }

hwFanInfoCountFailed OBJECT-TYPE
    SYNTAX  INTEGER
    MAX-ACCESS  read-only
    STATUS  current
    DESCRIPTION
		"The total count of failed fans."
    ::= { hwFanInfoTableEntry 4 }

hwFanInfoIsCritical OBJECT-TYPE
    SYNTAX INTEGER {
        no(0),
        yes(1),
        notRelevant(2)
    }
    MAX-ACCESS  read-only
    STATUS  current
    DESCRIPTION
		"A flag indicates whether the fan is critical or not."
    ::= { hwFanInfoTableEntry 5 }

-- Temperature slot information table

hwTemperatureInfoTable OBJECT-TYPE
    SYNTAX  SEQUENCE OF HwTemperatureInfoTableEntry
    MAX-ACCESS  not-accessible
    STATUS  current
    DESCRIPTION
        "The table of temperature slot information."
    ::= { hardware 32 }

hwTemperatureInfoTableEntry OBJECT-TYPE
    SYNTAX  HwTemperatureInfoTableEntry
    MAX-ACCESS  not-accessible
    STATUS  current
    DESCRIPTION
        "A row in the temperature information table."
    INDEX   { hwTempInfoSlotIndex, hwTempInfoSensorIndex }
    ::= { hwTemperatureInfoTable 1 }

HwTemperatureInfoTableEntry ::= SEQUENCE {
	hwTempInfoSlotIndex        Integer32,
	hwTempInfoSensorIndex	Integer32,
	hwTempInfoSensorStatus	INTEGER,
	hwTempInfoSensorTemp  INTEGER,
	hwTempInfoSensorStr	   DisplayString
    }

hwTempInfoSlotIndex OBJECT-TYPE
    SYNTAX  Integer32
    MAX-ACCESS  read-only
    STATUS  current
    DESCRIPTION
        "The slot index"
    ::= { hwTemperatureInfoTableEntry 1 }

hwTempInfoSensorIndex OBJECT-TYPE
    SYNTAX  Integer32
    MAX-ACCESS  read-only
    STATUS  current
    DESCRIPTION
        "The sensor index"
    ::= { hwTemperatureInfoTableEntry 2 }

hwTempInfoSensorStatus OBJECT-TYPE
    SYNTAX  INTEGER {
        low(1),
        normal(2),
	high(3),
	critical(4)
        }
    MAX-ACCESS  read-only
    STATUS  current
    DESCRIPTION
		"The sensor status"
    ::= { hwTemperatureInfoTableEntry 3 }

hwTempInfoSensorTemp OBJECT-TYPE
    SYNTAX  INTEGER
    MAX-ACCESS  read-only
    STATUS  current
    DESCRIPTION
		"The sensor temperature"
    ::= { hwTemperatureInfoTableEntry 4 }

hwTempInfoSensorStr OBJECT-TYPE
    SYNTAX DisplayString
    MAX-ACCESS read-only
    STATUS current
    DESCRIPTION
        "The sensor name"
    ::= { hwTemperatureInfoTableEntry 5 }

-- Fan speed information table

hwFanSpeedTable OBJECT-TYPE
    SYNTAX  SEQUENCE OF HwFanSpeedTableEntry
    MAX-ACCESS  not-accessible
    STATUS  current
    DESCRIPTION
        "The table of fans speed."
    ::= { hardware 34 }

hwFanSpeedTableEntry OBJECT-TYPE
    SYNTAX  HwFanSpeedTableEntry
    MAX-ACCESS  not-accessible
    STATUS  current
    DESCRIPTION
        "A row in the fans speed table."
    INDEX   { hwFanSpeedSlotIndex, hwFanSpeedSensorIndex }
    ::= { hwFanSpeedTable 1 }

HwFanSpeedTableEntry ::= SEQUENCE {
        hwFanSpeedSlotIndex        Integer32,
        hwFanSpeedSensorIndex   Integer32,
        hwFanSpeedVal                  INTEGER
    }

hwFanSpeedSlotIndex OBJECT-TYPE
    SYNTAX  Integer32
    MAX-ACCESS  read-only
    STATUS  current
    DESCRIPTION
        "The fan slot index."
    ::= { hwFanSpeedTableEntry 1 }

hwFanSpeedSensorIndex OBJECT-TYPE
    SYNTAX  Integer32
    MAX-ACCESS  read-only
    STATUS  current
    DESCRIPTION
        "The fan sensor index."
    ::= { hwFanSpeedTableEntry 2 }

hwFanSpeedVal OBJECT-TYPE
    SYNTAX  INTEGER
    MAX-ACCESS  read-only
    STATUS  current
    DESCRIPTION
        "The fan speed."
    ::= { hwFanSpeedTableEntry 3 }

hwSslChipInfo OBJECT-TYPE
    SYNTAX  DisplayString
    MAX-ACCESS  read-only
    STATUS  current
    DESCRIPTION
        "SSl Chip information."
    ::= { hardware 36 }

hwApplicationSwitchNameInfo OBJECT-TYPE
    SYNTAX  DisplayString
    MAX-ACCESS  read-only
    STATUS  current
    DESCRIPTION
        "Application Switch name information."
    ::= { hardware 37 }

portStatsPerSecTable OBJECT-TYPE
   SYNTAX SEQUENCE OF PortStatsPerSecEntry
   MAX-ACCESS not-accessible
   STATUS  current
   DESCRIPTION
    "Table for the device ports statistics per second"
   ::=  {portStats 2}

portStatsPerSecEntry OBJECT-TYPE
   SYNTAX  PortStatsPerSecEntry
   MAX-ACCESS not-accessible
   STATUS  current
   DESCRIPTION
    "The row definition for this table"
   INDEX { portStatsPortNumber }
   ::=  { portStatsPerSecTable 1}

PortStatsPerSecEntry ::= SEQUENCE {
  portStatsPortNumber          Integer32,
  portStatsInOctetsPerSec      Counter64,
  portStatsInPktsPerSec        Counter32,
  portStatsInDiscardsPerSec    Counter32,
  portStatsInErrorsPerSec      Counter32,
  portStatsOutOctetsPerSec     Counter64,
  portStatsOutPktsPerSec       Counter32,
  portStatsOutDiscardsPerSec   Counter32,
  portStatsOutErrorsPerSec     Counter32
  }

portStatsPortNumber OBJECT-TYPE
    SYNTAX  Integer32
    MAX-ACCESS read-only
    STATUS  current
    DESCRIPTION
      "The port number"
    ::=  { portStatsPerSecEntry 1}

portStatsInOctetsPerSec OBJECT-TYPE
    SYNTAX Counter64
    MAX-ACCESS read-only
    STATUS  current
    DESCRIPTION
      "Amount of input data in octets in the last sec"
    ::=  { portStatsPerSecEntry 2}

portStatsInPktsPerSec OBJECT-TYPE
    SYNTAX  Counter32
    MAX-ACCESS read-only
    STATUS  current
    DESCRIPTION
      "Amount of input data in packets in the last sec"
    ::=  { portStatsPerSecEntry 3}

portStatsInDiscardsPerSec OBJECT-TYPE
    SYNTAX  Counter32
    MAX-ACCESS read-only
    STATUS  current
    DESCRIPTION
      "amount of input data that got discarded in the last sec"
    ::=  { portStatsPerSecEntry 4}

portStatsInErrorsPerSec OBJECT-TYPE
    SYNTAX  Counter32
    MAX-ACCESS read-only
    STATUS  current
    DESCRIPTION
      "Amount of input data that have error in the last sec"
    ::=  { portStatsPerSecEntry 5}

portStatsOutOctetsPerSec OBJECT-TYPE
    SYNTAX Counter64
    MAX-ACCESS read-only
    STATUS  current
    DESCRIPTION
      "Amount of output data in octets in the last sec"
    ::=  { portStatsPerSecEntry 6}

portStatsOutPktsPerSec OBJECT-TYPE
    SYNTAX  Counter32
    MAX-ACCESS read-only
    STATUS  current
    DESCRIPTION
      "Amount of output data in packets in the last sec"
    ::=  { portStatsPerSecEntry 7}

portStatsOutDiscardsPerSec OBJECT-TYPE
    SYNTAX  Counter32
    MAX-ACCESS read-only
    STATUS  current
    DESCRIPTION
      "Amount of output data that got discarded in the last sec"
    ::=  { portStatsPerSecEntry 8}

portStatsOutErrorsPerSec OBJECT-TYPE
    SYNTAX  Counter32
    MAX-ACCESS read-only
    STATUS  current
    DESCRIPTION
      "Amount of output data that have error in the last sec"
    ::=  { portStatsPerSecEntry 9}

portStatsTotalPerSec         OBJECT IDENTIFIER ::= { portStats 3 }

portStatsTotalInOctetsPerSec OBJECT-TYPE
    SYNTAX  Counter64
    MAX-ACCESS read-only
    STATUS  current
    DESCRIPTION
      "Amount of total input, IN octets on all ports per second"
    ::=  { portStatsTotalPerSec 1 }

portStatsTotalOutOctetsPerSec OBJECT-TYPE
    SYNTAX Counter64
    MAX-ACCESS read-only
    STATUS  current
    DESCRIPTION
      "Amount of total output, OUT octets from all ports per second"
    ::=  { portStatsTotalPerSec 2 }
-- End of AAS

agentTimeInfo     OBJECT IDENTIFIER ::= { agentInfo 11 }

agSwitchUpTime OBJECT-TYPE
    SYNTAX  DisplayString (SIZE(0..127))
    MAX-ACCESS  read-only
    STATUS  current
    DESCRIPTION
        "Time since the switch is up in DisplayString, sysUpTime also provides the same data in TimeTicks."
    ::= { agentTimeInfo 1 }

agSwitchConfigChangeTime OBJECT-TYPE
    SYNTAX  TimeTicks
    MAX-ACCESS  read-only
    STATUS  current
    DESCRIPTION
        "The value of sysUpTime at the last configuration change."
    ::= { agentTimeInfo 2 }

agSwitchConfigChangeTimeStr OBJECT-TYPE
    SYNTAX  DisplayString (SIZE(0..127))
    MAX-ACCESS  read-only
    STATUS  current
    DESCRIPTION
        "Last configuration change time same as agSwitchConfigChangeTime but in user readable format."
    ::= { agentTimeInfo 3 }

agSwitchLastBootTime OBJECT-TYPE
    SYNTAX  DisplayString (SIZE(0..127))
    MAX-ACCESS  read-only
    STATUS  current
    DESCRIPTION
        "Last switch boot time and boot reason."
    ::= { agentTimeInfo 4 }

agSwitchLastApplyTime OBJECT-TYPE
    SYNTAX  DisplayString (SIZE(0..127))
    MAX-ACCESS  read-only
    STATUS  current
    DESCRIPTION
        "Last switch configuration apply time."
    ::= { agentTimeInfo 5 }

agSwitchLastSaveTime OBJECT-TYPE
    SYNTAX  DisplayString (SIZE(0..127))
    MAX-ACCESS  read-only
    STATUS  current
    DESCRIPTION
        "Last switch configuration save time."
    ::= { agentTimeInfo 6 }

agSwitchTimeSinceLastSlbStatsClear OBJECT-TYPE
    SYNTAX  DisplayString (SIZE(0..127))
    MAX-ACCESS  read-only
    STATUS  current
    DESCRIPTION
        "Time since the slb statistics were cleared in DisplayString."
    ::= { agentTimeInfo 7 }

agGeoDbAutoLastSuccUpdate OBJECT-TYPE
    SYNTAX  DisplayString (SIZE(0..127))
    MAX-ACCESS  read-only
    STATUS  current
    DESCRIPTION
        "Last Successful geolocation database update time."
    ::= { agentTimeInfo 8 }

agGeoDbAutoLastFailedUpdate OBJECT-TYPE
    SYNTAX  DisplayString (SIZE(0..127))
    MAX-ACCESS  read-only
    STATUS  current
    DESCRIPTION
        "Last failed geolocation database update time."
    ::= { agentTimeInfo 9 }

agGeoDbIsLicValid OBJECT-TYPE
    SYNTAX  INTEGER {
        enabled(1),
        disabled(2)
        }
    MAX-ACCESS  read-only
    STATUS  current
    DESCRIPTION
        "Geolocation database license is valid or not."
    ::= { agentTimeInfo 10 }

-- End of Vision Driver file

agentSwExtInfo OBJECT-TYPE
    SYNTAX  INTEGER {
        available(1),
        not-available(2)
        }
    MAX-ACCESS  read-only
    STATUS  current
    DESCRIPTION
        "The status of Switch Extension."
    ::= { agentInfo 12 }

-- Begin sync stat

agLastSyncInfoTable OBJECT-TYPE
    SYNTAX  SEQUENCE OF AgLastSyncInfoTableEntry
    MAX-ACCESS  not-accessible
    STATUS  current
    DESCRIPTION
        "The table of Last Sync Information."
    ::= { agentInfo 13 }

agLastSyncInfoTableEntry OBJECT-TYPE
    SYNTAX  AgLastSyncInfoTableEntry
    MAX-ACCESS not-accessible
    STATUS  current
    DESCRIPTION
        "A row in the Last Sync Information table."
    INDEX  { lastSyncInfoIdx }
    ::= { agLastSyncInfoTable 1 }

AgLastSyncInfoTableEntry ::=
    SEQUENCE {
        lastSyncInfoIdx                Integer32,
        lastSyncPeerIp                 DisplayString,
        lastSyncType                   INTEGER,
        lastSyncStatus                 INTEGER,
        lastSyncTime                   DisplayString,
        lastSyncFailReason             DisplayString,
        lastSuccessfulSyncType         INTEGER,
        lastSuccessfulSyncTime         DisplayString
    }

lastSyncInfoIdx OBJECT-TYPE
    SYNTAX Integer32
    MAX-ACCESS  read-only
    STATUS  current
    DESCRIPTION
        "Last sync table peer index."
    ::= { agLastSyncInfoTableEntry 1 }

lastSyncPeerIp OBJECT-TYPE
    SYNTAX DisplayString
    MAX-ACCESS  read-only
    STATUS  current
    DESCRIPTION
        "Last sync peer ip address."
    ::= { agLastSyncInfoTableEntry 2 }

lastSyncType OBJECT-TYPE
    SYNTAX  INTEGER {
        none(1),
        manual(2),
        auto(3)
        }
    MAX-ACCESS  read-only
    STATUS  current
    DESCRIPTION
        "Last sync type - none(1),manual(2) and auto(3)."
    ::= { agLastSyncInfoTableEntry 3 }

lastSyncStatus OBJECT-TYPE
    SYNTAX  INTEGER {
        idle(1),
        in-progress(2),
        success(3),
        failure(4)
        }
    MAX-ACCESS  read-only
    STATUS  current
    DESCRIPTION
        "Status of last sync sent- idle(1), in-progress(2),success(3) and failure(4)."
    ::= { agLastSyncInfoTableEntry 4 }

lastSyncTime OBJECT-TYPE
    SYNTAX  DisplayString (SIZE(0..127))
    MAX-ACCESS  read-only
    STATUS  current
    DESCRIPTION
        "Timestamp for last sync sent."
    ::= { agLastSyncInfoTableEntry 5 }

lastSyncFailReason OBJECT-TYPE
    SYNTAX  DisplayString
    MAX-ACCESS  read-only
    STATUS  current
    DESCRIPTION
        "Failure reason for last sync."
    ::= { agLastSyncInfoTableEntry 6 }

lastSuccessfulSyncType OBJECT-TYPE
    SYNTAX  INTEGER {
        none(1),
        manual(2),
        auto(3)
        }
    MAX-ACCESS  read-only
    STATUS  current
    DESCRIPTION
        "Type of the last successful sync sent - none(1), manual(2), auto(3)."
    ::= { agLastSyncInfoTableEntry 7 }

lastSuccessfulSyncTime OBJECT-TYPE
    SYNTAX  DisplayString (SIZE(0..127))
    MAX-ACCESS  read-only
    STATUS  current
    DESCRIPTION
        "Timestamp for last successful sync sent."
    ::= { agLastSyncInfoTableEntry 8 }

-- end sync stat

agentAppwallInfo     OBJECT IDENTIFIER ::= { agentInfo 14 }

agAppwallWafStatus OBJECT-TYPE
    SYNTAX INTEGER { disabled(0) ,enabled(1) }
    MAX-ACCESS read-only
    STATUS current
    DESCRIPTION
         "State of Appwall general waf."
    ::= { agentAppwallInfo 1 }

agAppwallProcessId OBJECT-TYPE
    SYNTAX INTEGER
    MAX-ACCESS read-only
    STATUS current
    DESCRIPTION
         "Appwall process ID"
    ::= { agentAppwallInfo 2 }

agAppwallProcessMemUsage OBJECT-TYPE
    SYNTAX INTEGER
    MAX-ACCESS read-only
    STATUS current
    DESCRIPTION
         "Appwall process memory usage"
    ::= { agentAppwallInfo 3 }

agentIpRepInfo     OBJECT IDENTIFIER ::= { agentInfo 15 }

agIpRepStatus OBJECT-TYPE
    SYNTAX INTEGER { notOperational(0) ,operational(1) }
    MAX-ACCESS read-only
    STATUS current
    DESCRIPTION
         "IP REP operational status."
    ::= { agentIpRepInfo 1 }

agIpRepStatusReason OBJECT-TYPE
    SYNTAX DisplayString
    MAX-ACCESS read-only
    STATUS current
    DESCRIPTION
        "IP REP operational status reason."
    ::= { agentIpRepInfo 2 }


agentAzureInfo     OBJECT IDENTIFIER ::= { agentInfo 16 }

agAzurePrimaryPublicIp OBJECT-TYPE
    SYNTAX  DisplayString (SIZE(0..127))
    MAX-ACCESS  read-only
    STATUS  current
    DESCRIPTION
        "Primary public IP address.
         Note: This MIB is only supported on VA platform."
    ::= { agentAzureInfo 1 }

agAzureSecondaryPublicIp OBJECT-TYPE
    SYNTAX  DisplayString (SIZE(0..127))
    MAX-ACCESS read-only
    STATUS current
    DESCRIPTION
        "Secondary public IP address.
         Note: This MIB is only supported on VA platform."
    ::= { agentAzureInfo 2 }

agentAwsInfo     OBJECT IDENTIFIER ::= { agentInfo 18 }

agAwsAccessId OBJECT-TYPE
    SYNTAX   DisplayString (SIZE(0..127))
    MAX-ACCESS  read-only
    STATUS  current
    DESCRIPTION
        "Set AWS account ID, used to construct Amazon Resource Names (ARNs).
         Note: This MIB is only supported on VA platform."
    ::= { agentAwsInfo 1 }

agAwsSecretAccessKey OBJECT-TYPE
    SYNTAX   DisplayString (SIZE(0..255))
    MAX-ACCESS  read-only
    STATUS  current
    DESCRIPTION
        "Set AWS account password.
         Note: This MIB is only supported on VA platform."
    ::= { agentAwsInfo 2 }

agAwsAssociatedIpTable OBJECT-TYPE
    SYNTAX  SEQUENCE OF AgAwsAssociatedIpTableIdEntry
    MAX-ACCESS  not-accessible
    STATUS  current
    DESCRIPTION
        "Associated ip table of for AWS ha.
         Note: This MIB is only supported on VA platform."
    ::= { agentAwsInfo 3 }

agAwsssociatedIpTableIdEntry OBJECT-TYPE
    SYNTAX  AgAwsAssociatedIpTableIdEntry
    MAX-ACCESS  not-accessible
    STATUS  current
    DESCRIPTION
        "A row in AWS ha associated ip table.
         Note: This MIB is only supported on VA platform."
    INDEX   { agAwsAssociatedIpIndex }
    ::= { agAwsAssociatedIpTable 1 }

AgAwsAssociatedIpTableIdEntry ::= SEQUENCE {
    agAwsAssociatedIpIndex       	INTEGER,
    agAwsAssociatedIpPrivateIp    DisplayString,
    agAwsAssociatedIpPeerIp     	DisplayString,
    agAwsAssociatedIpFloatingIp   DisplayString
    }

agAwsAssociatedIpIndex OBJECT-TYPE
    SYNTAX INTEGER
    MAX-ACCESS  read-only
    STATUS  current
    DESCRIPTION
        "AWS HA associated ip table index.
         Note: This MIB is only supported on VA platform."
    ::= { agAwsssociatedIpTableIdEntry 1 }


agAwsAssociatedIpPrivateIp OBJECT-TYPE
    SYNTAX   DisplayString (SIZE(0..40))
    MAX-ACCESS  read-only
    STATUS  current
    DESCRIPTION
        "Get AWS Alteon private IP, as a part of HA associated IP set.
         Note: This MIB is only supported on VA platform."
    ::= { agAwsssociatedIpTableIdEntry 2 }

agAwsAssociatedIpPeerIp OBJECT-TYPE
    SYNTAX   DisplayString (SIZE(0..40))
    MAX-ACCESS  read-only
    STATUS  current
    DESCRIPTION
        "Get AWS Alteon backup(s) IP, as a part of HA associated IP set.
         Note: This MIB is only supported on VA platform."
    ::= { agAwsssociatedIpTableIdEntry 3 }

agAwsAssociatedIpFloatingIp OBJECT-TYPE
    SYNTAX   DisplayString (SIZE(0..40))
    MAX-ACCESS  read-only
    STATUS  current
    DESCRIPTION
        "Get AWS Alteon floating/elastic IP, as a part of HA associated IP set.
         Note: This MIB is only supported on VA platform."
    ::= { agAwsssociatedIpTableIdEntry 4 }


-- Added in 31.x
-- agentIpRepInfo     OBJECT IDENTIFIER ::= { agentInfo 15 }

agLastSyncInfoTableToString OBJECT-TYPE
    SYNTAX  DisplayString
    MAX-ACCESS  read-only
    STATUS  current
    DESCRIPTION
        "The string with all peer's statuses from last config-sync."
    ::= { agentInfo 17 }



bootResourcesAWEna OBJECT-TYPE
	SYNTAX INTEGER{
		enabled(1),
		disabled(0)
		}
	MAX-ACCESS read-write
	STATUS current
	DESCRIPTION
		"Enable or disable AppWall resources allocation.
		Note: This MIB is only supported on VA platform."
	::= { agSystem 124 }

bootResourcesAWvCPUs OBJECT-TYPE
	SYNTAX INTEGER(2..16)
	MAX-ACCESS read-write
	STATUS current
	DESCRIPTION
		"Set AppWall number of vCPUs.
		Note: This MIB is only supported on VA platform."
	::= { agSystem 125 }

bootResourcesAWvRAM OBJECT-TYPE
	SYNTAX INTEGER(1..256)
	MAX-ACCESS read-write
	STATUS current
	DESCRIPTION
		"Set AppWall RAM allocation in GB.
		Note: This MIB is only supported on VA platform."
	::= { agSystem 126 }

bootResourcesAWvDisk OBJECT-TYPE
	SYNTAX INTEGER(1..256)
	MAX-ACCESS read-write
	STATUS current
	DESCRIPTION
		"Set AppWall disk allocation in GB.
		Note: This MIB is only supported on VA platform."
	::= { agSystem 127 }

bootResourcesFVEna OBJECT-TYPE
	SYNTAX INTEGER{
		enabled(1),
		disabled(0)
		}
	MAX-ACCESS read-write
	STATUS current
	DESCRIPTION
		"Enable or disable FastView resources allocation.
		Note: This MIB is only supported on VA platform."
	::= { agSystem 128 }

bootResourcesFVvRAM OBJECT-TYPE
	SYNTAX INTEGER(4..256)
	MAX-ACCESS read-write
	STATUS current
	DESCRIPTION
		"Set FastView RAM allocation in GB.
		Note: This MIB is only supported on VA platform."
	::= { agSystem 129 }

bootResourcesFVvDisk OBJECT-TYPE
	SYNTAX INTEGER(12..256)
	MAX-ACCESS read-write
	STATUS current
	DESCRIPTION
		"Set AppWall disk allocation in GB.
		Note: This MIB is only supported on VA platform."
	::= { agSystem 130 }

bootResourcesDoneFlag OBJECT-TYPE
	SYNTAX INTEGER{
		enabled(1),
		disabled(0)
		}
	MAX-ACCESS read-write
	STATUS current
	DESCRIPTION
		"Notify that resources allocation settings are ready to be applied.
		Note: This MIB is only supported on VA platform."
	::= { agSystem 131 }

bootResourcesTotalVCPUs OBJECT-TYPE
	SYNTAX INTEGER(1..256)
	MAX-ACCESS read-only
	STATUS current
	DESCRIPTION
		"Total amount of vCPUs in the system.
		Note: This MIB is only supported on VA platform."
	::= { agSystem 132 }

bootResourcesTotalVRAM OBJECT-TYPE
	SYNTAX DisplayString (SIZE(0..10))
	MAX-ACCESS read-only
	STATUS current
	DESCRIPTION
		"Total size of RAM in the system.
		Note: This MIB is only supported on VA platform."
	::= { agSystem 133 }

bootResourcesTotalVDisk OBJECT-TYPE
	SYNTAX DisplayString (SIZE(0..10))
	MAX-ACCESS read-only
	STATUS current
	DESCRIPTION
		"Total size of disk space in the system.
		Note: This MIB is only supported on VA platform."
	::= { agSystem 134 }

bootResourcesADCVCPUs OBJECT-TYPE
	SYNTAX INTEGER(1..256)
	MAX-ACCESS read-write
	STATUS current
	DESCRIPTION
		"ADC number of vCPUs.
		Note: This MIB is only supported on VA platform."
	::= { agSystem 135 }

bootResourcesADCVRAM OBJECT-TYPE
	SYNTAX INTEGER(1..256)
	MAX-ACCESS read-write
	STATUS current
	DESCRIPTION
		"ADC RAM allocation in GB.
		Note: This MIB is only supported on VA platform."
	::= { agSystem 136 }

bootResourcesADCVDisk OBJECT-TYPE
	SYNTAX INTEGER(1..256)
	MAX-ACCESS read-only
	STATUS current
	DESCRIPTION
		"ADC Disk allocation in GB.
		Note: This MIB is only supported on VA platform."
	::= { agSystem 137 }

bootResourcesFVvCPUs OBJECT-TYPE
	SYNTAX INTEGER(1..256)
	MAX-ACCESS read-only
	STATUS current
	DESCRIPTION
		"Get FastView number of vCPUs.
		Note: This MIB is only supported on VA platform."
	::= { agSystem 138 }

vatdStatsCpuUtilTable OBJECT-TYPE
    SYNTAX  SEQUENCE OF VatdStatsCpuUtilTableEntry
    MAX-ACCESS  not-accessible
    STATUS  current
    DESCRIPTION
        "The table of VATD CPU utilization."
    ::= { vatdStats 1 }

vatdStatsCpuUtilTableEntry OBJECT-TYPE
    SYNTAX  VatdStatsCpuUtilTableEntry
    MAX-ACCESS  not-accessible
    STATUS  current
    DESCRIPTION
        "A row in the VATD CPU utilization table."
    INDEX   { vatdStatsCpuUtilVatdIndex }
    ::= { vatdStatsCpuUtilTable 1 }

VatdStatsCpuUtilTableEntry ::= SEQUENCE {
    vatdStatsCpuUtilVatdIndex    Integer32,
    vatdStatsCpuUtil1Second    Integer32,
    vatdStatsCpuUtil64Seconds  Integer32
    }

vatdStatsCpuUtilVatdIndex OBJECT-TYPE
    SYNTAX  Integer32
    MAX-ACCESS  read-only
    STATUS  current
    DESCRIPTION
        "The VATD index."
    ::= { vatdStatsCpuUtilTableEntry 1 }

vatdStatsCpuUtil1Second OBJECT-TYPE
    SYNTAX  Integer32
    MAX-ACCESS  read-only
    STATUS  current
    DESCRIPTION
        "The utilization of this VATD over 1 second. It shows the percentage."
    ::= { vatdStatsCpuUtilTableEntry 2 }

vatdStatsCpuUtil64Seconds OBJECT-TYPE
    SYNTAX  Integer32
    MAX-ACCESS  read-only
    STATUS  current
    DESCRIPTION
        "The utilization of this VATD over 64 seconds. It shows the percentage."
    ::= { vatdStatsCpuUtilTableEntry 3 }

-- IPREP Count Statisitics


ipRepCountStatsAllowErtTorLow OBJECT-TYPE
    SYNTAX Integer32
    MAX-ACCESS read-only
    STATUS current
    DESCRIPTION
        "Hits Count statistics for action Allow, category ERT_Tor, sevirity Low."
    ::= { ipRepCountStats 1 }

ipRepCountStatsAllowErtTorMedium OBJECT-TYPE
    SYNTAX Integer32
    MAX-ACCESS read-only
    STATUS current
    DESCRIPTION
        "Hits Count statistics for action Allow, category ERT_Tor, sevirity Medium."
    ::= { ipRepCountStats 2 }

ipRepCountStatsAllowErtTorHigh OBJECT-TYPE
    SYNTAX Integer32
    MAX-ACCESS read-only
    STATUS current
    DESCRIPTION
        "Hits Count statistics for action Allow, category ERT_Tor, sevirity High."
    ::= { ipRepCountStats 3 }

ipRepCountStatsAllowErtMaliciousLow OBJECT-TYPE
    SYNTAX Integer32
    MAX-ACCESS read-only
    STATUS current
    DESCRIPTION
        "Hits Count statistics for action Allow, category ERT_Malicious, sevirity Low."
    ::= { ipRepCountStats 4 }

ipRepCountStatsAllowErtMaliciousMedium OBJECT-TYPE
    SYNTAX Integer32
    MAX-ACCESS read-only
    STATUS current
    DESCRIPTION
        "Hits Count statistics for action Allow, category ERT_Malicious, sevirity Medium."
    ::= { ipRepCountStats 5 }

ipRepCountStatsAllowErtMaliciousHigh OBJECT-TYPE
    SYNTAX Integer32
    MAX-ACCESS read-only
    STATUS current
    DESCRIPTION
        "Hits Count statistics for action Allow, category ERT_Malicious, sevirity High."
    ::= { ipRepCountStats 6 }

ipRepCountStatsBlockErtTorLow OBJECT-TYPE
    SYNTAX Integer32
    MAX-ACCESS read-only
    STATUS current
    DESCRIPTION
        "Hits Count statistics for action Block, category ERT_Tor, sevirity Low."
    ::= { ipRepCountStats 7 }

ipRepCountStatsBlockErtTorMedium OBJECT-TYPE
    SYNTAX Integer32
    MAX-ACCESS read-only
    STATUS current
    DESCRIPTION
        "Hits Count statistics for action Block, category ERT_Tor, sevirity Medium."
    ::= { ipRepCountStats 8 }

ipRepCountStatsBlockErtTorHigh OBJECT-TYPE
    SYNTAX Integer32
    MAX-ACCESS read-only
    STATUS current
    DESCRIPTION
        "Hits Count statistics for action Block, category ERT_Tor, sevirity High."
    ::= { ipRepCountStats 9 }

ipRepCountStatsBlockErtMaliciousLow OBJECT-TYPE
    SYNTAX Integer32
    MAX-ACCESS read-only
    STATUS current
    DESCRIPTION
        "Hits Count statistics for action Block, category ERT_Malicious, sevirity Low."
    ::= { ipRepCountStats 10 }

ipRepCountStatsBlockErtMaliciousMedium OBJECT-TYPE
    SYNTAX Integer32
    MAX-ACCESS read-only
    STATUS current
    DESCRIPTION
        "Hits Count statistics for action Block, category ERT_Malicious, sevirity Medium."
    ::= { ipRepCountStats 11 }

ipRepCountStatsBlockErtMaliciousHigh OBJECT-TYPE
    SYNTAX Integer32
    MAX-ACCESS read-only
    STATUS current
    DESCRIPTION
        "Hits Count statistics for action Block, category ERT_Malicious, sevirity High."
    ::= { ipRepCountStats 12 }

ipRepCountStatsAlarmErtTorLow OBJECT-TYPE
    SYNTAX Integer32
    MAX-ACCESS read-only
    STATUS current
    DESCRIPTION
        "Hits Count statistics for action Alarm, category ERT_Tor, sevirity Low."
    ::= { ipRepCountStats 13 }

ipRepCountStatsAlarmErtTorMedium OBJECT-TYPE
    SYNTAX Integer32
    MAX-ACCESS read-only
    STATUS current
    DESCRIPTION
        "Hits Count statistics for action Alarm, category ERT_Tor, sevirity Medium."
    ::= { ipRepCountStats 14 }

ipRepCountStatsAlarmErtTorHigh OBJECT-TYPE
    SYNTAX Integer32
    MAX-ACCESS read-only
    STATUS current
    DESCRIPTION
        "Hits Count statistics for action Alarm, category ERT_Tor, sevirity High."
    ::= { ipRepCountStats 15 }

ipRepCountStatsAlarmErtMaliciousLow OBJECT-TYPE
    SYNTAX Integer32
    MAX-ACCESS read-only
    STATUS current
    DESCRIPTION
        "Hits Count statistics for action Alarm, category ERT_Malicious, sevirity Low."
    ::= { ipRepCountStats 16 }

ipRepCountStatsAlarmErtMaliciousMedium OBJECT-TYPE
    SYNTAX Integer32
    MAX-ACCESS read-only
    STATUS current
    DESCRIPTION
        "Hits Count statistics for action Alarm, category ERT_Malicious, sevirity Medium."
    ::= { ipRepCountStats 17 }

ipRepCountStatsAlarmErtMaliciousHigh OBJECT-TYPE
    SYNTAX Integer32
    MAX-ACCESS read-only
    STATUS current
    DESCRIPTION
        "Hits Count statistics for action Alarm, category ERT_Malicious, sevirity High."
    ::= { ipRepCountStats 18 }

ipRepCountStatsClear OBJECT-TYPE
    SYNTAX  INTEGER {
        ok(1),
        clear(2)
        }
    MAX-ACCESS read-write
    STATUS current
    DESCRIPTION
        "Setting this value to clear(2) clears ip rep aggregated stats counters."
    ::= { ipRepCountStats 19 }

ipRepCountStatsWhiteListHits OBJECT-TYPE
    SYNTAX Integer32
    MAX-ACCESS read-only
    STATUS current
    DESCRIPTION
        "Hits Count statistics for White list."
    ::= { ipRepCountStats 20 }

-- system Disk Configurarion Menu

agSysDiskCurCfgCriThreshold OBJECT-TYPE
    SYNTAX  INTEGER (1..100)
    MAX-ACCESS  read-only
    STATUS  current
    DESCRIPTION
        "The system diskspace trap critical threshold in %."
    ::= { agSysDiskConfig 1 }

agSysDiskCurCfgCriInterval OBJECT-TYPE
    SYNTAX  INTEGER (1..1440)
    MAX-ACCESS  read-only
    STATUS  current
    DESCRIPTION
        "The system diskspace trap critical interval in sec."
    ::= { agSysDiskConfig 2 }

agSysDiskCurCfgCriEnable OBJECT-TYPE
    SYNTAX  INTEGER {
        enabled(1),
        disabled(2)
        }
    MAX-ACCESS  read-only
    STATUS  current
    DESCRIPTION
        "The system diskspace trap critical sending enable/disable."
    ::= { agSysDiskConfig 3 }

agSysDiskCurCfgExtThreshold OBJECT-TYPE
    SYNTAX  INTEGER (1..100)
    MAX-ACCESS  read-only
    STATUS  current
    DESCRIPTION
        "The system diskspace trap exceeded high threshold in %."
    ::= { agSysDiskConfig 4 }

agSysDiskCurCfgExtInterval OBJECT-TYPE
    SYNTAX  INTEGER (1..1440)
    MAX-ACCESS  read-only
    STATUS  current
    DESCRIPTION
        "The system diskspace trap exceeded high interval in sec."
    ::= { agSysDiskConfig 5 }

agSysDiskCurCfgExtEnable OBJECT-TYPE
    SYNTAX  INTEGER {
        enabled(1),
        disabled(2)
        }
    MAX-ACCESS  read-only
    STATUS  current
    DESCRIPTION
        "The system diskspace trap exceeded high sending enable/disable."
    ::= { agSysDiskConfig 6 }

agSysDiskCurCfgHighThreshold OBJECT-TYPE
    SYNTAX  INTEGER (1..100)
    MAX-ACCESS  read-only
    STATUS  current
    DESCRIPTION
        "The system diskspace trap high threshold in %."
    ::= { agSysDiskConfig 7 }

agSysDiskCurCfgHighInterval OBJECT-TYPE
    SYNTAX  INTEGER (1..1440)
    MAX-ACCESS  read-only
    STATUS  current
    DESCRIPTION
        "The system diskspace trap exceeded interval in sec."
    ::= { agSysDiskConfig 8 }

agSysDiskCurCfgHighEnable OBJECT-TYPE
    SYNTAX  INTEGER {
        enabled(1),
        disabled(2)
        }
    MAX-ACCESS  read-only
    STATUS  current
    DESCRIPTION
        "The system diskspace trap high sending enable/disable."
    ::= { agSysDiskConfig 9 }

agSysDiskNewCfgCriThreshold OBJECT-TYPE
    SYNTAX  INTEGER (1..100)
    MAX-ACCESS  read-write
    STATUS  current
    DESCRIPTION
        "The system diskspace trap critical threshold in %."
    ::= { agSysDiskConfig 10 }

agSysDiskNewCfgCriInterval OBJECT-TYPE
    SYNTAX  INTEGER (1..1440)
    MAX-ACCESS  read-write
    STATUS  current
    DESCRIPTION
        "The system diskspace trap critical interval in sec."
    ::= { agSysDiskConfig 11 }

agSysDiskNewCfgCriEnable OBJECT-TYPE
    SYNTAX  INTEGER {
        enabled(1),
        disabled(2)
        }
    MAX-ACCESS  read-write
    STATUS  current
    DESCRIPTION
        "The system diskspace trap critical sending enable/disable."
    ::= { agSysDiskConfig 12 }

agSysDiskNewCfgExtThreshold OBJECT-TYPE
    SYNTAX  INTEGER (1..100)
    MAX-ACCESS  read-write
    STATUS  current
    DESCRIPTION
        "The system diskspace trap exceeded high threshold in %."
    ::= { agSysDiskConfig 13 }

agSysDiskNewCfgExtInterval OBJECT-TYPE
    SYNTAX  INTEGER (1..1440)
    MAX-ACCESS  read-write
    STATUS  current
    DESCRIPTION
        "The system diskspace trap exceeded interval in sec."
    ::= { agSysDiskConfig 14 }

agSysDiskNewCfgExtEnable OBJECT-TYPE
    SYNTAX  INTEGER {
        enabled(1),
        disabled(2)
        }
    MAX-ACCESS  read-write
    STATUS  current
    DESCRIPTION
        "The system diskspace trap exceeded sending enable/disable."
    ::= { agSysDiskConfig 15 }

agSysDiskNewCfgHighThreshold OBJECT-TYPE
    SYNTAX  INTEGER (1..100)
    MAX-ACCESS  read-write
    STATUS  current
    DESCRIPTION
        "The system diskspace trap high threshold in %."
    ::= { agSysDiskConfig 16 }

agSysDiskNewCfgHighInterval OBJECT-TYPE
    SYNTAX  INTEGER (1..1440)
    MAX-ACCESS  read-write
    STATUS  current
    DESCRIPTION
        "The system diskspace trap high interval in sec."
    ::= { agSysDiskConfig 17 }

agSysDiskNewCfgHighEnable OBJECT-TYPE
    SYNTAX  INTEGER {
        enabled(1),
        disabled(2)
        }
    MAX-ACCESS  read-write
    STATUS  current
    DESCRIPTION
        "The system diskspace trap exceeded sending enable/disable."
    ::= { agSysDiskConfig 18 }

agSysCurUsedDiskspace OBJECT-TYPE
    SYNTAX  Integer32
    MAX-ACCESS  read-only
    STATUS  current
    DESCRIPTION
        "The system diskspace used in GB"
    ::= { agSysDiskConfig 19 }

agSysCurTotalDiskspace OBJECT-TYPE
    SYNTAX  Integer32
    MAX-ACCESS  read-only
    STATUS  current
    DESCRIPTION
        "The system diskspace total in MB"
    ::= { agSysDiskConfig 20 }

-- End system Diskspace Configuration

-- System AWS configuration

agAwsCurCfgAccessId OBJECT-TYPE
    SYNTAX   DisplayString (SIZE(0..127))
    MAX-ACCESS  read-only
    STATUS  current
    DESCRIPTION
        "Get AWS account ID, used to construct Amazon Resource Names (ARNs).
         Note: This MIB is only supported on VA platform."
    ::= { agSystemAws 1 }

agAwsCurCfgSecretAccessKey OBJECT-TYPE
    SYNTAX   DisplayString (SIZE(0..127))
    MAX-ACCESS  read-only
    STATUS  current
    DESCRIPTION
        "Set AWS account password.
         Note: This MIB is only supported on VA platform."
    ::= { agSystemAws 2 }

agAwsAssociatedIpTableMaxSize OBJECT-TYPE
    SYNTAX  Integer32
    MAX-ACCESS  read-only
    STATUS  current
    DESCRIPTION
        "The maximum number of ids in associated-ip table.
         Note: This MIB is only supported on VA platform."
    ::= { agSystemAws 3 }

agAwsCurCfgAssociatedIpTable OBJECT-TYPE
    SYNTAX  SEQUENCE OF AgAwsCurCfgAssociatedIpTableIdEntry
    MAX-ACCESS  not-accessible
    STATUS  current
    DESCRIPTION
        "Associated ip table of for AWS ha.
         Note: This MIB is only supported on VA platform."
    ::= { agSystemAws 4 }

agAwsCurCfgAssociatedIpTableIdEntry OBJECT-TYPE
    SYNTAX  AgAwsCurCfgAssociatedIpTableIdEntry
    MAX-ACCESS  not-accessible
    STATUS  current
    DESCRIPTION
        "A row in AWS ha associated ip table..
         Note: This MIB is only supported on VA platform."
    INDEX   { agAwsCurCfgAssociatedIpIndex }
    ::= { agAwsCurCfgAssociatedIpTable 1 }

AgAwsCurCfgAssociatedIpTableIdEntry ::= SEQUENCE {
    agAwsCurCfgAssociatedIpIndex       	INTEGER,
    agAwsCurCfgAssociatedIpPrivateIp    DisplayString,
    agAwsCurCfgAssociatedIpPeerIp     	DisplayString,
    agAwsCurCfgAssociatedIpFloatingIp   DisplayString
    }

agAwsCurCfgAssociatedIpIndex OBJECT-TYPE
    SYNTAX INTEGER
    MAX-ACCESS  read-only
    STATUS  current
    DESCRIPTION
        "AWS HA associated ip table index..
         Note: This MIB is only supported on VA platform."
    ::= { agAwsCurCfgAssociatedIpTableIdEntry 1 }


agAwsCurCfgAssociatedIpPrivateIp OBJECT-TYPE
    SYNTAX   DisplayString (SIZE(0..40))
    MAX-ACCESS  read-only
    STATUS  current
    DESCRIPTION
        "Get AWS Alteon private IP, as a part of HA associated IP set.
         Note: This MIB is only supported on VA platform."
    ::= { agAwsCurCfgAssociatedIpTableIdEntry 2 }

agAwsCurCfgAssociatedIpPeerIp OBJECT-TYPE
    SYNTAX   DisplayString (SIZE(0..40))
    MAX-ACCESS  read-only
    STATUS  current
    DESCRIPTION
        "Get AWS Alteon bachup(s) IP, as a part of HA associated IP set.
         Note: This MIB is only supported on VA platform."
    ::= { agAwsCurCfgAssociatedIpTableIdEntry 3 }

agAwsCurCfgAssociatedIpFloatingIp OBJECT-TYPE
    SYNTAX   DisplayString (SIZE(0..40))
    MAX-ACCESS  read-only
    STATUS  current
    DESCRIPTION
        "Get AWS Alteon floating/elastic IP, as a part of HA associated IP set.
         Note: This MIB is only supported on VA platform."
    ::= { agAwsCurCfgAssociatedIpTableIdEntry 4 }


agAwsNewCfgAccessId OBJECT-TYPE
    SYNTAX   DisplayString (SIZE(0..127))
    MAX-ACCESS  read-write
    STATUS  current
    DESCRIPTION
        "Set AWS account ID, used to construct Amazon Resource Names (ARNs).
         Note: This MIB is only supported on VA platform."
    ::= { agSystemAws 5 }

agAwsNewCfgSecretAccessKey OBJECT-TYPE
    SYNTAX   DisplayString (SIZE(0..255))
    MAX-ACCESS  read-write
    STATUS  current
    DESCRIPTION
        "Set AWS account password.
         Note: This MIB is only supported on VA platform."
    ::= { agSystemAws 6 }

agAwsNewCfgAssociatedIpTable OBJECT-TYPE
    SYNTAX  SEQUENCE OF AgAwsNewCfgAssociatedIpTableIdEntry
    MAX-ACCESS  not-accessible
    STATUS  current
    DESCRIPTION
        "Associated ip table of for AWS ha.
         Note: This MIB is only supported on VA platform."
    ::= { agSystemAws 7 }

agAwsNewCfgAssociatedIpTableIdEntry OBJECT-TYPE
    SYNTAX  AgAwsNewCfgAssociatedIpTableIdEntry
    MAX-ACCESS  not-accessible
    STATUS  current
    DESCRIPTION
        "A row in AWS ha associated ip table.
         Note: This MIB is only supported on VA platform."
    INDEX   { agAwsNewCfgAssociatedIpIndex }
    ::= { agAwsNewCfgAssociatedIpTable 1 }

AgAwsNewCfgAssociatedIpTableIdEntry ::= SEQUENCE {
    agAwsNewCfgAssociatedIpIndex       	INTEGER,
    agAwsNewCfgAssociatedIpPrivateIp    DisplayString,
    agAwsNewCfgAssociatedIpPeerIp     	DisplayString,
    agAwsNewCfgAssociatedIpFloatingIp   DisplayString,
    agAwsNewCfgAssociatedIpTableDelete  INTEGER
    }

agAwsNewCfgAssociatedIpIndex OBJECT-TYPE
    SYNTAX INTEGER
    MAX-ACCESS  read-write
    STATUS  current
    DESCRIPTION
        "AWS ha associated ip table index.
         Note: This MIB is only supported on VA platform."
    ::= { agAwsNewCfgAssociatedIpTableIdEntry 1 }


agAwsNewCfgAssociatedIpPrivateIp OBJECT-TYPE
    SYNTAX   DisplayString (SIZE(0..40))
    MAX-ACCESS  read-write
    STATUS  current
    DESCRIPTION
        "Set AWS Alteon private IP, as a part of HA associated IP set.
         Note: This MIB is only supported on VA platform."
    ::= { agAwsNewCfgAssociatedIpTableIdEntry 2 }

agAwsNewCfgAssociatedIpPeerIp OBJECT-TYPE
    SYNTAX   DisplayString (SIZE(0..40))
    MAX-ACCESS  read-write
    STATUS  current
    DESCRIPTION
        "Set AWS Alteon bachup(s) IP, as a part of HA associated IP set.
         Note: This MIB is only supported on VA platform."
    ::= { agAwsNewCfgAssociatedIpTableIdEntry 3 }

agAwsNewCfgAssociatedIpFloatingIp OBJECT-TYPE
    SYNTAX   DisplayString (SIZE(0..40))
    MAX-ACCESS  read-write
    STATUS  current
    DESCRIPTION
        "Set AWS Alteon floating/elastic IP, as a part of HA associated IP set.
         Note: This MIB is only supported on VA platform."
    ::= { agAwsNewCfgAssociatedIpTableIdEntry 4 }

agAwsNewCfgAssociatedIpTableDelete OBJECT-TYPE
    SYNTAX  INTEGER {
        other(1),
        delete(2),
        all(3)
    }
    MAX-ACCESS  read-write
    STATUS  current
    DESCRIPTION
        "By setting the value to delete(2), Delete a specific assiciated id table entry.
         Note: This MIB is only supported on VA platform."
    ::= { agAwsNewCfgAssociatedIpTableIdEntry 5 }






-- End of system AWS configuration

END
