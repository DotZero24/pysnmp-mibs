WSD-MIB DEFINITIONS ::= BEGIN

-- Title:      WSD specific MIB
--             This Private MIB supports WSD products
-- Version:    8.20
-- Date:       13 july 2004
-- By:         WMA (WSD MIB Authority)
-- E-mail:     support@radware.com
--
IMPORTS
	   InetAddress,
	   InetAddressType
			FROM INET-ADDRESS-MIB
       Ipv6Address
              FROM IPV6-TC
       NetworkAddress,
       IpAddress,
       Counter,
       Gauge,
       enterprises
              FROM RFC1155-SMI
      OBJECT-TYPE
              FROM RFC-1212
       DisplayString,
       PhysAddress,
       ipAddrEntry
              FROM RFC1213-MIB
       TRAP-TYPE
              FROM RFC-1215
       rsServerDispatcher,
       rsNWSD,
       rndErrorDesc,
       rndErrorSeverity,
       rsWSDThresholdWarnings,
       rdwrWSDCommon,
       BitFlag
              FROM RADWARE-MIB
       Unsigned32,
       Counter32,
	   Counter64
	      FROM SNMPv2-SMI
		bgp
					FROM BGP4-MIB;

    TruthValue ::= INTEGER {
         true (1),
         false (2)
        }
    RowStatus ::= INTEGER {
        active(1),
        notInService(2),
        notReady(3),
        createAndGo(4),
        createAndWait(5),
        destroy(6)
        }
    FeatureStatus ::= INTEGER {
         enable(1),
         disable(2)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

-- server table

rsWSDApplicationServersTable OBJECT-TYPE
    SYNTAX SEQUENCE OF RsWSDApplicationServerEntry
    ACCESS not-accessible
    STATUS mandatory
    DESCRIPTION
      "Table containing the list of application servers to which the
      clients requested are dispatched."
    ::=  {rsServerDispatcher 11}

rsWSDApplicationServerEntry OBJECT-TYPE
    SYNTAX RsWSDApplicationServerEntry
    ACCESS not-accessible
    STATUS  mandatory
    DESCRIPTION
       " The row definition for this table."
   INDEX { rsWSDAddr,
           rsWSDServerAddr,
           rsWSDMultiplexedServerPort }
    ::=  {rsWSDApplicationServersTable 1}

RsWSDApplicationServerEntry ::= SEQUENCE {
  rsWSDAddr                           IpAddress,
  rsWSDServerAddr                     IpAddress,
  rsWSDServerName                     DisplayString,
  rsWSDServerOperStatus               INTEGER,
  rsWSDServerWeight                   INTEGER,
  rsWSDServerAttachedUsersNumber      INTEGER,
  rsWSDServerPeakLoad                 INTEGER,
  rsWSDServerFramesRate               INTEGER,
  rsWSDServerFramesLoad               Counter,
  rsWSDServerStatus                   INTEGER,
  rsWSDServerOperMode                 INTEGER,
  rsWSDMultiplexedServerPort          INTEGER,
  rsWSDServerType                     INTEGER,
  rsWSDServerConnectionLimit          INTEGER,
  rsWSDServerAdminStatus              INTEGER,
  rsWSDServerBandWidth                INTEGER,
  rsWSDServerCckID                    INTEGER,
  rsWSDServerRedirectTo               DisplayString,
  rsWSDServerClientNATStatus          FeatureStatus,
  rsWSDServerDescription              DisplayString,
  rsWSDServerResponseThreshold        INTEGER,
  rsWSDServerBackupServerAddr         IpAddress,
  rsWSDServerBackupPreemption         FeatureStatus,
  rsWSDServerNATRangeIPFrom	          IpAddress,
  rsWSDFarmNameForLocalFarm           DisplayString,
  rsWSDServerInetAddress              InetAddress
 }

rsWSDAddr OBJECT-TYPE
    SYNTAX  IpAddress
    ACCESS  read-only
    STATUS  mandatory
    DESCRIPTION
     "WSD Virtual IP address"
 ::=  {rsWSDApplicationServerEntry 1}

rsWSDServerAddr  OBJECT-TYPE
    SYNTAX  IpAddress
    ACCESS  read-only
    STATUS  mandatory
    DESCRIPTION
     "Application  IP address"
 ::=  {rsWSDApplicationServerEntry 2 }

rsWSDServerName  OBJECT-TYPE
    SYNTAX DisplayString (SIZE(1..30))
    ACCESS  read-write
    STATUS  mandatory
    DESCRIPTION
      "The name assigned by the user to the server."
 ::=  {rsWSDApplicationServerEntry 3}

rsWSDServerOperStatus OBJECT-TYPE
    SYNTAX INTEGER {
      active(1),
      notInService(2),
      noNewSessions(3),
      inRecovery(4)
    }
    ACCESS  read-only
    STATUS  mandatory
    DESCRIPTION
      "Operational status of application on  server.
       active        - server is active
       notInService  - server is or will become inactive. Existing sessions
                       will be redirected to other servers.
       noNewSessions - server will receive no new sessions. Existing sessions
                       are allowed to complete."
 ::=  {rsWSDApplicationServerEntry 4 }

rsWSDServerWeight OBJECT-TYPE
    SYNTAX  INTEGER  (1..10000)
    ACCESS  read-write
    STATUS  mandatory
    DESCRIPTION
      "A numerical weight assigned by the user in order to impose some
       priority mechanism on the server dispatchers considerations of which
       server to choose for attaching a client ."
 ::=  {rsWSDApplicationServerEntry 5}

rsWSDServerAttachedUsersNumber OBJECT-TYPE
    SYNTAX  INTEGER
    ACCESS  read-only
    STATUS  mandatory
    DESCRIPTION
      "Number of currently active users attached to this server."
    ::=  {rsWSDApplicationServerEntry 6 }

rsWSDServerPeakLoad OBJECT-TYPE
    SYNTAX  INTEGER
    ACCESS  read-only
    STATUS  mandatory
    DESCRIPTION
      "Maximal number of frames per second dispatched to server
       since last reset."
    ::=  {rsWSDApplicationServerEntry 7}

rsWSDServerFramesRate OBJECT-TYPE
    SYNTAX  INTEGER
    ACCESS  read-only
    STATUS  mandatory
    DESCRIPTION
      "Number of frames per second dispatched to server."
    ::=  {rsWSDApplicationServerEntry 8}

rsWSDServerFramesLoad OBJECT-TYPE
    SYNTAX  Counter
    ACCESS  read-only
    STATUS  mandatory
    DESCRIPTION
      "Number of frames per second dispatched to server."
    ::=  {rsWSDApplicationServerEntry 9}

rsWSDServerStatus OBJECT-TYPE
    SYNTAX INTEGER {
        active(1),
        notInService(2),
        notReady(3),
        createAndGo(4),
        createAndWait(5),
        destroy(6) }
    ACCESS  read-write
    STATUS  mandatory
    DESCRIPTION
      "Administative status of appliaction on  server."
    ::=  {rsWSDApplicationServerEntry 10}

rsWSDServerOperMode OBJECT-TYPE
    SYNTAX INTEGER { regular(1), backup(2)}
    ACCESS  read-write
    STATUS  mandatory
    DESCRIPTION
      "This variable indicate the status of the server,
      the WSD will not send any messages to a backup server
      unless all other server are down  status.
      In case of more then one backup server, the WSD will decide  to which
      backup server to send the massages acordinf to rsWSDWeight."
    ::=  { rsWSDApplicationServerEntry 11}

rsWSDMultiplexedServerPort OBJECT-TYPE
    SYNTAX INTEGER (0..65535)
    ACCESS  read-only
    STATUS  mandatory
    DESCRIPTION
       "The port on which this server listens to the multiplexed port
        of its farm. Port 0 - no multiplexing on this server"
    ::= { rsWSDApplicationServerEntry 12 }

rsWSDServerType OBJECT-TYPE
    SYNTAX INTEGER {
      regular(1),
      distributed(2),
      remote(3),
      loopback(4),
      localFarm(5),
      localWSD(6)
    }
    ACCESS  read-write
    STATUS  mandatory
    DESCRIPTION
       "This variable indicates the server's type. Regular type servers
        have no other connection to the network except this WSD. Distributed
        type servers are remote WSDs. A remote type server is a server cpnnected
        to the network at a different entry point."
--  DEFVAL {regular}
    ::= { rsWSDApplicationServerEntry 13 }

rsWSDServerConnectionLimit OBJECT-TYPE
    SYNTAX INTEGER
    ACCESS  read-write
    STATUS  mandatory
    DESCRIPTION
      "The maximal number of client sessions which can be opened on this sever."
-- DEFVAL {0}
    ::= { rsWSDApplicationServerEntry 14 }

rsWSDServerAdminStatus OBJECT-TYPE
    SYNTAX INTEGER {
      enable(1),
      disable(2),
      shutdown(3)
          }
    ACCESS  read-write
    STATUS  mandatory
    DESCRIPTION
      "Administrative status of application on server.
       enable -   activates the server.
                  The rsWSDServerOperStatus will change to active.
       disable -  stops the server.
                  The rsWSDServerOperStatus will change to notInService.
       shutdown - gracefully shuts down the server.
                  The rsWSDServerOperStatus will change to noNewSessions."

 ::=  {rsWSDApplicationServerEntry 15 }

rsWSDServerBandWidth OBJECT-TYPE
    SYNTAX  INTEGER
    ACCESS  read-write
    STATUS  mandatory
    DESCRIPTION
      "Band width for server."
--  DEFVAL {0x7fffffff}
    ::=  {rsWSDApplicationServerEntry 16}

rsWSDServerCckID OBJECT-TYPE
    SYNTAX  INTEGER
    ACCESS  read-write
    STATUS  mandatory
    DESCRIPTION
      "Connectivity check module identifier."
    ::=  {rsWSDApplicationServerEntry 17}

rsWSDServerRedirectTo OBJECT-TYPE
    SYNTAX  DisplayString (SIZE(0..255))
    ACCESS  read-write
    STATUS  mandatory
    DESCRIPTION
      "String to be used by HTTP redirection."
    ::=  {rsWSDApplicationServerEntry 18}

rsWSDServerClientNATStatus OBJECT-TYPE
    SYNTAX FeatureStatus
    ACCESS  read-write
    STATUS  mandatory
    DESCRIPTION
      "enable or disable the NAT client feature for this server
       Default value is disable"
    DEFVAL { disable }
 ::=  {rsWSDApplicationServerEntry 19 }

rsWSDServerDescription  OBJECT-TYPE
    SYNTAX DisplayString (SIZE(0..80))
    ACCESS  read-write
    STATUS  mandatory
    DESCRIPTION
      "The user describe the server."
 ::=  {rsWSDApplicationServerEntry 20}

rsWSDServerResponseThreshold OBJECT-TYPE
    SYNTAX INTEGER (0..60000)
    ACCESS  read-write
    STATUS  mandatory
    DESCRIPTION
       "The amount of time (in milliseconds) that the server has to answer the client's request."
    DEFVAL {0}
    ::= { rsWSDApplicationServerEntry 21 }

rsWSDServerBackupServerAddr OBJECT-TYPE
    SYNTAX  IpAddress
    ACCESS  read-write
    STATUS  mandatory
    DESCRIPTION
     "Backup Server IP address"
 ::=  {rsWSDApplicationServerEntry 22}

rsWSDServerBackupPreemption OBJECT-TYPE
    SYNTAX FeatureStatus
    ACCESS  read-write
    STATUS  mandatory
    DESCRIPTION
     "Controls whether a regular server will preempt the backup server."
	DEFVAL  { enable }
	::=  {rsWSDApplicationServerEntry 23}


rsWSDServerNATRangeIPFrom OBJECT-TYPE
 SYNTAX IpAddress
    ACCESS  read-write
    STATUS  mandatory
    DESCRIPTION
 "choose beginning of existing range interval from NAT IP range table "
    ::=  {rsWSDApplicationServerEntry 24}

rsWSDFarmNameForLocalFarm  OBJECT-TYPE
    SYNTAX DisplayString (SIZE(0..50))
    ACCESS  read-write
    STATUS  mandatory
    DESCRIPTION
      "The name of Farm that is defined as local farm server."
 ::=  {rsWSDApplicationServerEntry 25}

 rsWSDServerInetAddress  OBJECT-TYPE
    SYNTAX  InetAddress
    ACCESS  read-write
    STATUS  mandatory
    DESCRIPTION
     "Server's IPv6 address"
    ::=  {rsWSDApplicationServerEntry 26}


-- AppDirector's server table

rsADApplicationServersTable OBJECT-TYPE
    SYNTAX SEQUENCE OF RsADApplicationServerEntry
    ACCESS not-accessible
    STATUS mandatory
    DESCRIPTION
      "Table containing the list of application servers to which the
      clients requested are dispatched."
    ::=  {rsServerDispatcher 136}

rsADApplicationServerEntry OBJECT-TYPE
    SYNTAX RsADApplicationServerEntry
    ACCESS not-accessible
    STATUS  mandatory
    DESCRIPTION
       " The row definition for this table."
    INDEX { rsADServerFarmName,
            rsADServerAddr,
            rsADServerPort }
    ::= {rsADApplicationServersTable 1}

RsADApplicationServerEntry ::= SEQUENCE {
  rsADServerFarmName                 DisplayString,
  rsADServerAddr                     IpAddress,
  rsADServerPort                     INTEGER,
  rsADServerStatus                   RowStatus,
  rsADServerName                     DisplayString,
  rsADServerAdminStatus              INTEGER,
  rsADServerOperStatus               INTEGER,
  rsADServerWeight                   INTEGER,
  rsADServerOperMode                 INTEGER,
  rsADServerType                     INTEGER,
  rsADServerConnectionLimit          INTEGER,
  rsADServerBandWidth                INTEGER,
  rsADServerCckID                    INTEGER,
  rsADServerRedirectTo               DisplayString,
  rsADServerClientNATStatus          FeatureStatus,
  rsADServerDescription              DisplayString,
  rsADServerResponseThreshold        INTEGER,
  rsADServerBackupServerAddr         IpAddress,
  rsADServerBackupPreemption         FeatureStatus,
  rsADServerNATRangeIPFrom	         IpAddress,
  rsADFarmNameForLocalFarm           DisplayString,
  rsADServerInetAddress              InetAddress
 }

rsADServerFarmName OBJECT-TYPE
    SYNTAX  DisplayString (SIZE(1..50))
    ACCESS  read-only
    STATUS  mandatory
    DESCRIPTION
     "Farm name to which this server belongs to."
    ::=  {rsADApplicationServerEntry 1}

rsADServerAddr  OBJECT-TYPE
    SYNTAX  IpAddress
    ACCESS  read-only
    STATUS  mandatory
    DESCRIPTION
     "Application  IP address"
    ::=  {rsADApplicationServerEntry 2 }

rsADServerPort OBJECT-TYPE
    SYNTAX INTEGER (0..65535)
    ACCESS  read-only
    STATUS  mandatory
    DESCRIPTION
        "The port on which the server is handling
        the application. Each port creates a
        different logical server instance and automatic
        port multiplexing is performed. Servers with no
        port (value 0) don't have a specific designated port.
        No multiplexing is done to it and it may handle any
        traffic to any destination port."
    ::= { rsADApplicationServerEntry 3 }

rsADServerStatus OBJECT-TYPE
    SYNTAX  RowStatus
    ACCESS  read-write
    STATUS  mandatory
    DESCRIPTION
      "Administative status of appliaction on  server."
    ::=  {rsADApplicationServerEntry 4}

rsADServerName  OBJECT-TYPE
    SYNTAX  DisplayString (SIZE(1..30))
    ACCESS  read-write
    STATUS  mandatory
    DESCRIPTION
      "The name assigned by the user to the server."
    ::=  {rsADApplicationServerEntry 5}

rsADServerAdminStatus OBJECT-TYPE
    SYNTAX INTEGER {
      enable(1),
      disable(2),
      connectionsShutdown(3),
      sessionsShutdown(4)
          }
    ACCESS  read-write
    STATUS  mandatory
    DESCRIPTION
      "Administrative status of application on server.
       enable -   activates the server.
                  The rsADServerOperStatus will change to active.
       disable -  stops the server.
                  The rsADServerOperStatus will change to notInService.
       connectionsShutdown - gracefully shuts down connections to the server by allowing existing connections to complete,
       			             while new connections are not forwarded to this server.
                  	         The rsADServerOperStatus will change to noNewSessions.
       sessionsShutdown - gracefully shuts down sessions to the server by allowing existing sessions to complete
       			         (new connections that match existing sessions on this server are still forwarded to the server), while new sessions are not forwarded to this server.
                  	      The rsADServerOperStatus will change to noNewSessions."


 ::=  {rsADApplicationServerEntry 6 }

rsADServerOperStatus OBJECT-TYPE
    SYNTAX INTEGER {
      active(1),
      notInService(2),
      noNewSessions(3),
      inRecovery(4)
    }
    ACCESS  read-only
    STATUS  mandatory
    DESCRIPTION
      "Operational status of application on  server.
       active        - server is active
       notInService  - server is or will become inactive. Existing sessions
                       will be redirected to other servers.
       noNewSessions - server will receive no new sessions. Existing sessions
                       are allowed to complete."
 ::=  {rsADApplicationServerEntry 7 }

rsADServerWeight OBJECT-TYPE
    SYNTAX  INTEGER  (1..10000)
    ACCESS  read-write
    STATUS  mandatory
    DESCRIPTION
      "A numerical weight assigned by the user in order to impose some
       priority mechanism on the server dispatchers considerations of which
       server to choose for attaching a client ."
    ::=  {rsADApplicationServerEntry 8}

rsADServerOperMode OBJECT-TYPE
    SYNTAX INTEGER { regular(1), backup(2)}
    ACCESS  read-write
    STATUS  mandatory
    DESCRIPTION
      "This variable indicate the status of the server,
      the AppDirector will not send any messages to a backup server
      unless all other server are down  status.
      In case of more then one backup server, the AppDirector will decide  to which
      backup server to send the messages acording to rsWSDWeight."
    ::=  { rsADApplicationServerEntry 9}

rsADServerType OBJECT-TYPE
    SYNTAX INTEGER {
      regular(1),
      distributed(2),
      remote(3),
      loopback(4),
      localFarm(5),
      localWSD(6)
    }
    ACCESS  read-write
    STATUS  mandatory
    DESCRIPTION
       "This variable indicates the server's type. Regular type servers
        have no other connection to the network except this WSD. Distributed
        type servers are remote WSDs. A remote type server is a server cpnnected
        to the network at a different entry point."
    DEFVAL {regular}
    ::= { rsADApplicationServerEntry 10 }

rsADServerConnectionLimit OBJECT-TYPE
    SYNTAX INTEGER
    ACCESS  read-write
    STATUS  mandatory
    DESCRIPTION
      "The maximal number of client sessions which can be opened on this sever."
   DEFVAL {0}
    ::= { rsADApplicationServerEntry 11 }

rsADServerBandWidth OBJECT-TYPE
    SYNTAX  INTEGER
    ACCESS  read-write
    STATUS  mandatory
    DESCRIPTION
      "Band width for server."
    DEFVAL {2147483647}
    ::=  {rsADApplicationServerEntry 12}

rsADServerCckID OBJECT-TYPE
    SYNTAX  INTEGER
    ACCESS  read-write
    STATUS  mandatory
    DESCRIPTION
      "Connectivity check module identifier."
    ::=  {rsADApplicationServerEntry 13}

rsADServerRedirectTo OBJECT-TYPE
    SYNTAX  DisplayString (SIZE(0..255))
    ACCESS  read-write
    STATUS  mandatory
    DESCRIPTION
      "String to be used by HTTP redirection."
    ::=  {rsADApplicationServerEntry 14}

rsADServerClientNATStatus OBJECT-TYPE
    SYNTAX FeatureStatus
    ACCESS  read-write
    STATUS  mandatory
    DESCRIPTION
      "enable or disable the NAT client feature for this server
       Default value is disable"
    DEFVAL { disable }
 ::=  {rsADApplicationServerEntry 15 }

rsADServerDescription  OBJECT-TYPE
    SYNTAX DisplayString (SIZE(0..80))
    ACCESS  read-write
    STATUS  mandatory
    DESCRIPTION
      "The user describe the server."
 ::=  {rsADApplicationServerEntry 16}

rsADServerResponseThreshold OBJECT-TYPE
    SYNTAX INTEGER (0..60000)
    ACCESS  read-write
    STATUS  mandatory
    DESCRIPTION
       "The amount of time (in milliseconds) that the server has to answer the client's request."
    DEFVAL {0}
    ::= { rsADApplicationServerEntry 17 }

rsADServerBackupServerAddr OBJECT-TYPE
    SYNTAX  IpAddress
    ACCESS  read-write
    STATUS  mandatory
    DESCRIPTION
     "Backup Server IP address"
 ::=  {rsADApplicationServerEntry 18}

rsADServerBackupPreemption OBJECT-TYPE
    SYNTAX FeatureStatus
    ACCESS  read-write
    STATUS  mandatory
    DESCRIPTION
     "Controls whether a regular server will preempt the backup server."
	DEFVAL  { enable }
	::=  {rsADApplicationServerEntry 19}


rsADServerNATRangeIPFrom OBJECT-TYPE
 SYNTAX IpAddress
    ACCESS  read-write
    STATUS  mandatory
    DESCRIPTION
        "choose beginning of existing range interval from NAT IP range table "
    ::=  {rsADApplicationServerEntry 20}

rsADFarmNameForLocalFarm  OBJECT-TYPE
    SYNTAX  DisplayString (SIZE(0..50))
    ACCESS  read-write
    STATUS  mandatory
    DESCRIPTION
      "The name of Farm that is defined as local farm server."
    ::=  {rsADApplicationServerEntry 21}

rsADServerInetAddress  OBJECT-TYPE
    SYNTAX  InetAddress
    ACCESS  read-write
    STATUS  mandatory
    DESCRIPTION
     "Server's IPv6 address"
    ::=  {rsADApplicationServerEntry 22 }

rsNADServerTable  OBJECT-TYPE
    SYNTAX SEQUENCE OF RsNADServerEntry
    ACCESS not-accessible
    STATUS mandatory
    DESCRIPTION
      "Table containing the list of application servers to which the
      clients requested are dispatched."
    ::=  {rsServerDispatcher 166}

rsNADServerEntry OBJECT-TYPE
    SYNTAX RsNADServerEntry
    ACCESS not-accessible
    STATUS  mandatory
    DESCRIPTION
       " The row definition for this table."
    INDEX { rsNADServerFarmName,
            rsNADServerName }
    ::= {rsNADServerTable 1}

RsNADServerEntry ::= SEQUENCE {
  rsNADServerFarmName                 DisplayString,
  rsNADServerName                     DisplayString,
  rsNADServerAddrType                 InetAddressType,
  rsNADServerAddr                     InetAddress,
  rsNADServerPort                     INTEGER,
  rsNADPhysicalServerName             DisplayString,
  rsNADServerDescription              DisplayString,
  rsNADServerAdminStatus              INTEGER,
  rsNADServerOperStatus               INTEGER,
  rsNADServerWeight                   INTEGER,
  rsNADServerOperMode                 INTEGER,
  rsNADServerType                     INTEGER,
  rsNADServerBackupServerAddrType     InetAddressType,
  rsNADServerBackupServerAddr         InetAddress,
  rsNADServerConnectionLimit          INTEGER,
  rsNADServerCckID                    INTEGER,
  rsNADServerRedirectTo               DisplayString,
  rsNADServerClientNATStatus          FeatureStatus,
  rsNADServerNATRangeIPFromType       InetAddressType,
  rsNADServerNATRangeIPFrom	          InetAddress,
  rsNADServerBandWidth                INTEGER,
  rsNADServerResponseThreshold        INTEGER,
  rsNADServerBackupPreemption         FeatureStatus,
  rsNADServerLocalFarmName            DisplayString,
  rsNADServerStatus                   RowStatus
 }

rsNADServerFarmName OBJECT-TYPE
    SYNTAX  DisplayString (SIZE(1..50))
    ACCESS  read-only
    STATUS  mandatory
    DESCRIPTION
     "Farm name to which this server belongs to."
    ::=  {rsNADServerEntry 1}

rsNADServerName  OBJECT-TYPE
    SYNTAX  DisplayString (SIZE(1..30))
    ACCESS  read-only
    STATUS  mandatory
    DESCRIPTION
      "The name assigned by the user to the server."
    ::=  {rsNADServerEntry 2}

rsNADServerAddrType  OBJECT-TYPE
    SYNTAX  InetAddressType
    ACCESS  read-write
    STATUS  mandatory
    DESCRIPTION
     "The type of server IP address"
	 DEFVAL { ipv4 }
    ::=  {rsNADServerEntry 3 }

rsNADServerAddr  OBJECT-TYPE
    SYNTAX  InetAddress
    ACCESS  read-write
    STATUS  mandatory
    DESCRIPTION
     "Application  IP address"
	DEFVAL {"0.0.0.0"}
    ::=  {rsNADServerEntry 4 }

rsNADServerPort OBJECT-TYPE
    SYNTAX INTEGER (0..65535)
    ACCESS  read-write
    STATUS  optional
    DESCRIPTION
        "The port on which the server is handling
        the application. Each port creates a
        different logical server instance and automatic
        port multiplexing is performed. Servers with no
        port (value 0) don't have a specific designated port.
        No multiplexing is done to it and it may handle any
        traffic to any destination port."
	DEFVAL{0}
    ::= { rsNADServerEntry 5 }

rsNADPhysicalServerName  OBJECT-TYPE
    SYNTAX  DisplayString (SIZE(1..30))
    ACCESS  read-write
    STATUS  mandatory
    DESCRIPTION
      	"The name of the physical server which this application server belongs to"
    ::=  {rsNADServerEntry 6}

rsNADServerDescription  OBJECT-TYPE
    SYNTAX DisplayString (SIZE(0..80))
    ACCESS  read-write
    STATUS  optional
    DESCRIPTION
      "The user describe the server."
 ::=  {rsNADServerEntry 7}

rsNADServerAdminStatus OBJECT-TYPE
    SYNTAX INTEGER {
      enable(1),
      disable(2),
      connectionsShutdown(3),
      sessionsShutdown(4)
          }
    ACCESS  read-write
    STATUS  optional
    DESCRIPTION
      "Administrative status of application on server.
       enable -   activates the server.
                  The rsNADServerOperStatus will change to active.
       disable -  stops the server.
                  The rsNADServerOperStatus will change to notInService.
       connectionsShutdown - gracefully shuts down connections to the server by allowing existing connections to complete,
       			             while new connections are not forwarded to this server.
                  	         The rsADServerOperStatus will change to noNewSessions.
       sessionsShutdown - gracefully shuts down sessions to the server by allowing existing sessions to complete
       			         (new connections that match existing sessions on this server are still forwarded to the server), while new sessions are not forwarded to this server.
                  	      The rsADServerOperStatus will change to noNewSessions."
	DEFVAL{enable}
 ::=  {rsNADServerEntry 8 }

rsNADServerOperStatus OBJECT-TYPE
    SYNTAX INTEGER {
      active(1),
      notInService(2),
      noNewSessions(3),
      inRecovery(4)
    }
    ACCESS  read-only
    STATUS  optional
    DESCRIPTION
      "Operational status of application on  server.
       active        - server is active
       notInService  - server is or will become inactive. Existing sessions
                       will be redirected to other servers.
       noNewSessions - server will receive no new sessions. Existing sessions
                       are allowed to complete.
       inRecovery    - Server is active yet does not handle traffic until configured Recovery Time is over."
 ::=  {rsNADServerEntry 9 }

rsNADServerWeight OBJECT-TYPE
    SYNTAX  INTEGER  (1..10000)
    ACCESS  read-write
    STATUS  optional
    DESCRIPTION
      "A numerical weight assigned by the user in order to impose some
       priority mechanism on the server dispatchers considerations of which
       server to choose for attaching a client ."
	DEFVAL{1}
    ::=  {rsNADServerEntry 10}

rsNADServerOperMode OBJECT-TYPE
    SYNTAX INTEGER { regular(1), backup(2)}
    ACCESS  read-write
    STATUS  optional
    DESCRIPTION
      "This variable indicate the status of the server,
      the AppDirector will not send any messages to a backup server
      unless all other server are down  status.
      In case of more then one backup server, the AppDirector will decide  to which
      backup server to send the messages acording to rsNADServerWeight."
	DEFVAL{1}
    ::=  { rsNADServerEntry 11}

rsNADServerType OBJECT-TYPE
    SYNTAX INTEGER {
      regular(1),
      distributed(2),
      remote(3),
      loopback(4),
      localFarm(5),
      localWSD(6)
    }
    ACCESS  read-write
    STATUS  optional
    DESCRIPTION
       "This variable indicates the server's type. Regular type servers
        have no other connection to the network except this AppDirector. Distributed
        type servers are remote AppDirectors. A remote type server is a server cpnnected
        to the network at a different entry point."
    DEFVAL {regular}
    ::= { rsNADServerEntry 12 }

rsNADServerBackupServerAddrType OBJECT-TYPE
    SYNTAX  InetAddressType
    ACCESS  read-write
    STATUS  optional
    DESCRIPTION
     "Backup Server Address Type"
	 DEFVAL { ipv4 }
 ::=  {rsNADServerEntry 13}

rsNADServerBackupServerAddr OBJECT-TYPE
    SYNTAX  InetAddress
    ACCESS  read-write
    STATUS  optional
    DESCRIPTION
     "Backup Server Address"
	DEFVAL {"0.0.0.0"}
 ::=  {rsNADServerEntry 14}

rsNADServerConnectionLimit OBJECT-TYPE
    SYNTAX INTEGER
    ACCESS  read-write
    STATUS  optional
    DESCRIPTION
      "The maximal number of client sessions which can be opened on this sever."
   DEFVAL {0}
    ::= { rsNADServerEntry 15 }

rsNADServerCckID OBJECT-TYPE
    SYNTAX  INTEGER
    ACCESS  read-write
    STATUS  optional
    DESCRIPTION
      "Connectivity check module identifier."
    ::=  {rsNADServerEntry 16}

rsNADServerRedirectTo OBJECT-TYPE
    SYNTAX  DisplayString (SIZE(0..255))
    ACCESS  read-write
    STATUS  optional
    DESCRIPTION
      "String to be used by HTTP redirection."
    ::=  {rsNADServerEntry 17}

rsNADServerClientNATStatus OBJECT-TYPE
    SYNTAX FeatureStatus
    ACCESS  read-write
    STATUS  optional
    DESCRIPTION
      "enable or disable the NAT client feature for this server
       Default value is disable"
    DEFVAL { disable }
 ::=  {rsNADServerEntry 18 }

rsNADServerNATRangeIPFromType  OBJECT-TYPE
    SYNTAX  InetAddressType
    ACCESS  read-write
    STATUS  optional
    DESCRIPTION
     "The type of the range address"
	 DEFVAL { ipv4 }
    ::=  {rsNADServerEntry 19}

rsNADServerNATRangeIPFrom OBJECT-TYPE
 SYNTAX InetAddress
    ACCESS  read-write
    STATUS  optional
    DESCRIPTION
        "choose beginning of existing range interval from NAT IP range table "
	DEFVAL {"0.0.0.0"}
    ::=  {rsNADServerEntry 20}

rsNADServerBandWidth OBJECT-TYPE
    SYNTAX  INTEGER
    ACCESS  read-write
    STATUS  optional
    DESCRIPTION
      "Band width for server in Kb."
    DEFVAL {2147483647}
    ::=  {rsNADServerEntry 21}

rsNADServerResponseThreshold OBJECT-TYPE
    SYNTAX INTEGER (0..60000)
    ACCESS  read-write
    STATUS  optional
    DESCRIPTION
       "The amount of time (in milliseconds) that the server has to answer the client's request."
    DEFVAL {0}
    ::= { rsNADServerEntry 22}

rsNADServerBackupPreemption OBJECT-TYPE
    SYNTAX FeatureStatus
    ACCESS  read-write
    STATUS  optional
    DESCRIPTION
     "Controls whether a regular server will preempt the backup server."
	DEFVAL  { enable }
	::=  {rsNADServerEntry 23}

rsNADServerLocalFarmName  OBJECT-TYPE
    SYNTAX  DisplayString (SIZE(0..50))
    ACCESS  read-write
    STATUS  optional
    DESCRIPTION
      "The name of Farm that is defined as local farm server."
    ::=  {rsNADServerEntry 24}

rsNADServerStatus OBJECT-TYPE
    SYNTAX  RowStatus
    ACCESS  read-write
    STATUS  mandatory
    DESCRIPTION
       "This variable indicates the administrative status of this entry.
        Used to delete an entry of this table."
    ::=  {rsNADServerEntry 25}


-- farm table
rsWSDFarmTable OBJECT-TYPE
   SYNTAX SEQUENCE OF RsWSDFarmEntry
   ACCESS not-accessible
   STATUS mandatory
   DESCRIPTION
          "In this table the WSD saves the general parameters per
           server farme IP Addr."
   ::= {rsServerDispatcher 13}

rsWSDFarmEntry OBJECT-TYPE
    SYNTAX RsWSDFarmEntry
    ACCESS not-accessible
    STATUS  mandatory
    DESCRIPTION
       " The row definition for this table."
   INDEX  {rsWSDFarmAddress}
   ::= {rsWSDFarmTable 1}


RsWSDFarmEntry  ::= SEQUENCE {
  rsWSDFarmAddress                       IpAddress,
  rsWSDFarmName                          DisplayString,
  rsWSDAdminStatus                       FeatureStatus,
  rsWSDClientsLifeTime                   INTEGER,
  rsWSDDispatchMethod                    INTEGER,
  rsWSDCheckConnectivityStatus           INTEGER,
  rsWSDCheckConnectivityMethod           INTEGER,
  rsWSDCheckConnectivityInterval         INTEGER,
  rsWSDCheckConnectivityRetries          INTEGER,
  rsWSDClientsConnectDenials             Counter,
  rsWSDFarmStatus                        INTEGER,
  rsWSDMultiplexedFarmPort               INTEGER,
  rsWSDFarmDistThreshold                 INTEGER,
  rsWSDFarmTrafficThreshold              INTEGER,
  rsWSDFarmRedirectionMode               INTEGER,
  rsNsdFarmRegister                      FeatureStatus,
  rsWSDFarmMode                          INTEGER,
  rsWSDExtendedConnectivityCheckInterval INTEGER,
  rsWSDConnectivityCheckUrl              DisplayString,
  rsWSDFarmClientMode                    INTEGER,
  rsWSDDNSRedir2ndMode                   INTEGER,
  rsWSDFarmHttpRedirectionMode           INTEGER,
  rsWSDFarmOperStatus                    INTEGER,
  rsWSDFarmBandWidth                     INTEGER,
  rsWSDFarmSidKey                        DisplayString,
  rsWSDConnCheckUserName                 DisplayString,
  rsWSDConnCheckPassword                 DisplayString
 }

rsWSDFarmAddress OBJECT-TYPE
    SYNTAX IpAddress
    ACCESS  read-only
    STATUS  mandatory
    DESCRIPTION
      "The IP Address of the WEB farm."
    ::= {rsWSDFarmEntry 1}

rsWSDFarmName OBJECT-TYPE
    SYNTAX DisplayString (SIZE(1..50))
    ACCESS  read-write
    STATUS  mandatory
    DESCRIPTION
      "The name assigned by the user to this WEB farm."
    ::= {rsWSDFarmEntry 2}

rsWSDAdminStatus  OBJECT-TYPE
    SYNTAX FeatureStatus
    ACCESS  read-write
    STATUS  mandatory
    DESCRIPTION
      "Enable/Disable server dispatcher."
    ::=  {rsWSDFarmEntry 3}

rsWSDClientsLifeTime OBJECT-TYPE
    SYNTAX  INTEGER
    ACCESS  read-write
    STATUS  mandatory
    DESCRIPTION
      "Maximal period of time in seconds a non-active client is kept
      in the clients table."
--  DEFVAL  { 60 }
    ::=  {rsWSDFarmEntry 4}

  rsWSDDispatchMethod OBJECT-TYPE
    SYNTAX INTEGER {
      cyclic(1),
      leastTraffic(2),
      leastUsersNumber(3),
      leastTrafficLocal(4),
      leastUsersNumberLocal(5),
      nt-1(6),
      nt-2(7),
      private-1(8),
      private-2(9),
      weightedCyclic(10),
      static(11),
      cck-stats(12)
   }
    ACCESS  read-write
    STATUS  mandatory
    DESCRIPTION
      "Type of dispatching required."
    ::=  {rsWSDFarmEntry 5}

  rsWSDCheckConnectivityStatus OBJECT-TYPE
    SYNTAX INTEGER {
		ping(1),
		disable(2),
    http(3),
		tcp(4),
		udp(5)
   }
    ACCESS  read-write
    STATUS  mandatory
    DESCRIPTION
     	 "Connectivity check method."
--  DEFVAL  { 1 }
    ::=  {rsWSDFarmEntry 6}

  rsWSDCheckConnectivityMethod OBJECT-TYPE
    SYNTAX INTEGER
    ACCESS  read-write
    STATUS  mandatory
    DESCRIPTION
     	 "Application port for TCP or UDP connectivity check."
--  DEFVAL  { 80 }
    ::=  {rsWSDFarmEntry 7}

  rsWSDCheckConnectivityInterval OBJECT-TYPE
    SYNTAX  INTEGER  (1..3600)
    ACCESS  read-write
    STATUS  mandatory
    DESCRIPTION
      "Polling interval in seconds for servers polling."
--  DEFVAL  { 10 }
    ::=  {rsWSDFarmEntry 8}

  rsWSDCheckConnectivityRetries OBJECT-TYPE
    SYNTAX  INTEGER  (1..20)
    ACCESS  read-write
    STATUS  mandatory
    DESCRIPTION
      "This variable indicate the Minimal number of unsuccessful polling
       attempts before considering a server disconnected."
--  DEFVAL  { 5 }
    ::=  {rsWSDFarmEntry 9}

  rsWSDClientsConnectDenials OBJECT-TYPE
    SYNTAX Counter
    ACCESS  read-only
    STATUS  mandatory
    DESCRIPTION
      "This variable indicate the Number of connection requests from clients
       that were denied by the the server dispatcher."
    ::=  {rsWSDFarmEntry 10}

  rsWSDFarmStatus OBJECT-TYPE
      SYNTAX INTEGER {
        active(1),
        notInService(2),
        notReady(3),
        createAndGo(4),
        createAndWait(5),
        destroy(6) }
    ACCESS  read-write
    STATUS  mandatory
    DESCRIPTION
      "This variable indicate the Administative status of this entry.
       Use for delete an entry in this table."
  ::=  {rsWSDFarmEntry 11}

  rsWSDMultiplexedFarmPort OBJECT-TYPE
    SYNTAX INTEGER (0..65535)
    ACCESS  read-write
    STATUS  mandatory
    DESCRIPTION
       "The port on this farm's virtual IP for which port
        multiplexing is enabled. Port 0 - multiplexing is disabled"
--  DEFVAL {0}
    ::= { rsWSDFarmEntry 12 }

rsWSDFarmDistThreshold OBJECT-TYPE
    SYNTAX INTEGER
    ACCESS  read-write
    STATUS  mandatory
    DESCRIPTION
       "This variable indicates the treshold above which the WSD starts
       distributing traffic to distributed WSDs. The significance of this
       parameter varies according to the load balancing algorithm chosen."
--  DEFVAL {1000}
    ::= { rsWSDFarmEntry 13 }

rsWSDFarmTrafficThreshold  OBJECT-TYPE
    SYNTAX INTEGER
    ACCESS  read-write
    STATUS  mandatory
    DESCRIPTION
       "This variable indicates the treshold above which the WSD signals
       to all the distributed WSDs not to send traffic to it."
--  DEFVAL {5000}
    ::= { rsWSDFarmEntry 14 }

rsWSDFarmRedirectionMode  OBJECT-TYPE
    SYNTAX INTEGER { httpRedirection(1),
                     triangleRedirection(2),
                     noRedirection(3),
                     httpAndTriangleRedirection(4),
                     dnsRedirection(5),
                     dnsReevaluationRedirection(6),
                     rtspRedirection(7)}
    ACCESS  read-write
    STATUS  mandatory
    DESCRIPTION
       "This variable indicates if redirection is enabled and if enable
        which redirection mode is established (http, triangle or dns redirection).
        If redirection is disabled (i.e. -noRedirection), HTTP traffic is
        handled as all other traffic."
--      DEFVAL {enable}
    ::= { rsWSDFarmEntry 15 }


rsNsdFarmRegister  OBJECT-TYPE
    SYNTAX FeatureStatus
    ACCESS  read-write
    STATUS  mandatory
    DESCRIPTION
        "Enable/Disable farm's registration in the WINS server."
--  DEFVAL  { enable }
    ::=  {rsWSDFarmEntry 16}

rsWSDFarmMode OBJECT-TYPE
    SYNTAX INTEGER {
           regular(1),
           backup(2)
    }
    ACCESS  read-write
    STATUS  mandatory
    DESCRIPTION
        "This variable indicate the mode of this farm weather
         its my farm or farm of my main WSD which this
         WSD make redundancy"
--  DEFVAL { 1 }
    ::= { rsWSDFarmEntry 17 }

rsWSDExtendedConnectivityCheckInterval OBJECT-TYPE
    SYNTAX  INTEGER
    ACCESS  read-write
    STATUS  mandatory
    DESCRIPTION
        "The frequency at which an extended http check will be sent if
         rsWSDCheckConnectivityMethod is equal to 2. After this number of
         normal http checks a extended http check will be performed."
--  DEFVAL  { 10 }
    ::=  {rsWSDFarmEntry 18}

rsWSDConnectivityCheckUrl OBJECT-TYPE
    SYNTAX DisplayString (SIZE(0..255))
    ACCESS  read-write
    STATUS  mandatory
    DESCRIPTION
        "The absolute path of the web page to be requested in the extended
         connectivity check. Example: ~smith/home.html    "
--  DEFVAL  ( "" )
    ::= {rsWSDFarmEntry 19}

rsWSDFarmClientMode  OBJECT-TYPE
    SYNTAX INTEGER {
      regular(1),
      entryPerSession(2),
      serverPerSession(3),
      removeEntryAtSessionEnd(4),
      removeEntryAtSessionEndForServerPerSession(5)
   }
    ACCESS  read-write
    STATUS  mandatory
    DESCRIPTION
      "Client mode for this farm. How a single client's sessions are handled in the client table.
       Regular: all sessions to the same server, differentiated by destination port.
       EntryPerSession: all sessions to the same server, differentiated by both ports.
       ServerPerSession: new server selected for every session.
       RemoveEntry: extends EntryPerSession by removing terminated TCP sessions.
       RemoveServerPerSession: extends ServerPerSession to remove terminated TCP sessions."
    DEFVAL  { 2 }
    ::=  {rsWSDFarmEntry 20}

rsWSDDNSRedir2ndMode  OBJECT-TYPE
    SYNTAX INTEGER {
      httpAndTriangle(1),
      http(2),
      triangulation(3),
      dnsOnly(4)
   }
    ACCESS  read-write
    STATUS  mandatory
    DESCRIPTION
      "Secondary choice to be used with DNS redirection, in case that a client tries to connect to the
        virtual IP although it can not receive local service."
    DEFVAL  { 1 }
    ::=  {rsWSDFarmEntry 21}

rsWSDFarmHttpRedirectionMode OBJECT-TYPE
    SYNTAX INTEGER {
       ipMode (1),
       nameMode (2)
     }
    ACCESS  read-write
    STATUS  mandatory
    DESCRIPTION
      "Http redirection mode : IP address redirection mode or URL address redirection mode."
--  DEFVAL { 1 }
    ::= {rsWSDFarmEntry 22}

rsWSDFarmOperStatus OBJECT-TYPE
    SYNTAX INTEGER {
        active(1),
        notInService(2)
      }
    ACCESS  read-only
    STATUS  mandatory
    DESCRIPTION
      "Farm status. Active - farm is active. NotInService - service is not
       available."
    ::= {rsWSDFarmEntry 23}

rsWSDFarmBandWidth OBJECT-TYPE
    SYNTAX INTEGER
    ACCESS  read-write
    STATUS  mandatory
    DESCRIPTION
      "Band width for farm."
--  DEFVAL   {0x7fffffff}
    ::= {rsWSDFarmEntry 24}


rsWSDFarmSidKey OBJECT-TYPE
   SYNTAX DisplayString (SIZE(0..63))
   ACCESS  read-write
   STATUS  mandatory
   DESCRIPTION
     "String representing the session ID to look for. A value
      also indicates that the farm does session-id based persistency."
   ::= {rsWSDFarmEntry 25}

rsWSDConnCheckUserName OBJECT-TYPE
   SYNTAX DisplayString (SIZE(0..20))
   ACCESS  read-write
   STATUS  mandatory
   DESCRIPTION
     "Username used for extended connectivity checks."
   ::= {rsWSDFarmEntry 26}

rsWSDConnCheckPassword OBJECT-TYPE
   SYNTAX DisplayString (SIZE(0..20))
   ACCESS  read-write
   STATUS  mandatory
   DESCRIPTION
     "Password used for extended connectivity checks."
   ::= {rsWSDFarmEntry 27}

-- AppDirector farm table
rsADFarmTable OBJECT-TYPE
   SYNTAX SEQUENCE OF RsADFarmEntry
   ACCESS not-accessible
   STATUS mandatory
   DESCRIPTION
          "In this table the AppDirector saves the general parameters per
           server farm."
   ::= {rsServerDispatcher 135}

rsADFarmEntry OBJECT-TYPE
    SYNTAX RsADFarmEntry
    ACCESS not-accessible
    STATUS  mandatory
    DESCRIPTION
       " The row definition for this table."
   INDEX  {rsADFarmName}
   ::= {rsADFarmTable 1}

RsADFarmEntry  ::= SEQUENCE {
  rsADFarmName                          DisplayString,
  rsADFarmStatus                        RowStatus,
  rsADAdminStatus                       FeatureStatus,
  rsADFarmOperStatus                    INTEGER,
  rsADClientsLifeTime                   INTEGER,
  rsADDispatchMethod                    INTEGER,
  rsADCheckConnectivityStatus           INTEGER,
  rsADCheckConnectivityMethod           INTEGER,
  rsADCheckConnectivityInterval         INTEGER,
  rsADCheckConnectivityRetries          INTEGER,
  rsADClientsConnectDenials             Counter,
  rsADExtendedConnectivityCheckInterval INTEGER,
  rsADConnectivityCheckUrl              DisplayString,
  rsADFarmClientMode                    INTEGER,
  rsADFarmBandWidth                     INTEGER,
  rsADFarmSidKey                        DisplayString,
  rsADConnCheckUserName                 DisplayString,
  rsADConnCheckPassword                 DisplayString,
  rsADFarmContent                       INTEGER
 }

rsADFarmName OBJECT-TYPE
    SYNTAX DisplayString (SIZE(1..50))
    ACCESS  read-only
    STATUS  mandatory
    DESCRIPTION
      "The name assigned by the user to this WEB farm."
    ::= {rsADFarmEntry 1}

rsADFarmStatus OBJECT-TYPE
    SYNTAX  RowStatus
    ACCESS  read-write
    STATUS  mandatory
    DESCRIPTION
      "This variable indicates the Administative status of this entry.
       Use for deleting an entry in this table."
  ::=  {rsADFarmEntry 2}

rsADAdminStatus  OBJECT-TYPE
    SYNTAX  FeatureStatus
    ACCESS  read-write
    STATUS  mandatory
    DESCRIPTION
      "Enable/Disable server dispatcher."
    ::=  {rsADFarmEntry 3}

rsADFarmOperStatus OBJECT-TYPE
    SYNTAX INTEGER {
        active(1),
        notInService(2)
      }
    ACCESS  read-only
    STATUS  mandatory
    DESCRIPTION
      "Farm status. Active - farm is active. NotInService - service is not
       available."
    ::= {rsADFarmEntry 4}

rsADClientsLifeTime OBJECT-TYPE
    SYNTAX  INTEGER
    ACCESS  read-write
    STATUS  mandatory
    DESCRIPTION
      "Maximal period of time in seconds a non-active client is kept
      in the clients table."
    DEFVAL  { 60 }
    ::=  {rsADFarmEntry 5}

rsADDispatchMethod OBJECT-TYPE
    SYNTAX INTEGER {
      cyclic(1),
      leastTraffic(2),
      leastUsersNumber(3),
      leastTrafficLocal(4),
      leastUsersNumberLocal(5),
      nt-1(6),
      nt-2(7),
      private-1(8),
      private-2(9),
      weightedCyclic(10),
      static(11),
      cck-stats(12)
   }
    ACCESS  read-write
    STATUS  mandatory
    DESCRIPTION
      "Type of dispatching required."
    ::=  {rsADFarmEntry 6}

rsADCheckConnectivityStatus OBJECT-TYPE
    SYNTAX INTEGER {
  		ping(1),
  		disable(2),
        http(3),
		tcp(4),
		udp(5)
    }
    ACCESS  read-write
    STATUS  mandatory
    DESCRIPTION
     	 "Connectivity check method."
    DEFVAL  { 1 }
    ::=  {rsADFarmEntry 7}

rsADCheckConnectivityMethod OBJECT-TYPE
    SYNTAX INTEGER
    ACCESS  read-write
    STATUS  mandatory
    DESCRIPTION
     	 "Application port for TCP or UDP connectivity check."
    DEFVAL  { 80 }
    ::=  {rsADFarmEntry 8}

rsADCheckConnectivityInterval OBJECT-TYPE
    SYNTAX  INTEGER  (1..3600)
    ACCESS  read-write
    STATUS  mandatory
    DESCRIPTION
      "Polling interval in seconds for servers polling."
    DEFVAL  { 10 }
    ::=  {rsADFarmEntry 9}

rsADCheckConnectivityRetries OBJECT-TYPE
    SYNTAX  INTEGER  (1..20)
    ACCESS  read-write
    STATUS  mandatory
    DESCRIPTION
      "This variable indicate the Minimal number of unsuccessful polling
       attempts before considering a server disconnected."
    DEFVAL  { 5 }
    ::=  {rsADFarmEntry 10}

rsADClientsConnectDenials OBJECT-TYPE
    SYNTAX Counter
    ACCESS  read-only
    STATUS  mandatory
    DESCRIPTION
      "This variable indicates the Number of connection requests from clients
       that were denied by the the server dispatcher."
    ::=  {rsADFarmEntry 11}

rsADExtendedConnectivityCheckInterval OBJECT-TYPE
    SYNTAX  INTEGER  (0..50)
    ACCESS  read-write
    STATUS  mandatory
    DESCRIPTION
        "The frequency at which an extended http check will be sent if
         rsADCheckConnectivityMethod is equal to 2. After this number of
         normal http checks a extended http check will be performed."
    DEFVAL  { 10 }
    ::=  {rsADFarmEntry 12}

rsADConnectivityCheckUrl OBJECT-TYPE
    SYNTAX DisplayString (SIZE(0..255))
    ACCESS  read-write
    STATUS  mandatory
    DESCRIPTION
        "The absolute path of the web page to be requested in the extended
         connectivity check. Example: ~smith/home.html    "
--  DEFVAL  ( "" )
    ::= {rsADFarmEntry 13}

rsADFarmClientMode  OBJECT-TYPE
    SYNTAX INTEGER {
      regular(1),
      entryPerSession(2),
      serverPerSession(3),
      removeEntryAtSessionEnd(4),
      removeEntryAtSessionEndForServerPerSession(5)
   }
    ACCESS  read-write
    STATUS  mandatory
    DESCRIPTION
      "Client mode for this farm. How a single client's sessions are handled in the client table.
       Regular: all sessions to the same server, differentiated by destination port.
       EntryPerSession: all sessions to the same server, differentiated by both ports.
       ServerPerSession: new server selected for every session.
       RemoveEntry: extends EntryPerSession by removing terminated TCP sessions.
       RemoveServerPerSession: extends ServerPerSession to remove terminated TCP sessions."
    DEFVAL  { 2 }
    ::= {rsADFarmEntry 14}

rsADFarmBandWidth OBJECT-TYPE
    SYNTAX INTEGER
    ACCESS  read-write
    STATUS  mandatory
    DESCRIPTION
      "Band width for farm."
    DEFVAL   {2147483647}
    ::= {rsADFarmEntry 15}

rsADFarmSidKey OBJECT-TYPE
    SYNTAX DisplayString (SIZE(0..63))
    ACCESS  read-write
    STATUS  mandatory
    DESCRIPTION
      "String representing the session ID to look for. A value
       also indicates that the farm does session-id based persistency."
    ::= {rsADFarmEntry 16}

rsADConnCheckUserName OBJECT-TYPE
    SYNTAX DisplayString (SIZE(0..20))
    ACCESS  read-write
    STATUS  mandatory
    DESCRIPTION
      "Username used for extended connectivity checks."
    ::= {rsADFarmEntry 17}

rsADConnCheckPassword OBJECT-TYPE
    SYNTAX DisplayString (SIZE(0..20))
    ACCESS  read-write
    STATUS  mandatory
    DESCRIPTION
      "Password used for extended connectivity checks."
    ::= {rsADFarmEntry 18}

rsADFarmContent OBJECT-TYPE
    SYNTAX INTEGER {
      nonSip(1),
      sip(2)
   }
    ACCESS  read-write
    STATUS  mandatory
    DESCRIPTION
      "Content type of the farm."
    DEFVAL  { nonSip }
    ::= {rsADFarmEntry 19}


rsWSDClientsTable OBJECT-TYPE
    SYNTAX SEQUENCE OF RsWSDClientEntry
    ACCESS not-accessible
    STATUS  mandatory
    DESCRIPTION
      "Table containing the list of clients currently attached to a server."
    ::=  {rsServerDispatcher 14}

rsWSDClientEntry OBJECT-TYPE
    SYNTAX RsWSDClientEntry
    ACCESS not-accessible
    STATUS  mandatory
    DESCRIPTION
       " The row definition for this table."
   INDEX { rsWSDFarmAddr,
           rsWSDClientAddr}
    ::=  {rsWSDClientsTable 1}

RsWSDClientEntry ::= SEQUENCE {
  rsWSDFarmAddr                  IpAddress,
  rsWSDClientAddr                IpAddress,
  rsWSDAttachedServerAddr        IpAddress,
  rsWSDClientLastActivityTime    INTEGER,
  rsWSDClientAttachmentTime      INTEGER,
  rsWSDClientType                INTEGER,
  rsWSDClientStatus              RowStatus,
  rsWSDAttachedServerPort        INTEGER
}

rsWSDFarmAddr OBJECT-TYPE
    SYNTAX  IpAddress
    ACCESS  read-only
    STATUS  mandatory
    DESCRIPTION
     "IP Address of the WEB farm the client trough which the client connected."
    ::=  {rsWSDClientEntry 1}

rsWSDClientAddr  OBJECT-TYPE
    SYNTAX  IpAddress
    ACCESS  read-only
    STATUS  mandatory
    DESCRIPTION
      "Client IP Address."
    ::=  {rsWSDClientEntry 2}

rsWSDAttachedServerAddr OBJECT-TYPE
    SYNTAX  IpAddress
    ACCESS  read-write
    STATUS  mandatory
    DESCRIPTION
      "IP Address of server currently serving this client."
    ::=  {rsWSDClientEntry 3 }

rsWSDClientLastActivityTime  OBJECT-TYPE
    SYNTAX  INTEGER
    ACCESS  read-only
    STATUS  mandatory
    DESCRIPTION
      "Indicates when the last frame from the client was dispatched.
       Measured in seconds since device re-initialization."
    ::=  {rsWSDClientEntry 4}

rsWSDClientAttachmentTime OBJECT-TYPE
    SYNTAX  INTEGER
    ACCESS  read-only
    STATUS  mandatory
    DESCRIPTION
      "Indicates when the client was attached.
       Measured in seconds since device re-initialization."
    ::=  {rsWSDClientEntry 5}

rsWSDClientType OBJECT-TYPE
    SYNTAX INTEGER {
                    dynamic(1),
                    static(2),
             	    nat(3),
                    clientnat(4),
                    outbound(5)
                    }
    ACCESS  read-write
    STATUS  mandatory
    DESCRIPTION
              "This variable indicates the administrative type of this entry."
    ::=  { rsWSDClientEntry 6}

rsWSDClientStatus OBJECT-TYPE
    SYNTAX  RowStatus
    ACCESS  read-write
    STATUS  mandatory
    DESCRIPTION
       "This variable indicates the administrative status of this entry.
        Used to delete an entry of this table."
    ::=  { rsWSDClientEntry 7}

rsWSDAttachedServerPort  OBJECT-TYPE
    SYNTAX	INTEGER
    ACCESS  read-write
    STATUS  mandatory
	DESCRIPTION
        "The port of the server currently serving this client."
	DEFVAL {0}
    ::= { rsWSDClientEntry 8}

rsADClientsTable OBJECT-TYPE
    SYNTAX SEQUENCE OF RsADClientEntry
    ACCESS not-accessible
    STATUS  mandatory
    DESCRIPTION
      "Table containing the list of clients currently attached to a server."
    ::=  {rsServerDispatcher 137}

rsADClientEntry OBJECT-TYPE
    SYNTAX RsADClientEntry
    ACCESS not-accessible
    STATUS  mandatory
    DESCRIPTION
       " The row definition for this table."
   INDEX { rsADClientFarmName,
           rsADClientAddr}
    ::=  {rsADClientsTable 1}

RsADClientEntry ::= SEQUENCE {
  rsADClientFarmName            DisplayString,
  rsADClientAddr                IpAddress,
  rsADClientStatus              RowStatus,
  rsADAttachedServerAddr        IpAddress,
  rsADAttachedServerPort        INTEGER,
  rsADClientLastActivityTime    INTEGER,
  rsADClientAttachmentTime      INTEGER,
  rsADClientType                INTEGER
}

rsADClientFarmName OBJECT-TYPE
    SYNTAX  DisplayString (SIZE(1..50))
    ACCESS  read-only
    STATUS  mandatory
    DESCRIPTION
     "The name of the WEB farm through which the client connected."
    ::=  {rsADClientEntry 1}

rsADClientAddr  OBJECT-TYPE
    SYNTAX  IpAddress
    ACCESS  read-only
    STATUS  mandatory
    DESCRIPTION
      "Client IP Address."
    ::=  {rsADClientEntry 2}

rsADClientStatus OBJECT-TYPE
    SYNTAX  RowStatus
    ACCESS  read-write
    STATUS  mandatory
    DESCRIPTION
       "This variable indicates the administrative status of this entry.
        Used to delete an entry of this table."
    ::=  {rsADClientEntry 3}

rsADAttachedServerAddr OBJECT-TYPE
    SYNTAX  IpAddress
    ACCESS  read-write
    STATUS  mandatory
    DESCRIPTION
      "IP Address of server currently serving this client."
    ::=  {rsADClientEntry 4}

rsADAttachedServerPort  OBJECT-TYPE
    SYNTAX	INTEGER
    ACCESS  read-write
    STATUS  mandatory
	DESCRIPTION
        "The port of the server currently serving this client."
	DEFVAL {0}
    ::= { rsADClientEntry 5}

rsADClientLastActivityTime  OBJECT-TYPE
    SYNTAX  INTEGER
    ACCESS  read-only
    STATUS  mandatory
    DESCRIPTION
      "Indicates when the last frame from the client was dispatched.
       Measured in seconds since device re-initialization."
    ::=  {rsADClientEntry 6}

rsADClientAttachmentTime OBJECT-TYPE
    SYNTAX  INTEGER
    ACCESS  read-only
    STATUS  mandatory
    DESCRIPTION
      "Indicates when the client was attached.
       Measured in seconds since device re-initialization."
    ::=  {rsADClientEntry 7}

rsADClientType OBJECT-TYPE
    SYNTAX INTEGER {
                    dynamic(1),
                    static(2),
             	    nat(3),
                    clientnat(4),
                    outbound(5)
                    }
    ACCESS  read-write
    STATUS  mandatory
    DESCRIPTION
              "This variable indicates the administrative type of this entry."
    ::=  { rsADClientEntry 8}


rsWSDLoadReportTable OBJECT-TYPE
   SYNTAX SEQUENCE OF RsWSDLoadReportEntry
   ACCESS not-accessible
   STATUS mandatory
   DESCRIPTION
      ""
   ::= {rsServerDispatcher 17}

rsWSDLoadReportEntry  OBJECT-TYPE
   SYNTAX RsWSDLoadReportEntry
   ACCESS not-accessible
   STATUS mandatory
   DESCRIPTION
      "The row definition for this table."
   INDEX {rsWSDReportFarmAddress,
          rsWSDReportDstFarmAddress,
          rsWSDReportLclSuperFarmAddr,
          rsWSDReportNATIpAddr}
   ::= {rsWSDLoadReportTable  1 }

RsWSDLoadReportEntry ::= SEQUENCE {
        rsWSDReportFarmAddress      IpAddress,
        rsWSDReportDstFarmAddress   IpAddress,
        rsWSDReportLclSuperFarmAddr IpAddress,
        rsWSDReportDstIpAddress     IpAddress,
        rsWSDReportMapFarmAddress   IpAddress,
        rsWSDReportStatus           RowStatus,
        rsWSDReportRdnDstIpAddr     IpAddress,
        rsWSDReportDstSuperFarmAddr IpAddress,
        rsWSDReportNATIpAddr        IpAddress,
		rsWSDReportNATMAPIpAddr     IpAddress,
        rsWSDReportHMID             DisplayString,
		rsWSDReportOperationStatus  INTEGER,
        rsWSDReportCckID            INTEGER
  }

rsWSDReportFarmAddress  OBJECT-TYPE
   SYNTAX IpAddress
   ACCESS read-only
   STATUS mandatory
   DESCRIPTION
      "The farm IP address."
   ::=  {rsWSDLoadReportEntry 1}

rsWSDReportDstFarmAddress OBJECT-TYPE
   SYNTAX IpAddress
   ACCESS read-only
   STATUS mandatory
   DESCRIPTION
      "The farm IP address in the remote system which corresponding
       rsWSDReportFarmAddress."
   ::=  {rsWSDLoadReportEntry 2}

rsWSDReportLclSuperFarmAddr OBJECT-TYPE
   SYNTAX IpAddress
   ACCESS read-only
   STATUS mandatory
   DESCRIPTION
      "The Superfarm IP address in the local system"
-- DEFVAL   { 0.0.0.0 }
   ::=  {rsWSDLoadReportEntry 3}

rsWSDReportDstIpAddress OBJECT-TYPE
   SYNTAX IpAddress
   ACCESS read-write
   STATUS mandatory
   DESCRIPTION
      "The IP address of the remote system which should receive the load
       report."
   ::=  {rsWSDLoadReportEntry 4}

rsWSDReportMapFarmAddress OBJECT-TYPE
   SYNTAX IpAddress
   ACCESS read-write
   STATUS mandatory
   DESCRIPTION
      "The virtual address to which the request should be mapped when a
       distributed unit redirects traffic using the triangulation method."
--     DEFVAL   { 0.0.0.0 }
   ::=  {rsWSDLoadReportEntry 5}

rsWSDReportStatus OBJECT-TYPE
   SYNTAX  RowStatus
   ACCESS read-write
   STATUS mandatory
   DESCRIPTION
      ""
   ::=  {rsWSDLoadReportEntry 6}

rsWSDReportRdnDstIpAddr OBJECT-TYPE
   SYNTAX IpAddress
   ACCESS read-write
   STATUS mandatory
   DESCRIPTION
      "The IP address of the redundant remote system which should receive the
      load report."
--     DEFVAL   { 0.0.0.0 }
   ::=  {rsWSDLoadReportEntry 7}

rsWSDReportDstSuperFarmAddr OBJECT-TYPE
   SYNTAX IpAddress
   ACCESS read-write
   STATUS mandatory
   DESCRIPTION
      "The Superfarm IP address in the remote system"
-- DEFVAL   { 0.0.0.0 }
   ::=  {rsWSDLoadReportEntry 8}

rsWSDReportNATIpAddr OBJECT-TYPE
   SYNTAX IpAddress
   ACCESS read-only
   STATUS mandatory
   DESCRIPTION
      "The NAT IP Addresses that is associated with the farm IP address "
-- DEFVAL   { 0.0.0.0 }
   ::=  {rsWSDLoadReportEntry 9}

rsWSDReportNATMAPIpAddr OBJECT-TYPE
   SYNTAX IpAddress
   ACCESS read-write
   STATUS mandatory
   DESCRIPTION
"The NAT IP Addresses that is associated with the farm MAP IP address "
   ::=  {rsWSDLoadReportEntry 10}

rsWSDReportHMID OBJECT-TYPE
   SYNTAX DisplayString (SIZE (0..80))
   ACCESS read-write
  STATUS mandatory
   DESCRIPTION
"key id to associate with Health checks of the Health Monitoring module"
   ::=  {rsWSDLoadReportEntry 11}

rsWSDReportOperationStatus OBJECT-TYPE
SYNTAX INTEGER {
	active(1),
	notInService(2) }
   ACCESS  read-only
   STATUS  mandatory
   DESCRIPTION
" indicate if the entry is available"
   ::=  {rsWSDLoadReportEntry 12}


rsWSDReportCckID OBJECT-TYPE
    SYNTAX  INTEGER
    ACCESS  read-write
    STATUS  mandatory
    DESCRIPTION
      "Connectivity check module identifier."
    ::=  {rsWSDLoadReportEntry 13}


rsWSDFarmMappingTable OBJECT-TYPE
   SYNTAX SEQUENCE OF RsWSDFarmMappingEntry
   ACCESS not-accessible
   STATUS mandatory
   DESCRIPTION
      ""
   ::= {rsServerDispatcher 18}

rsWSDFarmMappingEntry  OBJECT-TYPE
   SYNTAX RsWSDFarmMappingEntry
   ACCESS not-accessible
   STATUS mandatory
   DESCRIPTION
      "The row definition for this table."
   INDEX {rsWSDMappingAddress}
   ::= {rsWSDFarmMappingTable  1 }

RsWSDFarmMappingEntry ::= SEQUENCE {
        rsWSDMappingAddress     IpAddress,
        rsWSDMappingFarmAddress IpAddress,
        rsWSDOriginalAddress    IpAddress,
        rsWSDMappingAdminStatus FeatureStatus,
        rsWSDMappingStatus      RowStatus
   }

rsWSDMappingAddress  OBJECT-TYPE
   SYNTAX IpAddress
   ACCESS read-only
   STATUS mandatory
   DESCRIPTION
      "The sub-virtual address of the farm. A distributed WSD directs the clients
       to this address."
   ::=  {rsWSDFarmMappingEntry 1}

rsWSDMappingFarmAddress OBJECT-TYPE
   SYNTAX IpAddress
   ACCESS read-write
   STATUS mandatory
   DESCRIPTION
      "The local virtual address of the farm. A couple of sub virtual addresses
       can belong to the same farm address. The local servers are defined per farm
       address."
   ::=  {rsWSDFarmMappingEntry 2}

rsWSDOriginalAddress OBJECT-TYPE
   SYNTAX IpAddress
   ACCESS read-write
   STATUS mandatory
   DESCRIPTION
      "The original IP address. This address replaces the server IP address when
       responding to the client. This IP address is the virtual IP address which the
       customer approached."
   ::=  {rsWSDFarmMappingEntry 3}

rsWSDMappingAdminStatus OBJECT-TYPE
   SYNTAX FeatureStatus
   ACCESS read-write
   STATUS mandatory
   DESCRIPTION
      "Indicates/controls the sub virtual address mapping enabling."
   ::=  {rsWSDFarmMappingEntry 4}

rsWSDMappingStatus OBJECT-TYPE
   SYNTAX RowStatus
-- SYNTAX INTEGER
   ACCESS read-write
   STATUS mandatory
   DESCRIPTION
      "Row control."
   ::=  {rsWSDFarmMappingEntry 5}


rsWSDLoadReportInterval OBJECT-TYPE
    SYNTAX INTEGER
    ACCESS  read-write
    STATUS  mandatory
    DESCRIPTION
        "The interval in seconds between two load reports."
--     DEFVAL   { 10 }
    ::=  {rsServerDispatcher 24}

rsWSDLoadReportTimeout OBJECT-TYPE
    SYNTAX INTEGER
    ACCESS  read-write
    STATUS  mandatory
    DESCRIPTION
        "The timeout in seconds between two load report messages."
--     DEFVAL   { 25 }
    ::=  {rsServerDispatcher 25}

rsWSDPortFarmTable OBJECT-TYPE
   SYNTAX SEQUENCE OF RsWSDPortFarmEntry
   ACCESS not-accessible
   STATUS mandatory
   DESCRIPTION
       "A table for managing the farm decision according to the incoming port."
   ::= {rsServerDispatcher 30}

rsWSDPortFarmEntry OBJECT-TYPE
   SYNTAX RsWSDPortFarmEntry
   ACCESS not-accessible
   STATUS  mandatory
   DESCRIPTION
       " The row definition for this table."
   INDEX  {rsWSDPortMainAddress,
           rsWSDPortNumber,
           rsWSDPortL4Protocol}
   ::= {rsWSDPortFarmTable 1}

RsWSDPortFarmEntry  ::= SEQUENCE {
      rsWSDPortMainAddress  IpAddress,
      rsWSDPortNumber       INTEGER,
      rsWSDPortL4Protocol   INTEGER,
      rsWSDPortFarmAddress  IpAddress,
      rsWSDPortFarmStatus   RowStatus,
      rsWSDPortFarmHeader   DisplayString,
      rsWSDPortArgs         DisplayString
  }

rsWSDPortMainAddress OBJECT-TYPE
   SYNTAX IpAddress
   ACCESS  read-only
   STATUS  mandatory
   DESCRIPTION
       "The Main IP address given by clients."
   ::= {rsWSDPortFarmEntry 1}

rsWSDPortNumber OBJECT-TYPE
   SYNTAX INTEGER
   ACCESS  read-only
   STATUS  mandatory
   DESCRIPTION
       "The port number which defines the virtual farm."
   ::= {rsWSDPortFarmEntry 2}

rsWSDPortL4Protocol OBJECT-TYPE
   SYNTAX INTEGER {
        tcp(1),
        udp(2),
        icmp(3),
        any(4)
   }
   ACCESS  read-only
   STATUS  mandatory
   DESCRIPTION
       "The L4 protocol."
   ::= {rsWSDPortFarmEntry 3}

rsWSDPortFarmAddress OBJECT-TYPE
   SYNTAX IpAddress
   ACCESS  read-write
   STATUS  mandatory
   DESCRIPTION
       "The IP Address to use for the port."
   ::= {rsWSDPortFarmEntry 4}

rsWSDPortFarmStatus OBJECT-TYPE
   SYNTAX  RowStatus
   ACCESS  read-write
   STATUS  mandatory
   DESCRIPTION
       "The  status of this entry."
   ::= {rsWSDPortFarmEntry 5}

rsWSDPortFarmHeader OBJECT-TYPE
   SYNTAX  DisplayString (SIZE(0..62))
   ACCESS  read-write
   STATUS  mandatory
   DESCRIPTION
       "L7 policy to be used. Maximum length allowed is 20."
   ::= {rsWSDPortFarmEntry 6}

rsWSDPortArgs OBJECT-TYPE
   SYNTAX  DisplayString (SIZE(0..255))
   ACCESS  read-write
   STATUS  mandatory
   DESCRIPTION
       "Arguments for the SuperFarm entry."
   ::= {rsWSDPortFarmEntry 7}


rsWSDProximity  OBJECT IDENTIFIER ::= { rsServerDispatcher 32 }

rsWSDStaticProximityTable OBJECT-TYPE
   SYNTAX SEQUENCE OF RsWSDStaticProximityEntry
   ACCESS not-accessible
   STATUS mandatory
   DESCRIPTION
          "In this table the WSD saves the static proximity ranges per server farm IP Address"
   ::= {rsWSDProximity 1}


rsWSDStaticProximityEntry OBJECT-TYPE
    SYNTAX RsWSDStaticProximityEntry
    ACCESS not-accessible
    STATUS  mandatory
    DESCRIPTION
       " The row definition for this table."
   INDEX  {rsWSDStaticProximityFarmAddress,
           rsWSDStaticProximityRangeFrom }
   ::= {rsWSDStaticProximityTable 1}


RsWSDStaticProximityEntry  ::= SEQUENCE {
  rsWSDStaticProximityFarmAddress               IpAddress,
  rsWSDStaticProximityRangeFrom                 IpAddress,
  rsWSDStaticProximityRangeTo                   IpAddress,
  rsWSDStaticProximityStatus                    INTEGER,
  rsWSDStaticProximityServer1                   IpAddress,
  rsWSDStaticProximityServer2                   IpAddress,
  rsWSDStaticProximityServer3                   IpAddress
  }

rsWSDStaticProximityFarmAddress OBJECT-TYPE
    SYNTAX IpAddress
    ACCESS  read-only
    STATUS  mandatory
    DESCRIPTION
      "The IP Address of the WEB farm."
    ::= {rsWSDStaticProximityEntry 1}

rsWSDStaticProximityRangeFrom OBJECT-TYPE
    SYNTAX IpAddress
    ACCESS  read-only
    STATUS  mandatory
    DESCRIPTION
      "The IP Address of the low boundary of the interval."
    ::= {rsWSDStaticProximityEntry 2}

rsWSDStaticProximityRangeTo OBJECT-TYPE
    SYNTAX IpAddress
    ACCESS  read-write
    STATUS  mandatory
    DESCRIPTION
      "The IP Address of the high boundary of the interval."
    ::= {rsWSDStaticProximityEntry 3}

rsWSDStaticProximityStatus OBJECT-TYPE
      SYNTAX INTEGER {
        active(1),
        notInService(2),
        notReady(3),
        createAndGo(4),
        createAndWait(5),
        destroy(6) }
    ACCESS  read-write
    STATUS  mandatory
    DESCRIPTION
      "This variable indicate the Administative status of this entry.
       Use for delete an entry in this table."
  ::= {rsWSDStaticProximityEntry 4}

rsWSDStaticProximityServer1 OBJECT-TYPE
    SYNTAX IpAddress
    ACCESS  read-write
    STATUS  mandatory
    DESCRIPTION
"The first priority server that this range of clients will be redirected to"
    ::= {rsWSDStaticProximityEntry 5}

rsWSDStaticProximityServer2 OBJECT-TYPE
    SYNTAX IpAddress
    ACCESS  read-write
    STATUS  mandatory
    DESCRIPTION
"The second priority server that this range of clients will be redirected to"
       ::= {rsWSDStaticProximityEntry 6}

rsWSDStaticProximityServer3 OBJECT-TYPE
    SYNTAX IpAddress
    ACCESS  read-write
    STATUS  mandatory
    DESCRIPTION
" The third priority server that this range of clients will be redirected to "
    ::= {rsWSDStaticProximityEntry 7}


rsADStaticProximityTable OBJECT-TYPE
   SYNTAX SEQUENCE OF RsADStaticProximityEntry
   ACCESS not-accessible
   STATUS mandatory
   DESCRIPTION
          "In this table the AppDirector saves the static proximity ranges per server farm."
   ::= {rsWSDProximity 16}

rsADStaticProximityEntry OBJECT-TYPE
    SYNTAX RsADStaticProximityEntry
    ACCESS not-accessible
    STATUS  mandatory
    DESCRIPTION
       " The row definition for this table."
   INDEX  {rsADStaticProximityFarmName,
           rsADStaticProximityRangeFrom }
   ::= {rsADStaticProximityTable 1}


RsADStaticProximityEntry  ::= SEQUENCE {
  rsADStaticProximityFarmName                  DisplayString,
  rsADStaticProximityRangeFrom                 IpAddress,
  rsADStaticProximityStatus                    RowStatus,
  rsADStaticProximityRangeTo                   IpAddress,
  rsADStaticProximityServer1                   IpAddress,
  rsADStaticProximityServer2                   IpAddress,
  rsADStaticProximityServer3                   IpAddress
}

rsADStaticProximityFarmName OBJECT-TYPE
    SYNTAX  DisplayString (SIZE (1..50))
    ACCESS  read-only
    STATUS  mandatory
    DESCRIPTION
      "The name of the WEB farm."
    ::= {rsADStaticProximityEntry 1}

rsADStaticProximityRangeFrom OBJECT-TYPE
    SYNTAX IpAddress
    ACCESS  read-only
    STATUS  mandatory
    DESCRIPTION
      "The IP Address of the low boundary of the interval."
    ::= {rsADStaticProximityEntry 2}

rsADStaticProximityStatus OBJECT-TYPE
    SYNTAX  RowStatus
    ACCESS  read-write
    STATUS  mandatory
    DESCRIPTION
      "This variable indicate the Administative status of this entry.
       Use for delete an entry in this table."
  ::= {rsADStaticProximityEntry 3}

rsADStaticProximityRangeTo OBJECT-TYPE
    SYNTAX IpAddress
    ACCESS  read-write
    STATUS  mandatory
    DESCRIPTION
      "The IP Address of the high boundary of the interval."
    ::= {rsADStaticProximityEntry 4}

rsADStaticProximityServer1 OBJECT-TYPE
    SYNTAX IpAddress
    ACCESS  read-write
    STATUS  mandatory
    DESCRIPTION
"The first priority server that this range of clients will be redirected to"
    ::= {rsADStaticProximityEntry 5}

rsADStaticProximityServer2 OBJECT-TYPE
    SYNTAX IpAddress
    ACCESS  read-write
    STATUS  mandatory
    DESCRIPTION
"The second priority server that this range of clients will be redirected to"
       ::= {rsADStaticProximityEntry 6}

rsADStaticProximityServer3 OBJECT-TYPE
    SYNTAX IpAddress
    ACCESS  read-write
    STATUS  mandatory
    DESCRIPTION
" The third priority server that this range of clients will be redirected to "
    ::= {rsADStaticProximityEntry 7}

rsNADStaticProximityTable OBJECT-TYPE
   SYNTAX SEQUENCE OF RsNADStaticProximityEntry
   ACCESS not-accessible
   STATUS mandatory
   DESCRIPTION
          "In this table the AppDirector saves the static proximity ranges per server farm."
   ::= {rsWSDProximity 18}

rsNADStaticProximityEntry OBJECT-TYPE
    SYNTAX RsNADStaticProximityEntry
    ACCESS not-accessible
    STATUS  mandatory
    DESCRIPTION
       " The row definition for this table."
   INDEX  {rsNADStaticProximityFarmName,
		   rsNADStaticProximityRangeFromAddrType,
           rsNADStaticProximityRangeFrom }
   ::= {rsNADStaticProximityTable 1}


RsNADStaticProximityEntry  ::= SEQUENCE {
  rsNADStaticProximityFarmName                  DisplayString,
  rsNADStaticProximityRangeFromAddrType			InetAddressType,
  rsNADStaticProximityRangeFrom                 InetAddress,
  rsNADStaticProximityRangeToAddrType			InetAddressType,
  rsNADStaticProximityRangeTo                   InetAddress,
  rsNADStaticProximityServer1AddrType			InetAddressType,
  rsNADStaticProximityServer1	                InetAddress,
  rsNADStaticProximityServer2AddrType			InetAddressType,
  rsNADStaticProximityServer2					InetAddress,
  rsNADStaticProximityServer3AddrType			InetAddressType,
  rsNADStaticProximityServer3					InetAddress,
  rsNADStaticProximityStatus                    RowStatus
}

rsNADStaticProximityFarmName OBJECT-TYPE
    SYNTAX  DisplayString (SIZE (1..50))
    ACCESS  read-only
    STATUS  mandatory
    DESCRIPTION
      "The name of the WEB farm."
    ::= {rsNADStaticProximityEntry 1}

rsNADStaticProximityRangeFromAddrType OBJECT-TYPE
    SYNTAX InetAddressType
    ACCESS  read-only
    STATUS  mandatory
    DESCRIPTION
      "The Type of IP Address of the low boundary of the interval."
    ::= {rsNADStaticProximityEntry 2}

rsNADStaticProximityRangeFrom OBJECT-TYPE
    SYNTAX InetAddress
    ACCESS  read-only
    STATUS  mandatory
    DESCRIPTION
      "The IP Address of the low boundary of the interval."
    ::= {rsNADStaticProximityEntry 3}

rsNADStaticProximityRangeToAddrType OBJECT-TYPE
    SYNTAX InetAddressType
    ACCESS  read-write
    STATUS  optional
    DESCRIPTION
      "The Type of IP Address of the high boundary of the interval."
	DEFVAL { ipv4 }
    ::= {rsNADStaticProximityEntry 4}

rsNADStaticProximityRangeTo OBJECT-TYPE
    SYNTAX InetAddress
    ACCESS  read-write
    STATUS  optional
    DESCRIPTION
      "The IP Address of the high boundary of the interval."
	DEFVAL{"0.0.0.0"}
    ::= {rsNADStaticProximityEntry 5}

rsNADStaticProximityServer1AddrType OBJECT-TYPE
    SYNTAX InetAddressType
    ACCESS  read-write
    STATUS  optional
    DESCRIPTION
      "The IP address type of the first priority server that this range of clients will be redirected to."
	DEFVAL { ipv4 }
    ::= {rsNADStaticProximityEntry 6}

rsNADStaticProximityServer1 OBJECT-TYPE
    SYNTAX InetAddress
    ACCESS  read-write
    STATUS  optional
    DESCRIPTION
	"The first priority server that this range of clients will be redirected to"
	DEFVAL{"0.0.0.0"}
    ::= {rsNADStaticProximityEntry 7}

rsNADStaticProximityServer2AddrType OBJECT-TYPE
    SYNTAX InetAddressType
    ACCESS  read-write
    STATUS  optional
    DESCRIPTION
      "The IP address type of the second priority server that this range of clients will be redirected to."
	DEFVAL { ipv4 }
    ::= {rsNADStaticProximityEntry 8}

rsNADStaticProximityServer2 OBJECT-TYPE
    SYNTAX InetAddress
    ACCESS  read-write
    STATUS  optional
    DESCRIPTION
	"The second priority server that this range of clients will be redirected to"
	DEFVAL{"0.0.0.0"}
       ::= {rsNADStaticProximityEntry 9}

rsNADStaticProximityServer3AddrType OBJECT-TYPE
    SYNTAX InetAddressType
    ACCESS  read-write
    STATUS  optional
    DESCRIPTION
      "The IP address type of the third priority server that this range of clients will be redirected to."
	DEFVAL { ipv4 }
    ::= {rsNADStaticProximityEntry 10}

rsNADStaticProximityServer3 OBJECT-TYPE
    SYNTAX InetAddress
    ACCESS  read-write
    STATUS  optional
    DESCRIPTION
	" The third priority server that this range of clients will be redirected to "
	DEFVAL{"0.0.0.0"}
    ::= {rsNADStaticProximityEntry 11}

rsNADStaticProximityStatus OBJECT-TYPE
    SYNTAX  RowStatus
    ACCESS  read-write
    STATUS  mandatory
    DESCRIPTION
      "This variable indicate the Administative status of this entry.
       Use for delete an entry in this table."
  ::= {rsNADStaticProximityEntry 12}

rsWSDProximityOperationMode  OBJECT-TYPE
   SYNTAX INTEGER {
        noProximity(1),
        staticProximity(2),
	fullProximity(3)
   }
   ACCESS  read-write
   STATUS  mandatory
   DESCRIPTION
       "Allow proximity operation, and choose between operating only static proximity or dynamic proximity as well "
-- DEFVAL { 1 }
   ::=  {rsWSDProximity 2}

rsWSDProximityMainDNS OBJECT-TYPE
SYNTAX IpAddress
    ACCESS  read-write
    STATUS  mandatory
    DESCRIPTION
        "The IP Address of the main DNS to be ignored in the proximity operation"
    ::= { rsWSDProximity 3}

rsWSDProximityBackupDNS OBJECT-TYPE
SYNTAX IpAddress
    ACCESS  read-write
    STATUS  mandatory
    DESCRIPTION
        "The IP Address of the backup DNS to be ignored in the proximity operation"
    ::= { rsWSDProximity 4}


rsNADProximityDNSTable OBJECT-TYPE
   SYNTAX SEQUENCE OF RsNADProximityDNSEntry
   ACCESS not-accessible
   STATUS mandatory
   DESCRIPTION
        "The IP Address of the DNS server to be ignored in the proximity operation"
   ::= {rsWSDProximity 19}


rsNADPrxClientGroupingPrefixLen OBJECT-TYPE
    SYNTAX INTEGER (3..64)
    ACCESS  read-write
    STATUS  mandatory
    DESCRIPTION
        "The prefix length for grouping of ipv6 clients in the dynamic proximity table."
--     DEFVAL   { 48 }
   ::=  { rsWSDProximity 20}


rsNADProximityDNSEntry OBJECT-TYPE
   SYNTAX RsNADProximityDNSEntry
   ACCESS not-accessible
   STATUS mandatory
   DESCRIPTION
       " The row definition for this table."
   INDEX  {rsNADProximityDNSAddrType, rsNADProximityDNSAddr}
   ::= {rsNADProximityDNSTable 1}

RsNADProximityDNSEntry  ::= SEQUENCE {
  rsNADProximityDNSAddrType	InetAddressType,
  rsNADProximityDNSAddr		InetAddress,
  rsNADProximityDNSStatus   RowStatus
}

rsNADProximityDNSAddrType OBJECT-TYPE
   	SYNTAX InetAddressType
   	ACCESS read-write
   	STATUS optional
   	DESCRIPTION
	 	 "The IP Address type of the main DNS server."
	DEFVAL  { ipv4 }
	::=  {rsNADProximityDNSEntry 1}

rsNADProximityDNSAddr OBJECT-TYPE
   	SYNTAX InetAddress
   	ACCESS read-write
   	STATUS optional
   	DESCRIPTION
     	 "The IP Address of the main DNS server."
	::=  {rsNADProximityDNSEntry 2}

rsNADProximityDNSStatus OBJECT-TYPE
  SYNTAX RowStatus
  ACCESS read-write
  STATUS mandatory
  DESCRIPTION
    "Row status for the code."
	::=  {rsNADProximityDNSEntry 3}

rsWSDProximityAgingPeriod OBJECT-TYPE
    SYNTAX INTEGER
    ACCESS  read-write
    STATUS  mandatory
    DESCRIPTION
        "The time in hours after which an old dynamic entry is invalid."
--     DEFVAL   { 48 }
    ::=  { rsWSDProximity 5}

rsWSDProximityClientMode  OBJECT-TYPE
   SYNTAX FeatureStatus
   ACCESS  read-write
   STATUS  mandatory
   DESCRIPTION
       "Enable or disable the proximity operation of the distributed WSD"
-- DEFVAL { disable }
   ::=  {rsWSDProximity 6}

rsWSDProximityRetries  OBJECT-TYPE
   SYNTAX INTEGER (1..5)
   ACCESS  read-write
   STATUS  mandatory
   DESCRIPTION
       "The number of tries for checking the client distance"
-- DEFVAL { 2 }
   ::=  {rsWSDProximity 7}

rsWSDProximityTimeout  OBJECT-TYPE
   SYNTAX INTEGER (1..10)
   ACCESS  read-write
   STATUS  mandatory
   DESCRIPTION
       "The timeout between proximity checks"
-- DEFVAL { 5 }
   ::=  {rsWSDProximity 8}


rsWSDProximityTuning OBJECT IDENTIFIER ::= { rsWSDProximity 9}

rsWSDMaxDynEntries OBJECT-TYPE
    SYNTAX INTEGER
    ACCESS  read-only
    STATUS  mandatory
    DESCRIPTION
      "Maximal number of entries in the dynamic proximity table."
    ::=  { rsWSDProximityTuning 1 }

rsWSDMaxDynEntriesAfterReset OBJECT-TYPE
    SYNTAX INTEGER
    ACCESS  read-write
    STATUS  mandatory
    DESCRIPTION
      "Future maximal number of entries in the dynamic proximity table."
    ::=  { rsWSDProximityTuning 2 }


rsWSDPrxBasicCheckMethod  OBJECT-TYPE
   SYNTAX FeatureStatus
   ACCESS  read-write
   STATUS  mandatory
   DESCRIPTION
       "Enable or disable basic proximity check (ICMP)"
-- DEFVAL { enable }
   ::=  {rsWSDProximity 10}

rsWSDPrxAdvancedCheckMethod  OBJECT-TYPE
   SYNTAX FeatureStatus
   ACCESS  read-write
   STATUS  mandatory
   DESCRIPTION
       "Enable or disable advanced proximity check (UDP)"
-- DEFVAL { enable }
   ::=  {rsWSDProximity 11}

rsWSDPrxApplIndpndCheckMethod  OBJECT-TYPE
   SYNTAX FeatureStatus
   ACCESS  read-write
   STATUS  mandatory
   DESCRIPTION
       "Enable or disable application independent proximity check (TCP to port 80)"
-- DEFVAL { enable }
   ::=  {rsWSDProximity 12}

rsWSDPrxApplAwareCheckMethod  OBJECT-TYPE
   SYNTAX FeatureStatus
   ACCESS  read-write
   STATUS  mandatory
   DESCRIPTION
       "Enable or disable application aware proximity check (TCP)"
-- DEFVAL { enable }
   ::=  {rsWSDProximity 13}

rsWSDPrxTableCleanupInterval OBJECT-TYPE
    SYNTAX INTEGER (0..604800)
    ACCESS  read-write
    STATUS  mandatory
    DESCRIPTION
        "The time in minutes after which the dynamic table can undergo cleanup."
--     DEFVAL   { 0 }
    ::=  { rsWSDProximity 14}

rsWSDPrxCheckFailureNotification  OBJECT-TYPE
   SYNTAX FeatureStatus
   ACCESS  read-write
   STATUS  mandatory
   DESCRIPTION
       "Enable or disable proximity failure notification (by default disabled)"
   ::=  {rsWSDProximity 15}

rsADPrxTracerouteCheckMethod  OBJECT-TYPE
   SYNTAX INTEGER {
        enable(1),
        disable(2)
   }
   ACCESS  read-write
   STATUS  mandatory
   DESCRIPTION
       "Enable or disable traceroute proximity check (UDP)"
-- DEFVAL { 1 }
   ::=  {rsWSDProximity 17}

rsADGeographicProximityTable OBJECT-TYPE
   SYNTAX SEQUENCE OF RsADGeographicProximityEntry
   ACCESS not-accessible
   STATUS mandatory
   DESCRIPTION
          "In this table the AD saves the Geographic proximity ranges per server farm IP Address"
   ::= {rsWSDProximity 21}


rsADGeographicProximityEntry OBJECT-TYPE
    SYNTAX RsADGeographicProximityEntry
    ACCESS not-accessible
    STATUS  mandatory
    DESCRIPTION
       "The row definition for this table."
   INDEX  {rsADGeographicProximityFarmName,
           rsADGeographicProximityLocation }
   ::= {rsADGeographicProximityTable 1}


RsADGeographicProximityEntry  ::= SEQUENCE {
  rsADGeographicProximityFarmName               DisplayString,
  rsADGeographicProximityLocation                 DisplayString,
  rsADGeographicProximityServer1                   IpAddress,
  rsADGeographicProximityServer2                   IpAddress,
  rsADGeographicProximityServer3                   IpAddress,
   rsADGeographicProximityStatus                    RowStatus
  }

rsADGeographicProximityFarmName OBJECT-TYPE
    SYNTAX DisplayString (SIZE(1..50))
    ACCESS  read-only
    STATUS  mandatory
    DESCRIPTION
      "The IP Address of the WEB farm."
    ::= {rsADGeographicProximityEntry 1}

rsADGeographicProximityLocation OBJECT-TYPE
    SYNTAX DisplayString (SIZE (1..55))
    ACCESS  read-only
    STATUS  mandatory
    DESCRIPTION
      "The country or region."
    ::= {rsADGeographicProximityEntry 2}

rsADGeographicProximityServer1 OBJECT-TYPE
    SYNTAX IpAddress
    ACCESS  read-write
    STATUS  mandatory
    DESCRIPTION
"The first priority server that this range of clients will be redirected to"
    ::= {rsADGeographicProximityEntry 3}

rsADGeographicProximityServer2 OBJECT-TYPE
    SYNTAX IpAddress
    ACCESS  read-write
    STATUS  mandatory
    DESCRIPTION
"The second priority server that this range of clients will be redirected to"
       ::= {rsADGeographicProximityEntry 4}

rsADGeographicProximityServer3 OBJECT-TYPE
    SYNTAX IpAddress
    ACCESS  read-write
    STATUS  mandatory
    DESCRIPTION
" The third priority server that this range of clients will be redirected to "
    ::= {rsADGeographicProximityEntry 5}
rsADGeographicProximityStatus OBJECT-TYPE
      SYNTAX RowStatus
    ACCESS  read-write
    STATUS  mandatory
    DESCRIPTION
      "This variable indicate the Administative status of this entry.
       Use for delete an entry in this table."
  ::= {rsADGeographicProximityEntry 6}


rsADGeographicRegionTable OBJECT-TYPE
   SYNTAX SEQUENCE OF RsADGeographicRegionEntry
   ACCESS not-accessible
   STATUS mandatory
   DESCRIPTION
          "In this table the WSD saves the Geographic Regions
           A user can add and update new regions but cannot update the
           Default regions"
   ::= {rsWSDProximity 22}


rsADGeographicRegionEntry OBJECT-TYPE
    SYNTAX RsADGeographicRegionEntry
    ACCESS not-accessible
    STATUS  mandatory
    DESCRIPTION
       "The row definition for this table."
   INDEX  {rsADGeographicRegionName,
           rsADGeographicRegionCountry }
   ::= {rsADGeographicRegionTable 1}


RsADGeographicRegionEntry  ::= SEQUENCE {
  rsADGeographicRegionName                         DisplayString,
  rsADGeographicRegionCountry                      DisplayString,
  rsADGeographicRegionStatus                       RowStatus
  }
rsADGeographicRegionName OBJECT-TYPE
    SYNTAX DisplayString (SIZE (1..16))
    ACCESS  read-only
    STATUS  mandatory
    DESCRIPTION
      "The region Name."
    ::= {rsADGeographicRegionEntry 1}

rsADGeographicRegionCountry OBJECT-TYPE
    SYNTAX DisplayString (SIZE (1..55))
    ACCESS  read-only
    STATUS  mandatory
    DESCRIPTION
      "The country Name."
    ::= {rsADGeographicRegionEntry 2}

rsADGeographicRegionStatus OBJECT-TYPE
    SYNTAX RowStatus
    ACCESS  read-write
    STATUS  mandatory
    DESCRIPTION
      "This variable indicate the Administative status of this entry.
       Use for delete an entry in this table."
  ::= {rsADGeographicRegionEntry 3}

rsADGeographicCopyRegionTable OBJECT-TYPE
   SYNTAX SEQUENCE OF RsADGeographicCopyRegionEntry
   ACCESS not-accessible
   STATUS mandatory
   DESCRIPTION
          "This table is used to create new region by copying an existing one"
   ::= {rsWSDProximity 23}


rsADGeographicCopyRegionEntry OBJECT-TYPE
    SYNTAX RsADGeographicCopyRegionEntry
    ACCESS not-accessible
    STATUS  mandatory
    DESCRIPTION
       "The row definition for this table."
   INDEX  {rsADGeographicCopyRegionSrcName,
			rsADGeographicCopyRegionDstName}
   ::= {rsADGeographicCopyRegionTable 1}


RsADGeographicCopyRegionEntry  ::= SEQUENCE {
  rsADGeographicCopyRegionSrcName                         DisplayString,
  rsADGeographicCopyRegionDstName                      DisplayString,
   rsADGeographicCopyRegionStatus                        RowStatus
  }
rsADGeographicCopyRegionSrcName OBJECT-TYPE
    SYNTAX DisplayString (SIZE (1..16))
    ACCESS  read-only
    STATUS  mandatory
    DESCRIPTION
      "The source region Name."
    ::= {rsADGeographicCopyRegionEntry 1}

rsADGeographicCopyRegionDstName OBJECT-TYPE
    SYNTAX DisplayString (SIZE (1..16))
    ACCESS  read-only
    STATUS  mandatory
    DESCRIPTION
      "The destination region Name."
    ::= {rsADGeographicCopyRegionEntry 2}

rsADGeographicCopyRegionStatus OBJECT-TYPE
      SYNTAX RowStatus
    ACCESS  read-write
    STATUS  mandatory
    DESCRIPTION
      "This variable indicate the Administative status of this entry.
       Use for delete an entry in this table."
  ::= {rsADGeographicCopyRegionEntry 3}

rsADGeographicCountryTable OBJECT-TYPE
   SYNTAX SEQUENCE OF RsADGeographicCountryEntry
   ACCESS not-accessible
   STATUS mandatory
   DESCRIPTION
          "This table shows all the countries"
   ::= {rsWSDProximity 24}

rsADGeographicCountryEntry OBJECT-TYPE
    SYNTAX RsADGeographicCountryEntry
    ACCESS not-accessible
    STATUS  mandatory
    DESCRIPTION
       "The row definition for this table."
   INDEX  {rsADGeographicCountryName}
   ::= {rsADGeographicCountryTable 1}


RsADGeographicCountryEntry  ::= SEQUENCE {
  rsADGeographicCountryName                         DisplayString
  }
rsADGeographicCountryName OBJECT-TYPE
    SYNTAX DisplayString (SIZE (1..55))
    ACCESS  read-only
    STATUS  mandatory
    DESCRIPTION
      "The country Name."
    ::= {rsADGeographicCountryEntry 1}

rsADGeographicProximityFeatureStatus  OBJECT-TYPE
   SYNTAX FeatureStatus
   ACCESS  read-write
   STATUS  mandatory
   DESCRIPTION
       "Enable or disable the geographical proximity operation"
-- DEFVAL { disable }
   ::=  {rsWSDProximity 25}


rsNWSDProximity  OBJECT IDENTIFIER ::= { rsNWSD 1 }

rsWSDProximityHopsWeight  OBJECT-TYPE
   SYNTAX INTEGER (1..100)
   ACCESS  read-write
   STATUS  mandatory
   DESCRIPTION
       "The weight given to the clients hops distance in the dispatching decision"
-- DEFVAL { 50 }
   ::=  {rsNWSDProximity 1}

rsWSDProximityLatencyWeight  OBJECT-TYPE
   SYNTAX INTEGER (1..100)
   ACCESS  read-write
   STATUS  mandatory
   DESCRIPTION
       "The weight given to the clients latency in the dispatching decision"
-- DEFVAL { 50 }
   ::=  {rsNWSDProximity 2}

rsWSDProximityLoadWeight  OBJECT-TYPE
   SYNTAX INTEGER (1..100)
   ACCESS  read-write
   STATUS  mandatory
   DESCRIPTION
       "The weight given to the site load in the dispatching decision"
-- DEFVAL { 50 }
   ::=  {rsNWSDProximity 3}

rsWSDProximityMirrorPercentage  OBJECT-TYPE
   SYNTAX INTEGER (1..100)
   ACCESS  read-write
   STATUS  mandatory
   DESCRIPTION
       "The percent of the proximity table to back up"
-- DEFVAL { 100 }
   ::=  {rsNWSDProximity 4}

rsWSDProximityMirrorPollingTime  OBJECT-TYPE
   SYNTAX INTEGER (3..4294967)
   ACCESS  read-write
   STATUS  mandatory
   DESCRIPTION
       "The polling time of the proximity mirror messages"
-- DEFVAL { 10 }
   ::=  {rsNWSDProximity 5}

rsWSDDNSttl  OBJECT-TYPE
   SYNTAX INTEGER
   ACCESS  read-write
   STATUS  mandatory
   DESCRIPTION
        "TTL for DNS replies."
-- DEFVAL { 0 }
   ::=  {rsNWSD 2}

rsWSDURLSuperFarmTable OBJECT-TYPE
   SYNTAX SEQUENCE OF RsWSDURLSuperFarmEntry
   ACCESS not-accessible
   STATUS mandatory
   DESCRIPTION
       "Hosts table, defines the DNS resolution for farms and SuperFarms"
   ::= {rsNWSD 3}

rsWSDURLSuperFarmEntry OBJECT-TYPE
   SYNTAX RsWSDURLSuperFarmEntry
   ACCESS not-accessible
   STATUS mandatory
   DESCRIPTION
       " The row definition for this table."
   INDEX  {rsWSDURL}
   ::= {rsWSDURLSuperFarmTable 1}

RsWSDURLSuperFarmEntry  ::= SEQUENCE {
  rsWSDURLFarmAddress           IpAddress,
  rsWSDURL                      DisplayString,
  rsWSDURLStatus                RowStatus,
  rsWSDURLSuperFarm             IpAddress,
  rsWSDURLNATAddr               IpAddress,
  rsWSDURLL4PolicyName          DisplayString,
  rsWSDURLPreferredResolveIP    IpAddress,
  rsWSDURLFarmName              DisplayString
}

rsWSDURLFarmAddress OBJECT-TYPE
    	SYNTAX IpAddress
    	ACCESS read-only
   	STATUS mandatory
   	DESCRIPTION
     	 "IP address of the farm to use with the URL."
	::=  {rsWSDURLSuperFarmEntry 1}

rsWSDURL  OBJECT-TYPE
        SYNTAX DisplayString (SIZE (1..63))
    	ACCESS read-write
   	STATUS mandatory
   	DESCRIPTION
     	 "The URL representing the farm."
	::=  {rsWSDURLSuperFarmEntry 2}

rsWSDURLStatus OBJECT-TYPE
    	SYNTAX RowStatus
    	ACCESS read-write
   	STATUS mandatory
   	DESCRIPTION
     	 "Row status for the URL."
	::=  {rsWSDURLSuperFarmEntry 3}

rsWSDURLSuperFarm OBJECT-TYPE
    	SYNTAX IpAddress
    	ACCESS read-write
   	STATUS mandatory
   	DESCRIPTION
     	 "The SuperFarm address to resolve for the URL"
	::=  {rsWSDURLSuperFarmEntry 4}

rsWSDURLNATAddr OBJECT-TYPE
    	SYNTAX IpAddress
    	ACCESS read-write
   	STATUS mandatory
   	DESCRIPTION
     	 "The IP address to resolve for the URL"
	::=  {rsWSDURLSuperFarmEntry 5}

rsWSDURLL4PolicyName OBJECT-TYPE
   	SYNTAX DisplayString (SIZE (1..50))
   	ACCESS read-write
   	STATUS mandatory
   	DESCRIPTION
     	 "L4Policy Name"
	::=  {rsWSDURLSuperFarmEntry 6}

rsWSDURLPreferredResolveIP OBJECT-TYPE
   	SYNTAX IpAddress
   	ACCESS read-write
   	STATUS mandatory
   	DESCRIPTION
     	 "Configures to which IP the host name should be resolved preferably."
	::=  {rsWSDURLSuperFarmEntry 7}

rsWSDURLFarmName OBJECT-TYPE
    SYNTAX DisplayString (SIZE(1..50))
    ACCESS read-write
   	STATUS mandatory
   	DESCRIPTION
        "The name of the farm to use with the URL."
	::=  {rsWSDURLSuperFarmEntry 8}

rsNADURLTable OBJECT-TYPE
   SYNTAX SEQUENCE OF RsNADURLEntry
   ACCESS not-accessible
   STATUS mandatory
   DESCRIPTION
       "Hosts table, defines the DNS resolution for farms and SuperFarms"
   ::= {rsNWSD 71}

rsNADURLEntry OBJECT-TYPE
   SYNTAX RsNADURLEntry
   ACCESS not-accessible
   STATUS mandatory
   DESCRIPTION
       " The row definition for this table."
   INDEX  {rsNADURL}
   ::= {rsNADURLTable 1}

RsNADURLEntry  ::= SEQUENCE {
  rsNADURL							DisplayString,
  rsNADURLL4PolicyNameV4			DisplayString,
  rsNADURLFarmNameV4				DisplayString,
  rsNADURLPreferredResolveIPTypeV4	InetAddressType,
  rsNADURLPreferredResolveIPV4		InetAddress,
  rsNADURLNATAddrTypeV4       		InetAddressType,
  rsNADURLNATAddrV4					InetAddress,
  rsNADURLL4PolicyNameV6			DisplayString,
  rsNADURLFarmNameV6			    DisplayString,
  rsNADURLPreferredResolveIPTypeV6	InetAddressType,
  rsNADURLPreferredResolveIPV6		InetAddress,
  rsNADURLNATAddrTypeV6       		InetAddressType,
  rsNADURLNATAddrV6					InetAddress,
  rsNADURLStatus					RowStatus
}

rsNADURL OBJECT-TYPE
        SYNTAX DisplayString (SIZE (1..63))
    	ACCESS read-write
   	STATUS mandatory
   	DESCRIPTION
     	 "The URL representing the farm."
	::=  {rsNADURLEntry 1}

rsNADURLL4PolicyNameV4 OBJECT-TYPE
   	SYNTAX DisplayString (SIZE (1..50))
   	ACCESS read-write
   	STATUS mandatory
   	DESCRIPTION
     	 "L4Policy Name with IPV4 VIP"
	DEFVAL  { "None" }
	::=  {rsNADURLEntry 2}

rsNADURLFarmNameV4 OBJECT-TYPE
    SYNTAX DisplayString (SIZE(1..50))
    ACCESS read-write
   	STATUS mandatory
   	DESCRIPTION
        "The name of the farm to use with the URL and IPV4 L4 policy."
    DEFVAL  { "None" }
	::=  {rsNADURLEntry 3}

rsNADURLPreferredResolveIPTypeV4 OBJECT-TYPE
   	SYNTAX InetAddressType
   	ACCESS read-write
   	STATUS mandatory
   	DESCRIPTION
     	 "The IP address type of the IP which the host name should be resolved preferably, IPV4."
	DEFVAL  { ipv4 }
	::=  {rsNADURLEntry 4}

rsNADURLPreferredResolveIPV4 OBJECT-TYPE
   	SYNTAX InetAddress
   	ACCESS read-write
   	STATUS mandatory
   	DESCRIPTION
     	 "Configures to which IP the host name should be resolved preferably, IPV4."
	DEFVAL{"0.0.0.0"}
	::=  {rsNADURLEntry 5}

rsNADURLNATAddrTypeV4 OBJECT-TYPE
   	SYNTAX InetAddressType
   	ACCESS read-write
   	STATUS mandatory
   	DESCRIPTION
     	 "The type of NAT IP address of the farm to use with the  URL, IPV4 ."
	DEFVAL  { ipv4 }
	::=  {rsNADURLEntry 6}

rsNADURLNATAddrV4 OBJECT-TYPE
   	SYNTAX InetAddress
   	ACCESS read-write
   	STATUS mandatory
   	DESCRIPTION
     	 "NAT IP address of the farm to use with the  URL, IPV4."
	DEFVAL{"0.0.0.0"}
	::=  {rsNADURLEntry 7}

rsNADURLL4PolicyNameV6 OBJECT-TYPE
   	SYNTAX DisplayString (SIZE (1..50))
   	ACCESS read-write
   	STATUS mandatory
   	DESCRIPTION
     	 "L4Policy Name with V6 VIP"
	DEFVAL  { "None" }
	::=  {rsNADURLEntry 8}

rsNADURLFarmNameV6 OBJECT-TYPE
    SYNTAX DisplayString (SIZE(1..50))
    ACCESS read-write
   	STATUS mandatory
   	DESCRIPTION
        "The name of the farm to use with the URL and IPV6 L4 policy."
	DEFVAL  { "None" }
	::=  {rsNADURLEntry 9}

rsNADURLPreferredResolveIPTypeV6 OBJECT-TYPE
   	SYNTAX InetAddressType
   	ACCESS read-write
   	STATUS mandatory
   	DESCRIPTION
     	 "The IP address type of the IP which the host name should be resolved preferably, IPV6."
	DEFVAL  { ipv6 }
	::=  {rsNADURLEntry 10}

rsNADURLPreferredResolveIPV6 OBJECT-TYPE
   	SYNTAX InetAddress
   	ACCESS read-write
   	STATUS mandatory
   	DESCRIPTION
     	 "Configures to which IP the host name should be resolved preferably, IPV6."
	DEFVAL{"::"}
	::=  {rsNADURLEntry 11}

rsNADURLNATAddrTypeV6 OBJECT-TYPE
   	SYNTAX InetAddressType
   	ACCESS read-write
   	STATUS mandatory
   	DESCRIPTION
     	 "The type of NAT IP address of the farm to use with the  URL, IPV6."
	DEFVAL  { ipv6 }
	::=  {rsNADURLEntry 12}

rsNADURLNATAddrV6 OBJECT-TYPE
   	SYNTAX InetAddress
   	ACCESS read-write
   	STATUS mandatory
   	DESCRIPTION
     	 "NAT IP address of the farm to use with the  URL, IPV6."
	DEFVAL{"::"}
	::=  {rsNADURLEntry 13}

rsNADURLStatus OBJECT-TYPE
    	SYNTAX RowStatus
    	ACCESS read-write
   	STATUS mandatory
   	DESCRIPTION
     	 "Row status for the URL."
	::=  {rsNADURLEntry 14}

rsNADRegexURLTable OBJECT-TYPE
   SYNTAX SEQUENCE OF RsNADRegexURLEntry
   ACCESS not-accessible
   STATUS mandatory
   DESCRIPTION
       "Hosts table, defines the DNS resolution for farms and SuperFarms"
   ::= {rsNWSD 103}

rsNADRegexURLEntry OBJECT-TYPE
   SYNTAX RsNADRegexURLEntry
   ACCESS not-accessible
   STATUS mandatory
   DESCRIPTION
       " The row definition for this table."
   INDEX  {rsNADRegexURL}
   ::= {rsNADRegexURLTable 1}

RsNADRegexURLEntry  ::= SEQUENCE {
  rsNADRegexURL                         DisplayString,
  rsNADRegexURLL4PolicyNameV4           DisplayString,
  rsNADRegexURLFarmNameV4               DisplayString,
  rsNADRegexURLPreferredResolveIPTypeV4 InetAddressType,
  rsNADRegexURLPreferredResolveIPV4     InetAddress,
  rsNADRegexURLNATAddrTypeV4            InetAddressType,
  rsNADRegexURLNATAddrV4                InetAddress,
  rsNADRegexURLL4PolicyNameV6           DisplayString,
  rsNADRegexURLFarmNameV6               DisplayString,
  rsNADRegexURLPreferredResolveIPTypeV6 InetAddressType,
  rsNADRegexURLPreferredResolveIPV6     InetAddress,
  rsNADRegexURLNATAddrTypeV6            InetAddressType,
  rsNADRegexURLNATAddrV6                InetAddress,
  rsNADRegexURLIndex                    INTEGER,
  rsNADRegexURLStatus                   RowStatus
}

rsNADRegexURL OBJECT-TYPE
        SYNTAX DisplayString (SIZE (1..80))
        ACCESS read-write
    STATUS mandatory
    DESCRIPTION
         "The URL representing the farm."
    ::=  {rsNADRegexURLEntry 1}

rsNADRegexURLL4PolicyNameV4 OBJECT-TYPE
    SYNTAX DisplayString (SIZE (1..50))
    ACCESS read-write
    STATUS mandatory
    DESCRIPTION
         "L4Policy Name with IPV4 VIP"
    DEFVAL  { "None" }
    ::=  {rsNADRegexURLEntry 2}

rsNADRegexURLFarmNameV4 OBJECT-TYPE
    SYNTAX DisplayString (SIZE(1..50))
    ACCESS read-write
    STATUS mandatory
    DESCRIPTION
        "The name of the farm to use with the URL and IPV4 L4 policy."
    DEFVAL  { "None" }
    ::=  {rsNADRegexURLEntry 3}

rsNADRegexURLPreferredResolveIPTypeV4 OBJECT-TYPE
    SYNTAX InetAddressType
    ACCESS read-write
    STATUS mandatory
    DESCRIPTION
         "The IP address type of the IP which the host name should be resolved preferably, IPV4."
    DEFVAL  { ipv4 }
    ::=  {rsNADRegexURLEntry 4}

rsNADRegexURLPreferredResolveIPV4 OBJECT-TYPE
    SYNTAX InetAddress
    ACCESS read-write
    STATUS mandatory
    DESCRIPTION
       "Configures to which IP the host name should be resolved preferably, IPV4."
    DEFVAL{"0.0.0.0"}
    ::=  {rsNADRegexURLEntry 5}

rsNADRegexURLNATAddrTypeV4 OBJECT-TYPE
    SYNTAX InetAddressType
    ACCESS read-write
    STATUS mandatory
    DESCRIPTION
         "The type of NAT IP address of the farm to use with the  URL, IPV4 ."
    DEFVAL  { ipv4 }
    ::=  {rsNADRegexURLEntry 6}

rsNADRegexURLNATAddrV4 OBJECT-TYPE
    SYNTAX InetAddress
    ACCESS read-write
    STATUS mandatory
    DESCRIPTION
         "NAT IP address of the farm to use with the  URL, IPV4."
    DEFVAL{"0.0.0.0"}
    ::=  {rsNADRegexURLEntry 7}

rsNADRegexURLL4PolicyNameV6 OBJECT-TYPE
    SYNTAX DisplayString (SIZE (1..50))
    ACCESS read-write
    STATUS mandatory
    DESCRIPTION
       "L4Policy Name with V6 VIP"
    DEFVAL  { "None" }
    ::=  {rsNADRegexURLEntry 8}

rsNADRegexURLFarmNameV6 OBJECT-TYPE
    SYNTAX DisplayString (SIZE(1..50))
    ACCESS read-write
    STATUS mandatory
    DESCRIPTION
        "The name of the farm to use with the URL and IPV6 L4 policy."
    DEFVAL  { "None" }
    ::=  {rsNADRegexURLEntry 9}

rsNADRegexURLPreferredResolveIPTypeV6 OBJECT-TYPE
    SYNTAX InetAddressType
    ACCESS read-write
    STATUS mandatory
    DESCRIPTION
         "The IP address type of the IP which the host name should be resolved preferably, IPV6."
    DEFVAL  { ipv6 }
    ::=  {rsNADRegexURLEntry 10}

rsNADRegexURLPreferredResolveIPV6 OBJECT-TYPE
    SYNTAX InetAddress
    ACCESS read-write
    STATUS mandatory
    DESCRIPTION
         "Configures to which IP the host name should be resolved preferably, IPV6."
    DEFVAL{"::"}
    ::=  {rsNADRegexURLEntry 11}

rsNADRegexURLNATAddrTypeV6 OBJECT-TYPE
    SYNTAX InetAddressType
    ACCESS read-write
    STATUS mandatory
    DESCRIPTION
         "The type of NAT IP address of the farm to use with the  URL, IPV6."
    DEFVAL  { ipv6 }
    ::=  {rsNADRegexURLEntry 12}

rsNADRegexURLNATAddrV6 OBJECT-TYPE
    SYNTAX InetAddress
    ACCESS read-write
    STATUS mandatory
    DESCRIPTION
         "NAT IP address of the farm to use with the  URL, IPV6."
    DEFVAL{"::"}
    ::=  {rsNADRegexURLEntry 13}

rsNADRegexURLIndex OBJECT-TYPE
    SYNTAX INTEGER
    ACCESS read-write
    STATUS mandatory
    DESCRIPTION
    "Regular expression evaluation order."
    ::= { rsNADRegexURLEntry 14}


rsNADRegexURLStatus OBJECT-TYPE
    SYNTAX RowStatus
    ACCESS read-write
    STATUS mandatory
    DESCRIPTION
         "Row status for the URL."
    ::=  {rsNADRegexURLEntry 15}

rsWSDMainVirtualDNS OBJECT-TYPE
    	SYNTAX IpAddress
    	ACCESS read-write
   	STATUS mandatory
   	DESCRIPTION
     	 "Main DNS virtual IP address."
	::=  {rsNWSD 4}

rsWSDBackupVirtualDNS OBJECT-TYPE
    	SYNTAX IpAddress
    	ACCESS read-write
   	STATUS mandatory
   	DESCRIPTION
     	 "Backup WSD virtual DNS IP address."
	::=  {rsNWSD 5}

rsWSDProximityMirrorProtocolMode OBJECT-TYPE
    SYNTAX  FeatureStatus
    ACCESS  read-write
    STATUS  mandatory
    DESCRIPTION
      "Enable/Disable of the mirror protocol mode."
        ::=  {rsNWSD 7}

rsWSDTwoDNSAnswers OBJECT-TYPE
 SYNTAX  FeatureStatus
 ACCESS  read-write
 STATUS  mandatory
 DESCRIPTION
   "Enable/Disable two answers to DNS queries."
     ::=  {rsNWSD 10}

-- Note that in older versions (e.g. AppDirector 1.07) this MIB is rsNWSD 80 but it conflicts with
-- rsADSSLTPSLicense
rsADDNSAnswerThroughNhr OBJECT-TYPE
 SYNTAX  FeatureStatus
 ACCESS  read-write
 STATUS  mandatory
 DESCRIPTION
   "Enable/Disable DNS Reply by first DNS Answer."
     ::=  {rsNWSD 125}

rsWSDStatisticsDstIpAddr OBJECT-TYPE
    SYNTAX  IpAddress
    ACCESS  read-write
    STATUS  mandatory
    DESCRIPTION
      "Statistics Destination Ip Address"
        ::=  {rsNWSD 11}

rsWSDStatisticsReportingMode OBJECT-TYPE
    SYNTAX  INTEGER {
      full(1),
      disable(2),
      general(3),
      health(4)
    }
    ACCESS  read-write
    STATUS  mandatory
    DESCRIPTION
      "Statistics Reporting Mode: reporting enable / disable, full statistics
      report or partial"
        ::=  {rsNWSD 12}

rsWSDGeneralStatisticsPollingTime OBJECT-TYPE
    SYNTAX  INTEGER
    ACCESS  read-write
    STATUS  mandatory
    DESCRIPTION
      "Reporting polling time for general statistics"
        ::=  {rsNWSD 13}

rsWSDHealthStatisticsPollingTime OBJECT-TYPE
    SYNTAX  INTEGER
    ACCESS  read-write
    STATUS  mandatory
    DESCRIPTION
      "Reporting polling time for health statistics"
        ::=  {rsNWSD 14}

rsWSDAcceptableHTTPCodesTable OBJECT-TYPE
   SYNTAX SEQUENCE OF RsWSDAcceptableHTTPCodeEntry
   ACCESS not-accessible
   STATUS mandatory
   DESCRIPTION
       "A table for managing the acceptable HTTP codes received by extended
        connectivity check."
   ::= {rsNWSD 15}

rsWSDAcceptableHTTPCodeEntry OBJECT-TYPE
   SYNTAX RsWSDAcceptableHTTPCodeEntry
   ACCESS not-accessible
   STATUS mandatory
   DESCRIPTION
       " The row definition for this table."
   INDEX  {rsWSDAcceptableHTTPCodeFarm,
           rsWSDAcceptableHTTPCode}
   ::= {rsWSDAcceptableHTTPCodesTable 1}

RsWSDAcceptableHTTPCodeEntry ::= SEQUENCE {
  rsWSDAcceptableHTTPCodeFarm     IpAddress,
  rsWSDAcceptableHTTPCode         INTEGER,
  rsWSDAcceptableHTTPCodeStatus   RowStatus
}

rsWSDAcceptableHTTPCodeFarm OBJECT-TYPE
  SYNTAX IpAddress
  ACCESS read-write
  STATUS mandatory
  DESCRIPTION
     "IP address of the farm where the code is defined."
  ::=  {rsWSDAcceptableHTTPCodeEntry 1}

rsWSDAcceptableHTTPCode  OBJECT-TYPE
  SYNTAX INTEGER
  ACCESS read-write
  STATUS mandatory
  DESCRIPTION
     "The HTTP code acceptable in that farm."
  ::=  {rsWSDAcceptableHTTPCodeEntry 2}

rsWSDAcceptableHTTPCodeStatus OBJECT-TYPE
  SYNTAX RowStatus
  ACCESS read-write
  STATUS mandatory
  DESCRIPTION
    "Row status for the code."
  ::=  {rsWSDAcceptableHTTPCodeEntry 3}



-- AppDirector's Acceptable HTTP Codes table.

rsADAcceptableHTTPCodesTable OBJECT-TYPE
   SYNTAX SEQUENCE OF RsADAcceptableHTTPCodeEntry
   ACCESS not-accessible
   STATUS mandatory
   DESCRIPTION
       "A table for managing the acceptable HTTP codes received by extended
        connectivity check."
   ::= {rsNWSD 65}

rsADAcceptableHTTPCodeEntry OBJECT-TYPE
   SYNTAX RsADAcceptableHTTPCodeEntry
   ACCESS not-accessible
   STATUS mandatory
   DESCRIPTION
       " The row definition for this table."
   INDEX  {rsADAcceptableHTTPCodeFarm,
           rsADAcceptableHTTPCode}
   ::= {rsADAcceptableHTTPCodesTable 1}

RsADAcceptableHTTPCodeEntry ::= SEQUENCE {
  rsADAcceptableHTTPCodeFarm     DisplayString,
  rsADAcceptableHTTPCode         INTEGER,
  rsADAcceptableHTTPCodeStatus   RowStatus
}

rsADAcceptableHTTPCodeFarm OBJECT-TYPE
  SYNTAX DisplayString (SIZE(1..50))
  ACCESS read-only
  STATUS mandatory
  DESCRIPTION
     "The name of the farm where the code is defined."
  ::=  {rsADAcceptableHTTPCodeEntry 1}

rsADAcceptableHTTPCode  OBJECT-TYPE
  SYNTAX INTEGER
  ACCESS read-only
  STATUS mandatory
  DESCRIPTION
     "The HTTP code acceptable in that farm."
  ::=  {rsADAcceptableHTTPCodeEntry 2}

rsADAcceptableHTTPCodeStatus OBJECT-TYPE
  SYNTAX RowStatus
  ACCESS read-write
  STATUS mandatory
  DESCRIPTION
    "Row status for the code."
  ::=  {rsADAcceptableHTTPCodeEntry 3}




rsWSDTotalNumberOfClients OBJECT-TYPE
  SYNTAX OCTET STRING (SIZE(8))
  ACCESS read-only
  STATUS mandatory
  DESCRIPTION
    "Total number of clients per device."
   ::= {rsNWSD 16}

rsWSDCurrentNumberOfClients OBJECT-TYPE
  SYNTAX INTEGER
  ACCESS read-only
  STATUS mandatory
  DESCRIPTION
    "Current number of clients per device."
   ::= {rsNWSD 17}

rsWSDFramesLoadInBytes OBJECT-TYPE
  SYNTAX OCTET STRING (SIZE(8))
  ACCESS read-only
  STATUS mandatory
  DESCRIPTION
    "Frames load in bytes per device."
   ::= {rsNWSD 18}

rsWSDRedundancyFailed OBJECT-TYPE
  SYNTAX INTEGER
  ACCESS read-only
  STATUS mandatory
  DESCRIPTION
    "Redundancy failed flag."
   ::= {rsNWSD 19}

rsWSDRedundancyTakeOver OBJECT-TYPE
  SYNTAX INTEGER
  ACCESS read-only
  STATUS mandatory
  DESCRIPTION
    "Redundancy take over flag."
   ::= {rsNWSD 20}

rsWSDDynamicProximityTableFilledUp OBJECT-TYPE
  SYNTAX INTEGER
  ACCESS read-only
  STATUS mandatory
  DESCRIPTION
    "Proximity table filled up flag."
   ::= {rsNWSD 21}

rsWSDClientTableFilledUp OBJECT-TYPE
  SYNTAX INTEGER
  ACCESS read-only
  STATUS mandatory
  DESCRIPTION
    "Client table filled up flag."
   ::= {rsNWSD 22}

rsWSDSSFTable OBJECT-TYPE
   SYNTAX SEQUENCE OF RsWSDSSFEntry
   ACCESS not-accessible
   STATUS mandatory
   DESCRIPTION
          "The table that contains general parameters for secondary servers."
   ::= {rsNWSD 23}

rsWSDSSFEntry OBJECT-TYPE
    SYNTAX RsWSDSSFEntry
    ACCESS not-accessible
    STATUS  mandatory
    DESCRIPTION
       " The row definition for the SSF table."
   INDEX  {rsWSDSSFName}
   ::= {rsWSDSSFTable 1}

RsWSDSSFEntry  ::= SEQUENCE {
  rsWSDSSFName                 DisplayString,
  rsWSDSSFStatus               INTEGER,
  rsWSDSSFCheckMethod          INTEGER,
  rsWSDSSFCheckInterval        INTEGER,
  rsWSDSSFCheckRetries         INTEGER,
  rsWSDSSFCheckPort            INTEGER,
  rsWSDSSFCheckCommunity       DisplayString,
  rsWSDSSFMode                 INTEGER,
  rsWSDSSFOperStatus           INTEGER,
  rsWSDSSFId                   INTEGER
}

rsWSDSSFName OBJECT-TYPE
    SYNTAX DisplayString (SIZE(1..20))
    ACCESS  read-write
    STATUS  mandatory
    DESCRIPTION
      "The name assigned by the user to this SSF."
    ::= {rsWSDSSFEntry 1}

rsWSDSSFStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSSFEntry 2}

rsWSDSSFCheckMethod OBJECT-TYPE
    SYNTAX INTEGER {
         disable(1),
         ping(2),
         tcp(3),
         oAS(4),
         oDB(5)
      }
    ACCESS  read-write
    STATUS  mandatory
    DESCRIPTION
     	 "Connectivity check method for the SSF."
    DEFVAL  { 2 }
    ::=  {rsWSDSSFEntry 3}

rsWSDSSFCheckInterval OBJECT-TYPE
    SYNTAX  INTEGER  (1..3600)
    ACCESS  read-write
    STATUS  mandatory
    DESCRIPTION
      "Polling interval in seconds for the secondary servers."
   DEFVAL  { 10 }
    ::=  {rsWSDSSFEntry 4}

rsWSDSSFCheckRetries OBJECT-TYPE
    SYNTAX  INTEGER  (1..20)
    ACCESS  read-write
    STATUS  mandatory
    DESCRIPTION
      "Minimum number of unsuccessful polling attempts before a server is
deemed
      disconnected."
    DEFVAL  { 5 }
    ::=  {rsWSDSSFEntry 5}

rsWSDSSFCheckPort OBJECT-TYPE
    SYNTAX INTEGER
    ACCESS  read-write
    STATUS  mandatory
    DESCRIPTION
     	 "Application port for TCP secondary server connectivity check."
    DEFVAL  { 80 }
    ::=  {rsWSDSSFEntry 6}

rsWSDSSFCheckCommunity OBJECT-TYPE
    SYNTAX DisplayString (SIZE(1..20))
    ACCESS  read-write
    STATUS  mandatory
    DESCRIPTION
        "The SNMP community to use in special secondary server polling."
    DEFVAL  { "public" }
    ::= {rsWSDSSFEntry 7}

rsWSDSSFMode  OBJECT-TYPE
    SYNTAX INTEGER {
      inclusive(1),
      singleFailure(2)
    }
    ACCESS  read-write
    STATUS  mandatory
    DESCRIPTION
      "Operation mode for SSF in case of failure. Either fail farm/server
        when all secondary servers
       fail (inclusive mode), or fail them when just one secondary server
        fails (single failure)."
    DEFVAL { 1 }
    ::=  {rsWSDSSFEntry 8}

rsWSDSSFOperStatus OBJECT-TYPE
   SYNTAX INTEGER {
       active(1),
       notInService(2)
     }
   ACCESS read-only
   STATUS  mandatory
    DESCRIPTION
      "Secondary server farm status. Active - farm is active.
       NotInService - one or more servers are not responding."
  ::=  { rsWSDSSFEntry 9}

rsWSDSSFId OBJECT-TYPE
   SYNTAX INTEGER
   ACCESS read-write
   STATUS  mandatory
    DESCRIPTION
      "The Id is used an alternate key to the SSF table"
  ::=  { rsWSDSSFEntry 10}

rsWSDSecondaryServerTable OBJECT-TYPE
   SYNTAX SEQUENCE OF RsWSDSecondaryServerEntry
   ACCESS not-accessible
   STATUS mandatory
   DESCRIPTION
          "The table that contains specific parameters for secondary servers."
   ::= {rsNWSD 24}

rsWSDSecondaryServerEntry OBJECT-TYPE
    SYNTAX RsWSDSecondaryServerEntry
    ACCESS not-accessible
    STATUS  mandatory
    DESCRIPTION
       "The row definition for the secondary server table."
   INDEX  {rsWSDSecondaryServerSSFName,
           rsWSDSecondaryServerAddr}
   ::= {rsWSDSecondaryServerTable 1}

RsWSDSecondaryServerEntry ::= SEQUENCE {
  rsWSDSecondaryServerSSFName           DisplayString,
  rsWSDSecondaryServerAddr              IpAddress,
  rsWSDSecondaryServerStatus            INTEGER,
  rsWSDSecondaryServerOperStatus        INTEGER,
  rsWSDSecondaryServerId                INTEGER
}

rsWSDSecondaryServerSSFName OBJECT-TYPE
    SYNTAX DisplayString (SIZE(1..20))
    ACCESS  read-write
    STATUS  mandatory
    DESCRIPTION
      "The name of the SSF of which the secondary server is a member."
    ::= {rsWSDSecondaryServerEntry 1}

rsWSDSecondaryServerAddr  OBJECT-TYPE
    SYNTAX  IpAddress
    ACCESS  read-write
    STATUS  mandatory
    DESCRIPTION
     "Secondary Server IP address."
 ::=  {rsWSDSecondaryServerEntry 2}

rsWSDSecondaryServerStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSecondaryServerEntry 3}

rsWSDSecondaryServerOperStatus OBJECT-TYPE
      SYNTAX INTEGER {
        active(1),
        notInService(2)
      }
    ACCESS  read-only
    STATUS  mandatory
    DESCRIPTION
      "Secondary server status. Active - server is active. NotInService -
server is not responding."
  ::=  {rsWSDSecondaryServerEntry 4}

rsWSDSecondaryServerId OBJECT-TYPE
    SYNTAX INTEGER
    ACCESS  read-write
    STATUS  mandatory
    DESCRIPTION
      "The Id serves as an alternate key to the SSF table"
  ::=  {rsWSDSecondaryServerEntry 5}

rsWSDSSFFarmTable OBJECT-TYPE
   SYNTAX SEQUENCE OF RsWSDSSFFarmEntry
   ACCESS not-accessible
   STATUS mandatory
   DESCRIPTION
          "The table that is used to configure farms in SSF."
   ::= {rsNWSD 25}

rsWSDSSFFarmEntry OBJECT-TYPE
    SYNTAX RsWSDSSFFarmEntry
    ACCESS not-accessible
    STATUS  mandatory
    DESCRIPTION
       "The row definition for the farm-SSF table."
   INDEX  {rsWSDSSFFarmSSFName,
           rsWSDSSFFarmAddr}
   ::= {rsWSDSSFFarmTable 1}

RsWSDSSFFarmEntry ::= SEQUENCE {
  rsWSDSSFFarmSSFName                       DisplayString,
  rsWSDSSFFarmAddr                          IpAddress,
  rsWSDSSFFarmStatus                        INTEGER,
  rsWSDSSFFarmId                            INTEGER
}

rsWSDSSFFarmSSFName OBJECT-TYPE
    SYNTAX DisplayString (SIZE(1..20))
    ACCESS  read-write
    STATUS  mandatory
    DESCRIPTION
      "The name of the SSF to which the farm is attached."
    ::= {rsWSDSSFFarmEntry 1}

rsWSDSSFFarmAddr  OBJECT-TYPE
    SYNTAX  IpAddress
    ACCESS  read-write
    STATUS  mandatory
    DESCRIPTION
     "Attached farm IP address."
 ::=  {rsWSDSSFFarmEntry 2}

rsWSDSSFFarmStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSSFFarmEntry 3}

rsWSDSSFFarmId OBJECT-TYPE
    SYNTAX INTEGER
    ACCESS  read-write
    STATUS  mandatory
    DESCRIPTION
      "The Id is an alternate key to the SSF table"
  ::=  {rsWSDSSFFarmEntry 4}

rsWSDClientGroupingMask OBJECT-TYPE
   SYNTAX IpAddress
   ACCESS read-write
   STATUS mandatory
   DESCRIPTION
           "Client IP address mask."
   ::=  {rsNWSD 26}

rsNADClientGroupingSuffixLen OBJECT-TYPE
   SYNTAX INTEGER (0..32)
   ACCESS read-write
   STATUS mandatory
   DESCRIPTION
           "Client IP address mask."
   ::=  {rsNWSD 89}


rsNADClientGroupingSuffixLenV6 OBJECT-TYPE
   SYNTAX INTEGER (0..128)
   ACCESS read-write
   STATUS mandatory
   DESCRIPTION
           "Client IP address mask."
   ::=  {rsNWSD 79}


rsWSDSSFServerTable OBJECT-TYPE
   SYNTAX SEQUENCE OF RsWSDSSFServerEntry
   ACCESS not-accessible
   STATUS mandatory
   DESCRIPTION
          "The table that is used to configure servers in SSF."
   ::= {rsNWSD 27}

rsWSDSSFServerEntry OBJECT-TYPE
    SYNTAX RsWSDSSFServerEntry
    ACCESS not-accessible
    STATUS  mandatory
    DESCRIPTION
       "The row definition for the server-SSF table."
   INDEX  {rsWSDSSFServerSSFName,
                 rsWSDSSFServerFarmAddr,
                 rsWSDSSFServerSrvrAddr}
   ::= {rsWSDSSFServerTable 1}

RsWSDSSFServerEntry ::= SEQUENCE {
  rsWSDSSFServerSSFName                DisplayString,
  rsWSDSSFServerFarmAddr               IpAddress,
  rsWSDSSFServerSrvrAddr               IpAddress,
  rsWSDSSFServerStatus                 INTEGER,
  rsWSDSSFServerId                     INTEGER
}

rsWSDSSFServerSSFName OBJECT-TYPE
    SYNTAX DisplayString (SIZE(1..20))
    ACCESS  read-write
    STATUS  mandatory
    DESCRIPTION
      "The name of the SSF to which the server is attached."
    ::= {rsWSDSSFServerEntry 1}

rsWSDSSFServerFarmAddr  OBJECT-TYPE
    SYNTAX  IpAddress
    ACCESS  read-write
    STATUS  mandatory
    DESCRIPTION
     "Attached server's farm IP address."
 ::=  {rsWSDSSFServerEntry 2}

rsWSDSSFServerSrvrAddr  OBJECT-TYPE
    SYNTAX  IpAddress
    ACCESS  read-write
    STATUS  mandatory
    DESCRIPTION
     "Attached server's IP address."
 ::=  {rsWSDSSFServerEntry 3}

rsWSDSSFServerStatus OBJECT-TYPE
      SYNTAX INTEGER {
        active(1),
        notInService(2),
        notReady(3),
        createAndGo(4),
        createAndWait(5),
        destroy(6) }
    ACCESS  read-write
    STATUS  mandatory
    DESCRIPTION
      "Administrative status of this entry. "
  ::=  {rsWSDSSFServerEntry 4}

rsWSDSSFServerId OBJECT-TYPE
    SYNTAX INTEGER
    ACCESS  read-write
    STATUS  mandatory
    DESCRIPTION
      "The Id is an alternate key to the SSF table"
  ::=  {rsWSDSSFServerEntry 5}

rsWSDHTTPContentCheckTable OBJECT-TYPE
   SYNTAX SEQUENCE OF RsWSDHTTPContentCheckEntry
   ACCESS not-accessible
   STATUS mandatory
   DESCRIPTION
       "A table for managing the strings that the WSD looks for in HTTP responses (to extended
        connectivity checks)."
   ::= {rsNWSD 28}

rsWSDHTTPContentCheckEntry OBJECT-TYPE
   SYNTAX RsWSDHTTPContentCheckEntry
   ACCESS not-accessible
   STATUS mandatory
   DESCRIPTION
       " The row definition for this table."
   INDEX  {rsWSDHTTPContentCheckFarm}
   ::= {rsWSDHTTPContentCheckTable 1}

RsWSDHTTPContentCheckEntry ::= SEQUENCE {
  rsWSDHTTPContentCheckFarm    IpAddress,
  rsWSDHTTPContentCheckString   DisplayString,
  rsWSDHTTPContentCheckMode    INTEGER,
  rsWSDHTTPContentCheckStatus     RowStatus
}

rsWSDHTTPContentCheckFarm OBJECT-TYPE
  SYNTAX IpAddress
  ACCESS read-only
  STATUS mandatory
  DESCRIPTION
     "IP address of the farm where the extended check is made."
  ::=  {rsWSDHTTPContentCheckEntry 1}

rsWSDHTTPContentCheckString OBJECT-TYPE
    SYNTAX DisplayString (SIZE(1..64))
    ACCESS  read-write
    STATUS  mandatory
    DESCRIPTION
      "The string to look for in the HTTP response."
    ::= {rsWSDHTTPContentCheckEntry 2}

rsWSDHTTPContentCheckMode OBJECT-TYPE
      SYNTAX INTEGER {
        stringExists(1),
        stringIsAbsent(2)}
    ACCESS  read-write
    STATUS  mandatory
    DESCRIPTION
      "Type of checks - should the check be that the string exists or that it is absent."
    DEFVAL  { 1 }
  ::=  {rsWSDHTTPContentCheckEntry 3}

rsWSDHTTPContentCheckStatus OBJECT-TYPE
  SYNTAX RowStatus
  ACCESS read-write
  STATUS mandatory
  DESCRIPTION
    "Row status for the string."
  ::=  {rsWSDHTTPContentCheckEntry 4}


-- AppDirector's HTTP content check table

rsADHTTPContentCheckTable OBJECT-TYPE
   SYNTAX SEQUENCE OF RsADHTTPContentCheckEntry
   ACCESS not-accessible
   STATUS mandatory
   DESCRIPTION
       "A table for managing the strings that the AppDirector looks for in HTTP responses (for extended
        connectivity checks)."
   ::= {rsNWSD 66}

rsADHTTPContentCheckEntry OBJECT-TYPE
   SYNTAX RsADHTTPContentCheckEntry
   ACCESS not-accessible
   STATUS mandatory
   DESCRIPTION
       " The row definition for this table."
   INDEX  {rsADHTTPContentCheckFarm}
   ::= {rsADHTTPContentCheckTable 1}

RsADHTTPContentCheckEntry ::= SEQUENCE {
  rsADHTTPContentCheckFarm      DisplayString,
  rsADHTTPContentCheckStatus    RowStatus,
  rsADHTTPContentCheckString    DisplayString,
  rsADHTTPContentCheckMode      INTEGER
}

rsADHTTPContentCheckFarm OBJECT-TYPE
  SYNTAX DisplayString (SIZE(1..50))
  ACCESS read-only
  STATUS mandatory
  DESCRIPTION
     "The name of the farm where the extended check is made."
  ::=  {rsADHTTPContentCheckEntry 1}

rsADHTTPContentCheckStatus OBJECT-TYPE
  SYNTAX RowStatus
  ACCESS read-write
  STATUS mandatory
  DESCRIPTION
    "Row status for the string."
  ::=  {rsADHTTPContentCheckEntry 2}

rsADHTTPContentCheckString OBJECT-TYPE
    SYNTAX DisplayString (SIZE(1..64))
    ACCESS  read-write
    STATUS  mandatory
    DESCRIPTION
      "The string to look for in the HTTP response."
    ::= {rsADHTTPContentCheckEntry 3}

rsADHTTPContentCheckMode OBJECT-TYPE
      SYNTAX INTEGER {
        stringExists(1),
        stringIsAbsent(2)}
    ACCESS  read-write
    STATUS  mandatory
    DESCRIPTION
      "Type of checks - should the check be that the string exists or that it is absent."
    DEFVAL  { 1 }
  ::=  {rsADHTTPContentCheckEntry 4}



rsNWSDStats  OBJECT IDENTIFIER ::= { rsNWSD 29 }

rsWSDTotalDNSReqCounter OBJECT-TYPE
    SYNTAX  OCTET STRING (SIZE(8))
    ACCESS  read-only
    STATUS  mandatory
    DESCRIPTION
    "Total DNS requests counter."
    ::= {rsNWSDStats 1}

rsWSDAnsweredDNSReqCounter OBJECT-TYPE
    SYNTAX  OCTET STRING (SIZE(8))
    ACCESS  read-only
    STATUS  mandatory
    DESCRIPTION
    "Answered DNS requests counter."
    ::= {rsNWSDStats 2}

rsWSDBadDNSReqCounter OBJECT-TYPE
    SYNTAX  OCTET STRING (SIZE(8))
    ACCESS  read-only
    STATUS  mandatory
    DESCRIPTION
    "Bad DNS requests counter."
    ::= {rsNWSDStats 3}

rsWSDTotalDNSReqLastSecCounter OBJECT-TYPE
    SYNTAX INTEGER
    ACCESS read-only
    STATUS mandatory
    DESCRIPTION
    "Total DNS requests last second counter."
    ::=  {rsNWSDStats 4}

rsWSDAnsweredDNSReqLastSecCounter OBJECT-TYPE
    SYNTAX INTEGER
    ACCESS read-only
    STATUS mandatory
    DESCRIPTION
    "Answered DNS requests last second counter."
    ::=  {rsNWSDStats 5}

rsWSDBadDNSReqLastSecCounter OBJECT-TYPE
    SYNTAX INTEGER
    ACCESS read-only
    STATUS mandatory
    DESCRIPTION
    "Bad DNS requests last second counter."
    ::=  {rsNWSDStats 6}


rsNWSDFarmStatisticsTable OBJECT-TYPE
    SYNTAX SEQUENCE OF RsNWSDFarmStatisticsEntry
    ACCESS not-accessible
    STATUS mandatory
    DESCRIPTION
      "Table containing the Farm statistics values."
    ::=  {rsNWSDStats 7}

rsNWSDFarmStatisticsEntry OBJECT-TYPE
    SYNTAX RsNWSDFarmStatisticsEntry
    ACCESS not-accessible
    STATUS  mandatory
    DESCRIPTION
       " The row definition for this table."
   INDEX { rsNWSDFarmStatisticsAddress }
    ::=  {rsNWSDFarmStatisticsTable 1}

RsNWSDFarmStatisticsEntry ::= SEQUENCE {
  rsNWSDFarmStatisticsAddress					IpAddress,
  rsNWSDFarmStatisticsAttachedUsersNumber			INTEGER,
  rsNWSDFarmStatisticsTotalAttachedUsersNumber			OCTET STRING,
  rsNWSDFarmStatisticsPeakLoad					INTEGER,
  rsNWSDFarmStatisticsFramesLoad				OCTET STRING,
  rsNWSDFarmStatisticsFramesRate				INTEGER,
  rsNWSDFarmStatisticsFramesLoadInBytes				OCTET STRING,
  rsNWSDFarmStatisticsFramesRateInBytes				Counter,
  rsNWSDFarmStatisticsBackupServerUsed				INTEGER,
  rsNWSDFarmStatisticsDistThresholdReached			INTEGER,
  rsNWSDFarmStatisticsCapacityThresholdReached			INTEGER,
  rsNWSDFarmStatisticsTotalDNSReqCounter			Counter,
  rsNWSDFarmStatisticsTotalDNSReqLastSecCounter			Counter,
  rsNWSDFarmStatisticsLocalyAnsweredDNSReqCounter		Counter,
  rsNWSDFarmStatisticsLocalyAnsweredDNSReqLastSecCounter	Counter,
  rsNWSDFarmStatisticsRedirectedDNSReqCounter			Counter,
  rsNWSDFarmStatisticsRedirectedDNSReqLastSecCounter	  	Counter,
  rsNWSDFarmStatisticsTotalHTTPSessionsCounter                 OCTET STRING,
  rsNWSDFarmStatisticsTotalHTTPSessionsLastSecCounter          Counter,
  rsNWSDFarmStatisticsLocalHTTPSessionsCounter                 OCTET STRING,
  rsNWSDFarmStatisticsLocalHTTPSessionsLastSecCounter          Counter,
  rsNWSDFarmStatisticsRedirectedHTTPSessionsCounter            OCTET STRING,
  rsNWSDFarmStatisticsRedirectedHTTPSessionsLastSecCounter     Counter,
  rsNWSDFarmStatisticsTotalTriangSessionsCounter               OCTET STRING,
  rsNWSDFarmStatisticsTotalTriangSessionsLastSecCounter        Counter,
  rsNWSDFarmStatisticsLocalTriangSessionsCounter               OCTET STRING,
  rsNWSDFarmStatisticsLocalTriangSessionsLastSecCounter        Counter,
  rsNWSDFarmStatisticsRedirectedTriangSessionsCounter          OCTET STRING,
  rsNWSDFarmStatisticsRedirectedTriangSessionsLastSecCounter   Counter,
  rsNWSDFarmStatisticsTotalRTSPSessionsCounter                 OCTET STRING,
  rsNWSDFarmStatisticsTotalRTSPSessionsLastSecCounter          Counter,
  rsNWSDFarmStatisticsLocalRTSPSessionsCounter                 OCTET STRING,
  rsNWSDFarmStatisticsLocalRTSPSessionsLastSecCounter          Counter,
  rsNWSDFarmStatisticsRedirectedRTSPSessionsCounter            OCTET STRING,
  rsNWSDFarmStatisticsRedirectedRTSPSessionsLastSecCounter     Counter,
  rsNWSDFarmStatisticsDirectedAttachedUsersNum                 INTEGER,
  rsNWSDFarmStatisticsAverageDirectedAttachedUsersNum          INTEGER,
  rsNWSDFarmStatisticsTotalSIPSessionsCounter                  OCTET STRING,
  rsNWSDFarmStatisticsTotalSIPSessionsLastSecCounter           Counter,
  rsNWSDFarmStatisticsLocalSIPSessionsCounter                  OCTET STRING,
  rsNWSDFarmStatisticsLocalSIPSessionsLastSecCounter           Counter,
  rsNWSDFarmStatisticsRedirectedSIPSessionsCounter             OCTET STRING,
  rsNWSDFarmStatisticsRedirectedSIPSessionsLastSecCounter      Counter,
  rsNWSDFarmStatisticsTotalProxySessionsCounter                OCTET STRING,
  rsNWSDFarmStatisticsTotalProxySessionsLastSecCounter         Counter,
  rsNWSDFarmStatisticsLocalProxySessionsCounter                OCTET STRING,
  rsNWSDFarmStatisticsLocalProxySessionsLastSecCounter         Counter,
  rsNWSDFarmStatisticsRedirectedProxySessionsCounter           OCTET STRING,
  rsNWSDFarmStatisticsRedirectedProxySessionsLastSecCounter    Counter
}


rsNWSDFarmStatisticsAddress OBJECT-TYPE
    SYNTAX IpAddress
    ACCESS  read-only
    STATUS  mandatory
    DESCRIPTION
      "The IP Address of the farm."
    ::= {rsNWSDFarmStatisticsEntry 1}

rsNWSDFarmStatisticsAttachedUsersNumber OBJECT-TYPE
    SYNTAX  INTEGER
    ACCESS  read-only
    STATUS  mandatory
    DESCRIPTION
      "Farm current connected users number."
    ::= {rsNWSDFarmStatisticsEntry 2}

rsNWSDFarmStatisticsTotalAttachedUsersNumber OBJECT-TYPE
    SYNTAX  OCTET STRING (SIZE(8))
    ACCESS  read-only
    STATUS  mandatory
    DESCRIPTION
      "Farm total users number since last reset of the device."
    ::= {rsNWSDFarmStatisticsEntry 3}

rsNWSDFarmStatisticsPeakLoad OBJECT-TYPE
    SYNTAX  INTEGER
    ACCESS  read-only
    STATUS  mandatory
    DESCRIPTION
      "Farm peak load of packets per second."
    ::= {rsNWSDFarmStatisticsEntry 4}

rsNWSDFarmStatisticsFramesLoad OBJECT-TYPE
    SYNTAX  OCTET STRING (SIZE(8))
    ACCESS  read-only
    STATUS  mandatory
    DESCRIPTION
      "Farm total number of frames handled by the device."
    ::= {rsNWSDFarmStatisticsEntry 5}

rsNWSDFarmStatisticsFramesRate OBJECT-TYPE
    SYNTAX  INTEGER
    ACCESS  read-only
    STATUS  mandatory
    DESCRIPTION
      "Farm frames rate in the last minute."
    ::= {rsNWSDFarmStatisticsEntry 6}

rsNWSDFarmStatisticsFramesLoadInBytes OBJECT-TYPE
    SYNTAX  OCTET STRING (SIZE(8))
    ACCESS  read-only
    STATUS  mandatory
    DESCRIPTION
      "Bytes load per second."
    ::=  {rsNWSDFarmStatisticsEntry 7}

rsNWSDFarmStatisticsFramesRateInBytes OBJECT-TYPE
    SYNTAX  Counter
    ACCESS  read-only
    STATUS  mandatory
    DESCRIPTION
      "Bytes load rate per second."
    ::=  {rsNWSDFarmStatisticsEntry 8}

rsNWSDFarmStatisticsBackupServerUsed OBJECT-TYPE
    SYNTAX  INTEGER
    ACCESS  read-only
    STATUS  mandatory
    DESCRIPTION
      "Backup server used flag. It shows true if the
       backup server was used in the last reporting period"
    ::= {rsNWSDFarmStatisticsEntry 9}

rsNWSDFarmStatisticsDistThresholdReached OBJECT-TYPE
    SYNTAX  INTEGER
    ACCESS  read-only
    STATUS  mandatory
    DESCRIPTION
      "Distribution threshold reached flag. It shows true if the
       distribution threshold was reached in the last reporting period"
    ::= {rsNWSDFarmStatisticsEntry 10}

rsNWSDFarmStatisticsCapacityThresholdReached OBJECT-TYPE
    SYNTAX  INTEGER
    ACCESS  read-only
    STATUS  mandatory
    DESCRIPTION
      "Capacity threshold reached flag. It shows true if the
       capacity threshold was reached in the last reporting period"
    ::= {rsNWSDFarmStatisticsEntry 11}

rsNWSDFarmStatisticsTotalDNSReqCounter OBJECT-TYPE
    SYNTAX  Counter
    ACCESS  read-only
    STATUS  mandatory
    DESCRIPTION
    "Total number of DNS requests which arrived for this Farm."
    ::= {rsNWSDFarmStatisticsEntry 12}

rsNWSDFarmStatisticsTotalDNSReqLastSecCounter OBJECT-TYPE
    SYNTAX  Counter
    ACCESS  read-only
    STATUS  mandatory
    DESCRIPTION
    "Total number of DNS requests which arrived
	 for this Farm during the last second."
    ::= {rsNWSDFarmStatisticsEntry 13}

rsNWSDFarmStatisticsLocalyAnsweredDNSReqCounter OBJECT-TYPE
    SYNTAX  Counter
    ACCESS  read-only
    STATUS  mandatory
    DESCRIPTION
    "The number of DNS Requests which arrived for this
	 farm and were answered by the local farm."
    ::= {rsNWSDFarmStatisticsEntry 14}

rsNWSDFarmStatisticsLocalyAnsweredDNSReqLastSecCounter OBJECT-TYPE
    SYNTAX  Counter
    ACCESS  read-only
    STATUS  mandatory
    DESCRIPTION
    "The number of DNS Requests which arrived during the last second
	 for this farm and were answered by the local farm."
    ::= {rsNWSDFarmStatisticsEntry 15}

rsNWSDFarmStatisticsRedirectedDNSReqCounter OBJECT-TYPE
    SYNTAX  Counter
    ACCESS  read-only
    STATUS  mandatory
    DESCRIPTION
    "The number of DNS Requests which arrived for this
	 farm and were redirecteded to remote/distributed servers."
    ::= {rsNWSDFarmStatisticsEntry 16}

rsNWSDFarmStatisticsRedirectedDNSReqLastSecCounter OBJECT-TYPE
    SYNTAX  Counter
    ACCESS  read-only
    STATUS  mandatory
    DESCRIPTION
    "The number of DNS Requests which arrived during the last second
	 for this farm and were redirecteded to remote/distributed servers."
    ::= {rsNWSDFarmStatisticsEntry 17}

rsNWSDFarmStatisticsTotalHTTPSessionsCounter OBJECT-TYPE
    SYNTAX  OCTET STRING (SIZE(8))
    ACCESS  read-only
    STATUS  mandatory
    DESCRIPTION
    "Total number of HTTP sessions which arrived for this Farm."
    ::= {rsNWSDFarmStatisticsEntry 18}

rsNWSDFarmStatisticsTotalHTTPSessionsLastSecCounter OBJECT-TYPE
    SYNTAX  Counter
    ACCESS  read-only
    STATUS  mandatory
    DESCRIPTION
    "Total number of HTTP sessions which arrived
  	 for this Farm during the last second."
    ::= {rsNWSDFarmStatisticsEntry 19}

rsNWSDFarmStatisticsLocalHTTPSessionsCounter OBJECT-TYPE
    SYNTAX  OCTET STRING (SIZE(8))
    ACCESS  read-only
    STATUS  mandatory
    DESCRIPTION
    "The number of HTTP sessions which arrived for this
	   farm and were directed to a local server."
    ::= {rsNWSDFarmStatisticsEntry 20}

rsNWSDFarmStatisticsLocalHTTPSessionsLastSecCounter OBJECT-TYPE
    SYNTAX  Counter
    ACCESS  read-only
    STATUS  mandatory
    DESCRIPTION
    "The number of HTTP sessions which arrived during the
	   last second for this farm and were directed to a local server."
    ::= {rsNWSDFarmStatisticsEntry 21}

rsNWSDFarmStatisticsRedirectedHTTPSessionsCounter OBJECT-TYPE
    SYNTAX  OCTET STRING (SIZE(8))
    ACCESS  read-only
    STATUS  mandatory
    DESCRIPTION
    "The number of HTTP sessions which arrived for this
	   farm and were redirecteded to remote/distributed servers."
    ::= {rsNWSDFarmStatisticsEntry 22}

rsNWSDFarmStatisticsRedirectedHTTPSessionsLastSecCounter OBJECT-TYPE
    SYNTAX  Counter
    ACCESS  read-only
    STATUS  mandatory
    DESCRIPTION
    "The number of HTTP sessions which arrived during the last second
	   for this farm and were redirecteded to remote/distributed servers."
    ::= {rsNWSDFarmStatisticsEntry 23}


rsNWSDFarmStatisticsTotalTriangSessionsCounter OBJECT-TYPE
    SYNTAX  OCTET STRING (SIZE(8))
    ACCESS  read-only
    STATUS  mandatory
    DESCRIPTION
    "Total number of Tringulation sessions for this Farm."
    ::= {rsNWSDFarmStatisticsEntry 24}

rsNWSDFarmStatisticsTotalTriangSessionsLastSecCounter OBJECT-TYPE
    SYNTAX  Counter
    ACCESS  read-only
    STATUS  mandatory
    DESCRIPTION
    "Total number of Tringulation sessions which arrived
	   for this Farm during the last second."
    ::= {rsNWSDFarmStatisticsEntry 25}

rsNWSDFarmStatisticsLocalTriangSessionsCounter OBJECT-TYPE
    SYNTAX  OCTET STRING (SIZE(8))
    ACCESS  read-only
    STATUS  mandatory
    DESCRIPTION
    "The number of Tringulation sessions which arrived for this
	   farm and were answered by the a local server."
    ::= {rsNWSDFarmStatisticsEntry 26}

rsNWSDFarmStatisticsLocalTriangSessionsLastSecCounter OBJECT-TYPE
    SYNTAX  Counter
    ACCESS  read-only
    STATUS  mandatory
    DESCRIPTION
    "The number of Tringulation sessions which arrived during the
	   last second for this farm and were answered by a local server."
    ::= {rsNWSDFarmStatisticsEntry 27}

rsNWSDFarmStatisticsRedirectedTriangSessionsCounter OBJECT-TYPE
    SYNTAX  OCTET STRING (SIZE(8))
    ACCESS  read-only
    STATUS  mandatory
    DESCRIPTION
    "The number of sessions which were redirecteded by triangulation
     to distributed servers."
    ::= {rsNWSDFarmStatisticsEntry 28}

rsNWSDFarmStatisticsRedirectedTriangSessionsLastSecCounter OBJECT-TYPE
    SYNTAX  Counter
    ACCESS  read-only
    STATUS  mandatory
    DESCRIPTION
    "The number of sessions which were redirecteded by triangulation
	   during the last second to distributed servers."
    ::= {rsNWSDFarmStatisticsEntry 29}

rsNWSDFarmStatisticsTotalRTSPSessionsCounter OBJECT-TYPE
    SYNTAX  OCTET STRING (SIZE(8))
    ACCESS  read-only
    STATUS  mandatory
    DESCRIPTION
    "Total number of RTSP sessions which arrived for this Farm."
    ::= {rsNWSDFarmStatisticsEntry 30}

rsNWSDFarmStatisticsTotalRTSPSessionsLastSecCounter OBJECT-TYPE
    SYNTAX  Counter
    ACCESS  read-only
    STATUS  mandatory
    DESCRIPTION
    "Total number of RTSP sessions which arrived
  	 for this Farm during the last second."
    ::= {rsNWSDFarmStatisticsEntry 31}

rsNWSDFarmStatisticsLocalRTSPSessionsCounter OBJECT-TYPE
    SYNTAX  OCTET STRING (SIZE(8))
    ACCESS  read-only
    STATUS  mandatory
    DESCRIPTION
    "The number of RTSP sessions which arrived for this
	   farm and were directed to a local server."
    ::= {rsNWSDFarmStatisticsEntry 32}

rsNWSDFarmStatisticsLocalRTSPSessionsLastSecCounter OBJECT-TYPE
    SYNTAX  Counter
    ACCESS  read-only
    STATUS  mandatory
    DESCRIPTION
    "The number of RTSP sessions which arrived during the
	   last second for this farm and were directed to a local server."
    ::= {rsNWSDFarmStatisticsEntry 33}

rsNWSDFarmStatisticsRedirectedRTSPSessionsCounter OBJECT-TYPE
    SYNTAX  OCTET STRING (SIZE(8))
    ACCESS  read-only
    STATUS  mandatory
    DESCRIPTION
    "The number of RTSP sessions which arrived for this
	   farm and were redirecteded to remote/distributed servers."
    ::= {rsNWSDFarmStatisticsEntry 34}

rsNWSDFarmStatisticsRedirectedRTSPSessionsLastSecCounter OBJECT-TYPE
    SYNTAX  Counter
    ACCESS  read-only
    STATUS  mandatory
    DESCRIPTION
    "The number of RTSP sessions which arrived during the last second
	   for this farm and were redirecteded to remote/distributed servers."
    ::= {rsNWSDFarmStatisticsEntry 35}


rsNWSDFarmStatisticsDirectedAttachedUsersNum OBJECT-TYPE
    SYNTAX INTEGER
    ACCESS  read-only
    STATUS  mandatory
    DESCRIPTION
      "The number of directed attached clients to this farm"
    ::= {rsNWSDFarmStatisticsEntry 36}

rsNWSDFarmStatisticsAverageDirectedAttachedUsersNum OBJECT-TYPE
    SYNTAX INTEGER
    ACCESS  read-only
    STATUS  mandatory
    DESCRIPTION
      "The average number of directed attached clients to this farm"
    ::= {rsNWSDFarmStatisticsEntry 37}

rsNWSDFarmStatisticsTotalSIPSessionsCounter OBJECT-TYPE
    SYNTAX  OCTET STRING (SIZE(8))
    ACCESS  read-only
    STATUS  mandatory
    DESCRIPTION
    "Total number of SIP sessions which arrived for this Farm."
    ::= {rsNWSDFarmStatisticsEntry 38}

rsNWSDFarmStatisticsTotalSIPSessionsLastSecCounter OBJECT-TYPE
    SYNTAX  Counter
    ACCESS  read-only
    STATUS  mandatory
    DESCRIPTION
    "Total number of SIP sessions which arrived
  	 for this Farm during the last second."
    ::= {rsNWSDFarmStatisticsEntry 39}

rsNWSDFarmStatisticsLocalSIPSessionsCounter OBJECT-TYPE
    SYNTAX  OCTET STRING (SIZE(8))
    ACCESS  read-only
    STATUS  mandatory
    DESCRIPTION
    "The number of SIP sessions which arrived for this
	   farm and were directed to a local server."
    ::= {rsNWSDFarmStatisticsEntry 40}

rsNWSDFarmStatisticsLocalSIPSessionsLastSecCounter OBJECT-TYPE
    SYNTAX  Counter
    ACCESS  read-only
    STATUS  mandatory
    DESCRIPTION
    "The number of SIP sessions which arrived during the
	   last second for this farm and were directed to a local server."
    ::= {rsNWSDFarmStatisticsEntry 41}

rsNWSDFarmStatisticsRedirectedSIPSessionsCounter OBJECT-TYPE
    SYNTAX  OCTET STRING (SIZE(8))
    ACCESS  read-only
    STATUS  mandatory
    DESCRIPTION
    "The number of SIP sessions which arrived for this
	   farm and were redirecteded to remote/distributed servers."
    ::= {rsNWSDFarmStatisticsEntry 42}

rsNWSDFarmStatisticsRedirectedSIPSessionsLastSecCounter OBJECT-TYPE
    SYNTAX  Counter
    ACCESS  read-only
    STATUS  mandatory
    DESCRIPTION
    "The number of SIP sessions which arrived during the last second
	   for this farm and were redirecteded to remote/distributed servers."
    ::= {rsNWSDFarmStatisticsEntry 43}

rsNWSDFarmStatisticsTotalProxySessionsCounter OBJECT-TYPE
    SYNTAX  OCTET STRING (SIZE(8))
    ACCESS  read-only
    STATUS  mandatory
    DESCRIPTION
    "Total number of Proxy (Client NAT redirection) sessions which arrived for this Farm."
    ::= {rsNWSDFarmStatisticsEntry 44}

rsNWSDFarmStatisticsTotalProxySessionsLastSecCounter OBJECT-TYPE
    SYNTAX  Counter
    ACCESS  read-only
    STATUS  mandatory
    DESCRIPTION
    "Total number of Proxy (Client NAT redirection) sessions which arrived
  	 for this Farm during the last second."
    ::= {rsNWSDFarmStatisticsEntry 45}

rsNWSDFarmStatisticsLocalProxySessionsCounter OBJECT-TYPE
    SYNTAX  OCTET STRING (SIZE(8))
    ACCESS  read-only
    STATUS  mandatory
    DESCRIPTION
    "The number of Proxy (Client NAT redirection) sessions which arrived for this
	   farm and were directed to a local server."
    ::= {rsNWSDFarmStatisticsEntry 46}

rsNWSDFarmStatisticsLocalProxySessionsLastSecCounter OBJECT-TYPE
    SYNTAX  Counter
    ACCESS  read-only
    STATUS  mandatory
    DESCRIPTION
    "The number of Proxy (Client NAT redirection) sessions which arrived during the
	   last second for this farm and were directed to a local server."
    ::= {rsNWSDFarmStatisticsEntry 47}

rsNWSDFarmStatisticsRedirectedProxySessionsCounter OBJECT-TYPE
    SYNTAX  OCTET STRING (SIZE(8))
    ACCESS  read-only
    STATUS  mandatory
    DESCRIPTION
    "The number of Proxy (Client NAT redirection) sessions which arrived for this
	   farm and were redirecteded to remote/distributed servers."
    ::= {rsNWSDFarmStatisticsEntry 48}

rsNWSDFarmStatisticsRedirectedProxySessionsLastSecCounter OBJECT-TYPE
    SYNTAX  Counter
    ACCESS  read-only
    STATUS  mandatory
    DESCRIPTION
    "The number of Proxy (Client NAT redirection) sessions which arrived during the last second
	   for this farm and were redirecteded to remote/distributed servers."
    ::= {rsNWSDFarmStatisticsEntry 49}


rsADFarmStatisticsTable OBJECT-TYPE
    SYNTAX SEQUENCE OF RsADFarmStatisticsEntry
    ACCESS not-accessible
    STATUS mandatory
    DESCRIPTION
      "Table containing the Farm statistics values."
    ::=  {rsNWSDStats 20}

rsADFarmStatisticsEntry OBJECT-TYPE
    SYNTAX RsADFarmStatisticsEntry
    ACCESS not-accessible
    STATUS  mandatory
    DESCRIPTION
       " The row definition for this table."
   INDEX { rsADFarmStatisticsName }
    ::=  {rsADFarmStatisticsTable 1}

RsADFarmStatisticsEntry ::= SEQUENCE {
  rsADFarmStatisticsName					        DisplayString,
  rsADFarmStatisticsAttachedUsersNumber			INTEGER,
  rsADFarmStatisticsTotalAttachedUsersNumber			OCTET STRING,
  rsADFarmStatisticsPeakLoad					INTEGER,
  rsADFarmStatisticsFramesLoad				OCTET STRING,
  rsADFarmStatisticsFramesRate				INTEGER,
  rsADFarmStatisticsFramesLoadInBytes				OCTET STRING,
  rsADFarmStatisticsFramesRateInBytes				Counter,
  rsADFarmStatisticsBackupServerUsed				INTEGER,
  rsADFarmStatisticsDistThresholdReached			INTEGER,
  rsADFarmStatisticsCapacityThresholdReached			INTEGER,
  rsADFarmStatisticsTotalDNSReqCounter			Counter,
  rsADFarmStatisticsTotalDNSReqLastSecCounter			Counter,
  rsADFarmStatisticsLocalyAnsweredDNSReqCounter		Counter,
  rsADFarmStatisticsLocalyAnsweredDNSReqLastSecCounter	Counter,
  rsADFarmStatisticsRedirectedDNSReqCounter			Counter,
  rsADFarmStatisticsRedirectedDNSReqLastSecCounter	  	Counter,
  rsADFarmStatisticsTotalHTTPSessionsCounter                 OCTET STRING,
  rsADFarmStatisticsTotalHTTPSessionsLastSecCounter          Counter,
  rsADFarmStatisticsLocalHTTPSessionsCounter                 OCTET STRING,
  rsADFarmStatisticsLocalHTTPSessionsLastSecCounter          Counter,
  rsADFarmStatisticsRedirectedHTTPSessionsCounter            OCTET STRING,
  rsADFarmStatisticsRedirectedHTTPSessionsLastSecCounter     Counter,
  rsADFarmStatisticsTotalTriangSessionsCounter               OCTET STRING,
  rsADFarmStatisticsTotalTriangSessionsLastSecCounter        Counter,
  rsADFarmStatisticsLocalTriangSessionsCounter               OCTET STRING,
  rsADFarmStatisticsLocalTriangSessionsLastSecCounter        Counter,
  rsADFarmStatisticsRedirectedTriangSessionsCounter          OCTET STRING,
  rsADFarmStatisticsRedirectedTriangSessionsLastSecCounter   Counter,
  rsADFarmStatisticsTotalRTSPSessionsCounter                 OCTET STRING,
  rsADFarmStatisticsTotalRTSPSessionsLastSecCounter          Counter,
  rsADFarmStatisticsLocalRTSPSessionsCounter                 OCTET STRING,
  rsADFarmStatisticsLocalRTSPSessionsLastSecCounter          Counter,
  rsADFarmStatisticsRedirectedRTSPSessionsCounter            OCTET STRING,
  rsADFarmStatisticsRedirectedRTSPSessionsLastSecCounter     Counter,
  rsADFarmStatisticsDirectedAttachedUsersNum                 INTEGER,
  rsADFarmStatisticsAverageDirectedAttachedUsersNum          INTEGER,
  rsADFarmStatisticsTotalSIPSessionsCounter                  OCTET STRING,
  rsADFarmStatisticsTotalSIPSessionsLastSecCounter           Counter,
  rsADFarmStatisticsLocalSIPSessionsCounter                  OCTET STRING,
  rsADFarmStatisticsLocalSIPSessionsLastSecCounter           Counter,
  rsADFarmStatisticsRedirectedSIPSessionsCounter             OCTET STRING,
  rsADFarmStatisticsRedirectedSIPSessionsLastSecCounter      Counter,
  rsADFarmStatisticsTotalProxySessionsCounter                OCTET STRING,
  rsADFarmStatisticsTotalProxySessionsLastSecCounter         Counter,
  rsADFarmStatisticsLocalProxySessionsCounter                OCTET STRING,
  rsADFarmStatisticsLocalProxySessionsLastSecCounter         Counter,
  rsADFarmStatisticsRedirectedProxySessionsCounter           OCTET STRING,
  rsADFarmStatisticsRedirectedProxySessionsLastSecCounter    Counter
}


rsADFarmStatisticsName OBJECT-TYPE
    SYNTAX  DisplayString
    ACCESS  read-only
    STATUS  mandatory
    DESCRIPTION
      "The name of the farm."
    ::= {rsADFarmStatisticsEntry 1}

rsADFarmStatisticsAttachedUsersNumber OBJECT-TYPE
    SYNTAX  INTEGER
    ACCESS  read-only
    STATUS  mandatory
    DESCRIPTION
      "Farm current connected users number."
    ::= {rsADFarmStatisticsEntry 2}

rsADFarmStatisticsTotalAttachedUsersNumber OBJECT-TYPE
    SYNTAX  OCTET STRING (SIZE(8))
    ACCESS  read-only
    STATUS  mandatory
    DESCRIPTION
      "Farm total users number since last reset of the device."
    ::= {rsADFarmStatisticsEntry 3}

rsADFarmStatisticsPeakLoad OBJECT-TYPE
    SYNTAX  INTEGER
    ACCESS  read-only
    STATUS  mandatory
    DESCRIPTION
      "Farm peak load of packets per second."
    ::= {rsADFarmStatisticsEntry 4}

rsADFarmStatisticsFramesLoad OBJECT-TYPE
    SYNTAX  OCTET STRING (SIZE(8))
    ACCESS  read-only
    STATUS  mandatory
    DESCRIPTION
      "Farm total number of frames handled by the device."
    ::= {rsADFarmStatisticsEntry 5}

rsADFarmStatisticsFramesRate OBJECT-TYPE
    SYNTAX  INTEGER
    ACCESS  read-only
    STATUS  mandatory
    DESCRIPTION
      "Farm frames rate in the last minute."
    ::= {rsADFarmStatisticsEntry 6}

rsADFarmStatisticsFramesLoadInBytes OBJECT-TYPE
    SYNTAX  OCTET STRING (SIZE(8))
    ACCESS  read-only
    STATUS  mandatory
    DESCRIPTION
      "Bytes load per second."
    ::=  {rsADFarmStatisticsEntry 7}

rsADFarmStatisticsFramesRateInBytes OBJECT-TYPE
    SYNTAX  Counter
    ACCESS  read-only
    STATUS  mandatory
    DESCRIPTION
      "Bytes load rate per second."
    ::=  {rsADFarmStatisticsEntry 8}

rsADFarmStatisticsBackupServerUsed OBJECT-TYPE
    SYNTAX  INTEGER
    ACCESS  read-only
    STATUS  mandatory
    DESCRIPTION
      "Backup server used flag. It shows true if the
       backup server was used in the last reporting period"
    ::= {rsADFarmStatisticsEntry 9}

rsADFarmStatisticsDistThresholdReached OBJECT-TYPE
    SYNTAX  INTEGER
    ACCESS  read-only
    STATUS  mandatory
    DESCRIPTION
      "Distribution threshold reached flag. It shows true if the
       distribution threshold was reached in the last reporting period"
    ::= {rsADFarmStatisticsEntry 10}

rsADFarmStatisticsCapacityThresholdReached OBJECT-TYPE
    SYNTAX  INTEGER
    ACCESS  read-only
    STATUS  mandatory
    DESCRIPTION
      "Capacity threshold reached flag. It shows true if the
       capacity threshold was reached in the last reporting period"
    ::= {rsADFarmStatisticsEntry 11}

rsADFarmStatisticsTotalDNSReqCounter OBJECT-TYPE
    SYNTAX  Counter
    ACCESS  read-only
    STATUS  mandatory
    DESCRIPTION
    "Total number of DNS requests which arrived for this Farm."
    ::= {rsADFarmStatisticsEntry 12}

rsADFarmStatisticsTotalDNSReqLastSecCounter OBJECT-TYPE
    SYNTAX  Counter
    ACCESS  read-only
    STATUS  mandatory
    DESCRIPTION
    "Total number of DNS requests which arrived
	 for this Farm during the last second."
    ::= {rsADFarmStatisticsEntry 13}

rsADFarmStatisticsLocalyAnsweredDNSReqCounter OBJECT-TYPE
    SYNTAX  Counter
    ACCESS  read-only
    STATUS  mandatory
    DESCRIPTION
    "The number of DNS Requests which arrived for this
	 farm and were answered by the local farm."
    ::= {rsADFarmStatisticsEntry 14}

rsADFarmStatisticsLocalyAnsweredDNSReqLastSecCounter OBJECT-TYPE
    SYNTAX  Counter
    ACCESS  read-only
    STATUS  mandatory
    DESCRIPTION
    "The number of DNS Requests which arrived during the last second
	 for this farm and were answered by the local farm."
    ::= {rsADFarmStatisticsEntry 15}

rsADFarmStatisticsRedirectedDNSReqCounter OBJECT-TYPE
    SYNTAX  Counter
    ACCESS  read-only
    STATUS  mandatory
    DESCRIPTION
    "The number of DNS Requests which arrived for this
	 farm and were redirecteded to remote/distributed servers."
    ::= {rsADFarmStatisticsEntry 16}

rsADFarmStatisticsRedirectedDNSReqLastSecCounter OBJECT-TYPE
    SYNTAX  Counter
    ACCESS  read-only
    STATUS  mandatory
    DESCRIPTION
    "The number of DNS Requests which arrived during the last second
	 for this farm and were redirecteded to remote/distributed servers."
    ::= {rsADFarmStatisticsEntry 17}

rsADFarmStatisticsTotalHTTPSessionsCounter OBJECT-TYPE
    SYNTAX  OCTET STRING (SIZE(8))
    ACCESS  read-only
    STATUS  mandatory
    DESCRIPTION
    "Total number of HTTP sessions which arrived for this Farm."
    ::= {rsADFarmStatisticsEntry 18}

rsADFarmStatisticsTotalHTTPSessionsLastSecCounter OBJECT-TYPE
    SYNTAX  Counter
    ACCESS  read-only
    STATUS  mandatory
    DESCRIPTION
    "Total number of HTTP sessions which arrived
  	 for this Farm during the last second."
    ::= {rsADFarmStatisticsEntry 19}

rsADFarmStatisticsLocalHTTPSessionsCounter OBJECT-TYPE
    SYNTAX  OCTET STRING (SIZE(8))
    ACCESS  read-only
    STATUS  mandatory
    DESCRIPTION
    "The number of HTTP sessions which arrived for this
	   farm and were directed to a local server."
    ::= {rsADFarmStatisticsEntry 20}

rsADFarmStatisticsLocalHTTPSessionsLastSecCounter OBJECT-TYPE
    SYNTAX  Counter
    ACCESS  read-only
    STATUS  mandatory
    DESCRIPTION
    "The number of HTTP sessions which arrived during the
	   last second for this farm and were directed to a local server."
    ::= {rsADFarmStatisticsEntry 21}

rsADFarmStatisticsRedirectedHTTPSessionsCounter OBJECT-TYPE
    SYNTAX  OCTET STRING (SIZE(8))
    ACCESS  read-only
    STATUS  mandatory
    DESCRIPTION
    "The number of HTTP sessions which arrived for this
	   farm and were redirecteded to remote/distributed servers."
    ::= {rsADFarmStatisticsEntry 22}

rsADFarmStatisticsRedirectedHTTPSessionsLastSecCounter OBJECT-TYPE
    SYNTAX  Counter
    ACCESS  read-only
    STATUS  mandatory
    DESCRIPTION
    "The number of HTTP sessions which arrived during the last second
	   for this farm and were redirecteded to remote/distributed servers."
    ::= {rsADFarmStatisticsEntry 23}


rsADFarmStatisticsTotalTriangSessionsCounter OBJECT-TYPE
    SYNTAX  OCTET STRING (SIZE(8))
    ACCESS  read-only
    STATUS  mandatory
    DESCRIPTION
    "Total number of Tringulation sessions for this Farm."
    ::= {rsADFarmStatisticsEntry 24}

rsADFarmStatisticsTotalTriangSessionsLastSecCounter OBJECT-TYPE
    SYNTAX  Counter
    ACCESS  read-only
    STATUS  mandatory
    DESCRIPTION
    "Total number of Tringulation sessions which arrived
	   for this Farm during the last second."
    ::= {rsADFarmStatisticsEntry 25}

rsADFarmStatisticsLocalTriangSessionsCounter OBJECT-TYPE
    SYNTAX  OCTET STRING (SIZE(8))
    ACCESS  read-only
    STATUS  mandatory
    DESCRIPTION
    "The number of Tringulation sessions which arrived for this
	   farm and were answered by the a local server."
    ::= {rsADFarmStatisticsEntry 26}

rsADFarmStatisticsLocalTriangSessionsLastSecCounter OBJECT-TYPE
    SYNTAX  Counter
    ACCESS  read-only
    STATUS  mandatory
    DESCRIPTION
    "The number of Tringulation sessions which arrived during the
	   last second for this farm and were answered by a local server."
    ::= {rsADFarmStatisticsEntry 27}

rsADFarmStatisticsRedirectedTriangSessionsCounter OBJECT-TYPE
    SYNTAX  OCTET STRING (SIZE(8))
    ACCESS  read-only
    STATUS  mandatory
    DESCRIPTION
    "The number of sessions which were redirecteded by triangulation
     to distributed servers."
    ::= {rsADFarmStatisticsEntry 28}

rsADFarmStatisticsRedirectedTriangSessionsLastSecCounter OBJECT-TYPE
    SYNTAX  Counter
    ACCESS  read-only
    STATUS  mandatory
    DESCRIPTION
    "The number of sessions which were redirecteded by triangulation
	   during the last second to distributed servers."
    ::= {rsADFarmStatisticsEntry 29}

rsADFarmStatisticsTotalRTSPSessionsCounter OBJECT-TYPE
    SYNTAX  OCTET STRING (SIZE(8))
    ACCESS  read-only
    STATUS  mandatory
    DESCRIPTION
    "Total number of RTSP sessions which arrived for this Farm."
    ::= {rsADFarmStatisticsEntry 30}

rsADFarmStatisticsTotalRTSPSessionsLastSecCounter OBJECT-TYPE
    SYNTAX  Counter
    ACCESS  read-only
    STATUS  mandatory
    DESCRIPTION
    "Total number of RTSP sessions which arrived
  	 for this Farm during the last second."
    ::= {rsADFarmStatisticsEntry 31}

rsADFarmStatisticsLocalRTSPSessionsCounter OBJECT-TYPE
    SYNTAX  OCTET STRING (SIZE(8))
    ACCESS  read-only
    STATUS  mandatory
    DESCRIPTION
    "The number of RTSP sessions which arrived for this
	   farm and were directed to a local server."
    ::= {rsADFarmStatisticsEntry 32}

rsADFarmStatisticsLocalRTSPSessionsLastSecCounter OBJECT-TYPE
    SYNTAX  Counter
    ACCESS  read-only
    STATUS  mandatory
    DESCRIPTION
    "The number of RTSP sessions which arrived during the
	   last second for this farm and were directed to a local server."
    ::= {rsADFarmStatisticsEntry 33}

rsADFarmStatisticsRedirectedRTSPSessionsCounter OBJECT-TYPE
    SYNTAX  OCTET STRING (SIZE(8))
    ACCESS  read-only
    STATUS  mandatory
    DESCRIPTION
    "The number of RTSP sessions which arrived for this
	   farm and were redirecteded to remote/distributed servers."
    ::= {rsADFarmStatisticsEntry 34}

rsADFarmStatisticsRedirectedRTSPSessionsLastSecCounter OBJECT-TYPE
    SYNTAX  Counter
    ACCESS  read-only
    STATUS  mandatory
    DESCRIPTION
    "The number of RTSP sessions which arrived during the last second
	   for this farm and were redirecteded to remote/distributed servers."
    ::= {rsADFarmStatisticsEntry 35}


rsADFarmStatisticsDirectedAttachedUsersNum OBJECT-TYPE
    SYNTAX INTEGER
    ACCESS  read-only
    STATUS  mandatory
    DESCRIPTION
      "The number of directed attached clients to this farm"
    ::= {rsADFarmStatisticsEntry 36}

rsADFarmStatisticsAverageDirectedAttachedUsersNum OBJECT-TYPE
    SYNTAX INTEGER
    ACCESS  read-only
    STATUS  mandatory
    DESCRIPTION
      "The average number of directed attached clients to this farm"
    ::= {rsADFarmStatisticsEntry 37}

rsADFarmStatisticsTotalSIPSessionsCounter OBJECT-TYPE
    SYNTAX  OCTET STRING (SIZE(8))
    ACCESS  read-only
    STATUS  mandatory
    DESCRIPTION
    "Total number of SIP sessions which arrived for this Farm."
    ::= {rsADFarmStatisticsEntry 38}

rsADFarmStatisticsTotalSIPSessionsLastSecCounter OBJECT-TYPE
    SYNTAX  Counter
    ACCESS  read-only
    STATUS  mandatory
    DESCRIPTION
    "Total number of SIP sessions which arrived
  	 for this Farm during the last second."
    ::= {rsADFarmStatisticsEntry 39}

rsADFarmStatisticsLocalSIPSessionsCounter OBJECT-TYPE
    SYNTAX  OCTET STRING (SIZE(8))
    ACCESS  read-only
    STATUS  mandatory
    DESCRIPTION
    "The number of SIP sessions which arrived for this
	   farm and were directed to a local server."
    ::= {rsADFarmStatisticsEntry 40}

rsADFarmStatisticsLocalSIPSessionsLastSecCounter OBJECT-TYPE
    SYNTAX  Counter
    ACCESS  read-only
    STATUS  mandatory
    DESCRIPTION
    "The number of SIP sessions which arrived during the
	   last second for this farm and were directed to a local server."
    ::= {rsADFarmStatisticsEntry 41}

rsADFarmStatisticsRedirectedSIPSessionsCounter OBJECT-TYPE
    SYNTAX  OCTET STRING (SIZE(8))
    ACCESS  read-only
    STATUS  mandatory
    DESCRIPTION
    "The number of SIP sessions which arrived for this
	   farm and were redirecteded to remote/distributed servers."
    ::= {rsADFarmStatisticsEntry 42}

rsADFarmStatisticsRedirectedSIPSessionsLastSecCounter OBJECT-TYPE
    SYNTAX  Counter
    ACCESS  read-only
    STATUS  mandatory
    DESCRIPTION
    "The number of SIP sessions which arrived during the last second
	   for this farm and were redirecteded to remote/distributed servers."
    ::= {rsADFarmStatisticsEntry 43}

rsADFarmStatisticsTotalProxySessionsCounter OBJECT-TYPE
    SYNTAX  OCTET STRING (SIZE(8))
    ACCESS  read-only
    STATUS  mandatory
    DESCRIPTION
    "Total number of Proxy (Client NAT redirection) sessions which arrived for this Farm."
    ::= {rsADFarmStatisticsEntry 44}

rsADFarmStatisticsTotalProxySessionsLastSecCounter OBJECT-TYPE
    SYNTAX  Counter
    ACCESS  read-only
    STATUS  mandatory
    DESCRIPTION
    "Total number of Proxy (Client NAT redirection) sessions which arrived
  	 for this Farm during the last second."
    ::= {rsADFarmStatisticsEntry 45}

rsADFarmStatisticsLocalProxySessionsCounter OBJECT-TYPE
    SYNTAX  OCTET STRING (SIZE(8))
    ACCESS  read-only
    STATUS  mandatory
    DESCRIPTION
    "The number of Proxy (Client NAT redirection) sessions which arrived for this
	   farm and were directed to a local server."
    ::= {rsADFarmStatisticsEntry 46}

rsADFarmStatisticsLocalProxySessionsLastSecCounter OBJECT-TYPE
    SYNTAX  Counter
    ACCESS  read-only
    STATUS  mandatory
    DESCRIPTION
    "The number of Proxy (Client NAT redirection) sessions which arrived during the
	   last second for this farm and were directed to a local server."
    ::= {rsADFarmStatisticsEntry 47}

rsADFarmStatisticsRedirectedProxySessionsCounter OBJECT-TYPE
    SYNTAX  OCTET STRING (SIZE(8))
    ACCESS  read-only
    STATUS  mandatory
    DESCRIPTION
    "The number of Proxy (Client NAT redirection) sessions which arrived for this
	   farm and were redirecteded to remote/distributed servers."
    ::= {rsADFarmStatisticsEntry 48}

rsADFarmStatisticsRedirectedProxySessionsLastSecCounter OBJECT-TYPE
    SYNTAX  Counter
    ACCESS  read-only
    STATUS  mandatory
    DESCRIPTION
    "The number of Proxy (Client NAT redirection) sessions which arrived during the last second
	   for this farm and were redirecteded to remote/distributed servers."
    ::= {rsADFarmStatisticsEntry 49}



rsNWSDServerStatisticsTable OBJECT-TYPE
    SYNTAX SEQUENCE OF RsNWSDServerStatisticsEntry
    ACCESS not-accessible
    STATUS mandatory
    DESCRIPTION
      "Table containing the Server statistics values."
    ::=  {rsNWSDStats 8}

rsNWSDServerStatisticsEntry OBJECT-TYPE
    SYNTAX RsNWSDServerStatisticsEntry
    ACCESS not-accessible
    STATUS  mandatory
    DESCRIPTION
       " The row definition for this table."
   INDEX { rsNWSDServerStatisticsFarmAddr,
           rsNWSDServerStatisticsServerAddr,
           rsNWSDServerStatisticsServerPort }
    ::=  {rsNWSDServerStatisticsTable 1}

RsNWSDServerStatisticsEntry ::= SEQUENCE {
  rsNWSDServerStatisticsFarmAddr                     IpAddress,
  rsNWSDServerStatisticsServerAddr                   IpAddress,
  rsNWSDServerStatisticsAttachedUsersNumber          INTEGER,
  rsNWSDServerStatisticsPeakLoad                     INTEGER,
  rsNWSDServerStatisticsFramesRate                   INTEGER,
  rsNWSDServerStatisticsFramesLoad                   OCTET STRING,
  rsNWSDServerStatisticsTotalAttachedUsersNumber     OCTET STRING,
  rsNWSDServerStatisticsFramesLoadInBytes            OCTET STRING,
  rsNWSDServerStatisticsFramesRateInBytes            Counter,
  rsNWSDServerStatisticsConnectivityCheckFailed      INTEGER,
  rsNWSDServerStatisticsConnectionLimitReached       INTEGER,
  rsNWSDServerStatisticsAnsweredDNSReqCounter        Counter,
  rsNWSDServerStatisticsAnsweredDNSReqLastSecCounter Counter,
  rsNWSDServerStatisticsRedirectedHTTPSessions                  OCTET STRING,
  rsNWSDServerStatisticsRedirectedHTTPSessionsLastSecCounter    Counter,
  rsNWSDServerStatisticsRedirectedTriangSessions                OCTET STRING,
  rsNWSDServerStatisticsRedirectedTriangSessionsLastSecCount    Counter,
  rsNWSDServerStatisticsRedirectedRTSPSessions                  OCTET STRING,
  rsNWSDServerStatisticsRedirectedRTSPSessionsLastSecCounter    Counter,
  rsNWSDServerStatisticsAverageUsersNum                         INTEGER,
  rsNWSDServerStatisticsServerPort                              INTEGER,
  rsNWSDServerStatisticsRedirectedSIPSessions                   OCTET STRING,
  rsNWSDServerStatisticsRedirectedSIPSessionsLastSecCounter     Counter,
  rsNWSDServerStatisticsRedirectedProxySessions                 OCTET STRING,
  rsNWSDServerStatisticsRedirectedProxySessionsLastSecCounter   Counter
  }



rsNWSDServerStatisticsFarmAddr OBJECT-TYPE
    SYNTAX  IpAddress
    ACCESS  read-only
    STATUS  mandatory
    DESCRIPTION
     "WSD Virtual IP address (Farm addr)"
	::=  {rsNWSDServerStatisticsEntry 1}

rsNWSDServerStatisticsServerAddr  OBJECT-TYPE
    SYNTAX  IpAddress
    ACCESS  read-only
    STATUS  mandatory
    DESCRIPTION
     "Server  IP address"
	::=  {rsNWSDServerStatisticsEntry 2 }

rsNWSDServerStatisticsAttachedUsersNumber OBJECT-TYPE
    SYNTAX  INTEGER
    ACCESS  read-only
    STATUS  mandatory
    DESCRIPTION
      "Number of currently active users attached to this server."
    ::=  {rsNWSDServerStatisticsEntry 3 }

rsNWSDServerStatisticsPeakLoad OBJECT-TYPE
    SYNTAX  INTEGER
    ACCESS  read-only
    STATUS  mandatory
    DESCRIPTION
      "Maximal number of frames per second dispatched to server
       since last reset."
    ::=  {rsNWSDServerStatisticsEntry 4}

rsNWSDServerStatisticsFramesRate OBJECT-TYPE
    SYNTAX  INTEGER
    ACCESS  read-only
    STATUS  mandatory
    DESCRIPTION
      "Number of frames per second dispatched to server."
    ::=  {rsNWSDServerStatisticsEntry 5}

rsNWSDServerStatisticsFramesLoad OBJECT-TYPE
    SYNTAX  OCTET STRING (SIZE(8))
    ACCESS  read-only
    STATUS  mandatory
    DESCRIPTION
      "Number of frames dispatched to server."
    ::=  {rsNWSDServerStatisticsEntry 6 }

rsNWSDServerStatisticsTotalAttachedUsersNumber OBJECT-TYPE
    SYNTAX  OCTET STRING (SIZE(8))
    ACCESS  read-only
    STATUS  mandatory
    DESCRIPTION
      "Total number of users ever attached to this server."
    ::=  {rsNWSDServerStatisticsEntry 7 }

rsNWSDServerStatisticsFramesLoadInBytes OBJECT-TYPE
    SYNTAX  OCTET STRING (SIZE(8))
    ACCESS  read-only
    STATUS  mandatory
    DESCRIPTION
      "Bytes load per second dispatched to server."
    ::=  {rsNWSDServerStatisticsEntry 8 }

rsNWSDServerStatisticsFramesRateInBytes OBJECT-TYPE
    SYNTAX  Counter
    ACCESS  read-only
    STATUS  mandatory
    DESCRIPTION
      "Bytes Rate dispatched to server."
    ::=  {rsNWSDServerStatisticsEntry 9}

rsNWSDServerStatisticsConnectivityCheckFailed OBJECT-TYPE
    SYNTAX  INTEGER
    ACCESS  read-only
    STATUS  mandatory
    DESCRIPTION
      "Connectivity check failed flag. It shows true if the
        checks of this server failed in the last reporting period"
    ::=  {rsNWSDServerStatisticsEntry 10}

rsNWSDServerStatisticsConnectionLimitReached OBJECT-TYPE
    SYNTAX  INTEGER
    ACCESS  read-only
    STATUS  mandatory
    DESCRIPTION
      "Connection limit reached flag. It shows true if the
       connection limit was reached in the last reporting period"
    ::=  {rsNWSDServerStatisticsEntry 11}

rsNWSDServerStatisticsAnsweredDNSReqCounter OBJECT-TYPE
    SYNTAX  Counter
    ACCESS  read-only
    STATUS  mandatory
    DESCRIPTION
    "Number of DNS requests answered by this Server."
    ::=  {rsNWSDServerStatisticsEntry 12}

rsNWSDServerStatisticsAnsweredDNSReqLastSecCounter OBJECT-TYPE
    SYNTAX  Counter
    ACCESS  read-only
    STATUS  mandatory
    DESCRIPTION
    "Number of DNS requests answered by this Server during the last second."
    ::=  {rsNWSDServerStatisticsEntry 13}
rsNWSDServerStatisticsRedirectedHTTPSessions OBJECT-TYPE
    SYNTAX  OCTET STRING (SIZE(8))
    ACCESS  read-only
    STATUS  mandatory
    DESCRIPTION
    "Number of HTTP sessions redirected to this Server."
    ::=  {rsNWSDServerStatisticsEntry 14}

rsNWSDServerStatisticsRedirectedHTTPSessionsLastSecCounter OBJECT-TYPE
    SYNTAX  Counter
    ACCESS  read-only
    STATUS  mandatory
    DESCRIPTION
    "Number of HTTP sessions redirected to this Server during the last second."
    ::=  {rsNWSDServerStatisticsEntry 15}

rsNWSDServerStatisticsRedirectedTriangSessions OBJECT-TYPE
    SYNTAX  OCTET STRING (SIZE(8))
    ACCESS  read-only
    STATUS  mandatory
    DESCRIPTION
    "Number of sessions triangulated to this site."
    ::=  {rsNWSDServerStatisticsEntry 16}

rsNWSDServerStatisticsRedirectedTriangSessionsLastSecCount OBJECT-TYPE
    SYNTAX  Counter
    ACCESS  read-only
    STATUS  mandatory
    DESCRIPTION
    "Number of sessions triangulated to this site during the last second."
    ::=  {rsNWSDServerStatisticsEntry 17}

rsNWSDServerStatisticsRedirectedRTSPSessions OBJECT-TYPE
    SYNTAX  OCTET STRING (SIZE(8))
    ACCESS  read-only
    STATUS  mandatory
    DESCRIPTION
    "Number of RTSP sessions redirected to this Server."
    ::=  {rsNWSDServerStatisticsEntry 18}

rsNWSDServerStatisticsRedirectedRTSPSessionsLastSecCounter OBJECT-TYPE
    SYNTAX  Counter
    ACCESS  read-only
    STATUS  mandatory
    DESCRIPTION
    "Number of RTSP sessions redirected to this Server during the last second."
    ::=  {rsNWSDServerStatisticsEntry 19}

rsNWSDServerStatisticsAverageUsersNum OBJECT-TYPE
    SYNTAX INTEGER
    ACCESS  read-only
    STATUS  mandatory
    DESCRIPTION
      "The average number of active connections attached to this server"
    ::= {rsNWSDServerStatisticsEntry 20}

rsNWSDServerStatisticsServerPort  OBJECT-TYPE
    SYNTAX INTEGER (0..65535)
    ACCESS  read-only
    STATUS  mandatory
    DESCRIPTION
        "Server port."
    ::= {rsNWSDServerStatisticsEntry 21}

rsNWSDServerStatisticsRedirectedSIPSessions OBJECT-TYPE
    SYNTAX  OCTET STRING (SIZE(8))
    ACCESS  read-only
    STATUS  mandatory
    DESCRIPTION
    "Number of SIP sessions redirected to this Server."
    ::=  {rsNWSDServerStatisticsEntry 22}

rsNWSDServerStatisticsRedirectedSIPSessionsLastSecCounter OBJECT-TYPE
    SYNTAX  Counter
    ACCESS  read-only
    STATUS  mandatory
    DESCRIPTION
    "Number of SIP sessions redirected to this Server during the last second."
    ::=  {rsNWSDServerStatisticsEntry 23}

rsNWSDServerStatisticsRedirectedProxySessions OBJECT-TYPE
    SYNTAX  OCTET STRING (SIZE(8))
    ACCESS  read-only
    STATUS  mandatory
    DESCRIPTION
    "Number of Proxy (Client NAT redirection) sessions redirected to this Server."
    ::=  {rsNWSDServerStatisticsEntry 24}

rsNWSDServerStatisticsRedirectedProxySessionsLastSecCounter OBJECT-TYPE
    SYNTAX  Counter
    ACCESS  read-only
    STATUS  mandatory
    DESCRIPTION
    "Number of Proxy (Client NAT redirection) sessions redirected to this Server during the last second."
    ::=  {rsNWSDServerStatisticsEntry 25}


rsADServerStatisticsTable OBJECT-TYPE
    SYNTAX SEQUENCE OF RsADServerStatisticsEntry
    ACCESS not-accessible
    STATUS mandatory
    DESCRIPTION
      "Table containing the Server statistics values."
    ::=  {rsNWSDStats 21}

rsADServerStatisticsEntry OBJECT-TYPE
    SYNTAX RsADServerStatisticsEntry
    ACCESS not-accessible
    STATUS  mandatory
    DESCRIPTION
       " The row definition for this table."
   INDEX { rsADServerStatisticsFarmName,
           rsADServerStatisticsServerAddr,
           rsADServerStatisticsServerPort }
    ::=  {rsADServerStatisticsTable 1}

RsADServerStatisticsEntry ::= SEQUENCE {
  rsADServerStatisticsFarmName                     DisplayString,
  rsADServerStatisticsServerAddr                   IpAddress,
  rsADServerStatisticsServerPort                   INTEGER,
  rsADServerStatisticsAttachedUsersNumber          INTEGER,
  rsADServerStatisticsPeakLoad                     INTEGER,
  rsADServerStatisticsFramesRate                   INTEGER,
  rsADServerStatisticsFramesLoad                   OCTET STRING,
  rsADServerStatisticsTotalAttachedUsersNumber     OCTET STRING,
  rsADServerStatisticsFramesLoadInBytes            OCTET STRING,
  rsADServerStatisticsFramesRateInBytes            Counter,
  rsADServerStatisticsConnectivityCheckFailed      INTEGER,
  rsADServerStatisticsConnectionLimitReached       INTEGER,
  rsADServerStatisticsAnsweredDNSReqCounter        Counter,
  rsADServerStatisticsAnsweredDNSReqLastSecCounter Counter,
  rsADServerStatisticsRedirectedHTTPSessions                  OCTET STRING,
  rsADServerStatisticsRedirectedHTTPSessionsLastSecCounter    Counter,
  rsADServerStatisticsRedirectedTriangSessions                OCTET STRING,
  rsADServerStatisticsRedirectedTriangSessionsLastSecCount    Counter,
  rsADServerStatisticsRedirectedRTSPSessions                  OCTET STRING,
  rsADServerStatisticsRedirectedRTSPSessionsLastSecCounter    Counter,
  rsADServerStatisticsAverageUsersNum                         INTEGER,
  rsADServerStatisticsRedirectedSIPSessions                   OCTET STRING,
  rsADServerStatisticsRedirectedSIPSessionsLastSecCounter     Counter,
  rsADServerStatisticsRedirectedProxySessions                 OCTET STRING,
  rsADServerStatisticsRedirectedProxySessionsLastSecCounter   Counter
  }



rsADServerStatisticsFarmName OBJECT-TYPE
    SYNTAX  DisplayString (SIZE (1..50))
    ACCESS  read-only
    STATUS  mandatory
    DESCRIPTION
     "AppDirector farm name"
	::=  {rsADServerStatisticsEntry 1}

rsADServerStatisticsServerAddr  OBJECT-TYPE
    SYNTAX  IpAddress
    ACCESS  read-only
    STATUS  mandatory
    DESCRIPTION
     "Server  IP address"
	::=  {rsADServerStatisticsEntry 2 }

rsADServerStatisticsServerPort  OBJECT-TYPE
    SYNTAX INTEGER (0..65535)
    ACCESS  read-only
    STATUS  mandatory
    DESCRIPTION
        "Server port."
    ::= {rsADServerStatisticsEntry 3}

rsADServerStatisticsAttachedUsersNumber OBJECT-TYPE
    SYNTAX  INTEGER
    ACCESS  read-only
    STATUS  mandatory
    DESCRIPTION
      "Number of currently active users attached to this server."
    ::=  {rsADServerStatisticsEntry 4 }

rsADServerStatisticsPeakLoad OBJECT-TYPE
    SYNTAX  INTEGER
    ACCESS  read-only
    STATUS  mandatory
    DESCRIPTION
      "Maximal number of frames per second dispatched to server
       since last reset."
    ::=  {rsADServerStatisticsEntry 5}

rsADServerStatisticsFramesRate OBJECT-TYPE
    SYNTAX  INTEGER
    ACCESS  read-only
    STATUS  mandatory
    DESCRIPTION
      "Number of frames per second dispatched to server."
    ::=  {rsADServerStatisticsEntry 6}

rsADServerStatisticsFramesLoad OBJECT-TYPE
    SYNTAX  OCTET STRING (SIZE(8))
    ACCESS  read-only
    STATUS  mandatory
    DESCRIPTION
      "Number of frames dispatched to server."
    ::=  {rsADServerStatisticsEntry 7 }

rsADServerStatisticsTotalAttachedUsersNumber OBJECT-TYPE
    SYNTAX  OCTET STRING (SIZE(8))
    ACCESS  read-only
    STATUS  mandatory
    DESCRIPTION
      "Total number of users ever attached to this server."
    ::=  {rsADServerStatisticsEntry 8 }

rsADServerStatisticsFramesLoadInBytes OBJECT-TYPE
    SYNTAX  OCTET STRING (SIZE(8))
    ACCESS  read-only
    STATUS  mandatory
    DESCRIPTION
      "Bytes load per second dispatched to server."
    ::=  {rsADServerStatisticsEntry 9 }

rsADServerStatisticsFramesRateInBytes OBJECT-TYPE
    SYNTAX  Counter
    ACCESS  read-only
    STATUS  mandatory
    DESCRIPTION
      "Bytes Rate dispatched to server."
    ::=  {rsADServerStatisticsEntry 10}

rsADServerStatisticsConnectivityCheckFailed OBJECT-TYPE
    SYNTAX  INTEGER
    ACCESS  read-only
    STATUS  mandatory
    DESCRIPTION
      "Connectivity check failed flag. It shows true if the
        checks of this server failed in the last reporting period"
    ::=  {rsADServerStatisticsEntry 11}

rsADServerStatisticsConnectionLimitReached OBJECT-TYPE
    SYNTAX  INTEGER
    ACCESS  read-only
    STATUS  mandatory
    DESCRIPTION
      "Connection limit reached flag. It shows true if the
       connection limit was reached in the last reporting period"
    ::=  {rsADServerStatisticsEntry 12}

rsADServerStatisticsAnsweredDNSReqCounter OBJECT-TYPE
    SYNTAX  Counter
    ACCESS  read-only
    STATUS  mandatory
    DESCRIPTION
    "Number of DNS requests answered by this Server."
    ::=  {rsADServerStatisticsEntry 13}

rsADServerStatisticsAnsweredDNSReqLastSecCounter OBJECT-TYPE
    SYNTAX  Counter
    ACCESS  read-only
    STATUS  mandatory
    DESCRIPTION
    "Number of DNS requests answered by this Server during the last second."
    ::=  {rsADServerStatisticsEntry 14}

rsADServerStatisticsRedirectedHTTPSessions OBJECT-TYPE
    SYNTAX  OCTET STRING (SIZE(8))
    ACCESS  read-only
    STATUS  mandatory
    DESCRIPTION
    "Number of HTTP sessions redirected to this Server."
    ::=  {rsADServerStatisticsEntry 15}

rsADServerStatisticsRedirectedHTTPSessionsLastSecCounter OBJECT-TYPE
    SYNTAX  Counter
    ACCESS  read-only
    STATUS  mandatory
    DESCRIPTION
    "Number of HTTP sessions redirected to this Server during the last second."
    ::=  {rsADServerStatisticsEntry 16}

rsADServerStatisticsRedirectedTriangSessions OBJECT-TYPE
    SYNTAX  OCTET STRING (SIZE(8))
    ACCESS  read-only
    STATUS  mandatory
    DESCRIPTION
    "Number of sessions triangulated to this site."
    ::=  {rsADServerStatisticsEntry 17}

rsADServerStatisticsRedirectedTriangSessionsLastSecCount OBJECT-TYPE
    SYNTAX  Counter
    ACCESS  read-only
    STATUS  mandatory
    DESCRIPTION
    "Number of sessions triangulated to this site during the last second."
    ::=  {rsADServerStatisticsEntry 18}

rsADServerStatisticsRedirectedRTSPSessions OBJECT-TYPE
    SYNTAX  OCTET STRING (SIZE(8))
    ACCESS  read-only
    STATUS  mandatory
    DESCRIPTION
    "Number of RTSP sessions redirected to this Server."
    ::=  {rsADServerStatisticsEntry 19}

rsADServerStatisticsRedirectedRTSPSessionsLastSecCounter OBJECT-TYPE
    SYNTAX  Counter
    ACCESS  read-only
    STATUS  mandatory
    DESCRIPTION
    "Number of RTSP sessions redirected to this Server during the last second."
    ::=  {rsADServerStatisticsEntry 20}

rsADServerStatisticsAverageUsersNum OBJECT-TYPE
    SYNTAX INTEGER
    ACCESS  read-only
    STATUS  mandatory
    DESCRIPTION
      "The average number of active connections attached to this server"
    ::= {rsADServerStatisticsEntry 21}

rsADServerStatisticsRedirectedSIPSessions OBJECT-TYPE
    SYNTAX  OCTET STRING (SIZE(8))
    ACCESS  read-only
    STATUS  mandatory
    DESCRIPTION
    "Number of SIP sessions redirected to this Server."
    ::=  {rsADServerStatisticsEntry 22}

rsADServerStatisticsRedirectedSIPSessionsLastSecCounter OBJECT-TYPE
    SYNTAX  Counter
    ACCESS  read-only
    STATUS  mandatory
    DESCRIPTION
    "Number of SIP sessions redirected to this Server during the last second."
    ::=  {rsADServerStatisticsEntry 23}

rsADServerStatisticsRedirectedProxySessions OBJECT-TYPE
    SYNTAX  OCTET STRING (SIZE(8))
    ACCESS  read-only
    STATUS  mandatory
    DESCRIPTION
    "Number of Proxy (Client NAT redirection) sessions redirected to this Server."
    ::=  {rsADServerStatisticsEntry 24}

rsADServerStatisticsRedirectedProxySessionsLastSecCounter OBJECT-TYPE
    SYNTAX  Counter
    ACCESS  read-only
    STATUS  mandatory
    DESCRIPTION
    "Number of Proxy (Client NAT redirection) sessions redirected to this Server during the last second."
    ::=  {rsADServerStatisticsEntry 25}

rsNADServerStatisticsTable OBJECT-TYPE
    SYNTAX SEQUENCE OF RsNADServerStatisticsEntry
    ACCESS not-accessible
    STATUS mandatory
    DESCRIPTION
      "Table containing the Server statistics values."
    ::=  {rsNWSDStats 26}

rsNADServerStatisticsEntry OBJECT-TYPE
    SYNTAX RsNADServerStatisticsEntry
    ACCESS not-accessible
    STATUS  mandatory
    DESCRIPTION
       " The row definition for this table."
   INDEX { rsNADServerStatisticsFarmName,
           rsNADServerStatisticsServerName }
    ::=  {rsNADServerStatisticsTable 1}

RsNADServerStatisticsEntry ::= SEQUENCE {
  rsNADServerStatisticsFarmName                     DisplayString,
  rsNADServerStatisticsServerName					DisplayString,
  rsNADServerStatisticsAttachedUsersNumber          INTEGER,
  rsNADServerStatisticsPeakLoad                     INTEGER,
  rsNADServerStatisticsFramesRate                   INTEGER,
  rsNADServerStatisticsFramesLoad                   Counter64,
  rsNADServerStatisticsTotalAttachedUsersNumber     Counter64,
  rsNADServerStatisticsFramesLoadInBytes            Counter64,
  rsNADServerStatisticsFramesRateInBytes            Counter,
  rsNADServerStatisticsConnectivityCheckFailed      INTEGER,
  rsNADServerStatisticsConnectionLimitReached       INTEGER,
  rsNADServerStatisticsAnsweredDNSReqCounter        Counter,
  rsNADServerStatisticsAnsweredDNSReqLastSecCounter Counter,
  rsNADServerStatisticsRedirectedHTTPSessions                  OCTET STRING,
  rsNADServerStatisticsRedirectedHTTPSessionsLastSecCounter    Counter,
  rsNADServerStatisticsRedirectedTriangSessions                OCTET STRING,
  rsNADServerStatisticsRedirectedTriangSessionsLastSecCount    Counter,
  rsNADServerStatisticsRedirectedRTSPSessions                  OCTET STRING,
  rsNADServerStatisticsRedirectedRTSPSessionsLastSecCounter    Counter,
  rsNADServerStatisticsAverageUsersNum                         INTEGER,
  rsNADServerStatisticsRedirectedSIPSessions                   OCTET STRING,
  rsNADServerStatisticsRedirectedSIPSessionsLastSecCounter     Counter,
  rsNADServerStatisticsRedirectedProxySessions                 OCTET STRING,
  rsNADServerStatisticsRedirectedProxySessionsLastSecCounter   Counter,
  rsNADServerStatisticsCurrentConnections 		       INTEGER,
  rsNADServerStatisticsNewTcpConnections		       INTEGER,
  rsNADServerStatisticsTrafficIn			       INTEGER,
  rsNADServerStatisticsTrafficOut			       INTEGER
  }



rsNADServerStatisticsFarmName OBJECT-TYPE
    SYNTAX  DisplayString (SIZE (1..50))
    ACCESS  read-only
    STATUS  mandatory
    DESCRIPTION
     "AppDirector farm name"
	::=  {rsNADServerStatisticsEntry 1}

rsNADServerStatisticsServerName  OBJECT-TYPE
    SYNTAX  DisplayString (SIZE(1..30))
    ACCESS  read-only
    STATUS  mandatory
    DESCRIPTION
      "Server  IP address"
    ::=  {rsNADServerStatisticsEntry 2}

rsNADServerStatisticsAttachedUsersNumber OBJECT-TYPE
    SYNTAX  INTEGER
    ACCESS  read-only
    STATUS  optional
    DESCRIPTION
      "Number of currently active users attached to this server."
    ::=  {rsNADServerStatisticsEntry 3 }

rsNADServerStatisticsPeakLoad OBJECT-TYPE
    SYNTAX  INTEGER
    ACCESS  read-only
    STATUS  optional
    DESCRIPTION
      "Maximal number of frames per second dispatched to server
       since last reset."
    ::=  {rsNADServerStatisticsEntry 4}

rsNADServerStatisticsFramesRate OBJECT-TYPE
    SYNTAX  INTEGER
    ACCESS  read-only
    STATUS  optional
    DESCRIPTION
      "Number of frames per second dispatched to server."
    ::=  {rsNADServerStatisticsEntry 5}

rsNADServerStatisticsFramesLoad OBJECT-TYPE
    SYNTAX  Counter64
    ACCESS  read-only
    STATUS  optional
    DESCRIPTION
      "Number of frames dispatched to server."
    ::=  {rsNADServerStatisticsEntry 6 }

rsNADServerStatisticsTotalAttachedUsersNumber OBJECT-TYPE
    SYNTAX  Counter64
    ACCESS  read-only
    STATUS  optional
    DESCRIPTION
      "Total number of users ever attached to this server."
    ::=  {rsNADServerStatisticsEntry 7}

rsNADServerStatisticsFramesLoadInBytes OBJECT-TYPE
    SYNTAX  Counter64
    ACCESS  read-only
    STATUS  optional
    DESCRIPTION
      "Bytes load per second dispatched to server."
    ::=  {rsNADServerStatisticsEntry 8}

rsNADServerStatisticsFramesRateInBytes OBJECT-TYPE
    SYNTAX  Counter
    ACCESS  read-only
    STATUS  optional
    DESCRIPTION
      "Bytes Rate dispatched to server."
    ::=  {rsNADServerStatisticsEntry 9}

rsNADServerStatisticsConnectivityCheckFailed OBJECT-TYPE
    SYNTAX  INTEGER
    ACCESS  read-only
    STATUS  optional
    DESCRIPTION
      "Connectivity check failed flag. It shows true if the
        checks of this server failed in the last reporting period"
    ::=  {rsNADServerStatisticsEntry 10}

rsNADServerStatisticsConnectionLimitReached OBJECT-TYPE
    SYNTAX  INTEGER
    ACCESS  read-only
    STATUS  optional
    DESCRIPTION
      "Connection limit reached flag. It shows true if the
       connection limit was reached in the last reporting period"
    ::=  {rsNADServerStatisticsEntry 11}

rsNADServerStatisticsAnsweredDNSReqCounter OBJECT-TYPE
    SYNTAX  Counter
    ACCESS  read-only
    STATUS  optional
    DESCRIPTION
    "Number of DNS requests answered by this Server."
    ::=  {rsNADServerStatisticsEntry 12}

rsNADServerStatisticsAnsweredDNSReqLastSecCounter OBJECT-TYPE
    SYNTAX  Counter
    ACCESS  read-only
    STATUS  optional
    DESCRIPTION
    "Number of DNS requests answered by this Server during the last second."
    ::=  {rsNADServerStatisticsEntry 13}

rsNADServerStatisticsRedirectedHTTPSessions OBJECT-TYPE
    SYNTAX  OCTET STRING (SIZE(8))
    ACCESS  read-only
    STATUS  optional
    DESCRIPTION
    "Number of HTTP sessions redirected to this Server."
    ::=  {rsNADServerStatisticsEntry 14}

rsNADServerStatisticsRedirectedHTTPSessionsLastSecCounter OBJECT-TYPE
    SYNTAX  Counter
    ACCESS  read-only
    STATUS  optional
    DESCRIPTION
    "Number of HTTP sessions redirected to this Server during the last second."
    ::=  {rsNADServerStatisticsEntry 15}

rsNADServerStatisticsRedirectedTriangSessions OBJECT-TYPE
    SYNTAX  OCTET STRING (SIZE(8))
    ACCESS  read-only
    STATUS  optional
    DESCRIPTION
    "Number of sessions triangulated to this site."
    ::=  {rsNADServerStatisticsEntry 16}

rsNADServerStatisticsRedirectedTriangSessionsLastSecCount OBJECT-TYPE
    SYNTAX  Counter
    ACCESS  read-only
    STATUS  optional
    DESCRIPTION
    "Number of sessions triangulated to this site during the last second."
    ::=  {rsNADServerStatisticsEntry 17}

rsNADServerStatisticsRedirectedRTSPSessions OBJECT-TYPE
    SYNTAX  OCTET STRING (SIZE(8))
    ACCESS  read-only
    STATUS  optional
    DESCRIPTION
    "Number of RTSP sessions redirected to this Server."
    ::=  {rsNADServerStatisticsEntry 18}

rsNADServerStatisticsRedirectedRTSPSessionsLastSecCounter OBJECT-TYPE
    SYNTAX  Counter
    ACCESS  read-only
    STATUS  optional
    DESCRIPTION
    "Number of RTSP sessions redirected to this Server during the last second."
    ::=  {rsNADServerStatisticsEntry 19}

rsNADServerStatisticsAverageUsersNum OBJECT-TYPE
    SYNTAX INTEGER
    ACCESS  read-only
    STATUS  optional
    DESCRIPTION
      "The average number of active connections attached to this server"
    ::= {rsNADServerStatisticsEntry 20}

rsNADServerStatisticsRedirectedSIPSessions OBJECT-TYPE
    SYNTAX  OCTET STRING (SIZE(8))
    ACCESS  read-only
    STATUS  optional
    DESCRIPTION
    "Number of SIP sessions redirected to this Server."
    ::=  {rsNADServerStatisticsEntry 21}

rsNADServerStatisticsRedirectedSIPSessionsLastSecCounter OBJECT-TYPE
    SYNTAX  Counter
    ACCESS  read-only
    STATUS  optional
    DESCRIPTION
    "Number of SIP sessions redirected to this Server during the last second."
    ::=  {rsNADServerStatisticsEntry 22}

rsNADServerStatisticsRedirectedProxySessions OBJECT-TYPE
    SYNTAX  OCTET STRING (SIZE(8))
    ACCESS  read-only
    STATUS  optional
    DESCRIPTION
    "Number of Proxy (Client NAT redirection) sessions redirected to this Server."
    ::=  {rsNADServerStatisticsEntry 23}

rsNADServerStatisticsRedirectedProxySessionsLastSecCounter OBJECT-TYPE
    SYNTAX  Counter
    ACCESS  read-only
    STATUS  optional
    DESCRIPTION
    "Number of Proxy (Client NAT redirection) sessions redirected to this Server during the last second."
    ::=  {rsNADServerStatisticsEntry 24}

rsNADServerStatisticsCurrentConnections  OBJECT-TYPE
    SYNTAX  INTEGER
    ACCESS  read-only
    STATUS  optional
    DESCRIPTION
     "Number of connections established with the server"
	 DEFVAL { 0 }
    ::=  {rsNADServerStatisticsEntry 25 }

rsNADServerStatisticsNewTcpConnections  OBJECT-TYPE
    SYNTAX  INTEGER
    ACCESS  read-only
    STATUS  optional
    DESCRIPTION
     "Number of TCP connections with the server"
	DEFVAL {0}
    ::=  {rsNADServerStatisticsEntry 26}

rsNADServerStatisticsTrafficIn  OBJECT-TYPE
    SYNTAX  INTEGER
    ACCESS  read-only
    STATUS  optional
    DESCRIPTION
     "Amount of traffic in kbits forwarded to the server"
	DEFVAL {0}
    ::=  {rsNADServerStatisticsEntry 27 }

rsNADServerStatisticsTrafficOut  OBJECT-TYPE
    SYNTAX  INTEGER
    ACCESS  read-only
    STATUS  optional
    DESCRIPTION
     "Amount of traffic in kbits forwarded from the server"
	DEFVAL {0}
    ::=  {rsNADServerStatisticsEntry 28 }


rsWSDSidTable OBJECT-TYPE
   SYNTAX SEQUENCE OF RsWSDSidTableEntry
   ACCESS not-accessible
   STATUS mandatory
   DESCRIPTION
       "A table for managing session ID information."
   ::= {rsNWSD 30}

rsWSDSidTableEntry OBJECT-TYPE
   SYNTAX RsWSDSidTableEntry
   ACCESS not-accessible
   STATUS mandatory
   DESCRIPTION
       " The row definition for this table."
   INDEX  {rsWSDSidFarm,
           rsWSDSidValue}
   ::= {rsWSDSidTable 1}

RsWSDSidTableEntry ::= SEQUENCE {
  rsWSDSidFarm       IpAddress,
  rsWSDSidValue      DisplayString,
  rsWSDSidServer     IpAddress,
  rsWSDSidStatus     RowStatus,
  rsWSDSidType       INTEGER,
  rsWSDSidServerPort INTEGER,
  rsWSDSidFlags      BitFlag
}

rsWSDSidFarm OBJECT-TYPE
  SYNTAX IpAddress
  ACCESS read-write
  STATUS mandatory
  DESCRIPTION
     "IP address of the farm."
  ::=  {rsWSDSidTableEntry 1}

rsWSDSidValue OBJECT-TYPE
    SYNTAX DisplayString (SIZE(1..63))
    ACCESS  read-write
    STATUS  mandatory
    DESCRIPTION
      "The session ID value that identifies the server."
    ::= {rsWSDSidTableEntry 2}

rsWSDSidServer OBJECT-TYPE
  SYNTAX IpAddress
  ACCESS read-write
  STATUS mandatory
  DESCRIPTION
     "IP address of the server identified by the session ID."
  ::=  {rsWSDSidTableEntry 3}

rsWSDSidStatus OBJECT-TYPE
  SYNTAX RowStatus
  ACCESS read-write
  STATUS mandatory
  DESCRIPTION
    "Row status for the entry."
  ::=  {rsWSDSidTableEntry 4}

rsWSDSidType OBJECT-TYPE
  SYNTAX INTEGER {
  text     (1),
  pattern  (2)
  }
  ACCESS read-write
  STATUS mandatory
  DESCRIPTION
    "The data type of the value Text / Pattern."
  DEFVAL { 1 }
  ::=  {rsWSDSidTableEntry 5}

rsWSDSidServerPort  OBJECT-TYPE
    SYNTAX INTEGER
    ACCESS  read-write
    STATUS  mandatory
    DESCRIPTION
        "Port of the server identified by the session ID. "
    DEFVAL {0}
    ::= { rsWSDSidTableEntry 6}

rsWSDSidFlags OBJECT-TYPE
    SYNTAX    BitFlag
    ACCESS    read-only
    STATUS    mandatory
    DESCRIPTION
       "Flags for internal use."
    ::= { rsWSDSidTableEntry 7 }


rsADSidTable OBJECT-TYPE
   SYNTAX SEQUENCE OF RsADSidTableEntry
   ACCESS not-accessible
   STATUS mandatory
   DESCRIPTION
       "A table for managing session ID information."
   ::= {rsNWSD 67}

rsADSidTableEntry OBJECT-TYPE
   SYNTAX RsADSidTableEntry
   ACCESS not-accessible
   STATUS mandatory
   DESCRIPTION
       " The row definition for this table."
   INDEX  {rsADSidFarm,
           rsADSidValue}
   ::= {rsADSidTable 1}

RsADSidTableEntry ::= SEQUENCE {
  rsADSidFarm        DisplayString,
  rsADSidValue       DisplayString,
  rsADSidStatus      RowStatus,
  rsADSidServer      IpAddress,
  rsADSidServerPort  INTEGER,
  rsADSidType        INTEGER,
  rsADSidFlags   			BitFlag,
  rsADSidServerName			DisplayString
}

rsADSidFarm OBJECT-TYPE
  SYNTAX DisplayString (SIZE(1..50))
  ACCESS read-only
  STATUS mandatory
  DESCRIPTION
     "The name of the farm."
  ::=  {rsADSidTableEntry 1}

rsADSidValue OBJECT-TYPE
    SYNTAX DisplayString (SIZE(1..63))
    ACCESS  read-write
    STATUS  mandatory
    DESCRIPTION
      "The session ID value that identifies the server."
    ::= {rsADSidTableEntry 2}

rsADSidStatus OBJECT-TYPE
  SYNTAX RowStatus
  ACCESS read-write
  STATUS mandatory
  DESCRIPTION
    "Row status for the entry."
  ::=  {rsADSidTableEntry 3}

rsADSidServer OBJECT-TYPE
  SYNTAX IpAddress
  ACCESS read-write
  STATUS optional
  DESCRIPTION
     "Field is obsolete"
  DEFVAL {0}
  ::=  {rsADSidTableEntry 4}

rsADSidServerPort  OBJECT-TYPE
    SYNTAX INTEGER
    ACCESS  read-write
    STATUS  optional
    DESCRIPTION
        "Field is obsolete"
    DEFVAL {0}
    ::= { rsADSidTableEntry 5}

rsADSidType OBJECT-TYPE
  SYNTAX INTEGER {
  text     (1),
  pattern  (2)
  }
  ACCESS read-write
  STATUS mandatory
  DESCRIPTION
    "The data type of the value Text / Pattern."
  DEFVAL { 1 }
  ::=  {rsADSidTableEntry 6}

rsADSidFlags OBJECT-TYPE
    SYNTAX    BitFlag
    ACCESS    read-only
    STATUS    mandatory
    DESCRIPTION
       "Flags for internal use."
    ::= { rsADSidTableEntry 7 }

rsADSidServerName  OBJECT-TYPE
  SYNTAX DisplayString (SIZE(1..30))
  ACCESS read-write
  STATUS mandatory
  DESCRIPTION
     "The Name of the server"
  ::=  {rsADSidTableEntry 8}

rsWSDTrackUDPSessionsMode OBJECT-TYPE
    SYNTAX  FeatureStatus
    ACCESS  read-write
    STATUS  mandatory
    DESCRIPTION
      "Enable/Disable tracking of UDP sessions. When disabled, such sessions are not inserted into the client table."
    DEFVAL { enable }
        ::=  {rsNWSD 31}

rsWSDTrackSSLIDinSelectServerMode OBJECT-TYPE
    SYNTAX  FeatureStatus
    ACCESS  read-write
    STATUS  mandatory
    DESCRIPTION
      "Enable/Disable tracking of SSL session IDs in Select Server mode. When disabled (default), SSL sessions
       are treated as if New Entry mode is used."
--  DEFVAL { disable }
        ::=  {rsNWSD 32}

rsWSDTuning OBJECT IDENTIFIER ::= { rsNWSD 33}

rsWSDMaxURLEntriesTuning OBJECT IDENTIFIER ::= { rsWSDTuning 1}

rsWSDMaxURLEntries OBJECT-TYPE
    SYNTAX INTEGER
    ACCESS  read-only
    STATUS  mandatory
    DESCRIPTION
      "Maximal number of entries in the URL table."
    ::=  { rsWSDMaxURLEntriesTuning 1 }

rsWSDMaxURLEntriesAfterReset OBJECT-TYPE
    SYNTAX INTEGER
    ACCESS  read-write
    STATUS  mandatory
    DESCRIPTION
      "Future maximal number of entries in the URL table."
    ::=  { rsWSDMaxURLEntriesTuning 2 }

rsWSDMaxRequestEntriesTuning OBJECT IDENTIFIER ::= { rsWSDTuning 2}

rsWSDMaxRequestEntries OBJECT-TYPE
    SYNTAX INTEGER
    ACCESS  read-only
    STATUS  mandatory
    DESCRIPTION
      "Maximal number of entries in the request table."
    ::=  { rsWSDMaxRequestEntriesTuning 1 }

rsWSDMaxRequestEntriesAfterReset OBJECT-TYPE
    SYNTAX INTEGER
    ACCESS  read-write
    STATUS  mandatory
    DESCRIPTION
      "Future maximal number of entries in the request table."
    ::=  { rsWSDMaxRequestEntriesTuning 2 }

rsWSDMaxSSLEntriesTuning OBJECT IDENTIFIER ::= { rsWSDTuning 3}

rsWSDMaxSSLEntries OBJECT-TYPE
    SYNTAX INTEGER
    ACCESS  read-only
    STATUS  mandatory
    DESCRIPTION
      "Maximal number of entries in the SSL table."
    ::=  { rsWSDMaxSSLEntriesTuning 1 }

rsWSDMaxSSLEntriesAfterReset OBJECT-TYPE
    SYNTAX INTEGER
    ACCESS  read-write
    STATUS  mandatory
    DESCRIPTION
      "Future maximal number of entries in the SSL table."
    ::=  { rsWSDMaxSSLEntriesTuning 2 }

rsWSDMaxNATAddrEntriesTuning OBJECT IDENTIFIER ::= { rsWSDTuning 4}

rsWSDMaxNATAddrEntries OBJECT-TYPE
    SYNTAX INTEGER
    ACCESS  read-only
    STATUS  mandatory
    DESCRIPTION
      "Maximal number of entries in the NAT addr table."
    ::=  { rsWSDMaxNATAddrEntriesTuning 1 }

rsWSDMaxNATAddrEntriesAfterReset OBJECT-TYPE
    SYNTAX INTEGER
    ACCESS  read-write
    STATUS  mandatory
    DESCRIPTION
      "Future maximal number of entries in the NAT addr table."
    ::=  { rsWSDMaxNATAddrEntriesTuning  2 }

rsWSDMaxNATPortsEntriesTuning OBJECT IDENTIFIER ::= { rsWSDTuning 5}

rsWSDMaxNATPortsEntries OBJECT-TYPE
    SYNTAX INTEGER
    ACCESS  read-only
    STATUS  mandatory
    DESCRIPTION
      "Maximal number of ports in each NAT addr."
    ::=  { rsWSDMaxNATPortsEntriesTuning 1 }

rsWSDMaxNATPortsEntriesAfterReset OBJECT-TYPE
    SYNTAX INTEGER
    ACCESS  read-write
    STATUS  mandatory
    DESCRIPTION
      "Future maximal number of ports in each NAT addr."
    ::=  { rsWSDMaxNATPortsEntriesTuning 2 }

rsWSDMaxDynSidEntriesTuning OBJECT IDENTIFIER ::= { rsWSDTuning 6}

rsWSDMaxDynSidEntries OBJECT-TYPE
    SYNTAX INTEGER
    ACCESS  read-only
    STATUS  mandatory
    DESCRIPTION
      "Maximal number of entries in the dynamic session ID table."
    ::=  { rsWSDMaxDynSidEntriesTuning 1 }

rsWSDMaxDynSidEntriesAfterReset OBJECT-TYPE
    SYNTAX INTEGER
    ACCESS  read-write
    STATUS  mandatory
    DESCRIPTION
      "Future maximal number of entries in the dynamic session ID table."
    ::=  { rsWSDMaxDynSidEntriesTuning 2 }

rsWSDMaxDynSrvrNATAddrEntriesTuning OBJECT IDENTIFIER ::= { rsWSDTuning 7 }

rsWSDMaxDynSrvrNATAddrEntries OBJECT-TYPE
    SYNTAX INTEGER
    ACCESS  read-only
    STATUS  mandatory
    DESCRIPTION
      "Maximal number of entries in the Dynamic Server NAT addr table."
    ::=  { rsWSDMaxDynSrvrNATAddrEntriesTuning 1 }

rsWSDMaxDynSrvrNATAddrEntriesAfterReset OBJECT-TYPE
    SYNTAX INTEGER
    ACCESS  read-write
    STATUS  mandatory
    DESCRIPTION
      "Future maximal number of entries in the Dynamic Server NAT addr table."
    ::=  { rsWSDMaxDynSrvrNATAddrEntriesTuning  2 }

rsWSDMaxDynSrvrNATPortsEntriesTuning OBJECT IDENTIFIER ::= { rsWSDTuning 8 }

rsWSDMaxDynSrvrNATPortsEntries OBJECT-TYPE
    SYNTAX INTEGER
    ACCESS  read-only
    STATUS  mandatory
    DESCRIPTION
      "Maximal number of ports in each NAT addr."
    ::=  { rsWSDMaxDynSrvrNATPortsEntriesTuning 1 }

rsWSDMaxDynSrvrNATPortsEntriesAfterReset OBJECT-TYPE
    SYNTAX INTEGER
    ACCESS  read-write
    STATUS  mandatory
    DESCRIPTION
      "Future maximal number of ports in each NAT addr."
    ::=  { rsWSDMaxDynSrvrNATPortsEntriesTuning 2 }



rsWSDMaxDynSrvrAddrEntriesTuning OBJECT IDENTIFIER ::= { rsWSDTuning 9 }

rsWSDMaxDynSrvrAddrEntries OBJECT-TYPE
    SYNTAX INTEGER
    ACCESS  read-only
    STATUS  mandatory
    DESCRIPTION
      "Maximal number of entries in the Dynamic Server NAT addr table."
    ::=  { rsWSDMaxDynSrvrAddrEntriesTuning 1 }

rsWSDMaxDynSrvrAddrEntriesAfterReset OBJECT-TYPE
    SYNTAX INTEGER
    ACCESS  read-write
    STATUS  mandatory
    DESCRIPTION
      "Future maximal number of entries in the Dynamic Server NAT addr table."
    ::=  { rsWSDMaxDynSrvrAddrEntriesTuning  2 }


rsWSDMaxGlobalAuxiliaryEntriesTuning OBJECT IDENTIFIER ::= { rsWSDTuning 10 }

rsWSDMaxGlobalAuxiliaryEntries OBJECT-TYPE
    SYNTAX INTEGER
    ACCESS  read-only
    STATUS  mandatory
    DESCRIPTION
      "Maximal number of entries in the global auxiliary table.
      In precentage of the client table."
    ::=  { rsWSDMaxGlobalAuxiliaryEntriesTuning 1 }

rsWSDMaxGlobalAuxiliaryEntriesAfterReset OBJECT-TYPE
    SYNTAX INTEGER
    ACCESS  read-write
    STATUS  mandatory
    DESCRIPTION
      "Future maximal number of entries in the global auxiliary table.
      In precentage of the client table."
    ::=  { rsWSDMaxGlobalAuxiliaryEntriesTuning 2 }

rsWSDMaxRadiusAttrEntriesTuning OBJECT IDENTIFIER ::= { rsWSDTuning 11}

rsWSDMaxRadiusAttrEntries OBJECT-TYPE
    SYNTAX INTEGER
    ACCESS  read-only
    STATUS  mandatory
    DESCRIPTION
		"Maximal number of entries in the Attribute table."
    ::= { rsWSDMaxRadiusAttrEntriesTuning 1 }

rsWSDMaxRadiusAttrEntriesAfterReset OBJECT-TYPE
    SYNTAX INTEGER
    ACCESS  read-write
    STATUS  mandatory
    DESCRIPTION
		"Future maximal number of entries in the Attribute table."
    ::=  { rsWSDMaxRadiusAttrEntriesTuning 2 }

rsWSDMaxSegmentEntriesTuning OBJECT IDENTIFIER ::= { rsWSDTuning 12}

rsWSDMaxSegmentEntries OBJECT-TYPE
    SYNTAX INTEGER
    ACCESS  read-only
    STATUS  mandatory
    DESCRIPTION
		"Maximal number of network segments."
    ::= { rsWSDMaxSegmentEntriesTuning 1 }

rsWSDMaxSegmentEntriesAfterReset OBJECT-TYPE
    SYNTAX INTEGER
    ACCESS  read-write
    STATUS  mandatory
    DESCRIPTION
		"Future maximal number of network segments."
    ::=  { rsWSDMaxSegmentEntriesTuning 2 }

rsWSDMaxStaticDNSPersistencyEntriesTuning OBJECT IDENTIFIER ::= { rsWSDTuning 13}
rsWSDMaxStaticDNSPersistencyEntries OBJECT-TYPE
    SYNTAX INTEGER
    ACCESS  read-only
    STATUS  mandatory
    DESCRIPTION
		"Maximal number of entries in the DNS persistency table."
    ::= { rsWSDMaxStaticDNSPersistencyEntriesTuning 1 }

rsWSDMaxStaticDNSPersistencyEntriesAfterReset OBJECT-TYPE
    SYNTAX INTEGER
    ACCESS  read-write
    STATUS  mandatory
    DESCRIPTION
		"Future maximal number of entries in the DNS persistency table."
    ::=  { rsWSDMaxStaticDNSPersistencyEntriesTuning 2 }

rsWSDMaxDynamicDNSPersistencyEntriesTuning OBJECT IDENTIFIER ::= { rsWSDTuning 14}

rsWSDMaxDynamicDNSPersistencyEntries OBJECT-TYPE
    SYNTAX INTEGER
    ACCESS  read-only
    STATUS  mandatory
    DESCRIPTION
		"Maximal number of entries in the DNS persistency table."
    ::= { rsWSDMaxDynamicDNSPersistencyEntriesTuning 1 }

rsWSDMaxDynamicDNSPersistencyEntriesAfterReset OBJECT-TYPE
    SYNTAX INTEGER
    ACCESS  read-write
    STATUS  mandatory
    DESCRIPTION
		"Future maximal number of entries in the DNS persistency table."
    ::=  { rsWSDMaxDynamicDNSPersistencyEntriesTuning 2 }


rsWSDMaxL4PolicyEntriesTuning OBJECT IDENTIFIER ::= { rsWSDTuning 15}

rsWSDMaxL4PolicyEntries OBJECT-TYPE
    SYNTAX INTEGER
    ACCESS  read-only
    STATUS  mandatory
    DESCRIPTION
		"Maximal number of L4 policy entries."
    ::= { rsWSDMaxL4PolicyEntriesTuning 1 }

rsWSDMaxL4PolicyEntriesAfterReset OBJECT-TYPE
    SYNTAX INTEGER
    ACCESS  read-write
    STATUS  mandatory
    DESCRIPTION
		"Future maximal number of L4 policy entries."
    ::=  { rsWSDMaxL4PolicyEntriesTuning 2 }

--rsADMaxSrvrNATAddrEntriesTuning OBJECT IDENTIFIER ::= { rsWSDTuning 16 }

--rsADMaxSrvrNATAddrEntries OBJECT-TYPE
--    SYNTAX INTEGER
--    ACCESS  read-only
--    STATUS  mandatory
--    DESCRIPTION
--      "Deprecated - Maximal number of entries in the Server NAT addr table."
--    ::=  { rsADMaxSrvrNATAddrEntriesTuning 1 }

--rsADMaxSrvrNATAddrEntriesAfterReset OBJECT-TYPE
--    SYNTAX INTEGER
--    ACCESS  read-write
--    STATUS  mandatory
--    DESCRIPTION
--      "Deprecated - Future maximal number of entries in the Server NAT addr table."
--    ::=  { rsADMaxSrvrNATAddrEntriesTuning 2 }

--rsADMaxSrvrNATPortsEntriesTuning OBJECT IDENTIFIER ::= { rsWSDTuning 17 }

--rsADMaxSrvrNATPortsEntries OBJECT-TYPE
--    SYNTAX INTEGER
--    ACCESS  read-only
--    STATUS  mandatory
--    DESCRIPTION
--      "Deprecated - Maximal number of ports in each NAT addr."
--   ::=  { rsADMaxSrvrNATPortsEntriesTuning 1 }

--rsADMaxSrvrNATPortsEntriesAfterReset OBJECT-TYPE
--    SYNTAX INTEGER
--    ACCESS  read-write
--    STATUS  mandatory
--    DESCRIPTION
--      "Deprecated - Future maximal number of ports in each NAT addr."
--    ::=  { rsADMaxSrvrNATPortsEntriesTuning 2 }

rsWSDTweaks OBJECT IDENTIFIER ::= { rsNWSD 34}

rsWSDMaintainURLSFPersistency OBJECT-TYPE
    SYNTAX FeatureStatus
    ACCESS  read-write
    STATUS  mandatory
    DESCRIPTION
      "maintain HTTP persistency in URL SuperFarm sessions. enable -
      persistency is maintained, disable - persistency is broken."
--  DEFVAL  { disable }
    ::=  { rsWSDTweaks 1 }

rsWSDAllowAnyAppPortForSid OBJECT-TYPE
    SYNTAX FeatureStatus
    ACCESS  read-write
    STATUS  mandatory
    DESCRIPTION
      "enable - allow session id parsing on any application port. disable -
      mechanism works for port 80 only."
--  DEFVAL  { disable }
    ::=  { rsWSDTweaks 2 }

rsWSDSrcPortInClientHash OBJECT-TYPE
    SYNTAX FeatureStatus
    ACCESS  read-write
    STATUS  mandatory
    DESCRIPTION
      "enable - client's source port is used in client table hashing, disable
      - only client IP is used."
--  DEFVAL  { disable }
    ::=  { rsWSDTweaks 3 }

rsWSDUserDefinedTimeoutAfterTCPFailure OBJECT-TYPE
    SYNTAX FeatureStatus
    ACCESS  read-write
    STATUS  mandatory
    DESCRIPTION
      "enable - use user defined timeout between failed TCP checks, disable -
      use 0.5 seconds delay between checks."
--  DEFVAL  { disable }
    ::=  { rsWSDTweaks 4 }

rsWSDNoSlashAfterGET OBJECT-TYPE
    SYNTAX FeatureStatus
    ACCESS  read-write
    STATUS  mandatory
    DESCRIPTION
      "enable - no slash is used when trying to read a HTTP page on the server
      (for syntax that includes a host name), disable - request is with a
      slash (for syntax that does not include a host name)."
--  DEFVAL  { disable }
    ::=  { rsWSDTweaks 5 }

rsWSDTimeoutForSYN OBJECT-TYPE
    SYNTAX INTEGER  (0..10)
    ACCESS  read-write
    STATUS  mandatory
    DESCRIPTION
      "The initial aging time that a client entry will use when a SYN packet
      arrives. 0 means use the regular aging time.
      Now using rsSESSIONSynProtectionTimeout"
--  DEFVAL  { 5 }
    ::=  { rsWSDTweaks 6 }


rsWSDSpecificNATAddress OBJECT-TYPE
    SYNTAX IpAddress
    ACCESS  read-write
    STATUS  mandatory
    DESCRIPTION
      "Use this (farm) address as the one used for all NAT sessions."
    ::=  { rsWSDTweaks 7 }

rsWSDExtendedCheckHostMode OBJECT-TYPE
    SYNTAX INTEGER {
      ipMode(1),
      nameMode(2)
    }
    ACCESS  read-write
    STATUS  mandatory
    DESCRIPTION
      "How the host in the extended HTTP check appears. Can be the server IP
      or the farm name."
    DEFVAL  { 1 }
    ::=  { rsWSDTweaks 8 }

rsWSDExtendedLRPSecurity OBJECT-TYPE
    SYNTAX FeatureStatus
    ACCESS  read-write
    STATUS  mandatory
    DESCRIPTION
      "When extended LRP security is enabled, the map address supplied by a distributed
       WSD must be in the same subnet as it's farm."
    DEFVAL  { enable }
    ::=  { rsWSDTweaks 9 }

rsWSDURLSid OBJECT-TYPE
    SYNTAX FeatureStatus
    ACCESS  read-write
    STATUS  mandatory
    DESCRIPTION
      "When enabled, sesion ID parsing is performed on URL parameters, rather than the
       entire HTTP header."
    DEFVAL  { disable }
    ::=  { rsWSDTweaks 10 }

rsWSDURLTableLookupPrecedence OBJECT-TYPE
    SYNTAX INTEGER {
      url(1),
      fileType(2)
    }
    ACCESS  read-write
    STATUS  mandatory
    DESCRIPTION
      "This parameter sets the lookup precedence of the URL table. URL means look for URL first,
       fileType means look for file type match first."
    DEFVAL  { 1 }
    ::=  { rsWSDTweaks 11 }

rsWSDDynamicSidSharing OBJECT-TYPE
    SYNTAX FeatureStatus
    ACCESS  read-write
    STATUS  mandatory
    DESCRIPTION
      "When enabled, the WSD ignores the farm attribute of a dynamic session ID, i.e. a session to farm a
       will be forwarded to a server from farm b if the same session ID is identified as the one that was
       originally set by the same server in a session to farm b. The two farms must have the same
       servers."
    DEFVAL  { disable }
    ::=  { rsWSDTweaks 12 }

rsWSDNATSessionHandle OBJECT-TYPE
    SYNTAX INTEGER {
      nat(1),
      forward(2),
	    discard(3)
    }
    ACCESS  read-write
    STATUS  mandatory
    DESCRIPTION
      "How to handle new NAT sessions when server is not in service"
    DEFVAL  { 1 }
    ::=  { rsWSDTweaks 13 }

rsWSDAutoL4PolicyForFarm OBJECT-TYPE
    SYNTAX FeatureStatus
    ACCESS  read-write
    STATUS  mandatory
    DESCRIPTION
      "When enabled, WSD creates entry in the L4 Policy table automatically each time a Farm is created by the user."
    DEFVAL  { disable }
    ::=  { rsWSDTweaks 14 }

rsWSDServerNATVLANHandle OBJECT-TYPE
    SYNTAX INTEGER {
      natAndBridge(1),
      bridge(2)
    }
    ACCESS  read-write
    STATUS  mandatory
    DESCRIPTION
      "How to handle new NAT sessions when server is in bridge"
    DEFVAL  { natAndBridge }
    ::=  { rsWSDTweaks 15 }


rsWSDServerReplyInspectionWithFirstMode OBJECT-TYPE
    SYNTAX INTEGER {
      inspectAllServerReplies(1),
      inspectFirstReply(2)
    }
    ACCESS  read-write
    STATUS  mandatory
    DESCRIPTION
      "Enables old behavior of Dynamic Session ID learned from server reply when Persistent L7 Switching mode configured to 'First'.
       Using this mode (inspectAllServerReplies) AD is inspecting each response from server in order to learn the Session ID.
       If the server will change the Session ID, AD will change it on the DSID table.
       When set to inspectFirstReply, AD will learn only from the server reply to the first transaction.
       In case there is a need to learn from each response, the user should configure one of the 'complete' or Persistent L7 Switching modes (overite/maintain)."
    DEFVAL  { inspectAllServerReplies }
    ::=  { rsWSDTweaks 16 }

rsADOutboundSIP  OBJECT-TYPE
    SYNTAX FeatureStatus
    ACCESS  read-write
    STATUS  mandatory
    DESCRIPTION
      "enable or disable the Outbound SIP support feature"
    DEFVAL  { disable }
   ::=  { rsWSDTweaks 17 }

rsADSIPAgingOnSessionEnd  OBJECT-TYPE
    SYNTAX INTEGER (0..65535)
    ACCESS  read-write
    STATUS  mandatory
    DESCRIPTION
      "Aging time for SIP dynamic SID entries and SIP client entries as a result of SIP session end, in seconds."
    DEFVAL  { 32 }
   ::=  { rsWSDTweaks 29 }

rsADL7AnswerRstToClientFin  OBJECT-TYPE
    SYNTAX FeatureStatus
    ACCESS  read-write
    STATUS  mandatory
    DESCRIPTION
      "When enabled, the AD replaces the client TCP fin by reset"
    DEFVAL  { disable }
   ::=  { rsWSDTweaks 18 }

rndPeakSSLTPS OBJECT-TYPE
   SYNTAX INTEGER
   ACCESS read-only
   STATUS mandatory
   DESCRIPTION
        "Deprecated"
    ::= { rsWSDTweaks 19 }

rndPeakCompressionMbitServer OBJECT-TYPE
   SYNTAX INTEGER
   ACCESS read-only
   STATUS mandatory
   DESCRIPTION
    "The peak Mbit that are received from server side and are compressed."
    ::= { rsWSDTweaks 20 }

rdwrDXPNumOfConcurentConnections OBJECT-TYPE
   SYNTAX INTEGER
   ACCESS read-only
   STATUS mandatory
   DESCRIPTION
    "Number Of Concurent Connections in accelerarot (AE)."
    ::= { rsWSDTweaks 21 }

rsWSDGlobalConnectivityCheckTcpTimeout OBJECT-TYPE
    SYNTAX INTEGER
    ACCESS  read-write
    STATUS  mandatory
    DESCRIPTION
      "Gets\sets the timeout of TCP check response"
--  DEFVAL  { 3000 }
    ::=  { rsWSDTweaks 22 }

rsNADSpecificNATAddress OBJECT-TYPE
   SYNTAX  InetAddress
   ACCESS  read-write
   STATUS  mandatory
   DESCRIPTION
       "Use this VIP address as the one used for all NAT IPv4 sessions.."
	DEFVAL{"0.0.0.0"}
   ::= {rsWSDTweaks 23}

rsNADSpecificNATAddressType OBJECT-TYPE
   SYNTAX  InetAddressType
   ACCESS  read-only
   STATUS  mandatory
   DESCRIPTION
       "NAT IP address Type."
	DEFVAL  { ipv4 }
   ::= {rsWSDTweaks 24}


rndPeakSSLCPS OBJECT-TYPE
   SYNTAX INTEGER
   ACCESS read-only
   STATUS mandatory
   DESCRIPTION
    "The peak of SSL CPS the device handles."
    ::= { rsWSDTweaks 25 }

rsNADIPv6SpecificNATAddress OBJECT-TYPE
   SYNTAX  InetAddress
   ACCESS  read-write
   STATUS  mandatory
   DESCRIPTION
       "Use this VIP address as the one used for all NAT IPv6 sessions.."
	DEFVAL{"0::0"}
   ::= {rsWSDTweaks 26}

rsNADIPv6SpecificNATAddressType OBJECT-TYPE
   SYNTAX  InetAddressType
   ACCESS  read-only
   STATUS  mandatory
   DESCRIPTION
       "NAT IP address Type."
	DEFVAL  { ipv6 }
   ::= {rsWSDTweaks 27}

rndCompressionTrafficPeak OBJECT-TYPE
   SYNTAX INTEGER
   ACCESS read-only
   STATUS mandatory
   DESCRIPTION
    "The Compression traffic peak of the device."
    ::= { rsWSDTweaks 28 }

-- Place Holder
--rsSystemInternalResetCounterRateForPassiveHealthCheck OBJECT-TYPE
--    SYNTAX INTEGER (1..3600)
--    ACCESS  read-write
--    STATUS  mandatory
--    DESCRIPTION
--      "Set the counter reset rate for Passive Health Check feature (seconds)"
--    DEFVAL  { 2 }
--    ::=  { rsWSDTweaks 30 }

rsADFragmentMtu  OBJECT-TYPE
    SYNTAX INTEGER (40..1500)
    ACCESS  read-write
    STATUS  mandatory
    DESCRIPTION
      "The MTU used when AppDirector generates IP fragmetned traffic "
    DEFVAL  { 1500 }
   ::=  { rsWSDTweaks 30 }
--
-- extended farm table
--

rsWSDExtendedFarmTable OBJECT-TYPE
   SYNTAX SEQUENCE OF RsWSDExtendedFarmEntry
   ACCESS not-accessible
   STATUS mandatory
   DESCRIPTION
          "In this table the WSD saves the general parameters per
           server farme IP Addr."
   ::= {rsNWSD 35}

rsWSDExtendedFarmEntry OBJECT-TYPE
    SYNTAX RsWSDExtendedFarmEntry
    ACCESS not-accessible
    STATUS  mandatory
    DESCRIPTION
       " The row definition for this table."
   INDEX  {rsWSDExtendedFarmAddress}
   ::= {rsWSDExtendedFarmTable 1}


RsWSDExtendedFarmEntry  ::= SEQUENCE {
  rsWSDExtendedFarmAddress              IpAddress,
  rsWSDExtendedFarmHttpsType            INTEGER,
  rsWSDConnCheckSecret                  DisplayString,
  rsWSDOverLoadStatus                   FeatureStatus,
  rsWSDFarmURLSid                       FeatureStatus,
  rsWSDExtendedFarmNATRangeIPFrom       IpAddress,
  rsWSDExtendedFarmSessionChaining      INTEGER,
  rsWSDTerminalServerPort               INTEGER,
  rsWSDTrackSslId                       FeatureStatus,
  rsWSDCloseSessionAtAging              FeatureStatus,
  rsWSDDNSResponseTTL                   INTEGER,
  rsWSDSegName                          DisplayString,
  rsWSDStaticPrxEntries                 INTEGER,
  rsWSDHostRouteInjection               IpAddress,
  rsWSDRadiusAttribute                  INTEGER,
  rsWSDHostRouteMetric                  INTEGER,
  rsWSDSipPort                          INTEGER,
  rsWSDAutoXForwardedFor                FeatureStatus,
  rsWSDAutoInsertCookie                 INTEGER,
  rsWSDRSTonServerFailure               FeatureStatus,
  rsWSDRadiusProxyAttribute             INTEGER,
  rsWSDHashParameterForSIP              INTEGER,
  rsWSDSSLAging                         INTEGER,
  rsWSDSelectServerPerTransaction       FeatureStatus,
  rsWSDNoServicePageHTTPCode			INTEGER,
  rsWSDExtendedFarmBackendSSLState		INTEGER
}

rsWSDExtendedFarmAddress OBJECT-TYPE
    SYNTAX IpAddress
    ACCESS  read-only
    STATUS  mandatory
    DESCRIPTION
      "The IP Address of the WEB farm."
    ::= {rsWSDExtendedFarmEntry 1}

rsWSDExtendedFarmHttpsType OBJECT-TYPE
    SYNTAX INTEGER {
      regular(1),
      httpsonly(2)
   }
    ACCESS  read-write
    STATUS  mandatory
    DESCRIPTION
      " regular - means that this server applies all requests
        httpsonly - applies only HTTPS requests"
    ::=  {rsWSDExtendedFarmEntry 2}

rsWSDConnCheckSecret OBJECT-TYPE
   SYNTAX DisplayString (SIZE(0..20))
   ACCESS  read-write
   STATUS  mandatory
   DESCRIPTION
     "Secret used for radius connectivity checks."
   ::= {rsWSDExtendedFarmEntry 3}

rsWSDOverLoadStatus OBJECT-TYPE
   SYNTAX FeatureStatus
   ACCESS  read-write
   STATUS  mandatory
   DESCRIPTION
       "Enable or disable to open more clients session to a server even though
        its connection limit is reached"
-- DEFVAL { disable }
   ::=  {rsWSDExtendedFarmEntry 4}

rsWSDFarmURLSid OBJECT-TYPE
   SYNTAX FeatureStatus
   ACCESS  read-write
   STATUS  mandatory
   DESCRIPTION
       "Set session ID search in URL per farm (not just globally)."
   DEFVAL { disable }
   ::=  {rsWSDExtendedFarmEntry 5}

rsWSDExtendedFarmNATRangeIPFrom OBJECT-TYPE
 SYNTAX IpAddress
    ACCESS  read-write
    STATUS  mandatory
    DESCRIPTION
 "choose beginning of existing range interval from NAT IP range table "
    ::=  {rsWSDExtendedFarmEntry 6}

rsWSDExtendedFarmSessionChaining  OBJECT-TYPE
   SYNTAX INTEGER {
        enable(1),
        disable(2),
        manageaxfarm(3),
        tcpsplitting(4)
   }
   ACCESS  read-write
   STATUS  mandatory
   DESCRIPTION
       "Enable or disable session chaining for current farm."
   DEFVAL { 2 }
   ::=  {rsWSDExtendedFarmEntry 7 }


rsWSDTerminalServerPort OBJECT-TYPE
    SYNTAX INTEGER (0..65535)
    ACCESS  read-write
    STATUS  mandatory
    DESCRIPTION
      "Port number used for terminal server traffic."
    DEFVAL {0}
   ::= {rsWSDExtendedFarmEntry 8}

rsWSDTrackSslId OBJECT-TYPE
    SYNTAX FeatureStatus
   ACCESS  read-write
   STATUS  mandatory
   DESCRIPTION
       "Enable or disable SSL ID tracking for a farm."
   DEFVAL { disable }
   ::=  {rsWSDExtendedFarmEntry 9 }

rsWSDCloseSessionAtAging OBJECT-TYPE
   SYNTAX FeatureStatus
   ACCESS  read-write
   STATUS  mandatory
   DESCRIPTION
       "Close connection to server when a client is aged."
   DEFVAL { disable }
   ::=  {rsWSDExtendedFarmEntry 10 }

rsWSDDNSResponseTTL OBJECT-TYPE
   SYNTAX INTEGER (0..2147483647)
   ACCESS  read-write
   STATUS  mandatory
   DESCRIPTION
        "TTL for DNS replies."
   DEFVAL { 0 }
   ::=  {rsWSDExtendedFarmEntry 11 }


rsWSDSegName OBJECT-TYPE
    SYNTAX  DisplayString (SIZE(0..20))
    ACCESS  read-write
    STATUS  mandatory
    DESCRIPTION
      "Segments Name."

   ::= {rsWSDExtendedFarmEntry 12}

rsWSDStaticPrxEntries OBJECT-TYPE
   SYNTAX INTEGER (1..5000)
   ACCESS  read-write
   STATUS  mandatory
   DESCRIPTION
       "Maximum number of static proximity entries for this farm. Changing this number while static
        proximity entries already exist for the farm - requires a reset."
   DEFVAL { 500 }

   ::=  {rsWSDExtendedFarmEntry 13}

rsWSDHostRouteInjection OBJECT-TYPE
   SYNTAX  IpAddress
   ACCESS  read-write
   STATUS  mandatory
   DESCRIPTION
       "The IP address to be advertised via dynamic
	    routing protocols - OSPF and RIPv2"
-- DEFVAL   { 0.0.0.0 }
   ::=  {rsWSDExtendedFarmEntry 14}

rsWSDRadiusAttribute OBJECT-TYPE
    SYNTAX INTEGER
    ACCESS  read-write
    STATUS  mandatory
    DESCRIPTION
      "RADIUS attribute to use in client table hashing ."
    DEFVAL {0}
   ::= {rsWSDExtendedFarmEntry 15}

rsWSDHostRouteMetric OBJECT-TYPE
    SYNTAX INTEGER
    ACCESS  read-write
    STATUS  mandatory
    DESCRIPTION
      "Metric to be used when adding static host route."
    DEFVAL { 1 }
   ::= {rsWSDExtendedFarmEntry 16}

rsWSDSipPort OBJECT-TYPE
    SYNTAX  INTEGER (0..65535)
    ACCESS  read-write
    STATUS  mandatory
    DESCRIPTION
      "Determine the port number that identify SIP sessions"
    DEFVAL { 0 }
    ::=  { rsWSDExtendedFarmEntry 17 }

rsWSDAutoXForwardedFor OBJECT-TYPE
    SYNTAX FeatureStatus
   ACCESS  read-write
   STATUS  mandatory
   DESCRIPTION
       "Add X-Forwarded-For to HTTP requests."
   DEFVAL { disable }
   ::=  {rsWSDExtendedFarmEntry 18 }

rsWSDAutoInsertCookie OBJECT-TYPE
   SYNTAX INTEGER {
        enable(1),
        disable(2),
        enableAndRemoveCookieOnReturn(3)
   }
   ACCESS  read-write
   STATUS  mandatory
   DESCRIPTION
       "Add Cookie to HTTP replies."
   DEFVAL { disable }
   ::=  {rsWSDExtendedFarmEntry 19 }


rsWSDRSTonServerFailure OBJECT-TYPE
    SYNTAX FeatureStatus
    ACCESS  read-write
    STATUS  mandatory
    DESCRIPTION
      "Sets status for sending reset to client on server failures"
    DEFVAL { disable }
    ::=  { rsWSDExtendedFarmEntry 20 }

rsWSDRadiusProxyAttribute OBJECT-TYPE
    SYNTAX INTEGER
    ACCESS  read-write
    STATUS  mandatory
    DESCRIPTION
      "RADIUS attribute to use in support Radius Proxy reply, will hold the server IP."
    DEFVAL {0}
   ::= {rsWSDExtendedFarmEntry 21}

rsWSDHashParameterForSIP OBJECT-TYPE
    SYNTAX INTEGER {
      callID (1),
      requestURI(2)
   }
    ACCESS  read-write
    STATUS  mandatory
    DESCRIPTION
      "Defines the parameter to be used for SIP load balancing when Dispatch Method is Hashing."
	DEFVAL { callID }
    ::=  { rsWSDExtendedFarmEntry 22 }

rsWSDSSLAging OBJECT-TYPE
    SYNTAX INTEGER
    ACCESS  read-write
    STATUS  mandatory
    DESCRIPTION
      "The aging for the SSL ID's in seconds."
    DEFVAL {120}
    ::=  { rsWSDExtendedFarmEntry 23 }

rsWSDSelectServerPerTransaction OBJECT-TYPE
    SYNTAX FeatureStatus
    ACCESS  read-write
    STATUS  mandatory
    DESCRIPTION
      "Select server per transaction"
    DEFVAL {disable}
    ::=  { rsWSDExtendedFarmEntry 24 }

rsWSDNoServicePageHTTPCode  OBJECT-TYPE
   SYNTAX INTEGER {
        continue(100),
		ok(200),
		accepted(202),
		no-content(204),
		reset-content(205),
		partial-content(206),
		multiple-choices(300),
		moved-permanently(301),
		moved-temporarily(302),
		not-modified(304),
		bad-request(400),
		unauthorized(401),
		payment-required(402),
		forbidden(403),
		object-not-found(404),
		service-unavailable(503)
   }
   ACCESS  read-write
   STATUS  mandatory
   DESCRIPTION
       "The HTTP code acceptable in that farm."
   DEFVAL { 200 }
   ::=  {rsWSDExtendedFarmEntry 25}


rsWSDExtendedFarmBackendSSLState OBJECT-TYPE
  SYNTAX INTEGER{
        overrideToClearText(1),
        respectSslPolicy(2)
  }
  ACCESS read-write
  STATUS mandatory
  DESCRIPTION
    "Controls whether backend connections are over SSL."
  DEFVAL { respectSslPolicy }
  ::=  {rsWSDExtendedFarmEntry 26}

  -- Place Holder
--  rsWSDPassiveHealthCheckFailures OBJECT-TYPE
--  SYNTAX INTEGER (0..1000)
--  ACCESS read-write
--  STATUS mandatory
--  DESCRIPTION
--    "Number of TCP handshake failures to bring farm server to NIS"
--  DEFVAL { 0 }
--  ::=  {rsWSDExtendedFarmEntry 27}



rsADExtendedFarmTable OBJECT-TYPE
   SYNTAX SEQUENCE OF RsADExtendedFarmEntry
   ACCESS not-accessible
   STATUS mandatory
   DESCRIPTION
          "In this table the AppDirector saves the general parameters per
           servers farm."
   ::= {rsNWSD 63}

rsADExtendedFarmEntry OBJECT-TYPE
    SYNTAX RsADExtendedFarmEntry
    ACCESS not-accessible
    STATUS  mandatory
    DESCRIPTION
       " The row definition for this table."
   INDEX  {rsADExtendedFarmName}
   ::= {rsADExtendedFarmTable 1}


RsADExtendedFarmEntry  ::= SEQUENCE {
  rsADExtendedFarmName              DisplayString,
  rsADConnCheckSecret               DisplayString,
  rsADOverLoadStatus                FeatureStatus,
  rsADExtendedFarmNATRangeIPFrom    IpAddress,
  rsADExtendedFarmSessionChaining   INTEGER,
  rsADTrackSslId                    FeatureStatus,
  rsADCloseSessionAtAging           INTEGER,
  rsADSegName                       DisplayString,
  rsADRadiusAttribute               INTEGER,
  rsADRadiusProxyAttribute          INTEGER,
  rsADAutoXForwardedFor             FeatureStatus,
  rsADAutoInsertCookie              INTEGER,
  rsADRSTonServerFailure            FeatureStatus,
  rsADHashParameterForSIP           INTEGER,
  rsADSSLAging                      INTEGER,
  rsADSelectServerPerTransaction    		FeatureStatus,
  rsADNoServicePageHTTPCode    	    INTEGER,
  rsADExtendedFarmNATRangeIPV4FromAddrType  	InetAddressType,
  rsADExtendedFarmNATRangeIPV4FromAddr  		InetAddress,
  rsADExtendedFarmNATRangeIPV6FromAddrType  	InetAddressType,
  rsADExtendedFarmNATRangeIPV6FromAddr         	InetAddress,
  rsADExtendedFarmBackendSSLState   INTEGER
}

rsADExtendedFarmName OBJECT-TYPE
    SYNTAX DisplayString (SIZE(1..50))
    ACCESS  read-only
    STATUS  mandatory
    DESCRIPTION
      "The name of the farm."
    ::= {rsADExtendedFarmEntry 1}


rsADConnCheckSecret OBJECT-TYPE
   SYNTAX DisplayString (SIZE(0..20))
   ACCESS  read-write
   STATUS  optional
   DESCRIPTION
     "Secret used for radius connectivity checks."
   ::= {rsADExtendedFarmEntry 2}

rsADOverLoadStatus OBJECT-TYPE
   SYNTAX FeatureStatus
   ACCESS  read-write
   STATUS  optional
   DESCRIPTION
       "Enable or disable to open more clients session to a server even though
        its connection limit is reached"
   DEFVAL { disable }
   ::=  {rsADExtendedFarmEntry 3}

-- obsolete
rsADExtendedFarmNATRangeIPFrom OBJECT-TYPE
   SYNTAX IpAddress
   ACCESS  read-write
   STATUS  optional
   DESCRIPTION
       "Field is obsolete"
   DEFVAL {0}
   ::=  {rsADExtendedFarmEntry 4}

rsADExtendedFarmSessionChaining  OBJECT-TYPE
   SYNTAX INTEGER {
        enable(1),
        disable(2),
        manageaxfarm(3),
        tcpsplitting(4)
   }
   ACCESS  read-write
   STATUS  optional
   DESCRIPTION
       "Enable or disable session chaining for current farm."
   DEFVAL { 2 }
   ::=  {rsADExtendedFarmEntry 5 }

rsADTrackSslId OBJECT-TYPE
   SYNTAX FeatureStatus
   ACCESS  read-write
   STATUS  optional
   DESCRIPTION
       "Enable or disable SSL ID tracking for a farm."
   DEFVAL { disable }
   ::=  {rsADExtendedFarmEntry 6 }

rsADCloseSessionAtAging OBJECT-TYPE
   SYNTAX INTEGER {
        toSrvr(1),
		disable(2),
		toClnt(3),
		toSrvrClnt(4)
   }
   ACCESS  read-write
   STATUS  optional
   DESCRIPTION
       "Close connection when a client is aged."
   DEFVAL { disable }
   ::=  {rsADExtendedFarmEntry 7 }

rsADSegName OBJECT-TYPE
    SYNTAX  DisplayString (SIZE(0..20))
    ACCESS  read-write
    STATUS  optional
    DESCRIPTION
      "Segments Name."

   ::= {rsADExtendedFarmEntry 8}

rsADRadiusAttribute OBJECT-TYPE
    SYNTAX INTEGER
    ACCESS  read-write
    STATUS  optional
    DESCRIPTION
        "RADIUS attribute to use in client table hashing ."
    DEFVAL {0}
    ::= {rsADExtendedFarmEntry 9}

rsADRadiusProxyAttribute OBJECT-TYPE
    SYNTAX INTEGER
    ACCESS  read-write
    STATUS  optional
    DESCRIPTION
      "RADIUS attribute to use in support Radius Proxy reply, will hold the server IP."
    DEFVAL {0}
    ::= {rsADExtendedFarmEntry 10}

rsADAutoXForwardedFor OBJECT-TYPE
    SYNTAX FeatureStatus
    ACCESS  read-write
    STATUS  optional
    DESCRIPTION
        "Add X-Forwarded-For to HTTP requests."
    DEFVAL { disable }
    ::=  {rsADExtendedFarmEntry 11 }

rsADAutoInsertCookie OBJECT-TYPE
    SYNTAX INTEGER {
        enable(1),
        disable(2),
        enableAndRemoveCookieOnReturn(3)
   }
    ACCESS  read-write
    STATUS  optional
    DESCRIPTION
        "Add Cookie to HTTP replies."
    DEFVAL { disable }
    ::=  {rsADExtendedFarmEntry 12 }

rsADRSTonServerFailure OBJECT-TYPE
    SYNTAX FeatureStatus
    ACCESS  read-write
    STATUS  optional
    DESCRIPTION
      "Sets status for sending reset to client on server failures"
    DEFVAL { disable }
    ::=  { rsADExtendedFarmEntry 13 }

rsADHashParameterForSIP OBJECT-TYPE
    SYNTAX INTEGER {
      callID (1),
      requestURI(2)
   }
    ACCESS  read-write
    STATUS  optional
    DESCRIPTION
      "Defines the parameter to be used for SIP load balancing when Dispatch Method is Hashing."
	DEFVAL { callID }
    ::=  { rsADExtendedFarmEntry 14 }

rsADSSLAging OBJECT-TYPE
    SYNTAX INTEGER
    ACCESS  read-write
    STATUS  optional
    DESCRIPTION
      "Aging time for SSL ID's in seconds"
    DEFVAL {120}
    ::=  { rsADExtendedFarmEntry 15 }

rsADSelectServerPerTransaction OBJECT-TYPE
    SYNTAX FeatureStatus
    ACCESS  read-write
    STATUS  optional
    DESCRIPTION
      "Select server per transaction"
    DEFVAL {disable}
    ::=  { rsADExtendedFarmEntry 16 }

rsADNoServicePageHTTPCode  OBJECT-TYPE
   SYNTAX INTEGER {
        continue(100),
		ok(200),
		accepted(202),
		no-content(204),
		reset-content(205),
		partial-content(206),
		multiple-choices(300),
		moved-permanently(301),
		moved-temporarily(302),
		not-modified(304),
		bad-request(400),
		unauthorized(401),
		payment-required(402),
		forbidden(403),
		object-not-found(404),
		service-unavailable(503)
   }
   ACCESS  read-write
   STATUS  mandatory
   DESCRIPTION
       "The HTTP code acceptable in that farm."
   DEFVAL { 200 }
   ::=  {rsADExtendedFarmEntry 17}

rsADExtendedFarmNATRangeIPV4FromAddrType OBJECT-TYPE
   SYNTAX InetAddressType
   ACCESS  read-write
   STATUS  optional
   DESCRIPTION
       "IP type for beginning of existing range interval from NAT IPv4 range table"
   DEFVAL { ipv4 }
   ::=  {rsADExtendedFarmEntry 18}

rsADExtendedFarmNATRangeIPV4FromAddr OBJECT-TYPE
   SYNTAX InetAddress
   ACCESS  read-write
   STATUS  optional
   DESCRIPTION
       "choose beginning of existing range interval from NAT IPv4 range table "
   ::=  {rsADExtendedFarmEntry 19}

rsADExtendedFarmNATRangeIPV6FromAddrType OBJECT-TYPE
   SYNTAX InetAddressType
   ACCESS  read-write
   STATUS  optional
   DESCRIPTION
       "IP type for beginning of existing range interval from NAT IPv6 range table"
   DEFVAL { ipv6 }
   ::=  {rsADExtendedFarmEntry 20}

rsADExtendedFarmNATRangeIPV6FromAddr OBJECT-TYPE
   SYNTAX InetAddress
   ACCESS  read-write
   STATUS  optional
   DESCRIPTION
       "choose beginning of existing range interval from NAT IPv6 range table "
   ::=  {rsADExtendedFarmEntry 21}

rsADExtendedFarmBackendSSLState OBJECT-TYPE
  SYNTAX INTEGER{
        overrideToClearText(1),
        respectSslPolicy(2)
  }
  ACCESS read-write
  STATUS mandatory
  DESCRIPTION
    "Controls whether backend connections are over SSL."
  DEFVAL { respectSslPolicy }
  ::=  {rsADExtendedFarmEntry 22}

-- Place Holder
--  rsADPassiveHealthCheckFailures OBJECT-TYPE
--  SYNTAX INTEGER (0..1000)
--  ACCESS read-write
--  STATUS mandatory
--  DESCRIPTION
--    "Number of TCP handshake failures to bring farm server to NIS"
--  DEFVAL { 0 }
--  ::=  {rsADExtendedFarmEntry 23}



rsWSDNHRTable OBJECT-TYPE
   SYNTAX SEQUENCE OF RsWSDNHREntry
   ACCESS not-accessible
   STATUS mandatory
   DESCRIPTION
          "In this table the WSD holds the Next Hop Routers to be used as Default Routers."
   ::= {rsNWSD 36}

rsWSDNHREntry OBJECT-TYPE
    SYNTAX RsWSDNHREntry
    ACCESS not-accessible
    STATUS mandatory
    DESCRIPTION
       " The row definition for NHR table."
   INDEX  {rsWSDNHRNHRIP}
   ::= {rsWSDNHRTable 1}

RsWSDNHREntry  ::= SEQUENCE {
        rsWSDNHRNHRIP                   IpAddress,
        rsWSDNHRDestinationMAC          PhysAddress,
        rsWSDNHRSourceMAC               PhysAddress,
        rsWSDNHRPhysicalPortNumber      INTEGER,
        rsWSDNHRAdminStatus             FeatureStatus,
        rsWSDNHROperStatus              INTEGER,
        rsWSDNHRPathHealthCheckIP       IpAddress,
        rsWSDNHRCheckMethod             INTEGER,
        rsWSDNHRCheckInterval           INTEGER,
        rsWSDNRHCheckRetries            INTEGER,
        rsWSDNHRRowStatus               RowStatus,
        rsWSDNHRTag                     INTEGER,
		rsWSDNHRCckID                   INTEGER,
		rsWSDNHRFlags                   BitFlag
}

rsWSDNHRNHRIP OBJECT-TYPE
    SYNTAX IpAddress
    ACCESS  read-only
    STATUS  mandatory
    DESCRIPTION
      "NHR's IP address."
   ::= { rsWSDNHREntry 1}

rsWSDNHRDestinationMAC OBJECT-TYPE
    SYNTAX PhysAddress
    ACCESS  read-only
    STATUS  mandatory
    DESCRIPTION
      "The router's MAC address."
   ::= { rsWSDNHREntry 2}

rsWSDNHRSourceMAC OBJECT-TYPE
    SYNTAX PhysAddress
    ACCESS  read-only
    STATUS  mandatory
    DESCRIPTION
      "WDS port's MAC address."
   ::= { rsWSDNHREntry 3}

rsWSDNHRPhysicalPortNumber OBJECT-TYPE
    SYNTAX INTEGER
    ACCESS  read-only
    STATUS  mandatory
    DESCRIPTION
      "WSD port's physical number."
   ::= { rsWSDNHREntry 4}


rsWSDNHRAdminStatus OBJECT-TYPE
    SYNTAX  FeatureStatus
    ACCESS  read-write
    STATUS  mandatory
    DESCRIPTION
      "Forces the administrative state of the router."
    DEFVAL {enable}
   ::= { rsWSDNHREntry 5}

rsWSDNHROperStatus OBJECT-TYPE
    SYNTAX INTEGER {
	active(1),
	notInService(2) }
    ACCESS  read-only
    STATUS  mandatory
    DESCRIPTION
      "The availability status of the router."
   ::= { rsWSDNHREntry 6}

rsWSDNHRPathHealthCheckIP OBJECT-TYPE
    SYNTAX IpAddress
    ACCESS  read-write
    STATUS  mandatory
    DESCRIPTION
      "The IP address of a network entity to check through the router - in order to check it's functionality."
   ::= { rsWSDNHREntry 7}

rsWSDNHRCheckMethod OBJECT-TYPE
    SYNTAX INTEGER {
	ping(1),
	disable(2),
	cck(3) }
    ACCESS  read-write
    STATUS  mandatory
    DESCRIPTION
      "The test method."
    DEFVAL {2}
   ::= { rsWSDNHREntry 8}

rsWSDNHRCheckInterval OBJECT-TYPE
    SYNTAX INTEGER (1..3600)
    ACCESS  read-write
    STATUS  mandatory
    DESCRIPTION
      "The period of time between checks in seconds."
    DEFVAL {10}
   ::= { rsWSDNHREntry 9}

rsWSDNRHCheckRetries OBJECT-TYPE
    SYNTAX INTEGER (0..10)
    ACCESS  read-write
    STATUS  mandatory
    DESCRIPTION
      "The number of times a test will fail until Operational Status will be updated."
    DEFVAL {3}
   ::= { rsWSDNHREntry 10}

rsWSDNHRRowStatus OBJECT-TYPE
   SYNTAX RowStatus
   ACCESS read-write
   STATUS mandatory
   DESCRIPTION
      "Row status for the current row."
   ::=  { rsWSDNHREntry 11}

rsWSDNHRTag OBJECT-TYPE
    SYNTAX INTEGER
    ACCESS  read-write
    STATUS  mandatory
    DESCRIPTION
      "NHR's tag - matching the destination MAC."
   ::= { rsWSDNHREntry 12}

rsWSDNHRCckID OBJECT-TYPE
    SYNTAX  INTEGER
    ACCESS  read-write
    STATUS  mandatory
    DESCRIPTION
      "Connectivity check module identifier."
    ::=  {rsWSDNHREntry 13}

rsWSDNHRFlags OBJECT-TYPE
    SYNTAX    BitFlag
    ACCESS    read-only
    STATUS    mandatory
    DESCRIPTION
       "Flags for internal use."
    ::= { rsWSDNHREntry 14 }

rsNADNHRTable OBJECT-TYPE
   SYNTAX SEQUENCE OF RsNADNHREntry
   ACCESS not-accessible
   STATUS mandatory
   DESCRIPTION
          "In this table the WSD holds the Next Hop Routers to be used as Default Routers."
   ::= {rsNWSD 86}

rsNADNHREntry OBJECT-TYPE
    SYNTAX RsNADNHREntry
    ACCESS not-accessible
    STATUS mandatory
    DESCRIPTION
       " The row definition for NHR table."
   INDEX  {rsNADNHRNHRIPType,
		   rsNADNHRNHRIP}
   ::= {rsNADNHRTable 1}

RsNADNHREntry  ::= SEQUENCE {
		rsNADNHRNHRIPType               InetAddressType,
        rsNADNHRNHRIP                   InetAddress,
        rsNADNHRNHRMAC			        PhysAddress,
        rsNADNHRSourceMAC               PhysAddress,
        rsNADNHRInterfaceNumber         INTEGER,
        rsNADNHRAdminStatus             FeatureStatus,
        rsNADNHROperStatus              INTEGER,
		rsNADNHRPathHealthCheckIPType   InetAddressType,
        rsNADNHRPathHealthCheckIP       InetAddress,
        rsNADNHRCheckMethod             INTEGER,
        rsNADNHRCheckInterval           INTEGER,
        rsNADNHRCheckRetries            INTEGER,
		rsNADNHRCckID                   INTEGER,
		rsNADNHRFlags                   BitFlag,
		rsNADNHRTag                     INTEGER,
		rsNADNHRRowStatus               RowStatus
}


rsNADNHRNHRIPType OBJECT-TYPE
    SYNTAX InetAddressType
    ACCESS  read-only
    STATUS  mandatory
    DESCRIPTION
      "The IP address type of NHR's."
   ::= { rsNADNHREntry 1}

rsNADNHRNHRIP OBJECT-TYPE
    SYNTAX InetAddress
    ACCESS  read-only
    STATUS  mandatory
    DESCRIPTION
      "NHR's IP address."
   ::= { rsNADNHREntry 2}

rsNADNHRNHRMAC OBJECT-TYPE
    SYNTAX PhysAddress
    ACCESS  read-only
    STATUS  optional
    DESCRIPTION
      "The router's MAC address."
   ::= { rsNADNHREntry 3}

rsNADNHRSourceMAC OBJECT-TYPE
    SYNTAX PhysAddress
    ACCESS  read-only
    STATUS  optional
    DESCRIPTION
      "AD port's MAC address."
   ::= { rsNADNHREntry 4}

rsNADNHRInterfaceNumber OBJECT-TYPE
    SYNTAX INTEGER
    ACCESS  read-write
    STATUS  optional
    DESCRIPTION
      "AD Interface number."
   ::= { rsNADNHREntry 5}


rsNADNHRAdminStatus OBJECT-TYPE
    SYNTAX  FeatureStatus
    ACCESS  read-write
    STATUS  optional
    DESCRIPTION
      "Forces the administrative state of the router."
    DEFVAL {enable}
   ::= { rsNADNHREntry 6}

rsNADNHROperStatus OBJECT-TYPE
    SYNTAX INTEGER {
	active(1),
	notInService(2) }
    ACCESS  read-only
    STATUS  optional
    DESCRIPTION
      "The availability status of the router."
   ::= { rsNADNHREntry 7}

rsNADNHRPathHealthCheckIPType OBJECT-TYPE
    SYNTAX InetAddressType
    ACCESS  read-write
    STATUS  optional
    DESCRIPTION
      "The Type of IP address of a network entity to check through the router - in order to check it's functionality."
	DEFVAL { ipv4 }
   ::= { rsNADNHREntry 8}

rsNADNHRPathHealthCheckIP OBJECT-TYPE
    SYNTAX InetAddress
    ACCESS  read-write
    STATUS  optional
    DESCRIPTION
      "IP address type of a network entity to check through the router - in order to check it's functionality."
	DEFVAL{"0.0.0.0"}
   ::= { rsNADNHREntry 9}

rsNADNHRCheckMethod OBJECT-TYPE
    SYNTAX INTEGER {
	ping(1),
	disable(2),
	cck(3) }
    ACCESS  read-write
    STATUS  optional
    DESCRIPTION
      "The test method."
    DEFVAL {2}
   ::= { rsNADNHREntry 10}

rsNADNHRCheckInterval OBJECT-TYPE
    SYNTAX INTEGER (1..3600)
    ACCESS  read-write
    STATUS  optional
    DESCRIPTION
      "The period of time between checks in seconds."
    DEFVAL {10}
   ::= { rsNADNHREntry 11}

rsNADNHRCheckRetries OBJECT-TYPE
    SYNTAX INTEGER (0..10)
    ACCESS  read-write
    STATUS  optional
    DESCRIPTION
      "The number of times a test will fail until Operational Status will be updated."
    DEFVAL {3}
   ::= { rsNADNHREntry 12}

rsNADNHRCckID OBJECT-TYPE
    SYNTAX  INTEGER
    ACCESS  read-write
    STATUS  optional
    DESCRIPTION
      "Connectivity check module identifier."
    ::=  {rsNADNHREntry 13}

rsNADNHRFlags OBJECT-TYPE
    SYNTAX    BitFlag
    ACCESS    read-only
    STATUS    optional
    DESCRIPTION
       "Flags for internal use."
	DEFVAL{0}
    ::= { rsNADNHREntry 14 }

rsNADNHRTag OBJECT-TYPE
    SYNTAX INTEGER
    ACCESS  read-write
    STATUS  optional
    DESCRIPTION
      "NHR's tag - matching the destination MAC."
	DEFVAL{0}
   ::= { rsNADNHREntry 15}

rsNADNHRRowStatus OBJECT-TYPE
   SYNTAX RowStatus
   ACCESS read-write
   STATUS mandatory
   DESCRIPTION
      "Row status for the current row."
   ::=  { rsNADNHREntry 16}

rsWSDVIPNHRTable OBJECT-TYPE
   SYNTAX SEQUENCE OF RsWSDVIPNHREntry
   ACCESS not-accessible
   STATUS mandatory
   DESCRIPTION
          "The table that contains WSD associations of Virtual IPs to the Next Hop Routers,
          planned be used as Default and Backup Routers."
   ::= { rsNWSD 37 }

rsWSDVIPNHREntry OBJECT-TYPE
    SYNTAX RsWSDVIPNHREntry
    ACCESS not-accessible
    STATUS mandatory
    DESCRIPTION
       " The row definition for VIR-NHR table."
   INDEX  {rsWSDVIPNHRVIP}
   ::= {rsWSDVIPNHRTable 1}

RsWSDVIPNHREntry  ::= SEQUENCE {
  rsWSDVIPNHRVIP                  IpAddress,
  rsWSDVIPNHRNHRIP                IpAddress,
  rsWSDVIPNHRBackupNHRIP          IpAddress,
  rsWSDVIPNHRNoRouteAction        INTEGER,
  rsWSDVIPNHRRowStatus            RowStatus,
  rsWSDVIPNHRNHRWeight            INTEGER,
  rsWSDVIPNHRBackupWeight         INTEGER,
  rsWSDVIPNHRAdminLoadSharing     INTEGER,
  rsWSDVIPNHRFlags                BitFlag
}

rsWSDVIPNHRVIP OBJECT-TYPE
    SYNTAX IpAddress
    ACCESS read-only
    STATUS mandatory
    DESCRIPTION
      "The virtual IP of the farm\superfarm."
  ::= {rsWSDVIPNHREntry 1}


rsWSDVIPNHRNHRIP OBJECT-TYPE
    SYNTAX IpAddress
    ACCESS read-write
    STATUS mandatory
    DESCRIPTION
      "The IP of Next Hop Router."
  ::= {rsWSDVIPNHREntry 2}


rsWSDVIPNHRBackupNHRIP OBJECT-TYPE
    SYNTAX IpAddress
    ACCESS read-write
    STATUS mandatory
    DESCRIPTION
      "The IP of the Backup to Next Hop Router."
  ::= {rsWSDVIPNHREntry 3}

rsWSDVIPNHRNoRouteAction OBJECT-TYPE
    SYNTAX INTEGER {
    discard(1),
    useFFT(2) }
    ACCESS read-write
    STATUS mandatory
    DESCRIPTION
      "The action taken when NHR and Backup NHR are unavailable."
    DEFVAL  { 2 }
  ::= {rsWSDVIPNHREntry 4}

rsWSDVIPNHRRowStatus OBJECT-TYPE
   SYNTAX RowStatus
   ACCESS read-write
   STATUS mandatory
   DESCRIPTION
      "Row status for the current row."
   ::=  {rsWSDVIPNHREntry 5}

rsWSDVIPNHRNHRWeight OBJECT-TYPE
    SYNTAX INTEGER (1..100)
    ACCESS read-write
    STATUS mandatory
    DESCRIPTION
      "The NHR's weight."
    DEFVAL  { 1 }
  ::= {rsWSDVIPNHREntry 6}

rsWSDVIPNHRBackupWeight OBJECT-TYPE
    SYNTAX INTEGER (1..100)
    ACCESS read-write
    STATUS mandatory
    DESCRIPTION
      "The backup NHR's weight."
    DEFVAL  { 1 }
  ::= {rsWSDVIPNHREntry 7}

rsWSDVIPNHRAdminLoadSharing OBJECT-TYPE
    SYNTAX INTEGER {
    enable(1),
    disable(2),
    l4hashing(3) }
    ACCESS read-write
    STATUS mandatory
    DESCRIPTION
      "Enable/Disable NHR Load Sharing for this VIPNHR."
    DEFVAL  { 2 }
  ::= {rsWSDVIPNHREntry 8}

rsWSDVIPNHRFlags OBJECT-TYPE
    SYNTAX    BitFlag
    ACCESS    read-only
    STATUS    mandatory
    DESCRIPTION
       "Flags for internal use."
    ::= { rsWSDVIPNHREntry 9 }

rsNADVipNhrTable OBJECT-TYPE
   SYNTAX SEQUENCE OF RsNADVipNhrEntry
   ACCESS not-accessible
   STATUS mandatory
   DESCRIPTION
          "The table that contains WSD associations of Virtual IPs to the Next Hop Routers,
          planned be used as Default and Backup Routers."
   ::= { rsNWSD 87 }

rsNADVipNhrEntry OBJECT-TYPE
    SYNTAX RsNADVipNhrEntry
    ACCESS not-accessible
    STATUS mandatory
    DESCRIPTION
       " The row definition for VIR-NHR table."
   INDEX  {rsNADVipNhrVIPAddrType,
		   rsNADVipNhrVIP}
   ::= {rsNADVipNhrTable 1}

RsNADVipNhrEntry  ::= SEQUENCE {
  rsNADVipNhrVIPAddrType          InetAddressType,
  rsNADVipNhrVIP                  InetAddress,
  rsNADVipNhrNHRIPAddrType        InetAddressType,
  rsNADVipNhrNHRIP                InetAddress,
  rsNADVipNhrNHRWeight            INTEGER,
  rsNADVipNhrBackupNHRIPAddrType  InetAddressType,
  rsNADVipNhrBackupNHRIP          InetAddress,
  rsNADVipNhrBackupWeight         INTEGER,
  rsNADVipNhrNoRouteAction        INTEGER,
  rsNADVipNhrAdminLoadSharing     INTEGER,
  rsNADVipNhrFlags                BitFlag,
  rsNADVipNhrRowStatus            RowStatus
}

rsNADVipNhrVIPAddrType OBJECT-TYPE
    SYNTAX InetAddressType
    ACCESS read-only
    STATUS mandatory
    DESCRIPTION
      "The type of virtual IP of the farm\superfarm."
  ::= {rsNADVipNhrEntry 1}

rsNADVipNhrVIP OBJECT-TYPE
    SYNTAX InetAddress
    ACCESS read-only
    STATUS mandatory
    DESCRIPTION
      "The virtual IP of the farm\superfarm."
  ::= {rsNADVipNhrEntry 2}

rsNADVipNhrNHRIPAddrType OBJECT-TYPE
    SYNTAX InetAddressType
    ACCESS read-write
    STATUS mandatory
    DESCRIPTION
      "The type of IP of Next Hop Router."
  ::= {rsNADVipNhrEntry 3}

rsNADVipNhrNHRIP OBJECT-TYPE
    SYNTAX InetAddress
    ACCESS read-write
    STATUS mandatory
    DESCRIPTION
      "The IP of Next Hop Router."
  ::= {rsNADVipNhrEntry 4}

rsNADVipNhrNHRWeight OBJECT-TYPE
    SYNTAX INTEGER (1..100)
    ACCESS read-write
    STATUS optional
    DESCRIPTION
      "The NHR's weight."
    DEFVAL  { 1 }
  ::= {rsNADVipNhrEntry 5}

rsNADVipNhrBackupNHRIPAddrType OBJECT-TYPE
    SYNTAX InetAddressType
    ACCESS read-write
    STATUS optional
    DESCRIPTION
      "The type of IP of the Backup to Next Hop Router."
	DEFVAL { ipv4 }
  ::= {rsNADVipNhrEntry 6}

rsNADVipNhrBackupNHRIP OBJECT-TYPE
    SYNTAX InetAddress
    ACCESS read-write
    STATUS optional
    DESCRIPTION
      "The IP of the Backup to Next Hop Router."
	DEFVAL{"0.0.0.0"}
  ::= {rsNADVipNhrEntry 7}

rsNADVipNhrBackupWeight OBJECT-TYPE
    SYNTAX INTEGER (1..100)
    ACCESS read-write
    STATUS optional
    DESCRIPTION
      "The backup NHR's weight."
    DEFVAL  { 1 }
  ::= {rsNADVipNhrEntry 8}

rsNADVipNhrNoRouteAction OBJECT-TYPE
    SYNTAX INTEGER {
    discard(1),
    useFFT(2) }
    ACCESS read-write
    STATUS optional
    DESCRIPTION
      "The action taken when NHR and Backup NHR are unavailable."
    DEFVAL  { 2 }
  ::= {rsNADVipNhrEntry 9}

rsNADVipNhrAdminLoadSharing OBJECT-TYPE
    SYNTAX INTEGER {
    enable(1),
    disable(2),
    l4hashing(3) }
    ACCESS read-write
    STATUS optional
    DESCRIPTION
      "Enable/Disable NHR Load Sharing for this VIPNHR."
    DEFVAL  { 2 }
  ::= {rsNADVipNhrEntry 10}

rsNADVipNhrFlags OBJECT-TYPE
    SYNTAX    BitFlag
    ACCESS    read-only
    STATUS    optional
    DESCRIPTION
       "Flags for internal use."
    DEFVAL{0}
    ::= { rsNADVipNhrEntry 11 }

rsNADVipNhrRowStatus OBJECT-TYPE
   SYNTAX RowStatus
   ACCESS read-write
   STATUS mandatory
   DESCRIPTION
      "Row status for the current row."
   ::=  {rsNADVipNhrEntry 12 }



rsWSDTokenTable OBJECT-TYPE
   SYNTAX SEQUENCE OF RsWSDTokenTableEntry
   ACCESS not-accessible
   STATUS mandatory
   DESCRIPTION
       "A table for managing HTTP token information."
   ::= {rsNWSD 38}

rsWSDTokenTableEntry OBJECT-TYPE
   SYNTAX RsWSDTokenTableEntry
   ACCESS not-accessible
   STATUS mandatory
   DESCRIPTION
       " The row definition for this table."
   INDEX  { rsWSDToken }
   ::= {rsWSDTokenTable 1}

RsWSDTokenTableEntry ::= SEQUENCE {
  rsWSDToken         DisplayString,
  rsWSDTokenFarmMap  IpAddress,
  rsWSDTokenFarm     IpAddress,
  rsWSDTokenDefault  INTEGER,
  rsWSDTokenStatus   RowStatus
}

rsWSDToken OBJECT-TYPE
    SYNTAX DisplayString (SIZE(1..63))
    ACCESS  read-write
    STATUS  mandatory
    DESCRIPTION
      "The token value that identifies the farm."
    ::= {rsWSDTokenTableEntry 1}

rsWSDTokenFarmMap OBJECT-TYPE
  SYNTAX IpAddress
  ACCESS read-write
  STATUS mandatory
  DESCRIPTION
     "IP address of the superfarm in which the token farm is defined."
  ::=  {rsWSDTokenTableEntry 2}

rsWSDTokenFarm OBJECT-TYPE
  SYNTAX IpAddress
  ACCESS read-write
  STATUS mandatory
  DESCRIPTION
     "IP address of the farm for which the token is defined."
  ::=  {rsWSDTokenTableEntry 3}

rsWSDTokenDefault OBJECT-TYPE
  SYNTAX INTEGER {
    notDefault(1),
    noToken(2),
    noHeaderField(3),
    alwaysDefault(4)
  }
  ACCESS read-write
  STATUS mandatory
  DESCRIPTION
     "Indication whether this farm is the default one. noToken indicates that the farm
      should be used as default when no matching token was found. noHeaderField indicates
      that the farm should be used when no matching header field was found, and
      alwaysDefault indicates that this farm should be used in either case."
  ::=  {rsWSDTokenTableEntry 4}

rsWSDTokenStatus OBJECT-TYPE
  SYNTAX RowStatus
  ACCESS read-write
  STATUS mandatory
  DESCRIPTION
    "Row status for the token entry."
  ::=  {rsWSDTokenTableEntry 5}


rsWSDVirtualDNSTable OBJECT-TYPE
   SYNTAX SEQUENCE OF RsWSDVirtualDNSTableEntry
   ACCESS not-accessible
   STATUS mandatory
   DESCRIPTION
       "A table for managing virtual DNS addresses."
   ::= {rsNWSD 39}

rsWSDVirtualDNSTableEntry OBJECT-TYPE
   SYNTAX RsWSDVirtualDNSTableEntry
   ACCESS not-accessible
   STATUS mandatory
   DESCRIPTION
       " The row definition for this table."
   INDEX  { rsWSDVirtualDNSAddress }
   ::= {rsWSDVirtualDNSTable 1}

RsWSDVirtualDNSTableEntry ::= SEQUENCE {
  rsWSDVirtualDNSAddress    IpAddress,
  rsWSDVirtualDNSRedunType  INTEGER,
  rsWSDVirtualDNSStatus     RowStatus,
  rsWSDVirtualDNSSegmentName DisplayString
}

rsWSDVirtualDNSAddress OBJECT-TYPE
  SYNTAX IpAddress
  ACCESS read-only
  STATUS mandatory
  DESCRIPTION
     "The virtual DNS address."
  ::=  {rsWSDVirtualDNSTableEntry 1}

rsWSDVirtualDNSRedunType OBJECT-TYPE
  SYNTAX INTEGER {
    active(1),
    backup(2)
  }
  ACCESS read-write
  STATUS mandatory
  DESCRIPTION
     "A virtual DNS address can be either active or backup. Backup addresses are the active addresses
      on a backed-up unit."
-- DEFVAL { active }
  ::=  {rsWSDVirtualDNSTableEntry 2}

rsWSDVirtualDNSStatus OBJECT-TYPE
  SYNTAX RowStatus
  ACCESS read-write
  STATUS mandatory
  DESCRIPTION
    "Row status for the virtual dns entry."
  ::=  {rsWSDVirtualDNSTableEntry 3}

rsWSDVirtualDNSSegmentName OBJECT-TYPE
  SYNTAX DisplayString (SIZE(0..20))
  ACCESS read-write
  STATUS mandatory
   DESCRIPTION
       "Segment name in virtual DNS."
  ::= {rsWSDVirtualDNSTableEntry 4}

rsWSDClientNAT  OBJECT IDENTIFIER ::= { rsNWSD 40 }

rsWSDClientNATRangeTable OBJECT-TYPE
   SYNTAX SEQUENCE OF RsWSDClientNATRangeIPEntry
   ACCESS not-accessible
   STATUS mandatory
   DESCRIPTION
          "In this table the WSD saves the client's IP ranges "
   ::= {rsWSDClientNAT 1}


rsWSDClientNATRangeIPEntry OBJECT-TYPE
    SYNTAX RsWSDClientNATRangeIPEntry
    ACCESS not-accessible
    STATUS  mandatory
    DESCRIPTION
       " The row definition for this table."
   INDEX  { rsWSDClientNATRangeIPFrom }
   ::= {rsWSDClientNATRangeTable 1}

RsWSDClientNATRangeIPEntry  ::= SEQUENCE {
  rsWSDClientNATRangeIPFrom             IpAddress,
  rsWSDClientNATRangeIPTo                 IpAddress,
  rsWSDClientNATRangeIPStatus            RowStatus
}

rsWSDClientNATRangeIPFrom OBJECT-TYPE
    SYNTAX IpAddress
    ACCESS  read-only
    STATUS  mandatory
    DESCRIPTION
      "The IP Address of the low boundary of the interval."
    ::= {rsWSDClientNATRangeIPEntry 1}

rsWSDClientNATRangeIPTo OBJECT-TYPE
    SYNTAX IpAddress
    ACCESS  read-write
    STATUS  mandatory
    DESCRIPTION
      "The IP Address of the high boundary of the interval."
    ::= {rsWSDClientNATRangeIPEntry 2}

rsWSDClientNATRangeIPStatus OBJECT-TYPE
   SYNTAX  RowStatus
   ACCESS  read-write
   STATUS  mandatory
   DESCRIPTION
       "The  status of this entry."
   ::= {rsWSDClientNATRangeIPEntry 3}

rsNADClientNATRangeTable OBJECT-TYPE
   SYNTAX SEQUENCE OF RsNADClientNATRangeIPEntry
   ACCESS not-accessible
   STATUS mandatory
   DESCRIPTION
          "In this table the WSD saves the client's IP ranges "
   ::= {rsWSDClientNAT 6}


rsNADClientNATRangeIPEntry OBJECT-TYPE
    SYNTAX RsNADClientNATRangeIPEntry
    ACCESS not-accessible
    STATUS  mandatory
    DESCRIPTION
       " The row definition for this table."
   INDEX  { rsNADClientNATRangeIPFromAddrType,
			rsNADClientNATRangeIPFrom }
   ::= {rsNADClientNATRangeTable 1}

RsNADClientNATRangeIPEntry  ::= SEQUENCE {
  rsNADClientNATRangeIPFromAddrType		InetAddressType,
  rsNADClientNATRangeIPFrom             InetAddress,
  rsNADClientNATRangeIPToAddrType		InetAddressType,
  rsNADClientNATRangeIPTo               InetAddress,
  rsNADClientNATRangeIPStatus           RowStatus
}

rsNADClientNATRangeIPFromAddrType OBJECT-TYPE
    SYNTAX InetAddressType
    ACCESS  read-only
    STATUS  mandatory
    DESCRIPTION
      "The Type of IP Address of the low boundary of the interval."
    ::= {rsNADClientNATRangeIPEntry 1}

rsNADClientNATRangeIPFrom OBJECT-TYPE
    SYNTAX InetAddress
    ACCESS  read-only
    STATUS  mandatory
    DESCRIPTION
      "The IP Address of the low boundary of the interval."
    ::= {rsNADClientNATRangeIPEntry 2}

rsNADClientNATRangeIPToAddrType OBJECT-TYPE
    SYNTAX InetAddressType
    ACCESS  read-write
    STATUS  mandatory
    DESCRIPTION
      "The Type of IP Address of the high boundary of the interval."
    ::= {rsNADClientNATRangeIPEntry 3}

rsNADClientNATRangeIPTo OBJECT-TYPE
    SYNTAX InetAddress
    ACCESS  read-write
    STATUS  mandatory
    DESCRIPTION
      "The IP Address of the high boundary of the interval."
    ::= {rsNADClientNATRangeIPEntry 4}

rsNADClientNATRangeIPStatus OBJECT-TYPE
   SYNTAX  RowStatus
   ACCESS  read-write
   STATUS  mandatory
   DESCRIPTION
       "The  status of this entry."
   ::= {rsNADClientNATRangeIPEntry 5}

rsWSDNATRangeTable OBJECT-TYPE
   SYNTAX SEQUENCE OF RsWSDNATRangeIPEntry
   ACCESS not-accessible
   STATUS mandatory
   DESCRIPTION
          "In this table the WSD saves the NAT's IP ranges "
   ::= {rsWSDClientNAT 2}

rsWSDNATRangeIPEntry OBJECT-TYPE
    SYNTAX RsWSDNATRangeIPEntry
    ACCESS not-accessible
    STATUS  mandatory
    DESCRIPTION
       " The row definition for this table."
   INDEX  { rsWSDNATRangeIPFrom }
   ::= {rsWSDNATRangeTable 1}

RsWSDNATRangeIPEntry ::= SEQUENCE {
  rsWSDNATRangeIPFrom             IpAddress,
  rsWSDNATRangeIPTo               IpAddress,
  rsWSDNATRangeStatus             RowStatus
}

rsWSDNATRangeIPFrom OBJECT-TYPE
    SYNTAX IpAddress
    ACCESS  read-only
    STATUS  mandatory
    DESCRIPTION
      "The IP Address of the low boundary of the interval."
    ::= {rsWSDNATRangeIPEntry 1}

rsWSDNATRangeIPTo OBJECT-TYPE
    SYNTAX IpAddress
    ACCESS  read-write
    STATUS  mandatory
    DESCRIPTION
      "The IP Address of the high boundary of the interval."
    ::= {rsWSDNATRangeIPEntry 2}

rsWSDNATRangeStatus OBJECT-TYPE
 SYNTAX  RowStatus
   ACCESS  read-write
   STATUS  mandatory
   DESCRIPTION
       "The  status of this entry."
  ::= {rsWSDNATRangeIPEntry 3}

rsNADNATRangeTable OBJECT-TYPE
   SYNTAX SEQUENCE OF RsNADNATRangeIPEntry
   ACCESS not-accessible
   STATUS mandatory
   DESCRIPTION
          "In this table the WSD saves the NAT's IP ranges "
   ::= {rsWSDClientNAT 7}

rsNADNATRangeIPEntry OBJECT-TYPE
    SYNTAX RsNADNATRangeIPEntry
    ACCESS not-accessible
    STATUS  mandatory
    DESCRIPTION
       " The row definition for this table."
   INDEX  { rsNADNATRangeIPFromAddrType,
			rsNADNATRangeIPFrom }
   ::= {rsNADNATRangeTable 1}

RsNADNATRangeIPEntry ::= SEQUENCE {
  rsNADNATRangeIPFromAddrType     InetAddressType,
  rsNADNATRangeIPFrom             InetAddress,
  rsNADNATRangeIPToAddrType       InetAddressType,
  rsNADNATRangeIPTo               InetAddress,
  rsNADNATRangeStatus             RowStatus
}

rsNADNATRangeIPFromAddrType OBJECT-TYPE
    SYNTAX InetAddressType
    ACCESS  read-only
    STATUS  mandatory
    DESCRIPTION
      "The Type of IP Address of the low boundary of the interval."
    ::= {rsNADNATRangeIPEntry 1}

rsNADNATRangeIPFrom OBJECT-TYPE
    SYNTAX InetAddress
    ACCESS  read-only
    STATUS  mandatory
    DESCRIPTION
      "The IP Address of the low boundary of the interval."
    ::= {rsNADNATRangeIPEntry 2}

rsNADNATRangeIPToAddrType OBJECT-TYPE
    SYNTAX InetAddressType
    ACCESS  read-write
    STATUS  mandatory
    DESCRIPTION
      "The Type of IP Address of the high boundary of the interval."
    ::= {rsNADNATRangeIPEntry 3}

rsNADNATRangeIPTo OBJECT-TYPE
    SYNTAX InetAddress
    ACCESS  read-write
    STATUS  mandatory
    DESCRIPTION
      "The IP Address of the high boundary of the interval."
    ::= {rsNADNATRangeIPEntry 4}

rsNADNATRangeStatus OBJECT-TYPE
 SYNTAX  RowStatus
   ACCESS  read-write
   STATUS  mandatory
   DESCRIPTION
       "The  status of this entry."
  ::= {rsNADNATRangeIPEntry 5}

rsWSDClientNATStatus  OBJECT-TYPE
   SYNTAX FeatureStatus
   ACCESS  read-write
   STATUS  mandatory
   DESCRIPTION
       "Enable or disable the NAT client feature in WSD"
   DEFVAL { disable }
   ::=  {rsWSDClientNAT 3 }

rsWSDNATPortInUseTable OBJECT-TYPE
   SYNTAX SEQUENCE OF RsWSDClientNATNumOfPortInUseEntry
   ACCESS not-accessible
   STATUS mandatory
   DESCRIPTION
          "Client NAT port in use statistics"
  ::= {rsWSDClientNAT 4}


rsWSDClientNATNumOfPortInUseEntry OBJECT-TYPE
    SYNTAX RsWSDClientNATNumOfPortInUseEntry
    ACCESS not-accessible
    STATUS  mandatory
    DESCRIPTION
       " The row definition for this table."
   INDEX  { rsWSDClientNATAddress }
   ::= {rsWSDNATPortInUseTable 1}

RsWSDClientNATNumOfPortInUseEntry  ::= SEQUENCE {
  rsWSDClientNATAddress       IpAddress,
  rsWSDClientNATPortInUse     INTEGER,
  rsWSDClientNATAgvPortInUse     INTEGER
}

rsWSDClientNATAddress OBJECT-TYPE
    SYNTAX IpAddress
    ACCESS  read-only
    STATUS  mandatory
    DESCRIPTION
      "The NAT IP Address"
    ::= {rsWSDClientNATNumOfPortInUseEntry 1}

rsWSDClientNATPortInUse OBJECT-TYPE
    SYNTAX INTEGER
    ACCESS  read-only
    STATUS  mandatory
    DESCRIPTION
      "The number of ports in use for this address"
    ::= {rsWSDClientNATNumOfPortInUseEntry 2}

rsWSDClientNATAgvPortInUse OBJECT-TYPE
    SYNTAX INTEGER
    ACCESS  read-only
    STATUS  mandatory
    DESCRIPTION
      "The number of ports in use for this address"
    ::= {rsWSDClientNATNumOfPortInUseEntry 3}

rsNADNATPortInUseTable OBJECT-TYPE
   SYNTAX SEQUENCE OF RsNADClientNATNumOfPortInUseEntry
   ACCESS not-accessible
   STATUS mandatory
   DESCRIPTION
          "Client NAT port in use statistics"
  ::= {rsWSDClientNAT 5}


rsNADClientNATNumOfPortInUseEntry OBJECT-TYPE
    SYNTAX RsNADClientNATNumOfPortInUseEntry
    ACCESS not-accessible
    STATUS  mandatory
    DESCRIPTION
       " The row definition for this table."
   INDEX  { rsNADClientNATAddressType,
			rsNADClientNATAddress }
   ::= {rsNADNATPortInUseTable 1}

RsNADClientNATNumOfPortInUseEntry  ::= SEQUENCE {
  rsNADClientNATAddressType   InetAddressType,
  rsNADClientNATAddress       InetAddress,
  rsNADClientNATPortInUse     INTEGER,
  rsNADClientNATAvgPortInUse  INTEGER
}

rsNADClientNATAddressType OBJECT-TYPE
    SYNTAX InetAddressType
    ACCESS  read-only
    STATUS  mandatory
    DESCRIPTION
      "The IP address type of NAT IP Address"
    ::= {rsNADClientNATNumOfPortInUseEntry 1}

rsNADClientNATAddress OBJECT-TYPE
    SYNTAX InetAddress
    ACCESS  read-only
    STATUS  mandatory
    DESCRIPTION
      "The NAT IP Address"
    ::= {rsNADClientNATNumOfPortInUseEntry 2}

rsNADClientNATPortInUse OBJECT-TYPE
    SYNTAX INTEGER
    ACCESS  read-only
    STATUS  mandatory
    DESCRIPTION
      "The number of ports in use for this address"
    ::= {rsNADClientNATNumOfPortInUseEntry 3}

rsNADClientNATAvgPortInUse OBJECT-TYPE
    SYNTAX INTEGER
    ACCESS  read-only
    STATUS  mandatory
    DESCRIPTION
      "The average number of port in use for the NAT address"
    ::= {rsNADClientNATNumOfPortInUseEntry 4}

rsWSDDynSrvrNAT    OBJECT IDENTIFIER ::= { rsNWSD 45}

rsWSDDynSrvrNATStatus  OBJECT-TYPE
   SYNTAX FeatureStatus
   ACCESS  read-write
   STATUS  mandatory
   DESCRIPTION
       "Enable or disable the Dynamic Server NAT feature in WSD"
   DEFVAL { disable }
   ::=  { rsWSDDynSrvrNAT   1 }

rsWSDDynSrvrNATRangeTable OBJECT-TYPE
   SYNTAX SEQUENCE OF RsWSDDynSrvrNATRangeIPEntry
   ACCESS not-accessible
   STATUS mandatory
   DESCRIPTION
          "In this table the WSD saves the NAT's IP ranges "
   ::= { rsWSDDynSrvrNAT   2}

rsWSDDynSrvrNATRangeIPEntry OBJECT-TYPE
    SYNTAX RsWSDDynSrvrNATRangeIPEntry
    ACCESS not-accessible
    STATUS  mandatory
    DESCRIPTION
       " The row definition for this table."
   INDEX  { rsWSDDynSrvrNATRangeIPFrom }
   ::= {rsWSDDynSrvrNATRangeTable 1}

RsWSDDynSrvrNATRangeIPEntry ::= SEQUENCE {
  rsWSDDynSrvrNATRangeIPFrom             IpAddress,
  rsWSDDynSrvrNATRangeIPTo               IpAddress,
  rsWSDDynSrvrNATRangeRedundancyMode        INTEGER,
  rsWSDDynSrvrNATRangeStatus             RowStatus,
  rsWSDDynSrvrNATSegmentName             DisplayString,
  rsWSDDynSrvrNATRangeNATMode			 INTEGER
}

rsWSDDynSrvrNATRangeIPFrom OBJECT-TYPE
    SYNTAX IpAddress
    ACCESS  read-only
    STATUS  mandatory
    DESCRIPTION
      "The IP Address of the low boundary of the interval."
    ::= {rsWSDDynSrvrNATRangeIPEntry 1}

rsWSDDynSrvrNATRangeIPTo OBJECT-TYPE
    SYNTAX IpAddress
    ACCESS  read-write
    STATUS  mandatory
    DESCRIPTION
      "The IP Address of the high boundary of the interval."
    ::= {rsWSDDynSrvrNATRangeIPEntry 2}

rsWSDDynSrvrNATRangeRedundancyMode OBJECT-TYPE
    SYNTAX INTEGER {
           active(1),
           backup(2)
    }
    ACCESS  read-write
    STATUS  mandatory
    DESCRIPTION
        "This variable indicate the type of this WSD "
 DEFVAL { 1 }
    ::= { rsWSDDynSrvrNATRangeIPEntry 3}

rsWSDDynSrvrNATRangeStatus OBJECT-TYPE
 SYNTAX  RowStatus
   ACCESS  read-write
   STATUS  mandatory
   DESCRIPTION
       "The  status of this entry."
  ::= {rsWSDDynSrvrNATRangeIPEntry 4}

rsWSDDynSrvrNATSegmentName OBJECT-TYPE
  SYNTAX DisplayString (SIZE(0..20))
  ACCESS read-write
  STATUS mandatory
   DESCRIPTION
       "The  status of this entry."
  ::= {rsWSDDynSrvrNATRangeIPEntry 5}

rsWSDDynSrvrNATRangeNATMode OBJECT-TYPE
  SYNTAX INTEGER {
		 dynamic(1),
		 static(2),   -- SCTP static
		 vipstatic(3) -- Server NAT VIP selection per server
  }
  ACCESS  read-write
  STATUS  mandatory
  DESCRIPTION
	  "This variable indicates the type of NAT "
DEFVAL { 1 }
  ::= { rsWSDDynSrvrNATRangeIPEntry 6}



rsNADDynSrvrNATRangeTable OBJECT-TYPE
   SYNTAX SEQUENCE OF RsNADDynSrvrNATRangeIPEntry
   ACCESS not-accessible
   STATUS mandatory
   DESCRIPTION
          "In this table the WSD saves the NAT's IP ranges "
   ::= { rsWSDDynSrvrNAT 7}

rsNADDynSrvrNATRangeIPEntry OBJECT-TYPE
    SYNTAX RsNADDynSrvrNATRangeIPEntry
    ACCESS not-accessible
    STATUS  mandatory
    DESCRIPTION
       " The row definition for this table."
   INDEX  { rsNADDynSrvrNATRangeIPFromAddrType,
			rsNADDynSrvrNATRangeIPFrom }
   ::= {rsNADDynSrvrNATRangeTable 1}

RsNADDynSrvrNATRangeIPEntry ::= SEQUENCE {
  rsNADDynSrvrNATRangeIPFromAddrType     InetAddressType,
  rsNADDynSrvrNATRangeIPFrom			 InetAddress,
  rsNADDynSrvrNATRangeIPToAddrType       InetAddressType,
  rsNADDynSrvrNATRangeIPTo               InetAddress,
  rsNADDynSrvrNATRangeRedundancyMode     INTEGER,
  rsNADDynSrvrNATSegmentName             DisplayString,
  rsNADDynSrvrNATRangeNATMode		 INTEGER,
  rsNADDynSrvrNATRangeStatus             RowStatus
}

rsNADDynSrvrNATRangeIPFromAddrType OBJECT-TYPE
    SYNTAX InetAddressType
    ACCESS  read-only
    STATUS  mandatory
    DESCRIPTION
      "The Type of IP Address of the low boundary of the interval."
    ::= {rsNADDynSrvrNATRangeIPEntry 1}

rsNADDynSrvrNATRangeIPFrom OBJECT-TYPE
    SYNTAX InetAddress
    ACCESS  read-only
    STATUS  mandatory
    DESCRIPTION
      "The IP Address of the low boundary of the interval."
    ::= {rsNADDynSrvrNATRangeIPEntry 2}

rsNADDynSrvrNATRangeIPToAddrType OBJECT-TYPE
    SYNTAX InetAddressType
    ACCESS  read-write
    STATUS  mandatory
    DESCRIPTION
      "The IP Address of the high boundary of the interval."
    ::= {rsNADDynSrvrNATRangeIPEntry 3}

rsNADDynSrvrNATRangeIPTo OBJECT-TYPE
    SYNTAX InetAddress
    ACCESS  read-write
    STATUS  mandatory
    DESCRIPTION
      "The IP Address of the high boundary of the interval."
    ::= {rsNADDynSrvrNATRangeIPEntry 4}

rsNADDynSrvrNATRangeRedundancyMode OBJECT-TYPE
    SYNTAX INTEGER {
           active(1),
           backup(2)
    }
    ACCESS  read-write
    STATUS  optional
    DESCRIPTION
        "This variable indicate the type of this WSD "
 DEFVAL { 1 }
    ::= { rsNADDynSrvrNATRangeIPEntry 5}

rsNADDynSrvrNATSegmentName OBJECT-TYPE
  SYNTAX DisplayString (SIZE(0..20))
  ACCESS read-write
  STATUS optional
   DESCRIPTION
       "The  status of this entry."
  ::= {rsNADDynSrvrNATRangeIPEntry 6}

rsNADDynSrvrNATRangeNATMode OBJECT-TYPE
  SYNTAX INTEGER {
		 dynamic(1),
		 static(2),   -- SCTP static
		 vipstatic(3) -- Server NAT VIP selection per server
  }
  ACCESS  read-write
  STATUS  mandatory
  DESCRIPTION
	  "This variable indicate the type of NAT "
DEFVAL { 1 }
  ::= { rsNADDynSrvrNATRangeIPEntry 7}

rsNADDynSrvrNATRangeStatus OBJECT-TYPE
 SYNTAX  RowStatus
   ACCESS  read-write
   STATUS  mandatory
   DESCRIPTION
       "The  status of this entry."
  ::= {rsNADDynSrvrNATRangeIPEntry 8}

rsWSDDynSrvrRangeTable OBJECT-TYPE
   SYNTAX SEQUENCE OF RsWSDDynSrvrRangeIPEntry
   ACCESS not-accessible
   STATUS mandatory
   DESCRIPTION
          "In this table the WSD saves the NAT's IP ranges "
   ::= { rsWSDDynSrvrNAT   3}

rsWSDDynSrvrRangeIPEntry OBJECT-TYPE
    SYNTAX RsWSDDynSrvrRangeIPEntry
    ACCESS not-accessible
    STATUS  mandatory
    DESCRIPTION
       " The row definition for this table."
   INDEX  { rsWSDDynSrvrRangeIPFrom }
   ::= {rsWSDDynSrvrRangeTable 1}

RsWSDDynSrvrRangeIPEntry ::= SEQUENCE {
  rsWSDDynSrvrRangeIPFrom           IpAddress,
  rsWSDDynSrvrRangeIPTo               IpAddress,
  rsWSDDynSrvrAgingPeriod                INTEGER,
  rsWSDDynSrvrNATRange               IpAddress,
  rsWSDDynSrvrRangeStatus             RowStatus,
--  rsWSDDynSrvrRangeNatType          INTEGER
  rsWSDDynSrvrRangeNatRemoveEntryAtSessionEnd FeatureStatus
}


  rsWSDDynSrvrRangeIPFrom   OBJECT-TYPE
    SYNTAX IpAddress
    ACCESS  read-only
    STATUS  mandatory
    DESCRIPTION
      "The IP Address of the low boundary of the interval."
    ::= { rsWSDDynSrvrRangeIPEntry 1}

rsWSDDynSrvrRangeIPTo OBJECT-TYPE
    SYNTAX IpAddress
    ACCESS  read-write
    STATUS  mandatory
    DESCRIPTION
      "The IP Address of the high boundary of the interval."
    ::= { rsWSDDynSrvrRangeIPEntry 2}


rsWSDDynSrvrAgingPeriod OBJECT-TYPE
    SYNTAX INTEGER
    ACCESS  read-write
    STATUS  mandatory
    DESCRIPTION
        "The time in hours after which an old dynamic Server entry is invalid."
DEFVAL   { 60 }
    ::=  { rsWSDDynSrvrRangeIPEntry 3}

rsWSDDynSrvrNATRange OBJECT-TYPE
    SYNTAX IpAddress
    ACCESS  read-write
    STATUS  mandatory
    DESCRIPTION
        "The NAT rang that related with that Nated rang entry."
DEFVAL   { 0 }
    ::=  { rsWSDDynSrvrRangeIPEntry 4}


rsWSDDynSrvrRangeStatus OBJECT-TYPE
   SYNTAX  RowStatus
   ACCESS  read-write
   STATUS  mandatory
   DESCRIPTION
       "The  status of this entry."
   ::= { rsWSDDynSrvrRangeIPEntry 5}
--rsWSDDynSrvrRangeNatType OBJECT-TYPE
--    SYNTAX INTEGER {
--		dynamic(1),
--		static(2)
--	}
--    ACCESS  read-write
--    STATUS  mandatory
--    DESCRIPTION
--        "Deprecated - The NAT type, Dynamic or Static."
--DEFVAL   { dynamic }
--    ::=  { rsWSDDynSrvrRangeIPEntry 6}

rsWSDDynSrvrRangeNatRemoveEntryAtSessionEnd OBJECT-TYPE
    SYNTAX FeatureStatus
    ACCESS  read-write
    STATUS  mandatory
    DESCRIPTION
        "Whether the entries will be deleted when the session is over."
    DEFVAL   { disable }
    ::=  { rsWSDDynSrvrRangeIPEntry 7}


rsNADDynSrvrRangeTable OBJECT-TYPE
   SYNTAX SEQUENCE OF RsNADDynSrvrRangeIPEntry
   ACCESS not-accessible
   STATUS mandatory
   DESCRIPTION
          "In this table the WSD saves the NAT's IP ranges "
   ::= { rsWSDDynSrvrNAT   6}

rsNADDynSrvrRangeIPEntry OBJECT-TYPE
    SYNTAX RsNADDynSrvrRangeIPEntry
    ACCESS not-accessible
    STATUS  mandatory
    DESCRIPTION
       " The row definition for this table."
   INDEX  { rsNADDynSrvrRangeIPFromAddrType,
			rsNADDynSrvrRangeIPFrom }
   ::= {rsNADDynSrvrRangeTable 1}

RsNADDynSrvrRangeIPEntry ::= SEQUENCE {
  rsNADDynSrvrRangeIPFromAddrType             InetAddressType,
  rsNADDynSrvrRangeIPFrom                     InetAddress,
  rsNADDynSrvrRangeIPToAddrType   	          InetAddressType,
  rsNADDynSrvrRangeIPTo                       InetAddress,
  rsNADDynSrvrAgingPeriod                     INTEGER ,
  rsNADDynSrvrNATRangeAddrType   	          InetAddressType,
  rsNADDynSrvrNATRange                        InetAddress,
  rsNADDynSrvrRangeStatus                     RowStatus,
  rsNADDynSrvrRangeNatRemoveEntryAtSessionEnd FeatureStatus
}

rsNADDynSrvrRangeIPFromAddrType   OBJECT-TYPE
    SYNTAX InetAddressType
    ACCESS  read-only
    STATUS  mandatory
    DESCRIPTION
      "The Type of IP Address of the low boundary of the interval."
	DEFVAL{ipv4}
    ::= { rsNADDynSrvrRangeIPEntry 1}

rsNADDynSrvrRangeIPFrom   OBJECT-TYPE
    SYNTAX InetAddress
    ACCESS  read-only
    STATUS  mandatory
    DESCRIPTION
      "The IP Address of the low boundary of the interval."
	DEFVAL{"0.0.0.0"}
    ::= { rsNADDynSrvrRangeIPEntry 2}

rsNADDynSrvrRangeIPToAddrType OBJECT-TYPE
    SYNTAX InetAddressType
    ACCESS  read-write
    STATUS  mandatory
    DESCRIPTION
      "The Type of IP Address of the high boundary of the interval."
	DEFVAL { ipv4 }
    ::= { rsNADDynSrvrRangeIPEntry 3}

rsNADDynSrvrRangeIPTo OBJECT-TYPE
    SYNTAX InetAddress
    ACCESS  read-write
    STATUS  mandatory
    DESCRIPTION
      "The IP Address of the high boundary of the interval."
	DEFVAL{"0.0.0.0"}
    ::= { rsNADDynSrvrRangeIPEntry 4}


rsNADDynSrvrAgingPeriod OBJECT-TYPE
    SYNTAX INTEGER
    ACCESS  read-write
    STATUS  optional
    DESCRIPTION
        "The time in seconds after which an old dynamic Server entry is invalid."
	DEFVAL   { 60 }
    ::=  { rsNADDynSrvrRangeIPEntry 5}

rsNADDynSrvrNATRangeAddrType OBJECT-TYPE
    SYNTAX InetAddressType
    ACCESS  read-write
    STATUS  optional
    DESCRIPTION
        "The IP address type of NAT rang that related with that Nated rang entry."
	DEFVAL { ipv4 }
    ::=  { rsNADDynSrvrRangeIPEntry 6}

rsNADDynSrvrNATRange OBJECT-TYPE
    SYNTAX InetAddress
    ACCESS  read-write
    STATUS  optional
    DESCRIPTION
        "The NAT rang that related with that Nated rang entry."
	DEFVAL{"0.0.0.0"}
    ::=  { rsNADDynSrvrRangeIPEntry 7}


rsNADDynSrvrRangeStatus OBJECT-TYPE
   SYNTAX  RowStatus
   ACCESS  read-write
   STATUS  mandatory
   DESCRIPTION
       "The  status of this entry."
   ::= { rsNADDynSrvrRangeIPEntry 8}

rsNADDynSrvrRangeNatRemoveEntryAtSessionEnd OBJECT-TYPE
    SYNTAX FeatureStatus
    ACCESS  read-write
    STATUS  mandatory
    DESCRIPTION
        "Whether the entries will be deleted when the session is over."
    DEFVAL   { disable }
    ::=  { rsNADDynSrvrRangeIPEntry 9}

rsWSDOutboundNATPortInUseTable OBJECT-TYPE
   SYNTAX SEQUENCE OF RsWSDOutboundNATNumOfPortInUseEntry
   ACCESS not-accessible
   STATUS mandatory
   DESCRIPTION
          "Outbound NAT port in use statistics"
  ::= {rsWSDDynSrvrNAT 4}


rsWSDOutboundNATNumOfPortInUseEntry OBJECT-TYPE
    SYNTAX RsWSDOutboundNATNumOfPortInUseEntry
    ACCESS not-accessible
    STATUS  mandatory
    DESCRIPTION
       " The row definition for this table."
   INDEX  { rsWSDOutboundNATAddress }
   ::= {rsWSDOutboundNATPortInUseTable 1}

RsWSDOutboundNATNumOfPortInUseEntry  ::= SEQUENCE {
  rsWSDOutboundNATAddress       IpAddress,
  rsWSDOutboundNATPortInUse     INTEGER,
  rsWSDOutboundNATAgvPortInUse     INTEGER
}

rsWSDOutboundNATAddress OBJECT-TYPE
    SYNTAX IpAddress
    ACCESS  read-only
    STATUS  mandatory
    DESCRIPTION
      "The NAT IP Address"
    ::= {rsWSDOutboundNATNumOfPortInUseEntry 1}

rsWSDOutboundNATPortInUse OBJECT-TYPE
    SYNTAX INTEGER
    ACCESS  read-only
    STATUS  mandatory
    DESCRIPTION
      "The number of ports in use for this address"
    ::= {rsWSDOutboundNATNumOfPortInUseEntry 2}

rsWSDOutboundNATAgvPortInUse OBJECT-TYPE
    SYNTAX INTEGER
    ACCESS  read-only
    STATUS  mandatory
    DESCRIPTION
      "The number of ports in use for this address"
    ::= {rsWSDOutboundNATNumOfPortInUseEntry 3}

rsNADOutboundNATPortInUseTable OBJECT-TYPE
   SYNTAX SEQUENCE OF RsNADOutboundNATNumOfPortInUseEntry
   ACCESS not-accessible
   STATUS mandatory
   DESCRIPTION
          "Outbound NAT port in use statistics"
  ::= {rsWSDDynSrvrNAT 5}

rsNADOutboundNATNumOfPortInUseEntry OBJECT-TYPE
    SYNTAX RsNADOutboundNATNumOfPortInUseEntry
    ACCESS not-accessible
    STATUS  mandatory
    DESCRIPTION
       " The row definition for this table."
   INDEX  { rsNADOutboundNATAddressType,
			rsNADOutboundNATAddress }
   ::= {rsNADOutboundNATPortInUseTable 1}

RsNADOutboundNATNumOfPortInUseEntry  ::= SEQUENCE {
  rsNADOutboundNATAddressType   InetAddressType,
  rsNADOutboundNATAddress       InetAddress,
  rsNADOutboundNATPortInUse     INTEGER,
  rsNADOutboundNATAvgPortInUse  INTEGER
}

rsNADOutboundNATAddressType OBJECT-TYPE
    SYNTAX InetAddressType
    ACCESS  read-only
    STATUS  mandatory
    DESCRIPTION
      "TheType of  NAT IP Address"
    ::= {rsNADOutboundNATNumOfPortInUseEntry 1}

rsNADOutboundNATAddress OBJECT-TYPE
    SYNTAX InetAddress
    ACCESS  read-only
    STATUS  mandatory
    DESCRIPTION
      "The NAT IP Address"
    ::= {rsNADOutboundNATNumOfPortInUseEntry 2}

rsNADOutboundNATPortInUse OBJECT-TYPE
    SYNTAX INTEGER
    ACCESS  read-only
    STATUS  optional
    DESCRIPTION
      "The number of ports in use for this address"
    ::= {rsNADOutboundNATNumOfPortInUseEntry 3}

rsNADOutboundNATAvgPortInUse OBJECT-TYPE
    SYNTAX INTEGER
    ACCESS  read-only
    STATUS  optional
    DESCRIPTION
      "The number of ports in use for this address"
    ::= {rsNADOutboundNATNumOfPortInUseEntry 4}

rsWSDSessionChaining  OBJECT-TYPE
   SYNTAX INTEGER {
        enable(1),
        disable(2),
        enable-same-VIP(3)
   }
   ACCESS  read-write
   STATUS  mandatory
   DESCRIPTION
       "Enable or disable session chaining in delayed binding."
   DEFVAL { disable }
   ::=  {rsNWSD 41 }

rsWSDDynamicSidTable OBJECT-TYPE
   SYNTAX SEQUENCE OF RsWSDDynamicSidEntry
   ACCESS not-accessible
   STATUS mandatory
   DESCRIPTION
       "A table for managing dynamic session ID L7 information."
   ::= {rsNWSD 42}

rsWSDDynamicSidEntry OBJECT-TYPE
   SYNTAX RsWSDDynamicSidEntry
   ACCESS not-accessible
   STATUS mandatory
   DESCRIPTION
       " The row definition for this table."
   INDEX  { rsWSDDynamicSidFarm,
            rsWSDDynamicSidPort,
            rsWSDDynamicSidL4Protocol}
   ::= {rsWSDDynamicSidTable 1}

RsWSDDynamicSidEntry ::= SEQUENCE {
  rsWSDDynamicSidFarm            IpAddress,
  rsWSDDynamicSidPort            INTEGER,
  rsWSDDynamicSid                DisplayString,
  rsWSDDynamicSidMatch           INTEGER,
  rsWSDDynamicSidLookupMode      INTEGER,
  rsWSDDynamicSidIgnoreServer    INTEGER,
  rsWSDDynamicSidValMaxLen       INTEGER,
  rsWSDDynamicSidValOffset       INTEGER,
  rsWSDDynamicSidStopChar        DisplayString,
  rsWSDDynamicSidInactTimeout    INTEGER,
  rsWSDDynamicSidStatus          RowStatus,
  rsWSDDynamicSidLearnDirection  INTEGER,
  rsWSDDynamicSidPrsstL7Mode     INTEGER,
  rsWSDDynamicSidL4Protocol      INTEGER,
  rsWSDDynamicSidPatternOffset   INTEGER,
  rsWSDDynamicSidPatternMask     DisplayString,
  rsWSDDynamicSidOffsetFrom      INTEGER,
  rsWSDDynamicSidIgnoreSourceIp  FeatureStatus,
  rsWSDDynamicSidPersistencyMode INTEGER,
  rsWSDDynamicSidHeaderName      DisplayString,
  rsWSDDynamicSidArgs            DisplayString,
  rsWSDDynamicSidFlags           BitFlag,
  rsWSDDynamicSidPersistencyMethod INTEGER,
  rsWSDDynamicSidDataFormat      INTEGER,
  rsWSDDynamicSidForReply        DisplayString,
  rsWSDDynamicSidParameterMatch  INTEGER,
  rsWSDDynamicSidValueMatch      INTEGER
}

rsWSDDynamicSidFarm OBJECT-TYPE
  SYNTAX IpAddress
  ACCESS read-only
  STATUS mandatory
  DESCRIPTION
     "Virtual IP address for dynamic session ID search."
  ::=  {rsWSDDynamicSidEntry 1}

rsWSDDynamicSidPort OBJECT-TYPE
  SYNTAX INTEGER (0..65535)
  ACCESS read-only
  STATUS mandatory
  DESCRIPTION
     "TCP/UDP destination port for dynamic session ID search. 0 means that dynamic session ID parsing is performed
      on all destination ports."
  ::=  {rsWSDDynamicSidEntry 2}

rsWSDDynamicSid OBJECT-TYPE
  SYNTAX DisplayString (SIZE(0..63))
  ACCESS read-write
  STATUS mandatory
  DESCRIPTION
     "ID to look for during dynamic session ID search. Case sensitive. When rsWSDDynamicSidLookupMode is xmlTag this ID is searched in the request only."
 ::=  {rsWSDDynamicSidEntry 3}

rsWSDDynamicSidMatch OBJECT-TYPE
  SYNTAX INTEGER {
   exact(1),
   prefix(2)
  }
  ACCESS read-write
  STATUS mandatory
  DESCRIPTION
     "Defines whether the ID match should be exactly as specified or if it can be prefix (in cases were
      the application also changes the end of the ID)."
  DEFVAL { exact }
  ::=  {rsWSDDynamicSidEntry 4}

rsWSDDynamicSidLookupMode OBJECT-TYPE
  SYNTAX INTEGER {
   indicator (1),
   offset    (2),
   header    (3),
   regexp    (4),
   httpCookie(5),
   requestUrl(6),
   xmlTag    (7),
   radiusAttr(8)
-- diameter  (9)
  }
  ACCESS read-write
  STATUS mandatory
  DESCRIPTION
     "Defines scope for the persistency identifier search.
      indicator (1),     search for a token=value pair that may appear anywhere within the the HTTP header.
      offset    (2),     indicates that the entry is of 'Pattern Match' type.
      header    (3),     search for HTTP header name given by rsADDynamicSidHeaderName. Header parameter may be indicated by rsADDynamicSid variable.
      regexp    (4),     search regular expression in all the HTTP header.
      httpCookie(5),     search for a token=value pair within the Cookie header. token is given by the rsADDynamicSid field value.
      requestUrl(6),     search for a token=value pair within the HTTP request line. token is given by the rsADDynamicSid field value.
      xmlTag    (7)      maintain persistency based on a SOAP tag and/or SOAP Header Field. Available only with ADXL and TSL license."
--    diameter  (9),	 perform persistency on diameter."
  DEFVAL { httpCookie }
  ::=  {rsWSDDynamicSidEntry 5}

rsWSDDynamicSidIgnoreServer OBJECT-TYPE
  SYNTAX INTEGER {
   enable(1),
   disable(2)
  }
  ACCESS read-write
  STATUS mandatory
  DESCRIPTION
     "When enabled, the WSD will not look for a new session ID in server responses if the client GET already had a
      session ID in it. This is less time consuming, but may not work correctly with all applications."
  DEFVAL { disable }
  ::=  {rsWSDDynamicSidEntry 6}

rsWSDDynamicSidValMaxLen OBJECT-TYPE
  SYNTAX INTEGER (1..256)
  ACCESS read-write
  STATUS mandatory
  DESCRIPTION
     "Maximum length of dynamic session ID."
  DEFVAL { 256 }
  ::=  {rsWSDDynamicSidEntry 7}

rsWSDDynamicSidValOffset OBJECT-TYPE
  SYNTAX INTEGER (0..1500)
  ACCESS read-write
  STATUS mandatory
  DESCRIPTION
     "Optional. In case dynamic session ID is in a known offset."
  DEFVAL { 0 }
  ::=  {rsWSDDynamicSidEntry 8}

rsWSDDynamicSidStopChar OBJECT-TYPE
  SYNTAX DisplayString (SIZE(0..10))
  ACCESS read-write
  STATUS mandatory
  DESCRIPTION
     "All possible delimiters that indicate the end of a session ID. Whitespace is always a delimiter."
--  DEFVAL { ';' }
  ::=  {rsWSDDynamicSidEntry 9}

rsWSDDynamicSidInactTimeout OBJECT-TYPE
  SYNTAX INTEGER
  ACCESS read-write
  STATUS mandatory
  DESCRIPTION
     "Inactivity timeout for a dynamic session ID. If a dynamic session ID has not been used for this number
      of seconds, it will be removed from internal tables."
  DEFVAL { 60 }
  ::=  {rsWSDDynamicSidEntry 10}

rsWSDDynamicSidStatus OBJECT-TYPE
  SYNTAX RowStatus
  ACCESS read-write
  STATUS mandatory
  DESCRIPTION
     "Row status for this entry."
  ::=  {rsWSDDynamicSidEntry 11}

rsWSDDynamicSidLearnDirection OBJECT-TYPE
  SYNTAX INTEGER {
   reply(1),
   request(2),
   both(3),
   none(4)
  }
  ACCESS read-write
  STATUS mandatory
  DESCRIPTION
     "Defines whether the WSD learns the session IDs from the reply or request packets."
  DEFVAL { reply }
  ::=  {rsWSDDynamicSidEntry 12}

rsWSDDynamicSidPrsstL7Mode OBJECT-TYPE
   SYNTAX INTEGER {
        first (1),
        maintain (2),
        overwrite (3)
   }
   ACCESS  read-write
   STATUS  mandatory
   DESCRIPTION
       "first     -  Parse only first request of a persistent connection.
        Maintain  -  Parse all requests and Maintain connections to servers alive.
        Overwrite -  Parse all requests and keep only the active server connection alive overwriting the old servers."
   DEFVAL { 1 }
   ::=  {rsWSDDynamicSidEntry 13}

rsWSDDynamicSidL4Protocol OBJECT-TYPE
   SYNTAX INTEGER {
        tcp   (1),
        udp   (2),
        other (3)
   }
   ACCESS  read-only
   STATUS  mandatory
   DESCRIPTION
       "L4 Protocol for dynamic session ID search. WSD uses Delayed Binding
        Only when TCP is configured"
   DEFVAL { 1 }
   ::=  {rsWSDDynamicSidEntry 14}

rsWSDDynamicSidPatternOffset OBJECT-TYPE
   SYNTAX INTEGER (0..65536)
   ACCESS  read-write
   STATUS  mandatory
   DESCRIPTION
       "offset from which to take the pattern for matching.
        The offset is relative to a certain location in the packet,
        as indicated in the 'Offset Relative To' field."
   DEFVAL { 0 }
   ::=  {rsWSDDynamicSidEntry 15}

rsWSDDynamicSidPatternMask OBJECT-TYPE
   SYNTAX DisplayString (SIZE(0..18))
   ACCESS  read-write
   STATUS  mandatory
   DESCRIPTION
       "mask to apply to the pattern found at the offset.
        The outcome is used for the lookup in the dynamic session ID table"
   DEFVAL { "0xFFFFFFFF" }
   ::=  {rsWSDDynamicSidEntry 16}


rsWSDDynamicSidOffsetFrom OBJECT-TYPE
   SYNTAX INTEGER {
        ipHeader   (1),
        ipData     (2),
        l4Header   (3),
        l4Data     (4)
   }
   ACCESS  read-write
   STATUS  mandatory
   DESCRIPTION
       "Defines the position in the packet which the value in rsWSDDynamicSidPatternOffset
	    field relates to"
   DEFVAL { 1 }
   ::=  {rsWSDDynamicSidEntry 17}

rsWSDDynamicSidIgnoreSourceIp OBJECT-TYPE
   SYNTAX FeatureStatus
   ACCESS  read-write
   STATUS  mandatory
   DESCRIPTION
       "Defines the factors used for the persistency decision.
	    When enabled (default), persistency is based on the SID value only.
	    When disabled, persistency is based both on the SID value and the Client IP address"
   DEFVAL { enable }
   ::=  {rsWSDDynamicSidEntry 18}

rsWSDDynamicSidPersistencyMode OBJECT-TYPE
   SYNTAX INTEGER {
        inspect      (1),
        insert       (2),
	rewrite      (3)
   }
   ACCESS  read-write
   STATUS  mandatory
   DESCRIPTION
       "Defines the method of SID operation.
        When inspect (default), SID mechnisem doesn't change the packet but only inspect them.
        When insert in used, SID mechnisem adds a new SID header to the reply packets.
	When rewrite in used, SID mechnisem rewrites an existing SID value in a given SID header.
	Only affect the reply packets."
   DEFVAL { 1 }
   ::=  {rsWSDDynamicSidEntry 19}

rsWSDDynamicSidHeaderName OBJECT-TYPE
   SYNTAX DisplayString (SIZE(0..255))
   ACCESS  read-write
   STATUS  mandatory
   DESCRIPTION
       "Holds the modified header name"
   ::=  {rsWSDDynamicSidEntry 20}

rsWSDDynamicSidArgs OBJECT-TYPE
   SYNTAX DisplayString (SIZE(0..255))
   ACCESS  read-write
   STATUS  mandatory
   DESCRIPTION
       "Holds the arguments for the Insert/Rewrite modes"
   ::=  {rsWSDDynamicSidEntry 21}

rsWSDDynamicSidFlags OBJECT-TYPE
    SYNTAX    BitFlag
    ACCESS    read-only
    STATUS    mandatory
    DESCRIPTION
       "Flags for internal use."
    ::= { rsWSDDynamicSidEntry 22 }

rsWSDDynamicSidPersistencyMethod OBJECT-TYPE
   SYNTAX INTEGER {
        table        (1),
        hash         (2)
   }
   ACCESS  read-write
   STATUS  mandatory
   DESCRIPTION
       "Defines the persistency method - either by storing session IDs and additional info in a table,
        or performing a hash over them that maps each to a server."
   DEFVAL { 1 }
   ::=  {rsWSDDynamicSidEntry 23}

rsWSDDynamicSidDataFormat OBJECT-TYPE
  SYNTAX INTEGER {
   binary(1),
   ipString(2)
  }
  ACCESS read-write
  STATUS mandatory
  DESCRIPTION
     "Defines the type of data to look for according to the SID parameter."
  DEFVAL { binary }
  ::=  {rsWSDDynamicSidEntry 24}

rsWSDDynamicSidForReply OBJECT-TYPE
  SYNTAX DisplayString (SIZE(0..63))
  ACCESS read-write
  STATUS mandatory
  DESCRIPTION
     "ID to look for during dynamic session ID search on the server reply (used only when rsWDDDynamicSidLookupMode is xmlTag). Case sensitive."
 ::=  {rsWSDDynamicSidEntry 25}


 rsWSDDynamicSidParameterMatch OBJECT-TYPE
  SYNTAX INTEGER {
   sensitive      (1),
   insensitive    (2)
  }
  ACCESS read-write
  STATUS mandatory
  DESCRIPTION
     "Defines the SID parameter match case."
  DEFVAL { sensitive }
  ::=  {rsWSDDynamicSidEntry 26}


 rsWSDDynamicSidValueMatch OBJECT-TYPE
  SYNTAX INTEGER {
   sensitive      (1),
   insensitive    (2)
  }
  ACCESS read-write
  STATUS mandatory
  DESCRIPTION
     "Defines the SID Value match case."
  DEFVAL { sensitive }
  ::=  {rsWSDDynamicSidEntry 27}

rsADDynamicSidTable OBJECT-TYPE
   SYNTAX SEQUENCE OF RsADDynamicSidEntry
   ACCESS not-accessible
   STATUS mandatory
   DESCRIPTION
       "A table for managing dynamic session ID L7 information."
   ::= {rsNWSD 68}

rsADDynamicSidEntry OBJECT-TYPE
   SYNTAX RsADDynamicSidEntry
   ACCESS not-accessible
   STATUS mandatory
   DESCRIPTION
       " The row definition for this table."
   INDEX  { rsADDynamicSidFarm,
            rsADDynamicSidPort,
            rsADDynamicSidL4Protocol}
   ::= {rsADDynamicSidTable 1}

RsADDynamicSidEntry ::= SEQUENCE {
  rsADDynamicSidFarm            DisplayString,
  rsADDynamicSidPort            INTEGER,
  rsADDynamicSidL4Protocol      INTEGER,
  rsADDynamicSidStatus          RowStatus,
  rsADDynamicSid                DisplayString,
  rsADDynamicSidMatch           INTEGER,
  rsADDynamicSidLookupMode      INTEGER,
  rsADDynamicSidIgnoreServer    INTEGER,
  rsADDynamicSidValMaxLen       INTEGER,
  rsADDynamicSidValOffset       INTEGER,
  rsADDynamicSidStopChar        DisplayString,
  rsADDynamicSidInactTimeout    INTEGER,
  rsADDynamicSidLearnDirection  INTEGER,
  rsADDynamicSidPrsstL7Mode     INTEGER,
  rsADDynamicSidPatternOffset   INTEGER,
  rsADDynamicSidPatternMask     DisplayString,
  rsADDynamicSidOffsetFrom      INTEGER,
  rsADDynamicSidIgnoreSourceIp  FeatureStatus,
  rsADDynamicSidHeaderName      DisplayString,
  rsADDynamicSidArgs            DisplayString,
  rsADDynamicSidFlags           BitFlag,
  rsADDynamicSidPersistencyMethod INTEGER,
  rsADDynamicSidDataFormat		INTEGER,
  rsADDynamicSidForReply        DisplayString,
  rsADDynamicSidParameterMatch  INTEGER,
  rsADDynamicSidValueMatch      INTEGER
}

rsADDynamicSidFarm OBJECT-TYPE
  SYNTAX DisplayString (SIZE(1..50))
  ACCESS read-only
  STATUS mandatory
  DESCRIPTION
     "Farm name for dynamic session ID search."
  ::=  {rsADDynamicSidEntry 1}

rsADDynamicSidPort OBJECT-TYPE
  SYNTAX INTEGER (0..65535)
  ACCESS read-only
  STATUS mandatory
  DESCRIPTION
     "TCP/UDP destination port for dynamic session ID search. 0 means that dynamic session ID parsing is performed
      on all destination ports."
  ::=  {rsADDynamicSidEntry 2}

rsADDynamicSidL4Protocol OBJECT-TYPE
   SYNTAX INTEGER {
        tcp   (1),
        udp   (2),
        other (3)
   }
   ACCESS  read-only
   STATUS  mandatory
   DESCRIPTION
       "L4 Protocol for dynamic session ID search. AppDirector uses Delayed Binding
        Only when TCP is configured"
   DEFVAL { 1 }
   ::=  {rsADDynamicSidEntry 3}

rsADDynamicSidStatus OBJECT-TYPE
  SYNTAX RowStatus
  ACCESS read-write
  STATUS mandatory
  DESCRIPTION
     "Row status for this entry."
  ::=  {rsADDynamicSidEntry 4}

rsADDynamicSid OBJECT-TYPE
  SYNTAX DisplayString (SIZE(0..63))
  ACCESS read-write
  STATUS mandatory
  DESCRIPTION
     "ID to look for during dynamic session ID search. Case sensitive. When rsADDynamicSidLookupMode is xmlTag this ID is searched in the request only."
 ::=  {rsADDynamicSidEntry 5}

rsADDynamicSidMatch OBJECT-TYPE
  SYNTAX INTEGER {
   exact(1),
   prefix(2)
  }
  ACCESS read-write
  STATUS mandatory
  DESCRIPTION
     "Defines whether the ID match should be exactly as specified or if it can be prefix (in cases were
      the application also changes the end of the ID)."
  DEFVAL { exact }
  ::=  {rsADDynamicSidEntry 6}

rsADDynamicSidLookupMode OBJECT-TYPE
  SYNTAX INTEGER {
   indicator (1),
   offset    (2),
   header    (3),
   regexp    (4),
   httpCookie(5),
   requestUrl(6),
   xmlTag    (7),
   radiusAttr(8)
-- diameter  (9)
  }
  ACCESS read-write
  STATUS mandatory
  DESCRIPTION
     "Defines scope for the persistency identifier search.
      indicator (1),     search for a token=value pair that may appear anywhere within the the HTTP header.
      offset    (2),     indicates that the entry is of 'Pattern Match' type.
      header    (3),     search for HTTP header name given by rsADDynamicSidHeaderName. Header parameter may be indicated by rsADDynamicSid variable.
      regexp    (4),     search regular expression in all the HTTP header.
      httpCookie(5),     search for a token=value pair within the Cookie header. token is given by the rsADDynamicSid field value.
      requestUrl(6)      search for a token=value pair within the HTTP request line. token is given by the rsADDynamicSid field value.
      xmlTag    (7)      maintain persistency based on a SOAP tag and/or SOAP Header Field. Available only with ADXL and TSL license."
--    diameter  (9),	 perform persistency on diameter."
  DEFVAL { httpCookie }
  ::=  {rsADDynamicSidEntry 7}

rsADDynamicSidIgnoreServer OBJECT-TYPE
  SYNTAX INTEGER {
   enable(1),
   disable(2)
  }
  ACCESS read-write
  STATUS mandatory
  DESCRIPTION
     "When enabled, the WSD will not look for a new session ID in server responses if the client GET already had a
      session ID in it. This is less time consuming, but may not work correctly with all applications."
  DEFVAL { disable }
  ::=  {rsADDynamicSidEntry 8}

rsADDynamicSidValMaxLen OBJECT-TYPE
  SYNTAX INTEGER (1..256)
  ACCESS read-write
  STATUS mandatory
  DESCRIPTION
     "Maximum length of dynamic session ID."
  DEFVAL { 256 }
  ::=  {rsADDynamicSidEntry 9}

rsADDynamicSidValOffset OBJECT-TYPE
  SYNTAX INTEGER (0..1500)
  ACCESS read-write
  STATUS mandatory
  DESCRIPTION
     "Optional. In case dynamic session ID is in a known offset."
  DEFVAL { 0 }
  ::=  {rsADDynamicSidEntry 10}

rsADDynamicSidStopChar OBJECT-TYPE
  SYNTAX DisplayString (SIZE(0..10))
  ACCESS read-write
  STATUS mandatory
  DESCRIPTION
     "All possible delimiters that indicate the end of a session ID. Whitespace is always a delimiter."
--DEFVAL { ';' }
  ::=  {rsADDynamicSidEntry 11}

rsADDynamicSidInactTimeout OBJECT-TYPE
  SYNTAX INTEGER
  ACCESS read-write
  STATUS mandatory
  DESCRIPTION
     "Inactivity timeout for a dynamic session ID. If a dynamic session ID has not been used for this number
      of seconds, it will be removed from internal tables."
  DEFVAL { 60 }
  ::=  {rsADDynamicSidEntry 12}

rsADDynamicSidLearnDirection OBJECT-TYPE
  SYNTAX INTEGER {
   reply(1),
   request(2),
   both(3),
   none(4)
  }
  ACCESS read-write
  STATUS mandatory
  DESCRIPTION
     "Defines whether the AppDirector learns the session IDs from the reply or request packets."
  DEFVAL { reply }
  ::=  {rsADDynamicSidEntry 13}

rsADDynamicSidPrsstL7Mode OBJECT-TYPE
   SYNTAX INTEGER {
        first (1),
        maintain (2),
        overwrite (3)
   }
   ACCESS  read-write
   STATUS  mandatory
   DESCRIPTION
       "first     -  Parse only first request of a persistent connection.
        Maintain  -  Parse all requests and Maintain connections to servers alive.
        Overwrite -  Parse all requests and keep only the active server connection alive overwriting the old servers."
   DEFVAL { 1 }
   ::=  {rsADDynamicSidEntry 14}

rsADDynamicSidPatternOffset OBJECT-TYPE
   SYNTAX INTEGER (0..65536)
   ACCESS  read-write
   STATUS  mandatory
   DESCRIPTION
       "offset from which to take the pattern for matching.
        The offset is relative to a certain location in the packet,
        as indicated in the 'Offset Relative To' field."
   DEFVAL { 0 }
   ::=  {rsADDynamicSidEntry 15}

rsADDynamicSidPatternMask OBJECT-TYPE
   SYNTAX DisplayString (SIZE(0..102))
   ACCESS  read-write
   STATUS  mandatory
   DESCRIPTION
       "mask to apply to the pattern found at the offset.
        The outcome is used for the lookup in the dynamic session ID table"
   DEFVAL { "0xFFFFFFFF" }
   ::=  {rsADDynamicSidEntry 16}


rsADDynamicSidOffsetFrom OBJECT-TYPE
   SYNTAX INTEGER {
        ipHeader   (1),
        ipData     (2),
        l4Header   (3),
        l4Data     (4)
   }
   ACCESS  read-write
   STATUS  mandatory
   DESCRIPTION
       "Defines the position in the packet which the value in rsADDynamicSidPatternOffset
	    field relates to"
   DEFVAL { 1 }
   ::=  {rsADDynamicSidEntry 17}

rsADDynamicSidIgnoreSourceIp OBJECT-TYPE
   SYNTAX FeatureStatus
   ACCESS  read-write
   STATUS  mandatory
   DESCRIPTION
       "Defines the factors used for the persistency decision.
	    When enabled (default), persistency is based on the SID value only.
	    When disabled, persistency is based both on the SID value and the Client IP address"
   DEFVAL { enable }
   ::=  {rsADDynamicSidEntry 18}

rsADDynamicSidHeaderName OBJECT-TYPE
   SYNTAX DisplayString (SIZE(0..255))
   ACCESS  read-write
   STATUS  mandatory
   DESCRIPTION
       "Holds the modified header name"
   ::=  {rsADDynamicSidEntry 19}

rsADDynamicSidArgs OBJECT-TYPE
   SYNTAX DisplayString (SIZE(0..255))
   ACCESS  read-write
   STATUS  mandatory
   DESCRIPTION
       "Holds the arguments for the Insert/Rewrite modes"
   ::=  {rsADDynamicSidEntry 20}

rsADDynamicSidFlags OBJECT-TYPE
    SYNTAX    BitFlag
    ACCESS    read-only
    STATUS    mandatory
    DESCRIPTION
       "Flags for internal use."
    ::= { rsADDynamicSidEntry 21 }

rsADDynamicSidPersistencyMethod OBJECT-TYPE
   SYNTAX INTEGER {
        table        (1),
        hash         (2)
   }
   ACCESS  read-write
   STATUS  mandatory
   DESCRIPTION
       "Defines the persistency method - either by storing session IDs and additional info in a table,
        or performing a hash over them that maps each to a server."
   DEFVAL { 1 }
   ::=  {rsADDynamicSidEntry 22}

rsADDynamicSidDataFormat OBJECT-TYPE
  SYNTAX INTEGER {
   binary(1),
   ipString(2)
  }
  ACCESS read-write
  STATUS mandatory
  DESCRIPTION
     "Defines the type of data to look for according to the SID parameter."
  DEFVAL { binary }
  ::=  {rsADDynamicSidEntry 23}

rsADDynamicSidForReply OBJECT-TYPE
  SYNTAX DisplayString (SIZE(0..63))
  ACCESS read-write
  STATUS mandatory
  DESCRIPTION
     "ID to look for during dynamic session ID search on the server reply (used only when rsADDynamicSidLookupMode is xmlTag). Case sensitive."
 ::=  {rsADDynamicSidEntry 24}

 rsADDynamicSidParameterMatch OBJECT-TYPE
  SYNTAX INTEGER {
   sensitive      (1),
   insensitive    (2)
  }
  ACCESS read-write
  STATUS mandatory
  DESCRIPTION
     "Defines the SID parameter match case."
  DEFVAL { sensitive }
  ::=  {rsADDynamicSidEntry 25}


 rsADDynamicSidValueMatch OBJECT-TYPE
  SYNTAX INTEGER {
   sensitive      (1),
   insensitive    (2)
  }
  ACCESS read-write
  STATUS mandatory
  DESCRIPTION
     "Defines the SID Value match case."
  DEFVAL { sensitive }
  ::=  {rsADDynamicSidEntry 26}


rsWSDDefaultRedirectionTable OBJECT-TYPE
   SYNTAX SEQUENCE OF RsWSDDefaultRedirectionEntry
   ACCESS not-accessible
   STATUS mandatory
   DESCRIPTION
          "In this table the WSD saves the default redirection servers IP Address"
   ::= {rsNWSD 43}

rsWSDDefaultRedirectionEntry OBJECT-TYPE
    SYNTAX RsWSDDefaultRedirectionEntry
    ACCESS not-accessible
    STATUS  mandatory
    DESCRIPTION
       " The row definition for this table."
   INDEX  {rsWSDDefaultRedirectionFarmAddress,
           rsWSDDefaultRedirectionPriority}
   ::= {rsWSDDefaultRedirectionTable 1}

RsWSDDefaultRedirectionEntry  ::= SEQUENCE {
  rsWSDDefaultRedirectionFarmAddress  IpAddress,
  rsWSDDefaultRedirectionPriority     INTEGER,
  rsWSDDefaultRedirectionServer       IpAddress,
  rsWSDDefaultRedirectionAdminStatus  FeatureStatus,
  rsWSDDefaultRedirectionStatus       RowStatus,
  rsWSDDefaultRedirectionServerPort   INTEGER
  }

rsWSDDefaultRedirectionFarmAddress OBJECT-TYPE
    SYNTAX IpAddress
    ACCESS  read-only
    STATUS  mandatory
    DESCRIPTION
      "The IP Address of the WEB farm."
    ::= {rsWSDDefaultRedirectionEntry 1}

rsWSDDefaultRedirectionPriority OBJECT-TYPE
    SYNTAX INTEGER
    ACCESS  read-only
    STATUS  mandatory
    DESCRIPTION
      "Rediretion priority of the server."
    ::= {rsWSDDefaultRedirectionEntry 2}

rsWSDDefaultRedirectionServer OBJECT-TYPE
    SYNTAX IpAddress
    ACCESS  read-write
    STATUS  mandatory
    DESCRIPTION
"The IP address of the server for default redirection"
    ::= {rsWSDDefaultRedirectionEntry 3}

rsWSDDefaultRedirectionAdminStatus OBJECT-TYPE
    SYNTAX  FeatureStatus
    ACCESS  read-write
    STATUS  mandatory
    DESCRIPTION
      "Administrative status of default redirection on the server.
       enable -   activates default redirection on the server.
       disable -  stops default redirection on the server."
	DEFVAL { enable }
	::=  {rsWSDDefaultRedirectionEntry 4 }

rsWSDDefaultRedirectionStatus OBJECT-TYPE
    SYNTAX  RowStatus
    ACCESS  read-write
    STATUS  mandatory
    DESCRIPTION
       "This variable indicates the administrative status of this entry.
        Used to delete an entry of this table."
    ::=  { rsWSDDefaultRedirectionEntry 5}

rsWSDDefaultRedirectionServerPort  OBJECT-TYPE
    SYNTAX INTEGER
    ACCESS  read-write
    STATUS  mandatory
    DESCRIPTION
        "The port of the server for default redirection."
    DEFVAL {0}
    ::= { rsWSDDefaultRedirectionEntry 6}


rsADDefaultRedirectionTable OBJECT-TYPE
   SYNTAX SEQUENCE OF RsADDefaultRedirectionEntry
   ACCESS not-accessible
   STATUS mandatory
   DESCRIPTION
          "In this table the AppDirector saves the default redirection servers IP Address"
   ::= {rsNWSD 69}

rsADDefaultRedirectionEntry OBJECT-TYPE
    SYNTAX RsADDefaultRedirectionEntry
    ACCESS not-accessible
    STATUS  mandatory
    DESCRIPTION
       " The row definition for this table."
   INDEX  {rsADDefaultRedirectionFarmName,
           rsADDefaultRedirectionPriority}
   ::= {rsADDefaultRedirectionTable 1}

RsADDefaultRedirectionEntry  ::= SEQUENCE {
  rsADDefaultRedirectionFarmName     DisplayString,
  rsADDefaultRedirectionPriority     INTEGER,
  rsADDefaultRedirectionStatus       RowStatus,
  rsADDefaultRedirectionServer       IpAddress,
  rsADDefaultRedirectionServerPort   INTEGER,
  rsADDefaultRedirectionAdminStatus  	FeatureStatus,
  rsADDefaultRedirectionServerName  	DisplayString
}

rsADDefaultRedirectionFarmName OBJECT-TYPE
    SYNTAX  DisplayString (SIZE(1..50))
    ACCESS  read-only
    STATUS  mandatory
    DESCRIPTION
      "The name of the WEB farm."
    ::= {rsADDefaultRedirectionEntry 1}

rsADDefaultRedirectionPriority OBJECT-TYPE
    SYNTAX INTEGER (0..2147483647)
    ACCESS  read-only
    STATUS  mandatory
    DESCRIPTION
      "Redirection priority of the server."
	DEFVAL {0}
    ::= {rsADDefaultRedirectionEntry 2}

rsADDefaultRedirectionStatus OBJECT-TYPE
    SYNTAX  RowStatus
    ACCESS  read-write
    STATUS  mandatory
    DESCRIPTION
       "This variable indicates the administrative status of this entry.
        Used to delete an entry of this table."
    ::=  { rsADDefaultRedirectionEntry 3}

rsADDefaultRedirectionServer OBJECT-TYPE
    SYNTAX IpAddress
    ACCESS  read-write
    STATUS  mandatory
    DESCRIPTION
	"Field is obsolete"
	DEFVAL {0}
    ::= {rsADDefaultRedirectionEntry 4}

rsADDefaultRedirectionServerPort  OBJECT-TYPE
    SYNTAX INTEGER
    ACCESS  read-write
    STATUS  mandatory
    DESCRIPTION
        "The port of the server for default redirection."
    DEFVAL {0}
    ::= { rsADDefaultRedirectionEntry 5}

rsADDefaultRedirectionAdminStatus OBJECT-TYPE
    SYNTAX  FeatureStatus
    ACCESS  read-write
    STATUS  mandatory
    DESCRIPTION
      "Administrative status of default redirection on the server.
       enable -   activates default redirection on the server.
       disable -  stops default redirection on the server."
	DEFVAL { enable }
	::=  {rsADDefaultRedirectionEntry 6 }

rsADDefaultRedirectionServerName OBJECT-TYPE
    SYNTAX DisplayString (SIZE(1..30))
    ACCESS  read-write
    STATUS  mandatory
    DESCRIPTION
	"The Name of the server for default redirection"
    ::= {rsADDefaultRedirectionEntry 7}

--
-- L7 parameters
--
   rsWSDL7 OBJECT IDENTIFIER ::= { rsNWSD 44 }

rsWSDL7PolicyTable OBJECT-TYPE
   SYNTAX SEQUENCE OF RsWSDL7PolicyEntry
   ACCESS not-accessible
   STATUS mandatory
   DESCRIPTION
       "A table for managing farm selection by L7 information."
   ::= {rsWSDL7 1}

rsWSDL7PolicyEntry OBJECT-TYPE
   SYNTAX RsWSDL7PolicyEntry
   ACCESS not-accessible
   STATUS  mandatory
   DESCRIPTION
       " The row definition for this table."
   INDEX  { rsWSDL7PolicyName,
            rsWSDL7PolicyIndex }
   ::= {rsWSDL7PolicyTable 1}

RsWSDL7PolicyEntry  ::= SEQUENCE {
      rsWSDL7PolicyName        DisplayString,
      rsWSDL7PolicyIndex       INTEGER,
      rsWSDL7PolicyMethod1     DisplayString,
      rsWSDL7PolicyMethod2     DisplayString,
      rsWSDL7PolicyArgs        DisplayString,
      rsWSDL7PolicyFarm        IpAddress,
      rsWSDL7PolicyStatus      RowStatus,
      rsWSDL7PolicyFarmName    DisplayString
  }

rsWSDL7PolicyName OBJECT-TYPE
    SYNTAX    DisplayString (SIZE(1..20))
    ACCESS    read-only
    STATUS    mandatory
    DESCRIPTION
       "The policy name"
    ::= { rsWSDL7PolicyEntry 1 }

rsWSDL7PolicyIndex OBJECT-TYPE
    SYNTAX    INTEGER
    ACCESS    read-only
    STATUS    mandatory
    DESCRIPTION
      "The policy index, used to define classification order"
    ::= { rsWSDL7PolicyEntry 2 }

rsWSDL7PolicyMethod1 OBJECT-TYPE
    SYNTAX    DisplayString (SIZE(0..50))
    ACCESS    read-write
    STATUS    mandatory
    DESCRIPTION
      "The first L7 method used for classification. Mandatory."
    ::= { rsWSDL7PolicyEntry 3 }

rsWSDL7PolicyMethod2 OBJECT-TYPE
    SYNTAX    DisplayString (SIZE(0..50))
    ACCESS    read-write
    STATUS    mandatory
    DESCRIPTION
      "The second L7 method used for classification. Optional. Classification is according to logical AND of first and second methods."
    ::= { rsWSDL7PolicyEntry 4 }

rsWSDL7PolicyArgs OBJECT-TYPE
    SYNTAX    DisplayString (SIZE(0..255))
    ACCESS    read-write
    STATUS    mandatory
    DESCRIPTION
      "Arguments for classification"
    ::= { rsWSDL7PolicyEntry 5 }

rsWSDL7PolicyFarm OBJECT-TYPE
    SYNTAX    IpAddress
    ACCESS    read-write
    STATUS    mandatory
    DESCRIPTION
      "Policy action - the farm to use when policy is matched."
    ::= { rsWSDL7PolicyEntry 6 }

rsWSDL7PolicyStatus OBJECT-TYPE
    SYNTAX    RowStatus
    ACCESS    read-write
    STATUS    mandatory
    DESCRIPTION
      "Row status for this entry."
    ::= { rsWSDL7PolicyEntry 7 }

rsWSDL7PolicyFarmName OBJECT-TYPE
    SYNTAX    DisplayString (SIZE (0..50))
    ACCESS    read-write
    STATUS    mandatory
    DESCRIPTION
      "Policy action - the farm to use when policy is matched. Farm is referred here by its name."
    ::= { rsWSDL7PolicyEntry 8 }


rsWSDL7PolicyStatsTable OBJECT-TYPE
   SYNTAX SEQUENCE OF RsWSDL7PolicyStatsEntry
   ACCESS not-accessible
   STATUS mandatory
   DESCRIPTION
       "A read-only table for L7 statistical information."
   ::= {rsWSDL7 2}

rsWSDL7PolicyStatsEntry OBJECT-TYPE
   SYNTAX RsWSDL7PolicyStatsEntry
   ACCESS not-accessible
   STATUS  mandatory
   DESCRIPTION
       " The row definition for this table."
   INDEX  { rsWSDL7PolicyStatsName,
            rsWSDL7PolicyStatsIndex }
   ::= {rsWSDL7PolicyStatsTable 1}

RsWSDL7PolicyStatsEntry  ::= SEQUENCE {
      rsWSDL7PolicyStatsName      DisplayString,
      rsWSDL7PolicyStatsIndex     INTEGER,
      rsWSDL7PolicyStatsMatches   Counter,
      rsWSDL7PolicyStatsLSMatches Counter
  }

rsWSDL7PolicyStatsName OBJECT-TYPE
    SYNTAX    DisplayString (SIZE(1..20))
    ACCESS    read-only
    STATUS    mandatory
    DESCRIPTION
       "The policy name"
    ::= { rsWSDL7PolicyStatsEntry 1 }

rsWSDL7PolicyStatsIndex OBJECT-TYPE
    SYNTAX    INTEGER
    ACCESS    read-only
    STATUS    mandatory
    DESCRIPTION
      "The policy index, used to define classification order"
    ::= { rsWSDL7PolicyStatsEntry 2 }

rsWSDL7PolicyStatsMatches OBJECT-TYPE
    SYNTAX    Counter
    ACCESS    read-only
    STATUS    mandatory
    DESCRIPTION
      "Number of total matches for this policy"
    ::= { rsWSDL7PolicyStatsEntry 3 }

rsWSDL7PolicyStatsLSMatches OBJECT-TYPE
    SYNTAX    Counter
    ACCESS    read-only
    STATUS    mandatory
    DESCRIPTION
      "Number of last second matches for this policy"
    ::= { rsWSDL7PolicyStatsEntry 4 }

rsWSDL7MethodTable OBJECT-TYPE
   SYNTAX SEQUENCE OF RsWSDL7MethodEntry
   ACCESS not-accessible
   STATUS mandatory
   DESCRIPTION
       "A table for L7 methods."
   ::= {rsWSDL7 3}

rsWSDL7MethodEntry OBJECT-TYPE
   SYNTAX RsWSDL7MethodEntry
   ACCESS not-accessible
   STATUS  mandatory
   DESCRIPTION
       " The row definition for this table."
   INDEX  { rsWSDL7MethodName }
   ::= {rsWSDL7MethodTable 1}

RsWSDL7MethodEntry  ::= SEQUENCE {
      rsWSDL7MethodName                          DisplayString,
      rsWSDL7MethodType                          INTEGER,
      rsWSDL7MethodArgs                          DisplayString,
      rsWSDL7MethodStatus                        RowStatus,
      rsWSDL7Inverse	                         FeatureStatus,
      rsWSDL7MethodAdvancedUrlProtocol           INTEGER,
      rsWSDL7MethodAdvancedUrlPort               INTEGER,
      rsWSDL7MethodAdvancedUrlHostname           DisplayString,
      rsWSDL7MethodAdvancedUrlHostnameMatchType  INTEGER,
      rsWSDL7MethodAdvancedUrlHostnameActionType INTEGER,
      rsWSDL7MethodAdvancedUrlPath               DisplayString,
      rsWSDL7MethodAdvancedUrlPathMatchType      INTEGER,
      rsWSDL7MethodAdvancedUrlPathActionType     INTEGER,
      rsWSDL7MethodAdvancedPageName              DisplayString,
      rsWSDL7MethodAdvancedPageType              DisplayString
  }

rsWSDL7MethodName OBJECT-TYPE
    SYNTAX    DisplayString (SIZE(1..50))
    ACCESS    read-only
    STATUS    mandatory
    DESCRIPTION
       "The method name"
    ::= { rsWSDL7MethodEntry 1 }

rsWSDL7MethodType OBJECT-TYPE
    SYNTAX    INTEGER {
        url                       (1),
        fileType                  (2),
        headerField               (3),
        cookieKeyVal              (4),
        regExp                    (5),
        text                      (6),
        statusLine                (7),
        setCookie                 (8),
        requestLine               (9),
        from                      (10),
        to                        (11),
        contact                   (12),
        callID                    (13),
        cseq                      (14),
        via                       (15),
        route                     (16),
        recordRoute               (17),
        pAssertedID               (18),
        pPreferredID              (19),
        sipHeader                 (20),
        sdp                       (21),
        advancedUrlCondition      (22),
        advancedUrlModification   (23),
        radiusAttribute           (24),
        certificate               (25)
    }
    ACCESS    read-write
    STATUS    mandatory
    DESCRIPTION
       "The method type - what to look for in L7"
    ::= { rsWSDL7MethodEntry 2 }

rsWSDL7MethodArgs OBJECT-TYPE
    SYNTAX    DisplayString (SIZE(0..255))
    ACCESS    read-write
    STATUS    mandatory
    DESCRIPTION
      "Arguments for the method definition"
    ::= { rsWSDL7MethodEntry 3 }

rsWSDL7MethodStatus OBJECT-TYPE
    SYNTAX    RowStatus
    ACCESS    read-write
    STATUS    mandatory
    DESCRIPTION
      "Row status for this entry."
    ::= { rsWSDL7MethodEntry 4 }

rsWSDL7Inverse OBJECT-TYPE
    SYNTAX FeatureStatus
    ACCESS read-write
    STATUS mandatory
    DESCRIPTION
      "Whether to treat all policies that do not match the criteria."
	DEFVAL { disable }
    ::= {rsWSDL7MethodEntry 5}

rsWSDL7MethodAdvancedUrlProtocol OBJECT-TYPE
    SYNTAX    INTEGER
        {
        http    (1),
        https   (2),
	none	(3)
        }
    ACCESS    read-write
    STATUS    mandatory
    DESCRIPTION
       "Indicates matching/action on Protocol"
    DEFVAL { http }
    ::= { rsWSDL7MethodEntry 6 }


rsWSDL7MethodAdvancedUrlPort OBJECT-TYPE
    SYNTAX INTEGER (0..65535)
    ACCESS    read-write
    STATUS    mandatory
    DESCRIPTION
       "Indicates matching/action on Hostname"
    ::= { rsWSDL7MethodEntry 7 }


rsWSDL7MethodAdvancedUrlHostname OBJECT-TYPE
    SYNTAX    DisplayString (SIZE(0..255))
    ACCESS    read-write
    STATUS    mandatory
    DESCRIPTION
       "Indicates matching/action on Hostname"
    ::= { rsWSDL7MethodEntry 8 }



rsWSDL7MethodAdvancedUrlHostnameMatchType OBJECT-TYPE
    SYNTAX    INTEGER {
        none    (1),
        equal   (2),
        contain (3),
        prefix  (4),
        suffix  (5)    }
    ACCESS    read-write
    STATUS    mandatory
    DESCRIPTION
       "Indicates matching/action on Hostname"
    DEFVAL { equal }
    ::= { rsWSDL7MethodEntry 9 }


rsWSDL7MethodAdvancedUrlHostnameActionType OBJECT-TYPE
    SYNTAX  INTEGER {
    none         (1),
    insertBefore (2),
    insertAfter  (3),
    remove       (4),
    replace      (5)
    }
    ACCESS  read-write
    STATUS  mandatory
    DESCRIPTION
     "Action to be taken on hostname/text"
    DEFVAL { none }
 ::=  { rsWSDL7MethodEntry 10}


rsWSDL7MethodAdvancedUrlPath OBJECT-TYPE
    SYNTAX    DisplayString (SIZE(0..256))
    ACCESS    read-write
    STATUS    mandatory
    DESCRIPTION
       "Indicates matching/action on path"
    ::= { rsWSDL7MethodEntry 11 }


rsWSDL7MethodAdvancedUrlPathMatchType OBJECT-TYPE
    SYNTAX    INTEGER {
        none    (1),
        equal   (2),
        contain (3),
        prefix  (4),
        suffix  (5)    }
    ACCESS    read-write
    STATUS    mandatory
    DESCRIPTION
       "Indicates how path matching of string will be done "
    DEFVAL { equal }
    ::= { rsWSDL7MethodEntry 12 }


rsWSDL7MethodAdvancedUrlPathActionType OBJECT-TYPE
    SYNTAX  INTEGER {
    none         (1),
    insertBefore (2),
    insertAfter  (3),
    remove       (4),
    replace      (5)
    }
    ACCESS  read-write
    STATUS  mandatory
    DESCRIPTION
     "Action to be taken on path"
    DEFVAL { none }
 ::=  { rsWSDL7MethodEntry 13}


rsWSDL7MethodAdvancedPageName OBJECT-TYPE
    SYNTAX    DisplayString (SIZE(0..256))
    ACCESS    read-write
    STATUS    mandatory
    DESCRIPTION
       "Indicates matching/action on Page name"
    ::= { rsWSDL7MethodEntry 14 }


rsWSDL7MethodAdvancedPageType OBJECT-TYPE
    SYNTAX    DisplayString (SIZE(0..20))
    ACCESS    read-write
    STATUS    mandatory
    DESCRIPTION
       "Indicates matching/action on Page type"
    ::= { rsWSDL7MethodEntry 15 }

rsWSDL7Actions OBJECT-TYPE
    SYNTAX  INTEGER {
       reset(1)
     }
    ACCESS  read-write
    STATUS  mandatory
    DESCRIPTION
      "This variable enables the operator to perform one of the
      specified actions on the tables maintained by the network device."
   ::= { rsWSDL7 4  }


--
-- Persistent L7 Switching
--
rsWSDPersistentL7Switching OBJECT IDENTIFIER ::= { rsWSDL7 5 }

rsWSDPersistentL7SwitchingClientTable OBJECT-TYPE
    SYNTAX SEQUENCE OF RsWSDPersistentL7SwitchingClientEntry
    ACCESS not-accessible
    STATUS  mandatory
    DESCRIPTION
      "Table containing the list of client table entries which use the Persistent L7 switching  feature"
    ::=  {rsWSDPersistentL7Switching 1}

rsWSDPersistentL7SwitchingClientEntry OBJECT-TYPE
    SYNTAX RsWSDPersistentL7SwitchingClientEntry
    ACCESS not-accessible
    STATUS  mandatory
    DESCRIPTION
       " The row definition for this table."
   INDEX { rsWSDPrsstL7SuperFarmAddr,
           rsWSDPrsstL7FarmAddr,
		   rsWSDPrsstL7ClientAddr,
		   rsWSDPrsstL7AttachedServerAddr,
		   rsWSDPrsstL7SrcPort,
		   rsWSDPrsstL7AttachedServerPort}
    ::=  {rsWSDPersistentL7SwitchingClientTable 1}

RsWSDPersistentL7SwitchingClientEntry ::= SEQUENCE {
  rsWSDPrsstL7SuperFarmAddr         IpAddress,
  rsWSDPrsstL7FarmAddr              IpAddress,
  rsWSDPrsstL7ClientAddr            IpAddress,
  rsWSDPrsstL7AttachedServerAddr    IpAddress,
  rsWSDPrsstL7SrcPort               INTEGER,
  rsWSDPrsstL7DstPort               INTEGER,
  rsWSDSharedConnectionCounter      INTEGER,
  rsWSDPrsstL7AttachedServerPort    INTEGER
  }

rsWSDPrsstL7SuperFarmAddr OBJECT-TYPE
    SYNTAX  IpAddress
    ACCESS  read-only
    STATUS  mandatory
    DESCRIPTION
     "Superfarm IP Address."
    ::=  {rsWSDPersistentL7SwitchingClientEntry 1}

rsWSDPrsstL7FarmAddr OBJECT-TYPE
    SYNTAX  IpAddress
    ACCESS  read-only
    STATUS  mandatory
    DESCRIPTION
     "Farm IP Address."
    ::=  {rsWSDPersistentL7SwitchingClientEntry 2}

rsWSDPrsstL7ClientAddr OBJECT-TYPE
    SYNTAX  IpAddress
    ACCESS  read-only
    STATUS  mandatory
    DESCRIPTION
     "Client IP Address."
    ::=  {rsWSDPersistentL7SwitchingClientEntry 3}


rsWSDPrsstL7AttachedServerAddr OBJECT-TYPE
    SYNTAX  IpAddress
    ACCESS  read-only
    STATUS  mandatory
    DESCRIPTION
     "Server IP Address."
    ::=  {rsWSDPersistentL7SwitchingClientEntry 4}

rsWSDPrsstL7SrcPort OBJECT-TYPE
    SYNTAX  INTEGER
    ACCESS  read-only
    STATUS  mandatory
    DESCRIPTION
     "Source port."
    ::=  {rsWSDPersistentL7SwitchingClientEntry 5}

rsWSDPrsstL7DstPort OBJECT-TYPE
    SYNTAX  INTEGER
    ACCESS  read-only
    STATUS  mandatory
    DESCRIPTION
     "destination port."
    ::=  {rsWSDPersistentL7SwitchingClientEntry 6}

rsWSDSharedConnectionCounter OBJECT-TYPE
    SYNTAX  INTEGER
    ACCESS  read-only
    STATUS  mandatory
    DESCRIPTION
     "Number of open server connections."
    ::=  {rsWSDPersistentL7SwitchingClientEntry 7}

rsWSDPrsstL7AttachedServerPort OBJECT-TYPE
    SYNTAX  INTEGER
    ACCESS  read-only
    STATUS  mandatory
    DESCRIPTION
     "Server Port."
    ::=  {rsWSDPersistentL7SwitchingClientEntry 8}

adL7PolicyTable OBJECT-TYPE
    SYNTAX SEQUENCE OF AdL7PolicyEntry
    ACCESS not-accessible
    STATUS mandatory
    DESCRIPTION
        "A table for managing farm selection by L7 information. Replaces rsWSDL7PolicyTable."
    ::= {rsWSDL7 6}

adL7PolicyEntry OBJECT-TYPE
    SYNTAX AdL7PolicyEntry
    ACCESS not-accessible
    STATUS mandatory
    DESCRIPTION
        " The row definition for this table."
    INDEX { adL7PolicyName,
    adL7PolicyIndex }
    ::= {adL7PolicyTable 1}

AdL7PolicyEntry  ::= SEQUENCE {
    adL7PolicyName		    DisplayString,
    adL7PolicyIndex		    INTEGER,
    adL7PolicyExpression 	DisplayString,
    adL7PolicyActionType	INTEGER,
    adL7PolicyAction		DisplayString,
    adL7PolicySIPControlPolicy DisplayString,
    adL7PolicyStatus		RowStatus
    }

adL7PolicyName OBJECT-TYPE
    SYNTAX DisplayString (SIZE(1..20))
    ACCESS read-only
    STATUS mandatory
    DESCRIPTION
        "The policy name"
    ::= {adL7PolicyEntry 1}

adL7PolicyIndex OBJECT-TYPE
    SYNTAX INTEGER
    ACCESS read-only
    STATUS mandatory
    DESCRIPTION
        "The policy index, used to define classification order"
    ::= {adL7PolicyEntry 2}

adL7PolicyExpression OBJECT-TYPE
    SYNTAX DisplayString (SIZE(1..50))
    ACCESS read-write
    STATUS mandatory
    DESCRIPTION
        "Expression to be evaluated. Contains a logical expression or methods and expressions (from the expression table)."
    ::= {adL7PolicyEntry 3}

adL7PolicyActionType OBJECT-TYPE
    SYNTAX INTEGER {
        farm(1),
        replyCode(2),
        route(3),
        uri(4),
        ip(5),
        none(6)
        }
    ACCESS read-write
    STATUS mandatory
    DESCRIPTION
        "Type of action to take on classification success.
         Farm – farm name to select server from.
         Reply code - specify a reply code.
         Route – specify a SIP route table. Can be a comma-separated list of tables.
         URI – send request to specified URI.
         IP – send request to IP."
	DEFVAL { farm }
    ::= {adL7PolicyEntry 4}

adL7PolicyAction OBJECT-TYPE
    SYNTAX DisplayString
    ACCESS read-write
    STATUS mandatory
    DESCRIPTION
        "Policy action - the farm to use when policy is matched, or next L7 lookup."
    ::= {adL7PolicyEntry 5}

adL7PolicySIPControlPolicy OBJECT-TYPE
    SYNTAX DisplayString (SIZE (0..50))
    ACCESS read-write
    STATUS mandatory
    DESCRIPTION
        "SIP policy to be used."
    ::= {adL7PolicyEntry 6}

adL7PolicyStatus OBJECT-TYPE
    SYNTAX RowStatus
    ACCESS read-write
    STATUS mandatory
    DESCRIPTION
        "Row status for this entry."
    ::= {adL7PolicyEntry 7}

rsADPersistentL7SwitchingClientTable OBJECT-TYPE
    SYNTAX SEQUENCE OF RsADPersistentL7SwitchingClientEntry
    ACCESS not-accessible
    STATUS  mandatory
    DESCRIPTION
      "Table containing the list of client table entries which use the Persistent L7 switching  feature"
    ::=  {rsWSDPersistentL7Switching 4}

rsADPersistentL7SwitchingClientEntry OBJECT-TYPE
    SYNTAX RsADPersistentL7SwitchingClientEntry
    ACCESS not-accessible
    STATUS  mandatory
    DESCRIPTION
       " The row definition for this table."
   INDEX { rsADPrsstL7SuperFarmAddr,
           rsADPrsstL7FarmName,
		   rsADPrsstL7ClientAddr,
		   rsADPrsstL7AttachedServerAddr,
           rsADPrsstL7AttachedServerPort,
		   rsADPrsstL7SrcPort }
    ::=  {rsADPersistentL7SwitchingClientTable 1}

RsADPersistentL7SwitchingClientEntry ::= SEQUENCE {
  rsADPrsstL7SuperFarmAddr         IpAddress,
  rsADPrsstL7FarmName              DisplayString,
  rsADPrsstL7ClientAddr            IpAddress,
  rsADPrsstL7AttachedServerAddr    IpAddress,
  rsADPrsstL7AttachedServerPort    INTEGER,
  rsADPrsstL7SrcPort               INTEGER,
  rsADPrsstL7DstPort               INTEGER,
  rsADSharedConnectionCounter      INTEGER
}

rsADPrsstL7SuperFarmAddr OBJECT-TYPE
    SYNTAX  IpAddress
    ACCESS  read-only
    STATUS  mandatory
    DESCRIPTION
     "Superfarm IP Address."
    ::=  {rsADPersistentL7SwitchingClientEntry 1}

rsADPrsstL7FarmName OBJECT-TYPE
    SYNTAX  DisplayString (SIZE (1..50))
    ACCESS  read-only
    STATUS  mandatory
    DESCRIPTION
     "Farm name."
    ::=  {rsADPersistentL7SwitchingClientEntry 2}

rsADPrsstL7ClientAddr OBJECT-TYPE
    SYNTAX  IpAddress
    ACCESS  read-only
    STATUS  mandatory
    DESCRIPTION
     "Client IP Address."
    ::=  {rsADPersistentL7SwitchingClientEntry 3}


rsADPrsstL7AttachedServerAddr OBJECT-TYPE
    SYNTAX  IpAddress
    ACCESS  read-only
    STATUS  mandatory
    DESCRIPTION
     "Server IP Address."
    ::=  {rsADPersistentL7SwitchingClientEntry 4}

rsADPrsstL7AttachedServerPort OBJECT-TYPE
    SYNTAX  INTEGER
    ACCESS  read-only
    STATUS  mandatory
    DESCRIPTION
     "Server Port."
    ::=  {rsADPersistentL7SwitchingClientEntry 5}

rsADPrsstL7SrcPort OBJECT-TYPE
    SYNTAX  INTEGER
    ACCESS  read-only
    STATUS  mandatory
    DESCRIPTION
     "Source port."
    ::=  {rsADPersistentL7SwitchingClientEntry 6}

rsADPrsstL7DstPort OBJECT-TYPE
    SYNTAX  INTEGER
    ACCESS  read-only
    STATUS  mandatory
    DESCRIPTION
     "destination port."
    ::=  {rsADPersistentL7SwitchingClientEntry 7}

rsADSharedConnectionCounter OBJECT-TYPE
    SYNTAX  INTEGER
    ACCESS  read-only
    STATUS  mandatory
    DESCRIPTION
     "Number of open server connections."
    ::=  {rsADPersistentL7SwitchingClientEntry 8}



rsWSDPersistentL7SwitchingStatisticsTable OBJECT-TYPE
    SYNTAX SEQUENCE OF RsWSDPersistentL7SwitchingStatistics
    ACCESS not-accessible
    STATUS  mandatory
    DESCRIPTION
      "Statistics table for the Persistent L7 Switching feature."
    ::=  {rsWSDPersistentL7Switching 2}

rsWSDPersistentL7SwitchingStatistics OBJECT-TYPE
    SYNTAX RsWSDPersistentL7SwitchingStatistics
    ACCESS not-accessible
    STATUS  mandatory
    DESCRIPTION
       " The row definition for this table."
   INDEX { rsWSDHTTPPFarmAddr,
           rsWSDHTTPPPort}
    ::=  {rsWSDPersistentL7SwitchingStatisticsTable 1}

RsWSDPersistentL7SwitchingStatistics ::= SEQUENCE {
  rsWSDHTTPPFarmAddr               IpAddress,
  rsWSDHTTPPPort                   INTEGER,
  rsClientSessions                 INTEGER,
  rsPersistentL7SwitchingEntries   INTEGER,
  rsAverageServerConnection        INTEGER
  }

rsWSDHTTPPFarmAddr OBJECT-TYPE
    SYNTAX  IpAddress
    ACCESS  read-only
    STATUS  mandatory
    DESCRIPTION
     "Destination IP Address"
    ::=  {rsWSDPersistentL7SwitchingStatistics 1}

rsWSDHTTPPPort OBJECT-TYPE
    SYNTAX  INTEGER
    ACCESS  read-only
    STATUS  mandatory
    DESCRIPTION
     "Destination Port number"
    ::=  {rsWSDPersistentL7SwitchingStatistics 2}

rsClientSessions OBJECT-TYPE
    SYNTAX  INTEGER
    ACCESS  read-only
    STATUS  mandatory
    DESCRIPTION
     "Number of Client Sessions"
    ::=  {rsWSDPersistentL7SwitchingStatistics 3}

rsPersistentL7SwitchingEntries OBJECT-TYPE
    SYNTAX  INTEGER
    ACCESS  read-only
    STATUS  mandatory
    DESCRIPTION
     "Number of Persistent L7 Switching Entries"
    ::=  {rsWSDPersistentL7SwitchingStatistics 4}

rsAverageServerConnection OBJECT-TYPE
    SYNTAX  INTEGER
    ACCESS  read-only
    STATUS  mandatory
    DESCRIPTION
     "Average of Server Connections per Client"
    ::=  {rsWSDPersistentL7SwitchingStatistics 5}


rsADPersistentL7SwitchingStatisticsTable OBJECT-TYPE
    SYNTAX SEQUENCE OF RsADPersistentL7SwitchingStatistics
    ACCESS not-accessible
    STATUS  mandatory
    DESCRIPTION
      "Statistics table for the Persistent L7 Switching feature."
    ::=  {rsWSDPersistentL7Switching 5}

rsADPersistentL7SwitchingStatistics OBJECT-TYPE
    SYNTAX RsADPersistentL7SwitchingStatistics
    ACCESS not-accessible
    STATUS  mandatory
    DESCRIPTION
       " The row definition for this table."
   INDEX { rsADHTTPPFarmName,
           rsADHTTPPPort}
    ::=  {rsADPersistentL7SwitchingStatisticsTable 1}

RsADPersistentL7SwitchingStatistics ::= SEQUENCE {
  rsADHTTPPFarmName                  DisplayString,
  rsADHTTPPPort                      INTEGER,
  rsADClientSessions                 INTEGER,
  rsADPersistentL7SwitchingEntries   INTEGER,
  rsADAverageServerConnection        INTEGER
  }

rsADHTTPPFarmName OBJECT-TYPE
    SYNTAX  DisplayString (SIZE (1..50))
    ACCESS  read-only
    STATUS  mandatory
    DESCRIPTION
     "Destination farm name"
    ::=  {rsADPersistentL7SwitchingStatistics 1}

rsADHTTPPPort OBJECT-TYPE
    SYNTAX  INTEGER
    ACCESS  read-only
    STATUS  mandatory
    DESCRIPTION
     "Destination Port number"
    ::=  {rsADPersistentL7SwitchingStatistics 2}

rsADClientSessions OBJECT-TYPE
    SYNTAX  INTEGER
    ACCESS  read-only
    STATUS  mandatory
    DESCRIPTION
     "Number of Client Sessions"
    ::=  {rsADPersistentL7SwitchingStatistics 3}

rsADPersistentL7SwitchingEntries OBJECT-TYPE
    SYNTAX  INTEGER
    ACCESS  read-only
    STATUS  mandatory
    DESCRIPTION
     "Number of Persistent L7 Switching Entries"
    ::=  {rsADPersistentL7SwitchingStatistics 4}

rsADAverageServerConnection OBJECT-TYPE
    SYNTAX  INTEGER
    ACCESS  read-only
    STATUS  mandatory
    DESCRIPTION
     "Average of Server Connections per Client"
    ::=  {rsADPersistentL7SwitchingStatistics 5}



rsWSDPersistentL7SwitchingGlobalStatistics OBJECT IDENTIFIER
    ::=  {rsWSDPersistentL7Switching 3}

rsClientRequestsParsed OBJECT-TYPE
    SYNTAX  INTEGER
    ACCESS  read-only
    STATUS  mandatory
    DESCRIPTION
     "Total client requests parsed"
    ::=  {rsWSDPersistentL7SwitchingGlobalStatistics 1}

rsClientRequestsParsedSec OBJECT-TYPE
    SYNTAX  INTEGER
    ACCESS  read-only
    STATUS  mandatory
    DESCRIPTION
     "Client requests parsed last second"
    ::=  {rsWSDPersistentL7SwitchingGlobalStatistics 2}

rsServerChanges OBJECT-TYPE
    SYNTAX  INTEGER
    ACCESS  read-only
    STATUS  mandatory
    DESCRIPTION
     "Total number of server changes"
    ::=  {rsWSDPersistentL7SwitchingGlobalStatistics 3}

rsServerChangesSec OBJECT-TYPE
    SYNTAX  INTEGER
    ACCESS  read-only
    STATUS  mandatory
    DESCRIPTION
     "Number of server changes last second"
    ::=  {rsWSDPersistentL7SwitchingGlobalStatistics 4}

rsPersistentClientRequetsParsed OBJECT-TYPE
    SYNTAX  INTEGER
    ACCESS  read-only
    STATUS  mandatory
    DESCRIPTION
     "Number of persistent request parsed
	  (starts counting from the second requst of a client TCP session)"
    ::=  {rsWSDPersistentL7SwitchingGlobalStatistics 5}

rsPersistentClientRequetsParsedSec OBJECT-TYPE
    SYNTAX  INTEGER
    ACCESS  read-only
    STATUS  mandatory
    DESCRIPTION
     "Number of persistent request parsed last second
	  (starts counting from the second requst of a client TCP session)"
    ::=  {rsWSDPersistentL7SwitchingGlobalStatistics 6}

rsWSDPersistentL7SwitchingResetGlobalStatistics OBJECT-TYPE
    SYNTAX  INTEGER {
       reset(1)
     }
    ACCESS  read-write
    STATUS  mandatory
    DESCRIPTION
      "This variable resets the global statistics of Persistent L7 Switching."
   ::= { rsWSDPersistentL7SwitchingGlobalStatistics 7 }

adL7ExpressionTable OBJECT-TYPE
	SYNTAX SEQUENCE OF AdL7ExpressionEntry
	ACCESS not-accessible
	STATUS mandatory
	DESCRIPTION
		"A table for L7 expressions. The expressions are logical operations on L7 methods."
		::= { rsWSDL7 8}

adL7ExpressionEntry OBJECT-TYPE
	SYNTAX AdL7ExpressionEntry
	ACCESS not-accessible
	STATUS mandatory
	DESCRIPTION
		" The row definition for this table."
	INDEX { adL7ExpressionName }
	::= {adL7ExpressionTable 1}

AdL7ExpressionEntry ::= SEQUENCE {
	adL7ExpressionName	DisplayString,
	adL7ExpressionValue	DisplayString,
	adL7ExpressionStatus	RowStatus
}

adL7ExpressionName OBJECT-TYPE
	SYNTAX DisplayString (SIZE(1..50))
	ACCESS read-only
	STATUS mandatory
	DESCRIPTION
	"The L7 expression name."
	::=  {adL7ExpressionEntry 1}

adL7ExpressionValue OBJECT-TYPE
	SYNTAX DisplayString (SIZE(0..255))
	ACCESS read-write
	STATUS mandatory
	DESCRIPTION
	"The L7 expression."
	::=  {adL7ExpressionEntry 2}

adL7ExpressionStatus OBJECT-TYPE
	SYNTAX RowStatus
	ACCESS read-write
	STATUS mandatory
	DESCRIPTION
	"row status field."
	::=  {adL7ExpressionEntry 3}


rsWSDRegexpURLTable OBJECT-TYPE
   SYNTAX SEQUENCE OF RsWSDRegexpURLEntry
   ACCESS not-accessible
   STATUS mandatory
   DESCRIPTION
       "Regular expressions URL table, defines the DNS resolution for farms and SuperFarms"
   ::= {rsNWSD 46}

rsWSDRegexpURLEntry OBJECT-TYPE
   SYNTAX RsWSDRegexpURLEntry
   ACCESS not-accessible
   STATUS mandatory
   DESCRIPTION
       " The row definition for this table."
   INDEX  {rsWSDRegexpURL}
   ::= {rsWSDRegexpURLTable 1}

RsWSDRegexpURLEntry  ::= SEQUENCE {
  rsWSDRegexpURL                       DisplayString,
  rsWSDRegexpURLIndex	               INTEGER,
  rsWSDRegexpURLFarmAddress            IpAddress,
  rsWSDRegexpURLSuperFarm              IpAddress,
  rsWSDRegexpURLStatus                 RowStatus,
  rsWSDRegexpURLNATAddr                IpAddress,
  rsWSDRegexpURLL4PolicyName           DisplayString,
  rsWSDRegexpPreferredResolveIP        IpAddress,
  rsWSDRegexpURLFarmName               DisplayString
}

rsWSDRegexpURL  OBJECT-TYPE
    SYNTAX DisplayString (SIZE (1..80))
    ACCESS read-only
   	STATUS mandatory
   	DESCRIPTION
     	 "The regexp URL representing the farm."
	::=  {rsWSDRegexpURLEntry 1}

rsWSDRegexpURLIndex OBJECT-TYPE
    SYNTAX INTEGER
    ACCESS read-write
    STATUS mandatory
    DESCRIPTION
    "Regular expression evaluation order."
    ::= { rsWSDRegexpURLEntry 2}

rsWSDRegexpURLFarmAddress OBJECT-TYPE
   	SYNTAX IpAddress
   	ACCESS read-only
   	STATUS mandatory
   	DESCRIPTION
     	 "IP address of the farm to use with the regexp URL."
	::=  {rsWSDRegexpURLEntry 3}

rsWSDRegexpURLSuperFarm OBJECT-TYPE
    SYNTAX IpAddress
    ACCESS read-write
   	STATUS mandatory
   	DESCRIPTION
     	 "The SuperFarm address to resolve for the regexp URL"
	::=  {rsWSDRegexpURLEntry 4}

rsWSDRegexpURLStatus OBJECT-TYPE
    SYNTAX RowStatus
    ACCESS read-write
   	STATUS mandatory
   	DESCRIPTION
     	 "Row status for the regexp URL."
	::=  {rsWSDRegexpURLEntry 5}


rsWSDRegexpURLNATAddr OBJECT-TYPE
   	SYNTAX IpAddress
   	ACCESS read-write
   	STATUS mandatory
   	DESCRIPTION
     	 "NAT IP address of the farm to use with the regexp URL."
	::=  {rsWSDRegexpURLEntry 6}

 rsWSDRegexpURLL4PolicyName  OBJECT-TYPE
    SYNTAX DisplayString (SIZE (1..50))
   	ACCESS read-write
   	STATUS mandatory
   	DESCRIPTION
     	 "L4Policy Name"
	::=  {rsWSDRegexpURLEntry 7}

rsWSDRegexpPreferredResolveIP OBJECT-TYPE
   	SYNTAX IpAddress
   	ACCESS read-write
   	STATUS mandatory
   	DESCRIPTION
     	 "Configures to which IP the host name should be resolved preferably."
	::=  {rsWSDRegexpURLEntry 8}

rsWSDRegexpURLFarmName OBJECT-TYPE
    SYNTAX DisplayString (SIZE(1..50))
    ACCESS read-write
   	STATUS mandatory
   	DESCRIPTION
        "The name of the farm to use with the regexp URL."
	::=  {rsWSDRegexpURLEntry 9}

-- No-Service Page table
rsWSDNoSrvPageTable OBJECT-TYPE
   SYNTAX SEQUENCE OF RsWSDNoSrvPageEntry
   ACCESS not-accessible
   STATUS mandatory
   DESCRIPTION
          "In this table the WSD saves the No-Service Page (sorry page)
           that the user config."
   ::= {rsNWSD 47}

rsWSDNoSrvPageEntry OBJECT-TYPE
    SYNTAX RsWSDNoSrvPageEntry
    ACCESS not-accessible
    STATUS mandatory
    DESCRIPTION
       " The row definition for this table."
   INDEX  { rsWSDNoSrvPageFarmAddress ,
            rsWSDNoSrvPageIndex  }
   ::= {rsWSDNoSrvPageTable 1}


RsWSDNoSrvPageEntry  ::= SEQUENCE {
   rsWSDNoSrvPageFarmAddress     IpAddress,
   rsWSDNoSrvPageIndex           INTEGER,
   rsWSDNoSrvPageSize            INTEGER,
   rsWSDNoSrvPageData            OCTET STRING,
   rsWSDNoSrvPageStatus          RowStatus
}

rsWSDNoSrvPageFarmAddress OBJECT-TYPE
    SYNTAX IpAddress
    ACCESS  read-only
    STATUS  mandatory
    DESCRIPTION
      "The IP Address of the farm."
    ::= {rsWSDNoSrvPageEntry 1}


rsWSDNoSrvPageIndex OBJECT-TYPE
    SYNTAX  INTEGER
    ACCESS  read-only
    STATUS  mandatory
    DESCRIPTION
      "The No-Service page is saved in 80 bytes pieces the index
       tell which piece is this entry."
 ::=  {rsWSDNoSrvPageEntry 2}


rsWSDNoSrvPageSize OBJECT-TYPE
    SYNTAX  INTEGER
    ACCESS  read-write
    STATUS  mandatory
    DESCRIPTION
      "The total size of No-Service page (all the rows holds the same value)."
 ::=  {rsWSDNoSrvPageEntry 3}


rsWSDNoSrvPageData OBJECT-TYPE
    SYNTAX OCTET STRING (SIZE(1..80))
    ACCESS  read-write
    STATUS  mandatory
    DESCRIPTION
      "The one peice of the No-Service page."
 ::=  {rsWSDNoSrvPageEntry 4}


rsWSDNoSrvPageStatus OBJECT-TYPE
   SYNTAX  RowStatus
   ACCESS  read-write
   STATUS  mandatory
   DESCRIPTION
       "The  status of this entry."
   ::= {rsWSDNoSrvPageEntry 5}


-- AppDirector's No-Service Page table
rsADNoSrvPageTable OBJECT-TYPE
   SYNTAX SEQUENCE OF RsADNoSrvPageEntry
   ACCESS not-accessible
   STATUS mandatory
   DESCRIPTION
          "In this table the AppDirector saves the No-Service Page (sorry page)
           that the user config."
   ::= {rsNWSD 64}

rsADNoSrvPageEntry OBJECT-TYPE
    SYNTAX RsADNoSrvPageEntry
    ACCESS not-accessible
    STATUS mandatory
    DESCRIPTION
       " The row definition for this table."
   INDEX  { rsADNoSrvPageFarmName ,
            rsADNoSrvPageIndex  }
   ::= {rsADNoSrvPageTable 1}


RsADNoSrvPageEntry  ::= SEQUENCE {
   rsADNoSrvPageFarmName        DisplayString,
   rsADNoSrvPageIndex           INTEGER,
   rsADNoSrvPageStatus          RowStatus,
   rsADNoSrvPageSize            INTEGER,
   rsADNoSrvPageData            OCTET STRING
}

rsADNoSrvPageFarmName OBJECT-TYPE
    SYNTAX DisplayString (SIZE(1..50))
    ACCESS  read-only
    STATUS  mandatory
    DESCRIPTION
      "The name of the farm."
    ::= {rsADNoSrvPageEntry 1}

rsADNoSrvPageIndex OBJECT-TYPE
    SYNTAX  INTEGER
    ACCESS  read-only
    STATUS  mandatory
    DESCRIPTION
      "The No-Service page is saved in 80 bytes pieces the index
       tell which piece is this entry."
 ::=  {rsADNoSrvPageEntry 2}

rsADNoSrvPageStatus OBJECT-TYPE
   SYNTAX  RowStatus
   ACCESS  read-write
   STATUS  mandatory
   DESCRIPTION
       "The  status of this entry."
   ::= {rsADNoSrvPageEntry 3}

rsADNoSrvPageSize OBJECT-TYPE
    SYNTAX  INTEGER
    ACCESS  read-write
    STATUS  mandatory
    DESCRIPTION
      "The total size of No-Service page (all the rows holds the same value)."
 ::=  {rsADNoSrvPageEntry 4}


rsADNoSrvPageData OBJECT-TYPE
    SYNTAX OCTET STRING (SIZE(1..80))
    ACCESS  read-write
    STATUS  mandatory
    DESCRIPTION
      "The one peice of the No-Service page."
 ::=  {rsADNoSrvPageEntry 5}



rsNWSDSegment  OBJECT IDENTIFIER ::= { rsNWSD 48 }

rsWSDSegmentOpMode OBJECT-TYPE
   SYNTAX INTEGER {
        port(1),
        vlantag(2),
        disable(3)
   }
   ACCESS  read-write
   STATUS  mandatory
   DESCRIPTION
       " port - segments are based on the device ports
         vlan tag - segments are based on VLAN tags.
         disable -feature is disabled"
   DEFVAL { 3 }
   ::=  { rsNWSDSegment  1}

rsWSDNonSegmentAction OBJECT-TYPE
   SYNTAX INTEGER {
        forward (1),
        discard (2),
        defaultGW (3)
   }
   ACCESS  read-write
   STATUS  mandatory
   DESCRIPTION
       " forward - regular mode without segmentation.
         discard - discard packets destined to segments.
         DefaultGW - change destination packet to the default gateway."
   DEFVAL { 1 }
   ::=  { rsNWSDSegment  2}

rsWSDSgmntSharedPort OBJECT-TYPE
   SYNTAX INTEGER
   ACCESS  read-write
   STATUS  obsolete
   DESCRIPTION
       "Deprecated"
   DEFVAL { 0 }
   ::=  { rsNWSDSegment  5}


rsWSDSgmntSharedPortList OBJECT-TYPE
   SYNTAX DisplayString
   ACCESS  read-write
   STATUS  mandatory
   DESCRIPTION
       "The device wouldn't handle segmentation to all session arrives from these ports."
   ::=  { rsNWSDSegment  7}

rsWSDNonSegmentSharedVip OBJECT-TYPE
   SYNTAX INTEGER {
	   enable(1),
	   disable(2)
   }
   ACCESS  read-write
   STATUS  mandatory
   DESCRIPTION
       "This flag indicates  segmentation prevention for sessions from server
	     to L4 policy with this segment. In this case, when the flag is up, the segmentation will not be honored."
   DEFVAL { disable }
   ::=  { rsNWSDSegment 6}



rsWSDSegmentTable OBJECT-TYPE
   SYNTAX SEQUENCE OF RsWSDSegmentEntry
   ACCESS not-accessible
   STATUS mandatory
   DESCRIPTION
      "The table that contains WSD Segments."
   ::= { rsNWSDSegment  3}

rsWSDSegmentEntry  OBJECT-TYPE
   SYNTAX RsWSDSegmentEntry
   ACCESS not-accessible
   STATUS mandatory
   DESCRIPTION
      "The row definition for segment table."
   INDEX { rsWSDSegmentName }
   ::= { rsWSDSegmentTable 1 }

RsWSDSegmentEntry ::= SEQUENCE {
  rsWSDSegmentName      DisplayString,
  rsWSDSegmentPortList 	DisplayString,
  rsWSDSegmentVLANTAG   INTEGER,
  rsWSDSegmentRowStatus RowStatus,
  rsWSDSegmentVLANTAGList   DisplayString,
  rsWSDSegmentPreventSgmntForSrvrRqst INTEGER,
  rsWSDBackendSegmentation   INTEGER
}

rsWSDSegmentName OBJECT-TYPE
   SYNTAX DisplayString (SIZE(1..20))
   ACCESS read-only
   STATUS mandatory
   DESCRIPTION
      "Segments Name."
   ::=  { rsWSDSegmentEntry 1}

rsWSDSegmentPortList OBJECT-TYPE
   SYNTAX DisplayString (SIZE(0..255))
   ACCESS read-write
   STATUS mandatory
   DESCRIPTION
      "Port List. Seperated by semicolons"
   ::=  { rsWSDSegmentEntry 2}

rsWSDSegmentVLANTAG   OBJECT-TYPE
   SYNTAX INTEGER (0..4095)
   ACCESS read-write
   STATUS mandatory
   DESCRIPTION
      "VLAN TAG associated with this segment"
   DEFVAL { 0 }
   ::=  { rsWSDSegmentEntry 3}

rsWSDSegmentRowStatus  OBJECT-TYPE
    SYNTAX  RowStatus
    ACCESS  read-write
    STATUS  mandatory
    DESCRIPTION
       "This variable indicates the administrative status of this entry.
        Used to delete an entry of this table."
    ::=  { rsWSDSegmentEntry 4}

rsWSDSegmentVLANTAGList   OBJECT-TYPE
   SYNTAX DisplayString (SIZE(0..255))
   ACCESS read-write
   STATUS mandatory
   DESCRIPTION
      "VLAN TAG List associated with this segment"
   ::=  { rsWSDSegmentEntry 5}

rsWSDSegmentPreventSgmntForSrvrRqst  OBJECT-TYPE
    SYNTAX INTEGER {
	   enable(1),
	   disable(2)
	  }
    ACCESS  read-write
    STATUS  mandatory
    DESCRIPTION
       "This  flag indicates  segmentation prevention for sessions from server
	     to L4 policy with this segment. In this case, when the flag is up, the segmentation will not be honored."
	DEFVAL { disable }
    ::=  { rsWSDSegmentEntry 6}

rsWSDBackendSegmentation   OBJECT-TYPE
    SYNTAX INTEGER {
	   enable(1),
	   disable(2)
	  }
    ACCESS  read-write
    STATUS  mandatory
    DESCRIPTION
       "This parameter defines whether to perform segmentation or not for traffic to VIPs belonging to this segment
        when the selected server belongs to a different segment."
	DEFVAL { enable }
    ::=  { rsWSDSegmentEntry 7}

rsWSDSegmentNHRTable OBJECT-TYPE
   SYNTAX SEQUENCE OF RsWSDSegmentNHREntry
   ACCESS not-accessible
   STATUS mandatory
   DESCRIPTION
          "The table that contains WSD associations of Segments to the Next Hop Routers."
   ::= { rsNWSDSegment  4 }

rsWSDSegmentNHREntry OBJECT-TYPE
    SYNTAX RsWSDSegmentNHREntry
    ACCESS not-accessible
    STATUS mandatory
    DESCRIPTION
       " The row definition for Segment-NHR table."
   INDEX  { rsWSDSegmentNHRName }
   ::= {rsWSDSegmentNHRTable 1}

RsWSDSegmentNHREntry  ::= SEQUENCE {
  rsWSDSegmentNHRName              DisplayString,
  rsWSDSegmentNHRNHRIP             IpAddress,
  rsWSDSegmentNHRBackupNHRIP       IpAddress,
  rsWSDSegmentNHRNHRWeight         INTEGER,
  rsWSDSegmentNHRBackupWeight      INTEGER,
  rsWSDSegmentNHRAdminLoadSharing  FeatureStatus,
  rsWSDSegmentNHRNoRouteAction     INTEGER,
  rsWSDSegmentNHRRowStatus         RowStatus,
  rsWSDSegmentNHRFlags             	   BitFlag,
  rsWSDSegmentNHRV4NHRIPAddrType       InetAddressType,
  rsWSDSegmentNHRV4NHRIPAddr           InetAddress,
  rsWSDSegmentNHRV4BackupNHRIPAddrType InetAddressType,
  rsWSDSegmentNHRV4BackupNHRIPAddr     InetAddress,
  rsWSDSegmentNHRV6NHRIPAddrType       InetAddressType,
  rsWSDSegmentNHRV6NHRIPAddr           InetAddress,
  rsWSDSegmentNHRV6BackupNHRIPAddrType InetAddressType,
  rsWSDSegmentNHRV6BackupNHRIPAddr     InetAddress



}

rsWSDSegmentNHRName OBJECT-TYPE
    SYNTAX DisplayString (SIZE(1..20))
    ACCESS read-only
    STATUS mandatory
    DESCRIPTION
      "The Segments Index."
  ::= {rsWSDSegmentNHREntry 1}

-- obsolete
rsWSDSegmentNHRNHRIP OBJECT-TYPE
    SYNTAX IpAddress
    ACCESS read-write
    STATUS optional
    DESCRIPTION
      "THIS FIELD IS NOT IN USE"
	DEFVAL {0}
  ::= { rsWSDSegmentNHREntry 2}

-- obsolete
rsWSDSegmentNHRBackupNHRIP OBJECT-TYPE
    SYNTAX IpAddress
    ACCESS read-write
    STATUS optional
    DESCRIPTION
      "THIS FIELD IS NOT IN USE"
	DEFVAL {0}
  ::= { rsWSDSegmentNHREntry 3}

rsWSDSegmentNHRNHRWeight OBJECT-TYPE
    SYNTAX INTEGER (1..100)
    ACCESS read-write
    STATUS optional
    DESCRIPTION
      "The NHR's weight."
    DEFVAL  { 1 }
  ::= { rsWSDSegmentNHREntry 4}

rsWSDSegmentNHRBackupWeight OBJECT-TYPE
    SYNTAX INTEGER (1..100)
    ACCESS read-write
    STATUS optional
    DESCRIPTION
      "The backup NHR's weight."
    DEFVAL  { 1 }
  ::= { rsWSDSegmentNHREntry 5}

rsWSDSegmentNHRAdminLoadSharing OBJECT-TYPE
    SYNTAX FeatureStatus
    ACCESS read-write
    STATUS optional
    DESCRIPTION
      "Enable/Disable NHR Load Sharing for this SegmentNHR."
    DEFVAL  { disable }
  ::= { rsWSDSegmentNHREntry 6}

rsWSDSegmentNHRNoRouteAction OBJECT-TYPE
    SYNTAX INTEGER {
    discard(1),
    regRoute(2) }
    ACCESS read-write
    STATUS optional
    DESCRIPTION
      "The action taken when NHR and Backup NHR are unavailable."
    DEFVAL  { 1 }
  ::= {rsWSDSegmentNHREntry 7}

rsWSDSegmentNHRRowStatus OBJECT-TYPE
   SYNTAX RowStatus
   ACCESS read-write
   STATUS mandatory
   DESCRIPTION
      "Row status for the current row."
   ::=  { rsWSDSegmentNHREntry 8}

rsWSDSegmentNHRFlags OBJECT-TYPE
    SYNTAX    BitFlag
    ACCESS    read-only
    STATUS    optional
    DESCRIPTION
       "Flags for internal use."
    ::= { rsWSDSegmentNHREntry 9 }

rsWSDSegmentNHRV4NHRIPAddrType OBJECT-TYPE
    SYNTAX InetAddressType
    ACCESS read-write
    STATUS optional
    DESCRIPTION
      "The IP V4 address type of Next Hop Router."
	DEFVAL  { ipv4 }
  ::= { rsWSDSegmentNHREntry 10}

rsWSDSegmentNHRV4NHRIPAddr OBJECT-TYPE
    SYNTAX InetAddress
    ACCESS read-write
    STATUS optional
    DESCRIPTION
      "The IP V4 of Next Hop Router."
  ::= { rsWSDSegmentNHREntry 11}

rsWSDSegmentNHRV4BackupNHRIPAddrType OBJECT-TYPE
    SYNTAX InetAddressType
    ACCESS read-write
    STATUS optional
    DESCRIPTION
      "The IP V4 of the Backup to Next Hop Router."
	DEFVAL  { ipv4 }
  ::= { rsWSDSegmentNHREntry 12}

rsWSDSegmentNHRV4BackupNHRIPAddr OBJECT-TYPE
    SYNTAX InetAddress
    ACCESS read-write
    STATUS optional
    DESCRIPTION
      "The IP V4 of the Backup to Next Hop Router."
  ::= { rsWSDSegmentNHREntry 13}

rsWSDSegmentNHRV6NHRIPAddrType OBJECT-TYPE
    SYNTAX InetAddressType
    ACCESS read-write
    STATUS optional
    DESCRIPTION
      "The IP V6 address type of Next Hop Router."
	DEFVAL  { ipv6 }
  ::= { rsWSDSegmentNHREntry 14}

rsWSDSegmentNHRV6NHRIPAddr OBJECT-TYPE
    SYNTAX InetAddress
    ACCESS read-write
    STATUS optional
    DESCRIPTION
      "The IP V6 of Next Hop Router."
  ::= { rsWSDSegmentNHREntry 15}

rsWSDSegmentNHRV6BackupNHRIPAddrType OBJECT-TYPE
    SYNTAX InetAddressType
    ACCESS read-write
    STATUS optional
    DESCRIPTION
      "The IP V6 of the Backup to Next Hop Router."
	DEFVAL  { ipv6 }
  ::= { rsWSDSegmentNHREntry 16}

rsWSDSegmentNHRV6BackupNHRIPAddr OBJECT-TYPE
    SYNTAX InetAddress
    ACCESS read-write
    STATUS optional
    DESCRIPTION
      "The IP V6 of the Backup to Next Hop Router."
  ::= { rsWSDSegmentNHREntry 17}

rsWSDRadiusAttributeAging OBJECT-TYPE
    SYNTAX INTEGER
    ACCESS  read-write
    STATUS  mandatory
    DESCRIPTION
      "Aging for RADIUS attribute table."
    DEFVAL {60}
   ::= {rsNWSD 49}

rsNWSDDNS  OBJECT IDENTIFIER ::= { rsNWSD 51 }

rsWSDStaticDNSPersistencyTable OBJECT-TYPE
   SYNTAX SEQUENCE OF RsWSDStaticDNSPersistencyEntry
   ACCESS not-accessible
   STATUS mandatory
   DESCRIPTION
          "This table is used to statically assign preferred DNS answers for ranges of requesters' IP addresses. "
   ::= {rsNWSDDNS 1}

rsWSDStaticDNSPersistencyEntry OBJECT-TYPE
    SYNTAX RsWSDStaticDNSPersistencyEntry
    ACCESS not-accessible
    STATUS  mandatory
    DESCRIPTION
       " The row definition for the static DNS persistency table."
   INDEX  {rsWSDStaticDNSFarmAddress,
           rsWSDStaticDNSRangeFrom }
   ::= {rsWSDStaticDNSPersistencyTable 1}

RsWSDStaticDNSPersistencyEntry ::= SEQUENCE {
  rsWSDStaticDNSFarmAddress  IpAddress,
  rsWSDStaticDNSRangeFrom    IpAddress,
  rsWSDStaticDNSRangeTo      IpAddress,
  rsWSDStaticDNSStatus       RowStatus,
  rsWSDStaticDNSPreferredVIP IpAddress,
  rsWSDStaticDNSAlternateVIP IpAddress
  }

rsWSDStaticDNSFarmAddress OBJECT-TYPE
    SYNTAX IpAddress
    ACCESS  read-only
    STATUS  mandatory
    DESCRIPTION
      "The IP Address of the farm."
    ::= { rsWSDStaticDNSPersistencyEntry 1}

rsWSDStaticDNSRangeFrom OBJECT-TYPE
    SYNTAX IpAddress
    ACCESS  read-only
    STATUS  mandatory
    DESCRIPTION
      " The IP Address of the lower boundary of the interval."
    ::= { rsWSDStaticDNSPersistencyEntry 2}

rsWSDStaticDNSRangeTo OBJECT-TYPE
    SYNTAX IpAddress
    ACCESS  read-write
    STATUS  mandatory
    DESCRIPTION
      " The IP Address of the upper boundary of the interval."
    ::= { rsWSDStaticDNSPersistencyEntry 3}

rsWSDStaticDNSStatus OBJECT-TYPE
   SYNTAX RowStatus
   ACCESS read-write
   STATUS mandatory
   DESCRIPTION
      "The status of this entry"
   ::=  { rsWSDStaticDNSPersistencyEntry 4}

rsWSDStaticDNSPreferredVIP OBJECT-TYPE
    SYNTAX IpAddress
    ACCESS  read-write
    STATUS  mandatory
    DESCRIPTION
      "VIP to use in DNS reply."
    ::= { rsWSDStaticDNSPersistencyEntry 5}

rsWSDStaticDNSAlternateVIP OBJECT-TYPE
    SYNTAX IpAddress
    ACCESS  read-write
    STATUS  mandatory
    DESCRIPTION
      "VIP to use in DNS reply in case the preferred VIP is not in service or
	   the two records in reply flag is enabled."
    ::= { rsWSDStaticDNSPersistencyEntry 6}


rsADStaticDNSPersistencyTable OBJECT-TYPE
   SYNTAX SEQUENCE OF RsADStaticDNSPersistencyEntry
   ACCESS not-accessible
   STATUS mandatory
   DESCRIPTION
          "This table is used to statically assign preferred DNS answers for ranges of requesters' IP addresses. "
   ::= {rsNWSDDNS 7}

rsADStaticDNSPersistencyEntry OBJECT-TYPE
    SYNTAX RsADStaticDNSPersistencyEntry
    ACCESS not-accessible
    STATUS  mandatory
    DESCRIPTION
       " The row definition for the static DNS persistency table."
   INDEX  {rsADStaticDNSFarmName,
           rsADStaticDNSRangeFrom }
   ::= {rsADStaticDNSPersistencyTable 1}

RsADStaticDNSPersistencyEntry ::= SEQUENCE {
  rsADStaticDNSFarmName     DisplayString,
  rsADStaticDNSRangeFrom    IpAddress,
  rsADStaticDNSStatus       RowStatus,
  rsADStaticDNSRangeTo      IpAddress,
  rsADStaticDNSPreferredVIP IpAddress,
  rsADStaticDNSAlternateVIP IpAddress
}

rsADStaticDNSFarmName OBJECT-TYPE
    SYNTAX  DisplayString (SIZE(1..50))
    ACCESS  read-only
    STATUS  mandatory
    DESCRIPTION
      "The name of the farm."
    ::= { rsADStaticDNSPersistencyEntry 1}

rsADStaticDNSRangeFrom OBJECT-TYPE
    SYNTAX  IpAddress
    ACCESS  read-only
    STATUS  mandatory
    DESCRIPTION
      " The IP Address of the lower boundary of the interval."
    ::= { rsADStaticDNSPersistencyEntry 2}

rsADStaticDNSStatus OBJECT-TYPE
   SYNTAX  RowStatus
   ACCESS  read-write
   STATUS  mandatory
   DESCRIPTION
      "The status of this entry"
   ::=  { rsADStaticDNSPersistencyEntry 3}

rsADStaticDNSRangeTo OBJECT-TYPE
    SYNTAX  IpAddress
    ACCESS  read-write
    STATUS  mandatory
    DESCRIPTION
      " The IP Address of the upper boundary of the interval."
    ::= { rsADStaticDNSPersistencyEntry 4}

rsADStaticDNSPreferredVIP OBJECT-TYPE
    SYNTAX  IpAddress
    ACCESS  read-write
    STATUS  mandatory
    DESCRIPTION
      "VIP to use in DNS reply."
    ::= { rsADStaticDNSPersistencyEntry 5}

rsADStaticDNSAlternateVIP OBJECT-TYPE
    SYNTAX  IpAddress
    ACCESS  read-write
    STATUS  mandatory
    DESCRIPTION
      "VIP to use in DNS reply in case the preferred VIP is not in service or
	   the two records in reply flag is enabled."
    ::= { rsADStaticDNSPersistencyEntry 6}

rsNADStaticDNSPersistencyTable OBJECT-TYPE
   SYNTAX SEQUENCE OF RsNADStaticDNSPersistencyEntry
   ACCESS not-accessible
   STATUS mandatory
   DESCRIPTION
          "This table is used to statically assign preferred DNS answers for ranges of requesters' IP addresses. "
   ::= {rsNWSDDNS 8}

rsNADStaticDNSPersistencyEntry OBJECT-TYPE
    SYNTAX RsNADStaticDNSPersistencyEntry
    ACCESS not-accessible
    STATUS  mandatory
    DESCRIPTION
       " The row definition for the static DNS persistency table."
   INDEX  {rsNADStaticDNSFarmName,
		   rsNADStaticDNSRangeFromAddrType,
           rsNADStaticDNSRangeFrom }
   ::= {rsNADStaticDNSPersistencyTable 1}

RsNADStaticDNSPersistencyEntry ::= SEQUENCE {
  rsNADStaticDNSFarmName     			DisplayString,
  rsNADStaticDNSRangeFromAddrType   	InetAddressType,
  rsNADStaticDNSRangeFrom    			InetAddress,
  rsNADStaticDNSRangeToAddrType   		InetAddressType,
  rsNADStaticDNSRangeTo      			InetAddress,
  rsNADStaticDNSPreferredVIPAddrTypeV4	InetAddressType,
  rsNADStaticDNSPreferredVIPV4 			InetAddress,
  rsNADStaticDNSAlternateVIPAddrTypeV4 	InetAddressType,
  rsNADStaticDNSAlternateVIPV4 			InetAddress,
  rsNADStaticDNSPreferredVIPAddrTypeV6	InetAddressType,
  rsNADStaticDNSPreferredVIPV6 			InetAddress,
  rsNADStaticDNSAlternateVIPAddrTypeV6 	InetAddressType,
  rsNADStaticDNSAlternateVIPV6 			InetAddress,
  rsNADStaticDNSStatus       			RowStatus
}

rsNADStaticDNSFarmName OBJECT-TYPE
    SYNTAX  DisplayString (SIZE(1..50))
    ACCESS  read-only
    STATUS  mandatory
    DESCRIPTION
      "The name of the farm."
    ::= { rsNADStaticDNSPersistencyEntry 1}

rsNADStaticDNSRangeFromAddrType OBJECT-TYPE
    SYNTAX  InetAddressType
    ACCESS  read-only
    STATUS  mandatory
    DESCRIPTION
      " The Type of IP Address of the lower boundary of the interval."
	DEFVAL{ipv4}
    ::= { rsNADStaticDNSPersistencyEntry 2}

rsNADStaticDNSRangeFrom OBJECT-TYPE
    SYNTAX  InetAddress
    ACCESS  read-only
    STATUS  mandatory
    DESCRIPTION
      " The IP Address of the lower boundary of the interval."
	DEFVAL{"0.0.0.0"}
    ::= { rsNADStaticDNSPersistencyEntry 3}

rsNADStaticDNSRangeToAddrType OBJECT-TYPE
    SYNTAX  InetAddressType
    ACCESS  read-write
    STATUS  mandatory
    DESCRIPTION
      " The Type of IP Address of the upper boundary of the interval."
	DEFVAL  { ipv4 }
    ::= { rsNADStaticDNSPersistencyEntry 4}

rsNADStaticDNSRangeTo OBJECT-TYPE
    SYNTAX  InetAddress
    ACCESS  read-write
    STATUS  mandatory
    DESCRIPTION
      " The IP Address of the upper boundary of the interval."
	DEFVAL{"0.0.0.0"}
    ::= { rsNADStaticDNSPersistencyEntry 5}

rsNADStaticDNSPreferredVIPAddrTypeV4 OBJECT-TYPE
    SYNTAX  InetAddressType
    ACCESS  read-write
    STATUS  optional
    DESCRIPTION
      "The IP address type of VIP IPv4 to use in DNS reply in case the preferred VIP is not in service or
	   the two records in reply flag is enabled."
	DEFVAL  { ipv4 }
    ::= { rsNADStaticDNSPersistencyEntry 6}

rsNADStaticDNSPreferredVIPV4 OBJECT-TYPE
    SYNTAX  InetAddress
    ACCESS  read-write
    STATUS  optional
    DESCRIPTION
      "VIP IPv4 to use in DNS reply in case the preferred VIP IPv4 is not in service or
	   the two records in reply flag is enabled."
	DEFVAL{"0.0.0.0"}
    ::= { rsNADStaticDNSPersistencyEntry 7}

rsNADStaticDNSAlternateVIPAddrTypeV4 OBJECT-TYPE
    SYNTAX  InetAddressType
    ACCESS  read-write
    STATUS  optional
    DESCRIPTION
      "The IP address type of VIP IPv4 to use in DNS reply in case the preferred VIP IPv4 is not in service or
	   the two records in reply flag is enabled."
	DEFVAL  { ipv4 }
    ::= { rsNADStaticDNSPersistencyEntry 8}

rsNADStaticDNSAlternateVIPV4 OBJECT-TYPE
    SYNTAX  InetAddress
    ACCESS  read-write
    STATUS  optional
    DESCRIPTION
      "VIP IPv4 to use in DNS reply in case the preferred VIP IPv4 is not in service or
	   the two records in reply flag is enabled."
	DEFVAL{"0.0.0.0"}
    ::= { rsNADStaticDNSPersistencyEntry 9}

rsNADStaticDNSPreferredVIPAddrTypeV6 OBJECT-TYPE
    SYNTAX  InetAddressType
    ACCESS  read-write
    STATUS  optional
    DESCRIPTION
      "The IP address type of VIP IPv6 to use in DNS reply in case the preferred VIP is not in service or
	   the two records in reply flag is enabled."
	DEFVAL  { ipv6 }
    ::= { rsNADStaticDNSPersistencyEntry 10}

rsNADStaticDNSPreferredVIPV6 OBJECT-TYPE
    SYNTAX  InetAddress
    ACCESS  read-write
    STATUS  optional
    DESCRIPTION
      "VIP IPv6 to use in DNS reply in case the preferred VIP IPv6 is not in service or
	   the two records in reply flag is enabled."
	DEFVAL{"::"}
    ::= { rsNADStaticDNSPersistencyEntry 11}

rsNADStaticDNSAlternateVIPAddrTypeV6 OBJECT-TYPE
    SYNTAX  InetAddressType
    ACCESS  read-write
    STATUS  optional
    DESCRIPTION
      "The IP address type of VIP IPv6 to use in DNS reply in case the preferred VIP IPv6 is not in service or
	   the two records in reply flag is enabled."
	DEFVAL  { ipv6 }
    ::= { rsNADStaticDNSPersistencyEntry 12}

rsNADStaticDNSAlternateVIPV6 OBJECT-TYPE
    SYNTAX  InetAddress
    ACCESS  read-write
    STATUS  optional
    DESCRIPTION
      "VIP IPv6 to use in DNS reply in case the preferred VIP IPv6 is not in service or
	   the two records in reply flag is enabled."
	DEFVAL{"::"}
    ::= { rsNADStaticDNSPersistencyEntry 13}

rsNADStaticDNSStatus OBJECT-TYPE
   SYNTAX  RowStatus
   ACCESS  read-write
   STATUS  mandatory
   DESCRIPTION
      "The status of this entry"
   ::=  { rsNADStaticDNSPersistencyEntry 14}


rsWSDDNSMirrorPercentage  OBJECT-TYPE
   SYNTAX INTEGER (1..100)
   ACCESS  read-write
   STATUS  mandatory
   DESCRIPTION
       "The percent of the DNS persistency table to back up"
   DEFVAL { 100 }
   ::=  { rsNWSDDNS 2}

rsWSDDNSMirrorProtocolMode OBJECT-TYPE
    SYNTAX  FeatureStatus
    ACCESS  read-write
    STATUS  mandatory
    DESCRIPTION
      "Enable/Disable of the dns mirror protocol mode."
    DEFVAL { disable }
    ::=  { rsNWSDDNS 3}

rsWSDDNSMirrorPollingTime  OBJECT-TYPE
   SYNTAX INTEGER
   ACCESS  read-write
   STATUS  mandatory
   DESCRIPTION
       "The polling time in seconds of the DNS mirror messages"
   DEFVAL { 10 }
   ::=  { rsNWSDDNS 4}

rsWSDDNSPersistencyParametersTable OBJECT-TYPE
   SYNTAX SEQUENCE OF RsWSDDNSPersistencyParametersEntry
   ACCESS not-accessible
   STATUS mandatory
   DESCRIPTION
          "This table defines the DNS Persistency Parameters used for a Farm"
   ::= {rsNWSDDNS 5}

rsWSDDNSPersistencyParametersEntry OBJECT-TYPE
   SYNTAX RsWSDDNSPersistencyParametersEntry
   ACCESS not-accessible
   STATUS  mandatory
   DESCRIPTION
       " The row definition for the DNS Persistency Parameters Table."
   INDEX  {rsWSDDNSPersistencyParametersFarm}
   ::= {rsWSDDNSPersistencyParametersTable 1}


RsWSDDNSPersistencyParametersEntry ::= SEQUENCE {
  rsWSDDNSPersistencyParametersFarm                IpAddress,
  rsWSDDNSPersistencyParametersStatus              FeatureStatus,
  rsWSDDNSPersistencyParametersMode                INTEGER,
  rsWSDDNSPersistencyParametersStaticMode          FeatureStatus,
  rsWSDDNSPersistencyParametersAgingMode           INTEGER,
  rsWSDDNSPersistencyParametersAgingTime           INTEGER,
  rsWSDDNSPersistencyParametersDynamicTableMode    INTEGER,
  rsWSDDNSPersistencyParametersGroupingMask        IpAddress
  }

rsWSDDNSPersistencyParametersFarm OBJECT-TYPE
    SYNTAX IpAddress
    ACCESS  read-only
    STATUS  mandatory
    DESCRIPTION
      "The IP of the Farm that use the specified parameters"
    ::= { rsWSDDNSPersistencyParametersEntry 1 }

rsWSDDNSPersistencyParametersStatus OBJECT-TYPE
   SYNTAX FeatureStatus
   ACCESS  read-write
   STATUS  mandatory
   DESCRIPTION
       "Enable/disable the use of DNS persistency for the Farm."
   DEFVAL { disable }
   ::=  { rsWSDDNSPersistencyParametersEntry 2 }

rsWSDDNSPersistencyParametersMode OBJECT-TYPE
   SYNTAX INTEGER {
        loadBalancing(1),
        hash(2)
   }
   ACCESS  read-write
   STATUS  mandatory
   DESCRIPTION
       "Set how to select the VIP used in DNS replies for the farm:
	   loadBalancing - usual load balancing algorithm
	   hash - static hash on client IP"
   DEFVAL { loadBalancing }
   ::=  { rsWSDDNSPersistencyParametersEntry 3 }

rsWSDDNSPersistencyParametersStaticMode OBJECT-TYPE
   SYNTAX FeatureStatus
   ACCESS  read-write
   STATUS  mandatory
   DESCRIPTION
       "Enable/disable use of static DNS persistency table for the farm"
   DEFVAL { disable }
   ::=  { rsWSDDNSPersistencyParametersEntry 4 }


rsWSDDNSPersistencyParametersAgingMode OBJECT-TYPE
SYNTAX INTEGER {
   inactivity(1),
   fixed(2) }
   ACCESS  read-write
   STATUS  mandatory
   DESCRIPTION
"Aging mode for entries in the Dynamic DNS persistency table:
Inactivity Timeout - aging timer is restarted when an entry is used
Fixed Timeout - the entry is removed when its time-to-live expires."
   DEFVAL { inactivity }
   ::=  { rsWSDDNSPersistencyParametersEntry 5 }

rsWSDDNSPersistencyParametersAgingTime  OBJECT-TYPE
   SYNTAX INTEGER
   ACCESS  read-write
   STATUS  mandatory
   DESCRIPTION
"Aging time for entries in the DNS persistency table in seconds"
   DEFVAL { 60 }
   ::=  { rsWSDDNSPersistencyParametersEntry 6 }

rsWSDDNSPersistencyParametersDynamicTableMode OBJECT-TYPE
   SYNTAX INTEGER {
        sourceIpAndHostname(1),
        sourceIpOnly       (2)
   }
   ACCESS  read-write
   STATUS  mandatory
   DESCRIPTION
       "The mode of the Dynamic DNS Persistency Table:
        sourceIpAndHostname:
          Separate entries are used for requests from the same source IP and different Hostnames.
        sourceIpOnly:
          Requests from the same source IP and different Hostnames will use the same entry in the dynamic table."
   DEFVAL { sourceIpOnly }
   ::=  { rsWSDDNSPersistencyParametersEntry 7 }

rsWSDDNSPersistencyParametersGroupingMask OBJECT-TYPE
    SYNTAX IpAddress
    ACCESS  read-write
    STATUS  mandatory
    DESCRIPTION
      "IP address mask"
    ::= { rsWSDDNSPersistencyParametersEntry 8 }



rsADDNSPersistencyParametersTable OBJECT-TYPE
   SYNTAX SEQUENCE OF RsADDNSPersistencyParametersEntry
   ACCESS not-accessible
   STATUS mandatory
   DESCRIPTION
          "This table defines the AS Persistency Parameters used for a Farm"
   ::= {rsNWSDDNS 6}

rsADDNSPersistencyParametersEntry OBJECT-TYPE
   SYNTAX RsADDNSPersistencyParametersEntry
   ACCESS not-accessible
   STATUS  mandatory
   DESCRIPTION
       " The row definition for the DNS Persistency Parameters Table."
   INDEX  {rsADDNSPersistencyParametersFarm}
   ::= {rsADDNSPersistencyParametersTable 1}


RsADDNSPersistencyParametersEntry ::= SEQUENCE {
  rsADDNSPersistencyParametersFarm                DisplayString,
  rsADDNSPersistencyParametersStatus              FeatureStatus,
  rsADDNSPersistencyParametersMode                INTEGER,
  rsADDNSPersistencyParametersStaticMode          FeatureStatus,
  rsADDNSPersistencyParametersAgingMode           INTEGER,
  rsADDNSPersistencyParametersAgingTime           INTEGER,
  rsADDNSPersistencyParametersDynamicTableMode    INTEGER,
  rsADDNSPersistencyParametersGroupingMask        	IpAddress,
  rsADDNSPersistencyParametersGroupingSuffixLen     INTEGER,
  rsADDNSPersistencyParametersGroupingSuffixType    InetAddressType
  }

rsADDNSPersistencyParametersFarm OBJECT-TYPE
    SYNTAX DisplayString (SIZE(1..50))
    ACCESS  read-only
    STATUS  mandatory
    DESCRIPTION
      "The name of the farm that uses the specified parameters"
    ::= { rsADDNSPersistencyParametersEntry 1 }

rsADDNSPersistencyParametersStatus OBJECT-TYPE
   SYNTAX FeatureStatus
   ACCESS  read-write
   STATUS  mandatory
   DESCRIPTION
       "Enable/disable the use of DNS persistency for the Farm."
   DEFVAL { disable }
   ::=  { rsADDNSPersistencyParametersEntry 2 }

rsADDNSPersistencyParametersMode OBJECT-TYPE
   SYNTAX INTEGER {
        loadBalancing(1),
        hash(2)
   }
   ACCESS  read-write
   STATUS  mandatory
   DESCRIPTION
       "Set how to select the VIP used in DNS replies for the farm:
	   loadBalancing - usual load balancing algorithm
	   hash - static hash on client IP"
   DEFVAL { loadBalancing }
   ::=  { rsADDNSPersistencyParametersEntry 3 }

rsADDNSPersistencyParametersStaticMode OBJECT-TYPE
   SYNTAX FeatureStatus
   ACCESS  read-write
   STATUS  mandatory
   DESCRIPTION
       "Enable/disable use of static DNS persistency table for the farm"
   DEFVAL { disable }
   ::=  { rsADDNSPersistencyParametersEntry 4 }


rsADDNSPersistencyParametersAgingMode OBJECT-TYPE
SYNTAX INTEGER {
   inactivity(1),
   fixed(2) }
   ACCESS  read-write
   STATUS  mandatory
   DESCRIPTION
"Aging mode for entries in the Dynamic DNS persistency table:
Inactivity Timeout - aging timer is restarted when an entry is used
Fixed Timeout - the entry is removed when its time-to-live expires."
   DEFVAL { inactivity }
   ::=  { rsADDNSPersistencyParametersEntry 5 }

rsADDNSPersistencyParametersAgingTime  OBJECT-TYPE
   SYNTAX INTEGER
   ACCESS  read-write
   STATUS  mandatory
   DESCRIPTION
"Aging time for entries in the DNS persistency table in seconds"
   DEFVAL { 60 }
   ::=  { rsADDNSPersistencyParametersEntry 6 }

rsADDNSPersistencyParametersDynamicTableMode OBJECT-TYPE
   SYNTAX INTEGER {
        sourceIpAndHostname(1),
        sourceIpOnly       (2)
   }
   ACCESS  read-write
   STATUS  mandatory
   DESCRIPTION
       "The mode of the Dynamic DNS Persistency Table:
        sourceIpAndHostname:
          Separate entries are used for requests from the same source IP and different Hostnames.
        sourceIpOnly:
          Requests from the same source IP and different Hostnames will use the same entry in the dynamic table."
   DEFVAL { sourceIpOnly }
   ::=  { rsADDNSPersistencyParametersEntry 7 }
--obsolete
rsADDNSPersistencyParametersGroupingMask OBJECT-TYPE
    SYNTAX IpAddress
    ACCESS  read-write
    STATUS  optional
    DESCRIPTION
      "THIS FIELD IS NOT IN USE"
	DEFVAL {0}
    ::= { rsADDNSPersistencyParametersEntry 8 }



rsADDNSPersistencyParametersGroupingSuffixLen OBJECT-TYPE
    SYNTAX  INTEGER  (0..128)
   ACCESS  read-write
   STATUS  mandatory
   DESCRIPTION
      "DNS persistency grouping suffix length"
    ::= { rsADDNSPersistencyParametersEntry 9 }

rsADDNSPersistencyParametersGroupingSuffixType OBJECT-TYPE
   SYNTAX  InetAddressType
   ACCESS  read-write
   STATUS  mandatory
   DESCRIPTION
      "DNS persistency grouping suffix type"
   DEFVAL  { ipv4 }
    ::= { rsADDNSPersistencyParametersEntry 10 }

-- L4 Policy table

rsWSDL4Policy OBJECT IDENTIFIER ::= { rsNWSD 52 }

rsWSDL4PolicyTable OBJECT-TYPE
   SYNTAX SEQUENCE OF RsWSDL4PolicyEntry
   ACCESS not-accessible
   STATUS mandatory
   DESCRIPTION
       "A table for managing load balancing policies information."
   ::= {rsWSDL4Policy 1}

rsWSDL4PolicyEntry OBJECT-TYPE
   SYNTAX RsWSDL4PolicyEntry
   ACCESS not-accessible
   STATUS  mandatory
   DESCRIPTION
       " The row definition for this table."
   INDEX  { rsWSDL4PolicyVirtualIP,
            rsWSDL4PolicyL4Protocol,
            rsWSDL4PolicyDstPort,
            rsWSDL4PolicyRangeIPFrom}
   ::= {rsWSDL4PolicyTable 1}

RsWSDL4PolicyEntry  ::= SEQUENCE {
      rsWSDL4PolicyVirtualIP          IpAddress,
      rsWSDL4PolicyL4Protocol         INTEGER,
      rsWSDL4PolicyDstPort            INTEGER,
      rsWSDL4PolicyRangeIPFrom        IpAddress,
      rsWSDL4PolicyRangeIPTo          IpAddress,
      rsWSDL4PolicyName               DisplayString,
      rsWSDL4PolicyL7PolicyName       DisplayString,
      rsWSDL4PolicyFarmName           DisplayString,
      rsWSDL4PolicyApplication        INTEGER,
      rsWSDL4PolicyBEPort             INTEGER,
      rsWSDL4PolicyDepthRead          INTEGER,
      rsWSDL4PolicyRedunStatus        INTEGER,
      rsWSDL4PolicyPostClassification INTEGER,
      rsWSDL4PolicyHTTPNormalization  FeatureStatus,
      rsWSDL4PolicyPersistL7Mode      INTEGER,
      rsWSDL4PolicyDefinedBy          INTEGER,
      rsWSDL4PolicySegmentName        DisplayString,
      rsWSDL4PolicyExplicitFarmName   DisplayString,
      rsWSDL4PolicyStatus             RowStatus,
      rsWSDL4PolicyActionType         INTEGER,
      rsWSDL4PolicyAction               DisplayString,
      rsWSDL4PolicyClientSSLPolicy      DisplayString,
      rsWSDL4PolicyCompressionPolicy    DisplayString,
      rsWSDL4PolicyCachingPolicy        DisplayString,
      rsWSDL4PolicyAuthenticationPolicy DisplayString,
	  rsWSDL4PolicyHttpPolicy           DisplayString,
	  rsWSDL4PolicyTcpPolicy            DisplayString
  }

rsWSDL4PolicyVirtualIP OBJECT-TYPE
   SYNTAX  IpAddress
   ACCESS  read-only
   STATUS  mandatory
   DESCRIPTION
       "Virtual destination IP address."
   ::= {rsWSDL4PolicyEntry 1}

rsWSDL4PolicyL4Protocol OBJECT-TYPE
    SYNTAX    INTEGER {
        tcp(1),
        udp(2),
        icmp(3),
        any(4),
        other(5),
 		sctp(6)

    }
    ACCESS    read-only
    STATUS    mandatory
    DESCRIPTION
       "The L4 protocol type"
    ::= { rsWSDL4PolicyEntry 2}

rsWSDL4PolicyDstPort OBJECT-TYPE
    SYNTAX  INTEGER  (0..65535)
    ACCESS  read-only
    STATUS  mandatory
    DESCRIPTION
      "Destination port. Destination port 0 means any port"
 ::=  {rsWSDL4PolicyEntry 3}

rsWSDL4PolicyRangeIPFrom OBJECT-TYPE
   SYNTAX  IpAddress
   ACCESS  read-only
   STATUS  mandatory
   DESCRIPTION
       "Start address of the source IP range. The 0.0.0.0 address means that source
        IP ranges are not used for that entry"
   ::= {rsWSDL4PolicyEntry 4}

rsWSDL4PolicyRangeIPTo OBJECT-TYPE
   SYNTAX  IpAddress
   ACCESS  read-write
   STATUS  mandatory
   DESCRIPTION
       "Last address of the source IP range."
   ::= {rsWSDL4PolicyEntry 5}

rsWSDL4PolicyName  OBJECT-TYPE
    SYNTAX DisplayString (SIZE (1..50))
    ACCESS read-write
   	STATUS mandatory
   	DESCRIPTION
     	 "The L4 policy name."
	::=  {rsWSDL4PolicyEntry 6}

rsWSDL4PolicyL7PolicyName  OBJECT-TYPE
    SYNTAX DisplayString (SIZE(0..20))
    ACCESS read-write
   	STATUS mandatory
   	DESCRIPTION
     	 "The L7 policy name."
    DEFVAL { "None" }
	::=  {rsWSDL4PolicyEntry 7}

rsWSDL4PolicyFarmName  OBJECT-TYPE
    SYNTAX DisplayString (SIZE(0..50))
    ACCESS read-write
   	STATUS mandatory
   	DESCRIPTION
     	 "The farm name."
    DEFVAL { "None" }
	::=  {rsWSDL4PolicyEntry 8}

rsWSDL4PolicyApplication OBJECT-TYPE
    SYNTAX  INTEGER  {
        na (1),
        http(2),
        ftpcontrol(3),
        ftpdata(4),
        https(5),
        rtsp(6),
        rsh(7),
        rexec(8),
        tftp(9),
        sip(10),
        tsCookie(11),
        radius(12),
        fix(13),
        virtualIPInterface(14),
        ping(15),
        tcp(16),
        udp(17),
        sctp(18),
        mh-sctp(19),
        restricted-icap(20), -- Added in 1.03.06DL
        sips(21),
        generic-ssl(22)
--		diameter(24)
    }
    ACCESS  read-write
    STATUS  mandatory
    DESCRIPTION
      "Treat as given port number. Tells how to treat the traffic that matches
       the L4 policy."
    DEFVAL { na }
   ::=  {rsWSDL4PolicyEntry 9}

rsWSDL4PolicyBEPort OBJECT-TYPE
    SYNTAX  INTEGER  (0..65535)
    ACCESS  read-write
    STATUS  mandatory
    DESCRIPTION
        "Backend encryption port."
    DEFVAL { 0 }
   ::=  {rsWSDL4PolicyEntry 10}

rsWSDL4PolicyDepthRead OBJECT-TYPE
    SYNTAX  INTEGER (1..65535)
    ACCESS  read-write
    STATUS  mandatory
    DESCRIPTION
      "A number of bytes of request to read for classification."
    DEFVAL {3584}
   ::=  {rsWSDL4PolicyEntry 11}

rsWSDL4PolicyRedunStatus  OBJECT-TYPE
    SYNTAX    INTEGER {
        master(1),
        backup(2)
    }
    ACCESS    read-write
    STATUS    mandatory
    DESCRIPTION
       "The L4 policy on backup or master device."
    DEFVAL {master}
   ::= { rsWSDL4PolicyEntry 12 }

rsWSDL4PolicyPostClassification OBJECT-TYPE
    SYNTAX    INTEGER {
        header(1),
        body(2),
        headerandbody(3)
    }
    ACCESS    read-write
    STATUS    mandatory
    DESCRIPTION
       "The part of request to read for classification."
    DEFVAL {header}
    ::= { rsWSDL4PolicyEntry 13 }

rsWSDL4PolicyHTTPNormalization OBJECT-TYPE
    SYNTAX    FeatureStatus
    ACCESS    read-write
    STATUS    mandatory
    DESCRIPTION
       "HTTP normalization status."
    DEFVAL { disable }
    ::= { rsWSDL4PolicyEntry 14 }

rsWSDL4PolicyPersistL7Mode OBJECT-TYPE
    SYNTAX    INTEGER {
        first (1),
        overwrite(2),
        maintain(3)
    }
    ACCESS    read-write
    STATUS    mandatory
    DESCRIPTION
       "L7 persistency method."
    DEFVAL { first }
    ::= { rsWSDL4PolicyEntry 15 }

rsWSDL4PolicyDefinedBy OBJECT-TYPE
    SYNTAX    INTEGER {
        userdefined (1),
        system(2)
    }
    ACCESS    read-only
    STATUS    mandatory
    DESCRIPTION
       "The L4 policy origin. The policy may be defined by user, or by application
         for internal purpose."
    ::= { rsWSDL4PolicyEntry 16 }

rsWSDL4PolicySegmentName  OBJECT-TYPE
    SYNTAX DisplayString (SIZE(0..20))
    ACCESS read-write
   	STATUS mandatory
   	DESCRIPTION
     	 "The segment name."
	::=  {rsWSDL4PolicyEntry 17}

rsWSDL4PolicyExplicitFarmName  OBJECT-TYPE
    SYNTAX DisplayString (SIZE(0..50))
    ACCESS read-write
   	STATUS mandatory
   	DESCRIPTION
        "Explicit Farm Name defines the farm to be used for load and global considerations,
         when the L4 Policy is bound to a L7 Policy.
         This is required because  tables such as LRP Table and Hostname Table
         refer to L4 Policy entries, and at the same time must be correlated
         to a specific farm."
    DEFVAL { "None" }
	::=  {rsWSDL4PolicyEntry 18}

rsWSDL4PolicyStatus OBJECT-TYPE
    SYNTAX    RowStatus
    ACCESS    read-write
    STATUS    mandatory
    DESCRIPTION
      "Row status for this entry."
    ::= { rsWSDL4PolicyEntry 19 }

rsWSDL4PolicyActionType OBJECT-TYPE
  SYNTAX INTEGER {
    farm(1),
    l7policy(2),
    route(3),
    uri(4),
    ip(5),
    replyCode(6),
    none(7)
  }
  ACCESS read-write
  STATUS mandatory
  DESCRIPTION
    "Type of action to take on classification success.
    Farm – farm name to select server from.
    L7 Policy – perform L7 classification to select farm.
    Route – specify a SIP route table.
    URI – send request to specified URI.
    IP – send request to IP.
    Reply Code - send a reply with specified code (SIP).
    None – destination is determined by SIP headers."
	DEFVAL { farm }
  ::= {rsWSDL4PolicyEntry 20}

rsWSDL4PolicyAction OBJECT-TYPE
	SYNTAX DisplayString (SIZE(0..50))
	ACCESS read-write
	STATUS mandatory
	DESCRIPTION
    "Action to take on classification success. Must match action type. Replaces both rsWSDL4PolicyL7PolicyName
    and rsWSDL4PolicyFarmName."
	::= {rsWSDL4PolicyEntry 21}

rsWSDL4PolicyClientSSLPolicy OBJECT-TYPE
  SYNTAX DisplayString (SIZE (1..50))
  ACCESS read-write
  STATUS mandatory
  DESCRIPTION
    "The Client SSL Policy name."
  DEFVAL { "None" }
  ::=  {rsWSDL4PolicyEntry 22}

rsWSDL4PolicyCompressionPolicy OBJECT-TYPE
  SYNTAX DisplayString (SIZE (1..50))
  ACCESS read-write
  STATUS mandatory
  DESCRIPTION
    "The Compression Policy name."
  DEFVAL { "None" }
  ::=  {rsWSDL4PolicyEntry 23}

rsWSDL4PolicyCachingPolicy OBJECT-TYPE
  SYNTAX DisplayString (SIZE (1..50))
  ACCESS read-write
  STATUS mandatory
  DESCRIPTION
    "The Caching Policy name."
  DEFVAL { "None" }
  ::=  {rsWSDL4PolicyEntry 24}

rsWSDL4PolicyAuthenticationPolicy OBJECT-TYPE
  SYNTAX DisplayString (SIZE (1..50))
  ACCESS read-write
  STATUS mandatory
  DESCRIPTION
    "The Authentication Policy name."
  DEFVAL { "None" }
  ::=  {rsWSDL4PolicyEntry 25}

rsWSDL4PolicyHttpPolicy OBJECT-TYPE
  SYNTAX DisplayString (SIZE (1..50))
  ACCESS read-write
  STATUS mandatory
  DESCRIPTION
    "The Http Policy name."
  DEFVAL { "None" }
  ::=  {rsWSDL4PolicyEntry 26}

rsWSDL4PolicyTcpPolicy OBJECT-TYPE
  SYNTAX DisplayString (SIZE (1..50))
  ACCESS read-write
  STATUS mandatory
  DESCRIPTION
    "The Tcp Policy name."
  DEFVAL { "None" }
  ::=  {rsWSDL4PolicyEntry 27}

-- L4 policy statistics table

rsWSDL4PolicyStatsTable OBJECT-TYPE
   SYNTAX SEQUENCE OF RsWSDL4PolicyStatsEntry
   ACCESS not-accessible
   STATUS mandatory
   DESCRIPTION
       "A read-only table for L4 policy statistical information."
   ::= {rsWSDL4Policy 2}

rsWSDL4PolicyStatsEntry OBJECT-TYPE
   SYNTAX RsWSDL4PolicyStatsEntry
   ACCESS not-accessible
   STATUS  mandatory
   DESCRIPTION
       " The row definition for this table."
   INDEX  { rsWSDL4PolicyStatsVirtualIP,
            rsWSDL4PolicyStatsL4Protocol,
            rsWSDL4PolicyStatsDstPort,
            rsWSDL4PolicyStatsRangeIPFrom}
   ::= {rsWSDL4PolicyStatsTable 1}

RsWSDL4PolicyStatsEntry  ::= SEQUENCE {
      rsWSDL4PolicyStatsVirtualIP   IpAddress,
      rsWSDL4PolicyStatsL4Protocol  INTEGER,
      rsWSDL4PolicyStatsDstPort     INTEGER,
      rsWSDL4PolicyStatsRangeIPFrom IpAddress,
      rsWSDL4PolicyStatsMatches     Counter,
      rsWSDL4PolicyStatsLSMatches   Counter
  }

rsWSDL4PolicyStatsVirtualIP OBJECT-TYPE
   SYNTAX  IpAddress
   ACCESS  read-only
   STATUS  mandatory
   DESCRIPTION
       "Virtual destination IP address."
   ::= {rsWSDL4PolicyStatsEntry 1}

rsWSDL4PolicyStatsL4Protocol OBJECT-TYPE
    SYNTAX    INTEGER {
        tcp(1),
        udp(2),
        icmp(3),
        any(4),
        other(5),
	sctp(6)
    }
    ACCESS    read-only
    STATUS    mandatory
    DESCRIPTION
       "The L4 protocol type"
    ::= { rsWSDL4PolicyStatsEntry 2 }

rsWSDL4PolicyStatsDstPort OBJECT-TYPE
    SYNTAX  INTEGER  (0..65535)
    ACCESS  read-only
    STATUS  mandatory
    DESCRIPTION
      "Destination port. Destination port 0 means any port"
 ::=  {rsWSDL4PolicyStatsEntry 3}

rsWSDL4PolicyStatsRangeIPFrom OBJECT-TYPE
   SYNTAX  IpAddress
   ACCESS  read-only
   STATUS  mandatory
   DESCRIPTION
       "Start address of the source IP range. The 0.0.0.0 address means that source
        IP ranges are not used for that entry"
   ::= {rsWSDL4PolicyStatsEntry 4}

rsWSDL4PolicyStatsMatches OBJECT-TYPE
    SYNTAX    Counter
    ACCESS    read-only
    STATUS    mandatory
    DESCRIPTION
      "Number of total matches for this policy"
    ::= { rsWSDL4PolicyStatsEntry 5 }

rsWSDL4PolicyStatsLSMatches OBJECT-TYPE
    SYNTAX    Counter
    ACCESS    read-only
    STATUS    mandatory
    DESCRIPTION
      "Number of last second matches for this policy"
    ::= { rsWSDL4PolicyStatsEntry 6 }


rsWSDL4PolicyActions OBJECT-TYPE
    SYNTAX  INTEGER {
       resetstat(1)
     }
    ACCESS  read-write
    STATUS  mandatory
    DESCRIPTION
      "This variable enables the operator to perform one of the
      specified actions on the tables maintained by the network device."
   ::= { rsWSDL4Policy 3  }

-- rsWSDL4Policy 4 is saved for the new L4 policy

-- L4 Policy extension table
adL4PolicyExtTable OBJECT-TYPE
  SYNTAX SEQUENCE OF AdL4PolicyExtEntry
  ACCESS not-accessible
  STATUS mandatory
  DESCRIPTION
    "A table for managing extensions to the L4 Policy Table."
  ::= {rsWSDL4Policy 5}

adL4PolicyExtEntry OBJECT-TYPE
  SYNTAX AdL4PolicyExtEntry
  ACCESS not-accessible
  STATUS mandatory
  DESCRIPTION
    " The row definition for this table."
  INDEX { adL4PolicyExtName }
  ::= {adL4PolicyExtTable 1}

AdL4PolicyExtEntry ::= SEQUENCE {
  adL4PolicyExtName                 DisplayString,
  adL4PolicyExtClientSSLPolicy      DisplayString,
  adL4PolicyExtCompressionPolicy    DisplayString,
  adL4PolicyExtCachingPolicy        DisplayString,
  adL4PolicyExtSIPControlPolicy     DisplayString,
  adL4PolicyExtAuthenticationPolicy DisplayString,
  adL4PolicyExtHttpPolicy           DisplayString
}

adL4PolicyExtName OBJECT-TYPE
  SYNTAX DisplayString (SIZE (1..50))
  ACCESS read-only
  STATUS mandatory
  DESCRIPTION
    "The L4 Policy name."
  ::=  {adL4PolicyExtEntry 1}

adL4PolicyExtClientSSLPolicy OBJECT-TYPE
  SYNTAX DisplayString (SIZE (1..50))
  ACCESS read-write
  STATUS mandatory
  DESCRIPTION
    "The Client SSL Policy name."
  DEFVAL { "None" }
  ::=  {adL4PolicyExtEntry 2}

adL4PolicyExtCompressionPolicy OBJECT-TYPE
  SYNTAX DisplayString (SIZE (1..50))
  ACCESS read-write
  STATUS mandatory
  DESCRIPTION
    "The Compression Policy name."
  DEFVAL { "None" }
  ::=  {adL4PolicyExtEntry 3}

adL4PolicyExtCachingPolicy OBJECT-TYPE
  SYNTAX DisplayString (SIZE (1..50))
  ACCESS read-write
  STATUS mandatory
  DESCRIPTION
    "The Caching Policy name."
  DEFVAL { "None" }
  ::=  {adL4PolicyExtEntry 4}

adL4PolicyExtSIPControlPolicy OBJECT-TYPE
  SYNTAX DisplayString (SIZE (1..50))
  ACCESS read-write
  STATUS mandatory
  DESCRIPTION
    "The SIP Policy name."
  DEFVAL { "None" }
  ::=  {adL4PolicyExtEntry 5}

adL4PolicyExtAuthenticationPolicy OBJECT-TYPE
  SYNTAX DisplayString (SIZE (1..50))
  ACCESS read-write
  STATUS mandatory
  DESCRIPTION
    "The Authentication Policy name."
  DEFVAL { "None" }
  ::=  {adL4PolicyExtEntry 6}

  adL4PolicyExtHttpPolicy OBJECT-TYPE
  SYNTAX DisplayString (SIZE (1..50))
  ACCESS read-write
  STATUS mandatory
  DESCRIPTION
    "The Http Policy name."
  DEFVAL { "None" }
  ::=  {adL4PolicyExtEntry 7}

-- Client SSL Policy
adClientSSLPolicyTable OBJECT-TYPE
  SYNTAX SEQUENCE OF AdClientSSLPolicyEntry
  ACCESS not-accessible
  STATUS mandatory
  DESCRIPTION
    "A table for managing client SSL parameters."
  ::= {rsWSDL4Policy 8}

adClientSSLPolicyEntry OBJECT-TYPE
  SYNTAX AdClientSSLPolicyEntry
  ACCESS not-accessible
  STATUS mandatory
  DESCRIPTION
    " The row definition for this table."
  INDEX { adClientSSLPolicyName }
  ::= {adClientSSLPolicyTable 1}

AdClientSSLPolicyEntry ::= SEQUENCE {
  adClientSSLPolicyName					DisplayString,
  adClientSSLPolicyCertificate			DisplayString,
  adClientSSLPolicyCipherSuite			INTEGER,
  adClientSSLPolicyUserDefinedCipher	DisplayString,
  adClientSSLPolicyIntermediateCert		DisplayString,
  adClientSSLPolicyStatus				RowStatus,
  adClientSSLPolicyListeningServerPort	INTEGER,
  adClientSSLPolicyBackendSSLState		FeatureStatus,
  adClientSSLPolicyBESSLCipher					INTEGER,
  adClientSSLPolicyHTTPRedirectionConversion	FeatureStatus,
  adClientSSLPolicyAlsoRedirectWhenHostMatch	DisplayString,
  adClientSSLPolicyCertificateHeaderToBEServerInfoArg		DisplayString,
  adClientSSLPolicyBEUserDefinedCipher	DisplayString,
  adClientSSLPolicyFrontendSSLState		FeatureStatus,
  adClientSSLPolicyBECertificate		DisplayString,
  adClientSSLPolicyBETrustedCACertificate DisplayString,
  adClientSSLPolicyFrontEndSSLVersions    DisplayString,
  adClientSSLPolicyBackEndSSLVersions     DisplayString
}

adClientSSLPolicyName OBJECT-TYPE
  SYNTAX DisplayString (SIZE (1..50))
  ACCESS read-only
  STATUS mandatory
  DESCRIPTION
    "The ClientSSL policy name."
  ::=  {adClientSSLPolicyEntry 1}

adClientSSLPolicyCertificate OBJECT-TYPE
  SYNTAX DisplayString (SIZE (0..50))
  ACCESS read-write
  STATUS mandatory
  DESCRIPTION
    "The certificate name as appears in the certificate table."
  ::=  {adClientSSLPolicyEntry 2}

adClientSSLPolicyCipherSuite OBJECT-TYPE
  SYNTAX INTEGER {
    rsa(1),
    all(2),
    allNonNullCiphers(3),
    sslV3(4),
    tlsV1(5),
    export(6),
    low(7),
    medium(8),
    high(9),
    rsaRc4-128Md5(10),
    rsaRc4-128Sha1(11),
    rsaDesSha1(12),
    rsa3desSha1(13),
    rsaAes128Sha1(14),
    rsaAes256Sha1(15),
    msieExport56(16),
    userDefined(17),
    pciDss(18)
  }
  ACCESS read-write
  STATUS mandatory
  DESCRIPTION
    "Cipher suite to be used in the context of this policy. When user-defined suite is selected
    it should be specified in adClientSSLPolicyUserDefinedCipher."
  DEFVAL { rsa }
  ::=  {adClientSSLPolicyEntry 3}

adClientSSLPolicyUserDefinedCipher OBJECT-TYPE
  SYNTAX DisplayString
  ACCESS read-write
  STATUS mandatory
  DESCRIPTION
    "User defined ciphers in OpenSSL format. Must be specified when adClientSSLPolicyCipherSuite
    is set to userDefined."
  ::=  {adClientSSLPolicyEntry 4}

adClientSSLPolicyIntermediateCert OBJECT-TYPE
  SYNTAX DisplayString (SIZE (0..50))
  ACCESS read-write
  STATUS mandatory
  DESCRIPTION
    "Intermediate certificate chain name as appears in the certificate table."
  ::=  {adClientSSLPolicyEntry 5}

adClientSSLPolicyStatus OBJECT-TYPE
  SYNTAX RowStatus
  ACCESS read-write
  STATUS mandatory
  DESCRIPTION
    "Row status for this entry."
  ::= { adClientSSLPolicyEntry 6}

adClientSSLPolicyListeningServerPort OBJECT-TYPE
  SYNTAX INTEGER (0..65535)
  ACCESS read-write
  STATUS mandatory
  DESCRIPTION
    "Backend server’s port. 0 – use L4 policy port."
  DEFVAL { 80 }
  ::=  {adClientSSLPolicyEntry 7}

adClientSSLPolicyBackendSSLState OBJECT-TYPE
  SYNTAX FeatureStatus
  ACCESS read-write
  STATUS mandatory
  DESCRIPTION
    "Controls whether backend connections are over SSL."
  DEFVAL { disable }
  ::=  {adClientSSLPolicyEntry 8}

adClientSSLPolicyBESSLCipher OBJECT-TYPE
  SYNTAX INTEGER {
    low(1),
    medium(2),
    high(3),
    userDefined(4)
  }
  ACCESS read-write
  STATUS mandatory
  DESCRIPTION
    "Backend SSL cipher strength."
  DEFVAL { low }
  ::=  {adClientSSLPolicyEntry 9}

adClientSSLPolicyHTTPRedirectionConversion OBJECT-TYPE
  SYNTAX FeatureStatus
  ACCESS read-write
  STATUS mandatory
  DESCRIPTION
    "Controls whether the device will modify the location header of any HTTP header in server's responses from HTTP:
	 to HTTPS://, and the target port."
  DEFVAL { disable }
  ::=  {adClientSSLPolicyEntry 10}

adClientSSLPolicyAlsoRedirectWhenHostMatch OBJECT-TYPE
  SYNTAX DisplayString (SIZE (0..255))
  ACCESS read-write
  STATUS mandatory
  DESCRIPTION
    "Optional string with regex characters allowed."
  ::=  {adClientSSLPolicyEntry 11}

adClientSSLPolicyCertificateHeaderToBEServerInfoArg OBJECT-TYPE
  SYNTAX DisplayString (SIZE (0..255))
  ACCESS read-write
  STATUS mandatory
  DESCRIPTION
    "Headers that are added to the request going to the BE server."
  ::=  {adClientSSLPolicyEntry 12}

adClientSSLPolicyBEUserDefinedCipher OBJECT-TYPE
  SYNTAX DisplayString
  ACCESS read-write
  STATUS mandatory
  DESCRIPTION
    "User defined ciphers in OpenSSL format. Must be specified when adClientSSLPolicyBESSLCipher
    is set to userDefined."
  ::=  {adClientSSLPolicyEntry 13}

adClientSSLPolicyFrontendSSLState OBJECT-TYPE
  SYNTAX FeatureStatus
  ACCESS read-write
  STATUS mandatory
  DESCRIPTION
    "Controls whether frontend connections are over SSL."
  DEFVAL { enable }
  ::=  {adClientSSLPolicyEntry 14}

adClientSSLPolicyBECertificate OBJECT-TYPE
  SYNTAX DisplayString (SIZE (0..50))
  ACCESS read-write
  STATUS mandatory
  DESCRIPTION
    "The certificate name as appears in the certificate table."
  ::=  {adClientSSLPolicyEntry 15}

 adClientSSLPolicyBETrustedCACertificate OBJECT-TYPE
  SYNTAX DisplayString (SIZE (0..50))
  ACCESS read-write
  STATUS mandatory
  DESCRIPTION
    "The CA certificate name as appears in the certificate table."
  ::=  {adClientSSLPolicyEntry 16}

 adClientSSLPolicyFrontEndSSLVersions OBJECT-TYPE
  SYNTAX DisplayString
  ACCESS read-write
  STATUS mandatory
  DESCRIPTION
    "Front end SSL versions supported for the front end connection."
  ::=  {adClientSSLPolicyEntry 17}

 adClientSSLPolicyBackEndSSLVersions OBJECT-TYPE
  SYNTAX DisplayString
  ACCESS read-write
  STATUS mandatory
  DESCRIPTION
    "Back end SSL versions supported for the back end connection."
  ::=  {adClientSSLPolicyEntry 18}

-- compression policy

adCompressionPolicyTable OBJECT-TYPE
SYNTAX SEQUENCE OF AdCompressionPolicyEntry
ACCESS not-accessible
STATUS mandatory
DESCRIPTION
"A table for managing compression parameters."
::= {rsWSDL4Policy 9}

adCompressionPolicyEntry OBJECT-TYPE
SYNTAX AdCompressionPolicyEntry
ACCESS not-accessible
STATUS mandatory
DESCRIPTION
" The row definition for this table."
INDEX { adCompressionPolicyName }
::= {adCompressionPolicyTable 1}

AdCompressionPolicyEntry ::= SEQUENCE {
adCompressionPolicyName		DisplayString,
adCompressionPolicyAlgorithm	INTEGER,
adCompressionPolicyCompLevel	INTEGER,
adCompressionPolicyMinSize	INTEGER,
adCompressionPolicyMaxSize	Unsigned32,
adCompressionPolicyEngine	INTEGER,
adCompressionPolicyStatus	RowStatus,
adCompressionURLExceptionsRuleList		DisplayString,
adCompressionBrowserExceptionsRuleList		DisplayString,
adCompressionUsePredefinedBrowserExceptions	INTEGER,
adCompressionAllowCompressionByBackendServer FeatureStatus
}

adCompressionPolicyName OBJECT-TYPE
SYNTAX DisplayString (SIZE (1..50))
ACCESS read-only
STATUS mandatory
DESCRIPTION
"The Compression policy name."
::=  {adCompressionPolicyEntry 1}

adCompressionPolicyAlgorithm OBJECT-TYPE
SYNTAX INTEGER {
	gzip(1),
	deflate(2)
}
ACCESS read-write
STATUS mandatory
DESCRIPTION
"The compression algorithm."
	DEFVAL { gzip }
::=  {adCompressionPolicyEntry 2}

adCompressionPolicyCompLevel OBJECT-TYPE
SYNTAX INTEGER (1..9)
ACCESS read-write
STATUS mandatory
DESCRIPTION
"The compression level from 1 (low) to 9 (high)."
	DEFVAL { 1 }
::=  {adCompressionPolicyEntry 3}

adCompressionPolicyMinSize OBJECT-TYPE
SYNTAX INTEGER (1..65535)
ACCESS read-write
STATUS mandatory
DESCRIPTION
"Minimum object size for compression. 0 – no minimum."
	DEFVAL { 10240 }
::=  {adCompressionPolicyEntry 4}

adCompressionPolicyMaxSize OBJECT-TYPE
SYNTAX Unsigned32 (0..2147483647)
ACCESS read-write
STATUS mandatory
DESCRIPTION
"Maximum object size for compression. 0 – no maximum."
	DEFVAL { 10485760 }
::=  {adCompressionPolicyEntry 5}

adCompressionPolicyEngine OBJECT-TYPE
SYNTAX INTEGER {
	software(1),
	hardware(2)
}
ACCESS read-write
STATUS mandatory
DESCRIPTION
"Compression engine type software/hardware (where applicable)."
	DEFVAL { software }
::=  {adCompressionPolicyEntry 6}

adCompressionPolicyStatus OBJECT-TYPE
SYNTAX RowStatus
ACCESS read-write
STATUS mandatory
DESCRIPTION
"Row status for this entry."
::= { adCompressionPolicyEntry 7}

adCompressionURLExceptionsRuleList OBJECT-TYPE
SYNTAX DisplayString (SIZE (1..50))
ACCESS read-write
STATUS mandatory
DESCRIPTION
"The URL Exceptions Rule List."
DEFVAL { "None" }
::= {adCompressionPolicyEntry 8}

adCompressionBrowserExceptionsRuleList OBJECT-TYPE
SYNTAX DisplayString (SIZE (1..50))
ACCESS read-write
STATUS mandatory
DESCRIPTION
"The Browser Exceptions Rule List."
DEFVAL { "None" }
::= {adCompressionPolicyEntry 9}

adCompressionUsePredefinedBrowserExceptions OBJECT-TYPE
SYNTAX INTEGER {
	predefinedBrowserLimitationsList(1),
	none(2)
}
ACCESS read-write
STATUS mandatory
DESCRIPTION
" Enable or Disable workarounds for browser limitations according to their type."
DEFVAL { predefinedBrowserLimitationsList }
::=  { adCompressionPolicyEntry 10}

adCompressionAllowCompressionByBackendServer OBJECT-TYPE
SYNTAX FeatureStatus
ACCESS read-write
STATUS mandatory
DESCRIPTION
" Delete 'Accept Encoding' Header from request sent to server to avoid it compressing as well ."
DEFVAL { disable }
::=  { adCompressionPolicyEntry 11}

-- caching policy
adCachingPolicyTable OBJECT-TYPE
SYNTAX SEQUENCE OF AdCachingPolicyEntry
ACCESS not-accessible
STATUS mandatory
DESCRIPTION
"A table for managing cache parameters."
::= {rsWSDL4Policy 10}

adCachingPolicyEntry OBJECT-TYPE
SYNTAX AdCachingPolicyEntry
ACCESS not-accessible
STATUS mandatory
DESCRIPTION
" The row definition for this table."
INDEX { adCachingPolicyName }
::= {adCachingPolicyTable 1}

AdCachingPolicyEntry ::= SEQUENCE {
	adCachingPolicyName			DisplayString,
	adCachingPolicyAdminStatus	FeatureStatus,
	adCachingPolicyExpiration	Unsigned32,
	adCachingPolicyStatus                             RowStatus,
	adCachingMinimumObjectSize                        Unsigned32,
	adCachingMaximumObjectSize                        Unsigned32,
	adCachingMaximumCacheEntries                      Unsigned32,
	adCachingWeight                                   INTEGER,
	adCachingByRuleListPolicy                         DisplayString,
	adCachingRespectServerCacheHeaders                INTEGER,
	adCachingRespectClientCacheHeadersInRequests      INTEGER,
	adCachingLeverageBrowserCache                     INTEGER,
	adCachingIgnoreQueryParamWhenServingObjFromCache  FeatureStatus,
	adDynamicCaching                                  INTEGER
}

adCachingPolicyName OBJECT-TYPE
SYNTAX DisplayString (SIZE (1..50))
ACCESS read-only
STATUS mandatory
DESCRIPTION
"The Caching policy name."
::=  {adCachingPolicyEntry 1}

adCachingPolicyAdminStatus OBJECT-TYPE
SYNTAX FeatureStatus
ACCESS read-write
STATUS mandatory
DESCRIPTION
"Administrative caching status."
	DEFVAL { enable }
::=  { adCachingPolicyEntry 2}

adCachingPolicyExpiration OBJECT-TYPE
SYNTAX Unsigned32 (60..43200400 )
ACCESS read-write
STATUS mandatory
DESCRIPTION
"Cached object invalidation time in seconds."
	DEFVAL { 86400 }
::=  { adCachingPolicyEntry 3}

adCachingPolicyStatus OBJECT-TYPE
SYNTAX RowStatus
ACCESS read-write
STATUS mandatory
DESCRIPTION
"Row status for this entry."
::= { adCachingPolicyEntry 4}

adCachingMinimumObjectSize OBJECT-TYPE
SYNTAX Unsigned32 (0..1048576)
ACCESS read-write
STATUS mandatory
DESCRIPTION
" minimum size in bytes of object to be stored."
DEFVAL { 1024 }
::=  { adCachingPolicyEntry 5}

adCachingMaximumObjectSize OBJECT-TYPE
SYNTAX Unsigned32 (0..20971520)
ACCESS read-write
STATUS mandatory
DESCRIPTION
" maximum size in bytes of objects to stored."
DEFVAL { 1048576 }
::=  { adCachingPolicyEntry 6}

adCachingMaximumCacheEntries OBJECT-TYPE
SYNTAX Unsigned32
ACCESS read-write
STATUS mandatory
DESCRIPTION
" maximum number of entries in cache."
DEFVAL { 10000 }
::=  { adCachingPolicyEntry 7}

adCachingWeight OBJECT-TYPE
SYNTAX INTEGER (1..100)
ACCESS read-write
STATUS mandatory
DESCRIPTION
" relative weight of Tunnel cache to other Tunnels for RAM distribution."
DEFVAL { 50 }
::=  { adCachingPolicyEntry 8}

adCachingByRuleListPolicy OBJECT-TYPE
SYNTAX DisplayString (SIZE (1..50))
ACCESS read-write
STATUS mandatory
DESCRIPTION
" Cache URL Rule list."
DEFVAL { "None" }
::=  { adCachingPolicyEntry 9}

adCachingRespectServerCacheHeaders OBJECT-TYPE
	SYNTAX  INTEGER {
        respectAll(1),
		cacheAll(2)
    }
ACCESS read-write
STATUS mandatory
DESCRIPTION
" specifies how Server Response cache headers are treated."
DEFVAL { respectAll }
::=  { adCachingPolicyEntry  10}

adCachingRespectClientCacheHeadersInRequests OBJECT-TYPE
	SYNTAX  INTEGER {
        respectAll(1),
		respectRefreshHeadersOnly (2),
		serveAllFromCache (3)
	}
ACCESS read-write
STATUS mandatory
DESCRIPTION
" specifies how Client request cache headers are treated."
DEFVAL { respectAll }
::=  { adCachingPolicyEntry  11}

adCachingLeverageBrowserCache OBJECT-TYPE
   SYNTAX  INTEGER {
        enable(1),
        disable(2)
  }
  ACCESS read-write
  STATUS mandatory
  DESCRIPTION
  " Leverage browser cache."
  DEFVAL { disable }
  ::=  { adCachingPolicyEntry  12}

adCachingIgnoreQueryParamWhenServingObjFromCache OBJECT-TYPE
  SYNTAX FeatureStatus
  ACCESS read-write
  STATUS mandatory
  DESCRIPTION
" Ignore query parameters when serving object from cache (Total Media specific)."
  DEFVAL { disable }
  ::=  { adCachingPolicyEntry  13}

adDynamicCaching OBJECT-TYPE
   SYNTAX  INTEGER {
        enable(1),
        disable(2)
  }
  ACCESS read-write
  STATUS mandatory
  DESCRIPTION
  " Dynamic Caching."
  DEFVAL { disable }
  ::=  { adCachingPolicyEntry  14}




-- SIP Policy
adSIPControlPolicyTable OBJECT-TYPE
  SYNTAX SEQUENCE OF AdSIPControlPolicyEntry
  ACCESS not-accessible
  STATUS mandatory
  DESCRIPTION
    "A table for managing SIP-related parameters."
  ::= {rsWSDL4Policy 12}

adSIPControlPolicyEntry OBJECT-TYPE
  SYNTAX AdSIPControlPolicyEntry
  ACCESS not-accessible
  STATUS mandatory
  DESCRIPTION
    " The row definition for this table."
  INDEX { adSIPControlPolicyName }
  ::= {adSIPControlPolicyTable 1}

AdSIPControlPolicyEntry ::= SEQUENCE {
  adSIPControlPolicyName           DisplayString,
  adSIPControlPolicySIPSrvList     DisplayString,
  adSIPControlPolicySiteVIP        DisplayString,
  adSIPControlPolicyPeerVIP1       DisplayString,
  adSIPControlPolicyPeerVIP2       DisplayString,
  adSIPControlPolicyPeerVIP3       DisplayString,
  adSIPControlPolicyParamLocator   DisplayString,
  adSIPControlPolicyAddRR          FeatureStatus,
  adSIPControlPolicyReclassify     FeatureStatus,
  adSIPControlPolicyCallAging      Unsigned32,
  adSIPControlPolicyAcceptAlias    INTEGER,
  adSIPControlPolicyRecordPath     FeatureStatus,
  adSIPControlPolicyMaxRegExprires Unsigned32,
  adSIPControlPolicyReuseRegFlow   INTEGER,
  adSIPControlPolicyStatus         RowStatus
}

adSIPControlPolicyName OBJECT-TYPE
  SYNTAX DisplayString (SIZE (1..50))
  ACCESS read-only
  STATUS mandatory
  DESCRIPTION
    "The SIP policy name."
  ::=  {adSIPControlPolicyEntry 1}

adSIPControlPolicySIPSrvList OBJECT-TYPE
  SYNTAX DisplayString
  ACCESS read-write
  STATUS mandatory
  DESCRIPTION
    "Server preference list in case policy action type is farm. Only servers from the
    specified farm can be listed, and they should be separated with a semicolon.
    Equal servers are separated by a comma. Write each server in the format <IP>:<port>"
  ::=  {adSIPControlPolicyEntry 2}

adSIPControlPolicySiteVIP OBJECT-TYPE
  SYNTAX DisplayString (SIZE(0..39))
  ACCESS read-write
  STATUS mandatory
  DESCRIPTION
    "VIP to be used to create a read-only duplicate of the L4 Policy. This is used in SIP global solution."
  ::=  {adSIPControlPolicyEntry 3}

adSIPControlPolicyPeerVIP1 OBJECT-TYPE
  SYNTAX DisplayString (SIZE(0..39))
  ACCESS read-write
  STATUS mandatory
  DESCRIPTION
    "Site VIP of peer. Can be used when L4 Policy does not resolve directly to a farm. Peer with
    least overall load will be used first."
  ::=  {adSIPControlPolicyEntry 4}

adSIPControlPolicyPeerVIP2 OBJECT-TYPE
  SYNTAX DisplayString (SIZE(0..39))
  ACCESS read-write
  STATUS mandatory
  DESCRIPTION
    "Site VIP of peer. Can be used when L4 Policy does not resolve directly to a farm. Peer with
    least overall load will be used first."
  ::=  {adSIPControlPolicyEntry 5}

adSIPControlPolicyPeerVIP3 OBJECT-TYPE
  SYNTAX DisplayString (SIZE(0..39))
  ACCESS read-write
  STATUS mandatory
  DESCRIPTION
    "Site VIP of peer. Can be used when L4 Policy does not resolve directly to a farm. Peer with
    least overall load will be used first."
  ::=  {adSIPControlPolicyEntry 6}

adSIPControlPolicyParamLocator OBJECT-TYPE
  SYNTAX DisplayString
  ACCESS read-write
  STATUS mandatory
  DESCRIPTION
    "Entry name from SIP Parameter Locator Table. Must be specified if L4 policy action type is route."
  ::=  {adSIPControlPolicyEntry 7}

adSIPControlPolicyAddRR OBJECT-TYPE
  SYNTAX FeatureStatus
  ACCESS read-write
  STATUS mandatory
  DESCRIPTION
    "Whether a Record-Route header should be added to SIP messages. If SIP forwarding requires it,
    a RR header may be added regardless of this value. If the policy points to a L7 Policy this
    parameter may be overridden."
  DEFVAL { enable }
  ::=  {adSIPControlPolicyEntry 8}

adSIPControlPolicyReclassify OBJECT-TYPE
  SYNTAX FeatureStatus
  ACCESS read-write
  STATUS mandatory
  DESCRIPTION
    "Indicates whether future requests of existing dialogues should be reclassified. If the policy
    points to a L7 Policy this parameter may be overridden."
  DEFVAL { disable }
  ::=  {adSIPControlPolicyEntry 9}

adSIPControlPolicyCallAging OBJECT-TYPE
  SYNTAX Unsigned32
  ACCESS read-write
  STATUS mandatory
  DESCRIPTION
    "Idle interval length, in seconds, after which the call information is deleted. This value will
    be added to the session expires header if exists in the request, and only if RR is added. If
    the policy points to a L7 Policy this parameter may be overridden."
  DEFVAL { 5400 }
  ::=  {adSIPControlPolicyEntry 10}

adSIPControlPolicyAcceptAlias OBJECT-TYPE
  SYNTAX INTEGER {
    never(1),
    always(2),
    tlsOnly(3),
    authTls(4)
  }
  ACCESS read-write
  STATUS mandatory
  DESCRIPTION
    "Specifies whether 'alias' parameter is accepted. Default is to accept only when TLS is
    authenticated using a client certificate."
  DEFVAL { authTls }
  ::=  {adSIPControlPolicyEntry 11}

adSIPControlPolicyRecordPath OBJECT-TYPE
  SYNTAX FeatureStatus
  ACCESS read-write
  STATUS mandatory
  DESCRIPTION
    "Indicates whether Path header should be added to REGISTER requests."
  DEFVAL { enable }
  ::=  {adSIPControlPolicyEntry 12}

adSIPControlPolicyMaxRegExprires OBJECT-TYPE
  SYNTAX Unsigned32
  ACCESS read-write
  STATUS mandatory
  DESCRIPTION
    "Indicates the maximum desired value of the 'expires' header in a REGISTER request. If a
    matching REGISTER request contains a higher value, it is changed to this value. Default
    behavior is not to change anything (0)."
  DEFVAL { 0 }
  ::=  {adSIPControlPolicyEntry 13}

adSIPControlPolicyReuseRegFlow OBJECT-TYPE
  SYNTAX INTEGER {
    yes(1),
    no(2),
    onNatDetection(3)
  }
  ACCESS read-write
  STATUS mandatory
  DESCRIPTION
    "When will the connection table save the flow reuse"
  DEFVAL { no }
  ::=  {adSIPControlPolicyEntry 14}

adSIPControlPolicyStatus OBJECT-TYPE
  SYNTAX RowStatus
  ACCESS read-write
  STATUS mandatory
  DESCRIPTION
    "Row status for this entry."
  ::= { adSIPControlPolicyEntry 15}

-- Authentication Policy
adAuthenticationPolicyTable OBJECT-TYPE
  SYNTAX SEQUENCE OF AdAuthenticationPolicyEntry
  ACCESS not-accessible
  STATUS mandatory
  DESCRIPTION
    "A table for managing authentication parameters."
  ::= {rsWSDL4Policy 13}

adAuthenticationPolicyEntry OBJECT-TYPE
  SYNTAX AdAuthenticationPolicyEntry
  ACCESS not-accessible
  STATUS mandatory
  DESCRIPTION
    " The row definition for this table."
  INDEX { adAuthPolicyName }
  ::= {adAuthenticationPolicyTable 1}

AdAuthenticationPolicyEntry ::= SEQUENCE {
  adAuthPolicyName          				DisplayString,
  adAuthPolicyClientCACert  				DisplayString,
  adAuthPolicyLDAPServerURL 				DisplayString,
  adAuthCertRevocationCheck 				INTEGER,
  adAuthOCSPURI             				DisplayString,
  adAuthOCSPURIPrec         				INTEGER,
  adAuthPolicyStatus        				RowStatus,
  adAuthPolicyCertificateHeaderToBEServerInfoArg DisplayString,
  adAuthRedirectionURLOnFailedAuth			DisplayString,
  adAuthCADepthToCheck						INTEGER,
  adAuthCACheckRequired      				INTEGER,
  adAuthOcspVerifyCAStatus                  FeatureStatus,
  adAuthOcspCacheTime						INTEGER,
  adAuthPolicyCertFieldValidationPolicy             DisplayString,
  adAuthOcspResponseAllowedSigningAlgorithm         DisplayString,
  adAuthOcspResponseTimestampDeviationGracePeriod   INTEGER,
  adAuthOcspNonce                         FeatureStatus,
  adAuthCrlFileName                       DisplayString,
  adAuthCdpBackupUri                      DisplayString,
  adAuthCdpBackupUsername                 DisplayString,
  adAuthCdpBackupPassword                 DisplayString,
  adAuthCdpBackupUpdateInterval           INTEGER,
  adAuthCdpGeneralGraceTime               INTEGER,
  adAuthCrlLastSuccessfulFetch            DisplayString,
  adAuthCrlLastUnsuccessfulFetch          DisplayString,
  adAuthCdpGroup                          DisplayString,
  adAuthCdpURIPrec                        INTEGER
}

adAuthPolicyName OBJECT-TYPE
  SYNTAX DisplayString (SIZE (1..50))
  ACCESS read-only
  STATUS mandatory
  DESCRIPTION
    "The Authentication policy name."
  ::=  {adAuthenticationPolicyEntry 1}

adAuthPolicyClientCACert OBJECT-TYPE
  SYNTAX DisplayString (SIZE (0..50))
  ACCESS read-write
  STATUS mandatory
  DESCRIPTION
    "Client CA certificate(s) to be used."
  ::=  {adAuthenticationPolicyEntry 2}

adAuthPolicyLDAPServerURL OBJECT-TYPE
  SYNTAX DisplayString
  ACCESS read-write
  STATUS mandatory
  DESCRIPTION
    "URL for LDAP server."
  ::=  {adAuthenticationPolicyEntry 3}

adAuthCertRevocationCheck OBJECT-TYPE
  SYNTAX INTEGER {
    disable(1),
    ocsp(2),
	crl(3),
    cdp(4)
  }
  ACCESS read-write
  STATUS mandatory
  DESCRIPTION
    "Whether certificate revocation check is performed. Currently only OCSP is implemented."
  DEFVAL { disable }
  ::=  {adAuthenticationPolicyEntry 4}

adAuthOCSPURI OBJECT-TYPE
  SYNTAX DisplayString
  ACCESS read-write
  STATUS mandatory
  DESCRIPTION
    "Specify a URI for OCSP certificate status check."
  ::=  {adAuthenticationPolicyEntry 5}

adAuthOCSPURIPrec OBJECT-TYPE
  SYNTAX INTEGER {
    embeddedUri(1),
    userDefined(2)
  }
  ACCESS read-write
  STATUS mandatory
  DESCRIPTION
    "Controls OCSP URI precedence - whether the user-configured URI is used or the URI that is embedded
     in the client's certificate."
  DEFVAL { embeddedUri }
  ::=  {adAuthenticationPolicyEntry 6}

adAuthPolicyStatus OBJECT-TYPE
  SYNTAX RowStatus
  ACCESS read-write
  STATUS mandatory
  DESCRIPTION
    "Row status for this entry."
  ::= { adAuthenticationPolicyEntry 7}

adAuthPolicyCertificateHeaderToBEServerInfoArg OBJECT-TYPE
  SYNTAX DisplayString (SIZE (0..255))
  ACCESS read-write
  STATUS mandatory
  DESCRIPTION
    "Holds the list of headers that will be added to the client request sent to the BE server. List is consisted of header names."
  ::=  {adAuthenticationPolicyEntry 8}

adAuthRedirectionURLOnFailedAuth OBJECT-TYPE
  SYNTAX DisplayString (SIZE (0..255))
  ACCESS read-write
  STATUS mandatory
  DESCRIPTION
    "A URL that the user will be redirected to if the authentication fails."
  ::=  {adAuthenticationPolicyEntry 9}

adAuthCADepthToCheck OBJECT-TYPE
  SYNTAX INTEGER (1..9)
  ACCESS read-write
  STATUS mandatory
  DESCRIPTION
  "The maximum depth that the client CA chain will be checked in order to authenticate the user."
	DEFVAL { 2 }
  ::=  {adAuthenticationPolicyEntry 10}

adAuthCACheckRequired OBJECT-TYPE
  SYNTAX INTEGER {
		enabled(1),
		optional(2),
		disabled(3)
		}
  ACCESS read-write
  STATUS mandatory
  DESCRIPTION
  "Determine whether a CA authentication is is mandatory or optional."
  DEFVAL { 1 }
  ::=  { adAuthenticationPolicyEntry  11}

adAuthOcspVerifyCAStatus                        OBJECT-TYPE
  SYNTAX FeatureStatus
  ACCESS read-write
  STATUS mandatory
  DESCRIPTION     "If enabled send an OCSP request for every certificate in the chain, otherwise to client certificate only."
  DEFVAL          { disable }
  ::= {adAuthenticationPolicyEntry    12}

adAuthOcspCacheTime                          OBJECT-TYPE
  SYNTAX INTEGER (0..180000)
  ACCESS read-write
  STATUS mandatory
  DESCRIPTION     "The time in minutes that OCSP responses should be cached.
                     When set to 0, OCSP Cache is disabled"
  DEFVAL          { 0 }
  ::= {adAuthenticationPolicyEntry    13}

adAuthPolicyCertFieldValidationPolicy        OBJECT-TYPE
  SYNTAX DisplayString (SIZE (0..50))
  ACCESS read-write
  STATUS mandatory
  DESCRIPTION     "Name of Certificate Field Validation Policy"
  DEFVAL { "None" }
  ::=  {adAuthenticationPolicyEntry 14}

adAuthOcspResponseAllowedSigningAlgorithm        OBJECT-TYPE
  SYNTAX DisplayString (SIZE (1..255))
  ACCESS read-write
  STATUS mandatory
  DESCRIPTION     "Defines the specific signature algorithms allows for signing OCSP responses"
  DEFVAL          { "All" }
  ::= {adAuthenticationPolicyEntry    15}

adAuthOcspResponseTimestampDeviationGracePeriod    OBJECT-TYPE
  SYNTAX INTEGER (0..2678400)
  ACCESS read-write
  STATUS mandatory
  DESCRIPTION     "Allows for overlooking small deviations between AppDirector and OCSP server timestamps for OCSP signatures verification (seconds)"
  DEFVAL          { 75 }
  ::= {adAuthenticationPolicyEntry    16}

adAuthOcspNonce                          OBJECT-TYPE
  SYNTAX FeatureStatus
  ACCESS read-write
  STATUS mandatory
  DESCRIPTION     "Determine whether nonce will be used in OCSP verification"
  DEFVAL          { enable }
  ::= {adAuthenticationPolicyEntry    17}

adAuthCrlFileName  OBJECT-TYPE
  SYNTAX DisplayString (SIZE (0..255))
  ACCESS read-write
  STATUS mandatory
  DESCRIPTION
    "Name of the CRL file"
  ::=  { adAuthenticationPolicyEntry  18}

adAuthCdpBackupUri  OBJECT-TYPE
  SYNTAX DisplayString (SIZE (0..250))
  ACCESS read-write
  STATUS mandatory
  DESCRIPTION
    "Field is obsolete"
  ::=  { adAuthenticationPolicyEntry  19}

adAuthCdpBackupUsername OBJECT-TYPE
  SYNTAX DisplayString (SIZE (0..250))
  ACCESS read-write
  STATUS mandatory
  DESCRIPTION
    "Field is obsolete"
  ::=  { adAuthenticationPolicyEntry 20}

adAuthCdpBackupPassword OBJECT-TYPE
  SYNTAX DisplayString (SIZE (0..250))
  ACCESS read-write
  STATUS mandatory
  DESCRIPTION
    "Field is obsolete"
  ::=  { adAuthenticationPolicyEntry 21}

adAuthCdpBackupUpdateInterval OBJECT-TYPE
  SYNTAX INTEGER (0..720000)
  ACCESS read-write
  STATUS mandatory
  DESCRIPTION
    "CDP backup update interval"
  DEFVAL { 0 }
  ::=  { adAuthenticationPolicyEntry 22}

 adAuthCdpGeneralGraceTime OBJECT-TYPE
  SYNTAX INTEGER (0..100000)
  ACCESS read-write
  STATUS mandatory
  DESCRIPTION
    "CDP general grace time"
  DEFVAL { 0 }
  ::=  { adAuthenticationPolicyEntry 23}

adAuthCrlLastSuccessfulFetch OBJECT-TYPE
  SYNTAX DisplayString (SIZE (0..25))
  ACCESS read-only
  STATUS mandatory
  DESCRIPTION
    "Last successful CRL file fetch time"
  ::=  { adAuthenticationPolicyEntry 24}


adAuthCrlLastUnsuccessfulFetch OBJECT-TYPE
  SYNTAX DisplayString (SIZE (0..25))
  ACCESS read-only
  STATUS mandatory
  DESCRIPTION
    "Last unsuccessful CRL file fetch time"
  ::=  { adAuthenticationPolicyEntry 25}

adAuthCdpGroup OBJECT-TYPE
  SYNTAX DisplayString (SIZE (0..50))
  ACCESS read-write
  STATUS mandatory
  DESCRIPTION
    "The name of the CDP group"
  ::=  { adAuthenticationPolicyEntry 26}

adAuthCdpURIPrec OBJECT-TYPE
  SYNTAX INTEGER {
    embeddedUri(1),
    userDefined(2)
  }
  ACCESS read-write
  STATUS mandatory
  DESCRIPTION
    "Controls CDP URI precedence - whether the user-configured URI is used or the URI that is embedded
     in the client's certificate."
  DEFVAL { embeddedUri }
  ::=  {adAuthenticationPolicyEntry 27}

-- End of Client Authentication policy


adL4PolicyCachePurge  OBJECT-TYPE
    SYNTAX DisplayString (SIZE (1..50))
    ACCESS read-write
   	STATUS mandatory
   	DESCRIPTION
     	 "Purge the cache information attached to a L4 Policy. Takes the name of the L4 policy that is bound to a cache policy
          or all for purge of the entire cache."
	::=  {rsWSDL4Policy 14}

-- 	Compression Browser Exception Policy Table
adCompressionBrowserExceptionPolicyTable OBJECT-TYPE
   	SYNTAX SEQUENCE OF AdCompressionBrowserExceptionPolicyEntry
   	ACCESS not-accessible
   	STATUS mandatory
   	DESCRIPTION
   	"A table for managing compression browser exception parameters."
   	::= {rsWSDL4Policy 16}

   	adCompressionBrowserExceptionPolicyEntry OBJECT-TYPE
   	SYNTAX AdCompressionBrowserExceptionPolicyEntry
   	ACCESS not-accessible
   	STATUS mandatory
   	DESCRIPTION
   	" The row definition for this table."
   	INDEX { adCompressionBrowserExceptionPolicyRuleListName,
	   	    adCompressionBrowserExceptionPolicyRuleName }
   	::= {adCompressionBrowserExceptionPolicyTable 1}

   	AdCompressionBrowserExceptionPolicyEntry ::= SEQUENCE {
   	adCompressionBrowserExceptionPolicyRuleListName		DisplayString,
   	adCompressionBrowserExceptionPolicyRuleName		DisplayString,
   	adCompressionBrowserExceptionPolicyRulePriority	        INTEGER,
   	adCompressionBrowserExceptionPolicyUserAgent		DisplayString,
   	adCompressionBrowserExceptionPolicyContentType		DisplayString,
   	adCompressionBrowserExceptionPolicyCompress		FeatureStatus,
        adCompressionBrowserExceptionPolicyStatus		RowStatus,
   	adCompressionBrowserExceptionPolicyUserAgentType	INTEGER,
   	adCompressionBrowserExceptionPolicyContentTypeType	INTEGER
   	}

   	adCompressionBrowserExceptionPolicyRuleListName OBJECT-TYPE
   	SYNTAX DisplayString (SIZE (1..50))
   	ACCESS read-only
   	STATUS mandatory
   	DESCRIPTION
   	"Compression browser exception rule list name."
   	::=  {adCompressionBrowserExceptionPolicyEntry 1}

   	adCompressionBrowserExceptionPolicyRuleName OBJECT-TYPE
   	SYNTAX DisplayString (SIZE (1..50))
   	ACCESS read-only
   	STATUS mandatory
   	DESCRIPTION
   	"Compression browser exception rule name."
   	::=  {adCompressionBrowserExceptionPolicyEntry 2}

   	adCompressionBrowserExceptionPolicyRulePriority OBJECT-TYPE
   	SYNTAX INTEGER (1..2147483647)
   	ACCESS read-write
   	STATUS mandatory
   	DESCRIPTION
   	"the index that determine the evaluation order."
        DEFVAL { 1 }
   	::=  {adCompressionBrowserExceptionPolicyEntry 3}

   	adCompressionBrowserExceptionPolicyUserAgent OBJECT-TYPE
   	SYNTAX DisplayString (SIZE (0..255))
   	ACCESS read-write
   	STATUS mandatory
   	DESCRIPTION
   	" Compression browser exception user agent."
   	::=  {adCompressionBrowserExceptionPolicyEntry 4}

   	adCompressionBrowserExceptionPolicyContentType OBJECT-TYPE
   	SYNTAX DisplayString (SIZE (0..100))
   	ACCESS read-write
   	STATUS mandatory
   	DESCRIPTION
   	"Compression browser exception user content type."
   	::=  {adCompressionBrowserExceptionPolicyEntry 5}

   	adCompressionBrowserExceptionPolicyCompress OBJECT-TYPE
     	SYNTAX FeatureStatus
     	ACCESS read-write
     	STATUS mandatory
     	DESCRIPTION
     	"Compression browser exception policy compress."
     	DEFVAL { disable }
     	::=  { adCompressionBrowserExceptionPolicyEntry 6}

	adCompressionBrowserExceptionPolicyStatus OBJECT-TYPE
   	SYNTAX RowStatus
   	ACCESS read-write
   	STATUS mandatory
   	DESCRIPTION
   	"Row status for this entry."
   	::= { adCompressionBrowserExceptionPolicyEntry 7}

    adCompressionBrowserExceptionPolicyUserAgentType OBJECT-TYPE
      SYNTAX  INTEGER {
        textMatch(1),
        regularExpression(2)
       }
    ACCESS read-write
    STATUS mandatory
    DESCRIPTION
    " whether user agent field should be evaluated as simple text or regular expression."
    DEFVAL { textMatch }
    ::=  {adCompressionBrowserExceptionPolicyEntry 8}

    adCompressionBrowserExceptionPolicyContentTypeType OBJECT-TYPE
      SYNTAX  INTEGER {
        textMatch(1),
        regularExpression(2)
       }
    ACCESS read-write
    STATUS mandatory
    DESCRIPTION
    " whether content type field should be evaluated as simple text or regular expression."
    DEFVAL { textMatch }
    ::=  {adCompressionBrowserExceptionPolicyEntry 9}

--         adCompressionURLExceptionPolicyTable

adCompressionURLExceptionPolicyTable OBJECT-TYPE
  SYNTAX SEQUENCE OF AdCompressionURLExceptionPolicyEntry
  ACCESS not-accessible
  STATUS mandatory
  DESCRIPTION
  "A table for managing compression URL exception parameters."
  ::= {rsWSDL4Policy 17}

adCompressionURLExceptionPolicyEntry OBJECT-TYPE
  SYNTAX AdCompressionURLExceptionPolicyEntry
  ACCESS not-accessible
  STATUS mandatory
  DESCRIPTION
  " The row definition for this table."
  INDEX { adCompressionURLExceptionPolicyRuleListName,
	    adCompressionURLExceptionPolicyRuleName }
  ::= {adCompressionURLExceptionPolicyTable 1}

AdCompressionURLExceptionPolicyEntry ::= SEQUENCE {
  adCompressionURLExceptionPolicyRuleListName	        DisplayString,
  adCompressionURLExceptionPolicyRuleName		DisplayString,
  adCompressionURLExceptionPolicyRulePriority		INTEGER,
  adCompressionURLExceptionPolicyURLType		INTEGER,
  adCompressionURLExceptionPolicyURL			DisplayString,
  adCompressionURLExceptionPolicyCompress               FeatureStatus,
  adCompressionURLExceptionPolicyStatus			RowStatus,
  adCompressionURLExceptionPolicyDomainType		INTEGER,
  adCompressionURLExceptionPolicyDomain			DisplayString
  }

adCompressionURLExceptionPolicyRuleListName OBJECT-TYPE
  SYNTAX DisplayString (SIZE (1..50))
  ACCESS read-only
  STATUS mandatory
  DESCRIPTION
  "Compression URL exception rule list name."
  ::=  {adCompressionURLExceptionPolicyEntry 1}

adCompressionURLExceptionPolicyRuleName OBJECT-TYPE
  SYNTAX DisplayString (SIZE (1..50))
  ACCESS read-only
  STATUS mandatory
  DESCRIPTION
  "Compression URL exception rule name."
  ::=  {adCompressionURLExceptionPolicyEntry 2}

adCompressionURLExceptionPolicyRulePriority OBJECT-TYPE
  SYNTAX INTEGER (1..2147483647)
  ACCESS read-write
  STATUS mandatory
  DESCRIPTION
  " the index that determine the evaluation order."
  DEFVAL { 1 }
  ::=  {adCompressionURLExceptionPolicyEntry 3}

adCompressionURLExceptionPolicyURLType OBJECT-TYPE
  SYNTAX  INTEGER {
        textMatch(1),
        regularExpression(2)
       }
  ACCESS read-write
  STATUS mandatory
  DESCRIPTION
  " whether URL field should be evaluated as simple text or regular expression."
  DEFVAL { textMatch }
  ::=  {adCompressionURLExceptionPolicyEntry 4}

adCompressionURLExceptionPolicyURL OBJECT-TYPE
  SYNTAX DisplayString (SIZE (0..255))
  ACCESS read-write
  STATUS mandatory
  DESCRIPTION
  " Compression URL exception url."
  ::=  {adCompressionURLExceptionPolicyEntry 5}

adCompressionURLExceptionPolicyCompress OBJECT-TYPE
  SYNTAX FeatureStatus
  ACCESS read-write
  STATUS mandatory
  DESCRIPTION
  "Compression URL exception policy compress."
  DEFVAL { disable }
  ::=  { adCompressionURLExceptionPolicyEntry 6}

adCompressionURLExceptionPolicyStatus OBJECT-TYPE
  SYNTAX RowStatus
  ACCESS read-write
  STATUS mandatory
  DESCRIPTION
  "Row status for this entry."
  ::= { adCompressionURLExceptionPolicyEntry 7}

adCompressionURLExceptionPolicyDomainType OBJECT-TYPE
  SYNTAX  INTEGER {
      none(0),
        textMatch(1),
        regularExpression(2)
       }
  ACCESS read-write
  STATUS mandatory
  DESCRIPTION
  " whether Domain field should be evaluated as simple text ,regular expression or not at all."
  DEFVAL { none }
  ::=  {adCompressionURLExceptionPolicyEntry 8}

adCompressionURLExceptionPolicyDomain OBJECT-TYPE
  SYNTAX DisplayString (SIZE (0..255))
  ACCESS read-write
  STATUS mandatory
  DESCRIPTION
  " Compression URL exception domain."
  ::=  {adCompressionURLExceptionPolicyEntry 9}

--  adCacheURLPolicyTable

adCacheURLPolicyTable OBJECT-TYPE
  SYNTAX SEQUENCE OF AdCacheURLPolicyTableEntry
  ACCESS not-accessible
  STATUS mandatory
  DESCRIPTION
  "A table for managing cache URL exception parameters."
  ::= {rsWSDL4Policy 18}

adCacheURLPolicyTableEntry OBJECT-TYPE
  SYNTAX AdCacheURLPolicyTableEntry
  ACCESS not-accessible
  STATUS mandatory
  DESCRIPTION
  " The row definition for this table."
  INDEX { adCacheURLPolicyRuleListName,
	    adCacheURLPolicyRuleName }
  ::= {adCacheURLPolicyTable 1}

AdCacheURLPolicyTableEntry ::= SEQUENCE {
  adCacheURLPolicyRuleListName	DisplayString,
  adCacheURLPolicyRuleName	DisplayString,
  adCacheURLPolicyRulePriority	INTEGER,
  adCacheURLPolicyURLType	INTEGER,
  adCacheURLPolicyURL		DisplayString,
  adCacheURLPolicyCache		FeatureStatus,
  adCacheURLPolicyTime		INTEGER,
  adCacheURLPolicyStatus		RowStatus,
  adCacheURLPolicyDomainType	INTEGER,
  adCacheURLPolicyDomain		DisplayString
  }

adCacheURLPolicyRuleListName OBJECT-TYPE
  SYNTAX DisplayString (SIZE (1..50))
  ACCESS read-only
  STATUS mandatory
  DESCRIPTION
  "Cache URL exception rule list name."
  ::=  {adCacheURLPolicyTableEntry 1}

adCacheURLPolicyRuleName OBJECT-TYPE
  SYNTAX DisplayString (SIZE (1..50))
  ACCESS read-only
  STATUS mandatory
  DESCRIPTION
  "Cache URL exception rule name."
  ::=  {adCacheURLPolicyTableEntry 2}

adCacheURLPolicyRulePriority OBJECT-TYPE
  SYNTAX INTEGER (1..2147483647)
  ACCESS read-write
  STATUS mandatory
  DESCRIPTION
  " the index that determine the evaluation order."
  DEFVAL { 1 }
  ::=  {adCacheURLPolicyTableEntry 3}

adCacheURLPolicyURLType OBJECT-TYPE
  SYNTAX  INTEGER {
        textMatch(1),
        regularExpression(2)
       }
  ACCESS read-write
  STATUS mandatory
  DESCRIPTION
  " whether URL field should be evaluated as simple text or Regular Expression."
  DEFVAL { textMatch }
  ::=  { adCacheURLPolicyTableEntry 4}

adCacheURLPolicyURL OBJECT-TYPE
  SYNTAX DisplayString (SIZE (0..255))
  ACCESS read-write
  STATUS mandatory
  DESCRIPTION
  " Cache URL exception URL."
  ::=  {adCacheURLPolicyTableEntry 5}

adCacheURLPolicyCache OBJECT-TYPE
  SYNTAX FeatureStatus
  ACCESS read-write
  STATUS mandatory
  DESCRIPTION
  "Cache URL policy."
  DEFVAL { disable }
  ::=  { adCacheURLPolicyTableEntry  6}

adCacheURLPolicyTime OBJECT-TYPE
  SYNTAX INTEGER (0.. 43200400)
  ACCESS read-write
  STATUS mandatory
  DESCRIPTION
  "Specifies the time length to cache the object."
  DEFVAL { 86400 }
  ::=  {adCacheURLPolicyTableEntry 7}

adCacheURLPolicyStatus OBJECT-TYPE
  SYNTAX RowStatus
  ACCESS read-write
  STATUS mandatory
  DESCRIPTION
  "Row status for this entry."
  ::= { adCacheURLPolicyTableEntry 8}

adCacheURLPolicyDomainType OBJECT-TYPE
  SYNTAX  INTEGER {
      none(0),
        textMatch(1),
        regularExpression(2)
       }
  ACCESS read-write
  STATUS mandatory
  DESCRIPTION
  " whether domain field should be evaluated as simple text ,Regular Expression or not at all."
  DEFVAL { none }
  ::=  { adCacheURLPolicyTableEntry 9}

adCacheURLPolicyDomain OBJECT-TYPE
  SYNTAX DisplayString (SIZE (0..255))
  ACCESS read-write
  STATUS mandatory
  DESCRIPTION
  " Cache URL exception Domain."
  ::=  {adCacheURLPolicyTableEntry 10}

-- duplicate rule lists
adDuplicateTable OBJECT-TYPE
  SYNTAX SEQUENCE OF AdDuplicateEntry
  ACCESS not-accessible
  STATUS mandatory
  DESCRIPTION
  "A table for managing duplication of entries (like cache-rulelist , compression-rulelist)."
  ::= {rsWSDL4Policy 19}

adDuplicateEntry OBJECT-TYPE
  SYNTAX AdDuplicateEntry
  ACCESS not-accessible
  STATUS mandatory
  DESCRIPTION
  " The row definition for this table."
  INDEX { adDuplicateEntryType }
  ::= { adDuplicateTable 1}

AdDuplicateEntry ::= SEQUENCE {
  adDuplicateEntryType		INTEGER,
  adDuplicateEntrySource 	DisplayString,
  adDuplicateEntryDest 		DisplayString,
  adDuplicateEntryStatus    RowStatus
  }

adDuplicateEntryType OBJECT-TYPE
  SYNTAX  INTEGER {
      none(1),
      compressionBrowserExceptionList (2),
      compressionURLExceptionList (3),
      cacheURLPolicyList (4)
       }
  ACCESS read-write
  STATUS mandatory
  DESCRIPTION
  " specifies the type of the list to duplicate."
  DEFVAL { none }
  ::=  { adDuplicateEntry 1}

adDuplicateEntrySource OBJECT-TYPE
  SYNTAX DisplayString
  ACCESS read-write
  STATUS mandatory
  DESCRIPTION
  " the name of the list to be duplicated."
  ::=  { adDuplicateEntry 2}

adDuplicateEntryDest OBJECT-TYPE
  SYNTAX DisplayString
  ACCESS read-write
  STATUS mandatory
  DESCRIPTION
  " the name of new list to create."
  ::=  { adDuplicateEntry 3}

adDuplicateEntryStatus OBJECT-TYPE
   SYNTAX  RowStatus
   ACCESS read-write
   STATUS mandatory
   DESCRIPTION
      ""
   ::=  {adDuplicateEntry 4}

-- Acceleration Engine Statistics

adAccelerationEngineThroughputStatisticsTable OBJECT-TYPE
   SYNTAX SEQUENCE OF AdAccelerationEngineThroughputStatisticsEntry
   ACCESS not-accessible
   STATUS mandatory
   DESCRIPTION
       "A table for showing acceleration engine throughput statistics."
   ::= {rsWSDL4Policy 24}

adAccelerationEngineThroughputStatisticsEntry OBJECT-TYPE
   SYNTAX AdAccelerationEngineThroughputStatisticsEntry
   ACCESS not-accessible
   STATUS  mandatory
   DESCRIPTION
       " The row definition for this table."
   INDEX  { adAccelerationEngineThroughputStatisticsParameter}
   ::= {adAccelerationEngineThroughputStatisticsTable 1}

AdAccelerationEngineThroughputStatisticsEntry  ::= SEQUENCE {
   	adAccelerationEngineThroughputStatisticsParameter		DisplayString,
   	adAccelerationEngineThroughputStatisticsMbitsIn 	    INTEGER,
   	adAccelerationEngineThroughputStatisticsMbitsOut	    INTEGER,
   	adAccelerationEngineThroughputStatisticsTwoWay  	    INTEGER
	}

adAccelerationEngineThroughputStatisticsParameter OBJECT-TYPE
   SYNTAX  DisplayString
   ACCESS  read-only
   STATUS  mandatory
   DESCRIPTION
       "The parameter name ( client side/server side etc')."
   ::= {adAccelerationEngineThroughputStatisticsEntry 1}

adAccelerationEngineThroughputStatisticsMbitsIn OBJECT-TYPE
   SYNTAX  INTEGER
   ACCESS  read-only
   STATUS  mandatory
   DESCRIPTION
       "The throughtput in of this parameter."
   ::= {adAccelerationEngineThroughputStatisticsEntry 2}

adAccelerationEngineThroughputStatisticsMbitsOut OBJECT-TYPE
   SYNTAX  INTEGER
   ACCESS  read-only
   STATUS  mandatory
   DESCRIPTION
       "The throughtput out of this parameter."
   ::= {adAccelerationEngineThroughputStatisticsEntry 3}

adAccelerationEngineThroughputStatisticsTwoWay OBJECT-TYPE
   SYNTAX  INTEGER
   ACCESS  read-only
   STATUS  mandatory
   DESCRIPTION
       "The throughtput twoway  of this parameter."
   ::= {adAccelerationEngineThroughputStatisticsEntry 4}

adAccelerationEngineThroughputPerL4StatisticsTable OBJECT-TYPE
   SYNTAX SEQUENCE OF AdAccelerationEngineThroughputPerL4StatisticsEntry
   ACCESS not-accessible
   STATUS mandatory
   DESCRIPTION
       "A table for showing acceleration engine throughput per L4 statistics."
   ::= {rsWSDL4Policy 25}

adAccelerationEngineThroughputPerL4StatisticsEntry OBJECT-TYPE
   SYNTAX AdAccelerationEngineThroughputPerL4StatisticsEntry
   ACCESS not-accessible
   STATUS  mandatory
   DESCRIPTION
       " The row definition for this table."
   INDEX  { adAccelerationEngineThroughputPerL4StatisticsName}
   ::= {adAccelerationEngineThroughputPerL4StatisticsTable 1}

AdAccelerationEngineThroughputPerL4StatisticsEntry  ::= SEQUENCE {
   	adAccelerationEngineThroughputPerL4StatisticsName		DisplayString,
   	adAccelerationEngineThroughputPerL4StatisticsTotalMbitsIn    INTEGER,
   	adAccelerationEngineThroughputPerL4StatisticsTotalMbitsOut   INTEGER,
   	adAccelerationEngineThroughputPerL4StatisticsTotalTwoWay     INTEGER,
   	adAccelerationEngineThroughputPerL4StatisticsClientMbitsIn   INTEGER,
   	adAccelerationEngineThroughputPerL4StatisticsClientMbitsOut  INTEGER,
   	adAccelerationEngineThroughputPerL4StatisticsClientTwoWay    INTEGER,
   	adAccelerationEngineThroughputPerL4StatisticsServerMbitsIn    INTEGER,
   	adAccelerationEngineThroughputPerL4StatisticsServerMbitsOut   INTEGER,
   	adAccelerationEngineThroughputPerL4StatisticsServerTwoWay     INTEGER
	}

adAccelerationEngineThroughputPerL4StatisticsName OBJECT-TYPE
   SYNTAX  DisplayString
   ACCESS  read-only
   STATUS  mandatory
   DESCRIPTION
       "The L4 name."
   ::= {adAccelerationEngineThroughputPerL4StatisticsEntry 1}

adAccelerationEngineThroughputPerL4StatisticsTotalMbitsIn OBJECT-TYPE
   SYNTAX  INTEGER
   ACCESS  read-only
   STATUS  mandatory
   DESCRIPTION
       "The total throughtput in."
   ::= {adAccelerationEngineThroughputPerL4StatisticsEntry 2}

adAccelerationEngineThroughputPerL4StatisticsTotalMbitsOut OBJECT-TYPE
   SYNTAX  INTEGER
   ACCESS  read-only
   STATUS  mandatory
   DESCRIPTION
       "The total throughtput out."
   ::= {adAccelerationEngineThroughputPerL4StatisticsEntry 3}

adAccelerationEngineThroughputPerL4StatisticsTotalTwoWay OBJECT-TYPE
   SYNTAX  INTEGER
   ACCESS  read-only
   STATUS  mandatory
   DESCRIPTION
       "The total throughtput both ways."
   ::= {adAccelerationEngineThroughputPerL4StatisticsEntry 4}

adAccelerationEngineThroughputPerL4StatisticsClientMbitsIn OBJECT-TYPE
   SYNTAX  INTEGER
   ACCESS  read-only
   STATUS  mandatory
   DESCRIPTION
       "The Client throughtput in."
   ::= {adAccelerationEngineThroughputPerL4StatisticsEntry 5}

adAccelerationEngineThroughputPerL4StatisticsClientMbitsOut OBJECT-TYPE
   SYNTAX  INTEGER
   ACCESS  read-only
   STATUS  mandatory
   DESCRIPTION
       "The Client throughtput out."
   ::= {adAccelerationEngineThroughputPerL4StatisticsEntry 6}

adAccelerationEngineThroughputPerL4StatisticsClientTwoWay OBJECT-TYPE
   SYNTAX  INTEGER
   ACCESS  read-only
   STATUS  mandatory
   DESCRIPTION
       "The Client throughtput both ways."
   ::= {adAccelerationEngineThroughputPerL4StatisticsEntry 7}

adAccelerationEngineThroughputPerL4StatisticsServerMbitsIn OBJECT-TYPE
   SYNTAX  INTEGER
   ACCESS  read-only
   STATUS  mandatory
   DESCRIPTION
       "The Server throughtput in."
   ::= {adAccelerationEngineThroughputPerL4StatisticsEntry 8}

adAccelerationEngineThroughputPerL4StatisticsServerMbitsOut OBJECT-TYPE
   SYNTAX  INTEGER
   ACCESS  read-only
   STATUS  mandatory
   DESCRIPTION
       "The Server throughtput out."
   ::= {adAccelerationEngineThroughputPerL4StatisticsEntry 9}

adAccelerationEngineThroughputPerL4StatisticsServerTwoWay OBJECT-TYPE
   SYNTAX  INTEGER
   ACCESS  read-only
   STATUS  mandatory
   DESCRIPTION
       "The Server throughtput both ways."
   ::= {adAccelerationEngineThroughputPerL4StatisticsEntry 10}

   adAccelerationEngineThroughputStatisticsReset OBJECT-TYPE
    SYNTAX  INTEGER {
       reset(1)
     }
    ACCESS  read-write
    STATUS  mandatory
    DESCRIPTION
      "This variable resets acceleration engine throughput statistics ."
   ::= { rsWSDL4Policy 26  }

adAccelerationEngineConnectionStatisticsTable OBJECT-TYPE
   SYNTAX SEQUENCE OF AdAccelerationEngineConnectionStatisticsEntry
   ACCESS not-accessible
   STATUS mandatory
   DESCRIPTION
       "A table for showing acceleration engine Connection statistics."
   ::= {rsWSDL4Policy 27}

adAccelerationEngineConnectionStatisticsEntry OBJECT-TYPE
   SYNTAX AdAccelerationEngineConnectionStatisticsEntry
   ACCESS not-accessible
   STATUS  mandatory
   DESCRIPTION
       " The row definition for this table."
   INDEX  { adAccelerationEngineConnectionStatisticsParameter}
   ::= {adAccelerationEngineConnectionStatisticsTable 1}

AdAccelerationEngineConnectionStatisticsEntry  ::= SEQUENCE {
   	adAccelerationEngineConnectionStatisticsParameter	 DisplayString,
   	adAccelerationEngineConnectionStatisticsValue 	     INTEGER
	}

adAccelerationEngineConnectionStatisticsParameter OBJECT-TYPE
   SYNTAX  DisplayString
   ACCESS  read-only
   STATUS  mandatory
   DESCRIPTION
       "The parameter name."
   ::= {adAccelerationEngineConnectionStatisticsEntry 1}

adAccelerationEngineConnectionStatisticsValue OBJECT-TYPE
   SYNTAX  INTEGER
   ACCESS  read-only
   STATUS  mandatory
   DESCRIPTION
       "The value."
   ::= {adAccelerationEngineConnectionStatisticsEntry 2}

adAccelerationEngineConnectionPerL4StatisticsTable OBJECT-TYPE
   SYNTAX SEQUENCE OF AdAccelerationEngineConnectionPerL4StatisticsEntry
   ACCESS not-accessible
   STATUS mandatory
   DESCRIPTION
       "A table for showing acceleration engine Connection per L4 statistics."
   ::= {rsWSDL4Policy 28}

adAccelerationEngineConnectionPerL4StatisticsEntry OBJECT-TYPE
   SYNTAX AdAccelerationEngineConnectionPerL4StatisticsEntry
   ACCESS not-accessible
   STATUS  mandatory
   DESCRIPTION
       " The row definition for this table."
   INDEX  { adAccelerationEngineConnectionPerL4StatisticsName}
   ::= {adAccelerationEngineConnectionPerL4StatisticsTable 1}

AdAccelerationEngineConnectionPerL4StatisticsEntry  ::= SEQUENCE {
   	adAccelerationEngineConnectionPerL4StatisticsName		        DisplayString,
   	adAccelerationEngineConnectionPerL4StatisticsClientConcurrent   INTEGER,
   	adAccelerationEngineConnectionPerL4StatisticsClientNew          INTEGER,
   	adAccelerationEngineConnectionPerL4StatisticsServerConcurrent   INTEGER,
   	adAccelerationEngineConnectionPerL4StatisticsServerNew          INTEGER,
	adAccelerationEngineConnectionPerL4StatisticsTotalConcurrent    INTEGER,
   	adAccelerationEngineConnectionPerL4StatisticsTotalNew           INTEGER,
   	adAccelerationEngineConnectionPerL4StatisticsMultiplexingRatio  INTEGER,
   	adAccelerationEngineConnectionPerL4StatisticsNewEstablishRate   INTEGER
	}

adAccelerationEngineConnectionPerL4StatisticsName OBJECT-TYPE
   SYNTAX  DisplayString
   ACCESS  read-only
   STATUS  mandatory
   DESCRIPTION
       "The L4 name."
   ::= {adAccelerationEngineConnectionPerL4StatisticsEntry 1}

adAccelerationEngineConnectionPerL4StatisticsClientConcurrent OBJECT-TYPE
   SYNTAX  INTEGER
   ACCESS  read-only
   STATUS  mandatory
   DESCRIPTION
       "The Client concurrent connections."
   ::= {adAccelerationEngineConnectionPerL4StatisticsEntry 2}

adAccelerationEngineConnectionPerL4StatisticsClientNew OBJECT-TYPE
   SYNTAX  INTEGER
   ACCESS  read-only
   STATUS  mandatory
   DESCRIPTION
       "The Client new connections."
   ::= {adAccelerationEngineConnectionPerL4StatisticsEntry 3}

adAccelerationEngineConnectionPerL4StatisticsServerConcurrent OBJECT-TYPE
   SYNTAX  INTEGER
   ACCESS  read-only
   STATUS  mandatory
   DESCRIPTION
       "The Server concurrent connections."
   ::= {adAccelerationEngineConnectionPerL4StatisticsEntry 4}

adAccelerationEngineConnectionPerL4StatisticsServerNew OBJECT-TYPE
   SYNTAX  INTEGER
   ACCESS  read-only
   STATUS  mandatory
   DESCRIPTION
       "The Server new connections."
   ::= {adAccelerationEngineConnectionPerL4StatisticsEntry 5}

adAccelerationEngineConnectionPerL4StatisticsTotalConcurrent OBJECT-TYPE
   SYNTAX  INTEGER
   ACCESS  read-only
   STATUS  mandatory
   DESCRIPTION
       "The total concurrent connections."
   ::= {adAccelerationEngineConnectionPerL4StatisticsEntry 6}

adAccelerationEngineConnectionPerL4StatisticsTotalNew OBJECT-TYPE
   SYNTAX  INTEGER
   ACCESS  read-only
   STATUS  mandatory
   DESCRIPTION
       "The total new connections."
   ::= {adAccelerationEngineConnectionPerL4StatisticsEntry 7}

adAccelerationEngineConnectionPerL4StatisticsMultiplexingRatio OBJECT-TYPE
   SYNTAX  INTEGER
   ACCESS  read-only
   STATUS  mandatory
   DESCRIPTION
       "The connections multiplexing ratio."
   ::= {adAccelerationEngineConnectionPerL4StatisticsEntry 8}

adAccelerationEngineConnectionPerL4StatisticsNewEstablishRate OBJECT-TYPE
   SYNTAX  INTEGER
   ACCESS  read-only
   STATUS  mandatory
   DESCRIPTION
       "The new connections establish rate."
   ::= {adAccelerationEngineConnectionPerL4StatisticsEntry 9}

   adAccelerationEngineConnectionStatisticsReset OBJECT-TYPE
    SYNTAX  INTEGER {
       reset(1)
     }
    ACCESS  read-write
    STATUS  mandatory
    DESCRIPTION
      "This variable resets acceleration engine Connection statistics ."
   ::= { rsWSDL4Policy 29  }

adAccelerationEngineHTTPRequestsStatisticsTable OBJECT-TYPE
   SYNTAX SEQUENCE OF AdAccelerationEngineHTTPRequestsStatisticsEntry
   ACCESS not-accessible
   STATUS mandatory
   DESCRIPTION
       "A table for showing acceleration engine HTTP requests statistics."
   ::= {rsWSDL4Policy 30}

adAccelerationEngineHTTPRequestsStatisticsEntry OBJECT-TYPE
   SYNTAX AdAccelerationEngineHTTPRequestsStatisticsEntry
   ACCESS not-accessible
   STATUS  mandatory
   DESCRIPTION
       " The row definition for this table."
   INDEX  { adAccelerationEngineHTTPRequestsStatisticsParameter}
   ::= {adAccelerationEngineHTTPRequestsStatisticsTable 1}

AdAccelerationEngineHTTPRequestsStatisticsEntry  ::= SEQUENCE {
   	adAccelerationEngineHTTPRequestsStatisticsParameter	 DisplayString,
   	adAccelerationEngineHTTPRequestsStatisticsValue 	     INTEGER
	}

adAccelerationEngineHTTPRequestsStatisticsParameter OBJECT-TYPE
   SYNTAX  DisplayString
   ACCESS  read-only
   STATUS  mandatory
   DESCRIPTION
       "The parameter name."
   ::= {adAccelerationEngineHTTPRequestsStatisticsEntry 1}

adAccelerationEngineHTTPRequestsStatisticsValue OBJECT-TYPE
   SYNTAX  INTEGER
   ACCESS  read-only
   STATUS  mandatory
   DESCRIPTION
       "The value."
   ::= {adAccelerationEngineHTTPRequestsStatisticsEntry 2}

adAccelerationEngineHTTPRequestsPerL4StatisticsTable OBJECT-TYPE
   SYNTAX SEQUENCE OF AdAccelerationEngineHTTPRequestsPerL4StatisticsEntry
   ACCESS not-accessible
   STATUS mandatory
   DESCRIPTION
       "A table for showing acceleration engine HTTP Requests per L4 statistics."
   ::= {rsWSDL4Policy 31}

adAccelerationEngineHTTPRequestsPerL4StatisticsEntry OBJECT-TYPE
   SYNTAX AdAccelerationEngineHTTPRequestsPerL4StatisticsEntry
   ACCESS not-accessible
   STATUS  mandatory
   DESCRIPTION
       " The row definition for this table."
   INDEX  { adAccelerationEngineHTTPRequestsPerL4StatisticsName}
   ::= {adAccelerationEngineHTTPRequestsPerL4StatisticsTable 1}

AdAccelerationEngineHTTPRequestsPerL4StatisticsEntry  ::= SEQUENCE {
   	adAccelerationEngineHTTPRequestsPerL4StatisticsName		               DisplayString,
   	adAccelerationEngineHTTPRequestsPerL4StatisticsRequestClientsAcclEng    INTEGER,
   	adAccelerationEngineHTTPRequestsPerL4StatisticsRequestAcclEngServers    INTEGER,
   	adAccelerationEngineHTTPRequestsPerL4StatisticsResponseClientsAcclEng   INTEGER,
   	adAccelerationEngineHTTPRequestsPerL4StatisticsResponseAcclEngServers   INTEGER,
   	adAccelerationEngineHTTPRequestsPerL4StatisticsTransactionRate          INTEGER
	}

adAccelerationEngineHTTPRequestsPerL4StatisticsName OBJECT-TYPE
   SYNTAX  DisplayString
   ACCESS  read-only
   STATUS  mandatory
   DESCRIPTION
       "The L4 name."
   ::= {adAccelerationEngineHTTPRequestsPerL4StatisticsEntry 1}

adAccelerationEngineHTTPRequestsPerL4StatisticsRequestClientsAcclEng OBJECT-TYPE
   SYNTAX  INTEGER
   ACCESS  read-only
   STATUS  mandatory
   DESCRIPTION
       "HTTP requests from clients to acceleration engine."
   ::= {adAccelerationEngineHTTPRequestsPerL4StatisticsEntry 2}

adAccelerationEngineHTTPRequestsPerL4StatisticsRequestAcclEngServers OBJECT-TYPE
   SYNTAX  INTEGER
   ACCESS  read-only
   STATUS  mandatory
   DESCRIPTION
       "HTTP requests from acceleration engine to servers."
   ::= {adAccelerationEngineHTTPRequestsPerL4StatisticsEntry 3}

adAccelerationEngineHTTPRequestsPerL4StatisticsResponseClientsAcclEng OBJECT-TYPE
   SYNTAX  INTEGER
   ACCESS  read-only
   STATUS  mandatory
   DESCRIPTION
       "HTTP responses from clients to acceleration engine."
   ::= {adAccelerationEngineHTTPRequestsPerL4StatisticsEntry 4}

adAccelerationEngineHTTPRequestsPerL4StatisticsResponseAcclEngServers OBJECT-TYPE
   SYNTAX  INTEGER
   ACCESS  read-only
   STATUS  mandatory
   DESCRIPTION
       "HTTP responses from acceleration engine to servers."
   ::= {adAccelerationEngineHTTPRequestsPerL4StatisticsEntry 5}

adAccelerationEngineHTTPRequestsPerL4StatisticsTransactionRate OBJECT-TYPE
   SYNTAX  INTEGER
   ACCESS  read-only
   STATUS  mandatory
   DESCRIPTION
       "HTTP Transaction rate."
   ::= {adAccelerationEngineHTTPRequestsPerL4StatisticsEntry 6}

adAccelerationEngineHTTPRequestsStatisticsReset OBJECT-TYPE
    SYNTAX  INTEGER {
       reset(1)
     }
    ACCESS  read-write
    STATUS  mandatory
    DESCRIPTION
      "This variable resets acceleration engine HTTP requests statistics ."
   ::= { rsWSDL4Policy 32  }

adAccelerationEngineHTTPSummaryStatisticsTable OBJECT-TYPE
   SYNTAX SEQUENCE OF AdAccelerationEngineHTTPSummaryStatisticsEntry
   ACCESS not-accessible
   STATUS mandatory
   DESCRIPTION
       "A table for showing acceleration engine HTTP statistics summary."
   ::= {rsWSDL4Policy 33}

adAccelerationEngineHTTPSummaryStatisticsEntry OBJECT-TYPE
   SYNTAX AdAccelerationEngineHTTPSummaryStatisticsEntry
   ACCESS not-accessible
   STATUS  mandatory
   DESCRIPTION
       " The row definition for this table."
   INDEX  { adAccelerationEngineHTTPSummaryStatisticsParameter}
   ::= {adAccelerationEngineHTTPSummaryStatisticsTable 1}

AdAccelerationEngineHTTPSummaryStatisticsEntry  ::= SEQUENCE {
   	adAccelerationEngineHTTPSummaryStatisticsParameter	 DisplayString,
   	adAccelerationEngineHTTPSummaryStatisticsValue 	     INTEGER
	}

adAccelerationEngineHTTPSummaryStatisticsParameter OBJECT-TYPE
   SYNTAX  DisplayString
   ACCESS  read-only
   STATUS  mandatory
   DESCRIPTION
       "The parameter name."
   ::= {adAccelerationEngineHTTPSummaryStatisticsEntry 1}

adAccelerationEngineHTTPSummaryStatisticsValue OBJECT-TYPE
   SYNTAX  INTEGER
   ACCESS  read-only
   STATUS  mandatory
   DESCRIPTION
       "The value."
   ::= {adAccelerationEngineHTTPSummaryStatisticsEntry 2}

adAccelerationEngineHTTPSummaryPerL4StatisticsTable OBJECT-TYPE
   SYNTAX SEQUENCE OF AdAccelerationEngineHTTPSummaryPerL4StatisticsEntry
   ACCESS not-accessible
   STATUS mandatory
   DESCRIPTION
       "A table for showing acceleration engine HTTP Summary per L4 statistics."
   ::= {rsWSDL4Policy 34}

adAccelerationEngineHTTPSummaryPerL4StatisticsEntry OBJECT-TYPE
   SYNTAX AdAccelerationEngineHTTPSummaryPerL4StatisticsEntry
   ACCESS not-accessible
   STATUS  mandatory
   DESCRIPTION
       " The row definition for this table."
   INDEX  { adAccelerationEngineHTTPSummaryPerL4StatisticsName}
   ::= {adAccelerationEngineHTTPSummaryPerL4StatisticsTable 1}

AdAccelerationEngineHTTPSummaryPerL4StatisticsEntry  ::= SEQUENCE {
   	adAccelerationEngineHTTPSummaryPerL4StatisticsName		          DisplayString,
   	adAccelerationEngineHTTPSummaryPerL4StatisticsClientsKeepAlive    INTEGER,
   	adAccelerationEngineHTTPSummaryPerL4StatisticsHTTP10v11Ratio      INTEGER,
   	adAccelerationEngineHTTPSummaryPerL4StatisticsHTTP2HTTPSRedirect  INTEGER,
   	adAccelerationEngineHTTPSummaryPerL4StatisticsAverageRequets      INTEGER,
   	adAccelerationEngineHTTPSummaryPerL4StatisticsSmaller1KB          INTEGER,
   	adAccelerationEngineHTTPSummaryPerL4StatisticsSmaller10KB         INTEGER,
   	adAccelerationEngineHTTPSummaryPerL4StatisticsSmaller50KB         INTEGER,
   	adAccelerationEngineHTTPSummaryPerL4StatisticsSmaller100KB        INTEGER,
   	adAccelerationEngineHTTPSummaryPerL4StatisticsLarger100KB         INTEGER
	}

adAccelerationEngineHTTPSummaryPerL4StatisticsName OBJECT-TYPE
   SYNTAX  DisplayString
   ACCESS  read-only
   STATUS  mandatory
   DESCRIPTION
       "The L4 name."
   ::= {adAccelerationEngineHTTPSummaryPerL4StatisticsEntry 1}

adAccelerationEngineHTTPSummaryPerL4StatisticsClientsKeepAlive OBJECT-TYPE
   SYNTAX  INTEGER
   ACCESS  read-only
   STATUS  mandatory
   DESCRIPTION
       "Percentage of HTTP clients that uses keep alive."
   ::= {adAccelerationEngineHTTPSummaryPerL4StatisticsEntry 2}

adAccelerationEngineHTTPSummaryPerL4StatisticsHTTP10v11Ratio OBJECT-TYPE
   SYNTAX  INTEGER
   ACCESS  read-only
   STATUS  mandatory
   DESCRIPTION
       "Ratio of HTTP clients that uses v1.0 vs v1.1."
   ::= {adAccelerationEngineHTTPSummaryPerL4StatisticsEntry 3}

adAccelerationEngineHTTPSummaryPerL4StatisticsHTTP2HTTPSRedirect OBJECT-TYPE
   SYNTAX  INTEGER
   ACCESS  read-only
   STATUS  mandatory
   DESCRIPTION
       "Number of HTTP to HTTPS redirections."
   ::= {adAccelerationEngineHTTPSummaryPerL4StatisticsEntry 4}

adAccelerationEngineHTTPSummaryPerL4StatisticsAverageRequets OBJECT-TYPE
   SYNTAX  INTEGER
   ACCESS  read-only
   STATUS  mandatory
   DESCRIPTION
       "Average number of requests per connection."
   ::= {adAccelerationEngineHTTPSummaryPerL4StatisticsEntry 5}

adAccelerationEngineHTTPSummaryPerL4StatisticsSmaller1KB OBJECT-TYPE
   SYNTAX  INTEGER
   ACCESS  read-only
   STATUS  mandatory
   DESCRIPTION
       "Number of Responses with content size smaller than 1 KB."
   ::= {adAccelerationEngineHTTPSummaryPerL4StatisticsEntry 6}

adAccelerationEngineHTTPSummaryPerL4StatisticsSmaller10KB OBJECT-TYPE
   SYNTAX  INTEGER
   ACCESS  read-only
   STATUS  mandatory
   DESCRIPTION
       "Number of Responses with content size smaller than 10 KB."
   ::= {adAccelerationEngineHTTPSummaryPerL4StatisticsEntry 7}

adAccelerationEngineHTTPSummaryPerL4StatisticsSmaller50KB OBJECT-TYPE
   SYNTAX  INTEGER
   ACCESS  read-only
   STATUS  mandatory
   DESCRIPTION
       "Number of Responses with content size smaller than 50 KB."
   ::= {adAccelerationEngineHTTPSummaryPerL4StatisticsEntry 8}

adAccelerationEngineHTTPSummaryPerL4StatisticsSmaller100KB OBJECT-TYPE
   SYNTAX  INTEGER
   ACCESS  read-only
   STATUS  mandatory
   DESCRIPTION
       "Number of Responses with content size smaller than 100 KB."
   ::= {adAccelerationEngineHTTPSummaryPerL4StatisticsEntry 9}

adAccelerationEngineHTTPSummaryPerL4StatisticsLarger100KB OBJECT-TYPE
   SYNTAX  INTEGER
   ACCESS  read-only
   STATUS  mandatory
   DESCRIPTION
       "Number of Responses with content size larger than 100 KB."
   ::= {adAccelerationEngineHTTPSummaryPerL4StatisticsEntry 10}

adAccelerationEngineHTTPSummaryStatisticsReset OBJECT-TYPE
    SYNTAX  INTEGER {
       reset(1)
     }
    ACCESS  read-write
    STATUS  mandatory
    DESCRIPTION
      "This variable resets acceleration engine HTTP statistics summary."
   ::= { rsWSDL4Policy 35  }

adAccelerationEngineSSLSummaryStatisticsTable OBJECT-TYPE
   SYNTAX SEQUENCE OF AdAccelerationEngineSSLSummaryStatisticsEntry
   ACCESS not-accessible
   STATUS mandatory
   DESCRIPTION
       "A table for showing acceleration engine SSL statistics summary."
   ::= {rsWSDL4Policy 36}

adAccelerationEngineSSLSummaryStatisticsEntry OBJECT-TYPE
   SYNTAX AdAccelerationEngineSSLSummaryStatisticsEntry
   ACCESS not-accessible
   STATUS  mandatory
   DESCRIPTION
       " The row definition for this table."
   INDEX  { adAccelerationEngineSSLSummaryStatisticsParameter}
   ::= {adAccelerationEngineSSLSummaryStatisticsTable 1}

AdAccelerationEngineSSLSummaryStatisticsEntry  ::= SEQUENCE {
   	adAccelerationEngineSSLSummaryStatisticsParameter	 DisplayString,
   	adAccelerationEngineSSLSummaryStatisticsValue 	     INTEGER
	}

adAccelerationEngineSSLSummaryStatisticsParameter OBJECT-TYPE
   SYNTAX  DisplayString
   ACCESS  read-only
   STATUS  mandatory
   DESCRIPTION
       "The parameter name."
   ::= {adAccelerationEngineSSLSummaryStatisticsEntry 1}

adAccelerationEngineSSLSummaryStatisticsValue OBJECT-TYPE
   SYNTAX  INTEGER
   ACCESS  read-only
   STATUS  mandatory
   DESCRIPTION
       "The value."
   ::= {adAccelerationEngineSSLSummaryStatisticsEntry 2}

adAccelerationEngineSSLSummaryPerL4StatisticsTable OBJECT-TYPE
   SYNTAX SEQUENCE OF AdAccelerationEngineSSLSummaryPerL4StatisticsEntry
   ACCESS not-accessible
   STATUS mandatory
   DESCRIPTION
       "A table for showing acceleration engine SSL Summary per L4 statistics."
   ::= {rsWSDL4Policy 37}

adAccelerationEngineSSLSummaryPerL4StatisticsEntry OBJECT-TYPE
   SYNTAX AdAccelerationEngineSSLSummaryPerL4StatisticsEntry
   ACCESS not-accessible
   STATUS  mandatory
   DESCRIPTION
       " The row definition for this table."
   INDEX  { adAccelerationEngineSSLSummaryPerL4StatisticsName}
   ::= {adAccelerationEngineSSLSummaryPerL4StatisticsTable 1}

AdAccelerationEngineSSLSummaryPerL4StatisticsEntry  ::= SEQUENCE {
   	adAccelerationEngineSSLSummaryPerL4StatisticsName		              DisplayString,
   	adAccelerationEngineSSLSummaryPerL4StatisticsNewHandshake             INTEGER,
   	adAccelerationEngineSSLSummaryPerL4StatisticsReusedSessions           INTEGER,
   	adAccelerationEngineSSLSummaryPerL4StatisticsReusedSessionPrecentage  INTEGER,
   	adAccelerationEngineSSLSummaryPerL4StatisticsV2Precentage             INTEGER,
   	adAccelerationEngineSSLSummaryPerL4StatisticsV3Precentage             INTEGER,
   	adAccelerationEngineSSLSummaryPerL4StatisticsTLSPrecentage            INTEGER
	}

adAccelerationEngineSSLSummaryPerL4StatisticsName OBJECT-TYPE
   SYNTAX  DisplayString
   ACCESS  read-only
   STATUS  mandatory
   DESCRIPTION
       "The L4 name."
   ::= {adAccelerationEngineSSLSummaryPerL4StatisticsEntry 1}

adAccelerationEngineSSLSummaryPerL4StatisticsNewHandshake OBJECT-TYPE
   SYNTAX  INTEGER
   ACCESS  read-only
   STATUS  mandatory
   DESCRIPTION
       "New SSL handshake per second."
   ::= {adAccelerationEngineSSLSummaryPerL4StatisticsEntry 2}

adAccelerationEngineSSLSummaryPerL4StatisticsReusedSessions OBJECT-TYPE
   SYNTAX  INTEGER
   ACCESS  read-only
   STATUS  mandatory
   DESCRIPTION
       "SSL reused sessions."
   ::= {adAccelerationEngineSSLSummaryPerL4StatisticsEntry 3}

adAccelerationEngineSSLSummaryPerL4StatisticsReusedSessionPrecentage OBJECT-TYPE
   SYNTAX  INTEGER
   ACCESS  read-only
   STATUS  mandatory
   DESCRIPTION
       "SSL reused sessions percentage."
   ::= {adAccelerationEngineSSLSummaryPerL4StatisticsEntry 4}

adAccelerationEngineSSLSummaryPerL4StatisticsV2Precentage OBJECT-TYPE
   SYNTAX  INTEGER
   ACCESS  read-only
   STATUS  mandatory
   DESCRIPTION
       "SSL v2 percentage.The percentage of using SSL2 out of the total use of SSL2,SSL3 and TLS"
   ::= {adAccelerationEngineSSLSummaryPerL4StatisticsEntry 5}

adAccelerationEngineSSLSummaryPerL4StatisticsV3Precentage OBJECT-TYPE
   SYNTAX  INTEGER
   ACCESS  read-only
   STATUS  mandatory
   DESCRIPTION
       "SSL v3 percentage.The percentage of using SSL3 out of the total use of SSL2,SSL3 and TLS"
   ::= {adAccelerationEngineSSLSummaryPerL4StatisticsEntry 6}

adAccelerationEngineSSLSummaryPerL4StatisticsTLSPrecentage OBJECT-TYPE
   SYNTAX  INTEGER
   ACCESS  read-only
   STATUS  mandatory
   DESCRIPTION
       "TLS percentage.The percentage of using TLS out of the total use of SSL2,SSL3 and TLS"
   ::= {adAccelerationEngineSSLSummaryPerL4StatisticsEntry 7}

adAccelerationEngineSSLSummaryPerL4StatisticsReset OBJECT-TYPE
    SYNTAX  INTEGER {
       reset(1)
     }
    ACCESS  read-write
    STATUS  mandatory
    DESCRIPTION
      "This variable resets acceleration engine SSL statistics summary."
   ::= { rsWSDL4Policy 38  }

adAccelerationEngineCacheSummaryStatisticsTable OBJECT-TYPE
   SYNTAX SEQUENCE OF AdAccelerationEngineCacheSummaryStatisticsEntry
   ACCESS not-accessible
   STATUS mandatory
   DESCRIPTION
       "A table for showing acceleration engine Cache statistics summary."
   ::= {rsWSDL4Policy 39}

adAccelerationEngineCacheSummaryStatisticsEntry OBJECT-TYPE
   SYNTAX AdAccelerationEngineCacheSummaryStatisticsEntry
   ACCESS not-accessible
   STATUS  mandatory
   DESCRIPTION
       " The row definition for this table."
   INDEX  { adAccelerationEngineCacheSummaryStatisticsParameter}
   ::= {adAccelerationEngineCacheSummaryStatisticsTable 1}

AdAccelerationEngineCacheSummaryStatisticsEntry  ::= SEQUENCE {
   	adAccelerationEngineCacheSummaryStatisticsParameter	 DisplayString,
   	adAccelerationEngineCacheSummaryStatisticsValue 	     INTEGER
	}

adAccelerationEngineCacheSummaryStatisticsParameter OBJECT-TYPE
   SYNTAX  DisplayString
   ACCESS  read-only
   STATUS  mandatory
   DESCRIPTION
       "The parameter name."
   ::= {adAccelerationEngineCacheSummaryStatisticsEntry 1}

adAccelerationEngineCacheSummaryStatisticsValue OBJECT-TYPE
   SYNTAX  INTEGER
   ACCESS  read-only
   STATUS  mandatory
   DESCRIPTION
       "The value."
   ::= {adAccelerationEngineCacheSummaryStatisticsEntry 2}

adAccelerationEngineCacheRatePerL4StatisticsTable OBJECT-TYPE
   SYNTAX SEQUENCE OF AdAccelerationEngineCacheRatePerL4StatisticsEntry
   ACCESS not-accessible
   STATUS mandatory
   DESCRIPTION
       "A table for showing acceleration engine Cache Rate per L4 statistics."
   ::= {rsWSDL4Policy 40}

adAccelerationEngineCacheRatePerL4StatisticsEntry OBJECT-TYPE
   SYNTAX AdAccelerationEngineCacheRatePerL4StatisticsEntry
   ACCESS not-accessible
   STATUS  mandatory
   DESCRIPTION
       " The row definition for this table."
   INDEX  { adAccelerationEngineCacheRatePerL4StatisticsName}
   ::= {adAccelerationEngineCacheRatePerL4StatisticsTable 1}

AdAccelerationEngineCacheRatePerL4StatisticsEntry  ::= SEQUENCE {
   	adAccelerationEngineCacheRatePerL4StatisticsName		              DisplayString,
   	adAccelerationEngineCacheRatePerL4StatisticsObjectFromCache  INTEGER,
   	adAccelerationEngineCacheRatePerL4StatisticsHits             INTEGER,
   	adAccelerationEngineCacheRatePerL4StatisticsServingRate      INTEGER,
   	adAccelerationEngineCacheRatePerL4StatisticsNewCacheObjects  INTEGER,
   	adAccelerationEngineCacheRatePerL4StatisticsCachingRate      INTEGER,
   	adAccelerationEngineCacheRatePerL4StatisticsNewCacheBytes    INTEGER,
   	adAccelerationEngineCacheRatePerL4StatisticsBytesCachingRate INTEGER,
	adAccelerationEngineCacheRatePerL4StatisticsBcoProccessed    INTEGER,
	adAccelerationEngineCacheRatePerL4StatisticsBcoOptimized     INTEGER,
	adAccelerationEngineCacheRatePerL4StatisticsBcoRevalidated   INTEGER
	}

adAccelerationEngineCacheRatePerL4StatisticsName OBJECT-TYPE
   SYNTAX  DisplayString
   ACCESS  read-only
   STATUS  mandatory
   DESCRIPTION
       "The L4 name."
   ::= {adAccelerationEngineCacheRatePerL4StatisticsEntry 1}

adAccelerationEngineCacheRatePerL4StatisticsObjectFromCache OBJECT-TYPE
   SYNTAX  INTEGER
   ACCESS  read-only
   STATUS  mandatory
   DESCRIPTION
       "Number of objects served from cache."
   ::= {adAccelerationEngineCacheRatePerL4StatisticsEntry 2}

adAccelerationEngineCacheRatePerL4StatisticsHits OBJECT-TYPE
   SYNTAX  INTEGER
   ACCESS  read-only
   STATUS  mandatory
   DESCRIPTION
       "Cache hits."
   ::= {adAccelerationEngineCacheRatePerL4StatisticsEntry 3}

adAccelerationEngineCacheRatePerL4StatisticsServingRate OBJECT-TYPE
   SYNTAX  INTEGER
   ACCESS  read-only
   STATUS  mandatory
   DESCRIPTION
       "Cache serving rate.request/seconds."
   ::= {adAccelerationEngineCacheRatePerL4StatisticsEntry 4}

adAccelerationEngineCacheRatePerL4StatisticsNewCacheObjects OBJECT-TYPE
   SYNTAX  INTEGER
   ACCESS  read-only
   STATUS  mandatory
   DESCRIPTION
       "Newly cached objects."
   ::= {adAccelerationEngineCacheRatePerL4StatisticsEntry 5}

adAccelerationEngineCacheRatePerL4StatisticsCachingRate OBJECT-TYPE
   SYNTAX  INTEGER
   ACCESS  read-only
   STATUS  mandatory
   DESCRIPTION
       "Object caching rate.request/seconds"
   ::= {adAccelerationEngineCacheRatePerL4StatisticsEntry 6}

adAccelerationEngineCacheRatePerL4StatisticsNewCacheBytes OBJECT-TYPE
   SYNTAX  INTEGER
   ACCESS  read-only
   STATUS  mandatory
   DESCRIPTION
       "Newly cached bytes."
   ::= {adAccelerationEngineCacheRatePerL4StatisticsEntry 7}

adAccelerationEngineCacheRatePerL4StatisticsBytesCachingRate OBJECT-TYPE
   SYNTAX  INTEGER
   ACCESS  read-only
   STATUS  mandatory
   DESCRIPTION
       "Byte caching rate.Bytes/seconds"
   ::= {adAccelerationEngineCacheRatePerL4StatisticsEntry 8}

adAccelerationEngineCacheRatePerL4StatisticsBcoProccessed OBJECT-TYPE
   SYNTAX  INTEGER
   ACCESS  read-only
   STATUS  mandatory
   DESCRIPTION
       "Number of pages processed for Dynamic caching"
   ::= {adAccelerationEngineCacheRatePerL4StatisticsEntry 9}

adAccelerationEngineCacheRatePerL4StatisticsBcoOptimized OBJECT-TYPE
   SYNTAX  INTEGER
   ACCESS  read-only
   STATUS  mandatory
   DESCRIPTION
       "Number of objects set for Dynamic caching"
   ::= {adAccelerationEngineCacheRatePerL4StatisticsEntry 10}

adAccelerationEngineCacheRatePerL4StatisticsBcoRevalidated OBJECT-TYPE
   SYNTAX  INTEGER
   ACCESS  read-only
   STATUS  mandatory
   DESCRIPTION
       "Number of objects revalidated with server"
   ::= {adAccelerationEngineCacheRatePerL4StatisticsEntry 11}

adAccelerationEngineCacheStatisticsPerL4StatisticsTable OBJECT-TYPE
   SYNTAX SEQUENCE OF AdAccelerationEngineCacheStatisticsPerL4StatisticsEntry
   ACCESS not-accessible
   STATUS mandatory
   DESCRIPTION
       "A table for showing acceleration engine Cache Statistics per L4."
   ::= {rsWSDL4Policy 41}

adAccelerationEngineCacheStatisticsPerL4StatisticsEntry OBJECT-TYPE
   SYNTAX AdAccelerationEngineCacheStatisticsPerL4StatisticsEntry
   ACCESS not-accessible
   STATUS  mandatory
   DESCRIPTION
       " The row definition for this table."
   INDEX  { adAccelerationEngineCacheStatisticsPerL4Name}
   ::= {adAccelerationEngineCacheStatisticsPerL4StatisticsTable 1}

AdAccelerationEngineCacheStatisticsPerL4StatisticsEntry  ::= SEQUENCE {
   	adAccelerationEngineCacheStatisticsPerL4Name		           DisplayString,
   	adAccelerationEngineCacheStatisticsPerL4Smaller10K             INTEGER,
   	adAccelerationEngineCacheStatisticsPerL4Smaller100K            INTEGER,
   	adAccelerationEngineCacheStatisticsPerL4Smaller1M              INTEGER,
   	adAccelerationEngineCacheStatisticsPerL4Larger1M               INTEGER
	}

adAccelerationEngineCacheStatisticsPerL4Name OBJECT-TYPE
   SYNTAX  DisplayString
   ACCESS  read-only
   STATUS  mandatory
   DESCRIPTION
       "The L4 name."
   ::= {adAccelerationEngineCacheStatisticsPerL4StatisticsEntry 1}

adAccelerationEngineCacheStatisticsPerL4Smaller10K OBJECT-TYPE
   SYNTAX  INTEGER
   ACCESS  read-only
   STATUS  mandatory
   DESCRIPTION
       "Objects average size smaller then 10 KB."
   ::= {adAccelerationEngineCacheStatisticsPerL4StatisticsEntry 2}

adAccelerationEngineCacheStatisticsPerL4Smaller100K OBJECT-TYPE
   SYNTAX  INTEGER
   ACCESS  read-only
   STATUS  mandatory
   DESCRIPTION
       "Objects average size smaller then 100 KB."
   ::= {adAccelerationEngineCacheStatisticsPerL4StatisticsEntry 3}

adAccelerationEngineCacheStatisticsPerL4Smaller1M OBJECT-TYPE
   SYNTAX  INTEGER
   ACCESS  read-only
   STATUS  mandatory
   DESCRIPTION
       "Objects average size smaller then 1 MB."
   ::= {adAccelerationEngineCacheStatisticsPerL4StatisticsEntry 4}

adAccelerationEngineCacheStatisticsPerL4Larger1M OBJECT-TYPE
   SYNTAX  INTEGER
   ACCESS  read-only
   STATUS  mandatory
   DESCRIPTION
       "Objects average size larger then 1 MB."
   ::= {adAccelerationEngineCacheStatisticsPerL4StatisticsEntry 5}

adAccelerationEngineCacheSummaryPerL4StatisticsReset OBJECT-TYPE
    SYNTAX  INTEGER {
       reset(1)
     }
    ACCESS  read-write
    STATUS  mandatory
    DESCRIPTION
      "This variable resets acceleration engine Cache statistics summary."
   ::= { rsWSDL4Policy 42  }

adAccelerationEngineCacheStatisticsContentViewFileCommand OBJECT-TYPE
    SYNTAX  DisplayString
    ACCESS  read-only
    STATUS  mandatory
    DESCRIPTION
      "Cache content view is received as a file from the acceleration engine. get command means send the file from the acceleration engine to the user."
   ::= { rsWSDL4Policy 43  }


adAccelerationEngineCacheRuleListSummaryStatisticsTable OBJECT-TYPE
   SYNTAX SEQUENCE OF AdAccelerationEngineCacheRuleListSummaryStatisticsEntry
   ACCESS not-accessible
   STATUS mandatory
   DESCRIPTION
       "A table for showing acceleration engine Cache Rule List statistics summary."
   ::= {rsWSDL4Policy 44}

adAccelerationEngineCacheRuleListSummaryEntry OBJECT-TYPE
   SYNTAX AdAccelerationEngineCacheRuleListSummaryStatisticsEntry
   ACCESS not-accessible
   STATUS  mandatory
   DESCRIPTION
       " The row definition for this table."
   INDEX  { adAccelerationEngineCacheRuleListSummaryStatisticsListName}
   ::= {adAccelerationEngineCacheRuleListSummaryStatisticsTable 1}

AdAccelerationEngineCacheRuleListSummaryStatisticsEntry  ::= SEQUENCE {
   	adAccelerationEngineCacheRuleListSummaryStatisticsListName	     DisplayString,
   	adAccelerationEngineCacheRuleListSummaryStatisticsCachedObjects  INTEGER,
   	adAccelerationEngineCacheRuleListSummaryStatisticsCachedBytes    INTEGER
	}

adAccelerationEngineCacheRuleListSummaryStatisticsListName OBJECT-TYPE
   SYNTAX  DisplayString
   ACCESS  read-only
   STATUS  mandatory
   DESCRIPTION
       "The list name."
   ::= {adAccelerationEngineCacheRuleListSummaryEntry 1}

adAccelerationEngineCacheRuleListSummaryStatisticsCachedObjects OBJECT-TYPE
   SYNTAX  INTEGER
   ACCESS  read-only
   STATUS  mandatory
   DESCRIPTION
       "Number of Cached objects."
   ::= {adAccelerationEngineCacheRuleListSummaryEntry 2}

adAccelerationEngineCacheRuleListSummaryStatisticsCachedBytes OBJECT-TYPE
   SYNTAX  INTEGER
   ACCESS  read-only
   STATUS  mandatory
   DESCRIPTION
       "Cached Bytes."
   ::= {adAccelerationEngineCacheRuleListSummaryEntry 3}

adAccelerationEngineCacheRuleListPerRuleStatisticsTable OBJECT-TYPE
   SYNTAX SEQUENCE OF AdAccelerationEngineCacheRuleListPerRuleStatisticsEntry
   ACCESS not-accessible
   STATUS mandatory
   DESCRIPTION
       "A table for showing acceleration engine Cache Rule List Per Rule statistics."
   ::= {rsWSDL4Policy 45}

adAccelerationEngineCacheRuleListPerRuleStatisticsEntry OBJECT-TYPE
   SYNTAX AdAccelerationEngineCacheRuleListPerRuleStatisticsEntry
   ACCESS not-accessible
   STATUS  mandatory
   DESCRIPTION
       " The row definition for this table."
   INDEX  { adAccelerationEngineCacheRuleListPerRuleStatisticsListName,
            adAccelerationEngineCacheRuleListPerRuleStatisticsRuleName
   }
   ::= {adAccelerationEngineCacheRuleListPerRuleStatisticsTable 1}

AdAccelerationEngineCacheRuleListPerRuleStatisticsEntry  ::= SEQUENCE {
   	adAccelerationEngineCacheRuleListPerRuleStatisticsListName	    DisplayString,
   	adAccelerationEngineCacheRuleListPerRuleStatisticsRuleName	    DisplayString,
   	adAccelerationEngineCacheRuleListPerRuleStatisticsRulePriority  INTEGER,
   	adAccelerationEngineCacheRuleListPerRuleStatisticsCachedObjects INTEGER,
   	adAccelerationEngineCacheRuleListPerRuleStatisticsCachedBytes   INTEGER
	}

adAccelerationEngineCacheRuleListPerRuleStatisticsListName OBJECT-TYPE
   SYNTAX  DisplayString
   ACCESS  read-only
   STATUS  mandatory
   DESCRIPTION
       "The List name."
   ::= {adAccelerationEngineCacheRuleListPerRuleStatisticsEntry 1}

adAccelerationEngineCacheRuleListPerRuleStatisticsRuleName OBJECT-TYPE
   SYNTAX  DisplayString
   ACCESS  read-only
   STATUS  mandatory
   DESCRIPTION
       "The rule name."
   ::= {adAccelerationEngineCacheRuleListPerRuleStatisticsEntry 2}

adAccelerationEngineCacheRuleListPerRuleStatisticsRulePriority OBJECT-TYPE
   SYNTAX  INTEGER (1..2147483647)
   ACCESS  read-only
   STATUS  mandatory
   DESCRIPTION
       "The rule priority."
   DEFVAL { 1 }
   ::= {adAccelerationEngineCacheRuleListPerRuleStatisticsEntry 3}

adAccelerationEngineCacheRuleListPerRuleStatisticsCachedObjects OBJECT-TYPE
   SYNTAX  INTEGER
   ACCESS  read-only
   STATUS  mandatory
   DESCRIPTION
       "The rule cached objects."
   ::= {adAccelerationEngineCacheRuleListPerRuleStatisticsEntry 4}

adAccelerationEngineCacheRuleListPerRuleStatisticsCachedBytes OBJECT-TYPE
   SYNTAX  INTEGER
   ACCESS  read-only
   STATUS  mandatory
   DESCRIPTION
       "Number of cached objects by this rule."
   ::= {adAccelerationEngineCacheRuleListPerRuleStatisticsEntry 5}

adAccelerationEngineCacheRuleListPerRuleStatisticsReset OBJECT-TYPE
    SYNTAX  INTEGER {
       reset(1)
     }
    ACCESS  read-write
    STATUS  mandatory
    DESCRIPTION
      "This variable resets acceleration engine Cache rule list statistics summary."
   ::= { rsWSDL4Policy 46  }


adAccelerationEngineCompressionSummaryStatisticsTable OBJECT-TYPE
   SYNTAX SEQUENCE OF AdAccelerationEngineCompressionSummaryStatisticsEntry
   ACCESS not-accessible
   STATUS mandatory
   DESCRIPTION
       "A table for showing acceleration engine Compression statistics summary."
   ::= {rsWSDL4Policy 47}

adAccelerationEngineCompressionSummaryEntry OBJECT-TYPE
   SYNTAX AdAccelerationEngineCompressionSummaryStatisticsEntry
   ACCESS not-accessible
   STATUS  mandatory
   DESCRIPTION
       " The row definition for this table."
   INDEX  { adAccelerationEngineCompressionSummaryStatisticsParameter}
   ::= {adAccelerationEngineCompressionSummaryStatisticsTable 1}

AdAccelerationEngineCompressionSummaryStatisticsEntry  ::= SEQUENCE {
   	adAccelerationEngineCompressionSummaryStatisticsParameter	DisplayString,
   	adAccelerationEngineCompressionSummaryStatisticsValue       INTEGER
	}

adAccelerationEngineCompressionSummaryStatisticsParameter OBJECT-TYPE
   SYNTAX  DisplayString
   ACCESS  read-only
   STATUS  mandatory
   DESCRIPTION
       "The parameter."
   ::= {adAccelerationEngineCompressionSummaryEntry 1}

adAccelerationEngineCompressionSummaryStatisticsValue OBJECT-TYPE
   SYNTAX  INTEGER
   ACCESS  read-only
   STATUS  mandatory
   DESCRIPTION
       "The value."
   ::= {adAccelerationEngineCompressionSummaryEntry 2}

adAccelerationEngineCompressionPerL4StatisticsTable OBJECT-TYPE
   SYNTAX SEQUENCE OF AdAccelerationEngineCompressionPerL4StatisticsEntry
   ACCESS not-accessible
   STATUS mandatory
   DESCRIPTION
       "A table for showing acceleration engine Compression Per L4 statistics."
   ::= {rsWSDL4Policy 48}

adAccelerationEngineCompressionPerL4StatisticsEntry OBJECT-TYPE
   SYNTAX AdAccelerationEngineCompressionPerL4StatisticsEntry
   ACCESS not-accessible
   STATUS  mandatory
   DESCRIPTION
       " The row definition for this table."
   INDEX  { adAccelerationEngineCompressionPerL4StatisticsName }
   ::= {adAccelerationEngineCompressionPerL4StatisticsTable 1}

AdAccelerationEngineCompressionPerL4StatisticsEntry  ::= SEQUENCE {
   	adAccelerationEngineCompressionPerL4StatisticsName	              DisplayString,
   	adAccelerationEngineCompressionPerL4StatisticsSizeUncompressed    INTEGER,
   	adAccelerationEngineCompressionPerL4StatisticsAvgSizeUnconpressed INTEGER,
   	adAccelerationEngineCompressionPerL4StatisticsSizeCompressed      INTEGER,
   	adAccelerationEngineCompressionPerL4StatisticsAvgSizeCompressed   INTEGER,
   	adAccelerationEngineCompressionPerL4StatisticsCompressionRatio    INTEGER
	}

adAccelerationEngineCompressionPerL4StatisticsName OBJECT-TYPE
   SYNTAX  DisplayString
   ACCESS  read-only
   STATUS  mandatory
   DESCRIPTION
       "The List name."
   ::= {adAccelerationEngineCompressionPerL4StatisticsEntry 1}

adAccelerationEngineCompressionPerL4StatisticsSizeUncompressed OBJECT-TYPE
   SYNTAX  INTEGER
   ACCESS  read-only
   STATUS  mandatory
   DESCRIPTION
       "Size uncompressed."
   ::= {adAccelerationEngineCompressionPerL4StatisticsEntry 2}

   adAccelerationEngineCompressionPerL4StatisticsAvgSizeUnconpressed OBJECT-TYPE
   SYNTAX  INTEGER
   ACCESS  read-only
   STATUS  mandatory
   DESCRIPTION
       "Average Size uncompressed."
   ::= {adAccelerationEngineCompressionPerL4StatisticsEntry 3}

adAccelerationEngineCompressionPerL4StatisticsSizeCompressed OBJECT-TYPE
   SYNTAX  INTEGER
   ACCESS  read-only
   STATUS  mandatory
   DESCRIPTION
       "Size compressed."
   ::= {adAccelerationEngineCompressionPerL4StatisticsEntry 4}

adAccelerationEngineCompressionPerL4StatisticsAvgSizeCompressed OBJECT-TYPE
   SYNTAX  INTEGER
   ACCESS  read-only
   STATUS  mandatory
   DESCRIPTION
       "Average Size compressed."
   ::= {adAccelerationEngineCompressionPerL4StatisticsEntry 5}

adAccelerationEngineCompressionPerL4StatisticsCompressionRatio OBJECT-TYPE
   SYNTAX  INTEGER
   ACCESS  read-only
   STATUS  mandatory
   DESCRIPTION
       "Compression Ratio."
   ::= {adAccelerationEngineCompressionPerL4StatisticsEntry 6}

adAccelerationEngineCompressionPerL4StatisticsReset OBJECT-TYPE
    SYNTAX  INTEGER {
       reset(1)
     }
    ACCESS  read-write
    STATUS  mandatory
    DESCRIPTION
      "This variable resets acceleration compression statistics summary."
   ::= { rsWSDL4Policy 49  }

adCompressionBrowserExceptionPolicyStatisticsSummaryTable OBJECT-TYPE
   SYNTAX SEQUENCE OF AdCompressionBrowserExceptionPolicyStatisticsSummaryEntry
   ACCESS not-accessible
   STATUS mandatory
   DESCRIPTION
       "A table for showing compression browser exception Statistics."
   ::= {rsWSDL4Policy 50}

adCompressionBrowserExceptionPolicyStatisticsSummaryEntry OBJECT-TYPE
   SYNTAX AdCompressionBrowserExceptionPolicyStatisticsSummaryEntry
   ACCESS not-accessible
   STATUS  mandatory
   DESCRIPTION
       " The row definition for this table."
   INDEX  { adCompressionBrowserExceptionPolicyStatisticsSummaryRuleListName}
   ::= {adCompressionBrowserExceptionPolicyStatisticsSummaryTable 1}

AdCompressionBrowserExceptionPolicyStatisticsSummaryEntry  ::= SEQUENCE {
   	adCompressionBrowserExceptionPolicyStatisticsSummaryRuleListName		DisplayString,
   	adCompressionBrowserExceptionPolicyStatisticsSummaryMatchedObjects      INTEGER,
   	adCompressionBrowserExceptionPolicyStatisticsSummarySizeBeforeComp      INTEGER,
   	adCompressionBrowserExceptionPolicyStatisticsSummarySizeAfterComp       INTEGER
	}

adCompressionBrowserExceptionPolicyStatisticsSummaryRuleListName OBJECT-TYPE
   SYNTAX  DisplayString
   ACCESS  read-only
   STATUS  mandatory
   DESCRIPTION
       "The rule list name."
   ::= {adCompressionBrowserExceptionPolicyStatisticsSummaryEntry 1}

adCompressionBrowserExceptionPolicyStatisticsSummaryMatchedObjects OBJECT-TYPE
   SYNTAX  INTEGER
   ACCESS  read-only
   STATUS  mandatory
   DESCRIPTION
       "Number Of Matched objects."
   ::= {adCompressionBrowserExceptionPolicyStatisticsSummaryEntry 2}

adCompressionBrowserExceptionPolicyStatisticsSummarySizeBeforeComp OBJECT-TYPE
   SYNTAX  INTEGER
   ACCESS  read-only
   STATUS  mandatory
   DESCRIPTION
       "Size Before Compression."
   ::= {adCompressionBrowserExceptionPolicyStatisticsSummaryEntry 3}

adCompressionBrowserExceptionPolicyStatisticsSummarySizeAfterComp OBJECT-TYPE
   SYNTAX  INTEGER
   ACCESS  read-only
   STATUS  mandatory
   DESCRIPTION
       "Size After Compression."
   ::= {adCompressionBrowserExceptionPolicyStatisticsSummaryEntry 4}

adCompressionBrowserExceptionPolicyStatisticsTable OBJECT-TYPE
   SYNTAX SEQUENCE OF AdCompressionBrowserExceptionPolicyStatisticsEntry
   ACCESS not-accessible
   STATUS mandatory
   DESCRIPTION
       "A table for showing compression browser exception Statistics."
   ::= {rsWSDL4Policy 51}

adCompressionBrowserExceptionPolicyStatisticsEntry OBJECT-TYPE
   SYNTAX AdCompressionBrowserExceptionPolicyStatisticsEntry
   ACCESS not-accessible
   STATUS  mandatory
   DESCRIPTION
       " The row definition for this table."
   INDEX  { adCompressionBrowserExceptionPolicyStatisticsRuleListName,
	   	    adCompressionBrowserExceptionPolicyStatisticsRuleName}
   ::= {adCompressionBrowserExceptionPolicyStatisticsTable 1}

AdCompressionBrowserExceptionPolicyStatisticsEntry  ::= SEQUENCE {
   	adCompressionBrowserExceptionPolicyStatisticsRuleListName		DisplayString,
   	adCompressionBrowserExceptionPolicyStatisticsRuleName			DisplayString,
   	adCompressionBrowserExceptionPolicyStatisticsRulePriority	    INTEGER,
   	adCompressionBrowserExceptionPolicyStatisticsNumOfMatched	    INTEGER,
   	adCompressionBrowserExceptionPolicyStatisticsSizeBeforeComp	    INTEGER,
   	adCompressionBrowserExceptionPolicyStatisticsSizeAfterComp 	    INTEGER,
   	adCompressionBrowserExceptionPolicyStatisticsCompRatio  	    INTEGER
	}

adCompressionBrowserExceptionPolicyStatisticsRuleListName OBJECT-TYPE
   SYNTAX  DisplayString
   ACCESS  read-only
   STATUS  mandatory
   DESCRIPTION
       "The rule list name."
   ::= {adCompressionBrowserExceptionPolicyStatisticsEntry 1}

adCompressionBrowserExceptionPolicyStatisticsRuleName OBJECT-TYPE
   SYNTAX  DisplayString
   ACCESS  read-only
   STATUS  mandatory
   DESCRIPTION
       "The rule name."
   ::= {adCompressionBrowserExceptionPolicyStatisticsEntry 2}

adCompressionBrowserExceptionPolicyStatisticsRulePriority OBJECT-TYPE
   SYNTAX  INTEGER (1..2147483647)
   ACCESS  read-only
   STATUS  mandatory
   DESCRIPTION
       "The rule priority."
   DEFVAL { 1 }
   ::= {adCompressionBrowserExceptionPolicyStatisticsEntry 3}

adCompressionBrowserExceptionPolicyStatisticsNumOfMatched OBJECT-TYPE
   SYNTAX  INTEGER
   ACCESS  read-only
   STATUS  mandatory
   DESCRIPTION
       "Number Of Matched."
   ::= {adCompressionBrowserExceptionPolicyStatisticsEntry 4}

adCompressionBrowserExceptionPolicyStatisticsSizeBeforeComp OBJECT-TYPE
   SYNTAX  INTEGER
   ACCESS  read-only
   STATUS  mandatory
   DESCRIPTION
       "Size before compression."
   ::= {adCompressionBrowserExceptionPolicyStatisticsEntry 5}

adCompressionBrowserExceptionPolicyStatisticsSizeAfterComp OBJECT-TYPE
   SYNTAX  INTEGER
   ACCESS  read-only
   STATUS  mandatory
   DESCRIPTION
       "Size after compression."
   ::= {adCompressionBrowserExceptionPolicyStatisticsEntry 6}

adCompressionBrowserExceptionPolicyStatisticsCompRatio OBJECT-TYPE
   SYNTAX  INTEGER
   ACCESS  read-only
   STATUS  mandatory
   DESCRIPTION
       "Compression ratio."
   ::= {adCompressionBrowserExceptionPolicyStatisticsEntry 7}

  adCompressionBrowserExceptionPolicyStatisticsReset OBJECT-TYPE
    SYNTAX  INTEGER {
       reset(1)
     }
    ACCESS  read-write
    STATUS  mandatory
    DESCRIPTION
      "This variable resets the l4 compression browser rule lists statistics."
   ::= { rsWSDL4Policy 52  }

adCompressionUrlExceptionPolicyStatisticsSummaryTable OBJECT-TYPE
   SYNTAX SEQUENCE OF AdCompressionUrlExceptionPolicyStatisticsSummaryEntry
   ACCESS not-accessible
   STATUS mandatory
   DESCRIPTION
       "A table for showing compression Url exception Statistics."
   ::= {rsWSDL4Policy 53}

adCompressionUrlExceptionPolicyStatisticsSummaryEntry OBJECT-TYPE
   SYNTAX AdCompressionUrlExceptionPolicyStatisticsSummaryEntry
   ACCESS not-accessible
   STATUS  mandatory
   DESCRIPTION
       " The row definition for this table."
   INDEX  { adCompressionUrlExceptionPolicyStatisticsSummaryRuleListName}
   ::= {adCompressionUrlExceptionPolicyStatisticsSummaryTable 1}

AdCompressionUrlExceptionPolicyStatisticsSummaryEntry  ::= SEQUENCE {
   	adCompressionUrlExceptionPolicyStatisticsSummaryRuleListName		DisplayString,
   	adCompressionUrlExceptionPolicyStatisticsSummaryMatchedObjects      INTEGER,
   	adCompressionUrlExceptionPolicyStatisticsSummarySizeBeforeComp      INTEGER,
   	adCompressionUrlExceptionPolicyStatisticsSummarySizeAfterComp       INTEGER
	}

adCompressionUrlExceptionPolicyStatisticsSummaryRuleListName OBJECT-TYPE
   SYNTAX  DisplayString
   ACCESS  read-only
   STATUS  mandatory
   DESCRIPTION
       "The rule list name."
   ::= {adCompressionUrlExceptionPolicyStatisticsSummaryEntry 1}

adCompressionUrlExceptionPolicyStatisticsSummaryMatchedObjects OBJECT-TYPE
   SYNTAX  INTEGER
   ACCESS  read-only
   STATUS  mandatory
   DESCRIPTION
       "Matched Objects."
   ::= {adCompressionUrlExceptionPolicyStatisticsSummaryEntry 2}

adCompressionUrlExceptionPolicyStatisticsSummarySizeBeforeComp OBJECT-TYPE
   SYNTAX  INTEGER
   ACCESS  read-only
   STATUS  mandatory
   DESCRIPTION
       "Size Before Compression."
   ::= {adCompressionUrlExceptionPolicyStatisticsSummaryEntry 3}

adCompressionUrlExceptionPolicyStatisticsSummarySizeAfterComp OBJECT-TYPE
   SYNTAX  INTEGER
   ACCESS  read-only
   STATUS  mandatory
   DESCRIPTION
       "Size After Compression."
   ::= {adCompressionUrlExceptionPolicyStatisticsSummaryEntry 4}

adCompressionUrlExceptionPolicyStatisticsTable OBJECT-TYPE
   SYNTAX SEQUENCE OF AdCompressionUrlExceptionPolicyStatisticsEntry
   ACCESS not-accessible
   STATUS mandatory
   DESCRIPTION
       "A table for showing compression Url exception Statistics."
   ::= {rsWSDL4Policy 54}

adCompressionUrlExceptionPolicyStatisticsEntry OBJECT-TYPE
   SYNTAX AdCompressionUrlExceptionPolicyStatisticsEntry
   ACCESS not-accessible
   STATUS  mandatory
   DESCRIPTION
       " The row definition for this table."
   INDEX  { adCompressionUrlExceptionPolicyStatisticsRuleListName,
	   	    adCompressionUrlExceptionPolicyStatisticsRuleName}
   ::= {adCompressionUrlExceptionPolicyStatisticsTable 1}

AdCompressionUrlExceptionPolicyStatisticsEntry  ::= SEQUENCE {
   	adCompressionUrlExceptionPolicyStatisticsRuleListName		DisplayString,
   	adCompressionUrlExceptionPolicyStatisticsRuleName			DisplayString,
   	adCompressionUrlExceptionPolicyStatisticsRulePriority	    INTEGER,
   	adCompressionUrlExceptionPolicyStatisticsNumOfMatched	    INTEGER,
   	adCompressionUrlExceptionPolicyStatisticsSizeBeforeComp	    INTEGER,
   	adCompressionUrlExceptionPolicyStatisticsSizeAfterComp 	    INTEGER,
   	adCompressionUrlExceptionPolicyStatisticsCompRatio  	    INTEGER
	}

adCompressionUrlExceptionPolicyStatisticsRuleListName OBJECT-TYPE
   SYNTAX  DisplayString
   ACCESS  read-only
   STATUS  mandatory
   DESCRIPTION
       "The rule list name."
   ::= {adCompressionUrlExceptionPolicyStatisticsEntry 1}

adCompressionUrlExceptionPolicyStatisticsRuleName OBJECT-TYPE
   SYNTAX  DisplayString
   ACCESS  read-only
   STATUS  mandatory
   DESCRIPTION
       "The rule name."
   ::= {adCompressionUrlExceptionPolicyStatisticsEntry 2}

adCompressionUrlExceptionPolicyStatisticsRulePriority OBJECT-TYPE
   SYNTAX  INTEGER (1..2147483647)
   ACCESS  read-only
   STATUS  mandatory
   DESCRIPTION
       "The rule priority."
   DEFVAL { 1 }
   ::= {adCompressionUrlExceptionPolicyStatisticsEntry 3}

adCompressionUrlExceptionPolicyStatisticsNumOfMatched OBJECT-TYPE
   SYNTAX  INTEGER
   ACCESS  read-only
   STATUS  mandatory
   DESCRIPTION
       "Number of matched."
   ::= {adCompressionUrlExceptionPolicyStatisticsEntry 4}

adCompressionUrlExceptionPolicyStatisticsSizeBeforeComp OBJECT-TYPE
   SYNTAX  INTEGER
   ACCESS  read-only
   STATUS  mandatory
   DESCRIPTION
       "Size before compression."
   ::= {adCompressionUrlExceptionPolicyStatisticsEntry 5}

adCompressionUrlExceptionPolicyStatisticsSizeAfterComp OBJECT-TYPE
   SYNTAX  INTEGER
   ACCESS  read-only
   STATUS  mandatory
   DESCRIPTION
       "Size After compression."
   ::= {adCompressionUrlExceptionPolicyStatisticsEntry 6}

adCompressionUrlExceptionPolicyStatisticsCompRatio OBJECT-TYPE
   SYNTAX  INTEGER
   ACCESS  read-only
   STATUS  mandatory
   DESCRIPTION
       "Compression ratio."
   ::= {adCompressionUrlExceptionPolicyStatisticsEntry 7}

  adCompressionUrlExceptionPolicyStatisticsReset OBJECT-TYPE
    SYNTAX  INTEGER {
       reset(1)
     }
    ACCESS  read-write
    STATUS  mandatory
    DESCRIPTION
      "This variable resets the l4 compression Url rule lists statistics."
   ::= { rsWSDL4Policy 55  }

   adAcclEngineStatisticsDataInterval OBJECT-TYPE
    SYNTAX  INTEGER (5..3600)
    ACCESS  read-write
    STATUS  mandatory
    DESCRIPTION
      "This variable changes the AE statistics interval measured in seconds."
   ::= { rsWSDL4Policy 56 }

   adAcclEngineStatisticsWebRefreshInterval OBJECT-TYPE
    SYNTAX  INTEGER (5..3600)
    ACCESS  read-write
    STATUS  mandatory
    DESCRIPTION
      "This variable changes the AE statistics web refresh interval measured in seconds."
   ::= { rsWSDL4Policy 57 }

   adOcspCachePurge OBJECT-TYPE
    SYNTAX DisplayString (SIZE (1..50))
    ACCESS read-write
   	STATUS mandatory
   	DESCRIPTION
     	 "Purge the cache information for an Authentication Policy"
	::=  {rsWSDL4Policy 61}

  adCDPCachePurge OBJECT-TYPE
    SYNTAX DisplayString (SIZE (1..50))
    ACCESS read-write
    STATUS mandatory
    DESCRIPTION
    "Purge CDP cache information for an Authentication Policy"
	::=  {rsWSDL4Policy 66}


adL4PolicyCachePurgeTable OBJECT-TYPE
   SYNTAX SEQUENCE OF AdL4PolicyCachePurgeEntry
   ACCESS not-accessible
   STATUS mandatory
   DESCRIPTION
       "A table for purging the cache information attached to a L4 Policy. Takes the name of the L4 policy that is bound to a cache policy
          or all for purge of the entire cache. URL is an optional parameter, invalidates a specific object."
   ::= {rsWSDL4Policy 67}

adL4PolicyCachePurgeEntry OBJECT-TYPE
   SYNTAX AdL4PolicyCachePurgeEntry
   ACCESS not-accessible
   STATUS  mandatory
   DESCRIPTION
       " The row definition for this table."
   INDEX  { adL4PolicyCachePurgeL4PolicyName }
   ::= {adL4PolicyCachePurgeTable 1}

AdL4PolicyCachePurgeEntry  ::= SEQUENCE {
   	adL4PolicyCachePurgeL4PolicyName		DisplayString,
   	adL4PolicyCachePurgeURL                 DisplayString,
	adL4PolicyCachePurgeStatus              RowStatus
	}

adL4PolicyCachePurgeL4PolicyName OBJECT-TYPE
   SYNTAX  DisplayString (SIZE (1..50))
   ACCESS  read-write
   STATUS  mandatory
   DESCRIPTION
       "The L4 name to purge the cache for it."
   ::= {adL4PolicyCachePurgeEntry 1}

adL4PolicyCachePurgeURL OBJECT-TYPE
   SYNTAX  DisplayString (SIZE (0..255))
   ACCESS  read-write
   STATUS  optional
   DESCRIPTION
       "The URL to invalidate specific object."
   ::= {adL4PolicyCachePurgeEntry 2}

adL4PolicyCachePurgeStatus OBJECT-TYPE
    SYNTAX    RowStatus
    ACCESS    read-write
    STATUS    mandatory
    DESCRIPTION
      "Row status for this entry."
    ::= { adL4PolicyCachePurgeEntry 3 }

adL4PolicyCachePurgeWebURL  OBJECT-TYPE
    SYNTAX DisplayString (SIZE (0..255))
    ACCESS read-write
   	STATUS optional
   	DESCRIPTION
     	 "The URL to invalidate specific cache object."
	::=  {rsWSDL4Policy 68}

adCRLFileListTable OBJECT-TYPE
   SYNTAX SEQUENCE OF AdCRLFileListEntry
   ACCESS not-accessible
   STATUS mandatory
   DESCRIPTION
       "."
   ::= {rsWSDL4Policy 69}

adCRLFileListEntry OBJECT-TYPE
   SYNTAX AdCRLFileListEntry
   ACCESS not-accessible
   STATUS  mandatory
   DESCRIPTION
       " The row definition for this table."
   INDEX  { adCRLFileListFileName, adCRLFileListAuthenticationPolicyName}
   ::= {adCRLFileListTable 1}

AdCRLFileListEntry  ::= SEQUENCE {
   	adCRLFileListFileName		           DisplayString,
   	adCRLFileListAuthenticationPolicyName  DisplayString,
	adCRLFileListStatus                    RowStatus
	}

adCRLFileListFileName OBJECT-TYPE
   SYNTAX  DisplayString (SIZE (1..50))
   ACCESS  read-only
   STATUS  mandatory
   DESCRIPTION
       "The CRL File Name."
   ::= {adCRLFileListEntry 1}

 adCRLFileListAuthenticationPolicyName OBJECT-TYPE
   SYNTAX  DisplayString (SIZE (1..50))
   ACCESS  read-only
   STATUS  mandatory
   DESCRIPTION
       "The Authentication Policy Name."
   ::= {adCRLFileListEntry 2}

 adCRLFileListStatus OBJECT-TYPE
   SYNTAX  RowStatus
   ACCESS read-only
   STATUS mandatory
   DESCRIPTION
      ""
   ::=  {adCRLFileListEntry 3}

 adAccelerationEngineThroughputPerL4StatisticsPartTable OBJECT-TYPE
   SYNTAX SEQUENCE OF AdAccelerationEngineThroughputPerL4StatisticsPartEntry
   ACCESS not-accessible
   STATUS mandatory
   DESCRIPTION
       "A table for showing acceleration engine partial throughput per L4 statistics."
   ::= {rsWSDL4Policy 62}

adAccelerationEngineThroughputPerL4StatisticsPartEntry OBJECT-TYPE
   SYNTAX AdAccelerationEngineThroughputPerL4StatisticsPartEntry
   ACCESS not-accessible
   STATUS  mandatory
   DESCRIPTION
       " The row definition for this table."
   INDEX  { adAccelerationEngineThroughputPerL4StatisticsPartName}
   ::= {adAccelerationEngineThroughputPerL4StatisticsPartTable 1}

AdAccelerationEngineThroughputPerL4StatisticsPartEntry  ::= SEQUENCE {
   	adAccelerationEngineThroughputPerL4StatisticsPartName		DisplayString,
   	adAccelerationEngineThroughputPerL4StatisticsClientPartMbitsIn   INTEGER,
   	adAccelerationEngineThroughputPerL4StatisticsClientPartMbitsOut  INTEGER,
   	adAccelerationEngineThroughputPerL4StatisticsClientPartTwoWay    INTEGER,
   	adAccelerationEngineThroughputPerL4StatisticsServerPartMbitsIn    INTEGER,
   	adAccelerationEngineThroughputPerL4StatisticsServerPartMbitsOut   INTEGER,
   	adAccelerationEngineThroughputPerL4StatisticsServerPartTwoWay     INTEGER
	}

adAccelerationEngineThroughputPerL4StatisticsPartName OBJECT-TYPE
   SYNTAX  DisplayString
   ACCESS  read-only
   STATUS  mandatory
   DESCRIPTION
       "The L4 name."
   ::= {adAccelerationEngineThroughputPerL4StatisticsPartEntry 1}

adAccelerationEngineThroughputPerL4StatisticsClientPartMbitsIn OBJECT-TYPE
   SYNTAX  INTEGER
   ACCESS  read-only
   STATUS  mandatory
   DESCRIPTION
       "The Client throughtput in."
   ::= {adAccelerationEngineThroughputPerL4StatisticsPartEntry 2}

adAccelerationEngineThroughputPerL4StatisticsClientPartMbitsOut OBJECT-TYPE
   SYNTAX  INTEGER
   ACCESS  read-only
   STATUS  mandatory
   DESCRIPTION
       "The Client throughtput out."
   ::= {adAccelerationEngineThroughputPerL4StatisticsPartEntry 3}

adAccelerationEngineThroughputPerL4StatisticsClientPartTwoWay OBJECT-TYPE
   SYNTAX  INTEGER
   ACCESS  read-only
   STATUS  mandatory
   DESCRIPTION
       "The Client throughtput both ways."
   ::= {adAccelerationEngineThroughputPerL4StatisticsPartEntry 4}

adAccelerationEngineThroughputPerL4StatisticsServerPartMbitsIn OBJECT-TYPE
   SYNTAX  INTEGER
   ACCESS  read-only
   STATUS  mandatory
   DESCRIPTION
       "The Server throughtput in."
   ::= {adAccelerationEngineThroughputPerL4StatisticsPartEntry 5}

adAccelerationEngineThroughputPerL4StatisticsServerPartMbitsOut OBJECT-TYPE
   SYNTAX  INTEGER
   ACCESS  read-only
   STATUS  mandatory
   DESCRIPTION
       "The Server throughtput out."
   ::= {adAccelerationEngineThroughputPerL4StatisticsPartEntry 6}

adAccelerationEngineThroughputPerL4StatisticsServerPartTwoWay OBJECT-TYPE
   SYNTAX  INTEGER
   ACCESS  read-only
   STATUS  mandatory
   DESCRIPTION
       "The Server throughtput both ways."
   ::= {adAccelerationEngineThroughputPerL4StatisticsPartEntry 7}

--	rsWSDLRPTable
rsWSDLRPTable OBJECT-TYPE
   SYNTAX SEQUENCE OF RsWSDLRPEntry
   ACCESS not-accessible
   STATUS mandatory
   DESCRIPTION
      ""
   ::= {rsNWSD 50}

rsWSDLRPEntry  OBJECT-TYPE
   SYNTAX RsWSDLRPEntry
   ACCESS not-accessible
   STATUS mandatory
   DESCRIPTION
      "New Report Table (WSD version 10 and up)."
   INDEX { rsWSDLRPDistributedFarmName,
           rsWSDLRPDistributedServer
	   }
   ::= {rsWSDLRPTable  1 }

RsWSDLRPEntry ::= SEQUENCE {
        rsWSDLRPDistributedFarmName       DisplayString,
        rsWSDLRPDistributedServer         IpAddress,
        rsWSDLRPFarmName                  DisplayString,
        rsWSDLRPL4PolicyName              DisplayString,
        rsWSDLRPTriangulationVip          IpAddress,
        rsWSDLRPTriangulationNatAddress   IpAddress,
        rsWSDLRPDestinationIP             IpAddress,
        rsWSDLRPRedundantDestinationIP    IpAddress,
        rsWSDLRPHMID                      DisplayString,
        rsWSDLRPCckID                     INTEGER,
        rsWSDLRPOperationStatus           INTEGER,
        rsWSDLRPStatus                    RowStatus,
        rsWSDLRPOriginVip                 IpAddress
  }

rsWSDLRPDistributedFarmName OBJECT-TYPE
   SYNTAX DisplayString
   ACCESS read-only
   STATUS mandatory
   DESCRIPTION
      " The name of the farm on the WSD DS that contains the Distributed WSD server we report on."
   ::=  {rsWSDLRPEntry 1}

rsWSDLRPDistributedServer OBJECT-TYPE
   SYNTAX IpAddress
   ACCESS read-only
   STATUS mandatory
   DESCRIPTION
      "The address of the Distributed Server configured in the WSD DS."
   ::=  {rsWSDLRPEntry 2}

rsWSDLRPFarmName OBJECT-TYPE
   SYNTAX DisplayString
   ACCESS read-write
   STATUS mandatory
   DESCRIPTION
      "The name of the local farm that its load is reported."
   ::=  {rsWSDLRPEntry 3}

rsWSDLRPL4PolicyName OBJECT-TYPE
   SYNTAX DisplayString
   ACCESS read-write
   STATUS mandatory
   DESCRIPTION
      "The name of the relevant L4 Policy."
   ::=  {rsWSDLRPEntry 4}

rsWSDLRPTriangulationVip OBJECT-TYPE
   SYNTAX IpAddress
   ACCESS read-write
   STATUS mandatory
   DESCRIPTION
      "The Virtual IP on which WSD intercepts traffic from a distributed using
       the triangulation method."
   ::=  {rsWSDLRPEntry 5}

rsWSDLRPTriangulationNatAddress OBJECT-TYPE
   SYNTAX IpAddress
   ACCESS read-write
   STATUS mandatory
   DESCRIPTION
      "The NAT address that is associated with the Triangulation Vip.
       This is the IP address on which the WSD DS send triangled requests to."
   ::=  {rsWSDLRPEntry 6}

rsWSDLRPDestinationIP OBJECT-TYPE
   SYNTAX IpAddress
   ACCESS read-write
   STATUS mandatory
   DESCRIPTION
      "The IP address of the remote system which should receive the load
       report."
   ::=  {rsWSDLRPEntry 7}

rsWSDLRPRedundantDestinationIP OBJECT-TYPE
   SYNTAX IpAddress
   ACCESS read-write
   STATUS mandatory
   DESCRIPTION
      "The IP address of the redundant remote system which should receive the
       load report."
   ::=  {rsWSDLRPEntry 8}

rsWSDLRPHMID OBJECT-TYPE
   SYNTAX DisplayString (SIZE (0..80))
   ACCESS read-write
   STATUS mandatory
   DESCRIPTION
      "Key id to associate with Health checks of the Health Monitoring module"
   ::=  {rsWSDLRPEntry 9}

rsWSDLRPCckID OBJECT-TYPE
    SYNTAX  INTEGER
    ACCESS  read-only
    STATUS  mandatory
    DESCRIPTION
      "Connectivity check module identifier."
    ::=  {rsWSDLRPEntry 10}

rsWSDLRPOperationStatus OBJECT-TYPE
SYNTAX INTEGER {
	active(1),
	notInService(2) }
   ACCESS  read-only
   STATUS  mandatory
   DESCRIPTION
     "Indicate if the entry is available"
   ::=  {rsWSDLRPEntry 11}


rsWSDLRPStatus OBJECT-TYPE
   SYNTAX  RowStatus
   ACCESS read-write
   STATUS mandatory
   DESCRIPTION
      ""
   ::=  {rsWSDLRPEntry 12}

rsWSDLRPOriginVip OBJECT-TYPE
    SYNTAX  IpAddress
    ACCESS  read-write
    STATUS  mandatory
    DESCRIPTION
      "The original IP which the client issued its request to.
	   This is the VIP of the L4 Policy in the WSD-DS.
	   The field  is relevant only when using Global Triangulation"
    ::=  {rsWSDLRPEntry 13}


rsNADLRPTable OBJECT-TYPE
   SYNTAX SEQUENCE OF RsNADLRPEntry
   ACCESS not-accessible
   STATUS mandatory
   DESCRIPTION
      ""
   ::= {rsNWSD 88}

rsNADLRPEntry  OBJECT-TYPE
   SYNTAX RsNADLRPEntry
   ACCESS not-accessible
   STATUS mandatory
   DESCRIPTION
      "New Report Table (WSD version 10.07.06 and up)."
   INDEX { rsNADLRPDistributedFarmName,
		   rsNADLRPDistributedServerIPType,
		   rsNADLRPDistributedServerIP
	   }
   ::= {rsNADLRPTable  1 }

RsNADLRPEntry ::= SEQUENCE {
        rsNADLRPDistributedFarmName     DisplayString,
		rsNADLRPDistributedServerIPType InetAddressType,
		rsNADLRPDistributedServerIP		InetAddress,
        rsNADLRPFarmName                DisplayString,
        rsNADLRPL4PolicyName            DisplayString,
		rsNADLRPTriangulationVipType    InetAddressType,
        rsNADLRPTriangulationVip        InetAddress,
		rsNADLRPTriangulationNatIPType  InetAddressType,
        rsNADLRPTriangulationNatIP      InetAddress,
		rsNADLRPReportDestinationIPType InetAddressType,
        rsNADLRPReportDestinationIP     InetAddress,
		rsNADLRPBackupDestinationIPType InetAddressType,
        rsNADLRPBackupDestinationIP     InetAddress,
        rsNADLRPHMID                    DisplayString,
        rsNADLRPCckID                   INTEGER,
		rsNADLRPOriginVipType       	InetAddressType,
        rsNADLRPOriginVip               InetAddress,
        rsNADLRPOperationStatus         INTEGER,
        rsNADLRPStatus                  RowStatus
  }

rsNADLRPDistributedFarmName OBJECT-TYPE
   SYNTAX DisplayString (SIZE(0..50))
   ACCESS read-only
   STATUS mandatory
   DESCRIPTION
      " The name of the farm on the WSD DS that contains the Distributed WSD server we report on."
   ::=  {rsNADLRPEntry 1}

rsNADLRPDistributedServerIPType OBJECT-TYPE
   SYNTAX InetAddressType
   ACCESS read-only
   STATUS mandatory
   DESCRIPTION
      "The IP of the Distributed Server configured in the Ad DS."
   DEFVAL{ipv4}
   ::=  {rsNADLRPEntry 2}

rsNADLRPDistributedServerIP OBJECT-TYPE
   SYNTAX InetAddress
   ACCESS read-only
   STATUS mandatory
   DESCRIPTION
      "The IP of the Distributed Server configured in the Ad DS."
	DEFVAL{"0.0.0.0"}
   ::=  {rsNADLRPEntry 3}


rsNADLRPFarmName OBJECT-TYPE
   SYNTAX DisplayString
   ACCESS read-write
   STATUS optional
   DESCRIPTION
      "The name of the local farm that its load is reported."
   DEFVAL{"None"}
   ::=  {rsNADLRPEntry 4}

rsNADLRPL4PolicyName OBJECT-TYPE
   SYNTAX DisplayString
   ACCESS read-write
   STATUS mandatory
   DESCRIPTION
      "The name of the relevant L4 Policy."
   ::=  {rsNADLRPEntry 5}

rsNADLRPTriangulationVipType OBJECT-TYPE
   SYNTAX InetAddressType
   ACCESS read-write
   STATUS mandatory
   DESCRIPTION
      "The Virtual IP on which WSD intercepts traffic from a distributed using
       the triangulation method."
	DEFVAL  { ipv4 }
   ::=  {rsNADLRPEntry 6}

rsNADLRPTriangulationVip OBJECT-TYPE
   SYNTAX InetAddress
   ACCESS read-write
   STATUS mandatory
   DESCRIPTION
      "The Virtual IP on which WSD intercepts traffic from a distributed using
       the triangulation method."
	DEFVAL{"0.0.0.0"}
   ::=  {rsNADLRPEntry 7}

rsNADLRPTriangulationNatIPType OBJECT-TYPE
   SYNTAX InetAddressType
   ACCESS read-write
   STATUS optional
   DESCRIPTION
      "The NAT address that is associated with the Triangulation Vip.
       This is the IP address on which the WSD DS send triangled requests to."
	DEFVAL  { ipv4 }
   ::=  {rsNADLRPEntry 8}

rsNADLRPTriangulationNatIP OBJECT-TYPE
   SYNTAX InetAddress
   ACCESS read-write
   STATUS optional
   DESCRIPTION
      "The NAT address that is associated with the Triangulation Vip.
       This is the IP address on which the WSD DS send triangled requests to."
	DEFVAL{"0.0.0.0"}
   ::=  {rsNADLRPEntry 9}

rsNADLRPReportDestinationIPType OBJECT-TYPE
   SYNTAX InetAddressType
   ACCESS read-write
   STATUS mandatory
   DESCRIPTION
      "The IP address of the remote system which should receive the load
       report."
	DEFVAL  { ipv4 }
   ::=  {rsNADLRPEntry 10}

rsNADLRPReportDestinationIP OBJECT-TYPE
   SYNTAX InetAddress
   ACCESS read-write
   STATUS mandatory
   DESCRIPTION
      "The IP address of the remote system which should receive the load
       report."
	DEFVAL{"0.0.0.0"}
   ::=  {rsNADLRPEntry 11}

rsNADLRPBackupDestinationIPType OBJECT-TYPE
   SYNTAX InetAddressType
   ACCESS read-write
   STATUS optional
   DESCRIPTION
      "The IP address of the redundant remote system which should receive the
       load report."
	DEFVAL  { ipv4 }
   ::=  {rsNADLRPEntry 12}

rsNADLRPBackupDestinationIP OBJECT-TYPE
   SYNTAX InetAddress
   ACCESS read-write
   STATUS optional
   DESCRIPTION
      "The IP address of the redundant remote system which should receive the
       load report."
	DEFVAL{"0.0.0.0"}
   ::=  {rsNADLRPEntry 13}

rsNADLRPHMID OBJECT-TYPE
   SYNTAX DisplayString (SIZE (0..80))
   ACCESS read-write
   STATUS optional
   DESCRIPTION
      "Key id to associate with Health checks of the Health Monitoring module"
   ::=  {rsNADLRPEntry 14}

rsNADLRPCckID OBJECT-TYPE
    SYNTAX  INTEGER
    ACCESS  read-only
    STATUS  optional
    DESCRIPTION
      "Connectivity check module identifier."
    ::=  {rsNADLRPEntry 15}

rsNADLRPOriginVipType OBJECT-TYPE
    SYNTAX  InetAddressType
    ACCESS  read-write
    STATUS  mandatory
    DESCRIPTION
      "The original IP which the client issued its request to.
	   This is the VIP of the L4 Policy in the WSD-DS.
	   The field  is relevant only when using Global Triangulation"
	DEFVAL  { ipv4 }
    ::=  {rsNADLRPEntry 16}

rsNADLRPOriginVip OBJECT-TYPE
    SYNTAX  InetAddress
    ACCESS  read-write
    STATUS  mandatory
    DESCRIPTION
      "The original IP which the client issued its request to.
	   This is the VIP of the L4 Policy in the WSD-DS.
	   The field  is relevant only when using Global Triangulation"
	DEFVAL{"0.0.0.0"}
    ::=  {rsNADLRPEntry 17}

rsNADLRPOperationStatus OBJECT-TYPE
SYNTAX INTEGER {
	active(1),
	notInService(2) }
   ACCESS  read-only
   STATUS  optional
   DESCRIPTION
     "Indicate if the entry is available"
   ::=  {rsNADLRPEntry 18}


rsNADLRPStatus OBJECT-TYPE
   SYNTAX  RowStatus
   ACCESS read-write
   STATUS mandatory
   DESCRIPTION
      ""
   ::=  {rsNADLRPEntry 19}

rsWSDDynamicSessionIdTableStatistics OBJECT IDENTIFIER ::= { rsNWSD 54 }

rsWSDDynamicSessionIdTableEntriesNum OBJECT-TYPE
  SYNTAX INTEGER
  ACCESS  read-only
  STATUS  mandatory
  DESCRIPTION
  "Number of entries in the dynamic session id table."
  ::= {rsWSDDynamicSessionIdTableStatistics 1}

rsWSDDynamicSessionIdTableEntriesNum5SecAvg OBJECT-TYPE
  SYNTAX INTEGER
  ACCESS  read-only
  STATUS  mandatory
  DESCRIPTION
  "Average number of entries in the dynamic session id table in the last 5 seconds."
  ::= {rsWSDDynamicSessionIdTableStatistics 2}

rsWSDDynamicSessionIdTableEntriesNum60SecAvg OBJECT-TYPE
  SYNTAX INTEGER
  ACCESS  read-only
  STATUS  mandatory
  DESCRIPTION
  "Average number of entries in the dynamic session id table in the last 60 seconds."
  ::= {rsWSDDynamicSessionIdTableStatistics 3}

rsWSDRequestTableStatistics OBJECT IDENTIFIER ::= { rsNWSD 56 }

rsWSDRequestTableEntriesNum OBJECT-TYPE
  SYNTAX INTEGER
  ACCESS  read-only
  STATUS  mandatory
  DESCRIPTION
  "Number of entries in the Request table."
  ::= {rsWSDRequestTableStatistics 1}

rsWSDRequestTableEntriesNum5SecAvg OBJECT-TYPE
  SYNTAX INTEGER
  ACCESS  read-only
  STATUS  mandatory
  DESCRIPTION
  "Average number of entries in the Request table in the last 5 seconds."
  ::= {rsWSDRequestTableStatistics 2}

rsWSDRequestTableEntriesNum60SecAvg OBJECT-TYPE
  SYNTAX INTEGER
  ACCESS  read-only
  STATUS  mandatory
  DESCRIPTION
  "Average number of entries in the Request table in the last 60 seconds."
  ::= {rsWSDRequestTableStatistics 3}


rsWSDPhysicalServerConnectionNumTable OBJECT-TYPE
   SYNTAX SEQUENCE OF RsWSDPhysicalServerConnectionNumEntry
   ACCESS not-accessible
   STATUS mandatory
   DESCRIPTION
          "Physical servers connections statistics"
  ::= {rsNWSD 55}

rsWSDPhysicalServerConnectionNumEntry OBJECT-TYPE
    SYNTAX RsWSDPhysicalServerConnectionNumEntry
    ACCESS not-accessible
    STATUS  mandatory
    DESCRIPTION
       " The row definition for this table."
   INDEX  {rsWSDPhysicalServerName}
   ::= {rsWSDPhysicalServerConnectionNumTable 1}

RsWSDPhysicalServerConnectionNumEntry  ::= SEQUENCE {
  rsWSDPhysicalServerName                   DisplayString,
  rsWSDPhysicalCurrentConnectionNum         INTEGER,
  rsWSDPhysicalAverageConnectionNum         INTEGER
}
rsWSDPhysicalServerName OBJECT-TYPE
    SYNTAX DisplayString
    ACCESS  read-only
    STATUS  mandatory
    DESCRIPTION
      "The server name"
    ::= {rsWSDPhysicalServerConnectionNumEntry 1}

rsWSDPhysicalCurrentConnectionNum OBJECT-TYPE
    SYNTAX INTEGER
    ACCESS  read-only
    STATUS  mandatory
    DESCRIPTION
      "The number of active connections attached to this server"
    ::= {rsWSDPhysicalServerConnectionNumEntry 2}

rsWSDPhysicalAverageConnectionNum OBJECT-TYPE
    SYNTAX INTEGER
    ACCESS  read-only
    STATUS  mandatory
    DESCRIPTION
      "The average number of active connections attached to this server"
    ::= {rsWSDPhysicalServerConnectionNumEntry 3}

rsWSDThersholdWarningTraps OBJECT IDENTIFIER ::= { rsNWSD 53 }


rsWSDThresholdWarningTrapsEnable OBJECT-TYPE
  SYNTAX  FeatureStatus
  ACCESS  read-write
  STATUS  mandatory
  DESCRIPTION
  "Enable the threshold warning traps."
  DEFVAL {enable}
  ::= {rsWSDThersholdWarningTraps 1}

rsWSDThresholdWarningMinTimeBetweenTraps OBJECT-TYPE
  SYNTAX INTEGER
  ACCESS  read-write
  STATUS  mandatory
  DESCRIPTION
  "Minimum time between threshold warning traps (seconds)"
  DEFVAL {60}
  ::= {rsWSDThersholdWarningTraps 2}

rsWSDClientTableWarningThresholdLevel OBJECT-TYPE
  SYNTAX INTEGER (0..100)
  ACCESS  read-write
  STATUS  mandatory
  DESCRIPTION
  "Warning threshold level."
  DEFVAL {85}
  ::= {rsWSDThersholdWarningTraps 3}


rsWSDAppServerConnectionLimitThresholdLvl OBJECT-TYPE
  SYNTAX INTEGER (0..100)
  ACCESS  read-write
  STATUS  mandatory
  DESCRIPTION
  "Warning threshold level."
  DEFVAL {85}
  ::= {rsWSDThersholdWarningTraps 4}

rsWSDPhyServerConnectionLimitThresholdLvl OBJECT-TYPE
  SYNTAX INTEGER (0..100)
  ACCESS  read-write
  STATUS  mandatory
  DESCRIPTION
  "Warning threshold level."
  DEFVAL {85}
  ::= {rsWSDThersholdWarningTraps 5}

rsWSDFarmCapacityThresholdLvl OBJECT-TYPE
  SYNTAX INTEGER (0..100)
  ACCESS  read-write
  STATUS  mandatory
  DESCRIPTION
  "Warning threshold level."
  DEFVAL {85}
  ::= {rsWSDThersholdWarningTraps 6}

rsWSDClientNATPortNumThresholdLvl OBJECT-TYPE
  SYNTAX INTEGER (0..100)
  ACCESS  read-write
  STATUS  mandatory
  DESCRIPTION
  "Warning threshold level."
  DEFVAL {85}
  ::= {rsWSDThersholdWarningTraps 7}

rsWSDOutboundNATPortNumThresholdLvl OBJECT-TYPE
  SYNTAX INTEGER (0..100)
  ACCESS  read-write
  STATUS  mandatory
  DESCRIPTION
  "Warning threshold level."
  DEFVAL {85}
  ::= {rsWSDThersholdWarningTraps 8}

rsWSDDSIDTableEntriesNumThresholdLvl OBJECT-TYPE
  SYNTAX INTEGER (0..100)
  ACCESS  read-write
  STATUS  mandatory
  DESCRIPTION
  "Warning threshold level."
  DEFVAL {85}
  ::= {rsWSDThersholdWarningTraps 9}

rsWSDRequestTableEntriesNumThresholdLvl OBJECT-TYPE
  SYNTAX INTEGER (0..100)
  ACCESS  read-write
  STATUS  mandatory
  DESCRIPTION
  "Warning threshold level."
  DEFVAL {85}
  ::= {rsWSDThersholdWarningTraps 10}

rsWSDAuxiliaryTableWarningThresholdLevel OBJECT-TYPE
  SYNTAX INTEGER (0..100)
  ACCESS  read-write
  STATUS  mandatory
  DESCRIPTION
  "Warning threshold level."
  DEFVAL {85}
  ::= {rsWSDThersholdWarningTraps 11}


--  SID Statictics
rsWSDSIDTableStatistics OBJECT IDENTIFIER ::= { rsNWSD 57 }

rsWSDSIDKeyInRequst OBJECT-TYPE
  SYNTAX Counter64
  ACCESS  read-only
  STATUS  mandatory
  DESCRIPTION
  "Persistency Identifier matches.
   Number of packets (both requests and responses) matching the Persistency Identifier configured it the DSID policy"
  ::= {rsWSDSIDTableStatistics 1}

rsWSDSIDValueInRequst OBJECT-TYPE
  SYNTAX INTEGER
  ACCESS  read-only
  STATUS  mandatory
  DESCRIPTION
  "Successfully parsed Dynamic SID values
   Number of Dynamic SID values found following the configured Persistency Identider (should be identical to the previous counter unless the packet contains an empty cookie)."


  ::= {rsWSDSIDTableStatistics 2}

rsWSDNewSIDLearedServer OBJECT-TYPE
  SYNTAX INTEGER
  ACCESS  read-only
  STATUS  mandatory
  DESCRIPTION
  "Number of learned SID value from server."
  ::= {rsWSDSIDTableStatistics 3}

rsWSDNewSIDLearedClient OBJECT-TYPE
  SYNTAX INTEGER
  ACCESS  read-only
  STATUS  mandatory
  DESCRIPTION
  "Number of learned SID value from client."
  ::= {rsWSDSIDTableStatistics 4}

rsWSDSIDInsertInReplyOK OBJECT-TYPE
  SYNTAX INTEGER
  ACCESS  read-only
  STATUS  mandatory
  DESCRIPTION
  "Deprecated"
  ::= {rsWSDSIDTableStatistics 5}

rsWSDSIDInsertInReplyFail OBJECT-TYPE
  SYNTAX INTEGER
  ACCESS  read-only
  STATUS  mandatory
  DESCRIPTION
  "Deprecated"
  ::= {rsWSDSIDTableStatistics 6}

rsWSDSIDRewriteInReplyOK OBJECT-TYPE
  SYNTAX INTEGER
  ACCESS  read-only
  STATUS  mandatory
  DESCRIPTION
  "Deprecated"
  ::= {rsWSDSIDTableStatistics 7}

rsWSDSIDRewriteToReplyFail OBJECT-TYPE
  SYNTAX INTEGER
  ACCESS  read-only
  STATUS  mandatory
  DESCRIPTION
  "Deprecated"
  ::= {rsWSDSIDTableStatistics 8}

rsWSDSIDTableStatReset OBJECT-TYPE
    SYNTAX  INTEGER {
       reset(1)
     }
  ACCESS  read-write
  STATUS  mandatory
  DESCRIPTION
  "Reset the SID tbale statistics."
  ::= {rsWSDSIDTableStatistics 9}

rdwrTrapSync OBJECT IDENTIFIER ::= { rdwrWSDCommon  2 }

rdwrTrapSyncStatus  OBJECT-TYPE
    SYNTAX  FeatureStatus
    ACCESS  read-write
    STATUS  mandatory
    DESCRIPTION
       "Enable Disable the trap sync feature"
   DEFVAL { disable }
    ::= { rdwrTrapSync  1  }

rdwrTrapFileMaxEntries  OBJECT-TYPE
    SYNTAX  INTEGER (50..32768)
    ACCESS  read-write
    STATUS  mandatory
    DESCRIPTION
       "TL maximum File Size in log entries"
   DEFVAL { 1000 }
    ::= { rdwrTrapSync  2  }

rdwrTrapMinSeverity  OBJECT-TYPE
    SYNTAX  INTEGER {
       informational(1),
       warning(2),
       error(3)
    }
    ACCESS  read-write
    STATUS  mandatory
    DESCRIPTION
       "Minimun severity for trap logging"
    ::= { rdwrTrapSync  3  }

rdwrTrapLastID  OBJECT-TYPE
    SYNTAX  INTEGER
    ACCESS  read-only
    STATUS  mandatory
    DESCRIPTION
       "Last issued Trap ID. form 1..32768"
    ::= { rdwrTrapSync  4  }

rdwrTrapSyncTable  OBJECT-TYPE
   SYNTAX SEQUENCE OF RdwrTrapSyncEntry
   ACCESS not-accessible
   STATUS mandatory
   DESCRIPTION
       "A table for trap SYNC."
   ::= { rdwrTrapSync   5}

rdwrTrapSyncEntry  OBJECT-TYPE
   SYNTAX RdwrTrapSyncEntry
   ACCESS not-accessible
   STATUS mandatory
   DESCRIPTION
       " The row definition for this table."
   INDEX  { rdwrTrapSyncTableID}
   ::= { rdwrTrapSyncTable 1}

RdwrTrapSyncEntry ::= SEQUENCE {
  rdwrTrapSyncTableID            INTEGER,
  rdwrTrapSyncTableSeverity      INTEGER,
  rdwrTrapSyncTableText          DisplayString,
  rdwrTrapSyncTableDateTime      DisplayString,
  rdwrTrapSyncTableTrapOID       OBJECT IDENTIFIER
}


rdwrTrapSyncTableID   OBJECT-TYPE
  SYNTAX INTEGER
  ACCESS read-only
  STATUS mandatory
  DESCRIPTION
     "Index for traps log file."
  ::=  { rdwrTrapSyncEntry 1}

rdwrTrapSyncTableSeverity   OBJECT-TYPE
  SYNTAX INTEGER {
       informational(1),
       warning(2),
       error(3)
    }
  ACCESS read-only
  STATUS mandatory
  DESCRIPTION
     "Severity of the logged trap."
  ::=  { rdwrTrapSyncEntry 2}

rdwrTrapSyncTableText   OBJECT-TYPE
  SYNTAX DisplayString
  ACCESS read-only
  STATUS mandatory
  DESCRIPTION
     " The text of the logged trap."
  ::=  { rdwrTrapSyncEntry 3}


rdwrTrapSyncTableDateTime   OBJECT-TYPE
  SYNTAX DisplayString
  ACCESS read-only
  STATUS mandatory
  DESCRIPTION
     "Trap date and time {dd-mm-yyyy hh:mm:ss }."
  ::=  { rdwrTrapSyncEntry 4}


rdwrTrapSyncTableTrapOID  OBJECT-TYPE
  SYNTAX OBJECT IDENTIFIER
  ACCESS read-only
  STATUS mandatory
  DESCRIPTION
     "Trap MIB name."
  ::=  { rdwrTrapSyncEntry 5}

rdwrVrrpCommon  OBJECT IDENTIFIER ::= { rdwrWSDCommon 3 }

rdwrVrrpAutomatedConfiguration OBJECT-TYPE
    SYNTAX  FeatureStatus
    ACCESS  read-write
    STATUS  mandatory
    DESCRIPTION
        "When Vrrp Automated Configuration is enabled, if vrrp is enable then new vip will be added
         to the Associated Ip Table Automatically."
    DEFVAL { enable }
    ::=  { rdwrVrrpCommon  1}


rdwrManagedDevice OBJECT IDENTIFIER ::= { rdwrWSDCommon  4 }

--	 rdwrWSDCommon  12 - Reserve this for AD 20.10.00

rdwrManagedDeviceTable  OBJECT-TYPE
   SYNTAX SEQUENCE OF RdwrManagedDeviceEntry
   ACCESS not-accessible
   STATUS mandatory
   DESCRIPTION
       "Managed device table."
   ::= { rdwrManagedDevice 1}

rdwrManagedDeviceEntry  OBJECT-TYPE
   SYNTAX RdwrManagedDeviceEntry
   ACCESS not-accessible
   STATUS mandatory
   DESCRIPTION
       " The row definition for this table."
   INDEX  { rdwrManagedDeviceTableName }
   ::= { rdwrManagedDeviceTable 1}

RdwrManagedDeviceEntry::= SEQUENCE {
  rdwrManagedDeviceTableName          DisplayString,
  rdwrManagedDeviceTableDescription   DisplayString,
  rdwrManagedDeviceTableIP            IpAddress,
  rdwrManagedDeviceTableApplication   INTEGER,
  rdwrManagedDeviceTablePort          INTEGER,
  rdwrManagedDeviceAdminStatus        FeatureStatus,
  rdwrManagedDeviceUserName           DisplayString,
  rdwrManagedDevicePassword           DisplayString,
  rdwrManagedConnectionStatus         INTEGER,
  rdwrManagedTxMessageCounter         INTEGER,
  rdwrManagedRxMessageCounter         INTEGER,
  rdwrManagedLastRxMessage	      OCTET STRING,
  rdwrManagedRowStatus                RowStatus,
  rdwrManagedEntryOrigin                INTEGER,
  rdwrManagedDeviceTableAddrType       	InetAddressType,
  rdwrManagedDeviceTableAddr            InetAddress
}

rdwrManagedDeviceTableName      OBJECT-TYPE
    SYNTAX DisplayString (SIZE(1..50))
    ACCESS  read-only
    STATUS  mandatory
    DESCRIPTION
      "The name of the manged device."
 ::=  { rdwrManagedDeviceEntry  1}


rdwrManagedDeviceTableDescription  OBJECT-TYPE
    SYNTAX DisplayString (SIZE(0..50))
    ACCESS  read-write
    STATUS  optional
    DESCRIPTION
      "The manged device description."
 ::=  { rdwrManagedDeviceEntry  2}

-- obsolete
rdwrManagedDeviceTableIP           OBJECT-TYPE
    SYNTAX IpAddress
    ACCESS  read-write
    STATUS  optional
    DESCRIPTION
      "THIS FIELD IS NOT IN USE"
	DEFVAL {0}
 ::=  { rdwrManagedDeviceEntry  3}

rdwrManagedDeviceTableApplication  OBJECT-TYPE
    SYNTAX INTEGER {
      ssh(1),
      telnet(2),
      dxp(3)
    }
    ACCESS  read-write
    STATUS  optional
    DESCRIPTION
      "Management application for the device."
    DEFVAL {1}
 ::=  { rdwrManagedDeviceEntry  4}

rdwrManagedDeviceTablePort   OBJECT-TYPE
    SYNTAX INTEGER (0..65535)
    ACCESS  read-write
    STATUS  optional
    DESCRIPTION
      "The manged device Port."
    DEFVAL {22}
 ::=  { rdwrManagedDeviceEntry  5}

rdwrManagedDeviceAdminStatus   OBJECT-TYPE
    SYNTAX  FeatureStatus
    ACCESS  read-write
    STATUS  optional
    DESCRIPTION
      "Admin status of the connection"
    DEFVAL {enable}
 ::=  { rdwrManagedDeviceEntry  6}


rdwrManagedDeviceUserName OBJECT-TYPE
    SYNTAX DisplayString (SIZE(0..64))
    ACCESS  read-write
    STATUS  mandatory
    DESCRIPTION
      "The managed device SSH/TELNET user name."
 ::=  { rdwrManagedDeviceEntry  7}

rdwrManagedDevicePassword    OBJECT-TYPE
    SYNTAX DisplayString (SIZE(0..64))
    ACCESS  read-write
    STATUS  mandatory
    DESCRIPTION
      "The managed device SSH/TELNET password."
 ::=  { rdwrManagedDeviceEntry  8}

rdwrManagedConnectionStatus   OBJECT-TYPE
     SYNTAX INTEGER {
      connecting(1),
      open(2),
      insync(3),
      terminated(4),
      closed(5)
    }
    ACCESS  read-only
    STATUS  optional
    DESCRIPTION
      "State of the connection"
 ::=  { rdwrManagedDeviceEntry  9}
rdwrManagedTxMessageCounter    OBJECT-TYPE
     SYNTAX INTEGER
    ACCESS  read-only
    STATUS  optional
    DESCRIPTION
      "The accumulated amount of tx messages"
 ::=  { rdwrManagedDeviceEntry  10}

rdwrManagedRxMessageCounter    OBJECT-TYPE
    SYNTAX INTEGER
    ACCESS  read-only
    STATUS  optional
    DESCRIPTION
      "The accumulated amount of rx messages"
 ::=  { rdwrManagedDeviceEntry  11}


rdwrManagedLastRxMessage     OBJECT-TYPE
    SYNTAX OCTET STRING (SIZE(0..255))
    ACCESS  read-only
    STATUS  optional
    DESCRIPTION
      "the first 256 chars of the last message received "
 ::=  { rdwrManagedDeviceEntry  12}

rdwrManagedRowStatus         OBJECT-TYPE
     SYNTAX RowStatus
    ACCESS  read-write
    STATUS  mandatory
    DESCRIPTION
      "Row status"
 ::=  { rdwrManagedDeviceEntry  13}

rdwrManagedEntryOrigin      OBJECT-TYPE
    SYNTAX  INTEGER {
        user(1),
        internal(2)
    }
    ACCESS  read-only
    STATUS  mandatory
    DESCRIPTION
        "shows whether the device was added by the user or internally by the application.
         internal devices cannot be edited and/or deleted."
 ::=  { rdwrManagedDeviceEntry  14}

rdwrManagedDeviceTableAddrType           OBJECT-TYPE
    SYNTAX InetAddressType
    ACCESS  read-write
    STATUS  mandatory
    DESCRIPTION
      "The manged device IP Type."
	DEFVAL  { ipv4 }
 ::=  { rdwrManagedDeviceEntry  15}

rdwrManagedDeviceTableAddr           OBJECT-TYPE
    SYNTAX InetAddress
    ACCESS  read-write
    STATUS  mandatory
    DESCRIPTION
      "The manged device IP."
 ::=  { rdwrManagedDeviceEntry  16}

rdwrTCPSplittingTable  OBJECT-TYPE
   SYNTAX SEQUENCE OF RdwrTCPSplittingEntry
   ACCESS not-accessible
   STATUS mandatory
   DESCRIPTION
       " AX to BE Farm Table."
   ::= { rdwrManagedDevice 2}

rdwrTCPSplittingEntry OBJECT-TYPE
   SYNTAX RdwrTCPSplittingEntry
   ACCESS not-accessible
   STATUS mandatory
   DESCRIPTION
       " The row definition for this table."
   INDEX  { rdwrTCPSplittingTableFarmName,
            rdwrTCPSplittingTableL4PolicyName   }
   ::= { rdwrTCPSplittingTable 1}

RdwrTCPSplittingEntry::= SEQUENCE {
  rdwrTCPSplittingTableFarmName      DisplayString,
  rdwrTCPSplittingTableL4PolicyName  DisplayString,
  rdwrTCPSplittingTableRowStatus       RowStatus
}

rdwrTCPSplittingTableFarmName      OBJECT-TYPE
    SYNTAX DisplayString (SIZE(1..50))
    ACCESS  read-only
    STATUS  mandatory
    DESCRIPTION
      "The FE AX farm name."
 ::=  { rdwrTCPSplittingEntry 1}

rdwrTCPSplittingTableL4PolicyName OBJECT-TYPE
    SYNTAX DisplayString (SIZE(1..50))
    ACCESS  read-only
    STATUS  mandatory
    DESCRIPTION
      "The BE L4 Policy Name."
 ::=  { rdwrTCPSplittingEntry 2}

rdwrTCPSplittingTableRowStatus       OBJECT-TYPE
    SYNTAX RowStatus
    ACCESS  read-write
    STATUS  mandatory
    DESCRIPTION
      "Row Status of the table."
 ::=  { rdwrTCPSplittingEntry 3}

rdwrADAppServerTCPSplitTable  OBJECT-TYPE
   SYNTAX SEQUENCE OF RdwrADAppServerTCPSplitEntry
   ACCESS not-accessible
   STATUS mandatory
   DESCRIPTION
       " Application server parametes for the TCP Splitting."
   ::= { rdwrManagedDevice 3}

rdwrADAppServerTCPSplitEntry OBJECT-TYPE
   SYNTAX RdwrADAppServerTCPSplitEntry
   ACCESS not-accessible
   STATUS mandatory
   DESCRIPTION
       " The row definition for this table."
   INDEX  { rdwrADAppServerTCPSplitTableFarmName,
            rdwrADAppServerTCPSplitTableServerAddr,
	    rdwrADAppServerTCPSplitTableServerPort}
   ::= { rdwrADAppServerTCPSplitTable 1}

RdwrADAppServerTCPSplitEntry::= SEQUENCE {
  rdwrADAppServerTCPSplitTableFarmName        DisplayString,
  rdwrADAppServerTCPSplitTableServerAddr      IpAddress,
  rdwrADAppServerTCPSplitTableServerPort       INTEGER,
  rdwrADAppServerTCPSplitTableMngmDeviceName  DisplayString,
  rdwrADAppServerTCPSplitTableTunnelID        INTEGER,
  rdwrADAppServerTCPSplitTableRowStatus       RowStatus
}


rdwrADAppServerTCPSplitTableFarmName   OBJECT-TYPE
    SYNTAX DisplayString (SIZE(1..50))
    ACCESS  read-only
    STATUS  mandatory
    DESCRIPTION
      "The farm name."
 ::=  { rdwrADAppServerTCPSplitEntry 1}

rdwrADAppServerTCPSplitTableServerAddr OBJECT-TYPE
    SYNTAX  IpAddress
    ACCESS  read-only
    STATUS  mandatory
    DESCRIPTION
      "Application server IP"
 ::=  { rdwrADAppServerTCPSplitEntry 2}

rdwrADAppServerTCPSplitTableServerPort OBJECT-TYPE
    SYNTAX  INTEGER (0..65535)
    ACCESS  read-only
    STATUS  mandatory
    DESCRIPTION
      "Application server Port"
 ::=  { rdwrADAppServerTCPSplitEntry 3}

rdwrADAppServerTCPSplitTableMngmDeviceName   OBJECT-TYPE
    SYNTAX DisplayString (SIZE(1..50))
    ACCESS  read-write
    STATUS  mandatory
    DESCRIPTION
      "This is the name of the AppXcel device on which the Tunnel with this IP is configured"
 ::=  {rdwrADAppServerTCPSplitEntry 4}

rdwrADAppServerTCPSplitTableTunnelID         OBJECT-TYPE
    SYNTAX INTEGER (1..214748364)
    ACCESS  read-write
    STATUS  mandatory
    DESCRIPTION
      "This is the AppXcel Tunnel ID that has represents that Application Server on AppXcel and has the same IP and port"
 ::=  {rdwrADAppServerTCPSplitEntry 5}

rdwrADAppServerTCPSplitTableRowStatus  OBJECT-TYPE
    SYNTAX RowStatus
    ACCESS  read-write
    STATUS  mandatory
    DESCRIPTION
      "Row Status of the table."
 ::=  { rdwrADAppServerTCPSplitEntry 6}

rdwrNADServerTCPSplitTable  OBJECT-TYPE
   SYNTAX SEQUENCE OF RdwrNADServerTCPSplitEntry
   ACCESS not-accessible
   STATUS mandatory
   DESCRIPTION
       " Application server parametes for the TCP Splitting."
   ::= { rdwrManagedDevice 4}

rdwrNADServerTCPSplitEntry OBJECT-TYPE
   SYNTAX RdwrNADServerTCPSplitEntry
   ACCESS not-accessible
   STATUS mandatory
   DESCRIPTION
       " The row definition for this table."
   INDEX  { rdwrNADServerTCPSplitTableFarmName,
            rdwrNADServerTCPSplitTableServerName}
   ::= { rdwrNADServerTCPSplitTable 1}

RdwrNADServerTCPSplitEntry::= SEQUENCE {
  rdwrNADServerTCPSplitTableFarmName        DisplayString,
  rdwrNADServerTCPSplitTableServerName	   DisplayString,
  rdwrNADServerTCPSplitTableMngmDeviceName  DisplayString,
  rdwrNADServerTCPSplitTableTunnelID        INTEGER,
  rdwrNADServerTCPSplitTableRowStatus       RowStatus
}


rdwrNADServerTCPSplitTableFarmName   OBJECT-TYPE
    SYNTAX DisplayString (SIZE(1..50))
    ACCESS  read-only
    STATUS  mandatory
    DESCRIPTION
      "The farm name."
 ::=  { rdwrNADServerTCPSplitEntry 1}

rdwrNADServerTCPSplitTableServerName  OBJECT-TYPE
    SYNTAX  DisplayString (SIZE(1..30))
    ACCESS  read-only
    STATUS  mandatory
    DESCRIPTION
      "The name assigned by the user to the server."
    ::=  {rdwrNADServerTCPSplitEntry 2}


rdwrNADServerTCPSplitTableMngmDeviceName   OBJECT-TYPE
    SYNTAX DisplayString (SIZE(1..50))
    ACCESS  read-write
    STATUS  mandatory
    DESCRIPTION
      "This is the name of the AppXcel device on which the Tunnel with this IP is configured"
 ::=  {rdwrNADServerTCPSplitEntry 3}

rdwrNADServerTCPSplitTableTunnelID         OBJECT-TYPE
    SYNTAX INTEGER (1..214748364)
    ACCESS  read-write
    STATUS  mandatory
    DESCRIPTION
      "This is the AppXcel Tunnel ID that has represents that Application Server on AppXcel and has the same Name"
 ::=  {rdwrNADServerTCPSplitEntry 4}

rdwrNADServerTCPSplitTableRowStatus  OBJECT-TYPE
    SYNTAX RowStatus
    ACCESS  read-write
    STATUS  mandatory
    DESCRIPTION
      "Row Status of the table."
 ::=  { rdwrNADServerTCPSplitEntry 5}


rdwrADL7Modification OBJECT IDENTIFIER ::= { rsNWSD 58 }

rdwrADL7ModificationTable OBJECT-TYPE
    SYNTAX SEQUENCE OF RdwrADL7ModificationEntry
    ACCESS not-accessible
    STATUS mandatory
    DESCRIPTION
      "Table containing the list change rules for HTTP L7."
    ::=  { rdwrADL7Modification 1}

rdwrADL7ModificationEntry OBJECT-TYPE
    SYNTAX RdwrADL7ModificationEntry
    ACCESS not-accessible
    STATUS  mandatory
    DESCRIPTION
       " The row definition for this table."
   INDEX { rdwrADL7ModificationName }
    ::=  { rdwrADL7ModificationTable 1}

RdwrADL7ModificationEntry::= SEQUENCE {
  rdwrADL7ModificationName                   DisplayString,
  rdwrADL7ModificationIndex                  Unsigned32,
  rdwrADL7ModificationFarmName               DisplayString,
  rdwrADL7ModificationAction                 INTEGER,
  rdwrADL7ModificationDirection              INTEGER,
  rdwrADL7ModificationMatchMethodName        DisplayString,
  rdwrADL7ModificationActionMethodName       DisplayString,
  rdwrADL7ModificationAdminStatus            FeatureStatus,
  rdwrADL7ModificationStatus                 RowStatus,
  rdwrADL7ModificationScope                  INTEGER,
  rdwrADL7ModificationHeaderBodyCondition    DisplayString,
  rdwrADL7ModificationHeaderBodyModification DisplayString
 }

rdwrADL7ModificationName OBJECT-TYPE
    SYNTAX  DisplayString (SIZE(1..50))
    ACCESS  read-only
    STATUS  mandatory
    DESCRIPTION
     "L7 modification name"
 ::=  { rdwrADL7ModificationEntry 1}

rdwrADL7ModificationIndex OBJECT-TYPE
    SYNTAX  Unsigned32
    ACCESS  read-write
    STATUS  mandatory
    DESCRIPTION
     "Order of rules to be executed"
 ::=  { rdwrADL7ModificationEntry 2}

rdwrADL7ModificationFarmName OBJECT-TYPE
    SYNTAX  DisplayString (SIZE(1..50))
    ACCESS  read-write
    STATUS  mandatory
    DESCRIPTION
     "farm name"
 ::=  { rdwrADL7ModificationEntry 3}

rdwrADL7ModificationAction OBJECT-TYPE
    SYNTAX  INTEGER {
    insert      (1),
    update      (2),
    remove      (3),
    insertBefore(4),
    insertAfter (5),
    updateAll   (6)
    }
    ACCESS  read-write
    STATUS  mandatory
    DESCRIPTION
     "Action of the rule"
    DEFVAL { insert }
 ::=  { rdwrADL7ModificationEntry 4}

rdwrADL7ModificationDirection OBJECT-TYPE
    SYNTAX  INTEGER       {
    request         (1),
    reply           (2),
    bidirectional   (3)   }
    ACCESS  read-write
    STATUS  mandatory
    DESCRIPTION
     "Direction of packet to apply the rule"
    DEFVAL { request }
 ::=  { rdwrADL7ModificationEntry 5}

rdwrADL7ModificationMatchMethodName OBJECT-TYPE
    SYNTAX  DisplayString (SIZE(0..50))
    ACCESS  read-write
    STATUS  mandatory
    DESCRIPTION
     "Method name to be used for match"
 ::=  { rdwrADL7ModificationEntry 6}

rdwrADL7ModificationActionMethodName OBJECT-TYPE
    SYNTAX  DisplayString (SIZE(0..50))
    ACCESS  read-write
    STATUS  mandatory
    DESCRIPTION
     "Method name to be used to change"
 ::=  { rdwrADL7ModificationEntry 7}

rdwrADL7ModificationAdminStatus  OBJECT-TYPE
    SYNTAX  FeatureStatus
    ACCESS  read-write
    STATUS  mandatory
    DESCRIPTION
      "Enable/Disable L7 modification rule."
    ::=  {rdwrADL7ModificationEntry 8}

rdwrADL7ModificationStatus OBJECT-TYPE
    SYNTAX  RowStatus
    ACCESS  read-write
    STATUS  mandatory
    DESCRIPTION
     ""
 ::=  { rdwrADL7ModificationEntry 9}

 rdwrADL7ModificationScope OBJECT-TYPE
    SYNTAX  INTEGER        {
    headerOnly       (1),
    headerAndBody    (2)   }
    ACCESS  read-write
    STATUS  mandatory
    DESCRIPTION
     "Defines whether L7 modifications are applied to HTTP header only or both header and body"
    DEFVAL { headerOnly }
 ::=  { rdwrADL7ModificationEntry 10}

 rdwrADL7ModificationHeaderBodyCondition OBJECT-TYPE
    SYNTAX  DisplayString (SIZE(0..50))
    ACCESS  read-write
    STATUS  mandatory
    DESCRIPTION
     "Indicates name of an Advanced URL Condition to be used for matching response modifications in modifications using header & body scope"
 ::=  { rdwrADL7ModificationEntry 11}

rdwrADL7ModificationHeaderBodyModification OBJECT-TYPE
    SYNTAX  DisplayString (SIZE(0..50))
    ACCESS  read-write
    STATUS  mandatory
    DESCRIPTION
     "Indicates name of an Advanced URL Modification be used for modifications using header & body scope"
 ::=  { rdwrADL7ModificationEntry 12}

rdwrADL7ModificationStatisticsTable OBJECT-TYPE
    SYNTAX SEQUENCE OF RdwrADL7ModificationStatisticsEntry
    ACCESS not-accessible
    STATUS mandatory
    DESCRIPTION
      "Table containing the statistics of L7 modification rules."
    ::=  { rdwrADL7Modification 2}

rdwrADL7ModificationStatisticsEntry OBJECT-TYPE
    SYNTAX RdwrADL7ModificationStatisticsEntry
    ACCESS not-accessible
    STATUS  mandatory
    DESCRIPTION
       " The row definition for this table."
   INDEX { rdwrADL7ModificationStatisticsName }
    ::=  { rdwrADL7ModificationStatisticsTable 1}

RdwrADL7ModificationStatisticsEntry::= SEQUENCE {
  rdwrADL7ModificationStatisticsName DisplayString,
  rdwrADL7Modification5SecMatchCounter Counter,
  rdwrADL7Modification60MatchSecCounter Counter,
  rdwrADL7ModificationGlobalMatchCounter Counter
 }

rdwrADL7ModificationStatisticsName OBJECT-TYPE
    SYNTAX  DisplayString
    ACCESS  read-only
    STATUS  mandatory
    DESCRIPTION
     "L7 modification rule name"
 ::=  { rdwrADL7ModificationStatisticsEntry 1}

rdwrADL7Modification5SecMatchCounter OBJECT-TYPE
    SYNTAX  Counter
    ACCESS  read-only
    STATUS  mandatory
    DESCRIPTION
     "Number of matches in the last 5 seconds"
::=  { rdwrADL7ModificationStatisticsEntry 2}

rdwrADL7Modification60MatchSecCounter OBJECT-TYPE
    SYNTAX  Counter
    ACCESS  read-only
    STATUS  mandatory
    DESCRIPTION
     "Number of matches in the last 60 seconds"
 ::=  { rdwrADL7ModificationStatisticsEntry 3}

rdwrADL7ModificationGlobalMatchCounter OBJECT-TYPE
    SYNTAX  Counter
    ACCESS  read-only
    STATUS  mandatory
    DESCRIPTION
     "number of matches since rest"
 ::=  { rdwrADL7ModificationStatisticsEntry 4}

rdwrADL7ModificationMatchCounterResetScalar OBJECT-TYPE
    SYNTAX  INTEGER {
       reset(1)
     }
    ACCESS  read-write
    STATUS  mandatory
    DESCRIPTION
     "Resets the global statistics of l7 modification rules"
 ::=  { rdwrADL7Modification 3}

rsWSDAuxiliaryTableStatistics OBJECT IDENTIFIER ::= { rsNWSD 59 }

rsWSDAuxiliaryTableNumEntries OBJECT-TYPE
  SYNTAX INTEGER
  ACCESS  read-only
  STATUS  mandatory
  DESCRIPTION
  "Number of entries in the Auxiliary table."
  ::= {rsWSDAuxiliaryTableStatistics 1}

rsWSDAuxiliaryTableEntriesNum5SecAvg OBJECT-TYPE
  SYNTAX INTEGER
  ACCESS  read-only
  STATUS  mandatory
  DESCRIPTION
  "Average number of entries in the Auxiliary table in the last 5 seconds."
  ::= {rsWSDAuxiliaryTableStatistics 2}

rsWSDAuxiliaryTableEntriesNum60SecAvg OBJECT-TYPE
  SYNTAX INTEGER
  ACCESS  read-only
  STATUS  mandatory
  DESCRIPTION
  "Average number of entries in the Auxiliary table in the last 60 seconds."
  ::= {rsWSDAuxiliaryTableStatistics 3}


rdwrBgp  OBJECT IDENTIFIER ::= { rdwrWSDCommon 1 }


rdwrBgpAdminStatus OBJECT-TYPE
   SYNTAX  FeatureStatus
   ACCESS  read-write
   STATUS  mandatory
   DESCRIPTION
         "Global BGP admin status."
   DEFVAL { disable }
   ::= { rdwrBgp 2 }

rdwrBgpLocalAS OBJECT-TYPE
   SYNTAX  INTEGER (0..65535)
   ACCESS read-write
   STATUS  mandatory
   DESCRIPTION
         "The Autonomous System (AS) number of this site"
   DEFVAL { 65535 }
   ::= { rdwrBgp 3 }


-- Radware BGP Peer table. Configure peers using this table.

                rdwrBgpPeerTable OBJECT-TYPE
                    SYNTAX     SEQUENCE OF RdwrBgpPeerEntry
                    ACCESS     not-accessible
                    STATUS     mandatory
                    DESCRIPTION
                            "BGP peer table. "
                    ::= { rdwrBgp 4 }

                rdwrBgpPeerEntry OBJECT-TYPE
                    SYNTAX     RdwrBgpPeerEntry
                    ACCESS     not-accessible
                    STATUS     mandatory
                    DESCRIPTION
                            "Entry containing peer configuration parameters and information"
                    INDEX { rdwrBgpPeerRemoteAddr }
                    ::= { rdwrBgpPeerTable 1 }

                RdwrBgpPeerEntry ::= SEQUENCE {
                        rdwrBgpPeerRemoteAddr                IpAddress,
                        rdwrBgpPeerAdminStatus               FeatureStatus,
                        rdwrBgpPeerConnectRetryInterval      INTEGER,
                        rdwrBgpPeerHoldTime                  INTEGER,
                        rdwrBgpPeerKeepAlive                 INTEGER,
                        rdwrBgpPeerState                     INTEGER,
                        rdwrBgpPeerRemoteAs                  INTEGER,
                        rdwrBgpPeerLastError                 DisplayString,
                        rdwrBgpPeerRowStatus                 RowStatus
                        }

                rdwrBgpPeerRemoteAddr OBJECT-TYPE
                    SYNTAX     IpAddress
                    ACCESS     read-only
                    STATUS     mandatory
                    DESCRIPTION
                            "The BGP Identifier of this entry's BGP
                            peer."
                    ::= { rdwrBgpPeerEntry 1 }

                rdwrBgpPeerAdminStatus OBJECT-TYPE
                    SYNTAX     FeatureStatus
                    ACCESS     read-write
                    STATUS     mandatory
                    DESCRIPTION
                            "The desired state of the BGP connection.
                            A transition from 'stop' to 'start' will
                            cause the BGP Start Event to be generated.
                            A transition from 'start' to 'stop' will
                            cause the BGP Stop Event to be generated.
                            This parameter can be used to restart BGP
                            peer connections.  Care should be used in
                            providing write access to this object
                            without adequate authentication."
                     DEFVAL { enable }
                    ::= { rdwrBgpPeerEntry 2 }

                rdwrBgpPeerConnectRetryInterval OBJECT-TYPE
                    SYNTAX     INTEGER (1..65535)
                    ACCESS     read-write
                    STATUS     mandatory
                    DESCRIPTION
                            "Time interval in seconds for the
                            ConnectRetry timer.  The suggested value
                            for this timer is 120 seconds."
                    DEFVAL { 120 }
                    ::= { rdwrBgpPeerEntry 3 }



                rdwrBgpPeerHoldTime OBJECT-TYPE
                    SYNTAX     INTEGER ( 0 | 3..65535 )
                    ACCESS     read-write
                    STATUS     mandatory
                    DESCRIPTION
                            "Time interval in seconds for the Hold Time
                            configured for this BGP speaker with this
                            peer.  This value is placed in an OPEN
                            message sent to this peer by this BGP
                            speaker, and is compared with the Hold
                            Time field in an OPEN message received
                            from the peer when determining the Hold
                            Time (bgpPeerHoldTime) with the peer.
                            This value must not be less than three
                            seconds if it is not zero (0) in which
                            case the Hold Time is NOT to be
                            established with the peer.  The suggested
                            value for this timer is 90 seconds."
                    DEFVAL { 90 }
                    ::= { rdwrBgpPeerEntry 4 }

                rdwrBgpPeerKeepAlive OBJECT-TYPE
                    SYNTAX     INTEGER ( 0 | 1..21845 )
                    ACCESS     read-write
                    STATUS     mandatory
                    DESCRIPTION
                            "Time interval in seconds for the
                            KeepAlive timer configured for this BGP
                            speaker with this peer.  The value of this
                            object will only determine the
                            KEEPALIVE messages' frequency relative to
                            the value specified in
                            bgpPeerHoldTimeConfigured; the actual
                            time interval for the KEEPALIVE messages
                            is indicated by bgpPeerKeepAlive.  A
                            reasonable maximum value for this timer
                            would be configured to be one
                            third of that of
                            bgpPeerHoldTimeConfigured.
                            If the value of this object is zero (0),
                            no periodical KEEPALIVE messages are sent
                            to the peer after the BGP connection has
                            been established.  The suggested value for
                            this timer is 30 seconds."
                    DEFVAL { 30 }
                    ::= { rdwrBgpPeerEntry 5 }

               rdwrBgpPeerState OBJECT-TYPE
                    SYNTAX     INTEGER {
                                        idle(1),
                                        connect(2),
                                        active(3),
                                        opensent(4),
                                        openconfirm(5),
                                        established(6)
                               }
                    ACCESS     read-only
                    STATUS     mandatory
                    DESCRIPTION
                            "The BGP peer connection state."
                    ::= { rdwrBgpPeerEntry 6 }

                rdwrBgpPeerRemoteAs OBJECT-TYPE
                    SYNTAX     INTEGER (0..65535)
                    ACCESS     read-only
                    STATUS     mandatory
                    DESCRIPTION
                            "The remote autonomous system number."
                    ::= { rdwrBgpPeerEntry 7 }

                rdwrBgpPeerLastError OBJECT-TYPE
                    SYNTAX     DisplayString (SIZE(0..255))
                    ACCESS     read-only
                    STATUS     mandatory
                    DESCRIPTION
                            "The last error message seen by this peer."
                    ::= { rdwrBgpPeerEntry 8 }

                rdwrBgpPeerRowStatus OBJECT-TYPE
                     SYNTAX  RowStatus
                     ACCESS  read-write
                     STATUS  mandatory
                     DESCRIPTION
                        "This variable indicates the administrative action to perform on the entry.
                         create / update / delete."
                    ::=  { rdwrBgpPeerEntry 9 }


rdwrBgpTraps  OBJECT IDENTIFIER ::= { rdwrBgp 5 }

    rdwrBgpEstablished TRAP-TYPE
        ENTERPRISE rdwrBgpTraps
        VARIABLES { rndErrorDesc, rndErrorSeverity }
        DESCRIPTION
           "The BGP Established event is generated when
            the BGP FSM enters the ESTABLISHED state."

    ::= 1


    rdwrBgpBackwardTransition TRAP-TYPE
        ENTERPRISE rdwrBgpTraps
        VARIABLES { rndErrorDesc, rndErrorSeverity }
        DESCRIPTION
           "The BGPBackwardTransition Event is generated
            when the BGP FSM moves from a higher numbered
            state to a lower numbered statee."

    ::= 2

rdwrBgpInitDelay OBJECT-TYPE
   SYNTAX  INTEGER (15..120)
   ACCESS read-write
   STATUS  mandatory
   DESCRIPTION
         "Time in seconds to wait at device startup before establishing BGP connections"
   DEFVAL { 15 }
   ::= { rdwrBgp 6 }


rsADFarmClientStatsTable OBJECT-TYPE
    SYNTAX SEQUENCE OF RsADFarmClientStatsEntry
    ACCESS not-accessible
    STATUS mandatory
    DESCRIPTION
      "Table containing farm client statistics."
    ::=  {rsNWSDStats 9}

rsADFarmClientStatsEntry OBJECT-TYPE
    SYNTAX RsADFarmClientStatsEntry
    ACCESS not-accessible
    STATUS  mandatory
    DESCRIPTION
       " The row definition for this table."
   INDEX { rsADFarmClientStatsFarmIPaddr ,
           rsADFarmClientStatsFarmName}
    ::=  {rsADFarmClientStatsTable 1}

RsADFarmClientStatsEntry ::= SEQUENCE {
  rsADFarmClientStatsFarmIPaddr			        IpAddress,
  rsADFarmClientStatsFarmName			        DisplayString,
  rsADFarmClientStatsAllClientCurrent			Counter32,
  rsADFarmClientStatsAllClientPeak	                Counter32,
  rsADFarmClientStatsAllClientTotal	                Counter64,
  rsADFarmClientStatsRegularClientCurrent		Counter32,
  rsADFarmClientStatsRegularClientPeak	                Counter32,
  rsADFarmClientStatsRegularClientTotal	                Counter64,
  rsADFarmClientStatsClientNATClientCurrent		Counter32,
  rsADFarmClientStatsClientNATClientPeak	        Counter32,
  rsADFarmClientStatsClientNATClientTotal               Counter64
}

rsADFarmClientStatsFarmIPaddr OBJECT-TYPE
    SYNTAX IpAddress
    ACCESS  read-only
    STATUS  mandatory
    DESCRIPTION
      "The farm IP."
    ::= {rsADFarmClientStatsEntry 1}

rsADFarmClientStatsFarmName OBJECT-TYPE
    SYNTAX DisplayString (SIZE(1..50))
    ACCESS  read-only
    STATUS  mandatory
    DESCRIPTION
      "The farm name."
    ::= {rsADFarmClientStatsEntry 2}

rsADFarmClientStatsAllClientCurrent OBJECT-TYPE
    SYNTAX  Counter32
    ACCESS  read-only
    STATUS  mandatory
    DESCRIPTION
      "Current amount of client entries in the client table"
    ::= {rsADFarmClientStatsEntry 3}

rsADFarmClientStatsAllClientPeak OBJECT-TYPE
    SYNTAX  Counter32
    ACCESS  read-only
    STATUS  mandatory
    DESCRIPTION
      "Peak amount of client entries in the client table"
    ::= {rsADFarmClientStatsEntry 4}

rsADFarmClientStatsAllClientTotal OBJECT-TYPE
    SYNTAX  Counter64
    ACCESS  read-only
    STATUS  mandatory
    DESCRIPTION
      "Total amount of Regular client entries in the client table"
    ::= {rsADFarmClientStatsEntry 5}

rsADFarmClientStatsRegularClientCurrent OBJECT-TYPE
    SYNTAX  Counter32
    ACCESS  read-only
    STATUS  mandatory
    DESCRIPTION
      "Current amount of Regular client entries in the client table"
    ::= {rsADFarmClientStatsEntry 6}

rsADFarmClientStatsRegularClientPeak OBJECT-TYPE
    SYNTAX  Counter32
    ACCESS  read-only
    STATUS  mandatory
    DESCRIPTION
      "Peak amount of Regular client entries in the client table"
    ::= {rsADFarmClientStatsEntry 7}

rsADFarmClientStatsRegularClientTotal OBJECT-TYPE
    SYNTAX  Counter64
    ACCESS  read-only
    STATUS  mandatory
    DESCRIPTION
      "Total amount of Regular client entries in the client table"
    ::= {rsADFarmClientStatsEntry 8}


rsADFarmClientStatsClientNATClientCurrent OBJECT-TYPE
    SYNTAX  Counter32
    ACCESS  read-only
    STATUS  mandatory
    DESCRIPTION
      "Current amount of client NAT entries in the client table"
    ::= {rsADFarmClientStatsEntry 9}

rsADFarmClientStatsClientNATClientPeak OBJECT-TYPE
    SYNTAX  Counter32
    ACCESS  read-only
    STATUS  mandatory
    DESCRIPTION
      "Peak amount of client NAT entries in the client table"
    ::= {rsADFarmClientStatsEntry 10}

rsADFarmClientStatsClientNATClientTotal OBJECT-TYPE
    SYNTAX  Counter64
    ACCESS  read-only
    STATUS  mandatory
    DESCRIPTION
      "Total amount of client NAT entries in the client table"
    ::= {rsADFarmClientStatsEntry 11}


rsADFarmClientStatisticsTable OBJECT-TYPE
    SYNTAX SEQUENCE OF RsADFarmClientStatisticsEntry
    ACCESS not-accessible
    STATUS mandatory
    DESCRIPTION
      "Table containing farm client statistics."
    ::=  {rsNWSDStats 22}

rsADFarmClientStatisticsEntry OBJECT-TYPE
    SYNTAX RsADFarmClientStatisticsEntry
    ACCESS not-accessible
    STATUS  mandatory
    DESCRIPTION
       " The row definition for this table."
   INDEX { rsADFarmClientStatisticsFarmName}
    ::=  {rsADFarmClientStatisticsTable 1}

RsADFarmClientStatisticsEntry ::= SEQUENCE {
  rsADFarmClientStatisticsFarmName			        DisplayString,
  rsADFarmClientStatisticsAllClientCurrent			Counter32,
  rsADFarmClientStatisticsAllClientPeak	                Counter32,
  rsADFarmClientStatisticsAllClientTotal	                Counter64,
  rsADFarmClientStatisticsRegularClientCurrent		Counter32,
  rsADFarmClientStatisticsRegularClientPeak	                Counter32,
  rsADFarmClientStatisticsRegularClientTotal	                Counter64,
  rsADFarmClientStatisticsClientNATClientCurrent		Counter32,
  rsADFarmClientStatisticsClientNATClientPeak	        Counter32,
  rsADFarmClientStatisticsClientNATClientTotal               Counter64
}

rsADFarmClientStatisticsFarmName OBJECT-TYPE
    SYNTAX DisplayString (SIZE(1..50))
    ACCESS  read-only
    STATUS  mandatory
    DESCRIPTION
      "The farm name."
    ::= {rsADFarmClientStatisticsEntry 1}

rsADFarmClientStatisticsAllClientCurrent OBJECT-TYPE
    SYNTAX  Counter32
    ACCESS  read-only
    STATUS  mandatory
    DESCRIPTION
      "Current amount of client entries in the client table"
    ::= {rsADFarmClientStatisticsEntry 2}

rsADFarmClientStatisticsAllClientPeak OBJECT-TYPE
    SYNTAX  Counter32
    ACCESS  read-only
    STATUS  mandatory
    DESCRIPTION
      "Peak amount of client entries in the client table"
    ::= {rsADFarmClientStatisticsEntry 3}

rsADFarmClientStatisticsAllClientTotal OBJECT-TYPE
    SYNTAX  Counter64
    ACCESS  read-only
    STATUS  mandatory
    DESCRIPTION
      "Total amount of Regular client entries in the client table"
    ::= {rsADFarmClientStatisticsEntry 4}

rsADFarmClientStatisticsRegularClientCurrent OBJECT-TYPE
    SYNTAX  Counter32
    ACCESS  read-only
    STATUS  mandatory
    DESCRIPTION
      "Current amount of Regular client entries in the client table"
    ::= {rsADFarmClientStatisticsEntry 5}

rsADFarmClientStatisticsRegularClientPeak OBJECT-TYPE
    SYNTAX  Counter32
    ACCESS  read-only
    STATUS  mandatory
    DESCRIPTION
      "Peak amount of Regular client entries in the client table"
    ::= {rsADFarmClientStatisticsEntry 6}

rsADFarmClientStatisticsRegularClientTotal OBJECT-TYPE
    SYNTAX  Counter64
    ACCESS  read-only
    STATUS  mandatory
    DESCRIPTION
      "Total amount of Regular client entries in the client table"
    ::= {rsADFarmClientStatisticsEntry 7}


rsADFarmClientStatisticsClientNATClientCurrent OBJECT-TYPE
    SYNTAX  Counter32
    ACCESS  read-only
    STATUS  mandatory
    DESCRIPTION
      "Current amount of client NAT entries in the client table"
    ::= {rsADFarmClientStatisticsEntry 8}

rsADFarmClientStatisticsClientNATClientPeak OBJECT-TYPE
    SYNTAX  Counter32
    ACCESS  read-only
    STATUS  mandatory
    DESCRIPTION
      "Peak amount of client NAT entries in the client table"
    ::= {rsADFarmClientStatisticsEntry 9}

rsADFarmClientStatisticsClientNATClientTotal OBJECT-TYPE
    SYNTAX  Counter64
    ACCESS  read-only
    STATUS  mandatory
    DESCRIPTION
      "Total amount of client NAT entries in the client table"
    ::= {rsADFarmClientStatisticsEntry 10}



rsADFarmNetStatsTable OBJECT-TYPE
    SYNTAX SEQUENCE OF RsADFarmNetStatsEntry
    ACCESS not-accessible
    STATUS mandatory
    DESCRIPTION
      "Table containing farm network statistics."
    ::= {rsNWSDStats 10}

rsADFarmNetStatsEntry OBJECT-TYPE
    SYNTAX RsADFarmNetStatsEntry
    ACCESS not-accessible
    STATUS  mandatory
    DESCRIPTION
       " The row definition for this table."
   INDEX { rsADFarmNetStatsFarmIPaddr,
           rsADFarmNetStatsFarmName}
    ::= {rsADFarmNetStatsTable 1}

RsADFarmNetStatsEntry ::= SEQUENCE {
  rsADFarmNetStatsFarmIPaddr                          IpAddress,
  rsADFarmNetStatsFarmName			      DisplayString,
  rsADFarmNetStatsNewTCPConCurrent                    Counter32,
  rsADFarmNetStatsNewTCPConPeak                       Counter32,
  rsADFarmNetStatsNewTCPConTotal                      Counter64,
  rsADFarmNetStatsTCPDisconnectCurrent                Counter32,
  rsADFarmNetStatsTCPDisconnectPeak                   Counter32,
  rsADFarmNetStatsTCPDisconnectTotal                  Counter64,
  rsADFarmNetStatsPacketSendtoCurrent                 Counter32,
  rsADFarmNetStatsPacketSendtoTotal                   Counter64,
  rsADFarmNetStatsPacketReceiveCurrent                Counter32,
  rsADFarmNetStatsPacketReceiveTotal                  Counter64,
  rsADFarmNetStatsKBitSendtoCurrent                   Counter32,
  rsADFarmNetStatsKBitSendtoTotal                     Counter64,
  rsADFarmNetStatsKBitReceiveCurrent                  Counter32,
  rsADFarmNetStatsKBitReceiveTotal                    Counter64
}

rsADFarmNetStatsFarmIPaddr OBJECT-TYPE
    SYNTAX IpAddress
    ACCESS  read-only
    STATUS  mandatory
    DESCRIPTION
      "The farm IP."
    ::= {rsADFarmNetStatsEntry 1}
rsADFarmNetStatsFarmName OBJECT-TYPE
    SYNTAX DisplayString (SIZE(1..50))
    ACCESS  read-only
    STATUS  mandatory
    DESCRIPTION
      "The farm name."
    ::= {rsADFarmNetStatsEntry 2}

rsADFarmNetStatsNewTCPConCurrent OBJECT-TYPE
    SYNTAX  Counter32
    ACCESS  read-only
    STATUS  mandatory
    DESCRIPTION
      "last sec counter of new TCP connections"
    ::= {rsADFarmNetStatsEntry 3}

rsADFarmNetStatsNewTCPConPeak  OBJECT-TYPE
    SYNTAX  Counter32
    ACCESS  read-only
    STATUS  mandatory
    DESCRIPTION
      "peak counter of new TCP connections"
    ::= {rsADFarmNetStatsEntry 4}

rsADFarmNetStatsNewTCPConTotal   OBJECT-TYPE
    SYNTAX  Counter64
    ACCESS  read-only
    STATUS  mandatory
    DESCRIPTION
      "total counter of new TCP connections"
    ::= {rsADFarmNetStatsEntry 5}

rsADFarmNetStatsTCPDisconnectCurrent  OBJECT-TYPE
    SYNTAX  Counter32
    ACCESS  read-only
    STATUS  mandatory
    DESCRIPTION
      "last sec counter TCP disconnections"
    ::= {rsADFarmNetStatsEntry 6}

rsADFarmNetStatsTCPDisconnectPeak  OBJECT-TYPE
    SYNTAX  Counter32
    ACCESS  read-only
    STATUS  mandatory
    DESCRIPTION
      "peak counter of TCP disconnections"
    ::= {rsADFarmNetStatsEntry 7}

rsADFarmNetStatsTCPDisconnectTotal  OBJECT-TYPE
    SYNTAX  Counter64
    ACCESS  read-only
    STATUS  mandatory
    DESCRIPTION
      "total counter of TCP disconnections"
    ::= {rsADFarmNetStatsEntry 8}

rsADFarmNetStatsPacketSendtoCurrent  OBJECT-TYPE
    SYNTAX  Counter32
    ACCESS  read-only
    STATUS  mandatory
    DESCRIPTION
      "last sec amount of packets sendto the farm"
    ::= {rsADFarmNetStatsEntry 9}

rsADFarmNetStatsPacketSendtoTotal   OBJECT-TYPE
    SYNTAX  Counter64
    ACCESS  read-only
    STATUS  mandatory
    DESCRIPTION
      "total amount of packets sendto the farm"
    ::= {rsADFarmNetStatsEntry 10}


rsADFarmNetStatsPacketReceiveCurrent                OBJECT-TYPE
    SYNTAX  Counter32
    ACCESS  read-only
    STATUS  mandatory
    DESCRIPTION
      "last sec amount of packets received from the farm"
    ::= {rsADFarmNetStatsEntry 11}

rsADFarmNetStatsPacketReceiveTotal                  OBJECT-TYPE
    SYNTAX  Counter64
    ACCESS  read-only
    STATUS  mandatory
    DESCRIPTION
      "total amount of packets received from the farm"
    ::= {rsADFarmNetStatsEntry 12}

rsADFarmNetStatsKBitSendtoCurrent                   OBJECT-TYPE
    SYNTAX  Counter32
    ACCESS  read-only
    STATUS  mandatory
    DESCRIPTION
      "last sec amount of bits sendto the farm"
    ::= {rsADFarmNetStatsEntry 13}

rsADFarmNetStatsKBitSendtoTotal                    OBJECT-TYPE
    SYNTAX  Counter64
    ACCESS  read-only
    STATUS  mandatory
    DESCRIPTION
      "total amount of bits sendto the farm"
    ::= {rsADFarmNetStatsEntry 14}

rsADFarmNetStatsKBitReceiveCurrent                  OBJECT-TYPE
    SYNTAX  Counter32
    ACCESS  read-only
    STATUS  mandatory
    DESCRIPTION
      "last sec amount of bits received from the farm"
    ::= {rsADFarmNetStatsEntry 15}

rsADFarmNetStatsKBitReceiveTotal                    OBJECT-TYPE
    SYNTAX  Counter64
    ACCESS  read-only
    STATUS  mandatory
    DESCRIPTION
      "total amount of bits received from the farm"
    ::= {rsADFarmNetStatsEntry 16}


rsADFarmNetStatisticsTable OBJECT-TYPE
    SYNTAX SEQUENCE OF RsADFarmNetStatisticsEntry
    ACCESS not-accessible
    STATUS mandatory
    DESCRIPTION
      "Table containing farm network statistics."
    ::= {rsNWSDStats 23}

rsADFarmNetStatisticsEntry OBJECT-TYPE
    SYNTAX RsADFarmNetStatisticsEntry
    ACCESS not-accessible
    STATUS  mandatory
    DESCRIPTION
       " The row definition for this table."
   INDEX { rsADFarmNetStatisticsFarmName}
    ::= {rsADFarmNetStatisticsTable 1}

RsADFarmNetStatisticsEntry ::= SEQUENCE {

  rsADFarmNetStatisticsFarmName			                   DisplayString,
  rsADFarmNetStatisticsNewTCPConCurrent                    Counter32,
  rsADFarmNetStatisticsNewTCPConPeak                       Counter32,
  rsADFarmNetStatisticsNewTCPConTotal                      Counter64,
  rsADFarmNetStatisticsTCPDisconnectCurrent                Counter32,
  rsADFarmNetStatisticsTCPDisconnectPeak                   Counter32,
  rsADFarmNetStatisticsTCPDisconnectTotal                  Counter64,
  rsADFarmNetStatisticsPacketSendtoCurrent                 Counter32,
  rsADFarmNetStatisticsPacketSendtoTotal                   Counter64,
  rsADFarmNetStatisticsPacketReceiveCurrent                Counter32,
  rsADFarmNetStatisticsPacketReceiveTotal                  Counter64,
  rsADFarmNetStatisticsKBitSendtoCurrent                   Counter32,
  rsADFarmNetStatisticsKBitSendtoTotal                     Counter64,
  rsADFarmNetStatisticsKBitReceiveCurrent                  Counter32,
  rsADFarmNetStatisticsKBitReceiveTotal                    Counter64
}

rsADFarmNetStatisticsFarmName OBJECT-TYPE
    SYNTAX DisplayString (SIZE(1..50))
    ACCESS  read-only
    STATUS  mandatory
    DESCRIPTION
      "The farm name."
    ::= {rsADFarmNetStatisticsEntry 1}

rsADFarmNetStatisticsNewTCPConCurrent OBJECT-TYPE
    SYNTAX  Counter32
    ACCESS  read-only
    STATUS  mandatory
    DESCRIPTION
      "last sec counter of new TCP connections"
    ::= {rsADFarmNetStatisticsEntry 2}

rsADFarmNetStatisticsNewTCPConPeak  OBJECT-TYPE
    SYNTAX  Counter32
    ACCESS  read-only
    STATUS  mandatory
    DESCRIPTION
      "peak counter of new TCP connections"
    ::= {rsADFarmNetStatisticsEntry 3}

rsADFarmNetStatisticsNewTCPConTotal   OBJECT-TYPE
    SYNTAX  Counter64
    ACCESS  read-only
    STATUS  mandatory
    DESCRIPTION
      "total counter of new TCP connections"
    ::= {rsADFarmNetStatisticsEntry 4}

rsADFarmNetStatisticsTCPDisconnectCurrent  OBJECT-TYPE
    SYNTAX  Counter32
    ACCESS  read-only
    STATUS  mandatory
    DESCRIPTION
      "last sec counter TCP disconnections"
    ::= {rsADFarmNetStatisticsEntry 5}

rsADFarmNetStatisticsTCPDisconnectPeak  OBJECT-TYPE
    SYNTAX  Counter32
    ACCESS  read-only
    STATUS  mandatory
    DESCRIPTION
      "peak counter of TCP disconnections"
    ::= {rsADFarmNetStatisticsEntry 6}

rsADFarmNetStatisticsTCPDisconnectTotal  OBJECT-TYPE
    SYNTAX  Counter64
    ACCESS  read-only
    STATUS  mandatory
    DESCRIPTION
      "total counter of TCP disconnections"
    ::= {rsADFarmNetStatisticsEntry 7}

rsADFarmNetStatisticsPacketSendtoCurrent  OBJECT-TYPE
    SYNTAX  Counter32
    ACCESS  read-only
    STATUS  mandatory
    DESCRIPTION
      "last sec amount of packets sendto the farm"
    ::= {rsADFarmNetStatisticsEntry 8}

rsADFarmNetStatisticsPacketSendtoTotal   OBJECT-TYPE
    SYNTAX  Counter64
    ACCESS  read-only
    STATUS  mandatory
    DESCRIPTION
      "total amount of packets sendto the farm"
    ::= {rsADFarmNetStatisticsEntry 9}


rsADFarmNetStatisticsPacketReceiveCurrent                OBJECT-TYPE
    SYNTAX  Counter32
    ACCESS  read-only
    STATUS  mandatory
    DESCRIPTION
      "last sec amount of packets received from the farm"
    ::= {rsADFarmNetStatisticsEntry 10}

rsADFarmNetStatisticsPacketReceiveTotal                  OBJECT-TYPE
    SYNTAX  Counter64
    ACCESS  read-only
    STATUS  mandatory
    DESCRIPTION
      "total amount of packets received from the farm"
    ::= {rsADFarmNetStatisticsEntry 11}

rsADFarmNetStatisticsKBitSendtoCurrent                   OBJECT-TYPE
    SYNTAX  Counter32
    ACCESS  read-only
    STATUS  mandatory
    DESCRIPTION
      "last sec amount of bits sent to the farm"
    ::= {rsADFarmNetStatisticsEntry 12}

rsADFarmNetStatisticsKBitSendtoTotal                    OBJECT-TYPE
    SYNTAX  Counter64
    ACCESS  read-only
    STATUS  mandatory
    DESCRIPTION
      "total amount of bits sent to the farm"
    ::= {rsADFarmNetStatisticsEntry 13}

rsADFarmNetStatisticsKBitReceiveCurrent                  OBJECT-TYPE
    SYNTAX  Counter32
    ACCESS  read-only
    STATUS  mandatory
    DESCRIPTION
      "last sec amount of bits received from the farm"
    ::= {rsADFarmNetStatisticsEntry 14}

rsADFarmNetStatisticsKBitReceiveTotal                    OBJECT-TYPE
    SYNTAX  Counter64
    ACCESS  read-only
    STATUS  mandatory
    DESCRIPTION
      "total amount of bits received from the farm"
    ::= {rsADFarmNetStatisticsEntry 15}



rsADAXFarmStatisticsResetGlobalStatistics OBJECT-TYPE
    SYNTAX  INTEGER {
       reset(1)
     }
    ACCESS  read-write
    STATUS  mandatory
    DESCRIPTION
      "This variable resets all of the AX statistics FE and BE."
   ::= {rsNWSDStats 11 }


rsADAXFarmStatisticsTable OBJECT-TYPE
    SYNTAX SEQUENCE OF RsADAXFarmStatisticsEntry
    ACCESS not-accessible
    STATUS mandatory
    DESCRIPTION
      "Table containing farm statistics taken from AppXcel."
    ::= {rsNWSDStats 12}

rsADAXFarmStatisticsEntry OBJECT-TYPE
    SYNTAX RsADAXFarmStatisticsEntry
    ACCESS not-accessible
    STATUS  mandatory
    DESCRIPTION
       " The row definition for this table."
   INDEX { rsADAXFarmStatisticsFarmName}
    ::= {rsADAXFarmStatisticsTable 1}

RsADAXFarmStatisticsEntry ::= SEQUENCE {
  rsADAXFarmStatisticsFarmName		        	DisplayString,
  rsADAXFarmStatisticsAppConCurrent                     Counter32,
  rsADAxFarmStatisticsAppConPeak                        Counter32,
  rsADAXFarmStatisticsAppConTotal                       Counter64,
  rsADAXFarmStatisticsAppDisConCurrent                  Counter32,
  rsADAxFarmStatisticsAppDisConPeak                     Counter32,
  rsADAXFarmStatisticsAppDisConTotal                    Counter64,
  rsADAXFarmStatisticsAppRequestCurrent                 Counter32,
  rsADAxFarmStatisticsAppRequestPeak                    Counter32,
  rsADAXFarmStatisticsAppRequestTotal                   Counter64,
  rsADAXFarmStatisticsAppFailureCurrent                 Counter32,
  rsADAxFarmStatisticsAppFailurePeak                    Counter32,
  rsADAXFarmStatisticsAppFailureTotal                   Counter64
}

rsADAXFarmStatisticsFarmName OBJECT-TYPE
    SYNTAX DisplayString (SIZE(1..50))
    ACCESS  read-only
    STATUS  mandatory
    DESCRIPTION
      "The farm name."
    ::= {rsADAXFarmStatisticsEntry 1}

rsADAXFarmStatisticsAppConCurrent         OBJECT-TYPE
    SYNTAX  Counter32
    ACCESS  read-only
    STATUS  mandatory
    DESCRIPTION
      "Current amount of application connections last 5 sec, taken from AX"
    ::= {rsADAXFarmStatisticsEntry 2}

rsADAxFarmStatisticsAppConPeak            OBJECT-TYPE
    SYNTAX  Counter32
    ACCESS  read-only
    STATUS  mandatory
    DESCRIPTION
      "Peak amount of application connections, taken from AX"
    ::= {rsADAXFarmStatisticsEntry 3}

rsADAXFarmStatisticsAppConTotal           OBJECT-TYPE
    SYNTAX  Counter64
    ACCESS  read-only
    STATUS  mandatory
    DESCRIPTION
      "Total amount of application connections, taken from AX"
    ::= {rsADAXFarmStatisticsEntry 4}

rsADAXFarmStatisticsAppDisConCurrent                  OBJECT-TYPE
    SYNTAX  Counter32
    ACCESS  read-only
    STATUS  mandatory
    DESCRIPTION
      "Current amount of application disconnections last 5 sec, taken from AX"
    ::= {rsADAXFarmStatisticsEntry 5}

rsADAxFarmStatisticsAppDisConPeak                     OBJECT-TYPE
    SYNTAX  Counter32
    ACCESS  read-only
    STATUS  mandatory
    DESCRIPTION
      "Peak amount of application disconnections, taken from AX"
    ::= {rsADAXFarmStatisticsEntry 6}

rsADAXFarmStatisticsAppDisConTotal                    OBJECT-TYPE
    SYNTAX  Counter64
    ACCESS  read-only
    STATUS  mandatory
    DESCRIPTION
      "Total amount of application disconnections, taken from AX"
    ::= {rsADAXFarmStatisticsEntry 7}

rsADAXFarmStatisticsAppRequestCurrent                 OBJECT-TYPE
    SYNTAX  Counter32
    ACCESS  read-only
    STATUS  mandatory
    DESCRIPTION
      "Current amount of requests last 5 sec, taken from AX"
    ::= {rsADAXFarmStatisticsEntry 8}

rsADAxFarmStatisticsAppRequestPeak                    OBJECT-TYPE
    SYNTAX  Counter32
    ACCESS  read-only
    STATUS  mandatory
    DESCRIPTION
      "Peak amount of requests ,taken from AX"
    ::= {rsADAXFarmStatisticsEntry 9}

rsADAXFarmStatisticsAppRequestTotal                   OBJECT-TYPE
    SYNTAX  Counter64
    ACCESS  read-only
    STATUS  mandatory
    DESCRIPTION
      "Total amount of requests ,taken from AX"
    ::= {rsADAXFarmStatisticsEntry 10}

rsADAXFarmStatisticsAppFailureCurrent                 OBJECT-TYPE
    SYNTAX  Counter32
    ACCESS  read-only
    STATUS  mandatory
    DESCRIPTION
      "Current amount of failure last 5 sec, taken from AX"
    ::= {rsADAXFarmStatisticsEntry 11}

rsADAxFarmStatisticsAppFailurePeak                    OBJECT-TYPE
    SYNTAX  Counter32
    ACCESS  read-only
    STATUS  mandatory
    DESCRIPTION
      "Peak amount of failure ,taken from AX"
    ::= {rsADAXFarmStatisticsEntry 12}

rsADAXFarmStatisticsAppFailureTotal                   OBJECT-TYPE
    SYNTAX  Counter64
    ACCESS  read-only
    STATUS  mandatory
    DESCRIPTION
      "Total amount of failure ,taken from AX"
    ::= {rsADAXFarmStatisticsEntry 13}

rsADServerStatsTableResetGlobalStatistics OBJECT-TYPE
    SYNTAX  INTEGER {
       reset(1)
     }
    ACCESS  read-write
    STATUS  mandatory
    DESCRIPTION
      "This variable resets all of the application server statistics client and network."
   ::= {rsNWSDStats 13 }


rsADServerClientStatsTable OBJECT-TYPE
    SYNTAX SEQUENCE OF RsADServerClientStatsEntry
    ACCESS not-accessible
    STATUS mandatory
    DESCRIPTION
      "Table containing Server client statistics."
    ::= {rsNWSDStats 14}

rsADServerClientStatsEntry OBJECT-TYPE
    SYNTAX RsADServerClientStatsEntry
    ACCESS not-accessible
    STATUS  mandatory
    DESCRIPTION
       " The row definition for this table."
   INDEX { rsADServerClientStatsFarmIPAddr,
           rsADServerClientStatsFarmName,
           rsADServerClientStatsServerAddress,
           rsADServerClientStatsPort}
    ::= {rsADServerClientStatsTable 1}

RsADServerClientStatsEntry ::= SEQUENCE {
  rsADServerClientStatsFarmIPAddr                     IpAddress,
  rsADServerClientStatsFarmName     	                  DisplayString,
  rsADServerClientStatsServerAddress		          IpAddress,
  rsADServerClientStatsPort		  	          INTEGER,
  rsADServerClientStatsAllClientCurrent	        	  Counter32,
  rsADServerClientStatsAllClientPeak	                  Counter32,
  rsADServerClientStatsAllClientTotal	                  Counter64,
  rsADServerClientStatsRegularClientCurrent		  Counter32,
  rsADServerClientStatsRegularClientPeak	          Counter32,
  rsADServerClientStatsRegularClientTotal	          Counter64,
  rsADServerClientStatsClientNATClientCurrent		  Counter32,
  rsADServerClientStatsClientNATClientPeak	          Counter32,
  rsADServerClientStatsClientNATClientTotal               Counter64
}

rsADServerClientStatsFarmIPAddr     OBJECT-TYPE
    SYNTAX  IpAddress
    ACCESS  read-only
    STATUS  mandatory
    DESCRIPTION
      "The farm IP Addr."
    ::= {rsADServerClientStatsEntry 1}
rsADServerClientStatsFarmName     OBJECT-TYPE
    SYNTAX DisplayString (SIZE(1..50))
    ACCESS  read-only
    STATUS  mandatory
    DESCRIPTION
      "The farm name."
    ::= {rsADServerClientStatsEntry 2}

rsADServerClientStatsServerAddress OBJECT-TYPE
    SYNTAX IpAddress
    ACCESS  read-only
    STATUS  mandatory
    DESCRIPTION
      "The server IP address"
    ::= {rsADServerClientStatsEntry 3}

rsADServerClientStatsPort     OBJECT-TYPE
    SYNTAX INTEGER(0..65535)
    ACCESS  read-only
    STATUS  mandatory
    DESCRIPTION
      "The server port."
    ::= {rsADServerClientStatsEntry 4}

rsADServerClientStatsAllClientCurrent OBJECT-TYPE
    SYNTAX  Counter32
    ACCESS  read-only
    STATUS  mandatory
    DESCRIPTION
      "Current amount of client entries in the client table"
    ::= {rsADServerClientStatsEntry 5}

rsADServerClientStatsAllClientPeak OBJECT-TYPE
    SYNTAX  Counter32
    ACCESS  read-only
    STATUS  mandatory
    DESCRIPTION
      "Peak amount of client entries in the client table"
    ::= {rsADServerClientStatsEntry 6}

rsADServerClientStatsAllClientTotal OBJECT-TYPE
    SYNTAX  Counter64
    ACCESS  read-only
    STATUS  mandatory
    DESCRIPTION
      "Total amount of Regular client entries in the client table"
    ::= {rsADServerClientStatsEntry 7}

rsADServerClientStatsRegularClientCurrent OBJECT-TYPE
    SYNTAX  Counter32
    ACCESS  read-only
    STATUS  mandatory
    DESCRIPTION
      "Current amount of Regular client entries in the client table"
    ::= {rsADServerClientStatsEntry 8}

rsADServerClientStatsRegularClientPeak OBJECT-TYPE
    SYNTAX  Counter32
    ACCESS  read-only
    STATUS  mandatory
    DESCRIPTION
      "Peak amount of Regular client entries in the client table"
    ::= {rsADServerClientStatsEntry 9}

rsADServerClientStatsRegularClientTotal OBJECT-TYPE
    SYNTAX  Counter64
    ACCESS  read-only
    STATUS  mandatory
    DESCRIPTION
      "Total amount of Regular client entries in the client table"
    ::= {rsADServerClientStatsEntry  10}

rsADServerClientStatsClientNATClientCurrent OBJECT-TYPE
    SYNTAX  Counter32
    ACCESS  read-only
    STATUS  mandatory
    DESCRIPTION
      "Current amount of client NAT entries in the client table"
    ::= {rsADServerClientStatsEntry  11}

rsADServerClientStatsClientNATClientPeak OBJECT-TYPE
    SYNTAX  Counter32
    ACCESS  read-only
    STATUS  mandatory
    DESCRIPTION
      "Peak amount of client NAT entries in the client table"
    ::= {rsADServerClientStatsEntry  12}

rsADServerClientStatsClientNATClientTotal OBJECT-TYPE
    SYNTAX  Counter64
    ACCESS  read-only
    STATUS  mandatory
    DESCRIPTION
      "Total amount of client NAT entries in the client table"
    ::= {rsADServerClientStatsEntry  13}

rsADServerClientStatisticsTable OBJECT-TYPE
    SYNTAX SEQUENCE OF RsADServerClientStatisticsEntry
    ACCESS not-accessible
    STATUS mandatory
    DESCRIPTION
      "Table containing Server client statistics."
    ::= {rsNWSDStats 24}

rsADServerClientStatisticsEntry OBJECT-TYPE
    SYNTAX RsADServerClientStatisticsEntry
    ACCESS not-accessible
    STATUS  mandatory
    DESCRIPTION
       " The row definition for this table."
   INDEX { rsADServerClientStatisticsFarmName,
           rsADServerClientStatisticsServerAddress,
           rsADServerClientStatisticsPort}
    ::= {rsADServerClientStatisticsTable 1}

RsADServerClientStatisticsEntry ::= SEQUENCE {
  rsADServerClientStatisticsFarmName     	                  DisplayString,
  rsADServerClientStatisticsServerAddress		          IpAddress,
  rsADServerClientStatisticsPort		  	          INTEGER,
  rsADServerClientStatisticsAllClientCurrent	        	  Counter32,
  rsADServerClientStatisticsAllClientPeak	                  Counter32,
  rsADServerClientStatisticsAllClientTotal	                  Counter64,
  rsADServerClientStatisticsRegularClientCurrent		  Counter32,
  rsADServerClientStatisticsRegularClientPeak	          Counter32,
  rsADServerClientStatisticsRegularClientTotal	          Counter64,
  rsADServerClientStatisticsClientNATClientCurrent		  Counter32,
  rsADServerClientStatisticsClientNATClientPeak	          Counter32,
  rsADServerClientStatisticsClientNATClientTotal               Counter64
}

rsADServerClientStatisticsFarmName     OBJECT-TYPE
    SYNTAX DisplayString (SIZE(1..50))
    ACCESS  read-only
    STATUS  mandatory
    DESCRIPTION
      "The farm name."
    ::= {rsADServerClientStatisticsEntry 1}

rsADServerClientStatisticsServerAddress OBJECT-TYPE
    SYNTAX IpAddress
    ACCESS  read-only
    STATUS  mandatory
    DESCRIPTION
      "The server IP address"
    ::= {rsADServerClientStatisticsEntry 2}

rsADServerClientStatisticsPort     OBJECT-TYPE
    SYNTAX INTEGER(0..65535)
    ACCESS  read-only
    STATUS  mandatory
    DESCRIPTION
      "The server port."
    ::= {rsADServerClientStatisticsEntry 3}

rsADServerClientStatisticsAllClientCurrent OBJECT-TYPE
    SYNTAX  Counter32
    ACCESS  read-only
    STATUS  mandatory
    DESCRIPTION
      "Current amount of client entries in the client table"
    ::= {rsADServerClientStatisticsEntry 4}

rsADServerClientStatisticsAllClientPeak OBJECT-TYPE
    SYNTAX  Counter32
    ACCESS  read-only
    STATUS  mandatory
    DESCRIPTION
      "Peak amount of client entries in the client table"
    ::= {rsADServerClientStatisticsEntry 5}

rsADServerClientStatisticsAllClientTotal OBJECT-TYPE
    SYNTAX  Counter64
    ACCESS  read-only
    STATUS  mandatory
    DESCRIPTION
      "Total amount of Regular client entries in the client table"
    ::= {rsADServerClientStatisticsEntry 6}

rsADServerClientStatisticsRegularClientCurrent OBJECT-TYPE
    SYNTAX  Counter32
    ACCESS  read-only
    STATUS  mandatory
    DESCRIPTION
      "Current amount of Regular client entries in the client table"
    ::= {rsADServerClientStatisticsEntry 7}

rsADServerClientStatisticsRegularClientPeak OBJECT-TYPE
    SYNTAX  Counter32
    ACCESS  read-only
    STATUS  mandatory
    DESCRIPTION
      "Peak amount of Regular client entries in the client table"
    ::= {rsADServerClientStatisticsEntry 8}

rsADServerClientStatisticsRegularClientTotal OBJECT-TYPE
    SYNTAX  Counter64
    ACCESS  read-only
    STATUS  mandatory
    DESCRIPTION
      "Total amount of Regular client entries in the client table"
    ::= {rsADServerClientStatisticsEntry  9}

rsADServerClientStatisticsClientNATClientCurrent OBJECT-TYPE
    SYNTAX  Counter32
    ACCESS  read-only
    STATUS  mandatory
    DESCRIPTION
      "Current amount of client NAT entries in the client table"
    ::= {rsADServerClientStatisticsEntry  10}

rsADServerClientStatisticsClientNATClientPeak OBJECT-TYPE
    SYNTAX  Counter32
    ACCESS  read-only
    STATUS  mandatory
    DESCRIPTION
      "Peak amount of client NAT entries in the client table"
    ::= {rsADServerClientStatisticsEntry  11}

rsADServerClientStatisticsClientNATClientTotal OBJECT-TYPE
    SYNTAX  Counter64
    ACCESS  read-only
    STATUS  mandatory
    DESCRIPTION
      "Total amount of client NAT entries in the client table"
    ::= {rsADServerClientStatisticsEntry  12}

rsNADServerClientStatisticsTable OBJECT-TYPE
    SYNTAX SEQUENCE OF RsNADServerClientStatisticsEntry
    ACCESS not-accessible
    STATUS mandatory
    DESCRIPTION
      "Table containing Server client statistics."
    ::= {rsNWSDStats 27}

rsNADServerClientStatisticsEntry OBJECT-TYPE
    SYNTAX RsNADServerClientStatisticsEntry
    ACCESS not-accessible
    STATUS  mandatory
    DESCRIPTION
       " The row definition for this table."
   INDEX { rsNADServerClientStatisticsFarmName,
           rsNADServerClientStatisticsServerName}
    ::= {rsNADServerClientStatisticsTable 1}

RsNADServerClientStatisticsEntry ::= SEQUENCE {
  rsNADServerClientStatisticsFarmName     	            DisplayString,
  rsNADServerClientStatisticsServerName					DisplayString,
  rsNADServerClientStatisticsAllClientCurrent	        Counter32,
  rsNADServerClientStatisticsAllClientPeak	            Counter32,
  rsNADServerClientStatisticsAllClientTotal	            Counter64,
  rsNADServerClientStatisticsRegularClientCurrent		Counter32,
  rsNADServerClientStatisticsRegularClientPeak	        Counter32,
  rsNADServerClientStatisticsRegularClientTotal	        Counter64,
  rsNADServerClientStatisticsClientNATClientCurrent		Counter32,
  rsNADServerClientStatisticsClientNATClientPeak	    Counter32,
  rsNADServerClientStatisticsClientNATClientTotal       Counter64
}

rsNADServerClientStatisticsFarmName     OBJECT-TYPE
    SYNTAX DisplayString (SIZE(1..50))
    ACCESS  read-only
    STATUS  mandatory
    DESCRIPTION
      "The farm name."
    ::= {rsNADServerClientStatisticsEntry 1}

rsNADServerClientStatisticsServerName	OBJECT-TYPE
    SYNTAX  DisplayString (SIZE(1..30))
    ACCESS  read-only
    STATUS  mandatory
    DESCRIPTION
      "The name assigned by the user to the server."
    ::=  {rsNADServerClientStatisticsEntry 2}

rsNADServerClientStatisticsAllClientCurrent OBJECT-TYPE
    SYNTAX  Counter32
    ACCESS  read-only
    STATUS  optional
    DESCRIPTION
      "Current amount of client entries in the client table"
    ::= {rsNADServerClientStatisticsEntry 3}

rsNADServerClientStatisticsAllClientPeak OBJECT-TYPE
    SYNTAX  Counter32
    ACCESS  read-only
    STATUS  optional
    DESCRIPTION
      "Peak amount of client entries in the client table"
    ::= {rsNADServerClientStatisticsEntry 4}

rsNADServerClientStatisticsAllClientTotal OBJECT-TYPE
    SYNTAX  Counter64
    ACCESS  read-only
    STATUS  optional
    DESCRIPTION
      "Total amount of Regular client entries in the client table"
    ::= {rsNADServerClientStatisticsEntry 5}

rsNADServerClientStatisticsRegularClientCurrent OBJECT-TYPE
    SYNTAX  Counter32
    ACCESS  read-only
    STATUS  optional
    DESCRIPTION
      "Current amount of Regular client entries in the client table"
    ::= {rsNADServerClientStatisticsEntry 6}

rsNADServerClientStatisticsRegularClientPeak OBJECT-TYPE
    SYNTAX  Counter32
    ACCESS  read-only
    STATUS  optional
    DESCRIPTION
      "Peak amount of Regular client entries in the client table"
    ::= {rsNADServerClientStatisticsEntry 7}

rsNADServerClientStatisticsRegularClientTotal OBJECT-TYPE
    SYNTAX  Counter64
    ACCESS  read-only
    STATUS  optional
    DESCRIPTION
      "Total amount of Regular client entries in the client table"
    ::= {rsNADServerClientStatisticsEntry  8}

rsNADServerClientStatisticsClientNATClientCurrent OBJECT-TYPE
    SYNTAX  Counter32
    ACCESS  read-only
    STATUS  optional
    DESCRIPTION
      "Current amount of client NAT entries in the client table"
    ::= {rsNADServerClientStatisticsEntry  9}

rsNADServerClientStatisticsClientNATClientPeak OBJECT-TYPE
    SYNTAX  Counter32
    ACCESS  read-only
    STATUS  optional
    DESCRIPTION
      "Peak amount of client NAT entries in the client table"
    ::= {rsNADServerClientStatisticsEntry  10}

rsNADServerClientStatisticsClientNATClientTotal OBJECT-TYPE
    SYNTAX  Counter64
    ACCESS  read-only
    STATUS  optional
    DESCRIPTION
      "Total amount of client NAT entries in the client table"
    ::= {rsNADServerClientStatisticsEntry  11}


rsADPhyServeStatisticsResetGlobalStatistics OBJECT-TYPE
    SYNTAX  INTEGER {
       reset(1)
     }
    ACCESS  read-write
    STATUS  mandatory
    DESCRIPTION
      "This variable resets all physical server statistics related to outbound and server NAT traffic."
   ::= {rsNWSDStats 15 }


rsADPhyServerClientStatsTable OBJECT-TYPE
    SYNTAX SEQUENCE OF RsADPhyServerClientStatsEntry
    ACCESS not-accessible
    STATUS mandatory
    DESCRIPTION
      "Table containing Physical Server client statistics."
    ::= {rsNWSDStats 16}

rsADPhyServerClientStatsEntry OBJECT-TYPE
    SYNTAX RsADPhyServerClientStatsEntry
    ACCESS not-accessible
    STATUS  mandatory
    DESCRIPTION
       " The row definition for this table."
   INDEX { rsADPhyServerClientStatsSrvrName}
    ::= {rsADPhyServerClientStatsTable 1}

RsADPhyServerClientStatsEntry ::= SEQUENCE {
  rsADPhyServerClientStatsSrvrName                        DisplayString,
  rsADPhyServerClientStatsCurrent		  	  Counter32,
  rsADPhyServerClientStatsPeak	                          Counter32,
  rsADPhyServerClientStatsTotal	                          Counter64,
  rsADPhyServerClientStatsServerNATClientCurrent	  Counter32,
  rsADPhyServerClientStatsServerNATClientPeak	          Counter32,
  rsADPhyServerClientStatsServerNATClientTotal            Counter64,
  rsADPhyServerClientStatsOutboundNATClientCurrent   	  Counter32,
  rsADPhyServerClientStatsOutboundNATClientPeak           Counter32,
  rsADPhyServerClientStatsOutboundNATClientTotal          Counter64
}

rsADPhyServerClientStatsSrvrName     OBJECT-TYPE
    SYNTAX DisplayString (SIZE(1..50))
    ACCESS  read-only
    STATUS  mandatory
    DESCRIPTION
      "The physical server name."
    ::= {rsADPhyServerClientStatsEntry 1}

rsADPhyServerClientStatsCurrent OBJECT-TYPE
    SYNTAX  Counter32
    ACCESS  read-only
    STATUS  mandatory
    DESCRIPTION
      "Current amount of serverNAT entries in the client table"
    ::= {rsADPhyServerClientStatsEntry  2}

rsADPhyServerClientStatsPeak OBJECT-TYPE
    SYNTAX  Counter32
    ACCESS  read-only
    STATUS  mandatory
    DESCRIPTION
      "Peak amount of serverNAT entries in the client table"
    ::= {rsADPhyServerClientStatsEntry  3}

rsADPhyServerClientStatsTotal  OBJECT-TYPE
    SYNTAX  Counter64
    ACCESS  read-only
    STATUS  mandatory
    DESCRIPTION
      "Total amount of serverNAT entries in the client table"
    ::= {rsADPhyServerClientStatsEntry  4}

rsADPhyServerClientStatsServerNATClientCurrent OBJECT-TYPE
    SYNTAX  Counter32
    ACCESS  read-only
    STATUS  mandatory
    DESCRIPTION
      "Current amount of serverNAT entries in the client table"
    ::= {rsADPhyServerClientStatsEntry  5}

rsADPhyServerClientStatsServerNATClientPeak OBJECT-TYPE
    SYNTAX  Counter32
    ACCESS  read-only
    STATUS  mandatory
    DESCRIPTION
      "Peak amount of serverNAT entries in the client table"
    ::= {rsADPhyServerClientStatsEntry  6}

rsADPhyServerClientStatsServerNATClientTotal  OBJECT-TYPE
    SYNTAX  Counter64
    ACCESS  read-only
    STATUS  mandatory
    DESCRIPTION
      "Total amount of serverNAT entries in the client table"
    ::= {rsADPhyServerClientStatsEntry  7}

rsADPhyServerClientStatsOutboundNATClientCurrent OBJECT-TYPE
    SYNTAX  Counter32
    ACCESS  read-only
    STATUS  mandatory
    DESCRIPTION
      "Current amount of Outbound NAT entries in the client table"
    ::= {rsADPhyServerClientStatsEntry  8}

rsADPhyServerClientStatsOutboundNATClientPeak  OBJECT-TYPE
    SYNTAX  Counter32
    ACCESS  read-only
    STATUS  mandatory
    DESCRIPTION
      "Peak amount of Outbound NAT entries in the client table"
    ::= {rsADPhyServerClientStatsEntry  9}

rsADPhyServerClientStatsOutboundNATClientTotal  OBJECT-TYPE
    SYNTAX  Counter64
    ACCESS  read-only
    STATUS  mandatory
    DESCRIPTION
      "Total amount of Outbound NAT entries in the client table"
    ::= {rsADPhyServerClientStatsEntry  10}

rsADPhyServerNetStatsTable OBJECT-TYPE
    SYNTAX SEQUENCE OF RsADPhyServerNetStatsTable
    ACCESS not-accessible
    STATUS mandatory
    DESCRIPTION
      "Table containing Physical Server client statistics."
    ::= {rsNWSDStats 17}

rsADPhyServerNetStatsEntry OBJECT-TYPE
    SYNTAX RsADPhyServerNetStatsTable
    ACCESS not-accessible
    STATUS  mandatory
    DESCRIPTION
       " The row definition for this table."
   INDEX { rsADPhyServerNetStatsSrvrName}
    ::= {rsADPhyServerNetStatsTable 1}


RsADPhyServerNetStatsTable ::= SEQUENCE {
  rsADPhyServerNetStatsSrvrName     	             DisplayString,
  rsADPhyServerNetStatsNewTCPConCurrent                 Counter32,
  rsADPhyServerNetStatsNewTCPConPeak                    Counter32,
  rsADPhyServerNetStatsNewTCPConTotal                   Counter64,
  rsADPhyServerNetStatsTCPDisconnectCurrent             Counter32,
  rsADPhyServerNetStatsTCPDisconnectPeak                Counter32,
  rsADPhyServerNetStatsTCPDisconnectTotal               Counter64,
  rsADPhyServerNetStatsPacketSendtoCurrent              Counter32,
  rsADPhyServerNetStatsPacketSendtoTotal                Counter64,
  rsADPhyServerNetStatsPacketReceiveCurrent             Counter32,
  rsADPhyServerNetStatsPacketReceiveTotal               Counter64,
  rsADPhyServerNetStatsKBitSendtoCurrent                Counter32,
  rsADPhyServerNetStatsKBitSendtoTotal                  Counter64,
  rsADPhyServerNetStatsKBitReceiveCurrent               Counter32,
  rsADPhyServerNetStatsKBitReceiveTotal                 Counter64
}

rsADPhyServerNetStatsSrvrName     OBJECT-TYPE
    SYNTAX DisplayString (SIZE(1..50))
    ACCESS  read-only
    STATUS  mandatory
    DESCRIPTION
      "The physical server name."
    ::= {rsADPhyServerNetStatsEntry 1}


rsADPhyServerNetStatsNewTCPConCurrent OBJECT-TYPE
    SYNTAX  Counter32
    ACCESS  read-only
    STATUS  mandatory
    DESCRIPTION
      "last sec counter of new TCP connections"
    ::= {rsADPhyServerNetStatsEntry  2}

rsADPhyServerNetStatsNewTCPConPeak  OBJECT-TYPE
    SYNTAX  Counter32
    ACCESS  read-only
    STATUS  mandatory
    DESCRIPTION
      "peak counter of new TCP connections"
    ::= {rsADPhyServerNetStatsEntry  3}

rsADPhyServerNetStatsNewTCPConTotal   OBJECT-TYPE
    SYNTAX  Counter64
    ACCESS  read-only
    STATUS  mandatory
    DESCRIPTION
      "total counter of new TCP connections"
    ::= {rsADPhyServerNetStatsEntry  4}

rsADPhyServerNetStatsTCPDisconnectCurrent  OBJECT-TYPE
    SYNTAX  Counter32
    ACCESS  read-only
    STATUS  mandatory
    DESCRIPTION
      "last sec counter TCP disconnections"
    ::= {rsADPhyServerNetStatsEntry  5}

rsADPhyServerNetStatsTCPDisconnectPeak  OBJECT-TYPE
    SYNTAX  Counter32
    ACCESS  read-only
    STATUS  mandatory
    DESCRIPTION
      "peak counter of TCP disconnections"
    ::= {rsADPhyServerNetStatsEntry  6}

rsADPhyServerNetStatsTCPDisconnectTotal  OBJECT-TYPE
    SYNTAX  Counter64
    ACCESS  read-only
    STATUS  mandatory
    DESCRIPTION
      "total counter of TCP disconnections"
    ::= {rsADPhyServerNetStatsEntry  7}

rsADPhyServerNetStatsPacketSendtoCurrent  OBJECT-TYPE
    SYNTAX  Counter32
    ACCESS  read-only
    STATUS  mandatory
    DESCRIPTION
      "last sec amount of packets sendto the server"
    ::= {rsADPhyServerNetStatsEntry  8}

rsADPhyServerNetStatsPacketSendtoTotal   OBJECT-TYPE
    SYNTAX  Counter64
    ACCESS  read-only
    STATUS  mandatory
    DESCRIPTION
      "total amount of packets sendto the server"
    ::= {rsADPhyServerNetStatsEntry  9}

rsADPhyServerNetStatsPacketReceiveCurrent                OBJECT-TYPE
    SYNTAX  Counter32
    ACCESS  read-only
    STATUS  mandatory
    DESCRIPTION
      "last sec amount of packets received from the server"
    ::= {rsADPhyServerNetStatsEntry  10}

rsADPhyServerNetStatsPacketReceiveTotal                  OBJECT-TYPE
    SYNTAX  Counter64
    ACCESS  read-only
    STATUS  mandatory
    DESCRIPTION
      "total amount of packets received from the server"
    ::= {rsADPhyServerNetStatsEntry  11}

rsADPhyServerNetStatsKBitSendtoCurrent                   OBJECT-TYPE
    SYNTAX  Counter32
    ACCESS  read-only
    STATUS  mandatory
    DESCRIPTION
      "last sec amount of bits sendto the server"
    ::= {rsADPhyServerNetStatsEntry  12}

rsADPhyServerNetStatsKBitSendtoTotal                    OBJECT-TYPE
    SYNTAX  Counter64
    ACCESS  read-only
    STATUS  mandatory
    DESCRIPTION
      "total amount of bits sendto the server"
    ::= {rsADPhyServerNetStatsEntry  13}

rsADPhyServerNetStatsKBitReceiveCurrent                  OBJECT-TYPE
    SYNTAX  Counter32
    ACCESS  read-only
    STATUS  mandatory
    DESCRIPTION
      "last sec amount of bits received from the server"
    ::= {rsADPhyServerNetStatsEntry  14}

rsADPhyServerNetStatsKBitReceiveTotal                    OBJECT-TYPE
    SYNTAX  Counter64
    ACCESS  read-only
    STATUS  mandatory
    DESCRIPTION
      "total amount of bits received from the server"
    ::= {rsADPhyServerNetStatsEntry  15}




rsADServerNetStatsTable OBJECT-TYPE
    SYNTAX SEQUENCE OF RsADServerNetStatsEntry
    ACCESS not-accessible
    STATUS mandatory
    DESCRIPTION
      "Table containing Server network statistics."
    ::= {rsNWSDStats 18}

rsADServerNetStatsEntry OBJECT-TYPE
    SYNTAX RsADServerNetStatsEntry
    ACCESS not-accessible
    STATUS  mandatory
    DESCRIPTION
       " The row definition for this table."
   INDEX { rsADServerNetStatsFarmIPAddr ,
           rsADServerNetStatsFarmName,
           rsADServerNetStatsServerAddress,
           rsADServerNetStatsPort}
    ::= {rsADServerNetStatsTable 1}

RsADServerNetStatsEntry ::= SEQUENCE {
  rsADServerNetStatsFarmIPAddr                       IpAddress,
  rsADServerNetStatsFarmName     	             DisplayString,
  rsADServerNetStatsServerAddress		     IpAddress,
  rsADServerNetStatsPort		  	     INTEGER,
  rsADServerNetStatsNewTCPConCurrent                 Counter32,
  rsADServerNetStatsNewTCPConPeak                    Counter32,
  rsADServerNetStatsNewTCPConTotal                   Counter64,
  rsADServerNetStatsTCPDisconnectCurrent             Counter32,
  rsADServerNetStatsTCPDisconnectPeak                Counter32,
  rsADServerNetStatsTCPDisconnectTotal               Counter64,
  rsADServerNetStatsPacketSendtoCurrent              Counter32,
  rsADServerNetStatsPacketSendtoTotal                Counter64,
  rsADServerNetStatsPacketReceiveCurrent             Counter32,
  rsADServerNetStatsPacketReceiveTotal               Counter64,
  rsADServerNetStatsKBitSendtoCurrent                Counter32,
  rsADServerNetStatsKBitSendtoTotal                  Counter64,
  rsADServerNetStatsKBitReceiveCurrent               Counter32,
  rsADServerNetStatsKBitReceiveTotal                 Counter64
}

rsADServerNetStatsFarmIPAddr     OBJECT-TYPE
    SYNTAX IpAddress
    ACCESS  read-only
    STATUS  mandatory
    DESCRIPTION
      "The farm IP Addr."
    ::= {rsADServerNetStatsEntry 1}
rsADServerNetStatsFarmName     OBJECT-TYPE
    SYNTAX DisplayString (SIZE(1..50))
    ACCESS  read-only
    STATUS  mandatory
    DESCRIPTION
      "The farm name."
    ::= {rsADServerNetStatsEntry 2}

rsADServerNetStatsServerAddress OBJECT-TYPE
    SYNTAX IpAddress
    ACCESS  read-only
    STATUS  mandatory
    DESCRIPTION
      "The server IP address"
    ::= {rsADServerNetStatsEntry 3}

rsADServerNetStatsPort     OBJECT-TYPE
    SYNTAX INTEGER(0..65535)
    ACCESS  read-only
    STATUS  mandatory
    DESCRIPTION
      "The server port."
    ::= {rsADServerNetStatsEntry 4}

rsADServerNetStatsNewTCPConCurrent OBJECT-TYPE
    SYNTAX  Counter32
    ACCESS  read-only
    STATUS  mandatory
    DESCRIPTION
      "last sec counter of new TCP connections"
    ::= {rsADServerNetStatsEntry  5}

rsADServerNetStatsNewTCPConPeak  OBJECT-TYPE
    SYNTAX  Counter32
    ACCESS  read-only
    STATUS  mandatory
    DESCRIPTION
      "peak counter of new TCP connections"
    ::= {rsADServerNetStatsEntry  6}

rsADServerNetStatsNewTCPConTotal   OBJECT-TYPE
    SYNTAX  Counter64
    ACCESS  read-only
    STATUS  mandatory
    DESCRIPTION
      "total counter of new TCP connections"
    ::= {rsADServerNetStatsEntry  7}

rsADServerNetStatsTCPDisconnectCurrent  OBJECT-TYPE
    SYNTAX  Counter32
    ACCESS  read-only
    STATUS  mandatory
    DESCRIPTION
      "last sec counter TCP disconnections"
    ::= {rsADServerNetStatsEntry  8}

rsADServerNetStatsTCPDisconnectPeak  OBJECT-TYPE
    SYNTAX  Counter32
    ACCESS  read-only
    STATUS  mandatory
    DESCRIPTION
      "peak counter of TCP disconnections"
    ::= {rsADServerNetStatsEntry  9}

rsADServerNetStatsTCPDisconnectTotal  OBJECT-TYPE
    SYNTAX  Counter64
    ACCESS  read-only
    STATUS  mandatory
    DESCRIPTION
      "total counter of TCP disconnections"
    ::= {rsADServerNetStatsEntry  10}

rsADServerNetStatsPacketSendtoCurrent  OBJECT-TYPE
    SYNTAX  Counter32
    ACCESS  read-only
    STATUS  mandatory
    DESCRIPTION
      "last sec amount of packets sendto the server"
    ::= {rsADServerNetStatsEntry  11}

rsADServerNetStatsPacketSendtoTotal   OBJECT-TYPE
    SYNTAX  Counter64
    ACCESS  read-only
    STATUS  mandatory
    DESCRIPTION
      "total amount of packets sendto the server"
    ::= {rsADServerNetStatsEntry  12}

rsADServerNetStatsPacketReceiveCurrent                OBJECT-TYPE
    SYNTAX  Counter32
    ACCESS  read-only
    STATUS  mandatory
    DESCRIPTION
      "last sec amount of packets received from the server"
    ::= {rsADServerNetStatsEntry  13}

rsADServerNetStatsPacketReceiveTotal                  OBJECT-TYPE
    SYNTAX  Counter64
    ACCESS  read-only
    STATUS  mandatory
    DESCRIPTION
      "total amount of packets received from the server"
    ::= {rsADServerNetStatsEntry  14}

rsADServerNetStatsKBitSendtoCurrent                   OBJECT-TYPE
    SYNTAX  Counter32
    ACCESS  read-only
    STATUS  mandatory
    DESCRIPTION
      "last sec amount of bits sendto the server"
    ::= {rsADServerNetStatsEntry  15}

rsADServerNetStatsKBitSendtoTotal                    OBJECT-TYPE
    SYNTAX  Counter64
    ACCESS  read-only
    STATUS  mandatory
    DESCRIPTION
      "total amount of bits sendto the server"
    ::= {rsADServerNetStatsEntry  16}

rsADServerNetStatsKBitReceiveCurrent                  OBJECT-TYPE
    SYNTAX  Counter32
    ACCESS  read-only
    STATUS  mandatory
    DESCRIPTION
      "last sec amount of bits received from the server"
    ::= {rsADServerNetStatsEntry  17}

rsADServerNetStatsKBitReceiveTotal                    OBJECT-TYPE
    SYNTAX  Counter64
    ACCESS  read-only
    STATUS  mandatory
    DESCRIPTION
      "total amount of bits received from the server"
    ::= {rsADServerNetStatsEntry  18}

rsADServerNetStatisticsTable OBJECT-TYPE
    SYNTAX SEQUENCE OF RsADServerNetStatisticsEntry
    ACCESS not-accessible
    STATUS mandatory
    DESCRIPTION
      "Table containing Server network statistics."
    ::= {rsNWSDStats 25}

rsADServerNetStatisticsEntry OBJECT-TYPE
    SYNTAX RsADServerNetStatisticsEntry
    ACCESS not-accessible
    STATUS  mandatory
    DESCRIPTION
       " The row definition for this table."
   INDEX { rsADServerNetStatisticsFarmName,
           rsADServerNetStatisticsServerAddress,
           rsADServerNetStatisticsPort}
    ::= {rsADServerNetStatisticsTable 1}

RsADServerNetStatisticsEntry ::= SEQUENCE {
  rsADServerNetStatisticsFarmName     	             DisplayString,
  rsADServerNetStatisticsServerAddress		     IpAddress,
  rsADServerNetStatisticsPort		  	     INTEGER,
  rsADServerNetStatisticsNewTCPConCurrent                 Counter32,
  rsADServerNetStatisticsNewTCPConPeak                    Counter32,
  rsADServerNetStatisticsNewTCPConTotal                   Counter64,
  rsADServerNetStatisticsTCPDisconnectCurrent             Counter32,
  rsADServerNetStatisticsTCPDisconnectPeak                Counter32,
  rsADServerNetStatisticsTCPDisconnectTotal               Counter64,
  rsADServerNetStatisticsPacketSendtoCurrent              Counter32,
  rsADServerNetStatisticsPacketSendtoTotal                Counter64,
  rsADServerNetStatisticsPacketReceiveCurrent             Counter32,
  rsADServerNetStatisticsPacketReceiveTotal               Counter64,
  rsADServerNetStatisticsKBitSendtoCurrent                Counter32,
  rsADServerNetStatisticsKBitSendtoTotal                  Counter64,
  rsADServerNetStatisticsKBitReceiveCurrent               Counter32,
  rsADServerNetStatisticsKBitReceiveTotal                 Counter64
}

rsADServerNetStatisticsFarmName     OBJECT-TYPE
    SYNTAX DisplayString (SIZE(1..50))
    ACCESS  read-only
    STATUS  mandatory
    DESCRIPTION
      "The farm name."
    ::= {rsADServerNetStatisticsEntry 1}

rsADServerNetStatisticsServerAddress OBJECT-TYPE
    SYNTAX IpAddress
    ACCESS  read-only
    STATUS  mandatory
    DESCRIPTION
      "The server IP address"
    ::= {rsADServerNetStatisticsEntry 2}

rsADServerNetStatisticsPort     OBJECT-TYPE
    SYNTAX INTEGER(0..65535)
    ACCESS  read-only
    STATUS  mandatory
    DESCRIPTION
      "The server port."
    ::= {rsADServerNetStatisticsEntry 3}

rsADServerNetStatisticsNewTCPConCurrent OBJECT-TYPE
    SYNTAX  Counter32
    ACCESS  read-only
    STATUS  mandatory
    DESCRIPTION
      "last sec counter of new TCP connections"
    ::= {rsADServerNetStatisticsEntry  4}

rsADServerNetStatisticsNewTCPConPeak  OBJECT-TYPE
    SYNTAX  Counter32
    ACCESS  read-only
    STATUS  mandatory
    DESCRIPTION
      "peak counter of new TCP connections"
    ::= {rsADServerNetStatisticsEntry  5}

rsADServerNetStatisticsNewTCPConTotal   OBJECT-TYPE
    SYNTAX  Counter64
    ACCESS  read-only
    STATUS  mandatory
    DESCRIPTION
      "total counter of new TCP connections"
    ::= {rsADServerNetStatisticsEntry  6}

rsADServerNetStatisticsTCPDisconnectCurrent  OBJECT-TYPE
    SYNTAX  Counter32
    ACCESS  read-only
    STATUS  mandatory
    DESCRIPTION
      "last sec counter TCP disconnections"
    ::= {rsADServerNetStatisticsEntry  7}

rsADServerNetStatisticsTCPDisconnectPeak  OBJECT-TYPE
    SYNTAX  Counter32
    ACCESS  read-only
    STATUS  mandatory
    DESCRIPTION
      "peak counter of TCP disconnections"
    ::= {rsADServerNetStatisticsEntry  8}

rsADServerNetStatisticsTCPDisconnectTotal  OBJECT-TYPE
    SYNTAX  Counter64
    ACCESS  read-only
    STATUS  mandatory
    DESCRIPTION
      "total counter of TCP disconnections"
    ::= {rsADServerNetStatisticsEntry  9}

rsADServerNetStatisticsPacketSendtoCurrent  OBJECT-TYPE
    SYNTAX  Counter32
    ACCESS  read-only
    STATUS  mandatory
    DESCRIPTION
      "last sec amount of packets sendto the server"
    ::= {rsADServerNetStatisticsEntry  10}

rsADServerNetStatisticsPacketSendtoTotal   OBJECT-TYPE
    SYNTAX  Counter64
    ACCESS  read-only
    STATUS  mandatory
    DESCRIPTION
      "total amount of packets sendto the server"
    ::= {rsADServerNetStatisticsEntry  11}

rsADServerNetStatisticsPacketReceiveCurrent                OBJECT-TYPE
    SYNTAX  Counter32
    ACCESS  read-only
    STATUS  mandatory
    DESCRIPTION
      "last sec amount of packets received from the server"
    ::= {rsADServerNetStatisticsEntry  12}

rsADServerNetStatisticsPacketReceiveTotal                  OBJECT-TYPE
    SYNTAX  Counter64
    ACCESS  read-only
    STATUS  mandatory
    DESCRIPTION
      "total amount of packets received from the server"
    ::= {rsADServerNetStatisticsEntry  13}

rsADServerNetStatisticsKBitSendtoCurrent                   OBJECT-TYPE
    SYNTAX  Counter32
    ACCESS  read-only
    STATUS  mandatory
    DESCRIPTION
      "last sec amount of bits sendto the server"
    ::= {rsADServerNetStatisticsEntry  14}

rsADServerNetStatisticsKBitSendtoTotal                    OBJECT-TYPE
    SYNTAX  Counter64
    ACCESS  read-only
    STATUS  mandatory
    DESCRIPTION
      "total amount of bits sendto the server"
    ::= {rsADServerNetStatisticsEntry  15}

rsADServerNetStatisticsKBitReceiveCurrent                  OBJECT-TYPE
    SYNTAX  Counter32
    ACCESS  read-only
    STATUS  mandatory
    DESCRIPTION
      "last sec amount of bits received from the server"
    ::= {rsADServerNetStatisticsEntry  16}

rsADServerNetStatisticsKBitReceiveTotal                    OBJECT-TYPE
    SYNTAX  Counter64
    ACCESS  read-only
    STATUS  mandatory
    DESCRIPTION
      "total amount of bits received from the server"
    ::= {rsADServerNetStatisticsEntry  17}


rsNADServerNetStatisticsTable OBJECT-TYPE
    SYNTAX SEQUENCE OF RsNADServerNetStatisticsEntry
    ACCESS not-accessible
    STATUS mandatory
    DESCRIPTION
      "Table containing Server network statistics."
    ::= {rsNWSDStats 31}

rsNADServerNetStatisticsEntry OBJECT-TYPE
    SYNTAX RsNADServerNetStatisticsEntry
    ACCESS not-accessible
    STATUS  mandatory
    DESCRIPTION
       " The row definition for this table."
   INDEX { rsNADServerNetStatisticsFarmName,
           rsNADServerNetStatisticsServerName}
    ::= {rsNADServerNetStatisticsTable 1}

RsNADServerNetStatisticsEntry ::= SEQUENCE {
  rsNADServerNetStatisticsFarmName     	             DisplayString,
  rsNADServerNetStatisticsServerName				 DisplayString,
  rsNADServerNetStatisticsNewTCPConCurrent           Counter32,
  rsNADServerNetStatisticsNewTCPConPeak              Counter32,
  rsNADServerNetStatisticsNewTCPConTotal             Counter64,
  rsNADServerNetStatisticsTCPDisconnectCurrent       Counter32,
  rsNADServerNetStatisticsTCPDisconnectPeak          Counter32,
  rsNADServerNetStatisticsTCPDisconnectTotal         Counter64,
  rsNADServerNetStatisticsPacketSendtoCurrent        Counter32,
  rsNADServerNetStatisticsPacketSendtoTotal          Counter64,
  rsNADServerNetStatisticsPacketReceiveCurrent       Counter32,
  rsNADServerNetStatisticsPacketReceiveTotal         Counter64,
  rsNADServerNetStatisticsKBitSendtoCurrent          Counter32,
  rsNADServerNetStatisticsKBitSendtoTotal            Counter64,
  rsNADServerNetStatisticsKBitReceiveCurrent         Counter32,
  rsNADServerNetStatisticsKBitReceiveTotal           Counter64
}

rsNADServerNetStatisticsFarmName     OBJECT-TYPE
    SYNTAX DisplayString (SIZE(1..50))
    ACCESS  read-only
    STATUS  mandatory
    DESCRIPTION
      "The farm name."
    ::= {rsNADServerNetStatisticsEntry 1}

rsNADServerNetStatisticsServerName  OBJECT-TYPE
    SYNTAX  DisplayString (SIZE(1..30))
    ACCESS  read-only
    STATUS  mandatory
    DESCRIPTION
      "The name assigned by the user to the server."
    ::=  {rsNADServerNetStatisticsEntry 2}

rsNADServerNetStatisticsNewTCPConCurrent OBJECT-TYPE
    SYNTAX  Counter32
    ACCESS  read-only
    STATUS  optional
    DESCRIPTION
      "last sec counter of new TCP connections"
    ::= {rsNADServerNetStatisticsEntry  3}

rsNADServerNetStatisticsNewTCPConPeak  OBJECT-TYPE
    SYNTAX  Counter32
    ACCESS  read-only
    STATUS  optional
    DESCRIPTION
      "peak counter of new TCP connections"
    ::= {rsNADServerNetStatisticsEntry 4}

rsNADServerNetStatisticsNewTCPConTotal   OBJECT-TYPE
    SYNTAX  Counter64
    ACCESS  read-only
    STATUS  optional
    DESCRIPTION
      "total counter of new TCP connections"
    ::= {rsNADServerNetStatisticsEntry  5}

rsNADServerNetStatisticsTCPDisconnectCurrent  OBJECT-TYPE
    SYNTAX  Counter32
    ACCESS  read-only
    STATUS  optional
    DESCRIPTION
      "last sec counter TCP disconnections"
    ::= {rsNADServerNetStatisticsEntry  6}

rsNADServerNetStatisticsTCPDisconnectPeak  OBJECT-TYPE
    SYNTAX  Counter32
    ACCESS  read-only
    STATUS  optional
    DESCRIPTION
      "peak counter of TCP disconnections"
    ::= {rsNADServerNetStatisticsEntry  7}

rsNADServerNetStatisticsTCPDisconnectTotal  OBJECT-TYPE
    SYNTAX  Counter64
    ACCESS  read-only
    STATUS  optional
    DESCRIPTION
      "total counter of TCP disconnections"
    ::= {rsNADServerNetStatisticsEntry 8}

rsNADServerNetStatisticsPacketSendtoCurrent  OBJECT-TYPE
    SYNTAX  Counter32
    ACCESS  read-only
    STATUS  optional
    DESCRIPTION
      "last sec amount of packets sendto the server"
    ::= {rsNADServerNetStatisticsEntry  9}

rsNADServerNetStatisticsPacketSendtoTotal   OBJECT-TYPE
    SYNTAX  Counter64
    ACCESS  read-only
    STATUS  optional
    DESCRIPTION
      "total amount of packets sendto the server"
    ::= {rsNADServerNetStatisticsEntry  10}

rsNADServerNetStatisticsPacketReceiveCurrent                OBJECT-TYPE
    SYNTAX  Counter32
    ACCESS  read-only
    STATUS  optional
    DESCRIPTION
      "last sec amount of packets received from the server"
    ::= {rsNADServerNetStatisticsEntry  11}

rsNADServerNetStatisticsPacketReceiveTotal                  OBJECT-TYPE
    SYNTAX  Counter64
    ACCESS  read-only
    STATUS  optional
    DESCRIPTION
      "total amount of packets received from the server"
    ::= {rsNADServerNetStatisticsEntry  12}

rsNADServerNetStatisticsKBitSendtoCurrent                   OBJECT-TYPE
    SYNTAX  Counter32
    ACCESS  read-only
    STATUS  optional
    DESCRIPTION
      "last sec amount of bits sendto the server"
    ::= {rsNADServerNetStatisticsEntry  13}

rsNADServerNetStatisticsKBitSendtoTotal                    OBJECT-TYPE
    SYNTAX  Counter64
    ACCESS  read-only
    STATUS  optional
    DESCRIPTION
      "total amount of bits sendto the server"
    ::= {rsNADServerNetStatisticsEntry  14}

rsNADServerNetStatisticsKBitReceiveCurrent                  OBJECT-TYPE
    SYNTAX  Counter32
    ACCESS  read-only
    STATUS  optional
    DESCRIPTION
      "last sec amount of bits received from the server"
    ::= {rsNADServerNetStatisticsEntry  15}

rsNADServerNetStatisticsKBitReceiveTotal                    OBJECT-TYPE
    SYNTAX  Counter64
    ACCESS  read-only
    STATUS  optional
    DESCRIPTION
      "total amount of bits received from the server"
    ::= {rsNADServerNetStatisticsEntry  16}

rsADAXServerStatisticsTable OBJECT-TYPE
    SYNTAX SEQUENCE OF RsADAXServerStatisticsEntry
    ACCESS not-accessible
    STATUS mandatory
    DESCRIPTION
      "Table containing Server statistics from AppXcel."
    ::= {rsNWSDStats 19}

rsADAXServerStatisticsEntry OBJECT-TYPE
    SYNTAX RsADAXServerStatisticsEntry
    ACCESS not-accessible
    STATUS  mandatory
    DESCRIPTION
       " The row definition for this table."
   INDEX { rsADAXServerStatisticsFarmName,
           rsADAXServerStatisticsServerAddress,
           rsADAXServerStatisticsPort}
    ::= {rsADAXServerStatisticsTable 1}

RsADAXServerStatisticsEntry ::= SEQUENCE {
  rsADAXServerStatisticsFarmName     	                  DisplayString,
  rsADAXServerStatisticsServerAddress		          IpAddress,
  rsADAXServerStatisticsPort		  	          INTEGER,
  rsADAXServerStatisticsAppConCurrent                     Counter32,
  rsADAXServerStatisticsAppConPeak                        Counter32,
  rsADAXServerStatisticsAppConTotal                       Counter64,
  rsADAXServerStatisticsAppDisConCurrent                  Counter32,
  rsADAXServerStatisticsAppDisConPeak                     Counter32,
  rsADAXServerStatisticsAppDisConTotal                    Counter64,
  rsADAXServerStatisticsAppRequestCurrent                 Counter32,
  rsADAXServerStatisticsAppRequestPeak                    Counter32,
  rsADAXServerStatisticsAppRequestTotal                   Counter64,
  rsADAXServerStatisticsAppFailureCurrent                 Counter32,
  rsADAXServerStatisticsAppFailurePeak                    Counter32,
  rsADAXServerStatisticsAppFailureTotal                   Counter64
}

rsADAXServerStatisticsFarmName     OBJECT-TYPE
    SYNTAX DisplayString (SIZE(1..50))
    ACCESS  read-only
    STATUS  mandatory
    DESCRIPTION
      "The farm name."
    ::= {rsADAXServerStatisticsEntry 1}

rsADAXServerStatisticsServerAddress OBJECT-TYPE
    SYNTAX IpAddress
    ACCESS  read-only
    STATUS  mandatory
    DESCRIPTION
      "The server IP address"
    ::= {rsADAXServerStatisticsEntry 2}

rsADAXServerStatisticsPort     OBJECT-TYPE
    SYNTAX INTEGER(0..65535)
    ACCESS  read-only
    STATUS  mandatory
    DESCRIPTION
      "The server port."
    ::= {rsADAXServerStatisticsEntry 3}

rsADAXServerStatisticsAppConCurrent         OBJECT-TYPE
    SYNTAX  Counter32
    ACCESS  read-only
    STATUS  mandatory
    DESCRIPTION
      "Current amount of application connections last 5 sec, taken from AX"
    ::= {rsADAXServerStatisticsEntry  4}

rsADAXServerStatisticsAppConPeak            OBJECT-TYPE
    SYNTAX  Counter32
    ACCESS  read-only
    STATUS  mandatory
    DESCRIPTION
      "Peak amount of application connections, taken from AX"
    ::= {rsADAXServerStatisticsEntry  5}

rsADAXServerStatisticsAppConTotal           OBJECT-TYPE
    SYNTAX  Counter64
    ACCESS  read-only
    STATUS  mandatory
    DESCRIPTION
      "Total amount of application connections, taken from AX"
    ::= {rsADAXServerStatisticsEntry  6}

rsADAXServerStatisticsAppDisConCurrent                  OBJECT-TYPE
    SYNTAX  Counter32
    ACCESS  read-only
    STATUS  mandatory
    DESCRIPTION
      "Current amount of application disconnections last 5 sec, taken from AX"
    ::= {rsADAXServerStatisticsEntry  7}

rsADAXServerStatisticsAppDisConPeak                     OBJECT-TYPE
    SYNTAX  Counter32
    ACCESS  read-only
    STATUS  mandatory
    DESCRIPTION
      "Peak amount of application disconnections, taken from AX"
    ::= {rsADAXServerStatisticsEntry  8}

rsADAXServerStatisticsAppDisConTotal                    OBJECT-TYPE
    SYNTAX  Counter64
    ACCESS  read-only
    STATUS  mandatory
    DESCRIPTION
      "Total amount of application disconnections, taken from AX"
    ::= {rsADAXServerStatisticsEntry  9}

rsADAXServerStatisticsAppRequestCurrent                 OBJECT-TYPE
    SYNTAX  Counter32
    ACCESS  read-only
    STATUS  mandatory
    DESCRIPTION
      "Current amount of requests last 5 sec, taken from AX"
    ::= {rsADAXServerStatisticsEntry  10}

rsADAXServerStatisticsAppRequestPeak                    OBJECT-TYPE
    SYNTAX  Counter32
    ACCESS  read-only
    STATUS  mandatory
    DESCRIPTION
      "Peak amount of requests ,taken from AX"
    ::= {rsADAXServerStatisticsEntry  11}

rsADAXServerStatisticsAppRequestTotal                   OBJECT-TYPE
    SYNTAX  Counter64
    ACCESS  read-only
    STATUS  mandatory
    DESCRIPTION
      "Total amount of requests ,taken from AX"
    ::= {rsADAXServerStatisticsEntry  12}

rsADAXServerStatisticsAppFailureCurrent                 OBJECT-TYPE
    SYNTAX  Counter32
    ACCESS  read-only
    STATUS  mandatory
    DESCRIPTION
      "Current amount of failure last 5 sec, taken from AX"
    ::= {rsADAXServerStatisticsEntry  13}

rsADAXServerStatisticsAppFailurePeak                    OBJECT-TYPE
    SYNTAX  Counter32
    ACCESS  read-only
    STATUS  mandatory
    DESCRIPTION
      "Peak amount of failure ,taken from AX"
    ::= {rsADAXServerStatisticsEntry  14}

rsADAXServerStatisticsAppFailureTotal                   OBJECT-TYPE
    SYNTAX  Counter64
    ACCESS  read-only
    STATUS  mandatory
    DESCRIPTION
      "Total amount of failure ,taken from AX"
    ::= {rsADAXServerStatisticsEntry  15}

--------------------------------------
rsNADAXServerStatisticsTable OBJECT-TYPE
    SYNTAX SEQUENCE OF RsNADAXServerStatisticsEntry
    ACCESS not-accessible
    STATUS mandatory
    DESCRIPTION
      "Table containing Server statistics from AppXcel."
    ::= {rsNWSDStats 32}

rsNADAXServerStatisticsEntry OBJECT-TYPE
    SYNTAX RsNADAXServerStatisticsEntry
    ACCESS not-accessible
    STATUS  mandatory
    DESCRIPTION
       " The row definition for this table."
   INDEX { rsNADAXServerStatisticsFarmName,
           rsNADAXServerStatisticsServerName}
    ::= {rsNADAXServerStatisticsTable 1}

RsNADAXServerStatisticsEntry ::= SEQUENCE {
  rsNADAXServerStatisticsFarmName     	                   DisplayString,
  rsNADAXServerStatisticsServerName						   DisplayString,
  rsNADAXServerStatisticsAppConCurrent                     Counter32,
  rsNADAXServerStatisticsAppConPeak                        Counter32,
  rsNADAXServerStatisticsAppConTotal                       Counter64,
  rsNADAXServerStatisticsAppDisConCurrent                  Counter32,
  rsNADAXServerStatisticsAppDisConPeak                     Counter32,
  rsNADAXServerStatisticsAppDisConTotal                    Counter64,
  rsNADAXServerStatisticsAppRequestCurrent                 Counter32,
  rsNADAXServerStatisticsAppRequestPeak                    Counter32,
  rsNADAXServerStatisticsAppRequestTotal                   Counter64,
  rsNADAXServerStatisticsAppFailureCurrent                 Counter32,
  rsNADAXServerStatisticsAppFailurePeak                    Counter32,
  rsNADAXServerStatisticsAppFailureTotal                   Counter64
}

rsNADAXServerStatisticsFarmName     OBJECT-TYPE
    SYNTAX DisplayString (SIZE(1..50))
    ACCESS  read-only
    STATUS  mandatory
    DESCRIPTION
      "The farm name."
    ::= {rsNADAXServerStatisticsEntry 1}

rsNADAXServerStatisticsServerName	OBJECT-TYPE
    SYNTAX  DisplayString (SIZE(1..30))
    ACCESS  read-only
    STATUS  mandatory
    DESCRIPTION
      "The name assigned by the user to the server."
    ::=  {rsNADAXServerStatisticsEntry 2}

rsNADAXServerStatisticsAppConCurrent         OBJECT-TYPE
    SYNTAX  Counter32
    ACCESS  read-only
    STATUS  optional
    DESCRIPTION
      "Current amount of application connections last 5 sec, taken from AX"
    ::= {rsNADAXServerStatisticsEntry  3}

rsNADAXServerStatisticsAppConPeak            OBJECT-TYPE
    SYNTAX  Counter32
    ACCESS  read-only
    STATUS  optional
    DESCRIPTION
      "Peak amount of application connections, taken from AX"
    ::= {rsNADAXServerStatisticsEntry  4}

rsNADAXServerStatisticsAppConTotal           OBJECT-TYPE
    SYNTAX  Counter64
    ACCESS  read-only
    STATUS  optional
    DESCRIPTION
      "Total amount of application connections, taken from AX"
    ::= {rsNADAXServerStatisticsEntry  5}

rsNADAXServerStatisticsAppDisConCurrent                  OBJECT-TYPE
    SYNTAX  Counter32
    ACCESS  read-only
    STATUS  optional
    DESCRIPTION
      "Current amount of application disconnections last 5 sec, taken from AX"
    ::= {rsNADAXServerStatisticsEntry  6}

rsNADAXServerStatisticsAppDisConPeak                     OBJECT-TYPE
    SYNTAX  Counter32
    ACCESS  read-only
    STATUS  optional
    DESCRIPTION
      "Peak amount of application disconnections, taken from AX"
    ::= {rsNADAXServerStatisticsEntry  7}

rsNADAXServerStatisticsAppDisConTotal                    OBJECT-TYPE
    SYNTAX  Counter64
    ACCESS  read-only
    STATUS  optional
    DESCRIPTION
      "Total amount of application disconnections, taken from AX"
    ::= {rsNADAXServerStatisticsEntry  8}

rsNADAXServerStatisticsAppRequestCurrent                 OBJECT-TYPE
    SYNTAX  Counter32
    ACCESS  read-only
    STATUS  optional
    DESCRIPTION
      "Current amount of requests last 5 sec, taken from AX"
    ::= {rsNADAXServerStatisticsEntry  9}

rsNADAXServerStatisticsAppRequestPeak                    OBJECT-TYPE
    SYNTAX  Counter32
    ACCESS  read-only
    STATUS  optional
    DESCRIPTION
      "Peak amount of requests ,taken from AX"
    ::= {rsNADAXServerStatisticsEntry  10}

rsNADAXServerStatisticsAppRequestTotal                   OBJECT-TYPE
    SYNTAX  Counter64
    ACCESS  read-only
    STATUS  optional
    DESCRIPTION
      "Total amount of requests ,taken from AX"
    ::= {rsNADAXServerStatisticsEntry  11}

rsNADAXServerStatisticsAppFailureCurrent                 OBJECT-TYPE
    SYNTAX  Counter32
    ACCESS  read-only
    STATUS  optional
    DESCRIPTION
      "Current amount of failure last 5 sec, taken from AX"
    ::= {rsNADAXServerStatisticsEntry  12}

rsNADAXServerStatisticsAppFailurePeak                    OBJECT-TYPE
    SYNTAX  Counter32
    ACCESS  read-only
    STATUS  optional
    DESCRIPTION
      "Peak amount of failure ,taken from AX"
    ::= {rsNADAXServerStatisticsEntry  13}

rsNADAXServerStatisticsAppFailureTotal                   OBJECT-TYPE
    SYNTAX  Counter64
    ACCESS  read-only
    STATUS  optional
    DESCRIPTION
      "Total amount of failure ,taken from AX"
    ::= {rsNADAXServerStatisticsEntry  14}

rdwrRIPAdvInterval OBJECT-TYPE
   SYNTAX     INTEGER (1..65535)
   ACCESS     read-write
   STATUS     mandatory
   DESCRIPTION
   "Time interval in seconds for RIP advertisement"
   DEFVAL { 30 }
   ::= {rdwrWSDCommon 5 }

rsWSDCpuUtilizationTrapThreshold OBJECT-TYPE
    SYNTAX  INTEGER  (0..99)
    ACCESS  read-write
    STATUS  mandatory
    DESCRIPTION
      "30 seconds CPU utilization threshold for trap sending. if the value is zero (0) traps will not be sent"
    DEFVAL {0}
   ::= {rsNWSD 73}


rsADSrvrNatRemoveEntryAtSessionEnd OBJECT-TYPE
    SYNTAX INTEGER {
                    enable(1),
                    disable(2)
                   }
    ACCESS  read-write
    STATUS  mandatory
    DESCRIPTION
      "Enable/Disable Server NAT remove at session end mode - whether the entries will be deleted when the session is over."
    DEFVAL {2}
   ::= {rsNWSD 104}

rdwrSystemIntMemUtilizationStat OBJECT-TYPE
SYNTAX DisplayString (SIZE(1..255))
    ACCESS read-only
    STATUS mandatory
    DESCRIPTION
        "Prints memory utilization statistics."
::= {rsNWSD 105}

rsWSDLastUsedFarmIP OBJECT-TYPE
    SYNTAX  IpAddress
    ACCESS  read-only
    STATUS  mandatory
    DESCRIPTION
        "The last used farm IP address"
    ::=  {rsServerDispatcher 138}

rsADTsl OBJECT IDENTIFIER ::= {rsServerDispatcher 170}


rsADTslFileChainTable                        OBJECT-TYPE
    SYNTAX SEQUENCE OF RsADTslFileChainTableEntry
    ACCESS             not-accessible
    STATUS             mandatory
    DESCRIPTION        "A table listing imported TSL files"
    ::= {rsADTsl 1}


rsADTslFileChainTableEntry                   OBJECT-TYPE
    SYNTAX          RsADTslFileChainTableEntry
    ACCESS          not-accessible
    STATUS          mandatory
    DESCRIPTION     "The Row definition for the TSL table"
    INDEX           {rsADTslFileChainName}
    ::= {rsADTslFileChainTable 1}


RsADTslFileChainTableEntry ::= SEQUENCE {
    rsADTslFileChainName            DisplayString,
    rsADTslFileImportTime           DisplayString,
    rsADTslFileActiveUntil          DisplayString,
    rsADTslOriginalFile             DisplayString,
    rsADTslActiveFile               DisplayString,
    rsADTslLastActiveFile           DisplayString,
    rsADTslLastFailedFile           DisplayString,
    rsADTslRootCertificate          DisplayString,
    rsADTslAutomaticUpdateHours     DisplayString,
    rsADTslNextTslRoot              DisplayString,
    rsADTslNextTslRootValidDate     DisplayString,
	rsADTslFileTslProxyUrl          OCTET STRING,
    rsADTslFileTslProxyUsername     OCTET STRING,
	rsADTslFileTslProxyPassword     OCTET STRING,
    rsADTslFileRowStatus            RowStatus
}

rsADTslFileChainName                OBJECT-TYPE
    SYNTAX DisplayString (SIZE(1..50))
    ACCESS read-write
    STATUS mandatory
    DESCRIPTION
        "The name of the TSL file."
    ::= {rsADTslFileChainTableEntry 1}

rsADTslFileImportTime               OBJECT-TYPE
    SYNTAX DisplayString (SIZE(0..16))
    ACCESS read-write
    STATUS mandatory
    DESCRIPTION
        "The import time of the TSL file in DD-MM-YYYY HH:MM format "
    ::= {rsADTslFileChainTableEntry 2}

rsADTslFileActiveUntil              OBJECT-TYPE
    SYNTAX DisplayString (SIZE(0..16))
    ACCESS read-write
    STATUS mandatory
    DESCRIPTION
        "Time in which Active TSL file becomes inactive (in DD-MM-YYYY HH:MM format) "
    ::= {rsADTslFileChainTableEntry 3}

rsADTslOriginalFile                 OBJECT-TYPE
    SYNTAX DisplayString (SIZE(1..50))
    ACCESS read-write
    STATUS mandatory
    DESCRIPTION
        "The name of the original manually uploaded TSL file."
    ::= {rsADTslFileChainTableEntry 4}

rsADTslActiveFile                   OBJECT-TYPE
    SYNTAX DisplayString (SIZE(0..50))
    ACCESS read-write
    STATUS mandatory
    DESCRIPTION
        "The name of active TSL file."
    ::= {rsADTslFileChainTableEntry 5}


rsADTslLastActiveFile               OBJECT-TYPE
    SYNTAX DisplayString (SIZE(0..50))
    ACCESS read-write
    STATUS mandatory
    DESCRIPTION
        "The name of the previous active TSL file."
    ::= {rsADTslFileChainTableEntry 6}


rsADTslLastFailedFile               OBJECT-TYPE
    SYNTAX DisplayString (SIZE(0..50))
    ACCESS read-write
    STATUS mandatory
    DESCRIPTION
        "The name of the recent TSL file which its validation has failed."
    ::= {rsADTslFileChainTableEntry 7}

rsADTslRootCertificate OBJECT-TYPE
  SYNTAX DisplayString (SIZE (0..50))
  ACCESS read-write
  STATUS mandatory
  DESCRIPTION   "Name of root certificate"
  ::=  {rsADTslFileChainTableEntry 8}

rsADTslAutomaticUpdateHours            OBJECT-TYPE
  SYNTAX DisplayString (SIZE (0..251))
  ACCESS read-write
  STATUS mandatory
  DESCRIPTION    "Defines the time in which AD checks for an updated TSL File (hh:mm,hh:mm...).
                  Empty string indicates no automatic TSL updates"
  DEFVAL { "02:00" }
  ::= { rsADTslFileChainTableEntry 9}

rsADTslNextTslRoot                       OBJECT-TYPE
  SYNTAX DisplayString (SIZE (0..50))
  ACCESS read-write
  STATUS mandatory
  DESCRIPTION   "Next Root TSL file"
  ::=  { rsADTslFileChainTableEntry  10}

rsADTslNextTslRootValidDate               OBJECT-TYPE
  SYNTAX DisplayString (SIZE(0..16))
    ACCESS read-write
    STATUS mandatory
    DESCRIPTION "Validity time start for the next TSL root file in DD-MM-YYYY HH:MM format "
  ::=  { rsADTslFileChainTableEntry  11}

rsADTslFileTslProxyUrl               OBJECT-TYPE
  SYNTAX OCTET STRING (SIZE(0..250))
    ACCESS read-write
    STATUS mandatory
    DESCRIPTION "Proxy URL address"
  ::=  { rsADTslFileChainTableEntry  12}

rsADTslFileTslProxyUsername               OBJECT-TYPE
  SYNTAX OCTET STRING (SIZE(0..50))
    ACCESS read-write
    STATUS mandatory
    DESCRIPTION "User name for proxy server"
  ::=  { rsADTslFileChainTableEntry  13}

rsADTslFileTslProxyPassword               OBJECT-TYPE
  SYNTAX OCTET STRING (SIZE(0..50))
    ACCESS read-write
    STATUS mandatory
    DESCRIPTION "Password for proxy server"
  ::=  { rsADTslFileChainTableEntry  14}

rsADTslFileRowStatus                OBJECT-TYPE
    SYNTAX RowStatus
    ACCESS read-write
    STATUS mandatory
    DESCRIPTION
        "The row status of the TLS file"
    ::= {rsADTslFileChainTableEntry 15}
------------------------

adTslFileChainFetchNow OBJECT-TYPE
    SYNTAX DisplayString (SIZE (1..50))
    ACCESS read-write
   	STATUS mandatory
   	DESCRIPTION
     	 "Fetch TSL file chain"
	::=  {rsWSDL4Policy 63}

------------------------

adTslInitialFetch OBJECT-TYPE
    SYNTAX FeatureStatus
    ACCESS read-write
   	STATUS mandatory
   	DESCRIPTION
     	 "Controls Auto Initial TSL Updates"
    DEFVAL { enable }
	::=  {rsWSDL4Policy 64}


rsADTslCertFieldValidationPolicy                   OBJECT-TYPE
    SYNTAX SEQUENCE OF RsADTslCertFieldValidationPolicyEntry
    ACCESS             not-accessible
    STATUS             mandatory
    DESCRIPTION        ""
    ::= {rsADTsl 2}


rsADTslCertFieldValidationPolicyEntry              OBJECT-TYPE
    SYNTAX          RsADTslCertFieldValidationPolicyEntry
    ACCESS          not-accessible
    STATUS          mandatory
    DESCRIPTION     "The Row definition for the TSL table"
    INDEX           {rsADTslCertFieldValidationPolicyName,
					 rsADTslCertFieldValidationFieldName,
                     rsADTslCertFieldValidationPolicyIndex}
    ::= {rsADTslCertFieldValidationPolicy 1}


RsADTslCertFieldValidationPolicyEntry ::= SEQUENCE {
    rsADTslCertFieldValidationPolicyName         DisplayString,
    rsADTslCertFieldValidationFieldName          DisplayString,
    rsADTslCertFieldValidationPolicyIndex        INTEGER,
    rsADTslCertFieldValidationValidFieldValue    OCTET STRING,
    rsADTslCertFieldValidationOptionalField      FeatureStatus,
    rsADTslCertFieldValidationRowStatus          RowStatus
}

rsADTslCertFieldValidationPolicyName            OBJECT-TYPE
    SYNTAX DisplayString (SIZE(1..50))
    ACCESS read-only
    STATUS mandatory
    DESCRIPTION
        "The name of the Certificate Validation Policy."
    ::= {rsADTslCertFieldValidationPolicyEntry 1}

    rsADTslCertFieldValidationFieldName              OBJECT-TYPE
    SYNTAX DisplayString (SIZE(1..190))
    ACCESS read-write
    STATUS mandatory
    DESCRIPTION
        "The Field name to validate"
    ::= {rsADTslCertFieldValidationPolicyEntry 2}

rsADTslCertFieldValidationPolicyIndex            OBJECT-TYPE
    SYNTAX INTEGER     (1..65000)
    ACCESS read-write
    STATUS mandatory
    DESCRIPTION
        "The Index of the Certificate Validation Policy, enables binding multiple fields to validate "
    ::= {rsADTslCertFieldValidationPolicyEntry 3}

rsADTslCertFieldValidationValidFieldValue        OBJECT-TYPE
    SYNTAX OCTET STRING (SIZE(1..250))
    ACCESS read-write
    STATUS mandatory
    DESCRIPTION        "The valid field value"
    ::= {rsADTslCertFieldValidationPolicyEntry 4}

rsADTslCertFieldValidationOptionalField          OBJECT-TYPE
    SYNTAX FeatureStatus
    ACCESS read-write
    STATUS mandatory
    DESCRIPTION        "Enabled for fields that may not appear in the certificate (but in case it does appear it must match the given value)."
    ::= {rsADTslCertFieldValidationPolicyEntry 5}


rsADTslCertFieldValidationRowStatus       OBJECT-TYPE
    SYNTAX RowStatus
    ACCESS read-write
    STATUS mandatory
    DESCRIPTION        "The row status of the Certificate Validation Policy"
    ::= {rsADTslCertFieldValidationPolicyEntry 6}


rsAdTslImportExport OBJECT IDENTIFIER ::= { rsADTsl 3 }

rsAdTslImportExportEntryName OBJECT-TYPE
    SYNTAX DisplayString (SIZE(0..50))
    ACCESS  read-write
    STATUS  mandatory
    DESCRIPTION       "entry name to be addressed."
    ::= { rsAdTslImportExport 1  }

rsAdTslImportExportFileName OBJECT-TYPE
    SYNTAX DisplayString
    ACCESS  read-write
    STATUS  mandatory
    DESCRIPTION
       "file name path to export to or import from according to action."
    ::= { rsAdTslImportExport 2  }

rsAdTslImportExportPassphrase OBJECT-TYPE
    SYNTAX DisplayString (SIZE(0..64))
    ACCESS  read-write
    STATUS  mandatory
    DESCRIPTION
       "Passphrase to be used when importing a key."
    ::= { rsAdTslImportExport 3 }

rsAdTslImportExportAction OBJECT-TYPE
    SYNTAX INTEGER {
     import         (1),
     export         (2)
    }
    ACCESS  read-write
    STATUS  mandatory
    DESCRIPTION
       "Action to be performed on the entry name or file specified."
    ::= { rsAdTslImportExport 4 }

-- AppDirector's SIP IP Header Adaptation Table

rsADSIPIPHeaderAdaptationTable OBJECT-TYPE
    SYNTAX SEQUENCE OF RsADSIPIPHeaderAdaptationEntry
    ACCESS not-accessible
    STATUS mandatory
    DESCRIPTION
      "Table containing the list of headers that will be updated."
    ::=  {rsServerDispatcher 182}

rsADSIPIPHeaderAdaptationEntry OBJECT-TYPE
    SYNTAX RsADSIPIPHeaderAdaptationEntry
    ACCESS not-accessible
    STATUS  mandatory
    DESCRIPTION
       " The row definition for this table."
    INDEX { rsADSIPIPHeaderField }
    ::= {rsADSIPIPHeaderAdaptationTable 1}

RsADSIPIPHeaderAdaptationEntry ::= SEQUENCE {
  rsADSIPIPHeaderField               DisplayString,
  rsADSIPIPHeaderFieldStatus         RowStatus
 }

rsADSIPIPHeaderField OBJECT-TYPE
    SYNTAX  DisplayString (SIZE(1..63))
    ACCESS  read-only
    STATUS  mandatory
    DESCRIPTION
     "SIP IP Header field."
    ::=  {rsADSIPIPHeaderAdaptationEntry 1}

rsADSIPIPHeaderFieldStatus OBJECT-TYPE
    SYNTAX  RowStatus
    ACCESS  read-write
    STATUS  mandatory
    DESCRIPTION
      "Administative status of header field."
    ::=  {rsADSIPIPHeaderAdaptationEntry 2}

rsADSIPIPHeaderAdaptationHideStatus OBJECT-TYPE
   SYNTAX INTEGER {
        enable(1),
        disable(2)
   }
   ACCESS  read-write
   STATUS  mandatory
   DESCRIPTION
       "Enable or disable SIP TCP header adaptation page."
   DEFVAL { disable }
   ::=  {rsServerDispatcher 183 }

-- Redirection table
rsADRedirectionTable                     OBJECT-TYPE
   SYNTAX SEQUENCE OF RsADRedirectionEntry
   ACCESS not-accessible
   STATUS mandatory
   DESCRIPTION
          "In this table the AppDirector saves the redirection modes
           per farm."
   ::= {rsNWSD 60}

rsADRedirectionEntry                     OBJECT-TYPE
    SYNTAX RsADRedirectionEntry
    ACCESS not-accessible
    STATUS mandatory
    DESCRIPTION
       " The row definition for this table."
   INDEX  {rsADRedirectionFarmName}
   ::= {rsADRedirectionTable 1}


RsADRedirectionEntry  ::= SEQUENCE {
  rsADRedirectionFarmName               DisplayString,
  rsADRedirectionDns                    FeatureStatus,
  rsADRedirectionDnsResponseTTL         Unsigned32,
  rsADRedirectionHttp                   INTEGER,
  rsADRedirectionRedirectToHttps        INTEGER,
  rsADRedirectionRtsp                   FeatureStatus,
  rsADRedirectionSip                    FeatureStatus,
  rsADRedirectionGlobalTriangle         FeatureStatus,
  rsADRedirectionProxy                  FeatureStatus,
  rsADRedirectionRedirectByName         FeatureStatus,
  rsADRedirectionFarmDistThreshold      INTEGER,
  rsADRedirectionFarmTrafficThreshold   INTEGER,
  rsADRedirectionStaticPrxEntries       INTEGER,
  rsADRedirectionAppRedirMode           INTEGER
 }

rsADRedirectionFarmName                  OBJECT-TYPE
    SYNTAX DisplayString (SIZE(1..50))
    ACCESS read-only
    STATUS mandatory
    DESCRIPTION
        "The name assigned by the user to this farm."
    ::= {rsADRedirectionEntry 1}

rsADRedirectionDns                       OBJECT-TYPE
    SYNTAX FeatureStatus
    ACCESS  read-write
    STATUS  mandatory
    DESCRIPTION
        "Enable or disable the DNS redirection feature for this farm."
    DEFVAL { 2 }
    ::= {rsADRedirectionEntry 2}

rsADRedirectionDnsResponseTTL            OBJECT-TYPE
   SYNTAX  Unsigned32
   ACCESS  read-write
   STATUS  mandatory
   DESCRIPTION
        "TTL for DNS replies."
   DEFVAL { 0 }
   ::=  {rsADRedirectionEntry 3 }

rsADRedirectionHttp                      OBJECT-TYPE
    SYNTAX INTEGER {
     enable(1),
     disable(2),
     moved-permanently(3),
     rfc-moved-temporarily(4)
    }
    ACCESS  read-write
    STATUS  mandatory
    DESCRIPTION
         "Defines the HTTP status code that is used for HTTP redirection:
          enable                 - '302 Moved Temporarily'.
          disable                - HTTP redirection is disabled.
          moved-permanently      - '301 Moved-Permanently' for any HTTP version.
          rfc-moved-temporarily  - '302 Moved Temporarily' for HTTP 1.0 and '307 Moved Temporarily' for HTTP 1.1."
    DEFVAL { 2 }
    ::= {rsADRedirectionEntry 4}


rsADRedirectionRedirectToHttps           OBJECT-TYPE
    SYNTAX  INTEGER {
				enable(1),
				disable(2),
				https-only(3)
    }
    ACCESS  read-write
    STATUS  mandatory
    DESCRIPTION
        "When enabled, HTTP redirects are transformed to HTTPS redirects.
		 When https-only, HTTP redirects to HTTP, and HTTPS redirects to HTTPS"
    ::= {rsADRedirectionEntry 5}

rsADRedirectionRtsp                      OBJECT-TYPE
    SYNTAX FeatureStatus
    ACCESS  read-write
    STATUS  mandatory
    DESCRIPTION
        "Enable or disable the RTSP redirection feature for this farm."
    DEFVAL { 2 }
    ::= {rsADRedirectionEntry 6}

rsADRedirectionSip                       OBJECT-TYPE
    SYNTAX FeatureStatus
    ACCESS  read-write
    STATUS  mandatory
    DESCRIPTION
        "Enable or disable the SIP redirection feature for this farm."
    DEFVAL { 2 }
    ::= {rsADRedirectionEntry 7}

rsADRedirectionGlobalTriangle            OBJECT-TYPE
    SYNTAX FeatureStatus
    ACCESS  read-write
    STATUS  mandatory
    DESCRIPTION
        "Enable or disable the Global Triangulation redirection feature for this farm."
    DEFVAL { 2 }
    ::= {rsADRedirectionEntry 8}

rsADRedirectionProxy                     OBJECT-TYPE
    SYNTAX FeatureStatus
    ACCESS  read-write
    STATUS  mandatory
    DESCRIPTION
        "Enable or disable the Proxy redirection (Client NAT) feature for this farm."
    DEFVAL { 2 }
    ::= {rsADRedirectionEntry 9}

rsADRedirectionRedirectByName            OBJECT-TYPE
    SYNTAX FeatureStatus
    ACCESS  read-write
    STATUS  mandatory
    DESCRIPTION
        "Redirect by name : When enabled redirection of HTTP, RTSP and SIP is done by URL address.
         When disabled redirection of HTTP, RTSP and SIP is done by IP address."
    DEFVAL { 1 }
    ::= {rsADRedirectionEntry 10}

rsADRedirectionFarmDistThreshold         OBJECT-TYPE
    SYNTAX INTEGER
    ACCESS  read-write
    STATUS  mandatory
    DESCRIPTION
       "This variable indicates the treshold above which the AppDirector starts
       distributing traffic to distributed AppDirectors. The significance of this
       parameter varies according to the load balancing algorithm chosen."
    DEFVAL { 2500 }
    ::= {rsADRedirectionEntry 11}

rsADRedirectionFarmTrafficThreshold      OBJECT-TYPE
    SYNTAX INTEGER
    ACCESS  read-write
    STATUS  mandatory
    DESCRIPTION
       "This variable indicates the treshold above which the AppDirector signals
       to all the distributed AppDirectors not to send traffic to it."
    DEFVAL { 5000 }
    ::= {rsADRedirectionEntry 12}

rsADRedirectionStaticPrxEntries          OBJECT-TYPE
   SYNTAX INTEGER (1..5000)
   ACCESS  read-write
   STATUS  mandatory
   DESCRIPTION
       "Maximum number of static proximity entries for this farm. Changing this number while static
        proximity entries already exist for the farm - requires a reset."
   DEFVAL { 500 }

   ::=  {rsADRedirectionEntry 13}

rsADRedirectionAppRedirMode              OBJECT-TYPE
    SYNTAX INTEGER {
      enable(1),
      disable(2),
      dns2ndRedir(3)
    }
    ACCESS  read-write
    STATUS  mandatory
    DESCRIPTION
        "Application redirection status can be in one of three modes:
            enable      - any of enabled the redirection modes can be used.
            disable     - none of the redirection modes can be used (equiv. to
                          enable with all redirection modes disabled)
            dns2ndRedir - can only use dns redirection, but as a fall back all
                          enabled redirection modes can be used."
    DEFVAL { 2 }
    ::= {rsADRedirectionEntry 14}

rsWSDAdvertVip OBJECT IDENTIFIER ::= { rsNWSD 61 }

rsWSDAdvertisedVIPsTable OBJECT-TYPE
    SYNTAX SEQUENCE OF RsWSDAdvertisedVIPsEntry
    ACCESS not-accessible
    STATUS  mandatory
    DESCRIPTION
      "Table containing the list of advertised VIPs."
    ::=  {rsWSDAdvertVip 1}

rsWSDAdvertisedVIPsEntry OBJECT-TYPE
    SYNTAX RsWSDAdvertisedVIPsEntry
    ACCESS not-accessible
    STATUS  mandatory
    DESCRIPTION
       " The row definition for this table."
   INDEX { rsWSDAVL4PolicyName}
    ::=  {rsWSDAdvertisedVIPsTable 1}

RsWSDAdvertisedVIPsEntry ::= SEQUENCE {
  rsWSDAVL4PolicyName            DisplayString,
  rsWSDAVHostRouteMetric         INTEGER,
  rsWSDExternalNatIp    	 IpAddress,
  rsWSDAdvertVipStatus		 RowStatus,
  rsWSDAdvertVipFarmName	 	DisplayString,
  rsWSDExternalNatAddrType    	InetAddressType,
  rsWSDExternalNatAddr		 	InetAddress
}

rsWSDAVL4PolicyName OBJECT-TYPE
    SYNTAX  DisplayString (SIZE(1..50))
    ACCESS  read-write
    STATUS  mandatory
    DESCRIPTION
     "Layer 4 policy name that advertised this entry."
    ::=  {rsWSDAdvertisedVIPsEntry 1}

rsWSDAVHostRouteMetric OBJECT-TYPE
    SYNTAX  INTEGER  (1..65535)
    ACCESS  read-write
    STATUS  mandatory
    DESCRIPTION
     "Host Routing Metric."
    ::=  {rsWSDAdvertisedVIPsEntry 2}

rsWSDExternalNatIp OBJECT-TYPE
    SYNTAX  IpAddress
    ACCESS  read-write
    STATUS  optional
    DESCRIPTION
     "Field is obsolete"
	DEFVAL {0}
    ::=  {rsWSDAdvertisedVIPsEntry 3}

rsWSDAdvertVipStatus OBJECT-TYPE
    	SYNTAX RowStatus
    	ACCESS read-write
   	STATUS mandatory
   	DESCRIPTION
     	 "Row status for the Advert vip."
	::=  {rsWSDAdvertisedVIPsEntry 4}

rsWSDAdvertVipFarmName OBJECT-TYPE
    SYNTAX  DisplayString (SIZE(1..50))
    ACCESS  read-write
    STATUS  mandatory
    DESCRIPTION
     "Name of farm to be advertised by the VIP."
    ::=  {rsWSDAdvertisedVIPsEntry 5}

rsWSDExternalNatAddrType OBJECT-TYPE
    SYNTAX  InetAddressType
    ACCESS  read-write
    STATUS  mandatory
    DESCRIPTION
     "The IP address type of Net Addr For the case where AppDirector is installed behind a NAT"
	DEFVAL  { ipv4 }
    ::=  {rsWSDAdvertisedVIPsEntry 6}

rsWSDExternalNatAddr OBJECT-TYPE
    SYNTAX  InetAddress
    ACCESS  read-write
    STATUS  mandatory
    DESCRIPTION
     "For the case where AppDirector is installed behind a NAT"
    ::=  {rsWSDAdvertisedVIPsEntry 7}

rsWSDSIDParameters OBJECT IDENTIFIER ::= { rsNWSD 62 }

rsWSDSIDMirroring OBJECT IDENTIFIER ::= { rsWSDSIDParameters 1 }

rsWSDSIDMirroringProtocolMode OBJECT-TYPE
    SYNTAX  FeatureStatus
    ACCESS  read-write
    STATUS  mandatory
    DESCRIPTION
      "Enable/Disable of the Session ID mirror protocol mode."
    DEFVAL { disable }
    ::=  { rsWSDSIDMirroring 1}


rsWSDSIDMirroringPercentage  OBJECT-TYPE
   SYNTAX INTEGER (1..100)
   ACCESS  read-write
   STATUS  mandatory
   DESCRIPTION
       "The percent of the Session ID Persistency table to back up"
   DEFVAL { 100 }
   ::=  { rsWSDSIDMirroring 2}


rsWSDSIDMirroringPollingTime  OBJECT-TYPE
   SYNTAX INTEGER (3..4294967)
   ACCESS  read-write
   STATUS  mandatory
   DESCRIPTION
       "The polling time in seconds of the Session ID mirror messages"
   DEFVAL { 10 }
   ::=  { rsWSDSIDMirroring 3}
--
-- DHCP MIB
--

rdwrDHCP OBJECT IDENTIFIER ::= { rdwrWSDCommon  7 }

rdwrDHCPServerStatus OBJECT-TYPE
    SYNTAX FeatureStatus
    ACCESS read-write
    STATUS mandatory
    DESCRIPTION
        "Enable or disable DHCP server for AppXcel. Enabled by default."
    ::= { rdwrDHCP 1 }

rdwrDHCPServerSubnet  OBJECT-TYPE
    SYNTAX IpAddress
    ACCESS read-write
    STATUS mandatory
    DESCRIPTION
        "Class B subnet to allocate IP addresses from. Default value is 169.254.0.0"
    ::= { rdwrDHCP 2 }

rdwrDHCPLeaseTable OBJECT-TYPE
    SYNTAX SEQUENCE OF RdwrDHCPLeaseEntry
    ACCESS not-accessible
    STATUS mandatory
    DESCRIPTION
        "A table showing the DHCP leases."
    ::= { rdwrDHCP 3 }

rdwrDHCPLeaseEntry OBJECT-TYPE
    SYNTAX RdwrDHCPLeaseEntry
    ACCESS not-accessible
    STATUS mandatory
    DESCRIPTION
        " The row definition for this table."
    INDEX { rdwrDHCPLeaseMAC,
            rdwrDHCPLeaseID }
    ::= { rdwrDHCPLeaseTable 1 }

RdwrDHCPLeaseEntry ::= SEQUENCE {
    rdwrDHCPLeaseMAC        PhysAddress,
    rdwrDHCPLeaseID			Unsigned32,
    rdwrDHCPLeaseIPAddress	IpAddress,
    rdwrDHCPLeaseClientID	DisplayString,
    rdwrDHCPLeaseTime		Unsigned32,
    rdwrDHCPLeaseGrantTime  DisplayString,
    rdwrDHCPLeaseTimeRemain	INTEGER
}

rdwrDHCPLeaseMAC OBJECT-TYPE
    SYNTAX PhysAddress
    ACCESS read-only
    STATUS mandatory
    DESCRIPTION
        "Client MAC address."
    ::=  { rdwrDHCPLeaseEntry 1 }

rdwrDHCPLeaseID OBJECT-TYPE
    SYNTAX Unsigned32
    ACCESS read-only
    STATUS mandatory
    DESCRIPTION
        "Internal client identifier."
    ::=  { rdwrDHCPLeaseEntry 2 }

rdwrDHCPLeaseIPAddress OBJECT-TYPE
    SYNTAX IpAddress
    ACCESS read-only
    STATUS mandatory
    DESCRIPTION
        "IP address leased to the client."
    ::=  { rdwrDHCPLeaseEntry 3 }

rdwrDHCPLeaseClientID OBJECT-TYPE
    SYNTAX DisplayString
    ACCESS read-only
    STATUS mandatory
    DESCRIPTION
        "Client identifier as stated in DHCP request."
    ::=  { rdwrDHCPLeaseEntry 4 }

rdwrDHCPLeaseTime OBJECT-TYPE
    SYNTAX Unsigned32
    ACCESS read-write
    STATUS mandatory
    DESCRIPTION
        "Lease time in seconds. Setting Lease Time to 0 deletes the entry from the Lease Table."
    ::=  { rdwrDHCPLeaseEntry 5 }

rdwrDHCPLeaseGrantTime OBJECT-TYPE
    SYNTAX DisplayString
    ACCESS read-only
    STATUS mandatory
    DESCRIPTION
        "Date and time of lease start. Format is: dd/mm/yyyy hh:mm:ss"
    ::=  { rdwrDHCPLeaseEntry 6 }

rdwrDHCPLeaseTimeRemain OBJECT-TYPE
    SYNTAX INTEGER
    ACCESS read-only
    STATUS mandatory
    DESCRIPTION
        "Number of seconds left to the lease."
    ::=  { rdwrDHCPLeaseEntry 7 }


--
-- DXP MIB
--

rdwrDXP OBJECT IDENTIFIER ::= { rdwrWSDCommon  8 }

rdwrDXPStatus OBJECT-TYPE
    SYNTAX FeatureStatus
    ACCESS read-write
    STATUS mandatory
    DESCRIPTION
        "Controls whether AD listens on DXP ports."
	DEFVAL { enable }
    ::= { rdwrDXP 1 }

rdwrDXPVersion OBJECT-TYPE
    SYNTAX DisplayString
    ACCESS read-only
    STATUS mandatory
    DESCRIPTION
        "The DXP version."
    ::= { rdwrDXP 2 }

rdwrDXPTransportParams OBJECT IDENTIFIER ::= { rdwrDXP 3 }

rdwrDXPManagementTransport OBJECT-TYPE
    SYNTAX INTEGER {
		tcp(1),
		tls(2)
	}
    ACCESS read-write
    STATUS mandatory
    DESCRIPTION
        "Transport protocol for DXP management messages."
	DEFVAL { tcp }
    ::= { rdwrDXPTransportParams 1 }

rdwrDXPRuntimeTransport OBJECT-TYPE
    SYNTAX INTEGER {
		udp(1),
		tls(2)
	}
    ACCESS read-write
    STATUS mandatory
    DESCRIPTION
        "Transport protocol for DXP runtime messages."
	DEFVAL { udp }
    ::= { rdwrDXPTransportParams 2 }

rdwrDXPXXPTransport OBJECT-TYPE
    SYNTAX INTEGER {
		tcp(1),
		tls(2)
	}
    ACCESS read-write
    STATUS mandatory
    DESCRIPTION
        "Transport protocol for XXP messages."
	DEFVAL { tcp }
    ::= { rdwrDXPTransportParams 3 }

rdwrDXPL4PortParams OBJECT IDENTIFIER ::= { rdwrDXP 4 }

rdwrDXPPort OBJECT-TYPE
    SYNTAX INTEGER (1025..65535)
    ACCESS read-write
    STATUS mandatory
    DESCRIPTION
        "DXP application port."
	DEFVAL { 7000 }
    ::= { rdwrDXPL4PortParams 1 }

rdwrDXPSecurePort OBJECT-TYPE
    SYNTAX INTEGER (1025..65535)
    ACCESS read-write
    STATUS mandatory
    DESCRIPTION
        "DXP secure port."
	DEFVAL { 7001 }
    ::= { rdwrDXPL4PortParams 2 }

rdwrDXPXXPPort OBJECT-TYPE
    SYNTAX INTEGER (1025..65535)
    ACCESS read-write
    STATUS mandatory
    DESCRIPTION
        "XXP application port."
	DEFVAL { 7000 }
    ::= { rdwrDXPL4PortParams 3 }

rdwrDXPXXPSecurePort OBJECT-TYPE
    SYNTAX INTEGER (1025..65535)
    ACCESS read-write
    STATUS mandatory
    DESCRIPTION
        "XXP secure port."
	DEFVAL { 7001 }
    ::= { rdwrDXPL4PortParams 4 }

rdwrDXPTimers OBJECT IDENTIFIER ::= { rdwrDXP 5 }

rdwrDXPInitTimer OBJECT-TYPE
    SYNTAX INTEGER (1..100)
    ACCESS read-write
    STATUS mandatory
    DESCRIPTION
        "DXP Init wait timer."
    DEFVAL { 10 }
    ::= { rdwrDXPTimers 1 }

rdwrDXPHealthCheckInteval OBJECT-TYPE
    SYNTAX INTEGER (0..100)
    ACCESS read-write
    STATUS mandatory
    DESCRIPTION
        "DXP Heath Check Interval in seconds."
    DEFVAL { 5 }
    ::= { rdwrDXPTimers 2 }

rdwrDXPHealthCheckTimeout OBJECT-TYPE
    SYNTAX INTEGER (0..100)
    ACCESS read-write
    STATUS mandatory
    DESCRIPTION
        "DXP AD Heath Check Timeout in seconds."
    DEFVAL { 12 }
    ::= { rdwrDXPTimers 3 }

rdwrDXPTCPHealthCheckInteval OBJECT-TYPE
    SYNTAX INTEGER (0..100)
    ACCESS read-write
    STATUS mandatory
    DESCRIPTION
        "DXP TCP Heath Check Interval in seconds."
    DEFVAL { 5 }
    ::= { rdwrDXPTimers 4 }

rdwrDXPTCPHealthCheckTimeout OBJECT-TYPE
    SYNTAX INTEGER (0..100)
    ACCESS read-write
    STATUS mandatory
    DESCRIPTION
        "DXP TCP Heath Check timeout in seconds."
    DEFVAL { 5 }
    ::= { rdwrDXPTimers 5 }

rdwrDXPUDPHealthCheckInteval OBJECT-TYPE
    SYNTAX INTEGER (0..100)
    ACCESS read-write
    STATUS mandatory
    DESCRIPTION
        "DXP UDP Heath Check Interval in seconds."
    DEFVAL { 5 }
    ::= { rdwrDXPTimers 6 }

rdwrDXPUDPHealthCheckTimeout OBJECT-TYPE
    SYNTAX INTEGER (0..100)
    ACCESS read-write
    STATUS mandatory
    DESCRIPTION
        "DXP UDP Heath Check timeout in seconds."
    DEFVAL { 5 }
    ::= { rdwrDXPTimers 7 }

rdwrDXPBackupParams OBJECT IDENTIFIER ::= { rdwrDXP 6 }

rdwrDXPNumberAXBackup OBJECT-TYPE
    SYNTAX INTEGER {
        none(1),
        one(2),
        half(3)
    }
    ACCESS read-write
    STATUS mandatory
    DESCRIPTION
        "Amount of AX system which are defined as backup systems."
    DEFVAL { 2 }
    ::= { rdwrDXPBackupParams 1 }


--
-- AD tuning
--

rsADTuning OBJECT IDENTIFIER ::= { rsNWSD 75}

rsADMaxSIPCallEntriesTuning OBJECT IDENTIFIER ::= { rsADTuning 1}

rsADMaxCALLIDEntries OBJECT-TYPE
    SYNTAX INTEGER
    ACCESS  read-only
    STATUS  mandatory
    DESCRIPTION
      "Maximal number of entries in the call-id table."
    ::=  { rsADMaxSIPCallEntriesTuning 1 }

rsADMaxCALLIDEntriesAfterReset OBJECT-TYPE
    SYNTAX INTEGER
    ACCESS  read-write
    STATUS  mandatory
    DESCRIPTION
      "Future maximal number of entries in the call-id table."
    ::=  { rsADMaxSIPCallEntriesTuning 2 }


rsADMaxSecondPersistencyParamEntries OBJECT-TYPE
    SYNTAX INTEGER
    ACCESS  read-only
    STATUS  mandatory
    DESCRIPTION
      "Maximal number of entries in the secondary persistency parameter table."
    ::=  { rsADMaxSIPCallEntriesTuning 3 }

rsADMaxSecondPersistencyParamEntriesAfterReset OBJECT-TYPE
    SYNTAX INTEGER
    ACCESS  read-write
    STATUS  mandatory
    DESCRIPTION
      "Future maximal number of entries in the secondory persistency parameter table."
    ::=  { rsADMaxSIPCallEntriesTuning 4 }


-- IP Networks table

adIpNetworksTable OBJECT-TYPE
	SYNTAX SEQUENCE OF AdIpNetworksEntry
	ACCESS not-accessible
	STATUS mandatory
	DESCRIPTION
		"A table for managing groups of IP networks."
  ::= {rsNWSD 76}

adIpNetworksEntry OBJECT-TYPE
	SYNTAX AdIpNetworksEntry
	ACCESS not-accessible
	STATUS mandatory
	DESCRIPTION
		" The row definition for this table."
	INDEX { adIpNetworkName, adIpNetworkIndex }
	::= {adIpNetworksTable 1}

AdIpNetworksEntry ::= SEQUENCE {
	adIpNetworkName		DisplayString,
	adIpNetworkIndex	Unsigned32,
	adIpNetworkFrom		DisplayString,
	adIpNetworkTo		DisplayString,
	adIpNetworkStatus	RowStatus
}

adIpNetworkName OBJECT-TYPE
	SYNTAX DisplayString (SIZE(1..50))
	ACCESS read-only
	STATUS mandatory
	DESCRIPTION
		"Name of network entity"
	::=  {adIpNetworksEntry 1}

adIpNetworkIndex OBJECT-TYPE
	SYNTAX Unsigned32
	ACCESS read-only
	STATUS mandatory
	DESCRIPTION
		"Arbitrary range index. Does not necessarily enforce order."
	::=  {adIpNetworksEntry 2}

adIpNetworkFrom OBJECT-TYPE
	SYNTAX DisplayString (SIZE(1..40))
	ACCESS read-write
	STATUS mandatory
	DESCRIPTION
		"Start of range IP address"
	::=  {adIpNetworksEntry 3}

adIpNetworkTo OBJECT-TYPE
	SYNTAX DisplayString (SIZE(1..40))
	ACCESS read-write
	STATUS mandatory
	DESCRIPTION
		"End of range IP address"
	::=  {adIpNetworksEntry 4}

adIpNetworkStatus OBJECT-TYPE
	SYNTAX RowStatus
	ACCESS read-write
	STATUS mandatory
	DESCRIPTION
		"Row status for the entry"
	::=  {adIpNetworksEntry 5}

--
-- AppDirector farm persistency table
--

rsADFarmPersistencyTable OBJECT-TYPE
   SYNTAX SEQUENCE OF RsADFarmPersistencyEntry
   ACCESS not-accessible
   STATUS mandatory
   DESCRIPTION
          "In this table the AppDirector saves the persistency parameters per
           servers farm."
   ::= {rsNWSD 77}

rsADFarmPersistencyEntry OBJECT-TYPE
    SYNTAX RsADFarmPersistencyEntry
    ACCESS not-accessible
    STATUS  mandatory
    DESCRIPTION
       " The row definition for this table."
   INDEX  {rsADFarmPersistencyFarmName}
   ::= {rsADFarmPersistencyTable 1}


RsADFarmPersistencyEntry  ::= SEQUENCE {
  rsADFarmPersistencyFarmName                     DisplayString,
  rsADFarmPersistencyType                         INTEGER,
  rsADFarmPersistencyAging                        Unsigned32,
  rsADFarmPersistencyAgingType                    INTEGER,
  rsADFarmPersistencyDefaultParameterLocator      DisplayString,
  rsADFarmPersistencyRegisterParameterLocator     DisplayString
}

rsADFarmPersistencyFarmName OBJECT-TYPE
    SYNTAX DisplayString (SIZE(1..50))
    ACCESS  read-only
    STATUS  mandatory
    DESCRIPTION
      "The name of the farm."
    ::= { rsADFarmPersistencyEntry 1}

rsADFarmPersistencyType OBJECT-TYPE
   SYNTAX INTEGER {
        callId(1),
        callIdWithParameter(2),
        parameter(3),
        parameterWithRegister(4),
        simpleCallWithConference(5),
        simpleUser(6)
   }
   ACCESS  read-write
   STATUS  mandatory
   DESCRIPTION
       "Choose the type of persistency for the farm."
   DEFVAL { callId }
   ::= { rsADFarmPersistencyEntry 2 }

rsADFarmPersistencyAging OBJECT-TYPE
    SYNTAX Unsigned32
    ACCESS read-write
    STATUS mandatory
    DESCRIPTION
        "The aging time in seconds ."
        DEFVAL { 5400 }
    ::= {rsADFarmPersistencyEntry 3}

rsADFarmPersistencyAgingType OBJECT-TYPE
   SYNTAX INTEGER {
        absolute(1),
        lastActivity(2)
   }
   ACCESS  read-write
   STATUS  mandatory
   DESCRIPTION
       "Aging type. Absolute will delete the persistency information after the aging time expires. Last activity tracks usgae of the persisntecy information and deletes it after aging time has elapsed since the last activity."
   DEFVAL { lastActivity }
   ::= { rsADFarmPersistencyEntry 4 }

rsADFarmPersistencyDefaultParameterLocator OBJECT-TYPE
    SYNTAX DisplayString (SIZE(0..50))
    ACCESS  read-write
    STATUS  mandatory
    DESCRIPTION
      "The default parameter locator."
    ::= { rsADFarmPersistencyEntry 5}

rsADFarmPersistencyRegisterParameterLocator OBJECT-TYPE
    SYNTAX DisplayString (SIZE(0..50))
    ACCESS  read-write
    STATUS  mandatory
    DESCRIPTION
      "The parameter locator used for REGISTER persisntecy."
    ::= { rsADFarmPersistencyEntry 6}

--
-- SIP params
--

adSIP OBJECT IDENTIFIER ::= { rsNWSD 74 }

adSIPConnControlTable OBJECT-TYPE
	SYNTAX SEQUENCE OF AdSIPConnControlEntry
	ACCESS not-accessible
	STATUS mandatory
	DESCRIPTION
		"A table for SIP/TCP connection control."
	::= {adSIP 1}

adSIPConnControlEntry OBJECT-TYPE
	SYNTAX AdSIPConnControlEntry
	ACCESS not-accessible
	STATUS mandatory
	DESCRIPTION
		" The row definition for this table."
	INDEX { adSIPConnControlEntryName }
	::= {adSIPConnControlTable 1}

AdSIPConnControlEntry ::= SEQUENCE {
	adSIPConnControlEntryName       DisplayString,
    adSIPConnControlProtocol        INTEGER,
    adSIPConnControlEntityType      INTEGER,
	adSIPConnControlEntityValue     DisplayString,
    adSIPConnControlNetPriority     INTEGER,
	adSIPConnControlConnNum	        Unsigned32,
    adSIPConnControlTcpConnReuse    INTEGER,
	adSIPConnControlCheckAlive      Unsigned32,
    adSIPConnControlMaxChkAlvfail   Unsigned32,
    adSIPConnControlChkAliveType    INTEGER,
	adSIPConnControlAgingTime       Unsigned32,
    adSIPConnControlRetryInterval   Unsigned32,
	adSIPConnControlStatus          RowStatus
}

adSIPConnControlEntryName OBJECT-TYPE
	SYNTAX DisplayString (SIZE(1..50))
	ACCESS read-only
	STATUS mandatory
	DESCRIPTION
		"Connection Control Table entry name."
	::=  {adSIPConnControlEntry 1}

adSIPConnControlProtocol OBJECT-TYPE
  SYNTAX INTEGER {
    udp(1),
    tcp(2)
  }
  ACCESS read-write
  STATUS mandatory
  DESCRIPTION
    "Connection protocol type."
  DEFVAL { tcp }
  ::=  {adSIPConnControlEntry 2}


adSIPConnControlEntityType OBJECT-TYPE
	SYNTAX INTEGER {
		ipAddress(1),
		network(2)
	}
	ACCESS read-write
	STATUS mandatory
	DESCRIPTION
		"Type of network entity."
	::=  {adSIPConnControlEntry 3}

adSIPConnControlEntityValue OBJECT-TYPE
	SYNTAX DisplayString (SIZE(1..50))
	ACCESS read-write
	STATUS mandatory
	DESCRIPTION
		"Name (or IP) of network entity with which TCP/UDP connections are maintained."
	::=  {adSIPConnControlEntry 4}

adSIPConnControlNetPriority OBJECT-TYPE
	SYNTAX INTEGER (0..1000)
	ACCESS read-write
	STATUS mandatory
	DESCRIPTION
		"Relevant only when type is a network. Determines order in case of overlapping
		 between networks on other connection control entries."
	::=  {adSIPConnControlEntry 5}

adSIPConnControlConnNum OBJECT-TYPE
	SYNTAX Unsigned32
	ACCESS read-write
	STATUS mandatory
	DESCRIPTION
	"Number of concurrent TCP or TLS connections that can be maintained
	 with a user-agent or proxy that belongs to the entity."
	DEFVAL { 1 }
	::=  {adSIPConnControlEntry 6}

adSIPConnControlTcpConnReuse OBJECT-TYPE
  SYNTAX INTEGER {
    never(1),
    always(2),
    tlsOnly(3),
    authTls(4)
  }
  ACCESS read-write
  STATUS mandatory
  DESCRIPTION
    "Defines when connection reuse is allowed. Relevant only when number of connections is 1."
  DEFVAL { always }
  ::=  {adSIPConnControlEntry 7}

adSIPConnControlCheckAlive OBJECT-TYPE
	SYNTAX Unsigned32
	ACCESS read-write
	STATUS mandatory
	DESCRIPTION
		"How often an idle connection should be checked (in seconds). If a check
		 fails, the connection is closed and cleared from internal tables. Check
		 alive success does not reset the aging timer."
	DEFVAL { 60 }
  ::=  {adSIPConnControlEntry 8}


adSIPConnControlMaxChkAlvfail OBJECT-TYPE
	SYNTAX Unsigned32
	ACCESS read-write
	STATUS mandatory
	DESCRIPTION
		"How many times the chk alive will fail before we close the connection. 0 - infinite"
	DEFVAL { 3 }
  ::=  {adSIPConnControlEntry 9}

adSIPConnControlChkAliveType OBJECT-TYPE
  SYNTAX INTEGER {
    doubleCRLF(1),
    optionsMsg(2)
  }
  ACCESS read-write
  STATUS mandatory
  DESCRIPTION
    "Check Alive Type."
  DEFVAL { doubleCRLF }
  ::=  {adSIPConnControlEntry 10}

adSIPConnControlAgingTime OBJECT-TYPE
	SYNTAX Unsigned32
	ACCESS read-write
	STATUS mandatory
	DESCRIPTION
		"After how long an idle connection is killed (in seconds). 0 denotes
		 no aging"
	DEFVAL { 1800 }
  ::=  {adSIPConnControlEntry 11}

adSIPConnControlRetryInterval OBJECT-TYPE
	SYNTAX Unsigned32
	ACCESS read-write
	STATUS mandatory
	DESCRIPTION
		"Check alive retry interval in seconds."
	DEFVAL { 5 }
  ::=  {adSIPConnControlEntry 12}

adSIPConnControlStatus OBJECT-TYPE
	SYNTAX RowStatus
	ACCESS read-write
	STATUS mandatory
	DESCRIPTION
		"row status for this table entry."
  ::=  {adSIPConnControlEntry 13}

 -- SIP Forwarding Classification Table

adSIPForwardingClassTable OBJECT-TYPE
  SYNTAX SEQUENCE OF AdSIPForwardingClassEntry
  ACCESS not-accessible
  STATUS mandatory
  DESCRIPTION
    "A table for SIP forwarding rules classification."
  ::= {adSIP 3}

adSIPForwardingClassEntry OBJECT-TYPE
  SYNTAX AdSIPForwardingClassEntry
  ACCESS not-accessible
  STATUS mandatory
  DESCRIPTION
    " The row definition for this table."
  INDEX { adSIPFrwrdClassPriority }
  ::= {adSIPForwardingClassTable 1}

AdSIPForwardingClassEntry ::= SEQUENCE {
  adSIPFrwrdClassPriority   Unsigned32,
  adSIPFrwrdClassName       DisplayString,
  adSIPFrwrdClassSourceNet  DisplayString,
  adSIPFrwrdClassVIP        DisplayString,
  adSIPFrwrdClassDestPort   INTEGER,
  adSIPFrwrdClassTransport  INTEGER,
  adSIPFrwrdClassScheme     INTEGER,
  adSIPFrwrdClassDestNet    DisplayString,
  adSIPFrwrdClassL7Cond     DisplayString,
  adSIPFrwrdClassStatus     RowStatus
}

adSIPFrwrdClassPriority OBJECT-TYPE
  SYNTAX Unsigned32 (1..1000)
  ACCESS read-only
  STATUS mandatory
  DESCRIPTION
    "Determines classification order. Forwarding classification is first-fit."
  ::=  {adSIPForwardingClassEntry 1}

adSIPFrwrdClassName OBJECT-TYPE
  SYNTAX DisplayString (SIZE(0..50))
  ACCESS read-write
  STATUS mandatory
  DESCRIPTION
    "The SIP Forwarding rule name."
  ::=  {adSIPForwardingClassEntry 2}

adSIPFrwrdClassSourceNet OBJECT-TYPE
  SYNTAX DisplayString (SIZE(0..50))
  ACCESS read-write
  STATUS mandatory
  DESCRIPTION
    "Source network on received request."
  DEFVAL { "ANY" }
  ::=  {adSIPForwardingClassEntry 3}

adSIPFrwrdClassVIP OBJECT-TYPE
  SYNTAX DisplayString (SIZE(0..40))
  ACCESS read-write
  STATUS mandatory
  DESCRIPTION
    "Destination IP on received request."
  ::=  {adSIPForwardingClassEntry 4}

adSIPFrwrdClassDestPort OBJECT-TYPE
  SYNTAX INTEGER (0..65535)
  ACCESS read-write
  STATUS mandatory
  DESCRIPTION
    "Destination port on received request. 0 stands for any port."
  DEFVAL { 0 }
  ::=  {adSIPForwardingClassEntry 5}

adSIPFrwrdClassTransport OBJECT-TYPE
  SYNTAX INTEGER {
    any(1),
    udp(2),
    tcp(3),
    sctp(4),
    tls(5)
  }
  ACCESS read-write
  STATUS mandatory
  DESCRIPTION
    "Transport of received request."
  DEFVAL { any }
  ::=  {adSIPForwardingClassEntry 6}

adSIPFrwrdClassScheme OBJECT-TYPE
  SYNTAX INTEGER {
    any(1),
    sip(2),
    sips(3)
  }
  ACCESS read-write
  STATUS mandatory
  DESCRIPTION
    "Received request scheme."
  DEFVAL { any }
  ::=  {adSIPForwardingClassEntry 7}

adSIPFrwrdClassDestNet OBJECT-TYPE
  SYNTAX DisplayString (SIZE(0..50))
  ACCESS read-write
  STATUS mandatory
  DESCRIPTION
    "Destination network after SIP next hop has been determined."
  DEFVAL { "ANY" }
  ::=  {adSIPForwardingClassEntry 8}

adSIPFrwrdClassL7Cond OBJECT-TYPE
  SYNTAX DisplayString
  ACCESS read-write
  STATUS mandatory
  DESCRIPTION
    "Logical expression constructed of L7 methods and expressions."
  ::=  {adSIPForwardingClassEntry 9}

adSIPFrwrdClassStatus OBJECT-TYPE
  SYNTAX RowStatus
  ACCESS read-write
  STATUS mandatory
  DESCRIPTION
    "Row status for this table entry."
  ::=  {adSIPForwardingClassEntry 10}

-- SIP Forwarding Result Table

adSIPForwardingResultTable OBJECT-TYPE
  SYNTAX SEQUENCE OF AdSIPForwardingResultEntry
  ACCESS not-accessible
  STATUS mandatory
  DESCRIPTION
    "A table for SIP forwarding rules actions."
  ::= {adSIP 4}

adSIPForwardingResultEntry OBJECT-TYPE
  SYNTAX AdSIPForwardingResultEntry
  ACCESS not-accessible
  STATUS mandatory
  DESCRIPTION
    " The row definition for this table."
  INDEX { adSIPFrwrdResultPriority }
  ::= {adSIPForwardingResultTable 1}

AdSIPForwardingResultEntry ::= SEQUENCE {
  adSIPFrwrdResultPriority        Unsigned32,
  adSIPFrwrdResultAction          INTEGER,
  adSIPFrwrdResultRespCode        INTEGER,
  adSIPFrwrdResultSourceVIP       DisplayString,
  adSIPFrwrdResultTransport       INTEGER,
  adSIPFrwrdResultScheme          INTEGER,
  adSIPFrwrdResultReqURITransport INTEGER,
  adSIPFrwrdResultConURITransport INTEGER,
  adSIPFrwrdResultSentByUDPPort   INTEGER,
  adSIPFrwrdResultSentByTCPPort   INTEGER,
  adSIPFrwrdResultSentByTLSPort   INTEGER,
  adSIPFrwrdResultUDPDestPort     INTEGER,
  adSIPFrwrdResultTCPDestPort     INTEGER,
  adSIPFrwrdResultTLSDestPort     INTEGER,
  adSIPFrwrdResultCertName        DisplayString,
  adSIPFrwrdResultAddRouteHeader  FeatureStatus,
  adSIPFrwrdResultRequestUriDomain  INTEGER,
  adSIPFrwrdResultRequestUriDomainValue  DisplayString,
  adSIPFrwrdResulClassName        DisplayString
}

adSIPFrwrdResultPriority OBJECT-TYPE
  SYNTAX Unsigned32
  ACCESS read-only
  STATUS mandatory
  DESCRIPTION
    "The SIP Forwarding rule priority as set in the classification parameters table."
  ::=  {adSIPForwardingResultEntry 1}

adSIPFrwrdResultAction OBJECT-TYPE
  SYNTAX INTEGER {
    forward(1),
    discard(2)
  }
  ACCESS read-write
  STATUS mandatory
  DESCRIPTION
    "Whether the request should be forwarded or dropped. If action is discard, then
    no other vars in the table are relevant except response code."
  DEFVAL { forward }
  ::=  {adSIPForwardingResultEntry 2}

adSIPFrwrdResultRespCode OBJECT-TYPE
  SYNTAX INTEGER
  ACCESS read-write
  STATUS mandatory
  DESCRIPTION
    "Response code to use. 100 will only be used on initial invite. 0 denotes no change in
    response code."
  DEFVAL { 0 }
  ::=  {adSIPForwardingResultEntry 3}

adSIPFrwrdResultSourceVIP OBJECT-TYPE
  SYNTAX DisplayString (SIZE(0..40))
  ACCESS read-write
  STATUS mandatory
  DESCRIPTION
    "VIP to use as source IP while forwarding the request. Not specifying a VIP or 0.0.0.0 means
    that the VIP of the request will be used."
  DEFVAL { "0.0.0.0" }
  ::=  {adSIPForwardingResultEntry 4}

adSIPFrwrdResultTransport OBJECT-TYPE
  SYNTAX INTEGER {
    automatic(1),
    udp(2),
    tcp(3),
    sctp(4),
    tls(5)
  }
  ACCESS read-write
  STATUS mandatory
  DESCRIPTION
    "Transport to use while forwarding the request. Automatic means forward using the same
    transport as received request."
  DEFVAL { automatic }
  ::=  {adSIPForwardingResultEntry 5}

adSIPFrwrdResultScheme OBJECT-TYPE
  SYNTAX INTEGER {
    automatic(1),
    sip(2),
    sips(3)
  }
  ACCESS read-write
  STATUS mandatory
  DESCRIPTION
    "Scheme to use while forwarding request. Automatic means forward using same scheme
    as received request. "
  DEFVAL { automatic }
  ::=  {adSIPForwardingResultEntry 6}

adSIPFrwrdResultReqURITransport OBJECT-TYPE
  SYNTAX INTEGER {
    leaveUnchanged(1),
    matchTransport(2)
  }
  ACCESS read-write
  STATUS mandatory
  DESCRIPTION
    "Specifies if the request URI scheme should match the transport."
  DEFVAL { leaveUnchanged }
  ::=  {adSIPForwardingResultEntry 7}

adSIPFrwrdResultConURITransport OBJECT-TYPE
  SYNTAX INTEGER {
    leaveUnchanged(1),
    matchTransport(2)
  }
  ACCESS read-write
  STATUS mandatory
  DESCRIPTION
    "Specifies if the contact URI scheme should match the transport."
  DEFVAL { leaveUnchanged }
  ::=  {adSIPForwardingResultEntry 8}

adSIPFrwrdResultSentByUDPPort OBJECT-TYPE
  SYNTAX INTEGER (1..65535)
  ACCESS read-write
  STATUS mandatory
  DESCRIPTION
    "Specifies the value that should be placed in the sent-by field if the transport is UDP.
    This is the port to which responses will be sent."
  DEFVAL { 5060 }
  ::=  {adSIPForwardingResultEntry 9}

adSIPFrwrdResultSentByTCPPort OBJECT-TYPE
  SYNTAX INTEGER (1..65535)
  ACCESS read-write
  STATUS mandatory
  DESCRIPTION
    "Specifies the value that should be placed in the sent-by field if the transport is TCP.
    This is the port to which responses will be sent if the request connection goes down."
  DEFVAL { 5060 }
  ::=  {adSIPForwardingResultEntry 10}

adSIPFrwrdResultSentByTLSPort OBJECT-TYPE
  SYNTAX INTEGER (1..65535)
  ACCESS read-write
  STATUS mandatory
  DESCRIPTION
    "Specifies the value that should be placed in the sent-by field if the transport is TLS.
    This is the port to which responses will be sent if the request connection goes down."
  DEFVAL { 5061 }
  ::=  {adSIPForwardingResultEntry 11}

adSIPFrwrdResultUDPDestPort OBJECT-TYPE
  SYNTAX INTEGER (0..65535)
  ACCESS read-write
  STATUS mandatory
  DESCRIPTION
    "Specifies the port to use if the transport is UDP and port cannot be determined from
    the request."
  DEFVAL { 0 }
  ::=  {adSIPForwardingResultEntry 12}

adSIPFrwrdResultTCPDestPort OBJECT-TYPE
  SYNTAX INTEGER (0..65535)
  ACCESS read-write
  STATUS mandatory
  DESCRIPTION
    "Specifies the port to use if the transport is UDP and port cannot be determined from
    the request."
  DEFVAL { 0 }
  ::=  {adSIPForwardingResultEntry 13}

adSIPFrwrdResultTLSDestPort OBJECT-TYPE
  SYNTAX INTEGER (0..65535)
  ACCESS read-write
  STATUS mandatory
  DESCRIPTION
    "Specifies the port to use if the transport is UDP and port cannot be determined from
    the request."
  DEFVAL { 0 }
  ::=  {adSIPForwardingResultEntry 14}

adSIPFrwrdResultCertName OBJECT-TYPE
  SYNTAX DisplayString
  ACCESS read-write
  STATUS mandatory
  DESCRIPTION
    "Certificate to use if the transport is TLS. Optional."
  ::=  {adSIPForwardingResultEntry 15}

adSIPFrwrdResultAddRouteHeader OBJECT-TYPE
  SYNTAX FeatureStatus
  ACCESS read-write
  STATUS mandatory
  DESCRIPTION
    "Whether a route header to the target should appear in the request."
  DEFVAL { enable }
  ::=  {adSIPForwardingResultEntry 16}

adSIPFrwrdResultRequestUriDomain OBJECT-TYPE
 SYNTAX INTEGER {
    leaveUnchanged(1),
    useDestinationIP(2),
    useSpecified(3)
  }
  ACCESS read-write
  STATUS mandatory
  DESCRIPTION
    "Whether to change request URI."
  DEFVAL { leaveUnchanged }
  ::=  {adSIPForwardingResultEntry 17}

adSIPFrwrdResultRequestUriDomainValue OBJECT-TYPE
  SYNTAX DisplayString
  ACCESS read-write
  STATUS mandatory
  DESCRIPTION
    "Request URI new value if UriDomain is useSpecified ."
  ::=  {adSIPForwardingResultEntry 18}

adSIPFrwrdResulClassName OBJECT-TYPE
  SYNTAX DisplayString (SIZE(0..50))
  ACCESS read-only
  STATUS mandatory
  DESCRIPTION
    "The SIP Forwarding rule name."
  ::=  {adSIPForwardingResultEntry 19}

adSIPParamLocatorTable OBJECT-TYPE
	SYNTAX SEQUENCE OF AdSIPParamLocatorEntry
	ACCESS not-accessible
	STATUS mandatory
	DESCRIPTION
		"A table for defining a parameter and its location in the SIP headers."
	::= {adSIP 2}

adSIPParamLocatorEntry OBJECT-TYPE
	SYNTAX AdSIPParamLocatorEntry
	ACCESS not-accessible
	STATUS mandatory
	DESCRIPTION
		" The row definition for this table."
	INDEX { adSIPParamLocatorName }
	::= {adSIPParamLocatorTable 1}

AdSIPParamLocatorEntry ::= SEQUENCE {
	adSIPParamLocatorName		DisplayString,
	adSIPParamLocatorType		INTEGER,
	adSIPParamLocatorSubType	INTEGER,
	adSIPParamLocHeaderArg	    DisplayString,
	adSIPParamLocSDPParamArg    DisplayString,
	adSIPParamLocOffsetStartArg	INTEGER,
	adSIPParamLocOffsetLenArg	INTEGER,
	adSIPParamLocUriParamArg	DisplayString,
	adSIPParamLocHeaderParamArg DisplayString,
	adSIPParamLocSdpWordArg		Unsigned32,
	adSIPParamLocatorStatus	RowStatus
}

adSIPParamLocatorName OBJECT-TYPE
	SYNTAX DisplayString (SIZE(1..50))
	ACCESS read-only
	STATUS mandatory
	DESCRIPTION
		"Defines the Parameter Locator name."
	::=  {adSIPParamLocatorEntry 1}

adSIPParamLocatorType OBJECT-TYPE
SYNTAX INTEGER {
	sipRequestURI(1),
	sipFromURI(2),
	sipToURI(3),
	sipContactURI(4),
	sippAssertedSIPURI(5),
	sippAssertedTelURI(6),
	sippPreferredSIPURI(7),
	sippPreferredTelURI(8),
 	sipRouteURI(9),
	sipHeader(10),
	sdpParameter(11),
	offset(12)
}
	ACCESS read-write
	STATUS mandatory
	DESCRIPTION
		"URI or parameter to extract value from. In case of P_ASSERTED URI and P_PREFERRED URI, the value is taken from the first occurrence of the header. The URI from the ROUTE header is taken from the first ROUTE after the top one has been removed. Type header is generic. OFFSET is from the beginning of the message."
	::=  {adSIPParamLocatorEntry 2}

adSIPParamLocatorSubType OBJECT-TYPE
SYNTAX INTEGER {
	na(0),
	sipUriAll(1),
	sipUriDomain(2),
	sipUriUser(3),
	sipUriUserDomain(4),
	sipUriUserDomainPort(5),
	sipUriSchemeUserDomainPort(6),
 	sipUriParam(7),
	sipHeaderAll(8),
	sipHeaderMainValue(9),
	sipHeaderParam(10),
	sdpParamAll(11),
	sdpParamWord(12)
}
	ACCESS read-write
	STATUS mandatory
	DESCRIPTION
		"Defines how to find the value in the URI or header. Header-main-value means without any parameter."
	::=  {adSIPParamLocatorEntry 3}


adSIPParamLocHeaderArg OBJECT-TYPE
	SYNTAX DisplayString (SIZE(0..50))
	ACCESS read-write
	STATUS mandatory
	DESCRIPTION
		"Additional information needed according to type or sub type. Specify Header Name if type is HEADER."
	::=  {adSIPParamLocatorEntry 4}

adSIPParamLocSDPParamArg OBJECT-TYPE
	SYNTAX DisplayString (SIZE(0..50))
	ACCESS read-write
	STATUS mandatory
	DESCRIPTION
		"Additional information needed according to type or sub type. Specify SDP Parameter Name if type is SDP_PARAMETER."
	::=  {adSIPParamLocatorEntry 5}

adSIPParamLocOffsetStartArg OBJECT-TYPE
	SYNTAX INTEGER (0..65534)
	ACCESS read-write
	STATUS mandatory
	DESCRIPTION
		"Additional information needed according to type or sub type. Specify Offset Start if type is OFFSET."
	  DEFVAL { 0 }
	::=  {adSIPParamLocatorEntry 6}

adSIPParamLocOffsetLenArg OBJECT-TYPE
	SYNTAX INTEGER (1..65534)
	ACCESS read-write
	STATUS mandatory
	DESCRIPTION
		"Additional information needed according to type or sub type. Specify Offset Len if type is OFFSET."
	  DEFVAL { 1 }
	::=  {adSIPParamLocatorEntry 7}

adSIPParamLocUriParamArg OBJECT-TYPE
	SYNTAX DisplayString (SIZE(0..50))
	ACCESS read-write
	STATUS mandatory
	DESCRIPTION
		"Additional information needed according to type or sub type. Specify URI Parameter Name if sub type is URI_PARAMETER_NAME."
	::=  {adSIPParamLocatorEntry 8}

adSIPParamLocHeaderParamArg OBJECT-TYPE
	SYNTAX DisplayString (SIZE(0..50))
	ACCESS read-write
	STATUS mandatory
	DESCRIPTION
		"Additional information needed according to type or sub type. Specify Header Parameter Name if sub type is HEADER_PARAMETER."
	::=  {adSIPParamLocatorEntry 9}

adSIPParamLocSdpWordArg OBJECT-TYPE
	SYNTAX Unsigned32
	ACCESS read-write
	STATUS mandatory
	DESCRIPTION
		"Additional information needed according to type or sub type. Specify SDP Parameter Word Number of sub type is SDP_PARAMETER_WORD."
	  DEFVAL { 1 }
	::=  {adSIPParamLocatorEntry 10}

adSIPParamLocatorStatus OBJECT-TYPE
	SYNTAX RowStatus
	ACCESS read-write
	STATUS mandatory
	DESCRIPTION
		"row status field."
	::=  { adSIPParamLocatorEntry 11}


adSIPTimer OBJECT IDENTIFIER ::= { adSIP 5 }

adSIPTimerT1 OBJECT-TYPE
    SYNTAX INTEGER(1..32000)
    ACCESS  read-write
    STATUS  mandatory
    DESCRIPTION
      "Restransmition Timer T1 in milliseconds 1-32000 (32sec)."
     DEFVAL { 500 }
    ::=  { adSIPTimer 1 }

adSIPTimerT2 OBJECT-TYPE
    SYNTAX INTEGER(1..32)
    ACCESS  read-write
    STATUS  mandatory
    DESCRIPTION
      "Restransmition Timer T2 in seconds 1-32."
    DEFVAL { 4 }
    ::=  { adSIPTimer 2 }

adSIPTimerB OBJECT-TYPE
    SYNTAX INTEGER(1..32)
    ACCESS  read-write
    STATUS  mandatory
    DESCRIPTION
      "Restransmition Timer B  in seconds 1-32 ."
   DEFVAL { 2 }
    ::=  { adSIPTimer 3 }

adSIPTimerF OBJECT-TYPE
    SYNTAX INTEGER(1..32)
    ACCESS  read-write
    STATUS  mandatory
    DESCRIPTION
      "Restransmition Timer F in seconds 1-32 ."
   DEFVAL { 2 }
    ::=  { adSIPTimer 4 }


adSIPRedundancyStatus OBJECT-TYPE
    SYNTAX INTEGER {
	master(1),
	backup(2),
	unset(3)
    }
    ACCESS  read-write
    STATUS  mandatory
    DESCRIPTION
      "SipDirector redudency status master or backup. While value is unset no traffic will be
	      handled by the proxy."
   DEFVAL { 3 }
    ::=  {  adSIP 6 }

adSIPConcurrentCallsLicense OBJECT-TYPE
    SYNTAX DisplayString (SIZE(1..80))
    ACCESS  read-write
    STATUS  mandatory
    DESCRIPTION "The new SIP concurrent calls license for the device"
    ::=  { adSIP 7}

adSIPConcurrentCallsLicenseID OBJECT-TYPE
   SYNTAX DisplayString (SIZE(1..80))
   ACCESS  read-only
   STATUS  mandatory
   DESCRIPTION
    "License ID used for SIP concurrent calls license upgrade"
    ::= { adSIP 8 }

rdwrProxyFailureAction OBJECT-TYPE
    SYNTAX INTEGER {
    fail(1),
    failOnSSL(2),
    failOnComp(3),
    failOnSSLandComp(4),
    ignore(5)
}
    ACCESS read-write
    STATUS mandatory
    DESCRIPTION
    "Defines how AD handles proxy failure.
    fail – failover to backup on any proxy failure.
    failOnSSL – failover to backup on SSL acceleration
    failure.
    failOnComp – failover to backup on hardware compression
    failure.
    failOnSSLandComp - failover to backup on SSL acceleration
    and on hardware compression failures.
    ignore – proxy failure does not trigger failover to
    backup device."
    DEFVAL { ignore }
    ::= { rdwrWSDCommon 9 }

rdwrAccelerationModuleTable OBJECT-TYPE
  SYNTAX SEQUENCE OF RdwrAccelerationModuleEntry
  ACCESS not-accessible
  STATUS mandatory
  DESCRIPTION
    "A table describing acceleration modules"
  ::= {rdwrWSDCommon 10}

rdwrAccelerationModuleEntry OBJECT-TYPE
  SYNTAX RdwrAccelerationModuleEntry
  ACCESS not-accessible
  STATUS mandatory
  DESCRIPTION
    " The row definition for this table."
  INDEX { rdwrAccelerationModuleIndex }
  ::= {rdwrAccelerationModuleTable 1}

RdwrAccelerationModuleEntry ::= SEQUENCE {
  rdwrAccelerationModuleIndex          Unsigned32,
  rdwrAccelerationModuleDescription    DisplayString,
  rdwrAccelerationModuleOperStatus     INTEGER
}

rdwrAccelerationModuleIndex OBJECT-TYPE
  SYNTAX Unsigned32
  ACCESS read-only
  STATUS mandatory
  DESCRIPTION
    "An arbitrary number used solely for convenient sorting"
  ::=  {rdwrAccelerationModuleEntry 1}

rdwrAccelerationModuleDescription OBJECT-TYPE
  SYNTAX DisplayString
  ACCESS read-only
  STATUS mandatory
  DESCRIPTION
    "A free text description of the acceleration module. May contain name, index number,
     capacity, brand etc."
  ::=  {rdwrAccelerationModuleEntry 2}

rdwrAccelerationModuleOperStatus OBJECT-TYPE
  SYNTAX INTEGER {
    active(1),
    notInService(2)
  }
  ACCESS read-only
  STATUS mandatory
  DESCRIPTION
    "The module's operational status"
  ::=  {rdwrAccelerationModuleEntry 3}

rsWSDAcceleratorApplicationStatistics OBJECT-TYPE
    SYNTAX  FeatureStatus
    ACCESS  read-write
    STATUS  mandatory
    DESCRIPTION
      "Indicates if the accelerators should report application statistics."
    DEFVAL {enable}
   ::= {rsNWSD 78}

rdwrCoreInfoTable OBJECT-TYPE
  SYNTAX SEQUENCE OF RdwrCoreInfoEntry
  ACCESS not-accessible
  STATUS mandatory
  DESCRIPTION
    "A table providing system CPU core information"
  ::= {rdwrWSDCommon 11}

rdwrCoreInfoEntry OBJECT-TYPE
  SYNTAX RdwrCoreInfoEntry
  ACCESS not-accessible
  STATUS mandatory
  DESCRIPTION
    " The row definition for this table."
  INDEX { rdwrCoreInfoCoreIndex }
  ::= {rdwrCoreInfoTable 1}

RdwrCoreInfoEntry ::= SEQUENCE {
  rdwrCoreInfoCoreIndex          Unsigned32,
  rdwrCoreInfoUtilization        INTEGER
}

rdwrCoreInfoCoreIndex OBJECT-TYPE
  SYNTAX Unsigned32
  ACCESS read-only
  STATUS mandatory
  DESCRIPTION
    "Core index starting from 1."
  ::=  {rdwrCoreInfoEntry 1}


rdwrCoreInfoUtilization OBJECT-TYPE
  SYNTAX INTEGER (-1..100)
  ACCESS read-only
  STATUS mandatory
  DESCRIPTION
    "system CPU Core utilization percentage."
  ::=  {rdwrCoreInfoEntry 2}

--  Note that in older versions (e.g. Appdirector 1.07) rsNWSD 80 is rsADDNSAnswerThroughNhr.
rsADSSLTPSLicense OBJECT-TYPE
    SYNTAX DisplayString (SIZE(1..80))
    ACCESS  read-write
    STATUS  mandatory
    DESCRIPTION "Deprecated"
    ::=  { rsNWSD 80}

rsADSSLCPSLicense OBJECT-TYPE
	SYNTAX DisplayString (SIZE(1..80))
	ACCESS  read-write
	STATUS  mandatory
	DESCRIPTION "The SSL Transactions Per Second license for the device.
			 Possible licenses are:
			 appdirector-ssl-500
			 appdirector-ssl-2000
			 appdirector-ssl-5000
			 appdirector-ssl-10000
			 appdirector-ssl-20000
			 appdirector-ssl-30000
			 appdirector-ssl-40000
			 appdirector-ssl-50000
			 appdirector-ssl-unlimited"
	::=  { rsNWSD 101}

rsADSSLTPSLicenseID OBJECT-TYPE
   SYNTAX DisplayString (SIZE(1..80))
   ACCESS  read-only
   STATUS  mandatory
   DESCRIPTION
    "Deprecated"
    ::= { rsNWSD 81 }

rsADSSLCPSLicenseID OBJECT-TYPE
   SYNTAX DisplayString (SIZE(1..80))
   ACCESS  read-only
   STATUS  mandatory
   DESCRIPTION
    "License ID used for SSL Transactions Per Second license upgrade."
    ::= { rsNWSD 102 }

rsADCompressionLicense OBJECT-TYPE
    SYNTAX DisplayString (SIZE(1..80))
    ACCESS  read-write
    STATUS  mandatory
    DESCRIPTION "The Compression in Mbps on server side license for the device.
                 Possible licenses are:
                 appdirector-compression-100
                 appdirector-compression-250
                 appdirector-compression-500
                 appdirector-compression-750
                 appdirector-compression-1000
                 appdirector-compression-1250
                 appdirector-compression-1500
                 appdirector-compression-unlimited"
    ::=  { rsNWSD 82}

rsADCompressionLicenseID OBJECT-TYPE
   SYNTAX DisplayString (SIZE(1..80))
   ACCESS  read-only
   STATUS  mandatory
   DESCRIPTION
    "License ID used for Compression in Mbps on server side license upgrade."
    ::= { rsNWSD 83 }

adProxyRAMPercentageForCache OBJECT-TYPE
    SYNTAX INTEGER (1..50)
    ACCESS read-write
    STATUS mandatory
    DESCRIPTION "Amount of Acceleration Engine RAM allocated for cache."
	DEFVAL { 20 }
    ::= { rsWSDL4Policy 15 }

adProxyRAMPercentageForCacheBeforeChange OBJECT-TYPE
    SYNTAX INTEGER (1..50)
    ACCESS read-only
    STATUS mandatory
    DESCRIPTION "Amount of Acceleration Engine RAM allocated for cache."
	DEFVAL { 20 }
    ::= { rsWSDL4Policy 20 }


rdwrProxyServicesStatus OBJECT-TYPE
   SYNTAX FeatureStatus
   ACCESS read-write
   STATUS mandatory
   DESCRIPTION
   "Define if AD will have proxy services."
   DEFVAL { enable }
   ::= { rdwrWSDCommon 12 }

rdwrOutboundInquiriesTimeOut OBJECT-TYPE
   SYNTAX INTEGER
   ACCESS read-write
   STATUS mandatory
   DESCRIPTION
   "Time out for TCP outbound inquiries in secounds."
   DEFVAL { 30 }
   ::= { rdwrWSDCommon 13 }

adAccelEngineCompressionLogs OBJECT-TYPE
    SYNTAX FeatureStatus
    ACCESS read-write
    STATUS mandatory
    DESCRIPTION "Determines whether compression information will be logged in a file."
	DEFVAL { disable }
    ::= { rsWSDL4Policy 21 }

adAccelEngineCacheLogs OBJECT-TYPE
    SYNTAX FeatureStatus
    ACCESS read-write
    STATUS mandatory
    DESCRIPTION "Determines whether cache information will be logged in a file."
	DEFVAL { disable }
    ::= { rsWSDL4Policy 22 }

-- HTTP Policy
adHttpPolicyTable OBJECT-TYPE
  SYNTAX SEQUENCE OF AdHttpPolicyEntry
  ACCESS not-accessible
  STATUS mandatory
  DESCRIPTION
    "A table of HTTP policies."
  ::= {rsWSDL4Policy 23}

adHttpPolicyEntry OBJECT-TYPE
  SYNTAX AdHttpPolicyEntry
  ACCESS not-accessible
  STATUS mandatory
  DESCRIPTION
    " The row definition for this table."
  INDEX { adHttpPolicyName }
  ::= {adHttpPolicyTable 1}

AdHttpPolicyEntry ::= SEQUENCE {
  adHttpPolicyName                 	DisplayString,
  adHttpPolicyPostClassification      	INTEGER,
  adHttpPolicyDepthRead               	INTEGER,
  adHttpPolicyHTTPNormalization       	FeatureStatus,
  adHttpPolicyPersistL7Mode           	INTEGER,
  adHttpPolicyMultiplexBEConnections  	FeatureStatus,
  adHttpPolicyBEConnectionCloseIdleTimout INTEGER,
  adHttpPolicyStatus                   	RowStatus
}

adHttpPolicyName OBJECT-TYPE
  SYNTAX DisplayString (SIZE (1..50))
  ACCESS read-only
  STATUS mandatory
  DESCRIPTION
    "The Http Policy name."
  ::=  {adHttpPolicyEntry 1}

adHttpPolicyPostClassification OBJECT-TYPE
    SYNTAX    INTEGER {
        header(1),
        body(2),
        headerandbody(3)
    }
    ACCESS    read-write
    STATUS    mandatory
    DESCRIPTION
       "The part of request to read for classification."
    DEFVAL {header}
    ::= { adHttpPolicyEntry 2 }

adHttpPolicyDepthRead OBJECT-TYPE
    SYNTAX  INTEGER (1..65535)
    ACCESS  read-write
    STATUS  mandatory
    DESCRIPTION
      "A number of bytes of request to read for classification."
    DEFVAL {3584}
   ::=  {adHttpPolicyEntry 3}

adHttpPolicyHTTPNormalization OBJECT-TYPE
    SYNTAX    FeatureStatus
    ACCESS    read-write
    STATUS    mandatory
    DESCRIPTION
       "HTTP normalization status."
    DEFVAL { disable }
    ::= { adHttpPolicyEntry 4 }

adHttpPolicyPersistL7Mode OBJECT-TYPE
    SYNTAX    INTEGER {
        first (1),
        overwrite(2),
        maintain(3)
    }
    ACCESS    read-write
    STATUS    mandatory
    DESCRIPTION
       "L7 persistency method."
    DEFVAL { first }
    ::= { adHttpPolicyEntry 5 }

adHttpPolicyMultiplexBEConnections OBJECT-TYPE
    SYNTAX FeatureStatus
    ACCESS  read-write
    STATUS  mandatory
    DESCRIPTION
      "enable or disable backend connection multiplexing
       Default value is disable"
    DEFVAL { disable }
 ::=  {adHttpPolicyEntry 6 }

 adHttpPolicyBEConnectionCloseIdleTimout OBJECT-TYPE
    SYNTAX INTEGER  (1..86400)
    ACCESS  read-write
    STATUS  mandatory
    DESCRIPTION
      "Timeout to close idle BE client connection"
    DEFVAL  { 3600 }
    ::=  { adHttpPolicyEntry 7 }

adHttpPolicyStatus OBJECT-TYPE
    SYNTAX  RowStatus
    ACCESS  read-write
    STATUS  mandatory
    DESCRIPTION
      "Administative status http policy."
    ::=  {adHttpPolicyEntry 8}

-- TCP Policy
adTcpPolicyTable OBJECT-TYPE
  SYNTAX SEQUENCE OF AdTcpPolicyEntry
  ACCESS not-accessible
  STATUS mandatory
  DESCRIPTION
    "A table of TCP policies."
  ::= {rsWSDL4Policy 65}

adTcpPolicyEntry OBJECT-TYPE
  SYNTAX AdTcpPolicyEntry
  ACCESS not-accessible
  STATUS mandatory
  DESCRIPTION
    " The row definition for this table."
  INDEX { adTcpPolicyName }
  ::= {adTcpPolicyTable 1}

AdTcpPolicyEntry ::= SEQUENCE {
  adTcpPolicyName                 	DisplayString,
  adTcpPolicyConnectionsPoolSize      	INTEGER,
  adTcpPolicyBEConnectionIdleTimout		INTEGER,
  adTcpPoolingBEConnectionsPooling  	FeatureStatus,
  adTcpPolicyStatus                   	RowStatus
}

adTcpPolicyName OBJECT-TYPE
  SYNTAX DisplayString (SIZE (1..50))
  ACCESS read-only
  STATUS mandatory
  DESCRIPTION
    "The TCP Policy name."
  ::=  {adTcpPolicyEntry 1}

adTcpPolicyConnectionsPoolSize OBJECT-TYPE
    SYNTAX    INTEGER (1..65535)
    ACCESS    read-write
    STATUS    mandatory
    DESCRIPTION
       "The maximum number of connections that AD holds in the connection reuse pool."
    DEFVAL {1}
    ::= { adTcpPolicyEntry 2 }

 adTcpPolicyBEConnectionIdleTimout OBJECT-TYPE
    SYNTAX INTEGER  (1..86400)
    ACCESS  read-write
    STATUS  mandatory
    DESCRIPTION
      "Timeout to close idle BE client connection"
    DEFVAL  { 3600 }
    ::=  { adTcpPolicyEntry 3 }

adTcpPoolingBEConnectionsPooling OBJECT-TYPE
    SYNTAX FeatureStatus
    ACCESS  read-write
    STATUS  mandatory
    DESCRIPTION
      "enable or disable backend connection pooling
       Default value is disable"
    DEFVAL { disable }
 ::=  {adTcpPolicyEntry 4 }

adTcpPolicyStatus OBJECT-TYPE
    SYNTAX  RowStatus
    ACCESS  read-write
    STATUS  mandatory
    DESCRIPTION
      "Administative status Tcp policy."
    ::=  {adTcpPolicyEntry 5}

adAccelEngineHttpLogs OBJECT-TYPE
    SYNTAX FeatureStatus
    ACCESS read-write
    STATUS mandatory
    DESCRIPTION "Determines whether HTTP information will be logged in a file."
	DEFVAL { disable }
    ::= { rsWSDL4Policy 58 }

adAccelEngineSslLogs OBJECT-TYPE
    SYNTAX FeatureStatus
    ACCESS read-write
    STATUS mandatory
    DESCRIPTION "Determines whether SSL information will be logged in a file."
	DEFVAL { disable }
    ::= { rsWSDL4Policy 59 }

rsADFirstTrunkPortIndex OBJECT-TYPE
    SYNTAX  INTEGER
    ACCESS  read-only
    STATUS  mandatory
    DESCRIPTION
      "Indicates the device first trunk port index."
   ::= {rsNWSD 84}

nadVipTable OBJECT-TYPE
   SYNTAX SEQUENCE OF NadVipTableEntry
   ACCESS not-accessible
   STATUS mandatory
   DESCRIPTION
       "A table for managing VIPs."
   ::= {rsNWSD 90}

nadVipTableEntry OBJECT-TYPE
   SYNTAX NadVipTableEntry
   ACCESS not-accessible
   STATUS mandatory
   DESCRIPTION
       " The row definition for this table."
   INDEX  {nadVipAddressType,
    nadVipAddress}
   ::= {nadVipTable 1}

NadVipTableEntry ::= SEQUENCE {
  nadVipAddressType   InetAddressType,
  nadVipAddress       InetAddress
}

nadVipAddressType OBJECT-TYPE
  SYNTAX InetAddressType
  ACCESS read-only
  STATUS mandatory
  DESCRIPTION
     "IP address of the VIP."
  ::=  {nadVipTableEntry 1}

nadVipAddress OBJECT-TYPE
  SYNTAX InetAddress
  ACCESS read-only
  STATUS mandatory
  DESCRIPTION
     "IP address of the VIP."
  ::=  {nadVipTableEntry 2}


-- IPv6 License

-- MIB is obsolete
rsADIPv6License OBJECT-TYPE
    SYNTAX DisplayString (SIZE(1..80))
    ACCESS  read-write
    STATUS  mandatory
    DESCRIPTION "The new licence for the device"
--    DEFVAL
    ::=  {rsServerDispatcher 144}

-- MIB is obsolete
rsADIPv6LicenseID OBJECT-TYPE
   SYNTAX DisplayString (SIZE(1..80))
   ACCESS  read-only
   STATUS  mandatory
   DESCRIPTION
    "License ID used for license downgrade"
    ::= { rsServerDispatcher 145 }

-- IPv6 L4 Policy table

rsADL4Policy OBJECT IDENTIFIER ::= { rsNWSD 70 }

rsADL4PolicyTable OBJECT-TYPE
   SYNTAX SEQUENCE OF RsADL4PolicyEntry
   ACCESS not-accessible
   STATUS mandatory
   DESCRIPTION
       "A table for managing load balancing policies information."
   ::= {rsADL4Policy 1}

rsADL4PolicyEntry OBJECT-TYPE
   SYNTAX RsADL4PolicyEntry
   ACCESS not-accessible
   STATUS  mandatory
   DESCRIPTION
       " The row definition for this table."
   INDEX  { rsADL4PolicyVirtualIP,
            rsADL4PolicyL4Protocol,
            rsADL4PolicyDstPort,
            rsADL4PolicyRangeIPFrom}
   ::= {rsADL4PolicyTable 1}

RsADL4PolicyEntry  ::= SEQUENCE {
      rsADL4PolicyVirtualIP          InetAddress,
      rsADL4PolicyL4Protocol         INTEGER,
      rsADL4PolicyDstPort            INTEGER,
      rsADL4PolicyRangeIPFrom        InetAddress,
      rsADL4PolicyRangeIPTo          InetAddress,
      rsADL4PolicyName               DisplayString,
      rsADL4PolicyL7PolicyName       DisplayString,
      rsADL4PolicyFarmName           DisplayString,
      rsADL4PolicyApplication        INTEGER,
      rsADL4PolicyBEPort             INTEGER,
      rsADL4PolicyDepthRead          INTEGER,
      rsADL4PolicyRedunStatus        INTEGER,
      rsADL4PolicyPostClassification INTEGER,
      rsADL4PolicyHTTPNormalization  FeatureStatus,
      rsADL4PolicyPersistL7Mode      INTEGER,
      rsADL4PolicyDefinedBy          INTEGER,
      rsADL4PolicySegmentName        DisplayString,
      rsADL4PolicyStatus             RowStatus
  }

rsADL4PolicyVirtualIP OBJECT-TYPE
   SYNTAX  InetAddress
   ACCESS  read-only
   STATUS  mandatory
   DESCRIPTION
       "Virtual destination IP address."
   ::= {rsADL4PolicyEntry 1}

rsADL4PolicyL4Protocol OBJECT-TYPE
    SYNTAX    INTEGER {
        tcp(1),
        udp(2),
        icmp(3),
        any(4),
        other(5)
    }
    ACCESS    read-only
    STATUS    mandatory
    DESCRIPTION
       "The L4 protocol type"
    ::= { rsADL4PolicyEntry 2}

rsADL4PolicyDstPort OBJECT-TYPE
    SYNTAX  INTEGER  (0..65535)
    ACCESS  read-only
    STATUS  mandatory
    DESCRIPTION
      "Destination port. Destination port 0 means any port"
 ::=  {rsADL4PolicyEntry 3}

rsADL4PolicyRangeIPFrom OBJECT-TYPE
   SYNTAX  InetAddress
   ACCESS  read-only
   STATUS  mandatory
   DESCRIPTION
       "Start address of the source IP range. The 0.0.0.0 address means that source
        IP ranges are not used for that entry"
   ::= {rsADL4PolicyEntry 4}

rsADL4PolicyRangeIPTo OBJECT-TYPE
   SYNTAX  InetAddress
   ACCESS  read-write
   STATUS  mandatory
   DESCRIPTION
       "Last address of the source IP range."
   ::= {rsADL4PolicyEntry 5}

rsADL4PolicyName  OBJECT-TYPE
    SYNTAX DisplayString (SIZE (1..50))
    ACCESS read-write
   	STATUS mandatory
   	DESCRIPTION
     	 "The L4 policy name."
	::=  {rsADL4PolicyEntry 6}

rsADL4PolicyL7PolicyName  OBJECT-TYPE
    SYNTAX DisplayString (SIZE(0..20))
    ACCESS read-write
   	STATUS mandatory
   	DESCRIPTION
     	 "The L7 policy name."
    DEFVAL { "None" }
	::=  {rsADL4PolicyEntry 7}

rsADL4PolicyFarmName  OBJECT-TYPE
    SYNTAX DisplayString (SIZE(0..50))
    ACCESS read-write
   	STATUS mandatory
   	DESCRIPTION
     	 "The farm name."
    DEFVAL { "None" }
	::=  {rsADL4PolicyEntry 8}

rsADL4PolicyApplication OBJECT-TYPE
    SYNTAX  INTEGER  {
        na (1),
        http(2),
        ftpcontrol(3),
        ftpdata(4),
        https(5),
        rtsp(6),
        rsh(7),
        rexec(8),
        tftp(9),
        sip(10),
        tsCookie(11),
        radius(12),
        fix(13),
        virtualIPInterface(14),
        ping(15),
        tcp(16),
        udp(17)
    }
    ACCESS  read-write
    STATUS  mandatory
    DESCRIPTION
      "Treat as given port number. Tells how to treat the traffic that matches
       the L4 policy."
    DEFVAL { na }
   ::=  {rsADL4PolicyEntry 9}

rsADL4PolicyBEPort OBJECT-TYPE
    SYNTAX  INTEGER  (0..65535)
    ACCESS  read-write
    STATUS  mandatory
    DESCRIPTION
        "Backend encryption port."
    DEFVAL { 0 }
   ::=  {rsADL4PolicyEntry 10}

rsADL4PolicyDepthRead OBJECT-TYPE
    SYNTAX  INTEGER (1..65535)
    ACCESS  read-write
    STATUS  mandatory
    DESCRIPTION
      "A number of bytes of request to read for classification."
    DEFVAL {3584}
   ::=  {rsADL4PolicyEntry 11}

rsADL4PolicyRedunStatus  OBJECT-TYPE
    SYNTAX    INTEGER {
        master(1),
        backup(2)
    }
    ACCESS    read-write
    STATUS    mandatory
    DESCRIPTION
       "The L4 policy on backup or master device."
    DEFVAL {master}
   ::= { rsADL4PolicyEntry 12 }

rsADL4PolicyPostClassification OBJECT-TYPE
    SYNTAX    INTEGER {
        header(1),
        body(2),
        headerandbody(3)
    }
    ACCESS    read-write
    STATUS    mandatory
    DESCRIPTION
       "The part of request to read for classification."
    DEFVAL {header}
    ::= { rsADL4PolicyEntry 13 }

rsADL4PolicyHTTPNormalization OBJECT-TYPE
    SYNTAX    FeatureStatus
    ACCESS    read-write
    STATUS    mandatory
    DESCRIPTION
       "HTTP normalization status."
    DEFVAL { disable }
    ::= { rsADL4PolicyEntry 14 }

rsADL4PolicyPersistL7Mode OBJECT-TYPE
    SYNTAX    INTEGER {
        first (1),
        overwrite(2),
        maintain(3)
    }
    ACCESS    read-write
    STATUS    mandatory
    DESCRIPTION
       "L7 persistency method."
    DEFVAL { first }
    ::= { rsADL4PolicyEntry 15 }

rsADL4PolicyDefinedBy OBJECT-TYPE
    SYNTAX    INTEGER {
        userdefined (1),
        system(2)
    }
    ACCESS    read-only
    STATUS    mandatory
    DESCRIPTION
       "The L4 policy origin. The policy may be defined by user, or by application
         for internal purpose."
    DEFVAL { userdefined }
    ::= { rsADL4PolicyEntry 16 }

rsADL4PolicySegmentName  OBJECT-TYPE
    SYNTAX DisplayString (SIZE(0..20))
    ACCESS read-write
   	STATUS mandatory
   	DESCRIPTION
     	 "The segment name."
	::=  {rsADL4PolicyEntry 17}

rsADL4PolicyStatus OBJECT-TYPE
    SYNTAX    RowStatus
    ACCESS    read-write
    STATUS    mandatory
    DESCRIPTION
      "Row status for this entry."
    ::= { rsADL4PolicyEntry 18 }

rsNADL4PolicyTable OBJECT-TYPE
   SYNTAX SEQUENCE OF RsNADL4PolicyEntry
   ACCESS not-accessible
   STATUS mandatory
   DESCRIPTION
       "A table for managing load balancing policies information."
   ::= {rsADL4Policy 3}

rsNADL4PolicyEntry OBJECT-TYPE
   SYNTAX RsNADL4PolicyEntry
   ACCESS not-accessible
   STATUS  mandatory
   DESCRIPTION
       " The row definition for this table."
   INDEX  { rsNADL4PolicyName }
   ::= {rsNADL4PolicyTable 1}

RsNADL4PolicyEntry  ::= SEQUENCE {
	  rsNADL4PolicyName               	DisplayString,
	  rsNADL4PolicyVirtualIPAddrType  	InetAddressType,
      rsNADL4PolicyVirtualIP          	InetAddress,
      rsNADL4PolicyL4Protocol         	INTEGER,
      rsNADL4PolicyDstPort            	INTEGER,
	  rsNADL4PolicyRangeIPFromAddrType  InetAddressType,
      rsNADL4PolicyRangeIPFrom          InetAddress,
	  rsNADL4PolicyRangeIPToAddrType  	InetAddressType,
      rsNADL4PolicyRangeIPTo          	InetAddress,
      rsNADL4PolicyDescription        	DisplayString,
      rsNADL4PolicyL7PolicyName       	DisplayString,
      rsNADL4PolicyFarmName           	DisplayString,
      rsNADL4PolicyApplication        	INTEGER,
      rsNADL4PolicyBeckendPort        	INTEGER,
      rsNADL4PolicyRedunStatus        	INTEGER,
      rsNADL4PolicyDefinedBy          	INTEGER,
      rsNADL4PolicySegmentName        	DisplayString,
	  rsNADL4PolicyActionType			INTEGER,
      rsNADL4PolicyAction				DisplayString,
      rsNADL4PolicySIPControlPolicy		DisplayString,
      rsNADL4PolicyClientSSLPolicy		DisplayString,
      rsNADL4PolicyCompressionPolicy	DisplayString,
      rsNADL4PolicyCachingPolicy		DisplayString,
      rsNADL4PolicyAuthenticationPolicy	DisplayString,
      rsNADL4PolicyHttpPolicy			DisplayString,
      rsNADL4PolicyStatus             	RowStatus,
      rsNADL4PolicyTcpPolicy            DisplayString
  }


rsNADL4PolicyName  OBJECT-TYPE
    SYNTAX DisplayString (SIZE (1..50))
    ACCESS read-write
   	STATUS mandatory
   	DESCRIPTION
     	 "The L4 policy name."
	::=  {rsNADL4PolicyEntry 1}

rsNADL4PolicyVirtualIPAddrType OBJECT-TYPE
   SYNTAX  InetAddressType
   ACCESS  read-write
   STATUS  mandatory
   DESCRIPTION
       "Virtual destination IP address Type."
	DEFVAL  { ipv4 }
   ::= {rsNADL4PolicyEntry 2}

rsNADL4PolicyVirtualIP OBJECT-TYPE
   SYNTAX  InetAddress
   ACCESS  read-write
   STATUS  mandatory
   DESCRIPTION
       "Virtual destination IP address."
	DEFVAL{"0.0.0.0"}
   ::= {rsNADL4PolicyEntry 3}

rsNADL4PolicyL4Protocol OBJECT-TYPE
    SYNTAX    INTEGER {
        tcp(1),
        udp(2),
        icmp(3),
        any(4),
        other(5),
        sctp(6)
    }
    ACCESS    read-write
    STATUS    mandatory
    DESCRIPTION
       "The L4 protocol type"
    ::= { rsNADL4PolicyEntry 4}

rsNADL4PolicyDstPort OBJECT-TYPE
    SYNTAX  INTEGER  (0..65535)
    ACCESS  read-write
    STATUS  mandatory
    DESCRIPTION
      "Destination port. Destination port 0 means any port"
 ::=  {rsNADL4PolicyEntry 5}

rsNADL4PolicyRangeIPFromAddrType OBJECT-TYPE
   SYNTAX  InetAddressType
   ACCESS  read-write
   STATUS  optional
   DESCRIPTION
       "Start address of the source IP range Type"
	DEFVAL  { ipv4 }
   ::= {rsNADL4PolicyEntry 6}

rsNADL4PolicyRangeIPFrom OBJECT-TYPE
   SYNTAX  InetAddress
   ACCESS  read-write
   STATUS  optional
   DESCRIPTION
       "Start address of the source IP range. The 0.0.0.0 address means that source
        IP ranges are not used for that entry"
	DEFVAL{"0.0.0.0"}
   ::= {rsNADL4PolicyEntry 7}

rsNADL4PolicyRangeIPToAddrType OBJECT-TYPE
   SYNTAX  InetAddressType
   ACCESS  read-write
   STATUS  optional
   DESCRIPTION
       "The IP address type of Last address of the source IP range."
	DEFVAL  { ipv4 }
   ::= {rsNADL4PolicyEntry 8}

rsNADL4PolicyRangeIPTo OBJECT-TYPE
   SYNTAX  InetAddress
   ACCESS  read-write
   STATUS  optional
   DESCRIPTION
       "Last address of the source IP range."
	DEFVAL{"0.0.0.0"}
   ::= {rsNADL4PolicyEntry 9}

rsNADL4PolicyDescription  OBJECT-TYPE
    SYNTAX DisplayString (SIZE (0..50))
    ACCESS read-write
   	STATUS optional
   	DESCRIPTION
     	 "The L4 policy description."
	::=  {rsNADL4PolicyEntry 10}

rsNADL4PolicyL7PolicyName  OBJECT-TYPE
    SYNTAX DisplayString (SIZE(0..20))
    ACCESS read-write
   	STATUS mandatory
   	DESCRIPTION
     	 "The L7 policy name."
    DEFVAL { "None" }
	::=  {rsNADL4PolicyEntry 11}

rsNADL4PolicyFarmName  OBJECT-TYPE
    SYNTAX DisplayString (SIZE(0..50))
    ACCESS read-write
   	STATUS mandatory
   	DESCRIPTION
     	 "The farm name."
    DEFVAL { "None" }
	::=  {rsNADL4PolicyEntry 12}

rsNADL4PolicyApplication OBJECT-TYPE
    SYNTAX  INTEGER  {
        na (1),
        http(2),
        ftpcontrol(3),
        ftpdata(4),
        https(5),
        rtsp(6),
        rsh(7),
        rexec(8),
        tftp(9),
        sip(10),
        tsCookie(11),
        radius(12),
        fix(13),
        virtualIPInterface(14),
        ping(15),
        tcp(16),
        udp(17),
	sctp(18),
	mh-sctp(19),
	restricted-icap(20), -- Added in 1.03.06DL
        sips(21),
        generic-ssl(22)
--		diameter(24)
    }
    ACCESS  read-write
    STATUS  optional
    DESCRIPTION
      "Treat as given port number. Tells how to treat the traffic that matches
       the L4 policy."
    DEFVAL { na }
   ::=  {rsNADL4PolicyEntry 13}

rsNADL4PolicyBeckendPort OBJECT-TYPE
    SYNTAX  INTEGER  (0..65535)
    ACCESS  read-write
    STATUS  optional
    DESCRIPTION
        "Backend encryption port."
    DEFVAL { 0 }
   ::=  {rsNADL4PolicyEntry 14}


rsNADL4PolicyRedunStatus  OBJECT-TYPE
    SYNTAX    INTEGER {
        master(1),
        backup(2)
    }
    ACCESS    read-write
    STATUS    optional
    DESCRIPTION
       "The L4 policy on backup or master device."
    DEFVAL {master}
   ::= { rsNADL4PolicyEntry 15 }

rsNADL4PolicyDefinedBy OBJECT-TYPE
    SYNTAX    INTEGER {
        userdefined (1),
        system(2)
    }
    ACCESS    read-only
    STATUS    mandatory
    DESCRIPTION
       "The L4 policy origin. The policy may be defined by user, or by application
         for internal purpose."
    ::= { rsNADL4PolicyEntry 16}

rsNADL4PolicySegmentName  OBJECT-TYPE
    SYNTAX DisplayString (SIZE(0..20))
    ACCESS read-write
   	STATUS optional
   	DESCRIPTION
     	 "The segment name."
	::=  {rsNADL4PolicyEntry 17}

rsNADL4PolicyActionType OBJECT-TYPE
  SYNTAX INTEGER {
    farm(1),
    l7policy(2),
    route(3),
    uri(4),
    ip(5),
    replyCode(6),
    none(7)
  }
  ACCESS read-write
  STATUS mandatory
  DESCRIPTION
    "Type of action to take on classification success.
    Farm – farm name to select server from.
    L7 Policy – perform L7 classification to select farm.
    Route – specify a SIP route table.
    URI – send request to specified URI.
    IP – send request to IP.
    Reply Code - send a reply with specified code (SIP).
    None – destination is determined by SIP headers."
	DEFVAL { farm }
  ::= {rsNADL4PolicyEntry 18}

rsNADL4PolicyAction OBJECT-TYPE
	SYNTAX DisplayString (SIZE(0..50))
	ACCESS read-write
	STATUS mandatory
	DESCRIPTION
    "Action to take on classification success. Must match action type. Replaces both rsNADL4PolicyL7PolicyName
    and rsNADL4PolicyFarmName."
	::= {rsNADL4PolicyEntry 19}

rsNADL4PolicySIPControlPolicy OBJECT-TYPE
  SYNTAX DisplayString (SIZE (1..50))
  ACCESS read-write
  STATUS mandatory
  DESCRIPTION
    "The SIP Policy name."
  DEFVAL { "None" }
  ::=  {rsNADL4PolicyEntry 20}

rsNADL4PolicyClientSSLPolicy OBJECT-TYPE
  SYNTAX DisplayString (SIZE (1..50))
  ACCESS read-write
  STATUS mandatory
  DESCRIPTION
    "The Client SSL Policy name."
  DEFVAL { "None" }
  ::=  {rsNADL4PolicyEntry 21}

rsNADL4PolicyCompressionPolicy OBJECT-TYPE
  SYNTAX DisplayString (SIZE (1..50))
  ACCESS read-write
  STATUS mandatory
  DESCRIPTION
    "The Compression Policy name."
  DEFVAL { "None" }
  ::=  {rsNADL4PolicyEntry 22}

rsNADL4PolicyCachingPolicy OBJECT-TYPE
  SYNTAX DisplayString (SIZE (1..50))
  ACCESS read-write
  STATUS mandatory
  DESCRIPTION
    "The Caching Policy name."
  DEFVAL { "None" }
  ::=  {rsNADL4PolicyEntry 23}

rsNADL4PolicyAuthenticationPolicy OBJECT-TYPE
  SYNTAX DisplayString (SIZE (1..50))
  ACCESS read-write
  STATUS mandatory
  DESCRIPTION
    "The Authentication Policy name."
  DEFVAL { "None" }
  ::=  {rsNADL4PolicyEntry 24}

rsNADL4PolicyHttpPolicy OBJECT-TYPE
  SYNTAX DisplayString (SIZE (1..50))
  ACCESS read-write
  STATUS mandatory
  DESCRIPTION
    "The Http Policy name."
  DEFVAL { "None" }
  ::=  {rsNADL4PolicyEntry 25}

rsNADL4PolicyStatus OBJECT-TYPE
    SYNTAX    RowStatus
    ACCESS    read-write
    STATUS    mandatory
    DESCRIPTION
      "Row status for this entry."
    ::= { rsNADL4PolicyEntry 26 }

rsNADL4PolicyTcpPolicy OBJECT-TYPE
	SYNTAX DisplayString (SIZE (1..50))
	ACCESS read-write
	STATUS mandatory
	DESCRIPTION
     "The Tcp Policy name."
	DEFVAL { "None" }
	::=  {rsNADL4PolicyEntry 27}



-- L4 policy statistics table

rsADL4PolicyStatsTable OBJECT-TYPE
   SYNTAX SEQUENCE OF RsADL4PolicyStatsEntry
   ACCESS not-accessible
   STATUS mandatory
   DESCRIPTION
       "A read-only table for L4 policy statistical information."
   ::= {rsADL4Policy 2}

rsADL4PolicyStatsEntry OBJECT-TYPE
   SYNTAX RsADL4PolicyStatsEntry
   ACCESS not-accessible
   STATUS  mandatory
   DESCRIPTION
       " The row definition for this table."
   INDEX  { rsADL4PolicyStatsVirtualIP,
            rsADL4PolicyStatsL4Protocol,
            rsADL4PolicyStatsDstPort,
            rsADL4PolicyStatsRangeIPFrom}
   ::= {rsADL4PolicyStatsTable 1}

RsADL4PolicyStatsEntry  ::= SEQUENCE {
      rsADL4PolicyStatsVirtualIP   InetAddress,
      rsADL4PolicyStatsL4Protocol  INTEGER,
      rsADL4PolicyStatsDstPort     INTEGER,
      rsADL4PolicyStatsRangeIPFrom InetAddress,
      rsADL4PolicyStatsMatches     Counter,
      rsADL4PolicyStatsLSMatches   Counter
  }

rsADL4PolicyStatsVirtualIP OBJECT-TYPE
   SYNTAX  InetAddress
   ACCESS  read-only
   STATUS  mandatory
   DESCRIPTION
       "Virtual destination IP address."
   ::= {rsADL4PolicyStatsEntry 1}

rsADL4PolicyStatsL4Protocol OBJECT-TYPE
    SYNTAX    INTEGER {
        tcp(1),
        udp(2),
        icmp(3),
        any(4),
        other(5)
    }
    ACCESS    read-only
    STATUS    mandatory
    DESCRIPTION
       "The L4 protocol type"
    ::= { rsADL4PolicyStatsEntry 2 }

rsADL4PolicyStatsDstPort OBJECT-TYPE
    SYNTAX  INTEGER  (0..65535)
    ACCESS  read-only
    STATUS  mandatory
    DESCRIPTION
      "Destination port. Destination port 0 means any port"
 ::=  {rsADL4PolicyStatsEntry 3}

rsADL4PolicyStatsRangeIPFrom OBJECT-TYPE
   SYNTAX  InetAddress
   ACCESS  read-only
   STATUS  mandatory
   DESCRIPTION
       "Start address of the source IP range. The 0.0.0.0 address means that source
        IP ranges are not used for that entry"
   ::= {rsADL4PolicyStatsEntry 4}

rsADL4PolicyStatsMatches OBJECT-TYPE
    SYNTAX    Counter
    ACCESS    read-only
    STATUS    mandatory
    DESCRIPTION
      "Number of total matches for this policy"
    ::= { rsADL4PolicyStatsEntry 5 }

rsADL4PolicyStatsLSMatches OBJECT-TYPE
    SYNTAX    Counter
    ACCESS    read-only
    STATUS    mandatory
    DESCRIPTION
      "Number of last second matches for this policy"
    ::= { rsADL4PolicyStatsEntry 6 }

rsNADL4PolicyStatisticsTable OBJECT-TYPE
   SYNTAX SEQUENCE OF RsNADL4PolicyStatisticsEntry
   ACCESS not-accessible
   STATUS mandatory
   DESCRIPTION
       "A read-only table for L4 policy statistical information."
   ::= {rsADL4Policy 4}

rsNADL4PolicyStatisticsEntry OBJECT-TYPE
   SYNTAX RsNADL4PolicyStatisticsEntry
   ACCESS not-accessible
   STATUS  mandatory
   DESCRIPTION
       " The row definition for this table."
   INDEX  { rsNADL4PolicyStatisticsL4PolicyName }
   ::= {rsNADL4PolicyStatisticsTable 1}

RsNADL4PolicyStatisticsEntry  ::= SEQUENCE {
      rsNADL4PolicyStatisticsL4PolicyName DisplayString,
      rsNADL4PolicyStatisticsMatches     Counter,
      rsNADL4PolicyStatisticsLSMatches   Counter,
	  rsNADL4PolicyStatisticsActiveConnections Counter
  }

rsNADL4PolicyStatisticsL4PolicyName OBJECT-TYPE
   SYNTAX  DisplayString
   ACCESS  read-only
   STATUS  mandatory
   DESCRIPTION
       "The Name of the L4 policy"
   ::= {rsNADL4PolicyStatisticsEntry 1}

rsNADL4PolicyStatisticsMatches OBJECT-TYPE
    SYNTAX    Counter
    ACCESS    read-only
    STATUS    optional
    DESCRIPTION
      "Number of total matches for this policy"
    ::= { rsNADL4PolicyStatisticsEntry 2 }

rsNADL4PolicyStatisticsLSMatches OBJECT-TYPE
    SYNTAX    Counter
    ACCESS    read-only
    STATUS    optional
    DESCRIPTION
      "Number of last second matches for this policy"
    ::= { rsNADL4PolicyStatisticsEntry 3 }

rsNADL4PolicyStatisticsActiveConnections OBJECT-TYPE
    SYNTAX    Counter
    ACCESS    read-only
    STATUS    optional
    DESCRIPTION
      "Number of active connections for this policy"
    ::= { rsNADL4PolicyStatisticsEntry 4 }

-----------------------
-- Static Clients Table
-----------------------

rsADIPv6StaticClientsTable OBJECT-TYPE
    SYNTAX SEQUENCE OF RsADIPv6StaticClientEntry
    ACCESS not-accessible
    STATUS  mandatory
    DESCRIPTION
      "Table containing the list of clients currently attached to a server."
    ::=  {rsServerDispatcher 146}

rsADIPv6StaticClientEntry OBJECT-TYPE
    SYNTAX RsADIPv6StaticClientEntry
    ACCESS not-accessible
    STATUS  mandatory
    DESCRIPTION
       " The row definition for this table."
   INDEX { rsADIPv6StaticClientFarmName,
           rsADIPv6StaticClientAddr}
    ::=  {rsADIPv6StaticClientsTable 1}

RsADIPv6StaticClientEntry ::= SEQUENCE {
  rsADIPv6StaticClientFarmName            DisplayString,
  rsADIPv6StaticClientAddr                InetAddress,
  rsADIPv6StaticClientStatus              RowStatus,
  rsADIPv6AttachedServerAddr        	  IpAddress,
  rsADIPv6AttachedServerPort        	  INTEGER,
  rsADIPv6StaticClientLastActivityTime    INTEGER,
  rsADIPv6StaticClientAttachmentTime      INTEGER,
  rsADIPv6StaticClientType                INTEGER
}

rsADIPv6StaticClientFarmName OBJECT-TYPE
    SYNTAX  DisplayString (SIZE(1..50))
    ACCESS  read-only
    STATUS  mandatory
    DESCRIPTION
     "The name of the WEB farm through which the client connected."
    ::=  {rsADIPv6StaticClientEntry 1}

rsADIPv6StaticClientAddr  OBJECT-TYPE
    SYNTAX  InetAddress
    ACCESS  read-only
    STATUS  mandatory
    DESCRIPTION
      "Client IP Address."
    ::=  {rsADIPv6StaticClientEntry 2}

rsADIPv6StaticClientStatus OBJECT-TYPE
    SYNTAX  RowStatus
    ACCESS  read-write
    STATUS  mandatory
    DESCRIPTION
       "This variable indicates the administrative status of this entry.
        Used to delete an entry of this table."
    ::=  {rsADIPv6StaticClientEntry 3}

rsADIPv6AttachedServerAddr OBJECT-TYPE
    SYNTAX  IpAddress
    ACCESS  read-write
    STATUS  mandatory
    DESCRIPTION
      "this filed is replaced by rsADIPv6AttachedServerIPv6Addr"
    ::=  {rsADIPv6StaticClientEntry 4}

rsADIPv6AttachedServerPort  OBJECT-TYPE
    SYNTAX	INTEGER
    ACCESS  read-write
    STATUS  mandatory
	DESCRIPTION
        "The port of the server currently serving this client."
	DEFVAL {0}
    ::= { rsADIPv6StaticClientEntry 5}

rsADIPv6StaticClientLastActivityTime  OBJECT-TYPE
    SYNTAX  INTEGER
    ACCESS  read-only
    STATUS  mandatory
    DESCRIPTION
      "Indicates when the last frame from the client was dispatched.
       Measured in seconds since device re-initialization."
    ::=  {rsADIPv6StaticClientEntry 6}

rsADIPv6StaticClientAttachmentTime OBJECT-TYPE
    SYNTAX  INTEGER
    ACCESS  read-only
    STATUS  mandatory
    DESCRIPTION
      "Indicates when the client was attached.
       Measured in seconds since device re-initialization."
    ::=  {rsADIPv6StaticClientEntry 7}

rsADIPv6StaticClientType OBJECT-TYPE
    SYNTAX INTEGER {
                    dynamic(1),
                    static(2),
             	    nat(3),
                    clientnat(4),
                    outbound(5)
                    }
    ACCESS  read-write
    STATUS  mandatory
    DESCRIPTION
              "This variable indicates the administrative type of this entry."
    ::=  { rsADIPv6StaticClientEntry 8}


rsNADStaticClientsTable OBJECT-TYPE
    SYNTAX SEQUENCE OF RsNADStaticClientEntry
    ACCESS not-accessible
    STATUS  mandatory
    DESCRIPTION
      "Table containing the list of clients currently attached to a server."
    ::=  {rsServerDispatcher 165}

rsNADStaticClientEntry OBJECT-TYPE
    SYNTAX RsNADStaticClientEntry
    ACCESS not-accessible
    STATUS  mandatory
    DESCRIPTION
       " The row definition for this table."
   INDEX { rsNADStaticClientFarmName,
		   rsNADStaticClientAddrType,
           rsNADStaticClientAddr}
    ::=  {rsNADStaticClientsTable 1}

RsNADStaticClientEntry ::= SEQUENCE {
  rsNADStaticClientFarmName            DisplayString,
  rsNADStaticClientAddrType            InetAddressType,
  rsNADStaticClientAddr                InetAddress,
  rsNADStaticClientAttachedServerName  DisplayString,
  rsNADStaticClientLastActivityTime    INTEGER,
  rsNADStaticClientAttachmentTime      INTEGER,
  rsNADStaticClientType                INTEGER,
  rsNADStaticClientStatus              RowStatus
}

rsNADStaticClientFarmName OBJECT-TYPE
    SYNTAX  DisplayString (SIZE(1..50))
    ACCESS  read-only
    STATUS  mandatory
    DESCRIPTION
     "The name of the WEB farm through which the client connected."
    ::=  {rsNADStaticClientEntry 1}

rsNADStaticClientAddrType  OBJECT-TYPE
    SYNTAX  InetAddressType
    ACCESS  read-only
    STATUS  mandatory
    DESCRIPTION
      "The IP address type of Client IP."
    ::=  {rsNADStaticClientEntry 2}

rsNADStaticClientAddr  OBJECT-TYPE
    SYNTAX  InetAddress
    ACCESS  read-only
    STATUS  mandatory
    DESCRIPTION
      "Client IP Address."
    ::=  {rsNADStaticClientEntry 3}

rsNADStaticClientAttachedServerName OBJECT-TYPE
    SYNTAX  DisplayString (SIZE(1..50))
    ACCESS  read-write
    STATUS  mandatory
    DESCRIPTION
      "The Name of the server currently serving this client."
    ::=  {rsNADStaticClientEntry 4}

rsNADStaticClientLastActivityTime  OBJECT-TYPE
    SYNTAX  INTEGER
    ACCESS  read-only
    STATUS  optional
    DESCRIPTION
      "Indicates when the last frame from the client was dispatched.
       Measured in seconds since device re-initialization."
    ::=  {rsNADStaticClientEntry 5}

rsNADStaticClientAttachmentTime OBJECT-TYPE
    SYNTAX  INTEGER
    ACCESS  read-only
    STATUS  optional
    DESCRIPTION
      "Indicates when the client was attached.
       Measured in seconds since device re-initialization."
    ::=  {rsNADStaticClientEntry 6}

rsNADStaticClientType OBJECT-TYPE
    SYNTAX INTEGER {
                    dynamic(1),
                    static(2),
             	    nat(3),
                    clientnat(4),
                    outbound(5)
                    }
    ACCESS  read-write
    STATUS  mandatory
    DESCRIPTION
              "The client type."
	DEFVAL { 2 }
    ::=  { rsNADStaticClientEntry 7}

rsNADStaticClientStatus OBJECT-TYPE
    SYNTAX  RowStatus
    ACCESS  read-write
    STATUS  mandatory
    DESCRIPTION
       "This variable indicates the administrative status of this entry.
        Used to delete an entry of this table."
    ::=  {rsNADStaticClientEntry 8}

---------------------------
-- IPv6 CLIENT VIEW FILTERS
---------------------------


rsADIPv6ClientsViewTable  OBJECT-TYPE
   SYNTAX  SEQUENCE OF RsADIPv6ClientsViewEntry
   ACCESS  not-accessible
   STATUS  mandatory
   DESCRIPTION
         "A table holding information for defining client table views (filtering)"
   ::= { rsServerDispatcher 147 }


rsADIPv6ClientsViewEntry OBJECT-TYPE
   SYNTAX  RsADIPv6ClientsViewEntry
   ACCESS  not-accessible
   STATUS  mandatory
   DESCRIPTION
         "An entry in the client views table"
   INDEX  {rsADIPv6ClientsViewIndex}
   ::= { rsADIPv6ClientsViewTable 1 }

RsADIPv6ClientsViewEntry   ::= SEQUENCE {
     rsADIPv6ClientsViewIndex             INTEGER,
     rsADIPv6ClientsViewSrcAddrFrom       InetAddress,
     rsADIPv6ClientsViewSrcAddrTo         InetAddress,
     rsADIPv6ClientsViewDstAddrFrom       InetAddress,
     rsADIPv6ClientsViewDstAddrTo         InetAddress,
     rsADIPv6ClientsViewSrcPortFrom       INTEGER,
     rsADIPv6ClientsViewSrcPortTo         INTEGER,
     rsADIPv6ClientsViewDstPortFrom       INTEGER,
     rsADIPv6ClientsViewDstPortTo         INTEGER,
     rsADIPv6ClientsViewServerIPv4Addr    IpAddress,
	 rsADIPv6ClientsViewServerIPv6Addr	  InetAddress,
     rsADIPv6ClientsViewClientType        DisplayString,
     rsADIPv6ClientsViewAdminStatus       INTEGER,
     rsADIPv6ClientsViewStatus            RowStatus,
     rsADIPv6ClientsViewAction            INTEGER,
     rsADIPv6ClientsViewActionFeedback    DisplayString,
     rsADIPv6ClientsViewVlanTag           INTEGER,
     rsADIPv6ClientsViewFarmName          DisplayString
   }

rsADIPv6ClientsViewIndex OBJECT-TYPE
   SYNTAX  INTEGER
   ACCESS  read-only
   STATUS  mandatory
   DESCRIPTION
         "The index of this entry in the views table."
   ::= { rsADIPv6ClientsViewEntry 1 }

rsADIPv6ClientsViewSrcAddrFrom  OBJECT-TYPE
    SYNTAX InetAddress
    ACCESS  read-write
    STATUS  mandatory
    DESCRIPTION
        "The IP Address of the low boundary of the source interval."
    ::=  { rsADIPv6ClientsViewEntry 2 }

rsADIPv6ClientsViewSrcAddrTo  OBJECT-TYPE
    SYNTAX InetAddress
    ACCESS  read-write
    STATUS  mandatory
    DESCRIPTION
        "The IP Address of the high boundary of the source interval."
    ::=  { rsADIPv6ClientsViewEntry 3 }


rsADIPv6ClientsViewDstAddrFrom  OBJECT-TYPE
    SYNTAX InetAddress
    ACCESS  read-write
    STATUS  mandatory
    DESCRIPTION
        "The IP Address of the low boundary of the requested interval."
    ::=  { rsADIPv6ClientsViewEntry 4 }

rsADIPv6ClientsViewDstAddrTo  OBJECT-TYPE
    SYNTAX InetAddress
    ACCESS  read-write
    STATUS  mandatory
    DESCRIPTION
        "The IP Address of the high boundary of the requested interval."
    ::=  { rsADIPv6ClientsViewEntry 5 }

rsADIPv6ClientsViewSrcPortFrom  OBJECT-TYPE
    SYNTAX INTEGER (0..65535)
    ACCESS  read-write
    STATUS  mandatory
    DESCRIPTION
        "The TCP/UDP port of the low boundary of the source interval."
    ::=  { rsADIPv6ClientsViewEntry 6 }

rsADIPv6ClientsViewSrcPortTo  OBJECT-TYPE
    SYNTAX INTEGER (0..65535)
    ACCESS  read-write
    STATUS  mandatory
    DESCRIPTION
        "The TCP/UDP port of the high boundary of the source interval."
    ::=  { rsADIPv6ClientsViewEntry 7 }

rsADIPv6ClientsViewDstPortFrom  OBJECT-TYPE
    SYNTAX INTEGER (0..65535)
    ACCESS  read-write
    STATUS  mandatory
    DESCRIPTION
        "The TCP/UDP port of the low boundary of the requested interval."
    ::=  { rsADIPv6ClientsViewEntry 8 }

rsADIPv6ClientsViewDstPortTo  OBJECT-TYPE
    SYNTAX INTEGER (0..65535)
    ACCESS  read-write
    STATUS  mandatory
    DESCRIPTION
        "The TCP/UDP port of the high boundary of the requested interval."
    ::=  { rsADIPv6ClientsViewEntry 9 }

rsADIPv6ClientsViewServerIPv4Addr  OBJECT-TYPE
    SYNTAX IpAddress
    ACCESS  read-write
    STATUS  mandatory
    DESCRIPTION
        "The client IP Address of the server."
    ::=  { rsADIPv6ClientsViewEntry 10 }

rsADIPv6ClientsViewServerIPv6Addr  OBJECT-TYPE
    SYNTAX InetAddress
    ACCESS  read-write
    STATUS  mandatory
    DESCRIPTION
        "The client IP Address of the server."
    ::=  { rsADIPv6ClientsViewEntry 11 }

rsADIPv6ClientsViewClientType OBJECT-TYPE
   SYNTAX  DisplayString (SIZE(0..20))
   ACCESS  read-write
   STATUS  mandatory
   DESCRIPTION
         "The client type"
   ::= { rsADIPv6ClientsViewEntry 12 }

rsADIPv6ClientsViewAdminStatus  OBJECT-TYPE
    SYNTAX INTEGER {
           enabled(1),
           disabled(2)
    }
    ACCESS  read-write
    STATUS  mandatory
    DESCRIPTION
        "Administrative status of the view entry
	 enabled - activates the view.
         disabled - inactive the view."
    DEFVAL { 1 }
    ::=  { rsADIPv6ClientsViewEntry 13 }

rsADIPv6ClientsViewStatus  OBJECT-TYPE
   SYNTAX  RowStatus
   ACCESS  read-write
   STATUS  mandatory
   DESCRIPTION
         "It is used to create and delete a filter"
   ::= { rsADIPv6ClientsViewEntry 14 }

rsADIPv6ClientsViewAction OBJECT-TYPE
   SYNTAX INTEGER {
        noAction(1),
        deleteMatching(2),
        countMatching(3)
   }
   ACCESS  read-write
   STATUS  mandatory
   DESCRIPTION
         "The type of action to be performed on entries matching this filter."
   DEFVAL { 1 }
   ::= { rsADIPv6ClientsViewEntry 15 }

rsADIPv6ClientsViewActionFeedback OBJECT-TYPE
   SYNTAX  DisplayString (SIZE(0..240))
   ACCESS  read-only
   STATUS  mandatory
   DESCRIPTION
         "Message containing feedback for the action taken."
   ::= { rsADIPv6ClientsViewEntry 16 }

rsADIPv6ClientsViewVlanTag OBJECT-TYPE
   SYNTAX INTEGER (0..4095)
   ACCESS  read-write
   STATUS  mandatory
   DESCRIPTION
         "802.1q VLAN tag associated with the client entry. 0 - no tag."
   DEFVAL { 0 }
   ::= { rsADIPv6ClientsViewEntry 17 }

rsADIPv6ClientsViewFarmName  OBJECT-TYPE
    SYNTAX  DisplayString (SIZE (0..50))
    ACCESS  read-write
    STATUS  mandatory
    DESCRIPTION
        "The client's farm name."
    ::=  { rsADIPv6ClientsViewEntry 18 }



------------------------------------
--	IPv6 Clients Entry
-----------------------------------

rsADIPv6ClientsTable  OBJECT-TYPE
   SYNTAX  SEQUENCE OF RsADIPv6ClientsEntry
   ACCESS  not-accessible
   STATUS  mandatory
   DESCRIPTION
         "A table holding the device filtered client table"
   ::= { rsServerDispatcher 143 }

rsADIPv6ClientsEntry OBJECT-TYPE
   SYNTAX  RsADIPv6ClientsEntry
   ACCESS  not-accessible
   STATUS  mandatory
   DESCRIPTION
         "An entry in the client table"
   INDEX  {rsADIPv6ClientsIndex}
   ::= { rsADIPv6ClientsTable 1 }

RsADIPv6ClientsEntry   ::= SEQUENCE {
     rsADIPv6ClientsIndex                 INTEGER,
     rsADIPv6ClientsSourceAddr            InetAddress,
     rsADIPv6ClientsSourcePort            INTEGER,
     rsADIPv6ClientsRequestedAddr         InetAddress,
     rsADIPv6ClientsRequestedPort         INTEGER,
     rsADIPv6ClientsFarmAddr              IpAddress,
     rsADIPv6ClientsServerAddr            IpAddress,
     rsADIPv6ClientsServerPort            INTEGER,
     rsADIPv6ClientsAttachedTime          INTEGER,
     rsADIPv6ClientsNATaddr               IpAddress,
     rsADIPv6ClientsNATPort               INTEGER,
     rsADIPv6ClientsTimeToLive            INTEGER,
     rsADIPv6ClientsClientType            DisplayString,
     rsADIPv6ClientsClientMode            DisplayString,
     rsADIPv6ClientsUserData1             DisplayString,
     rsADIPv6ClientsUserData2             DisplayString,
     rsADIPv6ClientsStatus                RowStatus
   }

rsADIPv6ClientsIndex OBJECT-TYPE
   SYNTAX  INTEGER
   ACCESS  read-only
   STATUS  mandatory
   DESCRIPTION
         "The index of this entry in the table."
   ::= { rsADIPv6ClientsEntry 1 }

rsADIPv6ClientsSourceAddr  OBJECT-TYPE
    SYNTAX InetAddress
    ACCESS  read-write
    STATUS  mandatory
    DESCRIPTION
        "The client source address."
    ::=  { rsADIPv6ClientsEntry 2 }


rsADIPv6ClientsSourcePort OBJECT-TYPE
   SYNTAX  INTEGER
   ACCESS  read-write
   STATUS  mandatory
   DESCRIPTION
         "The clinet source port."
   ::= { rsADIPv6ClientsEntry 3 }

rsADIPv6ClientsRequestedAddr  OBJECT-TYPE
    SYNTAX InetAddress
    ACCESS  read-write
    STATUS  mandatory
    DESCRIPTION
        "The client requested address."
    ::=  {rsADIPv6ClientsEntry 4 }

rsADIPv6ClientsRequestedPort  OBJECT-TYPE
    SYNTAX INTEGER
    ACCESS  read-write
    STATUS  mandatory
    DESCRIPTION
        "The client requested TCP/UDP Port."
    ::=  {rsADIPv6ClientsEntry 5 }

rsADIPv6ClientsFarmAddr  OBJECT-TYPE
    SYNTAX IpAddress
    ACCESS  read-only
    STATUS  mandatory
    DESCRIPTION
        "IP Address of the farm the client trough which the client connected."
    ::=  {rsADIPv6ClientsEntry 6 }

rsADIPv6ClientsServerAddr  OBJECT-TYPE
    SYNTAX IpAddress
    ACCESS  read-only
    STATUS  mandatory
    DESCRIPTION
        "IP Address of server currently serving this client."
    ::=  {rsADIPv6ClientsEntry 7 }

rsADIPv6ClientsServerPort  OBJECT-TYPE
    SYNTAX INTEGER
    ACCESS  read-only
    STATUS  mandatory
    DESCRIPTION
        "TCP/UDP Port of server currently serving this client."
    ::=  {rsADIPv6ClientsEntry 8 }

rsADIPv6ClientsAttachedTime  OBJECT-TYPE
    SYNTAX INTEGER
    ACCESS  read-only
    STATUS  mandatory
    DESCRIPTION
        "Indicates when the client was attached.
         Measured in seconds since device re-initialization."
    ::=  {rsADIPv6ClientsEntry 9 }

rsADIPv6ClientsNATaddr  OBJECT-TYPE
    SYNTAX IpAddress
    ACCESS  read-only
    STATUS  mandatory
    DESCRIPTION
        "NAT IP Address of the client."
    ::=  {rsADIPv6ClientsEntry 10 }

rsADIPv6ClientsNATPort  OBJECT-TYPE
    SYNTAX INTEGER
    ACCESS  read-only
    STATUS  mandatory
    DESCRIPTION
        "NAT TCP/UDP port of the client."
    ::=  {rsADIPv6ClientsEntry 11 }

rsADIPv6ClientsTimeToLive  OBJECT-TYPE
    SYNTAX INTEGER
    ACCESS  read-only
    STATUS  mandatory
    DESCRIPTION
        "This variable measures the client time to live in seconds."
    ::=  {rsADIPv6ClientsEntry 12 }

rsADIPv6ClientsClientType OBJECT-TYPE
   SYNTAX  DisplayString (SIZE(1..20))
   ACCESS  read-only
   STATUS  mandatory
   DESCRIPTION
         "This variable indicates the administrative type of this entry."
   ::= { rsADIPv6ClientsEntry 13 }

rsADIPv6ClientsClientMode OBJECT-TYPE
   SYNTAX  DisplayString (SIZE(1..20))
   ACCESS  read-only
   STATUS  mandatory
   DESCRIPTION
         "This variable indicates how a single client's sessions are
         handled in the client table."
   ::= { rsADIPv6ClientsEntry 14 }

rsADIPv6ClientsUserData1 OBJECT-TYPE
   SYNTAX  DisplayString (SIZE(0..240))
   ACCESS  read-only
   STATUS  mandatory
   DESCRIPTION
         "This variable holds miscellaneous client information."
   ::= { rsADIPv6ClientsEntry 15 }

rsADIPv6ClientsUserData2 OBJECT-TYPE
   SYNTAX  DisplayString (SIZE(0..240))
   ACCESS  read-only
   STATUS  mandatory
   DESCRIPTION
         "This variable holds miscellaneous client information."
   ::= { rsADIPv6ClientsEntry 16 }

rsADIPv6ClientsStatus  OBJECT-TYPE
   SYNTAX  RowStatus
   ACCESS  read-write
   STATUS  mandatory
   DESCRIPTION
         "It is used to delete an entry"
   ::= { rsADIPv6ClientsEntry 17 }


rsNADClientTable  OBJECT-TYPE
   SYNTAX  SEQUENCE OF RsNADClientEntry
   ACCESS  not-accessible
   STATUS  mandatory
   DESCRIPTION
         "A table holding the device filtered client table"
   ::= { rsServerDispatcher 149 }

rsNADClientEntry OBJECT-TYPE
   SYNTAX  RsNADClientEntry
   ACCESS  not-accessible
   STATUS  mandatory
   DESCRIPTION
         "An entry in the client table"
   INDEX  {rsNADClientIndex}
   ::= { rsNADClientTable 1 }

RsNADClientEntry   ::= SEQUENCE {
     rsNADClientIndex                 INTEGER,
     rsNADClientSourceAddrType        InetAddressType,
     rsNADClientSourceAddr            InetAddress,
     rsNADClientSourcePort            INTEGER,
     rsNADClientRequestedAddrType     InetAddressType,
     rsNADClientRequestedAddr         InetAddress,
     rsNADClientRequestedPort         INTEGER,
     rsNADClientFarmName              DisplayString,
     rsNADClientServerAddrType        InetAddressType,
     rsNADClientServerAddr            InetAddress,
     rsNADClientServerPort            INTEGER,
     rsNADClientNATAddrType           InetAddressType,
     rsNADClientNATAddr               InetAddress,
     rsNADClientNATPort               INTEGER,
     rsNADClientAttachedTime          INTEGER,
     rsNADClientTimeToLive            INTEGER,
     rsNADClientClientType            DisplayString,
     rsNADClientClientMode            DisplayString,
     rsNADClientUserData1             DisplayString,
     rsNADClientUserData2             DisplayString,
     rsNADClientStatus                RowStatus
   }

rsNADClientIndex OBJECT-TYPE
   SYNTAX  INTEGER
   ACCESS  read-only
   STATUS  mandatory
   DESCRIPTION
         "The index of this entry in the table."
   ::= { rsNADClientEntry 1 }

rsNADClientSourceAddrType  OBJECT-TYPE
    SYNTAX InetAddressType
    ACCESS  read-only
    STATUS  optional
    DESCRIPTION
        "The IP address type of client source address."
    ::=  { rsNADClientEntry 2 }

rsNADClientSourceAddr  OBJECT-TYPE
    SYNTAX InetAddress
    ACCESS  read-only
    STATUS  optional
    DESCRIPTION
        "The client source address."
    ::=  { rsNADClientEntry 3 }


rsNADClientSourcePort OBJECT-TYPE
   SYNTAX  INTEGER (0..65535)
   ACCESS  read-only
   STATUS  optional
   DESCRIPTION
         "The clinet source port."
   ::= { rsNADClientEntry 4 }

rsNADClientRequestedAddrType  OBJECT-TYPE
    SYNTAX InetAddressType
    ACCESS  read-only
    STATUS  optional
    DESCRIPTION
        "The IP address type of client requested address."
    ::=  {rsNADClientEntry 5 }

rsNADClientRequestedAddr  OBJECT-TYPE
    SYNTAX InetAddress
    ACCESS  read-only
    STATUS  optional
    DESCRIPTION
        "The client requested address."
    ::=  {rsNADClientEntry 6 }

rsNADClientRequestedPort  OBJECT-TYPE
    SYNTAX INTEGER (0..65535)
    ACCESS  read-only
    STATUS  optional
    DESCRIPTION
        "The client requested TCP/UDP Port."
    ::=  {rsNADClientEntry 7 }

rsNADClientFarmName OBJECT-TYPE
   SYNTAX  DisplayString (SIZE(1..50))
   ACCESS  read-only
   STATUS  optional
   DESCRIPTION
         "The Name of the Farm"
   ::= { rsNADClientEntry 8 }


rsNADClientServerAddrType  OBJECT-TYPE
    SYNTAX InetAddressType
    ACCESS  read-only
    STATUS  optional
    DESCRIPTION
        "The Type of IP Address of server currently serving this client."
    ::=  {rsNADClientEntry 9 }

rsNADClientServerAddr  OBJECT-TYPE
    SYNTAX InetAddress
    ACCESS  read-only
    STATUS  optional
    DESCRIPTION
        "IP Address of server currently serving this client."
    ::=  {rsNADClientEntry 10 }

rsNADClientServerPort  OBJECT-TYPE
    SYNTAX INTEGER (0..65535)
    ACCESS  read-only
    STATUS  optional
    DESCRIPTION
        "TCP/UDP Port of server currently serving this client."
    ::=  {rsNADClientEntry 11}

rsNADClientNATAddrType  OBJECT-TYPE
    SYNTAX InetAddressType
    ACCESS  read-only
    STATUS  optional
    DESCRIPTION
        "The IP address type of NAT IP address"
    ::=  {rsNADClientEntry 12 }

rsNADClientNATAddr  OBJECT-TYPE
    SYNTAX InetAddress
    ACCESS  read-only
    STATUS  optional
    DESCRIPTION
        "The NAT IP address"
    ::=  {rsNADClientEntry 13 }

rsNADClientNATPort  OBJECT-TYPE
    SYNTAX INTEGER (0..65535)
    ACCESS  read-only
    STATUS  optional
    DESCRIPTION
        "NAT TCP/UDP port of the client."
    ::=  {rsNADClientEntry 14 }

rsNADClientAttachedTime  OBJECT-TYPE
    SYNTAX INTEGER
    ACCESS  read-only
    STATUS  optional
    DESCRIPTION
        "Indicates when the client was attached.
         Measured in seconds since device re-initialization."
    ::=  {rsNADClientEntry 15}

rsNADClientTimeToLive  OBJECT-TYPE
    SYNTAX INTEGER
    ACCESS  read-only
    STATUS  optional
    DESCRIPTION
        "This variable measures the client time to live in seconds."
    ::=  {rsNADClientEntry 16 }

rsNADClientClientType OBJECT-TYPE
   SYNTAX  DisplayString (SIZE(1..20))
   ACCESS  read-only
   STATUS  optional
   DESCRIPTION
         "This variable indicates the administrative type of this entry."
   ::= { rsNADClientEntry 17 }

rsNADClientClientMode OBJECT-TYPE
   SYNTAX  DisplayString (SIZE(1..20))
   ACCESS  read-only
   STATUS  optional
   DESCRIPTION
         "This variable indicates how a single client's sessions are
         handled in the client table."
   ::= { rsNADClientEntry 18 }

rsNADClientUserData1 OBJECT-TYPE
   SYNTAX  DisplayString (SIZE(0..240))
   ACCESS  read-only
   STATUS  optional
   DESCRIPTION
         "This variable holds miscellaneous client information."
   ::= { rsNADClientEntry 19 }

rsNADClientUserData2 OBJECT-TYPE
   SYNTAX  DisplayString (SIZE(0..240))
   ACCESS  read-only
   STATUS  optional
   DESCRIPTION
         "This variable holds miscellaneous client information."
   ::= { rsNADClientEntry 20 }

rsNADClientStatus  OBJECT-TYPE
   SYNTAX  RowStatus
   ACCESS  read-write
   STATUS  mandatory
   DESCRIPTION
         "It is used to delete an entry"
   ::= { rsNADClientEntry 21 }


------------------------------------------
-- IPv6 ADPersistentL7SwitchingClientTable
------------------------------------------

rsADIPv6PersistentL7SwitchingClientTable OBJECT-TYPE
    SYNTAX SEQUENCE OF RsADIPv6PersistentL7SwitchingClientEntry
    ACCESS not-accessible
    STATUS  mandatory
    DESCRIPTION
      "Table containing the list of client table entries which use the Persistent L7 switching  feature"
    ::=  {rsWSDPersistentL7Switching 6}

rsADIPv6PersistentL7SwitchingClientEntry OBJECT-TYPE
    SYNTAX RsADIPv6PersistentL7SwitchingClientEntry
    ACCESS not-accessible
    STATUS  mandatory
    DESCRIPTION
       " The row definition for this table."
   INDEX { rsADIPv6PrsstL7SuperFarmAddr,
           rsADIPv6PrsstL7FarmName,
		   rsADIPv6PrsstL7ClientAddr,
		   rsADIPv6PrsstL7AttachedServerAddr,
           rsADIPv6PrsstL7AttachedServerPort,
		   rsADIPv6PrsstL7SrcPort }
    ::=  {rsADIPv6PersistentL7SwitchingClientTable 1}

RsADIPv6PersistentL7SwitchingClientEntry ::= SEQUENCE {
  rsADIPv6PrsstL7SuperFarmAddr         InetAddress,
  rsADIPv6PrsstL7FarmName              DisplayString,
  rsADIPv6PrsstL7ClientAddr            InetAddress,
  rsADIPv6PrsstL7AttachedServerAddr    IpAddress,
  rsADIPv6PrsstL7AttachedServerPort    INTEGER,
  rsADIPv6PrsstL7SrcPort               INTEGER,
  rsADIPv6PrsstL7DstPort               INTEGER,
  rsADIPv6SharedConnectionCounter      INTEGER
}

rsADIPv6PrsstL7SuperFarmAddr OBJECT-TYPE
    SYNTAX  InetAddress
    ACCESS  read-only
    STATUS  mandatory
    DESCRIPTION
     "Superfarm IP Address."
    ::=  {rsADIPv6PersistentL7SwitchingClientEntry 1}

rsADIPv6PrsstL7FarmName OBJECT-TYPE
    SYNTAX  DisplayString (SIZE (1..50))
    ACCESS  read-only
    STATUS  mandatory
    DESCRIPTION
     "Farm name."
    ::=  {rsADIPv6PersistentL7SwitchingClientEntry 2}

rsADIPv6PrsstL7ClientAddr OBJECT-TYPE
    SYNTAX  InetAddress
    ACCESS  read-only
    STATUS  mandatory
    DESCRIPTION
     "Client IP Address."
    ::=  {rsADIPv6PersistentL7SwitchingClientEntry 3}


rsADIPv6PrsstL7AttachedServerAddr OBJECT-TYPE
    SYNTAX  IpAddress
    ACCESS  read-only
    STATUS  mandatory
    DESCRIPTION
     "Server IP Address."
    ::=  {rsADIPv6PersistentL7SwitchingClientEntry 4}

rsADIPv6PrsstL7AttachedServerPort OBJECT-TYPE
    SYNTAX  INTEGER
    ACCESS  read-only
    STATUS  mandatory
    DESCRIPTION
     "Server Port."
    ::=  {rsADIPv6PersistentL7SwitchingClientEntry 5}

rsADIPv6PrsstL7SrcPort OBJECT-TYPE
    SYNTAX  INTEGER
    ACCESS  read-only
    STATUS  mandatory
    DESCRIPTION
     "Source port."
    ::=  {rsADIPv6PersistentL7SwitchingClientEntry 6}

rsADIPv6PrsstL7DstPort OBJECT-TYPE
    SYNTAX  INTEGER
    ACCESS  read-only
    STATUS  mandatory
    DESCRIPTION
     "destination port."
    ::=  {rsADIPv6PersistentL7SwitchingClientEntry 7}

rsADIPv6SharedConnectionCounter OBJECT-TYPE
    SYNTAX  INTEGER
    ACCESS  read-only
    STATUS  mandatory
    DESCRIPTION
     "Number of open server connections."
    ::=  {rsADIPv6PersistentL7SwitchingClientEntry 8}

------------------------------------------
-- IPv6 NADPersistentL7SwitchingClientTable
------------------------------------------

rsNADPersistentL7ClientTable OBJECT-TYPE
    SYNTAX SEQUENCE OF RsNADPersistL7ClientEntry
    ACCESS not-accessible
    STATUS  mandatory
    DESCRIPTION
      "Table containing the list of client table entries which use the Persistent L7 switching  feature"
    ::=  {rsWSDPersistentL7Switching 7}

rsNADPersistL7ClientEntry OBJECT-TYPE
    SYNTAX RsNADPersistL7ClientEntry
    ACCESS not-accessible
    STATUS  mandatory
    DESCRIPTION
       " The row definition for this table."
   INDEX { 	rsNADHPSuperFarmAddrType,
		rsNADHPSuperFarmAddr,
		rsNADHPFarmName,
		rsNADHPClientAddrType,
		rsNADHPClientAddr,
		rsNADHPAttachedServerAddrType,
                rsNADHPAttachedServerAddr,
                rsNADHPAttachedServerPort,
		rsNADHPSrcPort }
    ::=  {rsNADPersistentL7ClientTable 1}

RsNADPersistL7ClientEntry ::= SEQUENCE {
  rsNADHPSuperFarmAddrType  	    InetAddressType,
  rsNADHPSuperFarmAddr         	    InetAddress,
  rsNADHPFarmName              	    DisplayString,
  rsNADHPClientAddrType             InetAddressType,
  rsNADHPClientAddr                 InetAddress,
  rsNADHPAttachedServerAddrType     InetAddressType,
  rsNADHPAttachedServerAddr         InetAddress,
  rsNADHPAttachedServerPort         INTEGER,
  rsNADHPSrcPort                    INTEGER,
  rsNADHPDstPort                    INTEGER,
  rsNADSharedConnectionCounter      INTEGER
}

rsNADHPSuperFarmAddrType OBJECT-TYPE
    SYNTAX  InetAddressType
    ACCESS  read-only
    STATUS  mandatory
    DESCRIPTION
     "The IP address type of Virtual IP Address."
    ::=  {rsNADPersistL7ClientEntry 1}

rsNADHPSuperFarmAddr OBJECT-TYPE
    SYNTAX  InetAddress
    ACCESS  read-only
    STATUS  mandatory
    DESCRIPTION
     "Virtual IP Address."
    ::=  {rsNADPersistL7ClientEntry 2}

rsNADHPFarmName OBJECT-TYPE
    SYNTAX  DisplayString (SIZE (1..50))
    ACCESS  read-only
    STATUS  mandatory
    DESCRIPTION
     "Farm name."
    ::=  {rsNADPersistL7ClientEntry 3}


rsNADHPClientAddrType OBJECT-TYPE
    SYNTAX  InetAddressType
    ACCESS  read-only
    STATUS  mandatory
    DESCRIPTION
     "The IP address type of Client IP."
    ::=  {rsNADPersistL7ClientEntry 4}

rsNADHPClientAddr OBJECT-TYPE
    SYNTAX  InetAddress
    ACCESS  read-only
    STATUS  mandatory
    DESCRIPTION
     "Client IP Address."
    ::=  {rsNADPersistL7ClientEntry 5}

rsNADHPAttachedServerAddrType OBJECT-TYPE
    SYNTAX  InetAddressType
    ACCESS  read-only
    STATUS  mandatory
    DESCRIPTION
     "The IP address type of Server IP."
    ::=  {rsNADPersistL7ClientEntry 6}

rsNADHPAttachedServerAddr OBJECT-TYPE
    SYNTAX  InetAddress
    ACCESS  read-only
    STATUS  mandatory
    DESCRIPTION
     "Server IP Address."
    ::=  {rsNADPersistL7ClientEntry 7}

rsNADHPAttachedServerPort OBJECT-TYPE
    SYNTAX  INTEGER
    ACCESS  read-only
    STATUS  mandatory
    DESCRIPTION
     "Server Port."
    ::=  {rsNADPersistL7ClientEntry 8}

rsNADHPSrcPort OBJECT-TYPE
    SYNTAX  INTEGER
    ACCESS  read-only
    STATUS  mandatory
    DESCRIPTION
     "Source port."
    ::=  {rsNADPersistL7ClientEntry 9}


rsNADHPDstPort OBJECT-TYPE
    SYNTAX  INTEGER
    ACCESS  read-only
    STATUS  optional
    DESCRIPTION
     "destination port."
    ::=  {rsNADPersistL7ClientEntry 10}

rsNADSharedConnectionCounter OBJECT-TYPE
    SYNTAX  INTEGER
    ACCESS  read-only
    STATUS  optional
    DESCRIPTION
     "Number of open server connections."
    ::=  {rsNADPersistL7ClientEntry 11}

rsNADMirrorActiveAddressType OBJECT-TYPE
    SYNTAX  InetAddressType
    ACCESS  read-only
    STATUS  mandatory
    DESCRIPTION
      "The IP address Type of the active device."
    ::=  {rsServerDispatcher 167}

rsNADMirrorActiveAddress OBJECT-TYPE
    SYNTAX  InetAddress
    ACCESS  read-write
    STATUS  mandatory
    DESCRIPTION
      "The IP address of the active device."
    ::=  {rsServerDispatcher 169}

rsNADClientsViewTable  OBJECT-TYPE
   SYNTAX  SEQUENCE OF RsNADClientsViewEntry
   ACCESS  not-accessible
   STATUS  mandatory
   DESCRIPTION
         "A table holding information for defining client table views (filtering)"
   ::= { rsServerDispatcher 168 }

rsNADConnectivityCheckLongUrlTable OBJECT-TYPE
   SYNTAX SEQUENCE OF RsNADConnectivityCheckLongUrlEntry
   ACCESS not-accessible
   STATUS mandatory
   DESCRIPTION
          "In this table the AppDirector saves the Connectivity
           Check long URL per server farm."
   ::= {rsServerDispatcher 179}

rsNADConnectivityCheckLongUrlEntry OBJECT-TYPE
    SYNTAX RsNADConnectivityCheckLongUrlEntry
    ACCESS not-accessible
    STATUS  mandatory
    DESCRIPTION
       " The row definition for this table."
  INDEX  {rsNADFarmNameForLongUrl}
   ::= {rsNADConnectivityCheckLongUrlTable 1}

RsNADConnectivityCheckLongUrlEntry  ::= SEQUENCE {
  rsNADFarmNameForLongUrl                 DisplayString,
  rsNADConnectivityLongCheckUrl           DisplayString,
  rsNADLongUrlRowStatus			  RowStatus
}

rsNADFarmNameForLongUrl OBJECT-TYPE
    SYNTAX DisplayString (SIZE(0..50))
    ACCESS  read-only
    STATUS  mandatory
    DESCRIPTION
      "The row definition for this table."
    ::= {rsNADConnectivityCheckLongUrlEntry 1}

rsNADConnectivityLongCheckUrl OBJECT-TYPE
    SYNTAX DisplayString (SIZE(0..255))
    ACCESS  read-write
    STATUS  mandatory
    DESCRIPTION
        "The absolute path of the web page to be requested in the extended
         connectivity check. Example: ~smith/home.html    "
--  DEFVAL  ( "" )
    ::= {rsNADConnectivityCheckLongUrlEntry 2}

rsNADLongUrlRowStatus         OBJECT-TYPE
    SYNTAX RowStatus
    ACCESS read-write
    STATUS mandatory
    DESCRIPTION
        "The row status of the Long URL"
    ::= {rsNADConnectivityCheckLongUrlEntry 3}

rsNADClientsViewEntry OBJECT-TYPE
   SYNTAX  RsNADClientsViewEntry
   ACCESS  not-accessible
   STATUS  mandatory
   DESCRIPTION
         "An entry in the client views table"
   INDEX  {rsNADClientsViewIndex}
   ::= { rsNADClientsViewTable 1 }

RsNADClientsViewEntry   ::= SEQUENCE {
     rsNADClientsViewIndex             INTEGER,
	 rsNADClientsViewSrcAddrFromType   InetAddressType,
     rsNADClientsViewSrcAddrFrom       InetAddress,
	 rsNADClientsViewSrcAddrToType     InetAddressType,
     rsNADClientsViewSrcAddrTo         InetAddress,
	 rsNADClientsViewDstAddrFromType   InetAddressType,
     rsNADClientsViewDstAddrFrom       InetAddress,
	 rsNADClientsViewDstAddrToType     InetAddressType,
     rsNADClientsViewDstAddrTo         InetAddress,
     rsNADClientsViewSrcPortFrom       INTEGER,
     rsNADClientsViewSrcPortTo         INTEGER,
     rsNADClientsViewDstPortFrom       INTEGER,
     rsNADClientsViewDstPortTo         INTEGER,
     rsNADClientsViewServerAddrType    InetAddressType,
	 rsNADClientsViewServerAddr	  	   InetAddress,
	 rsNADClientsViewFarmName          DisplayString,
     rsNADClientsViewClientType        DisplayString,
     rsNADClientsViewAdminStatus       INTEGER,
     rsNADClientsViewAction            INTEGER,
     rsNADClientsViewActionFeedback    DisplayString,
     rsNADClientsViewVlanTag           INTEGER,
	 rsNADClientsViewStatus            RowStatus
   }

rsNADClientsViewIndex OBJECT-TYPE
   SYNTAX  INTEGER
   ACCESS  read-only
   STATUS  mandatory
   DESCRIPTION
         "The index of this entry in the views table."
   ::= { rsNADClientsViewEntry 1 }

rsNADClientsViewSrcAddrFromType  OBJECT-TYPE
    SYNTAX InetAddressType
    ACCESS  read-write
    STATUS  optional
    DESCRIPTION
        "The IP Address Type of the low boundary of the source interval."
	DEFVAL  { ipv4 }
    ::=  { rsNADClientsViewEntry 2 }

rsNADClientsViewSrcAddrFrom  OBJECT-TYPE
    SYNTAX InetAddress
    ACCESS  read-write
    STATUS  optional
    DESCRIPTION
        "The IP Address of the low boundary of the source interval."
	DEFVAL{"0.0.0.0"}
    ::=  { rsNADClientsViewEntry 3 }

rsNADClientsViewSrcAddrToType  OBJECT-TYPE
    SYNTAX InetAddressType
    ACCESS  read-write
    STATUS  optional
    DESCRIPTION
        "The IP Address Type of the high boundary of the source interval."
	DEFVAL  { ipv4 }
    ::=  { rsNADClientsViewEntry 4 }

rsNADClientsViewSrcAddrTo  OBJECT-TYPE
    SYNTAX InetAddress
    ACCESS  read-write
    STATUS  optional
    DESCRIPTION
        "The IP Address of the high boundary of the source interval."
	DEFVAL{"0.0.0.0"}
    ::=  { rsNADClientsViewEntry 5 }



rsNADClientsViewDstAddrFromType  OBJECT-TYPE
    SYNTAX InetAddressType
    ACCESS  read-write
    STATUS  optional
    DESCRIPTION
        "The IP Address Type of the low boundary of the requested interval."
	DEFVAL  { ipv4 }
    ::=  { rsNADClientsViewEntry 6 }

rsNADClientsViewDstAddrFrom  OBJECT-TYPE
    SYNTAX InetAddress
    ACCESS  read-write
    STATUS  optional
    DESCRIPTION
        "The IP Address of the low boundary of the requested interval."
	DEFVAL{"0.0.0.0"}
    ::=  { rsNADClientsViewEntry 7 }

rsNADClientsViewDstAddrToType  OBJECT-TYPE
    SYNTAX InetAddressType
    ACCESS  read-write
    STATUS  optional
    DESCRIPTION
        "The IP Address Type of the high boundary of the requested interval."
	DEFVAL  { ipv4 }
    ::=  { rsNADClientsViewEntry 8 }

rsNADClientsViewDstAddrTo  OBJECT-TYPE
    SYNTAX InetAddress
    ACCESS  read-write
    STATUS  optional
    DESCRIPTION
        "The IP Address of the high boundary of the requested interval."
	DEFVAL{"0.0.0.0"}
    ::=  { rsNADClientsViewEntry 9 }

rsNADClientsViewSrcPortFrom  OBJECT-TYPE
    SYNTAX INTEGER (0..65535)
    ACCESS  read-write
    STATUS  optional
    DESCRIPTION
        "The TCP/UDP port of the low boundary of the source interval."
    DEFVAL{0}
    ::=  { rsNADClientsViewEntry 10}

rsNADClientsViewSrcPortTo  OBJECT-TYPE
    SYNTAX INTEGER (0..65535)
    ACCESS  read-write
    STATUS  optional
    DESCRIPTION
        "The TCP/UDP port of the high boundary of the source interval."
    DEFVAL{0}
    ::=  { rsNADClientsViewEntry 11}

rsNADClientsViewDstPortFrom  OBJECT-TYPE
    SYNTAX INTEGER (0..65535)
    ACCESS  read-write
    STATUS  optional
    DESCRIPTION
        "The TCP/UDP port of the low boundary of the requested interval."
    DEFVAL{0}
    ::=  { rsNADClientsViewEntry 12}

rsNADClientsViewDstPortTo  OBJECT-TYPE
    SYNTAX INTEGER (0..65535)
    ACCESS  read-write
    STATUS  optional
    DESCRIPTION
        "The TCP/UDP port of the high boundary of the requested interval."
    DEFVAL{0}
    ::=  { rsNADClientsViewEntry 13}

rsNADClientsViewServerAddrType  OBJECT-TYPE
    SYNTAX InetAddressType
    ACCESS  read-write
    STATUS  optional
    DESCRIPTION
        "The IP Address Type of the server."
	DEFVAL  { ipv4 }
    ::=  { rsNADClientsViewEntry 14 }

rsNADClientsViewServerAddr  OBJECT-TYPE
    SYNTAX InetAddress
    ACCESS  read-write
    STATUS  optional
    DESCRIPTION
        "The IP Address of the server."
	DEFVAL{"0.0.0.0"}
    ::=  { rsNADClientsViewEntry 15 }

rsNADClientsViewFarmName  OBJECT-TYPE
    SYNTAX  DisplayString (SIZE (0..50))
    ACCESS  read-write
    STATUS  optional
    DESCRIPTION
        "The client's farm name."
    ::=  { rsNADClientsViewEntry 16 }

rsNADClientsViewClientType OBJECT-TYPE
   SYNTAX  DisplayString (SIZE(0..20))
   ACCESS  read-write
   STATUS  optional
   DESCRIPTION
         "The client type"
   ::= { rsNADClientsViewEntry 17 }

rsNADClientsViewAdminStatus  OBJECT-TYPE
    SYNTAX INTEGER {
           enabled(1),
           disabled(2)
    }
    ACCESS  read-write
    STATUS  optional
    DESCRIPTION
        "Administrative status of the view entry
	 enabled - activates the view.
         disabled - inactive the view."
    DEFVAL { 1 }
    ::=  { rsNADClientsViewEntry 18 }

rsNADClientsViewAction OBJECT-TYPE
   SYNTAX INTEGER {
        noAction(1),
        deleteMatching(2),
        countMatching(3)
   }
   ACCESS  read-write
   STATUS  optional
   DESCRIPTION
         "The type of action to be performed on entries matching this filter."
   DEFVAL { 1 }
   ::= { rsNADClientsViewEntry 19 }

rsNADClientsViewActionFeedback OBJECT-TYPE
   SYNTAX  DisplayString (SIZE(0..240))
   ACCESS  read-only
   STATUS  optional
   DESCRIPTION
         "Message containing feedback for the action taken."
   ::= { rsNADClientsViewEntry 20 }

rsNADClientsViewVlanTag OBJECT-TYPE
   SYNTAX INTEGER (0..4095)
   ACCESS  read-write
   STATUS  optional
   DESCRIPTION
         "802.1q VLAN tag associated with the client entry. 0 - no tag."
   DEFVAL { 0 }
   ::= { rsNADClientsViewEntry 21 }

rsNADClientsViewStatus  OBJECT-TYPE
   SYNTAX  RowStatus
   ACCESS  read-write
   STATUS  mandatory
   DESCRIPTION
         "It is used to create and delete a filter"
   ::= { rsNADClientsViewEntry 22 }

adTslAuthenticationPolicyTable OBJECT-TYPE
  SYNTAX SEQUENCE OF AdTslAuthenticationPolicyEntry
  ACCESS not-accessible
  STATUS mandatory
  DESCRIPTION
    "A table for managing TSL authentication parameters."
  ::= {rsWSDL4Policy 60}


-- Authentication CDP
adAuthenticationCdpTable OBJECT-TYPE
  SYNTAX SEQUENCE OF AdAuthenticationCdpEntry
  ACCESS not-accessible
  STATUS mandatory
  DESCRIPTION
    "A table for managing authentication CDP entries."
  ::= {rsWSDL4Policy 76}

adAuthenticationCdpEntry OBJECT-TYPE
  SYNTAX AdAuthenticationCdpEntry
  ACCESS not-accessible
  STATUS mandatory
  DESCRIPTION
    " The row definition for this table."
  INDEX { adAuthCdpGroupName, adAuthCdpIndex }
  ::= {adAuthenticationCdpTable 1}

AdAuthenticationCdpEntry ::= SEQUENCE {
  adAuthCdpGroupName          				DisplayString,
  adAuthCdpIndex			 				INTEGER,
  adAuthCdpUri				  				DisplayString,
  adAuthCdpUserName 						DisplayString,
  adAuthCdpPassword             			DisplayString,
  adAuthCdpStatus			 				RowStatus
}

adAuthCdpGroupName OBJECT-TYPE
  SYNTAX DisplayString (SIZE (1..50))
  ACCESS read-only
  STATUS mandatory
  DESCRIPTION    "The CDP group name."
  ::=  {adAuthenticationCdpEntry  1}

adAuthCdpIndex OBJECT-TYPE
  SYNTAX INTEGER (0..128)
  ACCESS read-only
  STATUS mandatory
  DESCRIPTION    "Index within a given CDP group name."
  ::=  {adAuthenticationCdpEntry  2}

adAuthCdpUri  OBJECT-TYPE
  SYNTAX DisplayString (SIZE (0..255))
  ACCESS read-write
  STATUS mandatory
  DESCRIPTION
    "URI of the CDP"
  ::=  { adAuthenticationCdpEntry  3}

adAuthCdpUserName OBJECT-TYPE
  SYNTAX DisplayString (SIZE (0..250))
  ACCESS read-write
  STATUS mandatory
  DESCRIPTION
    "CDP username"
  ::=  { adAuthenticationCdpEntry  4}

adAuthCdpPassword OBJECT-TYPE
  SYNTAX DisplayString (SIZE (0..250))
  ACCESS read-write
  STATUS mandatory
  DESCRIPTION
    "CDP password"
  ::=  { adAuthenticationCdpEntry  5}

adAuthCdpStatus OBJECT-TYPE
  SYNTAX RowStatus
  ACCESS read-write
  STATUS mandatory
  DESCRIPTION
    "Row status for this entry."
  ::= { adAuthenticationCdpEntry  6}


adTslAuthenticationPolicyEntry OBJECT-TYPE
  SYNTAX AdTslAuthenticationPolicyEntry
  ACCESS not-accessible
  STATUS mandatory
  DESCRIPTION
    " The row definition for this table."
  INDEX { adTslAuthPolicyName }
  ::= {adTslAuthenticationPolicyTable 1}

AdTslAuthenticationPolicyEntry ::= SEQUENCE {
  adTslAuthPolicyName                                   DisplayString,
  adTslAuthRedirectionURLOnFailedAuth                   DisplayString,
  adTslAuthCADepthToCheck                               INTEGER,
  adTslAuthCACheckRequired                              FeatureStatus,
  adTslAuthPolicyCertificateHeaderToBEServerInfoArg     DisplayString,
  adTslAuthPolicyCertFieldValidationPolicy              DisplayString,
  adTslAuthPolicyTslFileChain                           DisplayString,
  adTslOcspCacheTime                                    INTEGER,
  adTslAuthPolicyRowStatus                              RowStatus,
  adTslAuthOcspResponseAllowedSigningAlgorithm          DisplayString,
  adTslAuthOcspResponseTimestampDeviationGracePeriod    INTEGER,
  adTslAuthOcspNonce                                    FeatureStatus,
  adTslAuthOcspVerifyCAStatus                           FeatureStatus
}

adTslAuthPolicyName OBJECT-TYPE
  SYNTAX DisplayString (SIZE (1..50))
  ACCESS read-only
  STATUS mandatory
  DESCRIPTION    "The Authentication policy name."
  ::=  {adTslAuthenticationPolicyEntry 1}

adTslAuthRedirectionURLOnFailedAuth OBJECT-TYPE
  SYNTAX DisplayString (SIZE (0..255))
  ACCESS read-write
  STATUS mandatory
  DESCRIPTION    "A URL that the user will be redirected to if the authentication fails."
  ::=  {adTslAuthenticationPolicyEntry 2}

adTslAuthCADepthToCheck OBJECT-TYPE
  SYNTAX INTEGER (1..9)
  ACCESS read-write
  STATUS mandatory
  DESCRIPTION  "The maximum depth that the client CA chain will be checked in order to authenticate the user."
  DEFVAL { 1 }
  ::=  {adTslAuthenticationPolicyEntry 3}

adTslAuthCACheckRequired       OBJECT-TYPE
  SYNTAX FeatureStatus
  ACCESS read-write
  STATUS mandatory
  DESCRIPTION    "Whether certificate revocation check is performed. Currently only OCSP is implemented."
  DEFVAL { disable }
  ::=  {adTslAuthenticationPolicyEntry 4}


adTslAuthPolicyCertificateHeaderToBEServerInfoArg  OBJECT-TYPE
  SYNTAX DisplayString (SIZE (0..255))
  ACCESS read-write
  STATUS mandatory
  DESCRIPTION  "Controls OCSP URI precedence - whether the user-configured URI is used or the URI that is embedded
     in the client's certificate."
  ::=  {adTslAuthenticationPolicyEntry 5}

adTslAuthPolicyCertFieldValidationPolicy        OBJECT-TYPE
  SYNTAX DisplayString (SIZE (0..50))
  ACCESS read-write
  STATUS mandatory
  DESCRIPTION     "Name of Certificate Field Validation Policy"
  DEFVAL { "None" }
  ::=  {adTslAuthenticationPolicyEntry 6}

adTslAuthPolicyTslFileChain                        OBJECT-TYPE
  SYNTAX DisplayString (SIZE (0..50))
  ACCESS read-write
  STATUS mandatory
  DESCRIPTION  "TSL File name"
  ::=  {adTslAuthenticationPolicyEntry 7}

adTslOcspCacheTime                    		      OBJECT-TYPE
  SYNTAX INTEGER (0..180000)
  ACCESS read-write
  STATUS mandatory
  DESCRIPTION     "The time in minutes that OCSP responses should be cached.
                     When set to 0, OCSP Cache is disabled"
  DEFVAL          { 0 }
  ::= {adTslAuthenticationPolicyEntry 8}

adTslAuthPolicyRowStatus           OBJECT-TYPE
  SYNTAX RowStatus
  ACCESS read-write
  STATUS mandatory
  DESCRIPTION
  "Row Status of the TSL Authentication policy"
  ::=  { adTslAuthenticationPolicyEntry  9}

adTslAuthOcspResponseAllowedSigningAlgorithm        OBJECT-TYPE
  SYNTAX DisplayString (SIZE (1..255))
  ACCESS read-write
  STATUS mandatory
  DESCRIPTION     "Defines the specific signature algorithms allows for signing OCSP responses"
  DEFVAL          { "All" }
  ::= {adTslAuthenticationPolicyEntry    10}

adTslAuthOcspResponseTimestampDeviationGracePeriod    OBJECT-TYPE
  SYNTAX INTEGER (0..2678400)
  ACCESS read-write
  STATUS mandatory
  DESCRIPTION     "Allows for overlooking small deviations between AppDirector and OCSP server timestamps for OCSP signatures verification (seconds)"
  DEFVAL          { 75 }
  ::= {adTslAuthenticationPolicyEntry    11}

adTslAuthOcspNonce                          OBJECT-TYPE
  SYNTAX FeatureStatus
  ACCESS read-write
  STATUS mandatory
  DESCRIPTION     "Determine whether nonce will be used in OCSP verification"
  DEFVAL          { enable }
  ::= {adTslAuthenticationPolicyEntry    12}

adTslAuthOcspVerifyCAStatus                         OBJECT-TYPE
  SYNTAX FeatureStatus
  ACCESS read-write
  STATUS mandatory
  DESCRIPTION     "If enabled send an OCSP request for every certificate in the chain, otherwise to client certificate only."
  DEFVAL          { disable }
  ::= {adTslAuthenticationPolicyEntry    13}


adVipTable OBJECT-TYPE
   SYNTAX SEQUENCE OF AdVipTableEntry
   ACCESS not-accessible
   STATUS mandatory
   DESCRIPTION
       "A table for managing VIPs."
   ::= {rsNWSD 85}

adVipTableEntry OBJECT-TYPE
   SYNTAX AdVipTableEntry
   ACCESS not-accessible
   STATUS mandatory
   DESCRIPTION
       " The row definition for this table."
   INDEX  {adVipAddress}
   ::= {adVipTable 1}

AdVipTableEntry ::= SEQUENCE {
  adVipAddress       IpAddress
}

adVipAddress OBJECT-TYPE
  SYNTAX IpAddress
  ACCESS read-only
  STATUS mandatory
  DESCRIPTION
     "IP address of the VIP."
  ::=  {adVipTableEntry 1}

rsADThroughputLicenseTrapThreshold OBJECT-TYPE
    SYNTAX  INTEGER  (0..99)
    ACCESS  read-write
    STATUS  mandatory
    DESCRIPTION
      "Throughput license threshold . if the value is zero (0) traps will not be sent"
    DEFVAL {90}
   ::= {rsNWSD 91}

rsADSSLLicenseTrapThreshold OBJECT-TYPE
    SYNTAX  INTEGER  (0..99)
    ACCESS  read-write
    STATUS  mandatory
    DESCRIPTION
      "SSL license threshold . if the value is zero (0) traps will not be sent"
    DEFVAL {90}
   ::= {rsNWSD 92}

rsADCompressionLicenseTrapThreshold OBJECT-TYPE
    SYNTAX  INTEGER  (0..99)
    ACCESS  read-write
    STATUS  mandatory
    DESCRIPTION
      "Compression license threshold . if the value is zero (0) traps will not be sent"
    DEFVAL {90}
   ::= {rsNWSD 93}

rdwrDeviceSslTps OBJECT-TYPE
   SYNTAX DisplayString (SIZE(0..255))
   ACCESS read-only
   STATUS mandatory
   DESCRIPTION
    "ADXL SSL TPS license."
    ::= { rsNWSD 94 }

rdwrDeviceCompression OBJECT-TYPE
   SYNTAX DisplayString (SIZE(0..255))
   ACCESS read-only
   STATUS mandatory
   DESCRIPTION
    "ADXL Compression license."
    ::= { rsNWSD 95 }

rdwrDeviceSslPeakTps OBJECT-TYPE
   SYNTAX INTEGER
   ACCESS read-only
   STATUS mandatory
   DESCRIPTION
    "ADXL SSL TPS peak usage."
    ::= { rsNWSD 96 }

rdwrDeviceCompressionPeakUsageMbps OBJECT-TYPE
   SYNTAX INTEGER
   ACCESS read-only
   STATUS mandatory
   DESCRIPTION
    "ADXL Compression peak usage in Mbps."
    ::= { rsNWSD 97 }

rdwrManageTerminalTrapEcho OBJECT-TYPE
   SYNTAX FeatureStatus
   ACCESS read-write
   STATUS mandatory
   DESCRIPTION
    "Defines whether traps are displayed in the terminal."
    ::= { rsNWSD 98 }

rdwrSystemInternalAppdirectorNonTestVisible OBJECT-TYPE
   SYNTAX FeatureStatus
   ACCESS read-write
   STATUS mandatory
   DESCRIPTION
    "Defines whether non test traps are displayed."
    ::= { rsNWSD 99 }

rdwrSystemInternalAppdirectorGenericFanVisible OBJECT-TYPE
   SYNTAX FeatureStatus
   ACCESS read-write
   STATUS mandatory
   DESCRIPTION
    "Defines whether generic fan trap are displayed."
    ::= { rsNWSD 100 }


rdwrLacpSystemID OBJECT-TYPE
    SYNTAX  PhysAddress
    ACCESS  read-write
    STATUS  mandatory
    DESCRIPTION
      "LACP Actor System ID"
        ::=  {rsNWSD 106}

rdwrLacpSystemPriority OBJECT-TYPE
	SYNTAX INTEGER (0..256)
    ACCESS  read-write
    STATUS  mandatory
    DESCRIPTION
      "LACP Actor System Priority"
        ::=  {rsNWSD 107}

rdwrAggTable OBJECT-TYPE
	SYNTAX SEQUENCE OF RdwrAggEntry
	ACCESS not-accessible
	STATUS mandatory
	DESCRIPTION
		"A Radware proprietary table that contains information about every
		Trunk (LA Group) that is associated with this System."
	::= {rsNWSD 108}

rdwrLinkAggregationHash OBJECT-TYPE
   	 SYNTAX INTEGER {
			l2src(1),
			l2dst(2),
			l2both(3),
			l3src(4),
			l3dst(5),
			l3both(6),
			l3srcl4src(7),
			l3dstl4dst(8),
			l3bothl4both(9)
			}
    ACCESS  read-write
    STATUS  mandatory
    DESCRIPTION
      "Link'Aggregation Distribution Method"
	::= {rsNWSD 109}

rdwrAggEntry OBJECT-TYPE
	SYNTAX RdwrAggEntry
	ACCESS not-accessible
	STATUS mandatory
	DESCRIPTION
		"A list of the Trunk (LA Group) parameters. This is indexed
		by the Name of the Trunk."
	INDEX { rdwrAggName }
	::= { rdwrAggTable 1 }

RdwrAggEntry ::= SEQUENCE {
		rdwrAggName 			DisplayString,
		rdwrAggMACAddress      		PhysAddress,
		rdwrAggActorSystemPriority	INTEGER,
		rdwrAggActorSystemID       	PhysAddress,
		rdwrAggAggregateOrIndividual	INTEGER,
		rdwrAggActorAdminKey		INTEGER,
		rdwrAggActorOperKey		INTEGER,
		rdwrAggPartnerSystemID      	PhysAddress,
		rdwrAggPartnerSystemPriority    INTEGER,
		rdwrAggPartnerOperKey    	INTEGER,
		rdwrAggCollectorMaxDelay    	INTEGER,
		rdwrAggPortList             	DisplayString,
		rdwrAggLacpMode			INTEGER,
		rdwrAggLacpTimeOut    		INTEGER,
		rdwrAggLacpWaitTime  		INTEGER,
		rdwrAggActorPortPriority	INTEGER
	}


rdwrAggName OBJECT-TYPE
	SYNTAX DisplayString (SIZE(0..255))
	ACCESS read-only
	STATUS mandatory
	DESCRIPTION
		"The unique identifier allocated to this Trunk by the local
		System.
		This attribute identifies a Trunk instance among the subordinate
		managed objects of the containing object. This value is read-only."
	::= { rdwrAggEntry 1 }

rdwrAggMACAddress OBJECT-TYPE
	SYNTAX PhysAddress
	ACCESS read-only
	STATUS mandatory
	DESCRIPTION
		"A 6-octet read-only value carrying the individual
	MAC address assigned to the Aggregator."
	REFERENCE
		"IEEE 802.3 Subclause 30.7.1.1.9"
	::= { rdwrAggEntry 2 }


rdwrAggActorSystemPriority OBJECT-TYPE
	SYNTAX INTEGER (0..65535)
	ACCESS read-only
	STATUS mandatory
	DESCRIPTION
		"A 2-octet read-write value indicating the priority value
		associated with the Actor's System ID."
	REFERENCE
		"IEEE 802.3 Subclause 30.7.1.1.5"
	::= { rdwrAggEntry 3 }


rdwrAggActorSystemID OBJECT-TYPE
	SYNTAX PhysAddress
	ACCESS read-only
	STATUS mandatory
	DESCRIPTION
		"A 6-octet read-write MAC address value used as a unique
		identifier for the System that contains this Aggregator.
		NOTE-From the perspective of the Link Aggregation mechanisms
		described in Clause , only a single combination of
		Actor's System ID and System Priority are considered, and no
		distinction is made between the values of these parameters
		for an Aggregator and the port(s) that are associated with
		it; i.e., the protocol is described in terms of the operation
		of aggregation within a single System. However, the managed
		objects provided for the Aggregator and the port both allow
		management of these parameters. The result of this is to
		permit a single piece of equipment to be configured by
		management to contain more than one System from the point of
		view of the operation of Link Aggregation. This may be of
		particular use in the configuration of equipment that has
		limited aggregation capability (see )."
	REFERENCE
		"IEEE 802.3 Subclause 30.7.1.1.4"
::= { rdwrAggEntry 4 }


rdwrAggAggregateOrIndividual OBJECT-TYPE
	SYNTAX INTEGER {
		true (1),
		false (2)
	}
	ACCESS read-only
	STATUS mandatory
	DESCRIPTION
		"A read-only Boolean value indicating whether the
		Aggregator represents an Aggregate ('TRUE') or
		an Individual link ('FALSE')."
	REFERENCE
		"IEEE 802.3 Subclause 30.7.1.1.6"
	::= { rdwrAggEntry 5 }


	rdwrAggActorAdminKey OBJECT-TYPE
	SYNTAX INTEGER (0..65535)
	ACCESS read-write
	STATUS mandatory
	DESCRIPTION
		"The current administrative value of the Key for the Aggregator.
		The administrative Key value may differ from the operational
		Key value for the reasons discussed in . This is a 16-bit,
		read-write value. The meaning of particular Key values
		is of local significance."
	REFERENCE
		"IEEE 802.3 Subclause 30.7.1.1.7"
	::= { rdwrAggEntry 6 }


rdwrAggActorOperKey OBJECT-TYPE
	SYNTAX INTEGER (0..65535)
	ACCESS read-only
	STATUS mandatory
	DESCRIPTION
		"The current operational value of the Key for the Aggregator.
		The administrative Key value may differ from the operational
		Key value for the reasons discussed in .
		This is a 16-bit read-only value. The meaning of particular Key
		values is of local significance."
	REFERENCE
		"IEEE 802.3 Subclause 30.7.1.1.8"
	::= { rdwrAggEntry 7 }


rdwrAggPartnerSystemID OBJECT-TYPE
	SYNTAX PhysAddress
	ACCESS read-only
	STATUS mandatory
	DESCRIPTION
		"A 6-octet read-only MAC address value consisting
		of the unique identifier for the current protocol Partner of
		this Aggregator. A value of zero indicates that there is no
		known Partner. If the aggregation is manually configured, this
		System ID value will be a value assigned by the local System."
	REFERENCE
		"IEEE 802.3 Subclause 30.7.1.1.10"
	::= { rdwrAggEntry 8 }


rdwrAggPartnerSystemPriority OBJECT-TYPE
	SYNTAX INTEGER (0..65535)
	ACCESS read-only
	STATUS mandatory
	DESCRIPTION
		"A 2-octet read-only value that indicates the priority
		value associated with the Partner's System ID. If the
		aggregation is manually configured, this System Priority value
		will be a value assigned by the local System."
	REFERENCE
		"IEEE 802.3 Subclause 30.7.1.1.11"
	::= { rdwrAggEntry 9 }


rdwrAggPartnerOperKey OBJECT-TYPE
	SYNTAX INTEGER (0..65535)
	ACCESS read-only
	STATUS mandatory
	DESCRIPTION
		"The current operational value of the Key for the
		Aggregator's current protocol Partner. This is
		a 16-bit read-only value. If the aggregation is manually
		configured, this Key value will be a value assigned by the
		local System."
	REFERENCE
		"IEEE 802.3 Subclause 30.7.1.1.12"
	::= { rdwrAggEntry 10 }


rdwrAggCollectorMaxDelay OBJECT-TYPE
	SYNTAX INTEGER (0..65535)
	ACCESS read-write
	STATUS mandatory
	DESCRIPTION
		"The value of this 16-bit read-write attribute defines
		the maximum delay, in tens of microseconds, that
		may be imposed by the Frame Collector between
		receiving a frame from an Aggregator Parser, and
		either delivering the frame to its MAC Client or discarding
		the frame (see )."
	REFERENCE
		"IEEE 802.3 Subclause 30.7.1.32"
	::= { rdwrAggEntry 11 }

rdwrAggPortList OBJECT-TYPE
	SYNTAX DisplayString (SIZE(0..255))
	ACCESS read-write
	STATUS mandatory
	DESCRIPTION
		" Port List. Separated by semicolons"
	::= { rdwrAggEntry 12 }


rdwrAggLacpMode OBJECT-TYPE
   	 SYNTAX INTEGER {
	      		manual(1),
      			passive(2),
      			active(3)
			}
	ACCESS read-write
	STATUS mandatory
	DESCRIPTION
		"LACP Mode: Manual/Active/Passive"
	::= { rdwrAggEntry 13 }

rdwrAggLacpTimeOut OBJECT-TYPE
   	 SYNTAX INTEGER {
	      		slow(1),
      			fast (2)
			}
	ACCESS read-write
	STATUS mandatory
	DESCRIPTION
		"LACP Time Out"
	::= { rdwrAggEntry 14 }

rdwrAggLacpWaitTime OBJECT-TYPE
   	 SYNTAX INTEGER (0..10)
	ACCESS read-write
	STATUS mandatory
	DESCRIPTION
		"LACP Wait Time period (sec)"
	::= { rdwrAggEntry 15 }

rdwrAggActorPortPriority OBJECT-TYPE
   	 SYNTAX INTEGER (0..32767)
	ACCESS read-write
	STATUS mandatory
	DESCRIPTION
		"LACP Actor Port Priority"
	::= { rdwrAggEntry 16 }


rsADClientEntrySyslogLoggingStatus OBJECT-TYPE
    SYNTAX INTEGER {
                    enable(1),
                    disable(2)
                   }
    ACCESS  read-write
    STATUS  mandatory
    DESCRIPTION
      "Enable/Disable the logging of each client entry."
    DEFVAL {2}
   ::= {rsNWSD 110}

rsADClientEntrySyslogLoggingCommitment OBJECT-TYPE
    SYNTAX INTEGER {
                    bestEffort(1),
                    full(2)
                   }
    ACCESS  read-write
    STATUS  mandatory
    DESCRIPTION
        "This MIB indicates whether the device is will attempt to log when it is lacking resources (buffers).
         BestEffort means that if resources are lacking (due to stress) then logging will not occur.
         Full means that the if resources are lacking, the logging will be delayed until such time as it
         can take place. This may result in further performance degradation."
    DEFVAL {1}
   ::= {rsNWSD 111}

rsADClientEntrySyslogFieldStatusClientIP OBJECT-TYPE
    SYNTAX INTEGER {
                    enable(1),
                    disable(2)
                   }
    ACCESS  read-write
    STATUS  mandatory
    DESCRIPTION
      "Whether or not the client IP should be logged when logging client entries."
    DEFVAL {1}
   ::= {rsNWSD 112}

rsADClientEntrySyslogFieldStatusSrcPort OBJECT-TYPE
    SYNTAX INTEGER {
                    enable(1),
                    disable(2)
                   }
    ACCESS  read-write
    STATUS  mandatory
    DESCRIPTION
      "Whether or not the source port should be logged when logging client entries."
    DEFVAL {1}
   ::= {rsNWSD 113}

rsADClientEntrySyslogFieldStatusDstIP OBJECT-TYPE
    SYNTAX INTEGER {
                    enable(1),
                    disable(2)
                   }
    ACCESS  read-write
    STATUS  mandatory
    DESCRIPTION
      "Whether or not the destination IP should be logged when logging client entries."
    DEFVAL {1}
   ::= {rsNWSD 114}

rsADClientEntrySyslogFieldStatusDstPort OBJECT-TYPE
    SYNTAX INTEGER {
                    enable(1),
                    disable(2)
                   }
    ACCESS  read-write
    STATUS  mandatory
    DESCRIPTION
      "Whether or not the destination port should be logged when logging client entries."
    DEFVAL {1}
   ::= {rsNWSD 115}

rsADClientEntrySyslogFieldStatusClientType OBJECT-TYPE
    SYNTAX INTEGER {
                    enable(1),
                    disable(2)
                   }
    ACCESS  read-write
    STATUS  mandatory
    DESCRIPTION
      "Whether or not the client type should be logged when logging client entries."
    DEFVAL {1}
   ::= {rsNWSD 116}

rsADClientEntrySyslogFieldStatusServerIP OBJECT-TYPE
    SYNTAX INTEGER {
                    enable(1),
                    disable(2)
                   }
    ACCESS  read-write
    STATUS  mandatory
    DESCRIPTION
      "Whether or not the server IP should be logged when logging client entries."
    DEFVAL {1}
   ::= {rsNWSD 117}

rsADClientEntrySyslogFieldStatusServerPort OBJECT-TYPE
    SYNTAX INTEGER {
                    enable(1),
                    disable(2)
                   }
    ACCESS  read-write
    STATUS  mandatory
    DESCRIPTION
      "Whether or not the server port should be logged when logging client entries."
    DEFVAL {1}
   ::= {rsNWSD 118}

rsADClientEntrySyslogFieldStatusNatIP OBJECT-TYPE
    SYNTAX INTEGER {
                    enable(1),
                    disable(2)
                   }
    ACCESS  read-write
    STATUS  mandatory
    DESCRIPTION
      "Whether or not the NAT IP should be logged when logging client entries."
    DEFVAL {1}
   ::= {rsNWSD 119}

rsADClientEntrySyslogFieldStatusNatPort OBJECT-TYPE
    SYNTAX INTEGER {
                    enable(1),
                    disable(2)
                   }
    ACCESS  read-write
    STATUS  mandatory
    DESCRIPTION
      "Whether or not the NAT port should be logged when logging client entries."
    DEFVAL {1}
   ::= {rsNWSD 120}

rsADClientEntrySyslogFieldStatusStartTime OBJECT-TYPE
    SYNTAX INTEGER {
                    enable(1),
                    disable(2)
                   }
    ACCESS  read-write
    STATUS  mandatory
    DESCRIPTION
      "Whether or not the entry's start time should be logged when logging client entries."
    DEFVAL {1}
   ::= {rsNWSD 121}

rsADClientEntrySyslogFieldStatusEndTime OBJECT-TYPE
    SYNTAX INTEGER {
                    enable(1),
                    disable(2)
                   }
    ACCESS  read-write
    STATUS  mandatory
    DESCRIPTION
      "Whether or not the entry's end time should be logged when logging client entries."
    DEFVAL {1}
   ::= {rsNWSD 122}

rsADClientNatPerFarmRangesTable OBJECT-TYPE
SYNTAX SEQUENCE OF RsADClientNatPerFarmRangesEntry
    ACCESS not-accessible
    STATUS obsolete
    DESCRIPTION
      "Table containing the list of IP addresses ranges for per farm
      clients NAT."
    ::=  {rsNWSD 123}

rsADClientNatPerFarmRangesEntry OBJECT-TYPE
SYNTAX RsADClientNatPerFarmRangesEntry
    ACCESS not-accessible
    STATUS  mandatory
    DESCRIPTION
       " The row definition for this table."
   INDEX { rsFarmName,
           rsClientNatRangeFrom }
    ::=  {rsADClientNatPerFarmRangesTable 1}

RsADClientNatPerFarmRangesEntry ::= SEQUENCE {
  rsFarmName				DisplayString,
  rsClientNatRangeFrom			IpAddress,
  rsClientNatRangeTo			IpAddress,
  rsClientNatPerFarmEntryStatus		RowStatus
 }

rsFarmName OBJECT-TYPE
    SYNTAX  DisplayString
    ACCESS  read-only
    STATUS  mandatory
    DESCRIPTION
     "Farm Name"
    ::=  {rsADClientNatPerFarmRangesEntry 1}

rsClientNatRangeFrom  OBJECT-TYPE
    SYNTAX  IpAddress
    ACCESS  read-write
    STATUS  mandatory
    DESCRIPTION
     "IP address range from"
    ::=  {rsADClientNatPerFarmRangesEntry 2 }

rsClientNatRangeTo  OBJECT-TYPE
    SYNTAX  IpAddress
    ACCESS  read-write
    STATUS  mandatory
    DESCRIPTION
     "IP address range To"
    ::=  {rsADClientNatPerFarmRangesEntry 3 }

rsClientNatPerFarmEntryStatus OBJECT-TYPE
    SYNTAX RowStatus
	ACCESS  read-write
	STATUS  mandatory
	DESCRIPTION "Entry Row status"
    ::=  {rsADClientNatPerFarmRangesEntry 4 }

rsNADClientNatPerFarmRangesTable OBJECT-TYPE
SYNTAX SEQUENCE OF RsNADClientNatPerFarmRangesEntry
    ACCESS not-accessible
    STATUS mandatory
    DESCRIPTION
      "Table containing the list of IP addresses ranges for per farm
      clients NAT."
    ::=  {rsNWSD 124}

rsNADClientNatPerFarmRangesEntry OBJECT-TYPE
SYNTAX RsNADClientNatPerFarmRangesEntry
    ACCESS not-accessible
    STATUS  mandatory
    DESCRIPTION
       " The row definition for this table."
   INDEX { rsNADFarmName,
			rsNADClientNatRangeFromType,
           rsNADClientNatRangeFromAddress }
    ::=  {rsNADClientNatPerFarmRangesTable 1}

RsNADClientNatPerFarmRangesEntry ::= SEQUENCE {
  rsNADFarmName					DisplayString,
  rsNADClientNatRangeFromType			InetAddressType,
  rsNADClientNatRangeFromAddress		InetAddress,
  rsNADClientNatRangeToType				InetAddressType,
  rsNADClientNatRangeToAddress			InetAddress,
  rsNADClientNatPerFarmEntryStatus		RowStatus
 }

rsNADFarmName OBJECT-TYPE
    SYNTAX  DisplayString
    ACCESS  read-only
    STATUS  mandatory
    DESCRIPTION
     "Farm Name"
    ::=  {rsNADClientNatPerFarmRangesEntry 1}

rsNADClientNatRangeFromType  OBJECT-TYPE
    SYNTAX  InetAddressType
    ACCESS  read-write
    STATUS  optional
    DESCRIPTION
     "IP address range from"
    ::=  {rsNADClientNatPerFarmRangesEntry 2 }

rsNADClientNatRangeFromAddress  OBJECT-TYPE
    SYNTAX  InetAddress
    ACCESS  read-write
    STATUS  mandatory
    DESCRIPTION
     "IP address range from"
    ::=  {rsNADClientNatPerFarmRangesEntry 3 }

rsNADClientNatRangeToType  OBJECT-TYPE
    SYNTAX  InetAddressType
    ACCESS  read-write
    STATUS  optional
    DESCRIPTION
     "IP address range To"
    ::=  {rsNADClientNatPerFarmRangesEntry 4 }

rsNADClientNatRangeToAddress  OBJECT-TYPE
    SYNTAX  InetAddress
    ACCESS  read-write
    STATUS  mandatory
    DESCRIPTION
     "IP address range To"
    ::=  {rsNADClientNatPerFarmRangesEntry 5 }

rsNADClientNatPerFarmEntryStatus OBJECT-TYPE
    SYNTAX RowStatus
	ACCESS  read-write
	STATUS  mandatory
	DESCRIPTION "Entry Row status"
    ::=  {rsNADClientNatPerFarmRangesEntry 6 }

-- Application-specific traps for WSD
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=
-- -------------

rsWSDTWTClientTableSize TRAP-TYPE
         ENTERPRISE rsNWSD
         VARIABLES { rndErrorDesc, rndErrorSeverity }
         DESCRIPTION
             "This informational trap is sent when client table threshold is
             reached."
     ::=  1

rsWSDTWTLogicServConnectLimit TRAP-TYPE
         ENTERPRISE rsNWSD
         VARIABLES { rndErrorDesc, rndErrorSeverity }
         DESCRIPTION
             "This informational trap is sent when a logical server connection
             limit threshold is reached."
     ::=  2

rsWSDTWTPhyServConnectLimit TRAP-TYPE
         ENTERPRISE rsNWSD
         VARIABLES { rndErrorDesc, rndErrorSeverity }
         DESCRIPTION
             "This informational trap is sent when a physical serevr
             connection limit threshold is reached."
     ::=  3

rsWSDTWTFarmCapacityLimit TRAP-TYPE
         ENTERPRISE rsNWSD
         VARIABLES { rndErrorDesc, rndErrorSeverity }
         DESCRIPTION
             "This informational trap is sent when a farm capacity limit
             threshold is reached."
     ::=  4

rsWSDTWTServBandwidthLimit TRAP-TYPE
         ENTERPRISE rsNWSD
         VARIABLES { rndErrorDesc, rndErrorSeverity }
         DESCRIPTION
             "This informational trap is sent when a server's bandwidth limit
             threshold is reached."
     ::=  5

rsWSDTWTFarmBandwidthLimit TRAP-TYPE
         ENTERPRISE rsNWSD
         VARIABLES { rndErrorDesc, rndErrorSeverity }
         DESCRIPTION
             "This informational trap is sent when a farm's bandwidth limit
             threshold is reached."
     ::=  6

rsWSDDynamicNATOutOfPorts TRAP-TYPE
         ENTERPRISE rsNWSD
         VARIABLES { rndErrorDesc, rndErrorSeverity }
         DESCRIPTION
             "This warning trap is sent when the WSD is out of dynamic NAT ports."
     ::=  7

rsWSDNHRUp TRAP-TYPE
         ENTERPRISE rsNWSD
         VARIABLES { rndErrorDesc, rndErrorSeverity }
         DESCRIPTION
             "This infomational trap is sent when an NHR changes state to up."
     ::=  8

rsWSDNHRDown TRAP-TYPE
         ENTERPRISE rsNWSD
         VARIABLES { rndErrorDesc, rndErrorSeverity }
         DESCRIPTION
             "This warning trap is sent when an NHR changes state to down."
     ::=  9

rsWSDSynProtectionTablesFull TRAP-TYPE
         ENTERPRISE rsNWSD
         VARIABLES { rndErrorDesc, rndErrorSeverity }
         DESCRIPTION
             "This warning trap is sent when the SYN protection flood table is full."
     ::=  10

rsWSDRequestTablesFull TRAP-TYPE
         ENTERPRISE rsNWSD
         VARIABLES { rndErrorDesc, rndErrorSeverity }
         DESCRIPTION
             "This warning trap is sent when the requst table is full. You should increase the tbale
			  size in the device tuning"
     ::=  11

rsWSDDynamicSIDTablesFull TRAP-TYPE
         ENTERPRISE rsNWSD
         VARIABLES { rndErrorDesc, rndErrorSeverity }
         DESCRIPTION
             "This warning trap is sent when the dynamic SID table is full. You should increase the tbale
			  size in the device tuning"
     ::=  12

rsWSDLRPActive TRAP-TYPE
         ENTERPRISE rsNWSD
         VARIABLES { rndErrorDesc, rndErrorSeverity }
         DESCRIPTION
             "This infomational trap is sent when report changes state to Active."
     ::=  13

rsWSDLRPNIS TRAP-TYPE
         ENTERPRISE rsNWSD
         VARIABLES { rndErrorDesc, rndErrorSeverity }
         DESCRIPTION
             "This warning trap is sent when report changes state to Not In Service."
     ::=  14

rsWSDClientNATPortsThresholdReached TRAP-TYPE
         ENTERPRISE rsNWSD
         VARIABLES { rndErrorDesc, rndErrorSeverity }
         DESCRIPTION
             "This warning trap is sent when the client NAT ports number threshold is reached."
     ::=  15

rsWSDOutboundNATPortsThresholdReached TRAP-TYPE
         ENTERPRISE rsNWSD
         VARIABLES { rndErrorDesc, rndErrorSeverity }
         DESCRIPTION
             "This warning trap is sent when the outbound NAT ports number threshold is reached."
     ::=  16

rsWSDDSIDTableEntriesThresholdReached TRAP-TYPE
         ENTERPRISE rsNWSD
         VARIABLES { rndErrorDesc, rndErrorSeverity }
         DESCRIPTION
             "This warning trap is sent when the number of entries in the dynamic seesion ID table threshold is reached."
     ::=  17

rsWSDRequestTableEntriesThresholdReached TRAP-TYPE
         ENTERPRISE rsNWSD
         VARIABLES { rndErrorDesc, rndErrorSeverity }
         DESCRIPTION
             "This warning trap is sent when the number of entries in the request table threshold is reached."
     ::=  18


rsWSDClientTableThresholdReached TRAP-TYPE
         ENTERPRISE rsNWSD
         VARIABLES { rndErrorDesc, rndErrorSeverity }
         DESCRIPTION
             "This informational trap is sent when client table threshold is reached."
     ::=  19

rsWSDAppServerConnectionThresholdReached TRAP-TYPE
         ENTERPRISE rsNWSD
         VARIABLES { rndErrorDesc, rndErrorSeverity }
         DESCRIPTION
             "This informational trap is sent when an application server connection
             limit threshold is reached."
     ::=  20

rsWSDPhyServerConnectionThresholdReached TRAP-TYPE
         ENTERPRISE rsNWSD
         VARIABLES { rndErrorDesc, rndErrorSeverity }
         DESCRIPTION
             "This informational trap is sent when a physical serevr
             connection limit threshold is reached."
     ::=  21

rsWSDFarmCapacityThresholdReached TRAP-TYPE
         ENTERPRISE rsNWSD
         VARIABLES { rndErrorDesc, rndErrorSeverity }
         DESCRIPTION
             "This informational trap is sent when a farm capacity limit
             threshold is reached."
     ::=  22

rsWSDDynamicSidRewriteNoPlaceForValue TRAP-TYPE
         ENTERPRISE rsNWSD
         VARIABLES { rndErrorDesc, rndErrorSeverity }
         DESCRIPTION
	"This trap is sent when Dynamic SID persistancy mode is in rewrite mode and the server's response packet doen't
	 hold enougth space for the SID value. The space size is measured between the end of key and delimeter"
     ::=  23

rsWSDDynamicSidRewriteIdentiferNotFound TRAP-TYPE
         ENTERPRISE rsNWSD
         VARIABLES { rndErrorDesc, rndErrorSeverity }
         DESCRIPTION
	"This trap is sent when Dynamic SID persistancy mode is in rewrite mode and the server's response packet doen't
	 contain the defined identifier"
     ::=  24

rdwrVrrpAutomatedConfigurationVIPNotAssociated TRAP-TYPE
         ENTERPRISE rsNWSD
         VARIABLES { rndErrorDesc, rndErrorSeverity }
         DESCRIPTION
	"This trap is sent when new l4 policy is not entered to the associated ip table"
     ::=  25

rdwrManagedDeviceFailedToEstablishConnection TRAP-TYPE
         ENTERPRISE rsNWSD
         VARIABLES { rndErrorDesc, rndErrorSeverity }
         DESCRIPTION
	"This trap is sent when we cannot establish a connection with the managed Device"
     ::=  26

rdwrManagedDeviceConnectionDropedByServer TRAP-TYPE
         ENTERPRISE rsNWSD
         VARIABLES { rndErrorDesc, rndErrorSeverity }
         DESCRIPTION
	"This trap is sent when the connection was dropped by the managed Device"
     ::=  27

rdwrManagedDeviceNoSyncWithServer TRAP-TYPE
         ENTERPRISE rsNWSD
         VARIABLES { rndErrorDesc, rndErrorSeverity }
         DESCRIPTION
	"This trap is sent when we can not synchronize with the managed Device"
     ::=  28

rdwrManagedDeviceConnectionClosedByAD TRAP-TYPE
         ENTERPRISE rsNWSD
         VARIABLES { rndErrorDesc, rndErrorSeverity }
         DESCRIPTION
	"This trap is sent when the connection to the managed Device was closed by appDirector"
     ::=  29

rdwrManagedDeviceConnectionEstablished TRAP-TYPE
         ENTERPRISE rsNWSD
         VARIABLES { rndErrorDesc, rndErrorSeverity }
         DESCRIPTION
	"This trap is sent when the connection to the managed Device is established"
     ::=  30

rsWSDPrxChkFailure TRAP-TYPE
         ENTERPRISE rsNWSD
         VARIABLES { rndErrorDesc, rndErrorSeverity }
         DESCRIPTION
             "This info trap is sent when proximity check of client failure."
     ::=  31

rsWSDAuxiliaryTableThresholdReached TRAP-TYPE
         ENTERPRISE rsNWSD
         VARIABLES { rndErrorDesc, rndErrorSeverity }
         DESCRIPTION
             "This informational trap is sent when L3 client table threshold is reached."
     ::=  32

rsWSDRemoteWSDAvailable TRAP-TYPE
       ENTERPRISE  rsNWSD
       VARIABLES   { rndErrorDesc, rndErrorSeverity }
       DESCRIPTION
             "This info is generated after remote AppDirector server became available"
     ::= 33

rsWSDFArmActive TRAP-TYPE
         ENTERPRISE rsNWSD
         VARIABLES { rndErrorDesc, rndErrorSeverity }
         DESCRIPTION
             "This infomational trap is sent when farm changes state to Active."
     ::=  34

rsWSDFarmNIS TRAP-TYPE
         ENTERPRISE rsNWSD
         VARIABLES { rndErrorDesc, rndErrorSeverity }
         DESCRIPTION
             "This warning trap is sent when farm changes state to Not In Service."
     ::=  35

rsADFailedL7ModificationOfServerSidToken TRAP-TYPE
         ENTERPRISE rsNWSD
         VARIABLES { rndErrorDesc, rndErrorSeverity }
         DESCRIPTION
             "This warning trap is sent when using L7 Modification containing the $Server_SID_Cookie token
			 (usually utilizing the Insert Cookie feature), and no static SID is configured for the server that
			 belongs to a treated session.The Modification will not be performed and the packet is discarded."
     ::=  36

rdwr30SecCpuUtilizationAvarageExceededThreshold TRAP-TYPE
         ENTERPRISE rsNWSD
         VARIABLES { rndErrorDesc, rndErrorSeverity }
         DESCRIPTION
	"This trap is sent when the 30 seconds CPU utilization average has exceeded the defined threshold"
     ::=  37

rdwr30SecCpuUtilizationAvarageBelowThreshold TRAP-TYPE
         ENTERPRISE rsNWSD
         VARIABLES { rndErrorDesc, rndErrorSeverity }
         DESCRIPTION
	"This trap is sent when the 30 seconds CPU utilization average has returned blow the defined threshold"
     ::=  38

rdwrShutdownOrReset TRAP-TYPE
         ENTERPRISE rsNWSD
         VARIABLES { rndErrorDesc, rndErrorSeverity }
         DESCRIPTION
        "This trap is sent when the device is shutdown or reset"
     ::=  39

rdwrTrafficThroughputLimitReached TRAP-TYPE
         ENTERPRISE rsNWSD
         VARIABLES { rndErrorDesc, rndErrorSeverity }
         DESCRIPTION
        "This trap is sent when the traffic throughput limit is reached"
     ::=  40

rsWSDDXPChannelActive TRAP-TYPE
         ENTERPRISE rsNWSD
         VARIABLES { rndErrorDesc, rndErrorSeverity }
         DESCRIPTION
             "This warning trap is sent when DXP channel changes state to Active."
     ::=  41

rsWSDDXPChannelNIS TRAP-TYPE
         ENTERPRISE rsNWSD
         VARIABLES { rndErrorDesc, rndErrorSeverity }
         DESCRIPTION
             "This warning trap is sent when DXP channel changes state to Not In Service."
     ::=  42

rsWSDDXPFailedDXPConfigUpdate TRAP-TYPE
         ENTERPRISE rsNWSD
         VARIABLES { rndErrorDesc, rndErrorSeverity }
         DESCRIPTION
             "This warning trap is sent when DXP channel fails on config update notify."
     ::=  43

rsWSDDXPSystemActive TRAP-TYPE
         ENTERPRISE rsNWSD
         VARIABLES { rndErrorDesc, rndErrorSeverity }
         DESCRIPTION
             "This warning trap is sent when DXP system changes state to Active."
     ::=  44

rsWSDDXPSystemNIS TRAP-TYPE
         ENTERPRISE rsNWSD
         VARIABLES { rndErrorDesc, rndErrorSeverity }
         DESCRIPTION
             "This warning trap is sent when DXP system changes state to Not In Service."
     ::=  45

rsWSDProxyCompressionCardNotAvailable TRAP-TYPE
         ENTERPRISE rsNWSD
         VARIABLES { rndErrorDesc, rndErrorSeverity }
         DESCRIPTION
             "No compression hardware was detected during boot-up."
     ::=  46

rsWSDProxySSLCardNotAvailable TRAP-TYPE
         ENTERPRISE rsNWSD
         VARIABLES { rndErrorDesc, rndErrorSeverity }
         DESCRIPTION
             "No SSL acceleration card was detected during boot-up."
     ::=  47

rsWSDProxyLoginAXViaSSH TRAP-TYPE
         ENTERPRISE rsNWSD
         VARIABLES { rndErrorDesc, rndErrorSeverity }
         DESCRIPTION
             "User <user-name> has logged in via SSH console."
     ::=  48

rsWSDProxyTempCECLimitStop TRAP-TYPE
         ENTERPRISE rsNWSD
         VARIABLES { rndErrorDesc, rndErrorSeverity }
         DESCRIPTION
             "Temporary limitation of maximum number of connections due to memory limitation has stopped."
     ::=  49

rsWSDProxyCacheLimitShortSpace TRAP-TYPE
         ENTERPRISE rsNWSD
         VARIABLES { rndErrorDesc, rndErrorSeverity }
         DESCRIPTION
             "Temporary limiting caching due to critical cache space shortage."
     ::=  50

rsWSDProxyCacheReached80Percent TRAP-TYPE
         ENTERPRISE rsNWSD
         VARIABLES { rndErrorDesc, rndErrorSeverity }
         DESCRIPTION
             "Cache space has reached 80%."
     ::=  51

rsWSDProxyCacheBelow80Percent TRAP-TYPE
         ENTERPRISE rsNWSD
         VARIABLES { rndErrorDesc, rndErrorSeverity }
         DESCRIPTION
             "Cache space is below 80%."
     ::=  52

rsWSDProxyLoggingDiskSpaceReached80Percent TRAP-TYPE
         ENTERPRISE rsNWSD
         VARIABLES { rndErrorDesc, rndErrorSeverity }
         DESCRIPTION
             "80% of logging disk space was reached."
     ::=  53

rsWSDProxyCPUCrossed80Percent TRAP-TYPE
         ENTERPRISE rsNWSD
         VARIABLES { rndErrorDesc, rndErrorSeverity }
         DESCRIPTION
             "CPU utilization has reached 80%, while before that it was below 80%."
     ::=  54

rsWSDProxyCPUFell80Percent TRAP-TYPE
         ENTERPRISE rsNWSD
         VARIABLES { rndErrorDesc, rndErrorSeverity }
         DESCRIPTION
             "utilization has dropped below 80%, while before that it was above 80%."
     ::=  55

rsWSDProxyTempCECLimitMemShortage TRAP-TYPE
         ENTERPRISE rsNWSD
         VARIABLES { rndErrorDesc, rndErrorSeverity }
         DESCRIPTION
             "The device is near full memory capacity <% memory usage>. Temporarily limiting maximum number of connections."
     ::=  56

rsWSDProxyConfigurationProtectionActivated TRAP-TYPE
         ENTERPRISE rsNWSD
         VARIABLES { rndErrorDesc, rndErrorSeverity }
         DESCRIPTION
             "Configuration Protection mechanism was initiated."
     ::=  57

rsWSDProxyKeyLoadingError TRAP-TYPE
         ENTERPRISE rsNWSD
         VARIABLES { rndErrorDesc, rndErrorSeverity }
         DESCRIPTION
             "An Error occurred while loading %s certificate key to HSM module. Check HSM management authorization and retry."
     ::=  58

rsWSDProxyHWCompressionCardDetected TRAP-TYPE
         ENTERPRISE rsNWSD
         VARIABLES { rndErrorDesc, rndErrorSeverity }
         DESCRIPTION
             "Hardware compression card detected. Hardware compression capabilities will be enabled."
     ::=  59

rsWSDProxyFIPSEngineNotRunning TRAP-TYPE
         ENTERPRISE rsNWSD
         VARIABLES { rndErrorDesc, rndErrorSeverity }
         DESCRIPTION
             "The HSM support engine is not detected as running. Reboot machine and contact Radware support if it fails to help."
     ::=  60

rsWSDProxySSLAcceleratorTypeDetected TRAP-TYPE
         ENTERPRISE rsNWSD
         VARIABLES { rndErrorDesc, rndErrorSeverity }
         DESCRIPTION
             "SSL Acceleration card <nCipher/Cavium/Broadcom> detected."
     ::=  61

rsWSDProxyOCSPServerError TRAP-TYPE
         ENTERPRISE rsNWSD
         VARIABLES { rndErrorDesc, rndErrorSeverity }
         DESCRIPTION
             "Failed to connect to OCSP server <OCSP-hostname> to verify certificate validity. Certificates will be rejected until connection is reestablished."
     ::=  62

rsWSDProxyOCSPResponseVerificationError TRAP-TYPE
         ENTERPRISE rsNWSD
         VARIABLES { rndErrorDesc, rndErrorSeverity }
         DESCRIPTION
             "Failed to verify OCSP response. Certificate will be rejected."
     ::=  63

rsWSDProxyOCSPQueryingError TRAP-TYPE
         ENTERPRISE rsNWSD
         VARIABLES { rndErrorDesc, rndErrorSeverity }
         DESCRIPTION
             "Failed to query <OCSP-hostname> OCSP server for certificate validity. Certificate will be rejected."
     ::=  64

rsWSDProxyCertificateRevokedRevocation TRAP-TYPE
         ENTERPRISE rsNWSD
         VARIABLES { rndErrorDesc, rndErrorSeverity }
         DESCRIPTION
             "Certificate was revoke according to CRL."
     ::=  65

rsWSDProxyErrorCRLUpdateTime TRAP-TYPE
         ENTERPRISE rsNWSD
         VARIABLES { rndErrorDesc, rndErrorSeverity }
         DESCRIPTION
             "CRL next update time not specified correctly. CRL updates may not occur until corrected."
     ::=  66

rsWSDProxyCRLExpired TRAP-TYPE
         ENTERPRISE rsNWSD
         VARIABLES { rndErrorDesc, rndErrorSeverity }
         DESCRIPTION
             "CRL has expired. Certificates will be accepted during prolongation period and rejected after it until CRL is updated."
     ::=  67

rsWSDProxyCertificateExpiresXDays TRAP-TYPE
         ENTERPRISE rsNWSD
         VARIABLES { rndErrorDesc, rndErrorSeverity }
         DESCRIPTION
             "Server Certificate will expire in X days."
     ::=  68

rsWSDProxyCompDisableDueMemoryLimit TRAP-TYPE
         ENTERPRISE rsNWSD
         VARIABLES { rndErrorDesc, rndErrorSeverity }
         DESCRIPTION
             "Compression disabled due memory limit."
     ::=  69

rsWSDProxyCompEnableAfterMemoryLimit TRAP-TYPE
         ENTERPRISE rsNWSD
         VARIABLES { rndErrorDesc, rndErrorSeverity }
         DESCRIPTION
             "Compression enabled after memory limit."
     ::=  70


rsWSDProxyCompLicenseOverFlow TRAP-TYPE
         ENTERPRISE rsNWSD
         VARIABLES { rndErrorDesc, rndErrorSeverity }
         DESCRIPTION
             "Compression License over flow."
     ::=  71

rsWSDProxySSLTpsLicenseOverFlow TRAP-TYPE
    ENTERPRISE rsNWSD
    VARIABLES { rndErrorDesc, rndErrorSeverity }
    DESCRIPTION
        "Deprecated"
     ::=  72


rsWSDProxyTslValidationFailure TRAP-TYPE
         ENTERPRISE rsNWSD
         VARIABLES { rndErrorDesc, rndErrorSeverity }
         DESCRIPTION
             "TSL file failed validation."
     ::=  73


rsWSDProxyTslOcspCertificateRevoked TRAP-TYPE
         ENTERPRISE rsNWSD
         VARIABLES { rndErrorDesc, rndErrorSeverity }
         DESCRIPTION
             "TSL OCSP Certificate revoced."
     ::=  74


rsWSDProxyTslOcspCertificateUnknown TRAP-TYPE
         ENTERPRISE rsNWSD
         VARIABLES { rndErrorDesc, rndErrorSeverity }
         DESCRIPTION
             "TSL OCSP Certificate unkonwn."
     ::=  75


rsWSDProxyTslSignNodeMissing TRAP-TYPE
         ENTERPRISE rsNWSD
         VARIABLES { rndErrorDesc, rndErrorSeverity }
         DESCRIPTION
             "TSL sign node missing."
     ::=  76

rsWSDProxyTslSignValidationFailure TRAP-TYPE
         ENTERPRISE rsNWSD
         VARIABLES { rndErrorDesc, rndErrorSeverity }
         DESCRIPTION
             "TSL sign validation failure."
     ::=  77

rsWSDProxyTslNewSeqLessThenExisting TRAP-TYPE
         ENTERPRISE rsNWSD
         VARIABLES { rndErrorDesc, rndErrorSeverity }
         DESCRIPTION
             "TSL new sequence less than existing."
     ::=  78


rsWSDProxyTslNextUpdateBeforeMinTtl TRAP-TYPE
         ENTERPRISE rsNWSD
         VARIABLES { rndErrorDesc, rndErrorSeverity }
         DESCRIPTION
             "TSL next update before configured minimum TTL."
     ::=  79

rdwrThroughputLicenseThresholdReache TRAP-TYPE
         ENTERPRISE rsNWSD
         VARIABLES { rndErrorDesc, rndErrorSeverity }
         DESCRIPTION
        "This trap is sent when the traffic throughput threshold is reached"
     ::=  80

rsADSSLThresholdReached TRAP-TYPE
         ENTERPRISE rsNWSD
         VARIABLES { rndErrorDesc, rndErrorSeverity }
         DESCRIPTION
        "This trap is sent when the ssl traffic throughput threshold is reached"
     ::=  81

rsADCompressionThresholdReached TRAP-TYPE
         ENTERPRISE rsNWSD
         VARIABLES { rndErrorDesc, rndErrorSeverity }
         DESCRIPTION
        "This trap is sent when the traffic compression rate  threshold is reached"
     ::=  82

rsWSDProxyTslOcspTimingErrorField TRAP-TYPE
         ENTERPRISE rsNWSD
         VARIABLES { rndErrorDesc, rndErrorSeverity }
         DESCRIPTION
        "This trap is sent when "
     ::=  83

rsWSDProxyTslInvalidOcspSigningAlg TRAP-TYPE
         ENTERPRISE rsNWSD
         VARIABLES { rndErrorDesc, rndErrorSeverity }
         DESCRIPTION
        "This trap is sent when the OCSP response is signed using non-authorized signing algorithm"
     ::=  84

rsWSDProxyTslFetcherFetchingError TRAP-TYPE
         ENTERPRISE rsNWSD
         VARIABLES { rndErrorDesc, rndErrorSeverity }
         DESCRIPTION
        "This trap is sent when a error occurs during TSL file fetching"
     ::=  85

rsWSDProxyTslFetcherSignatureError TRAP-TYPE
         ENTERPRISE rsNWSD
         VARIABLES { rndErrorDesc, rndErrorSeverity }
         DESCRIPTION
        "This trap is sent when the TSL signature fails to verify"
     ::=  86

rsWSDProxyTslFetcherOcspError TRAP-TYPE
         ENTERPRISE rsNWSD
         VARIABLES { rndErrorDesc, rndErrorSeverity }
         DESCRIPTION
        "This trap is sent when a TSL signature OCSP request fails"
     ::=  87

rsWSDProxyTslFetcherXmlParsingError TRAP-TYPE
         ENTERPRISE rsNWSD
         VARIABLES { rndErrorDesc, rndErrorSeverity }
         DESCRIPTION
        "This trap is sent when AppDirector fails to parse an TSL XML file"
     ::=  88

rsWSDProxyTslFetcherIdenticalSequenceNumber TRAP-TYPE
         ENTERPRISE rsNWSD
         VARIABLES { rndErrorDesc, rndErrorSeverity }
         DESCRIPTION
        "This trap is sent when a new fetched TSL file is identical to the existing one"
     ::=  89
rsWSDProxyTslTslFetchingDone TRAP-TYPE
         ENTERPRISE rsNWSD
         VARIABLES { rndErrorDesc, rndErrorSeverity }
         DESCRIPTION
        "This trap is sent when a new TSL file is fetched successfuly"
     ::=  90

rsWSDProxySSLCpsLicenseOverFlow TRAP-TYPE
         ENTERPRISE rsNWSD
         VARIABLES { rndErrorDesc, rndErrorSeverity }
         DESCRIPTION
             "SSL Cps License over flow."
     ::=  91

rsWSDProxyCRLOutOfDate TRAP-TYPE
         ENTERPRISE rsNWSD
         VARIABLES { rndErrorDesc, rndErrorSeverity }
         DESCRIPTION
        "This trap is sent when a CRL file attached to Client Authentication Policy is outdated"
     ::=  92

rsWSDFarmSessModeChanged TRAP-TYPE
         ENTERPRISE rsNWSD
         VARIABLES { rndErrorDesc, rndErrorSeverity }
         DESCRIPTION
        "This trap is sent when Farm Session Mode was changed"
     ::=  93

rdwrLacpPortUp TRAP-TYPE
         ENTERPRISE rsNWSD
         VARIABLES { rndErrorDesc, rndErrorSeverity }
         DESCRIPTION
        "This trap is sent when LACP controlled port is up"
     ::=  94

rdwrLacpPortDown TRAP-TYPE
         ENTERPRISE rsNWSD
         VARIABLES { rndErrorDesc, rndErrorSeverity }
         DESCRIPTION
        "This trap is sent when LACP controlled port is down"
     ::=  95

rsWSDProxyCRLFetchFailed TRAP-TYPE
         ENTERPRISE rsNWSD
         VARIABLES { rndErrorDesc, rndErrorSeverity }
         DESCRIPTION
        "This trap is sent when CRL file fetch fails"
     ::=  96

rdwrLacpPortSuspended TRAP-TYPE
         ENTERPRISE rsNWSD
         VARIABLES { rndErrorDesc, rndErrorSeverity }
         DESCRIPTION
        "This trap is sent when Link Aggregated port is suspended due to tunk's parameters incompatibility"
     ::=  97



END
