FASTPATH-QOS-AUTOVOIP-MIB DEFINITIONS ::= BEGIN

IMPORTS
    MODULE-IDENTITY, OBJECT-TYPE, IpAddress,
    Integer32, Unsigned32                FROM SNMPv2-SMI

    TEXTUAL-CONVENTION, RowStatus        FROM SNMPv2-TC
    InterfaceIndexOrZero                 FROM IF-MIB
    fastPathQOS                          FROM FASTPATH-QOS-MIB;

    fastPathQOSAUTOVOIP MODULE-IDENTITY
        LAST-UPDATED "200711230000Z" -- 23 Nov 2007 12:00:00 GMT
        ORGANIZATION "Broadcom Corporation"
        CONTACT-INFO
          "                      Customer Support
          Postal:                Broadcom Corporation
                                 100 Perimeter Park Drive
				 Suite H
                                 Morrisville, NC 27560
          Tel:                   +1 919 865 2700"
        DESCRIPTION
          "The MIB definitions for Quality of Service - VoIP Flex package."

        -- Revision history.
        REVISION
          "200711230000Z" -- 23 Nov 2007 12:00:00 GMT
        DESCRIPTION
          "Broadcom branding related changes."
        REVISION
          "200711230000Z" -- 3 Nov 2004 12:00:00 GMT
        DESCRIPTION
          "Initial revision."
    ::= { fastPathQOS 4 }

    PercentByFives ::= TEXTUAL-CONVENTION
         STATUS      current
         DESCRIPTION
                     "An unsigned integer representing a value expressed
                     as a percentage with five percent increments."
         SYNTAX      Unsigned32 (0|5|10|15|20|25|30|35|40|45|50|55|60|65|70|75|80|85|90|95|100)

    Sixteenths ::= TEXTUAL-CONVENTION
         STATUS      current
         DESCRIPTION
                     "An unsigned integer representing the numerator of a
                     value expressing a fraction in terms of sixteenths
                     (0/16, 1/16, 2/16, up to 16/16)."
         SYNTAX      Unsigned32 (0..16)

--*********************************************************************
--   agentAutoVoIPCfgGroup
--
--      Note: System-wide configuration is supported for this
--            group by using an index value of 0.
--*********************************************************************
agentAutoVoIPCfgGroup OBJECT IDENTIFIER ::= { fastPathQOSAUTOVOIP 1 }

    -- Auto VoIP Profile Configuration table (global and per-port)
    agentAutoVoIPTable OBJECT-TYPE
         SYNTAX      SEQUENCE OF AgentAutoVoIPEntry
         MAX-ACCESS  not-accessible
         STATUS      current
         DESCRIPTION
                     "A table providing configuration of Auto VoIP Profile."

         ::= { agentAutoVoIPCfgGroup 1 }

    agentAutoVoIPEntry OBJECT-TYPE
         SYNTAX      AgentAutoVoIPEntry
         MAX-ACCESS  not-accessible
         STATUS      current
         DESCRIPTION
                     "Auto VoIP Profile configuration for a port."
         INDEX   { agentAutoVoIPIntfIndex }
         ::= { agentAutoVoIPTable 1 }

    AgentAutoVoIPEntry::=
         SEQUENCE {
            agentAutoVoIPIntfIndex
                InterfaceIndexOrZero,
            agentAutoVoIPMode
                INTEGER,
            agentAutoVoIPCosQueue
                Unsigned32
         }

    agentAutoVoIPIntfIndex OBJECT-TYPE
         SYNTAX      InterfaceIndexOrZero
         MAX-ACCESS  not-accessible
         STATUS      current
         DESCRIPTION
                     "This is a unique index for an entry in the
                     agentAutoVoIPTable.  A non-zero value indicates
                     the ifIndex for the corresponding interface entry
                     in the ifTable.  A value of zero represents global
                     configuration, which in turn causes all interface
	         entries to be updated for a set operation, or
	         reflects the most recent global setting for a get
	         operation."

             ::= { agentAutoVoIPEntry 1 }

    agentAutoVoIPMode OBJECT-TYPE
         SYNTAX      INTEGER {
                       enable(1),
                       disable(2)
                       }
         MAX-ACCESS  read-write
         STATUS      current
         DESCRIPTION
                     "Enables / disables AutoVoIP profile on an interface."
         DEFVAL { 2 }

         ::= { agentAutoVoIPEntry 2 }

    agentAutoVoIPCosQueue OBJECT-TYPE
         SYNTAX      Unsigned32 (0..7)
         MAX-ACCESS  read-only
         STATUS      current
         DESCRIPTION
                     "Cos Queue to which all VoIP traffic is mapped to."

         ::= { agentAutoVoIPEntry 3 }


END
