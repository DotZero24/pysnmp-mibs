--****************************************************************************
--
-- Copyright (c) 2008 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--    Filename: brcm-cm-capability.mib
--    Author:   Kevin O'Neal
--    Creation Date: 11-feb-2004 (Happy 2nd Birthday Eric!)
--
--**************************************************************************
--    Description:
--
--		private MIB defining CM agent capability.
--              Note that this MIB does not define an accessible objects
--              and is provided strictly for use in the sysORTable.
--
--**************************************************************************
--    Revision History:
--
--**************************************************************************

BRCM-CM-CAPABILITY-MIB DEFINITIONS ::= BEGIN

IMPORTS
    MODULE-IDENTITY
        FROM SNMPv2-SMI
    AGENT-CAPABILITIES
        FROM SNMPv2-CONF
    cableDataAgentCapability
        FROM BRCM-CABLEDATA-SMI;

brcmCmCapability MODULE-IDENTITY
    LAST-UPDATED       "200803090000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Agent capabilities statement for DOCSIS 1.0, 1.1, 2.0, and 3.0
         cablemodem reference designs."
    REVISION      "200803090000Z"
    DESCRIPTION
        "Capabilities clauses for DOCSIS 2.0+IPv6 and DOCSIS 3.0 were added."
    REVISION      "200702050000Z"
    DESCRIPTION
        "Module description was updated.
         Product-Release statements were updated.
         Compilability issues were cleaned up:
         - snmpCommunityGroup changed to snmpCommunityTable group to reflect
           conformance group name change in revision 200308060000Z of the
           SNMP-COMMUNITY-MIB.
         - snmpCommunityTableGroup removed from SNMPv2-MIB statement"
    REVISION      "200402110000Z"
    DESCRIPTION
            "Initial version of this MIB module."
    ::= { cableDataAgentCapability 2 }

--
-- AGENT-CAPABILITIES statement for DOCSIS 1.0 CM agent
-- OID (for sysORID purposes) = 1.3.6.1.4.1.4413.2.3.2.1
--

cmDocsis10AgentCapability AGENT-CAPABILITIES
    PRODUCT-RELEASE
        "BFC DOCSIS 1.0 CM reference design 3.x, 4.x"
    STATUS	current
    DESCRIPTION
        "An agent which supports all MIBs required by the DOCSIS 1.0
         OSS specification."
    -- MIBs required by DOCSIS 1.0
    SUPPORTS    DOCS-CABLE-DEVICE-MIB -- RFC-2669
    INCLUDES    { docsDevBaseGroup,
                  docsDevEventGroup,
                  docsDevFilterGroup,
                  docsDevNmAccessGroup,
                  docsDevServerGroup,
                  docsDevSoftwareGroup,
                  docsDevCpeGroup }
    SUPPORTS    DOCS-IF-MIB -- RFC-2670
    INCLUDES    { docsIfBasicGroup,
                  docsIfCmGroup }
    SUPPORTS    DOCS-BPI-MIB -- RFC-3083
    INCLUDES    { docsBpiCmGroup }
 -- SUPPORTS    BRIDGE-MIB - - RFC-1493
 -- INCLUDES    { } - - No conformance section (SNMPv1 syntax), what to do??
    SUPPORTS    EtherLike-MIB -- RFC-2665
    INCLUDES    { etherStatsBaseGroup,
                  etherStatsLowSpeedGroup,
                  etherStatsHighSpeedGroup,
                  etherDuplexGroup }
    SUPPORTS    IP-MIB -- RFC-2011
    INCLUDES    { ipGroup,
                  icmpGroup }
    SUPPORTS    UDP-MIB -- RFC-2013
    INCLUDES    { udpGroup }
    SUPPORTS    USB-MIB -- draft-dolnik-usb-mib-00
    INCLUDES    { usbMibBasicGroup,
                  usbMibCDCGroup,
                  usbMibCDCEtherGroup,
                  usbCDCEtherXmtAddressGroup }
    SUPPORTS    IF-MIB -- RFC-2233
    INCLUDES    { ifGeneralInformationGroup,
                  ifVHCPacketGroup,
                  ifStackGroup2,
                  ifCounterDiscontinuityGroup }
    SUPPORTS    SNMPv2-MIB -- RFC-3418
    INCLUDES    { snmpGroup,
                  snmpSetGroup,
                  systemGroup,
                  snmpObsoleteGroup }
    ::= { brcmCmCapability 1 }

--
-- AGENT-CAPABILITIES statement for DOCSIS 1.1 CM agent
-- OID (for sysORID purposes) = 1.3.6.1.4.1.4413.2.3.2.2
--
cmDocsis11AgentCapability AGENT-CAPABILITIES
    PRODUCT-RELEASE
        "BFC DOCSIS 1.1 CM reference design 3.x, 4.x"
    STATUS	current
    DESCRIPTION
        "An agent which supports all MIBs required by the DOCSIS 1.1
         OSS specification."
    -- MIBs required by DOCSIS 1.1
    SUPPORTS    DOCS-CABLE-DEVICE-MIB -- RFC-2669
    INCLUDES    { docsDevBaseGroup,
                  docsDevEventGroup,
                  docsDevFilterGroup,
                  docsDevNmAccessGroup,
                  docsDevServerGroup,
                  docsDevSoftwareGroup,
                  docsDevCpeGroup }
    SUPPORTS    DOCS-IF-MIB -- draft-ietf-ipcdn-docs-rfmibv2-05
    INCLUDES    { docsIfBasicGroup,
                  docsIfCmGroup }
    SUPPORTS    DOCS-BPI-MIB -- RFC-3083
    INCLUDES    { docsBpiCmGroup }
    SUPPORTS    DOCS-BPI2-MIB -- draft-ietf-ipcdn-bpiplus-mib-05
    INCLUDES    { docsBpi2CmGroup,
                  docsBpi2CodeDownloadGroup }
    SUPPORTS    DOCS-QOS-MIB -- draft-ietf-ipcdn-qos-mib-04
    INCLUDES    { docsQosBaseGroup,
                  docsQosParamSetGroup,
                  docsQosSrvClassPolicyGroup }
    SUPPORTS    DOCS-CABLE-DEVICE-TRAP-MIB -- Appendix 'L' of the 1.1 OSS spec
    INCLUDES    { docsDevCmTrapControlGroup,
                  docsDevCmNotificationGroup }
    SUPPORTS    IF-MIB -- RFC-2863
    INCLUDES    { ifGeneralInformationGroup,
                  ifVHCPacketGroup,
                  ifStackGroup2,
                  ifCounterDiscontinuityGroup }
 -- SUPPORTS    BRIDGE-MIB - - RFC-1493
 -- INCLUDES    { } - - No conformance section (SNMPv1 syntax), what to do??
    SUPPORTS    EtherLike-MIB -- RFC-2665
    INCLUDES    { etherStatsBaseGroup,
                  etherStatsLowSpeedGroup,
                  etherStatsHighSpeedGroup,
                  etherDuplexGroup }
    SUPPORTS    IP-MIB -- RFC-2011
    INCLUDES    { ipGroup,
                  icmpGroup }
    SUPPORTS    UDP-MIB -- RFC-2013
    INCLUDES    { udpGroup }
    SUPPORTS    USB-MIB -- draft-dolnik-usb-mib-00
    INCLUDES    { usbMibBasicGroup,
                  usbMibCDCGroup,
                  usbMibCDCEtherGroup,
                  usbCDCEtherXmtAddressGroup }
    SUPPORTS    SNMP-TARGET-MIB -- RFC-3413
    INCLUDES    { snmpTargetBasicGroup,
                  snmpTargetResponseGroup,
                  snmpTargetCommandResponderGroup }
    SUPPORTS    SNMP-NOTIFICATION-MIB -- Also RFC-3413
    INCLUDES    { snmpNotifyGroup,
                  snmpNotifyFilterGroup }
    SUPPORTS    SNMP-USER-BASED-SM-MIB -- RFC-3414
    INCLUDES    { usmMIBBasicGroup }
    SUPPORTS    SNMP-VIEW-BASED-ACM-MIB -- RFC-3415
    INCLUDES    { vacmBasicGroup }
    SUPPORTS    SNMP-COMMUNITY-MIB -- RFC-2576
    INCLUDES    { snmpCommunityTableGroup }
    SUPPORTS    SNMP-USM-DH-OBJECTS-MIB -- RFC-2786
    INCLUDES    { usmDHKeyMIBBasicGroup,
                  usmDHKeyParamGroup,
                  usmDHKeyKickstartGroup }
    SUPPORTS    SNMPv2-MIB -- RFC-3418
    INCLUDES    { snmpGroup,
                  snmpSetGroup,
                  systemGroup,
                  snmpObsoleteGroup }
    ::= { brcmCmCapability 2 }

--
-- AGENT-CAPABILITIES statement for DOCSIS 2.0 CM agent
-- OID (for sysORID purposes) = 1.3.6.1.4.1.4413.2.3.2.3
--
cmDocsis20AgentCapability AGENT-CAPABILITIES
    PRODUCT-RELEASE
        "BFC DOCSIS 2.0 CM reference design 3.x, 4.x"
    STATUS	current
    DESCRIPTION
        "An agent which supports all MIBs required by the DOCSIS 2.0
         OSS specification."
    -- MIBs required by DOCSIS 2.0
    SUPPORTS    DOCS-CABLE-DEVICE-MIB -- RFC-2669
    INCLUDES    { docsDevBaseGroup,
                  docsDevEventGroup,
                  docsDevFilterGroup,
                  docsDevNmAccessGroup,
                  docsDevServerGroup,
                  docsDevSoftwareGroup,
                  docsDevCpeGroup }
    SUPPORTS    DOCS-IF-MIB -- draft-ietf-ipcdn-docs-rfmibv2-05
    INCLUDES    { docsIfBasicGroup,
                  docsIfCmGroup }
    SUPPORTS    DOCS-BPI-MIB -- RFC-3083
    INCLUDES    { docsBpiCmGroup }
    SUPPORTS    DOCS-BPI2-MIB -- draft-ietf-ipcdn-bpiplus-mib-05
    INCLUDES    { docsBpi2CmGroup,
                  docsBpi2CodeDownloadGroup }
    SUPPORTS    DOCS-QOS-MIB -- draft-ietf-ipcdn-qos-mib-04
    INCLUDES    { docsQosBaseGroup,
                  docsQosParamSetGroup,
                  docsQosSrvClassPolicyGroup }
    SUPPORTS    DOCS-CABLE-DEVICE-TRAP-MIB -- Annex 'H' of the 2.0 OSS spec
    INCLUDES    { docsDevCmTrapControlGroup,
                  docsDevCmNotificationGroup }
    SUPPORTS    IF-MIB -- RFC-2863
    INCLUDES    { ifGeneralInformationGroup,
                  ifVHCPacketGroup,
                  ifStackGroup2,
                  ifCounterDiscontinuityGroup }
 -- SUPPORTS    BRIDGE-MIB - - RFC-1493
 -- INCLUDES    { } - - No conformance section (SNMPv1 syntax), what to do??
    SUPPORTS    EtherLike-MIB -- RFC-2665
    INCLUDES    { etherStatsBaseGroup,
                  etherStatsLowSpeedGroup,
                  etherStatsHighSpeedGroup,
                  etherDuplexGroup }
    SUPPORTS    IP-MIB -- RFC-2011
    INCLUDES    { ipGroup,
                  icmpGroup }
    SUPPORTS    UDP-MIB -- RFC-2013
    INCLUDES    { udpGroup }
    SUPPORTS    USB-MIB -- draft-dolnik-usb-mib-00
    INCLUDES    { usbMibBasicGroup,
                  usbMibCDCGroup,
                  usbMibCDCEtherGroup,
                  usbCDCEtherXmtAddressGroup }
    SUPPORTS    SNMP-TARGET-MIB -- RFC-3413
    INCLUDES    { snmpTargetBasicGroup,
                  snmpTargetResponseGroup,
                  snmpTargetCommandResponderGroup }
    SUPPORTS    SNMP-NOTIFICATION-MIB -- Also RFC-3413
    INCLUDES    { snmpNotifyGroup,
                  snmpNotifyFilterGroup }
    SUPPORTS    SNMP-USER-BASED-SM-MIB -- RFC-3414
    INCLUDES    { usmMIBBasicGroup }
    SUPPORTS    SNMP-VIEW-BASED-ACM-MIB -- RFC-3415
    INCLUDES    { vacmBasicGroup }
    SUPPORTS    SNMP-COMMUNITY-MIB -- RFC-2576
    INCLUDES    { snmpCommunityTableGroup }
    SUPPORTS    SNMP-USM-DH-OBJECTS-MIB -- RFC-2786
    INCLUDES    { usmDHKeyMIBBasicGroup,
                  usmDHKeyParamGroup,
                  usmDHKeyKickstartGroup }
    SUPPORTS    SNMPv2-MIB -- RFC-3418
    INCLUDES    { snmpGroup,
                  snmpSetGroup,
                  systemGroup,
                  snmpObsoleteGroup }
    ::= { brcmCmCapability 3 }


--
-- AGENT-CAPABILITIES statement for DOCSIS 2.0 + IPv6 CM agent
-- OID (for sysORID purposes) = 1.3.6.1.4.1.4413.2.3.2.4
--
cmDocsis20AgentCapability AGENT-CAPABILITIES
    PRODUCT-RELEASE
        "BFC DOCSIS 2.0+IPv6 CM reference design 3.x, 4.x"
    STATUS	current
    DESCRIPTION
        "An agent which supports all MIBs required by the DOCSIS 2.0
         OSS specification as well as those specified by the 2.0+IPv6
         technical report."
    SUPPORTS    DOCS-CABLE-DEVICE-MIB -- RFC-4639
    INCLUDES    { docsDevBaseGroup,
                  docsDevBaseIgmpGroup,
                  docsDevBaseMaxCpeGroup,
                  docsDevSoftwareGroupV2,
                  docsDevServerGroupV2,
                  docsDevEventGroupV2,
                  docsDevFilterGroup,
                  docsDevNmAccessGroup,
                  docsDevCpeGroup }
    SUPPORTS    DOCS-IF-MIB -- RFC-4546
    INCLUDES    { docsIfBasicGroup,
                  docsIfCmGroup }
    SUPPORTS    DOCS-BPI-MIB -- RFC-3083
    INCLUDES    { docsBpiCmGroup }
    SUPPORTS    DOCS-BPI2-MIB -- draft-ietf-ipcdn-bpiplus-mib-05
    INCLUDES    { docsBpi2CmGroup,
                  docsBpi2CodeDownloadGroup }
    SUPPORTS    DOCS-IETF-BPI2-MIB -- RFC-4131
    INCLUDES    { docsBpi2CmGroup,
                  docsBpi2CodeDownloadGroup }
    SUPPORTS    DOCS-QOS-MIB -- draft-ietf-ipcdn-qos-mib-04
    INCLUDES    { docsQosBaseGroup,
                  docsQosParamSetGroup,
                  docsQosSrvClassPolicyGroup }
    SUPPORTS    DOCS-QOS3-MIB -- Annex Q OSS 3.0 spec
    INCLUDES    { docsQosBaseGroup, -- docsQosPktClassTable only
                  docsQosCmGroup }   -- docsQosCmDsidTable, docsQosCmDsidStatsTable, docsQosCmDsidClientTable only
    SUPPORTS    DOCS-CABLE-DEVICE-TRAP-MIB -- Annex 'H' of the 2.0 OSS spec
    INCLUDES    { docsDevCmTrapControlGroup,
                  docsDevCmNotificationGroup }
    SUPPORTS    IF-MIB -- RFC-2863
    INCLUDES    { ifGeneralInformationGroup,
                  ifVHCPacketGroup,
                  ifStackGroup2,
                  ifCounterDiscontinuityGroup }
    SUPPORTS    BRIDGE-MIB -- RFC-4188
    INCLUDES    { dot1dBaseBridgeGroup,
                  dot1dBasePortGroup,
                  dot1dTpFdbGroup,
                  dot1dTpGroup }
    SUPPORTS    EtherLike-MIB -- RFC-3635
    INCLUDES    { etherStatsLowSpeedGroup,
                  etherStatsHighSpeedGroup,
                  etherDuplexGroup,
                  etherStatsBaseGroup2,
                  etherStatsHalfDuplexGroup,
                  etherHCStatsGroup }
    SUPPORTS    IP-MIB -- RFC-4293
    INCLUDES    { ipGroup,
                  icmpGroup,
                  ipv4GeneralGroup,
                  ipv4IfGroup,
                  ipv6GeneralGroup2,
                  ipv6IfGroup,
                  ipLastChangeGroup,
                  ipAddressGroup,
                  ipNetToPhysicalGroup,
                  icmpStatsGroup }
    SUPPORTS    UDP-MIB -- RFC-4113
    INCLUDES    { udpGroup,
                  udpBaseGroup,
                  udpHCGroup,
                  udpEndpointGroup }
    SUPPORTS    USB-MIB -- draft-dolnik-usb-mib-02
    INCLUDES    { usbMibBasicGroup,
                  usbMibCDCGroup,
                  usbMibCDCEtherGroup,
                  usbCDCEtherXmtAddressGroup }
    SUPPORTS    SNMP-TARGET-MIB -- RFC-3413
    INCLUDES    { snmpTargetBasicGroup,
                  snmpTargetResponseGroup,
                  snmpTargetCommandResponderGroup }
    SUPPORTS    SNMP-NOTIFICATION-MIB -- Also RFC-3413
    INCLUDES    { snmpNotifyGroup,
                  snmpNotifyFilterGroup }
    SUPPORTS    SNMP-USER-BASED-SM-MIB -- RFC-3414
    INCLUDES    { usmMIBBasicGroup }
    SUPPORTS    SNMP-VIEW-BASED-ACM-MIB -- RFC-3415
    INCLUDES    { vacmBasicGroup }
    SUPPORTS    SNMP-COMMUNITY-MIB -- RFC-2576
    INCLUDES    { snmpCommunityTableGroup }
    SUPPORTS    SNMP-USM-DH-OBJECTS-MIB -- RFC-2786
    INCLUDES    { usmDHKeyMIBBasicGroup,
                  usmDHKeyParamGroup,
                  usmDHKeyKickstartGroup }
    SUPPORTS    SNMPv2-MIB -- RFC-3418
    INCLUDES    { snmpGroup,
                  snmpSetGroup,
                  systemGroup,
                  snmpObsoleteGroup }
    ::= { brcmCmCapability 4 }

--
-- AGENT-CAPABILITIES statement for DOCSIS 3.0 CM agent
-- OID (for sysORID purposes) = 1.3.6.1.4.1.4413.2.3.2.5
--
cmDocsis20AgentCapability AGENT-CAPABILITIES
    PRODUCT-RELEASE
        "BFC DOCSIS 3.0 CM reference design 4.x"
    STATUS	current
    DESCRIPTION
        "An agent which supports all MIBs required by the DOCSIS 3.0
         OSS specification."
    -- MIBs required by DOCSIS 3.0
    SUPPORTS    DOCS-CABLE-DEVICE-MIB -- RFC-4639
    INCLUDES    { docsDevBaseGroup,
                  docsDevBaseIgmpGroup,
                  docsDevBaseMaxCpeGroup,
                  docsDevSoftwareGroupV2,
                  docsDevServerGroupV2,
                  docsDevEventGroupV2,
                  docsDevFilterGroup,
                  docsDevNmAccessGroup,
                  docsDevCpeGroup }
    SUPPORTS    DOCS-IF-MIB -- RFC-4546
    INCLUDES    { docsIfBasicGroup,
                  docsIfCmGroup }
    SUPPORTS    DOCS-IF3-MIB -- Annex Q OSS 3.0 spec
    INCLUDES    { docsIf3CmGroup,
                  docsIfCmGroup }
    SUPPORTS    DOCS-BPI-MIB -- RFC-3083
    INCLUDES    { docsBpiCmGroup }
    SUPPORTS    DOCS-BPI2-MIB -- draft-ietf-ipcdn-bpiplus-mib-05
    INCLUDES    { docsBpi2CmGroup,
                  docsBpi2CodeDownloadGroup }
    SUPPORTS    DOCS-IETF-BPI2-MIB -- RFC-4131
    INCLUDES    { docsBpi2CmGroup,
                  docsBpi2CodeDownloadGroup }
    SUPPORTS    DOCS-QOS-MIB -- draft-ietf-ipcdn-qos-mib-04
    INCLUDES    { docsQosBaseGroup,
                  docsQosParamSetGroup,
                  docsQosSrvClassPolicyGroup }
    SUPPORTS    DOCS-QOS3-MIB -- Annex Q OSS 3.0 spec
    INCLUDES    { docsQosBaseGroup,
                  docsQosCmGroup }
    SUPPORTS    DOCS-CABLE-DEVICE-TRAP-MIB -- Annex 'H' of the 2.0 OSS spec
    INCLUDES    { docsDevCmTrapControlGroup,
                  docsDevCmNotificationGroup }
    SUPPORTS    IF-MIB -- RFC-2863
    INCLUDES    { ifGeneralInformationGroup,
                  ifVHCPacketGroup,
                  ifStackGroup2,
                  ifCounterDiscontinuityGroup }
    SUPPORTS    BRIDGE-MIB -- RFC-4188
    INCLUDES    { dot1dBaseBridgeGroup,
                  dot1dBasePortGroup,
                  dot1dTpFdbGroup,
                  dot1dTpGroup }
    SUPPORTS    EtherLike-MIB -- RFC-3635
    INCLUDES    { etherStatsLowSpeedGroup,
                  etherStatsHighSpeedGroup,
                  etherDuplexGroup,
                  etherStatsBaseGroup2,
                  etherStatsHalfDuplexGroup,
                  etherHCStatsGroup }
    SUPPORTS    IP-MIB -- RFC-4293
    INCLUDES    { ipGroup,
                  icmpGroup,
                  ipv4GeneralGroup,
                  ipv4IfGroup,
                  ipv6GeneralGroup2,
                  ipv6IfGroup,
                  ipLastChangeGroup,
                  ipAddressGroup,
                  ipNetToPhysicalGroup,
                  icmpStatsGroup }
    SUPPORTS    UDP-MIB -- RFC-4113
    INCLUDES    { udpGroup,
                  udpBaseGroup,
                  udpHCGroup,
                  udpEndpointGroup }
    SUPPORTS    USB-MIB -- draft-dolnik-usb-mib-02
    INCLUDES    { usbMibBasicGroup,
                  usbMibCDCGroup,
                  usbMibCDCEtherGroup,
                  usbCDCEtherXmtAddressGroup }
    SUPPORTS    SNMP-TARGET-MIB -- RFC-3413
    INCLUDES    { snmpTargetBasicGroup,
                  snmpTargetResponseGroup,
                  snmpTargetCommandResponderGroup }
    SUPPORTS    SNMP-NOTIFICATION-MIB -- Also RFC-3413
    INCLUDES    { snmpNotifyGroup,
                  snmpNotifyFilterGroup }
    SUPPORTS    SNMP-USER-BASED-SM-MIB -- RFC-3414
    INCLUDES    { usmMIBBasicGroup }
    SUPPORTS    SNMP-VIEW-BASED-ACM-MIB -- RFC-3415
    INCLUDES    { vacmBasicGroup }
    SUPPORTS    SNMP-COMMUNITY-MIB -- RFC-2576
    INCLUDES    { snmpCommunityTableGroup }
    SUPPORTS    SNMP-USM-DH-OBJECTS-MIB -- RFC-2786
    INCLUDES    { usmDHKeyMIBBasicGroup,
                  usmDHKeyParamGroup,
                  usmDHKeyKickstartGroup }
    SUPPORTS    SNMPv2-MIB -- RFC-3418
    INCLUDES    { snmpGroup,
                  snmpSetGroup,
                  systemGroup,
                  snmpObsoleteGroup }
    ::= { brcmCmCapability 5 }

END
