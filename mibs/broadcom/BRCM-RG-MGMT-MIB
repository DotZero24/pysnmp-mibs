--**************************************************************************
--
--    Copyright 2007 Broadcom Corporation
--    All Rights Reserved
--    No portions of this material may be reproduced in any form without the
--    written permission of:
--             Broadcom Corporation
--             16251 Laguna Canyon Road
--             Irvine, California  92618
--    All information contained in this document is Broadcom Corporation
--    company private, proprietary, and trade secret.
--
--
--
--**************************************************************************
--    Filename: brcm-cablehome-mgmt.mib
--    Author:   Kevin O'Neal
--    Creation Date: 6-march-2003
--
--**************************************************************************
--    Description:
--
--		private MIB for runtime (not factory) CableHome management
--
--**************************************************************************
--    Revision History:
--
--**************************************************************************

BRCM-RG-MGMT-MIB DEFINITIONS ::= BEGIN

IMPORTS
    MODULE-IDENTITY,
    OBJECT-TYPE
        FROM SNMPv2-SMI
    TruthValue
        FROM SNMPv2-TC
    cableDataMgmtMIBObjects
        FROM BRCM-CABLEDATA-MGMT-MIB;

residentialGatewayMgmt MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadacom proprietary MIB for runtime management of residential gateway
         devices."
    REVISION      "200702050000Z"
    DESCRIPTION
        "Module description was updated."
    REVISION      "200406160000Z"
    DESCRIPTION
        "Added object rgVpnEnabled."
    REVISION      "200303310000Z"
    DESCRIPTION
        "Initial version of this MIB module."
    ::= { cableDataMgmtMIBObjects 7 }

rgMgmtBase OBJECT IDENTIFIER ::= { residentialGatewayMgmt 1 }

rgOperMode OBJECT-TYPE
    SYNTAX      INTEGER {
                disabled(1),
                residentialGateway(2),
                cableHome10(3),
                cableHome11(4)
    }
    MAX-ACCESS  read-write
    STATUS      current
    DESCRIPTION
        "Sets the operational mode of the device with regard to residential
         gateway behaviour."
    ::= { rgMgmtBase 1 }

rgRipEnabled OBJECT-TYPE
    SYNTAX      TruthValue
    MAX-ACCESS  read-write
    STATUS      current
    DESCRIPTION
        "Enables or disable router information protocol support in the device."
    ::= { rgMgmtBase 2 }

rgVpnEnabled OBJECT-TYPE
    SYNTAX      TruthValue
    MAX-ACCESS  read-write
    STATUS      current
    DESCRIPTION
        "Enables or disable virtual private network support in the device."
    ::= { rgMgmtBase 3 }

END
