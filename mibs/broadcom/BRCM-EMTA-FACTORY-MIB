--**************************************************************************
--
--    Copyright 2007 Broadcom Corporation
--    All Rights Reserved
--    No portions of this material may be reproduced in any form without the
--    written permission of:
--             Broadcom Corporation
--             16251 Laguna Canyon Road
--             Irvine, California  92618
--    All information contained in this document is Broadcom Corporation
--    company private, proprietary, and trade secret.
--
--
--
--**************************************************************************
--    Filename: brcm-emta-factory.mib
--    Author:   Kevin O'Neal
--    Creation Date: 23-august-2002
--
--**************************************************************************
--    Description:
--
--		private MIB for EMTA factory
--
--**************************************************************************
--    Revision History:
--
--**************************************************************************

BRCM-EMTA-FACTORY-MIB DEFINITIONS ::= BEGIN

IMPORTS
    MODULE-IDENTITY,
    OBJECT-TYPE
        FROM SNMPv2-SMI
    TruthValue
        FROM SNMPv2-TC
    cableDataFactory
        FROM BRCM-CABLEDATA-FACTORY-MIB;

emtaFactory MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for factory management and configuration
         of objects related to EMTA products."
    REVISION      "200702050000Z"
    DESCRIPTION
        "Module description was updated.
         Compilability issues were cleaned up:
         - Chronological order of revision history was corrected."
    REVISION      "200511140000Z"
    DESCRIPTION
        "Changed description clause for objects emtaTelephonyRootCertificate
         and emtaManufacturerCertificate."
    REVISION      "200506280000Z"
    DESCRIPTION
        "Added object emtaDynamicLoadBalancingEnabled."
    REVISION      "200506140000Z"
    DESCRIPTION
        "Added object emtaHighVoltageRingEnabled."
    REVISION      "200403240000Z"
    DESCRIPTION
        "Changed behavior of emtaDevPrivKeyModulus and
         emtaDevPrivKeyExponent objects to return a CRC32 of the
         data when read rather than the data itself for security reasons."
    REVISION      "200208230000Z"
    DESCRIPTION
        "Initial version of this MIB module."
    ::= { cableDataFactory 6 }

-- emtaFactoryBase: miscellaneous control/state objects for factory mode
emtaFactoryBase OBJECT IDENTIFIER ::= { emtaFactory 1 }

emtaHighVoltageRingEnabled  OBJECT-TYPE
    SYNTAX      TruthValue
    MAX-ACCESS  read-write
    STATUS      current
    DESCRIPTION
        "Controls the use of high voltage ringing for this device."
    ::= { emtaFactoryBase 1 }

emtaDynamicLoadBalancingEnabled  OBJECT-TYPE
    SYNTAX      TruthValue
    MAX-ACCESS  read-write
    STATUS      current
    DESCRIPTION
        "Controls the use of dynamic load balancing for platforms which support
         this feature."
    ::= { emtaFactoryBase 2 }

-- chFactorySecurity: Security-related factory objects
emtaFactorySecurity OBJECT IDENTIFIER ::= { emtaFactory 2 }

emtaTelephonyRootCertificate  OBJECT-TYPE
    SYNTAX      OCTET STRING -- size?
    MAX-ACCESS  read-write
    STATUS      current
    DESCRIPTION
        "An alternate PacketCable telephony root certificate.  An alternate
         certificate is most often used during lab or certification testing.  It
         may also be used by an operator who does not use telephony certificates
         that chain the CableLabs root certificate."
    ::= { emtaFactorySecurity 1 }

emtaManufacturerCertificate  OBJECT-TYPE
    SYNTAX      OCTET STRING -- size?
    MAX-ACCESS  read-write
    STATUS      current
    DESCRIPTION
        "The Packetcable manufacturer certificate."
    ::= { emtaFactorySecurity 2 }

emtaDeviceCertificate  OBJECT-TYPE
    SYNTAX      OCTET STRING -- size?
    MAX-ACCESS  read-write
    STATUS      current
    DESCRIPTION
        "The PacketCable device certificate."
    ::= { emtaFactorySecurity 3 }

emtaDevPrivKeyModulus  OBJECT-TYPE
    SYNTAX      OCTET STRING -- size?
    MAX-ACCESS  read-write
    STATUS      current
    DESCRIPTION
        "The PacketCable private key modulus.  In order to prevent
         unauthorized discovery of the private key, when read this object
         does not return the modulus.  Instead, a CRC32 is performed over the
         modulus and the resulting 32 bit value is returned as a 4 byte octet
         string.  Note that if the modulus is empty, a CRC value of 00 00 00 00
         is returned."
    ::= { emtaFactorySecurity 4 }

emtaDevPrivKeyExponent  OBJECT-TYPE
    SYNTAX      OCTET STRING -- size?
    MAX-ACCESS  read-write
    STATUS      current
    DESCRIPTION
        "The PacketCable private key exponent.  In order to prevent
         unauthorized discovery of the private key, when read this object
         does not return the exponent.  Instead, a CRC32 is performed over the
         exponent and the resulting 32 bit value is returned as a 4 byte octet
         string.  Note that if the exponent is empty, a CRC value of 00 00 00 00
         is returned."
    ::= { emtaFactorySecurity 5 }

END
