--**************************************************************************
--
--    Copyright 2007 Broadcom Corporation
--    All Rights Reserved
--    No portions of this material may be reproduced in any form without the
--    written permission of:
--             Broadcom Corporation
--             16251 Laguna Canyon Road
--             Irvine, California  92618
--    All information contained in this document is Broadcom Corporation
--    company private, proprietary, and trade secret.
--
--
--
--**************************************************************************
--    Filename: brcm-v2-mgmt.mib
--    Author:   Kevin O'Neal
--    Creation Date: 6-march-2003
--
--**************************************************************************
--    Description:
--
--		private MIB for runtime (not factory) V2 management
--
--**************************************************************************
--    Revision History:
--
--**************************************************************************

BRCM-V2-MGMT-MIB DEFINITIONS ::= BEGIN

IMPORTS
    MODULE-IDENTITY,
    OBJECT-TYPE
        FROM SNMPv2-SMI
    cableDataMgmtMIBObjects
        FROM BRCM-CABLEDATA-MGMT-MIB;

v2Mgmt MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for runtime management and configuration
         of objects related to the V2 software architecture."
    REVISION      "200702050000Z"
    DESCRIPTION
        "Module description was updated."
    REVISION      "200303060000Z"
    DESCRIPTION
            "Initial version of this MIB module."
    ::= { cableDataMgmtMIBObjects 4 }

v2MgmtBase OBJECT IDENTIFIER ::= { v2Mgmt 1 }

END
