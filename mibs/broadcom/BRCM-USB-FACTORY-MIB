--**************************************************************************
--
--    Copyright 2007 Broadcom Corporation
--    All Rights Reserved
--    No portions of this material may be reproduced in any form without the
--    written permission of:
--             Broadcom Corporation
--             16251 Laguna Canyon Road
--             Irvine, California  92618
--    All information contained in this document is Broadcom Corporation
--    company private, proprietary, and trade secret.
--
--
--
--**************************************************************************
--    Filename: brcm-usb-factory.mib
--    Author:   Kevin O'Neal
--    Creation Date: 25-august-2004
--
--**************************************************************************
--    Description:
--
--		factory MIB for USB settings
--
--**************************************************************************
--    Revision History:
--
--**************************************************************************

BRCM-USB-FACTORY-MIB DEFINITIONS ::= BEGIN

IMPORTS
    MODULE-IDENTITY,
    OBJECT-TYPE,
    Unsigned32
        FROM SNMPv2-SMI
    TruthValue,
    MacAddress
        FROM SNMPv2-TC
    cableDataFactory
        FROM BRCM-CABLEDATA-FACTORY-MIB;

usbFactory MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB for factory management and configuration
         of objects related to the USB network interface."
    REVISION      "200702050000Z"
    DESCRIPTION
        "Module description was updated.
         Compilability issues were cleaned up:
         - Chronological order of revision history was corrected."
    REVISION      "200411120000Z"
    DESCRIPTION
        "Changed root node of this module to cableDataFactory.8 to resolve
         conflict with residentialGatewayFactory root node from the
         BRCM-RG-FACTORY-MIB."
    REVISION      "200408250000Z"
    DESCRIPTION
        "Initial version of this MIB module."
    ::= { cableDataFactory 8 }

usbFactMacAddress OBJECT-TYPE
    SYNTAX      MacAddress
    MAX-ACCESS  read-write
    STATUS      current
    DESCRIPTION
       "The MAC SA that will be used when building the LLC header for packets
        from the PC attached via USB."
    ::= { usbFactory 1 }

usbFactVendorId OBJECT-TYPE
    SYNTAX      Unsigned32
    MAX-ACCESS  read-write
    STATUS      current
    DESCRIPTION
       "The USB Vendor Id that will be used during USB enumeration.  This is
        used by the PC in combination with the USB Device Id to select a USB
        driver."
    ::= { usbFactory 2 }

usbFactDeviceId OBJECT-TYPE
    SYNTAX      Unsigned32
    MAX-ACCESS  read-write
    STATUS      current
    DESCRIPTION
       "The USB Device Id that will be used during USB enumeration.  This is
        used by the PC in combination with the USB Vendor Id to select a USB
        driver."
    ::= { usbFactory 3 }

usbFactRNDISDriverEnable OBJECT-TYPE
    SYNTAX      TruthValue
    MAX-ACCESS  read-write
    STATUS      current
    DESCRIPTION
       "Enables or Disables the USB RNDIS Driver that will be used during USB
        enumeration.  This is used by the PC in combination with the USB Vendor
        ID and USB Device Id to select a USB driver."
    ::= { usbFactory 4 }

END
