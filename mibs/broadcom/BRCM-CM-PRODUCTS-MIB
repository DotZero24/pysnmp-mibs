--**************************************************************************
--
--    Copyright 2007 Broadcom Corporation
--    All Rights Reserved
--    No portions of this material may be reproduced in any form without the
--    written permission of:
--             Broadcom Corporation
--             16251 Laguna Canyon Road
--             Irvine, California  92618
--    All information contained in this document is Broadcom Corporation
--    company private, proprietary, and trade secret.
--
--
--
--**************************************************************************
--    Filename: brcm-cm-products.mib
--    Author:   Kevin O'Neal
--    Creation Date: 11-feb-2004
--
--**************************************************************************
--    Description:
--
--		private MIB defining all CM product IDs.
--              Note that this MIB does not define an accessible objects
--              and is provided strictly for use in sysObjectID.
--
--**************************************************************************
--    Revision History:
--
--**************************************************************************

BRCM-CM-PRODUCTS-MIB DEFINITIONS ::= BEGIN

IMPORTS
    MODULE-IDENTITY
        FROM SNMPv2-SMI
    AGENT-CAPABILITIES
        FROM SNMPv2-CONF
    cableDataProducts
        FROM BRCM-CABLEDATA-SMI;

brcmCmProducts MODULE-IDENTITY
    LAST-UPDATED       "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadcom proprietary MIB which identifies the product IDs for various
         cablemodem reference designs.  These objects identifiers are the
         default values returned for sysObjectID in the unmodified reference
         design software."
    REVISION      "200702050000Z"
    DESCRIPTION
        "Module description was updated."
    REVISION      "200402110000Z"
    DESCRIPTION
            "Initial version of this MIB module."
    ::= { cableDataProducts 2 }

--
-- Product IDs for Broadcom DOCSIS cablemodem reference designs.
-- We use the convention of brcmCmProducts.chip for our reference design
-- sysObjectID values.  This is obviously not a solution which extends to
-- real-world products since there could well be many products based on a
-- given chipset.  However, for our internal purposes it is sufficient.
-- New products will be added to this list as new chipsets become available.
--

-- cmReferenceDesigns = 1.3.6.1.4.1.4413.2.1.2.1
cmReferenceDesigns OBJECT IDENTIFIER ::= { brcmCmProducts 1 }

bcm93220 OBJECT IDENTIFIER ::= { cmReferenceDesigns 3220 }
bcm93300 OBJECT IDENTIFIER ::= { cmReferenceDesigns 3300 }
bcm93345 OBJECT IDENTIFIER ::= { cmReferenceDesigns 3345 }
bcm93348 OBJECT IDENTIFIER ::= { cmReferenceDesigns 3348 }
bcm93349 OBJECT IDENTIFIER ::= { cmReferenceDesigns 3349 }
bcm93350 OBJECT IDENTIFIER ::= { cmReferenceDesigns 3350 }
bcm93351 OBJECT IDENTIFIER ::= { cmReferenceDesigns 3351 }
bcm93352 OBJECT IDENTIFIER ::= { cmReferenceDesigns 3352 }
bcm93360 OBJECT IDENTIFIER ::= { cmReferenceDesigns 3360 }
bcm93367 OBJECT IDENTIFIER ::= { cmReferenceDesigns 3367 }
bcm93368 OBJECT IDENTIFIER ::= { cmReferenceDesigns 3368 }
bcm93380 OBJECT IDENTIFIER ::= { cmReferenceDesigns 3380 }
bcm93381 OBJECT IDENTIFIER ::= { cmReferenceDesigns 3381 }

END
