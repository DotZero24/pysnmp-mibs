--****************************************************************************
--
-- Copyright (c) 2008 Broadcom Corporation
--
-- This program is the proprietary software of Broadcom Corporation and/or
-- its licensors, and may only be used, duplicated, modified or distributed
-- pursuant to the terms and conditions of a separate, written license
-- agreement executed between you and Broadcom (an "Authorized License").
-- Except as set forth in an Authorized License, Broadcom grants no license
-- (express or implied), right to use, or waiver of any kind with respect to
-- the Software, and Broadcom expressly reserves all rights in and to the
-- Software and all intellectual property rights therein.  IF YOU HAVE NO
-- AUTHORIZED LICENSE, THEN YOU HAVE NO RIGHT TO USE THIS SOFTWARE IN ANY WAY,
-- AND SHOULD IMMEDIATELY NOTIFY BROADCOM AND DISCONTINUE ALL USE OF THE
-- SOFTWARE.
--
-- Except as expressly set forth in the Authorized License,
--
-- 1.     This program, including its structure, sequence and organization,
-- constitutes the valuable trade secrets of Broadcom, and you shall use all
-- reasonable efforts to protect the confidentiality thereof, and to use this
-- information only in connection with your use of Broadcom integrated circuit
-- products.
--
-- 2.     TO THE MAXIMUM EXTENT PERMITTED BY LAW, THE SOFTWARE IS PROVIDED
-- "AS IS" AND WITH ALL FAULTS AND BROADCOM MAKES NO PROMISES, REPRESENTATIONS
-- OR WARRANTIES, EITHER EXPRESS, IMPLIED, STATUTORY, OR OTHERWISE, WITH
-- RESPECT TO THE SOFTWARE.  BROADCOM SPECIFICALLY DISCLAIMS ANY AND ALL
-- IMPLIED WARRANTIES OF TITLE, MERCHANTABILITY, NONINFRINGEMENT, FITNESS FOR
-- A PARTICULAR PURPOSE, LACK OF VIRUSES, ACCURACY OR COMPLETENESS, QUIET
-- ENJOYMENT, QUIET POSSESSION OR CORRESPONDENCE TO DESCRIPTION. YOU ASSUME
-- THE ENTIRE RISK ARISING OUT OF USE OR PERFORMANCE OF THE SOFTWARE.
--
-- 3.     TO THE MAXIMUM EXTENT PERMITTED BY LAW, IN NO EVENT SHALL BROADCOM
-- OR ITS LICENSORS BE LIABLE FOR (i) CONSEQUENTIAL, INCIDENTAL, SPECIAL,
-- INDIRECT, OR EXEMPLARY DAMAGES WHATSOEVER ARISING OUT OF OR IN ANY WAY
-- RELATING TO YOUR USE OF OR INABILITY TO USE THE SOFTWARE EVEN IF BROADCOM
-- HAS BEEN ADVISED OF THE POSSIBILITY OF SUCH DAMAGES; OR (ii) ANY AMOUNT IN
-- EXCESS OF THE AMOUNT ACTUALLY PAID FOR THE SOFTWARE ITSELF OR U.S. $1,
-- WHICHEVER IS GREATER. THESE LIMITATIONS SHALL APPLY NOTWITHSTANDING ANY
-- FAILURE OF ESSENTIAL PURPOSE OF ANY LIMITED REMEDY.
--
--****************************************************************************
--
--    Filename: brcm-cabledata-smi.mib
--    Author:   Kevin O'Neal
--    Creation Date: 15-march-2002
--
--**************************************************************************
--    Description:
--
--		SMI MIB for cableData branch of Broadcom private MIBs
--
--**************************************************************************
--    Revision History:
--
--**************************************************************************

BRCM-CABLEDATA-SMI DEFINITIONS ::= BEGIN

IMPORTS
    MODULE-IDENTITY,
    OBJECT-IDENTITY
        FROM SNMPv2-SMI
    broadcom
        FROM BRCM-SMI; -- Defined above in this same module

cableData MODULE-IDENTITY
    LAST-UPDATED "200705210000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "The Structure of Management Information for the Broadcom
         enterprise dealing with Cable Modems, Cable Modem Termination
         Systems, and related data-over-CATV systems."
    REVISION      "200705210000Z"
    DESCRIPTION
        "Fixed an error in the value of the broadcom root node."
    REVISION      "200702050000Z"
    DESCRIPTION
        "Compilability issues were cleaned up:
        - Changed method of defining broadcom root node."
    REVISION      "200207310000Z"
    DESCRIPTION
        "Initial version of this MIB module."
    ::= { broadcom 2 }

cableDataProducts OBJECT-IDENTITY
    STATUS	current
    DESCRIPTION
        "cableDataProducts is the root OBJECT IDENTIFIER from
         which sysObjectID values are assigned.  Actual
         values are defined in BRCM-CABLEDATA-PRODUCTS-MIB."
    ::= { cableData 1 }

cableDataMgmt OBJECT-IDENTITY
    STATUS	current
    DESCRIPTION
        "cableDataMgmt is the main subtree for new mib development."
    ::= { cableData 2 }

cableDataAgentCapability OBJECT-IDENTITY
    STATUS	current
    DESCRIPTION
        "cableDataAgentCapability provides a root OBJECT IDENTIFIER
         from which AGENT-CAPABILITIES values may be assigned,
         for use in the sysORTable."
    ::= { cableData 3 }

cableDataExperimental OBJECT-IDENTITY
    STATUS	current
    DESCRIPTION
        "cableDataExperimental provides a root OBJECT IDENTIFIER
         where experimental mibs may be temporarily
         placed.  MIBs are typically only located here as works-in-progress,
         on either the IANA or BRCM development path.

         MIBs should never be published under this branch, it
         should only be used internally for development purposes."
    ::= { cableData 4 }

cableDataPrivate OBJECT-IDENTITY
    STATUS	current
    DESCRIPTION
        "cableDataPrivate provides a root OBJECT IDENTIFIER under which are
         placed objects which are only intended to be used in a manufacturing,
         engineering, or other internal environment.  Objects under this node
         should not be available in a deployed device."
    ::= { cableData 99 }

END
