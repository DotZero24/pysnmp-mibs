--**************************************************************************
--
--    Copyright 2007 Broadcom Corporation
--    All Rights Reserved
--    No portions of this material may be reproduced in any form without the
--    written permission of:
--             Broadcom Corporation
--             16251 Laguna Canyon Road
--             Irvine, California  92618
--    All information contained in this document is Broadcom Corporation
--    company private, proprietary, and trade secret.
--
--
--
--**************************************************************************
--    Filename: brcm-cablehome-mgmt.mib
--    Author:   Kevin O'Neal
--    Creation Date: 6-march-2003
--
--**************************************************************************
--    Description:
--
--		private MIB for runtime (not factory) CableHome management
--
--**************************************************************************
--    Revision History:
--
--**************************************************************************

BRCM-CABLEHOME-MGMT-MIB DEFINITIONS ::= BEGIN

IMPORTS
    MODULE-IDENTITY,
    OBJECT-TYPE
        FROM SNMPv2-SMI
    cableDataMgmtMIBObjects
        FROM BRCM-CABLEDATA-MGMT-MIB;

cablehomeMgmt MODULE-IDENTITY
    LAST-UPDATED "200702050000Z"
    ORGANIZATION "Broadcom Corporation"
    CONTACT-INFO
        "	BANANA-CABLEDATA
                (cableData branch of the
                Broadcom Assigned Numbers and Naming Authority)
                Broadcom Corporation

        Postal: 4385 River Green Parkway
                Duluth, GA  30096
                USA

           Tel: +1 770 232-0018

        E-mail: banana-cabledata@broadcom.com"
    DESCRIPTION
        "Broadacom proprietary MIB for runtime management of CableHome devices."
    REVISION      "200702050000Z"
    DESCRIPTION
        "Module description was updated.
         Compilability issues were cleaned up:
         - Chronological order of revision history was corrected."
    REVISION      "200404050000Z"
    DESCRIPTION
        "Added chCsaEnabled object."
    REVISION      "200303060000Z"
    DESCRIPTION
        "Initial version of this MIB module."
    ::= { cableDataMgmtMIBObjects 3 }

chMgmtBase OBJECT IDENTIFIER ::= { cablehomeMgmt 1 }

chCsaOperMode OBJECT-TYPE
    SYNTAX      INTEGER {
                disabled(0),
                csa10(1)
    }
    MAX-ACCESS  read-write
    STATUS      current
    DESCRIPTION
        "Sets the operational mode of the device with regards to CSA
         (Commercial Services Annex) support.  Note that CSA is defined as an
         annex to the CableHome 1.1 specification, so rgOperMode must be set to
         cableHome11(4) for this object to be meaningfully set to any value
         other than disabled(0)."
    ::= { chMgmtBase 1 }

END
