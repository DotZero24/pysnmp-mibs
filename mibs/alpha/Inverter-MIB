Inverter-MIB DEFINITIONS ::= BEGIN

   --==========================================================================
   -- NOTE: Refer to RFC2578 for the formal definition of the SNMPv2-SMI MIB.
   --==========================================================================

	IMPORTS
		MODULE-IDENTITY, OBJECT-TYPE, NOTIFICATION-TYPE, enterprises
			FROM SNMPv2-SMI
		DisplayString
			FROM SNMPv2-TC;

	argus MODULE-IDENTITY
		LAST-UPDATED "201006020000Z"
		ORGANIZATION "Argus Technologies"
		CONTACT-INFO
		  "Postal: Argus Technologies
				   5700 Sidley Street
				   Burnaby, BC V5J 5E5
				   Canada

			  Tel: 1-604-436-5900
			  Fax: 1-604-436-1233"
		DESCRIPTION
			"TSI Inverter Support for CXC controllers."
	::= { enterprises 7309 }

   pwrSysInv                      OBJECT IDENTIFIER ::= { argus 10 }

   	tsiModules               	 	OBJECT IDENTIFIER ::= { pwrSysInv 5 }
   	phaseGroup    			     	OBJECT IDENTIFIER ::= { pwrSysInv 6 }
   	acGroup		                 	OBJECT IDENTIFIER ::= { pwrSysInv 7 }
   	dcGroup		                 	OBJECT IDENTIFIER ::= { pwrSysInv 8 }
   	miscInfoGroup                 	OBJECT IDENTIFIER ::= { pwrSysInv 9 }
 	alarmGroup   	              	OBJECT IDENTIFIER ::= { pwrSysInv 10 }
--  dataTimeTable                 	OBJECT IDENTIFIER ::= { pwrSysInv 11 }
--	extendedTsiModulesEntry			OBJECT IDENTIFIER ::= { pwrSysInv 12 }


	pwrInvCount OBJECT-TYPE
		SYNTAX INTEGER (0..255)
		MAX-ACCESS read-only
		STATUS current
		DESCRIPTION ""
	::= { pwrSysInv 1 }

	-- TSI Modules

	tsiModulesCount OBJECT-TYPE
		SYNTAX INTEGER (0..255)
		MAX-ACCESS read-only
		STATUS current
		DESCRIPTION "Number of TSI modules acquired by the Inv."
	::= { tsiModules 1 }

	tsiModulesTable OBJECT-TYPE
		SYNTAX SEQUENCE OF TSIModulesEntry
		MAX-ACCESS not-accessible
		STATUS current
		DESCRIPTION "TSI Modules information table."
	::= { tsiModules 5 }

	tsiModulesEntry OBJECT-TYPE
		SYNTAX TSIModulesEntry
		MAX-ACCESS not-accessible
		STATUS current
		DESCRIPTION "One TSI Modules information entry."
		INDEX { tsiModulesIndex }
	::= { tsiModulesTable 1 }

	TSIModulesEntry ::= SEQUENCE
	{
		tsiModulesIndex					INTEGER,
		tsiStatusACOut					INTEGER,
   	 	tsiStatusACIn					INTEGER,
    	tsiStatusDCIn					INTEGER,
    	tsiAddress						INTEGER,
    	tsiLoadPosition 				INTEGER,
    	tsiLoadRatioW 					INTEGER,
		tsiLoadRatioVA					INTEGER,
		tsiSerialNumber					INTEGER,
		tsiVout							INTEGER,
		tsiIout							INTEGER,
		tsiPoutW						INTEGER,
		tsiPoutVA						INTEGER,
		tsiVinAC						INTEGER,
		tsiIinAC						INTEGER,
		tsiPinACW						INTEGER,
		tsiPinACVA						INTEGER,
		tsiACInFreq						INTEGER,
		tsiVinDC						INTEGER,
		tsiIinDC						INTEGER,
		tsiPinDC						INTEGER,
		tsiTemperature					INTEGER,
		tsiSoftVersion					INTEGER,
		tsiBusErrorCnt					INTEGER,
		tsiPhaseNumber					INTEGER,
		tsiStatusMod					INTEGER,
		tsiStatusAC						INTEGER,
		tsiStatusDC						INTEGER,
		tsiPresent						INTEGER,
		tsiGroupAC						INTEGER,
		tsiGroupDC						INTEGER,
		tsiRestrained					INTEGER,
		tsiNoEPC 						INTEGER,
		tsiPoutNominalW					INTEGER,
		tsiPoutNominalVA				INTEGER,
		tsiVinNominalAC					INTEGER,
		tsiVinNominalDC 				INTEGER,
		tsiVinNominalFreqAC 			INTEGER
	}

    tsiModulesIndex OBJECT-TYPE
    	SYNTAX INTEGER (0..255)
    	MAX-ACCESS read-only
    	STATUS current
    ::= { tsiModulesEntry 1 }

	tsiStatusACOut OBJECT-TYPE
		SYNTAX INTEGER (0..255)
		MAX-ACCESS read-only
		STATUS current
	::= { tsiModulesEntry 2 }


    tsiStatusACIn OBJECT-TYPE
		SYNTAX INTEGER (0..255)
		MAX-ACCESS read-only
		STATUS current
	::= {tsiModulesEntry 3  }


    tsiStatusDCIn OBJECT-TYPE
		SYNTAX INTEGER (0..255)
		MAX-ACCESS read-only
		STATUS current
	::= {tsiModulesEntry 4  }


   	tsiAddress OBJECT-TYPE
		SYNTAX INTEGER (0..255)
		MAX-ACCESS read-only
		STATUS current
	::= {tsiModulesEntry 5  }


   	tsiLoadPosition OBJECT-TYPE
		SYNTAX INTEGER (0..255)
		MAX-ACCESS read-only
		STATUS current
	::= {tsiModulesEntry 6  }


   	tsiLoadRatioW OBJECT-TYPE
		SYNTAX INTEGER (0..255)
		MAX-ACCESS read-only
		STATUS current
	::= {tsiModulesEntry 7  }


   	tsiLoadRatioVA OBJECT-TYPE
		SYNTAX INTEGER (0..255)
		MAX-ACCESS read-only
		STATUS current
	::= {tsiModulesEntry 8  }

   	tsiSerialNumber OBJECT-TYPE
		SYNTAX INTEGER (0..4294967295)
		MAX-ACCESS read-only
		STATUS current
	::= {tsiModulesEntry 9 }

   	tsiVout OBJECT-TYPE
		SYNTAX INTEGER (0..65535)
		MAX-ACCESS read-only
		STATUS current
	::= {tsiModulesEntry 10  }


   	tsiIout OBJECT-TYPE
		SYNTAX INTEGER (0..65535)
		MAX-ACCESS read-only
		STATUS current
	::= {tsiModulesEntry 11 }


   	tsiPoutW OBJECT-TYPE
		SYNTAX INTEGER (0..65535)
		MAX-ACCESS read-only
		STATUS current
	::= {tsiModulesEntry 12 }


   	tsiPoutVA OBJECT-TYPE
		SYNTAX INTEGER (0..65535)
		MAX-ACCESS read-only
		STATUS current
	::= {tsiModulesEntry 13 }


   	tsiVinAC OBJECT-TYPE
		SYNTAX INTEGER (0..65535)
		MAX-ACCESS read-only
		STATUS current
	::= {tsiModulesEntry 14 }


   	tsiIinAC OBJECT-TYPE
		SYNTAX INTEGER (0..65535)
		MAX-ACCESS read-only
		STATUS current
	::= {tsiModulesEntry 15 }


   	tsiPinACW OBJECT-TYPE
		SYNTAX INTEGER (0..65535)
		MAX-ACCESS read-only
		STATUS current
	::= {tsiModulesEntry 16 }


   	tsiPinACVA OBJECT-TYPE
		SYNTAX INTEGER (0..65535)
		MAX-ACCESS read-only
		STATUS current
	::= {tsiModulesEntry 17 }


   	tsiACInFreq OBJECT-TYPE
		SYNTAX INTEGER (0..65535)
		MAX-ACCESS read-only
		STATUS current
	::= {tsiModulesEntry 18 }


   	tsiVinDC OBJECT-TYPE
		SYNTAX INTEGER (0..65535)
		MAX-ACCESS read-only
		STATUS current
	::= {tsiModulesEntry 19 }


   	tsiIinDC OBJECT-TYPE
		SYNTAX INTEGER (0..65535)
		MAX-ACCESS read-only
		STATUS current
	::= {tsiModulesEntry 20 }


   	tsiPinDC OBJECT-TYPE
		SYNTAX INTEGER (0..65535)
		MAX-ACCESS read-only
		STATUS current
	::= {tsiModulesEntry 21 }


   	tsiTemperature OBJECT-TYPE
		SYNTAX INTEGER (0..65535)
		MAX-ACCESS read-only
		STATUS current
	::= {tsiModulesEntry 22 }


   	tsiSoftVersion OBJECT-TYPE
		SYNTAX INTEGER (0..65535)
		MAX-ACCESS read-only
		STATUS current
	::= {tsiModulesEntry 23 }

   	tsiBusErrorCnt OBJECT-TYPE
		SYNTAX INTEGER (0..4294967295)
		MAX-ACCESS read-only
		STATUS current
	::= {tsiModulesEntry 24 }


   	tsiPhaseNumber OBJECT-TYPE
		SYNTAX INTEGER (0..255)
		MAX-ACCESS read-only
		STATUS current
	::= {tsiModulesEntry 25  }


   	tsiStatusMod OBJECT-TYPE
		SYNTAX INTEGER (0..255)
		MAX-ACCESS read-only
		STATUS current
	::= {tsiModulesEntry 26 }


   	tsiStatusAC OBJECT-TYPE
		SYNTAX INTEGER (0..255)
		MAX-ACCESS read-only
		STATUS current
	::= {tsiModulesEntry 27 }


   	tsiStatusDC  OBJECT-TYPE
		SYNTAX INTEGER (0..255)
		MAX-ACCESS read-only
		STATUS current
	::= {tsiModulesEntry 28 }


   	tsiPresent OBJECT-TYPE
		SYNTAX INTEGER (0..255)
		MAX-ACCESS read-only
		STATUS current
	::= {tsiModulesEntry 29 }


   	tsiGroupAC OBJECT-TYPE
		SYNTAX INTEGER (0..255)
		MAX-ACCESS read-only
		STATUS current
	::= {tsiModulesEntry 30 }


   	tsiGroupDC OBJECT-TYPE
		SYNTAX INTEGER (0..255)
		MAX-ACCESS read-only
		STATUS current
	::= {tsiModulesEntry 31 }


   	tsiRestrained OBJECT-TYPE
		SYNTAX INTEGER (0..255)
		MAX-ACCESS read-only
		STATUS current
	::= {tsiModulesEntry 32 }


   	tsiNoEPC OBJECT-TYPE
		SYNTAX INTEGER (0..255)
		MAX-ACCESS read-only
		STATUS current
	::= {tsiModulesEntry 33 }


   	tsiPoutNominalW OBJECT-TYPE
		SYNTAX INTEGER (0..65535)
		MAX-ACCESS read-only
		STATUS current
	::= {tsiModulesEntry 34 }


   	tsiPoutNominalVA OBJECT-TYPE
		SYNTAX INTEGER (0..65535)
		MAX-ACCESS read-only
		STATUS current
	::= {tsiModulesEntry 35 }


   	tsiVinNominalAC OBJECT-TYPE
		SYNTAX INTEGER (0..65535)
		MAX-ACCESS read-only
		STATUS current
	::= {tsiModulesEntry 36 }


   	tsiVinNominalDC OBJECT-TYPE
		SYNTAX INTEGER (0..65535)
		MAX-ACCESS read-only
		STATUS current
	::= {tsiModulesEntry 37 }


   	tsiVinNominalFreqAC OBJECT-TYPE
		SYNTAX INTEGER (0..65535)
		MAX-ACCESS read-only
		STATUS current
	::= {tsiModulesEntry 38 }


    -- lReserved OBJECT-TYPE
--		SYNTAX INTEGER (0..4294967295)
--		MAX-ACCESS read-only
--		STATUS current
--	::= {extendedtsiModulesEntry 1  }


	-- Phase Group

	phaseCount OBJECT-TYPE
		SYNTAX INTEGER (0..255)
		MAX-ACCESS read-only
		STATUS current
	::= { phaseGroup 1 }

	phaseGroupTable OBJECT-TYPE
		SYNTAX SEQUENCE OF PhaseGroupEntry
		MAX-ACCESS not-accessible
		STATUS current
	::= { phaseGroup 5 }

	phaseGroupEntry OBJECT-TYPE
		SYNTAX PhaseGroupEntry
		MAX-ACCESS not-accessible
		STATUS current
		INDEX { phaseGroupIndex }
	::= { phaseGroupTable 1 }

	PhaseGroupEntry ::= SEQUENCE
	{
		phaseGroupIndex			INTEGER,
		bRatioAvailableW		INTEGER,
		bRatioAvailableVA		INTEGER,
		bRatioInstalledW		INTEGER,
		bRatioInstalledWA		INTEGER,
		wVout					INTEGER,
		wIout					INTEGER,
		bNbOndCfg				INTEGER,
		bRedundancy				INTEGER,
		wACOutFreq				INTEGER,
		lPinDC					INTEGER,
		lPinACW					INTEGER,
		lPinACVA				INTEGER,
		lCurrentPowerInW		INTEGER,
		lCurrentPowerInVA		INTEGER,
		lInstalledPowerInW		INTEGER,
		lInstalledPowerInVA		INTEGER,
		lAvailablePowerInW		INTEGER,
		lAvailablePowerInVA		INTEGER,
		bNbInvSeen				INTEGER,
		bNbInvOK				INTEGER,
		bNbInvMO				INTEGER,
		bNbInvKO				INTEGER,
		bNbInvNT				INTEGER
	}

	phaseGroupIndex OBJECT-TYPE
		SYNTAX INTEGER (0..255)
		MAX-ACCESS read-only
		STATUS current
	::= { phaseGroupEntry 1 }

   bRatioAvailableW OBJECT-TYPE
		SYNTAX INTEGER (0..255)
		MAX-ACCESS read-only
		STATUS current
	::= {phaseGroupEntry 2  }


   bRatioAvailableVA OBJECT-TYPE
		SYNTAX INTEGER (0..255)
		MAX-ACCESS read-only
		STATUS current
	::= {phaseGroupEntry 3  }


   bRatioInstalledW OBJECT-TYPE
		SYNTAX INTEGER (0..255)
		MAX-ACCESS read-only
		STATUS current
	::= {phaseGroupEntry 4  }


   bRatioInstalledWA OBJECT-TYPE
		SYNTAX INTEGER (0..255)
		MAX-ACCESS read-only
		STATUS current
	::= {phaseGroupEntry 5  }


   wVout OBJECT-TYPE
		SYNTAX INTEGER (0..65535)
		MAX-ACCESS read-only
		STATUS current
	::= {phaseGroupEntry 6  }


   wIout OBJECT-TYPE
		SYNTAX INTEGER (0..65535)
		MAX-ACCESS read-only
		STATUS current
	::= {phaseGroupEntry 7  }


   bNbOndCfg OBJECT-TYPE
		SYNTAX INTEGER (0..255)
		MAX-ACCESS read-only
		STATUS current
	::= {phaseGroupEntry 8  }


   bRedundancy OBJECT-TYPE
		SYNTAX INTEGER (0..255)
		MAX-ACCESS read-only
		STATUS current
	::= {phaseGroupEntry 9  }


   wACOutFreq OBJECT-TYPE
		SYNTAX INTEGER (0..65535)
		MAX-ACCESS read-only
		STATUS current
	::= {phaseGroupEntry 10  }


   lPinDC OBJECT-TYPE
		SYNTAX INTEGER (0..4294967295)
		MAX-ACCESS read-only
		STATUS current
	::= {phaseGroupEntry 11 }


   lPinACW OBJECT-TYPE
		SYNTAX INTEGER (0..4294967295)
		MAX-ACCESS read-only
		STATUS current
	::= {phaseGroupEntry 12 }


   lPinACVA OBJECT-TYPE
		SYNTAX INTEGER (0..4294967295)
		MAX-ACCESS read-only
		STATUS current
	::= {phaseGroupEntry 13 }


   lCurrentPowerInW OBJECT-TYPE
		SYNTAX INTEGER (0..4294967295)
		MAX-ACCESS read-only
		STATUS current
	::= {phaseGroupEntry 14 }


   lCurrentPowerInVA OBJECT-TYPE
		SYNTAX INTEGER (0..4294967295)
		MAX-ACCESS read-only
		STATUS current
	::= {phaseGroupEntry 15 }


   lInstalledPowerInW OBJECT-TYPE
		SYNTAX INTEGER (0..4294967295)
		MAX-ACCESS read-only
		STATUS current
	::= {phaseGroupEntry 16 }


   lInstalledPowerInVA OBJECT-TYPE
		SYNTAX INTEGER (0..4294967295)
		MAX-ACCESS read-only
		STATUS current
	::= {phaseGroupEntry 17 }


   lAvailablePowerInW OBJECT-TYPE
		SYNTAX INTEGER (0..4294967295)
		MAX-ACCESS read-only
		STATUS current
	::= {phaseGroupEntry 18 }


   lAvailablePowerInVA OBJECT-TYPE
		SYNTAX INTEGER (0..4294967295)
		MAX-ACCESS read-only
		STATUS current
	::= {phaseGroupEntry 19 }


   bNbInvSeen OBJECT-TYPE
		SYNTAX INTEGER (0..255)
		MAX-ACCESS read-only
		STATUS current
	::= {phaseGroupEntry 20 }


   bNbInvOK OBJECT-TYPE
		SYNTAX INTEGER (0..255)
		MAX-ACCESS read-only
		STATUS current
	::= {phaseGroupEntry 21 }


   bNbInvMO OBJECT-TYPE
		SYNTAX INTEGER (0..255)
		MAX-ACCESS read-only
		STATUS current
	::= {phaseGroupEntry 22 }


   bNbInvKO OBJECT-TYPE
		SYNTAX INTEGER (0..255)
		MAX-ACCESS read-only
		STATUS current
   ::= {phaseGroupEntry 23 }


   bNbInvNT OBJECT-TYPE
		SYNTAX INTEGER (0..255)
		MAX-ACCESS read-only
		STATUS current
	::= {phaseGroupEntry 24 }


	-- AC Group

	acGroupCount OBJECT-TYPE
		SYNTAX INTEGER (0..255)
		MAX-ACCESS read-only
		STATUS current
	::= { acGroup 1 }

    acGroupTable OBJECT-TYPE
    	SYNTAX SEQUENCE OF ACGroupEntry
    	MAX-ACCESS not-accessible
    	STATUS current
    ::= { acGroup 5 }

	acGroupEntry OBJECT-TYPE
		SYNTAX ACGroupEntry
		MAX-ACCESS not-accessible
		STATUS current
		INDEX { acGroupIndex }
	::= { acGroupTable 1 }

	ACGroupEntry ::= SEQUENCE
	{
		acGroupIndex	INTEGER,
		acNbInvOK		INTEGER,
		acNbInvMO		INTEGER,
		acNbInvKO		INTEGER,
		acNbInvSeen		INTEGER,
		acPinACW		INTEGER,
		acPinACVA		INTEGER,
		acVinAC			INTEGER,
		acIinAC			INTEGER,
		acACinFreq		INTEGER,
		acACinOK		INTEGER
	}

	acGroupIndex OBJECT-TYPE
		SYNTAX INTEGER (0..255)
		MAX-ACCESS read-only
		STATUS current
	::= { acGroupEntry 1 }

 	acNbInvOK OBJECT-TYPE
		SYNTAX INTEGER (0..255)
		MAX-ACCESS read-only
		STATUS current
	::= { acGroupEntry 2  }

   	acNbInvMO OBJECT-TYPE
		SYNTAX INTEGER (0..255)
		MAX-ACCESS read-only
		STATUS current
	::= {acGroupEntry 3  }

   	acNbInvKO OBJECT-TYPE
		SYNTAX INTEGER (0..255)
		MAX-ACCESS read-only
		STATUS current
	::= {acGroupEntry 4  }

   	acNbInvSeen OBJECT-TYPE
		SYNTAX INTEGER (0..255)
		MAX-ACCESS read-only
		STATUS current
	::= {acGroupEntry 5  }

   	acPinACW OBJECT-TYPE
		SYNTAX INTEGER (0..4294967295)
		MAX-ACCESS read-only
		STATUS current
	::= {acGroupEntry 6  }

   	acPinACVA OBJECT-TYPE
		SYNTAX INTEGER (0..4294967295)
		MAX-ACCESS read-only
		STATUS current
	::= {acGroupEntry 7  }

   	acVinAC OBJECT-TYPE
		SYNTAX INTEGER (0..65535)
		MAX-ACCESS read-only
		STATUS current
	::= {acGroupEntry 8  }

   	acIinAC OBJECT-TYPE
		SYNTAX INTEGER (0..65535)
		MAX-ACCESS read-only
		STATUS current
	::= {acGroupEntry 9  }

   	acACinFreq OBJECT-TYPE
		SYNTAX INTEGER (0..65535)
		MAX-ACCESS read-only
		STATUS current
	::= {acGroupEntry 10  }

   	acACinOK OBJECT-TYPE
		SYNTAX INTEGER (0..255)
		MAX-ACCESS read-only
		STATUS current
	::= {acGroupEntry 11 }

    -- DC Group

	dcGroupCount OBJECT-TYPE
		SYNTAX INTEGER (0..255)
		MAX-ACCESS read-only
		STATUS current
	::= { dcGroup 1 }

	dcGroupTable OBJECT-TYPE
		SYNTAX SEQUENCE OF DCGroupEntry
		MAX-ACCESS not-accessible
		STATUS current
	::= { dcGroup 5 }

	dcGroupEntry OBJECT-TYPE
		SYNTAX DCGroupEntry
		MAX-ACCESS not-accessible
		STATUS current
		INDEX { dcGroupIndex }
	::= { dcGroupTable 1 }

	DCGroupEntry ::= SEQUENCE
	{
		dcGroupIndex 			INTEGER,
		dcNbInvOK 				INTEGER,
		dcNbInvMO 				INTEGER,
		dcNbInvKO 				INTEGER,
		dcNbInvSeen				INTEGER,
		dcPinDC 				INTEGER,
		dcVinDC 				INTEGER,
		dcIinDC 				INTEGER,
		dcDCInOK 				INTEGER
	}

	dcGroupIndex OBJECT-TYPE
		SYNTAX INTEGER (0..255)
		MAX-ACCESS read-only
		STATUS current
	::= { dcGroupEntry 1 }

   	dcNbInvOK OBJECT-TYPE
		SYNTAX INTEGER (0..255)
		MAX-ACCESS read-only
		STATUS current
	::= {dcGroupEntry 2  }


   	dcNbInvMO OBJECT-TYPE
		SYNTAX INTEGER (0..255)
		MAX-ACCESS read-only
		STATUS current
	::= {dcGroupEntry 3  }


   	dcNbInvKO OBJECT-TYPE
		SYNTAX INTEGER (0..255)
		MAX-ACCESS read-only
		STATUS current
	::= {dcGroupEntry 4  }


   	dcNbInvSeen OBJECT-TYPE
		SYNTAX INTEGER (0..255)
		MAX-ACCESS read-only
		STATUS current
	::= {dcGroupEntry 5  }


   	dcPinDC OBJECT-TYPE
		SYNTAX INTEGER (0..4294967295)
		MAX-ACCESS read-only
		STATUS current
	::= {dcGroupEntry 6  }


   	dcVinDC OBJECT-TYPE
		SYNTAX INTEGER (0..65535)
		MAX-ACCESS read-only
		STATUS current
	::= {dcGroupEntry 7  }


   	dcIinDC OBJECT-TYPE
		SYNTAX INTEGER (0..65535)
		MAX-ACCESS read-only
		STATUS current
	::= {dcGroupEntry 8  }


   	dcDCInOK OBJECT-TYPE
		SYNTAX INTEGER (0..255)
		MAX-ACCESS read-only
		STATUS current
	::= {dcGroupEntry 9  }


   	-- Misc Info Group

	miscInfoGroupCount OBJECT-TYPE
		SYNTAX INTEGER (0..255)
		MAX-ACCESS read-only
		STATUS current
	::= { miscInfoGroup 1 }

	miscInfoGroupTable OBJECT-TYPE
		SYNTAX SEQUENCE OF MiscInfoGroupEntry
		MAX-ACCESS not-accessible
		STATUS current
	::= { miscInfoGroup 5 }

	miscInfoGroupEntry OBJECT-TYPE
		SYNTAX MiscInfoGroupEntry
		MAX-ACCESS not-accessible
		STATUS current
		INDEX { miscInfoGroupIndex }
	::= { miscInfoGroupTable 1 }

	MiscInfoGroupEntry ::= SEQUENCE
	{
    	miscInfoGroupIndex 			INTEGER,
    	bOldVersionNumber 			INTEGER,
    	ePhaseNumber 				INTEGER,
		bNbMajor 					INTEGER,
		wTempoMajorAl 				INTEGER,
		wtempoMinorAl 				INTEGER,
	    lSerialNumber 				INTEGER,
		bNbMinor 					INTEGER,
		bNbTotalAlarmNumber 		INTEGER,
		bACInputPresent 			INTEGER,
		bSaturationThresh 			INTEGER,
		bNbGroupsDC 				INTEGER,
		bNbGroupsAC 				INTEGER,
		bProgRelay 					INTEGER,
		bSystemLoadPosition 		INTEGER,
		wSoftSubRevision 			INTEGER,
		wSoftMainRevision 			INTEGER,
		wInvVersionTextError 		INTEGER,
		bInvMaxKnowParameters 		INTEGER
	}

    miscInfoGroupIndex OBJECT-TYPE
		SYNTAX INTEGER (0..255)
		MAX-ACCESS read-only
		STATUS current
	::= { miscInfoGroupEntry 1  }

   bOldVersionNumber OBJECT-TYPE
		SYNTAX INTEGER (0..255)
		MAX-ACCESS read-only
		STATUS current
	::= {miscInfoGroupEntry 2  }


   ePhaseNumber OBJECT-TYPE
		SYNTAX INTEGER (0..255)
		MAX-ACCESS read-only
		STATUS current
	::= {miscInfoGroupEntry 3  }


   bNbMajor OBJECT-TYPE
		SYNTAX INTEGER (0..255)
		MAX-ACCESS read-only
		STATUS current
	::= {miscInfoGroupEntry 4  }


   wTempoMajorAl OBJECT-TYPE
		SYNTAX INTEGER (0..65535)
		MAX-ACCESS read-only
		STATUS current
	::= {miscInfoGroupEntry 5  }


   wtempoMinorAl OBJECT-TYPE
		SYNTAX INTEGER (0..65535)
		MAX-ACCESS read-only
		STATUS current
	::= {miscInfoGroupEntry 6  }


   lSerialNumber OBJECT-TYPE
		SYNTAX INTEGER (0..4294967295)
		MAX-ACCESS read-only
		STATUS current
	::= {miscInfoGroupEntry 7  }


   bNbMinor OBJECT-TYPE
		SYNTAX INTEGER (0..255)
		MAX-ACCESS read-only
		STATUS current
	::= {miscInfoGroupEntry 8  }


   bNbTotalAlarmNumber OBJECT-TYPE
		SYNTAX INTEGER (0..255)
		MAX-ACCESS read-only
		STATUS current
	::= {miscInfoGroupEntry 9  }


   bACInputPresent OBJECT-TYPE
		SYNTAX INTEGER (0..255)
		MAX-ACCESS read-only
		STATUS current
	::= {miscInfoGroupEntry 10  }


   bSaturationThresh OBJECT-TYPE
		SYNTAX INTEGER (0..255)
		MAX-ACCESS read-only
		STATUS current
	::= {miscInfoGroupEntry 11 }


   bNbGroupsDC OBJECT-TYPE
		SYNTAX INTEGER (0..255)
		MAX-ACCESS read-only
		STATUS current
	::= {miscInfoGroupEntry 12 }


   bNbGroupsAC OBJECT-TYPE
		SYNTAX INTEGER (0..255)
		MAX-ACCESS read-only
		STATUS current
	::= {miscInfoGroupEntry 13 }


   bProgRelay OBJECT-TYPE
		SYNTAX INTEGER (0..255)
		MAX-ACCESS read-only
		STATUS current
	::= {miscInfoGroupEntry 14 }

    bSystemLoadPosition OBJECT-TYPE
		SYNTAX INTEGER (0..255)
		MAX-ACCESS read-only
		STATUS current
	::= {miscInfoGroupEntry 15 }

   wSoftSubRevision OBJECT-TYPE
		SYNTAX INTEGER (0..65535)
		MAX-ACCESS read-only
		STATUS current
	::= {miscInfoGroupEntry 16 }

   wSoftMainRevision OBJECT-TYPE
		SYNTAX INTEGER (0..65535)
		MAX-ACCESS read-only
		STATUS current
	::= {miscInfoGroupEntry 17 }


   wInvVersionTextError OBJECT-TYPE
		SYNTAX INTEGER (0..65535)
		MAX-ACCESS read-only
		STATUS current
	::= {miscInfoGroupEntry 18 }

    bInvMaxKnowParameters OBJECT-TYPE
		SYNTAX INTEGER (0..255)
		MAX-ACCESS read-only
		STATUS current
	::= {miscInfoGroupEntry 19 }


	-- Data time table


--   lTime OBJECT-TYPE
--		SYNTAX INTEGER (0..4294967295)
--		MAX-ACCESS read-only
--		STATUS current
--	::= {dataTimeTable 1  }
--
--
--   bSeconds OBJECT-TYPE
--		SYNTAX INTEGER (0..255)
--		MAX-ACCESS read-only
--		STATUS current
--	::= {dataTimeTable 2  }
--

--   bMinutes OBJECT-TYPE
--		SYNTAX INTEGER (0..255)
--		MAX-ACCESS read-only
--		STATUS current
--	::= {dataTimeTable 3  }
--
--
--   bHours OBJECT-TYPE
--		SYNTAX INTEGER (0..255)
--		MAX-ACCESS read-only
--		STATUS current
--	::= {dataTimeTable 4  }
--

--   bDay OBJECT-TYPE
--		SYNTAX INTEGER (0..255)
--		MAX-ACCESS read-only
--		STATUS current
--	::= {dataTimeTable 5  }
--
--
--   bMonth OBJECT-TYPE
--		SYNTAX INTEGER (0..255)
--		MAX-ACCESS read-only
--		STATUS current
--	::= {dataTimeTable 6  }
--

--   bDaylightSaving OBJECT-TYPE
--		SYNTAX INTEGER (0..255)
--		MAX-ACCESS read-only
--		STATUS current
--	::= {dataTimeTable 7  }
--
--
--   wYear OBJECT-TYPE
--		SYNTAX INTEGER (0..65535)
--		MAX-ACCESS read-only
--		STATUS current
--	::= {dataTimeTable 8  }
--

	-- Alarm Group

	alarmGroupCount OBJECT-TYPE
		SYNTAX INTEGER (0..255)
		MAX-ACCESS read-only
		STATUS current
	::= {alarmGroup 1  }

	alarmGroupTable OBJECT-TYPE
		SYNTAX SEQUENCE OF AlarmGroupEntry
		MAX-ACCESS not-accessible
		STATUS current
	::= { alarmGroup 5 }

	alarmGroupEntry OBJECT-TYPE
		SYNTAX AlarmGroupEntry
		MAX-ACCESS not-accessible
		STATUS current
		INDEX { alarmGroupIndex }
	::= { alarmGroupTable 1 }

	AlarmGroupEntry ::= SEQUENCE
	{
		alarmGroupIndex			INTEGER,
   		bDeviceNumber			INTEGER,
   		bEventType 				INTEGER,
     	wEventNumber			INTEGER,
     	sEventString			DisplayString
	}

	alarmGroupIndex OBJECT-TYPE
		SYNTAX INTEGER (0..255)
		MAX-ACCESS read-only
		STATUS current
	::= { alarmGroupEntry 1  }

   bDeviceNumber OBJECT-TYPE
		SYNTAX INTEGER (0..255)
		MAX-ACCESS read-only
		STATUS current
	::= { alarmGroupEntry 2 }

   bEventType OBJECT-TYPE
		SYNTAX INTEGER (0..255)
		MAX-ACCESS read-only
		STATUS current
	::= { alarmGroupEntry 3 }

   wEventNumber OBJECT-TYPE
		SYNTAX INTEGER (0..65535)
		MAX-ACCESS read-only
		STATUS current
	::= { alarmGroupEntry 4 }

	sEventString OBJECT-TYPE
		SYNTAX DisplayString (SIZE(0..255))
		MAX-ACCESS read-only
		STATUS current
		DESCRIPTION "String identifier of the occurring event."
	::= { alarmGroupEntry 5 }


END
