AlphaPowerSystem-MIB DEFINITIONS ::= BEGIN

	--==========================================================================
	-- ALPHA.MIB
	--
	-- NOTE: Refer to RFC2578 for the formal definition of the SNMPv2-SMI MIB.
	--
	-- Changes:
	-- September 23 2014
	-- Added LPS alarms
	--
	-- February 22, 2011
	--
	-- Changed the property of Custom Signals to be Read and Write to
	-- support SNMP Set feature.
	--
	-- June 03, 2010
	--
	-- Added inverter alarms.
	--
	-- January 25, 2010
	--
	-- Company name changed from Argus to Alpha.
	-- All references changed accordingly.
	--
	-- November 3, 2008
	--
	-- The following new definitions were added:
	-- 		Resync
	-- 		Alarm Trigger
	-- 		Time stamp
	--
	-- Subtyping removed from sequence definitions.
	--==========================================================================

	IMPORTS
		MODULE-IDENTITY, OBJECT-TYPE, NOTIFICATION-TYPE, enterprises
			FROM SNMPv2-SMI
		DisplayString
			FROM SNMPv2-TC;

	alpha MODULE-IDENTITY
		LAST-UPDATED "201409230000Z"
		ORGANIZATION "Alpha Technologies"
		CONTACT-INFO
		  	 "Alpha Technologies
			  7700 Riverfront Gate
			  Burnaby, BC  V5J 5M4
			  Canada

			  Tel: 1-604-436-5900
			  Fax: 1-604-436-1233"
		DESCRIPTION
		  "This MIB defines the information block(s) available in system controllers
		   as defined by the following list:
				- dcPwrSysDevice: Cordex series of Controllers"
	::= { enterprises 7309 }

	dcpower	    	    	OBJECT IDENTIFIER ::= { alpha 4 }
	dcPwrSysDevice			OBJECT IDENTIFIER ::= { dcpower 1 }
	dcPwrSysVariable		OBJECT IDENTIFIER ::= { dcPwrSysDevice 1 }
	dcPwrSysString			OBJECT IDENTIFIER ::= { dcPwrSysDevice 2 }
	dcPwrSysTraps			OBJECT IDENTIFIER ::= { dcPwrSysDevice 3 }

	dcPwrSysOutputsTbl		OBJECT IDENTIFIER ::= { dcPwrSysDevice 4 }
	dcPwrSysRelayTbl 		OBJECT IDENTIFIER ::= { dcPwrSysOutputsTbl 1 }
	dcPwrSysAnalogOpTbl		OBJECT IDENTIFIER ::= { dcPwrSysOutputsTbl 2 }

	dcPwrSysAlrmsTbl		OBJECT IDENTIFIER ::= { dcPwrSysDevice 5 }
	dcPwrSysRectAlrmTbl		OBJECT IDENTIFIER ::= { dcPwrSysAlrmsTbl 1 }
	dcPwrSysDigAlrmTbl		OBJECT IDENTIFIER ::= { dcPwrSysAlrmsTbl 2 }
	dcPwrSysCurrAlrmTbl		OBJECT IDENTIFIER ::= { dcPwrSysAlrmsTbl 3 }
	dcPwrSysVoltAlrmTbl		OBJECT IDENTIFIER ::= { dcPwrSysAlrmsTbl 4 }
	dcPwrSysBattAlrmTbl		OBJECT IDENTIFIER ::= { dcPwrSysAlrmsTbl 5 }
	dcPwrSysTempAlrmTbl		OBJECT IDENTIFIER ::= { dcPwrSysAlrmsTbl 6 }
	dcPwrSysCustomAlrmTbl 	OBJECT IDENTIFIER ::= { dcPwrSysAlrmsTbl 7 }
	dcPwrSysMiscAlrmTbl		OBJECT IDENTIFIER ::= { dcPwrSysAlrmsTbl 8 }
	dcPwrSysCtrlAlrmTbl		OBJECT IDENTIFIER ::= { dcPwrSysAlrmsTbl 9 }
	dcPwrSysAdioAlrmTbl		OBJECT IDENTIFIER ::= { dcPwrSysAlrmsTbl 10 }
	dcPwrSysConvAlrmTbl		OBJECT IDENTIFIER ::= { dcPwrSysAlrmsTbl 11 }

	dcPwrSysInvAlrmTbl		OBJECT IDENTIFIER ::= { dcPwrSysAlrmsTbl 12 }
	dcPwrSysLpsAlrmTbl		OBJECT IDENTIFIER ::= { dcPwrSysAlrmsTbl 13 }

	dcPwrSysInputsTbl		OBJECT IDENTIFIER ::= { dcPwrSysDevice 6 }
	dcPwrSysDigIpTbl		OBJECT IDENTIFIER ::= { dcPwrSysInputsTbl 1 }
	dcPwrSysCntrlrIpTbl		OBJECT IDENTIFIER ::= { dcPwrSysInputsTbl 2 }
	dcPwrSysRectIpTbl		OBJECT IDENTIFIER ::= { dcPwrSysInputsTbl 3 }
	dcPwrSysCustomIpTbl		OBJECT IDENTIFIER ::= { dcPwrSysInputsTbl 4 }
	dcPwrSysConvIpTbl		OBJECT IDENTIFIER ::= { dcPwrSysInputsTbl 5 }
	dcPwrSysTimerIpTbl		OBJECT IDENTIFIER ::= { dcPwrSysInputsTbl 6 }
	dcPwrSysCounterIpTbl	OBJECT IDENTIFIER ::= { dcPwrSysInputsTbl 7 }
	dcPwrSysLpsTbl			OBJECT IDENTIFIER ::= { dcPwrSysInputsTbl 8 }

	dcPwrExternalControls	OBJECT IDENTIFIER ::= { dcPwrSysDevice 8 }
	dcPwrVarbindNameReference	OBJECT IDENTIFIER ::= { dcPwrSysDevice 9 }


	--==========================================================================
	-- Start of variables
	--==========================================================================

	dcPwrSysChargeVolts OBJECT-TYPE
		SYNTAX INTEGER (-1000000000..1000000000)
		MAX-ACCESS read-only
		STATUS current
		DESCRIPTION	"This value indicates the present battery voltage.

					 The integer value represent a two digit fix decimal (Value = real voltage * 100) in Volts."
	::= { dcPwrSysVariable 1 }

	dcPwrSysDischargeVolts OBJECT-TYPE
		SYNTAX INTEGER (-1000000000..1000000000)
		MAX-ACCESS read-only
		STATUS current
		DESCRIPTION	"This value indicates the present load voltage.

					 The integer value represent a two digit fix decimal (Value = real voltage * 100) in Volts."
	::= { dcPwrSysVariable  2 }

	dcPwrSysChargeAmps OBJECT-TYPE
		SYNTAX INTEGER (-1000000000..1000000000)
		MAX-ACCESS read-only
		STATUS current
		DESCRIPTION	"This value indicates the present battery currrent.

					 The integer value represent a two digit fix decimal (Value = real current * 100) in Amps."
	::= { dcPwrSysVariable  3 }

	dcPwrSysDischargeAmps OBJECT-TYPE
		SYNTAX INTEGER (-1000000000..1000000000)
		MAX-ACCESS read-only
		STATUS current
		DESCRIPTION	"This value indicates the present load current.

					 The integer value represent a two digit fix decimal (Value = real current * 100) in Amps."
	::= { dcPwrSysVariable  4 }

	dcPwrSysMajorAlarm OBJECT-TYPE
		SYNTAX INTEGER (0..65535)
		MAX-ACCESS read-only
		STATUS current
		DESCRIPTION	"Major Alarm"
	::= { dcPwrSysVariable  5 }

	dcPwrSysMinorAlarm OBJECT-TYPE
		SYNTAX INTEGER (0..65535)
		MAX-ACCESS read-only
		STATUS current
		DESCRIPTION	"Minor Alarm"
	::= { dcPwrSysVariable  6 }

	--==========================================================================
	-- Start of Strings
	--==========================================================================

	dcPwrSysSiteName OBJECT-TYPE
		SYNTAX DisplayString (SIZE(0..255))
		MAX-ACCESS read-only
		STATUS current
		DESCRIPTION	"Site Name"
	::= { dcPwrSysString 1 }

	dcPwrSysSiteCity OBJECT-TYPE
		SYNTAX DisplayString (SIZE(0..255))
		MAX-ACCESS read-only
		STATUS current
		DESCRIPTION	"Site City"
	::= { dcPwrSysString 2 }

	dcPwrSysSiteRegion OBJECT-TYPE
		SYNTAX DisplayString (SIZE(0..255))
		MAX-ACCESS read-only
		STATUS current
		DESCRIPTION	"Site Region"
	::= { dcPwrSysString 3 }

	dcPwrSysSiteCountry OBJECT-TYPE
		SYNTAX DisplayString (SIZE(0..255))
		MAX-ACCESS read-only
		STATUS current
		DESCRIPTION	"Site Country"
	::= { dcPwrSysString 4 }

	dcPwrSysContactName OBJECT-TYPE
		SYNTAX DisplayString (SIZE(0..255))
		MAX-ACCESS read-only
		STATUS current
		DESCRIPTION	"Contact Name"
	::= { dcPwrSysString 5 }

	dcPwrSysPhoneNumber OBJECT-TYPE
		SYNTAX DisplayString (SIZE(0..255))
		MAX-ACCESS read-only
		STATUS current
		DESCRIPTION	"Phone Number"
	::= { dcPwrSysString 6 }

	dcPwrSysSiteNumber OBJECT-TYPE
		SYNTAX DisplayString (SIZE(0..255))
		MAX-ACCESS read-only
		STATUS current
		DESCRIPTION	"Site Number"
	::= { dcPwrSysString 7 }

	dcPwrSysSystemType OBJECT-TYPE
		SYNTAX DisplayString (SIZE(0..255))
		MAX-ACCESS read-only
		STATUS current
		DESCRIPTION	"The type of system being monitored by the agent."
	::= { dcPwrSysString 8 }

	dcPwrSysSystemSerial OBJECT-TYPE
		SYNTAX DisplayString (SIZE(0..255))
		MAX-ACCESS read-only
		STATUS current
		DESCRIPTION	"The serial number of the monitored system."
	::= { dcPwrSysString 9 }

	dcPwrSysSystemNumber OBJECT-TYPE
		SYNTAX DisplayString (SIZE(0..255))
		MAX-ACCESS read-only
		STATUS current
		DESCRIPTION	"The number of the monitored system."
	::= { dcPwrSysString 10 }

	dcPwrSysSoftwareVersion OBJECT-TYPE
		SYNTAX DisplayString (SIZE(0..255))
		MAX-ACCESS read-only
		STATUS current
		DESCRIPTION	"The version of software running on the monitored system."
	::= { dcPwrSysString 11 }

	dcPwrSysSoftwareTimestamp OBJECT-TYPE
		SYNTAX DisplayString (SIZE(0..255))
		MAX-ACCESS read-only
		STATUS current
		DESCRIPTION	"The time stamp of the software running on the monitored system."
	::= { dcPwrSysString 12 }

	--==========================================================================
	-- Start of Tables Information
	--==========================================================================
	--=================
	-- Output table
	--=================
	--========================
	-- Relay output	sub table
	--=========================
	dcPwrSysRelayCount OBJECT-TYPE
		SYNTAX INTEGER (0..65535)
		MAX-ACCESS read-only
		STATUS current
		DESCRIPTION	"Number of relay variables in system controller relay table."
	::= { dcPwrSysRelayTbl 1 }

	dcPwrSysRelayTable OBJECT-TYPE
		SYNTAX SEQUENCE OF DcPwrSysRelayEntry
		MAX-ACCESS not-accessible
		STATUS current
		DESCRIPTION	"A table of DC power system controller rectifier relay output variables."
	::= { dcPwrSysRelayTbl 2 }

	dcPwrSysRelayEntry OBJECT-TYPE
		SYNTAX DcPwrSysRelayEntry
		MAX-ACCESS not-accessible
		STATUS current
		DESCRIPTION	"An entry into the DC power system controller relay output group."
		INDEX { dcPwrSysRelayIndex }
		::= { dcPwrSysRelayTable 1 }

	DcPwrSysRelayEntry
	::= SEQUENCE {
		dcPwrSysRelayIndex 			INTEGER,
		dcPwrSysRelayName 			DisplayString,
		dcPwrSysRelayIntegerValue 	INTEGER,
		dcPwrSysRelayStringValue 	DisplayString,
		dcPwrSysRelaySeverity		INTEGER
	}

	dcPwrSysRelayIndex OBJECT-TYPE
		SYNTAX INTEGER (0..65535)
		MAX-ACCESS read-only
		STATUS current
		DESCRIPTION	"The index of the relay variable in the power system controller relay output group."
	::= { dcPwrSysRelayEntry 1 }

	dcPwrSysRelayName OBJECT-TYPE
		SYNTAX DisplayString (SIZE(0..30))
		MAX-ACCESS read-only
		STATUS current
		DESCRIPTION	"The description of the relay variable as reported by the DC power system controller relay output group."
	::= { dcPwrSysRelayEntry 2 }

	dcPwrSysRelayIntegerValue OBJECT-TYPE
		SYNTAX INTEGER (-1000000000..1000000000)
		MAX-ACCESS read-only
		STATUS current
		DESCRIPTION	"The integer value of the relay variable as reported by the DC power system controller relay output group."
	::= { dcPwrSysRelayEntry 3 }

	dcPwrSysRelayStringValue OBJECT-TYPE
		SYNTAX DisplayString (SIZE(0..255))
		MAX-ACCESS read-only
		STATUS current
		DESCRIPTION	"The string value of the relay variable as reported by the DC power system controller relay output group."
	::= { dcPwrSysRelayEntry 4 }

	dcPwrSysRelaySeverity OBJECT-TYPE
		SYNTAX INTEGER (0..65535)
		MAX-ACCESS read-only
		STATUS current
		DESCRIPTION	"The integer value of relay severity level of the extra variable as reported by the DC power system controller relay output group."
	::= { dcPwrSysRelayEntry 5 }

	--========================
	-- Analog output sub table
	--=========================
	dcPwrSysAnalogOpCount OBJECT-TYPE
		SYNTAX INTEGER (0..65535)
		MAX-ACCESS read-only
		STATUS current
		DESCRIPTION	"Number of analog output variables in system controller analog output table."
	::= { dcPwrSysAnalogOpTbl 1 }

	dcPwrSysAnalogOpTable OBJECT-TYPE
		SYNTAX SEQUENCE OF DcPwrSysAnalogOpEntry
		MAX-ACCESS not-accessible
		STATUS current
		DESCRIPTION	"A table of DC power system controller analog output variables."
	::= { dcPwrSysAnalogOpTbl 2 }

	dcPwrSysAnalogOpEntry OBJECT-TYPE
		SYNTAX DcPwrSysAnalogOpEntry
		MAX-ACCESS not-accessible
		STATUS current
		DESCRIPTION	"An entry into the DC power system controller analog output group."
		INDEX { dcPwrSysAnalogOpIndex }
		::= { dcPwrSysAnalogOpTable 1 }

	DcPwrSysAnalogOpEntry
	::= SEQUENCE {
		dcPwrSysAnalogOpIndex 			INTEGER,
		dcPwrSysAnalogOpName 			DisplayString,
		dcPwrSysAnalogOpIntegerValue 	INTEGER,
		dcPwrSysAnalogOpStringValue 	DisplayString,
		dcPwrSysAnalogOpSeverity 		INTEGER
	}

	dcPwrSysAnalogOpIndex OBJECT-TYPE
		SYNTAX INTEGER (0..65535)
		MAX-ACCESS read-only
		STATUS current
		DESCRIPTION	"The index of the analog variable in the power system controller analog output group."
	::= { dcPwrSysAnalogOpEntry 1 }

	dcPwrSysAnalogOpName OBJECT-TYPE
		SYNTAX DisplayString (SIZE(0..30))
		MAX-ACCESS read-only
		STATUS current
		DESCRIPTION	"The description of the analog variable as reported by the DC power system controller analog output group."
	::= { dcPwrSysAnalogOpEntry 2 }

	dcPwrSysAnalogOpIntegerValue OBJECT-TYPE
		SYNTAX INTEGER (-1000000000..1000000000)
		MAX-ACCESS read-only
		STATUS current
		DESCRIPTION	"The integer value of the analog variable as reported by the DC power system controller analog output group."
	::= { dcPwrSysAnalogOpEntry 3 }

	dcPwrSysAnalogOpStringValue OBJECT-TYPE
		SYNTAX DisplayString (SIZE(0..255))
		MAX-ACCESS read-only
		STATUS current
		DESCRIPTION	"The string value of the analog variable as reported by the DC power system controller analog output group."
	::= { dcPwrSysAnalogOpEntry 4 }

	dcPwrSysAnalogOpSeverity OBJECT-TYPE
		SYNTAX INTEGER (0..65535)
		MAX-ACCESS read-only
		STATUS current
		DESCRIPTION	"The integer value of analog severity level of the extra variable as reported by the DC power system controller analog output group."
	::= { dcPwrSysAnalogOpEntry 5 }

	--=================
	-- Alarm table
	--=================
	--============================
	--  Rectifier alarm group
	--============================
	dcPwrSysRectAlrmCount OBJECT-TYPE
		SYNTAX INTEGER (0..65535)
		MAX-ACCESS read-only
		STATUS current
		DESCRIPTION	"Number of rectifier alarm variables in system controller alarm table."
	::= { dcPwrSysRectAlrmTbl 1 }

	dcPwrSysRectAlrmTable OBJECT-TYPE
		SYNTAX SEQUENCE OF DcPwrSysRectAlrmEntry
		MAX-ACCESS not-accessible
		STATUS current
		DESCRIPTION	"A table of DC power system controller rectifier alarm variables."
	::= { dcPwrSysRectAlrmTbl 2 }

	dcPwrSysRectAlrmEntry OBJECT-TYPE
		SYNTAX DcPwrSysRectAlrmEntry
		MAX-ACCESS not-accessible
		STATUS current
		DESCRIPTION	"An entry into the DC power system controller rectifier alarm group."
		INDEX { dcPwrSysRectAlrmIndex }
		::= { dcPwrSysRectAlrmTable 1 }

	DcPwrSysRectAlrmEntry
	::= SEQUENCE {
		dcPwrSysRectAlrmIndex 			INTEGER,
		dcPwrSysRectAlrmName 			DisplayString,
		dcPwrSysRectAlrmIntegerValue 	INTEGER,
		dcPwrSysRectAlrmStringValue 	DisplayString,
		dcPwrSysRectAlrmSeverity		INTEGER
	}

	dcPwrSysRectAlrmIndex OBJECT-TYPE
		SYNTAX INTEGER (0..65535)
		MAX-ACCESS read-only
		STATUS current
		DESCRIPTION	"The index of the alarm variable in the DC power system controller table rectifier alarm group."
	::= { dcPwrSysRectAlrmEntry 1 }

	dcPwrSysRectAlrmName OBJECT-TYPE
		SYNTAX DisplayString (SIZE(0..30))
		MAX-ACCESS read-only
		STATUS current
		DESCRIPTION	"The description of the alarm variable as reported by the DC power system controller rectifier alarm group."
	::= { dcPwrSysRectAlrmEntry 2 }

	dcPwrSysRectAlrmIntegerValue OBJECT-TYPE
		SYNTAX INTEGER (-1000000000..1000000000)
		MAX-ACCESS read-only
		STATUS current
		DESCRIPTION	"The integer value of the alarm variable as reported by the DC power system controller rectifier alarm group."
	::= { dcPwrSysRectAlrmEntry 3 }

	dcPwrSysRectAlrmStringValue OBJECT-TYPE
		SYNTAX DisplayString (SIZE(0..255))
		MAX-ACCESS read-only
		STATUS current
		DESCRIPTION	"The string value of the alarm variable as reported by the DC power system controller rectifier alarm group."
	::= { dcPwrSysRectAlrmEntry 4 }

	dcPwrSysRectAlrmSeverity OBJECT-TYPE
		SYNTAX INTEGER (0..65535)
		MAX-ACCESS read-only
		STATUS current
		DESCRIPTION	"The integer value of alarm severity level of the extra variable as reported by the DC power system controller rectifier alarm group."
	::= { dcPwrSysRectAlrmEntry 5 }

	--============================
	--  Digital alarm group
	--============================
	dcPwrSysDigAlrmCount OBJECT-TYPE
		SYNTAX INTEGER (0..65535)
		MAX-ACCESS read-only
		STATUS current
		DESCRIPTION	"Number of digital alarm variables in system controller alarm table."
	::= { dcPwrSysDigAlrmTbl 1 }

	dcPwrSysDigAlrmTable OBJECT-TYPE
		SYNTAX SEQUENCE OF DcPwrSysDigAlrmEntry
		MAX-ACCESS not-accessible
		STATUS current
		DESCRIPTION	"A table of DC power system controller digital alarm variables."
	::= { dcPwrSysDigAlrmTbl 2 }

	dcPwrSysDigAlrmEntry OBJECT-TYPE
		SYNTAX DcPwrSysDigAlrmEntry
		MAX-ACCESS not-accessible
		STATUS current
		DESCRIPTION	"An entry into the DC power system controller digital alarm group."
		INDEX { dcPwrSysDigAlrmIndex }
		::= { dcPwrSysDigAlrmTable 1 }

	DcPwrSysDigAlrmEntry
	::= SEQUENCE {
		dcPwrSysDigAlrmIndex 			INTEGER,
		dcPwrSysDigAlrmName 			DisplayString,
		dcPwrSysDigAlrmIntegerValue 	INTEGER,
		dcPwrSysDigAlrmStringValue 		DisplayString,
		dcPwrSysDigAlrmSeverity 		INTEGER
	}

	dcPwrSysDigAlrmIndex OBJECT-TYPE
		SYNTAX INTEGER (0..65535)
		MAX-ACCESS read-only
		STATUS current
		DESCRIPTION	"The index of the alarm variable in the DC power system controller table digital alarm group."
	::= { dcPwrSysDigAlrmEntry 1 }

	dcPwrSysDigAlrmName OBJECT-TYPE
		SYNTAX DisplayString (SIZE(0..30))
		MAX-ACCESS read-only
		STATUS current
		DESCRIPTION	"The description of the alarm variable as reported by the DC power system controller digital alarm group."
	::= { dcPwrSysDigAlrmEntry 2 }

	dcPwrSysDigAlrmIntegerValue OBJECT-TYPE
		SYNTAX INTEGER (-1000000000..1000000000)
		MAX-ACCESS read-only
		STATUS current
		DESCRIPTION	"The integer value of the alarm variable as reported by the DC power system controller digital alarm group."
	::= { dcPwrSysDigAlrmEntry 3 }

	dcPwrSysDigAlrmStringValue OBJECT-TYPE
		SYNTAX DisplayString (SIZE(0..255))
		MAX-ACCESS read-only
		STATUS current
		DESCRIPTION	"The string value of the alarm variable as reported by the DC power system controller digital alarm group."
	::= { dcPwrSysDigAlrmEntry 4 }

	dcPwrSysDigAlrmSeverity OBJECT-TYPE
		SYNTAX INTEGER (0..65535)
		MAX-ACCESS read-only
		STATUS current
		DESCRIPTION	"The integer value of alarm severity level of the extra variable as reported by the DC power system controller digital alarm group."
	::= { dcPwrSysDigAlrmEntry 5 }

	--============================
	--  Current alarm group
	--============================
	dcPwrSysCurrAlrmCount OBJECT-TYPE
		SYNTAX INTEGER (0..65535)
		MAX-ACCESS read-only
		STATUS current
		DESCRIPTION	"Number of current alarm variables in system controller alarm table."
	::= { dcPwrSysCurrAlrmTbl 1 }

	dcPwrSysCurrAlrmTable OBJECT-TYPE
		SYNTAX SEQUENCE OF DcPwrSysCurrAlrmEntry
		MAX-ACCESS not-accessible
		STATUS current
		DESCRIPTION	"A table of DC power system controller current alarm variables."
	::= { dcPwrSysCurrAlrmTbl 2 }

	dcPwrSysCurrAlrmEntry OBJECT-TYPE
		SYNTAX DcPwrSysCurrAlrmEntry
		MAX-ACCESS not-accessible
		STATUS current
		DESCRIPTION	"An entry into the DC power system controller current alarm group."
		INDEX { dcPwrSysCurrAlrmIndex }
		::= { dcPwrSysCurrAlrmTable 1 }

	DcPwrSysCurrAlrmEntry
	::= SEQUENCE {
		dcPwrSysCurrAlrmIndex 			INTEGER,
		dcPwrSysCurrAlrmName 			DisplayString,
		dcPwrSysCurrAlrmIntegerValue 	INTEGER,
		dcPwrSysCurrAlrmStringValue 	DisplayString,
		dcPwrSysCurrAlrmSeverity 		INTEGER
	}

	dcPwrSysCurrAlrmIndex OBJECT-TYPE
		SYNTAX INTEGER (0..65535)
		MAX-ACCESS read-only
		STATUS current
		DESCRIPTION	"The index of the alarm variable in the DC power system controller table current alarm group."
	::= { dcPwrSysCurrAlrmEntry 1 }

	dcPwrSysCurrAlrmName OBJECT-TYPE
		SYNTAX DisplayString (SIZE(0..30))
		MAX-ACCESS read-only
		STATUS current
		DESCRIPTION	"The description of the alarm variable as reported by the DC power system controller current alarm group."
	::= { dcPwrSysCurrAlrmEntry 2 }

	dcPwrSysCurrAlrmIntegerValue OBJECT-TYPE
		SYNTAX INTEGER (-1000000000..1000000000)
		MAX-ACCESS read-only
		STATUS current
		DESCRIPTION	"The integer value of the alarm variable as reported by the DC power system controller current alarm group."
	::= { dcPwrSysCurrAlrmEntry 3 }

	dcPwrSysCurrAlrmStringValue OBJECT-TYPE
		SYNTAX DisplayString (SIZE(0..255))
		MAX-ACCESS read-only
		STATUS current
		DESCRIPTION	"The string value of the alarm variable as reported by the DC power system controller current alarm group."
	::= { dcPwrSysCurrAlrmEntry 4 }

	dcPwrSysCurrAlrmSeverity OBJECT-TYPE
		SYNTAX INTEGER (0..65535)
		MAX-ACCESS read-only
		STATUS current
		DESCRIPTION	"The integer value of alarm severity level of the extra variable as reported by the DC power system controller current alarm group."
	::= { dcPwrSysCurrAlrmEntry 5 }

	--============================
	--  Voltage alarm group
	--============================
	dcPwrSysVoltAlrmCount OBJECT-TYPE
		SYNTAX INTEGER (0..65535)
		MAX-ACCESS read-only
		STATUS current
		DESCRIPTION	"Number of voltage alarm variables in system controller alarm table."
	::= { dcPwrSysVoltAlrmTbl 1 }

	dcPwrSysVoltAlrmTable OBJECT-TYPE
		SYNTAX SEQUENCE OF DcPwrSysVoltAlrmEntry
		MAX-ACCESS not-accessible
		STATUS current
		DESCRIPTION	"A table of DC power system controller voltage alarm variables."
	::= { dcPwrSysVoltAlrmTbl 2 }

	dcPwrSysVoltAlrmEntry OBJECT-TYPE
		SYNTAX DcPwrSysVoltAlrmEntry
		MAX-ACCESS not-accessible
		STATUS current
		DESCRIPTION	"An entry into the DC power system controller voltage alarm group."
		INDEX { dcPwrSysVoltAlrmIndex }
		::= { dcPwrSysVoltAlrmTable 1 }

	DcPwrSysVoltAlrmEntry
	::= SEQUENCE {
		dcPwrSysVoltAlrmIndex 			INTEGER,
		dcPwrSysVoltAlrmName 			DisplayString,
		dcPwrSysVoltAlrmIntegerValue 	INTEGER,
		dcPwrSysVoltAlrmStringValue 	DisplayString,
		dcPwrSysVoltAlrmSeverity 		INTEGER
	}

	dcPwrSysVoltAlrmIndex OBJECT-TYPE
		SYNTAX INTEGER (0..65535)
		MAX-ACCESS read-only
		STATUS current
		DESCRIPTION	"The index of the alarm variable in the DC power system controller table voltage alarm group."
	::= { dcPwrSysVoltAlrmEntry 1 }

	dcPwrSysVoltAlrmName OBJECT-TYPE
		SYNTAX DisplayString (SIZE(0..30))
		MAX-ACCESS read-only
		STATUS current
		DESCRIPTION	"The description of the alarm variable as reported by the DC power system controller voltage alarm group."
	::= { dcPwrSysVoltAlrmEntry 2 }

	dcPwrSysVoltAlrmIntegerValue OBJECT-TYPE
		SYNTAX INTEGER (-1000000000..1000000000)
		MAX-ACCESS read-only
		STATUS current
		DESCRIPTION	"The integer value of the alarm variable as reported by the DC power system controller voltage alarm group."
	::= { dcPwrSysVoltAlrmEntry 3 }

	dcPwrSysVoltAlrmStringValue OBJECT-TYPE
		SYNTAX DisplayString (SIZE(0..255))
		MAX-ACCESS read-only
		STATUS current
		DESCRIPTION	"The string value of the alarm variable as reported by the DC power system controller voltage alarm group."
	::= { dcPwrSysVoltAlrmEntry 4 }

	dcPwrSysVoltAlrmSeverity OBJECT-TYPE
		SYNTAX INTEGER (0..65535)
		MAX-ACCESS read-only
		STATUS current
		DESCRIPTION	"The integer value of alarm severity level of the extra variable as reported by the DC power system controller voltage alarm group."
	::= { dcPwrSysVoltAlrmEntry 5 }

	--============================
	--  Battery alarm group
	--============================
	dcPwrSysBattAlrmCount OBJECT-TYPE
		SYNTAX INTEGER (0..65535)
		MAX-ACCESS read-only
		STATUS current
		DESCRIPTION	"Number of battery alarm variables in system controller alarm table."
	::= { dcPwrSysBattAlrmTbl 1 }

	dcPwrSysBattAlrmTable OBJECT-TYPE
		SYNTAX SEQUENCE OF DcPwrSysBattAlrmEntry
		MAX-ACCESS not-accessible
		STATUS current
		DESCRIPTION	"A table of DC power system controller battery alarm variables."
	::= { dcPwrSysBattAlrmTbl 2 }

	dcPwrSysBattAlrmEntry OBJECT-TYPE
		SYNTAX DcPwrSysBattAlrmEntry
		MAX-ACCESS not-accessible
		STATUS current
		DESCRIPTION	"An entry into the DC power system controller battery alarm group."
		INDEX { dcPwrSysBattAlrmIndex }
		::= { dcPwrSysBattAlrmTable 1 }

	DcPwrSysBattAlrmEntry
	::= SEQUENCE {
		dcPwrSysBattAlrmIndex 			INTEGER,
		dcPwrSysBattAlrmName 			DisplayString,
		dcPwrSysBattAlrmIntegerValue 	INTEGER,
		dcPwrSysBattAlrmStringValue 	DisplayString,
		dcPwrSysBattAlrmSeverity 		INTEGER
	}

	dcPwrSysBattAlrmIndex OBJECT-TYPE
		SYNTAX INTEGER (0..65535)
		MAX-ACCESS read-only
		STATUS current
		DESCRIPTION	"The index of the alarm variable in the DC power system controller table battery alarm group."
	::= { dcPwrSysBattAlrmEntry 1 }

	dcPwrSysBattAlrmName OBJECT-TYPE
		SYNTAX DisplayString (SIZE(0..30))
		MAX-ACCESS read-only
		STATUS current
		DESCRIPTION	"The description of the alarm variable as reported by the DC power system controller battery alarm group."
	::= { dcPwrSysBattAlrmEntry 2 }

	dcPwrSysBattAlrmIntegerValue OBJECT-TYPE
		SYNTAX INTEGER (-1000000000..1000000000)
		MAX-ACCESS read-only
		STATUS current
		DESCRIPTION	"The integer value of the alarm variable as reported by the DC power system controller battery alarm group."
	::= { dcPwrSysBattAlrmEntry 3 }

	dcPwrSysBattAlrmStringValue OBJECT-TYPE
		SYNTAX DisplayString (SIZE(0..255))
		MAX-ACCESS read-only
		STATUS current
		DESCRIPTION	"The string value of the alarm variable as reported by the DC power system controller battery alarm group."
	::= { dcPwrSysBattAlrmEntry 4 }

	dcPwrSysBattAlrmSeverity OBJECT-TYPE
		SYNTAX INTEGER (0..65535)
		MAX-ACCESS read-only
		STATUS current
		DESCRIPTION	"The integer value of alarm severity level of the extra variable as reported by the DC power system controller battery alarm group."
	::= { dcPwrSysBattAlrmEntry 5 }

	--============================
	--  Temperature alarm group
	--============================
	dcPwrSysTempAlrmCount OBJECT-TYPE
		SYNTAX INTEGER (0..65535)
		MAX-ACCESS read-only
		STATUS current
		DESCRIPTION	"Number of temperature alarm variables in system controller alarm table."
	::= { dcPwrSysTempAlrmTbl 1 }

	dcPwrSysTempAlrmTable OBJECT-TYPE
		SYNTAX SEQUENCE OF DcPwrSysTempAlrmEntry
		MAX-ACCESS not-accessible
		STATUS current
		DESCRIPTION	"A table of DC power system controller temperature alarm variables."
	::= { dcPwrSysTempAlrmTbl 2 }

	dcPwrSysTempAlrmEntry OBJECT-TYPE
		SYNTAX DcPwrSysTempAlrmEntry
		MAX-ACCESS not-accessible
		STATUS current
		DESCRIPTION	"An entry into the DC power system controller temperature alarm group."
		INDEX { dcPwrSysTempAlrmIndex }
		::= { dcPwrSysTempAlrmTable 1 }

	DcPwrSysTempAlrmEntry
	::= SEQUENCE {
		dcPwrSysTempAlrmIndex 			INTEGER,
		dcPwrSysTempAlrmName 			DisplayString,
		dcPwrSysTempAlrmIntegerValue 	INTEGER,
		dcPwrSysTempAlrmStringValue 	DisplayString,
		dcPwrSysTempAlrmSeverity 		INTEGER
	}

	dcPwrSysTempAlrmIndex OBJECT-TYPE
		SYNTAX INTEGER (0..65535)
		MAX-ACCESS read-only
		STATUS current
		DESCRIPTION	"The index of the alarm variable in the DC power system controller table temperature alarm group."
	::= { dcPwrSysTempAlrmEntry 1 }

	dcPwrSysTempAlrmName OBJECT-TYPE
		SYNTAX DisplayString (SIZE(0..30))
		MAX-ACCESS read-only
		STATUS current
		DESCRIPTION	"The description of the alarm variable as reported by the DC power system controller temperature alarm group."
	::= { dcPwrSysTempAlrmEntry 2 }

	dcPwrSysTempAlrmIntegerValue OBJECT-TYPE
		SYNTAX INTEGER (-1000000000..1000000000)
		MAX-ACCESS read-only
		STATUS current
		DESCRIPTION	"The integer value of the alarm variable as reported by the DC power system controller temperature alarm group."
	::= { dcPwrSysTempAlrmEntry 3 }

	dcPwrSysTempAlrmStringValue OBJECT-TYPE
		SYNTAX DisplayString (SIZE(0..255))
		MAX-ACCESS read-only
		STATUS current
		DESCRIPTION	"The string value of the alarm variable as reported by the DC power system controller temperature alarm group."
	::= { dcPwrSysTempAlrmEntry 4 }

	dcPwrSysTempAlrmSeverity OBJECT-TYPE
		SYNTAX INTEGER (0..65535)
		MAX-ACCESS read-only
		STATUS current
		DESCRIPTION	"The integer value of alarm severity level of the extra variable as reported by the DC power system controller temperature alarm group."
	::= { dcPwrSysTempAlrmEntry 5 }

	--============================
	--  Custom alarm group
	--============================
	dcPwrSysCustomAlrmCount OBJECT-TYPE
		SYNTAX INTEGER (0..65535)
		MAX-ACCESS read-only
		STATUS current
		DESCRIPTION	"Number of custom alarm variables in system controller alarm table."
	::= { dcPwrSysCustomAlrmTbl 1 }

	dcPwrSysCustomAlrmTable OBJECT-TYPE
		SYNTAX SEQUENCE OF DcPwrSysCustomAlrmEntry
		MAX-ACCESS not-accessible
		STATUS current
		DESCRIPTION	"A table of DC power system controller custom alarm variables."
	::= { dcPwrSysCustomAlrmTbl 2 }

	dcPwrSysCustomAlrmEntry OBJECT-TYPE
		SYNTAX DcPwrSysCustomAlrmEntry
		MAX-ACCESS not-accessible
		STATUS current
		DESCRIPTION	"An entry into the DC power system controller custom alarm group."
		INDEX { dcPwrSysCustomAlrmIndex }
		::= { dcPwrSysCustomAlrmTable 1 }

	DcPwrSysCustomAlrmEntry
	::= SEQUENCE {
		dcPwrSysCustomAlrmIndex 	 	INTEGER,
		dcPwrSysCustomAlrmName 			DisplayString,
		dcPwrSysCustomAlrmIntegerValue 	INTEGER,
		dcPwrSysCustomAlrmStringValue 	DisplayString,
		dcPwrSysCustomAlrmSeverity 		INTEGER
	}

	dcPwrSysCustomAlrmIndex OBJECT-TYPE
		SYNTAX INTEGER (0..65535)
		MAX-ACCESS read-only
		STATUS current
		DESCRIPTION	"The index of the alarm variable in the DC power system controller table custom alarm group."
	::= { dcPwrSysCustomAlrmEntry 1 }

	dcPwrSysCustomAlrmName OBJECT-TYPE
		SYNTAX DisplayString (SIZE(0..30))
		MAX-ACCESS read-only
		STATUS current
		DESCRIPTION	"The description of the alarm variable as reported by the DC power system controller custom alarm group."
	::= { dcPwrSysCustomAlrmEntry 2 }

	dcPwrSysCustomAlrmIntegerValue OBJECT-TYPE
		SYNTAX INTEGER (-1000000000..1000000000)
		MAX-ACCESS read-only
		STATUS current
		DESCRIPTION	"The integer value of the alarm variable as reported by the DC power system controller custom alarm group."
	::= { dcPwrSysCustomAlrmEntry 3 }

	dcPwrSysCustomAlrmStringValue OBJECT-TYPE
		SYNTAX DisplayString (SIZE(0..255))
		MAX-ACCESS read-only
		STATUS current
		DESCRIPTION	"The string value of the alarm variable as reported by the DC power system controller custom alarm group."
	::= { dcPwrSysCustomAlrmEntry 4 }

	dcPwrSysCustomAlrmSeverity OBJECT-TYPE
		SYNTAX INTEGER (0..65535)
		MAX-ACCESS read-only
		STATUS current
		DESCRIPTION	"The integer value of alarm severity level of the extra variable as reported by the DC power system controller custom alarm group."
	::= { dcPwrSysCustomAlrmEntry 5 }

	--============================
	--  Misc alarm group
	--============================
	dcPwrSysMiscAlrmCount OBJECT-TYPE
		SYNTAX INTEGER (0..65535)
		MAX-ACCESS read-only
		STATUS current
		DESCRIPTION	"Number of misc alarm variables in system controller alarm table."
	::= { dcPwrSysMiscAlrmTbl 1 }

	dcPwrSysMiscAlrmTable OBJECT-TYPE
		SYNTAX SEQUENCE OF DcPwrSysMiscAlrmEntry
		MAX-ACCESS not-accessible
		STATUS current
		DESCRIPTION	"A table of DC power system controller misc alarm variables."
	::= { dcPwrSysMiscAlrmTbl 2 }

	dcPwrSysMiscAlrmEntry OBJECT-TYPE
		SYNTAX DcPwrSysMiscAlrmEntry
		MAX-ACCESS not-accessible
		STATUS current
		DESCRIPTION	"An entry into the DC power system controller misc alarm group."
		INDEX { dcPwrSysMiscAlrmIndex }
		::= { dcPwrSysMiscAlrmTable 1 }

	DcPwrSysMiscAlrmEntry
	::= SEQUENCE {
		dcPwrSysMiscAlrmIndex 			INTEGER,
		dcPwrSysMiscAlrmName 			DisplayString,
		dcPwrSysMiscAlrmIntegerValue 	INTEGER,
		dcPwrSysMiscAlrmStringValue 	DisplayString,
		dcPwrSysMiscAlrmSeverity 		INTEGER
	}

	dcPwrSysMiscAlrmIndex OBJECT-TYPE
		SYNTAX INTEGER (0..65535)
		MAX-ACCESS read-only
		STATUS current
		DESCRIPTION	"The index of the alarm variable in the DC power system controller table misc alarm group."
	::= { dcPwrSysMiscAlrmEntry 1 }

	dcPwrSysMiscAlrmName OBJECT-TYPE
		SYNTAX DisplayString (SIZE(0..30))
		MAX-ACCESS read-only
		STATUS current
		DESCRIPTION	"The description of the alarm variable as reported by the DC power system controller misc alarm group."
	::= { dcPwrSysMiscAlrmEntry 2 }

	dcPwrSysMiscAlrmIntegerValue OBJECT-TYPE
		SYNTAX INTEGER (-1000000000..1000000000)
		MAX-ACCESS read-only
		STATUS current
		DESCRIPTION	"The integer value of the alarm variable as reported by the DC power system controller misc alarm group."
	::= { dcPwrSysMiscAlrmEntry 3 }

	dcPwrSysMiscAlrmStringValue OBJECT-TYPE
		SYNTAX DisplayString (SIZE(0..255))
		MAX-ACCESS read-only
		STATUS current
		DESCRIPTION	"The string value of the alarm variable as reported by the DC power system controller misc alarm group."
	::= { dcPwrSysMiscAlrmEntry 4 }

	dcPwrSysMiscAlrmSeverity OBJECT-TYPE
		SYNTAX INTEGER (0..65535)
		MAX-ACCESS read-only
		STATUS current
		DESCRIPTION	"The integer value of alarm severity level of the extra variable as reported by the DC power system controller misc alarm group."
	::= { dcPwrSysMiscAlrmEntry 5 }

	--============================
	--  Control alarm group
	--============================
	dcPwrSysCtrlAlrmCount OBJECT-TYPE
		SYNTAX INTEGER (0..65535)
		MAX-ACCESS read-only
		STATUS current
		DESCRIPTION	"The number of control alarm variables."
	::= { dcPwrSysCtrlAlrmTbl 1 }

	dcPwrSysCtrlAlrmTable OBJECT-TYPE
		SYNTAX SEQUENCE OF DcPwrSysCtrlAlrmEntry
		MAX-ACCESS not-accessible
		STATUS current
		DESCRIPTION	"A table of control alarm variables."
	::= { dcPwrSysCtrlAlrmTbl 2 }

	dcPwrSysCtrlAlrmEntry OBJECT-TYPE
		SYNTAX DcPwrSysCtrlAlrmEntry
		MAX-ACCESS not-accessible
		STATUS current
		DESCRIPTION	"An entry of the control alarm group"
		INDEX { dcPwrSysCtrlAlrmIndex }
		::= { dcPwrSysCtrlAlrmTable 1 }

	DcPwrSysCtrlAlrmEntry
	::= SEQUENCE {
		dcPwrSysCtrlAlrmIndex 			INTEGER,
		dcPwrSysCtrlAlrmName 			DisplayString,
		dcPwrSysCtrlAlrmIntegerValue 	INTEGER,
		dcPwrSysCtrlAlrmStringValue 	DisplayString,
		dcPwrSysCtrlAlrmSeverity 		INTEGER
	}

	dcPwrSysCtrlAlrmIndex OBJECT-TYPE
		SYNTAX INTEGER (0..65535)
		MAX-ACCESS read-only
		STATUS current
		DESCRIPTION	"The index of the alarm variable in the control alarm group."
	::= { dcPwrSysCtrlAlrmEntry 1 }

	dcPwrSysCtrlAlrmName OBJECT-TYPE
		SYNTAX DisplayString (SIZE(0..30))
		MAX-ACCESS read-only
		STATUS current
		DESCRIPTION	"The description of the alarm variable as reported by the control alarm group."
	::= { dcPwrSysCtrlAlrmEntry 2 }

	dcPwrSysCtrlAlrmIntegerValue OBJECT-TYPE
		SYNTAX INTEGER (-1000000000..1000000000)
		MAX-ACCESS read-only
		STATUS current
		DESCRIPTION	"The integer value of the alarm variable as reported by the control alarm group."
	::= { dcPwrSysCtrlAlrmEntry 3 }

	dcPwrSysCtrlAlrmStringValue OBJECT-TYPE
		SYNTAX DisplayString (SIZE(0..255))
		MAX-ACCESS read-only
		STATUS current
		DESCRIPTION	"The string value of the alarm variable as reported by the control alarm group."
	::= { dcPwrSysCtrlAlrmEntry 4 }

	dcPwrSysCtrlAlrmSeverity OBJECT-TYPE
		SYNTAX INTEGER (0..65535)
		MAX-ACCESS read-only
		STATUS current
		DESCRIPTION	"The integer value of alarm severity level of the extra variable as reported by the control alarm group."
	::= { dcPwrSysCtrlAlrmEntry 5 }


	--============================
	--  ADIO alarm group
	--============================

	dcPwrSysAdioAlrmCount OBJECT-TYPE
		SYNTAX INTEGER (0..65535)
		MAX-ACCESS read-only
		STATUS current
		DESCRIPTION	"Number of control alarm variables in Adio alarm table."
	::= { dcPwrSysAdioAlrmTbl 1 }

	dcPwrSysAdioAlrmTable OBJECT-TYPE
		SYNTAX SEQUENCE OF DcPwrSysAdioAlrmEntry
		MAX-ACCESS not-accessible
		STATUS current
		DESCRIPTION	"A table of Adio alarm variables."
	::= { dcPwrSysAdioAlrmTbl 2 }

	dcPwrSysAdioAlrmEntry OBJECT-TYPE
		SYNTAX DcPwrSysAdioAlrmEntry
		MAX-ACCESS not-accessible
		STATUS current
		DESCRIPTION	"An entry into the Adio alarm group."
		INDEX { dcPwrSysAdioAlrmIndex }
		::= { dcPwrSysAdioAlrmTable 1 }

	DcPwrSysAdioAlrmEntry
	::= SEQUENCE {
		dcPwrSysAdioAlrmIndex 			INTEGER,
		dcPwrSysAdioAlrmName 			DisplayString,
		dcPwrSysAdioAlrmIntegerValue 	INTEGER,
		dcPwrSysAdioAlrmStringValue 	DisplayString,
		dcPwrSysAdioAlrmSeverity 		INTEGER
	}

	dcPwrSysAdioAlrmIndex OBJECT-TYPE
		SYNTAX INTEGER (0..65535)
		MAX-ACCESS read-only
		STATUS current
		DESCRIPTION	"The index of the alarm variable in the table Adio alarm group."
	::= { dcPwrSysAdioAlrmEntry 1 }

	dcPwrSysAdioAlrmName OBJECT-TYPE
		SYNTAX DisplayString (SIZE(0..30))
		MAX-ACCESS read-only
		STATUS current
		DESCRIPTION	"The description of the alarm variable as reported by the Adio alarm group."
	::= { dcPwrSysAdioAlrmEntry 2 }

	dcPwrSysAdioAlrmIntegerValue OBJECT-TYPE
		SYNTAX INTEGER (-1000000000..1000000000)
		MAX-ACCESS read-only
		STATUS current
		DESCRIPTION	"The integer value of the alarm variable as reported by the Adio alarm group."
	::= { dcPwrSysAdioAlrmEntry 3 }

	dcPwrSysAdioAlrmStringValue OBJECT-TYPE
		SYNTAX DisplayString (SIZE(0..255))
		MAX-ACCESS read-only
		STATUS current
		DESCRIPTION	"The string value of the alarm variable as reported by the Adio alarm group."
	::= { dcPwrSysAdioAlrmEntry 4 }

	dcPwrSysAdioAlrmSeverity OBJECT-TYPE
		SYNTAX INTEGER (0..65535)
		MAX-ACCESS read-only
		STATUS current
		DESCRIPTION	"The integer value of alarm severity level of the extra variable as reported by the control alarm group."
	::= { dcPwrSysAdioAlrmEntry 5 }





	--============================
	--  Converter alarm group
	--============================
	dcPwrSysConvAlrmCount OBJECT-TYPE
		SYNTAX INTEGER (0..65535)
		MAX-ACCESS read-only
		STATUS current
		DESCRIPTION	"Number of Converter alarm variables in system controller alarm table."
	::= { dcPwrSysConvAlrmTbl 1 }

	dcPwrSysConvAlrmTable OBJECT-TYPE
		SYNTAX SEQUENCE OF DcPwrSysConvAlrmEntry
		MAX-ACCESS not-accessible
		STATUS current
		DESCRIPTION	"A table of Converter alarm variables."
	::= { dcPwrSysConvAlrmTbl 2 }

	dcPwrSysConvAlrmEntry OBJECT-TYPE
		SYNTAX DcPwrSysConvAlrmEntry
		MAX-ACCESS not-accessible
		STATUS current
		DESCRIPTION	"An entry into the Converter alarm group."
		INDEX { dcPwrSysConvAlrmIndex }
		::= { dcPwrSysConvAlrmTable 1 }

	DcPwrSysConvAlrmEntry
	::= SEQUENCE {
		dcPwrSysConvAlrmIndex 			INTEGER,
		dcPwrSysConvAlrmName 			DisplayString,
		dcPwrSysConvAlrmIntegerValue 	INTEGER,
		dcPwrSysConvAlrmStringValue 	DisplayString,
		dcPwrSysConvAlrmSeverity		INTEGER
	}

	dcPwrSysConvAlrmIndex OBJECT-TYPE
		SYNTAX INTEGER (0..65535)
		MAX-ACCESS read-only
		STATUS current
		DESCRIPTION	"The index of the alarm variable in the DC power system controller table Converter alarm group."
	::= { dcPwrSysConvAlrmEntry 1 }

	dcPwrSysConvAlrmName OBJECT-TYPE
		SYNTAX DisplayString (SIZE(0..30))
		MAX-ACCESS read-only
		STATUS current
		DESCRIPTION	"The description of the alarm variable as reported by the Converter alarm group."
	::= { dcPwrSysConvAlrmEntry 2 }

	dcPwrSysConvAlrmIntegerValue OBJECT-TYPE
		SYNTAX INTEGER (-1000000000..1000000000)
		MAX-ACCESS read-only
		STATUS current
		DESCRIPTION	"The integer value of the alarm variable as reported by the Converter alarm group."
	::= { dcPwrSysConvAlrmEntry 3 }

	dcPwrSysConvAlrmStringValue OBJECT-TYPE
		SYNTAX DisplayString (SIZE(0..255))
		MAX-ACCESS read-only
		STATUS current
		DESCRIPTION	"The string value of the alarm variable as reported by the Converter alarm group."
	::= { dcPwrSysConvAlrmEntry 4 }

	dcPwrSysConvAlrmSeverity OBJECT-TYPE
		SYNTAX INTEGER (0..65535)
		MAX-ACCESS read-only
		STATUS current
		DESCRIPTION	"The integer value of alarm severity level of the extra variable as reported by the Converter alarm group."
	::= { dcPwrSysConvAlrmEntry 5 }






	--============================
	--  alarm group
	--============================
	dcPwrSysInvAlrmCount OBJECT-TYPE
		SYNTAX INTEGER (0..65535)
		MAX-ACCESS read-only
		STATUS current
		DESCRIPTION	"Number of alarm variables in system controller alarm table"
	::= { dcPwrSysInvAlrmTbl 1 }

	dcPwrSysInvAlrmTable OBJECT-TYPE
		SYNTAX SEQUENCE OF DcPwrSysInvAlrmEntry
		MAX-ACCESS not-accessible
		STATUS current
		DESCRIPTION	"A table of power system controller Inv alarm variables"
	::= { dcPwrSysInvAlrmTbl 2 }

	dcPwrSysInvAlrmEntry OBJECT-TYPE
		SYNTAX DcPwrSysInvAlrmEntry
		MAX-ACCESS not-accessible
		STATUS current
		DESCRIPTION	"An entry into the power system controller Inv alarm group"
		INDEX { dcPwrSysInvAlrmIndex }
		::= { dcPwrSysInvAlrmTable 1 }

	DcPwrSysInvAlrmEntry
	::= SEQUENCE {
		dcPwrSysInvAlrmIndex 				INTEGER,
		dcPwrSysInvAlrmName 				DisplayString,
		dcPwrSysInvAlrmIntegerValue 		INTEGER,
		dcPwrSysInvAlrmStringValue	 		DisplayString,
		dcPwrSysInvAlrmSeverity				INTEGER
	}

	dcPwrSysInvAlrmIndex OBJECT-TYPE
		SYNTAX INTEGER (0..65535)
		MAX-ACCESS read-only
		STATUS current
		DESCRIPTION	""
	::= { dcPwrSysInvAlrmEntry 1 }

	dcPwrSysInvAlrmName OBJECT-TYPE
		SYNTAX DisplayString (SIZE(0..30))
		MAX-ACCESS read-only
		STATUS current
		DESCRIPTION	""
	::= { dcPwrSysInvAlrmEntry 2 }

	dcPwrSysInvAlrmIntegerValue OBJECT-TYPE
		SYNTAX INTEGER (-1000000000..1000000000)
		MAX-ACCESS read-only
		STATUS current
		DESCRIPTION	""
	::= { dcPwrSysInvAlrmEntry 3 }

	dcPwrSysInvAlrmStringValue OBJECT-TYPE
		SYNTAX DisplayString (SIZE(0..255))
		MAX-ACCESS read-only
		STATUS current
		DESCRIPTION	""
	::= { dcPwrSysInvAlrmEntry 4 }

	dcPwrSysInvAlrmSeverity OBJECT-TYPE
		SYNTAX INTEGER (0..65535)
		MAX-ACCESS read-only
		STATUS current
		DESCRIPTION	""
	::= { dcPwrSysInvAlrmEntry 5 }



	--============================
	--  Lps alarm group
	--============================
	dcPwrSysLpsAlrmCount OBJECT-TYPE
		SYNTAX INTEGER (0..65535)
		MAX-ACCESS read-only
		STATUS current
		DESCRIPTION	"Number of LPS alarm variables in system controller alarm table."
	::= { dcPwrSysLpsAlrmTbl 1 }

	dcPwrSysLpsAlrmTable OBJECT-TYPE
		SYNTAX SEQUENCE OF DcPwrSysLpsAlrmEntry
		MAX-ACCESS not-accessible
		STATUS current
		DESCRIPTION	"A table of LPS alarm variables."
	::= { dcPwrSysLpsAlrmTbl 2 }

	dcPwrSysLpsAlrmEntry OBJECT-TYPE
		SYNTAX DcPwrSysLpsAlrmEntry
		MAX-ACCESS not-accessible
		STATUS current
		DESCRIPTION	"An entry into the LPS alarm group."
		INDEX { dcPwrSysLpsAlrmIndex }
		::= { dcPwrSysLpsAlrmTable 1 }

	DcPwrSysLpsAlrmEntry
	::= SEQUENCE {
		dcPwrSysLpsAlrmIndex 			INTEGER,
		dcPwrSysLpsAlrmName 			DisplayString,
		dcPwrSysLpsAlrmIntegerValue 	INTEGER,
		dcPwrSysLpsAlrmStringValue 		DisplayString,
		dcPwrSysLpsAlrmSeverity			INTEGER
	}

	dcPwrSysLpsAlrmIndex OBJECT-TYPE
		SYNTAX INTEGER (0..65535)
		MAX-ACCESS read-only
		STATUS current
		DESCRIPTION	"The index of the alarm variable in the DC power system controller table LPS alarm group."
	::= { dcPwrSysLpsAlrmEntry 1 }

	dcPwrSysLpsAlrmName OBJECT-TYPE
		SYNTAX DisplayString (SIZE(0..30))
		MAX-ACCESS read-only
		STATUS current
		DESCRIPTION	"The description of the alarm variable as reported by the LPS alarm group."
	::= { dcPwrSysLpsAlrmEntry 2 }

	dcPwrSysLpsAlrmIntegerValue OBJECT-TYPE
		SYNTAX INTEGER (-1000000000..1000000000)
		MAX-ACCESS read-only
		STATUS current
		DESCRIPTION	"The integer value of the alarm variable as reported by the LPS alarm group."
	::= { dcPwrSysLpsAlrmEntry 3 }

	dcPwrSysLpsAlrmStringValue OBJECT-TYPE
		SYNTAX DisplayString (SIZE(0..255))
		MAX-ACCESS read-only
		STATUS current
		DESCRIPTION	"The string value of the alarm variable as reported by the LPS alarm group."
	::= { dcPwrSysLpsAlrmEntry 4 }

	dcPwrSysLpsAlrmSeverity OBJECT-TYPE
		SYNTAX INTEGER (0..65535)
		MAX-ACCESS read-only
		STATUS current
		DESCRIPTION	"The integer value of alarm severity level of the extra variable as reported by the LPS alarm group."
	::= { dcPwrSysLpsAlrmEntry 5 }




	--============
	-- Input table
	--============
	--=====================
	-- Digital input group
	--=====================
	dcPwrSysDigIpCount OBJECT-TYPE
		SYNTAX INTEGER (0..65535)
		MAX-ACCESS read-only
		STATUS current
		DESCRIPTION	"Number of digital input variables in system controller digital input table."
	::= { dcPwrSysDigIpTbl 1 }

	dcPwrSysDigIpTable OBJECT-TYPE
		SYNTAX SEQUENCE OF DcPwrSysDigIpEntry
		MAX-ACCESS not-accessible
		STATUS current
		DESCRIPTION	"A table of digital input variables."
	::= { dcPwrSysDigIpTbl 2 }

	dcPwrSysDigIpEntry OBJECT-TYPE
		SYNTAX DcPwrSysDigIpEntry
		MAX-ACCESS not-accessible
		STATUS current
		DESCRIPTION	"An entry into the digital input group."
		INDEX { dcPwrSysDigIpIndex }
		::= { dcPwrSysDigIpTable 1 }

	DcPwrSysDigIpEntry
	::= SEQUENCE {
		dcPwrSysDigIpIndex 			INTEGER,
		dcPwrSysDigIpName 			DisplayString,
		dcPwrSysDigIpIntegerValue 	INTEGER,
		dcPwrSysDigIpStringValue 	DisplayString
	}

	dcPwrSysDigIpIndex OBJECT-TYPE
		SYNTAX INTEGER (0..65535)
		MAX-ACCESS read-only
		STATUS current
		DESCRIPTION	"The index of the digital input variable in the table digital input group."
	::= { dcPwrSysDigIpEntry 1 }

	dcPwrSysDigIpName OBJECT-TYPE
		SYNTAX DisplayString (SIZE(0..30))
		MAX-ACCESS read-only
		STATUS current
		DESCRIPTION	"The description of the digital input variable as reported by the digital input group."
	::= { dcPwrSysDigIpEntry 2 }

	dcPwrSysDigIpIntegerValue OBJECT-TYPE
		SYNTAX INTEGER (-1000000000..1000000000)
		MAX-ACCESS read-only
		STATUS current
		DESCRIPTION	"The integer value of the digital input variable as reported by the digital input group."
	::= { dcPwrSysDigIpEntry 3 }

	dcPwrSysDigIpStringValue OBJECT-TYPE
		SYNTAX DisplayString (SIZE(0..255))
		MAX-ACCESS read-only
		STATUS current
		DESCRIPTION	"The string value of the digital input variable as reported by the digital input group."
	::= { dcPwrSysDigIpEntry 4 }

	--=========================
	-- Controller input group
	--=========================
	dcPwrSysCntrlrIpCount OBJECT-TYPE
		SYNTAX INTEGER (0..65535)
		MAX-ACCESS read-only
		STATUS current
		DESCRIPTION	"Number of controller input variables in system controller controller input table."
	::= { dcPwrSysCntrlrIpTbl 1 }

	dcPwrSysCntrlrIpTable OBJECT-TYPE
		SYNTAX SEQUENCE OF DcPwrSysCntrlrIpEntry
		MAX-ACCESS not-accessible
		STATUS current
		DESCRIPTION	"A table of controller input variables."
	::= { dcPwrSysCntrlrIpTbl 2 }

	dcPwrSysCntrlrIpEntry OBJECT-TYPE
		SYNTAX DcPwrSysCntrlrIpEntry
		MAX-ACCESS not-accessible
		STATUS current
		DESCRIPTION	"An entry into the controller input group."
		INDEX { dcPwrSysCntrlrIpIndex }
		::= { dcPwrSysCntrlrIpTable 1 }

	DcPwrSysCntrlrIpEntry
	::= SEQUENCE {
		dcPwrSysCntrlrIpIndex 			INTEGER,
		dcPwrSysCntrlrIpName 			DisplayString,
		dcPwrSysCntrlrIpIntegerValue 	INTEGER,
		dcPwrSysCntrlrIpStringValue 	DisplayString
	}

	dcPwrSysCntrlrIpIndex OBJECT-TYPE
		SYNTAX INTEGER (0..65535)
		MAX-ACCESS read-only
		STATUS current
		DESCRIPTION	"The index of the controller input variable in the table controller input group."
	::= { dcPwrSysCntrlrIpEntry 1 }

	dcPwrSysCntrlrIpName OBJECT-TYPE
		SYNTAX DisplayString (SIZE(0..30))
		MAX-ACCESS read-only
		STATUS current
		DESCRIPTION	"The description of the controller input variable as reported by the controller input group."
	::= { dcPwrSysCntrlrIpEntry 2 }

	dcPwrSysCntrlrIpIntegerValue OBJECT-TYPE
		SYNTAX INTEGER (-1000000000..1000000000)
		MAX-ACCESS read-only
		STATUS current
		DESCRIPTION	"The integer value of the controller input variable as reported by the controller input group."
	::= { dcPwrSysCntrlrIpEntry 3 }

	dcPwrSysCntrlrIpStringValue OBJECT-TYPE
		SYNTAX DisplayString (SIZE(0..255))
		MAX-ACCESS read-only
		STATUS current
		DESCRIPTION	"The string value of the controller input variable as reported by the controller input group."
	::= { dcPwrSysCntrlrIpEntry 4 }

	--========================
	-- Rectifier input group
	--========================
	dcPwrSysRectIpCount OBJECT-TYPE
		SYNTAX INTEGER (0..65535)
		MAX-ACCESS read-only
		STATUS current
		DESCRIPTION	"Number of rectifier input variables in system controller rectifier input table."
	::= { dcPwrSysRectIpTbl 1 }

	dcPwrSysRectIpTable OBJECT-TYPE
		SYNTAX SEQUENCE OF DcPwrSysRectIpEntry
		MAX-ACCESS not-accessible
		STATUS current
		DESCRIPTION	"A table of rectifier input variables."
	::= { dcPwrSysRectIpTbl 2 }

	dcPwrSysRectIpEntry OBJECT-TYPE
		SYNTAX DcPwrSysRectIpEntry
		MAX-ACCESS not-accessible
		STATUS current
		DESCRIPTION	"An entry into the rectifier input group."
		INDEX { dcPwrSysRectIpIndex }
		::= { dcPwrSysRectIpTable 1 }

	DcPwrSysRectIpEntry
	::= SEQUENCE {
		dcPwrSysRectIpIndex 	  	INTEGER,
		dcPwrSysRectIpName 			DisplayString,
		dcPwrSysRectIpIntegerValue 	INTEGER,
		dcPwrSysRectIpStringValue 	DisplayString
	}

	dcPwrSysRectIpIndex OBJECT-TYPE
		SYNTAX INTEGER (0..65535)
		MAX-ACCESS read-only
		STATUS current
		DESCRIPTION	"The index of the rectifier input variable in the table rectifier input group."
	::= { dcPwrSysRectIpEntry 1 }

	dcPwrSysRectIpName OBJECT-TYPE
		SYNTAX DisplayString (SIZE(0..30))
		MAX-ACCESS read-only
		STATUS current
		DESCRIPTION	"The description of the rectifier input variable as reported by the rectifier input group."
	::= { dcPwrSysRectIpEntry 2 }

	dcPwrSysRectIpIntegerValue OBJECT-TYPE
		SYNTAX INTEGER (-1000000000..1000000000)
		MAX-ACCESS read-only
		STATUS current
		DESCRIPTION	"The integer value of the rectifier input variable as reported by the rectifier input group."
	::= { dcPwrSysRectIpEntry 3 }

	dcPwrSysRectIpStringValue OBJECT-TYPE
		SYNTAX DisplayString (SIZE(0..255))
		MAX-ACCESS read-only
		STATUS current
		DESCRIPTION	"The string value of the rectifier input variable as reported by the rectifier input group."
	::= { dcPwrSysRectIpEntry 4 }

	--======================
	-- Custom input group
	--======================
	dcPwrSysCustomIpCount OBJECT-TYPE
		SYNTAX INTEGER (0..65535)
		MAX-ACCESS read-only
		STATUS current
		DESCRIPTION	"Number of custom input variables in system controller custom input table."
	::= { dcPwrSysCustomIpTbl 1 }

	dcPwrSysCustomIpTable OBJECT-TYPE
		SYNTAX SEQUENCE OF DcPwrSysCustomIpEntry
		MAX-ACCESS not-accessible
		STATUS current
		DESCRIPTION	"A table of digital custom variables."
	::= { dcPwrSysCustomIpTbl 2 }

	dcPwrSysCustomIpEntry OBJECT-TYPE
		SYNTAX DcPwrSysCustomIpEntry
		MAX-ACCESS not-accessible
		STATUS current
		DESCRIPTION	"An entry into the custom input group."
		INDEX { dcPwrSysCustomIpIndex }
		::= { dcPwrSysCustomIpTable 1 }

	DcPwrSysCustomIpEntry
	::= SEQUENCE {
		dcPwrSysCustomIpIndex 			INTEGER,
		dcPwrSysCustomIpName 			DisplayString,
		dcPwrSysgCustomIpIntegerValue 	INTEGER,
		dcPwrSysCustomIpStringValue 	DisplayString
	}

	dcPwrSysCustomIpIndex OBJECT-TYPE
		SYNTAX INTEGER (0..65535)
		MAX-ACCESS read-only
		STATUS current
		DESCRIPTION	"The index of the custom input variable in the table custom input group."
	::= { dcPwrSysCustomIpEntry 1 }

	dcPwrSysCustomIpName OBJECT-TYPE
		SYNTAX DisplayString (SIZE(0..30))
		MAX-ACCESS read-only
		STATUS current
		DESCRIPTION	"The description of the custom input variable as reported by the custom input group."
	::= { dcPwrSysCustomIpEntry 2 }

	dcPwrSysgCustomIpIntegerValue OBJECT-TYPE
		SYNTAX INTEGER (-1000000000..1000000000)
		MAX-ACCESS read-write
		STATUS current
		DESCRIPTION	"The integer value of the custom input variable as reported by the custom input group."
	::= { dcPwrSysCustomIpEntry 3 }

	dcPwrSysCustomIpStringValue OBJECT-TYPE
		SYNTAX DisplayString (SIZE(0..255))
		MAX-ACCESS read-only
		STATUS current
		DESCRIPTION	"The string value of the custom input variable as reported by the custom input group."
	::= { dcPwrSysCustomIpEntry 4 }



	--========================
	-- Converter input group
	--========================
	dcPwrSysConvIpCount OBJECT-TYPE
		SYNTAX INTEGER (0..65535)
		MAX-ACCESS read-only
		STATUS current
		DESCRIPTION	"Number of Converter input variables in system controller Converter input table."
	::= { dcPwrSysConvIpTbl 1 }

	dcPwrSysConvIpTable OBJECT-TYPE
		SYNTAX SEQUENCE OF DcPwrSysConvIpEntry
		MAX-ACCESS not-accessible
		STATUS current
		DESCRIPTION	"A table of Converter input variables."
	::= { dcPwrSysConvIpTbl 2 }

	dcPwrSysConvIpEntry OBJECT-TYPE
		SYNTAX DcPwrSysConvIpEntry
		MAX-ACCESS not-accessible
		STATUS current
		DESCRIPTION	"An entry into the Converter input group."
		INDEX { dcPwrSysConvIpIndex }
		::= { dcPwrSysConvIpTable 1 }

	DcPwrSysConvIpEntry
	::= SEQUENCE {
		dcPwrSysConvIpIndex 	  	INTEGER,
		dcPwrSysConvIpName 			DisplayString,
		dcPwrSysConvIpIntegerValue 	INTEGER,
		dcPwrSysConvIpStringValue 	DisplayString
	}

	dcPwrSysConvIpIndex OBJECT-TYPE
		SYNTAX INTEGER (0..65535)
		MAX-ACCESS read-only
		STATUS current
		DESCRIPTION	"The index of the Converter input variable in the table Converter input group."
	::= { dcPwrSysConvIpEntry 1 }

	dcPwrSysConvIpName OBJECT-TYPE
		SYNTAX DisplayString (SIZE(0..30))
		MAX-ACCESS read-only
		STATUS current
		DESCRIPTION	"The description of the Converter input variable as reported by the Converter input group."
	::= { dcPwrSysConvIpEntry 2 }

	dcPwrSysConvIpIntegerValue OBJECT-TYPE
		SYNTAX INTEGER (-1000000000..1000000000)
		MAX-ACCESS read-only
		STATUS current
		DESCRIPTION	"The integer value of the Converter input variable as reported by the Converter input group."
	::= { dcPwrSysConvIpEntry 3 }

	dcPwrSysConvIpStringValue OBJECT-TYPE
		SYNTAX DisplayString (SIZE(0..255))
		MAX-ACCESS read-only
		STATUS current
		DESCRIPTION	"The string value of the Converter input variable as reported by the Converter input group."
	::= { dcPwrSysConvIpEntry 4 }

	--========================
	-- Timer input group
	--========================
	dcPwrSysTimerIpCount OBJECT-TYPE
		SYNTAX INTEGER (0..65535)
		MAX-ACCESS read-only
		STATUS current
		DESCRIPTION	"Number of Timer input variables in system controller Timer input table."
	::= { dcPwrSysTimerIpTbl 1 }

	dcPwrSysTimerIpTable OBJECT-TYPE
		SYNTAX SEQUENCE OF DcPwrSysTimerIpEntry
		MAX-ACCESS not-accessible
		STATUS current
		DESCRIPTION	"A table of Timer input variables"
	::= { dcPwrSysTimerIpTbl 2 }

	dcPwrSysTimerIpEntry OBJECT-TYPE
		SYNTAX DcPwrSysTimerIpEntry
		MAX-ACCESS not-accessible
		STATUS current
		DESCRIPTION	"An entry into the Timer input group"
		INDEX { dcPwrSysTimerIpIndex }
		::= { dcPwrSysTimerIpTable 1 }

	DcPwrSysTimerIpEntry
	::= SEQUENCE {
		dcPwrSysTimerIpIndex 	  		INTEGER,
		dcPwrSysTimerIpName 			DisplayString,
		dcPwrSysTimerIpIntegerValue 	INTEGER,
		dcPwrSysTimerIpStringValue 		DisplayString
	}

	dcPwrSysTimerIpIndex OBJECT-TYPE
		SYNTAX INTEGER (0..65535)
		MAX-ACCESS read-only
		STATUS current
		DESCRIPTION	"The index of the Timer input variable in the table Timer input group."
	::= { dcPwrSysTimerIpEntry 1 }

	dcPwrSysTimerIpName OBJECT-TYPE
		SYNTAX DisplayString (SIZE(0..30))
		MAX-ACCESS read-only
		STATUS current
		DESCRIPTION	"The description of the Timer input variable as reported by the Timer input group."
	::= { dcPwrSysTimerIpEntry 2 }

	dcPwrSysTimerIpIntegerValue OBJECT-TYPE
		SYNTAX INTEGER (-1000000000..1000000000)
		MAX-ACCESS read-only
		STATUS current
		DESCRIPTION	"The integer value of the Timer input variable as reported by the Timer input group."
	::= { dcPwrSysTimerIpEntry 3 }

	dcPwrSysTimerIpStringValue OBJECT-TYPE
		SYNTAX DisplayString (SIZE(0..255))
		MAX-ACCESS read-only
		STATUS current
		DESCRIPTION	"The string value of the Timer input variable as reported by the Timer input group."
	::= { dcPwrSysTimerIpEntry 4 }


	--========================
	-- Counter input group
	--========================
	dcPwrSysCounterIpCount OBJECT-TYPE
		SYNTAX INTEGER (0..65535)
		MAX-ACCESS read-only
		STATUS current
		DESCRIPTION	"Number of Counter input variables in system controller Counter input table."
	::= { dcPwrSysCounterIpTbl 1 }

	dcPwrSysCounterIpTable OBJECT-TYPE
		SYNTAX SEQUENCE OF DcPwrSysCounterIpEntry
		MAX-ACCESS not-accessible
		STATUS current
		DESCRIPTION	"A table of Counter input variables."
	::= { dcPwrSysCounterIpTbl 2 }

	dcPwrSysCounterIpEntry OBJECT-TYPE
		SYNTAX DcPwrSysCounterIpEntry
		MAX-ACCESS not-accessible
		STATUS current
		DESCRIPTION	"An entry into the Counter input group."
		INDEX { dcPwrSysCounterIpIndex }
		::= { dcPwrSysCounterIpTable 1 }

	DcPwrSysCounterIpEntry
	::= SEQUENCE {
		dcPwrSysCounterIpIndex 	  		INTEGER,
		dcPwrSysCounterIpName 			DisplayString,
		dcPwrSysCounterIpIntegerValue 	INTEGER,
		dcPwrSysCounterIpStringValue 	DisplayString
	}

	dcPwrSysCounterIpIndex OBJECT-TYPE
		SYNTAX INTEGER (0..65535)
		MAX-ACCESS read-only
		STATUS current
		DESCRIPTION	"The index of the Counter input variable in the table Counter input group."
	::= { dcPwrSysCounterIpEntry 1 }

	dcPwrSysCounterIpName OBJECT-TYPE
		SYNTAX DisplayString (SIZE(0..30))
		MAX-ACCESS read-only
		STATUS current
		DESCRIPTION	"The description of the Counter input variable as reported by the Counter input group."
	::= { dcPwrSysCounterIpEntry 2 }

	dcPwrSysCounterIpIntegerValue OBJECT-TYPE
		SYNTAX INTEGER (-1000000000..1000000000)
		MAX-ACCESS read-only
		STATUS current
		DESCRIPTION	"The integer value of the Counter input variable as reported by the Counter input group."
	::= { dcPwrSysCounterIpEntry 3 }

	dcPwrSysCounterIpStringValue OBJECT-TYPE
		SYNTAX DisplayString (SIZE(0..255))
		MAX-ACCESS read-only
		STATUS current
		DESCRIPTION	"The string value of the Counter input variable as reported by the Counter input group."
	::= { dcPwrSysCounterIpEntry 4 }


	--==========================================================================
	-- LPS Data
	--==========================================================================

	lpsModuleCount OBJECT-TYPE
		SYNTAX INTEGER (0..65535)
		MAX-ACCESS read-only
		STATUS current
		DESCRIPTION	"The number of LPS modules acquired by the CXC."
	::= { dcPwrSysLpsTbl 1 }

	lpsModuleTable OBJECT-TYPE
		SYNTAX SEQUENCE OF LpsModuleEntry
		MAX-ACCESS not-accessible
		STATUS current
		DESCRIPTION	"A table of LPS modules."
	::= { dcPwrSysLpsTbl 2 }

	lpsModuleEntry OBJECT-TYPE
		SYNTAX LpsModuleEntry
		MAX-ACCESS not-accessible
		STATUS current
		DESCRIPTION	"An entry in the table of LPS modules."
		INDEX { lpsModuleIndex }
		::= { lpsModuleTable 1 }

	LpsModuleEntry
	::= SEQUENCE {
		lpsModuleIndex 	  			INTEGER,
		lpsShelfId 					INTEGER,
		lpsPosition 				INTEGER,
		lpsInputVoltage 			INTEGER,
		lpsHeatsinkTemperature 		INTEGER,
		lpsAmbientTemperature 		INTEGER,
		lpsSerialNumber				DisplayString,
		lpsDeviceName				DisplayString,
		lpsSoftwareVersionNumber	DisplayString
	}

	lpsModuleIndex OBJECT-TYPE
		SYNTAX INTEGER (0..65535)
		MAX-ACCESS read-only
		STATUS current
		DESCRIPTION	"The index of the LPS module."
	::= { lpsModuleEntry 1 }

	lpsShelfId OBJECT-TYPE
		SYNTAX INTEGER (0..65535)
		MAX-ACCESS read-only
		STATUS current
		DESCRIPTION	"LPS Shelf ID - identifies the shelf in which this LPS is located."
	::= { lpsModuleEntry 2 }

	lpsPosition OBJECT-TYPE
		SYNTAX INTEGER (0..65535)
		MAX-ACCESS read-only
		STATUS current
		DESCRIPTION	"Position (slot ID) - identifies the position within the shelf."
	::= { lpsModuleEntry 3 }

	lpsInputVoltage OBJECT-TYPE
		SYNTAX INTEGER (0..65535)
		MAX-ACCESS read-only
		STATUS current
		DESCRIPTION	"Input Voltage"
	::= { lpsModuleEntry 4 }

	lpsHeatsinkTemperature OBJECT-TYPE
		SYNTAX INTEGER (0..65535)
		MAX-ACCESS read-only
		STATUS current
		DESCRIPTION	"Heatsink Temperature."
	::= { lpsModuleEntry 5 }

	lpsAmbientTemperature OBJECT-TYPE
		SYNTAX INTEGER (0..65535)
		MAX-ACCESS read-only
		STATUS current
		DESCRIPTION	"Ambient Temperature"
	::= { lpsModuleEntry 6 }

	lpsSerialNumber OBJECT-TYPE
		SYNTAX DisplayString (SIZE(0..16))
		MAX-ACCESS read-only
		STATUS current
		DESCRIPTION	"LPS module serial number"
	::= { lpsModuleEntry 7 }

	lpsDeviceName OBJECT-TYPE
		SYNTAX DisplayString (SIZE(0..16))
		MAX-ACCESS read-only
		STATUS current
		DESCRIPTION	"LPS Device name."
	::= { lpsModuleEntry 8 }

	lpsSoftwareVersionNumber OBJECT-TYPE
		SYNTAX DisplayString (SIZE(0..16))
		MAX-ACCESS read-only
		STATUS current
		DESCRIPTION	"LPS software version number."
	::= { lpsModuleEntry 9 }


	lpsModuleAlarmTable OBJECT-TYPE
		SYNTAX SEQUENCE OF LpsModuleAlarmEntry
		MAX-ACCESS not-accessible
		STATUS current
		DESCRIPTION	"A table containing LPS alarms."
	::= { dcPwrSysLpsTbl 3 }

	lpsModuleAlarmEntry OBJECT-TYPE
		SYNTAX LpsModuleAlarmEntry
		MAX-ACCESS not-accessible
		STATUS current
		DESCRIPTION	"An entry in the table of LPS alarms."
		INDEX { lpsModuleIndex }
		::= { lpsModuleAlarmTable 1 }

	LpsModuleAlarmEntry
	::= SEQUENCE {
		lpsModuleAlarmEntryIndex	INTEGER,
		lpsHighInputVoltageAlarm	INTEGER,
		lpsLowInputVoltageAlarm		INTEGER,
		lpsAmbientHighAlarm         INTEGER,
		lpsHeatsinkHighAlarm		INTEGER,
		lpsMajorAlarm				INTEGER,
		lpsMinorAlarm				INTEGER,
		lpsOOTAlarm				INTEGER,
		lpsCommsLostAlarm			INTEGER
	}

	lpsModuleAlarmEntryIndex OBJECT-TYPE
		SYNTAX INTEGER (0..65535)
		MAX-ACCESS read-only
		STATUS current
		DESCRIPTION	"The index of the LPS module."
	::= { lpsModuleAlarmEntry 1 }


	lpsHighInputVoltageAlarm OBJECT-TYPE
		SYNTAX INTEGER (0..1)
		MAX-ACCESS read-only
		STATUS current
		DESCRIPTION	"Input voltage is too high."
	::= { lpsModuleAlarmEntry 2 }

	lpsLowInputVoltageAlarm OBJECT-TYPE
		SYNTAX INTEGER (0..1)
		MAX-ACCESS read-only
		STATUS current
		DESCRIPTION	"Input voltage is too low."
	::= { lpsModuleAlarmEntry 3 }

	lpsAmbientHighAlarm OBJECT-TYPE
		SYNTAX INTEGER (0..1)
		MAX-ACCESS read-only
		STATUS current
		DESCRIPTION	"Ambient temperature is too high."
	::= { lpsModuleAlarmEntry 4 }

	lpsHeatsinkHighAlarm OBJECT-TYPE
		SYNTAX INTEGER (0..1)
		MAX-ACCESS read-only
		STATUS current
		DESCRIPTION	"Heatsink temperature is too high."
	::= { lpsModuleAlarmEntry 5 }

	lpsMajorAlarm OBJECT-TYPE
		SYNTAX INTEGER (0..1)
		MAX-ACCESS read-only
		STATUS current
		DESCRIPTION	"Multiple LPS outputs have failed."
	::= { lpsModuleAlarmEntry 6 }

	lpsMinorAlarm OBJECT-TYPE
		SYNTAX INTEGER (0..1)
		MAX-ACCESS read-only
		STATUS current
		DESCRIPTION	"A single LPS output has failed."
	::= { lpsModuleAlarmEntry 7 }

	lpsOOTAlarm OBJECT-TYPE
		SYNTAX INTEGER (0..1)
		MAX-ACCESS read-only
		STATUS current
		DESCRIPTION	"The LPS settings do not match those required by the controller."
	::= { lpsModuleAlarmEntry 8 }

	lpsCommsLostAlarm OBJECT-TYPE
		SYNTAX INTEGER (0..1)
		MAX-ACCESS read-only
		STATUS current
		DESCRIPTION	"The controller has lost communication with the LPS."
	::= { lpsModuleAlarmEntry 9 }

	lpsOutputVoltageTable OBJECT-TYPE
		SYNTAX SEQUENCE OF LpsOutputVoltageEntry
		MAX-ACCESS not-accessible
		STATUS current
		DESCRIPTION	"A table containing the output voltage of the LPS channels."
	::= { dcPwrSysLpsTbl 4 }

	lpsOutputVoltageEntry OBJECT-TYPE
		SYNTAX LpsOutputVoltageEntry
		MAX-ACCESS not-accessible
		STATUS current
		DESCRIPTION	"An entry in the table containing the output voltage of the LPS channels."
		INDEX { lpsModuleIndex }
		::= { lpsOutputVoltageTable 1 }

	LpsOutputVoltageEntry
	::= SEQUENCE {
		lpsOutputVoltageEntryIndex	INTEGER,
		lpsOutputVoltageChannel1 	INTEGER,
		lpsOutputVoltageChannel2 	INTEGER,
		lpsOutputVoltageChannel3 	INTEGER,
		lpsOutputVoltageChannel4 	INTEGER,
	}

	lpsOutputVoltageEntryIndex OBJECT-TYPE
		SYNTAX INTEGER (0..65535)
		MAX-ACCESS read-only
		STATUS current
		DESCRIPTION	"index"
	::= { lpsOutputVoltageEntry 1 }


	lpsOutputVoltageChannel1 OBJECT-TYPE
		SYNTAX INTEGER (0..65535)
		MAX-ACCESS read-only
		STATUS current
		DESCRIPTION	"The output voltage of LPS Channel 1."
	::= { lpsOutputVoltageEntry 2 }

	lpsOutputVoltageChannel2 OBJECT-TYPE
		SYNTAX INTEGER (0..65535)
		MAX-ACCESS read-only
		STATUS current
		DESCRIPTION	"The output voltage of LPS Channel 2."
	::= { lpsOutputVoltageEntry 3 }

	lpsOutputVoltageChannel3 OBJECT-TYPE
		SYNTAX INTEGER (0..65535)
		MAX-ACCESS read-only
		STATUS current
		DESCRIPTION	"The output voltage of LPS Channel 3."
	::= { lpsOutputVoltageEntry 4 }

	lpsOutputVoltageChannel4 OBJECT-TYPE
		SYNTAX INTEGER (0..65535)
		MAX-ACCESS read-only
		STATUS current
		DESCRIPTION	"The output voltage of LPS Channel 4."
	::= { lpsOutputVoltageEntry 5 }


	lpsOutputCurrentTable OBJECT-TYPE
		SYNTAX SEQUENCE OF LpsOutputCurrentEntry
		MAX-ACCESS not-accessible
		STATUS current
		DESCRIPTION	"A table containing the output current of the LPS channels."
	::= { dcPwrSysLpsTbl 5 }

	lpsOutputCurrentEntry OBJECT-TYPE
		SYNTAX LpsOutputCurrentEntry
		MAX-ACCESS not-accessible
		STATUS current
		DESCRIPTION	"An entry in the table containing the output voltage of the LPS channels."
		INDEX { lpsModuleIndex }
		::= { lpsOutputCurrentTable 1 }

	LpsOutputCurrentEntry
	::= SEQUENCE {
		lpsOutputCurrentEntryIndex	INTEGER,
		lpsOutputCurrentChannel1 	INTEGER,
		lpsOutputCurrentChannel2 	INTEGER,
		lpsOutputCurrentChannel3 	INTEGER,
		lpsOutputCurrentChannel4 	INTEGER
	}

    lpsOutputCurrentEntryIndex OBJECT-TYPE
		SYNTAX INTEGER (0..65535)
		MAX-ACCESS read-only
		STATUS current
		DESCRIPTION	"index"
	::= { lpsOutputCurrentEntry 1 }


	lpsOutputCurrentChannel1 OBJECT-TYPE
		SYNTAX INTEGER (0..65535)
		MAX-ACCESS read-only
		STATUS current
		DESCRIPTION	"The output current of LPS Channel 1."
	::= { lpsOutputCurrentEntry 2 }

	lpsOutputCurrentChannel2 OBJECT-TYPE
		SYNTAX INTEGER (0..65535)
		MAX-ACCESS read-only
		STATUS current
		DESCRIPTION	"The output current of LPS Channel 2."
	::= { lpsOutputCurrentEntry 3 }

	lpsOutputCurrentChannel3 OBJECT-TYPE
		SYNTAX INTEGER (0..65535)
		MAX-ACCESS read-only
		STATUS current
		DESCRIPTION	"The output current of LPS Channel 3."
	::= { lpsOutputCurrentEntry 4 }

	lpsOutputCurrentChannel4 OBJECT-TYPE
		SYNTAX INTEGER (0..65535)
		MAX-ACCESS read-only
		STATUS current
		DESCRIPTION	"The output current of LPS Channel 4."
	::= { lpsOutputCurrentEntry 5 }

	lpsChannelStatusFaultsTable OBJECT-TYPE
		SYNTAX SEQUENCE OF LpsChannelStatusFaultsEntry
		MAX-ACCESS not-accessible
		STATUS current
		DESCRIPTION	"A table containing the faults for each LPS channel."
	::= { dcPwrSysLpsTbl 6 }

	lpsChannelStatusFaultsEntry OBJECT-TYPE
		SYNTAX LpsChannelStatusFaultsEntry
		MAX-ACCESS not-accessible
		STATUS current
		DESCRIPTION	"An entry in the table containing the faults for each LPS channel."
		INDEX { lpsModuleIndex }
		::= { lpsChannelStatusFaultsTable 1 }

	LpsChannelStatusFaultsEntry
	::= SEQUENCE {
		lpsChannelStatusFaultsEntryIndex	INTEGER,
		lpsGfiChannel1					INTEGER,
		lpsFuseChannel1					INTEGER,
		lpsOvpChannel1					INTEGER,
		lpsOverCurrentChannel1			INTEGER,
		lpsLowOutputVoltageChannel1		INTEGER,
		lpsRemoteShutdownChannel1		INTEGER,

		lpsGfiChannel2					INTEGER,
		lpsFuseChannel2					INTEGER,
		lpsOvpChannel2					INTEGER,
		lpsOverCurrentChannel2			INTEGER,
		lpsLowOutputVoltageChannel2		INTEGER,
		lpsRemoteShutdownChannel2		INTEGER,

		lpsGfiChannel3					INTEGER,
		lpsFuseChannel3					INTEGER,
		lpsOvpChannel3					INTEGER,
		lpsOverCurrentChannel3			INTEGER,
		lpsLowOutputVoltageChannel3		INTEGER,
		lpsRemoteShutdownChannel3		INTEGER,

		lpsGfiChannel4					INTEGER,
		lpsFuseChannel4					INTEGER,
		lpsOvpChannel4					INTEGER,
		lpsOverCurrentChannel4			INTEGER,
		lpsLowOutputVoltageChannel4		INTEGER,
		lpsRemoteShutdownChannel4		INTEGER,

		lpsLowCurrent1  				INTEGER,
		lpsTransientOVP1				INTEGER,
		lpsTransientGFI1				INTEGER,
		lpsTransientVoutLow1			INTEGER,

		lpsLowCurrent2  				INTEGER,
		lpsTransientOVP2				INTEGER,
		lpsTransientGFI2				INTEGER,
		lpsTransientVoutLow2			INTEGER,

		lpsLowCurrent3  				INTEGER,
		lpsTransientOVP3				INTEGER,
		lpsTransientGFI3				INTEGER,
		lpsTransientVoutLow3			INTEGER,

		lpsLowCurrent4  				INTEGER,
		lpsTransientOVP4				INTEGER,
		lpsTransientGFI4				INTEGER,
		lpsTransientVoutLow4			INTEGER,

		lpsCurrentSensorShorted1        INTEGER,
		lpsCurrentSensorShorted2        INTEGER,
		lpsCurrentSensorShorted3        INTEGER,
		lpsCurrentSensorShorted4        INTEGER

	}

 	lpsChannelStatusFaultsEntryIndex OBJECT-TYPE
		SYNTAX INTEGER (0..65535)
		MAX-ACCESS read-only
		STATUS current
		DESCRIPTION	"index"
	::= { lpsChannelStatusFaultsEntry 1 }

	lpsGfiChannel1 OBJECT-TYPE
		SYNTAX INTEGER (0..1)
		MAX-ACCESS read-only
		STATUS current
		DESCRIPTION	"LPS Channel 1 has a GFI fault."
	::= { lpsChannelStatusFaultsEntry 2 }

	lpsFuseChannel1 OBJECT-TYPE
		SYNTAX INTEGER (0..1)
		MAX-ACCESS read-only
		STATUS current
		DESCRIPTION	"LPS Channel 1 has a fuse fault."
	::= { lpsChannelStatusFaultsEntry 3 }

	lpsOvpChannel1 OBJECT-TYPE
		SYNTAX INTEGER (0..1)
		MAX-ACCESS read-only
		STATUS current
		DESCRIPTION	"LPS Channel 1 has an OVP fault."
	::= { lpsChannelStatusFaultsEntry 4 }

	lpsOverCurrentChannel1 OBJECT-TYPE
		SYNTAX INTEGER (0..1)
		MAX-ACCESS read-only
		STATUS current
		DESCRIPTION	"LPS Channel 1 has a Over-Current (OCP) fault."
	::= { lpsChannelStatusFaultsEntry 5 }

	lpsLowOutputVoltageChannel1 OBJECT-TYPE
		SYNTAX INTEGER (0..1)
		MAX-ACCESS read-only
		STATUS current
		DESCRIPTION	"LPS Channel 1 has low output voltage."
	::= { lpsChannelStatusFaultsEntry 6 }

	lpsRemoteShutdownChannel1 OBJECT-TYPE
		SYNTAX INTEGER (0..1)
		MAX-ACCESS read-only
		STATUS current
		DESCRIPTION	"LPS Channel 1 has been remotely shut down."
	::= { lpsChannelStatusFaultsEntry 7 }

	lpsGfiChannel2 OBJECT-TYPE
		SYNTAX INTEGER (0..1)
		MAX-ACCESS read-only
		STATUS current
		DESCRIPTION	"LPS Channel 2 has a GFI fault."
	::= { lpsChannelStatusFaultsEntry 8 }

	lpsFuseChannel2 OBJECT-TYPE
		SYNTAX INTEGER (0..1)
		MAX-ACCESS read-only
		STATUS current
		DESCRIPTION	"LPS Channel 2 has a fuse fault."
	::= { lpsChannelStatusFaultsEntry 9 }

	lpsOvpChannel2 OBJECT-TYPE
		SYNTAX INTEGER (0..1)
		MAX-ACCESS read-only
		STATUS current
		DESCRIPTION	"LPS Channel 2 has an OVP fault."
	::= { lpsChannelStatusFaultsEntry 10 }

	lpsOverCurrentChannel2 OBJECT-TYPE
		SYNTAX INTEGER (0..1)
		MAX-ACCESS read-only
		STATUS current
		DESCRIPTION	"LPS Channel 2 has a Over-Current (OCP) fault."
	::= { lpsChannelStatusFaultsEntry 11 }

	lpsLowOutputVoltageChannel2 OBJECT-TYPE
		SYNTAX INTEGER (0..1)
		MAX-ACCESS read-only
		STATUS current
		DESCRIPTION	"LPS Channel 2 has low output voltage."
	::= { lpsChannelStatusFaultsEntry 12 }

	lpsRemoteShutdownChannel2 OBJECT-TYPE
		SYNTAX INTEGER (0..1)
		MAX-ACCESS read-only
		STATUS current
		DESCRIPTION	"LPS Channel 2 has been remotely shut down."
	::= { lpsChannelStatusFaultsEntry 13 }

	lpsGfiChannel3 OBJECT-TYPE
		SYNTAX INTEGER (0..1)
		MAX-ACCESS read-only
		STATUS current
		DESCRIPTION	"LPS Channel 3 has a GFI fault."
	::= { lpsChannelStatusFaultsEntry 14 }

	lpsFuseChannel3 OBJECT-TYPE
		SYNTAX INTEGER (0..1)
		MAX-ACCESS read-only
		STATUS current
		DESCRIPTION	"LPS Channel 3 has a fuse fault."
	::= { lpsChannelStatusFaultsEntry 15 }

	lpsOvpChannel3 OBJECT-TYPE
		SYNTAX INTEGER (0..1)
		MAX-ACCESS read-only
		STATUS current
		DESCRIPTION	"LPS Channel 3 has an OVP fault."
	::= { lpsChannelStatusFaultsEntry 16 }

	lpsOverCurrentChannel3 OBJECT-TYPE
		SYNTAX INTEGER (0..1)
		MAX-ACCESS read-only
		STATUS current
		DESCRIPTION	"LPS Channel 3 has a Over-Current (OCP) fault."
	::= { lpsChannelStatusFaultsEntry 17 }

	lpsLowOutputVoltageChannel3 OBJECT-TYPE
		SYNTAX INTEGER (0..1)
		MAX-ACCESS read-only
		STATUS current
		DESCRIPTION	"LPS Channel 3 has low output voltage."
	::= { lpsChannelStatusFaultsEntry 18 }

	lpsRemoteShutdownChannel3 OBJECT-TYPE
		SYNTAX INTEGER (0..1)
		MAX-ACCESS read-only
		STATUS current
		DESCRIPTION	"LPS Channel 3 has been remotely shut down."
	::= { lpsChannelStatusFaultsEntry 19 }

	lpsGfiChannel4 OBJECT-TYPE
		SYNTAX INTEGER (0..1)
		MAX-ACCESS read-only
		STATUS current
		DESCRIPTION	"LPS Channel 4 has a GFI fault."
	::= { lpsChannelStatusFaultsEntry 20 }

	lpsFuseChannel4 OBJECT-TYPE
		SYNTAX INTEGER (0..1)
		MAX-ACCESS read-only
		STATUS current
		DESCRIPTION	"LPS Channel 4 has a fuse fault."
	::= { lpsChannelStatusFaultsEntry 21 }

	lpsOvpChannel4 OBJECT-TYPE
		SYNTAX INTEGER (0..1)
		MAX-ACCESS read-only
		STATUS current
		DESCRIPTION	"LPS Channel 4 has an OVP fault."
	::= { lpsChannelStatusFaultsEntry 22 }

	lpsOverCurrentChannel4 OBJECT-TYPE
		SYNTAX INTEGER (0..1)
		MAX-ACCESS read-only
		STATUS current
		DESCRIPTION	"LPS Channel 4 has a Over-Current (OCP) fault."
	::= { lpsChannelStatusFaultsEntry 23 }

	lpsLowOutputVoltageChannel4 OBJECT-TYPE
		SYNTAX INTEGER (0..1)
		MAX-ACCESS read-only
		STATUS current
		DESCRIPTION	"LPS Channel 4 has low output voltage."
	::= { lpsChannelStatusFaultsEntry 24 }

	lpsRemoteShutdownChannel4 OBJECT-TYPE
		SYNTAX INTEGER (0..1)
		MAX-ACCESS read-only
		STATUS current
		DESCRIPTION	"LPS Channel 4 has been remotely shut down."
	::= { lpsChannelStatusFaultsEntry 25 }

	lpsLowCurrent1 OBJECT-TYPE
		SYNTAX INTEGER (0..1)
		MAX-ACCESS read-only
		STATUS current
		DESCRIPTION	"LPS Channel 1 has a low current fault."
	::= { lpsChannelStatusFaultsEntry 26 }

	lpsTransientOVP1 OBJECT-TYPE
		SYNTAX INTEGER (0..1)
		MAX-ACCESS read-only
		STATUS current
		DESCRIPTION	"LPS Channel 1 had a transient OVP event."
	::= { lpsChannelStatusFaultsEntry 27 }

	lpsTransientGFI1 OBJECT-TYPE
		SYNTAX INTEGER (0..1)
		MAX-ACCESS read-only
		STATUS current
		DESCRIPTION	"LPS Channel 1 had a transient GFI event."
	::= { lpsChannelStatusFaultsEntry 28 }

	lpsTransientVoutLow1 OBJECT-TYPE
		SYNTAX INTEGER (0..1)
		MAX-ACCESS read-only
		STATUS current
		DESCRIPTION	"LPS Channel 1 had a transient Vout Low event."
	::= { lpsChannelStatusFaultsEntry 29 }

	lpsLowCurrent2 OBJECT-TYPE
		SYNTAX INTEGER (0..1)
		MAX-ACCESS read-only
		STATUS current
		DESCRIPTION	"LPS Channel 2 has a low current fault."
	::= { lpsChannelStatusFaultsEntry 30 }

	lpsTransientOVP2 OBJECT-TYPE
		SYNTAX INTEGER (0..1)
		MAX-ACCESS read-only
		STATUS current
		DESCRIPTION	"LPS Channel 2 had a transient OVP event."
	::= { lpsChannelStatusFaultsEntry 31 }

	lpsTransientGFI2 OBJECT-TYPE
		SYNTAX INTEGER (0..1)
		MAX-ACCESS read-only
		STATUS current
		DESCRIPTION	"LPS Channel 2 had a transient GFI event."
	::= { lpsChannelStatusFaultsEntry 32 }

	lpsTransientVoutLow2 OBJECT-TYPE
		SYNTAX INTEGER (0..1)
		MAX-ACCESS read-only
		STATUS current
		DESCRIPTION	"LPS Channel 2 had a transient Vout Low event."
	::= { lpsChannelStatusFaultsEntry 33 }

	lpsLowCurrent3 OBJECT-TYPE
		SYNTAX INTEGER (0..1)
		MAX-ACCESS read-only
		STATUS current
		DESCRIPTION	"LPS Channel 3 has a low current fault."
	::= { lpsChannelStatusFaultsEntry 34 }

	lpsTransientOVP3 OBJECT-TYPE
		SYNTAX INTEGER (0..1)
		MAX-ACCESS read-only
		STATUS current
		DESCRIPTION	"LPS Channel 3 had a transient OVP event."
	::= { lpsChannelStatusFaultsEntry 35 }

	lpsTransientGFI3 OBJECT-TYPE
		SYNTAX INTEGER (0..1)
		MAX-ACCESS read-only
		STATUS current
		DESCRIPTION	"LPS Channel 3 had a transient GFI event."
	::= { lpsChannelStatusFaultsEntry 36 }

	lpsTransientVoutLow3 OBJECT-TYPE
		SYNTAX INTEGER (0..1)
		MAX-ACCESS read-only
		STATUS current
		DESCRIPTION	"LPS Channel 3 had a transient Vout Low event."
	::= { lpsChannelStatusFaultsEntry 37 }

	lpsLowCurrent4 OBJECT-TYPE
		SYNTAX INTEGER (0..1)
		MAX-ACCESS read-only
		STATUS current
		DESCRIPTION	"LPS Channel 4 has a low current fault."
	::= { lpsChannelStatusFaultsEntry 38 }

	lpsTransientOVP4 OBJECT-TYPE
		SYNTAX INTEGER (0..1)
		MAX-ACCESS read-only
		STATUS current
		DESCRIPTION	"LPS Channel 4 had a transient OVP event."
	::= { lpsChannelStatusFaultsEntry 39 }

	lpsTransientGFI4 OBJECT-TYPE
		SYNTAX INTEGER (0..1)
		MAX-ACCESS read-only
		STATUS current
		DESCRIPTION	"LPS Channel 4 had a transient GFI event."
	::= { lpsChannelStatusFaultsEntry 40 }

	lpsTransientVoutLow4 OBJECT-TYPE
		SYNTAX INTEGER (0..1)
		MAX-ACCESS read-only
		STATUS current
		DESCRIPTION	"LPS Channel 4 had a transient Vout Low event."
	::= { lpsChannelStatusFaultsEntry 41 }

	lpsCurrentSensorShorted1 OBJECT-TYPE
		SYNTAX INTEGER (0..1)
		MAX-ACCESS read-only
		STATUS current
		DESCRIPTION	"LPS Channel 1 had a transient Current Sensor Shorted event."
	::= { lpsChannelStatusFaultsEntry 42 }

	lpsCurrentSensorShorted2 OBJECT-TYPE
		SYNTAX INTEGER (0..1)
		MAX-ACCESS read-only
		STATUS current
		DESCRIPTION	"LPS Channel 2 had a transient Current Sensor Shorted event."
	::= { lpsChannelStatusFaultsEntry 43 }

	lpsCurrentSensorShorted3 OBJECT-TYPE
		SYNTAX INTEGER (0..1)
		MAX-ACCESS read-only
		STATUS current
		DESCRIPTION	"LPS Channel 3 had a transient Current Sensor Shorted event."
	::= { lpsChannelStatusFaultsEntry 44 }

	lpsCurrentSensorShorted4 OBJECT-TYPE
		SYNTAX INTEGER (0..1)
		MAX-ACCESS read-only
		STATUS current
		DESCRIPTION	"LPS Channel 4 had a transient Current Sensor Shorted event."
	::= { lpsChannelStatusFaultsEntry 45 }

	lpsChannelInfoTable OBJECT-TYPE
		SYNTAX SEQUENCE OF LpsChannelInfoEntry
		MAX-ACCESS not-accessible
		STATUS current
		DESCRIPTION	"A table containing extra info about the LPS channels."
	::= { dcPwrSysLpsTbl 7 }

	lpsChannelInfoEntry OBJECT-TYPE
		SYNTAX LpsChannelInfoEntry
		MAX-ACCESS not-accessible
		STATUS current
		DESCRIPTION	"An entry in the table containing extra info about the LPS channels."
		INDEX { lpsModuleIndex }
		::= { lpsChannelInfoTable 1 }

	LpsChannelInfoEntry
	::= SEQUENCE {
		lpsChannelInfoEntryIndex	INTEGER,
		lpsGroupChannel1 		DisplayString,
		lpsCustomText1Channel1 	DisplayString,
		lpsCustomText2Channel1 	DisplayString,
		lpsGroupChannel2 		DisplayString,
		lpsCustomText1Channel2 	DisplayString,
		lpsCustomText2Channel2 	DisplayString,
		lpsGroupChannel3 		DisplayString,
		lpsCustomText1Channel3 	DisplayString,
		lpsCustomText2Channel3 	DisplayString,
		lpsGroupChannel4 		DisplayString,
		lpsCustomText1Channel4 	DisplayString,
		lpsCustomText2Channel4 	DisplayString
	}

	lpsChannelInfoEntryIndex OBJECT-TYPE
		SYNTAX INTEGER (0..65535)
		MAX-ACCESS read-only
		STATUS current
		DESCRIPTION	"index"
	::= { lpsChannelInfoEntry 1 }

	lpsGroupChannel1 OBJECT-TYPE
		SYNTAX DisplayString (SIZE(0..25))
		MAX-ACCESS read-only
		STATUS current
		DESCRIPTION	"The assigned group of LPS Channel 1."
	::= { lpsChannelInfoEntry 2 }

	lpsCustomText1Channel1 OBJECT-TYPE
		SYNTAX DisplayString (SIZE(0..50))
		MAX-ACCESS read-only
		STATUS current
		DESCRIPTION	"Custom Text 1 for LPS Channel 1."
	::= { lpsChannelInfoEntry 3 }

	lpsCustomText2Channel1 OBJECT-TYPE
		SYNTAX DisplayString (SIZE(0..50))
		MAX-ACCESS read-only
		STATUS current
		DESCRIPTION	"Custom Text 2 for LPS Channel 1."
	::= { lpsChannelInfoEntry 4 }

		lpsGroupChannel2 OBJECT-TYPE
		SYNTAX DisplayString (SIZE(0..25))
		MAX-ACCESS read-only
		STATUS current
		DESCRIPTION	"The assigned group of LPS Channel 2."
	::= { lpsChannelInfoEntry 5 }

	lpsCustomText1Channel2 OBJECT-TYPE
		SYNTAX DisplayString (SIZE(0..50))
		MAX-ACCESS read-only
		STATUS current
		DESCRIPTION	"Custom Text 1 for LPS Channel 2."
	::= { lpsChannelInfoEntry 6 }

	lpsCustomText2Channel2 OBJECT-TYPE
		SYNTAX DisplayString (SIZE(0..50))
		MAX-ACCESS read-only
		STATUS current
		DESCRIPTION	"Custom Text 2 for LPS Channel 2."
	::= { lpsChannelInfoEntry 7 }

		lpsGroupChannel3 OBJECT-TYPE
		SYNTAX DisplayString (SIZE(0..25))
		MAX-ACCESS read-only
		STATUS current
		DESCRIPTION	"The assigned group of LPS Channel 3."
	::= { lpsChannelInfoEntry 8 }

	lpsCustomText1Channel3 OBJECT-TYPE
		SYNTAX DisplayString (SIZE(0..50))
		MAX-ACCESS read-only
		STATUS current
		DESCRIPTION	"Custom Text 1 for LPS Channel 3."
	::= { lpsChannelInfoEntry 9 }

	lpsCustomText2Channel3 OBJECT-TYPE
		SYNTAX DisplayString (SIZE(0..50))
		MAX-ACCESS read-only
		STATUS current
		DESCRIPTION	"Custom Text 2 for LPS Channel 3."
	::= { lpsChannelInfoEntry 10 }

		lpsGroupChannel4 OBJECT-TYPE
		SYNTAX DisplayString (SIZE(0..25))
		MAX-ACCESS read-only
		STATUS current
		DESCRIPTION	"The assigned group of LPS Channel 4."
	::= { lpsChannelInfoEntry 11 }

	lpsCustomText1Channel4 OBJECT-TYPE
		SYNTAX DisplayString (SIZE(0..50))
		MAX-ACCESS read-only
		STATUS current
		DESCRIPTION	"Custom Text 1 for LPS Channel 4."
	::= { lpsChannelInfoEntry 12 }

	lpsCustomText2Channel4 OBJECT-TYPE
		SYNTAX DisplayString (SIZE(0..50))
		MAX-ACCESS read-only
		STATUS current
		DESCRIPTION	"Custom Text 2 for LPS Channel 4."
	::= { lpsChannelInfoEntry 13 }

 	--==========================================================================
	-- The OBJECT IDENTIFIERs for the traps must be defined in this manner to
	-- satisfy the NetSight MIB compiler; in particular, nodes cannot be defined
	-- concatenated in a single line, but must be defined explicitly node by node
	-- (hence, the dcPwrSysDevice.dcPwrSysTraps.dcPwrSysTrap definition)
	-- In addition, forward references to extra system variables are needed for
	-- dcPwrSysTrap by CastleRock SNMPc for event filter and match features.
	--==========================================================================
	dcPwrSysTrap		OBJECT IDENTIFIER ::= { dcPwrSysTraps 0 }

	--==========================================================================
	-- Start of Traps
	--==========================================================================

	dcPwrSysAlarmActiveTrap NOTIFICATION-TYPE
		OBJECTS {
			dcPwrSysRectAlrmStringValue,
			dcPwrSysRectAlrmIndex,
			dcPwrSysRectAlrmSeverity,
			dcPwrSysSiteName,
			dcPwrSysTimeStamp,
			dcPwrSysAlarmTriggerValue
		}
    	STATUS  current
    	DESCRIPTION "A trap issued when one of the alarms on the became active."
	::= { dcPwrSysTrap 1 }

	dcPwrSysAlarmClearedTrap NOTIFICATION-TYPE
		OBJECTS {
			dcPwrSysRectAlrmStringValue,
			dcPwrSysRectAlrmIndex,
			dcPwrSysRectAlrmSeverity,
			dcPwrSysSiteName,
			dcPwrSysAlarmTriggerValue
		}
    	STATUS  current
    	DESCRIPTION "A trap issued when one of the active alarms on the is cleared."
	::= { dcPwrSysTrap 2 }

	dcPwrSysRelayTrap NOTIFICATION-TYPE
		OBJECTS {
			dcPwrSysRelayIntegerValue,
			dcPwrSysRelayStringValue,
			dcPwrSysRelayIndex,
			dcPwrSysRelaySeverity,
			dcPwrSysSiteName
		}
    	STATUS  current
    	DESCRIPTION "A trap issued from a change in state in one of the relays on the DC power system controller."
	::= { dcPwrSysTrap 3 }

	dcPwrSysComOKTrap NOTIFICATION-TYPE
		OBJECTS {
			dcPwrSysSiteName
		}
		STATUS  current
		DESCRIPTION "A trap to indicate that communications with a DC power system controller has been established."
	::= { dcPwrSysTrap 4 }

	dcPwrSysComErrTrap NOTIFICATION-TYPE
		OBJECTS {
			dcPwrSysSiteName
		}
		STATUS  current
		DESCRIPTION "A trap to indicate that communications with a DC power system controller has been lost."
	::= { dcPwrSysTrap 5 }

	dcPwrSysAgentStartupTrap NOTIFICATION-TYPE
		OBJECTS {
			dcPwrSysSiteName
		}
		STATUS  current
		DESCRIPTION "A trap to indicate that the agent software has started up."
	::= { dcPwrSysTrap 6 }

	dcPwrSysAgentShutdownTrap NOTIFICATION-TYPE
		OBJECTS {
			dcPwrSysSiteName
		}
		STATUS  current
		DESCRIPTION "A trap to indicate that the agent software has shutdown."
	::= { dcPwrSysTrap 7 }

	dcPwrSysMajorAlarmActiveTrap NOTIFICATION-TYPE
		OBJECTS {
			dcPwrSysRectAlrmStringValue,
			dcPwrSysRectAlrmIndex,
			dcPwrSysRectAlrmSeverity,
			dcPwrSysSiteName
		}
    	STATUS  current
    	DESCRIPTION "A trap issued as a summary of DC power system status.  It is sent when the system goes into in Major Alarm"
	::= { dcPwrSysTrap 8 }

	dcPwrSysMajorAlarmClearedTrap NOTIFICATION-TYPE
		OBJECTS {
			dcPwrSysRectAlrmStringValue,
			dcPwrSysRectAlrmIndex,
			dcPwrSysRectAlrmSeverity,
			dcPwrSysSiteName
		}
    	STATUS  current
    	DESCRIPTION "A trap issued as a summary of DC power system status.  It is sent when the system comes out of Major Alarm"
	::= { dcPwrSysTrap 9 }

	dcPwrSysMinorAlarmActiveTrap NOTIFICATION-TYPE
		OBJECTS {
			dcPwrSysRectAlrmStringValue,
			dcPwrSysRectAlrmIndex,
			dcPwrSysRectAlrmSeverity,
			dcPwrSysSiteName
		}
    	STATUS  current
    	DESCRIPTION "A trap issued as a summary of DC power system status.  It is sent when the system goes into in Minor Alarm"
	::= { dcPwrSysTrap 10 }

	dcPwrSysMinorAlarmClearedTrap NOTIFICATION-TYPE
		OBJECTS {
			dcPwrSysRectAlrmStringValue,
			dcPwrSysRectAlrmIndex,
			dcPwrSysRectAlrmSeverity,
			dcPwrSysSiteName
		}
    	STATUS  current
    	DESCRIPTION "A trap issued as a summary of DC power system status.  It is sent when the system comes out of Minor Alarm"
	::= { dcPwrSysTrap 11 }


	--==========================================================================
	-- Start of External Controls
	--==========================================================================

	dcPwrSysResyncAlarms OBJECT-TYPE
		SYNTAX INTEGER (0..65535)
		MAX-ACCESS read-write
		STATUS current
		DESCRIPTION	"Send/Resend all active alarms that were previously sent through SNMP notification."
	::= { dcPwrExternalControls  1 }

	--==========================================================================
	-- Alarm Trigger
	--==========================================================================
	dcPwrSysAlarmTriggerValue OBJECT-TYPE
		SYNTAX INTEGER (0..65535)
		MAX-ACCESS read-only
		STATUS current
		DESCRIPTION	""
	::= { dcPwrVarbindNameReference  1 }

	--==========================================================================
	-- Time stamp
	--==========================================================================
	dcPwrSysTimeStamp OBJECT-TYPE
		SYNTAX DisplayString (SIZE(0..255))
		MAX-ACCESS read-only
		STATUS current
		DESCRIPTION	""
	::= { dcPwrVarbindNameReference  2 }

END
