ALPHA-INVERTER-SYS-MIB DEFINITIONS ::= BEGIN

	--==========================================================================
	--
	-- Alpha Technologies Ltd.
	-- Copyright 2014
	--
	--==========================================================================

	IMPORTS
		MODULE-IDENTITY, OBJECT-TYPE
			FROM SNMPv2-SMI
		ScaledNumber, simple
			FROM ALPHA-RESOURCE-MIB
	   	MODULE-COMPLIANCE, OBJECT-GROUP
      	 	FROM SNMPv2-CONF;

	inverterSystem MODULE-IDENTITY
		LAST-UPDATED "201602290000Z"
		ORGANIZATION "Alpha Technologies Ltd."
		CONTACT-INFO
		  	 "Alpha Technologies Ltd.
			  7700 Riverfront Gate
			  Burnaby, BC  V5J 5M4
			  Canada

			  Tel: 1-604-436-5900
			  Fax: 1-604-436-1233"
		DESCRIPTION
		  	"
		  	This MIB provides a flat list of data points available from the Cordex HP controller
		  	to present information of one Inverter System.
		  	"

		REVISION    "201602290000Z"  -- February 29, 2016
		DESCRIPTION
			"General revision."

	::= { simple 3 }

    --==========================================================================
    -- Subfolders for Phase, AC Input and DC Input groups.
    --==========================================================================

    phaseGroup 			OBJECT IDENTIFIER ::= { inverterSystem 80 }
    acInputGroup		OBJECT IDENTIFIER ::= { inverterSystem 81 }
    dcInputGroup		OBJECT IDENTIFIER ::= { inverterSystem 82 }


 	-- Inverter System data points

	invTotalAcOutputPowerVa OBJECT-TYPE
		SYNTAX      ScaledNumber
		MAX-ACCESS  read-only
		STATUS      current
		DESCRIPTION
			"The total output power summed from all the phases (VA)."
       ::= { inverterSystem 1 }

   	invSysAverageLoadingOfInstalledPowerVa OBJECT-TYPE
    	SYNTAX      ScaledNumber
       	MAX-ACCESS  read-only
       	STATUS      current
       	DESCRIPTION
        	"The average output loading of all phases (% VA). "
       	::= { inverterSystem 2 }

	invSysAverageDcInputToOutputPowerRatio OBJECT-TYPE
		SYNTAX      ScaledNumber
		MAX-ACCESS  read-only
		STATUS      current
		DESCRIPTION
            "The percentage of the output that is taken from the DC input (%)."
		::= { inverterSystem 3 }

	invSysSystemMode OBJECT-TYPE
		SYNTAX      ScaledNumber
		MAX-ACCESS  read-only
		STATUS      current
		DESCRIPTION
            "The mode of the system. See manual for decoding the number."
		::= { inverterSystem 4 }

	invSysPhase1OutputPowerVa OBJECT-TYPE
		SYNTAX      ScaledNumber
		MAX-ACCESS  read-only
		STATUS      current
		DESCRIPTION
            "The total output power from the phase 1 (VA)."
		::= { inverterSystem 5 }

	invSysPhase2OutputPowerVa OBJECT-TYPE
		SYNTAX      ScaledNumber
		MAX-ACCESS  read-only
		STATUS      current
		DESCRIPTION
            "The total output power from phase 2 (VA)."
		::= { inverterSystem 6 }

	invSysPhase3OutputPowerVa OBJECT-TYPE
		SYNTAX      ScaledNumber
		MAX-ACCESS  read-only
		STATUS      current
		DESCRIPTION
            "The total output power from the phase 3 (VA)."
		::= { inverterSystem 7 }

	invSysAverageOutputVoltageMeasured OBJECT-TYPE
		SYNTAX      ScaledNumber
		MAX-ACCESS  read-only
		STATUS      current
		DESCRIPTION
            "The average output voltage of all the phases (V)."
		::= { inverterSystem 8 }

	invSysEnabledDisconnects OBJECT-TYPE
		SYNTAX      ScaledNumber
		MAX-ACCESS  read-only
		STATUS      current
		DESCRIPTION
            "The number of disconnects that are enabled."
		::= { inverterSystem 9 }

	invSysActivatedDisconnects OBJECT-TYPE
		SYNTAX      ScaledNumber
		MAX-ACCESS  read-only
		STATUS      current
		DESCRIPTION
            "The number of disconnects that are active."
		::= { inverterSystem 10 }

	invSysTotalDCInputCurrent OBJECT-TYPE
		SYNTAX      ScaledNumber
		MAX-ACCESS  read-only
		STATUS      current
		DESCRIPTION
            "Total DC input current for the inverter system (A)."
        ::= { inverterSystem 11 }

   invSysAverageDcInputVoltage OBJECT-TYPE
		SYNTAX      ScaledNumber
		MAX-ACCESS  read-only
		STATUS      current
		DESCRIPTION
			"Average DC input voltage reading for the inverter system (V)."
		::= { inverterSystem 12 }

   invSysTotalDcInputPower OBJECT-TYPE
       SYNTAX      ScaledNumber
       MAX-ACCESS  read-only
       STATUS      current
       DESCRIPTION
               "Total DC input power reading for the inverter system (W)."
       ::= { inverterSystem 13 }

   invSysSystemOnBypass OBJECT-TYPE
		SYNTAX      ScaledNumber
		MAX-ACCESS  read-only
		STATUS      current
		DESCRIPTION
			"True when the bypass switch is on.  The AC input from the grid is fed to the AC load directly."
		::= { inverterSystem 14 }

   invSysTotalAcInputPowerVa OBJECT-TYPE
        SYNTAX      ScaledNumber
        MAX-ACCESS  read-only
        STATUS      current
        DESCRIPTION
                "Total AC input power reading of the Inverter System (VA)."
        ::= { inverterSystem 18 }


	-- Phase Group

    invSysAcPhaseCount OBJECT-TYPE
		SYNTAX Integer32
		MAX-ACCESS read-only
		STATUS current
		DESCRIPTION
		"
		"
		::= { phaseGroup 1 }

    invSysAcPhaseTable 	OBJECT-TYPE
   		SYNTAX      SEQUENCE OF InvSysAcPhaseEntry
   		MAX-ACCESS  not-accessible
   		STATUS      current
   		DESCRIPTION
       	"
       	"
		::= { phaseGroup 2 }

	invSysAcPhaseEntry	OBJECT-TYPE
		SYNTAX      InvSysAcPhaseEntry
 		MAX-ACCESS  not-accessible
   		STATUS      current
   		DESCRIPTION
       	"
       	"
   		INDEX	{ invSysAcPhaseCount }
   		::= { invSysAcPhaseTable 1 }

	InvSysAcPhaseEntry ::= SEQUENCE {
		invSysAcPhaseAcOutputPowerVa     					ScaledNumber,
		invSysAcPhaseOutputVoltageMeasured	                ScaledNumber,
		invSysAcPhaseOutputCurrent                          ScaledNumber,
		invSysAcPhaseFrequency                              ScaledNumber,
		invSysAcPhaseLoadingOfInstalledPowerVa              ScaledNumber,
		invSysAcPhaseNumberOfModulesOn                      ScaledNumber,
		invSysAcPhaseLoadingOfInstalledPowerWatts           ScaledNumber,
		invSysAcPhaseDcInputToOutputPowerRatioMeasured      ScaledNumber,
		invSysAcPhaseAcInputPowerWatts                      ScaledNumber,
		invSysAcPhaseAcInputPowerVa                         ScaledNumber,
		invSysAcPhaseAcOutputPowerWatts                     ScaledNumber,
		invSysAcPhaseDCInputPowerWatts                      ScaledNumber,
		invSysAcPhaseNumberOfRedundantModulesMeasured       ScaledNumber,
		invSysAcPhaseNumberOfModulesDetected                ScaledNumber,
		invSysAcPhaseNumberOfModulesOff                     ScaledNumber,
		invSysAcPhaseNumberOfModulesFailed                  ScaledNumber
	   }

	invSysAcPhaseAcOutputPowerVa OBJECT-TYPE
		SYNTAX      ScaledNumber
		MAX-ACCESS  read-only
		STATUS      current
		DESCRIPTION
			"The power of the AC output (VA)."
		::= { invSysAcPhaseEntry 1 }

	invSysAcPhaseOutputVoltageMeasured OBJECT-TYPE
		SYNTAX      ScaledNumber
		MAX-ACCESS  read-only
		STATUS      current
		DESCRIPTION
			"The output voltage of the phase or inverter (V)."
		::= { invSysAcPhaseEntry 2 }

	invSysAcPhaseOutputCurrent OBJECT-TYPE
		SYNTAX      ScaledNumber
		MAX-ACCESS  read-only
		STATUS      current
		DESCRIPTION
			"The output current of the phase or inverter (A)."
		::= { invSysAcPhaseEntry 3 }

	invSysAcPhaseFrequency OBJECT-TYPE
		SYNTAX      ScaledNumber
		MAX-ACCESS  read-only
		STATUS      current
		DESCRIPTION
			"Frequency to which the inverters will lock (Hz)."
		::= { invSysAcPhaseEntry 4 }

	invSysAcPhaseLoadingOfInstalledPowerVa OBJECT-TYPE
		SYNTAX      ScaledNumber
		MAX-ACCESS  read-only
		STATUS      current
		DESCRIPTION
			"The ratio of output load to installed power (%VA)."
		::= { invSysAcPhaseEntry 5 }

	invSysAcPhaseNumberOfModulesOn OBJECT-TYPE
		SYNTAX      ScaledNumber
		MAX-ACCESS  read-only
		STATUS      current
		DESCRIPTION
			"The number of inverters that are On and can deliver power."
		::= { invSysAcPhaseEntry 6 }

	invSysAcPhaseLoadingOfInstalledPowerWatts OBJECT-TYPE
		SYNTAX      ScaledNumber
		MAX-ACCESS  read-only
		STATUS      current
		DESCRIPTION
			"The ratio of output load to installed power (% W)."
		::= { invSysAcPhaseEntry 7 }

	invSysAcPhaseDcInputToOutputPowerRatioMeasured OBJECT-TYPE
		SYNTAX      ScaledNumber
		MAX-ACCESS  read-only
		STATUS      current
		DESCRIPTION
			"The measured percentage of DC input power to output power(%). Under light or no load this value will not computed accurately."
		::= { invSysAcPhaseEntry 8 }

	invSysAcPhaseAcInputPowerWatts OBJECT-TYPE
		SYNTAX      ScaledNumber
		MAX-ACCESS  read-only
		STATUS      current
		DESCRIPTION
			"The power drawn by the AC input (W)."
		::= { invSysAcPhaseEntry 9 }

	invSysAcPhaseAcInputPowerVa OBJECT-TYPE
		SYNTAX      ScaledNumber
		MAX-ACCESS  read-only
		STATUS      current
		DESCRIPTION
			"The power drawn by the AC input (VA)."
		::= { invSysAcPhaseEntry 10 }

	invSysAcPhaseAcOutputPowerWatts OBJECT-TYPE
		SYNTAX      ScaledNumber
		MAX-ACCESS  read-only
		STATUS      current
		DESCRIPTION
			"The power of the AC output (W)."
		::= { invSysAcPhaseEntry 11 }

	invSysAcPhaseDCInputPowerWatts OBJECT-TYPE
		SYNTAX      ScaledNumber
		MAX-ACCESS  read-only
		STATUS      current
		DESCRIPTION
			"The power drawn by the DC input (W)."
		::= { invSysAcPhaseEntry 12 }

	invSysAcPhaseNumberOfRedundantModulesMeasured OBJECT-TYPE
		SYNTAX      ScaledNumber
		MAX-ACCESS  read-only
		STATUS      current
		DESCRIPTION
			"Number of inverters currently unneeded by the load."
		::= { invSysAcPhaseEntry 13 }

	invSysAcPhaseNumberOfModulesDetected OBJECT-TYPE
		SYNTAX      ScaledNumber
		MAX-ACCESS  read-only
		STATUS      current
		DESCRIPTION
			"The number of inverters assigned to this phase that the T2S has detected."
		::= { invSysAcPhaseEntry 14 }

	invSysAcPhaseNumberOfModulesOff OBJECT-TYPE
		SYNTAX      ScaledNumber
		MAX-ACCESS  read-only
		STATUS      current
		DESCRIPTION
			"The number of inverters that are manually turned off."
		::= { invSysAcPhaseEntry 15 }

	invSysAcPhaseNumberOfModulesFailed OBJECT-TYPE
		SYNTAX      ScaledNumber
		MAX-ACCESS  read-only
		STATUS      current
		DESCRIPTION
			"The number of inverters that have failed and cannot deliver power."
		::= { invSysAcPhaseEntry 16 }


	-- AC Input Group

    invSysAcInputCount OBJECT-TYPE
		SYNTAX Integer32
		MAX-ACCESS read-only
		STATUS current
		DESCRIPTION
		"
		"
		::= { acInputGroup 1 }

    invSysAcInputTable 	OBJECT-TYPE
   		SYNTAX      SEQUENCE OF InvSysAcInputEntry
   		MAX-ACCESS  not-accessible
   		STATUS      current
   		DESCRIPTION
       	"
       	"
		::= { acInputGroup 2 }

	invSysAcInputEntry	OBJECT-TYPE
		SYNTAX      InvSysAcInputEntry
 		MAX-ACCESS  not-accessible
   		STATUS      current
   		DESCRIPTION
       	"
       	"
   		INDEX	{ invSysAcInputCount }
   		::= { invSysAcInputTable 1 }

	InvSysAcInputEntry ::= SEQUENCE {
		invSysAcInputInputVoltage     			ScaledNumber,
	    invSysAcInputInputCurrent      			ScaledNumber,
	    invSysAcInputFrequency     				ScaledNumber,
	    invSysAcInputAcInputPowerVa     		ScaledNumber,
	    invSysAcInputNumberOfModulesOn     		ScaledNumber,
	    invSysAcInputAcInputPowerWatts       	ScaledNumber,
	    invSysAcInputNumberOfModulesDetected    ScaledNumber,
	    invSysAcInputNumberOfModulesOff     	ScaledNumber,
	    invSysAcInputNumberOfModulesFailed      ScaledNumber
	    }

	invSysAcInputInputVoltage OBJECT-TYPE
   		SYNTAX      ScaledNumber
		MAX-ACCESS  read-only
		STATUS      current
		DESCRIPTION
			"The input voltage of the inverter or group (V)."
		::= { invSysAcInputEntry 1 }

	invSysAcInputInputCurrent  OBJECT-TYPE
   		SYNTAX      ScaledNumber
		MAX-ACCESS  read-only
		STATUS      current
		DESCRIPTION
			"The input current of the inverter or group (A)."
		::= { invSysAcInputEntry 2 }

	invSysAcInputFrequency OBJECT-TYPE
   		SYNTAX      ScaledNumber
		MAX-ACCESS  read-only
		STATUS      current
		DESCRIPTION
			"The frequency of the input voltage and current of the inverter or group (Hz)."
		::= { invSysAcInputEntry 3 }

	invSysAcInputAcInputPowerVa OBJECT-TYPE
   		SYNTAX      ScaledNumber
		MAX-ACCESS  read-only
		STATUS      current
		DESCRIPTION
			"The power drawn by the AC input (VA)."
		::= { invSysAcInputEntry 4 }

	invSysAcInputNumberOfModulesOn OBJECT-TYPE
   		SYNTAX      ScaledNumber
		MAX-ACCESS  read-only
		STATUS      current
		DESCRIPTION
			"The number of inverters that are On and can deliver power."
		::= { invSysAcInputEntry 5 }

	invSysAcInputAcInputPowerWatts OBJECT-TYPE
   		SYNTAX      ScaledNumber
		MAX-ACCESS  read-only
		STATUS      current
		DESCRIPTION
			"The power drawn by the AC input (W)."
		::= { invSysAcInputEntry 6 }

	invSysAcInputNumberOfModulesDetected OBJECT-TYPE
   		SYNTAX      ScaledNumber
		MAX-ACCESS  read-only
		STATUS      current
		DESCRIPTION
			"The number of inverters assigned to this phase that the T2S has detected."
		::= { invSysAcInputEntry 7 }

	invSysAcInputNumberOfModulesOff OBJECT-TYPE
   		SYNTAX      ScaledNumber
		MAX-ACCESS  read-only
		STATUS      current
		DESCRIPTION
			"The number of inverters that are manually turned off."
		::= { invSysAcInputEntry 8 }

	invSysAcInputNumberOfModulesFailed OBJECT-TYPE
   		SYNTAX      ScaledNumber
		MAX-ACCESS  read-only
		STATUS      current
		DESCRIPTION
			"The number of inverters that have failed and cannot deliver power."
		::= { invSysAcInputEntry 9 }


	-- DC Input Group

    invSysDcInputCount OBJECT-TYPE
		SYNTAX Integer32
		MAX-ACCESS read-only
		STATUS current
		DESCRIPTION
		"
		"
		::= { dcInputGroup 1 }

    invSysDcInputTable 	OBJECT-TYPE
   		SYNTAX      SEQUENCE OF InvSysDcInputEntry
   		MAX-ACCESS  not-accessible
   		STATUS      current
   		DESCRIPTION
       	"
       	"
		::= { dcInputGroup 2 }

	invSysDcInputEntry	OBJECT-TYPE
		SYNTAX      InvSysDcInputEntry
 		MAX-ACCESS  not-accessible
   		STATUS      current
   		DESCRIPTION
       	"
       	"
   		INDEX	{ invSysDcInputCount }
   		::= { invSysDcInputTable 1 }

	InvSysDcInputEntry ::= SEQUENCE {
        invSysDcInputInputVoltage              	ScaledNumber,
        invSysDcInputInputCurrent              	ScaledNumber,
        invSysDcInputDcInputPowerWatts          ScaledNumber,
        invSysDcInputNumberOfModulesOn          ScaledNumber,
        invSysDcInputNumberOfModulesOff         ScaledNumber,
        invSysDcInputNumberOfModulesFailed      ScaledNumber,
        invSysDcInputNumberOfModulesDetected    ScaledNumber
	    }


	invSysDcInputInputVoltage OBJECT-TYPE
   		SYNTAX      ScaledNumber
		MAX-ACCESS  read-only
		STATUS      current
		DESCRIPTION
			"The input voltage of the inverter or group (V)."
		::= { invSysDcInputEntry 1 }

	invSysDcInputInputCurrent OBJECT-TYPE
   		SYNTAX      ScaledNumber
		MAX-ACCESS  read-only
		STATUS      current
		DESCRIPTION
			"The input current of the inverter or group (A)."
		::= { invSysDcInputEntry 2 }

	invSysDcInputDcInputPowerWatts OBJECT-TYPE
   		SYNTAX      ScaledNumber
		MAX-ACCESS  read-only
		STATUS      current
		DESCRIPTION
			"The power drawn by the DC input (W)."
		::= { invSysDcInputEntry 3 }

    invSysDcInputNumberOfModulesOn OBJECT-TYPE
   		SYNTAX      ScaledNumber
		MAX-ACCESS  read-only
		STATUS      current
		DESCRIPTION
			"The number of inverters that are On and can deliver power."
		::= { invSysDcInputEntry 4 }

    invSysDcInputNumberOfModulesOff OBJECT-TYPE
   		SYNTAX      ScaledNumber
		MAX-ACCESS  read-only
		STATUS      current
		DESCRIPTION
			"The number of inverters that are manually turned off."
		::= { invSysDcInputEntry 5 }

	invSysDcInputNumberOfModulesFailed OBJECT-TYPE
   		SYNTAX      ScaledNumber
		MAX-ACCESS  read-only
		STATUS      current
		DESCRIPTION
			"The number of inverters that have failed and cannot deliver power."
		::= { invSysDcInputEntry 6 }

    invSysDcInputNumberOfModulesDetected OBJECT-TYPE
   		SYNTAX      ScaledNumber
		MAX-ACCESS  read-only
		STATUS      current
		DESCRIPTION
			"The number of inverters assigned to this phase that the T2S has detected."
		::= { invSysDcInputEntry 7 }

END
