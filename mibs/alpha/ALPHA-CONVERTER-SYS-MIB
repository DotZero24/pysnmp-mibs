ALPHA-CONVERTER-SYS-MIB DEFINITIONS ::= BEGIN

	--==========================================================================
	--
	-- Alpha Technologies Ltd.
	-- Copyright 2014
	--
	--==========================================================================

	IMPORTS
		MODULE-IDENTITY, OBJECT-TYPE
			FROM SNMPv2-SMI
		ScaledNumber, simple
			FROM ALPHA-RESOURCE-MIB
	   	MODULE-COMPLIANCE, OBJECT-GROUP
      	 	FROM SNMPv2-CONF;


	converterSystem MODULE-IDENTITY
		LAST-UPDATED "201507280000Z"
		ORGANIZATION "Alpha Technologies Ltd."
		CONTACT-INFO
		  	 "Alpha Technologies Ltd.
			  7700 Riverfront Gate
			  Burnaby, BC  V5J 5M4
			  Canada

			  Tel: 1-604-436-5900
			  Fax: 1-604-436-1233"
		DESCRIPTION
		  "This MIB defines the notification block(s) available in system controllers."

		REVISION    "201507280000Z"  -- July 28, 2015
		DESCRIPTION
			"
			Updated to follow MIB structure conformance rules.  Tested with
			SimpleWeb: http://www.simpleweb.org
			Passed highest level of compliance.  (level 6)
			"

		REVISION    "201507230000Z"  -- July 23, 2015
		DESCRIPTION
			"Fixed MIB syntax warnings."

		REVISION    "201506230000Z"  -- June 23, 2015
		DESCRIPTION
			"General revision."
	::= { simple 2 }


   convSysTotalOutputCurrent OBJECT-TYPE
       SYNTAX      ScaledNumber
       MAX-ACCESS  read-only
       STATUS      current
       DESCRIPTION
               "Total converter output current in AMPS."
       ::= { converterSystem 1 }

   convSysTotalOutputPower OBJECT-TYPE
       SYNTAX      ScaledNumber
       MAX-ACCESS  read-only
       STATUS      current
       DESCRIPTION
               "Total converter output power in WATTS."
       ::= { converterSystem 2 }

   convSysTotalCapacityInstalledAmps OBJECT-TYPE
       SYNTAX      ScaledNumber
       MAX-ACCESS  read-only
       STATUS      current
       DESCRIPTION
               "A converter output current multiplied by the number of converters installed."
       ::= { converterSystem 3 }

   convSysTotalCapacityInstalledPower OBJECT-TYPE
       SYNTAX      ScaledNumber
       MAX-ACCESS  read-only
       STATUS      current
       DESCRIPTION
               "A converter output power multiplied by the number of converters installed."
       ::= { converterSystem 4 }

   convSysAverageConverterOutputVoltage OBJECT-TYPE
       SYNTAX      ScaledNumber
       MAX-ACCESS  read-only
       STATUS      current
       DESCRIPTION
               "Average converter output voltage."
       ::= { converterSystem 5 }

   convSysAverageConverterInputVoltage OBJECT-TYPE
       SYNTAX      ScaledNumber
       MAX-ACCESS  read-only
       STATUS      current
       DESCRIPTION
               "Average input voltage supplied to the converters."
       ::= { converterSystem 6 }

   convSysSystemVoltage OBJECT-TYPE
       SYNTAX      ScaledNumber
       MAX-ACCESS  read-only
       STATUS      current
       DESCRIPTION
               "System voltage."
       ::= { converterSystem 7 }

   convSysTotalLoadCurrent OBJECT-TYPE
       SYNTAX      ScaledNumber
       MAX-ACCESS  read-only
       STATUS      current
       DESCRIPTION
               "Total load current."
       ::= { converterSystem 8 }

   convSysSystemNumber OBJECT-TYPE
       SYNTAX      ScaledNumber
       MAX-ACCESS  read-only
       STATUS      current
       DESCRIPTION
               "Snmp ID# assigned to the system."
       ::= { converterSystem 9 }



	-- Conformance

	conformance OBJECT IDENTIFIER ::= { converterSystem 100 }

	compliances OBJECT IDENTIFIER ::= { conformance 1 }

	compliance MODULE-COMPLIANCE
	      STATUS  current
	      DESCRIPTION
	          "The compliance statement for systems supporting the Alpha Converter System MIB."
	      MODULE -- this module
	          MANDATORY-GROUPS {
				converterGroup
	          }
	   ::= { compliances 1 }

	converterGroups OBJECT IDENTIFIER ::= { conformance 2 }

	converterGroup OBJECT-GROUP
	    OBJECTS {
	    	 convSysTotalOutputCurrent,
	    	 convSysTotalOutputPower,
	    	 convSysTotalCapacityInstalledAmps,
	    	 convSysTotalCapacityInstalledPower,
	    	 convSysAverageConverterOutputVoltage,
	    	 convSysAverageConverterInputVoltage,
	    	 convSysSystemVoltage,
	    	 convSysTotalLoadCurrent,
	    	 convSysSystemNumber
		}
		STATUS   current
		DESCRIPTION
		     "Alpha converter System data list group."
		::= { converterGroups 1 }



END
