REDLINE-AN80I-MIB DEFINITIONS ::= BEGIN

IMPORTS
	redlineSystem
		FROM REDLINE-MIB
	MODULE-IDENTITY,
	OBJECT-TYPE,
	NOTIFICATION-TYPE,
	TimeTicks, Integer32
		FROM SNMPv2-SMI
	OBJECT-GROUP,
	MODULE-COMPLIANCE,
	NOTIFICATION-GROUP
		FROM SNMPv2-CONF
	DisplayString,
	RowStatus
		FROM SNMPv2-TC
	InetAddress,
	InetAddressType,
	InetPortNumber
		FROM INET-ADDRESS-MIB;

redlineAn80iMib MODULE-IDENTITY
	LAST-UPDATED "200511291543Z"
	ORGANIZATION "Redline Communications Inc."
	CONTACT-INFO
		"Henryk Kijak
		email: hkijak@redlinecommunications.com"
	DESCRIPTION
		"This MIB module contains object definitions
		applicable only to Redline AN80i switched device."
	REVISION "200511291543Z"
	DESCRIPTION
		"Initial version."
	::= { redlineSystem 3 }


-- Scalars and Tables
--

-- AN80i ptp/pmp variables

redlineAn80iPtpPmpObjects OBJECT IDENTIFIER ::= { redlineAn80iMib 1 }

-- AN80i system variables

redlineAn80iSystemObjects OBJECT IDENTIFIER ::= { redlineAn80iPtpPmpObjects 1 }

-- An80i Option Key Table

an80iOptionsKeyTable OBJECT-TYPE
	SYNTAX      SEQUENCE OF An80iOptionsKeyEntry
	MAX-ACCESS  not-accessible
	STATUS      current
	DESCRIPTION
		"This table contains options key information.
		 The maximum number of configured options key is 2."
	::= { redlineAn80iSystemObjects 1 }

an80iOptionsKeyEntry OBJECT-TYPE
	SYNTAX      An80iOptionsKeyEntry
	MAX-ACCESS  not-accessible
	STATUS      current
	DESCRIPTION
		"This table provides one row for each option key defined in
		 the AN80i system"
	INDEX { an80iOptionsKeyId }
	::= { an80iOptionsKeyTable 1 }

An80iOptionsKeyEntry ::= SEQUENCE {
	an80iOptionsKeyId INTEGER,
	an80iOptionsKey DisplayString,
	an80iOptionsKeyStatus RowStatus
}

an80iOptionsKeyId OBJECT-TYPE
	SYNTAX INTEGER(1..2)
	MAX-ACCESS not-accessible
	STATUS current
	DESCRIPTION
		"The Options Key Identifier."
	::= { an80iOptionsKeyEntry 1 }

an80iOptionsKey OBJECT-TYPE
	SYNTAX DisplayString
	MAX-ACCESS read-create
	STATUS current
	DESCRIPTION
		"The options key value."
	::= { an80iOptionsKeyEntry 2 }

an80iOptionsKeyStatus OBJECT-TYPE
	SYNTAX  RowStatus
	MAX-ACCESS read-create
	STATUS current
	DESCRIPTION
		"This object is used to ctivate and deactivate rows in the an80iOptionsKeyTable
		table. There will be only two rows in the table and only one will be active.
		When one row is active the other one will be notInService. The row can not be
		created or deleted"
	::= { an80iOptionsKeyEntry 3 }

-- AN80i system general variables

an80iHardwareType OBJECT-TYPE
	SYNTAX Integer32
	MAX-ACCESS read-only
	STATUS current
	DESCRIPTION
		"The type/version/revision of the hardware."
	::= { redlineAn80iSystemObjects 2 }

an80iRadioType OBJECT-TYPE
	SYNTAX Integer32
	MAX-ACCESS read-only
	STATUS current
	DESCRIPTION
		"The radio type."
	::= { redlineAn80iSystemObjects 3 }

--an80iLastTrapTime OBJECT-TYPE
--	SYNTAX TimeTicks
--	MAX-ACCESS read-only
--	STATUS current
--	DESCRIPTION
--		"The value of system.sysUpTime when the last trap was
--               generated. If no traps have been generated since the
--               last reset, this attribute has a value of 0. No trap is
--               issued as a result of a change to this value."
--	::= { redlineAn80iSystemObjects 4 }

an80iSaveConfig OBJECT-TYPE
	SYNTAX INTEGER {
			noop(1),
			saveConfig(2) }
	MAX-ACCESS read-write
	STATUS current
	DESCRIPTION
		"This object will save the configuration in the
		 nonvolatile memory and will activate the new
		 configuration."
	::= { redlineAn80iSystemObjects 4 }

an80iActivateConfig OBJECT-TYPE
	SYNTAX INTEGER {
			noop(1),
			activeConfig(2) }
	MAX-ACCESS read-write
	STATUS current
	DESCRIPTION
		"This object will activate the new configuration
		 without saving it in the nonvolatile memory.
		 If after this event it will elapse more than 5
		 minutes and no save configuration occurs, then
		 system will restart with the configuration from
		 the nonvolatile memory."
	::= { redlineAn80iSystemObjects 5 }


-- AN80i ptp/pmp general wireless variables

redlineAn80iWirelesObjects OBJECT IDENTIFIER ::= { redlineAn80iPtpPmpObjects 2 }

an80iAntennaAllignmentMode OBJECT-TYPE
	SYNTAX INTEGER {
			off(1),
			buzzer(2) }
	MAX-ACCESS read-write
	STATUS current
	DESCRIPTION
		"Specifies if the antenna alignment buzzer is
		 enabled or not. In the future, new alignment
		 methods may be added."
	::= { redlineAn80iWirelesObjects 1 }

an80iCurrTxPower OBJECT-TYPE
	SYNTAX INTEGER (-10..20)
	MAX-ACCESS read-only
	STATUS current
	DESCRIPTION
		"The actual Tx Power of the AN-80i Node."
	::= { redlineAn80iWirelesObjects 2 }

an80iChannelAutoScan OBJECT-TYPE
	SYNTAX INTEGER {
			enable(1),
			disable(2)}
	MAX-ACCESS read-write
	STATUS current
	DESCRIPTION
		"Specifies if the frequency auto-scanning
		 feature is enabled"
	::= { redlineAn80iWirelesObjects 3 }

an80iCurrFrequency OBJECT-TYPE
	SYNTAX Integer32
	UNITS "KHz"
	MAX-ACCESS read-only
	STATUS current
	DESCRIPTION
		"The central frequency on which the equipment
		 operates. If the auto-scanning feature is
		 enabled then this may be different than the
		 an80iOPeratingFrequency. [KHz]"
	::= { redlineAn80iWirelesObjects 4 }

an80iOPeratingFrequency OBJECT-TYPE
	SYNTAX Integer32
	UNITS "KHz"
	MAX-ACCESS read-write
	STATUS current
	DESCRIPTION
		"Specifies the operating frequency of the system [KHz]."
	::= { redlineAn80iWirelesObjects 5 }

an80iMaxTxPower OBJECT-TYPE
	SYNTAX INTEGER (-20..20)
	MAX-ACCESS read-write
	STATUS current
	DESCRIPTION
		"The Tx Power of the AN-80i. Specifies the power level of the
		 system, which is preset at the factory  and should not be altered.
		 In the event that this parameter needs to be changed, please contact
		 the Redline support team."
	::= { redlineAn80iWirelesObjects 6 }

an80iSystemMode OBJECT-TYPE
	SYNTAX INTEGER {
			ptpSlave(1),
			ptpMaster(2),
			pmpSlave(3),
			pmpMaster(4) }
	MAX-ACCESS read-write
	STATUS current
	DESCRIPTION
		"1 = PMP Slave, 2 = PTP Master, 3 = PMP Slave,
		 4 = PMP Master"
	::= { redlineAn80iWirelesObjects 7 }

an80iRFStatusCode OBJECT-TYPE
	SYNTAX Integer32
	MAX-ACCESS read-only
	STATUS current
	DESCRIPTION
		"Specifies the Error Code for the RF Interface."
	::= { redlineAn80iWirelesObjects 8 }

an80iDFSAction OBJECT-TYPE
	SYNTAX INTEGER {
			none (1),
			txDisabled(2),
			changeFreq(3) }
	MAX-ACCESS read-write
	STATUS current
	DESCRIPTION
		"Action taken when a radar is detected on the
		 same frequency."
	::= { redlineAn80iWirelesObjects 9 }

an80iAntennaGain OBJECT-TYPE
	SYNTAX Integer32
	MAX-ACCESS read-write
	STATUS current
	DESCRIPTION
		"The gain of the antenna attached to the system."
	::= { redlineAn80iWirelesObjects 10 }

an80iActiveRFLinks OBJECT-TYPE
	SYNTAX Integer32
	MAX-ACCESS read-only
	STATUS current
	DESCRIPTION
		"The actual number of provisioned links."
	::= { redlineAn80iWirelesObjects 11 }

an80iAtpControl OBJECT-TYPE
	SYNTAX INTEGER {
			enable(1),
			disable(2) }
	MAX-ACCESS read-write
	STATUS current
	DESCRIPTION
		"Enable/disable the automatic Tx power control."
	::= { redlineAn80iWirelesObjects 12 }

an80iTurboModeControl OBJECT-TYPE
	SYNTAX INTEGER {
			enable(1),
			disable(2) }
	MAX-ACCESS read-write
	STATUS current
	DESCRIPTION
		"Enable/disable the turbo mode. In this mode the system
		 uses a 40MHz channel (20 MHz in normal mode). "
	::= { redlineAn80iWirelesObjects 13 }


an80iChannelWidth OBJECT-TYPE
	SYNTAX INTEGER {
			chWidth40MHz(7),
			chWidth20MHz(6),
			chWidth10MHz(5) }
	MAX-ACCESS read-write
	STATUS current
	DESCRIPTION
		"The width of the channel. "
	::= { redlineAn80iWirelesObjects 14 }


-- AN80i ptp/pmp ethernet variables

redlineAn80iEthernetObjects OBJECT IDENTIFIER ::= { redlineAn80iPtpPmpObjects 3 }

an80iEtherPortConn OBJECT-TYPE
	SYNTAX INTEGER {
			auto(1),
			normal(2),
			crossover(3) }
	MAX-ACCESS read-write
	STATUS current
	DESCRIPTION
		"Specifies Ethernet port connection auto(1), mdi(2)
		 or mdix(3)"
	::= { redlineAn80iEthernetObjects 1 }

an80iEtherPortMode OBJECT-TYPE
	SYNTAX INTEGER {
			auto(1),
			e10hd(2),
			e10fd(3),
			e100hd(4),
			e100fd(5) }
	MAX-ACCESS read-write
	STATUS current
	DESCRIPTION
		"The attribute specifies the Ethernet LED status of
		 the AN80i."
	::= { redlineAn80iEthernetObjects 2 }

an80iFlowControl OBJECT-TYPE
	SYNTAX  INTEGER {
			enabled(1),
			disabled(2) }
	MAX-ACCESS  read-write
	STATUS  current
	DESCRIPTION
		"This object specifies if flow control is enabled
		 or not."
	::= { redlineAn80iEthernetObjects 3 }


an80iLowLatencyMode OBJECT-TYPE
	SYNTAX  INTEGER {
			enabled(1),
			disabled(2) }
	MAX-ACCESS  read-write
	STATUS  current
	DESCRIPTION
		"This object specifies if prioritized low latency mode
		 is enabled or not."
	::= { redlineAn80iEthernetObjects 4 }


an80iEthernetFollowsWireless OBJECT-TYPE
	SYNTAX  INTEGER {
			enabled(1),
			disabled(2) }
	MAX-ACCESS  read-write
	STATUS  current
	DESCRIPTION
		"This object specifies if the Ethernet follows wireless mode
		 is enabled or not."
	::= { redlineAn80iEthernetObjects 5 }

an80iEthernetFollowsWirelessTimeout OBJECT-TYPE
	SYNTAX  INTEGER (0..65535)
	MAX-ACCESS  read-write
	STATUS  current
	DESCRIPTION
		"This object specifies if the timeout (seconds) for the
		 Ethernet follows wireless mode (0=infinite)."
	::= { redlineAn80iEthernetObjects 6 }

-- AN80i ptp/pmp management variables

redlineAn80iManagObjects OBJECT IDENTIFIER ::= { redlineAn80iPtpPmpObjects 4 }

an80iHttpAccess OBJECT-TYPE
	SYNTAX INTEGER {
			enabled(1),
			disabled(2) }
	MAX-ACCESS read-write
	STATUS current
	DESCRIPTION
		"This object specifies if Http Access is enabled
		 or not."
	::= { redlineAn80iManagObjects 1 }

an80iTelnetAccess OBJECT-TYPE
	SYNTAX INTEGER {
			enabled(1),
			disabled(2) }
	MAX-ACCESS read-write
	STATUS current
	DESCRIPTION
		"This object specifies if Telnet Access is enabled
		 or not."
	::= { redlineAn80iManagObjects 2 }

an80iTelnetPort OBJECT-TYPE
	SYNTAX  InetPortNumber
	MAX-ACCESS  read-write
	STATUS  current
	DESCRIPTION
		"This object specifies the Telnet port number."
	::= { redlineAn80iManagObjects 3 }

-- AN80i ptp/pmp software upgrade variables

redlineAn80iSWUpgradeObjects OBJECT IDENTIFIER ::= { redlineAn80iPtpPmpObjects 5 }

an80iSwDownloadTftpAddressType OBJECT-TYPE
	SYNTAX  InetAddressType
	MAX-ACCESS read-write
	STATUS current
	DESCRIPTION
		"The INET address type of the software upgrade TFTP server.
		IPv4 type supported only."
	::= { redlineAn80iSWUpgradeObjects 1 }


an80iSwDownloadTftpAddress OBJECT-TYPE
	SYNTAX  InetAddress
	MAX-ACCESS read-write
	STATUS current
	DESCRIPTION
		"The INET address of the TFTP server."
	::= { redlineAn80iSWUpgradeObjects 2 }


an80iSwDownloadTftpFile OBJECT-TYPE
	SYNTAX  DisplayString (SIZE (0..63))
	MAX-ACCESS read-write
	STATUS current
	DESCRIPTION
		"The image file name as required
		by the TFTP server."
	::= { redlineAn80iSWUpgradeObjects 3 }


an80iSwDownloadStatus OBJECT-TYPE
	SYNTAX  INTEGER {
			download(1), 	-- start tftp download
			inProgress(2),  -- download is in progress
			success(3),  	-- download completed successfully
			failed(4)   	-- download failed
			}
	MAX-ACCESS read-only
	STATUS current
	DESCRIPTION
		"The status of the current software download."
	::= { redlineAn80iSWUpgradeObjects 4 }

an80iSwDownloadControl OBJECT-TYPE
        SYNTAX  INTEGER {
                        noop(1),
                        startUpgrade(2) }
        MAX-ACCESS read-write
        STATUS current
        DESCRIPTION
                "Trigger software upgrade"
        ::= { redlineAn80iSWUpgradeObjects 5 }


-- AN80i pmp variables

redlineAn80iPmpObjects OBJECT IDENTIFIER ::= { redlineAn80iMib 2 }

-- AN80i pmp general wireless variables

redlineAn80iPmpWirelesObjects OBJECT IDENTIFIER ::= { redlineAn80iPmpObjects 1 }

an80iRegistrationPeriod OBJECT-TYPE
	SYNTAX  INTEGER (1..100)
	MAX-ACCESS  read-write
	STATUS  current
	DESCRIPTION
		"Number of frames between two consecutive registration periods."
	::= { redlineAn80iPmpWirelesObjects 1 }

an80iMaximumDistance OBJECT-TYPE
	SYNTAX  INTEGER (0..100)
	MAX-ACCESS  read-write
	STATUS  current
	DESCRIPTION
		"Maximum distance in km between the sector controller and
		 one subscriber station."
	::= { redlineAn80iPmpWirelesObjects 2 }

an80iRegisteredStations OBJECT-TYPE
	SYNTAX  Integer32
	MAX-ACCESS  read-only
	STATUS  current
	DESCRIPTION
		"The number of registered stations on the sector controller."
	::= { redlineAn80iPmpWirelesObjects 3 }

an80iRegisteredConnections OBJECT-TYPE
	SYNTAX  Integer32
	MAX-ACCESS  read-only
	STATUS  current
	DESCRIPTION
		"The number of registered connections on the sector controller."
	::= { redlineAn80iPmpWirelesObjects 4 }

an80iMaxId OBJECT-TYPE
	SYNTAX INTEGER (1..1023)
	MAX-ACCESS read-only
	STATUS current
	DESCRIPTION
		"The maximum number of ID used to identify links, connections and groups"
	::= { redlineAn80iPmpWirelesObjects 5 }

an80iNextAvailId OBJECT-TYPE
	SYNTAX Integer32
	MAX-ACCESS read-only
	STATUS current
	DESCRIPTION
		"The next available ID from the ID pool which is not grater
		 then that defined in 'an80iMaxId' "
	::= { redlineAn80iPmpWirelesObjects 6 }


an80iLastModifId OBJECT-TYPE
	SYNTAX Integer32
	MAX-ACCESS read-only
	STATUS current
	DESCRIPTION
		"The last modified ID from the ID pool which is not grater
		 then that defined in 'an80iMaxId' "
	::= { redlineAn80iPmpWirelesObjects 7 }


an80iSaveIdConfiguration OBJECT-TYPE
	SYNTAX  INTEGER {
			noop(1),
			save(2) }
	MAX-ACCESS read-write
	STATUS current
	DESCRIPTION
		"Save the ID table in the flash memory"
	::= { redlineAn80iPmpWirelesObjects 8 }

-- AN80i ptp variables

redlineAn80iPtpObjects OBJECT IDENTIFIER ::= { redlineAn80iMib 3 }

-- AN80i general ptp variables

redlineAn80iPtpSystemObjects OBJECT IDENTIFIER ::= { redlineAn80iPtpObjects 1 }

an80iResetStatistics OBJECT-TYPE
	SYNTAX INTEGER {
			noop(1),
			reset(2) }
	MAX-ACCESS read-write
	STATUS current
	DESCRIPTION
		"This object resets wireless and Ethernet counters"
	::= { redlineAn80iPtpSystemObjects 1 }



-- AN80i trap definitions

redlineAn80iTrapDefinitions OBJECT IDENTIFIER 	::= { redlineAn80iMib 0 }


an80iPswdChangeFailTrap NOTIFICATION-TYPE
	STATUS current
	DESCRIPTION
		"An event to report the failure of a password change."
	::= { redlineAn80iTrapDefinitions 1 }

an80iFirmwareConfigFailTrap NOTIFICATION-TYPE
	STATUS current
	DESCRIPTION
		"An event to report the failure of a firmware config."
	::= { redlineAn80iTrapDefinitions 2 }

an80iEepromCorruptedTrap NOTIFICATION-TYPE
	STATUS current
	DESCRIPTION
		"An event to report the corruption of the EEPROM."
	::= { redlineAn80iTrapDefinitions 3 }

an80iHardwareFailTrap NOTIFICATION-TYPE
	STATUS current
	DESCRIPTION
		"An event to report the hardware failure."
	::= { redlineAn80iTrapDefinitions 4 }

an80iSaveConfigTrap NOTIFICATION-TYPE
	STATUS current
	DESCRIPTION
		"An event to report the saving of configuration"
	::= { redlineAn80iTrapDefinitions 5 }

an80iDFSEventTrap NOTIFICATION-TYPE
	STATUS current
	DESCRIPTION
		"An event to report the radar frequency detection"
	::= { redlineAn80iTrapDefinitions 6 }

an80iIdChangedTrap NOTIFICATION-TYPE
	OBJECTS {
		an80iLastModifId }
	STATUS current
	DESCRIPTION
		"Event that reports the modification in the configuration
		 of an ID."
	::= { redlineAn80iTrapDefinitions 7 }

an80iSWUpgradeFailed NOTIFICATION-TYPE
	OBJECTS {
		an80iSwDownloadTftpAddressType,
		an80iSwDownloadTftpAddress,
		an80iSwDownloadTftpFile }
	STATUS current
	DESCRIPTION
		"Event that reports the failure of a software upgrade opration."
	::= { redlineAn80iTrapDefinitions 8 }

an80iSWUpgradeSuccess NOTIFICATION-TYPE
	OBJECTS {
		an80iSwDownloadTftpAddressType,
		an80iSwDownloadTftpAddress,
		an80iSwDownloadTftpFile }
	STATUS current
	DESCRIPTION
		"Event that reports the success of a software upgrade opration."
	::= { redlineAn80iTrapDefinitions 9 }

--
-- Conformance
--

redlineAn80iConformance OBJECT IDENTIFIER ::= { redlineAn80iMib 5 }


-- Groups
--

redlineAn80iGroups OBJECT IDENTIFIER ::= { redlineAn80iConformance 1 }

--
-- Compliance
--

redlineAn80iCompls OBJECT IDENTIFIER ::= { redlineAn80iConformance 2 }

redlineAn80iPtpPmpGroup OBJECT-GROUP
	OBJECTS {
		an80iOptionsKey,
		an80iHardwareType,
		an80iRadioType,
--		an80iLastTrapTime,
		an80iSaveConfig,
		an80iActivateConfig,
		an80iAntennaAllignmentMode,
		an80iCurrTxPower,
		an80iChannelAutoScan,
		an80iCurrFrequency,
		an80iOPeratingFrequency,
		an80iMaxTxPower,
		an80iSystemMode,
		an80iRFStatusCode,
		an80iDFSAction,
		an80iAntennaGain,
		an80iActiveRFLinks,
		an80iAtpControl,
		an80iTurboModeControl,
		an80iEtherPortConn,
		an80iEtherPortMode,
		an80iFlowControl,
		an80iLowLatencyMode,
		an80iEthernetFollowsWireless,
		an80iEthernetFollowsWirelessTimeout,
		an80iHttpAccess,
		an80iTelnetAccess,
		an80iTelnetPort,
		an80iSwDownloadTftpAddressType,
		an80iSwDownloadTftpAddress,
		an80iSwDownloadTftpFile,
		an80iSwDownloadStatus,
		an80iSwDownloadControl }
	STATUS current
	DESCRIPTION
		"AN80i PTP/PMP objects."
	::= { redlineAn80iGroups 1 }


redlineAn80iPmpGroup OBJECT-GROUP
	OBJECTS {
                an80iRegistrationPeriod,
		an80iMaximumDistance,
		an80iRegisteredStations,
		an80iRegisteredConnections,
		an80iMaxId,
		an80iNextAvailId,
		an80iLastModifId,
		an80iSaveIdConfiguration }
	STATUS current
	DESCRIPTION
		"AN80i PMP objects."
	::= { redlineAn80iGroups 2 }


redlineAn80iPtpGroup OBJECT-GROUP
	OBJECTS {
		an80iResetStatistics }
	STATUS current
	DESCRIPTION
		"AN80i PTP objects."
	::= { redlineAn80iGroups 3 }

redlineAn80iNotificationGroup NOTIFICATION-GROUP
	NOTIFICATIONS {
		an80iPswdChangeFailTrap,
		an80iFirmwareConfigFailTrap,
		an80iEepromCorruptedTrap,
		an80iHardwareFailTrap,
		an80iSaveConfigTrap,
		an80iDFSEventTrap,
		an80iIdChangedTrap,
		an80iSWUpgradeFailed,
 		an80iSWUpgradeSuccess }
	STATUS current
	DESCRIPTION
		"The notifications which indicate specific events
		 within the AN80i unit."
	::= { redlineAn80iGroups 4 }


redlineAn80iCompliance MODULE-COMPLIANCE
	STATUS current
	DESCRIPTION
		"The compliance statement for AN80i entities that
		implement this MIB module."

	MODULE
	MANDATORY-GROUPS {
			redlineAn80iPtpPmpGroup,
			redlineAn80iPmpGroup,
			redlineAn80iPtpGroup,
			redlineAn80iNotificationGroup }
	::= { redlineAn80iCompls 1 }

END
