-- *****************************************************************
-- REDLINE-PRODUCTS-MIB:  Redline Product Object Identifier Assignments
-- ECO Rev 1.00
--
-- March 2002, Claude Daniel Ndjouou
--
-- Copyright (c) 2002 by redline Communications, Inc.
-- All rights reserved.
--
-- *****************************************************************

   REDLINE-PRODUCTS-MIB DEFINITIONS ::= BEGIN

   IMPORTS
	MODULE-IDENTITY
		FROM SNMPv2-SMI
	redline
		FROM REDLINE-MIB;

   redlineProducts MODULE-IDENTITY
	LAST-UPDATED "200708221348Z"
        ORGANIZATION    "Redline Communications, Inc."
        CONTACT-INFO
        "Primary Author: Claude Ndjouou

        postal: Redline Communications Inc.
                90 Tiverton Court Suite 102
                Markham Ontario L2R 9V2
                Canada
        phone:     +1 905 479-8344
        email:     cndjouou@redlinecommunications.com "
       DESCRIPTION
                "This module defines the object identifiers that are
                assigned to various redline hardware platforms, and hence are
                returned as values for sysObjectID"
	REVISION "200708221348Z"
	DESCRIPTION
		"Added AN100UX, AN80i and SUO/SUI System Object IDs"
	REVISION "200504271348Z"
	DESCRIPTION
		"Added AN100U and WRS System Object IDs"
	REVISION "0206100000Z"
	DESCRIPTION
		"More product updates for PMP project"
        REVISION        "200203130000Z"
        DESCRIPTION
                "Miscellaneous updates."
        ::= { redline 1 }


-- AN 50 Node System Object ID

redlineAN50 OBJECT IDENTIFIER ::= { redlineProducts 1 }

-- WB 1000 Node System Object ID

redlineWB1000 OBJECT IDENTIFIER ::= { redlineProducts 2 }

-- AN100 Sector Controller Node System Object ID

  redlineAN100SC OBJECT IDENTIFIER ::= { redlineProducts 3 }

-- AN100 Subscriber Station Node System Object ID

  redlineAN100SS OBJECT IDENTIFIER ::= { redlineProducts 4 }

-- WS 58 Node System Object ID

redlineWS58 OBJECT IDENTIFIER ::= { redlineProducts 5 }

-- WS 35 Node System Object ID

redlineWS35 OBJECT IDENTIFIER ::= { redlineProducts 6 }

-- AN100 Node System Object ID

redlineAN100 OBJECT IDENTIFIER ::= { redlineProducts 7 }

-- AN50PMP Node System Object ID

redlineAN50PMP OBJECT IDENTIFIER ::= { redlineProducts 8 }

-- AN30 Node System Object ID

redlineAN30 OBJECT IDENTIFIER ::= { redlineProducts 9 }

-- AN100U Node System Object ID

redlineAN100U OBJECT IDENTIFIER ::= { redlineProducts 10 }

-- Outdoor Subscriber Station Node System Object ID

redlineWRS OBJECT IDENTIFIER ::= { redlineProducts 11 }

-- Indoor Subscriber Station Node System Object ID

redlineWRS OBJECT IDENTIFIER ::= { redlineProducts 12 }

-- AN100UX Node System Object ID

redlineAN100UX OBJECT IDENTIFIER ::= { redlineProducts 14 }

-- AN80i PTP Node System Object ID

redlineAN80iPTP OBJECT IDENTIFIER ::= { redlineProducts 15 }

-- AN80i PMP Node System Object ID

redlineAN80iPMP OBJECT IDENTIFIER ::= { redlineProducts 16 }

END
