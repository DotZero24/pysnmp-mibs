-- *****************************************************************
-- Redline e1t1 MIB
-- ECO Rev 1.00
-- Copyright (c) 2006 by Redline Communications, Inc.
-- All rights reserved.
-- *****************************************************************

REDLINE-E1T1-MIB DEFINITIONS ::= BEGIN

IMPORTS

        IpAddress, Counter, TimeTicks, enterprises  	FROM RFC1155-SMI
	  RowStatus							FROM SNMPv2-TC
        OBJECT-TYPE                             	FROM RFC-1212
        TRAP-TYPE                             		FROM RFC-1215;


--      ORGANIZATION "Redline Communications, Inc."

--      postal:  Redline Communications Inc.
--              302 Town Centre Blvd Suite 100
--              Markham Ontario L3R 0E8
--              Canada
--      phone:     +1 905 479-8344
--      DESCRIPTION "This MIB contains Redline-defined attributes for E1/T1 board."
--      LAST-UPDATED "200304170930Z"
--      Author: Bogdan Moldoveanu
--      DESCRIPTION "Attributes for E1/T1 board introduced."

--      LAST-UPDATED "200307250930Z"
--      Author: Bogdan Moldoveanu
--      DESCRIPTION "Change enumaration from 0 to 1, 1 to 2,... to comply with SMIv1"

--      LAST-UPDATED "200408040930Z"
--      Author: Ioan Cautil
--      DESCRIPTION "Completed descriptions of the mib variables"

--      LAST-UPDATED "200601160930Z"
--      Author: Mark Fairclough
--      DESCRIPTION "spelling and address change"


-- Registration of object identifiers
redline         	OBJECT IDENTIFIER ::= { enterprises 10728 }
redlineProducts 	OBJECT IDENTIFIER ::= { redline 1 }
redlineMgmt     	OBJECT IDENTIFIER ::= { redline 2 }
redlineE1T1		OBJECT IDENTIFIER ::= { redlineMgmt 52}
e1t1General		OBJECT IDENTIFIER ::= { redlineE1T1 1 }
e1t1Stats		OBJECT IDENTIFIER ::= { redlineE1T1 5 }
e1t1Commands	OBJECT IDENTIFIER ::= { redlineE1T1 6 }



e1t1VlanIdData		OBJECT-TYPE
 	  SYNTAX		INTEGER (0..4095)
        ACCESS  		read-write
        STATUS  		mandatory
        DESCRIPTION
            "VLAN ID for data on E1/T1 module"
	::= {e1t1General  1}


e1t1VlanIdVoice		OBJECT-TYPE
 	  SYNTAX		INTEGER (0..4095)
        ACCESS  		read-write
        STATUS  		mandatory
        DESCRIPTION
            "VLAN ID for voice on E1/T1 module"
	::= {e1t1General  2}


e1t1Clock		OBJECT-TYPE
 	  SYNTAX  		INTEGER (0..2)
        ACCESS  		read-write
        STATUS  		mandatory
        DESCRIPTION
            "Clocking information on the E1/T1 module"
	::= {e1t1General  3}


e1t1SyncOn		OBJECT-TYPE
 	  SYNTAX  		INTEGER (0..16)
        ACCESS  		read-write
        STATUS  		mandatory
        DESCRIPTION
            "The number of serial interface to be used as clocking reference.
		 For AN-50 the number of serial interfaces is 4"
	::= {e1t1General  4}


e1t1IdleCode		OBJECT-TYPE
 	  SYNTAX		INTEGER
        ACCESS  		read-write
        STATUS  		mandatory
        DESCRIPTION
            " Idle Code for unused timeslots on the E1/T1 module"
	::= {e1t1General  5}


e1t1Hostname	OBJECT-TYPE
 	SYNTAX		OCTET STRING (SIZE(0..20))
	ACCESS		read-write
	STATUS		mandatory
      DESCRIPTION
            "E1/T1 host name"
	::= {e1t1General  6}


e1t1IpAddress		OBJECT-TYPE
	SYNTAX  		IpAddress
      ACCESS  		read-write
      STATUS  		mandatory
      DESCRIPTION
            "E1/T1 IP address"
	::= {e1t1General  7}


e1t1IpMask		OBJECT-TYPE
 	SYNTAX  		IpAddress
      ACCESS  		read-write
      STATUS  		mandatory
      DESCRIPTION
            "E1/T1 IP mask"
	::= {e1t1General  8}


e1t1IpGateway		OBJECT-TYPE
 	  SYNTAX  		IpAddress
        ACCESS  		read-write
        STATUS  		mandatory
        DESCRIPTION
            "E1/T1 gateway."
	::= {e1t1General  9}


e1t1OptionKey		OBJECT-TYPE
 	  SYNTAX  		INTEGER
        ACCESS  		read-only
        STATUS  		mandatory
        DESCRIPTION
            "E1/T1 Option Key."
	::= {e1t1General  10}


e1t1Line			OBJECT-TYPE
 	  SYNTAX  		INTEGER
        ACCESS  		read-write
        STATUS  		mandatory
        DESCRIPTION
            "The type of the line (T1/E1)."
	::= {e1t1General  11}


e1t1SoftwareVersion	OBJECT-TYPE
 	  SYNTAX  		OCTET STRING (SIZE(3))
        ACCESS  		read-only
        STATUS  		mandatory
        DESCRIPTION
            "E1/T1 module Software Version."
	::= {e1t1General  12}


-- ----------------------------------------------------------------------------
--
-- T1/E1 Commands
--
-- ----------------------------------------------------------------------------

e1t1SaveConfig		OBJECT-TYPE
 	  SYNTAX  		INTEGER {
					donothing (1), -- do save configuration in flash
					saveConfig (2) -- save configuration in flash
				}
        ACCESS  		read-write
        STATUS  		mandatory
        DESCRIPTION
            "Save the running configuration in flash."
	::= {e1t1Commands  1}


e1t1ActivateConfig	OBJECT-TYPE
 	  SYNTAX  		INTEGER {
					donothing (1),   -- do not activate configuration
					activeConfig (2) -- activate configuration
					}
        ACCESS  		read-write
        STATUS  		mandatory
        DESCRIPTION
            "Activate temporary configuration in running configuration."
  	::= {e1t1Commands  2}


e1t1ResetBoard		OBJECT-TYPE
 	  SYNTAX  		INTEGER {
					donothing (1), -- donot reset the E1/T1 module
					reset (2)      -- reset the E1/T1 module
				}
        ACCESS  		read-write
        STATUS  		mandatory
        DESCRIPTION
            "Reset the E1/T1 module."
  	::= {e1t1Commands  3}


e1t1ResetStats		OBJECT-TYPE
 	  SYNTAX  		INTEGER (0..35)
        ACCESS  		read-write
        STATUS  		mandatory
        DESCRIPTION
            "Reset Statistics for the E1/T1 module."
  	::= {e1t1Commands  4}


e1t1ReStartConfig	OBJECT-TYPE
 	  SYNTAX  		INTEGER {
					donothing (1),
					reset (2)
				}
        ACCESS  		read-write
        STATUS  		mandatory
        DESCRIPTION
            "ReStart the configuration operation for the E1/T1 module."
  	::= {e1t1Commands  5}



-- ----------------------------------------------------------------------------
--
-- T1E1 Module Status
--
-- ----------------------------------------------------------------------------

e1t1EthRate			OBJECT-TYPE
 	  SYNTAX  		INTEGER
        ACCESS  		read-only
        STATUS  		mandatory
        DESCRIPTION
            "Ethernet rate for the E1/T1 module.
		 0 = 10 Mbps
		 1 = 100 Mbps"
	::= {e1t1Stats  1}


e1t1EthMode			OBJECT-TYPE
 	  SYNTAX  		INTEGER
        ACCESS  		read-only
        STATUS  		mandatory
        DESCRIPTION
            "E1/T1 module mode.
		0 - half duplex
		1 - full duplex"
	::= {e1t1Stats  2}


e1t1EthState		OBJECT-TYPE
 	  SYNTAX  		INTEGER
        ACCESS  		read-only
        STATUS  		mandatory
        DESCRIPTION
            "E1/T1 module state.
		0 - not connected
		1 - connected"
	::= {e1t1Stats  3}


e1t1EthMAC			OBJECT-TYPE
 	  SYNTAX  		INTEGER
        ACCESS  		read-only
        STATUS  		mandatory
        DESCRIPTION
            "E1/T1 module MAC Address."
	::= {e1t1Stats  4}


e1t1EthFROK			OBJECT-TYPE
 	  SYNTAX  		INTEGER
        ACCESS  		read-only
        STATUS  		mandatory
        DESCRIPTION
            "E1/T1 module frames received OK (FROK)."
	::= {e1t1Stats  5}


e1t1EthBROK			OBJECT-TYPE
 	  SYNTAX  		INTEGER
        ACCESS  		read-only
        STATUS  		mandatory
        DESCRIPTION
            "E1/T1 module bytes received OK (BROK)."
	::= {e1t1Stats  6}


e1t1EthAERR			OBJECT-TYPE
 	  SYNTAX  		INTEGER
        ACCESS  		read-only
        STATUS  		mandatory
        DESCRIPTION
            "E1/T1 module alignment errors (AERR)."
	::= {e1t1Stats  7}


e1t1EthCERR			OBJECT-TYPE
 	  SYNTAX  		INTEGER
        ACCESS  		read-only
        STATUS  		mandatory
        DESCRIPTION
            "E1/T1 module CRC errors (CERR)."
	::= {e1t1Stats  8}


e1t1EthFTOK			OBJECT-TYPE
 	  SYNTAX  		INTEGER
        ACCESS  		read-only
        STATUS  		mandatory
        DESCRIPTION
            "E1/T1 module frames transmitted OK (FTOK)."
	::= {e1t1Stats  9}


e1t1EthBTOK			OBJECT-TYPE
 	  SYNTAX  		INTEGER
        ACCESS  		read-only
        STATUS  		mandatory
        DESCRIPTION
            "E1/T1 module bytes transmitted OK (BTOK)."
	::= {e1t1Stats  10}


e1t1EthSCOL			OBJECT-TYPE
 	  SYNTAX  		INTEGER
        ACCESS  		read-only
        STATUS  		mandatory
        DESCRIPTION
            "E1/T1 module single collisions (SCOL)."
	::= {e1t1Stats  11}


e1t1EthMCOL			OBJECT-TYPE
 	  SYNTAX  		INTEGER
        ACCESS  		read-only
        STATUS  		mandatory
        DESCRIPTION
            "E1/T1 module multiple collisions (MCOL)."
	::= {e1t1Stats  12}


e1t1EthTDEF			OBJECT-TYPE
 	  SYNTAX  		INTEGER
        ACCESS  		read-only
        STATUS  		mandatory
        DESCRIPTION
            "E1/T1 module transmissions deferred (TDEF)."
	::= {e1t1Stats  13}


e1t1EthLCOL			OBJECT-TYPE
 	  SYNTAX  		INTEGER
        ACCESS  		read-only
        STATUS  		mandatory
        DESCRIPTION
            "E1/T1 module late collisions (LCOL)."
	::= {e1t1Stats  14}


e1t1FanStatus		OBJECT-TYPE
        SYNTAX  		INTEGER {
					off (1), -- fan off
					on (2)   -- fan on
				}
        ACCESS  		read-only
        STATUS  		mandatory
        DESCRIPTION
            "T1E1 Fan Status (off/on)."
	::= {e1t1Stats  15}


e1t1LastSaveErr		OBJECT-TYPE
 	  SYNTAX  		INTEGER
        ACCESS  		read-only
        STATUS  		mandatory
        DESCRIPTION
            "The Error code from the last TDM SAVE Command."
	::= {e1t1Stats  16}



-- ----------------------------------------------------------------------------
--
-- T1E1 Serial Table
--
-- ----------------------------------------------------------------------------

e1t1SerialTable	OBJECT-TYPE
	SYNTAX		SEQUENCE OF E1T1SerialEntry
	ACCESS		not-accessible
	STATUS		mandatory
	DESCRIPTION
		"Table T1 / E1 Channels."
	::= {redlineE1T1 2}

e1t1SerialEntry	OBJECT-TYPE
	SYNTAX		E1T1SerialEntry
	ACCESS		not-accessible
	STATUS		mandatory
	DESCRIPTION
		"A unique set of link parameters."
	INDEX	{e1t1SerialID}

	::= {e1t1SerialTable 1}

E1T1SerialEntry ::=
	SEQUENCE  {
		e1t1SerialID		INTEGER,
		e1t1SerialCoding		INTEGER,
		e1t1SerialFraming		INTEGER,
		e1t1SerialLBO		INTEGER
	}

e1t1SerialID		OBJECT-TYPE
	SYNTAX		INTEGER(1..4)
	ACCESS		read-only
	STATUS		mandatory
	DESCRIPTION
		"Serial ID."
	::= {e1t1SerialEntry 1}

e1t1SerialCoding	OBJECT-TYPE
	SYNTAX		INTEGER(1..128)
	ACCESS		read-write
	STATUS		mandatory
	DESCRIPTION
		"Serial Coding."
	::= {e1t1SerialEntry 2}

e1t1SerialFraming	OBJECT-TYPE
	SYNTAX		INTEGER(1..128)
	ACCESS		read-write
	STATUS		mandatory
	DESCRIPTION
		"Serial Framing."
	::= {e1t1SerialEntry 3}

e1t1SerialLBO		OBJECT-TYPE
	SYNTAX		INTEGER(1..128)
	ACCESS		read-write
	STATUS		mandatory
	DESCRIPTION
		"Serial LBO."
	::= {e1t1SerialEntry 4}


-- ----------------------------------------------------------------------------
--
-- T1E1 Group Table
--
-- ----------------------------------------------------------------------------

e1t1GroupTable	OBJECT-TYPE
	SYNTAX	SEQUENCE OF E1T1GroupEntry
	ACCESS	not-accessible
	STATUS	mandatory
	DESCRIPTION
		"Table E1 Groups."
	::= {redlineE1T1 3}

e1t1GroupEntry	OBJECT-TYPE
	SYNTAX	E1T1GroupEntry
	ACCESS	not-accessible
	STATUS	mandatory
	DESCRIPTION
		"A unique set of link parameters."
	INDEX	{e1t1GroupID}

	::= {e1t1GroupTable 1}

E1T1GroupEntry ::=
	SEQUENCE  {
		e1t1GroupID				INTEGER,
		e1t1GroupTsBegin 			INTEGER,
		e1t1GroupTsNum			INTEGER,
		e1t1GroupDestGroup 		INTEGER,
		e1t1GroupDestIp			IpAddress,
		e1t1GroupJitterBuffer		INTEGER,
		e1t1GroupPacketLength		INTEGER,
   		e1t1GroupRowStatus		RowStatus
	}


e1t1GroupID	OBJECT-TYPE
	SYNTAX		INTEGER(0..127)
	ACCESS		read-only
	STATUS		mandatory
	DESCRIPTION
		"Group ID."
	::= {e1t1GroupEntry 1}

e1t1GroupTsBegin		OBJECT-TYPE
	SYNTAX		INTEGER(0..255)
	ACCESS		read-write
	STATUS		mandatory
	DESCRIPTION
		"Group Ts Begin."
	::= {e1t1GroupEntry 2}

e1t1GroupTsNum		OBJECT-TYPE
	SYNTAX		INTEGER(0..255)
	ACCESS		read-write
	STATUS		mandatory
	DESCRIPTION
		"Group Ts Num."
	::= {e1t1GroupEntry 3}

e1t1GroupDestGroup	OBJECT-TYPE
	SYNTAX		INTEGER(0..255)
	ACCESS		read-write
	STATUS		mandatory
	DESCRIPTION
		"Group Destination."
	::= {e1t1GroupEntry 4}

e1t1GroupDestIp		OBJECT-TYPE
	SYNTAX		IpAddress
	ACCESS		read-write
	STATUS		mandatory
	DESCRIPTION
		"Group Destination Ip Address."
	::= {e1t1GroupEntry 5}

e1t1GroupJitterBuffer	OBJECT-TYPE
	SYNTAX		INTEGER(10..300)
	ACCESS		read-write
	STATUS		mandatory
	DESCRIPTION
		"Group Jitter Buffer in ms."
	::= {e1t1GroupEntry 6}

e1t1GroupPacketLength	OBJECT-TYPE
	SYNTAX		INTEGER(64..1024)
	ACCESS		read-write
	STATUS		mandatory
	DESCRIPTION
		"Group Jitter Buffer in bytes."
	::= {e1t1GroupEntry 7}

e1t1GroupRowStatus	OBJECT-TYPE
	SYNTAX		RowStatus
	ACCESS		read-write
	STATUS		mandatory
	DESCRIPTION
		"Status of the row."
	::= {e1t1GroupEntry 8}

-- ----------------------------------------------------------------------------
--
-- T1E1 Serial Status Table
--
-- ----------------------------------------------------------------------------

e1t1StatsTable		OBJECT-TYPE
	SYNTAX		SEQUENCE OF E1T1StatsEntry
	ACCESS		not-accessible
	STATUS		mandatory
	DESCRIPTION
		"Table of statistics for E1/T1 interfaces."
	::= {redlineE1T1 4}

e1t1StatsEntry		OBJECT-TYPE
	SYNTAX		E1T1StatsEntry
	ACCESS		not-accessible
	STATUS		mandatory
	DESCRIPTION
		"A unique set of statistics of link parameters."
	INDEX	{e1t1SerialStatsID}

	::= {e1t1StatsTable 1}

E1T1StatsEntry ::=
	SEQUENCE  {
		e1t1SerialStatsID		INTEGER,
		e1t1TdmsLOS			INTEGER,
		e1t1TdmsLFA			INTEGER,
		e1t1TdmsLOMF		INTEGER,
		e1t1TdmsRAI			INTEGER,
		e1t1TdmsAIS			INTEGER,
		e1t1TdmsES			INTEGER,
		e1t1TdmsFEC			INTEGER,
		e1t1TdmsCVC			INTEGER
	}

e1t1SerialStatsID		OBJECT-TYPE
	SYNTAX		INTEGER(1..4)
	ACCESS		read-only
	STATUS		mandatory
	DESCRIPTION
		"Serial Interface Statistics ID."
	::= {e1t1StatsEntry 1}

e1t1TdmsLOS		OBJECT-TYPE
	SYNTAX	INTEGER
	ACCESS	read-only
	STATUS	mandatory
	DESCRIPTION
		"E1/T1 module loss of signal."
	::= {e1t1StatsEntry 2}

e1t1TdmsLFA		OBJECT-TYPE
	SYNTAX	INTEGER
	ACCESS	read-only
	STATUS	mandatory
	DESCRIPTION
		"E1/T1 module loss of framing alignment."
	::= {e1t1StatsEntry 3}

e1t1TdmsLOMF	OBJECT-TYPE
	SYNTAX	INTEGER
	ACCESS	read-only
	STATUS	mandatory
	DESCRIPTION
		"E1/T1 module loss of multiframming."
	::= {e1t1StatsEntry 4}

e1t1TdmsRAI		OBJECT-TYPE
	SYNTAX	INTEGER
	ACCESS	read-only
	STATUS	mandatory
	DESCRIPTION
		"E1/T1 module remote alarm indication."
	::= {e1t1StatsEntry 5}

e1t1TdmsAIS		OBJECT-TYPE
	SYNTAX	INTEGER
	ACCESS	read-only
	STATUS	mandatory
	DESCRIPTION
		"E1/T1 module alarm indication signal."
	::= {e1t1StatsEntry 6}

e1t1TdmsES		OBJECT-TYPE
	SYNTAX	INTEGER
	ACCESS	read-only
	STATUS	mandatory
	DESCRIPTION
		"E1/T1 module errored seconds."
	::= {e1t1StatsEntry 7}

e1t1TdmsFEC		OBJECT-TYPE
	SYNTAX	INTEGER
	ACCESS	read-only
	STATUS	mandatory
	DESCRIPTION
		"E1/T1 module framing error counter."
	::= {e1t1StatsEntry 8}

e1t1TdmsCVC		OBJECT-TYPE
	SYNTAX	INTEGER
	ACCESS	read-only
	STATUS	mandatory
	DESCRIPTION
		"E1/T1 module code violation counter."
	::= {e1t1StatsEntry 9}

END
