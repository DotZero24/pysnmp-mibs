REDLINE-SYSTEM-MIB DEFINITIONS ::= BEGIN

IMPORTS
	redlineSystem
		FROM REDLINE-MIB
	MODULE-IDENTITY,
	OBJECT-TYPE,
	NOTIFICATION-TYPE,
	Unsigned32
		FROM SNMPv2-SMI
	OBJECT-GROUP,
	NOTIFICATION-GROUP,
	MODULE-COMPLIANCE
		FROM SNMPv2-CONF
	DateAndTime,
	DisplayString,
	RowStatus
		FROM SNMPv2-TC
	InetAddress,
	InetAddressType,
	InetPortNumber
		FROM INET-ADDRESS-MIB;

redlineSystemMib MODULE-IDENTITY
	LAST-UPDATED "200503311543Z"
	ORGANIZATION "Redline Communications Inc."
	CONTACT-INFO
		"Marek Koziol
		email: mkoziol@redlinecommunications.com"
	DESCRIPTION
		"This MIB module contains Redline extensions
		to the SNMPv2 MIB System Group."
	REVISION "200503311543Z"
	DESCRIPTION
		"Initial version."
	::= { redlineSystem 1 }


-- Scalars and Tables
--

redlineSystemSystemObjects OBJECT IDENTIFIER 	::= { redlineSystemMib 1 }

redlineSystemSerialNumber OBJECT-TYPE
	SYNTAX  DisplayString (SIZE (0..32))
	MAX-ACCESS read-only
	STATUS current
	DESCRIPTION
		"The serial number of the unit."
	::= { redlineSystemSystemObjects 1 }


-- system control variables

redlineSystemSysControl OBJECT IDENTIFIER 	::= { redlineSystemSystemObjects 2 }

redlineSystemSystemReboot OBJECT-TYPE
	SYNTAX  INTEGER {
			noop(1),
			reboot(2) }
	MAX-ACCESS read-write
	STATUS current
	DESCRIPTION
		"Setting this variable to 2 causes a reboot of the system."
	::= { redlineSystemSysControl 1 }


-- system dhcp variables

redlineSystemSysDhcpObjects OBJECT IDENTIFIER 	::= { redlineSystemSystemObjects 3 }


redlineSystemDHCPServerIpAddressType OBJECT-TYPE
	SYNTAX  InetAddressType
	MAX-ACCESS read-write
	STATUS current
	DESCRIPTION
		"The INET address type of Ip address of DHCP server.
		IPv4 type supported only."
	::= { redlineSystemSysDhcpObjects 1 }


redlineSystemDHCPServerIpAddress OBJECT-TYPE
	SYNTAX  InetAddress
	MAX-ACCESS read-write
	STATUS current
	DESCRIPTION
		"The INET address of DHCP server.

                 Note: This object can not be set if usage of
                 DHCP server is disabled. An attempt to set the
                 address will fail and return 'resourceUnavailable'
                 error"
	::= { redlineSystemSysDhcpObjects 2 }


-- system ip variables

redlineSystemSysIpObjects OBJECT IDENTIFIER 	::= { redlineSystemSystemObjects 4 }

redlineSystemIpAddressType OBJECT-TYPE
	SYNTAX  InetAddressType
	MAX-ACCESS read-write
	STATUS current
	DESCRIPTION
		"The INET address type of Ip address of the system.
		IPv4 type supported only."
	::= { redlineSystemSysIpObjects 1 }


redlineSystemIpAddress OBJECT-TYPE
	SYNTAX  InetAddress
	MAX-ACCESS read-write
	STATUS current
	DESCRIPTION
		"The INET address of the system.

                 Note: This object can not be set if usage of
                 DHCP server is enabled. An attempt to set the
                 address will fail and return 'resourceUnavailable'
                 error"
	::= { redlineSystemSysIpObjects 2 }

redlineSystemSubnetMaskAddressType OBJECT-TYPE
	SYNTAX  InetAddressType
	MAX-ACCESS read-write
	STATUS current
	DESCRIPTION
		"The INET address type of subnet mask of the system.
		IPv4 type supported only."
	::= { redlineSystemSysIpObjects 3 }


redlineSystemSubnetMask OBJECT-TYPE
	SYNTAX  InetAddress
	MAX-ACCESS read-write
	STATUS current
	DESCRIPTION
		"The Subnet Mask of the system.

                 Note: This object can not be set if usage of
                 DHCP server is enabled. An attempt to set the
                 address will fail and return 'resourceUnavailable'
                 error"
	::= { redlineSystemSysIpObjects 4 }


redlineSystemDefGatewayAddressType OBJECT-TYPE
	SYNTAX  InetAddressType
	MAX-ACCESS read-write
	STATUS current
	DESCRIPTION
		"The INET address type of the default gateway.
		IPv4 type supported only."
	::= { redlineSystemSysIpObjects 5 }


redlineSystemDefGatewayAddress OBJECT-TYPE
	SYNTAX  InetAddress
	MAX-ACCESS read-write
	STATUS current
	DESCRIPTION
		"The INET address of the default gateway.

                 Note: This object can not be set if usage of
                 DHCP server is enabled. An attempt to set the
                 address will fail and return 'resourceUnavailable'
                 error"
	::= { redlineSystemSysIpObjects 6 }


-- system syslog variables

redlineSystemSysSyslogObjects OBJECT IDENTIFIER 	::= { redlineSystemSystemObjects 5 }


redlineSystemSyslogServerIpAddressType OBJECT-TYPE
	SYNTAX  InetAddressType
	MAX-ACCESS read-write
	STATUS current
	DESCRIPTION
		"The INET address type of Ip address of Syslog server.
		IPv4 type supported only."
	::= { redlineSystemSysSyslogObjects 1 }


redlineSystemSyslogServerIpAddress OBJECT-TYPE
	SYNTAX  InetAddress
	MAX-ACCESS read-write
	STATUS current
	DESCRIPTION
		"The INET address of Syslog server.

                 Note: Entering '0.0.0.0' as an address will indicate
                 to the system that Syslog capability is not to be used."
	::= { redlineSystemSysSyslogObjects 2 }


redlineSystemSoftwareObjects OBJECT IDENTIFIER 	::= { redlineSystemMib 2 }

redlineSystemSwActiveVersion OBJECT-TYPE
	SYNTAX  DisplayString (SIZE (0..32))
	MAX-ACCESS read-only
	STATUS current
	DESCRIPTION
		"The s/w version of the active (running) image."
	::= { redlineSystemSoftwareObjects 1 }


redlineSystemSwAlternateVersion OBJECT-TYPE
	SYNTAX  DisplayString (SIZE (0..32))
	MAX-ACCESS read-only
	STATUS current
	DESCRIPTION
		"The s/w version of the alternate (non-active) image."
	::= { redlineSystemSoftwareObjects 2 }


redlineSystemSwActivateAlternate OBJECT-TYPE
	SYNTAX  INTEGER {
			noop(1),
			activate(2) }
	MAX-ACCESS read-write
	STATUS current
	DESCRIPTION
		"Setting this to 2 triggers the switch-over to the alternate s/w image and
		reboot of the system. Before the switch-over a validation of the alternate
		image is performed and if it fails the 'inconsistentValue' error status is
		returned."
	::= { redlineSystemSoftwareObjects 3 }


redlineSystemSwSyncAlternateTable OBJECT-TYPE
	SYNTAX  SEQUENCE OF RedlineSystemSwSyncAlternateEntry
	MAX-ACCESS not-accessible
	STATUS current
	DESCRIPTION
		"This table contains at most one entry representing a software
		synchronization process that is either currently in progress or one
		that was completed. When requested synchronization,the active s/w i
		image and the active configuration are copied to the alternate s/w
		image and configuration, respectively.
		A management station can create this entry if and only if either the table
		is empty or the only entry is for a synchronization that has already been
		completed.
		An attempt to create or write this entry when a synchronization is
		already in progress results in the 'resourceUnavailable' error status.
		The redlineSystemSwSyncAlternateStatus state object is used to control
		and monitor a s/w synchronization process. Setting it to the
		'synchronizeAlternate' value starts a new synchronization if none is active
		at the time (otherwise an error status is returned)."
	::= { redlineSystemSoftwareObjects 4 }


redlineSystemSwSyncAlternateEntry OBJECT-TYPE
	SYNTAX  RedlineSystemSwSyncAlternateEntry
	MAX-ACCESS not-accessible
	STATUS current
	DESCRIPTION
		"This entry contains information about a current or last
		software synchronization."
	INDEX {
		redlineSystemSwSyncAlternateIndex }
	::= { redlineSystemSwSyncAlternateTable 1 }


RedlineSystemSwSyncAlternateEntry ::= SEQUENCE {

	redlineSystemSwSyncAlternateIndex          INTEGER,
	redlineSystemSwSyncAlternate               INTEGER,
	redlineSystemSwSyncAlternateStatus         INTEGER,
	redlineSystemSwSyncAlternateTimeEnded      DateAndTime }


redlineSystemSwSyncAlternateIndex OBJECT-TYPE
	SYNTAX  INTEGER (1)
	MAX-ACCESS not-accessible
	STATUS current
	DESCRIPTION
		"The index of the software isynchronization table.
		The only value allowed is 1."
	::= { redlineSystemSwSyncAlternateEntry 1 }


redlineSystemSwSyncAlternate OBJECT-TYPE
	SYNTAX  INTEGER {
			noop(1),
			synchronizeAlternate(2) }
	MAX-ACCESS read-write
	STATUS current
	DESCRIPTION
		"Setting it to 2 will synchronize the alternate s/w image and
		configuration database, i.e. the active s/w image and the active
		configuration are copied to the alternate s/w image and
		configuration, respectively."
	::= { redlineSystemSwSyncAlternateEntry 2 }


redlineSystemSwSyncAlternateStatus OBJECT-TYPE
	SYNTAX  INTEGER {
			inProgress(1), 	-- sw synchronization is in progress
			success(2),  	-- sw synchronization completed successfully
			failed(3)   	-- sw synchronization failed
			}
	MAX-ACCESS read-only
	STATUS current
	DESCRIPTION
		"The status of the current or last software synchronization."
	::= { redlineSystemSwSyncAlternateEntry 3 }


redlineSystemSwSyncAlternateTimeEnded OBJECT-TYPE
	SYNTAX  DateAndTime
	MAX-ACCESS read-only
	STATUS current
	DESCRIPTION
		"The date and time this software synchronization finished."
	::= { redlineSystemSwSyncAlternateEntry 4 }


redlineSystemSwDownloadTable OBJECT-TYPE
	SYNTAX  SEQUENCE OF RedlineSystemSwDownloadEntry
	MAX-ACCESS not-accessible
	STATUS current
	DESCRIPTION
		"This table contains at most one entry representing a software download
		process that is either currently in progress or one that was completed.
		A management station can create this entry if and only if either the table
		is empty or the only entry is for a download that has already been
		completed.
		An attempt to create or write this entry when a download is already in
		progress results in the 'resourceUnavailable' error status.
		The redlineSystemSwDownloadStatus state object is used to
		control and monitor a s/w download process. Setting it to the 'download'
		value starts a new download if none is active at the time (otherwise
		an error status is returned)."
	::= { redlineSystemSoftwareObjects 5 }


redlineSystemSwDownloadEntry OBJECT-TYPE
	SYNTAX  RedlineSystemSwDownloadEntry
	MAX-ACCESS not-accessible
	STATUS current
	DESCRIPTION
		"This entry contains information about a current or last
		software download."
	INDEX {
		redlineSystemSwDownloadIndex }
	::= { redlineSystemSwDownloadTable 1 }


RedlineSystemSwDownloadEntry ::= SEQUENCE {

	redlineSystemSwDownloadIndex          INTEGER,
	redlineSystemSwDownloadFtpAddressType InetAddressType,
	redlineSystemSwDownloadFtpAddress     InetAddress,
	redlineSystemSwDownloadFtpUser        DisplayString,
	redlineSystemSwDownloadFtpPassword    DisplayString,
	redlineSystemSwDownloadFtpFile        DisplayString,
	redlineSystemSwDownloadStatus         INTEGER,
	redlineSystemSwDownloadTimeEnded      DateAndTime,
	redlineSystemSwDownloadFailureReason  DisplayString }


redlineSystemSwDownloadIndex OBJECT-TYPE
	SYNTAX  INTEGER (1)
	MAX-ACCESS not-accessible
	STATUS current
	DESCRIPTION
		"The index of the software download table.
		The only value allowed is 1."
	::= { redlineSystemSwDownloadEntry 1 }


redlineSystemSwDownloadFtpAddressType OBJECT-TYPE
	SYNTAX  InetAddressType
	MAX-ACCESS read-create
	STATUS current
	DESCRIPTION
		"The INET address type of the software upgrade FTP server.
		IPv4 type supported only."
	::= { redlineSystemSwDownloadEntry 2 }


redlineSystemSwDownloadFtpAddress OBJECT-TYPE
	SYNTAX  InetAddress
	MAX-ACCESS read-create
	STATUS current
	DESCRIPTION
		"The INET address of the FTP server."
	::= { redlineSystemSwDownloadEntry 3 }


redlineSystemSwDownloadFtpUser OBJECT-TYPE
	SYNTAX  DisplayString (SIZE (0..32))
	MAX-ACCESS read-create
	STATUS current
	DESCRIPTION
		"The FTP user name."
	::= { redlineSystemSwDownloadEntry 4 }


redlineSystemSwDownloadFtpPassword OBJECT-TYPE
	SYNTAX  DisplayString (SIZE (0..32))
	MAX-ACCESS read-create
	STATUS current
	DESCRIPTION
		"The FTP user password. After this object is created
		it is not accessible."
	::= { redlineSystemSwDownloadEntry 5 }


redlineSystemSwDownloadFtpFile OBJECT-TYPE
	SYNTAX  DisplayString (SIZE (0..255))
	MAX-ACCESS read-create
	STATUS current
	DESCRIPTION
		"The full software image file path name as required
		by the FTP server."
	::= { redlineSystemSwDownloadEntry 6 }


redlineSystemSwDownloadStatus OBJECT-TYPE
	SYNTAX  INTEGER {
			download(1), 	-- start ftp download/download is in progress
			validate(2), 	-- downloaded image is being validated
			commit(3),   	-- image is being saved in non-volatile memory
			success(4),  	-- download completed successfully
			failed(5)   	-- download failed
			}
	MAX-ACCESS read-only
	STATUS current
	DESCRIPTION
		"The status of the current or last software download."
	::= { redlineSystemSwDownloadEntry 7 }


redlineSystemSwDownloadTimeEnded OBJECT-TYPE
	SYNTAX  DateAndTime
	MAX-ACCESS read-only
	STATUS current
	DESCRIPTION
		"The date and time this software download finished."
	::= { redlineSystemSwDownloadEntry 8 }


redlineSystemSwDownloadFailureReason OBJECT-TYPE
	SYNTAX  DisplayString (SIZE (0..255))
	MAX-ACCESS read-only
	STATUS current
	DESCRIPTION
		"The short explanation of why software download failed.
		In a case of success this object will contain empty string."
	::= { redlineSystemSwDownloadEntry 9 }

redlineSystemConfigurationObjects OBJECT IDENTIFIER 	::= { redlineSystemMib 3}

redlineSystemConfigBackupTable OBJECT-TYPE
	SYNTAX  SEQUENCE OF RedlineSystemConfigBackupEntry
	MAX-ACCESS not-accessible
	STATUS current
	DESCRIPTION
		"This table contains at most one entry representing a configuration
		backup process that is either currently in progress or one that was
		completed. A management station can create this entry if and only if
		either the table is empty or the only entry is for a backup that has
		already been completed. An attempt to create or write this entry
		when a backup is already in progress results in the 'resourceUnavailable'
		error status."
	::= { redlineSystemConfigurationObjects 1 }


redlineSystemConfigBackupEntry OBJECT-TYPE
	SYNTAX  RedlineSystemConfigBackupEntry
	MAX-ACCESS not-accessible
	STATUS current
	DESCRIPTION
		"This entry contains information about a current or last
		configuration backup."
	INDEX {
		redlineSystemConfigBackupIndex }
	::= { redlineSystemConfigBackupTable 1 }


RedlineSystemConfigBackupEntry ::= SEQUENCE {

	redlineSystemConfigBackupIndex          INTEGER,
	redlineSystemConfigBackupConfigType     INTEGER,
	redlineSystemConfigBackupFtpAddressType InetAddressType,
	redlineSystemConfigBackupFtpAddress     InetAddress,
	redlineSystemConfigBackupFtpUser        DisplayString,
	redlineSystemConfigBackupFtpPassword    DisplayString,
	redlineSystemConfigBackupFtpFile        DisplayString,
	redlineSystemConfigBackupStatus         INTEGER,
	redlineSystemConfigBackupFailureReason  DisplayString }


redlineSystemConfigBackupIndex OBJECT-TYPE
	SYNTAX  INTEGER (1)
	MAX-ACCESS not-accessible
	STATUS current
	DESCRIPTION
		"The index of the software download table.
		The only value allowed is 1."
	::= { redlineSystemConfigBackupEntry 1 }


redlineSystemConfigBackupConfigType OBJECT-TYPE
	SYNTAX  INTEGER {
			active(1),
			alternate(2)
			}
	MAX-ACCESS read-create
	STATUS current
	DESCRIPTION
		"Specifies the type of configuration to be backup."
	::= { redlineSystemConfigBackupEntry 2 }


redlineSystemConfigBackupFtpAddressType OBJECT-TYPE
	SYNTAX  InetAddressType
	MAX-ACCESS read-create
	STATUS current
	DESCRIPTION
		"The INET address type of the configuration backup
		FTP server.  IPv4 type supported only."
	::= { redlineSystemConfigBackupEntry 3 }


redlineSystemConfigBackupFtpAddress OBJECT-TYPE
	SYNTAX  InetAddress
	MAX-ACCESS read-create
	STATUS current
	DESCRIPTION
		"The INET address of the FTP server."
	::= { redlineSystemConfigBackupEntry 4 }


redlineSystemConfigBackupFtpUser OBJECT-TYPE
	SYNTAX  DisplayString (SIZE (0..32))
	MAX-ACCESS read-create
	STATUS current
	DESCRIPTION
		"The FTP user name."
	::= { redlineSystemConfigBackupEntry 5 }


redlineSystemConfigBackupFtpPassword OBJECT-TYPE
	SYNTAX  DisplayString (SIZE (0..32))
	MAX-ACCESS read-create
	STATUS current
	DESCRIPTION
		"The FTP user password. After this object is created
		it is not accessible."
	::= { redlineSystemConfigBackupEntry 6 }


redlineSystemConfigBackupFtpFile OBJECT-TYPE
	SYNTAX  DisplayString (SIZE (0..255))
	MAX-ACCESS read-create
	STATUS current
	DESCRIPTION
		"The full software image file path name as required
		by the FTP server."
	::= { redlineSystemConfigBackupEntry 7 }


redlineSystemConfigBackupStatus OBJECT-TYPE
	SYNTAX  INTEGER {
                        backup(1),   -- start backup/the request was received by system
			commit(2),   -- configuration reading is in progress
			upload(3),   -- config uploading on server is in progress
			success(4),  -- backup completed successfully
			failed(5)    -- backup failed
			}
	MAX-ACCESS read-only
	STATUS current
	DESCRIPTION
		"The status of the current or last configuration backup."
	::= { redlineSystemConfigBackupEntry 8 }


redlineSystemConfigBackupFailureReason OBJECT-TYPE
	SYNTAX  DisplayString (SIZE (0..255))
	MAX-ACCESS read-only
	STATUS current
	DESCRIPTION
		"The short explanation of why configuration backup failed.
		In a case of success this object will contain empty string."
	::= { redlineSystemConfigBackupEntry 9 }


redlineSystemConfigRestoreTable OBJECT-TYPE
	SYNTAX  SEQUENCE OF RedlineSystemConfigRestoreEntry
	MAX-ACCESS not-accessible
	STATUS current
	DESCRIPTION
		"This table contains at most one entry representing a configuration
		restore process that is either currently in progress or one
		that was completed. A management station can create this entry if and
		only if either the table is empty or the only entry is for a restore
		that has already been completed. An attempt to create or write this
		entry when a restore is already in progress results in the
		'resourceUnavailable' error status. After the process is finished with
		the status set to 'success', then (and only then) the system will be
		automatically rebooted in order for the newly restored parameters to
		become active."
	::= { redlineSystemConfigurationObjects 2 }


redlineSystemConfigRestoreEntry OBJECT-TYPE
	SYNTAX  RedlineSystemConfigRestoreEntry
	MAX-ACCESS not-accessible
	STATUS current
	DESCRIPTION
		"This entry contains information about a current or last
		configuration restore."
	INDEX {
		redlineSystemConfigRestoreIndex }
	::= { redlineSystemConfigRestoreTable 1 }


RedlineSystemConfigRestoreEntry ::= SEQUENCE {

	redlineSystemConfigRestoreIndex          INTEGER,
	redlineSystemConfigRestoreConfigType     INTEGER,
	redlineSystemConfigRestoreFtpAddressType InetAddressType,
	redlineSystemConfigRestoreFtpAddress     InetAddress,
	redlineSystemConfigRestoreFtpUser        DisplayString,
	redlineSystemConfigRestoreFtpPassword    DisplayString,
	redlineSystemConfigRestoreFtpFile        DisplayString,
	redlineSystemConfigRestoreStatus         INTEGER,
	redlineSystemConfigRestoreFailureReason  DisplayString }


redlineSystemConfigRestoreIndex OBJECT-TYPE
	SYNTAX  INTEGER (1)
	MAX-ACCESS not-accessible
	STATUS current
	DESCRIPTION
		"The index of the software download table.
		The only value allowed is 1."
	::= { redlineSystemConfigRestoreEntry 1 }


redlineSystemConfigRestoreConfigType OBJECT-TYPE
	SYNTAX  INTEGER {
			active(1),
			alternate(2)
			}
	MAX-ACCESS read-create
	STATUS current
	DESCRIPTION
		"Specifies the type of configuration to be restored."
	::= { redlineSystemConfigRestoreEntry 2 }


redlineSystemConfigRestoreFtpAddressType OBJECT-TYPE
	SYNTAX  InetAddressType
	MAX-ACCESS read-create
	STATUS current
	DESCRIPTION
		"The INET address type of the configuration restore
		FTP server.  IPv4 type supported only."
	::= { redlineSystemConfigRestoreEntry 3 }


redlineSystemConfigRestoreFtpAddress OBJECT-TYPE
	SYNTAX  InetAddress
	MAX-ACCESS read-create
	STATUS current
	DESCRIPTION
		"The INET address of the FTP server."
	::= { redlineSystemConfigRestoreEntry 4 }


redlineSystemConfigRestoreFtpUser OBJECT-TYPE
	SYNTAX  DisplayString (SIZE (0..32))
	MAX-ACCESS read-create
	STATUS current
	DESCRIPTION
		"The FTP user name."
	::= { redlineSystemConfigRestoreEntry 5 }


redlineSystemConfigRestoreFtpPassword OBJECT-TYPE
	SYNTAX  DisplayString (SIZE (0..32))
	MAX-ACCESS read-create
	STATUS current
	DESCRIPTION
		"The FTP user password. After this object is created
		it is not accessible."
	::= { redlineSystemConfigRestoreEntry 6 }


redlineSystemConfigRestoreFtpFile OBJECT-TYPE
	SYNTAX  DisplayString (SIZE (0..255))
	MAX-ACCESS read-create
	STATUS current
	DESCRIPTION
		"The full software image file path name as required
		by the FTP server."
	::= { redlineSystemConfigRestoreEntry 7 }


redlineSystemConfigRestoreStatus OBJECT-TYPE
	SYNTAX  INTEGER {
			restore(1), 	-- start restore/the request was received by system
			download(2), 	-- config download in progress
			write(3), 	-- restored config writing
			success(4),  	-- restore completed successfully
			failed(5)   	-- restore failed
			}
	MAX-ACCESS read-only
	STATUS current
	DESCRIPTION
		"The status of the current or last configuration restore."
	::= { redlineSystemConfigRestoreEntry 8 }


redlineSystemConfigRestoreFailureReason OBJECT-TYPE
	SYNTAX  DisplayString (SIZE (0..255))
	MAX-ACCESS read-only
	STATUS current
	DESCRIPTION
		"The short explanation of why configuration restore failed.
		In a case of success this object will contain empty string."
	::= { redlineSystemConfigRestoreEntry 9 }


redlineSystemNotificationObjects OBJECT IDENTIFIER 	::= { redlineSystemMib 4 }

-- prefix for notification control objects

redlineSystemTrapControl OBJECT IDENTIFIER 	::= { redlineSystemNotificationObjects 1 }

-- Prefix for trap-specific objects.

redlineSystemTrapObjects OBJECT IDENTIFIER 	::= { redlineSystemNotificationObjects 2 }

redlineSystemTrapReceiverTable OBJECT-TYPE
	SYNTAX  SEQUENCE OF RedlineSystemTrapReceiverEntry
	MAX-ACCESS not-accessible
	STATUS current
	DESCRIPTION
		"This table contains information about provisioned
		trap receivers i.e. the trap receivers that this agent
		will send notifications to. The entries of this table
		are indexed by their IP address and port values.
		The maximum number of entries in this table is eight."
	::= { redlineSystemTrapControl 1 }


redlineSystemTrapReceiverEntry OBJECT-TYPE
	SYNTAX  RedlineSystemTrapReceiverEntry
	MAX-ACCESS not-accessible
	STATUS current
	DESCRIPTION
		"This entry contains information about a provisioned
		trap receiver (a trap destination from the agent's point
		of view."
	INDEX {
		redlineSystemTrapReceiverIndex }
	::= { redlineSystemTrapReceiverTable 1 }


RedlineSystemTrapReceiverEntry ::= SEQUENCE {

	redlineSystemTrapReceiverIndex       Unsigned32,
	redlineSystemTrapReceiverAddressType InetAddressType,
	redlineSystemTrapReceiverAddress     InetAddress,
	redlineSystemTrapReceiverPort        InetPortNumber,
	redlineSystemTrapReceiverCommunity   DisplayString,
	redlineSystemTrapReceiverStatus      RowStatus }


redlineSystemTrapReceiverIndex OBJECT-TYPE
	SYNTAX  Unsigned32
	MAX-ACCESS not-accessible
	STATUS current
	DESCRIPTION ""
	::= { redlineSystemTrapReceiverEntry 1 }


redlineSystemTrapReceiverAddressType OBJECT-TYPE
	SYNTAX  InetAddressType
	MAX-ACCESS read-create
	STATUS current
	DESCRIPTION
		"The INET address type of the trap receiver."
	::= { redlineSystemTrapReceiverEntry 2 }


redlineSystemTrapReceiverAddress OBJECT-TYPE
	SYNTAX  InetAddress
	MAX-ACCESS read-create
	STATUS current
	DESCRIPTION
		"The INET address of the trap receiver."
	::= { redlineSystemTrapReceiverEntry 3 }


redlineSystemTrapReceiverPort OBJECT-TYPE
	SYNTAX  InetPortNumber (0..65535)
	MAX-ACCESS read-create
	STATUS current
	DESCRIPTION
		"The UDP port of the trap receiver."
	DEFVAL { 162 }
	::= { redlineSystemTrapReceiverEntry 4 }


redlineSystemTrapReceiverCommunity OBJECT-TYPE
	SYNTAX  DisplayString (SIZE (0..32))
	MAX-ACCESS read-create
	STATUS current
	DESCRIPTION
		"The community string of the trap receiver."
	::= { redlineSystemTrapReceiverEntry 5 }


redlineSystemTrapReceiverStatus OBJECT-TYPE
	SYNTAX  RowStatus
	MAX-ACCESS read-create
	STATUS current
	DESCRIPTION
		"This object is used to create and delete rows in the
		redlineSystemTrapReceiverTable table. Only the 'createAndGo'
		and 'destroy' values can be specified in a set operation
		when an entry is created or destroyed, respectively."
	::= { redlineSystemTrapReceiverEntry 6 }


redlineSystemTrapActivationTable OBJECT-TYPE
	SYNTAX  SEQUENCE OF RedlineSystemTrapActivationEntry
	MAX-ACCESS not-accessible
	STATUS current
	DESCRIPTION
		"This table contains information about trap activation
		in the system i.e. the trap generation can be enabled
		or disabled. The entries of this table are indexed by
		the trap OID."
	::= { redlineSystemTrapControl 2 }


redlineSystemTrapActivationEntry OBJECT-TYPE
	SYNTAX  RedlineSystemTrapActivationEntry
	MAX-ACCESS not-accessible
	STATUS current
	DESCRIPTION
		"This entry contains information about trap acgtivation
		state."
	INDEX { IMPLIED redlineSystemTrapObjectID }
	::= { redlineSystemTrapActivationTable 1 }


RedlineSystemTrapActivationEntry ::= SEQUENCE {

	redlineSystemTrapObjectID              OBJECT IDENTIFIER,
	redlineSystemTrapEnable                INTEGER }


redlineSystemTrapObjectID OBJECT-TYPE
	SYNTAX  OBJECT IDENTIFIER
	MAX-ACCESS not-accessible
	STATUS current
	DESCRIPTION "Identifies the trap which generation is to be
		    controlled by this entry."
	::= { redlineSystemTrapActivationEntry 1 }


redlineSystemTrapEnable OBJECT-TYPE
        SYNTAX  INTEGER {
                        enabled(1),
                        disabled(2) }
        MAX-ACCESS read-write
        STATUS current
        DESCRIPTION
                "Indicates whether the system is permitted to
                generate traps specified by this entry."
        ::= { redlineSystemTrapActivationEntry 2 }


redlineSystemPingTrapTrigger OBJECT-TYPE
	SYNTAX  INTEGER {
			idle(1),
			ping(2) }
	MAX-ACCESS read-write
	STATUS current
	DESCRIPTION
		"Causes a ping trap to be sent"
	::= { redlineSystemTrapControl 999 }


-- Trap-specific objects are registered under this node.

redlineSystemSwDownloadProgress OBJECT-TYPE
	SYNTAX  INTEGER {
			initiated(1), 	-- started ftp download
			downloaded(2), 	-- downloaded/started validation
			validated(3), 	-- validated/started saving in non-volatile memory
			committed(4),  	-- image saved in non-volatile memory
			failed(5)   	-- download failed
			}
    	MAX-ACCESS  accessible-for-notify
    	STATUS current
    	DESCRIPTION
        "The software download progress states."
	::= { redlineSystemTrapObjects 1 }

-- Trap definitions are registered under this node.

redlineSystemTrapDefinitions OBJECT IDENTIFIER 	::= { redlineSystemNotificationObjects 3 }

redlineSWUpgradeStatusTrap NOTIFICATION-TYPE
	OBJECTS {
		redlineSystemSwDownloadProgress }
	STATUS current
	DESCRIPTION
		"Event that reports SW Upgrade progress and status changes."
	::= { redlineSystemTrapDefinitions 1 }

redlineSystemPingTrap NOTIFICATION-TYPE
	STATUS current
	DESCRIPTION
		"A ping trap notification."
	::= { redlineSystemTrapDefinitions 999 }

-- Snmp Access Control Objects
--
redlineSystemAccessControlObjects OBJECT IDENTIFIER 	::= { redlineSystemMib 5 }

redlineSystemAccessCtrlTable OBJECT-TYPE
	SYNTAX  SEQUENCE OF RedlineSystemAccessCtrlEntry
	MAX-ACCESS not-accessible
	STATUS current
	DESCRIPTION
		" This table contains a list of hosts which are allowed to access
                  the system. Each entry associated with the host, has ip address
                  and read and write passwords. Only hosts identified by a right
                  combination of ipAddress and password will be allowed to access
                  the system. An entry can contain Ip address of '0.0.0.0'. In which
                  case all hosts using password associated with this address will
                  be granted access to the system. Initially, the table will contain
                  only one entry with Ip address set to '0.0.0.0', read community set
                  to 'public' and write community set to 'private'.

                  The maximum number of entries in this table is eight"
	::= { redlineSystemAccessControlObjects 5 }


redlineSystemAccessCtrlEntry OBJECT-TYPE
	SYNTAX  RedlineSystemAccessCtrlEntry
	MAX-ACCESS not-accessible
	STATUS current
	DESCRIPTION
		"This entry contains privacy information about a host allowed
                 to access the system."
	INDEX {
		redlineSystemAccessCtrlIndex }
	::= { redlineSystemAccessCtrlTable 1 }


RedlineSystemAccessCtrlEntry ::= SEQUENCE {

	redlineSystemAccessCtrlIndex                Unsigned32,
	redlineSystemAccessCtrlManagerIpAddrType    InetAddressType,
	redlineSystemAccessCtrlManagerIpAddr        InetAddress,
	redlineSystemAccessCtrlReadCommunity        DisplayString,
	redlineSystemAccessCtrlWriteCommunity       DisplayString,
        redlineSystemAccessCtrlStatus               RowStatus }


redlineSystemAccessCtrlIndex OBJECT-TYPE
	SYNTAX  Unsigned32 (1 .. 8)
	MAX-ACCESS not-accessible
	STATUS current
	DESCRIPTION
		"The index of the Snmp Access Control table."
	::= { redlineSystemAccessCtrlEntry 1 }


redlineSystemAccessCtrlManagerIpAddrType OBJECT-TYPE
	SYNTAX  InetAddressType
	MAX-ACCESS read-create
	STATUS current
	DESCRIPTION
		"The INET address type of the host allowed to access the system.
		IPv4 type supported only."
	::= { redlineSystemAccessCtrlEntry 2 }


redlineSystemAccessCtrlManagerIpAddr OBJECT-TYPE
	SYNTAX  InetAddress
	MAX-ACCESS read-create
	STATUS current
	DESCRIPTION
		"The INET address of the host allowed to access the system."
	::= { redlineSystemAccessCtrlEntry 3 }


redlineSystemAccessCtrlReadCommunity OBJECT-TYPE
	SYNTAX  DisplayString (SIZE (0..32))
	MAX-ACCESS read-create
	STATUS current
	DESCRIPTION
		"The read community string associated
                 with redlineSystemAccessCtrlManagerIpAddress."
	::= { redlineSystemAccessCtrlEntry 4 }


redlineSystemAccessCtrlWriteCommunity OBJECT-TYPE
	SYNTAX  DisplayString (SIZE (0..32))
	MAX-ACCESS read-create
	STATUS current
	DESCRIPTION
		"The write community string associated
                 with redlineSystemAccessCtrlManagerIpAddress."
	::= { redlineSystemAccessCtrlEntry 5 }


redlineSystemAccessCtrlStatus OBJECT-TYPE
	SYNTAX  RowStatus
	MAX-ACCESS read-create
	STATUS current
	DESCRIPTION
		"This object is used to create and delete rows in the
		redlineSystemTrapReceiverTable table. Only the 'createAndGo'
		and 'destroy' values can be specified in a set operation
		when an entry is created or destroyed, respectively."
	::= { redlineSystemAccessCtrlEntry 6 }

-- Conformance
--

redlineSystemConformance OBJECT IDENTIFIER 	::= { redlineSystemMib 6 }

-- Groups
--

redlineSystemGroups OBJECT IDENTIFIER 	::= { redlineSystemConformance 1 }

-- Compliance
--

redlineSystemCompls OBJECT IDENTIFIER 	::= { redlineSystemConformance 2 }

redlineSystemBasicGroup OBJECT-GROUP
	OBJECTS {
		redlineSystemSystemReboot,
		redlineSystemSerialNumber,
		redlineSystemTrapReceiverCommunity,
		redlineSystemTrapReceiverStatus,
		redlineSystemPingTrapTrigger,
		redlineSystemSwDownloadFtpAddress,
		redlineSystemSwDownloadFtpUser,
		redlineSystemSwDownloadFtpPassword,
		redlineSystemSwDownloadFtpFile,
		redlineSystemSwDownloadStatus,
		redlineSystemSwDownloadFailureReason,
		redlineSystemSwDownloadTimeEnded,
		redlineSystemSwDownloadFtpAddressType,
		redlineSystemSwActiveVersion,
		redlineSystemSwAlternateVersion,
		redlineSystemSwActivateAlternate,
		redlineSystemTrapReceiverAddressType,
		redlineSystemTrapReceiverAddress,
		redlineSystemTrapReceiverPort,
		redlineSystemTrapEnable,
		redlineSystemSwSyncAlternate,
		redlineSystemSwSyncAlternateStatus,
		redlineSystemDHCPServerIpAddressType,
		redlineSystemDHCPServerIpAddress,
		redlineSystemIpAddressType,
		redlineSystemIpAddress,
		redlineSystemSubnetMaskAddressType,
		redlineSystemSubnetMask,
		redlineSystemDefGatewayAddressType,
		redlineSystemDefGatewayAddress,
		redlineSystemSyslogServerIpAddressType,
		redlineSystemSyslogServerIpAddress,
		redlineSystemSwDownloadProgress,
		redlineSystemConfigBackupConfigType,
		redlineSystemConfigBackupFtpAddressType,
		redlineSystemConfigBackupFtpAddress,
		redlineSystemConfigBackupFtpUser,
		redlineSystemConfigBackupFtpPassword,
		redlineSystemConfigBackupFtpFile,
		redlineSystemConfigBackupStatus,
		redlineSystemConfigBackupFailureReason,
		redlineSystemConfigRestoreConfigType,
		redlineSystemConfigRestoreFtpAddressType,
		redlineSystemConfigRestoreFtpAddress,
		redlineSystemConfigRestoreFtpUser,
		redlineSystemConfigRestoreFtpPassword,
		redlineSystemConfigRestoreFtpFile,
		redlineSystemConfigRestoreStatus,
		redlineSystemConfigRestoreFailureReason,
		redlineSystemAccessCtrlManagerIpAddrType,
		redlineSystemAccessCtrlManagerIpAddr,
		redlineSystemAccessCtrlReadCommunity,
		redlineSystemAccessCtrlWriteCommunity }

	STATUS current
	DESCRIPTION
		"Basic objects."
	::= { redlineSystemGroups 1 }

redlineSystemNotificationGroup NOTIFICATION-GROUP
	NOTIFICATIONS {
		redlineSWUpgradeStatusTrap,
		redlineSystemPingTrap }
	STATUS current
	DESCRIPTION ""
	::= { redlineSystemGroups 2 }


redlineSystemCompliance MODULE-COMPLIANCE
	STATUS current
	DESCRIPTION
		"The compliance statement for SNMP entities that
		implement this MIB module."

	MODULE
	MANDATORY-GROUPS {
			redlineSystemBasicGroup }

	::= { redlineSystemCompls 1 }

END
