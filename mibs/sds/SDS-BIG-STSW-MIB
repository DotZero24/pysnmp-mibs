SDS-BIG-STSW-MIB DEFINITIONS ::= BEGIN

IMPORTS
     MODULE-IDENTITY, OBJECT-TYPE,
     Counter32, Integer32, Gauge32,
     TimeTicks, IpAddress,
     enterprises
    FROM SNMPv2-SMI;


mib-AN-Dcz-SDS MODULE-IDENTITY
    LAST-UPDATED "202012101800Z"
    ORGANIZATION "AN-D.cz"
    CONTACT-INFO
            "   Adam Nemcek
                AN-D.cz
                -
                -
                CZ EUROPE

                -
                adam.nemcek@an-d.cz"
    DESCRIPTION
            "The MIB module to describe generic objects for AN-D.cz devices - SDS BIG and SDS STSW (and all the sub-variants using the STSW module), firmware of Q4-2019 and newer."


    REVISION      "202012100000Z"
    DESCRIPTION
            "Eight revision, by AN-D.cz."
    ::= { enterprises 33283 }


--
-- MIB file definition for all devices: SDS-BIG - STSW - MINI
--

sdsxpublic OBJECT IDENTIFIER ::= { mib-AN-Dcz-SDS 1 }

sdsBIGandSTSW   OBJECT IDENTIFIER ::= { sdsxpublic 30 }

-- ****************************************************************************

sdsIPWatchdog OBJECT IDENTIFIER ::= { sdsBIGandSTSW 1 }

ipwActive OBJECT-TYPE
    SYNTAX  INTEGER {
                disabled(0),
                active(255)
            }
    MAX-ACCESS  read-only
    STATUS      current
    DESCRIPTION
            "The current IP watchdog status."
    ::= { sdsIPWatchdog 1 }

ipwPingIP OBJECT-TYPE
    SYNTAX      IpAddress
    MAX-ACCESS  read-only
    STATUS      current
    DESCRIPTION
            "IP address of the wdg-monitored object."
    ::= { sdsIPWatchdog 2 }

ipwPauseAfterPwOn OBJECT-TYPE
    SYNTAX Integer32
    MAX-ACCESS  read-only
    STATUS      current
    DESCRIPTION
            "Amount of time in [sec]. Duration of the IP watchdog disable period, applied when watchdog device itself is first powered on."
    ::= { sdsIPWatchdog 3 }

ipwPingTimeout OBJECT-TYPE
    SYNTAX Integer32
    MAX-ACCESS  read-only
    STATUS      current
    DESCRIPTION
            "Config value - the RTT timeout."
    ::= { sdsIPWatchdog 4 }

ipwRepeatPingPer OBJECT-TYPE
    SYNTAX Integer32
    MAX-ACCESS  read-only
    STATUS      current
    DESCRIPTION
            "PING REQUEST packet sending: the configured send repeat period, in [miliseconds]."
    ::= { sdsIPWatchdog 5 }

ipwIgnoreLostCnt OBJECT-TYPE
    SYNTAX Gauge32
    MAX-ACCESS  read-only
    STATUS      current
    DESCRIPTION
            "How many lost PING REPLY packets should get ignored, before activating the relay."
    ::= { sdsIPWatchdog 6 }

ipwPauseWdAfterAct OBJECT-TYPE
    SYNTAX Integer32
    MAX-ACCESS  read-only
    STATUS      current
    DESCRIPTION
            "Delay of the IP watchdog pause, applied when the output relay is activated (e.g. the time for controlled device recovery)."
    ::= { sdsIPWatchdog 7 }

ipwRelayActTime OBJECT-TYPE
    SYNTAX Integer32
    MAX-ACCESS  read-only
    STATUS      current
    DESCRIPTION
            "How many [seconds] should be the output relay activated."
    ::= { sdsIPWatchdog 8 }

ipwActualFailed OBJECT-TYPE
    SYNTAX Gauge32
    MAX-ACCESS  read-only
    STATUS      current
    DESCRIPTION
            "How many unreceived PING REPLY packets are detected so far."
    ::= { sdsIPWatchdog 9 }

ipwLastRTT OBJECT-TYPE
    SYNTAX Gauge32
    MAX-ACCESS  read-only
    STATUS      current
    DESCRIPTION
            "Round Trip Time for the last ping echo."
    ::= { sdsIPWatchdog 10 }

ipwActualRelayState OBJECT-TYPE
    SYNTAX Integer32
    MAX-ACCESS  read-only
    STATUS      current
    DESCRIPTION
            "Actual (virtual) output relay status (before mapping this status to the selected hardware)."
    ::= { sdsIPWatchdog 11 }

-- ****************************************************************************

sdsOptoInput OBJECT IDENTIFIER ::= { sdsBIGandSTSW 2 }

opto1 OBJECT-TYPE
    SYNTAX  INTEGER {
                activeSignalPresent(0),
                noSignal(32768)
            }
    MAX-ACCESS  read-only
    STATUS      current
    DESCRIPTION
            "Current OPTO1 binary input status."
    ::= { sdsOptoInput 1 }

opto2 OBJECT-TYPE
    SYNTAX  INTEGER {
                activeSignalPresent(0),
                noSignal(1)
            }
    MAX-ACCESS  read-only
    STATUS      current
    DESCRIPTION
            "Current OPTO2 binary input status."
    ::= { sdsOptoInput 2 }

opto3 OBJECT-TYPE
    SYNTAX  INTEGER {
                activeSignalPresent(0),
                noSignal(2)
            }
    MAX-ACCESS  read-only
    STATUS      current
    DESCRIPTION
            "Current OPTO3 binary input status."
    ::= { sdsOptoInput 3 }

opto4 OBJECT-TYPE
    SYNTAX  INTEGER {
                activeSignalPresent(0),
                noSignal(128)
            }
    MAX-ACCESS  read-only
    STATUS      current
    DESCRIPTION
            "Current OPTO4 binary input status."
    ::= { sdsOptoInput 4 }

opto5 OBJECT-TYPE
    SYNTAX  INTEGER {
                activeSignalPresent(0),
                noSignal(256)
            }
    MAX-ACCESS  read-only
    STATUS      current
    DESCRIPTION
            "Current OPTO5 binary input status."
    ::= { sdsOptoInput 5 }

opto6 OBJECT-TYPE
    SYNTAX  INTEGER {
                activeSignalPresent(0),
                noSignal(512)
            }
    MAX-ACCESS  read-only
    STATUS      current
    DESCRIPTION
            "Current OPTO6 binary input status."
    ::= { sdsOptoInput 6 }

opto7 OBJECT-TYPE
    SYNTAX  INTEGER {
                activeSignalPresent(0),
                noSignal(1024)
            }
    MAX-ACCESS  read-only
    STATUS      current
    DESCRIPTION
            "Current OPTO7 binary input status."
    ::= { sdsOptoInput 7 }

opto8 OBJECT-TYPE
    SYNTAX  INTEGER {
                activeSignalPresent(0),
                noSignal(2048)
            }
    MAX-ACCESS  read-only
    STATUS      current
    DESCRIPTION
            "Current OPTO8 binary input status."
    ::= { sdsOptoInput 8 }

logics0input OBJECT-TYPE
    SYNTAX  INTEGER {
                activeSignalPresent(0),
                noSignal(16)
            }
    MAX-ACCESS  read-only
    STATUS      current
    DESCRIPTION
            "Current LOGIC-S0 binary input status."
    ::= { sdsOptoInput 9 }

-- ****************************************************************************

sdsOutputRelays OBJECT IDENTIFIER ::= { sdsBIGandSTSW 3 }

sdsOutputRelay1 OBJECT IDENTIFIER ::= { sdsOutputRelays 1 }

sdsRE1state OBJECT-TYPE
    SYNTAX  INTEGER {
                off(0),
                activated(255)
            }
    MAX-ACCESS  read-write
    STATUS      current
    DESCRIPTION
            "Current RELAY 1 output status."
    ::= { sdsOutputRelay1 1 }

sdsRE1cby OBJECT-TYPE
    SYNTAX  INTEGER {
                manualControl(0),
                sdscControl(2),
                ipwControl(4),
                oneShotReset(8)
            }
    MAX-ACCESS  read-write
    STATUS      current
    DESCRIPTION
            "RELAY 1 controled by ..."
    ::= { sdsOutputRelay1 2 }

sdsRE1name OBJECT-TYPE
    SYNTAX  OCTET STRING
    MAX-ACCESS  read-only
    STATUS      current
    DESCRIPTION
            "User name for RELAY 1."
    ::= { sdsOutputRelay1 3 }

sdsOutputRelay2 OBJECT IDENTIFIER ::= { sdsOutputRelays 2 }

sdsRE2state OBJECT-TYPE
    SYNTAX  INTEGER {
                off(0),
                activated(255)
            }
    MAX-ACCESS  read-write
    STATUS      current
    DESCRIPTION
            "Current RELAY 2 output status."
    ::= { sdsOutputRelay2 1 }

sdsRE2cby OBJECT-TYPE
    SYNTAX  INTEGER {
                manualControl(0),
                sdscControl(2),
                ipwControl(4),
                oneShotReset(8)
            }
    MAX-ACCESS  read-write
    STATUS      current
    DESCRIPTION
            "RELAY 2 controled by ..."
    ::= { sdsOutputRelay2 2 }

sdsRE2name OBJECT-TYPE
    SYNTAX  OCTET STRING
    MAX-ACCESS  read-only
    STATUS      current
    DESCRIPTION
            "User name for RELAY 2."
    ::= { sdsOutputRelay2 3 }

sdsOutputRelay3 OBJECT IDENTIFIER ::= { sdsOutputRelays 3 }

sdsRE3state OBJECT-TYPE
    SYNTAX  INTEGER {
                off(0),
                activated(255)
            }
    MAX-ACCESS  read-write
    STATUS      current
    DESCRIPTION
            "Current RELAY 3 output status."
    ::= { sdsOutputRelay3 1 }

sdsRE3cby OBJECT-TYPE
    SYNTAX  INTEGER {
                manualControl(0),
                sdscControl(2),
                ipwControl(4),
                oneShotReset(8)
            }
    MAX-ACCESS  read-write
    STATUS      current
    DESCRIPTION
            "RELAY 3 controled by ..."
    ::= { sdsOutputRelay3 2 }

sdsRE3name OBJECT-TYPE
    SYNTAX  OCTET STRING
    MAX-ACCESS  read-only
    STATUS      current
    DESCRIPTION
            "User name for RELAY 3."
    ::= { sdsOutputRelay3 3 }

sdsOutputRelay4 OBJECT IDENTIFIER ::= { sdsOutputRelays 4 }

sdsRE4state OBJECT-TYPE
    SYNTAX  INTEGER {
                off(0),
                activated(255)
            }
    MAX-ACCESS  read-write
    STATUS      current
    DESCRIPTION
            "Current RELAY 4 output status."
    ::= { sdsOutputRelay4 1 }

sdsRE4cby OBJECT-TYPE
    SYNTAX  INTEGER {
                manualControl(0),
                sdscControl(2),
                ipwControl(4),
                oneShotReset(8)
            }
    MAX-ACCESS  read-write
    STATUS      current
    DESCRIPTION
            "RELAY 4 controled by ..."
    ::= { sdsOutputRelay4 2 }

sdsRE4name OBJECT-TYPE
    SYNTAX  OCTET STRING
    MAX-ACCESS  read-only
    STATUS      current
    DESCRIPTION
            "User name for RELAY 4."
    ::= { sdsOutputRelay4 3 }

sdsOutputRelay5 OBJECT IDENTIFIER ::= { sdsOutputRelays 5 }

sdsRE5state OBJECT-TYPE
    SYNTAX  INTEGER {
                off(0),
                activated(255)
            }
    MAX-ACCESS  read-write
    STATUS      current
    DESCRIPTION
            "Current RELAY 5 output status."
    ::= { sdsOutputRelay5 1 }

sdsRE5cby OBJECT-TYPE
    SYNTAX  INTEGER {
                manualControl(0),
                sdscControl(2),
                ipwControl(4),
                oneShotReset(8)
            }
    MAX-ACCESS  read-write
    STATUS      current
    DESCRIPTION
            "RELAY 5 controled by ..."
    ::= { sdsOutputRelay5 2 }

sdsRE5name OBJECT-TYPE
    SYNTAX  OCTET STRING
    MAX-ACCESS  read-only
    STATUS      current
    DESCRIPTION
            "User name for RELAY 5."
    ::= { sdsOutputRelay5 3 }

sdsOutputRelay6 OBJECT IDENTIFIER ::= { sdsOutputRelays 6 }

sdsRE6state OBJECT-TYPE
    SYNTAX  INTEGER {
                off(0),
                activated(255)
            }
    MAX-ACCESS  read-write
    STATUS      current
    DESCRIPTION
            "Current RELAY 6 output status."
    ::= { sdsOutputRelay6 1 }

sdsRE6cby OBJECT-TYPE
    SYNTAX  INTEGER {
                manualControl(0),
                sdscControl(2),
                ipwControl(4),
                oneShotReset(8)
            }
    MAX-ACCESS  read-write
    STATUS      current
    DESCRIPTION
            "RELAY 6 controled by ..."
    ::= { sdsOutputRelay6 2 }

sdsRE6name OBJECT-TYPE
    SYNTAX  OCTET STRING
    MAX-ACCESS  read-only
    STATUS      current
    DESCRIPTION
            "User name for RELAY 6."
    ::= { sdsOutputRelay6 3 }

-- ****************************************************************************

sdsPWMoutput OBJECT IDENTIFIER ::= { sdsBIGandSTSW 4 }

sdsPWM1freq OBJECT-TYPE
    SYNTAX  Gauge32
    MAX-ACCESS  read-write
    STATUS      current
    DESCRIPTION
            "Actual PWM1 generator frequency [Hz]."
    ::= { sdsPWMoutput 1 }

sdsPWM1duty OBJECT-TYPE
    SYNTAX  Gauge32
    MAX-ACCESS  read-write
    STATUS      current
    DESCRIPTION
            "Actual PWM1 duty control setting."
    ::= { sdsPWMoutput 2 }

-- ****************************************************************************

-- the ADC input items

sdsADCinputs OBJECT IDENTIFIER ::= { sdsBIGandSTSW 5 }

sdsADCitem0 OBJECT IDENTIFIER ::= { sdsADCinputs 1 }

sdsADCrawValue0 OBJECT-TYPE
    SYNTAX      Gauge32
    MAX-ACCESS  read-only
    STATUS      current
    DESCRIPTION
            "Actual raw analog input [R] value (conversion result)."
    ::= { sdsADCitem0 1 }

sdsADCtext0 OBJECT-TYPE
    SYNTAX      OCTET STRING
    MAX-ACCESS  read-only
    STATUS      current
    DESCRIPTION
            "SI textual value for the analog input (conversion result)."
    ::= { sdsADCitem0 2 }

sdsADCintmul0 OBJECT-TYPE
    SYNTAX      Gauge32
    MAX-ACCESS  read-only
    STATUS      current
    DESCRIPTION
            "SI integer MUL value for the analog input (conversion result multiplied by 100)."
    ::= { sdsADCitem0 3 }

sdsADCname0 OBJECT-TYPE
    SYNTAX      OCTET STRING
    MAX-ACCESS  read-only
    STATUS      current
    DESCRIPTION
            "User name for the analog input."
    ::= { sdsADCitem0 4 }

sdsADCitem1 OBJECT IDENTIFIER ::= { sdsADCinputs 2 }

sdsADCrawValue1 OBJECT-TYPE
    SYNTAX      Gauge32
    MAX-ACCESS  read-only
    STATUS      current
    DESCRIPTION
            "Actual raw analog input [V] value (conversion result)."
    ::= { sdsADCitem1 1 }

sdsADCtext1 OBJECT-TYPE
    SYNTAX      OCTET STRING
    MAX-ACCESS  read-only
    STATUS      current
    DESCRIPTION
            "SI textual value for the analog input (conversion result)."
    ::= { sdsADCitem1 2 }

sdsADCintmul1 OBJECT-TYPE
    SYNTAX      Gauge32
    MAX-ACCESS  read-only
    STATUS      current
    DESCRIPTION
            "SI integer MUL value for the analog input (conversion result multiplied by 100)."
    ::= { sdsADCitem1 3 }

sdsADCname1 OBJECT-TYPE
    SYNTAX      OCTET STRING
    MAX-ACCESS  read-only
    STATUS      current
    DESCRIPTION
            "User name for the analog input."
    ::= { sdsADCitem1 4 }

sdsADCitem2 OBJECT IDENTIFIER ::= { sdsADCinputs 3 }

sdsADCrawValue2 OBJECT-TYPE
    SYNTAX      Gauge32
    MAX-ACCESS  read-only
    STATUS      current
    DESCRIPTION
            "Actual raw analog input [V] value (conversion result)."
    ::= { sdsADCitem2 1 }

sdsADCtext2 OBJECT-TYPE
    SYNTAX      OCTET STRING
    MAX-ACCESS  read-only
    STATUS      current
    DESCRIPTION
            "SI textual value for the analog input (conversion result)."
    ::= { sdsADCitem2 2 }

sdsADCintmul2 OBJECT-TYPE
    SYNTAX      Gauge32
    MAX-ACCESS  read-only
    STATUS      current
    DESCRIPTION
            "SI integer MUL value for the analog input (conversion result multiplied by 100)."
    ::= { sdsADCitem2 3 }

sdsADCname2 OBJECT-TYPE
    SYNTAX      OCTET STRING
    MAX-ACCESS  read-only
    STATUS      current
    DESCRIPTION
            "User name for the analog input."
    ::= { sdsADCitem2 4 }

sdsADCitem3 OBJECT IDENTIFIER ::= { sdsADCinputs 4 }

sdsADCrawValue3 OBJECT-TYPE
    SYNTAX      Gauge32
    MAX-ACCESS  read-only
    STATUS      current
    DESCRIPTION
            "Actual raw analog input [AI1] value (conversion result)."
    ::= { sdsADCitem3 1 }

sdsADCtext3 OBJECT-TYPE
    SYNTAX      OCTET STRING
    MAX-ACCESS  read-only
    STATUS      current
    DESCRIPTION
            "SI textual value for the analog input (conversion result)."
    ::= { sdsADCitem3 2 }

sdsADCintmul3 OBJECT-TYPE
    SYNTAX      Gauge32
    MAX-ACCESS  read-only
    STATUS      current
    DESCRIPTION
            "SI integer MUL value for the analog input (conversion result multiplied by 100)."
    ::= { sdsADCitem3 3 }

sdsADCname3 OBJECT-TYPE
    SYNTAX      OCTET STRING
    MAX-ACCESS  read-only
    STATUS      current
    DESCRIPTION
            "User name for the analog input."
    ::= { sdsADCitem3 4 }

sdsADCitem4 OBJECT IDENTIFIER ::= { sdsADCinputs 5 }

sdsADCrawValue4 OBJECT-TYPE
    SYNTAX      Gauge32
    MAX-ACCESS  read-only
    STATUS      current
    DESCRIPTION
            "Actual raw analog input [AI2] value (conversion result)."
    ::= { sdsADCitem4 1 }

sdsADCtext4 OBJECT-TYPE
    SYNTAX      OCTET STRING
    MAX-ACCESS  read-only
    STATUS      current
    DESCRIPTION
            "SI textual value for the analog input (conversion result)."
    ::= { sdsADCitem4 2 }

sdsADCintmul4 OBJECT-TYPE
    SYNTAX      Gauge32
    MAX-ACCESS  read-only
    STATUS      current
    DESCRIPTION
            "SI integer MUL value for the analog input (conversion result multiplied by 100)."
    ::= { sdsADCitem4 3 }

sdsADCname4 OBJECT-TYPE
    SYNTAX      OCTET STRING
    MAX-ACCESS  read-only
    STATUS      current
    DESCRIPTION
            "User name for the analog input."
    ::= { sdsADCitem4 4 }

sdsADCitem5 OBJECT IDENTIFIER ::= { sdsADCinputs 6 }

sdsADCrawValue5 OBJECT-TYPE
    SYNTAX      Gauge32
    MAX-ACCESS  read-only
    STATUS      current
    DESCRIPTION
            "Actual raw analog input [AI3] value (conversion result)."
    ::= { sdsADCitem5 1 }

sdsADCtext5 OBJECT-TYPE
    SYNTAX      OCTET STRING
    MAX-ACCESS  read-only
    STATUS      current
    DESCRIPTION
            "SI textual value for the analog input (conversion result)."
    ::= { sdsADCitem5 2 }

sdsADCintmul5 OBJECT-TYPE
    SYNTAX      Gauge32
    MAX-ACCESS  read-only
    STATUS      current
    DESCRIPTION
            "SI integer MUL value for the analog input (conversion result multiplied by 100)."
    ::= { sdsADCitem5 3 }

sdsADCname5 OBJECT-TYPE
    SYNTAX      OCTET STRING
    MAX-ACCESS  read-only
    STATUS      current
    DESCRIPTION
            "User name for the analog input."
    ::= { sdsADCitem5 4 }

sdsADCitem6 OBJECT IDENTIFIER ::= { sdsADCinputs 7 }

sdsADCrawValue6 OBJECT-TYPE
    SYNTAX      Gauge32
    MAX-ACCESS  read-only
    STATUS      current
    DESCRIPTION
            "Actual raw analog input [AI4] value (conversion result)."
    ::= { sdsADCitem6 1 }

sdsADCtext6 OBJECT-TYPE
    SYNTAX      OCTET STRING
    MAX-ACCESS  read-only
    STATUS      current
    DESCRIPTION
            "SI textual value for the analog input (conversion result)."
    ::= { sdsADCitem6 2 }

sdsADCintmul6 OBJECT-TYPE
    SYNTAX      Gauge32
    MAX-ACCESS  read-only
    STATUS      current
    DESCRIPTION
            "SI integer MUL value for the analog input (conversion result multiplied by 100)."
    ::= { sdsADCitem6 3 }

sdsADCname6 OBJECT-TYPE
    SYNTAX      OCTET STRING
    MAX-ACCESS  read-only
    STATUS      current
    DESCRIPTION
            "User name for the analog input."
    ::= { sdsADCitem6 4 }

sdsADCitem7 OBJECT IDENTIFIER ::= { sdsADCinputs 8 }

sdsADCrawValue7 OBJECT-TYPE
    SYNTAX      Gauge32
    MAX-ACCESS  read-only
    STATUS      current
    DESCRIPTION
            "Actual raw analog input [AI5] value (conversion result)."
    ::= { sdsADCitem7 1 }

sdsADCtext7 OBJECT-TYPE
    SYNTAX      OCTET STRING
    MAX-ACCESS  read-only
    STATUS      current
    DESCRIPTION
            "SI textual value for the analog input (conversion result)."
    ::= { sdsADCitem7 2 }

sdsADCintmul7 OBJECT-TYPE
    SYNTAX      Gauge32
    MAX-ACCESS  read-only
    STATUS      current
    DESCRIPTION
            "SI integer MUL value for the analog input (conversion result multiplied by 100)."
    ::= { sdsADCitem7 3 }

sdsADCname7 OBJECT-TYPE
    SYNTAX      OCTET STRING
    MAX-ACCESS  read-only
    STATUS      current
    DESCRIPTION
            "User name for the analog input."
    ::= { sdsADCitem7 4 }

-- ****************************************************************************

-- the 1-WIRE(r) table

-- The 1-WIRE table contains information about all the connected 1-W devices
-- (note that both BUS A and BUS B are joined together, into a single list)

sdsOneWireTable OBJECT-TYPE
    SYNTAX      SEQUENCE OF sdsOneWireEntry
    MAX-ACCESS  not-accessible
    STATUS      current
    DESCRIPTION
            "A list of 1-Wire (reg) devices."
    ::= { sdsBIGandSTSW 6 }

sdsOneWireEntry OBJECT-TYPE
    SYNTAX      sdsOneWireEntry
    MAX-ACCESS  not-accessible
    STATUS      current
    DESCRIPTION
            "An entry containing information applicable to a particular 1-WIRE device."
    INDEX   { sdsOneWireTableRowIndex }
    ::= { sdsOneWireTable 1 }

sdsOneWireEntry ::=
    SEQUENCE {
        sdsOneWireStatus            Integer32,
        sdsOneWireDeviceROMcode     OCTET STRING,
        sdsOneWireName              OCTET STRING,
        sdsOneWireFullValIDX0       Integer32,
        sdsOneWireFullValIDX1       Integer32,
        sdsOneWireConfigFlags       Integer32,
        sdsOneWireTableRowIndex     Integer32
    }

sdsOneWireStatus OBJECT-TYPE
    SYNTAX  Integer32 {
                none(0),
                presence(1),
                genericError(2),
                gotBadCRC(3),
                working(8),
                ds18x20failure(10),
                ds18x20gotResult(11)
            }
    MAX-ACCESS  read-only
    STATUS      current
    DESCRIPTION
            "Actual 1-WIRE device status. The sub-states for the 'working(8)' state are not provided yet."
    ::= { sdsOneWireEntry 1 }

sdsOneWireDeviceROMcode OBJECT-TYPE
    SYNTAX      OCTET STRING
    MAX-ACCESS  read-only
    STATUS      current
    DESCRIPTION
            "Internal 1-WIRE device ROM unique identification code."
    ::= { sdsOneWireEntry 2 }

sdsOneWireName OBJECT-TYPE
    SYNTAX      OCTET STRING
    MAX-ACCESS  read-only
    STATUS      current
    DESCRIPTION
            "Internal 1-WIRE device ROM unique identification code."
    ::= { sdsOneWireEntry 3 }

sdsOneWireFullValIDX0 OBJECT-TYPE
    SYNTAX      Integer32
    MAX-ACCESS  read-only
    STATUS      current
    DESCRIPTION
            "Primary value received from this 1-WIRE device."
    ::= { sdsOneWireEntry 4 }

sdsOneWireFullValIDX1 OBJECT-TYPE
    SYNTAX      Integer32
    MAX-ACCESS  read-only
    STATUS      current
    DESCRIPTION
            "Secondary value received from this 1-WIRE device."
    ::= { sdsOneWireEntry 5 }

sdsOneWireConfigFlags OBJECT-TYPE
    SYNTAX      Integer32
    MAX-ACCESS  read-only
    STATUS      current
    DESCRIPTION
            "Configuration flags for this 1-WIRE device."
    ::= { sdsOneWireEntry 6 }

sdsOneWireTableRowIndex OBJECT-TYPE
    SYNTAX  Integer32
    MAX-ACCESS  not-accessible
    STATUS      current
    DESCRIPTION
            "1-WIRE table row index."
    ::= { sdsOneWireEntry 7 }

-- ****************************************************************************

sdsVersionEntry OBJECT IDENTIFIER ::= { sdsBIGandSTSW 7 }

sdsVersionText OBJECT-TYPE
    SYNTAX    OCTET STRING
    MAX-ACCESS  read-only
    STATUS      current
    DESCRIPTION
            "SDS device version text."
    ::= { sdsVersionEntry 1 }

sdsCustomVarTrap1 OBJECT-TYPE
    SYNTAX    Integer32
    MAX-ACCESS  read-only
    STATUS      current
    DESCRIPTION
            "SDS custom-trap value."
    ::= { sdsVersionEntry 2 }

sdsCustomVarTrap2 OBJECT-TYPE
    SYNTAX    OCTET STRING
    MAX-ACCESS  read-only
    STATUS      current
    DESCRIPTION
            "SDS custom-trap value."
    ::= { sdsVersionEntry 3 }

sdsCustomVarTrap3 OBJECT-TYPE
    SYNTAX    Integer32
    MAX-ACCESS  read-only
    STATUS      current
    DESCRIPTION
            "SDS custom-trap value."
    ::= { sdsVersionEntry 4 }

sdsCustomVarTrap4 OBJECT-TYPE
    SYNTAX    Integer32
    MAX-ACCESS  read-only
    STATUS      current
    DESCRIPTION
            "SDS custom-trap value."
    ::= { sdsVersionEntry 5 }

sdsCustomVarTrap5 OBJECT-TYPE
    SYNTAX    Integer32
    MAX-ACCESS  read-only
    STATUS      current
    DESCRIPTION
            "SDS custom-trap value."
    ::= { sdsVersionEntry 6 }

sdsCustomVarTrap6 OBJECT-TYPE
    SYNTAX    Integer32
    MAX-ACCESS  read-only
    STATUS      current
    DESCRIPTION
            "SDS custom-trap value."
    ::= { sdsVersionEntry 7 }

sdsCustomVarTrap7 OBJECT-TYPE
    SYNTAX    Integer32
    MAX-ACCESS  read-only
    STATUS      current
    DESCRIPTION
            "SDS custom-trap value."
    ::= { sdsVersionEntry 8 }

sdsCustomVarTrap8 OBJECT-TYPE
    SYNTAX    Integer32
    MAX-ACCESS  read-only
    STATUS      current
    DESCRIPTION
            "SDS custom-trap value."
    ::= { sdsVersionEntry 9 }

sdsCustomVarTrap9 OBJECT-TYPE
    SYNTAX    Integer32
    MAX-ACCESS  read-only
    STATUS      current
    DESCRIPTION
            "SDS custom-trap value."
    ::= { sdsVersionEntry 10 }

-- ****************************************************************************

sdsGeneralInfoEntry OBJECT IDENTIFIER ::= { sdsBIGandSTSW 8 }

sdsNTPvalue OBJECT-TYPE
    SYNTAX    Counter32
    MAX-ACCESS  read-only
    STATUS      current
    DESCRIPTION
            "Actual NTP UTC time value (pure UTC from NTP, not corrected for a local time offset)."
    ::= { sdsGeneralInfoEntry 1 }

sdsSoCtempValue OBJECT-TYPE
    SYNTAX    Integer32
    MAX-ACCESS  read-only
    STATUS      current
    DESCRIPTION
            "Actual SoC chip internal temperature, represented in a special units [0..4095]. This needs to be recalculated to get a degC value."
    ::= { sdsGeneralInfoEntry 2 }

sdsOneWireBUSAcountValue OBJECT-TYPE
    SYNTAX    Integer32
    MAX-ACCESS  read-only
    STATUS      current
    DESCRIPTION
            "Number of discovered 1-Wire devices on BUS A."
    ::= { sdsGeneralInfoEntry 3 }

sdsOneWireBUSBcountValue OBJECT-TYPE
    SYNTAX    Integer32
    MAX-ACCESS  read-only
    STATUS      current
    DESCRIPTION
            "Number of discovered 1-Wire devices on BUS B."
    ::= { sdsGeneralInfoEntry 4 }

sdsGPIOTOPBOARDoutputState OBJECT-TYPE
    SYNTAX  Integer32
    MAX-ACCESS  read-only
    STATUS      current
    DESCRIPTION
            "GPIO-TOPBOARD actual output status."
    ::= { sdsGeneralInfoEntry 5 }

sdsGPIOTOPBOARDdirection OBJECT-TYPE
    SYNTAX  Integer32
    MAX-ACCESS  read-only
    STATUS      current
    DESCRIPTION
            "GPIO-TOPBOARD actual direction (in/out) status."
    ::= { sdsGeneralInfoEntry 6 }

sdsBackUpCoinBatteryVoltageValue OBJECT-TYPE
    SYNTAX    Integer32
    MAX-ACCESS  read-only
    STATUS      current
    DESCRIPTION
            "Actual voltage reading of the back-up coin battery, represented in a special units [0..4095]. This needs to be recalculated to get a value in Votls."
    ::= { sdsGeneralInfoEntry 7 }

sdsNTPvalueLocal OBJECT-TYPE
    SYNTAX    Counter32
    MAX-ACCESS  read-only
    STATUS      current
    DESCRIPTION
            "Actual LOCAL time value."
    ::= { sdsGeneralInfoEntry 10 }

sdsSDCARDpresence OBJECT-TYPE
    SYNTAX  Integer32 {
                cardRemoved(0)
            }
    MAX-ACCESS  read-only
    STATUS      current
    DESCRIPTION
            "Physical presence (insertion) of the SD-CARD."
    ::= { sdsGeneralInfoEntry 11 }

sdsSDCARDlastSN OBJECT-TYPE
    SYNTAX  Integer32
    MAX-ACCESS  read-only
    STATUS      current
    DESCRIPTION
            "Last known SN of the SD-CARD."
    ::= { sdsGeneralInfoEntry 12 }

sdsSDCARDreadCNT OBJECT-TYPE
    SYNTAX  Integer32
    MAX-ACCESS  read-only
    STATUS      current
    DESCRIPTION
            "Number of sector reads from the SD-CARD."
    ::= { sdsGeneralInfoEntry 13 }

sdsSDCARDwriteCNT OBJECT-TYPE
    SYNTAX  Integer32
    MAX-ACCESS  read-only
    STATUS      current
    DESCRIPTION
            "Number of sector writes from the SD-CARD."
    ::= { sdsGeneralInfoEntry 14 }

sdsSDCARDrwFails OBJECT-TYPE
    SYNTAX  Integer32
    MAX-ACCESS  read-only
    STATUS      current
    DESCRIPTION
            "Number of sector read-or-writes failures for the SD-CARD."
    ::= { sdsGeneralInfoEntry 15 }

sdsSDCARDinitAttempts OBJECT-TYPE
    SYNTAX  Integer32
    MAX-ACCESS  read-only
    STATUS      current
    DESCRIPTION
            "Number of attempts to initialize and mount, of the SD-CARD."
    ::= { sdsGeneralInfoEntry 16 }

sdsSDCARDinitFailedAttempts OBJECT-TYPE
    SYNTAX  Integer32
    MAX-ACCESS  read-only
    STATUS      current
    DESCRIPTION
            "Number of failed attempts to mount the SD-CARD."
    ::= { sdsGeneralInfoEntry 17 }

sdsCustomVarString1 OBJECT-TYPE
    SYNTAX    OCTET STRING
    MAX-ACCESS  read-only
    STATUS      current
    DESCRIPTION
            "SDS custom string."
    ::= { sdsGeneralInfoEntry 80 }

sdsCustomVarString2 OBJECT-TYPE
    SYNTAX    OCTET STRING
    MAX-ACCESS  read-only
    STATUS      current
    DESCRIPTION
            "SDS custom string."
    ::= { sdsGeneralInfoEntry 81 }

sdsCustomVarString3 OBJECT-TYPE
    SYNTAX    OCTET STRING
    MAX-ACCESS  read-only
    STATUS      current
    DESCRIPTION
            "SDS custom string."
    ::= { sdsGeneralInfoEntry 82 }

sdsCustomVarString4 OBJECT-TYPE
    SYNTAX    OCTET STRING
    MAX-ACCESS  read-only
    STATUS      current
    DESCRIPTION
            "SDS custom string."
    ::= { sdsGeneralInfoEntry 83 }

sdsCustomVarString5 OBJECT-TYPE
    SYNTAX    OCTET STRING
    MAX-ACCESS  read-only
    STATUS      current
    DESCRIPTION
            "SDS custom string."
    ::= { sdsGeneralInfoEntry 84 }

sdsFULLCrunStatus OBJECT-TYPE
    SYNTAX  Integer32 {
                unknown(0),
                noProgram(1),
                stopped(2),
                erasing(4),
                uploading(8),
                uploadDone(16),
                paused(32),
                running(64)
            }
    MAX-ACCESS  read-only
    STATUS      current
    DESCRIPTION
            "Actual state of the FULL-C program."
    ::= { sdsGeneralInfoEntry 90 }

-- ****************************************************************************

-- the S0 INPUT table

-- The S0 INPUT contains information from the S0 impulse input

sdsS0Table OBJECT-TYPE
    SYNTAX      SEQUENCE OF SdsS0Entry
    MAX-ACCESS  not-accessible
    STATUS      current
    DESCRIPTION
            "A list of S0 impulse inputs."
    ::= { sdsBIGandSTSW 9 }

sdsS0Entry OBJECT-TYPE
    SYNTAX      SdsS0Entry
    MAX-ACCESS  not-accessible
    STATUS      current
    DESCRIPTION
            "An entry containing information applicable to a particular S0 input."
    INDEX   { sdsS0tableRowIndex }
    ::= { sdsS0Table 1 }

SdsS0Entry ::=
    SEQUENCE {
        sdsS0impCountT0       Counter32,
        sdsS0impCountT1       Counter32,
        sdsS0impMoneyOffsetT0 Gauge32,
        sdsS0impMoneyOffsetT1 Gauge32,
        sdsS0constant         Gauge32,
        sdsS0translatedUnitT0 OCTET STRING,
        sdsS0translatedUnitT1 OCTET STRING,
        sdsS0translatedCashT0 OCTET STRING,
        sdsS0translatedCashT1 OCTET STRING,
        sdsS0actualEnergyFlow OCTET STRING,
        sdsS0constantMTD      Gauge32,
        sdsS0tableRowIndex    Integer32
    }

sdsS0impCountT0 OBJECT-TYPE
    SYNTAX  Counter32
    MAX-ACCESS  read-only
    STATUS      current
    DESCRIPTION
            "Actual S0 impulse counter value for the tarif state T0 (no tarif signal)."
    ::= { sdsS0Entry 1 }

sdsS0impCountT1 OBJECT-TYPE
    SYNTAX  Counter32
    MAX-ACCESS  read-only
    STATUS      current
    DESCRIPTION
            "Actual S0 impulse counter value for the tarif state T1 (active tarif signal)."
    ::= { sdsS0Entry 2 }

sdsS0impMoneyOffsetT0 OBJECT-TYPE
    SYNTAX  Gauge32
    MAX-ACCESS  read-only
    STATUS      current
    DESCRIPTION
            "Offset (impulse count) for cash calculation. Cash value is calculated relatively starting at this offset, for the T0 counter."
    ::= { sdsS0Entry 3 }

sdsS0impMoneyOffsetT1 OBJECT-TYPE
    SYNTAX  Gauge32
    MAX-ACCESS  read-only
    STATUS      current
    DESCRIPTION
            "Offset (impulse count) for cash calculation. Cash value is calculated relatively starting at this offset, for the T1 counter."
    ::= { sdsS0Entry 4 }

sdsS0constant OBJECT-TYPE
    SYNTAX  Gauge32
    MAX-ACCESS  read-only
    STATUS      current
    DESCRIPTION
            "S0 output constant (number of impulses for 1 energy unit)."
    ::= { sdsS0Entry 5 }

sdsS0translatedUnitT0 OBJECT-TYPE
    SYNTAX  OCTET STRING
    MAX-ACCESS  read-only
    STATUS      current
    DESCRIPTION
            "T0 related S0 impulse count value, recalculated into energy units, in a textual representation."
    ::= { sdsS0Entry 6 }

sdsS0translatedUnitT1 OBJECT-TYPE
    SYNTAX  OCTET STRING
    MAX-ACCESS  read-only
    STATUS      current
    DESCRIPTION
            "T1 related S0 impulse count value, recalculated into energy units, in a textual representation."
    ::= { sdsS0Entry 7 }

sdsS0translatedCashT0 OBJECT-TYPE
    SYNTAX  OCTET STRING
    MAX-ACCESS  read-only
    STATUS      current
    DESCRIPTION
            "T0 related S0 counter value recalculated into cash (total: T0_impulse_count minus T0_custom_offset), in a textual representation."
    ::= { sdsS0Entry 8 }

sdsS0translatedCashT1 OBJECT-TYPE
    SYNTAX  OCTET STRING
    MAX-ACCESS  read-only
    STATUS      current
    DESCRIPTION
            "T1 related S0 counter value recalculated into cash (total: T1_impulse_count minus T1_custom_offset), in a textual representation."
    ::= { sdsS0Entry 9 }

sdsS0actualEnergyFlow OBJECT-TYPE
    SYNTAX  OCTET STRING
    MAX-ACCESS  read-only
    STATUS      current
    DESCRIPTION
            "S0: the actual energy flow value."
    ::= { sdsS0Entry 10 }

sdsS0constantMTD OBJECT-TYPE
    SYNTAX  Gauge32
    MAX-ACCESS  read-only
    STATUS      current
    DESCRIPTION
            "Configuration: the MTD constant."
    ::= { sdsS0Entry 11 }

sdsS0tableRowIndex OBJECT-TYPE
    SYNTAX  Integer32
    MAX-ACCESS  not-accessible
    STATUS      current
    DESCRIPTION
            "S0 table row index."
    ::= { sdsS0Entry 12 }


-- ****************************************************************************

-- the FULL-C Shared Variables - Table

-- shared variables are used within the user's FULL-C program

sdsFCsharedVarsTable1 OBJECT-TYPE
    SYNTAX      SEQUENCE OF SdsFCSentry1
    MAX-ACCESS  not-accessible
    STATUS      current
    DESCRIPTION
            "FULL-C SHARED variables. Be careful about the offset in indexes."
    ::= { sdsBIGandSTSW 10  }

sdsFCsharedVarsTable2 OBJECT-TYPE
    SYNTAX      SEQUENCE OF SdsFCSentry2
    MAX-ACCESS  not-accessible
    STATUS      current
    DESCRIPTION
            "FULL-C SHARED variables. Be careful about the offset in indexes."
    ::= { sdsBIGandSTSW 10  }

sdsFCsharedVarsTable3 OBJECT-TYPE
    SYNTAX      SEQUENCE OF SdsFCSentry3
    MAX-ACCESS  not-accessible
    STATUS      current
    DESCRIPTION
            "FULL-C SHARED variables. Be careful about the offset in indexes."
    ::= { sdsBIGandSTSW 10  }

sdsFCsharedVarsTable4 OBJECT-TYPE
    SYNTAX      SEQUENCE OF SdsFCSentry4
    MAX-ACCESS  not-accessible
    STATUS      current
    DESCRIPTION
            "FULL-C SHARED variables. Be careful about the offset in indexes."
    ::= { sdsBIGandSTSW 10  }


sdsFCSentry1 OBJECT-TYPE
    SYNTAX      SdsFCSentry1
    MAX-ACCESS  not-accessible
    STATUS      current
    DESCRIPTION
            "Sxx entry."
    INDEX   { }
    ::= { sdsFCsharedVarsTable1 1 }

SdsFCSentry1::=
    SEQUENCE {
        sdsFC_Sxx Integer32
    }

sdsFCSentry2 OBJECT-TYPE
    SYNTAX      SdsFCSentry2
    MAX-ACCESS  not-accessible
    STATUS      current
    DESCRIPTION
            "Uxx entry."
    INDEX   { }
    ::= { sdsFCsharedVarsTable2 2 }

SdsFCSentry2::=
    SEQUENCE {
        sdsFC_Uxx Integer32
    }

sdsFCSentry3 OBJECT-TYPE
    SYNTAX      SdsFCSentry3
    MAX-ACCESS  not-accessible
    STATUS      current
    DESCRIPTION
            "Fxx entry."
    INDEX   { }
    ::= { sdsFCsharedVarsTable3 3 }

SdsFCSentry3::=
    SEQUENCE {
        sdsFC_Fxx OCTET STRING
    }

sdsFCSentry4 OBJECT-TYPE
    SYNTAX      SdsFCSentry4
    MAX-ACCESS  not-accessible
    STATUS      current
    DESCRIPTION
            "Txx entry."
    INDEX   { }
    ::= { sdsFCsharedVarsTable4 4 }

SdsFCSentry4::=
    SEQUENCE {
        sdsFC_Txx OCTET STRING
    }

sdsFC_Sxx OBJECT-TYPE
    SYNTAX  Integer32
    MAX-ACCESS  read-only
    STATUS      current
    DESCRIPTION
            "Actual Sxx value."
    ::= { sdsFCSentry1 1 }

sdsFC_Uxx OBJECT-TYPE
    SYNTAX  Integer32
    MAX-ACCESS  read-only
    STATUS      current
    DESCRIPTION
            "Actual Uxx value."
    ::= { sdsFCSentry2 1 }

sdsFC_Fxx OBJECT-TYPE
     SYNTAX  OCTET STRING
     MAX-ACCESS  read-only
     STATUS      current
     DESCRIPTION
             "Actual Fxx value."
     ::= { sdsFCSentry3 1 }

 sdsFC_Txx OBJECT-TYPE
     SYNTAX  OCTET STRING
     MAX-ACCESS  read-only
     STATUS      current
     DESCRIPTION
             "Actual Txx value."
     ::= { sdsFCSentry4 1 }


-- ****************************************************************************

sdsSerialPortsEntry OBJECT IDENTIFIER ::= { sdsBIGandSTSW 11 }

-- COM1

sdsPortCOM1Entry OBJECT IDENTIFIER ::= { sdsSerialPortsEntry 1 }

sdsCOM1telnetConnected OBJECT-TYPE
    SYNTAX    Integer32
    MAX-ACCESS  read-only
    STATUS      current
    DESCRIPTION
            "COM1: Is there any Ethernet client connected and using the Eth-to-Serial converter, at this moment."
    ::= { sdsPortCOM1Entry 1 }

sdsCOM1baudrate OBJECT-TYPE
    SYNTAX    Integer32
    MAX-ACCESS  read-only
    STATUS      current
    DESCRIPTION
            "COM1: Actual configured UART baud rate in [bps]."
    ::= { sdsPortCOM1Entry 2 }

sdsCOM1dataSize OBJECT-TYPE
    SYNTAX    Integer32
    MAX-ACCESS  read-only
    STATUS      current
    DESCRIPTION
            "COM1: Actual configured UART char data size [8 or 9 bits per char]."
    ::= { sdsPortCOM1Entry 3 }

sdsCOM1stopBits OBJECT-TYPE
    SYNTAX    Integer32
    MAX-ACCESS  read-only
    STATUS      current
    DESCRIPTION
            "COM1: Actual configured UART number of stop bits [1 or 2 stop bits]"
    ::= { sdsPortCOM1Entry 4 }

sdsCOM1parity OBJECT-TYPE
    SYNTAX  INTEGER {
                noParity(0),
                parityIsUsed(1)
            }
    MAX-ACCESS  read-only
    STATUS      current
    DESCRIPTION
            "COM1: Actual configured UART parity."
    ::= { sdsPortCOM1Entry 5 }

sdsCOM1uartInBytes OBJECT-TYPE
    SYNTAX    Counter32
    MAX-ACCESS  read-only
    STATUS      current
    DESCRIPTION
            "COM1: Total number of UART IN bytes."
    ::= { sdsPortCOM1Entry 6 }

sdsCOM1uartOutBytes OBJECT-TYPE
    SYNTAX    Counter32
    MAX-ACCESS  read-only
    STATUS      current
    DESCRIPTION
            "COM1: Total number of UART OUT bytes."
    ::= { sdsPortCOM1Entry 7 }

-- COM6

sdsPortCOM6Entry OBJECT IDENTIFIER ::= { sdsSerialPortsEntry 6 }

sdsCOM6telnetConnected OBJECT-TYPE
    SYNTAX    Integer32
    MAX-ACCESS  read-only
    STATUS      current
    DESCRIPTION
            "COM6: Is there any Ethernet client connected and using the Eth-to-Serial converter, at this moment."
    ::= { sdsPortCOM6Entry 1 }

sdsCOM6baudrate OBJECT-TYPE
    SYNTAX    Integer32
    MAX-ACCESS  read-only
    STATUS      current
    DESCRIPTION
            "COM6: Actual configured UART baud rate in [bps]."
    ::= { sdsPortCOM6Entry 2 }

sdsCOM6dataSize OBJECT-TYPE
    SYNTAX    Integer32
    MAX-ACCESS  read-only
    STATUS      current
    DESCRIPTION
            "COM6: Actual configured UART char data size [8 or 9 bits per char]."
    ::= { sdsPortCOM6Entry 3 }

sdsCOM6stopBits OBJECT-TYPE
    SYNTAX    Integer32
    MAX-ACCESS  read-only
    STATUS      current
    DESCRIPTION
            "COM6: Actual configured UART number of stop bits [1 or 2 stop bits]"
    ::= { sdsPortCOM6Entry 4 }

sdsCOM6parity OBJECT-TYPE
    SYNTAX  INTEGER {
                noParity(0),
                parityIsUsed(1)
            }
    MAX-ACCESS  read-only
    STATUS      current
    DESCRIPTION
            "COM6: Actual configured UART parity."
    ::= { sdsPortCOM6Entry 5 }

sdsCOM6uartInBytes OBJECT-TYPE
    SYNTAX    Counter32
    MAX-ACCESS  read-only
    STATUS      current
    DESCRIPTION
            "COM6: Total number of UART IN bytes."
    ::= { sdsPortCOM6Entry 6 }

sdsCOM6uartOutBytes OBJECT-TYPE
    SYNTAX    Counter32
    MAX-ACCESS  read-only
    STATUS      current
    DESCRIPTION
            "COM6: Total number of UART OUT bytes."
    ::= { sdsPortCOM6Entry 7 }

-- ****************************************************************************




-- ****************************************************************************
-- TRAP-SDS-MICRO-MIB DEFINITIONS
-- ****************************************************************************


ipwActive-trap TRAP-TYPE
	STATUS current
	ENTERPRISE mib-AN-Dcz-SDS
	VARIABLES { ipwActive }
    	DESCRIPTION "TRAP: The current IP watchdog status."
    ::= 70

ipwPingIP-trap TRAP-TYPE
	STATUS current
	ENTERPRISE mib-AN-Dcz-SDS
	VARIABLES { ipwPingIP }
    	DESCRIPTION "TRAP: IP address of the wdg monitored object."
    ::= 71

ipwPauseAfterPwOn-trap TRAP-TYPE
	STATUS current
	ENTERPRISE mib-AN-Dcz-SDS
	VARIABLES { ipwPauseAfterPwOn }
    	DESCRIPTION "TRAP: Duration of the IP watchdog disable period."
    ::= 72

ipwPingTimeout-trap TRAP-TYPE
	STATUS current
	ENTERPRISE mib-AN-Dcz-SDS
	VARIABLES { ipwPingTimeout }
    	DESCRIPTION "TRAP: IP watchdog RTT timeout."
    ::= 73

ipwRepeatPingPer-trap TRAP-TYPE
	STATUS current
	ENTERPRISE mib-AN-Dcz-SDS
	VARIABLES { ipwRepeatPingPer }
    	DESCRIPTION "TRAP: IP watchdog send repeat period."
    ::= 74

ipwIgnoreLostCnt-trap TRAP-TYPE
	STATUS current
	ENTERPRISE mib-AN-Dcz-SDS
	VARIABLES { ipwIgnoreLostCnt }
    	DESCRIPTION "TRAP: IP watchdog: number of missing packets to ignore."
    ::= 75

ipwPauseWdAfterAct-trap TRAP-TYPE
	STATUS current
	ENTERPRISE mib-AN-Dcz-SDS
	VARIABLES { ipwPauseWdAfterAct }
    	DESCRIPTION "TRAP: IP watchog pause applied after output activation."
    ::= 76

ipwRelayActTime-trap TRAP-TYPE
	STATUS current
	ENTERPRISE mib-AN-Dcz-SDS
	VARIABLES { ipwRelayActTime }
    	DESCRIPTION "TRAP: Length of IP watchdog notification output active state."
    ::= 77

ipwActualFailed-trap TRAP-TYPE
	STATUS current
	ENTERPRISE mib-AN-Dcz-SDS
	VARIABLES { ipwActualFailed }
    	DESCRIPTION "TRAP: number of missing IP watchdog ping responses."
    ::= 78

ipwLastRTT-trap TRAP-TYPE
	STATUS current
	ENTERPRISE mib-AN-Dcz-SDS
	VARIABLES { ipwLastRTT }
    	DESCRIPTION "TRAP: IP watchdog Round Trip Time for the last ping echo."
    ::= 79

ipwActualRelayState-trap TRAP-TYPE
	STATUS current
	ENTERPRISE mib-AN-Dcz-SDS
	VARIABLES { ipwActualRelayState }
    	DESCRIPTION "TRAP: Actual (virtual) output relay status of IP watchdog."
    ::= 80

-- next

opto1-trap TRAP-TYPE
	STATUS current
	ENTERPRISE mib-AN-Dcz-SDS
	VARIABLES { opto1 }
	DESCRIPTION "TRAP: optical input 1 status."
	::= 100

opto2-trap TRAP-TYPE
	STATUS current
	ENTERPRISE mib-AN-Dcz-SDS
	VARIABLES { opto2 }
	DESCRIPTION "TRAP: optical input 2 status."
	::= 101

opto3-trap TRAP-TYPE
	STATUS current
	ENTERPRISE mib-AN-Dcz-SDS
	VARIABLES { opto3 }
	DESCRIPTION "TRAP: optical input 3 status."
	::= 102

opto4-trap TRAP-TYPE
	STATUS current
	ENTERPRISE mib-AN-Dcz-SDS
	VARIABLES { opto4 }
	DESCRIPTION "TRAP: optical input 4 status."
	::= 103

opto5-trap TRAP-TYPE
	STATUS current
	ENTERPRISE mib-AN-Dcz-SDS
	VARIABLES { opto5 }
	DESCRIPTION "TRAP: optical input 5 status."
	::= 104

opto6-trap TRAP-TYPE
	STATUS current
	ENTERPRISE mib-AN-Dcz-SDS
	VARIABLES { opto6 }
	DESCRIPTION "TRAP: optical input 6 status."
	::= 105

opto7-trap TRAP-TYPE
	STATUS current
	ENTERPRISE mib-AN-Dcz-SDS
	VARIABLES { opto7 }
	DESCRIPTION "TRAP: optical input 7 status."
	::= 106

opto8-trap TRAP-TYPE
	STATUS current
	ENTERPRISE mib-AN-Dcz-SDS
	VARIABLES { opto8 }
	DESCRIPTION "TRAP: optical input 8 status."
	::= 107

logics0input-trap TRAP-TYPE
	STATUS current
	ENTERPRISE mib-AN-Dcz-SDS
	VARIABLES { logics0input }
	DESCRIPTION "TRAP: LOGIC-S0 input status."
	::= 108

-- next

sdsRE1state-trap TRAP-TYPE
	STATUS current
	ENTERPRISE mib-AN-Dcz-SDS
	VARIABLES { sdsRE1state }
	DESCRIPTION "TRAP: Current RELAY 1 output status."
    ::= 150

sdsRE1cby-trap TRAP-TYPE
	STATUS current
	ENTERPRISE mib-AN-Dcz-SDS
	VARIABLES { sdsRE1cby }
	DESCRIPTION "TRAP: RELAY 1 controled by ..."
    ::= 151

sdsRE1name-trap TRAP-TYPE
	STATUS current
	ENTERPRISE mib-AN-Dcz-SDS
	VARIABLES { sdsRE1name }
	DESCRIPTION "TRAP: User name for RELAY 1."
    ::= 152

sdsRE2state-trap TRAP-TYPE
	STATUS current
	ENTERPRISE mib-AN-Dcz-SDS
	VARIABLES { sdsRE2state }
	DESCRIPTION "TRAP: Current RELAY 2 output status."
    ::= 153

sdsRE2cby-trap TRAP-TYPE
	STATUS current
	ENTERPRISE mib-AN-Dcz-SDS
	VARIABLES { sdsRE2cby }
	DESCRIPTION "TRAP: RELAY 2 controled by ..."
    ::= 154

sdsRE2name-trap TRAP-TYPE
	STATUS current
	ENTERPRISE mib-AN-Dcz-SDS
	VARIABLES { sdsRE2name }
	DESCRIPTION "TRAP: User name for RELAY 2."
    ::= 155

sdsRE3state-trap TRAP-TYPE
	STATUS current
	ENTERPRISE mib-AN-Dcz-SDS
	VARIABLES { sdsRE3state }
	DESCRIPTION "TRAP: Current RELAY 3 output status."
    ::= 156

sdsRE3cby-trap TRAP-TYPE
	STATUS current
	ENTERPRISE mib-AN-Dcz-SDS
	VARIABLES { sdsRE3cby }
	DESCRIPTION "TRAP: RELAY 3 controled by ..."
    ::= 157

sdsRE3name-trap TRAP-TYPE
	STATUS current
	ENTERPRISE mib-AN-Dcz-SDS
	VARIABLES { sdsRE3name }
	DESCRIPTION "TRAP: User name for RELAY 3."
    ::= 158

sdsRE4state-trap TRAP-TYPE
	STATUS current
	ENTERPRISE mib-AN-Dcz-SDS
	VARIABLES { sdsRE4state }
	DESCRIPTION "TRAP: Current RELAY 4 output status."
    ::= 159

sdsRE4cby-trap TRAP-TYPE
	STATUS current
	ENTERPRISE mib-AN-Dcz-SDS
	VARIABLES { sdsRE4cby }
	DESCRIPTION "TRAP: RELAY 4 controled by ..."
    ::= 160

sdsRE4name-trap TRAP-TYPE
	STATUS current
	ENTERPRISE mib-AN-Dcz-SDS
	VARIABLES { sdsRE4name }
	DESCRIPTION "TRAP: User name for RELAY 4."
    ::= 161

sdsRE5state-trap TRAP-TYPE
	STATUS current
	ENTERPRISE mib-AN-Dcz-SDS
	VARIABLES { sdsRE5state }
	DESCRIPTION "TRAP: Current RELAY 5 output status."
    ::= 162

sdsRE5cby-trap TRAP-TYPE
	STATUS current
	ENTERPRISE mib-AN-Dcz-SDS
	VARIABLES { sdsRE5cby }
	DESCRIPTION "TRAP: RELAY 5 controled by ..."
    ::= 163

sdsRE5name-trap TRAP-TYPE
	STATUS current
	ENTERPRISE mib-AN-Dcz-SDS
	VARIABLES { sdsRE5name }
	DESCRIPTION "TRAP: User name for RELAY 5."
    ::= 164

sdsRE6state-trap TRAP-TYPE
	STATUS current
	ENTERPRISE mib-AN-Dcz-SDS
	VARIABLES { sdsRE6state }
	DESCRIPTION "TRAP: Current RELAY 6 output status."
    ::= 165

sdsRE6cby-trap TRAP-TYPE
	STATUS current
	ENTERPRISE mib-AN-Dcz-SDS
	VARIABLES { sdsRE6cby }
	DESCRIPTION "TRAP: RELAY 6 controled by ..."
    ::= 166

sdsRE6name-trap TRAP-TYPE
	STATUS current
	ENTERPRISE mib-AN-Dcz-SDS
	VARIABLES { sdsRE6name }
	DESCRIPTION "TRAP: User name for RELAY 6."
    ::= 167

-- next

sdsPWM1freq-trap TRAP-TYPE
	STATUS current
	ENTERPRISE mib-AN-Dcz-SDS
	VARIABLES { sdsPWM1freq }
	DESCRIPTION "TRAP: Actual PWM1 generator frequency [Hz]."
    ::= 200

sdsPWM1duty-trap TRAP-TYPE
	STATUS current
	ENTERPRISE mib-AN-Dcz-SDS
	VARIABLES { sdsPWM1duty }
	DESCRIPTION "TRAP: Actual PWM1 duty control setting."
    ::= 201

-- next

sdsADCrawValue0-trap TRAP-TYPE
	STATUS current
	ENTERPRISE mib-AN-Dcz-SDS
	VARIABLES { sdsADCrawValue0 }
	DESCRIPTION "TRAP: Actual analog input value [raw]."
    ::= 220

sdsADCtext0-trap TRAP-TYPE
	STATUS current
	ENTERPRISE mib-AN-Dcz-SDS
	VARIABLES { sdsADCtext0 }
	DESCRIPTION "TRAP: Textual conversion output for analog input."
    ::= 221

sdsADCintmul0-trap TRAP-TYPE
	STATUS current
	ENTERPRISE mib-AN-Dcz-SDS
	VARIABLES { sdsADCintmul0 }
	DESCRIPTION "TRAP: SI integer MUL value for the analog input (conversion result multiplied by 100)."
    ::= 222

sdsADCname0-trap TRAP-TYPE
	STATUS current
	ENTERPRISE mib-AN-Dcz-SDS
	VARIABLES { sdsADCname0 }
	DESCRIPTION "TRAP: User name for analog input."
    ::= 223

sdsADCrawValue1-trap TRAP-TYPE
	STATUS current
	ENTERPRISE mib-AN-Dcz-SDS
	VARIABLES { sdsADCrawValue1 }
	DESCRIPTION "TRAP: Actual analog input value [raw]."
    ::= 224

sdsADCtext1-trap TRAP-TYPE
	STATUS current
	ENTERPRISE mib-AN-Dcz-SDS
	VARIABLES { sdsADCtext1 }
	DESCRIPTION "TRAP: Textual conversion output for analog input."
    ::= 225

sdsADCintmul1-trap TRAP-TYPE
	STATUS current
	ENTERPRISE mib-AN-Dcz-SDS
	VARIABLES { sdsADCintmul1 }
	DESCRIPTION "TRAP: SI integer MUL value for the analog input (conversion result multiplied by 100)."
    ::= 226

sdsADCname1-trap TRAP-TYPE
	STATUS current
	ENTERPRISE mib-AN-Dcz-SDS
	VARIABLES { sdsADCname1 }
	DESCRIPTION "TRAP: User name for analog input."
    ::= 227

sdsADCrawValue2-trap TRAP-TYPE
	STATUS current
	ENTERPRISE mib-AN-Dcz-SDS
	VARIABLES { sdsADCrawValue2 }
	DESCRIPTION "TRAP: Actual analog input value [raw]."
    ::= 228

sdsADCtext2-trap TRAP-TYPE
	STATUS current
	ENTERPRISE mib-AN-Dcz-SDS
	VARIABLES { sdsADCtext2 }
	DESCRIPTION "TRAP: Textual conversion output for analog input."
    ::= 229

sdsADCintmul2-trap TRAP-TYPE
	STATUS current
	ENTERPRISE mib-AN-Dcz-SDS
	VARIABLES { sdsADCintmul2 }
	DESCRIPTION "TRAP: SI integer MUL value for the analog input (conversion result multiplied by 100)."
    ::= 230

sdsADCname2-trap TRAP-TYPE
	STATUS current
	ENTERPRISE mib-AN-Dcz-SDS
	VARIABLES { sdsADCname2 }
	DESCRIPTION "TRAP: User name for analog input."
    ::= 231

sdsADCrawValue3-trap TRAP-TYPE
	STATUS current
	ENTERPRISE mib-AN-Dcz-SDS
	VARIABLES { sdsADCrawValue3 }
	DESCRIPTION "TRAP: Actual analog input value [raw]."
    ::= 232

sdsADCtext3-trap TRAP-TYPE
	STATUS current
	ENTERPRISE mib-AN-Dcz-SDS
	VARIABLES { sdsADCtext3 }
	DESCRIPTION "TRAP: Textual conversion output for analog input."
    ::= 233

sdsADCintmul3-trap TRAP-TYPE
	STATUS current
	ENTERPRISE mib-AN-Dcz-SDS
	VARIABLES { sdsADCintmul3 }
	DESCRIPTION "TRAP: SI integer MUL value for the analog input (conversion result multiplied by 100)."
    ::= 234

sdsADCname3-trap TRAP-TYPE
	STATUS current
	ENTERPRISE mib-AN-Dcz-SDS
	VARIABLES { sdsADCname3 }
	DESCRIPTION "TRAP: User name for analog input."
    ::= 235

sdsADCrawValue4-trap TRAP-TYPE
	STATUS current
	ENTERPRISE mib-AN-Dcz-SDS
	VARIABLES { sdsADCrawValue4 }
	DESCRIPTION "TRAP: Actual analog input value [raw]."
    ::= 236

sdsADCtext4-trap TRAP-TYPE
	STATUS current
	ENTERPRISE mib-AN-Dcz-SDS
	VARIABLES { sdsADCtext4 }
	DESCRIPTION "TRAP: Textual conversion output for analog input."
    ::= 237

sdsADCintmul4-trap TRAP-TYPE
	STATUS current
	ENTERPRISE mib-AN-Dcz-SDS
	VARIABLES { sdsADCintmul4 }
	DESCRIPTION "TRAP: SI integer MUL value for the analog input (conversion result multiplied by 100)."
    ::= 238

sdsADCname4-trap TRAP-TYPE
	STATUS current
	ENTERPRISE mib-AN-Dcz-SDS
	VARIABLES { sdsADCname4 }
	DESCRIPTION "TRAP: User name for analog input."
    ::= 239

sdsADCrawValue5-trap TRAP-TYPE
	STATUS current
	ENTERPRISE mib-AN-Dcz-SDS
	VARIABLES { sdsADCrawValue5 }
	DESCRIPTION "TRAP: Actual analog input value [raw]."
    ::= 240

sdsADCtext5-trap TRAP-TYPE
	STATUS current
	ENTERPRISE mib-AN-Dcz-SDS
	VARIABLES { sdsADCtext5 }
	DESCRIPTION "TRAP: Textual conversion output for analog input."
    ::= 241

sdsADCintmul5-trap TRAP-TYPE
	STATUS current
	ENTERPRISE mib-AN-Dcz-SDS
	VARIABLES { sdsADCintmul5 }
	DESCRIPTION "TRAP: SI integer MUL value for the analog input (conversion result multiplied by 100)."
    ::= 242

sdsADCname5-trap TRAP-TYPE
	STATUS current
	ENTERPRISE mib-AN-Dcz-SDS
	VARIABLES { sdsADCname5 }
	DESCRIPTION "TRAP: User name for analog input."
    ::= 243

sdsADCrawValue6-trap TRAP-TYPE
	STATUS current
	ENTERPRISE mib-AN-Dcz-SDS
	VARIABLES { sdsADCrawValue6 }
	DESCRIPTION "TRAP: Actual analog input value [raw]."
    ::= 244

sdsADCtext6-trap TRAP-TYPE
	STATUS current
	ENTERPRISE mib-AN-Dcz-SDS
	VARIABLES { sdsADCtext6 }
	DESCRIPTION "TRAP: Textual conversion output for analog input."
    ::= 245

sdsADCintmul6-trap TRAP-TYPE
	STATUS current
	ENTERPRISE mib-AN-Dcz-SDS
	VARIABLES { sdsADCintmul6 }
	DESCRIPTION "TRAP: SI integer MUL value for the analog input (conversion result multiplied by 100)."
    ::= 246

sdsADCname6-trap TRAP-TYPE
	STATUS current
	ENTERPRISE mib-AN-Dcz-SDS
	VARIABLES { sdsADCname6 }
	DESCRIPTION "TRAP: User name for analog input."
    ::= 247

sdsADCrawValue7-trap TRAP-TYPE
	STATUS current
	ENTERPRISE mib-AN-Dcz-SDS
	VARIABLES { sdsADCrawValue7 }
	DESCRIPTION "TRAP: Actual analog input value [raw]."
    ::= 248

sdsADCtext7-trap TRAP-TYPE
	STATUS current
	ENTERPRISE mib-AN-Dcz-SDS
	VARIABLES { sdsADCtext7 }
	DESCRIPTION "TRAP: Textual conversion output for analog input."
    ::= 249

sdsADCintmul7-trap TRAP-TYPE
	STATUS current
	ENTERPRISE mib-AN-Dcz-SDS
	VARIABLES { sdsADCintmul7 }
	DESCRIPTION "TRAP: SI integer MUL value for the analog input (conversion result multiplied by 100)."
    ::= 250

sdsADCname7-trap TRAP-TYPE
	STATUS current
	ENTERPRISE mib-AN-Dcz-SDS
	VARIABLES { sdsADCname7 }
	DESCRIPTION "TRAP: User name for analog input."
    ::= 251

-- next

sdsOneWireStatus-trap TRAP-TYPE
	STATUS current
	ENTERPRISE mib-AN-Dcz-SDS
	VARIABLES { sdsOneWireStatus }
	DESCRIPTION "TRAP: 1-WIRE device status.  INFO: USE INDEX OID TO ACCESS THE TABLE ITEMS."
    ::= 301

sdsOneWireDeviceROMcode-trap TRAP-TYPE
	STATUS current
	ENTERPRISE mib-AN-Dcz-SDS
	VARIABLES { sdsOneWireDeviceROMcode }
	DESCRIPTION "TRAP: 1-WIRE device ROM-CODE.  INFO: USE INDEX OID TO ACCESS THE TABLE ITEMS."
    ::= 302

sdsOneWireName-trap TRAP-TYPE
	STATUS current
	ENTERPRISE mib-AN-Dcz-SDS
	VARIABLES { sdsOneWireName }
	DESCRIPTION "TRAP: 1-WIRE device name.  INFO: USE INDEX OID TO ACCESS THE TABLE ITEMS."
    ::= 303

sdsOneWireFullValIDX0-trap TRAP-TYPE
	STATUS current
	ENTERPRISE mib-AN-Dcz-SDS
	VARIABLES { sdsOneWireFullValIDX0 }
	DESCRIPTION "TRAP: First value received from 1-WIRE device.  INFO: USE INDEX OID TO ACCESS THE TABLE ITEMS."
    ::= 304

sdsOneWireFullValIDX1-trap TRAP-TYPE
	STATUS current
	ENTERPRISE mib-AN-Dcz-SDS
	VARIABLES { sdsOneWireFullValIDX1 }
	DESCRIPTION "TRAP: Second value received from 1-WIRE device.  INFO: USE INDEX OID TO ACCESS THE TABLE ITEMS."
    ::= 305

sdsOneWireConfigFlags-trap TRAP-TYPE
	STATUS current
	ENTERPRISE mib-AN-Dcz-SDS
	VARIABLES { sdsOneWireConfigFlags }
	DESCRIPTION "TRAP: 1-WIRE device user-configuration.  INFO: USE INDEX OID TO ACCESS THE TABLE ITEMS."
    ::= 306

-- next

sdsVersionText-trap TRAP-TYPE
	STATUS current
	ENTERPRISE mib-AN-Dcz-SDS
	VARIABLES { sdsVersionText }
        DESCRIPTION "TRAP: SDS device version text."
    ::= 400

sdsCustomVarTrap1-trap TRAP-TYPE
	STATUS current
	ENTERPRISE mib-AN-Dcz-SDS
	VARIABLES { sdsCustomVarTrap1 }
        DESCRIPTION "TRAP: SDS custom-trap value."
    ::= 401

sdsCustomVarTrap2-trap TRAP-TYPE
	STATUS current
	ENTERPRISE mib-AN-Dcz-SDS
	VARIABLES { sdsCustomVarTrap2 }
        DESCRIPTION "TRAP: SDS custom-trap value."
    ::= 402

sdsCustomVarTrap3-trap TRAP-TYPE
	STATUS current
	ENTERPRISE mib-AN-Dcz-SDS
	VARIABLES { sdsCustomVarTrap3 }
        DESCRIPTION "TRAP: SDS custom-trap value."
    ::= 403

sdsCustomVarTrap4-trap TRAP-TYPE
	STATUS current
	ENTERPRISE mib-AN-Dcz-SDS
	VARIABLES { sdsCustomVarTrap4 }
        DESCRIPTION "TRAP: SDS custom-trap value."
    ::= 404

sdsCustomVarTrap5-trap TRAP-TYPE
	STATUS current
	ENTERPRISE mib-AN-Dcz-SDS
	VARIABLES { sdsCustomVarTrap5 }
        DESCRIPTION "TRAP: SDS custom-trap value."
    ::= 405

sdsCustomVarTrap6-trap TRAP-TYPE
	STATUS current
	ENTERPRISE mib-AN-Dcz-SDS
	VARIABLES { sdsCustomVarTrap6 }
        DESCRIPTION "TRAP: SDS custom-trap value."
    ::= 406

sdsCustomVarTrap7-trap TRAP-TYPE
	STATUS current
	ENTERPRISE mib-AN-Dcz-SDS
	VARIABLES { sdsCustomVarTrap7 }
        DESCRIPTION "TRAP: SDS custom-trap value."
    ::= 407

sdsCustomVarTrap8-trap TRAP-TYPE
	STATUS current
	ENTERPRISE mib-AN-Dcz-SDS
	VARIABLES { sdsCustomVarTrap8 }
        DESCRIPTION "TRAP: SDS custom-trap value."
    ::= 408

sdsCustomVarTrap9-trap TRAP-TYPE
	STATUS current
	ENTERPRISE mib-AN-Dcz-SDS
	VARIABLES { sdsCustomVarTrap9 }
        DESCRIPTION "TRAP: SDS custom-trap value."
    ::= 409

-- next

sdsNTPvalue-trap TRAP-TYPE
	STATUS current
	ENTERPRISE mib-AN-Dcz-SDS
	VARIABLES { sdsNTPvalue }
        DESCRIPTION "TRAP: Actual NTP time value (SDS device is NTP client)."
    ::= 600

sdsSoCtempValue-trap TRAP-TYPE
	STATUS current
	ENTERPRISE mib-AN-Dcz-SDS
	VARIABLES { sdsSoCtempValue }
        DESCRIPTION "TRAP: Actual SoC chip internal temperature, in special units."
    ::= 601

sdsOneWireBUSAcountValue-trap TRAP-TYPE
	STATUS current
	ENTERPRISE mib-AN-Dcz-SDS
	VARIABLES { sdsOneWireBUSAcountValue }
        DESCRIPTION "TRAP: Number of discovered 1-Wire devices on BUS A."
    ::= 602

sdsOneWireBUSBcountValue-trap TRAP-TYPE
	STATUS current
	ENTERPRISE mib-AN-Dcz-SDS
	VARIABLES { sdsOneWireBUSBcountValue }
        DESCRIPTION "TRAP: Number of discovered 1-Wire devices on BUS B."
    ::= 603

sdsGPIOTOPBOARDoutputState-trap TRAP-TYPE
	STATUS current
	ENTERPRISE mib-AN-Dcz-SDS
	VARIABLES { sdsGPIOTOPBOARDoutputState }
        DESCRIPTION "TRAP: GPIO-TOPBOARD actual in-out value."
    ::= 604

sdsGPIOTOPBOARDdirection-trap TRAP-TYPE
	STATUS current
	ENTERPRISE mib-AN-Dcz-SDS
	VARIABLES { sdsGPIOTOPBOARDdirection }
        DESCRIPTION "TRAP: GPIO-TOPBOARD actual direction (in-out) status."
    ::= 605

sdsBackUpCoinBatteryVoltageValue-trap TRAP-TYPE
	STATUS current
	ENTERPRISE mib-AN-Dcz-SDS
	VARIABLES { sdsBackUpCoinBatteryVoltageValue }
        DESCRIPTION "TRAP: Actual voltage reading of the back-up coin battery."
    ::= 606

sdsBackUpCoinBatteryVoltageValue-trap TRAP-TYPE
	STATUS current
	ENTERPRISE mib-AN-Dcz-SDS
	VARIABLES { sdsBackUpCoinBatteryVoltageValue }
        DESCRIPTION "TRAP: Physical presence (insertion) of the SD-CARD."
    ::= 607

sdsCustomVarString1-trap TRAP-TYPE
	STATUS current
	ENTERPRISE mib-AN-Dcz-SDS
	VARIABLES { sdsCustomVarString1 }
        DESCRIPTION "TRAP: Custom String."
    ::= 680

sdsCustomVarString2-trap TRAP-TYPE
	STATUS current
	ENTERPRISE mib-AN-Dcz-SDS
	VARIABLES { sdsCustomVarString2 }
        DESCRIPTION "TRAP: Custom String."
    ::= 681

sdsCustomVarString3-trap TRAP-TYPE
	STATUS current
	ENTERPRISE mib-AN-Dcz-SDS
	VARIABLES { sdsCustomVarString3 }
        DESCRIPTION "TRAP: Custom String."
    ::= 682

sdsCustomVarString4-trap TRAP-TYPE
	STATUS current
	ENTERPRISE mib-AN-Dcz-SDS
	VARIABLES { sdsCustomVarString4 }
        DESCRIPTION "TRAP: Custom String."
    ::= 683

sdsCustomVarString5-trap TRAP-TYPE
	STATUS current
	ENTERPRISE mib-AN-Dcz-SDS
	VARIABLES { sdsCustomVarString5 }
        DESCRIPTION "TRAP: Custom String."
    ::= 684

sdsFULLCrunStatus-trap TRAP-TYPE
	STATUS current
	ENTERPRISE mib-AN-Dcz-SDS
	VARIABLES { sdsFULLCrunStatus }
        DESCRIPTION "TRAP: FULL-C program status."
    ::= 690

-- next

sdsS0impCountT0-trap TRAP-TYPE
	STATUS current
	ENTERPRISE mib-AN-Dcz-SDS
	VARIABLES { sdsS0impCountT0 }
	DESCRIPTION "TRAP: Actual S0 impulse counter value for T0 tarif.  INFO: USE INDEX OID TO ACCESS THE TABLE ITEMS."
    ::= 501

sdsS0impCountT1-trap TRAP-TYPE
	STATUS current
	ENTERPRISE mib-AN-Dcz-SDS
	VARIABLES { sdsS0impCountT1 }
	DESCRIPTION "TRAP: Actual S0 impulse counter value for T1 tarif.  INFO: USE INDEX OID TO ACCESS THE TABLE ITEMS."
    ::= 502

sdsS0impMoneyOffsetT0-trap TRAP-TYPE
	STATUS current
	ENTERPRISE mib-AN-Dcz-SDS
	VARIABLES { sdsS0impMoneyOffsetT0 }
	DESCRIPTION "TRAP: Offset (impulse count) for cash calculation for T0.  INFO: USE INDEX OID TO ACCESS THE TABLE ITEMS."
    ::= 503

sdsS0impMoneyOffsetT1-trap TRAP-TYPE
	STATUS current
	ENTERPRISE mib-AN-Dcz-SDS
	VARIABLES { sdsS0impMoneyOffsetT1 }
	DESCRIPTION "TRAP: Offset (impulse count) for cash calculation for T1.  INFO: USE INDEX OID TO ACCESS THE TABLE ITEMS."
    ::= 504

sdsS0constant-trap TRAP-TYPE
	STATUS current
	ENTERPRISE mib-AN-Dcz-SDS
	VARIABLES { sdsS0constant }
	DESCRIPTION "TRAP: S0 output constant (number of impulses for 1 energy unit).  INFO: USE INDEX OID TO ACCESS THE TABLE ITEMS."
    ::= 505

sdsS0translatedUnitT0-trap TRAP-TYPE
	STATUS current
	ENTERPRISE mib-AN-Dcz-SDS
	VARIABLES { sdsS0translatedUnitT0 }
	DESCRIPTION "TRAP: T0 related S0 impulse count value as textual energy unit.  INFO: USE INDEX OID TO ACCESS THE TABLE ITEMS."
    ::= 506

sdsS0translatedUnitT1-trap TRAP-TYPE
	STATUS current
	ENTERPRISE mib-AN-Dcz-SDS
	VARIABLES { sdsS0translatedUnitT1 }
	DESCRIPTION "TRAP: T1 related S0 impulse count value as textual energy unit.  INFO: USE INDEX OID TO ACCESS THE TABLE ITEMS."
     ::= 507

sdsS0translatedCashT0-trap TRAP-TYPE
	STATUS current
	ENTERPRISE mib-AN-Dcz-SDS
	VARIABLES { sdsS0translatedCashT0 }
	DESCRIPTION "TRAP: T0 related S0 counter value as textual cash value.  INFO: USE INDEX OID TO ACCESS THE TABLE ITEMS."
    ::= 508

sdsS0translatedCashT1-trap TRAP-TYPE
	STATUS current
	ENTERPRISE mib-AN-Dcz-SDS
	VARIABLES { sdsS0translatedCashT1 }
	DESCRIPTION "TRAP: T1 related S0 counter value as textual cash value.  INFO: USE INDEX OID TO ACCESS THE TABLE ITEMS."
    ::= 509

sdsS0actualEnergyFlow-trap TRAP-TYPE
	STATUS current
	ENTERPRISE mib-AN-Dcz-SDS
	VARIABLES { sdsS0actualEnergyFlow }
	DESCRIPTION "TRAP: S0: the actual energy flow value.  INFO: USE INDEX OID TO ACCESS THE TABLE ITEMS."
    ::= 510

sdsS0constantMTD-trap TRAP-TYPE
	STATUS current
	ENTERPRISE mib-AN-Dcz-SDS
	VARIABLES { sdsS0constantMTD }
	DESCRIPTION "TRAP: S0: configuration - the MTD constant.  INFO: USE INDEX OID TO ACCESS THE TABLE ITEMS."
    ::= 511

-- next

sdsCOM1telnetConnected-trap TRAP-TYPE
	STATUS current
	ENTERPRISE mib-AN-Dcz-SDS
	VARIABLES { sdsCOM1telnetConnected }
        DESCRIPTION "TRAP: COM1: Is any Ethernet client connected to Eth-to-Serial converter."
    ::= 800

sdsCOM1baudrate-trap TRAP-TYPE
	STATUS current
	ENTERPRISE mib-AN-Dcz-SDS
	VARIABLES { sdsCOM1baudrate }
        DESCRIPTION "TRAP: COM1: Actual configured UART baud rate in [bps]."
    ::= 801

sdsCOM1dataSize-trap TRAP-TYPE
	STATUS current
	ENTERPRISE mib-AN-Dcz-SDS
	VARIABLES { sdsCOM1dataSize }
        DESCRIPTION "TRAP: COM1: Actual configured UART char data size [num of bits]."
    ::= 802

sdsCOM1stopBits-trap TRAP-TYPE
	STATUS current
	ENTERPRISE mib-AN-Dcz-SDS
	VARIABLES { sdsCOM1stopBits }
        DESCRIPTION "TRAP: COM1: Actual configured UART number of stop bits."
    ::= 803

sdsCOM1parity-trap TRAP-TYPE
	STATUS current
	ENTERPRISE mib-AN-Dcz-SDS
	VARIABLES { sdsCOM1parity }
        DESCRIPTION "TRAP: COM1: Actual configured UART parity."
    ::= 804

sdsCOM1uartInBytes-trap TRAP-TYPE
	STATUS current
	ENTERPRISE mib-AN-Dcz-SDS
	VARIABLES { sdsCOM1uartInBytes }
        DESCRIPTION "TRAP: COM1: Total number of UART IN bytes."
    ::= 805

sdsCOM1uartOutBytes-trap TRAP-TYPE
	STATUS current
	ENTERPRISE mib-AN-Dcz-SDS
	VARIABLES { sdsCOM1uartOutBytes }
        DESCRIPTION "TRAP: COM1: Total number of UART OUT bytes."
    ::= 806

-- next

sdsCOM6telnetConnected-trap TRAP-TYPE
	STATUS current
	ENTERPRISE mib-AN-Dcz-SDS
	VARIABLES { sdsCOM6telnetConnected }
        DESCRIPTION "TRAP: COM6: Is any Ethernet client connected to Eth-to-Serial converter."
    ::= 850

sdsCOM6baudrate-trap TRAP-TYPE
	STATUS current
	ENTERPRISE mib-AN-Dcz-SDS
	VARIABLES { sdsCOM6baudrate }
        DESCRIPTION "TRAP: COM6: Actual configured UART baud rate in [bps]."
    ::= 851

sdsCOM6dataSize-trap TRAP-TYPE
	STATUS current
	ENTERPRISE mib-AN-Dcz-SDS
	VARIABLES { sdsCOM6dataSize }
        DESCRIPTION "TRAP: COM6: Actual configured UART char data size [num of bits]."
    ::= 852

sdsCOM6stopBits-trap TRAP-TYPE
	STATUS current
	ENTERPRISE mib-AN-Dcz-SDS
	VARIABLES { sdsCOM6stopBits }
        DESCRIPTION "TRAP: COM6: Actual configured UART number of stop bits."
    ::= 853

sdsCOM6parity-trap TRAP-TYPE
	STATUS current
	ENTERPRISE mib-AN-Dcz-SDS
	VARIABLES { sdsCOM6parity }
        DESCRIPTION "TRAP: COM6: Actual configured UART parity."
    ::= 854

sdsCOM6uartInBytes-trap TRAP-TYPE
	STATUS current
	ENTERPRISE mib-AN-Dcz-SDS
	VARIABLES { sdsCOM6uartInBytes }
        DESCRIPTION "TRAP: COM1: Total number of UART IN bytes."
    ::= 855

sdsCOM6uartOutBytes-trap TRAP-TYPE
	STATUS current
	ENTERPRISE mib-AN-Dcz-SDS
	VARIABLES { sdsCOM6uartOutBytes }
        DESCRIPTION "TRAP: COM6: Total number of UART OUT bytes."
    ::= 856

-- end

END
