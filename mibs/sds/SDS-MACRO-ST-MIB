SDS-MACRO-ST-MIB DEFINITIONS ::= BEGIN

IMPORTS
     MODULE-IDENTITY, OBJECT-TYPE,
     Counter32, Integer32, Gauge32,
     TimeTicks, IpAddress,
     enterprises
    FROM SNMPv2-SMI;


mib-AN-Dcz-SDS MODULE-IDENTITY
    LAST-UPDATED "202010282122Z"
    ORGANIZATION "AN-D.cz"
    CONTACT-INFO
            "   Adam Nemcek
                AN-D.cz
                -
                -
                CZ EUROPE

                -
                adam.nemcek@an-d.cz"
    DESCRIPTION
            "The MIB module to describe generic objects for AN-D.cz device - SDS MACRO ST."


    REVISION      "202010280000Z"
    DESCRIPTION
            " First revision. By AN."
    ::= { enterprises 33283 }


--
-- MIB file definition for SDS - MACRO ST
--


sdsxpublic OBJECT IDENTIFIER ::= { mib-AN-Dcz-SDS 1 }

sdsMACROST OBJECT IDENTIFIER ::= { sdsxpublic 55 }


-- ****************************************************************************

sdsIPWatchdog OBJECT IDENTIFIER ::= { sdsMACROST 1 }

ipwActive OBJECT-TYPE
    SYNTAX  INTEGER {
                disabled(0),
                active(255)
            }
    MAX-ACCESS  read-only
    STATUS      current
    DESCRIPTION
            "The current IP watchdog status."
    ::= { sdsIPWatchdog 1 }

ipwPingIP OBJECT-TYPE
    SYNTAX      IpAddress
    MAX-ACCESS  read-only
    STATUS      current
    DESCRIPTION
            "IP address of the wdg-monitored object."
    ::= { sdsIPWatchdog 2 }

ipwPauseAfterPwOn OBJECT-TYPE
    SYNTAX Integer32
    MAX-ACCESS  read-only
    STATUS      current
    DESCRIPTION
            "Amount of time in [sec].
             Duration of the IP watchdog disable period,
             applied when watchdog device itself is first powered on."
    ::= { sdsIPWatchdog 3 }

ipwPingTimeout OBJECT-TYPE
    SYNTAX Integer32
    MAX-ACCESS  read-only
    STATUS      current
    DESCRIPTION
            "Config value - the RTT timeout."
    ::= { sdsIPWatchdog 4 }

ipwRepeatPingPer OBJECT-TYPE
    SYNTAX Integer32
    MAX-ACCESS  read-only
    STATUS      current
    DESCRIPTION
            "PING REQUEST packet sending:
             the configured send repeat period, in [miliseconds]."
    ::= { sdsIPWatchdog 5 }

ipwIgnoreLostCnt OBJECT-TYPE
    SYNTAX Gauge32
    MAX-ACCESS  read-only
    STATUS      current
    DESCRIPTION
            "How many lost PING REPLY packets should get ignored,
             before activating the relay."
    ::= { sdsIPWatchdog 6 }

ipwPauseWdAfterAct OBJECT-TYPE
    SYNTAX Integer32
    MAX-ACCESS  read-only
    STATUS      current
    DESCRIPTION
            "Delay of the IP watchdog pause,
             applied when the output relay is activated
             (e.g. the time for controlled device recovery)."
    ::= { sdsIPWatchdog 7 }

ipwRelayActTime OBJECT-TYPE
    SYNTAX Integer32
    MAX-ACCESS  read-only
    STATUS      current
    DESCRIPTION
            "How many [seconds] should be the output relay activated."
    ::= { sdsIPWatchdog 8 }

ipwActualFailed OBJECT-TYPE
    SYNTAX Gauge32
    MAX-ACCESS  read-only
    STATUS      current
    DESCRIPTION
            "How many unreceived PING REPLY packets are detected so far."
    ::= { sdsIPWatchdog 9 }

ipwLastRTT OBJECT-TYPE
    SYNTAX Gauge32
    MAX-ACCESS  read-only
    STATUS      current
    DESCRIPTION
            "Round Trip Time for the last ping echo."
    ::= { sdsIPWatchdog 10 }

ipwActualRelayState OBJECT-TYPE
    SYNTAX Integer32
    MAX-ACCESS  read-only
    STATUS      current
    DESCRIPTION
            "Actual (virtual) output relay status
            (before mapping this status to the selected hardware)."
    ::= { sdsIPWatchdog 11 }

-- ****************************************************************************

sdsOptoInput OBJECT IDENTIFIER ::= { sdsMACROST 2 }

opto1 OBJECT-TYPE
    SYNTAX  INTEGER {
                activeSignalPresent(0),
                noSignal(16)
            }
    MAX-ACCESS  read-only
    STATUS      current
    DESCRIPTION
            "Current OPTO1 binary input status."
    ::= { sdsOptoInput 1 }

opto2 OBJECT-TYPE
    SYNTAX  INTEGER {
                activeSignalPresent(0),
                noSignal(8)
            }
    MAX-ACCESS  read-only
    STATUS      current
    DESCRIPTION
            "Current OPTO2 binary input status."
    ::= { sdsOptoInput 2 }

opto3 OBJECT-TYPE
    SYNTAX  INTEGER {
                activeSignalPresent(0),
                noSignal(4)
            }
    MAX-ACCESS  read-only
    STATUS      current
    DESCRIPTION
            "Current OPTO3 binary input status."
    ::= { sdsOptoInput 3 }

opto4 OBJECT-TYPE
    SYNTAX  INTEGER {
                activeSignalPresent(0),
                noSignal(2)
            }
    MAX-ACCESS  read-only
    STATUS      current
    DESCRIPTION
            "Current OPTO4 binary input status."
    ::= { sdsOptoInput 4 }

opto5 OBJECT-TYPE
    SYNTAX  INTEGER {
                activeSignalPresent(0),
                noSignal(128)
            }
    MAX-ACCESS  read-only
    STATUS      current
    DESCRIPTION
            "Current OPTO5 binary input status."
    ::= { sdsOptoInput 5 }


opto6 OBJECT-TYPE
    SYNTAX  INTEGER {
                activeSignalPresent(0),
                noSignal(64)
            }
    MAX-ACCESS  read-only
    STATUS      current
    DESCRIPTION
            "Current OPTO6 binary input status."
    ::= { sdsOptoInput 6 }


opto7 OBJECT-TYPE
    SYNTAX  INTEGER {
                activeSignalPresent(0),
                noSignal(32)
            }
    MAX-ACCESS  read-only
    STATUS      current
    DESCRIPTION
            "Current OPTO7 binary input status."
    ::= { sdsOptoInput 7 }


opto8 OBJECT-TYPE
    SYNTAX  INTEGER {
                activeSignalPresent(0),
                noSignal(16)
            }
    MAX-ACCESS  read-only
    STATUS      current
    DESCRIPTION
            "Current OPTO8 binary input status."
    ::= { sdsOptoInput 8 }

logics0input OBJECT-TYPE
    SYNTAX  INTEGER {
                activeSignalPresent(0),
                noSignal(1)
            }
    MAX-ACCESS  read-only
    STATUS      current
    DESCRIPTION
            "Current LOGIC-S0 binary input status."
    ::= { sdsOptoInput 9 }

-- ****************************************************************************

sdsOutputRelay OBJECT IDENTIFIER ::= { sdsMACROST 3 }

sdsRE1state OBJECT-TYPE
    SYNTAX  INTEGER {
                off(0),
                activated(255)
            }
    MAX-ACCESS  read-write
    STATUS      current
    DESCRIPTION
            "Current RELAY 1 output status."
    ::= { sdsOutputRelay 1 }

sdsRE1cby OBJECT-TYPE
    SYNTAX  INTEGER {
                manualControl(0),
                sdscControl(2),
                ipwControl(4),
                oneShotReset(8)
            }
    MAX-ACCESS  read-write
    STATUS      current
    DESCRIPTION
            "RELAY 1 controled by ..."
    ::= { sdsOutputRelay 2 }

sdsRE1name OBJECT-TYPE
    SYNTAX  OCTET STRING
    MAX-ACCESS  read-only
    STATUS      current
    DESCRIPTION
            "User name for RELAY 1."
    ::= { sdsOutputRelay 3 }

sdsRE2state OBJECT-TYPE
    SYNTAX  INTEGER {
                off(0),
                activated(255)
            }
    MAX-ACCESS  read-write
    STATUS      current
    DESCRIPTION
            "Current RELAY 2 output status."
    ::= { sdsOutputRelay 4 }

sdsRE2cby OBJECT-TYPE
    SYNTAX  INTEGER {
                manualControl(0),
                sdscControl(2),
                ipwControl(4),
                oneShotReset(8)
            }
    MAX-ACCESS  read-write
    STATUS      current
    DESCRIPTION
            "RELAY 2 controled by ..."
    ::= { sdsOutputRelay 5 }

sdsRE2name OBJECT-TYPE
    SYNTAX  OCTET STRING
    MAX-ACCESS  read-only
    STATUS      current
    DESCRIPTION
            "User name for RELAY 2."
    ::= { sdsOutputRelay 6 }

sdsRE3state OBJECT-TYPE
    SYNTAX  INTEGER {
                off(0),
                activated(255)
            }
    MAX-ACCESS  read-write
    STATUS      current
    DESCRIPTION
            "Current RELAY 3 output status."
    ::= { sdsOutputRelay 7 }

sdsRE3cby OBJECT-TYPE
    SYNTAX  INTEGER {
                manualControl(0),
                sdscControl(2),
                ipwControl(4),
                oneShotReset(8)
            }
    MAX-ACCESS  read-write
    STATUS      current
    DESCRIPTION
            "RELAY 3 controled by ..."
    ::= { sdsOutputRelay 8 }

sdsRE3name OBJECT-TYPE
    SYNTAX  OCTET STRING
    MAX-ACCESS  read-only
    STATUS      current
    DESCRIPTION
            "User name for RELAY 3."
    ::= { sdsOutputRelay 9 }

sdsRE4state OBJECT-TYPE
    SYNTAX  INTEGER {
                off(0),
                activated(255)
            }
    MAX-ACCESS  read-write
    STATUS      current
    DESCRIPTION
            "Current RELAY 4 output status."
    ::= { sdsOutputRelay 10 }

sdsRE4cby OBJECT-TYPE
    SYNTAX  INTEGER {
                manualControl(0),
                sdscControl(2),
                ipwControl(4),
                oneShotReset(8)
            }
    MAX-ACCESS  read-write
    STATUS      current
    DESCRIPTION
            "RELAY 4 controled by ..."
    ::= { sdsOutputRelay 11 }

sdsRE4name OBJECT-TYPE
    SYNTAX  OCTET STRING
    MAX-ACCESS  read-only
    STATUS      current
    DESCRIPTION
            "User name for RELAY 4."
    ::= { sdsOutputRelay 12 }

sdsRE5state OBJECT-TYPE
    SYNTAX  INTEGER {
                off(0),
                activated(255)
            }
    MAX-ACCESS  read-write
    STATUS      current
    DESCRIPTION
            "Current RELAY 5 output status."
    ::= { sdsOutputRelay 13 }

sdsRE5cby OBJECT-TYPE
    SYNTAX  INTEGER {
                manualControl(0),
                sdscControl(2),
                ipwControl(4),
                oneShotReset(8)
            }
    MAX-ACCESS  read-write
    STATUS      current
    DESCRIPTION
            "RELAY 5 controled by ..."
    ::= { sdsOutputRelay 14 }

sdsRE5name OBJECT-TYPE
    SYNTAX  OCTET STRING
    MAX-ACCESS  read-only
    STATUS      current
    DESCRIPTION
            "User name for RELAY 5."
    ::= { sdsOutputRelay 15 }

sdsRE6state OBJECT-TYPE
    SYNTAX  INTEGER {
                off(0),
                activated(255)
            }
    MAX-ACCESS  read-write
    STATUS      current
    DESCRIPTION
            "Current RELAY 6 output status."
    ::= { sdsOutputRelay 16 }

sdsRE6cby OBJECT-TYPE
    SYNTAX  INTEGER {
                manualControl(0),
                sdscControl(2),
                ipwControl(4),
                oneShotReset(8)
            }
    MAX-ACCESS  read-write
    STATUS      current
    DESCRIPTION
            "RELAY 6 controled by ..."
    ::= { sdsOutputRelay 17 }

sdsRE6name OBJECT-TYPE
    SYNTAX  OCTET STRING
    MAX-ACCESS  read-only
    STATUS      current
    DESCRIPTION
            "User name for RELAY 6."
    ::= { sdsOutputRelay 18 }


-- ****************************************************************************

sdsPWMoutput OBJECT IDENTIFIER ::= { sdsMACROST 4 }

sdsPWM1p2freq OBJECT-TYPE
    SYNTAX  Gauge32
    MAX-ACCESS  read-write
    STATUS      current
    DESCRIPTION
            "Actual (PWM 1 and PWM2) generator frequency [Hz]."
    ::= { sdsPWMoutput 1 }

sdsPWM1duty OBJECT-TYPE
    SYNTAX  Gauge32
    MAX-ACCESS  read-write
    STATUS      current
    DESCRIPTION
            "Actual PWM1 duty control setting 0 - 100 [percent]."
    ::= { sdsPWMoutput 2 }

-- { sdsPWMoutput 3 } is RESERVED

sdsPWM2duty OBJECT-TYPE
    SYNTAX  Gauge32
    MAX-ACCESS  read-write
    STATUS      current
    DESCRIPTION
            "Actual PWM2 duty control setting 0 - 100 [percent]."
    ::= { sdsPWMoutput 4 }

sdsPWM3p4freq OBJECT-TYPE
    SYNTAX  Gauge32
    MAX-ACCESS  read-write
    STATUS      current
    DESCRIPTION
            "Actual (PWM 3 and PWM4) generator frequency [Hz]."
    ::= { sdsPWMoutput 5 }

sdsPWM3duty OBJECT-TYPE
    SYNTAX  Gauge32
    MAX-ACCESS  read-write
    STATUS      current
    DESCRIPTION
            "Actual PWM3 duty control setting 0 - 100 [percent]."
    ::= { sdsPWMoutput 6 }

-- { sdsPWMoutput 7 } is RESERVED

sdsPWM4duty OBJECT-TYPE
    SYNTAX  Gauge32
    MAX-ACCESS  read-write
    STATUS      current
    DESCRIPTION
            "Actual PWM4 duty control setting 0 - 100 [percent]."
    ::= { sdsPWMoutput 8 }

-- ****************************************************************************

-- the ADC input items

sdsADCinputs OBJECT IDENTIFIER ::= { sdsMACROST 5 }

sdsADCrawValue1 OBJECT-TYPE
    SYNTAX      Gauge32
    MAX-ACCESS  read-only
    STATUS      current
    DESCRIPTION
            "Actual analog AD1 input value [raw value 0..4095]."
    ::= { sdsADCinputs 1 }

sdsADCtext1 OBJECT-TYPE
    SYNTAX      OCTET STRING
    MAX-ACCESS  read-only
    STATUS      current
    DESCRIPTION
            "SI textual value for AD1 input (conversion result)."
    ::= { sdsADCinputs 5 }

sdsADCunit1 OBJECT-TYPE
    SYNTAX      OCTET STRING
    MAX-ACCESS  read-only
    STATUS      current
    DESCRIPTION
            "User unit for AD1 input."
    ::= { sdsADCinputs 13 }

sdsADCname1 OBJECT-TYPE
    SYNTAX      OCTET STRING
    MAX-ACCESS  read-only
    STATUS      current
    DESCRIPTION
            "User name for AD1 input."
    ::= { sdsADCinputs 9 }

sdsADCrawValue2 OBJECT-TYPE
    SYNTAX      Gauge32
    MAX-ACCESS  read-only
    STATUS      current
    DESCRIPTION
            "Actual analog AD2 input value [raw value 0..4095]."
    ::= { sdsADCinputs 2 }

sdsADCtext2 OBJECT-TYPE
    SYNTAX      OCTET STRING
    MAX-ACCESS  read-only
    STATUS      current
    DESCRIPTION
            "SI textual value for AD2 input (conversion result)."
    ::= { sdsADCinputs 6 }

sdsADCunit2 OBJECT-TYPE
    SYNTAX      OCTET STRING
    MAX-ACCESS  read-only
    STATUS      current
    DESCRIPTION
            "User unit for AD2 input."
    ::= { sdsADCinputs 14 }

sdsADCname2 OBJECT-TYPE
    SYNTAX      OCTET STRING
    MAX-ACCESS  read-only
    STATUS      current
    DESCRIPTION
            "User name for AD2 input."
    ::= { sdsADCinputs 10 }

sdsADCrawValue3 OBJECT-TYPE
    SYNTAX      Gauge32
    MAX-ACCESS  read-only
    STATUS      current
    DESCRIPTION
            "Actual analog AD3 input value [raw value 0..4095]."
    ::= { sdsADCinputs 3 }

sdsADCtext3 OBJECT-TYPE
    SYNTAX      OCTET STRING
    MAX-ACCESS  read-only
    STATUS      current
    DESCRIPTION
            "SI textual value for AD3 input (conversion result)."
    ::= { sdsADCinputs 7 }

sdsADCunit3 OBJECT-TYPE
    SYNTAX      OCTET STRING
    MAX-ACCESS  read-only
    STATUS      current
    DESCRIPTION
            "User unit for AD3 input."
    ::= { sdsADCinputs 15 }

sdsADCname3 OBJECT-TYPE
    SYNTAX      OCTET STRING
    MAX-ACCESS  read-only
    STATUS      current
    DESCRIPTION
            "User name for AD3 input."
    ::= { sdsADCinputs 11 }

sdsADCrawValue4 OBJECT-TYPE
    SYNTAX      Gauge32
    MAX-ACCESS  read-only
    STATUS      current
    DESCRIPTION
            "Actual analog AD4 input value [raw value 0..4095]."
    ::= { sdsADCinputs 4 }

sdsADCtext4 OBJECT-TYPE
    SYNTAX      OCTET STRING
    MAX-ACCESS  read-only
    STATUS      current
    DESCRIPTION
            "SI textual value for AD4 input (conversion result)."
    ::= { sdsADCinputs 8 }

sdsADCunit4 OBJECT-TYPE
    SYNTAX      OCTET STRING
    MAX-ACCESS  read-only
    STATUS      current
    DESCRIPTION
            "User unit for AD4 input."
    ::= { sdsADCinputs 16 }

sdsADCname4 OBJECT-TYPE
    SYNTAX      OCTET STRING
    MAX-ACCESS  read-only
    STATUS      current
    DESCRIPTION
            "User name for AD4 input."
    ::= { sdsADCinputs 12 }

-- ****************************************************************************

-- the ONEWIRE table (MACRO-ST: both BUS A and BUS B in a single table)

-- The ONEWIRE table contains information on the OneWire devices (like DS18B20 or SDS-T-RH)

sdsONEWIRETable OBJECT-TYPE
    SYNTAX      SEQUENCE OF SdsONEWIREEntry
    MAX-ACCESS  not-accessible
    STATUS      current
    DESCRIPTION
            "A list of all (1-Wire) devices."
    ::= { sdsMACROST 6 }

sdsONEWIREEntry OBJECT-TYPE
    SYNTAX      SdsONEWIREEntry
    MAX-ACCESS  not-accessible
    STATUS      current
    DESCRIPTION
            "An entry containing information applicable to a
            particular ONEWIRE device."
    INDEX   { sdsONEWIREtableRowIndex }
    ::= { sdsONEWIRETable 1 }

SdsONEWIREEntry ::=
    SEQUENCE {
        sdsONEWIREdeviceROMcode            OCTET STRING,
        sdsONEWIREactualTempInteger        Integer32,
        sdsONEWIREactualTempFrac           Integer32,
        sdsONEWIREuserName                 OCTET STRING,
        sdsONEWIREactualTempCompleteMul100 Integer32,
        sdsONEWIREtableRowIndex            Integer32,
        sdsONEWIREactualRHpercent          Integer32
    }

sdsONEWIREdeviceROMcode OBJECT-TYPE
    SYNTAX      OCTET STRING
    MAX-ACCESS  read-only
    STATUS      current
    DESCRIPTION
            "Internal ONEWIRE device ROM unique identification code."
    ::= { sdsONEWIREEntry 1 }

sdsONEWIREactualTempInteger OBJECT-TYPE
    SYNTAX      Integer32
    MAX-ACCESS  read-only
    STATUS      current
    DESCRIPTION
            "Actual temperature for this ONEWIRE sensor,
             an integral part."
    ::= { sdsONEWIREEntry 2 }

sdsONEWIREactualTempFrac OBJECT-TYPE
    SYNTAX      Integer32
    MAX-ACCESS  read-only
    STATUS      current
    DESCRIPTION
            "Actual temperature for this ONEWIRE sensor,
             a fractional part."
    ::= { sdsONEWIREEntry 3 }

sdsONEWIREuserName OBJECT-TYPE
    SYNTAX      OCTET STRING
    MAX-ACCESS  read-only
    STATUS      current
    DESCRIPTION
            "User name for the actual ONEWIRE device."
    ::= { sdsONEWIREEntry 4 }

sdsONEWIREactualTempCompleteMul100 OBJECT-TYPE
    SYNTAX      Integer32
    MAX-ACCESS  read-only
    STATUS      current
    DESCRIPTION
            "Actual temperature for this ONEWIRE sensor:
             the complete value multiplied by 100
             (target precision: two post-zero digits)."
    ::= { sdsONEWIREEntry 5 }

sdsONEWIREtableRowIndex OBJECT-TYPE
    SYNTAX      Integer32
    MAX-ACCESS  not-accessible
    STATUS      current
    DESCRIPTION
            "ONEWIRE device index in this table."
    ::= { sdsONEWIREEntry 6 }

sdsONEWIREactualRHpercent OBJECT-TYPE
    SYNTAX      Integer32
    MAX-ACCESS  read-only
    STATUS      current
    DESCRIPTION
            "Actual RH value for this ONEWIRE sensor"
    ::= { sdsONEWIREEntry 7 }

-- ****************************************************************************

sdsVersionEntry OBJECT IDENTIFIER ::= { sdsMACROST 7 }

sdsVersionText OBJECT-TYPE
    SYNTAX    OCTET STRING
    MAX-ACCESS  read-only
    STATUS      current
    DESCRIPTION
            "SDS device version text."
    ::= { sdsVersionEntry 1 }

sdsCustomTrap1 OBJECT-TYPE
    SYNTAX    Integer32
    MAX-ACCESS  read-only
    STATUS      current
    DESCRIPTION
            "SDS-C custom int32 TRAP."
    ::= { sdsVersionEntry 2 }


-- ****************************************************************************

sdsGeneralInfoEntry OBJECT IDENTIFIER ::= { sdsMACROST 8 }

sdsNTPvalue OBJECT-TYPE
    SYNTAX    Counter32
    MAX-ACCESS  read-only
    STATUS      current
    DESCRIPTION
            "Actual NTP UTC time value (SDS device is NTP client)."
    ::= { sdsGeneralInfoEntry 1 }

sdsSoCtempValue OBJECT-TYPE
    SYNTAX    Integer32
    MAX-ACCESS  read-only
    STATUS      current
    DESCRIPTION
            "Actual SoC chip internal temperature,
             represented in a special units [0..4095].
             This needs to be recalculated to get a degC value."
    ::= { sdsGeneralInfoEntry 2 }

sdsOneWireBUSAcountValue OBJECT-TYPE
    SYNTAX    Integer32
    MAX-ACCESS  read-only
    STATUS      current
    DESCRIPTION
            "Number of discovered 1-Wire devices on BUS A."
    ::= { sdsGeneralInfoEntry 3 }

sdsOneWireBUSBcountValue OBJECT-TYPE
    SYNTAX    Integer32
    MAX-ACCESS  read-only
    STATUS      current
    DESCRIPTION
            "Number of discovered 1-Wire devices on BUS B."
    ::= { sdsGeneralInfoEntry 4 }

sdsPDgpioState OBJECT-TYPE
    SYNTAX  Integer32
    MAX-ACCESS  read-write
    STATUS      current
    DESCRIPTION
            "PD0 + PD1 + TOPB actual port-pin bit (log1/log0) status."
    ::= { sdsGeneralInfoEntry 5 }

sdsPDgpioDirection OBJECT-TYPE
    SYNTAX  Integer32
    MAX-ACCESS  read-write
    STATUS      current
    DESCRIPTION
            "PD0 + PD1 + TOPB actual port-pin direction (in/out) status."
    ::= { sdsGeneralInfoEntry 6 }

sdsBackUpCoinBatteryVoltageValue OBJECT-TYPE
    SYNTAX    Integer32
    MAX-ACCESS  read-only
    STATUS      current
    DESCRIPTION
            "Actual voltage reading of the back-up coin battery,
             represented as raw ADC value [0..4095].
             This needs to be recalculated to get a value in Volts."
    ::= { sdsGeneralInfoEntry 7 }

sdsLOCALTIMEvalue OBJECT-TYPE
    SYNTAX    Counter32
    MAX-ACCESS  read-only
    STATUS      current
    DESCRIPTION
            "Actual LOCAL time value (SDS device is NTP client)."
    ::= { sdsGeneralInfoEntry 10 }


-- ****************************************************************************

-- the S0 INPUT table

-- The S0 INPUT contains information from the S0 impulse input

sdsS0Table OBJECT-TYPE
    SYNTAX      SEQUENCE OF SdsS0Entry
    MAX-ACCESS  not-accessible
    STATUS      current
    DESCRIPTION
            "A list of S0 impulse inputs."
    ::= { sdsMACROST 9 }

sdsS0Entry OBJECT-TYPE
    SYNTAX      SdsS0Entry
    MAX-ACCESS  not-accessible
    STATUS      current
    DESCRIPTION
            "An entry containing information applicable to a
            particular S0 input."
    INDEX   { sdsS0tableRowIndex }
    ::= { sdsS0Table 1 }

SdsS0Entry ::=
    SEQUENCE {
        sdsS0impCountT0       Counter32,
        sdsS0impCountT1       Counter32,
        sdsS0impMoneyOffsetT0 Gauge32,
        sdsS0impMoneyOffsetT1 Gauge32,
        sdsS0constant         Gauge32,
        sdsS0translatedUnitT0 OCTET STRING,
        sdsS0translatedUnitT1 OCTET STRING,
        sdsS0translatedCashT0 OCTET STRING,
        sdsS0translatedCashT1 OCTET STRING,
        sdsS0actualEnergyFlow OCTET STRING,
        sdsS0constantMTD      Gauge32,
        sdsS0tableRowIndex    Integer32
    }

sdsS0impCountT0 OBJECT-TYPE
    SYNTAX  Counter32
    MAX-ACCESS  read-only
    STATUS      current
    DESCRIPTION
            "Actual S0 impulse counter value
             for the tarif state T0 (no tarif signal)."
    ::= { sdsS0Entry 1 }

sdsS0impCountT1 OBJECT-TYPE
    SYNTAX  Counter32
    MAX-ACCESS  read-only
    STATUS      current
    DESCRIPTION
            "Actual S0 impulse counter value
            for the tarif state T1 (active tarif signal)."
    ::= { sdsS0Entry 2 }

sdsS0impMoneyOffsetT0 OBJECT-TYPE
    SYNTAX  Gauge32
    MAX-ACCESS  read-only
    STATUS      current
    DESCRIPTION
            "Offset (impulse count) for cash calculation.
             Cash value is calculated relatively starting
             at this offset, for the T0 counter."
    ::= { sdsS0Entry 3 }

sdsS0impMoneyOffsetT1 OBJECT-TYPE
    SYNTAX  Gauge32
    MAX-ACCESS  read-only
    STATUS      current
    DESCRIPTION
            "Offset (impulse count) for cash calculation.
             Cash value is calculated relatively starting
             at this offset, for the T1 counter."
    ::= { sdsS0Entry 4 }

sdsS0constant OBJECT-TYPE
    SYNTAX  Gauge32
    MAX-ACCESS  read-only
    STATUS      current
    DESCRIPTION
            "S0 output constant (number of impulses for 1 energy unit)."
    ::= { sdsS0Entry 5 }

sdsS0translatedUnitT0 OBJECT-TYPE
    SYNTAX  OCTET STRING
    MAX-ACCESS  read-only
    STATUS      current
    DESCRIPTION
            "T0 related S0 impulse count value,
             recalculated into energy units,
             in a textual representation."
    ::= { sdsS0Entry 6 }

sdsS0translatedUnitT1 OBJECT-TYPE
    SYNTAX  OCTET STRING
    MAX-ACCESS  read-only
    STATUS      current
    DESCRIPTION
            "T1 related S0 impulse count value,
             recalculated into energy units,
             in a textual representation."
    ::= { sdsS0Entry 7 }

sdsS0translatedCashT0 OBJECT-TYPE
    SYNTAX  OCTET STRING
    MAX-ACCESS  read-only
    STATUS      current
    DESCRIPTION
            "T0 related S0 counter value recalculated into cash
             (total T0 impulse count minus a T0 custom offset),
             in a textual representation."
    ::= { sdsS0Entry 8 }

sdsS0translatedCashT1 OBJECT-TYPE
    SYNTAX  OCTET STRING
    MAX-ACCESS  read-only
    STATUS      current
    DESCRIPTION
            "T1 related S0 counter value recalculated into cash
             (total T1 impulse count minus a T1 custom offset),
             in a textual representation."
    ::= { sdsS0Entry 9 }

sdsS0actualEnergyFlow OBJECT-TYPE
    SYNTAX  OCTET STRING
    MAX-ACCESS  read-only
    STATUS      current
    DESCRIPTION
            "S0: the actual energy flow value."
    ::= { sdsS0Entry 10 }

sdsS0constantMTD OBJECT-TYPE
    SYNTAX  Gauge32
    MAX-ACCESS  read-only
    STATUS      current
    DESCRIPTION
            "S0 MTD constant."
    ::= { sdsS0Entry 11 }

sdsS0tableRowIndex OBJECT-TYPE
    SYNTAX  Integer32
    MAX-ACCESS  not-accessible
    STATUS      current
    DESCRIPTION
            "S0 table row index."
    ::= { sdsS0Entry 12 }


-- ****************************************************************************

-- the SDSCEP table

-- The SDSCEP contains values from SDS-C sys[140] to sys[147] (user data)

sdsSDSCEPTable OBJECT-TYPE
    SYNTAX      SEQUENCE OF SdsSDSCEPEntry
    MAX-ACCESS  not-accessible
    STATUS      current
    DESCRIPTION
            "A list of SDS-C SDSCEP user values.
             Equals to sys[140] thru sys[147]."
    ::= { sdsMACROST 10 }

sdsSDSCEPEntry OBJECT-TYPE
    SYNTAX      SdsSDSCEPEntry
    MAX-ACCESS  not-accessible
    STATUS      current
    DESCRIPTION
            "An entry containing the values
             for SDS-C SDSCEP items."
    INDEX   { sdsSDSCEPtableRowIndex }
    ::= { sdsSDSCEPTable 1 }

SdsSDSCEPEntry ::=
    SEQUENCE {
        sdsSDSCEPvalue          Integer32,
        sdsSDSCEPtableRowIndex  Integer32
    }

sdsSDSCEPvalue OBJECT-TYPE
    SYNTAX  Integer32
    MAX-ACCESS  read-write
    STATUS      current
    DESCRIPTION
            "Actual value for the particular SDS-C SDSCEP value.
             First index is starting at sys[140]."
    ::= { sdsSDSCEPEntry 1 }

sdsSDSCEPtableRowIndex OBJECT-TYPE
    SYNTAX  Integer32
    MAX-ACCESS  not-accessible
    STATUS      current
    DESCRIPTION
            "Index of the particular SDS-C SDSCEP value.
             Add a number of 139 to this item value,
             to get the exact sys[] location.
             Example: value == 1 -> sys[140]."
    ::= { sdsSDSCEPEntry 2 }

-- ****************************************************************************

sdsCOMxEntry OBJECT IDENTIFIER ::= { sdsMACROST 11 }

sdsETStelnetConnected_COM1 OBJECT-TYPE
    SYNTAX    Integer32
    MAX-ACCESS  read-only
    STATUS      current
    DESCRIPTION
            "Is there any Ethernet client connected
             and using the Eth-to-Serial(COM1) converter,
             at this moment."
    ::= { sdsCOMxEntry 1 }

sdsETSbaudrate_COM1 OBJECT-TYPE
    SYNTAX    Integer32
    MAX-ACCESS  read-write
    STATUS      current
    DESCRIPTION
            "COM1: Actual configured UART baud rate in [bps]."
    ::= { sdsCOMxEntry 2 }

sdsETSdataSize_COM1 OBJECT-TYPE
    SYNTAX    Integer32
    MAX-ACCESS  read-write
    STATUS      current
    DESCRIPTION
            "COM1: Actual configured UART char data size [number of bits per char]."
    ::= { sdsCOMxEntry 3 }

sdsETSstopBits_COM1 OBJECT-TYPE
    SYNTAX    Integer32
    MAX-ACCESS  read-write
    STATUS      current
    DESCRIPTION
            "COM1: Actual configured UART number of stop bits [0, 1 or 2 stop bits]"
    ::= { sdsCOMxEntry 4 }

sdsETSparity_COM1 OBJECT-TYPE
    SYNTAX  INTEGER {
                noParity(1),
                oddParity(2),
                evenParity(3)
            }
    MAX-ACCESS  read-write
    STATUS      current
    DESCRIPTION
            "COM1: Actual configured UART parity."
    ::= { sdsCOMxEntry 5 }

sdsETSuartInBytes_COM1 OBJECT-TYPE
    SYNTAX    Counter32
    MAX-ACCESS  read-only
    STATUS      current
    DESCRIPTION
            "COM1: Total number of UART IN bytes."
    ::= { sdsCOMxEntry 6 }

sdsETSuartOutBytes_COM1 OBJECT-TYPE
    SYNTAX    Counter32
    MAX-ACCESS  read-only
    STATUS      current
    DESCRIPTION
            "COM1: Total number of UART OUT bytes."
    ::= { sdsCOMxEntry 7 }

sdsCOM6baudrate OBJECT-TYPE
    SYNTAX    Integer32
    MAX-ACCESS  read-write
    STATUS      current
    DESCRIPTION
            "COM6: Actual configured UART baud rate in [bps]."
    ::= { sdsCOMxEntry 9 }

sdsCOM6dataSize OBJECT-TYPE
    SYNTAX    Integer32
    MAX-ACCESS  read-write
    STATUS      current
    DESCRIPTION
            "COM6: Actual configured UART char data size [number of bits per char]."
    ::= { sdsCOMxEntry 10 }

sdsCOM6stopBits OBJECT-TYPE
    SYNTAX    Integer32
    MAX-ACCESS  read-write
    STATUS      current
    DESCRIPTION
            "COM6: Actual configured UART number of stop bits [0, 1 or 2 stop bits]"
    ::= { sdsCOMxEntry 11 }

sdsCOM6parity OBJECT-TYPE
    SYNTAX  INTEGER {
                noParity(1),
                oddParity(2),
                evenParity(3)
            }
    MAX-ACCESS  read-write
    STATUS      current
    DESCRIPTION
            "COM6: Actual configured UART parity."
    ::= { sdsCOMxEntry 12 }

sdsCOM6uartInBytes OBJECT-TYPE
    SYNTAX    Counter32
    MAX-ACCESS  read-only
    STATUS      current
    DESCRIPTION
            "COM6: Total number of UART IN bytes."
    ::= { sdsCOMxEntry 13 }

sdsCOM6uartOutBytes OBJECT-TYPE
    SYNTAX    Counter32
    MAX-ACCESS  read-only
    STATUS      current
    DESCRIPTION
            "COM6: Total number of UART OUT bytes."
    ::= { sdsCOMxEntry 14 }


-- ****************************************************************************




-- ****************************************************************************
-- TRAP-SDS-MACROST-MIB DEFINITIONS
-- ****************************************************************************


ipwActive-trap TRAP-TYPE
	STATUS current
	ENTERPRISE mib-AN-Dcz-SDS
	VARIABLES { ipwActive }
    	DESCRIPTION "TRAP: The current IP watchdog status."
    ::= 70

ipwPingIP-trap TRAP-TYPE
	STATUS current
	ENTERPRISE mib-AN-Dcz-SDS
	VARIABLES { ipwPingIP }
    	DESCRIPTION "TRAP: IP address of the wdg monitored object."
    ::= 71

ipwPauseAfterPwOn-trap TRAP-TYPE
	STATUS current
	ENTERPRISE mib-AN-Dcz-SDS
	VARIABLES { ipwPauseAfterPwOn }
    	DESCRIPTION "TRAP: Duration of the IP watchdog disable period."
    ::= 72

ipwPingTimeout-trap TRAP-TYPE
	STATUS current
	ENTERPRISE mib-AN-Dcz-SDS
	VARIABLES { ipwPingTimeout }
    	DESCRIPTION "TRAP: IP watchdog RTT timeout."
    ::= 73

ipwRepeatPingPer-trap TRAP-TYPE
	STATUS current
	ENTERPRISE mib-AN-Dcz-SDS
	VARIABLES { ipwRepeatPingPer }
    	DESCRIPTION "TRAP: IP watchdog send repeat period."
    ::= 74

ipwIgnoreLostCnt-trap TRAP-TYPE
	STATUS current
	ENTERPRISE mib-AN-Dcz-SDS
	VARIABLES { ipwIgnoreLostCnt }
    	DESCRIPTION "TRAP: IP watchdog: number of missing packets to ignore."
    ::= 75

ipwPauseWdAfterAct-trap TRAP-TYPE
	STATUS current
	ENTERPRISE mib-AN-Dcz-SDS
	VARIABLES { ipwPauseWdAfterAct }
    	DESCRIPTION "TRAP: IP watchog pause applied after output activation."
    ::= 76

ipwRelayActTime-trap TRAP-TYPE
	STATUS current
	ENTERPRISE mib-AN-Dcz-SDS
	VARIABLES { ipwRelayActTime }
    	DESCRIPTION "TRAP: Length of IP watchdog notification output active state."
    ::= 77

ipwActualFailed-trap TRAP-TYPE
	STATUS current
	ENTERPRISE mib-AN-Dcz-SDS
	VARIABLES { ipwActualFailed }
    	DESCRIPTION "TRAP: number of missing IP watchdog ping responses."
    ::= 78

ipwLastRTT-trap TRAP-TYPE
	STATUS current
	ENTERPRISE mib-AN-Dcz-SDS
	VARIABLES { ipwLastRTT }
    	DESCRIPTION "TRAP: IP watchdog Round Trip Time for the last ping echo."
    ::= 79

ipwActualRelayState-trap TRAP-TYPE
	STATUS current
	ENTERPRISE mib-AN-Dcz-SDS
	VARIABLES { ipwActualRelayState }
    	DESCRIPTION "TRAP: Actual (virtual) output relay status of IP watchdog."
    ::= 80

-- next

opto1-trap TRAP-TYPE
	STATUS current
	ENTERPRISE mib-AN-Dcz-SDS
	VARIABLES { opto1 }
	DESCRIPTION "TRAP: optical input 1 status."
	::= 100

opto2-trap TRAP-TYPE
	STATUS current
	ENTERPRISE mib-AN-Dcz-SDS
	VARIABLES { opto2 }
	DESCRIPTION "TRAP: optical input 2 status."
	::= 101

opto3-trap TRAP-TYPE
	STATUS current
	ENTERPRISE mib-AN-Dcz-SDS
	VARIABLES { opto3 }
	DESCRIPTION "TRAP: optical input 3 status."
	::= 102

opto4-trap TRAP-TYPE
	STATUS current
	ENTERPRISE mib-AN-Dcz-SDS
	VARIABLES { opto4 }
	DESCRIPTION "TRAP: optical input 4 status."
	::= 103

opto5-trap TRAP-TYPE
	STATUS current
	ENTERPRISE mib-AN-Dcz-SDS
	VARIABLES { opto5 }
	DESCRIPTION "TRAP: optical input 5 status."
	::= 104

opto6-trap TRAP-TYPE
	STATUS current
	ENTERPRISE mib-AN-Dcz-SDS
	VARIABLES { opto6 }
	DESCRIPTION "TRAP: optical input 6 status."
	::= 105

opto7-trap TRAP-TYPE
	STATUS current
	ENTERPRISE mib-AN-Dcz-SDS
	VARIABLES { opto7 }
	DESCRIPTION "TRAP: optical input 7 status."
	::= 106

opto8-trap TRAP-TYPE
	STATUS current
	ENTERPRISE mib-AN-Dcz-SDS
	VARIABLES { opto8 }
	DESCRIPTION "TRAP: optical input 8 status."
	::= 107

logics0input-trap TRAP-TYPE
	STATUS current
	ENTERPRISE mib-AN-Dcz-SDS
	VARIABLES { logics0input }
	DESCRIPTION "TRAP: LOGIC-S0 input status."
	::= 108

-- next

sdsRE1state-trap TRAP-TYPE
	STATUS current
	ENTERPRISE mib-AN-Dcz-SDS
	VARIABLES { sdsRE1state }
	DESCRIPTION "TRAP: Current RELAY 1 output status."
    ::= 150

sdsRE1cby-trap TRAP-TYPE
	STATUS current
	ENTERPRISE mib-AN-Dcz-SDS
	VARIABLES { sdsRE1cby }
	DESCRIPTION "TRAP: RELAY 1 controled by ..."
    ::= 151

sdsRE1name-trap TRAP-TYPE
	STATUS current
	ENTERPRISE mib-AN-Dcz-SDS
	VARIABLES { sdsRE1name }
	DESCRIPTION "TRAP: User name for RELAY 1."
    ::= 152

sdsRE2state-trap TRAP-TYPE
	STATUS current
	ENTERPRISE mib-AN-Dcz-SDS
	VARIABLES { sdsRE2state }
	DESCRIPTION "TRAP: Current RELAY 2 output status."
    ::= 153

sdsRE2cby-trap TRAP-TYPE
	STATUS current
	ENTERPRISE mib-AN-Dcz-SDS
	VARIABLES { sdsRE2cby }
	DESCRIPTION "TRAP: RELAY 2 controled by ..."
    ::= 154

sdsRE2name-trap TRAP-TYPE
	STATUS current
	ENTERPRISE mib-AN-Dcz-SDS
	VARIABLES { sdsRE2name }
	DESCRIPTION "TRAP: User name for RELAY 2."
    ::= 155

sdsRE3state-trap TRAP-TYPE
	STATUS current
	ENTERPRISE mib-AN-Dcz-SDS
	VARIABLES { sdsRE3state }
	DESCRIPTION "TRAP: Current RELAY 3 output status."
    ::= 156

sdsRE3cby-trap TRAP-TYPE
	STATUS current
	ENTERPRISE mib-AN-Dcz-SDS
	VARIABLES { sdsRE3cby }
	DESCRIPTION "TRAP: RELAY 3 controled by ..."
    ::= 157

sdsRE3name-trap TRAP-TYPE
	STATUS current
	ENTERPRISE mib-AN-Dcz-SDS
	VARIABLES { sdsRE3name }
	DESCRIPTION "TRAP: User name for RELAY 3."
    ::= 158

sdsRE4state-trap TRAP-TYPE
	STATUS current
	ENTERPRISE mib-AN-Dcz-SDS
	VARIABLES { sdsRE4state }
	DESCRIPTION "TRAP: Current RELAY 4 output status."
    ::= 159

sdsRE4cby-trap TRAP-TYPE
	STATUS current
	ENTERPRISE mib-AN-Dcz-SDS
	VARIABLES { sdsRE4cby }
	DESCRIPTION "TRAP: RELAY 4 controled by ..."
    ::= 160

sdsRE4name-trap TRAP-TYPE
	STATUS current
	ENTERPRISE mib-AN-Dcz-SDS
	VARIABLES { sdsRE4name }
	DESCRIPTION "TRAP: User name for RELAY 4."
    ::= 161

sdsRE5state-trap TRAP-TYPE
	STATUS current
	ENTERPRISE mib-AN-Dcz-SDS
	VARIABLES { sdsRE5state }
	DESCRIPTION "TRAP: Current RELAY 5 output status."
    ::= 162

sdsRE5cby-trap TRAP-TYPE
	STATUS current
	ENTERPRISE mib-AN-Dcz-SDS
	VARIABLES { sdsRE5cby }
	DESCRIPTION "TRAP: RELAY 5 controled by ..."
    ::= 163

sdsRE5name-trap TRAP-TYPE
	STATUS current
	ENTERPRISE mib-AN-Dcz-SDS
	VARIABLES { sdsRE5name }
	DESCRIPTION "TRAP: User name for RELAY 5."
    ::= 164

sdsRE6state-trap TRAP-TYPE
	STATUS current
	ENTERPRISE mib-AN-Dcz-SDS
	VARIABLES { sdsRE6state }
	DESCRIPTION "TRAP: Current RELAY 6 output status."
    ::= 165

sdsRE6cby-trap TRAP-TYPE
	STATUS current
	ENTERPRISE mib-AN-Dcz-SDS
	VARIABLES { sdsRE6cby }
	DESCRIPTION "TRAP: RELAY 6 controled by ..."
    ::= 166

sdsRE6name-trap TRAP-TYPE
	STATUS current
	ENTERPRISE mib-AN-Dcz-SDS
	VARIABLES { sdsRE6name }
	DESCRIPTION "TRAP: User name for RELAY 6."
    ::= 167

-- next


sdsPWM1p2freq-trap TRAP-TYPE
	STATUS current
	ENTERPRISE mib-AN-Dcz-SDS
	VARIABLES { sdsPWM1p2freq }
	DESCRIPTION "TRAP: Actual (PWM1 and PWM2) generator frequency [Hz]."
    ::= 200

sdsPWM1duty-trap TRAP-TYPE
	STATUS current
	ENTERPRISE mib-AN-Dcz-SDS
	VARIABLES { sdsPWM1duty }
	DESCRIPTION "TRAP: Actual PWM1 duty control setting."
    ::= 201

sdsPWM2duty-trap TRAP-TYPE
	STATUS current
	ENTERPRISE mib-AN-Dcz-SDS
	VARIABLES { sdsPWM1duty }
	DESCRIPTION "TRAP: Actual PWM2 duty control setting."
    ::= 203

sdsPWM3p4freq-trap TRAP-TYPE
	STATUS current
	ENTERPRISE mib-AN-Dcz-SDS
	VARIABLES { sdsPWM3p4freq }
	DESCRIPTION "TRAP: Actual (PWM3 and PWM4) generator frequency [Hz]."
    ::= 204

sdsPWM3duty-trap TRAP-TYPE
	STATUS current
	ENTERPRISE mib-AN-Dcz-SDS
	VARIABLES { sdsPWM3duty }
	DESCRIPTION "TRAP: Actual PWM3 duty control setting."
    ::= 205

sdsPWM4duty-trap TRAP-TYPE
	STATUS current
	ENTERPRISE mib-AN-Dcz-SDS
	VARIABLES { sdsPWM4duty }
	DESCRIPTION "TRAP: Actual PWM4 duty control setting."
    ::= 207

-- next

sdsADCrawValue1-trap TRAP-TYPE
	STATUS current
	ENTERPRISE mib-AN-Dcz-SDS
	VARIABLES { sdsADCrawValue1 }
	DESCRIPTION "TRAP: Actual AD1 input value [raw]."
    ::= 250

sdsADCtext1-trap TRAP-TYPE
	STATUS current
	ENTERPRISE mib-AN-Dcz-SDS
	VARIABLES { sdsADCtext1 }
	DESCRIPTION "TRAP: Textual conversion output for AD1 input."
    ::= 254

sdsADCunit1-trap TRAP-TYPE
	STATUS current
	ENTERPRISE mib-AN-Dcz-SDS
	VARIABLES { sdsADCunit1 }
	DESCRIPTION "TRAP: User unit for AD1 input."
    ::= 262

sdsADCname1-trap TRAP-TYPE
	STATUS current
	ENTERPRISE mib-AN-Dcz-SDS
	VARIABLES { sdsADCname1 }
	DESCRIPTION "TRAP: User name for AD1 input."
    ::= 258

sdsADCrawValue2-trap TRAP-TYPE
	STATUS current
	ENTERPRISE mib-AN-Dcz-SDS
	VARIABLES { sdsADCrawValue2 }
	DESCRIPTION "TRAP: Actual AD2 input value [raw]."
    ::= 251

sdsADCtext2-trap TRAP-TYPE
	STATUS current
	ENTERPRISE mib-AN-Dcz-SDS
	VARIABLES { sdsADCtext2 }
	DESCRIPTION "TRAP: Textual conversion output for AD2 input."
    ::= 255

sdsADCunit2-trap TRAP-TYPE
	STATUS current
	ENTERPRISE mib-AN-Dcz-SDS
	VARIABLES { sdsADCunit2 }
	DESCRIPTION "TRAP: User unit for AD2 input."
    ::= 263

sdsADCname2-trap TRAP-TYPE
	STATUS current
	ENTERPRISE mib-AN-Dcz-SDS
	VARIABLES { sdsADCname2 }
	DESCRIPTION "TRAP: User name for AD2 input."
    ::= 259

sdsADCrawValue3-trap TRAP-TYPE
	STATUS current
	ENTERPRISE mib-AN-Dcz-SDS
	VARIABLES { sdsADCrawValue3 }
	DESCRIPTION "TRAP: Actual AD3 input value [raw]."
    ::= 252

sdsADCtext3-trap TRAP-TYPE
	STATUS current
	ENTERPRISE mib-AN-Dcz-SDS
	VARIABLES { sdsADCtext3 }
	DESCRIPTION "TRAP: Textual conversion output for AD3 input."
    ::= 256

sdsADCunit3-trap TRAP-TYPE
	STATUS current
	ENTERPRISE mib-AN-Dcz-SDS
	VARIABLES { sdsADCunit3 }
	DESCRIPTION "TRAP: User unit for AD3 input."
    ::= 264

sdsADCname3-trap TRAP-TYPE
	STATUS current
	ENTERPRISE mib-AN-Dcz-SDS
	VARIABLES { sdsADCname3 }
	DESCRIPTION "TRAP: User name for AD3 input."
    ::= 260

sdsADCrawValue4-trap TRAP-TYPE
	STATUS current
	ENTERPRISE mib-AN-Dcz-SDS
	VARIABLES { sdsADCrawValue3 }
	DESCRIPTION "TRAP: Actual AD4 input value [raw]."
    ::= 253

sdsADCtext4-trap TRAP-TYPE
	STATUS current
	ENTERPRISE mib-AN-Dcz-SDS
	VARIABLES { sdsADCtext4 }
	DESCRIPTION "TRAP: Textual conversion output for AD4 input."
    ::= 257

sdsADCunit4-trap TRAP-TYPE
	STATUS current
	ENTERPRISE mib-AN-Dcz-SDS
	VARIABLES { sdsADCunit4 }
	DESCRIPTION "TRAP: User unit for AD4 input."
    ::= 265

sdsADCname4-trap TRAP-TYPE
	STATUS current
	ENTERPRISE mib-AN-Dcz-SDS
	VARIABLES { sdsADCname4 }
	DESCRIPTION "TRAP: User name for AD4 input."
    ::= 261

-- next

sdsONEWIREactualTempInteger-trap TRAP-TYPE
	STATUS current
	ENTERPRISE mib-AN-Dcz-SDS
	VARIABLES { sdsONEWIREactualTempInteger }
	DESCRIPTION "TRAP: Actual temperature [integral part] for this DS18B20 sensor.
                     INFO: USE INDEX OID TO ACCESS THE TABLE ITEMS."
    ::= 300

sdsONEWIREactualTempFrac-trap TRAP-TYPE
	STATUS current
	ENTERPRISE mib-AN-Dcz-SDS
	VARIABLES { sdsONEWIREactualTempFrac }
	DESCRIPTION "TRAP: Actual temperature [a fractional part] for this DS18B20 sensor.
                     INFO: USE INDEX OID TO ACCESS THE TABLE ITEMS."
    ::= 301

sdsONEWIREdeviceROMcode-trap TRAP-TYPE
	STATUS current
	ENTERPRISE mib-AN-Dcz-SDS
	VARIABLES { sdsONEWIREdeviceROMcode }
	DESCRIPTION "TRAP: DS18B20 device ROM code.
                     INFO: USE INDEX OID TO ACCESS THE TABLE ITEMS."
    ::= 302

sdsONEWIREuserName-trap TRAP-TYPE
	STATUS current
	ENTERPRISE mib-AN-Dcz-SDS
	VARIABLES { sdsONEWIREuserName }
	DESCRIPTION "TRAP: User name for this DS18B20 device.
                     INFO: USE INDEX OID TO ACCESS THE TABLE ITEMS."
    ::= 303

sdsONEWIREactualTempCompleteMul100-trap TRAP-TYPE
	STATUS current
	ENTERPRISE mib-AN-Dcz-SDS
	VARIABLES { sdsONEWIREactualTempCompleteMul100 }
	DESCRIPTION "TRAP: Actual temperature [a complete value, multiplied by 100].
                     INFO: USE INDEX OID TO ACCESS THE TABLE ITEMS."
    ::= 304

sdsONEWIREactualRHpercent-trap TRAP-TYPE
	STATUS current
	ENTERPRISE mib-AN-Dcz-SDS
	VARIABLES { sdsONEWIREactualRHpercent }
	DESCRIPTION "TRAP: Actual RH value for SDS-T-RH sensor on this position.
                     INFO: USE INDEX OID TO ACCESS THE TABLE ITEMS."
    ::= 306

-- next

sdsVersionText-trap TRAP-TYPE
	STATUS current
	ENTERPRISE mib-AN-Dcz-SDS
	VARIABLES { sdsVersionText }
        DESCRIPTION "TRAP: SDS device version text."
    ::= 400

sdsCustomTrap1-trap TRAP-TYPE
	STATUS current
	ENTERPRISE mib-AN-Dcz-SDS
	VARIABLES { sdsCustomTrap1 }
        DESCRIPTION "TRAP: SDS-C custom int32 trap."
    ::= 401

-- next

sdsNTPvalue-trap TRAP-TYPE
	STATUS current
	ENTERPRISE mib-AN-Dcz-SDS
	VARIABLES { sdsNTPvalue }
        DESCRIPTION "TRAP: Actual NTP UTC time value (SDS device is NTP client)."
    ::= 600

sdsSoCtempValue-trap TRAP-TYPE
	STATUS current
	ENTERPRISE mib-AN-Dcz-SDS
	VARIABLES { sdsSoCtempValue }
        DESCRIPTION "TRAP: Actual SoC chip internal temperature, in special units."
    ::= 601

sdsOneWireBUSAcountValue-trap TRAP-TYPE
	STATUS current
	ENTERPRISE mib-AN-Dcz-SDS
	VARIABLES { sdsOneWireBUSAcountValue }
        DESCRIPTION "TRAP: Number of discovered 1-Wire devices on BUS A."
    ::= 602

sdsOneWireBUSBcountValue-trap TRAP-TYPE
	STATUS current
	ENTERPRISE mib-AN-Dcz-SDS
	VARIABLES { sdsOneWireBUSBcountValue }
        DESCRIPTION "TRAP: Number of discovered 1-Wire devices on BUS B."
    ::= 603

sdsPDgpioState-trap TRAP-TYPE
	STATUS current
	ENTERPRISE mib-AN-Dcz-SDS
	VARIABLES { sdsPDgpioState }
        DESCRIPTION "TRAP: actual port-pin bit (log1/log0) status."
    ::= 604

sdsPDgpioDirection-trap TRAP-TYPE
	STATUS current
	ENTERPRISE mib-AN-Dcz-SDS
	VARIABLES { sdsPDgpioDirection }
        DESCRIPTION "TRAP: actual port-pin direction (in/out) status."
    ::= 605

sdsBackUpCoinBatteryVoltageValue-trap TRAP-TYPE
	STATUS current
	ENTERPRISE mib-AN-Dcz-SDS
	VARIABLES { sdsBackUpCoinBatteryVoltageValue }
        DESCRIPTION "TRAP: Actual voltage reading of the back-up coin battery, raw ADC value."
    ::= 606

sdsLOCALTIMEvalue-trap TRAP-TYPE
	STATUS current
	ENTERPRISE mib-AN-Dcz-SDS
	VARIABLES { sdsLOCALTIMEvalue }
        DESCRIPTION "TRAP: Actual LOCAL time value (SDS device is NTP client)."
    ::= 610

-- next

sdsS0impCountT0-trap TRAP-TYPE
	STATUS current
	ENTERPRISE mib-AN-Dcz-SDS
	VARIABLES { sdsS0impCountT0 }
	DESCRIPTION "TRAP: Actual S0 impulse counter value for T0 tarif.
                     INFO: USE INDEX OID TO ACCESS THE TABLE ITEMS."
    ::= 501

sdsS0impCountT1-trap TRAP-TYPE
	STATUS current
	ENTERPRISE mib-AN-Dcz-SDS
	VARIABLES { sdsS0impCountT1 }
	DESCRIPTION "TRAP: Actual S0 impulse counter value for T1 tarif.
                     INFO: USE INDEX OID TO ACCESS THE TABLE ITEMS."
    ::= 502

sdsS0impMoneyOffsetT0-trap TRAP-TYPE
	STATUS current
	ENTERPRISE mib-AN-Dcz-SDS
	VARIABLES { sdsS0impMoneyOffsetT0 }
	DESCRIPTION "TRAP: Offset (impulse count) for cash calculation for T0.
                     INFO: USE INDEX OID TO ACCESS THE TABLE ITEMS."
    ::= 503

sdsS0impMoneyOffsetT1-trap TRAP-TYPE
	STATUS current
	ENTERPRISE mib-AN-Dcz-SDS
	VARIABLES { sdsS0impMoneyOffsetT1 }
	DESCRIPTION "TRAP: Offset (impulse count) for cash calculation for T1.
                     INFO: USE INDEX OID TO ACCESS THE TABLE ITEMS."
    ::= 504

sdsS0constant-trap TRAP-TYPE
	STATUS current
	ENTERPRISE mib-AN-Dcz-SDS
	VARIABLES { sdsS0constant }
	DESCRIPTION "TRAP: S0 output constant (number of impulses for 1 energy unit).
                     INFO: USE INDEX OID TO ACCESS THE TABLE ITEMS."
    ::= 505

sdsS0translatedUnitT0-trap TRAP-TYPE
	STATUS current
	ENTERPRISE mib-AN-Dcz-SDS
	VARIABLES { sdsS0translatedUnitT0 }
	DESCRIPTION "TRAP: T0 related S0 impulse count value as textual energy unit.
                     INFO: USE INDEX OID TO ACCESS THE TABLE ITEMS."
    ::= 506

sdsS0translatedUnitT1-trap TRAP-TYPE
	STATUS current
	ENTERPRISE mib-AN-Dcz-SDS
	VARIABLES { sdsS0translatedUnitT1 }
	DESCRIPTION "TRAP: T1 related S0 impulse count value as textual energy unit.
                     INFO: USE INDEX OID TO ACCESS THE TABLE ITEMS."
    ::= 507

sdsS0translatedCashT0-trap TRAP-TYPE
	STATUS current
	ENTERPRISE mib-AN-Dcz-SDS
	VARIABLES { sdsS0translatedCashT0 }
	DESCRIPTION "TRAP: T0 related S0 counter value as textual cash value.
                     INFO: USE INDEX OID TO ACCESS THE TABLE ITEMS."
    ::= 508

sdsS0translatedCashT1-trap TRAP-TYPE
	STATUS current
	ENTERPRISE mib-AN-Dcz-SDS
	VARIABLES { sdsS0translatedCashT1 }
	DESCRIPTION "TRAP: T1 related S0 counter value as textual cash value.
                     INFO: USE INDEX OID TO ACCESS THE TABLE ITEMS."
    ::= 509

sdsS0actualEnergyFlow-trap TRAP-TYPE
	STATUS current
	ENTERPRISE mib-AN-Dcz-SDS
	VARIABLES { sdsS0actualEnergyFlow }
	DESCRIPTION "TRAP: S0: the actual energy flow value.
                     INFO: USE INDEX OID TO ACCESS THE TABLE ITEMS."
    ::= 510

sdsS0constantMTD-trap TRAP-TYPE
	STATUS current
	ENTERPRISE mib-AN-Dcz-SDS
	VARIABLES { sdsS0constantMTD }
	DESCRIPTION "TRAP: Actual MTD constat configuration value.
                     INFO: USE INDEX OID TO ACCESS THE TABLE ITEMS."
    ::= 511

-- next

sdsSDSCEPvalue-trap TRAP-TYPE
	STATUS current
	ENTERPRISE mib-AN-Dcz-SDS
	VARIABLES { sdsSDSCEPvalue }
	DESCRIPTION "TRAP: Actual value for the particular SDS-C SDSCEP value.
                     INFO: USE INDEX OID TO ACCESS THE TABLE ITEMS."
    ::= 700

-- next

sdsETStelnetConnected_COM1-trap TRAP-TYPE
	STATUS current
	ENTERPRISE mib-AN-Dcz-SDS
	VARIABLES { sdsETStelnetConnected_COM1 }
        DESCRIPTION "TRAP: Is any Ethernet client connected to Eth-to-Serial COM1 converter."
    ::= 800

sdsETSbaudrate_COM1trap TRAP-TYPE
	STATUS current
	ENTERPRISE mib-AN-Dcz-SDS
	VARIABLES { sdsETSbaudrate_COM1 }
        DESCRIPTION "TRAP: COM1 actual configured UART baud rate in [bps]."
    ::= 801

sdsETSdataSize_COM1-trap TRAP-TYPE
	STATUS current
	ENTERPRISE mib-AN-Dcz-SDS
	VARIABLES { sdsETSdataSize_COM1 }
        DESCRIPTION "TRAP: COM1 actual configured UART char data size [num of bits]."
    ::= 802

sdsETSstopBits_COM1-trap TRAP-TYPE
	STATUS current
	ENTERPRISE mib-AN-Dcz-SDS
	VARIABLES { sdsETSstopBits_COM1 }
        DESCRIPTION "TRAP: COM1 actual configured UART number of stop bits."
    ::= 803

sdsETSparity_COM1-trap TRAP-TYPE
	STATUS current
	ENTERPRISE mib-AN-Dcz-SDS
	VARIABLES { sdsETSparity_COM1 }
        DESCRIPTION "TRAP: COM6 actual configured UART parity."
    ::= 804

sdsETSuartInBytes_COM1-trap TRAP-TYPE
	STATUS current
	ENTERPRISE mib-AN-Dcz-SDS
	VARIABLES { sdsETSuartInBytes_COM1 }
        DESCRIPTION "TRAP: COM6 total number of UART IN bytes."
    ::= 805

sdsETSuartOutBytes_COM1trap TRAP-TYPE
	STATUS current
	ENTERPRISE mib-AN-Dcz-SDS
	VARIABLES { sdsETSuartOutBytes_COM1 }
        DESCRIPTION "TRAP: COM6 total number of UART OUT bytes."
    ::= 806

sdsCOM6baudrate-trap TRAP-TYPE
	STATUS current
	ENTERPRISE mib-AN-Dcz-SDS
	VARIABLES { sdsCOM6baudrate }
        DESCRIPTION "TRAP: COM6 actual configured UART baud rate in [bps]."
    ::= 811

sdsCOM6dataSize-trap TRAP-TYPE
	STATUS current
	ENTERPRISE mib-AN-Dcz-SDS
	VARIABLES { sdsCOM6dataSize }
        DESCRIPTION "TRAP: COM6 actual configured UART char data size [num of bits]."
    ::= 812

sdsCOM6stopBits-trap TRAP-TYPE
	STATUS current
	ENTERPRISE mib-AN-Dcz-SDS
	VARIABLES { sdsCOM6stopBits }
        DESCRIPTION "TRAP: COM6 actual configured UART number of stop bits."
    ::= 813

sdsCOM6parity-trap TRAP-TYPE
	STATUS current
	ENTERPRISE mib-AN-Dcz-SDS
	VARIABLES { sdsCOM6parity }
        DESCRIPTION "TRAP: COM6 actual configured UART parity."
    ::= 814

sdsCOM6uartInBytes-trap TRAP-TYPE
	STATUS current
	ENTERPRISE mib-AN-Dcz-SDS
	VARIABLES { sdsCOM6uartInBytes }
        DESCRIPTION "TRAP: COM1 total number of UART IN bytes."
    ::= 815

sdsCOM6uartOutBytes-trap TRAP-TYPE
	STATUS current
	ENTERPRISE mib-AN-Dcz-SDS
	VARIABLES { sdsCOM6uartOutBytes }
        DESCRIPTION "TRAP: COM1 total number of UART OUT bytes."
    ::= 816

-- end

END
