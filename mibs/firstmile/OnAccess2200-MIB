-- FirstMileCom
--

-- OnAccess2200 V1.0 SVN375
--  2019-09-16


OnAccess2200-MIB DEFINITIONS ::= BEGIN

IMPORTS
					enterprises,Gauge				FROM RFC1155-SMI
					DisplayString					FROM RFC1213-MIB
					TRAP-TYPE						FROM RFC-1215;

firstmilecom  OBJECT IDENTIFIER ::= {enterprises 28350}

mc  OBJECT IDENTIFIER ::= {firstmilecom 4}

onaccess2200 OBJECT IDENTIFIER ::= {mc 1}

mc2200-NMC   OBJECT IDENTIFIER ::= {onaccess2200  1}

mc2200-TrapID OBJECT IDENTIFIER ::= {onaccess2200  2}

mc2200-GEmib OBJECT IDENTIFIER ::= {onaccess2200 3}

-- mc2200-TrapID   OBJECT IDENTIFIER ::= {mc2200-trap  1}

mc2200-SystemInfo OBJECT IDENTIFIER ::= {mc2200-NMC 0}
mc2200-Master OBJECT IDENTIFIER ::= {mc2200-NMC 1}





-- chassis 0
mc2200-ch0ChassisDetail OBJECT IDENTIFIER ::= {mc2200-Master 0}


-- System information
mc2200-SysIPAddress OBJECT-TYPE
        SYNTAX      IpAddress
        ACCESS      read-only
        STATUS      mandatory
        DESCRIPTION
                    " The IP Address used by the Ethernet interface
                     of this device"
        ::= { mc2200-SystemInfo 1 }

mc2200-SysSubnetMask OBJECT-TYPE
        SYNTAX      IpAddress
        ACCESS      read-only
        STATUS      mandatory
        DESCRIPTION
                    " The subnet mask used by the Ethernet interface
                     of this device"
        ::= { mc2200-SystemInfo 2 }

mc2200-SysGateway OBJECT-TYPE
        SYNTAX      IpAddress
        ACCESS      read-only
        STATUS      mandatory
        DESCRIPTION
                    " The IP gateway used by the Ethernet interface
                     of this device"
        ::= { mc2200-SystemInfo 3 }

mc2200-SysMACAddress OBJECT-TYPE
        SYNTAX      IpAddress
        ACCESS      read-only
        STATUS      mandatory
        DESCRIPTION
                    " The MAC Address used by the Ethernet interface
                    of this device"
        ::= { mc2200-SystemInfo 4 }

mc2200-SysContact OBJECT-TYPE
        SYNTAX      DisplayString
        ACCESS      read-write
        STATUS      mandatory
        DESCRIPTION
                   " Mirror of this Management Module's system contact."
        ::= { mc2200-SystemInfo 5 }

mc2200-SysName OBJECT-TYPE
        SYNTAX      DisplayString
        ACCESS      read-write
        STATUS      mandatory
        DESCRIPTION
                   " Mirror of this Management Module's system name."
        ::= { mc2200-SystemInfo 6 }

mc2200-SysLocation OBJECT-TYPE
        SYNTAX      DisplayString
        ACCESS      read-write
        STATUS      mandatory
        DESCRIPTION
                   " Mirror of this Management Module's system location"
        ::= { mc2200-SystemInfo 7 }

mc2200-SNMPTrapIP1 OBJECT-TYPE
        SYNTAX      IpAddress
        ACCESS      read-only
        STATUS      mandatory
        DESCRIPTION
                   " Traps generated by this management module will be sent
                     to this IP address."
        ::= { mc2200-SystemInfo 8 }

mc2200-SNMPTrapIP2 OBJECT-TYPE
        SYNTAX      IpAddress
        ACCESS      read-only
        STATUS      mandatory
        DESCRIPTION
                    " Traps generated by this management module will be sent
                     to this IP address."
        ::= { mc2200-SystemInfo 9 }

mc2200-SNMPTrapIP3 OBJECT-TYPE
        SYNTAX      IpAddress
        ACCESS      read-only
        STATUS      mandatory
        DESCRIPTION
                    " Traps generated by this management module will be sent
                     to this IP address."
        ::= { mc2200-SystemInfo 10 }

mc2200-SNMPTrapIP4 OBJECT-TYPE
        SYNTAX      IpAddress
        ACCESS      read-only
        STATUS      mandatory
        DESCRIPTION
                    " Traps generated by this management module will be sent
                     to this IP address."
        ::= { mc2200-SystemInfo 11 }

mc2200-SNMPTrapIP5 OBJECT-TYPE
        SYNTAX      IpAddress
        ACCESS      read-only
        STATUS      mandatory
        DESCRIPTION
                    " Traps generated by this management module will be sent
                     to this IP address."
        ::= { mc2200-SystemInfo 12}

mc2200-alarminfor OBJECT-TYPE
    SYNTAX  DisplayString
    ACCESS  not-accessible
    STATUS  mandatory
    DESCRIPTION
            "show alarm information."
    ::= { mc2200-SystemInfo 13 }

-- Chasiss 0 :master chassis
-- chassis detail
mc2200-ch0Status     OBJECT-TYPE
		SYNTAX		INTEGER {connected(1),disconnected(2)}
		MAX-ACCESS	read-only
		STATUS		current
		DESCRIPTION
                    " Chassis console is connected or disconnected."
        ::= {mc2200-ch0ChassisDetail 1 }

mc2200-ch0LocalConverterNumber     OBJECT-TYPE
		SYNTAX		INTEGER (0..15)
		MAX-ACCESS	read-only
		STATUS		current
		DESCRIPTION
                    " Number of converters inserted in this chassis."
        ::= {mc2200-ch0ChassisDetail 2 }

mc2200-ch0RemoteConverterNumber	OBJECT-TYPE
		SYNTAX		INTEGER (0..15)
		MAX-ACCESS	read-only
		STATUS		current
		DESCRIPTION
                    " Number of converters connect with the local cards
                      in this chassis"
		::= { mc2200-ch0ChassisDetail 3 }

mc2200-ch0PowerA	OBJECT-TYPE
		SYNTAX	    INTEGER {active(1),standby(2),down(3)}
		MAX-ACCESS	read-only
		STATUS		current
		DESCRIPTION
                    " Power unit B's status ,Active is in use, Standby is on but not use,Off is not"

		::= { mc2200-ch0ChassisDetail 4 }

mc2200-ch0PowerB	OBJECT-TYPE
		SYNTAX	    INTEGER {active(1),standby(2),down(3)}
		MAX-ACCESS	read-only
		STATUS		current
		DESCRIPTION
                    " Power unit B's status ,Active is in use, Standby is on but not use,Off is not"
		::= { mc2200-ch0ChassisDetail 5 }

mc2200-ch0FanA	    OBJECT-TYPE
		SYNTAX	    INTEGER {ok(1),fault(2)}
		MAX-ACCESS	read-only
		STATUS		current
		DESCRIPTION
                    " Fan unit A's status, OK is working,Fault is not. "
		::= { mc2200-ch0ChassisDetail 6 }

mc2200-ch0FanB	    OBJECT-TYPE
		SYNTAX	    INTEGER {ok(1),fault(2)}
		MAX-ACCESS	read-only
		STATUS		current
		DESCRIPTION
                 " Fan unit B's status, OK is working,Fault is not. "
		::= { mc2200-ch0ChassisDetail 7 }

mc2200-ch0HardwareVersion	    OBJECT-TYPE
		SYNTAX	    DisplayString
		MAX-ACCESS	read-only
		STATUS		current
		DESCRIPTION
                    "Chassis hardware version"
		::= { mc2200-ch0ChassisDetail 8 }

mc2200-ch0Description    OBJECT-TYPE
		SYNTAX	    DisplayString
		MAX-ACCESS	read-only
		STATUS		current
		DESCRIPTION
                 " Chassis Description. "
		::= { mc2200-ch0ChassisDetail 9 }

mc2200-ch0AvailableConverterSlots	    OBJECT-TYPE
		SYNTAX	    INTEGER
		MAX-ACCESS	read-only
		STATUS		current
		DESCRIPTION
                    " Chassis Available Converter Slots. "
		::= { mc2200-ch0ChassisDetail 10 }

mc2200-ch0OccupiedSlots	    OBJECT-TYPE
		SYNTAX	    INTEGER
		MAX-ACCESS	read-only
		STATUS		current
		DESCRIPTION
                 " Chassis Occupied Slots. "
		::= { mc2200-ch0ChassisDetail 11 }

mc2200-ch0EmptySlots	    OBJECT-TYPE
		SYNTAX	    INTEGER
		MAX-ACCESS	read-only
		STATUS		current
		DESCRIPTION
                 " Chassis Empty Slots. "
		::= { mc2200-ch0ChassisDetail 12 }




-- =========================
-- GEMux8 Table======================================================================

mc2200-GEmux8Table	   OBJECT-TYPE
					SYNTAX			SEQUENCE OF MC2200-GEmux8Entry
					MAX-ACCESS		not-accessible
					STATUS			current
					DESCRIPTION
                     "Sparse table containing one entry for each GEmux8
                     10/100Mbps Twisted-Pair to Fiber Ethernet Media Converter
                     in the system, indexed by chassisIndex and slotIndex."

					::= { mc2200-GEmib 1 }



mc2200-GEmux8Entry			OBJECT-TYPE
						SYNTAX			MC2200-GEmux8Entry
						MAX-ACCESS		not-accessible
						STATUS			current
						DESCRIPTION
            "One table entry per slot in the media converter chassis.
             If physical slot 'n' contains a powered GEmux8 media
             converter, then entry 'n' in this table exists and describes
             the state of the converter's lamps  If slot 'n' is empty, does
             not exist, or contains a different type of device, then table
             entry 'n' does not exist."

						INDEX			{ mc2200-GEmux8CardIndex }
						::= { mc2200-GEmux8Table 1 }


-- ==========================
-- CH-unit config info table --
-- ==========================
MC2200-GEmux8Entry ::=
				SEQUENCE {
					mc2200-GEmux8CardIndex			    INTEGER,	-- 2
					mc2200-GEmux8LocalLANSFPInfo       DisplayString,
					mc2200-GEmux8LocalLANLink          INTEGER,
					mc2200-GEmux8LocalWANSFPInfo       DisplayString,
					mc2200-GEmux8LocalWANLink          INTEGER,
					mc2200-GEmux8APSActivePort         INTEGER,
					mc2200-GEmux8LocalPort1Link        INTEGER,
		  	        mc2200-GEmux8LocalPort1Speed       INTEGER,
					mc2200-GEmux8LocalPort1Duplex      INTEGER, -- 10
					mc2200-GEmux8LocalPort1TxRate      INTEGER,
					mc2200-GEmux8LocalPort1RxRate      INTEGER,
					mc2200-GEmux8LocalPort1Mode	    INTEGER,
					mc2200-GEmux8LocalPort1MDIX        INTEGER,
					mc2200-GEmux8LocalPort2Link        INTEGER,
		  	        mc2200-GEmux8LocalPort2Speed       INTEGER,
					mc2200-GEmux8LocalPort2Duplex      INTEGER,
					mc2200-GEmux8LocalPort2TxRate      INTEGER,
					mc2200-GEmux8LocalPort2RxRate      INTEGER,
					mc2200-GEmux8LocalPort2Mode	    INTEGER, -- 20
					mc2200-GEmux8LocalPort2MDIX        INTEGER,
					mc2200-GEmux8LocalPort3Link        INTEGER,
		  	        mc2200-GEmux8LocalPort3Speed       INTEGER,
					mc2200-GEmux8LocalPort3Duplex      INTEGER,
					mc2200-GEmux8LocalPort3TxRate      INTEGER,
					mc2200-GEmux8LocalPort3RxRate      INTEGER,
					mc2200-GEmux8LocalPort3Mode	    INTEGER,
					mc2200-GEmux8LocalPort3MDIX        INTEGER,
					mc2200-GEmux8LocalPort4Link        INTEGER,
		  	        mc2200-GEmux8LocalPort4Speed       INTEGER, -- 30
					mc2200-GEmux8LocalPort4Duplex      INTEGER,
					mc2200-GEmux8LocalPort4TxRate      INTEGER,
					mc2200-GEmux8LocalPort4RxRate      INTEGER,
					mc2200-GEmux8LocalPort4Mode	    INTEGER,
					mc2200-GEmux8LocalPort4MDIX        INTEGER,
					mc2200-GEmux8LocalPort5Link        INTEGER,
		  	        mc2200-GEmux8LocalPort5Speed       INTEGER,
					mc2200-GEmux8LocalPort5Duplex      INTEGER,
					mc2200-GEmux8LocalPort5TxRate      INTEGER,
					mc2200-GEmux8LocalPort5RxRate      INTEGER, -- 40
					mc2200-GEmux8LocalPort5Mode	    INTEGER,
					mc2200-GEmux8LocalPort5MDIX        INTEGER,
					mc2200-GEmux8LocalPort6Link        INTEGER,
		  	        mc2200-GEmux8LocalPort6Speed       INTEGER,
					mc2200-GEmux8LocalPort6Duplex      INTEGER,
					mc2200-GEmux8LocalPort6TxRate      INTEGER,
					mc2200-GEmux8LocalPort6RxRate      INTEGER,
					mc2200-GEmux8LocalPort6Mode	    INTEGER,
					mc2200-GEmux8LocalPort6MDIX        INTEGER,
					mc2200-GEmux8LocalPort7Link        INTEGER, -- 50
		  	        mc2200-GEmux8LocalPort7Speed       INTEGER,
					mc2200-GEmux8LocalPort7Duplex      INTEGER,
					mc2200-GEmux8LocalPort7TxRate      INTEGER,
					mc2200-GEmux8LocalPort7RxRate      INTEGER,
					mc2200-GEmux8LocalPort7Mode	    INTEGER,
					mc2200-GEmux8LocalPort7MDIX        INTEGER,
					mc2200-GEmux8LocalPort8Link        INTEGER,
		  	        mc2200-GEmux8LocalPort8Speed       INTEGER,
					mc2200-GEmux8LocalPort8Duplex      INTEGER,
					mc2200-GEmux8LocalPort8TxRate      INTEGER, -- 60
					mc2200-GEmux8LocalPort8RxRate      INTEGER,
					mc2200-GEmux8LocalPort8Mode	    INTEGER,
					mc2200-GEmux8LocalPort8MDIX        INTEGER,
					mc2200-GEmux8MibPort1RxGoodOctets        Counter64,

                    mc2200-GEmux8MibPort1RxFCSErr        		Counter64,
                    mc2200-GEmux8MibPort1TxFCSErr        		Counter64,
					mc2200-GEmux8MibPort2RxGoodOctets        Counter64,

                    mc2200-GEmux8MibPort2RxFCSErr        		Counter64, -- 70
                    mc2200-GEmux8MibPort2TxFCSErr        		Counter64,
					mc2200-GEmux8MibPort3RxGoodOctets        Counter64,

                    mc2200-GEmux8MibPort3RxFCSErr        		Counter64,
                    mc2200-GEmux8MibPort3TxFCSErr        		Counter64,
					mc2200-GEmux8MibPort4RxGoodOctets        Counter64,

                    mc2200-GEmux8MibPort4RxFCSErr        		Counter64,
                    mc2200-GEmux8MibPort4TxFCSErr        		Counter64,
					mc2200-GEmux8MibPort5RxGoodOctets        Counter64, -- 80

                    mc2200-GEmux8MibPort5RxFCSErr        		Counter64,
                    mc2200-GEmux8MibPort5TxFCSErr        		Counter64,
					mc2200-GEmux8MibPort6RxGoodOctets        Counter64,

                    mc2200-GEmux8MibPort6RxFCSErr        		Counter64,
                    mc2200-GEmux8MibPort6TxFCSErr        		Counter64,
					mc2200-GEmux8MibPort7RxGoodOctets        Counter64,

                    mc2200-GEmux8MibPort7RxFCSErr        		Counter64, -- 90
                    mc2200-GEmux8MibPort7TxFCSErr        		Counter64,
					mc2200-GEmux8MibPort8RxGoodOctets        Counter64,

                    mc2200-GEmux8MibPort8RxFCSErr        		Counter64,
                    mc2200-GEmux8MibPort8TxFCSErr        		Counter64,
                    mc2200-GEmux8RemoteLANSFPInfo       DisplayString,
					mc2200-GEmux8RemoteLANLink         INTEGER,
					mc2200-GEmux8RemoteWANSFPInfo       DisplayString,
					mc2200-GEmux8RemoteWANLink         INTEGER,
					mc2200-GEmux8RemotePort1Link       INTEGER, -- 100
		  	        mc2200-GEmux8RemotePort1Speed      INTEGER,
					mc2200-GEmux8RemotePort1Duplex     INTEGER,
					mc2200-GEmux8RemotePort1Mode	    INTEGER,
					mc2200-GEmux8RemotePort1MDIX       INTEGER,
					mc2200-GEmux8RemotePort2Link       INTEGER,
		  	        mc2200-GEmux8RemotePort2Speed      INTEGER,
					mc2200-GEmux8RemotePort2Duplex     INTEGER,
					mc2200-GEmux8RemotePort2Mode	    INTEGER,
					mc2200-GEmux8RemotePort2MDIX       INTEGER,
					mc2200-GEmux8RemotePort3Link       INTEGER, -- 110
		  	        mc2200-GEmux8RemotePort3Speed      INTEGER,
					mc2200-GEmux8RemotePort3Duplex     INTEGER,
					mc2200-GEmux8RemotePort3Mode	    INTEGER,
					mc2200-GEmux8RemotePort3MDIX       INTEGER,
					mc2200-GEmux8RemotePort4Link       INTEGER,
		  	        mc2200-GEmux8RemotePort4Speed      INTEGER,
					mc2200-GEmux8RemotePort4Duplex     INTEGER,
					mc2200-GEmux8RemotePort4Mode	    INTEGER,
					mc2200-GEmux8RemotePort4MDIX       INTEGER,
					mc2200-GEmux8RemotePort5Link       INTEGER, -- 120
		  	        mc2200-GEmux8RemotePort5Speed      INTEGER,
					mc2200-GEmux8RemotePort5Duplex     INTEGER,
					mc2200-GEmux8RemotePort5Mode	    INTEGER,
					mc2200-GEmux8RemotePort5MDIX       INTEGER,
					mc2200-GEmux8RemotePort6Link       INTEGER,
		  	        mc2200-GEmux8RemotePort6Speed      INTEGER,
					mc2200-GEmux8RemotePort6Duplex     INTEGER,
					mc2200-GEmux8RemotePort6Mode	    INTEGER,
					mc2200-GEmux8RemotePort6MDIX       INTEGER,
					mc2200-GEmux8RemotePort7Link       INTEGER, -- 130
		  	        mc2200-GEmux8RemotePort7Speed      INTEGER,
					mc2200-GEmux8RemotePort7Duplex     INTEGER,
					mc2200-GEmux8RemotePort7Mode	    INTEGER,
					mc2200-GEmux8RemotePort7MDIX       INTEGER,
					mc2200-GEmux8RemotePort8Link       INTEGER,
		  	        mc2200-GEmux8RemotePort8Speed      INTEGER,
					mc2200-GEmux8RemotePort8Duplex     INTEGER,
					mc2200-GEmux8RemotePort8Mode	    INTEGER,
					mc2200-GEmux8RemotePort8MDIX       INTEGER,
					mc2200-GEmux8RemoteIPAddress       IpAddress, -- 140
		  	        mc2200-GEmux8RemoteSubnetMask      IpAddress,
					mc2200-GEmux8RemoteGateWay         IpAddress,
					mc2200-GEmux8RemoteVLANEnable	    INTEGER,
					mc2200-GEmux8RemoteVID         	INTEGER,
                    mc2200-GEmux8RemoteAlarm       	INTEGER,
                    mc2200-GEmux8RFD					INTEGER,
                    mc2200-GEmux8Default				INTEGER,
                    mc2200-GEmux8Reboot				INTEGER,  -- 148
                    mc2200-GEmux8LocalCardREMOTEMODE   INTEGER,  -- 149

                    mc2200-GEmux8Localportuser1     DisplayString,  -- 150
                    mc2200-GEmux8Localportuser2     DisplayString,
                    mc2200-GEmux8Localportuser3     DisplayString,
                    mc2200-GEmux8Localportuser4     DisplayString,
                    mc2200-GEmux8Localportuser5     DisplayString,
                    mc2200-GEmux8Localportuser6     DisplayString,
                    mc2200-GEmux8Localportuser7     DisplayString,
                    mc2200-GEmux8Localportuser8     DisplayString,    -- 157

                    mc2200-GEmux8Remoteportuser1     DisplayString,
                    mc2200-GEmux8Remoteportuser2     DisplayString,
                    mc2200-GEmux8Remoteportuser3     DisplayString,
                    mc2200-GEmux8Remoteportuser4     DisplayString,
                    mc2200-GEmux8Remoteportuser5     DisplayString,
                    mc2200-GEmux8Remoteportuser6     DisplayString,
                    mc2200-GEmux8Remoteportuser7     DisplayString,
                    mc2200-GEmux8Remoteportuser8     DisplayString,    -- 165
					mc2200-GEmux8TrapFilterLocalLAN			INTEGER,
					mc2200-GEmux8TrapFilterLocalWAN			INTEGER,
					mc2200-GEmux8TrapFilterRemotePower		INTEGER,
					mc2200-GEmux8TrapFilterRemoteLAN		INTEGER,
					mc2200-GEmux8TrapFilterRemoteWAN		INTEGER

				}


mc2200-GEmux8CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GEmux8Entry 2 }

mc2200-GEmux8LocalLANSFPInfo	OBJECT-TYPE
						SYNTAX		DisplayString
						MAX-ACCESS		read-only
						STATUS			current
						DESCRIPTION
                            "GEMux8 Local card's LAN port SFP infomation."
						::= { mc2200-GEmux8Entry 3 }
mc2200-GEmux8LocalLANLink      OBJECT-TYPE
						SYNTAX			INTEGER {up(1),
						                         down(2),
						                         active(3),
						                         standby(4)}
						MAX-ACCESS		read-only
						STATUS			mandatory
						DESCRIPTION
                            "GEmux8 Local card's LAN port work link status."
						::= { mc2200-GEmux8Entry 4 }
mc2200-GEmux8LocalWANSFPInfo	OBJECT-TYPE
						SYNTAX		DisplayString
						MAX-ACCESS		read-only
						STATUS			current
						DESCRIPTION
                            "GEMux8 Local card's WAN port SFP infomation."
						::= { mc2200-GEmux8Entry 5 }
mc2200-GEmux8LocalWANLink	    OBJECT-TYPE
						SYNTAX			INTEGER {up(1),
						                         down(2),
						                         active(3),
						                         standby(4)}
						MAX-ACCESS		read-only
						STATUS			current
						DESCRIPTION
                            "GEmux8 Local card's WAN port work link status."
						::= { mc2200-GEmux8Entry 6 }
mc2200-GEmux8APSActivePort		OBJECT-TYPE
						SYNTAX			INTEGER {wan(1),
						                         wan(2)}
						MAX-ACCESS		read-write
						STATUS			current
						DESCRIPTION
                            "GEmux8 APS Active Port setting."
						::= { mc2200-GEmux8Entry 7 }
mc2200-GEmux8LocalPort1Link	OBJECT-TYPE
						SYNTAX			INTEGER  {up(1),down(2)}
						MAX-ACCESS		read-only
						STATUS			current
						DESCRIPTION
                            "GEmux8 Local card's port1 work link status."
						::= { mc2200-GEmux8Entry 8 }

mc2200-GEmux8LocalPort1Speed	OBJECT-TYPE
						SYNTAX			INTEGER  {speed100M(1),speed10M(2),auto(3)}
						MAX-ACCESS		read-only
						STATUS			current
						DESCRIPTION
                            "GEmux8 Local card's port1 work speed status. "
						::= { mc2200-GEmux8Entry 9 }

mc2200-GEmux8LocalPort1Duplex	OBJECT-TYPE
						SYNTAX			INTEGER {full-duplex(1),half-duplex(2), auto(3)}
						MAX-ACCESS		read-only
						STATUS			current
						DESCRIPTION
                            "GEmux8 Local card's port1 work duplex status."
						::= { mc2200-GEmux8Entry 10 }

mc2200-GEmux8LocalPort1TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port1 Tx Rate. "
						::= { mc2200-GEmux8Entry 11 }
mc2200-GEmux8LocalPort1RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port1 Rx Rate."
						::= { mc2200-GEmux8Entry 12 }
mc2200-GEmux8LocalPort1Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port1 Mode configuration,
                    	set INTEGER(1) to Auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  13 }

mc2200-GEmux8LocalPort1MDIX    OBJECT-TYPE
						SYNTAX			INTEGER {auto(1),
						                         mdi(2),
						                         mdi-x(3)}
						MAX-ACCESS		read-write
						STATUS			current
						DESCRIPTION
                        "GEmux8 Local card's port1 Mode configuration,
                    	set INTEGER(1) to Auto,
                    	set INTEGER(2) to MDI,
                    	set INTEGER(3) to MDI-X,
                    	Ohter value is invalid"
						::= { mc2200-GEmux8Entry 14 }

mc2200-GEmux8LocalPort2Link	OBJECT-TYPE
						SYNTAX			INTEGER  {up(1),down(2)}
						MAX-ACCESS		read-only
						STATUS			current
						DESCRIPTION
                            "GEmux8 Local card's port2 work link status."
						::= { mc2200-GEmux8Entry 15 }

mc2200-GEmux8LocalPort2Speed	OBJECT-TYPE
						SYNTAX			INTEGER  {speed100M(1),speed10M(2),auto(3)}
						MAX-ACCESS		read-only
						STATUS			current
						DESCRIPTION
                            "GEmux8 Local card's port2 work speed status. "
						::= { mc2200-GEmux8Entry 16 }

mc2200-GEmux8LocalPort2Duplex	OBJECT-TYPE
						SYNTAX			INTEGER {full-duplex(1),half-duplex(2), auto(3)}
						MAX-ACCESS		read-only
						STATUS			current
						DESCRIPTION
                            "GEmux8 Local card's port2 work duplex status."
						::= { mc2200-GEmux8Entry 17 }

mc2200-GEmux8LocalPort2TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port2 Tx Rate. "
						::= { mc2200-GEmux8Entry 18 }
mc2200-GEmux8LocalPort2RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port2 Rx Rate."
						::= { mc2200-GEmux8Entry 19 }
mc2200-GEmux8LocalPort2Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port2 Mode configuration,
                    	set INTEGER(1) to Auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  20 }

mc2200-GEmux8LocalPort2MDIX    OBJECT-TYPE
						SYNTAX			INTEGER {auto(1),
						                         mdi(2),
						                         mdi-x(3)}
						MAX-ACCESS		read-write
						STATUS			current
						DESCRIPTION
                        "GEmux8 Local card's port2 Mode configuration,
                    	set INTEGER(1) to Auto,
                    	set INTEGER(2) to MDI,
                    	set INTEGER(3) to MDI-X,
                    	Ohter value is invalid"
						::= { mc2200-GEmux8Entry 21 }


mc2200-GEmux8LocalPort3Link	OBJECT-TYPE
						SYNTAX			INTEGER  {up(1),down(2)}
						MAX-ACCESS		read-only
						STATUS			current
						DESCRIPTION
                            "GEmux8 Local card's port3 work link status."
						::= { mc2200-GEmux8Entry 22 }

mc2200-GEmux8LocalPort3Speed	OBJECT-TYPE
						SYNTAX			INTEGER  {speed100M(1),speed10M(2),auto(3)}
						MAX-ACCESS		read-only
						STATUS			current
						DESCRIPTION
                            "GEmux8 Local card's port3 work speed status. "
						::= { mc2200-GEmux8Entry 23 }

mc2200-GEmux8LocalPort3Duplex	OBJECT-TYPE
						SYNTAX			INTEGER {full-duplex(1),half-duplex(2), auto(3)}
						MAX-ACCESS		read-only
						STATUS			current
						DESCRIPTION
                            "GEmux8 Local card's port3 work duplex status."
						::= { mc2200-GEmux8Entry 24 }

mc2200-GEmux8LocalPort3TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port3 Tx Rate. "
						::= { mc2200-GEmux8Entry 25 }
mc2200-GEmux8LocalPort3RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port3 Rx Rate."
						::= { mc2200-GEmux8Entry 26 }
mc2200-GEmux8LocalPort3Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port3 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  27 }

mc2200-GEmux8LocalPort3MDIX    OBJECT-TYPE
						SYNTAX			INTEGER {auto(1),
						                         mdi(2),
						                         mdi-x(3)}
						MAX-ACCESS		read-write
						STATUS			current
						DESCRIPTION
                        "GEmux8 Local card's port3 Mode configuration,
                    	set INTEGER(1) to auto,
                    	set INTEGER(2) to MDI,
                    	set INTEGER(3) to MDI-X,
                    	Ohter value is invalid"
						::= { mc2200-GEmux8Entry 28 }

mc2200-GEmux8LocalPort4Link	OBJECT-TYPE
						SYNTAX			INTEGER  {up(1),down(2)}
						MAX-ACCESS		read-only
						STATUS			current
						DESCRIPTION
                            "GEmux8 Local card's port4 work link status."
						::= { mc2200-GEmux8Entry 29 }

mc2200-GEmux8LocalPort4Speed	OBJECT-TYPE
						SYNTAX			INTEGER  {speed100M(1),speed10M(2),auto(3)}
						MAX-ACCESS		read-only
						STATUS			current
						DESCRIPTION
                            "GEmux8 Local card's port4 work speed status. "
						::= { mc2200-GEmux8Entry 30 }

mc2200-GEmux8LocalPort4Duplex	OBJECT-TYPE
						SYNTAX			INTEGER {full-duplex(1),half-duplex(2), auto(3)}
						MAX-ACCESS		read-only
						STATUS			current
						DESCRIPTION
                            "GEmux8 Local card's port4 work duplex status."
						::= { mc2200-GEmux8Entry 31 }

mc2200-GEmux8LocalPort4TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port4 Tx Rate. "
						::= { mc2200-GEmux8Entry 32 }
mc2200-GEmux8LocalPort4RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port4 Rx Rate."
						::= { mc2200-GEmux8Entry 33 }
mc2200-GEmux8LocalPort4Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port4 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  34 }
mc2200-GEmux8LocalPort4MDIX    OBJECT-TYPE
						SYNTAX			INTEGER {auto(1),
						                         mdi(2),
						                         mdi-x(3)}
						MAX-ACCESS		read-write
						STATUS			current
						DESCRIPTION
                        "GEmux8 Local card's port4 Mode configuration,
                    	set INTEGER(1) to auto,
                    	set INTEGER(2) to MDI,
                    	set INTEGER(3) to MDI-X,
                    	Ohter value is invalid"
						::= { mc2200-GEmux8Entry 35 }

mc2200-GEmux8LocalPort5Link	OBJECT-TYPE
						SYNTAX			INTEGER  {up(1),down(2)}
						MAX-ACCESS		read-only
						STATUS			current
						DESCRIPTION
                            "GEmux8 Local card's port5 work link status."
						::= { mc2200-GEmux8Entry 36 }
mc2200-GEmux8LocalPort5Speed	OBJECT-TYPE
						SYNTAX			INTEGER  {speed100M(1),speed10M(2),auto(3)}
						MAX-ACCESS		read-only
						STATUS			current
						DESCRIPTION
                            "GEmux8 Local card's port5 work speed status. "
						::= { mc2200-GEmux8Entry 37 }

mc2200-GEmux8LocalPort5Duplex	OBJECT-TYPE
						SYNTAX			INTEGER {full-duplex(1),half-duplex(2), auto(3)}
						MAX-ACCESS		read-only
						STATUS			current
						DESCRIPTION
                            "GEmux8 Local card's port5 work duplex status."
						::= { mc2200-GEmux8Entry 38}

mc2200-GEmux8LocalPort5TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port5 Tx Rate. "
						::= { mc2200-GEmux8Entry 39}
mc2200-GEmux8LocalPort5RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)						                          }
						MAX-ACCESS		read-write
						STATUS			current
						DESCRIPTION
                        " GEmux8 Local card's port5 Rx Rate."
						::= { mc2200-GEmux8Entry 40}
mc2200-GEmux8LocalPort5Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port5 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  41 }

mc2200-GEmux8LocalPort5MDIX    OBJECT-TYPE
						SYNTAX			INTEGER {auto(1),
						                         mdi(2),
						                         mdi-x(3)}
						MAX-ACCESS		read-write
						STATUS			current
						DESCRIPTION
                        "GEmux8 Local card's port5 Mode configuration,
                    	set INTEGER(1) to auto,
                    	set INTEGER(2) to MDI,
                    	set INTEGER(3) to MDI-X,
                    	Ohter value is invalid"
						::= { mc2200-GEmux8Entry 42 }
mc2200-GEmux8LocalPort6Link	OBJECT-TYPE
						SYNTAX			INTEGER  {up(1),down(2)}
						MAX-ACCESS		read-only
						STATUS			current
						DESCRIPTION
                            "GEmux8 Local card's port6 work link status."
						::= { mc2200-GEmux8Entry 43 }

mc2200-GEmux8LocalPort6Speed	OBJECT-TYPE
						SYNTAX			INTEGER  {speed100M(1),speed10M(2),auto(3)}
						MAX-ACCESS		read-only
						STATUS			current
						DESCRIPTION
                            "GEmux8 Local card's port6 work speed status. "
						::= { mc2200-GEmux8Entry 44 }

mc2200-GEmux8LocalPort6Duplex	OBJECT-TYPE
						SYNTAX			INTEGER {full-duplex(1),half-duplex(2), auto(3)}
						MAX-ACCESS		read-only
						STATUS			current
						DESCRIPTION
                            "GEmux8 Local card's port6 work duplex status."
						::= { mc2200-GEmux8Entry 45 }

mc2200-GEmux8LocalPort6TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port6 Tx Rate. "
						::= { mc2200-GEmux8Entry 46 }
mc2200-GEmux8LocalPort6RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port6 Rx Rate."
						::= { mc2200-GEmux8Entry 47 }
mc2200-GEmux8LocalPort6Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port6 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  48 }

mc2200-GEmux8LocalPort6MDIX    OBJECT-TYPE
						SYNTAX			INTEGER {auto(1),
						                         mdi(2),
						                         mdi-x(3)}
						MAX-ACCESS		read-write
						STATUS			current
						DESCRIPTION
                        "GEmux8 Local card's port6 Mode configuration,
                    	set INTEGER(1) to auto,
                    	set INTEGER(2) to MDI,
                    	set INTEGER(3) to MDI-X,
                    	Ohter value is invalid"
						::= { mc2200-GEmux8Entry 49 }
mc2200-GEmux8LocalPort7Link	OBJECT-TYPE
						SYNTAX			INTEGER  {up(1),down(2)}
						MAX-ACCESS		read-only
						STATUS			current
						DESCRIPTION
                            "GEmux8 Local card's port7 work link status."
						::= { mc2200-GEmux8Entry 50 }

mc2200-GEmux8LocalPort7Speed	OBJECT-TYPE
						SYNTAX			INTEGER  {speed100M(1),speed10M(2),auto(3)}
						MAX-ACCESS		read-only
						STATUS			current
						DESCRIPTION
                            "GEmux8 Local card's port7 work speed status. "
						::= { mc2200-GEmux8Entry 51 }

mc2200-GEmux8LocalPort7Duplex	OBJECT-TYPE
						SYNTAX			INTEGER {full-duplex(1),half-duplex(2), auto(3)}
						MAX-ACCESS		read-only
						STATUS			current
						DESCRIPTION
                            "GEmux8 Local card's port7 work duplex status."
						::= { mc2200-GEmux8Entry 52 }

mc2200-GEmux8LocalPort7TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port7 Tx Rate. "
						::= { mc2200-GEmux8Entry 53 }
mc2200-GEmux8LocalPort7RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port7 Rx Rate."
						::= { mc2200-GEmux8Entry 54 }
mc2200-GEmux8LocalPort7Mode   	OBJECT-TYPE
						SYNTAX		INTEGER {auto(1),
                          					speed10MHALFDUPLEX(2),
                          					speed10MFULLDUPLEX(3),
                          					speed100MHALFDUPLEX(4),
                          					speed100MFULLDUPLEX(5)}
						MAX-ACCESS		read-write
						STATUS			current
						DESCRIPTION
                        "GEmux8 Local card's port7 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  55 }

mc2200-GEmux8LocalPort7MDIX    OBJECT-TYPE
						SYNTAX			INTEGER {auto(1),
						                         mdi(2),
						                         mdi-x(3)}
						MAX-ACCESS		read-write
						STATUS			current
						DESCRIPTION
                        "GEmux8 Local card's port7 Mode configuration,
                    	set INTEGER(1) to auto,
                    	set INTEGER(2) to MDI,
                    	set INTEGER(3) to MDI-X,
                    	Ohter value is invalid"
						::= { mc2200-GEmux8Entry 56 }

mc2200-GEmux8LocalPort8Link	OBJECT-TYPE
						SYNTAX			INTEGER  {up(1),down(2)}
						MAX-ACCESS		read-only
						STATUS			current
						DESCRIPTION
                            "GEmux8 Local card's port8 work link status."
						::= { mc2200-GEmux8Entry 57 }

mc2200-GEmux8LocalPort8Speed	OBJECT-TYPE
						SYNTAX			INTEGER  {speed100M(1),speed10M(2),auto(3)}
						MAX-ACCESS		read-only
						STATUS			current
						DESCRIPTION
                            "GEmux8 Local card's port8 work speed status. "
						::= { mc2200-GEmux8Entry 58 }

mc2200-GEmux8LocalPort8Duplex	OBJECT-TYPE
						SYNTAX			INTEGER {full-duplex(1),half-duplex(2), auto(3)}
						MAX-ACCESS		read-only
						STATUS			current
						DESCRIPTION
                            "GEmux8 Local card's port8 work duplex status."
						::= { mc2200-GEmux8Entry 59 }

mc2200-GEmux8LocalPort8TxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GEmux8 Local card's port8 Tx Rate. "
						::= { mc2200-GEmux8Entry 60 }
mc2200-GEmux8LocalPort8RxRate	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GEmux8 Local card's port8 Rx Rate."
						::= { mc2200-GEmux8Entry 61 }
mc2200-GEmux8LocalPort8Mode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "GEmux8 Local card's port8 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  62 }
mc2200-GEmux8LocalPort8MDIX    OBJECT-TYPE
						SYNTAX			INTEGER {auto(1),
						                         mdi(2),
						                         mdi-x(3)}
						MAX-ACCESS		read-write
						STATUS			current
						DESCRIPTION
                        "GEmux8 Local card's port8 Mode configuration,
                    	set INTEGER(1) to auto,
                    	set INTEGER(2) to MDI,
                    	set INTEGER(3) to MDI-X,
                    	Ohter value is invalid"
						::= { mc2200-GEmux8Entry 63 }

mc2200-GEmux8MibPort1RxGoodOctets OBJECT-TYPE
						SYNTAX			Counter64
						MAX-ACCESS		read-only
						STATUS			current
						DESCRIPTION
                        "GEmux8 Local card's port1 MIB RxGoodOctetsLo counter."
						::= { mc2200-GEmux8Entry 64 }

mc2200-GEmux8MibPort1RxFCSErr OBJECT-TYPE
						SYNTAX			Counter64
						MAX-ACCESS		read-only
						STATUS			current
						DESCRIPTION
                        "GEmux8 Local card's port1 MIB RxFCSErr counter."
						::= { mc2200-GEmux8Entry 66 }
mc2200-GEmux8MibPort1TxFCSErr OBJECT-TYPE
						SYNTAX			Counter64
						MAX-ACCESS		read-only
						STATUS			current
						DESCRIPTION
                        "GEmux8 Local card's port1 MIB RxGoodOctetsLo counter."
						::= { mc2200-GEmux8Entry 67 }

mc2200-GEmux8MibPort2RxGoodOctets OBJECT-TYPE
						SYNTAX			Counter64
						MAX-ACCESS		read-only
						STATUS			current
						DESCRIPTION
                        "GEmux8 Local card's port2 MIB RxGoodOctetsLo counter."
						::= { mc2200-GEmux8Entry 68 }

mc2200-GEmux8MibPort2RxFCSErr OBJECT-TYPE
						SYNTAX			Counter64
						MAX-ACCESS		read-only
						STATUS			current
						DESCRIPTION
                        "GEmux8 Local card's port2 MIB RxFCSErr counter."
						::= { mc2200-GEmux8Entry 70 }
mc2200-GEmux8MibPort2TxFCSErr OBJECT-TYPE
						SYNTAX			Counter64
						MAX-ACCESS		read-only
						STATUS			current
						DESCRIPTION
                        "GEmux8 Local card's port2 MIB RxGoodOctetsLo counter."
						::= { mc2200-GEmux8Entry 71 }
mc2200-GEmux8MibPort3RxGoodOctets OBJECT-TYPE
						SYNTAX			Counter64
						MAX-ACCESS		read-only
						STATUS			current
						DESCRIPTION
                        "GEmux8 Local card's port3 MIB RxGoodOctetsLo counter."
						::= { mc2200-GEmux8Entry 72 }

mc2200-GEmux8MibPort3RxFCSErr OBJECT-TYPE
						SYNTAX			Counter64
						MAX-ACCESS		read-only
						STATUS			current
						DESCRIPTION
                        "GEmux8 Local card's port3 MIB RxFCSErr counter."
						::= { mc2200-GEmux8Entry 74 }
mc2200-GEmux8MibPort3TxFCSErr OBJECT-TYPE
						SYNTAX			Counter64
						MAX-ACCESS		read-only
						STATUS			current
						DESCRIPTION
                        "GEmux8 Local card's port3 MIB RxGoodOctetsLo counter."
						::= { mc2200-GEmux8Entry 75 }
mc2200-GEmux8MibPort4RxGoodOctets OBJECT-TYPE
						SYNTAX			Counter64
						MAX-ACCESS		read-only
						STATUS			current
						DESCRIPTION
                        "GEmux8 Local card's port4 MIB RxGoodOctetsLo counter."
						::= { mc2200-GEmux8Entry 76 }

mc2200-GEmux8MibPort4RxFCSErr OBJECT-TYPE
						SYNTAX			Counter64
						MAX-ACCESS		read-only
						STATUS			current
						DESCRIPTION
                        "GEmux8 Local card's port4 MIB RxFCSErr counter."
						::= { mc2200-GEmux8Entry 78 }
mc2200-GEmux8MibPort4TxFCSErr OBJECT-TYPE
						SYNTAX			Counter64
						MAX-ACCESS		read-only
						STATUS			current
						DESCRIPTION
                        "GEmux8 Local card's port4 MIB RxGoodOctetsLo counter."
						::= { mc2200-GEmux8Entry 79 }
mc2200-GEmux8MibPort5RxGoodOctets OBJECT-TYPE
						SYNTAX			Counter64
						MAX-ACCESS		read-only
						STATUS			current
						DESCRIPTION
                        "GEmux8 Local card's port5 MIB RxGoodOctetsLo counter."
						::= { mc2200-GEmux8Entry 80 }

mc2200-GEmux8MibPort5RxFCSErr OBJECT-TYPE
						SYNTAX			Counter64
						MAX-ACCESS		read-only
						STATUS			current
						DESCRIPTION
                        "GEmux8 Local card's port5 MIB RxFCSErr counter."
						::= { mc2200-GEmux8Entry 82 }
mc2200-GEmux8MibPort5TxFCSErr OBJECT-TYPE
						SYNTAX			Counter64
						MAX-ACCESS		read-only
						STATUS			current
						DESCRIPTION
                        "GEmux8 Local card's port5 MIB RxGoodOctetsLo counter."
						::= { mc2200-GEmux8Entry 83 }
mc2200-GEmux8MibPort6RxGoodOctets OBJECT-TYPE
						SYNTAX			Counter64
						MAX-ACCESS		read-only
						STATUS			current
						DESCRIPTION
                        "GEmux8 Local card's port6 MIB RxGoodOctetsLo counter."
						::= { mc2200-GEmux8Entry 84 }

mc2200-GEmux8MibPort6RxFCSErr OBJECT-TYPE
						SYNTAX			Counter64
						MAX-ACCESS		read-only
						STATUS			current
						DESCRIPTION
                        "GEmux8 Local card's port6 MIB RxFCSErr counter."
						::= { mc2200-GEmux8Entry 86 }
mc2200-GEmux8MibPort6TxFCSErr OBJECT-TYPE
						SYNTAX			Counter64
						MAX-ACCESS		read-only
						STATUS			current
						DESCRIPTION
                        "GEmux8 Local card's port6 MIB RxGoodOctetsLo counter."
						::= { mc2200-GEmux8Entry 87 }
mc2200-GEmux8MibPort7RxGoodOctets OBJECT-TYPE
						SYNTAX			Counter64
						MAX-ACCESS		read-only
						STATUS			current
						DESCRIPTION
                        "GEmux8 Local card's port7 MIB RxGoodOctetsLo counter."
						::= { mc2200-GEmux8Entry 88 }

mc2200-GEmux8MibPort7RxFCSErr OBJECT-TYPE
						SYNTAX			Counter64
						MAX-ACCESS		read-only
						STATUS			current
						DESCRIPTION
                        "GEmux8 Local card's port7 MIB RxFCSErr counter."
						::= { mc2200-GEmux8Entry 90 }
mc2200-GEmux8MibPort7TxFCSErr OBJECT-TYPE
						SYNTAX			Counter64
						MAX-ACCESS		read-only
						STATUS			current
						DESCRIPTION
                        "GEmux8 Local card's port7 MIB RxGoodOctetsLo counter."
						::= { mc2200-GEmux8Entry 91 }
mc2200-GEmux8MibPort8RxGoodOctets OBJECT-TYPE
						SYNTAX			Counter64
						MAX-ACCESS		read-only
						STATUS			current
						DESCRIPTION
                        "GEmux8 Local card's port8 MIB RxGoodOctetsLo counter."
						::= { mc2200-GEmux8Entry 92 }

mc2200-GEmux8MibPort8RxFCSErr OBJECT-TYPE
						SYNTAX			Counter64
						MAX-ACCESS		read-only
						STATUS			current
						DESCRIPTION
                        "GEmux8 Local card's port8 MIB RxFCSErr counter."
						::= { mc2200-GEmux8Entry 94 }
mc2200-GEmux8MibPort8TxFCSErr OBJECT-TYPE
						SYNTAX			Counter64
						MAX-ACCESS		read-only
						STATUS			current
						DESCRIPTION
                        "GEmux8 Local card's port8 MIB RxGoodOctetsLo counter."
						::= { mc2200-GEmux8Entry 95 }
mc2200-GEmux8RemoteLANSFPInfo	OBJECT-TYPE
						SYNTAX		DisplayString
						MAX-ACCESS		read-only
						STATUS			current
						DESCRIPTION
                            "GEmux8 Remote card's LAN port SFP infomation."
						::= { mc2200-GEmux8Entry 96 }
mc2200-GEmux8RemoteLANLink      OBJECT-TYPE
						SYNTAX			INTEGER {up(1),down(2),active(3),
						                          standby(4),noremotecard(0)}
						MAX-ACCESS		read-only
						STATUS			mandatory
						DESCRIPTION
                            "GEmux8 Remote card's LAN port work link status."
						::= { mc2200-GEmux8Entry 97 }
mc2200-GEmux8RemoteWANSFPInfo	OBJECT-TYPE
						SYNTAX		DisplayString
						MAX-ACCESS		read-only
						STATUS			current
						DESCRIPTION
                            "GEmux8 Remote card's WAN port SFP infomation."
						::= { mc2200-GEmux8Entry 98 }
mc2200-GEmux8RemoteWANLink	        OBJECT-TYPE
						SYNTAX			INTEGER {up(1),down(2),active(3),
						                          standby(4),noremotecard(0)}
						MAX-ACCESS		read-only
						STATUS			current
						DESCRIPTION
                            "GEmux8 Remote card's WAN port work link status."
						::= { mc2200-GEmux8Entry 99 }

mc2200-GEmux8RemotePort1Link	OBJECT-TYPE
						SYNTAX			INTEGER  {up(1),down(2), noremotecard(0)}
						MAX-ACCESS		read-only
						STATUS			current
						DESCRIPTION
                            "GEmux8 Remote card's port1 work link status."
						::= { mc2200-GEmux8Entry 100 }

mc2200-GEmux8RemotePort1Speed	OBJECT-TYPE
						SYNTAX			INTEGER  {speed100M(1),speed10M(2),auto(3), noremotecard(0)}
						MAX-ACCESS		read-only
						STATUS			current
						DESCRIPTION
                            "GEmux8 Remote card's port1 work speed status. "
						::= { mc2200-GEmux8Entry 101 }

mc2200-GEmux8RemotePort1Duplex	OBJECT-TYPE
						SYNTAX			INTEGER {full-duplex(1),half-duplex(2), auto(3), noremotecard(0)}
						MAX-ACCESS		read-only
						STATUS			current
						DESCRIPTION
                            "GEmux8 Remote card's port1 work duplex status."
						::= { mc2200-GEmux8Entry 102 }
mc2200-GEmux8RemotePort1Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port1 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  103 }

mc2200-GEmux8RemotePort1MDIX    OBJECT-TYPE
						SYNTAX			INTEGER {auto(1),
						                         mdi(2),
						                         mdi-x(3), noremotecard(0)}
						MAX-ACCESS		read-write
						STATUS			current
						DESCRIPTION
                        "GEmux8 Remote card's port1 Mode configuration,
                    	set INTEGER(1) to auto,
                    	set INTEGER(2) to MDI,
                    	set INTEGER(3) to MDI-X,
                    	Ohter value is invalid"
						::= { mc2200-GEmux8Entry 104 }

mc2200-GEmux8RemotePort2Link	OBJECT-TYPE
						SYNTAX			INTEGER  {up(1),down(2), noremotecard(0)}
						MAX-ACCESS		read-only
						STATUS			current
						DESCRIPTION
                            "GEmux8 Remote card's port2 work link status."
						::= { mc2200-GEmux8Entry 105 }

mc2200-GEmux8RemotePort2Speed	OBJECT-TYPE
						SYNTAX			INTEGER  {speed100M(1),speed10M(2),auto(3), noremotecard(0)}
						MAX-ACCESS		read-only
						STATUS			current
						DESCRIPTION
                            "GEmux8 Remote card's port2 work speed status. "
						::= { mc2200-GEmux8Entry 106 }

mc2200-GEmux8RemotePort2Duplex	OBJECT-TYPE
						SYNTAX			INTEGER {full-duplex(1),half-duplex(2), auto(3), noremotecard(0)}
						MAX-ACCESS		read-only
						STATUS			current
						DESCRIPTION
                            "GEmux8 Remote card's port2 work duplex status."
						::= { mc2200-GEmux8Entry 107 }
mc2200-GEmux8RemotePort2Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port2 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  108 }

mc2200-GEmux8RemotePort2MDIX    OBJECT-TYPE
						SYNTAX			INTEGER {auto(1),
						                         mdi(2),
						                         mdi-x(3), noremotecard(0)}
						MAX-ACCESS		read-write
						STATUS			current
						DESCRIPTION
                        "GEmux8 Remote card's port2 Mode configuration,
                    	set INTEGER(1) to auto,
                    	set INTEGER(2) to MDI,
                    	set INTEGER(3) to MDI-X,
                    	Ohter value is invalid"
						::= { mc2200-GEmux8Entry 109 }


mc2200-GEmux8RemotePort3Link	OBJECT-TYPE
						SYNTAX			INTEGER  {up(1),down(2), noremotecard(0)}
						MAX-ACCESS		read-only
						STATUS			current
						DESCRIPTION
                            "GEmux8 Remote card's port3 work link status."
						::= { mc2200-GEmux8Entry 110 }

mc2200-GEmux8RemotePort3Speed	OBJECT-TYPE
						SYNTAX			INTEGER  {speed100M(1),speed10M(2),auto(3), noremotecard(0)}
						MAX-ACCESS		read-only
						STATUS			current
						DESCRIPTION
                            "GEmux8 Remote card's port3 work speed status. "
						::= { mc2200-GEmux8Entry 111 }

mc2200-GEmux8RemotePort3Duplex	OBJECT-TYPE
						SYNTAX			INTEGER {full-duplex(1),half-duplex(2), auto(3), noremotecard(0)}
						MAX-ACCESS		read-only
						STATUS			current
						DESCRIPTION
                            "GEmux8 Remote card's port3 work duplex status."
						::= { mc2200-GEmux8Entry 112 }

mc2200-GEmux8RemotePort3Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port3 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  113 }

mc2200-GEmux8RemotePort3MDIX    OBJECT-TYPE
						SYNTAX			INTEGER {auto(1),
						                         mdi(2),
						                         mdi-x(3), noremotecard(0)}
						MAX-ACCESS		read-write
						STATUS			current
						DESCRIPTION
                        "GEmux8 Remote card's port3 Mode configuration,
                    	set INTEGER(1) to auto,
                    	set INTEGER(2) to MDI,
                    	set INTEGER(3) to MDI-X,
                    	Ohter value is invalid"
						::= { mc2200-GEmux8Entry 114 }

mc2200-GEmux8RemotePort4Link	OBJECT-TYPE
						SYNTAX			INTEGER  {up(1),down(2), noremotecard(0)}
						MAX-ACCESS		read-only
						STATUS			current
						DESCRIPTION
                            "GEmux8 Remote card's port4 work link status."
						::= { mc2200-GEmux8Entry 115 }

mc2200-GEmux8RemotePort4Speed	OBJECT-TYPE
						SYNTAX			INTEGER  {speed100M(1),speed10M(2),auto(3), noremotecard(0)}
						MAX-ACCESS		read-only
						STATUS			current
						DESCRIPTION
                            "GEmux8 Remote card's port4 work speed status. "
						::= { mc2200-GEmux8Entry 116 }

mc2200-GEmux8RemotePort4Duplex	OBJECT-TYPE
						SYNTAX			INTEGER {full-duplex(1),half-duplex(2), auto(3), noremotecard(0)}
						MAX-ACCESS		read-only
						STATUS			current
						DESCRIPTION
                            "GEmux8 Remote card's port4 work duplex status."
						::= { mc2200-GEmux8Entry 117 }
mc2200-GEmux8RemotePort4Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port4 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  118 }

mc2200-GEmux8RemotePort4MDIX    OBJECT-TYPE
						SYNTAX			INTEGER {auto(1),
						                         mdi(2),
						                         mdi-x(3), noremotecard(0)}
						MAX-ACCESS		read-write
						STATUS			current
						DESCRIPTION
                        "GEmux8 Remote card's port4 Mode configuration,
                    	set INTEGER(1) to auto,
                    	set INTEGER(2) to MDI,
                    	set INTEGER(3) to MDI-X,
                    	Ohter value is invalid"
						::= { mc2200-GEmux8Entry 119 }

mc2200-GEmux8RemotePort5Link	OBJECT-TYPE
						SYNTAX			INTEGER  {up(1),down(2), noremotecard(0)}
						MAX-ACCESS		read-only
						STATUS			current
						DESCRIPTION
                            "GEmux8 Remote card's port5 work link status."
						::= { mc2200-GEmux8Entry 120 }

mc2200-GEmux8RemotePort5Speed	OBJECT-TYPE
						SYNTAX			INTEGER  {speed100M(1),speed10M(2),auto(3), noremotecard(0)}
						MAX-ACCESS		read-only
						STATUS			current
						DESCRIPTION
                            "GEmux8 Remote card's port5 work speed status. "
						::= { mc2200-GEmux8Entry 121 }

mc2200-GEmux8RemotePort5Duplex	OBJECT-TYPE
						SYNTAX			INTEGER {full-duplex(1),half-duplex(2), auto(3), noremotecard(0)}
						MAX-ACCESS		read-only
						STATUS			current
						DESCRIPTION
                            "GEmux8 Remote card's port5 work duplex status."
						::= { mc2200-GEmux8Entry 122 }

mc2200-GEmux8RemotePort5Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port5 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  123 }

mc2200-GEmux8RemotePort5MDIX    OBJECT-TYPE
						SYNTAX			INTEGER {auto(1),
						                         mdi(2),
						                         mdi-x(3), noremotecard(0)}
						MAX-ACCESS		read-write
						STATUS			current
						DESCRIPTION
                        "GEmux8 Remote card's port5 Mode configuration,
                    	set INTEGER(1) to auto,
                    	set INTEGER(2) to MDI,
                    	set INTEGER(3) to MDI-X,
                    	Ohter value is invalid"
						::= { mc2200-GEmux8Entry 124 }

mc2200-GEmux8RemotePort6Link	OBJECT-TYPE
						SYNTAX			INTEGER  {up(1),down(2), noremotecard(0)}
						MAX-ACCESS		read-only
						STATUS			current
						DESCRIPTION
                            "GEmux8 Remote card's port6 work link status."
						::= { mc2200-GEmux8Entry 125 }

mc2200-GEmux8RemotePort6Speed	OBJECT-TYPE
						SYNTAX			INTEGER  {speed100M(1),speed10M(2),auto(3), noremotecard(0)}
						MAX-ACCESS		read-only
						STATUS			current
						DESCRIPTION
                            "GEmux8 Remote card's port6 work speed status. "
						::= { mc2200-GEmux8Entry 126 }

mc2200-GEmux8RemotePort6Duplex	OBJECT-TYPE
						SYNTAX			INTEGER {full-duplex(1),half-duplex(2), auto(3), noremotecard(0)}
						MAX-ACCESS		read-only
						STATUS			current
						DESCRIPTION
                            "GEmux8 Remote card's port6 work duplex status."
						::= { mc2200-GEmux8Entry 127 }
mc2200-GEmux8RemotePort6Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port6 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  128 }

mc2200-GEmux8RemotePort6MDIX    OBJECT-TYPE
						SYNTAX			INTEGER {auto(1),
						                         mdi(2),
						                         mdi-x(3), noremotecard(0)}
						MAX-ACCESS		read-write
						STATUS			current
						DESCRIPTION
                        "GEmux8 Remote card's port6 Mode configuration,
                    	set INTEGER(1) to auto,
                    	set INTEGER(2) to MDI,
                    	set INTEGER(3) to MDI-X,
                    	Ohter value is invalid"
						::= { mc2200-GEmux8Entry 129 }
mc2200-GEmux8RemotePort7Link	OBJECT-TYPE
						SYNTAX			INTEGER  {up(1),down(2), noremotecard(0)}
						MAX-ACCESS		read-only
						STATUS			current
						DESCRIPTION
                            "GEmux8 Remote card's port7 work link status."
						::= { mc2200-GEmux8Entry 130 }

mc2200-GEmux8RemotePort7Speed	OBJECT-TYPE
						SYNTAX			INTEGER  {speed100M(1),speed10M(2),auto(3), noremotecard(0)}
						MAX-ACCESS		read-only
						STATUS			current
						DESCRIPTION
                            "GEmux8 Remote card's port7 work speed status. "
						::= { mc2200-GEmux8Entry 131 }

mc2200-GEmux8RemotePort7Duplex	OBJECT-TYPE
						SYNTAX			INTEGER {full-duplex(1),half-duplex(2), auto(3), noremotecard(0)}
						MAX-ACCESS		read-only
						STATUS			current
						DESCRIPTION
                            "GEmux8 Remote card's port7 work duplex status."
						::= { mc2200-GEmux8Entry 132 }
mc2200-GEmux8RemotePort7Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port7 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  133 }

mc2200-GEmux8RemotePort7MDIX    OBJECT-TYPE
						SYNTAX			INTEGER {auto(1),
						                         mdi(2),
						                         mdi-x(3), noremotecard(0)}
						MAX-ACCESS		read-write
						STATUS			current
						DESCRIPTION
                        "GEmux8 Remote card's port7 Mode configuration,
                    	set INTEGER(1) to auto,
                    	set INTEGER(2) to MDI,
                    	set INTEGER(3) to MDI-X,
                    	Ohter value is invalid"
						::= { mc2200-GEmux8Entry 134 }

mc2200-GEmux8RemotePort8Link	OBJECT-TYPE
						SYNTAX			INTEGER  {up(1),down(2), noremotecard(0)}
						MAX-ACCESS		read-only
						STATUS			current
						DESCRIPTION
                            "GEmux8 Remote card's port8 work link status."
						::= { mc2200-GEmux8Entry 135 }

mc2200-GEmux8RemotePort8Speed	OBJECT-TYPE
						SYNTAX			INTEGER  {speed100M(1),speed10M(2),auto(3), noremotecard(0)}
						MAX-ACCESS		read-only
						STATUS			current
						DESCRIPTION
                            "GEmux8 Remote card's port8 work speed status. "
						::= { mc2200-GEmux8Entry 136 }

mc2200-GEmux8RemotePort8Duplex	OBJECT-TYPE
						SYNTAX			INTEGER {full-duplex(1),half-duplex(2), auto(3), noremotecard(0)}
						MAX-ACCESS		read-only
						STATUS			current
						DESCRIPTION
                            "GEmux8 Remote card's port8 work duplex status."
						::= { mc2200-GEmux8Entry 137 }
mc2200-GEmux8RemotePort8Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GEmux8 Remote card's port8 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GEmux8Entry  138 }
mc2200-GEmux8RemotePort8MDIX    OBJECT-TYPE
						SYNTAX			INTEGER {auto(1),
						                         mdi(2),
						                         mdi-x(3), noremotecard(0)}
						MAX-ACCESS		read-write
						STATUS			current
						DESCRIPTION
                        "GEmux8 Remote card's port8 Mode configuration,
                    	set INTEGER(1) to auto,
                    	set INTEGER(2) to MDI,
                    	set INTEGER(3) to MDI-X,
                    	Ohter value is invalid"
						::= { mc2200-GEmux8Entry 139 }

mc2200-GEmux8RemoteIPAddress  OBJECT-TYPE
        			SYNTAX      IpAddress
        			ACCESS      read-write
        			STATUS      mandatory
	    			DESCRIPTION
            		"The IP address to GEmux8 Remote IP ping."
        			::= {mc2200-GEmux8Entry 140}

mc2200-GEmux8RemoteSubnetMask    OBJECT-TYPE
        			SYNTAX      IpAddress
        			ACCESS      read-write
        			STATUS      mandatory
	    			DESCRIPTION
                    "The Net mask to  GEmux8 Remote IP ping."
        			::= {mc2200-GEmux8Entry 141}

mc2200-GEmux8RemoteGateWay    OBJECT-TYPE
        			SYNTAX      IpAddress
        			ACCESS      read-write
        			STATUS      mandatory
	   				 DESCRIPTION
                    "The gateware to GEmux8 Remote IP ping."
        			::= {mc2200-GEmux8Entry 142}

mc2200-GEmux8RemoteVLANEnable  OBJECT-TYPE
        			SYNTAX      INTEGER {enable(1),disable(2), noremotecard(0)}
        			ACCESS      read-write
        			STATUS      mandatory
	    			DESCRIPTION
                    "Enable or disable Remote GEmux8 IP ping 802.1Q VLAN."
        			::= {mc2200-GEmux8Entry 143}

mc2200-GEmux8RemoteVID  OBJECT-TYPE
        			SYNTAX      INTEGER
        			ACCESS      read-write
        			STATUS      mandatory
	    			DESCRIPTION
                    "GEmux8 Remote IP ping  802.1Q VLAN ID."
        			::= {mc2200-GEmux8Entry 144}
mc2200-GEmux8RemoteAlarm      OBJECT-TYPE
						SYNTAX			INTEGER  {enabled(1),disabled(2)}
						MAX-ACCESS		read-write
						STATUS			current
						DESCRIPTION
                        "Enable or disable GEmux8 Media converter card remote alarm.
                         set INTEGER(1) to Enable remote alarm,
                         set INTEGER(2) to Disable remote alarm,
                         Other value is invalid."
						::= { mc2200-GEmux8Entry 145 }
mc2200-GEmux8RFD		      OBJECT-TYPE
						SYNTAX			INTEGER  {enabled(1),disabled(2)}
						MAX-ACCESS		read-write
						STATUS			current
						DESCRIPTION
                        "GEmux8 Media converter card remote fault detect operation.
                         set INTEGER(1) to Enable RFD,
                         set INTEGER(2) to Disable RFD,
                         Other value is invalid."
						::= { mc2200-GEmux8Entry 146 }

mc2200-GEmux8Default		OBJECT-TYPE
						SYNTAX			INTEGER
						MAX-ACCESS		write-only
						STATUS			current
						DESCRIPTION
                        "Write GEmux8 card default setting,
                        set INTEGER(1) to write default.
                        Other value is invalid."
						::= { mc2200-GEmux8Entry 147 }
mc2200-GEmux8Reboot		OBJECT-TYPE
						SYNTAX			INTEGER
						MAX-ACCESS		write-only
						STATUS			current
						DESCRIPTION
                        "Reboot GEmux8 local card,
                        set INTEGER(1) to reboot this card.
                        Other value is invalid. "
						::= { mc2200-GEmux8Entry 148 }
mc2200-GEmux8LocalCardREMOTEMODE    OBJECT-TYPE
						SYNTAX			INTEGER  {remoteModeEnabled(1),remoteModeDisabled(2),noSetting(3)}
						MAX-ACCESS		read-write
						STATUS			current
						DESCRIPTION
                        "GEmux8 local card Remote Mode,if Remote mode is enabled, the control of
                        this converter is assigned to another remote management platform."
						::= { mc2200-GEmux8Entry 149 }

mc2200-GEmux8Localportuser1      OBJECT-TYPE
						SYNTAX			DisplayString
						MAX-ACCESS		read-write
						STATUS			current
						DESCRIPTION
                        " User of GEmux8 Local Port1. "
						::= { mc2200-GEmux8Entry 150 }



mc2200-GEmux8Localportuser2      OBJECT-TYPE
						SYNTAX			DisplayString
						MAX-ACCESS		read-write
						STATUS			current
						DESCRIPTION
                        " User of GEmux8 Local Port2."
						::= { mc2200-GEmux8Entry 151 }

mc2200-GEmux8Localportuser3      OBJECT-TYPE
						SYNTAX			DisplayString
						MAX-ACCESS		read-write
						STATUS			current
						DESCRIPTION
                        " User of GEmux8 Local Port3. "
						::= { mc2200-GEmux8Entry 152 }

mc2200-GEmux8Localportuser4      OBJECT-TYPE
						SYNTAX			DisplayString
						MAX-ACCESS		read-write
						STATUS			current
						DESCRIPTION
                        " User of GEmux8 Local Port4."
						::= { mc2200-GEmux8Entry 153 }

mc2200-GEmux8Localportuser5      OBJECT-TYPE
						SYNTAX			DisplayString
						MAX-ACCESS		read-write
						STATUS			current
						DESCRIPTION
                        " User of GEmux8 Local Port5. "
						::= { mc2200-GEmux8Entry 154 }
mc2200-GEmux8Localportuser6      OBJECT-TYPE
						SYNTAX			DisplayString
						MAX-ACCESS		read-write
						STATUS			current
						DESCRIPTION
                        " User of GEmux8 Local Port6. "
						::= { mc2200-GEmux8Entry 155 }

mc2200-GEmux8Localportuser7      OBJECT-TYPE
						SYNTAX			DisplayString
						MAX-ACCESS		read-write
						STATUS			current
						DESCRIPTION
                        " User of GEmux8 Local Port7. "
						::= { mc2200-GEmux8Entry 156 }

mc2200-GEmux8Localportuser8      OBJECT-TYPE
						SYNTAX			DisplayString
						MAX-ACCESS		read-write
						STATUS			current
						DESCRIPTION
                        " User of GEmux8 Local Port8. "
						::= { mc2200-GEmux8Entry 157 }

mc2200-GEmux8Remoteportuser1      OBJECT-TYPE
						SYNTAX			DisplayString
						MAX-ACCESS		read-write
						STATUS			current
						DESCRIPTION
                        " User of GEmux8 Remote Port1. "
						::= { mc2200-GEmux8Entry 158 }


mc2200-GEmux8Remoteportuser2      OBJECT-TYPE
						SYNTAX			DisplayString
						MAX-ACCESS		read-write
						STATUS			current
						DESCRIPTION
                        " User of GEmux8 Remote Port2. "
						::= { mc2200-GEmux8Entry 159 }

mc2200-GEmux8Remoteportuser3      OBJECT-TYPE
						SYNTAX			DisplayString
						MAX-ACCESS		read-write
						STATUS			current
						DESCRIPTION
                        " User of GEmux8 Remote Port3. "
						::= { mc2200-GEmux8Entry 160 }

mc2200-GEmux8Remoteportuser4      OBJECT-TYPE
						SYNTAX			DisplayString
						MAX-ACCESS		read-write
						STATUS			current
						DESCRIPTION
                        " User of GEmux8 Remote Port4. "
						::= { mc2200-GEmux8Entry 161 }

mc2200-GEmux8Remoteportuser5      OBJECT-TYPE
						SYNTAX			DisplayString
						MAX-ACCESS		read-write
						STATUS			current
						DESCRIPTION
                        " User of GEmux8 Remote Port5. "
						::= { mc2200-GEmux8Entry 162 }

mc2200-GEmux8Remoteportuser6      OBJECT-TYPE
						SYNTAX			DisplayString
						MAX-ACCESS		read-write
						STATUS			current
						DESCRIPTION
                        " User of GEmux8 Remote Port6. "
						::= { mc2200-GEmux8Entry 163 }

mc2200-GEmux8Remoteportuser7      OBJECT-TYPE
						SYNTAX			DisplayString
						MAX-ACCESS		read-write
						STATUS			current
						DESCRIPTION
                        " User of GEmux8 Remote Port7. "
						::= { mc2200-GEmux8Entry 164 }

mc2200-GEmux8Remoteportuser8      OBJECT-TYPE
						SYNTAX			DisplayString
						MAX-ACCESS		read-write
						STATUS			current
						DESCRIPTION
                        " User of GEmux8 Remote Port8. "
						::= { mc2200-GEmux8Entry 165 }
mc2200-GEmux8TrapFilterLocalLAN	        OBJECT-TYPE
						SYNTAX			INTEGER {enabled(1),disabled(2)}
						MAX-ACCESS		read-write
						STATUS			current
						DESCRIPTION
                            "Local LAN of GEmux8 Trap Filter ."
						::= { mc2200-GEmux8Entry 166 }
mc2200-GEmux8TrapFilterLocalWAN	        OBJECT-TYPE
						SYNTAX			INTEGER {enabled(1),disabled(2)}
						MAX-ACCESS		read-write
						STATUS			current
						DESCRIPTION
                            "Local WAN of GEmux8 Trap Filter ."
						::= { mc2200-GEmux8Entry 167 }
mc2200-GEmux8TrapFilterRemotePower	        OBJECT-TYPE
						SYNTAX			INTEGER {enabled(1),disabled(2)}
						MAX-ACCESS		read-write
						STATUS			current
						DESCRIPTION
                            "Remote Power of GEmux8 Trap Filter ."
						::= { mc2200-GEmux8Entry 168 }
mc2200-GEmux8TrapFilterRemoteLAN	        OBJECT-TYPE
						SYNTAX			INTEGER {enabled(1),disabled(2)}
						MAX-ACCESS		read-write
						STATUS			current
						DESCRIPTION
                            "Remote LAN of GEmux8 Trap Filter ."
						::= { mc2200-GEmux8Entry 169 }
mc2200-GEmux8TrapFilterRemoteWAN	        OBJECT-TYPE
						SYNTAX			INTEGER {enabled(1),disabled(2)}
						MAX-ACCESS		read-write
						STATUS			current
						DESCRIPTION
                            "Remote WAN of GEmux8 Trap Filter ."
						::= { mc2200-GEmux8Entry 170 }
-- GEMC4 Table ================================================================================

mc2200-GEMC4Table	   OBJECT-TYPE
					SYNTAX			SEQUENCE OF MC2200-GEMC4Entry
					MAX-ACCESS		not-accessible
					STATUS			current
					DESCRIPTION
                   "Sparse table containing one entry for each GEMC4
                     10/100Mbps Twisted-Pair to Fiber Ethernet Media Converter
                     in the system, indexed by chassisIndex and slotIndex."

					::= { mc2200-GEmib 5 }

mc2200-GEMC4Entry			OBJECT-TYPE
						SYNTAX			MC2200-GEMC4Entry
						MAX-ACCESS		not-accessible
						STATUS			current
						DESCRIPTION
            "One table entry per slot in the media converter chassis.
             If physical slot 'n' contains a powered GEMC4 media
             converter, then entry 'n' in this table exists and describes
             the state of the converter's lamps  If slot 'n' is empty, does
             not exist, or contains a different type of device, then table
             entry 'n' does not exist."

						INDEX			{ mc2200-GEMC4CardIndex }
						::= { mc2200-GEMC4Table 1 }


-- ==========================
-- CH-unit config info table --
-- ==========================
MC2200-GEMC4Entry ::=
				SEQUENCE {
					mc2200-GEMC4CardIndex			   	INTEGER,	-- 1
					mc2200-GEMC4CardMode				INTEGER,
					mc2200-GEMC4LocalLAN1SFPInfo      	DisplayString,
					mc2200-GEMC4LocalLAN1Link         	INTEGER,
					mc2200-GEMC4LocalLAN2SFPInfo      	DisplayString,
					mc2200-GEMC4LocalLAN2Link         	INTEGER,
					mc2200-GEMC4LocalWAN1SFPInfo      	DisplayString,
					mc2200-GEMC4LocalWAN1Link         	INTEGER,
					mc2200-GEMC4LocalWAN2LAN3SFPInfo      	DisplayString,
					mc2200-GEMC4LocalWAN2LAN3Link         	INTEGER,  -- 10
					mc2200-GEMC4LocalLAN1DownStreamBW  INTEGER,
					mc2200-GEMC4LocalLAN1UpStreamBW    INTEGER,
					mc2200-GEMC4LocalLAN2DownStreamBW  INTEGER,
					mc2200-GEMC4LocalLAN2UpStreamBW    INTEGER,
					mc2200-GEMC4LocalLAN3DownStreamBW  INTEGER,
					mc2200-GEMC4LocalLAN3UpStreamBW    INTEGER,
					mc2200-GEMC4LocalLAN1Mode         	INTEGER,
					mc2200-GEMC4LocalLAN2Mode         	INTEGER,
					mc2200-GEMC4LocalLAN3Mode         	INTEGER,
                    mc2200-GEMC4MibCounter1      	Counter64,   -- 20
                    mc2200-GEMC4MibCounter2      	Counter64,
                    mc2200-GEMC4MibCounter3      	Counter64,
                    mc2200-GEMC4MibCounter4      	Counter64,
                    mc2200-GEMC4MibCounter5      	Counter64,
                    mc2200-GEMC4MibCounter6      	Counter64,
                    mc2200-GEMC4MibCounter7      	Counter64,
                    mc2200-GEMC4MibCounter8      	Counter64,
                    mc2200-GEMC4MibCounter9      	Counter64,
                    mc2200-GEMC4MibCounter10     	Counter64,
                    mc2200-GEMC4MibCounter11     	Counter64,  -- 30
                    mc2200-GEMC4MibCounter12     	Counter64,
                    mc2200-GEMC4MibCounter13    	Counter64,
                    mc2200-GEMC4MibCounter14    	Counter64,
                    mc2200-GEMC4MibCounter15    	Counter64,
                    mc2200-GEMC4MibCounter16    	Counter64,
                    mc2200-GEMC4MibCounter17    	Counter64,
                    mc2200-GEMC4MibCounter18    	Counter64,
                    mc2200-GEMC4MibCounter19     	Counter64,
                    mc2200-GEMC4MibCounter20     	Counter64,
                    mc2200-GEMC4MibCounter21     	Counter64,  -- 40
                    mc2200-GEMC4MibCounter22    	Counter64,
                    mc2200-GEMC4MibCounter23   	Counter64,
                    mc2200-GEMC4MibCounter24    	Counter64,
                    mc2200-GEMC4MibCounter25    	Counter64,
                    mc2200-GEMC4MibCounter26    	Counter64,
                    mc2200-GEMC4MibCounter27    	Counter64,
                    mc2200-GEMC4MibCounter28    	Counter64,
                    mc2200-GEMC4MibCounter29   	Counter64,
                    mc2200-GEMC4MibCounter30   	Counter64,
                    mc2200-GEMC4MibCounter31   	Counter64, -- 50
                    mc2200-GEMC4MibCounter32    	Counter64,
					mc2200-GEMC4RemoteLAN1SFPInfo      DisplayString,
					mc2200-GEMC4RemoteLAN1Link         INTEGER,
					mc2200-GEMC4RemoteLAN2SFPInfo      DisplayString,
					mc2200-GEMC4RemoteLAN2Link         INTEGER,
					mc2200-GEMC4RemoteWAN1SFPInfo      DisplayString,
					mc2200-GEMC4RemoteWAN1Link         INTEGER,
					mc2200-GEMC4RemoteWAN2LAN3SFPInfo      DisplayString,
					mc2200-GEMC4RemoteWAN2LAN3Link         INTEGER,
					mc2200-GEMC4RemoteLAN1Mode         INTEGER, -- 60
					mc2200-GEMC4RemoteLAN2Mode         INTEGER,
					mc2200-GEMC4RemoteLAN3Mode         INTEGER,
					mc2200-GEMC4RemoteIPAddress       	IpAddress,
		  	        mc2200-GEMC4RemoteSubnetMask      	IpAddress,
					mc2200-GEMC4RemoteGateWay         	IpAddress,
					mc2200-GEMC4RemoteVLANEnable	    INTEGER,
					mc2200-GEMC4RemoteVID         		INTEGER,
                    mc2200-GEMC4RemoteAlarm       		INTEGER,
                    mc2200-GEMC4RFD					INTEGER,
                    mc2200-GEMC4Default				INTEGER, -- 70
                    mc2200-GEMC4Reboot					INTEGER,
                    mc2200-GEMC4LocalCardREMOTEMODE    INTEGER,   -- 72
					mc2200-GEMC4LocalLAN1Speed         	INTEGER,
					mc2200-GEMC4LocalLAN2Speed         	INTEGER,
					mc2200-GEMC4LocalWAN2LAN3Speed         INTEGER,
					mc2200-GEMC4RemoteLAN1Speed         INTEGER,
					mc2200-GEMC4RemoteLAN2Speed         INTEGER,
					mc2200-GEMC4RemoteWAN2LAN3Speed         INTEGER,
					mc2200-GEMC4APSActivePort         INTEGER,
					mc2200-GEMC4Localportuser1     DisplayString,   -- 80
					mc2200-GEMC4Localportuser2     DisplayString,
					mc2200-GEMC4Localportuser3     DisplayString,

					mc2200-GEMC4Remoteportuser1     DisplayString,
					mc2200-GEMC4Remoteportuser2     DisplayString,
					mc2200-GEMC4Remoteportuser3     DisplayString,  -- 85
					mc2200-GEMC4TrapFilterLocalLAN			INTEGER,
					mc2200-GEMC4TrapFilterLocalWAN			INTEGER,
					mc2200-GEMC4TrapFilterRemotePower		INTEGER,
					mc2200-GEMC4TrapFilterRemoteLAN		INTEGER,
					mc2200-GEMC4TrapFilterRemoteWAN		INTEGER
				}


mc2200-GEMC4CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GEMC4Entry 1 }
mc2200-GEMC4CardMode      OBJECT-TYPE
						SYNTAX			INTEGER {ge-MC2-2-STD(1),
						                         ge-MC2-2-APS(2),
						                         ge-MC1-2-APS(3),
						                         ge-MC3-1-MUX(4)}
						MAX-ACCESS		read-write
						STATUS			mandatory
						DESCRIPTION
                            "GEMC4 Card Mode: (GE-MC2/2-STD,GE-MC2/2-APS,GE-MC1/2-APS,GE-MC3/1-MUX)"
						::= { mc2200-GEMC4Entry 2 }

mc2200-GEMC4LocalLAN1SFPInfo	OBJECT-TYPE
						SYNTAX		DisplayString
						MAX-ACCESS		read-only
						STATUS			current
						DESCRIPTION
                        "GE-MC2/2-STD Local card's LAN1 port SFP infomation.
                         GE-MC2/2-APS Local card's LAN1 port SFP infomation.
                         GE-MC1/2-APS Local card's LAN1 port SFP infomation.
						 GE-MC3/1-MUX Local card's LAN1 port SFP infomation."
                        ::= { mc2200-GEMC4Entry 3 }
mc2200-GEMC4LocalLAN1Link      OBJECT-TYPE
						SYNTAX			INTEGER {up(1),
						                         down(2),active(3),standby(4)}
						MAX-ACCESS		read-only
						STATUS			mandatory
						DESCRIPTION
                        "GE-MC2/2-STD Local card's LAN1 port work link status.
                         GE-MC2/2-APS Local card's LAN1 port work link status.
                         GE-MC1/2-APS Local card's LAN1 port work link status.
						 GE-MC3/1-MUX Local card's LAN1 port work link status."
						::= { mc2200-GEMC4Entry 4 }
mc2200-GEMC4LocalLAN2SFPInfo	OBJECT-TYPE
						SYNTAX		DisplayString
						MAX-ACCESS		read-only
						STATUS			current
						DESCRIPTION
                        "GE-MC2/2-STD Local card's LAN2 port SFP infomation.
                         GE-MC2/2-APS Local card's LAN2 port SFP infomation.
						 GE-MC3/1-MUX Local card's LAN2 port SFP infomation."
                        ::= { mc2200-GEMC4Entry 5 }
mc2200-GEMC4LocalLAN2Link      OBJECT-TYPE
						SYNTAX			INTEGER {up(1),
						                         down(2)}
						MAX-ACCESS		read-only
						STATUS			mandatory
						DESCRIPTION
                        "GE-MC2/2-STD Local card's LAN2 port work link status.
                         GE-MC2/2-APS Local card's LAN2 port work link status.
						 GE-MC3/1-MUX Local card's LAN2 port work link status."
						::= { mc2200-GEMC4Entry 6 }

mc2200-GEMC4LocalWAN1SFPInfo	OBJECT-TYPE
						SYNTAX		DisplayString
						MAX-ACCESS		read-only
						STATUS			current
						DESCRIPTION
                        "GE-MC2/2-STD Local card's WAN1 port SFP infomation.
                         GE-MC2/2-APS Local card's WAN1 port SFP infomation.
                         GE-MC1/2-APS Local card's WAN1 port SFP infomation.
						 GE-MC3/1-MUX Local card's WAN1 port SFP infomation."
                        ::= { mc2200-GEMC4Entry 7 }
mc2200-GEMC4LocalWAN1Link      OBJECT-TYPE
						SYNTAX			INTEGER {up(1),
						                         down(2),active(3),standby(4)}
						MAX-ACCESS		read-only
						STATUS			mandatory
						DESCRIPTION
                        "GE-MC2/2-STD Local card's WAN1 port work link status.
                         GE-MC2/2-APS Local card's WAN1 port work link status.
                         GE-MC1/2-APS Local card's WAN1 port work link status.
						 GE-MC3/1-MUX Local card's WAN1 port work link status."
						::= { mc2200-GEMC4Entry 8 }
mc2200-GEMC4LocalWAN2LAN3SFPInfo	OBJECT-TYPE
						SYNTAX		DisplayString
						MAX-ACCESS		read-only
						STATUS			current
						DESCRIPTION
                            "GE-MC2/2-STD Local card's WAN2 port SFP infomation.
                             GE-MC2/2-APS Local card's WAN2 port SFP infomation.
                             GE-MC1/2-APS Local card's WAN2 port SFP infomation.
						     GE-MC3/1-MUX Local card's LAN3 port SFP infomation."
                        ::= { mc2200-GEMC4Entry 9}
mc2200-GEMC4LocalWAN2LAN3Link      OBJECT-TYPE
						SYNTAX			INTEGER {up(1),
						                         down(2),active(3),standby(4)}
						MAX-ACCESS		read-only
						STATUS			mandatory
						DESCRIPTION
                            "GE-MC2/2-STD Local card's WAN2LAN3 port work link status.
                             GE-MC2/2-APS Local card's WAN2LAN3 port work link status.
                             GE-MC1/2-APS Local card's WAN2LAN3 port work link status.
			     GE-MC3/1-MUX Local card's WAN2LAN3 port work link status."
						::= { mc2200-GEMC4Entry 10 }
mc2200-GEMC4LocalLAN1DownStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                            "GE-MC2/2-STD Local card's LAN1 port DownStream BandWidth.
                             GE-MC2/2-APS Local card's LAN1 port DownStream BandWidth.
                             GE-MC1/2-APS Local card's LAN1 port DownStream BandWidth.
						     GE-MC3/1-MUX Local card's LAN1 port DownStream BandWidth."
						::= { mc2200-GEMC4Entry 11 }
mc2200-GEMC4LocalLAN1UpStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        "GE-MC2/2-STD Local card's LAN1 port UpStream BandWidth.
                         GE-MC2/2-APS Local card's LAN1 port UpStream BandWidth.
                         GE-MC1/2-APS Local card's LAN1 port UpStream BandWidth.
						 GE-MC3/1-MUX Local card's LAN1 port UpStream BandWidth."
						::= { mc2200-GEMC4Entry 12 }

mc2200-GEMC4LocalLAN2DownStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        "GE-MC2/2-STD Local card's LAN2 port DownStream BandWidth.
                         GE-MC2/2-APS Local card's LAN2 port DownStream BandWidth.
						 GE-MC3/1-MUX Local card's LAN2 port DownStream BandWidth."
						::= { mc2200-GEMC4Entry 13 }
mc2200-GEMC4LocalLAN2UpStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        "GE-MC2/2-STD Local card's LAN2 port UpStream BandWidth.
                         GE-MC2/2-APS Local card's LAN2 port UpStream BandWidth.
						 GE-MC3/1-MUX Local card's LAN2 port UpStream BandWidth."
						::= { mc2200-GEMC4Entry 14 }
mc2200-GEMC4LocalLAN3DownStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
						 "GE-MC3/1-MUX Local card's LAN3 port UpStream BandWidth,
						 Other GEMC4(GE-MC2/2-STD,GE-MC2/2-APS,GE-MC1/2-APS) no this item."
						::= { mc2200-GEMC4Entry 15 }
mc2200-GEMC4LocalLAN3UpStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
						 "GE-MC3/1-MUX Local card's LAN3 port UpStream BandWidth.
						 Other GEMC4(GE-MC2/2-STD,GE-MC2/2-APS,GE-MC1/2-APS) no this item."
						::= { mc2200-GEMC4Entry 16 }
mc2200-GEMC4LocalLAN1Mode   	OBJECT-TYPE
						SYNTAX		INTEGER {auto-10-100-1000T(1),
                          					mode1000Base-X-auto(2),
                          					mode1000Base-T(3),
                          					mode100Base-Tx(4),
                          					mode10Base-T(5),
                          					mode1000Base-X-1000F(6)}
						MAX-ACCESS		read-write
						STATUS			current
						DESCRIPTION
                        "GEMC4 GE-MC2/2-STD,GE-MC2/2-APS,GE-MC1/2-APS,GE-MC3/1-MUX
                        Local card's LAN1 port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC4Entry  17 }
mc2200-GEMC4LocalLAN2Mode   	OBJECT-TYPE
						SYNTAX		INTEGER {auto-10-100-1000T(1),
                          					mode1000Base-X-auto(2),
                          					mode1000Base-T(3),
                          					mode100Base-Tx(4),
                          					mode10Base-T(5),
                          					mode1000Base-X-1000F(6)}
						MAX-ACCESS		read-write
						STATUS			current
						DESCRIPTION
                        "GEMC4  GE-MC2/2-STD,GE-MC2/2-APS,GE-MC3/1-MUX
                        Local card's LAN2 port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC4Entry  18 }
mc2200-GEMC4LocalLAN3Mode   	OBJECT-TYPE
						SYNTAX		INTEGER {auto-10-100-1000T(1),
                          					mode1000Base-X-auto(2),
                          					mode1000Base-T(3),
                          					mode100Base-Tx(4),
                          					mode10Base-T(5),
                          					mode1000Base-X-1000F(6)}
						MAX-ACCESS		read-write
						STATUS			current
						DESCRIPTION
                        "GEMC4 GE-MC3/1-MUX Local card's LAN3 port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC4Entry  19 }
mc2200-GEMC4MibCounter1 OBJECT-TYPE
						SYNTAX			Counter64
						MAX-ACCESS		read-only
						STATUS			current
						DESCRIPTION
                        "GEMC4 MibCounter1: GE-MC2/2-STD local LAN1 port MIB RxLoGoodByte counter.
                                            GE-MC2/2-APS local LAN1 port MIB RxLoGoodByte counter.
                                            GE-MC1/2-APS local LAN1 port MIB RxGoodOctetsLow counter.
                                            GE-MC3/1-MUX local LAN1 port MIB RxLoGoodByte counter."
						::= { mc2200-GEMC4Entry 20 }
mc2200-GEMC4MibCounter2 OBJECT-TYPE
						SYNTAX			Counter64
						MAX-ACCESS		read-only
						STATUS			current
						DESCRIPTION
                        "GEMC4 MibCounter2: GE-MC2/2-STD local LAN1 port MIB RxHiGoodByte counter.
                                            GE-MC2/2-APS local LAN1 port MIB RxHiGoodByte counter.
                                            GE-MC1/2-APS local LAN1 port MIB RxGoodOctetsHigh counter.
                                            GE-MC3/1-MUX local LAN1 port MIB RxHiGoodByte counter."
						::= { mc2200-GEMC4Entry 21 }
mc2200-GEMC4MibCounter3 OBJECT-TYPE
						SYNTAX			Counter64
						MAX-ACCESS		read-only
						STATUS			current
						DESCRIPTION
                        "GEMC4 MibCounter3: GE-MC2/2-STD local LAN1 port MIB RxBadByte counter.
                                            GE-MC2/2-APS local LAN1 port MIB RxBadByte counter.
                                            GE-MC1/2-APS local LAN1 port MIB RxBadOctets counter.
                                            GE-MC3/1-MUX local LAN1 port MIB RxBadByte counter."
						::= { mc2200-GEMC4Entry 22 }
mc2200-GEMC4MibCounter4 OBJECT-TYPE
						SYNTAX			Counter64
						MAX-ACCESS		read-only
						STATUS			current
						DESCRIPTION
                        "GEMC4 MibCounter4: GE-MC2/2-STD local LAN1 port MIB RxUnicastPkts counter.
                                            GE-MC2/2-APS local LAN1 port MIB RxUnicastPkts counter.
                                            GE-MC1/2-APS local LAN1 port MIB TxFCSErr counter.
                                            GE-MC3/1-MUX local LAN1 port MIB RxUnicastPkts counter."
						::= { mc2200-GEMC4Entry 23 }
mc2200-GEMC4MibCounter5 OBJECT-TYPE
						SYNTAX			Counter64
						MAX-ACCESS		read-only
						STATUS			current
						DESCRIPTION
                        "GEMC4 MibCounter5: GE-MC2/2-STD local LAN1 port MIB RxBroadcastPkts counter.
                                            GE-MC2/2-APS local LAN1 port MIB RxBroadcastPkts counter.
                                            GE-MC1/2-APS local LAN1 port MIB RxUnicast counter.
                                            GE-MC3/1-MUX local LAN1 port MIB RxBroadcastPkts counter."
						::= { mc2200-GEMC4Entry 24 }
mc2200-GEMC4MibCounter6 OBJECT-TYPE
						SYNTAX			Counter64
						MAX-ACCESS		read-only
						STATUS			current
						DESCRIPTION
                        "GEMC4 MibCounter6: GE-MC2/2-STD local LAN1 port MIB RxMulticastPkts counter.
                                            GE-MC2/2-APS local LAN1 port MIB RxMulticastPkts counter.
                                            GE-MC1/2-APS local LAN1 port MIB TxDeferred counter.
                                            GE-MC3/1-MUX local LAN1 port MIB RxMulticastPkts counter."
						::= { mc2200-GEMC4Entry 25 }

mc2200-GEMC4MibCounter7 OBJECT-TYPE
						SYNTAX			Counter64
						MAX-ACCESS		read-only
						STATUS			current
						DESCRIPTION
                        "GEMC4 MibCounter7: GE-MC2/2-STD local LAN1 port MIB TxLoGoodByte counter.
                                            GE-MC2/2-APS local LAN1 port MIB TxLoGoodByte counter.
                                            GE-MC1/2-APS local LAN1 port MIB RxBroadcasts counter.
                                            GE-MC3/1-MUX local LAN1 port MIB TxLoGoodByte counter."
						::= { mc2200-GEMC4Entry 26 }
mc2200-GEMC4MibCounter8 OBJECT-TYPE
						SYNTAX			Counter64
						MAX-ACCESS		read-only
						STATUS			current
						DESCRIPTION
                        "GEMC4 MibCounter8: GE-MC2/2-STD local LAN1 port MIB TxHiGoodByte counter.
                                            GE-MC2/2-APS local LAN1 port MIB TxHiGoodByte counter.
                                            GE-MC1/2-APS local LAN1 port MIB RxBroadcasts counter.
                                            GE-MC3/1-MUX local LAN1 port MIB TxHiGoodByte counter."
						::= { mc2200-GEMC4Entry 27 }
mc2200-GEMC4MibCounter9 OBJECT-TYPE
						SYNTAX			Counter64
						MAX-ACCESS		read-only
						STATUS			current
						DESCRIPTION
                        "GEMC4 MibCounter9: GE-MC2/2-STD local LAN1 port MIB TxUnicastPkts counter.
                                            GE-MC2/2-APS local LAN1 port MIB TxUnicastPkts counter.
                                            GE-MC1/2-APS local LAN1 port MIB Rx64Octets counter.
                                            GE-MC3/1-MUX local LAN1 port MIB TxUnicastPkts counter."
						::= { mc2200-GEMC4Entry 28 }
mc2200-GEMC4MibCounter10 OBJECT-TYPE
						SYNTAX			Counter64
						MAX-ACCESS		read-only
						STATUS			current
						DESCRIPTION
                        "GEMC4 MibCounter10: GE-MC2/2-STD local LAN1 port MIB TxMulticastPkts counter.
                                             GE-MC2/2-APS local LAN1 port MIB TxMulticastPkts counter.
                                             GE-MC1/2-APS local LAN1 port MIB Rx65to127Octets counter.
                                             GE-MC3/1-MUX local LAN1 port MIB TxMulticastPkts counter."
						::= { mc2200-GEMC4Entry 29 }
mc2200-GEMC4MibCounter11 OBJECT-TYPE
						SYNTAX			Counter64
						MAX-ACCESS		read-only
						STATUS			current
						DESCRIPTION
                        "GEMC4 MibCounter11: GE-MC2/2-STD local LAN1 port MIB TxBroadcastPkts counter.
                                             GE-MC2/2-APS local LAN1 port MIB TxBroadcastPkts counter.
                                             GE-MC1/2-APS local LAN1 port MIB Rx128to255Octets counter.
                                             GE-MC3/1-MUX local LAN1 port MIB TxBroadcastPkts counter."
						::= { mc2200-GEMC4Entry 30 }
mc2200-GEMC4MibCounter12 OBJECT-TYPE
						SYNTAX			Counter64
						MAX-ACCESS		read-only
						STATUS			current
						DESCRIPTION
                        "GEMC4 MibCounter12: GE-MC2/2-STD local LAN1 port MIB TxFC counter.
                                             GE-MC2/2-APS local LAN1 port MIB TxFC counter.
                                             GE-MC1/2-APS local LAN1 port MIB Rx256to511Octets counter.
                                             GE-MC3/1-MUX local LAN1 port MIB TxFC counter."
						::= { mc2200-GEMC4Entry 31 }
mc2200-GEMC4MibCounter13 OBJECT-TYPE
						SYNTAX			Counter64
						MAX-ACCESS		read-only
						STATUS			current
						DESCRIPTION
                        "GEMC4 MibCounter13: GE-MC2/2-STD local LAN1 port MIB RxFC counter.
                                             GE-MC2/2-APS local LAN1 port MIB RxFC counter.
                                             GE-MC1/2-APS local LAN1 port MIB Rx512to1023Octets counter.
                                             GE-MC3/1-MUX local LAN1 port MIB RxFC counter."
						::= { mc2200-GEMC4Entry 32 }
mc2200-GEMC4MibCounter14 OBJECT-TYPE
						SYNTAX			Counter64
						MAX-ACCESS		read-only
						STATUS			current
						DESCRIPTION
                        "GEMC4 MibCounter14: GE-MC2/2-STD local LAN1 port MIB RxUndersize counter.
                                             GE-MC2/2-APS local LAN1 port MIB RxUndersize counter.
                                             GE-MC1/2-APS local LAN1 port MIB Rx1024toMaxOctets counter.
                                             GE-MC3/1-MUX local LAN1 port MIB RxUndersize counter."
						::= { mc2200-GEMC4Entry 33 }
mc2200-GEMC4MibCounter15 OBJECT-TYPE
						SYNTAX			Counter64
						MAX-ACCESS		read-only
						STATUS			current
						DESCRIPTION
                        "GEMC4 MibCounter15: GE-MC2/2-STD local LAN1 port MIB RxOversize counter.
                                             GE-MC2/2-APS local LAN1 port MIB RxOversize counter.
                                             GE-MC1/2-APS local LAN1 port MIB TxOctetsLow counter.
                                             GE-MC3/1-MUX local LAN1 port MIB RxOversize counter."
						::= { mc2200-GEMC4Entry 34 }
mc2200-GEMC4MibCounter16 OBJECT-TYPE
						SYNTAX			Counter64
						MAX-ACCESS		read-only
						STATUS			current
						DESCRIPTION
                        "GEMC4 MibCounter16: GE-MC2/2-STD local LAN1 port MIB RxBadCRC counter.
                                             GE-MC2/2-APS local LAN1 port MIB RxBadCRC counter.
                                             GE-MC1/2-APS local LAN1 port MIB TxOctetsHigh counter."
						::= { mc2200-GEMC4Entry 35 }
mc2200-GEMC4MibCounter17 OBJECT-TYPE
						SYNTAX			Counter64
						MAX-ACCESS		read-only
						STATUS			current
						DESCRIPTION
                        "GEMC4 MibCounter17: GE-MC2/2-STD local LAN2 port MIB RxLoGoodByte counter.
                                             GE-MC2/2-APS local LAN2 port MIB RxLoGoodByte counter.
                                             GE-MC1/2-APS local LAN1 port MIB TxUnicast counter.
                                             GE-MC3/1-MUX local LAN2 port MIB RxLoGoodByte counter."
						::= { mc2200-GEMC4Entry 36 }
mc2200-GEMC4MibCounter18 OBJECT-TYPE
						SYNTAX			Counter64
						MAX-ACCESS		read-only
						STATUS			current
						DESCRIPTION
                        "GEMC4 MibCounter18: GE-MC2/2-STD local LAN2 port MIB RxHiGoodByte counter.
                                             GE-MC2/2-APS local LAN2 port MIB RxHiGoodByte counter.
                                             GE-MC1/2-APS local LAN1 port MIB TxExcessive counter.
                                             GE-MC3/1-MUX local LAN2 port MIB RxHiGoodByte counter."
						::= { mc2200-GEMC4Entry 37 }
mc2200-GEMC4MibCounter19 OBJECT-TYPE
						SYNTAX			Counter64
						MAX-ACCESS		read-only
						STATUS			current
						DESCRIPTION
                        "GEMC4 MibCounter19: GE-MC2/2-STD local LAN2 port MIB RxBadByte counter.
                                             GE-MC2/2-APS local LAN2 port MIB RxBadByte counter.
                                             GE-MC1/2-APS local LAN1 port MIB TxMulticasts counter.
                                             GE-MC3/1-MUX local LAN2 port MIB RxBadByte counter."
						::= { mc2200-GEMC4Entry 38 }
mc2200-GEMC4MibCounter20 OBJECT-TYPE
						SYNTAX			Counter64
						MAX-ACCESS		read-only
						STATUS			current
						DESCRIPTION
                        "GEMC4 MibCounter20: GE-MC2/2-STD local LAN2 port MIB RxUnicastPkts counter.
                                             GE-MC2/2-APS local LAN2 port MIB RxUnicastPkts counter.
                                             GE-MC1/2-APS local LAN1 port MIB TxBroadcasts counter.
                                             GE-MC3/1-MUX local LAN2 port MIB RxUnicastPkts counter."
						::= { mc2200-GEMC4Entry 39 }
mc2200-GEMC4MibCounter21 OBJECT-TYPE
						SYNTAX			Counter64
						MAX-ACCESS		read-only
						STATUS			current
						DESCRIPTION
                        "GEMC4 MibCounter21: GE-MC2/2-STD local LAN2 port MIB RxBroadcastPkts counter.
                                             GE-MC2/2-APS local LAN2 port MIB RxBroadcastPkts counter.
                                             GE-MC1/2-APS local LAN1 port MIB TxSingle counter.
                                             GE-MC3/1-MUX local LAN2 port MIB RxBroadcastPkts counter."
						::= { mc2200-GEMC4Entry 40 }
mc2200-GEMC4MibCounter22 OBJECT-TYPE
						SYNTAX			Counter64
						MAX-ACCESS		read-only
						STATUS			current
						DESCRIPTION
                        "GEMC4 MibCounter22: GE-MC2/2-STD local LAN2 port MIB RxMulticastPkts counter.
                                             GE-MC2/2-APS local LAN2 port MIB RxMulticastPkts counter.
                                             GE-MC1/2-APS local LAN1 port MIB TxPause counter.
                                             GE-MC3/1-MUX local LAN2 port MIB RxMulticastPkts counter."
						::= { mc2200-GEMC4Entry 41 }
mc2200-GEMC4MibCounter23 OBJECT-TYPE
						SYNTAX			Counter64
						MAX-ACCESS		read-only
						STATUS			current
						DESCRIPTION
                        "GEMC4 MibCounter23: GE-MC2/2-STD local LAN2 port MIB RxFCSErr counter.
                                             GE-MC2/2-APS local LAN2 port MIB RxFCSErr counter.
                                             GE-MC1/2-APS local LAN1 port MIB RxPause counter.
                                             GE-MC3/1-MUX local LAN2 port MIB RxFCSErr counter."
						::= { mc2200-GEMC4Entry 42 }
mc2200-GEMC4MibCounter24 OBJECT-TYPE
						SYNTAX			Counter64
						MAX-ACCESS		read-only
						STATUS			current
						DESCRIPTION
                        "GEMC4 MibCounter24: GE-MC2/2-STD local LAN2 port MIB TxLoGoodByte counter.
                                             GE-MC2/2-APS local LAN2 port MIB TxLoGoodByte counter.
                                             GE-MC1/2-APS local LAN1 port MIB TxMultiple counter.
                                             GE-MC3/1-MUX local LAN2 port MIB TxLoGoodByte counter."
						::= { mc2200-GEMC4Entry 43 }
mc2200-GEMC4MibCounter25 OBJECT-TYPE
						SYNTAX			Counter64
						MAX-ACCESS		read-only
						STATUS			current
						DESCRIPTION
                        "GEMC4 MibCounter25: GE-MC2/2-STD local LAN2 port MIB TxUnicastPkts counter.
                                             GE-MC2/2-APS local LAN2 port MIB TxUnicastPkts counter.
                                             GE-MC1/2-APS local LAN1 port MIB RxUndersize counter.
                                             GE-MC3/1-MUX local LAN2 port MIB TxUnicastPkts counter."
						::= { mc2200-GEMC4Entry 44 }
mc2200-GEMC4MibCounter26 OBJECT-TYPE
						SYNTAX			Counter64
						MAX-ACCESS		read-only
						STATUS			current
						DESCRIPTION
                        "GEMC4 MibCounter26: GE-MC2/2-STD local LAN2 port MIB TxMulticastPkts counter.
                                             GE-MC2/2-APS local LAN2 port MIB TxMulticastPkts counter.
                                             GE-MC1/2-APS local LAN1 port MIB RxFragments counter.
                                             GE-MC3/1-MUX local LAN2 port MIB TxMulticastPkts counter."
						::= { mc2200-GEMC4Entry 45 }
mc2200-GEMC4MibCounter27 OBJECT-TYPE
						SYNTAX			Counter64
						MAX-ACCESS		read-only
						STATUS			current
						DESCRIPTION
                        "GEMC4 MibCounter27: GE-MC2/2-STD local LAN2 port MIB TxBroadcastPkts counter.
                                             GE-MC2/2-APS local LAN2 port MIB TxBroadcastPkts counter.
                                             GE-MC1/2-APS local LAN1 port MIB RxOversize counter.
                                             GE-MC3/1-MUX local LAN2 port MIB TxBroadcastPkts counter."
						::= { mc2200-GEMC4Entry 46 }
mc2200-GEMC4MibCounter28 OBJECT-TYPE
						SYNTAX			Counter64
						MAX-ACCESS		read-only
						STATUS			current
						DESCRIPTION
                        "GEMC4 MibCounter28: GE-MC2/2-STD local LAN2 port MIB TxFC counter.
                                             GE-MC2/2-APS local LAN2 port MIB TxFC counter.
                                             GE-MC1/2-APS local LAN1 port MIB RxJabber counter.
                                             GE-MC3/1-MUX local LAN2 port MIB TxFC counter."
						::= { mc2200-GEMC4Entry 47 }
mc2200-GEMC4MibCounter29 OBJECT-TYPE
						SYNTAX			Counter64
						MAX-ACCESS		read-only
						STATUS			current
						DESCRIPTION
                        "GEMC4 MibCounter29: GE-MC2/2-STD local LAN2 port MIB RxFC counter.
                                             GE-MC2/2-APS local LAN2 port MIB RxFC counter.
                                             GE-MC1/2-APS local LAN1 port MIB RxErr counter.
                                             GE-MC3/1-MUX local LAN2 port MIB RxFC counter."
						::= { mc2200-GEMC4Entry 48 }
mc2200-GEMC4MibCounter30 OBJECT-TYPE
						SYNTAX			Counter64
						MAX-ACCESS		read-only
						STATUS			current
						DESCRIPTION
                        "GEMC4 MibCounter30: GE-MC2/2-STD local LAN2 port MIB RxUndersize counter.
                                             GE-MC2/2-APS local LAN2 port MIB RxUndersize counter.
                                             GE-MC1/2-APS local LAN1 port MIB RxFCSErr counter.
                                             GE-MC3/1-MUX local LAN2 port MIB RxUndersize counter."
						::= { mc2200-GEMC4Entry 49 }
mc2200-GEMC4MibCounter31 OBJECT-TYPE
						SYNTAX			Counter64
						MAX-ACCESS		read-only
						STATUS			current
						DESCRIPTION
                        "GEMC4 MibCounter31: GE-MC2/2-STD local LAN2 port MIB RxOversize counter.
                                             GE-MC2/2-APS local LAN2 port MIB RxOversize counter.
                                             GE-MC1/2-APS local LAN1 port MIB TxCollisions counter.
                                             GE-MC3/1-MUX local LAN2 port MIB RxOversize counter."
						::= { mc2200-GEMC4Entry 50 }
mc2200-GEMC4MibCounter32 OBJECT-TYPE
						SYNTAX			Counter64
						MAX-ACCESS		read-only
						STATUS			current
						DESCRIPTION
                        "GEMC4 MibCounter32: GE-MC2/2-STD local LAN2 port MIB RxBadCRC counter.
                                             GE-MC2/2-APS local LAN2 port MIB RxBadCRC counter.
                                             GE-MC1/2-APS local LAN1 port MIB TxLate counter."
						::= { mc2200-GEMC4Entry 51 }


mc2200-GEMC4RemoteLAN1SFPInfo	OBJECT-TYPE
						SYNTAX		DisplayString
						MAX-ACCESS		read-only
						STATUS			current
						DESCRIPTION
                            "GEMC4(GE-MC2/2-STD,GE-MC2/2-APS,GE-MC1/2-APS,GE-MC3/1-MUX)
                             Remote card's LAN1 port SFP infomation."
                        ::= { mc2200-GEMC4Entry 52 }
mc2200-GEMC4RemoteLAN1Link      OBJECT-TYPE
						SYNTAX			INTEGER {up(1),
						                         down(2), no-remotecard(0)}
						MAX-ACCESS		read-only
						STATUS			mandatory
						DESCRIPTION
                            "GEMC4(GE-MC2/2-STD,GE-MC2/2-APS,GE-MC1/2-APS,GE-MC3/1-MUX)
                             Remote card's LAN1 port work link status."
						::= { mc2200-GEMC4Entry 53 }
mc2200-GEMC4RemoteLAN2SFPInfo	OBJECT-TYPE
						SYNTAX		DisplayString
						MAX-ACCESS		read-only
						STATUS			current
						DESCRIPTION
                            "GEMC4(GE-MC2/2-STD,GE-MC2/2-APS,GE-MC3/1-MUX)
                             Remote card's LAN2 port SFP infomation."
                        ::= { mc2200-GEMC4Entry 54 }
mc2200-GEMC4RemoteLAN2Link      OBJECT-TYPE
						SYNTAX			INTEGER {up(1),
						                         down(2), no-remotecard(0)}
						MAX-ACCESS		read-only
						STATUS			mandatory
						DESCRIPTION
                            "GEMC4(GE-MC2/2-STD,GE-MC2/2-APS,GE-MC3/1-MUX)
                             Remote card's LAN2 port work link status."
						::= { mc2200-GEMC4Entry 55 }

mc2200-GEMC4RemoteWAN1SFPInfo	OBJECT-TYPE
						SYNTAX		DisplayString
						MAX-ACCESS		read-only
						STATUS			current
						DESCRIPTION
                            "GEMC4(GE-MC2/2-STD,GE-MC2/2-APS,GE-MC1/2-APS,GE-MC3/1-MUX)
                             Remote card's WAN port SFP infomation."
                        ::= { mc2200-GEMC4Entry 56 }
mc2200-GEMC4RemoteWAN1Link      OBJECT-TYPE
						SYNTAX			INTEGER {up(1),down(2),
						                         active(3),standby(4),no-remotecard(0)}
						MAX-ACCESS		read-only
						STATUS			mandatory
						DESCRIPTION
                            "GEMC4(GE-MC2/2-STD,GE-MC2/2-APS,GE-MC1/2-APS,GE-MC3/1-MUX)
                            Remote card's WAN port work link status."
						::= { mc2200-GEMC4Entry 57 }
mc2200-GEMC4RemoteWAN2LAN3SFPInfo	OBJECT-TYPE
						SYNTAX		DisplayString
						MAX-ACCESS		read-only
						STATUS			current
						DESCRIPTION
                            "GEMC4(GE-MC2/2-STD,GE-MC2/2-APS,GE-MC1/2-APS,GE-MC3/1-MUX)
                            Remote card's WAN2/LAN3 port SFP infomation."
                        ::= { mc2200-GEMC4Entry 58 }
mc2200-GEMC4RemoteWAN2LAN3Link      OBJECT-TYPE
						SYNTAX			INTEGER {up(1),down(2),
						                         active(3),standby(4),no-remotecard(0)}
						MAX-ACCESS		read-only
						STATUS			mandatory
						DESCRIPTION
                            "GEMC4(GE-MC2/2-STD,GE-MC2/2-APS,GE-MC1/2-APS,GE-MC3/1-MUX)
                             Remote card's LAN3 port work link status."
						::= { mc2200-GEMC4Entry 59 }
mc2200-GEMC4RemoteLAN1Mode   	OBJECT-TYPE
						SYNTAX		INTEGER {auto-10-100-1000T(1),
                          					mode1000Base-X-auto(2),
                          					mode1000Base-T(3),
                          					mode100Base-Tx(4),
                          					mode10Base-T(5),
                          					mode1000Base-X-1000F(6),no-remotecard(0)}

						MAX-ACCESS		read-write
						STATUS			current
						DESCRIPTION
                        "GEMC4(GE-MC2/2-STD,GE-MC2/2-APS,GE-MC1/2-APS,GE-MC3/1-MUX)
                        Remote card's LAN1 port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC4Entry  60 }
mc2200-GEMC4RemoteLAN2Mode   	OBJECT-TYPE
						SYNTAX		INTEGER {auto-10-100-1000T(1),
                          					mode1000Base-X-auto(2),
                          					mode1000Base-T(3),
                          					mode100Base-Tx(4),
                          					mode10Base-T(5),
                          					mode1000Base-X-1000F(6),no-remotecard(0)}
						MAX-ACCESS		read-write
						STATUS			current
						DESCRIPTION
                        "GEMC4(GE-MC2/2-STD,GE-MC2/2-APS,GE-MC3/1-MUX)
                        Remote card's LAN2 port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC4Entry  61 }
mc2200-GEMC4RemoteLAN3Mode   	OBJECT-TYPE
						SYNTAX		INTEGER {auto-10-100-1000T(1),
                          					mode1000Base-X-auto(2),
                          					mode1000Base-T(3),
                          					mode100Base-Tx(4),
                          					mode10Base-T(5),
                          					mode1000Base-X-1000F(6),no-remotecard(0)}
						MAX-ACCESS		read-write
						STATUS			current
						DESCRIPTION
                        "GEMC4(GE-MC3/1-MUX) Remote card's LAN3 port Mode configuration,
                        Other GEMC4(GE-MC2/2-STD,GE-MC2/2-APS,GE-MC1/2-APS) no this item.
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC4Entry  62 }
mc2200-GEMC4RemoteIPAddress  OBJECT-TYPE
        			SYNTAX      IpAddress
        			ACCESS      read-write
        			STATUS      mandatory
	    			DESCRIPTION
            		"The IP address to GEMC4(GE-MC2/2-STD,GE-MC2/2-APS,GE-MC1/2-APS,GE-MC3/1-MUX) Remote IP ping."
        			::= {mc2200-GEMC4Entry 63}

mc2200-GEMC4RemoteSubnetMask    OBJECT-TYPE
        			SYNTAX      IpAddress
        			ACCESS      read-write
        			STATUS      mandatory
	    			DESCRIPTION
                    "The Net mask to  GEMC4(GE-MC2/2-STD,GE-MC2/2-APS,GE-MC1/2-APS,GE-MC3/1-MUX) Remote IP ping."
        			::= {mc2200-GEMC4Entry 64}

mc2200-GEMC4RemoteGateWay    OBJECT-TYPE
        			SYNTAX      IpAddress
        			ACCESS      read-write
        			STATUS      mandatory
	   				 DESCRIPTION
                    "The gateware to GEMC4(GE-MC2/2-STD,GE-MC2/2-APS,GE-MC1/2-APS,GE-MC3/1-MUX) Remote IP ping."
        			::= {mc2200-GEMC4Entry 65}

mc2200-GEMC4RemoteVLANEnable  OBJECT-TYPE
        			SYNTAX      INTEGER {enable(1),disable(2), no-remotecard(0)}
        			ACCESS      read-write
        			STATUS      mandatory
	    			DESCRIPTION
                    "Enable or disable Remote GEMC4(GE-MC2/2-STD,GE-MC2/2-APS,GE-MC1/2-APS,GE-MC3/1-MUX) IP ping 802.1Q VLAN."
        			::= {mc2200-GEMC4Entry 66}

mc2200-GEMC4RemoteVID  OBJECT-TYPE
        			SYNTAX      INTEGER
        			ACCESS      read-write
        			STATUS      mandatory
	    			DESCRIPTION
                    "GEMC4 Remote IP ping  802.1Q VLAN ID."
        			::= {mc2200-GEMC4Entry 67}
mc2200-GEMC4RemoteAlarm      OBJECT-TYPE
						SYNTAX			INTEGER  {enabled(1),disabled(2)}
						MAX-ACCESS		read-write
						STATUS			current
						DESCRIPTION
                        "Enable or disable GEMC4(GE-MC2/2-STD,GE-MC2/2-APS,GE-MC1/2-APS,GE-MC3/1-MUX) Media converter card remote alarm.
                         set INTEGER(1) to Enable remote alarm,
                         set INTEGER(2) to Disable remote alarm,
                         Other value is invalid."
						::= { mc2200-GEMC4Entry 68 }
mc2200-GEMC4RFD		      OBJECT-TYPE
						SYNTAX			INTEGER  {enabled(1),disabled(2)}
						MAX-ACCESS		read-write
						STATUS			current
						DESCRIPTION
                        "GEMC4(GE-MC2/2-STD,GE-MC2/2-APS,GE-MC1/2-APS,GE-MC3/1-MUX) Media converter card remote fault detect operation.
                         set INTEGER(1) to Enable RFD,
                         set INTEGER(2) to Disable RFD,
                         Other value is invalid."
						::= { mc2200-GEMC4Entry 69 }

mc2200-GEMC4Default		OBJECT-TYPE
						SYNTAX			INTEGER
						MAX-ACCESS		write-only
						STATUS			current
						DESCRIPTION
                        "Write GEMC4(GE-MC2/2-STD,GE-MC2/2-APS,GE-MC1/2-APS,GE-MC3/1-MUX) card default setting,
                        set INTEGER(1) to write default.
                        Other value is invalid."
						::= { mc2200-GEMC4Entry 70 }
mc2200-GEMC4Reboot		OBJECT-TYPE
						SYNTAX			INTEGER
						MAX-ACCESS		write-only
						STATUS			current
						DESCRIPTION
                        "Reboot GEMC4 local card,
                        set INTEGER(1) to reboot this card.
                        Other value is invalid. "
						::= { mc2200-GEMC4Entry 71 }
mc2200-GEMC4LocalCardREMOTEMODE    OBJECT-TYPE
						SYNTAX			INTEGER  {remoteModeEnabled(1),remoteMode-Disabled(2),no-Setting(3)}
						MAX-ACCESS		read-write
						STATUS			current
						DESCRIPTION
                        "GEMC4(GE-MC2/2-STD,GE-MC2/2-APS,GE-MC1/2-APS,GE-MC3/1-MUX) local card Remote Mode,if Remote mode is enabled, the control of
                        this converter is assigned to another remote management platform."
						::= { mc2200-GEMC4Entry 72 }
mc2200-GEMC4LocalLAN1Speed      OBJECT-TYPE
						SYNTAX			INTEGER {speed1000M(1),
						                         speed100M(2),speed10M(3),down(4)}
						MAX-ACCESS		read-only
						STATUS			mandatory
						DESCRIPTION
                        "GE-MC2/2-STD Local card's LAN1 port work speed status.
                         GE-MC2/2-APS Local card's LAN1 port work speed status.
                         GE-MC1/2-APS Local card's LAN1 port work speed status.
			 GE-MC3/1-MUX Local card's LAN1 port work speed status."
						::= { mc2200-GEMC4Entry 73 }
mc2200-GEMC4LocalLAN2Speed      OBJECT-TYPE
						SYNTAX			INTEGER {speed1000M(1),
						                         speed100M(2),speed10M(3),down(4)}
						MAX-ACCESS		read-only
						STATUS			mandatory
						DESCRIPTION
                        "GE-MC2/2-STD Local card's LAN2 port work speed status.
                         GE-MC2/2-APS Local card's LAN2 port work speed status.
                         GE-MC1/2-APS Local card's LAN2 port work speed status.
			 GE-MC3/1-MUX Local card's LAN2 port work speed status."
						::= { mc2200-GEMC4Entry 74 }
mc2200-GEMC4LocalWAN2LAN3Speed      OBJECT-TYPE
						SYNTAX			INTEGER {speed1000M(1),
						                         speed100M(2),speed10M(3),down(4)}
						MAX-ACCESS		read-only
						STATUS			mandatory
						DESCRIPTION
                        "GE-MC2/2-STD Local card's WAN2LAN3 port work speed status.
                         GE-MC2/2-APS Local card's WAN2LAN3 port work speed status.
                         GE-MC1/2-APS Local card's WAN2LAN3 port work speed status.
			 GE-MC3/1-MUX Local card's WAN2LAN3 port work speed status."
						::= { mc2200-GEMC4Entry 75 }
mc2200-GEMC4RemoteLAN1Speed      OBJECT-TYPE
						SYNTAX			INTEGER {speed1000M(1),speed100M(2),
						                         speed10M(3),down(4),no-remotecard(0)}
						MAX-ACCESS		read-only
						STATUS			mandatory
						DESCRIPTION
                        "GE-MC2/2-STD Remote card's LAN1 port work speed status.
                         GE-MC2/2-APS Remote card's LAN1 port work speed status.
                         GE-MC1/2-APS Remote card's LAN1 port work speed status.
			 GE-MC3/1-MUX Remote card's LAN1 port work speed status."
						::= { mc2200-GEMC4Entry 76 }
mc2200-GEMC4RemoteLAN2Speed      OBJECT-TYPE
						SYNTAX			INTEGER {speed1000M(1),speed100M(2),
						                         speed10M(3),down(4),no-remotecard(0)}
						MAX-ACCESS		read-only
						STATUS			mandatory
						DESCRIPTION
                        "GE-MC2/2-STD Remote card's LAN2 port work speed status.
                         GE-MC2/2-APS Remote card's LAN2 port work speed status.
                         GE-MC1/2-APS Remote card's LAN2 port work speed status.
			 GE-MC3/1-MUX Remote card's LAN2 port work speed status."
						::= { mc2200-GEMC4Entry 77 }
mc2200-GEMC4RemoteWAN2LAN3Speed      OBJECT-TYPE
						SYNTAX			INTEGER {speed1000M(1),speed100M(2),
						                         speed10M(3),down(4),no-remotecard(0)}
						MAX-ACCESS		read-only
						STATUS			mandatory
						DESCRIPTION
                        "GE-MC2/2-STD Remote card's WAN2LAN3 port work speed status.
                         GE-MC2/2-APS Remote card's WAN2LAN3 port work speed status.
                         GE-MC1/2-APS Remote card's WAN2LAN3 port work speed status.
			 GE-MC3/1-MUX Remote card's WAN2LAN3 port work speed status."
						::= { mc2200-GEMC4Entry 78 }

mc2200-GEMC4APSActivePort   	OBJECT-TYPE
						SYNTAX		INTEGER {wan1(1),
                          					wan2-lan3(2),no-support-atciveport(3)}

						MAX-ACCESS		read-write
						STATUS			current
						DESCRIPTION
                        "GEMC4(GE-MC1-2-APS) APS Active Port setting."
						::= { mc2200-GEMC4Entry  79 }

mc2200-GEMC4Localportuser1      OBJECT-TYPE
						SYNTAX			DisplayString
						MAX-ACCESS		read-write
						STATUS			current
						DESCRIPTION
                        " User of GE-MC4 Local Port1. "
						::= { mc2200-GEMC4Entry 80 }

mc2200-GEMC4Localportuser2      OBJECT-TYPE
						SYNTAX			DisplayString
						MAX-ACCESS		read-write
						STATUS			current
						DESCRIPTION
                        " User of GE-MC4 Local Port2. "
						::= { mc2200-GEMC4Entry 81 }

mc2200-GEMC4Localportuser3      OBJECT-TYPE
						SYNTAX			DisplayString
						MAX-ACCESS		read-write
						STATUS			current
						DESCRIPTION
                        " User of GE-MC4 Local Port3. "
						::= { mc2200-GEMC4Entry 82 }

mc2200-GEMC4Remoteportuser1      OBJECT-TYPE
						SYNTAX			DisplayString
						MAX-ACCESS		read-write
						STATUS			current
						DESCRIPTION
                        " User of GE-MC4 Remote Port1. "
						::= { mc2200-GEMC4Entry 83 }

mc2200-GEMC4Remoteportuser2      OBJECT-TYPE
						SYNTAX			DisplayString
						MAX-ACCESS		read-write
						STATUS			current
						DESCRIPTION
                        " User of GE-MC4 Remote Port2. "
						::= { mc2200-GEMC4Entry 84 }

mc2200-GEMC4Remoteportuser3      OBJECT-TYPE
						SYNTAX			DisplayString
						MAX-ACCESS		read-write
						STATUS			current
						DESCRIPTION
                        " User of GE-MC4 Remote Port3. "
						::= { mc2200-GEMC4Entry 85 }
mc2200-GEMC4TrapFilterLocalLAN	        OBJECT-TYPE
						SYNTAX			INTEGER {enabled(1),disabled(2)}
						MAX-ACCESS		read-write
						STATUS			current
						DESCRIPTION
                            "Local LAN of GEMC4 Trap Filter ."
						::= { mc2200-GEMC4Entry 86 }
mc2200-GEMC4TrapFilterLocalWAN	        OBJECT-TYPE
						SYNTAX			INTEGER {enabled(1),disabled(2)}
						MAX-ACCESS		read-write
						STATUS			current
						DESCRIPTION
                            "Local WAN of GEMC4 Trap Filter ."
						::= { mc2200-GEMC4Entry 87 }
mc2200-GEMC4TrapFilterRemotePower	        OBJECT-TYPE
						SYNTAX			INTEGER {enabled(1),disabled(2)}
						MAX-ACCESS		read-write
						STATUS			current
						DESCRIPTION
                            "Remote Power of GEMC4 Trap Filter ."
						::= { mc2200-GEMC4Entry 88 }
mc2200-GEMC4TrapFilterRemoteLAN	        OBJECT-TYPE
						SYNTAX			INTEGER {enabled(1),disabled(2)}
						MAX-ACCESS		read-write
						STATUS			current
						DESCRIPTION
                            "Remote LAN of GEMC4 Trap Filter ."
						::= { mc2200-GEMC4Entry 89 }
mc2200-GEMC4TrapFilterRemoteWAN	        OBJECT-TYPE
						SYNTAX			INTEGER {enabled(1),disabled(2)}
						MAX-ACCESS		read-write
						STATUS			current
						DESCRIPTION
                            "Remote WAN of GEMC4 Trap Filter ."
						::= { mc2200-GEMC4Entry 90 }
-- =======================


-- GEMC2 Table  ====================================================

mc2200-GEMC2Table	   OBJECT-TYPE
					SYNTAX			SEQUENCE OF MC2200-GEMC2Entry
					MAX-ACCESS		not-accessible
					STATUS			current
					DESCRIPTION
                   "Sparse table containing one entry for each GEMC2
                     10/100Mbps Twisted-Pair to Fiber Ethernet Media Converter
                     in the system, indexed by chassisIndex and slotIndex."

					::= { mc2200-GEmib 6 }

mc2200-GEMC2Entry			OBJECT-TYPE
						SYNTAX			MC2200-GEMC2Entry
						MAX-ACCESS		not-accessible
						STATUS			current
						DESCRIPTION
            "One table entry per slot in the media converter chassis.
             If physical slot 'n' contains a powered GEMC2 media
             converter, then entry 'n' in this table exists and describes
             the state of the converter's lamps  If slot 'n' is empty, does
             not exist, or contains a different type of device, then table
             entry 'n' does not exist."

						INDEX			{ mc2200-GEMC2CardIndex }
						::= { mc2200-GEMC2Table 1 }






-- ==========================
-- CH-unit config info table --
-- ==========================
MC2200-GEMC2Entry ::=
				SEQUENCE {
					mc2200-GEMC2CardIndex			    INTEGER,	-- 2
					mc2200-GEMC2LocalLANSFPInfo         DisplayString,
					mc2200-GEMC2LocalLANLink          	INTEGER,
					mc2200-GEMC2LocalWANSFPInfo         DisplayString,
					mc2200-GEMC2LocalWANLink          	INTEGER,
					mc2200-GEMC2LocalLANDownStreamBW   	INTEGER,
					mc2200-GEMC2LocalLANUpStreamBW     	INTEGER,
					mc2200-GEMC2LocalLANMode	      	INTEGER,
					mc2200-GEMC2RxGoodOctets        	Counter64, -- 10

                    mc2200-GEMC2RxBadOctets        		Counter64,
                    mc2200-GEMC2TxFCSErr        		Counter64,
					mc2200-GEMC2RxUnicast        		Counter64,
					mc2200-GEMC2TxDeferred        		Counter64,
                    mc2200-GEMC2RxBroadcasts        	Counter64,
                    mc2200-GEMC2RxMulticasts        	Counter64,
					mc2200-GEMC2Rx64Octets        	Counter64,
					mc2200-GEMC2Rx65to127Octets        	Counter64,
                    mc2200-GEMC2Rx128to255Octets        Counter64, -- 20
                    mc2200-GEMC2Rx256to511Octets        Counter64,
                    mc2200-GEMC2Rx512to1023Octets       Counter64,
					mc2200-GEMC2Rx1024toMaxOctets       Counter64,
					mc2200-GEMC2TxOctets        		Counter64,

                    mc2200-GEMC2TxUnicast        		Counter64,
					mc2200-GEMC2TxExcessive        		Counter64,
					mc2200-GEMC2TxMulticasts            Counter64,
                    mc2200-GEMC2TxBroadcasts        	Counter64,
                    mc2200-GEMC2TxSingle        		Counter64, -- 30
					mc2200-GEMC2TxPause        			Counter64,
					mc2200-GEMC2RxPause        			Counter64,
                    mc2200-GEMC2TxMultiple        		Counter64,
                    mc2200-GEMC2RxUndersize        		Counter64,
					mc2200-GEMC2RxFragments             Counter64,
					mc2200-GEMC2RxOversize              Counter64,
                    mc2200-GEMC2RxJabber        		Counter64,
                    mc2200-GEMC2RxErr        		    Counter64,
					mc2200-GEMC2RxFCSErr                Counter64,
					mc2200-GEMC2TxCollisions            Counter64,  -- 40
                    mc2200-GEMC2TxLate        		    Counter64,
                    mc2200-GEMC2RemoteLANSFPInfo        DisplayString,
					mc2200-GEMC2RemoteLANLink           INTEGER,
					mc2200-GEMC2RemoteWANSFPInfo        DisplayString,
					mc2200-GEMC2RemoteWANLink           INTEGER,
					mc2200-GEMC2RemoteLANMode	        INTEGER,
					mc2200-GEMC2RemoteIPAddress       	IpAddress,
		  	        mc2200-GEMC2RemoteSubnetMask      	IpAddress,
					mc2200-GEMC2RemoteGateWay         	IpAddress,
					mc2200-GEMC2RemoteVLANEnable	    INTEGER, -- 50
					mc2200-GEMC2RemoteVID         		INTEGER,
                    mc2200-GEMC2RemoteAlarm      			INTEGER,
                    mc2200-GEMC2RFD						INTEGER,
                    mc2200-GEMC2Default					INTEGER,
                    mc2200-GEMC2Reboot						INTEGER, -- 55
		    		mc2200-GEMC2LocalCardREMOTEMODE		INTEGER,
		    		mc2200-GEMC2LocalLANSpeed              INTEGER,
		    		mc2200-GEMC2RemoteLANSpeed             INTEGER,
		    		mc2200-GEMC2Localportuser     			DisplayString,
		    		mc2200-GEMC2Remoteportuser    			DisplayString,		   -- 60


					mc2200-GEMC2TrapFilterLocalLAN			INTEGER,
					mc2200-GEMC2TrapFilterLocalWAN			INTEGER,
					mc2200-GEMC2TrapFilterRemotePower		INTEGER,
					mc2200-GEMC2TrapFilterRemoteLAN		INTEGER,
					mc2200-GEMC2TrapFilterRemoteWAN		INTEGER

				}


mc2200-GEMC2CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GEMC2Entry 2 }
mc2200-GEMC2LocalLANSFPInfo	OBJECT-TYPE
						SYNTAX		DisplayString
						MAX-ACCESS		read-only
						STATUS			current
						DESCRIPTION
                            "GEMC2 Local card's LAN port SFP infomation."
						::= { mc2200-GEMC2Entry 3 }
mc2200-GEMC2LocalLANLink      OBJECT-TYPE
						SYNTAX			INTEGER {up(1),
						                         down(2)}
						MAX-ACCESS		read-only
						STATUS			mandatory
						DESCRIPTION
                            "GEMC2 Local card's LAN port work link status."
						::= { mc2200-GEMC2Entry 4 }
mc2200-GEMC2LocalWANSFPInfo	OBJECT-TYPE
						SYNTAX		DisplayString
						MAX-ACCESS		read-only
						STATUS			current
						DESCRIPTION
                            "GEMC2 Local card's WAN port SFP infomation."
						::= { mc2200-GEMC2Entry 5 }
mc2200-GEMC2LocalWANLink	        OBJECT-TYPE
						SYNTAX			INTEGER {up(1),
						                         down(2)}
						MAX-ACCESS		read-only
						STATUS			current
						DESCRIPTION
                            "GEMC2 Local card's WAN port work link status."
						::= { mc2200-GEMC2Entry 6 }

mc2200-GEMC2LocalLANDownStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                            "GEMC2 Local card's LAN port DownStream BandWidth. "
						::= { mc2200-GEMC2Entry 7 }
mc2200-GEMC2LocalLANUpStreamBW	OBJECT-TYPE
						SYNTAX			INTEGER  {rate10M(10),rate20M(20),rate30M(30),rate40M(40),rate50M(50),
						                          rate60M(60),rate70M(70),rate80M(80),rate90M(90),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        " GEMC2 Local card's LAN port UpStream BandWidth."
						::= { mc2200-GEMC2Entry 8 }
mc2200-GEMC2LocalLANMode   	OBJECT-TYPE
						SYNTAX		INTEGER {auto-10-100-1000T(1),
                          					mode1000Base-X-auto(2),
                          					mode1000Base-T(3),
                          					mode100Base-Tx(4),
                          					mode10Base-T(5),
                          					mode1000Base-X-1000F(6)}
						MAX-ACCESS		read-write
						STATUS			current
						DESCRIPTION
                        "GEMC2 Local card's LAN port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC2Entry  9 }

mc2200-GEMC2RxGoodOctets OBJECT-TYPE
						SYNTAX			Counter64
						MAX-ACCESS		read-only
						STATUS			current
						DESCRIPTION
                        "GEMC2 Local card's LAN port MIB RxGoodOctetsLow counter."
						::= { mc2200-GEMC2Entry 10 }

mc2200-GEMC2RxBadOctets OBJECT-TYPE
						SYNTAX			Counter64
						MAX-ACCESS		read-only
						STATUS			current
						DESCRIPTION
                        "GEMC2 Local card's LAN port MIB RxBadOctets counter."
						::= { mc2200-GEMC2Entry 12 }
mc2200-GEMC2TxFCSErr OBJECT-TYPE
						SYNTAX			Counter64
						MAX-ACCESS		read-only
						STATUS			current
						DESCRIPTION
                        "GEMC2 Local card's LAN port MIB  TxFCSErr counter."
						::= { mc2200-GEMC2Entry 13 }

mc2200-GEMC2RxUnicast OBJECT-TYPE
						SYNTAX			Counter64
						MAX-ACCESS		read-only
						STATUS			current
						DESCRIPTION
                        "GEMC2 Local card's LAN port MIB RxUnicast counter."
						::= { mc2200-GEMC2Entry 14 }
mc2200-GEMC2TxDeferred OBJECT-TYPE
						SYNTAX			Counter64
						MAX-ACCESS		read-only
						STATUS			current
						DESCRIPTION
                        "GEMC2 Local card's LAN port MIB TxDeferred counter."
						::= { mc2200-GEMC2Entry 15 }
mc2200-GEMC2RxBroadcasts OBJECT-TYPE
						SYNTAX			Counter64
						MAX-ACCESS		read-only
						STATUS			current
						DESCRIPTION
                        "GEMC2 Local card's LAN port MIB RxBroadcasts counter."
						::= { mc2200-GEMC2Entry 16 }
mc2200-GEMC2RxMulticasts OBJECT-TYPE
						SYNTAX			Counter64
						MAX-ACCESS		read-only
						STATUS			current
						DESCRIPTION
                        "GEMC2 Local card's LAN port MIB RxMulticasts counter."
						::= { mc2200-GEMC2Entry 17 }
mc2200-GEMC2Rx64Octets OBJECT-TYPE
						SYNTAX			Counter64
						MAX-ACCESS		read-only
						STATUS			current
						DESCRIPTION
                        "GEMC2 Local card's LAN port MIB Rx64Octets counter."
						::= { mc2200-GEMC2Entry 18 }
mc2200-GEMC2Rx65to127Octets OBJECT-TYPE
						SYNTAX			Counter64
						MAX-ACCESS		read-only
						STATUS			current
						DESCRIPTION
                        "GEMC2 Local card's LAN port MIB Rx65to127Octets counter."
						::= { mc2200-GEMC2Entry 19 }
mc2200-GEMC2Rx128to255Octets OBJECT-TYPE
						SYNTAX			Counter64
						MAX-ACCESS		read-only
						STATUS			current
						DESCRIPTION
                        "GEMC2 Local card's LAN port MIB Rx128to255Octets counter."
						::= { mc2200-GEMC2Entry 20 }
mc2200-GEMC2Rx256to511Octets OBJECT-TYPE
						SYNTAX			Counter64
						MAX-ACCESS		read-only
						STATUS			current
						DESCRIPTION
                        "GEMC2 Local card's LAN port MIB Rx256to511Octets counter."
						::= { mc2200-GEMC2Entry 21 }
mc2200-GEMC2Rx512to1023Octets OBJECT-TYPE
						SYNTAX			Counter64
						MAX-ACCESS		read-only
						STATUS			current
						DESCRIPTION
                        "GEMC2 Local card's LAN port MIB Rx512to1023Octets counter."
						::= { mc2200-GEMC2Entry 22 }
mc2200-GEMC2Rx1024toMaxOctets OBJECT-TYPE
						SYNTAX			Counter64
						MAX-ACCESS		read-only
						STATUS			current
						DESCRIPTION
                        "GEMC2 Local card's LAN port MIB Rx1024toMaxOctets counter."
						::= { mc2200-GEMC2Entry 23 }
mc2200-GEMC2TxOctets OBJECT-TYPE
						SYNTAX			Counter64
						MAX-ACCESS		read-only
						STATUS			current
						DESCRIPTION
                        "GEMC2 Local card's LAN port MIB TxOctetsLow counter."
						::= { mc2200-GEMC2Entry 24 }

mc2200-GEMC2TxUnicast OBJECT-TYPE
						SYNTAX			Counter64
						MAX-ACCESS		read-only
						STATUS			current
						DESCRIPTION
                        "GEMC2 Local card's LAN port MIB TxUnicast counter."
						::= { mc2200-GEMC2Entry 26 }
mc2200-GEMC2TxExcessive OBJECT-TYPE
						SYNTAX			Counter64
						MAX-ACCESS		read-only
						STATUS			current
						DESCRIPTION
                        "GEMC2 Local card's LAN port MIB TxExcessive counter."
						::= { mc2200-GEMC2Entry 27 }
mc2200-GEMC2TxMulticasts OBJECT-TYPE
						SYNTAX			Counter64
						MAX-ACCESS		read-only
						STATUS			current
						DESCRIPTION
                        "GEMC2 Local card's LAN port MIB TxMulticasts counter."
						::= { mc2200-GEMC2Entry 28 }
mc2200-GEMC2TxBroadcasts OBJECT-TYPE
						SYNTAX			Counter64
						MAX-ACCESS		read-only
						STATUS			current
						DESCRIPTION
                        "GEMC2 Local card's LAN port MIB TxBroadcasts counter."
						::= { mc2200-GEMC2Entry 29 }
mc2200-GEMC2TxSingle OBJECT-TYPE
						SYNTAX			Counter64
						MAX-ACCESS		read-only
						STATUS			current
						DESCRIPTION
                        "GEMC2 Local card's LAN port MIB TxSingle counter."
						::= { mc2200-GEMC2Entry 30 }
mc2200-GEMC2TxPause OBJECT-TYPE
						SYNTAX			Counter64
						MAX-ACCESS		read-only
						STATUS			current
						DESCRIPTION
                        "GEMC2 Local card's LAN port MIB TxPause counter."
						::= { mc2200-GEMC2Entry 31 }
mc2200-GEMC2RxPause OBJECT-TYPE
						SYNTAX			Counter64
						MAX-ACCESS		read-only
						STATUS			current
						DESCRIPTION
                        "GEMC2 Local card's LAN port MIB RxPause counter."
						::= { mc2200-GEMC2Entry 32 }
mc2200-GEMC2TxMultiple OBJECT-TYPE
						SYNTAX			Counter64
						MAX-ACCESS		read-only
						STATUS			current
						DESCRIPTION
                        "GEMC2 Local card's LAN port MIB TxMultiple counter."
						::= { mc2200-GEMC2Entry 33 }
mc2200-GEMC2RxUndersize OBJECT-TYPE
						SYNTAX			Counter64
						MAX-ACCESS		read-only
						STATUS			current
						DESCRIPTION
                        "GEMC2 Local card's LAN port MIB RxUndersize counter."
						::= { mc2200-GEMC2Entry 34 }
mc2200-GEMC2RxFragments OBJECT-TYPE
						SYNTAX			Counter64
						MAX-ACCESS		read-only
						STATUS			current
						DESCRIPTION
                        "GEMC2 Local card's LAN port MIB RxFragments counter."
						::= { mc2200-GEMC2Entry 35 }
mc2200-GEMC2RxOversize OBJECT-TYPE
						SYNTAX			Counter64
						MAX-ACCESS		read-only
						STATUS			current
						DESCRIPTION
                        "GEMC2 Local card's LAN port MIB RxOversize counter."
						::= { mc2200-GEMC2Entry 36 }
mc2200-GEMC2RxJabber OBJECT-TYPE
						SYNTAX			Counter64
						MAX-ACCESS		read-only
						STATUS			current
						DESCRIPTION
                        "GEMC2 Local card's LAN port MIB RxJabber counter."
						::= { mc2200-GEMC2Entry 37 }
mc2200-GEMC2RxErr OBJECT-TYPE
						SYNTAX			Counter64
						MAX-ACCESS		read-only
						STATUS			current
						DESCRIPTION
                        "GEMC2 Local card's LAN port MIB RxErr counter."
						::= { mc2200-GEMC2Entry 38 }
mc2200-GEMC2RxFCSErr OBJECT-TYPE
						SYNTAX			Counter64
						MAX-ACCESS		read-only
						STATUS			current
						DESCRIPTION
                        "GEMC2 Local card's LAN port MIB RxFCSErr counter."
						::= { mc2200-GEMC2Entry 39 }
mc2200-GEMC2TxCollisions OBJECT-TYPE
						SYNTAX			Counter64
						MAX-ACCESS		read-only
						STATUS			current
						DESCRIPTION
                        "GEMC2 Local card's LAN port MIB TxCollisions counter."
						::= { mc2200-GEMC2Entry 40 }
mc2200-GEMC2TxLate OBJECT-TYPE
						SYNTAX			Counter64
						MAX-ACCESS		read-only
						STATUS			current
						DESCRIPTION
                        "GEMC2 Local card's port8 MIB TxLate counter."
						::= { mc2200-GEMC2Entry 41 }
mc2200-GEMC2RemoteLANSFPInfo	OBJECT-TYPE
						SYNTAX		DisplayString
						MAX-ACCESS		read-only
						STATUS			current
						DESCRIPTION
                            "GEMC2 Remote card's LAN port SFP infomation."
						::= { mc2200-GEMC2Entry 42 }
mc2200-GEMC2RemoteLANLink      OBJECT-TYPE
						SYNTAX			INTEGER {up(1),
						                         down(2), no-remotecard(0)}
						MAX-ACCESS		read-only
						STATUS			mandatory
						DESCRIPTION
                            "GEMC2 Remote card's LAN port work link status."
						::= { mc2200-GEMC2Entry 43 }
mc2200-GEMC2RemoteWANSFPInfo	OBJECT-TYPE
						SYNTAX		DisplayString
						MAX-ACCESS		read-only
						STATUS			current
						DESCRIPTION
                            "GEMC2 Remote card's WAN port SFP infomation."
						::= { mc2200-GEMC2Entry 44 }
mc2200-GEMC2RemoteWANLink	        OBJECT-TYPE
						SYNTAX			INTEGER {up(1),
						                         down(2), no-remotecard(0)}
						MAX-ACCESS		read-only
						STATUS			current
						DESCRIPTION
                            "GEMC2 Remote card's WAN port work link status."
						::= { mc2200-GEMC2Entry 45 }


mc2200-GEMC2RemoteLANMode   	OBJECT-TYPE
						SYNTAX		INTEGER {auto-10-100-1000T(1),
                          					mode1000Base-X-auto(2),
                          					mode1000Base-T(3),
                          					mode100Base-Tx(4),
                          					mode10Base-T(5),
                          					mode1000Base-X-1000F(6),no-remotecard(0)}
						MAX-ACCESS		read-write
						STATUS			current
						DESCRIPTION
                        "GEMC2 Remote card's LAN port Mode configuration,
                    	set INTEGER(1) to auto(10/100/1000T),
                    	set INTEGER(2) to 1000Base-X(auto),
                    	set INTEGER(3) to 1000Base-T,
                    	set INTEGER(4) to 100Base-Tx,
                    	set INTEGER(5) to 10Base-X,
                    	set INTEGER(6) to 1000Base-X(1000F),
                    	Ohter value is invalid"
						::= { mc2200-GEMC2Entry  46 }
mc2200-GEMC2RemoteIPAddress  OBJECT-TYPE
        			SYNTAX      IpAddress
        			ACCESS      read-write
        			STATUS      mandatory
	    			DESCRIPTION
            		"The IP address to GEMC2 Remote IP ping."
        			::= {mc2200-GEMC2Entry 47}

mc2200-GEMC2RemoteSubnetMask    OBJECT-TYPE
        			SYNTAX      IpAddress
        			ACCESS      read-write
        			STATUS      mandatory
	    			DESCRIPTION
                    "The Net mask to  GEMC2 Remote IP ping."
        			::= {mc2200-GEMC2Entry 48}

mc2200-GEMC2RemoteGateWay    OBJECT-TYPE
        			SYNTAX      IpAddress
        			ACCESS      read-write
        			STATUS      mandatory
	   				 DESCRIPTION
                    "The gateware to GEMC2 Remote IP ping."
        			::= {mc2200-GEMC2Entry 49}

mc2200-GEMC2RemoteVLANEnable  OBJECT-TYPE
        			SYNTAX      INTEGER {enable(1),disable(2), no-remotecard(0)}
        			ACCESS      read-write
        			STATUS      mandatory
	    			DESCRIPTION
                    "Enable or disable Remote GEMC2 IP ping 802.1Q VLAN."
        			::= {mc2200-GEMC2Entry 50}
mc2200-GEMC2RemoteVID  OBJECT-TYPE
        			SYNTAX      INTEGER
        			ACCESS      read-write
        			STATUS      mandatory
	    			DESCRIPTION
                    "GEMC2 Remote IP ping  802.1Q VLAN ID."
        			::= {mc2200-GEMC2Entry 51}
mc2200-GEMC2RemoteAlarm      OBJECT-TYPE
						SYNTAX			INTEGER  {enabled(1),disabled(2)}
						MAX-ACCESS		read-write
						STATUS			current
						DESCRIPTION
                        "Enable or disable GEMC2 Media converter card remote alarm.
                         set INTEGER(1) to Enable remote alarm,
                         set INTEGER(2) to Disable remote alarm,
                         Other value is invalid."
						::= { mc2200-GEMC2Entry 52 }
mc2200-GEMC2RFD		      OBJECT-TYPE
						SYNTAX			INTEGER  {enabled(1),disabled(2)}
						MAX-ACCESS		read-write
						STATUS			current
						DESCRIPTION
                        "GEMC2 Media converter card remote fault detect operation.
                         set INTEGER(1) to Enable RFD,
                         set INTEGER(2) to Disable RFD,
                         Other value is invalid."
						::= { mc2200-GEMC2Entry 53 }
mc2200-GEMC2Default		OBJECT-TYPE
						SYNTAX			INTEGER
						MAX-ACCESS		write-only
						STATUS			current
						DESCRIPTION
                        "Write GEMC2 card default setting,
                        set INTEGER(1) to write default.
                        Other value is invalid."
						::= { mc2200-GEMC2Entry 54 }
mc2200-GEMC2Reboot		OBJECT-TYPE
						SYNTAX			INTEGER
						MAX-ACCESS		write-only
						STATUS			current
						DESCRIPTION
                        "Reboot GEMC2 local card,
                        set INTEGER(1) to reboot this card.
                        Other value is invalid. "
						::= { mc2200-GEMC2Entry 55 }
mc2200-GEMC2LocalCardREMOTEMODE    OBJECT-TYPE
						SYNTAX			INTEGER  {remoteMode-Enabled(1),remoteMode-Disabled(2),no-Setting(3)}
						MAX-ACCESS		read-write
						STATUS			current
						DESCRIPTION
                        "GEMC2 local card Remote Mode,if Remote mode is enabled, the control of
                        this converter is assigned to another remote management platform."
						::= { mc2200-GEMC2Entry 56 }
mc2200-GEMC2LocalLANSpeed      OBJECT-TYPE
						SYNTAX			INTEGER {speed1000M(1),
						                         speed100M(2),speed10M(3),down(4)}
						MAX-ACCESS		read-only
						STATUS			mandatory
						DESCRIPTION
                        "GE-MC2 Local card's LAN port work speed status."
						::= { mc2200-GEMC2Entry 57 }
mc2200-GEMC2RemoteLANSpeed      OBJECT-TYPE
						SYNTAX			INTEGER {speed1000M(1),speed100M(2),
						                         speed10M(3),down(4),no-remotecard(0)}
						MAX-ACCESS		read-only
						STATUS			mandatory
						DESCRIPTION
                        "GE-MC2 Remote card's LAN port work speed status."
						::= { mc2200-GEMC2Entry 58 }

mc2200-GEMC2Localportuser      OBJECT-TYPE
						SYNTAX			DisplayString
						MAX-ACCESS		read-write
						STATUS			current
						DESCRIPTION
                        " User of GE-MC2 Local Port1. "
						::= { mc2200-GEMC2Entry 59 }

mc2200-GEMC2Remoteportuser      OBJECT-TYPE
						SYNTAX			DisplayString
						MAX-ACCESS		read-write
						STATUS			current
						DESCRIPTION
                        " User of GE-MC2 Remote Port1. "
						::= { mc2200-GEMC2Entry 60 }
mc2200-GEMC2TrapFilterLocalLAN	        OBJECT-TYPE
						SYNTAX			INTEGER {enabled(1),disabled(2)}
						MAX-ACCESS		read-write
						STATUS			current
						DESCRIPTION
                            "Local LAN of GEMC2 Trap Filter ."
						::= { mc2200-GEMC2Entry 61 }
mc2200-GEMC2TrapFilterLocalWAN	        OBJECT-TYPE
						SYNTAX			INTEGER {enabled(1),disabled(2)}
						MAX-ACCESS		read-write
						STATUS			current
						DESCRIPTION
                            "Local WAN of GEMC2 Trap Filter ."
						::= { mc2200-GEMC2Entry 62 }
mc2200-GEMC2TrapFilterRemotePower	        OBJECT-TYPE
						SYNTAX			INTEGER {enabled(1),disabled(2)}
						MAX-ACCESS		read-write
						STATUS			current
						DESCRIPTION
                            "Remote Power of GEMC2 Trap Filter ."
						::= { mc2200-GEMC2Entry 63 }
mc2200-GEMC2TrapFilterRemoteLAN	        OBJECT-TYPE
						SYNTAX			INTEGER {enabled(1),disabled(2)}
						MAX-ACCESS		read-write
						STATUS			current
						DESCRIPTION
                            "Remote LAN of GEMC2 Trap Filter ."
						::= { mc2200-GEMC2Entry 64 }
mc2200-GEMC2TrapFilterRemoteWAN	        OBJECT-TYPE
						SYNTAX			INTEGER {enabled(1),disabled(2)}
						MAX-ACCESS		read-write
						STATUS			current
						DESCRIPTION
                            "Remote WAN of GEMC2 Trap Filter ."
						::= { mc2200-GEMC2Entry 65 }

-- FESFP Table  ====================================================

mc2200-FESFPTable	   OBJECT-TYPE
					SYNTAX			SEQUENCE OF MC2200-FESFPEntry
					MAX-ACCESS		not-accessible
					STATUS			current
					DESCRIPTION
                   "Sparse table containing one entry for each FESFP
                     10/100Mbps Twisted-Pair to Fiber Ethernet Media Converter
                     in the system, indexed by chassisIndex and slotIndex."

					::= { mc2200-GEmib 11 }

mc2200-FESFPEntry			OBJECT-TYPE
						SYNTAX			MC2200-FESFPEntry
						MAX-ACCESS		not-accessible
						STATUS			current
						DESCRIPTION
            "One table entry per slot in the media converter chassis.
             If physical slot 'n' contains a powered FESFP media
             converter, then entry 'n' in this table exists and describes
             the state of the converter's lamps  If slot 'n' is empty, does
             not exist, or contains a different type of device, then table
             entry 'n' does not exist."

						INDEX			{ mc2200-FESFPCardIndex }
						::= { mc2200-FESFPTable 1 }






-- ==========================
-- CH-unit config info table --
-- ==========================
MC2200-FESFPEntry ::=
				SEQUENCE {
					mc2200-FESFPCardIndex			    INTEGER,	-- 1
					mc2200-FESFPLocalTXLink          	INTEGER,
					mc2200-FESFPLocalWANSFPInfo         DisplayString,
					mc2200-FESFPLocalWANLink          	INTEGER,
					mc2200-FESFPLocalTXDownStreamBW   	INTEGER,
					mc2200-FESFPLocalTXUpStreamBW     	INTEGER,
					mc2200-FESFPLocalTXMode	      	INTEGER,
					mc2200-FESFPLocalTXMDIX                INTEGER,
					mc2200-FESFPRxGoodOctets        	Counter64,

                    mc2200-FESFPRxBadOctets        		Counter64,
                    mc2200-FESFPTxFCSErr        		Counter64,
					mc2200-FESFPRxUnicast        		Counter64,
					mc2200-FESFPTxDeferred        		Counter64,
                    mc2200-FESFPRxBroadcasts        	Counter64,
                    mc2200-FESFPRxMulticasts        	Counter64,
					mc2200-FESFPRx64Octets        		Counter64,
					mc2200-FESFPRx65to127Octets        Counter64,
                    mc2200-FESFPRx128to255Octets        Counter64,
                    mc2200-FESFPRx256to511Octets        Counter64, -- 20
                    mc2200-FESFPRx512to1023Octets       Counter64,
					mc2200-FESFPRx1024toMaxOctets       Counter64,
					mc2200-FESFPTxOctets        		Counter64,

                    mc2200-FESFPTxUnicast        		Counter64,
					mc2200-FESFPTxExcessive        		Counter64,
					mc2200-FESFPTxMulticasts            Counter64,
                    mc2200-FESFPTxBroadcasts        	Counter64,
                    mc2200-FESFPTxSingle        		Counter64, -- 30
					mc2200-FESFPTxPause        			Counter64,
					mc2200-FESFPRxPause        			Counter64,
                    mc2200-FESFPTxMultiple        		Counter64,
                    mc2200-FESFPRxUndersize        		Counter64,
					mc2200-FESFPRxFragments             Counter64,
					mc2200-FESFPRxOversize              Counter64,
                    mc2200-FESFPRxJabber        		Counter64,
                    mc2200-FESFPRxErr        		    Counter64,
					mc2200-FESFPRxFCSErr                Counter64,
					mc2200-FESFPTxCollisions            Counter64,  -- 40
                    mc2200-FESFPTxLate        		    Counter64,
					mc2200-FESFPRemoteTXLink           INTEGER,
					mc2200-FESFPRemoteWANSFPInfo        DisplayString,
					mc2200-FESFPRemoteWANLink           INTEGER,
					mc2200-FESFPRemoteTXMode	        INTEGER,
                    mc2200-FESFPRemoteTXMDIX               INTEGER,
					mc2200-FESFPRemoteIPAddress       	IpAddress,
		  	        mc2200-FESFPRemoteSubnetMask      	IpAddress,
					mc2200-FESFPRemoteGateWay         	IpAddress,
					mc2200-FESFPRemoteVLANEnable	    INTEGER, -- 50
					mc2200-FESFPRemoteVID         		INTEGER,
                    mc2200-FESFPRemoteAlarm      		INTEGER,
                    mc2200-FESFPRFD						INTEGER,
                    mc2200-FESFPDefault					INTEGER,
                    mc2200-FESFPReboot					INTEGER, -- 55
					mc2200-FESFPLocalTXSpeed                  INTEGER,
					mc2200-FESFPRemoteTXSpeed                 INTEGER,
					mc2200-FESFPLocalportuser     DisplayString,
					mc2200-FESFPRemoteportuser    DisplayString,
					mc2200-FESFPLocalTXDuplex	    		INTEGER, -- 60
					mc2200-FESFPRemoteTXDuplex	    		INTEGER,
					mc2200-FESFPFlowControl			INTEGER,
					mc2200-FESFPWANOpticalPowerCheck			INTEGER,
					mc2200-FESFPWANThreshold			INTEGER,
					mc2200-FESFPTrapFilterLocalLAN			INTEGER,
					mc2200-FESFPTrapFilterLocalWAN			INTEGER,
					mc2200-FESFPTrapFilterRemotePower		INTEGER,
					mc2200-FESFPTrapFilterRemoteLAN		INTEGER,
					mc2200-FESFPTrapFilterRemoteWAN		INTEGER,
					mc2200-FESFPLoopback          		INTEGER,
					mc2200-FESFPCardType          		DisplayString
				}


mc2200-FESFPCardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-FESFPEntry 1 }
mc2200-FESFPLocalTXLink      OBJECT-TYPE
						SYNTAX			INTEGER {up(1),
						                         down(2)}
						MAX-ACCESS		read-only
						STATUS			mandatory
						DESCRIPTION
                            "FESFP Local card's LAN port work link status."
						::= { mc2200-FESFPEntry 2 }
mc2200-FESFPLocalWANSFPInfo	OBJECT-TYPE
						SYNTAX		DisplayString
						MAX-ACCESS		read-only
						STATUS			current
						DESCRIPTION
                            "FESFP Local card's WAN port SFP infomation."
						::= { mc2200-FESFPEntry 3 }
mc2200-FESFPLocalWANLink	        OBJECT-TYPE
						SYNTAX			INTEGER {up(1),
						                         down(2)}
						MAX-ACCESS		read-only
						STATUS			current
						DESCRIPTION
                            "FESFP Local card's WAN port work link status."
						::= { mc2200-FESFPEntry 4 }

mc2200-FESFPLocalTXDownStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),rate80M(80),rate85M(85),rate90M(90),rate95M(95),rate100M(100)
						                          }
						MAX-ACCESS		read-write
						STATUS			current
						DESCRIPTION
                            "FESFP Local card's LAN port DownStream BandWidth. "
						::= { mc2200-FESFPEntry 5 }
mc2200-FESFPLocalTXUpStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),rate80M(80),rate85M(85),rate90M(90),rate95M(95),rate100M(100)
						                          }
						MAX-ACCESS		read-write
						STATUS			current
						DESCRIPTION
                        " FESFP Local card's LAN port UpStream BandWidth."
						::= { mc2200-FESFPEntry 6 }
mc2200-FESFPLocalTXMode   	OBJECT-TYPE
						SYNTAX		INTEGER {auto(1),
                          					mode10MHALFDUPLEX(2),
                          					mode10MFULLDUPLEX(3),
                          					mode100MHALFDUPLEX(4),
                          					mode100MFULLDUPLEX(5)}
						MAX-ACCESS		read-write
						STATUS			current
						DESCRIPTION
                        "FESFP Local card's LAN port Mode configuration,
                    	set INTEGER(1) to auto(10/100),
                    	set INTEGER(2) to 10H,
                    	set INTEGER(3) to 10F,
                    	set INTEGER(4) to 100H,
                    	set INTEGER(5) to 100F,
                    	Ohter value is invalid"
						::= { mc2200-FESFPEntry  7 }
mc2200-FESFPLocalTXMDIX   	OBJECT-TYPE
						SYNTAX		INTEGER {auto(1),
                          					mdi(2),
                          					mdix(3)}
						MAX-ACCESS		read-write
						STATUS			current
						DESCRIPTION
                        "FESFP Local card's LAN port Mode configuration,
                    	set INTEGER(1) to auto,
                    	set INTEGER(2) to MDI,
                    	set INTEGER(3) to MDIX,
                    	Ohter value is invalid"
						::= { mc2200-FESFPEntry  8 }

mc2200-FESFPRxGoodOctets OBJECT-TYPE
						SYNTAX			Counter64
						MAX-ACCESS		read-only
						STATUS			current
						DESCRIPTION
                        "FESFP Local card's LAN port MIB RxGoodOctetsLow counter."
						::= { mc2200-FESFPEntry 9 }

mc2200-FESFPRxBadOctets OBJECT-TYPE
						SYNTAX			Counter64
						MAX-ACCESS		read-only
						STATUS			current
						DESCRIPTION
                        "FESFP Local card's LAN port MIB RxBadOctets counter."
						::= { mc2200-FESFPEntry 11 }
mc2200-FESFPTxFCSErr OBJECT-TYPE
						SYNTAX			Counter64
						MAX-ACCESS		read-only
						STATUS			current
						DESCRIPTION
                        "FESFP Local card's LAN port MIB  TxFCSErr counter."
						::= { mc2200-FESFPEntry 12 }

mc2200-FESFPRxUnicast OBJECT-TYPE
						SYNTAX			Counter64
						MAX-ACCESS		read-only
						STATUS			current
						DESCRIPTION
                        "FESFP Local card's LAN port MIB RxUnicast counter."
						::= { mc2200-FESFPEntry 13 }
mc2200-FESFPTxDeferred OBJECT-TYPE
						SYNTAX			Counter64
						MAX-ACCESS		read-only
						STATUS			current
						DESCRIPTION
                        "FESFP Local card's LAN port MIB TxDeferred counter."
						::= { mc2200-FESFPEntry 14 }
mc2200-FESFPRxBroadcasts OBJECT-TYPE
						SYNTAX			Counter64
						MAX-ACCESS		read-only
						STATUS			current
						DESCRIPTION
                        "FESFP Local card's LAN port MIB RxBroadcasts counter."
						::= { mc2200-FESFPEntry 15 }
mc2200-FESFPRxMulticasts OBJECT-TYPE
						SYNTAX			Counter64
						MAX-ACCESS		read-only
						STATUS			current
						DESCRIPTION
                        "FESFP Local card's LAN port MIB RxMulticasts counter."
						::= { mc2200-FESFPEntry 16 }
mc2200-FESFPRx64Octets OBJECT-TYPE
						SYNTAX			Counter64
						MAX-ACCESS		read-only
						STATUS			current
						DESCRIPTION
                        "FESFP Local card's LAN port MIB Rx64Octets counter."
						::= { mc2200-FESFPEntry 17 }
mc2200-FESFPRx65to127Octets OBJECT-TYPE
						SYNTAX			Counter64
						MAX-ACCESS		read-only
						STATUS			current
						DESCRIPTION
                        "FESFP Local card's LAN port MIB Rx65to127Octets counter."
						::= { mc2200-FESFPEntry 18 }
mc2200-FESFPRx128to255Octets OBJECT-TYPE
						SYNTAX			Counter64
						MAX-ACCESS		read-only
						STATUS			current
						DESCRIPTION
                        "FESFP Local card's LAN port MIB Rx128to255Octets counter."
						::= { mc2200-FESFPEntry 19 }
mc2200-FESFPRx256to511Octets OBJECT-TYPE
						SYNTAX			Counter64
						MAX-ACCESS		read-only
						STATUS			current
						DESCRIPTION
                        "FESFP Local card's LAN port MIB Rx256to511Octets counter."
						::= { mc2200-FESFPEntry 20 }
mc2200-FESFPRx512to1023Octets OBJECT-TYPE
						SYNTAX			Counter64
						MAX-ACCESS		read-only
						STATUS			current
						DESCRIPTION
                        "FESFP Local card's LAN port MIB Rx512to1023Octets counter."
						::= { mc2200-FESFPEntry 21 }
mc2200-FESFPRx1024toMaxOctets OBJECT-TYPE
						SYNTAX			Counter64
						MAX-ACCESS		read-only
						STATUS			current
						DESCRIPTION
                        "FESFP Local card's LAN port MIB Rx1024toMaxOctets counter."
						::= { mc2200-FESFPEntry 22 }
mc2200-FESFPTxOctets OBJECT-TYPE
						SYNTAX			Counter64
						MAX-ACCESS		read-only
						STATUS			current
						DESCRIPTION
                        "FESFP Local card's LAN port MIB TxOctetsLow counter."
						::= { mc2200-FESFPEntry 23 }

mc2200-FESFPTxUnicast OBJECT-TYPE
						SYNTAX			Counter64
						MAX-ACCESS		read-only
						STATUS			current
						DESCRIPTION
                        "FESFP Local card's LAN port MIB TxUnicast counter."
						::= { mc2200-FESFPEntry 25 }
mc2200-FESFPTxExcessive OBJECT-TYPE
						SYNTAX			Counter64
						MAX-ACCESS		read-only
						STATUS			current
						DESCRIPTION
                        "FESFP Local card's LAN port MIB TxExcessive counter."
						::= { mc2200-FESFPEntry 26 }
mc2200-FESFPTxMulticasts OBJECT-TYPE
						SYNTAX			Counter64
						MAX-ACCESS		read-only
						STATUS			current
						DESCRIPTION
                        "FESFP Local card's LAN port MIB TxMulticasts counter."
						::= { mc2200-FESFPEntry 27 }
mc2200-FESFPTxBroadcasts OBJECT-TYPE
						SYNTAX			Counter64
						MAX-ACCESS		read-only
						STATUS			current
						DESCRIPTION
                        "FESFP Local card's LAN port MIB TxBroadcasts counter."
						::= { mc2200-FESFPEntry 28 }
mc2200-FESFPTxSingle OBJECT-TYPE
						SYNTAX			Counter64
						MAX-ACCESS		read-only
						STATUS			current
						DESCRIPTION
                        "FESFP Local card's LAN port MIB TxSingle counter."
						::= { mc2200-FESFPEntry 29 }
mc2200-FESFPTxPause OBJECT-TYPE
						SYNTAX			Counter64
						MAX-ACCESS		read-only
						STATUS			current
						DESCRIPTION
                        "FESFP Local card's LAN port MIB TxPause counter."
						::= { mc2200-FESFPEntry 30 }
mc2200-FESFPRxPause OBJECT-TYPE
						SYNTAX			Counter64
						MAX-ACCESS		read-only
						STATUS			current
						DESCRIPTION
                        "FESFP Local card's LAN port MIB RxPause counter."
						::= { mc2200-FESFPEntry 31 }
mc2200-FESFPTxMultiple OBJECT-TYPE
						SYNTAX			Counter64
						MAX-ACCESS		read-only
						STATUS			current
						DESCRIPTION
                        "FESFP Local card's LAN port MIB TxMultiple counter."
						::= { mc2200-FESFPEntry 32 }
mc2200-FESFPRxUndersize OBJECT-TYPE
						SYNTAX			Counter64
						MAX-ACCESS		read-only
						STATUS			current
						DESCRIPTION
                        "FESFP Local card's LAN port MIB RxUndersize counter."
						::= { mc2200-FESFPEntry 33 }
mc2200-FESFPRxFragments OBJECT-TYPE
						SYNTAX			Counter64
						MAX-ACCESS		read-only
						STATUS			current
						DESCRIPTION
                        "FESFP Local card's LAN port MIB RxFragments counter."
						::= { mc2200-FESFPEntry 34 }
mc2200-FESFPRxOversize OBJECT-TYPE
						SYNTAX			Counter64
						MAX-ACCESS		read-only
						STATUS			current
						DESCRIPTION
                        "FESFP Local card's LAN port MIB RxOversize counter."
						::= { mc2200-FESFPEntry 35 }
mc2200-FESFPRxJabber OBJECT-TYPE
						SYNTAX			Counter64
						MAX-ACCESS		read-only
						STATUS			current
						DESCRIPTION
                        "FESFP Local card's LAN port MIB RxJabber counter."
						::= { mc2200-FESFPEntry 36 }
mc2200-FESFPRxErr OBJECT-TYPE
						SYNTAX			Counter64
						MAX-ACCESS		read-only
						STATUS			current
						DESCRIPTION
                        "FESFP Local card's LAN port MIB RxErr counter."
						::= { mc2200-FESFPEntry 37 }
mc2200-FESFPRxFCSErr OBJECT-TYPE
						SYNTAX			Counter64
						MAX-ACCESS		read-only
						STATUS			current
						DESCRIPTION
                        "FESFP Local card's LAN port MIB RxFCSErr counter."
						::= { mc2200-FESFPEntry 38 }
mc2200-FESFPTxCollisions OBJECT-TYPE
						SYNTAX			Counter64
						MAX-ACCESS		read-only
						STATUS			current
						DESCRIPTION
                        "FESFP Local card's LAN port MIB TxCollisions counter."
						::= { mc2200-FESFPEntry 39 }
mc2200-FESFPTxLate OBJECT-TYPE
						SYNTAX			Counter64
						MAX-ACCESS		read-only
						STATUS			current
						DESCRIPTION
                        "FESFP Local card's port8 MIB TxLate counter."
						::= { mc2200-FESFPEntry 40 }
mc2200-FESFPRemoteTXLink      OBJECT-TYPE
						SYNTAX			INTEGER {up(1),
						                         down(2), noremotecard(0)}
						MAX-ACCESS		read-only
						STATUS			mandatory
						DESCRIPTION
                            "FESFP Remote card's LAN port work link status."
						::= { mc2200-FESFPEntry 41 }
mc2200-FESFPRemoteWANSFPInfo	OBJECT-TYPE
						SYNTAX		DisplayString
						MAX-ACCESS		read-only
						STATUS			current
						DESCRIPTION
                            "FESFP Remote card's WAN port SFP infomation."
						::= { mc2200-FESFPEntry 42 }
mc2200-FESFPRemoteWANLink	        OBJECT-TYPE
						SYNTAX			INTEGER {up(1),
						                         down(2), noremotecard(0)}
						MAX-ACCESS		read-only
						STATUS			current
						DESCRIPTION
                            "FESFP Remote card's WAN port work link status."
						::= { mc2200-FESFPEntry 43 }


mc2200-FESFPRemoteTXMode   	OBJECT-TYPE
						SYNTAX		INTEGER {auto(1),
                          					mode10MHALFDUPLEX(2),
                          					mode10MFULLDUPLEX(3),
                          					mode100MHALFDUPLEX(4),
                          					mode100MFULLDUPLEX(5),noremotecard(0)}
						MAX-ACCESS		read-write
						STATUS			current
						DESCRIPTION
                        "FESFP Remote card's LAN port Mode configuration,
                    	set INTEGER(1) to auto(10/100),
                    	set INTEGER(2) to 10H,
                    	set INTEGER(3) to 10F,
                    	set INTEGER(4) to 100H,
                    	set INTEGER(5) to 100F,
                    	Ohter value is invalid"
						::= { mc2200-FESFPEntry  44 }

mc2200-FESFPRemoteTXMDIX   	OBJECT-TYPE
						SYNTAX		INTEGER {auto(1),
                          					mdi(2),
                          					mdix(3),noremotecard(0)}
						MAX-ACCESS		read-write
						STATUS			current
						DESCRIPTION
                        "FESFP Remote card's LAN port Mode configuration,
                    	set INTEGER(1) to auto,
                    	set INTEGER(2) to MDI,
                    	set INTEGER(3) to MDIX,
                    	Ohter value is invalid"
						::= { mc2200-FESFPEntry  45 }
mc2200-FESFPRemoteIPAddress  OBJECT-TYPE
        			SYNTAX      IpAddress
        			ACCESS      read-write
        			STATUS      mandatory
	    			DESCRIPTION
            		"The IP address to FESFP Remote IP ping."
        			::= {mc2200-FESFPEntry 46}

mc2200-FESFPRemoteSubnetMask    OBJECT-TYPE
        			SYNTAX      IpAddress
        			ACCESS      read-write
        			STATUS      mandatory
	    			DESCRIPTION
                    "The Net mask to  FESFP Remote IP ping."
        			::= {mc2200-FESFPEntry 47}

mc2200-FESFPRemoteGateWay    OBJECT-TYPE
        			SYNTAX      IpAddress
        			ACCESS      read-write
        			STATUS      mandatory
	   				 DESCRIPTION
                    "The gateware to FESFP Remote IP ping."
        			::= {mc2200-FESFPEntry 48}

mc2200-FESFPRemoteVLANEnable  OBJECT-TYPE
        			SYNTAX      INTEGER {enable(1),disable(2), noremotecard(0)}
        			ACCESS      read-write
        			STATUS      mandatory
	    			DESCRIPTION
                    "Enable or disable Remote FESFP IP ping 802.1Q VLAN."
        			::= {mc2200-FESFPEntry 49}
mc2200-FESFPRemoteVID  OBJECT-TYPE
        			SYNTAX      INTEGER
        			ACCESS      read-write
        			STATUS      mandatory
	    			DESCRIPTION
                    "FESFP Remote IP ping  802.1Q VLAN ID."
        			::= {mc2200-FESFPEntry 50}
mc2200-FESFPRemoteAlarm      OBJECT-TYPE
						SYNTAX			INTEGER  {enabled(1),disabled(2)}
						MAX-ACCESS		read-write
						STATUS			current
						DESCRIPTION
                        "Enable or disable FESFP Media converter card remote alarm.
                         set INTEGER(1) to Enable remote alarm,
                         set INTEGER(2) to Disable remote alarm,
                         Other value is invalid."
						::= { mc2200-FESFPEntry 51 }
mc2200-FESFPRFD		      OBJECT-TYPE
						SYNTAX			INTEGER  {enabled(1),disabled(2)}
						MAX-ACCESS		read-write
						STATUS			current
						DESCRIPTION
                        "FESFP Media converter card remote fault detect operation.
                         set INTEGER(1) to Enable RFD,
                         set INTEGER(2) to Disable RFD,
                         Other value is invalid."
						::= { mc2200-FESFPEntry 52 }
mc2200-FESFPDefault		OBJECT-TYPE
						SYNTAX			INTEGER
						MAX-ACCESS		write-only
						STATUS			current
						DESCRIPTION
                        "Write FESFP card default setting,
                        set INTEGER(1) to write default.
                        Other value is invalid."
						::= { mc2200-FESFPEntry 53 }
mc2200-FESFPReboot		OBJECT-TYPE
						SYNTAX			INTEGER
						MAX-ACCESS		write-only
						STATUS			current
						DESCRIPTION
                        "Reboot FESFP local card,
                        set INTEGER(1) to reboot this card.
                        Other value is invalid. "
						::= { mc2200-FESFPEntry 54 }
mc2200-FESFPLocalTXSpeed      OBJECT-TYPE
						SYNTAX			INTEGER {speed100M(1),
						                         speed10M(2),down(3)}
						MAX-ACCESS		read-only
						STATUS			mandatory
						DESCRIPTION
                        "FESFP Local card's LAN port work speed status."
						::= { mc2200-FESFPEntry 55 }
mc2200-FESFPRemoteTXSpeed      OBJECT-TYPE
						SYNTAX			INTEGER {speed100M(1),speed10M(2),
						                         down(3),noremotecard(0)}
						MAX-ACCESS		read-only
						STATUS			mandatory
						DESCRIPTION
                        "FESFP Remote card's LAN port work speed status."
						::= { mc2200-FESFPEntry 56 }

mc2200-FESFPLocalportuser      OBJECT-TYPE
						SYNTAX			DisplayString
						MAX-ACCESS		read-write
						STATUS			current
						DESCRIPTION
                        " User of FESFP Local Port1. "
						::= { mc2200-FESFPEntry 57 }

mc2200-FESFPRemoteportuser      OBJECT-TYPE
						SYNTAX			DisplayString
						MAX-ACCESS		read-write
						STATUS			current
						DESCRIPTION
                        " User of FESFP Remote Port1. "
						::= { mc2200-FESFPEntry 58 }

mc2200-FESFPLocalTXDuplex      OBJECT-TYPE
						SYNTAX			INTEGER {fullDuplex(1),
						                         halfDuplex(2),down(3)}
						MAX-ACCESS		read-only
						STATUS			mandatory
						DESCRIPTION
                        "FESFP Local card's TX port work duplex status."
						::= { mc2200-FESFPEntry 59 }
mc2200-FESFPRemoteTXDuplex      OBJECT-TYPE
						SYNTAX			INTEGER {fullDuplex(1),
						                         halfDuplex(2),down(3),noremotecard(0)}
						MAX-ACCESS		read-only
						STATUS			mandatory
						DESCRIPTION
                        "FESFP Remote card's TX port work duplex status."
						::= { mc2200-FESFPEntry 60 }
mc2200-FESFPFlowControl        OBJECT-TYPE
						SYNTAX			INTEGER  {enabled(1),disabled(2)}
						MAX-ACCESS		read-write
						STATUS			current
						DESCRIPTION
                        "FESFP Media converter card flow control operation.
                         set INTEGER(1) to Enable Flow Control,
                         set INTEGER(2) to Disable Flow Control,
                         Other value is invalid."
						::= { mc2200-FESFPEntry 61 }
mc2200-FESFPWANOpticalPowerCheck        OBJECT-TYPE
						SYNTAX			INTEGER  {enabled(1),disabled(2)}
						MAX-ACCESS		read-write
						STATUS			current
						DESCRIPTION
                        "FESFP Media converter card WANOpticalPowerCheck  operation.
                         set INTEGER(1) to Enable WANOpticalPowerCheck,
                         set INTEGER(2) to Disable WANOpticalPowerCheck,
                         Other value is invalid."
						::= { mc2200-FESFPEntry 62 }
mc2200-FESFPWANThreshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "FESFP Media converter card WANThreshold operation.
                         Other value is invalid."
						::= { mc2200-FESFPEntry 63 }
mc2200-FESFPTrapFilterLocalLAN	        OBJECT-TYPE
						SYNTAX			INTEGER {enabled(1),disabled(2)}
						MAX-ACCESS		read-write
						STATUS			current
						DESCRIPTION
                            "Local LAN of FEMC3 Trap Filter ."
						::= { mc2200-FESFPEntry 64 }
mc2200-FESFPTrapFilterLocalWAN	        OBJECT-TYPE
						SYNTAX			INTEGER {enabled(1),disabled(2)}
						MAX-ACCESS		read-write
						STATUS			current
						DESCRIPTION
                            "Local WAN of FEMC3 Trap Filter ."
						::= { mc2200-FESFPEntry 65 }
mc2200-FESFPTrapFilterRemotePower	        OBJECT-TYPE
						SYNTAX			INTEGER {enabled(1),disabled(2)}
						MAX-ACCESS		read-write
						STATUS			current
						DESCRIPTION
                            "Remote Power of FEMC3 Trap Filter ."
						::= { mc2200-FESFPEntry 66 }
mc2200-FESFPTrapFilterRemoteLAN	        OBJECT-TYPE
						SYNTAX			INTEGER {enabled(1),disabled(2)}
						MAX-ACCESS		read-write
						STATUS			current
						DESCRIPTION
                            "Remote LAN of FEMC3 Trap Filter ."
						::= { mc2200-FESFPEntry 67 }
mc2200-FESFPTrapFilterRemoteWAN	        OBJECT-TYPE
						SYNTAX			INTEGER {enabled(1),disabled(2)}
						MAX-ACCESS		read-write
						STATUS			current
						DESCRIPTION
                            "Remote WAN of FEMC3 Trap Filter ."
						::= { mc2200-FESFPEntry 68 }

mc2200-FESFPLoopback      OBJECT-TYPE
						SYNTAX			INTEGER {disable(1),local_lanouter(2),local_laninner(3),local_wanouter(4),
												local_waninner(5),remote_lanouter(6),remote_laninner(7)}
						MAX-ACCESS		read-write
						STATUS			mandatory
						DESCRIPTION
                            "FEMC3 card's loopback."
						::= { mc2200-FESFPEntry 69 }
mc2200-FESFPCardType	OBJECT-TYPE
						SYNTAX		DisplayString
						MAX-ACCESS		read-only
						STATUS			current
						DESCRIPTION
                            "FESFP card's Type."
						::= { mc2200-FESFPEntry 70 }



-- GESFP Table  ====================================================

mc2200-GESFPTable	   OBJECT-TYPE
					SYNTAX			SEQUENCE OF MC2200-GESFPEntry
					MAX-ACCESS		not-accessible
					STATUS			current
					DESCRIPTION
                   "Sparse table containing one entry for each GESFP
                     10/100Mbps Twisted-Pair to Fiber Ethernet Media Converter
                     in the system, indexed by chassisIndex and slotIndex."

					::= { mc2200-GEmib 12 }

mc2200-GESFPEntry			OBJECT-TYPE
						SYNTAX			MC2200-GESFPEntry
						MAX-ACCESS		not-accessible
						STATUS			current
						DESCRIPTION
            "One table entry per slot in the media converter chassis.
             If physical slot 'n' contains a powered GESFP media
             converter, then entry 'n' in this table exists and describes
             the state of the converter's lamps  If slot 'n' is empty, does
             not exist, or contains a different type of device, then table
             entry 'n' does not exist."

						INDEX			{ mc2200-GESFPCardIndex }
						::= { mc2200-GESFPTable 1 }






-- ==========================
-- CH-unit config info table --
-- ==========================
MC2200-GESFPEntry ::=
				SEQUENCE {
					mc2200-GESFPCardIndex			    INTEGER,	-- 1
					mc2200-GESFPLocalTXLink          	INTEGER,
					mc2200-GESFPLocalWANSFPInfo         DisplayString,
					mc2200-GESFPLocalWANLink          	INTEGER,
					mc2200-GESFPLocalTXDownStreamBW   	INTEGER,
					mc2200-GESFPLocalTXUpStreamBW     	INTEGER,
					mc2200-GESFPLocalTXMode	      	INTEGER,
					mc2200-GESFPLocalTXMDIX                INTEGER,
					mc2200-GESFPRxGoodOctets        	Counter64,

                    mc2200-GESFPRxBadOctets        		Counter64,
                    mc2200-GESFPTxFCSErr        		Counter64,
					mc2200-GESFPRxUnicast        		Counter64,
					mc2200-GESFPTxDeferred        		Counter64,
                    mc2200-GESFPRxBroadcasts        	Counter64,
                    mc2200-GESFPRxMulticasts        	Counter64,
					mc2200-GESFPRx64Octets        	Counter64,
					mc2200-GESFPRx65to127Octets        	Counter64,
                    mc2200-GESFPRx128to255Octets        Counter64, -- 20
                    mc2200-GESFPRx256to511Octets        Counter64,
                    mc2200-GESFPRx512to1023Octets       Counter64,
					mc2200-GESFPRx1024toMaxOctets       Counter64,
					mc2200-GESFPTxOctets        		Counter64,

                    mc2200-GESFPTxUnicast        		Counter64,
					mc2200-GESFPTxExcessive        		Counter64,
					mc2200-GESFPTxMulticasts            Counter64,
                    mc2200-GESFPTxBroadcasts        	Counter64,
                    mc2200-GESFPTxSingle        		Counter64, -- 30
					mc2200-GESFPTxPause        			Counter64,
					mc2200-GESFPRxPause        			Counter64,
                    mc2200-GESFPTxMultiple        		Counter64,
                    mc2200-GESFPRxUndersize        		Counter64,
					mc2200-GESFPRxFragments             Counter64,
					mc2200-GESFPRxOversize              Counter64,
                    mc2200-GESFPRxJabber        		Counter64,
                    mc2200-GESFPRxErr        		    Counter64,
					mc2200-GESFPRxFCSErr                Counter64,
					mc2200-GESFPTxCollisions            Counter64,  -- 40
                    mc2200-GESFPTxLate        		    Counter64,
					mc2200-GESFPRemoteTXLink           INTEGER,
					mc2200-GESFPRemoteWANSFPInfo        DisplayString,
					mc2200-GESFPRemoteWANLink           INTEGER,
					mc2200-GESFPRemoteTXMode	        INTEGER,
                    mc2200-GESFPRemoteTXMDIX               INTEGER,
					mc2200-GESFPRemoteIPAddress       	IpAddress,
		  	        mc2200-GESFPRemoteSubnetMask      	IpAddress,
					mc2200-GESFPRemoteGateWay         	IpAddress,
					mc2200-GESFPRemoteVLANEnable	    INTEGER, -- 50
					mc2200-GESFPRemoteVID         		INTEGER,
                    mc2200-GESFPRemoteAlarm      		INTEGER,
                    mc2200-GESFPRFD						INTEGER,
                    mc2200-GESFPDefault					INTEGER,
                    mc2200-GESFPReboot					INTEGER, -- 55
					mc2200-GESFPLocalTXSpeed                  INTEGER,
					mc2200-GESFPRemoteTXSpeed                 INTEGER,
					mc2200-GESFPLocalportuser     DisplayString,
					mc2200-GESFPRemoteportuser    DisplayString,		   -- 60
					mc2200-GESFPLocalTXDuplex	    		INTEGER,
					mc2200-GESFPRemoteTXDuplex	    		INTEGER,
					mc2200-GESFPFlowControl			INTEGER,
					mc2200-GESFPWANOpticalPowerCheck			INTEGER,
					mc2200-GESFPWANThreshold			INTEGER,
					mc2200-GESFPTrapFilterLocalLAN			INTEGER,
					mc2200-GESFPTrapFilterLocalWAN			INTEGER,
					mc2200-GESFPTrapFilterRemotePower		INTEGER,
					mc2200-GESFPTrapFilterRemoteLAN		INTEGER,
					mc2200-GESFPTrapFilterRemoteWAN		INTEGER,
					mc2200-GESFPLoopback		INTEGER,
					mc2200-GESFPCardType		DisplayString
				}


mc2200-GESFPCardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GESFPEntry 1 }
mc2200-GESFPLocalTXLink      OBJECT-TYPE
						SYNTAX			INTEGER {up(1),
						                         down(2)}
						MAX-ACCESS		read-only
						STATUS			mandatory
						DESCRIPTION
                            "GESFP Local card's LAN port work link status."
						::= { mc2200-GESFPEntry 2 }
mc2200-GESFPLocalWANSFPInfo	OBJECT-TYPE
						SYNTAX		DisplayString
						MAX-ACCESS		read-only
						STATUS			current
						DESCRIPTION
                            "GESFP Local card's WAN port SFP infomation."
						::= { mc2200-GESFPEntry 3 }
mc2200-GESFPLocalWANLink	        OBJECT-TYPE
						SYNTAX			INTEGER {up(1),
						                         down(2)}
						MAX-ACCESS		read-only
						STATUS			current
						DESCRIPTION
                            "GESFP Local card's WAN port work link status."
						::= { mc2200-GESFPEntry 4 }

mc2200-GESFPLocalTXDownStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                            "GESFP Local card's LAN port DownStream BandWidth. "
						::= { mc2200-GESFPEntry 5 }
mc2200-GESFPLocalTXUpStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        " GESFP Local card's LAN port UpStream BandWidth."
						::= { mc2200-GESFPEntry 6 }
mc2200-GESFPLocalTXMode   	OBJECT-TYPE
						SYNTAX		INTEGER {auto-10-100-1000(1),
                          					mode1000F(2),
                          					mode100F(3),
                          					mode10F(4),
                          					mode100H(5),
                          					mode10H(6)}
						MAX-ACCESS		read-write
						STATUS			current
						DESCRIPTION
                        "GESFP Local card's LAN port Mode configuration,
                    	set INTEGER(1) to auto(10/100/1000),
                    	set INTEGER(2) to 1000F,
                    	set INTEGER(3) to 100F,
                    	set INTEGER(4) to 10F,
                    	set INTEGER(5) to 100H,
                    	set INTEGER(6) to 10H,
                    	Ohter value is invalid"
						::= { mc2200-GESFPEntry  7 }
mc2200-GESFPLocalTXMDIX   	OBJECT-TYPE
						SYNTAX		INTEGER {auto(1),
                          					mdi(2),
                          					mdix(3)}
						MAX-ACCESS		read-write
						STATUS			current
						DESCRIPTION
                        "GESFP Local card's LAN port Mode configuration,
                    	set INTEGER(1) to auto,
                    	set INTEGER(2) to MDI,
                    	set INTEGER(3) to MDIX,
                    	Ohter value is invalid"
						::= { mc2200-GESFPEntry  8 }

mc2200-GESFPRxGoodOctets OBJECT-TYPE
						SYNTAX			Counter64
						MAX-ACCESS		read-only
						STATUS			current
						DESCRIPTION
                        "GESFP Local card's LAN port MIB RxGoodOctetsLow counter."
						::= { mc2200-GESFPEntry 9 }

mc2200-GESFPRxBadOctets OBJECT-TYPE
						SYNTAX			Counter64
						MAX-ACCESS		read-only
						STATUS			current
						DESCRIPTION
                        "GESFP Local card's LAN port MIB RxBadOctets counter."
						::= { mc2200-GESFPEntry 11 }
mc2200-GESFPTxFCSErr OBJECT-TYPE
						SYNTAX			Counter64
						MAX-ACCESS		read-only
						STATUS			current
						DESCRIPTION
                        "GESFP Local card's LAN port MIB  TxFCSErr counter."
						::= { mc2200-GESFPEntry 12 }

mc2200-GESFPRxUnicast OBJECT-TYPE
						SYNTAX			Counter64
						MAX-ACCESS		read-only
						STATUS			current
						DESCRIPTION
                        "GESFP Local card's LAN port MIB RxUnicast counter."
						::= { mc2200-GESFPEntry 13 }
mc2200-GESFPTxDeferred OBJECT-TYPE
						SYNTAX			Counter64
						MAX-ACCESS		read-only
						STATUS			current
						DESCRIPTION
                        "GESFP Local card's LAN port MIB TxDeferred counter."
						::= { mc2200-GESFPEntry 14 }
mc2200-GESFPRxBroadcasts OBJECT-TYPE
						SYNTAX			Counter64
						MAX-ACCESS		read-only
						STATUS			current
						DESCRIPTION
                        "GESFP Local card's LAN port MIB RxBroadcasts counter."
						::= { mc2200-GESFPEntry 15 }
mc2200-GESFPRxMulticasts OBJECT-TYPE
						SYNTAX			Counter64
						MAX-ACCESS		read-only
						STATUS			current
						DESCRIPTION
                        "GESFP Local card's LAN port MIB RxMulticasts counter."
						::= { mc2200-GESFPEntry 16 }
mc2200-GESFPRx64Octets OBJECT-TYPE
						SYNTAX			Counter64
						MAX-ACCESS		read-only
						STATUS			current
						DESCRIPTION
                        "GESFP Local card's LAN port MIB Rx64Octets counter."
						::= { mc2200-GESFPEntry 17 }
mc2200-GESFPRx65to127Octets OBJECT-TYPE
						SYNTAX			Counter64
						MAX-ACCESS		read-only
						STATUS			current
						DESCRIPTION
                        "GESFP Local card's LAN port MIB Rx65to127Octets counter."
						::= { mc2200-GESFPEntry 18 }
mc2200-GESFPRx128to255Octets OBJECT-TYPE
						SYNTAX			Counter64
						MAX-ACCESS		read-only
						STATUS			current
						DESCRIPTION
                        "GESFP Local card's LAN port MIB Rx128to255Octets counter."
						::= { mc2200-GESFPEntry 19 }
mc2200-GESFPRx256to511Octets OBJECT-TYPE
						SYNTAX			Counter64
						MAX-ACCESS		read-only
						STATUS			current
						DESCRIPTION
                        "GESFP Local card's LAN port MIB Rx256to511Octets counter."
						::= { mc2200-GESFPEntry 20 }
mc2200-GESFPRx512to1023Octets OBJECT-TYPE
						SYNTAX			Counter64
						MAX-ACCESS		read-only
						STATUS			current
						DESCRIPTION
                        "GESFP Local card's LAN port MIB Rx512to1023Octets counter."
						::= { mc2200-GESFPEntry 21 }
mc2200-GESFPRx1024toMaxOctets OBJECT-TYPE
						SYNTAX			Counter64
						MAX-ACCESS		read-only
						STATUS			current
						DESCRIPTION
                        "GESFP Local card's LAN port MIB Rx1024toMaxOctets counter."
						::= { mc2200-GESFPEntry 22 }
mc2200-GESFPTxOctets OBJECT-TYPE
						SYNTAX			Counter64
						MAX-ACCESS		read-only
						STATUS			current
						DESCRIPTION
                        "GESFP Local card's LAN port MIB TxOctetsLow counter."
						::= { mc2200-GESFPEntry 23 }

mc2200-GESFPTxUnicast OBJECT-TYPE
						SYNTAX			Counter64
						MAX-ACCESS		read-only
						STATUS			current
						DESCRIPTION
                        "GESFP Local card's LAN port MIB TxUnicast counter."
						::= { mc2200-GESFPEntry 25 }
mc2200-GESFPTxExcessive OBJECT-TYPE
						SYNTAX			Counter64
						MAX-ACCESS		read-only
						STATUS			current
						DESCRIPTION
                        "GESFP Local card's LAN port MIB TxExcessive counter."
						::= { mc2200-GESFPEntry 26 }
mc2200-GESFPTxMulticasts OBJECT-TYPE
						SYNTAX			Counter64
						MAX-ACCESS		read-only
						STATUS			current
						DESCRIPTION
                        "GESFP Local card's LAN port MIB TxMulticasts counter."
						::= { mc2200-GESFPEntry 27 }
mc2200-GESFPTxBroadcasts OBJECT-TYPE
						SYNTAX			Counter64
						MAX-ACCESS		read-only
						STATUS			current
						DESCRIPTION
                        "GESFP Local card's LAN port MIB TxBroadcasts counter."
						::= { mc2200-GESFPEntry 28 }
mc2200-GESFPTxSingle OBJECT-TYPE
						SYNTAX			Counter64
						MAX-ACCESS		read-only
						STATUS			current
						DESCRIPTION
                        "GESFP Local card's LAN port MIB TxSingle counter."
						::= { mc2200-GESFPEntry 29 }
mc2200-GESFPTxPause OBJECT-TYPE
						SYNTAX			Counter64
						MAX-ACCESS		read-only
						STATUS			current
						DESCRIPTION
                        "GESFP Local card's LAN port MIB TxPause counter."
						::= { mc2200-GESFPEntry 30 }
mc2200-GESFPRxPause OBJECT-TYPE
						SYNTAX			Counter64
						MAX-ACCESS		read-only
						STATUS			current
						DESCRIPTION
                        "GESFP Local card's LAN port MIB RxPause counter."
						::= { mc2200-GESFPEntry 31 }
mc2200-GESFPTxMultiple OBJECT-TYPE
						SYNTAX			Counter64
						MAX-ACCESS		read-only
						STATUS			current
						DESCRIPTION
                        "GESFP Local card's LAN port MIB TxMultiple counter."
						::= { mc2200-GESFPEntry 32 }
mc2200-GESFPRxUndersize OBJECT-TYPE
						SYNTAX			Counter64
						MAX-ACCESS		read-only
						STATUS			current
						DESCRIPTION
                        "GESFP Local card's LAN port MIB RxUndersize counter."
						::= { mc2200-GESFPEntry 33 }
mc2200-GESFPRxFragments OBJECT-TYPE
						SYNTAX			Counter64
						MAX-ACCESS		read-only
						STATUS			current
						DESCRIPTION
                        "GESFP Local card's LAN port MIB RxFragments counter."
						::= { mc2200-GESFPEntry 34 }
mc2200-GESFPRxOversize OBJECT-TYPE
						SYNTAX			Counter64
						MAX-ACCESS		read-only
						STATUS			current
						DESCRIPTION
                        "GESFP Local card's LAN port MIB RxOversize counter."
						::= { mc2200-GESFPEntry 35 }
mc2200-GESFPRxJabber OBJECT-TYPE
						SYNTAX			Counter64
						MAX-ACCESS		read-only
						STATUS			current
						DESCRIPTION
                        "GESFP Local card's LAN port MIB RxJabber counter."
						::= { mc2200-GESFPEntry 36 }
mc2200-GESFPRxErr OBJECT-TYPE
						SYNTAX			Counter64
						MAX-ACCESS		read-only
						STATUS			current
						DESCRIPTION
                        "GESFP Local card's LAN port MIB RxErr counter."
						::= { mc2200-GESFPEntry 37 }
mc2200-GESFPRxFCSErr OBJECT-TYPE
						SYNTAX			Counter64
						MAX-ACCESS		read-only
						STATUS			current
						DESCRIPTION
                        "GESFP Local card's LAN port MIB RxFCSErr counter."
						::= { mc2200-GESFPEntry 38 }
mc2200-GESFPTxCollisions OBJECT-TYPE
						SYNTAX			Counter64
						MAX-ACCESS		read-only
						STATUS			current
						DESCRIPTION
                        "GESFP Local card's LAN port MIB TxCollisions counter."
						::= { mc2200-GESFPEntry 39 }
mc2200-GESFPTxLate OBJECT-TYPE
						SYNTAX			Counter64
						MAX-ACCESS		read-only
						STATUS			current
						DESCRIPTION
                        "GESFP Local card's port8 MIB TxLate counter."
						::= { mc2200-GESFPEntry 40 }
mc2200-GESFPRemoteTXLink      OBJECT-TYPE
						SYNTAX			INTEGER {up(1),
						                         down(2), noremotecard(0)}
						MAX-ACCESS		read-only
						STATUS			mandatory
						DESCRIPTION
                            "GESFP Remote card's LAN port work link status."
						::= { mc2200-GESFPEntry 41 }
mc2200-GESFPRemoteWANSFPInfo	OBJECT-TYPE
						SYNTAX		DisplayString
						MAX-ACCESS		read-only
						STATUS			current
						DESCRIPTION
                            "GESFP Remote card's WAN port SFP infomation."
						::= { mc2200-GESFPEntry 42 }
mc2200-GESFPRemoteWANLink	        OBJECT-TYPE
						SYNTAX			INTEGER {up(1),
						                         down(2), noremotecard(0)}
						MAX-ACCESS		read-only
						STATUS			current
						DESCRIPTION
                            "GESFP Remote card's WAN port work link status."
						::= { mc2200-GESFPEntry 43 }


mc2200-GESFPRemoteTXMode   	OBJECT-TYPE
						SYNTAX		INTEGER {auto-10-100-1000(1),
                          					mode1000F(2),
                          					mode100F(3),
                          					mode10F(4),
                          					mode100H(5),
                          					mode10H(6),noremotecard(0)}
						MAX-ACCESS		read-write
						STATUS			current
						DESCRIPTION
                        "GESFP Remote card's LAN port Mode configuration,
                    	set INTEGER(1) to auto(10/100/1000),
                    	set INTEGER(2) to 1000F,
                    	set INTEGER(3) to 100F,
                    	set INTEGER(4) to 10F,
                    	set INTEGER(5) to 100H,
                    	set INTEGER(6) to 10H,
                    	Ohter value is invalid"
						::= { mc2200-GESFPEntry  44 }

mc2200-GESFPRemoteTXMDIX   	OBJECT-TYPE
						SYNTAX		INTEGER {auto(1),
                          					mdi(2),
                          					mdix(3),noremotecard(0)}
						MAX-ACCESS		read-write
						STATUS			current
						DESCRIPTION
                        "GESFP Remote card's LAN port Mode configuration,
                    	set INTEGER(1) to auto,
                    	set INTEGER(2) to MDI,
                    	set INTEGER(3) to MDIX,
                    	Ohter value is invalid"
						::= { mc2200-GESFPEntry  45 }
mc2200-GESFPRemoteIPAddress  OBJECT-TYPE
        			SYNTAX      IpAddress
        			ACCESS      read-write
        			STATUS      mandatory
	    			DESCRIPTION
            		"The IP address to GESFP Remote IP ping."
        			::= {mc2200-GESFPEntry 46}

mc2200-GESFPRemoteSubnetMask    OBJECT-TYPE
        			SYNTAX      IpAddress
        			ACCESS      read-write
        			STATUS      mandatory
	    			DESCRIPTION
                    "The Net mask to  GESFP Remote IP ping."
        			::= {mc2200-GESFPEntry 47}

mc2200-GESFPRemoteGateWay    OBJECT-TYPE
        			SYNTAX      IpAddress
        			ACCESS      read-write
        			STATUS      mandatory
	   				 DESCRIPTION
                    "The gateware to GESFP Remote IP ping."
        			::= {mc2200-GESFPEntry 48}

mc2200-GESFPRemoteVLANEnable  OBJECT-TYPE
        			SYNTAX      INTEGER {enable(1),disable(2), noremotecard(0)}
        			ACCESS      read-write
        			STATUS      mandatory
	    			DESCRIPTION
                    "Enable or disable Remote GESFP IP ping 802.1Q VLAN."
        			::= {mc2200-GESFPEntry 49}
mc2200-GESFPRemoteVID  OBJECT-TYPE
        			SYNTAX      INTEGER
        			ACCESS      read-write
        			STATUS      mandatory
	    			DESCRIPTION
                    "GESFP Remote IP ping  802.1Q VLAN ID."
        			::= {mc2200-GESFPEntry 50}
mc2200-GESFPRemoteAlarm      OBJECT-TYPE
						SYNTAX			INTEGER  {enabled(1),disabled(2)}
						MAX-ACCESS		read-write
						STATUS			current
						DESCRIPTION
                        "Enable or disable GESFP Media converter card remote alarm.
                         set INTEGER(1) to Enable remote alarm,
                         set INTEGER(2) to Disable remote alarm,
                         Other value is invalid."
						::= { mc2200-GESFPEntry 51 }
mc2200-GESFPRFD		      OBJECT-TYPE
						SYNTAX			INTEGER  {enabled(1),disabled(2)}
						MAX-ACCESS		read-write
						STATUS			current
						DESCRIPTION
                        "GESFP Media converter card remote fault detect operation.
                         set INTEGER(1) to Enable RFD,
                         set INTEGER(2) to Disable RFD,
                         Other value is invalid."
						::= { mc2200-GESFPEntry 52 }
mc2200-GESFPDefault		OBJECT-TYPE
						SYNTAX			INTEGER
						MAX-ACCESS		write-only
						STATUS			current
						DESCRIPTION
                        "Write GESFP card default setting,
                        set INTEGER(1) to write default.
                        Other value is invalid."
						::= { mc2200-GESFPEntry 53 }
mc2200-GESFPReboot		OBJECT-TYPE
						SYNTAX			INTEGER
						MAX-ACCESS		write-only
						STATUS			current
						DESCRIPTION
                        "Reboot GESFP local card,
                        set INTEGER(1) to reboot this card.
                        Other value is invalid. "
						::= { mc2200-GESFPEntry 54 }
mc2200-GESFPLocalTXSpeed      OBJECT-TYPE
						SYNTAX			INTEGER {speed1000M(1),
						                         speed100M(2),speed10M(3),down(4)}
						MAX-ACCESS		read-only
						STATUS			mandatory
						DESCRIPTION
                        "GESFP Local card's LAN port work speed status."
						::= { mc2200-GESFPEntry 55 }
mc2200-GESFPRemoteTXSpeed      OBJECT-TYPE
						SYNTAX			INTEGER {speed1000M(1),speed100M(2),
						                         speed10M(3),down(4),noremotecard(0)}
						MAX-ACCESS		read-only
						STATUS			mandatory
						DESCRIPTION
                        "GESFP Remote card's LAN port work speed status."
						::= { mc2200-GESFPEntry 56 }

mc2200-GESFPLocalportuser      OBJECT-TYPE
						SYNTAX			DisplayString
						MAX-ACCESS		read-write
						STATUS			current
						DESCRIPTION
                        " User of GESFP Local Port1. "
						::= { mc2200-GESFPEntry 57 }

mc2200-GESFPRemoteportuser      OBJECT-TYPE
						SYNTAX			DisplayString
						MAX-ACCESS		read-write
						STATUS			current
						DESCRIPTION
                        " User of GESFP Remote Port1. "
						::= { mc2200-GESFPEntry 58 }

mc2200-GESFPLocalTXDuplex      OBJECT-TYPE
						SYNTAX			INTEGER {fullDuplex(1),
						                         halfDuplex(2),down(3)}
						MAX-ACCESS		read-only
						STATUS			mandatory
						DESCRIPTION
                        "GESFP Local card's TX port work duplex status."
						::= { mc2200-GESFPEntry 59 }
mc2200-GESFPRemoteTXDuplex      OBJECT-TYPE
						SYNTAX			INTEGER {fullDuplex(1),
						                         halfDuplex(2),down(3),noremotecard(0)}
						MAX-ACCESS		read-only
						STATUS			mandatory
						DESCRIPTION
                        "GESFP Remote card's TX port work duplex status."
						::= { mc2200-GESFPEntry 60 }
mc2200-GESFPFlowControl        OBJECT-TYPE
						SYNTAX			INTEGER  {enabled(1),disabled(2)}
						MAX-ACCESS		read-write
						STATUS			current
						DESCRIPTION
                        "GESFP Media converter card flow control operation.
                         set INTEGER(1) to Enable Flow Control,
                         set INTEGER(2) to Disable Flow Control,
                         Other value is invalid."
						::= { mc2200-GESFPEntry 61 }
mc2200-GESFPWANOpticalPowerCheck        OBJECT-TYPE
						SYNTAX			INTEGER  {enabled(1),disabled(2)}
						MAX-ACCESS		read-write
						STATUS			current
						DESCRIPTION
                        "GESFP Media converter card WANOpticalPowerCheck operation.
                         set INTEGER(1) to Enable WANOpticalPowerCheck,
                         set INTEGER(2) to Disable WANOpticalPowerCheck,
                         Other value is invalid."
						::= { mc2200-GESFPEntry 62 }
mc2200-GESFPWANThreshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GESFP Media converter card WANThreshold operation.
                         Other value is invalid."
						::= { mc2200-GESFPEntry 63 }
mc2200-GESFPTrapFilterLocalLAN	        OBJECT-TYPE
						SYNTAX			INTEGER {enabled(1),disabled(2)}
						MAX-ACCESS		read-write
						STATUS			current
						DESCRIPTION
                            "Local LAN of GESFP Trap Filter ."
						::= { mc2200-GESFPEntry 64 }
mc2200-GESFPTrapFilterLocalWAN	        OBJECT-TYPE
						SYNTAX			INTEGER {enabled(1),disabled(2)}
						MAX-ACCESS		read-write
						STATUS			current
						DESCRIPTION
                            "Local WAN of GESFP Trap Filter ."
						::= { mc2200-GESFPEntry 65 }
mc2200-GESFPTrapFilterRemotePower	        OBJECT-TYPE
						SYNTAX			INTEGER {enabled(1),disabled(2)}
						MAX-ACCESS		read-write
						STATUS			current
						DESCRIPTION
                            "Remote Power of GESFP Trap Filter ."
						::= { mc2200-GESFPEntry 66 }
mc2200-GESFPTrapFilterRemoteLAN	        OBJECT-TYPE
						SYNTAX			INTEGER {enabled(1),disabled(2)}
						MAX-ACCESS		read-write
						STATUS			current
						DESCRIPTION
                            "Remote LAN of GESFP Trap Filter ."
						::= { mc2200-GESFPEntry 67 }
mc2200-GESFPTrapFilterRemoteWAN	        OBJECT-TYPE
						SYNTAX			INTEGER {enabled(1),disabled(2)}
						MAX-ACCESS		read-write
						STATUS			current
						DESCRIPTION
                            "Remote WAN of GESFP Trap Filter ."
						::= { mc2200-GESFPEntry 68 }

mc2200-GESFPLoopback      OBJECT-TYPE
						SYNTAX			INTEGER {disable(1),local_lanouter(2),local_laninner(3),local_wanouter(4),
												local_waninner(5),remote_lanouter(6),remote_laninner(7)}
						MAX-ACCESS		read-write
						STATUS			mandatory
						DESCRIPTION
                            "GESFP card's loopback."
						::= { mc2200-GESFPEntry 69 }
mc2200-GESFPCardType	OBJECT-TYPE
						SYNTAX		DisplayString
						MAX-ACCESS		read-only
						STATUS			current
						DESCRIPTION
                            "GESFP card's Type."
						::= { mc2200-GESFPEntry 70 }


-- GEMC3 Table  ====================================================

mc2200-GEMC3Table	   OBJECT-TYPE
					SYNTAX			SEQUENCE OF MC2200-GEMC3Entry
					MAX-ACCESS		not-accessible
					STATUS			current
					DESCRIPTION
                   "Sparse table containing one entry for each GEMC3
                     10/100Mbps Twisted-Pair to Fiber Ethernet Media Converter
                     in the system, indexed by chassisIndex and slotIndex."

					::= { mc2200-GEmib 13 }

mc2200-GEMC3Entry			OBJECT-TYPE
						SYNTAX			MC2200-GEMC3Entry
						MAX-ACCESS		not-accessible
						STATUS			current
						DESCRIPTION
            "One table entry per slot in the media converter chassis.
             If physical slot 'n' contains a powered GEMC3 media
             converter, then entry 'n' in this table exists and describes
             the state of the converter's lamps  If slot 'n' is empty, does
             not exist, or contains a different type of device, then table
             entry 'n' does not exist."

						INDEX			{ mc2200-GEMC3CardIndex }
						::= { mc2200-GEMC3Table 1 }






-- ==========================
-- CH-unit config info table --
-- ==========================
MC2200-GEMC3Entry ::=
				SEQUENCE {
					mc2200-GEMC3CardIndex			    INTEGER,	-- 1
					mc2200-GEMC3LocalLANSFPInfo         DisplayString,
					mc2200-GEMC3LocalLANLink          	INTEGER,
					mc2200-GEMC3LocalWANSFPInfo         DisplayString,
					mc2200-GEMC3LocalWANLink          	INTEGER,
					mc2200-GEMC3LocalLANDownStreamBW   	INTEGER,
					mc2200-GEMC3LocalLANUpStreamBW     	INTEGER,
					mc2200-GEMC3LocalLANMode	      	INTEGER,
					mc2200-GEMC3RxGoodOctets        	Counter64,

                    mc2200-GEMC3RxBadOctets        		Counter64,
                    mc2200-GEMC3TxFCSErr        		Counter64,
					mc2200-GEMC3RxUnicast        		Counter64,
					mc2200-GEMC3TxDeferred        		Counter64,
                    mc2200-GEMC3RxBroadcasts        	Counter64,
                    mc2200-GEMC3RxMulticasts        	Counter64,
					mc2200-GEMC3Rx64Octets        	Counter64,
					mc2200-GEMC3Rx65to127Octets        	Counter64,
                    mc2200-GEMC3Rx128to255Octets        Counter64, -- 20
                    mc2200-GEMC3Rx256to511Octets        Counter64,
                    mc2200-GEMC3Rx512to1023Octets       Counter64,
					mc2200-GEMC3Rx1024toMaxOctets       Counter64,
					mc2200-GEMC3TxOctets        		Counter64,

                    mc2200-GEMC3TxUnicast        		Counter64,
					mc2200-GEMC3TxExcessive        		Counter64,
					mc2200-GEMC3TxMulticasts            Counter64,
                    mc2200-GEMC3TxBroadcasts        	Counter64,
                    mc2200-GEMC3TxSingle        		Counter64, -- 30
					mc2200-GEMC3TxPause        			Counter64,
					mc2200-GEMC3RxPause        			Counter64,
                    mc2200-GEMC3TxMultiple        		Counter64,
                    mc2200-GEMC3RxUndersize        		Counter64,
					mc2200-GEMC3RxFragments             Counter64,
					mc2200-GEMC3RxOversize              Counter64,
                    mc2200-GEMC3RxJabber        		Counter64,
                    mc2200-GEMC3RxErr        		    Counter64,
					mc2200-GEMC3RxFCSErr                Counter64,
					mc2200-GEMC3TxCollisions            Counter64,  -- 40
                    mc2200-GEMC3TxLate        		    Counter64,
                    mc2200-GEMC3RemoteLANSFPInfo        DisplayString,
					mc2200-GEMC3RemoteLANLink           INTEGER,
					mc2200-GEMC3RemoteWANSFPInfo        DisplayString,
					mc2200-GEMC3RemoteWANLink           INTEGER,
					mc2200-GEMC3RemoteLANMode	        INTEGER,
					mc2200-GEMC3RemoteIPAddress       	IpAddress,
		  	        mc2200-GEMC3RemoteSubnetMask      	IpAddress,
					mc2200-GEMC3RemoteGateWay         	IpAddress,
					mc2200-GEMC3RemoteVLANEnable	    INTEGER, -- 50
					mc2200-GEMC3RemoteVID         		INTEGER,
                    mc2200-GEMC3RemoteAlarm      		INTEGER,
                    mc2200-GEMC3RFD						INTEGER,
                    mc2200-GEMC3Default					INTEGER,
                    mc2200-GEMC3Reboot					INTEGER, -- 55
					mc2200-GEMC3LocalLANSpeed                  INTEGER,
					mc2200-GEMC3RemoteLANSpeed                 INTEGER,
					mc2200-GEMC3Localportuser     DisplayString,
					mc2200-GEMC3Remoteportuser    DisplayString,
					mc2200-GEMC3WANOpticalPowerCheck			INTEGER,
					mc2200-GEMC3WANThreshold			INTEGER,
					mc2200-GEMC3TrapFilterLocalLAN			INTEGER,
					mc2200-GEMC3TrapFilterLocalWAN			INTEGER,
					mc2200-GEMC3TrapFilterRemotePower		INTEGER,
					mc2200-GEMC3TrapFilterRemoteLAN		INTEGER,
					mc2200-GEMC3TrapFilterRemoteWAN		INTEGER,
					mc2200-GEMC3Loopback		INTEGER,
					mc2200-GEMC3CardType		DisplayString
				}


mc2200-GEMC3CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GEMC3Entry 1 }
mc2200-GEMC3LocalLANSFPInfo	OBJECT-TYPE
						SYNTAX		DisplayString
						MAX-ACCESS		read-only
						STATUS			current
						DESCRIPTION
                            "GEMC3 Local card's LAN port SFP infomation."
						::= { mc2200-GEMC3Entry 2 }
mc2200-GEMC3LocalLANLink      OBJECT-TYPE
						SYNTAX			INTEGER {up(1),
						                         down(2)}
						MAX-ACCESS		read-only
						STATUS			mandatory
						DESCRIPTION
                            "GEMC3 Local card's LAN port work link status."
						::= { mc2200-GEMC3Entry 3 }
mc2200-GEMC3LocalWANSFPInfo	OBJECT-TYPE
						SYNTAX		DisplayString
						MAX-ACCESS		read-only
						STATUS			current
						DESCRIPTION
                            "GEMC3 Local card's WAN port SFP infomation."
						::= { mc2200-GEMC3Entry 4 }
mc2200-GEMC3LocalWANLink	        OBJECT-TYPE
						SYNTAX			INTEGER {up(1),
						                         down(2)}
						MAX-ACCESS		read-only
						STATUS			current
						DESCRIPTION
                            "GEMC3 Local card's WAN port work link status."
						::= { mc2200-GEMC3Entry 5 }

mc2200-GEMC3LocalLANDownStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                            "GEMC3 Local card's LAN port DownStream BandWidth. "
						::= { mc2200-GEMC3Entry 6 }
mc2200-GEMC3LocalLANUpStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        " GEMC3 Local card's LAN port UpStream BandWidth."
						::= { mc2200-GEMC3Entry 7 }
mc2200-GEMC3LocalLANMode   	OBJECT-TYPE
						SYNTAX		INTEGER {mode1000Base-X-auto(1),
                          					mode1000Base-X-Force(2),
                          					auto-10-100-1000T(3),
                          					mode1000Base-T-full(4),
                          					mode100Base-T-full(5),
                          					mode100Base-T-Half(6),
                          					mode10Base-T-full(7),
                          					mode10Base-T-Half(8)}
						MAX-ACCESS		read-write
						STATUS			current
						DESCRIPTION
                        "GEMC3 Local card's LAN port Mode configuration,
                    	set INTEGER(1) to 1000Base-X-auto,
                    	set INTEGER(2) to 1000Base-X-Force,
                    	set INTEGER(3) to auto-10-100-1000T,
                    	set INTEGER(4) to 1000Base-T-full,
                    	set INTEGER(5) to 100Base-T-full,
                    	set INTEGER(6) to 100Base-T-Half,
                    	set INTEGER(7) to 10Base-T-full,
                    	set INTEGER(8) to 10Base-T-Half,
                    	Ohter value is invalid"
						::= { mc2200-GEMC3Entry  8 }

mc2200-GEMC3RxGoodOctets OBJECT-TYPE
						SYNTAX			Counter64
						MAX-ACCESS		read-only
						STATUS			current
						DESCRIPTION
                        "GEMC3 Local card's LAN port MIB RxGoodOctetsLow counter."
						::= { mc2200-GEMC3Entry 9 }

mc2200-GEMC3RxBadOctets OBJECT-TYPE
						SYNTAX			Counter64
						MAX-ACCESS		read-only
						STATUS			current
						DESCRIPTION
                        "GEMC3 Local card's LAN port MIB RxBadOctets counter."
						::= { mc2200-GEMC3Entry 11 }
mc2200-GEMC3TxFCSErr OBJECT-TYPE
						SYNTAX			Counter64
						MAX-ACCESS		read-only
						STATUS			current
						DESCRIPTION
                        "GEMC3 Local card's LAN port MIB  TxFCSErr counter."
						::= { mc2200-GEMC3Entry 12 }

mc2200-GEMC3RxUnicast OBJECT-TYPE
						SYNTAX			Counter64
						MAX-ACCESS		read-only
						STATUS			current
						DESCRIPTION
                        "GEMC3 Local card's LAN port MIB RxUnicast counter."
						::= { mc2200-GEMC3Entry 13 }
mc2200-GEMC3TxDeferred OBJECT-TYPE
						SYNTAX			Counter64
						MAX-ACCESS		read-only
						STATUS			current
						DESCRIPTION
                        "GEMC3 Local card's LAN port MIB TxDeferred counter."
						::= { mc2200-GEMC3Entry 14 }
mc2200-GEMC3RxBroadcasts OBJECT-TYPE
						SYNTAX			Counter64
						MAX-ACCESS		read-only
						STATUS			current
						DESCRIPTION
                        "GEMC3 Local card's LAN port MIB RxBroadcasts counter."
						::= { mc2200-GEMC3Entry 15 }
mc2200-GEMC3RxMulticasts OBJECT-TYPE
						SYNTAX			Counter64
						MAX-ACCESS		read-only
						STATUS			current
						DESCRIPTION
                        "GEMC3 Local card's LAN port MIB RxMulticasts counter."
						::= { mc2200-GEMC3Entry 16 }
mc2200-GEMC3Rx64Octets OBJECT-TYPE
						SYNTAX			Counter64
						MAX-ACCESS		read-only
						STATUS			current
						DESCRIPTION
                        "GEMC3 Local card's LAN port MIB Rx64Octets counter."
						::= { mc2200-GEMC3Entry 17 }
mc2200-GEMC3Rx65to127Octets OBJECT-TYPE
						SYNTAX			Counter64
						MAX-ACCESS		read-only
						STATUS			current
						DESCRIPTION
                        "GEMC3 Local card's LAN port MIB Rx65to127Octets counter."
						::= { mc2200-GEMC3Entry 18 }
mc2200-GEMC3Rx128to255Octets OBJECT-TYPE
						SYNTAX			Counter64
						MAX-ACCESS		read-only
						STATUS			current
						DESCRIPTION
                        "GEMC3 Local card's LAN port MIB Rx128to255Octets counter."
						::= { mc2200-GEMC3Entry 19 }
mc2200-GEMC3Rx256to511Octets OBJECT-TYPE
						SYNTAX			Counter64
						MAX-ACCESS		read-only
						STATUS			current
						DESCRIPTION
                        "GEMC3 Local card's LAN port MIB Rx256to511Octets counter."
						::= { mc2200-GEMC3Entry 20 }
mc2200-GEMC3Rx512to1023Octets OBJECT-TYPE
						SYNTAX			Counter64
						MAX-ACCESS		read-only
						STATUS			current
						DESCRIPTION
                        "GEMC3 Local card's LAN port MIB Rx512to1023Octets counter."
						::= { mc2200-GEMC3Entry 21 }
mc2200-GEMC3Rx1024toMaxOctets OBJECT-TYPE
						SYNTAX			Counter64
						MAX-ACCESS		read-only
						STATUS			current
						DESCRIPTION
                        "GEMC3 Local card's LAN port MIB Rx1024toMaxOctets counter."
						::= { mc2200-GEMC3Entry 22 }
mc2200-GEMC3TxOctets OBJECT-TYPE
						SYNTAX			Counter64
						MAX-ACCESS		read-only
						STATUS			current
						DESCRIPTION
                        "GEMC3 Local card's LAN port MIB TxOctetsLow counter."
						::= { mc2200-GEMC3Entry 23 }

mc2200-GEMC3TxUnicast OBJECT-TYPE
						SYNTAX			Counter64
						MAX-ACCESS		read-only
						STATUS			current
						DESCRIPTION
                        "GEMC3 Local card's LAN port MIB TxUnicast counter."
						::= { mc2200-GEMC3Entry 25 }
mc2200-GEMC3TxExcessive OBJECT-TYPE
						SYNTAX			Counter64
						MAX-ACCESS		read-only
						STATUS			current
						DESCRIPTION
                        "GEMC3 Local card's LAN port MIB TxExcessive counter."
						::= { mc2200-GEMC3Entry 26 }
mc2200-GEMC3TxMulticasts OBJECT-TYPE
						SYNTAX			Counter64
						MAX-ACCESS		read-only
						STATUS			current
						DESCRIPTION
                        "GEMC3 Local card's LAN port MIB TxMulticasts counter."
						::= { mc2200-GEMC3Entry 27 }
mc2200-GEMC3TxBroadcasts OBJECT-TYPE
						SYNTAX			Counter64
						MAX-ACCESS		read-only
						STATUS			current
						DESCRIPTION
                        "GEMC3 Local card's LAN port MIB TxBroadcasts counter."
						::= { mc2200-GEMC3Entry 28 }
mc2200-GEMC3TxSingle OBJECT-TYPE
						SYNTAX			Counter64
						MAX-ACCESS		read-only
						STATUS			current
						DESCRIPTION
                        "GEMC3 Local card's LAN port MIB TxSingle counter."
						::= { mc2200-GEMC3Entry 29 }
mc2200-GEMC3TxPause OBJECT-TYPE
						SYNTAX			Counter64
						MAX-ACCESS		read-only
						STATUS			current
						DESCRIPTION
                        "GEMC3 Local card's LAN port MIB TxPause counter."
						::= { mc2200-GEMC3Entry 30 }
mc2200-GEMC3RxPause OBJECT-TYPE
						SYNTAX			Counter64
						MAX-ACCESS		read-only
						STATUS			current
						DESCRIPTION
                        "GEMC3 Local card's LAN port MIB RxPause counter."
						::= { mc2200-GEMC3Entry 31 }
mc2200-GEMC3TxMultiple OBJECT-TYPE
						SYNTAX			Counter64
						MAX-ACCESS		read-only
						STATUS			current
						DESCRIPTION
                        "GEMC3 Local card's LAN port MIB TxMultiple counter."
						::= { mc2200-GEMC3Entry 32 }
mc2200-GEMC3RxUndersize OBJECT-TYPE
						SYNTAX			Counter64
						MAX-ACCESS		read-only
						STATUS			current
						DESCRIPTION
                        "GEMC3 Local card's LAN port MIB RxUndersize counter."
						::= { mc2200-GEMC3Entry 33 }
mc2200-GEMC3RxFragments OBJECT-TYPE
						SYNTAX			Counter64
						MAX-ACCESS		read-only
						STATUS			current
						DESCRIPTION
                        "GEMC3 Local card's LAN port MIB RxFragments counter."
						::= { mc2200-GEMC3Entry 34 }
mc2200-GEMC3RxOversize OBJECT-TYPE
						SYNTAX			Counter64
						MAX-ACCESS		read-only
						STATUS			current
						DESCRIPTION
                        "GEMC3 Local card's LAN port MIB RxOversize counter."
						::= { mc2200-GEMC3Entry 35 }
mc2200-GEMC3RxJabber OBJECT-TYPE
						SYNTAX			Counter64
						MAX-ACCESS		read-only
						STATUS			current
						DESCRIPTION
                        "GEMC3 Local card's LAN port MIB RxJabber counter."
						::= { mc2200-GEMC3Entry 36 }
mc2200-GEMC3RxErr OBJECT-TYPE
						SYNTAX			Counter64
						MAX-ACCESS		read-only
						STATUS			current
						DESCRIPTION
                        "GEMC3 Local card's LAN port MIB RxErr counter."
						::= { mc2200-GEMC3Entry 37 }
mc2200-GEMC3RxFCSErr OBJECT-TYPE
						SYNTAX			Counter64
						MAX-ACCESS		read-only
						STATUS			current
						DESCRIPTION
                        "GEMC3 Local card's LAN port MIB RxFCSErr counter."
						::= { mc2200-GEMC3Entry 38 }
mc2200-GEMC3TxCollisions OBJECT-TYPE
						SYNTAX			Counter64
						MAX-ACCESS		read-only
						STATUS			current
						DESCRIPTION
                        "GEMC3 Local card's LAN port MIB TxCollisions counter."
						::= { mc2200-GEMC3Entry 39 }
mc2200-GEMC3TxLate OBJECT-TYPE
						SYNTAX			Counter64
						MAX-ACCESS		read-only
						STATUS			current
						DESCRIPTION
                        "GEMC3 Local card's port8 MIB TxLate counter."
						::= { mc2200-GEMC3Entry 40 }
mc2200-GEMC3RemoteLANSFPInfo	OBJECT-TYPE
						SYNTAX		DisplayString
						MAX-ACCESS		read-only
						STATUS			current
						DESCRIPTION
                            "GEMC3 Remote card's LAN port SFP infomation."
						::= { mc2200-GEMC3Entry 41 }
mc2200-GEMC3RemoteLANLink      OBJECT-TYPE
						SYNTAX			INTEGER {up(1),
						                         down(2), noremotecard(0)}
						MAX-ACCESS		read-only
						STATUS			mandatory
						DESCRIPTION
                            "GEMC3 Remote card's LAN port work link status."
						::= { mc2200-GEMC3Entry 42 }
mc2200-GEMC3RemoteWANSFPInfo	OBJECT-TYPE
						SYNTAX		DisplayString
						MAX-ACCESS		read-only
						STATUS			current
						DESCRIPTION
                            "GEMC3 Remote card's WAN port SFP infomation."
						::= { mc2200-GEMC3Entry 43 }
mc2200-GEMC3RemoteWANLink	        OBJECT-TYPE
						SYNTAX			INTEGER {up(1),
						                         down(2), noremotecard(0)}
						MAX-ACCESS		read-only
						STATUS			current
						DESCRIPTION
                            "GEMC3 Remote card's WAN port work link status."
						::= { mc2200-GEMC3Entry 44 }


mc2200-GEMC3RemoteLANMode   	OBJECT-TYPE
						SYNTAX		INTEGER {mode1000Base-X-auto(1),
                          					mode1000Base-X-Force(2),
                          					auto-10-100-1000T(3),
                          					mode1000Base-T-full(4),
                          					mode100Base-T-full(5),
                          					mode100Base-T-Half(6),
                          					mode10Base-T-full(7),
                          					mode10Base-T-Half(8),noremotecard(0)}
						MAX-ACCESS		read-write
						STATUS			current
						DESCRIPTION
                        "GEMC3 Remote card's LAN port Mode configuration,
                    	set INTEGER(1) to 1000Base-X-auto,
                    	set INTEGER(2) to 1000Base-X-Force,
                    	set INTEGER(3) to auto-10-100-1000T,
                    	set INTEGER(4) to 1000Base-T-full,
                    	set INTEGER(5) to 100Base-T-full,
                    	set INTEGER(6) to 100Base-T-Half,
                    	set INTEGER(7) to 10Base-T-full,
                    	set INTEGER(8) to 10Base-T-Half,
                    	Ohter value is invalid"
						::= { mc2200-GEMC3Entry  45 }
mc2200-GEMC3RemoteIPAddress  OBJECT-TYPE
        			SYNTAX      IpAddress
        			ACCESS      read-write
        			STATUS      mandatory
	    			DESCRIPTION
            		"The IP address to GEMC3 Remote IP ping."
        			::= {mc2200-GEMC3Entry 46}

mc2200-GEMC3RemoteSubnetMask    OBJECT-TYPE
        			SYNTAX      IpAddress
        			ACCESS      read-write
        			STATUS      mandatory
	    			DESCRIPTION
                    "The Net mask to  GEMC3 Remote IP ping."
        			::= {mc2200-GEMC3Entry 47}

mc2200-GEMC3RemoteGateWay    OBJECT-TYPE
        			SYNTAX      IpAddress
        			ACCESS      read-write
        			STATUS      mandatory
	   				 DESCRIPTION
                    "The gateware to GEMC3 Remote IP ping."
        			::= {mc2200-GEMC3Entry 48}

mc2200-GEMC3RemoteVLANEnable  OBJECT-TYPE
        			SYNTAX      INTEGER {enable(1),disable(2), noremotecard(0)}
        			ACCESS      read-write
        			STATUS      mandatory
	    			DESCRIPTION
                    "Enable or disable Remote GEMC3 IP ping 802.1Q VLAN."
        			::= {mc2200-GEMC3Entry 49}
mc2200-GEMC3RemoteVID  OBJECT-TYPE
        			SYNTAX      INTEGER
        			ACCESS      read-write
        			STATUS      mandatory
	    			DESCRIPTION
                    "GEMC3 Remote IP ping  802.1Q VLAN ID."
        			::= {mc2200-GEMC3Entry 50}
mc2200-GEMC3RemoteAlarm      OBJECT-TYPE
						SYNTAX			INTEGER  {enabled(1),disabled(2)}
						MAX-ACCESS		read-write
						STATUS			current
						DESCRIPTION
                        "Enable or disable GEMC3 Media converter card remote alarm.
                         set INTEGER(1) to Enable remote alarm,
                         set INTEGER(2) to Disable remote alarm,
                         Other value is invalid."
						::= { mc2200-GEMC3Entry 51 }
mc2200-GEMC3RFD		      OBJECT-TYPE
						SYNTAX			INTEGER  {enabled(1),disabled(2)}
						MAX-ACCESS		read-write
						STATUS			current
						DESCRIPTION
                        "GEMC3 Media converter card remote fault detect operation.
                         set INTEGER(1) to Enable RFD,
                         set INTEGER(2) to Disable RFD,
                         Other value is invalid."
						::= { mc2200-GEMC3Entry 52 }
mc2200-GEMC3Default		OBJECT-TYPE
						SYNTAX			INTEGER
						MAX-ACCESS		write-only
						STATUS			current
						DESCRIPTION
                        "Write GEMC3 card default setting,
                        set INTEGER(1) to write default.
                        Other value is invalid."
						::= { mc2200-GEMC3Entry 53 }
mc2200-GEMC3Reboot		OBJECT-TYPE
						SYNTAX			INTEGER
						MAX-ACCESS		write-only
						STATUS			current
						DESCRIPTION
                        "Reboot GEMC3 local card,
                        set INTEGER(1) to reboot this card.
                        Other value is invalid. "
						::= { mc2200-GEMC3Entry 54 }
mc2200-GEMC3LocalLANSpeed      OBJECT-TYPE
						SYNTAX			INTEGER {speed1000M(1),
						                         speed100M(2),speed10M(3),down(4)}
						MAX-ACCESS		read-only
						STATUS			mandatory
						DESCRIPTION
                        "GE-MC3 Local card's LAN port work speed status."
						::= { mc2200-GEMC3Entry 55 }
mc2200-GEMC3RemoteLANSpeed      OBJECT-TYPE
						SYNTAX			INTEGER {speed1000M(1),speed100M(2),
						                         speed10M(3),down(4),noremotecard(0)}
						MAX-ACCESS		read-only
						STATUS			mandatory
						DESCRIPTION
                        "GE-MC3 Remote card's LAN port work speed status."
						::= { mc2200-GEMC3Entry 56 }

mc2200-GEMC3Localportuser      OBJECT-TYPE
						SYNTAX			DisplayString
						MAX-ACCESS		read-write
						STATUS			current
						DESCRIPTION
                        " User of GE-MC3 Local Port1. "
						::= { mc2200-GEMC3Entry 57 }

mc2200-GEMC3Remoteportuser      OBJECT-TYPE
						SYNTAX			DisplayString
						MAX-ACCESS		read-write
						STATUS			current
						DESCRIPTION
                        " User of GE-MC3 Remote Port1. "
						::= { mc2200-GEMC3Entry 58 }

mc2200-GEMC3WANOpticalPowerCheck        OBJECT-TYPE
						SYNTAX			INTEGER  {enabled(1),disabled(2)}
						MAX-ACCESS		read-write
						STATUS			current
						DESCRIPTION
                        "GEMC3 Media converter card WANOpticalPowerCheck operation.
                         set INTEGER(1) to Enable WANOpticalPowerCheck,
                         set INTEGER(2) to Disable WANOpticalPowerCheck,
                         Other value is invalid."
						::= { mc2200-GEMC3Entry 59 }
mc2200-GEMC3WANThreshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GEMC3 Media converter card WANThreshold operation.
                         Other value is invalid."
						::= { mc2200-GEMC3Entry 60 }
mc2200-GEMC3TrapFilterLocalLAN	        OBJECT-TYPE
						SYNTAX			INTEGER {enabled(1),disabled(2)}
						MAX-ACCESS		read-write
						STATUS			current
						DESCRIPTION
                            "Local LAN of GEMC3 Trap Filter ."
						::= { mc2200-GEMC3Entry 61 }
mc2200-GEMC3TrapFilterLocalWAN	        OBJECT-TYPE
						SYNTAX			INTEGER {enabled(1),disabled(2)}
						MAX-ACCESS		read-write
						STATUS			current
						DESCRIPTION
                            "Local WAN of GEMC3 Trap Filter ."
						::= { mc2200-GEMC3Entry 62 }
mc2200-GEMC3TrapFilterRemotePower	        OBJECT-TYPE
						SYNTAX			INTEGER {enabled(1),disabled(2)}
						MAX-ACCESS		read-write
						STATUS			current
						DESCRIPTION
                            "Remote Power of GEMC3 Trap Filter ."
						::= { mc2200-GEMC3Entry 63 }
mc2200-GEMC3TrapFilterRemoteLAN	        OBJECT-TYPE
						SYNTAX			INTEGER {enabled(1),disabled(2)}
						MAX-ACCESS		read-write
						STATUS			current
						DESCRIPTION
                            "Remote LAN of GEMC3 Trap Filter ."
						::= { mc2200-GEMC3Entry 64 }
mc2200-GEMC3TrapFilterRemoteWAN	        OBJECT-TYPE
						SYNTAX			INTEGER {enabled(1),disabled(2)}
						MAX-ACCESS		read-write
						STATUS			current
						DESCRIPTION
                            "Remote WAN of GEMC3 Trap Filter ."
						::= { mc2200-GEMC3Entry 65 }

mc2200-GEMC3Loopback      OBJECT-TYPE
						SYNTAX			INTEGER {disable(1),local_lanouter(2),local_laninner(3),local_wanouter(4),
												local_waninner(5),remote_lanouter(6),remote_laninner(7)}
						MAX-ACCESS		read-write
						STATUS			mandatory
						DESCRIPTION
                            "GEMC3 card's loopback."
						::= { mc2200-GEMC3Entry 66 }
mc2200-GEMC3CardType	OBJECT-TYPE
						SYNTAX		DisplayString
						MAX-ACCESS		read-only
						STATUS			current
						DESCRIPTION
                            "GEMC3 card's Type."
						::= { mc2200-GEMC3Entry 67 }


-- GESFPAPS Table  ====================================================

mc2200-GESFPAPSTable	   OBJECT-TYPE
					SYNTAX			SEQUENCE OF MC2200-GESFPAPSEntry
					MAX-ACCESS		not-accessible
					STATUS			current
					DESCRIPTION
                   "Sparse table containing one entry for each GESFPAPS
                     10/100Mbps Twisted-Pair to Fiber Ethernet Media Converter
                     in the system, indexed by chassisIndex and slotIndex."

					::= { mc2200-GEmib 14 }

mc2200-GESFPAPSEntry			OBJECT-TYPE
						SYNTAX			MC2200-GESFPAPSEntry
						MAX-ACCESS		not-accessible
						STATUS			current
						DESCRIPTION
            "One table entry per slot in the media converter chassis.
             If physical slot 'n' contains a powered GESFPAPS media
             converter, then entry 'n' in this table exists and describes
             the state of the converter's lamps  If slot 'n' is empty, does
             not exist, or contains a different type of device, then table
             entry 'n' does not exist."

						INDEX			{ mc2200-GESFPAPSCardIndex }
						::= { mc2200-GESFPAPSTable 1 }






-- ==========================
-- CH-unit config info table --
-- ==========================
MC2200-GESFPAPSEntry ::=
				SEQUENCE {
					mc2200-GESFPAPSCardIndex			    INTEGER,	-- 1
					mc2200-GESFPAPSLocalTXLink          	INTEGER,
					mc2200-GESFPAPSLocalWAN1SFPInfo         DisplayString,
					mc2200-GESFPAPSLocalWAN1Link          	INTEGER,
					mc2200-GESFPAPSLocalWAN2SFPInfo         DisplayString,
					mc2200-GESFPAPSLocalWAN2Link          	INTEGER,
					mc2200-GESFPAPSLocalActivePort          	INTEGER,
					mc2200-GESFPAPSLocalTXDownStreamBW   	INTEGER,
					mc2200-GESFPAPSLocalTXUpStreamBW     	INTEGER,
					mc2200-GESFPAPSLocalTXMode	      	INTEGER,
					mc2200-GESFPAPSLocalTXMDIX                INTEGER,
					mc2200-GESFPAPSRxGoodOctets        	Counter64, -- 10

                    mc2200-GESFPAPSRxBadOctets        		Counter64,
                    mc2200-GESFPAPSTxFCSErr        		Counter64,
					mc2200-GESFPAPSRxUnicast        		Counter64,
					mc2200-GESFPAPSTxDeferred        		Counter64,
                    mc2200-GESFPAPSRxBroadcasts        	Counter64,
                    mc2200-GESFPAPSRxMulticasts        	Counter64,
					mc2200-GESFPAPSRx64Octets        	Counter64,
					mc2200-GESFPAPSRx65to127Octets        	Counter64,
                    mc2200-GESFPAPSRx128to255Octets        Counter64, -- 20
                    mc2200-GESFPAPSRx256to511Octets        Counter64,
                    mc2200-GESFPAPSRx512to1023Octets       Counter64,
					mc2200-GESFPAPSRx1024toMaxOctets       Counter64,
					mc2200-GESFPAPSTxOctets       		Counter64,

                    mc2200-GESFPAPSTxUnicast        		Counter64,
					mc2200-GESFPAPSTxExcessive        		Counter64,
					mc2200-GESFPAPSTxMulticasts            Counter64,
                    mc2200-GESFPAPSTxBroadcasts        	Counter64,
                    mc2200-GESFPAPSTxSingle        		Counter64, -- 30
					mc2200-GESFPAPSTxPause        			Counter64,
					mc2200-GESFPAPSRxPause        			Counter64,
                    mc2200-GESFPAPSTxMultiple        		Counter64,
                    mc2200-GESFPAPSRxUndersize        		Counter64,
					mc2200-GESFPAPSRxFragments             Counter64,
					mc2200-GESFPAPSRxOversize              Counter64,
                    mc2200-GESFPAPSRxJabber        		Counter64,
                    mc2200-GESFPAPSRxErr        		    Counter64,
					mc2200-GESFPAPSRxFCSErr                Counter64,
					mc2200-GESFPAPSTxCollisions            Counter64,  -- 40
                    mc2200-GESFPAPSTxLate        		    Counter64,
					mc2200-GESFPAPSRemoteTXLink           INTEGER,
					mc2200-GESFPAPSRemoteWAN1SFPInfo        DisplayString,
					mc2200-GESFPAPSRemoteWAN1Link           INTEGER,
					mc2200-GESFPAPSRemoteWAN2SFPInfo        DisplayString,
					mc2200-GESFPAPSRemoteWAN2Link           INTEGER,
					mc2200-GESFPAPSRemoteTXMode	        INTEGER,
                    mc2200-GESFPAPSRemoteTXMDIX               INTEGER,
					mc2200-GESFPAPSRemoteIPAddress       	IpAddress,
		  	        mc2200-GESFPAPSRemoteSubnetMask      	IpAddress,
					mc2200-GESFPAPSRemoteGateWay         	IpAddress,
					mc2200-GESFPAPSRemoteVLANEnable	    INTEGER, -- 50
					mc2200-GESFPAPSRemoteVID         		INTEGER,
                    mc2200-GESFPAPSRemoteAlarm      		INTEGER,
                    mc2200-GESFPAPSRFD						INTEGER,
                    mc2200-GESFPAPSDefault					INTEGER,
                    mc2200-GESFPAPSReboot					INTEGER, -- 55
					mc2200-GESFPAPSLocalTXSpeed                  INTEGER,
					mc2200-GESFPAPSRemoteTXSpeed                 INTEGER,
					mc2200-GESFPAPSLocalportuser     DisplayString,
					mc2200-GESFPAPSRemoteportuser    DisplayString,		   -- 60
					mc2200-GESFPAPSLocalTXDuplex	    		INTEGER,
					mc2200-GESFPAPSRemoteTXDuplex	    		INTEGER,
					mc2200-GESFPAPSFlowControl			INTEGER,
					mc2200-GESFPAPSRevertive				INTEGER,
					mc2200-GESFPAPSWAN1OpticalPowerCheck			INTEGER,
					mc2200-GESFPAPSWAN1Threshold			INTEGER,
					mc2200-GESFPAPSWAN2OpticalPowerCheck			INTEGER,
					mc2200-GESFPAPSWAN2Threshold			INTEGER,
					mc2200-GESFPAPSTrapFilterLocalLAN			INTEGER,
					mc2200-GESFPAPSTrapFilterLocalWAN			INTEGER,
					mc2200-GESFPAPSTrapFilterRemotePower		INTEGER,
					mc2200-GESFPAPSTrapFilterRemoteLAN			INTEGER,
					mc2200-GESFPAPSTrapFilterRemoteWAN			INTEGER,
					mc2200-GESFPAPSLoopback			INTEGER,
					mc2200-GESFPAPSCardType			DisplayString
				}


mc2200-GESFPAPSCardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GESFPAPSEntry 1 }
mc2200-GESFPAPSLocalTXLink      OBJECT-TYPE
						SYNTAX			INTEGER {up(1),
						                         down(2)}
						MAX-ACCESS		read-only
						STATUS			mandatory
						DESCRIPTION
                            "GESFPAPS Local card's LAN port work link status."
						::= { mc2200-GESFPAPSEntry 2 }
mc2200-GESFPAPSLocalWAN1SFPInfo	OBJECT-TYPE
						SYNTAX		DisplayString
						MAX-ACCESS		read-only
						STATUS			current
						DESCRIPTION
                            "GESFPAPS Local card's WAN port SFP infomation."
						::= { mc2200-GESFPAPSEntry 3 }
mc2200-GESFPAPSLocalWAN1Link	        OBJECT-TYPE
						SYNTAX			INTEGER {up(1),
						                         down(2),
						                         active(3),
						                         standby(4)}
						MAX-ACCESS		read-only
						STATUS			current
						DESCRIPTION
                            "GESFPAPS Local card's WAN port work link status."
						::= { mc2200-GESFPAPSEntry 4 }
mc2200-GESFPAPSLocalWAN2SFPInfo	OBJECT-TYPE
						SYNTAX		DisplayString
						MAX-ACCESS		read-only
						STATUS			current
						DESCRIPTION
                            "GESFPAPS Local card's WAN port SFP infomation."
						::= { mc2200-GESFPAPSEntry 5}

mc2200-GESFPAPSLocalWAN2Link	        OBJECT-TYPE
						SYNTAX			INTEGER {up(1),
						                         down(2),
						                         active(3),
						                         standby(4)}
						MAX-ACCESS		read-only
						STATUS			current
						DESCRIPTION
                            "GESFPAPS Local card's WAN port work link status."
						::= { mc2200-GESFPAPSEntry 6 }

mc2200-GESFPAPSLocalActivePort	        OBJECT-TYPE
						SYNTAX			INTEGER {wan1(1),
						                         wan2(2)}
						MAX-ACCESS		read-write
						STATUS			current
						DESCRIPTION
                            "GESFPAPS Local card's WAN port work link status."
						::= { mc2200-GESFPAPSEntry 7 }

mc2200-GESFPAPSLocalTXDownStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                            "GESFPAPS Local card's LAN port DownStream BandWidth. "
						::= { mc2200-GESFPAPSEntry 8 }
mc2200-GESFPAPSLocalTXUpStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        " GESFPAPS Local card's LAN port UpStream BandWidth."
						::= { mc2200-GESFPAPSEntry 9 }
mc2200-GESFPAPSLocalTXMode   	OBJECT-TYPE
						SYNTAX		INTEGER {auto-10-100-1000(1),
                          					mode1000F(2),
                          					mode100F(3),
                          					mode10F(4),
                          					mode100H(5),
                          					mode10H(6)}
						MAX-ACCESS		read-write
						STATUS			current
						DESCRIPTION
                        "GESFPAPS Local card's LAN port Mode configuration,
                    	set INTEGER(1) to auto(10/100/1000),
                    	set INTEGER(2) to 1000F,
                    	set INTEGER(3) to 100F,
                    	set INTEGER(4) to 10F,
                    	set INTEGER(5) to 100H,
                    	set INTEGER(6) to 10H,
                    	Ohter value is invalid"
						::= { mc2200-GESFPAPSEntry  10 }
mc2200-GESFPAPSLocalTXMDIX   	OBJECT-TYPE
						SYNTAX		INTEGER {auto(1),
                          					mdi(2),
                          					mdiX(3)}
						MAX-ACCESS		read-write
						STATUS			current
						DESCRIPTION
                        "GESFPAPS Local card's LAN port Mode configuration,
                    	set INTEGER(1) to auto,
                    	set INTEGER(2) to mdi,
                    	set INTEGER(3) to MDIX,
                    	Ohter value is invalid"
						::= { mc2200-GESFPAPSEntry  11 }

mc2200-GESFPAPSRxGoodOctets OBJECT-TYPE
						SYNTAX			Counter64
						MAX-ACCESS		read-only
						STATUS			current
						DESCRIPTION
                        "GESFPAPS Local card's LAN port MIB RxGoodOctetsLow counter."
						::= { mc2200-GESFPAPSEntry 12 }

mc2200-GESFPAPSRxBadOctets OBJECT-TYPE
						SYNTAX			Counter64
						MAX-ACCESS		read-only
						STATUS			current
						DESCRIPTION
                        "GESFPAPS Local card's LAN port MIB RxBadOctets counter."
						::= { mc2200-GESFPAPSEntry 14 }
mc2200-GESFPAPSTxFCSErr OBJECT-TYPE
						SYNTAX			Counter64
						MAX-ACCESS		read-only
						STATUS			current
						DESCRIPTION
                        "GESFPAPS Local card's LAN port MIB  TxFCSErr counter."
						::= { mc2200-GESFPAPSEntry 15 }

mc2200-GESFPAPSRxUnicast OBJECT-TYPE
						SYNTAX			Counter64
						MAX-ACCESS		read-only
						STATUS			current
						DESCRIPTION
                        "GESFPAPS Local card's LAN port MIB RxUnicast counter."
						::= { mc2200-GESFPAPSEntry 16 }
mc2200-GESFPAPSTxDeferred OBJECT-TYPE
						SYNTAX			Counter64
						MAX-ACCESS		read-only
						STATUS			current
						DESCRIPTION
                        "GESFPAPS Local card's LAN port MIB TxDeferred counter."
						::= { mc2200-GESFPAPSEntry 17 }
mc2200-GESFPAPSRxBroadcasts OBJECT-TYPE
						SYNTAX			Counter64
						MAX-ACCESS		read-only
						STATUS			current
						DESCRIPTION
                        "GESFPAPS Local card's LAN port MIB RxBroadcasts counter."
						::= { mc2200-GESFPAPSEntry 18 }
mc2200-GESFPAPSRxMulticasts OBJECT-TYPE
						SYNTAX			Counter64
						MAX-ACCESS		read-only
						STATUS			current
						DESCRIPTION
                        "GESFPAPS Local card's LAN port MIB RxMulticasts counter."
						::= { mc2200-GESFPAPSEntry 19 }
mc2200-GESFPAPSRx64Octets OBJECT-TYPE
						SYNTAX			Counter64
						MAX-ACCESS		read-only
						STATUS			current
						DESCRIPTION
                        "GESFPAPS Local card's LAN port MIB Rx64Octets counter."
						::= { mc2200-GESFPAPSEntry 20 }
mc2200-GESFPAPSRx65to127Octets OBJECT-TYPE
						SYNTAX			Counter64
						MAX-ACCESS		read-only
						STATUS			current
						DESCRIPTION
                        "GESFPAPS Local card's LAN port MIB Rx65to127Octets counter."
						::= { mc2200-GESFPAPSEntry 21 }
mc2200-GESFPAPSRx128to255Octets OBJECT-TYPE
						SYNTAX			Counter64
						MAX-ACCESS		read-only
						STATUS			current
						DESCRIPTION
                        "GESFPAPS Local card's LAN port MIB Rx128to255Octets counter."
						::= { mc2200-GESFPAPSEntry 22 }
mc2200-GESFPAPSRx256to511Octets OBJECT-TYPE
						SYNTAX			Counter64
						MAX-ACCESS		read-only
						STATUS			current
						DESCRIPTION
                        "GESFPAPS Local card's LAN port MIB Rx256to511Octets counter."
						::= { mc2200-GESFPAPSEntry 23 }
mc2200-GESFPAPSRx512to1023Octets OBJECT-TYPE
						SYNTAX			Counter64
						MAX-ACCESS		read-only
						STATUS			current
						DESCRIPTION
                        "GESFPAPS Local card's LAN port MIB Rx512to1023Octets counter."
						::= { mc2200-GESFPAPSEntry 24 }
mc2200-GESFPAPSRx1024toMaxOctets OBJECT-TYPE
						SYNTAX			Counter64
						MAX-ACCESS		read-only
						STATUS			current
						DESCRIPTION
                        "GESFPAPS Local card's LAN port MIB Rx1024toMaxOctets counter."
						::= { mc2200-GESFPAPSEntry 25 }
mc2200-GESFPAPSTxOctets OBJECT-TYPE
						SYNTAX			Counter64
						MAX-ACCESS		read-only
						STATUS			current
						DESCRIPTION
                        "GESFPAPS Local card's LAN port MIB TxOctetsLow counter."
						::= { mc2200-GESFPAPSEntry 26 }

mc2200-GESFPAPSTxUnicast OBJECT-TYPE
						SYNTAX			Counter64
						MAX-ACCESS		read-only
						STATUS			current
						DESCRIPTION
                        "GESFPAPS Local card's LAN port MIB TxUnicast counter."
						::= { mc2200-GESFPAPSEntry 28 }
mc2200-GESFPAPSTxExcessive OBJECT-TYPE
						SYNTAX			Counter64
						MAX-ACCESS		read-only
						STATUS			current
						DESCRIPTION
                        "GESFPAPS Local card's LAN port MIB TxExcessive counter."
						::= { mc2200-GESFPAPSEntry 29 }
mc2200-GESFPAPSTxMulticasts OBJECT-TYPE
						SYNTAX			Counter64
						MAX-ACCESS		read-only
						STATUS			current
						DESCRIPTION
                        "GESFPAPS Local card's LAN port MIB TxMulticasts counter."
						::= { mc2200-GESFPAPSEntry 30 }
mc2200-GESFPAPSTxBroadcasts OBJECT-TYPE
						SYNTAX			Counter64
						MAX-ACCESS		read-only
						STATUS			current
						DESCRIPTION
                        "GESFPAPS Local card's LAN port MIB TxBroadcasts counter."
						::= { mc2200-GESFPAPSEntry 31 }
mc2200-GESFPAPSTxSingle OBJECT-TYPE
						SYNTAX			Counter64
						MAX-ACCESS		read-only
						STATUS			current
						DESCRIPTION
                        "GESFPAPS Local card's LAN port MIB TxSingle counter."
						::= { mc2200-GESFPAPSEntry 32 }
mc2200-GESFPAPSTxPause OBJECT-TYPE
						SYNTAX			Counter64
						MAX-ACCESS		read-only
						STATUS			current
						DESCRIPTION
                        "GESFPAPS Local card's LAN port MIB TxPause counter."
						::= { mc2200-GESFPAPSEntry 33 }
mc2200-GESFPAPSRxPause OBJECT-TYPE
						SYNTAX			Counter64
						MAX-ACCESS		read-only
						STATUS			current
						DESCRIPTION
                        "GESFPAPS Local card's LAN port MIB RxPause counter."
						::= { mc2200-GESFPAPSEntry 34 }
mc2200-GESFPAPSTxMultiple OBJECT-TYPE
						SYNTAX			Counter64
						MAX-ACCESS		read-only
						STATUS			current
						DESCRIPTION
                        "GESFPAPS Local card's LAN port MIB TxMultiple counter."
						::= { mc2200-GESFPAPSEntry 35 }
mc2200-GESFPAPSRxUndersize OBJECT-TYPE
						SYNTAX			Counter64
						MAX-ACCESS		read-only
						STATUS			current
						DESCRIPTION
                        "GESFPAPS Local card's LAN port MIB RxUndersize counter."
						::= { mc2200-GESFPAPSEntry 36 }
mc2200-GESFPAPSRxFragments OBJECT-TYPE
						SYNTAX			Counter64
						MAX-ACCESS		read-only
						STATUS			current
						DESCRIPTION
                        "GESFPAPS Local card's LAN port MIB RxFragments counter."
						::= { mc2200-GESFPAPSEntry 37 }
mc2200-GESFPAPSRxOversize OBJECT-TYPE
						SYNTAX			Counter64
						MAX-ACCESS		read-only
						STATUS			current
						DESCRIPTION
                        "GESFPAPS Local card's LAN port MIB RxOversize counter."
						::= { mc2200-GESFPAPSEntry 38 }
mc2200-GESFPAPSRxJabber OBJECT-TYPE
						SYNTAX			Counter64
						MAX-ACCESS		read-only
						STATUS			current
						DESCRIPTION
                        "GESFPAPS Local card's LAN port MIB RxJabber counter."
						::= { mc2200-GESFPAPSEntry 39 }
mc2200-GESFPAPSRxErr OBJECT-TYPE
						SYNTAX			Counter64
						MAX-ACCESS		read-only
						STATUS			current
						DESCRIPTION
                        "GESFPAPS Local card's LAN port MIB RxErr counter."
						::= { mc2200-GESFPAPSEntry 40 }
mc2200-GESFPAPSRxFCSErr OBJECT-TYPE
						SYNTAX			Counter64
						MAX-ACCESS		read-only
						STATUS			current
						DESCRIPTION
                        "GESFPAPS Local card's LAN port MIB RxFCSErr counter."
						::= { mc2200-GESFPAPSEntry 41 }
mc2200-GESFPAPSTxCollisions OBJECT-TYPE
						SYNTAX			Counter64
						MAX-ACCESS		read-only
						STATUS			current
						DESCRIPTION
                        "GESFPAPS Local card's LAN port MIB TxCollisions counter."
						::= { mc2200-GESFPAPSEntry 42 }
mc2200-GESFPAPSTxLate OBJECT-TYPE
						SYNTAX			Counter64
						MAX-ACCESS		read-only
						STATUS			current
						DESCRIPTION
                        "GESFPAPS Local card's port8 MIB TxLate counter."
						::= { mc2200-GESFPAPSEntry 43 }
mc2200-GESFPAPSRemoteTXLink      OBJECT-TYPE
						SYNTAX			INTEGER {up(1),
						                         down(2), noremotecard(0)}
						MAX-ACCESS		read-only
						STATUS			mandatory
						DESCRIPTION
                            "GESFPAPS Remote card's LAN port work link status."
						::= { mc2200-GESFPAPSEntry 44 }
mc2200-GESFPAPSRemoteWAN1SFPInfo	OBJECT-TYPE
						SYNTAX		DisplayString
						MAX-ACCESS		read-only
						STATUS			current
						DESCRIPTION
                            "GESFPAPS Remote card's WAN port SFP infomation."
						::= { mc2200-GESFPAPSEntry 45 }
mc2200-GESFPAPSRemoteWAN1Link	        OBJECT-TYPE
						SYNTAX			INTEGER {up(1),
						                         down(2),
						                         active(3),
						                         standby(4),noremotecard(0)}
						MAX-ACCESS		read-only
						STATUS			current
						DESCRIPTION
                            "GESFPAPS Remote card's WAN port work link status."
						::= { mc2200-GESFPAPSEntry 46 }

mc2200-GESFPAPSRemoteWAN2SFPInfo	OBJECT-TYPE
						SYNTAX		DisplayString
						MAX-ACCESS		read-only
						STATUS			current
						DESCRIPTION
                            "GESFPAPS Remote card's WAN port SFP infomation."
						::= { mc2200-GESFPAPSEntry 47 }
mc2200-GESFPAPSRemoteWAN2Link	        OBJECT-TYPE
						SYNTAX			INTEGER {up(1),
						                         down(2),
						                         active(3),
						                         standby(4),noremotecard(0)}
						MAX-ACCESS		read-only
						STATUS			current
						DESCRIPTION
                            "GESFPAPS Remote card's WAN port work link status."
						::= { mc2200-GESFPAPSEntry 48 }


mc2200-GESFPAPSRemoteTXMode   	OBJECT-TYPE
						SYNTAX		INTEGER {auto-10-100-1000(1),
                          					mode1000F(2),
                          					mode100F(3),
                          					mode10F(4),
                          					mode100H(5),
                          					mode10H(6),noremotecard(0)}
						MAX-ACCESS		read-write
						STATUS			current
						DESCRIPTION
                        "GESFPAPS Remote card's LAN port Mode configuration,
                    	set INTEGER(1) to auto(10/100/1000),
                    	set INTEGER(2) to 1000F,
                    	set INTEGER(3) to 100F,
                    	set INTEGER(4) to 10F,
                    	set INTEGER(5) to 100H,
                    	set INTEGER(6) to 10H,
                    	Ohter value is invalid"
						::= { mc2200-GESFPAPSEntry  49 }

mc2200-GESFPAPSRemoteTXMDIX   	OBJECT-TYPE
						SYNTAX		INTEGER {auto(1),
                          					mdi(2),
                          					mdix(3),noremotecard(0)}
						MAX-ACCESS		read-write
						STATUS			current
						DESCRIPTION
                        "GESFPAPS Remote card's LAN port Mode configuration,
                    	set INTEGER(1) to auto,
                    	set INTEGER(2) to MDI,
                    	set INTEGER(3) to MDIX,
                    	Ohter value is invalid"
						::= { mc2200-GESFPAPSEntry  50 }
mc2200-GESFPAPSRemoteIPAddress  OBJECT-TYPE
        			SYNTAX      IpAddress
        			ACCESS      read-write
        			STATUS      mandatory
	    			DESCRIPTION
            		"The IP address to GESFPAPS Remote IP ping."
        			::= {mc2200-GESFPAPSEntry 51}

mc2200-GESFPAPSRemoteSubnetMask    OBJECT-TYPE
        			SYNTAX      IpAddress
        			ACCESS      read-write
        			STATUS      mandatory
	    			DESCRIPTION
                    "The Net mask to  GESFPAPS Remote IP ping."
        			::= {mc2200-GESFPAPSEntry 52}

mc2200-GESFPAPSRemoteGateWay    OBJECT-TYPE
        			SYNTAX      IpAddress
        			ACCESS      read-write
        			STATUS      mandatory
	   				 DESCRIPTION
                    "The gateware to GESFPAPS Remote IP ping."
        			::= {mc2200-GESFPAPSEntry 53}

mc2200-GESFPAPSRemoteVLANEnable  OBJECT-TYPE
        			SYNTAX      INTEGER {enable(1),disable(2), noremotecard(0)}
        			ACCESS      read-write
        			STATUS      mandatory
	    			DESCRIPTION
                    "Enable or disable Remote GESFPAPS IP ping 802.1Q VLAN."
        			::= {mc2200-GESFPAPSEntry 54}
mc2200-GESFPAPSRemoteVID  OBJECT-TYPE
        			SYNTAX      INTEGER
        			ACCESS      read-write
        			STATUS      mandatory
	    			DESCRIPTION
                    "GESFPAPS Remote IP ping  802.1Q VLAN ID."
        			::= {mc2200-GESFPAPSEntry 55}
mc2200-GESFPAPSRemoteAlarm      OBJECT-TYPE
						SYNTAX			INTEGER  {enabled(1),disabled(2)}
						MAX-ACCESS		read-write
						STATUS			current
						DESCRIPTION
                        "Enable or disable GESFPAPS Media converter card remote alarm.
                         set INTEGER(1) to Enable remote alarm,
                         set INTEGER(2) to Disable remote alarm,
                         Other value is invalid."
						::= { mc2200-GESFPAPSEntry 56 }
mc2200-GESFPAPSRFD		      OBJECT-TYPE
						SYNTAX			INTEGER  {enabled(1),disabled(2)}
						MAX-ACCESS		read-write
						STATUS			current
						DESCRIPTION
                        "GESFPAPS Media converter card remote fault detect operation.
                         set INTEGER(1) to Enable RFD,
                         set INTEGER(2) to Disable RFD,
                         Other value is invalid."
						::= { mc2200-GESFPAPSEntry 57 }
mc2200-GESFPAPSDefault		OBJECT-TYPE
						SYNTAX			INTEGER
						MAX-ACCESS		write-only
						STATUS			current
						DESCRIPTION
                        "Write GESFPAPS card default setting,
                        set INTEGER(1) to write default.
                        Other value is invalid."
						::= { mc2200-GESFPAPSEntry 58 }
mc2200-GESFPAPSReboot		OBJECT-TYPE
						SYNTAX			INTEGER
						MAX-ACCESS		write-only
						STATUS			current
						DESCRIPTION
                        "Reboot GESFPAPS local card,
                        set INTEGER(1) to reboot this card.
                        Other value is invalid. "
						::= { mc2200-GESFPAPSEntry 59 }
mc2200-GESFPAPSLocalTXSpeed      OBJECT-TYPE
						SYNTAX			INTEGER {speed1000M(1),
						                         speed100M(2),speed10M(3),down(4)}
						MAX-ACCESS		read-only
						STATUS			mandatory
						DESCRIPTION
                        "GESFPAPS Local card's LAN port work speed status."
						::= { mc2200-GESFPAPSEntry 60 }
mc2200-GESFPAPSRemoteTXSpeed      OBJECT-TYPE
						SYNTAX			INTEGER {speed1000M(1),speed100M(2),
						                         speed10M(3),down(4),noremotecard(0)}
						MAX-ACCESS		read-only
						STATUS			mandatory
						DESCRIPTION
                        "GESFPAPS Remote card's LAN port work speed status."
						::= { mc2200-GESFPAPSEntry 61 }

mc2200-GESFPAPSLocalportuser      OBJECT-TYPE
						SYNTAX			DisplayString
						MAX-ACCESS		read-write
						STATUS			current
						DESCRIPTION
                        " User of GESFPAPS Local Port1. "
						::= { mc2200-GESFPAPSEntry 62 }

mc2200-GESFPAPSRemoteportuser      OBJECT-TYPE
						SYNTAX			DisplayString
						MAX-ACCESS		read-write
						STATUS			current
						DESCRIPTION
                        " User of GESFPAPS Remote Port1. "
						::= { mc2200-GESFPAPSEntry 63 }

mc2200-GESFPAPSLocalTXDuplex      OBJECT-TYPE
						SYNTAX			INTEGER {fullDuplex(1),
						                         halfDuplex(2),down(3)}
						MAX-ACCESS		read-only
						STATUS			mandatory
						DESCRIPTION
                        "GESFPAPS Local card's TX port work duplex status."
						::= { mc2200-GESFPAPSEntry 64 }
mc2200-GESFPAPSRemoteTXDuplex      OBJECT-TYPE
						SYNTAX			INTEGER {fullDuplex(1),
						                         halfDuplex(2),down(3),noremotecard(0)}
						MAX-ACCESS		read-only
						STATUS			mandatory
						DESCRIPTION
                        "GESFPAPS Remote card's TX port work duplex status."
						::= { mc2200-GESFPAPSEntry 65 }
mc2200-GESFPAPSFlowControl        OBJECT-TYPE
						SYNTAX			INTEGER  {enabled(1),disabled(2)}
						MAX-ACCESS		read-write
						STATUS			current
						DESCRIPTION
                        "GESFPAPS Media converter card flow control operation.
                         set INTEGER(1) to Enable Flow Control,
                         set INTEGER(2) to Disable Flow Control,
                         Other value is invalid."
						::= { mc2200-GESFPAPSEntry 66 }

mc2200-GESFPAPSRevertive        OBJECT-TYPE
						SYNTAX			INTEGER  {revertive(1),norevertive(2)}
						MAX-ACCESS		read-write
						STATUS			current
						DESCRIPTION
                        "GESFPAPS Media converter card Revertive operation.
                         set INTEGER(1) to Enable Revertive,
                         set INTEGER(2) to Enable NoRevertive,
                         Other value is invalid."
						::= { mc2200-GESFPAPSEntry 67 }

mc2200-GESFPAPSWAN1OpticalPowerCheck        OBJECT-TYPE
						SYNTAX			INTEGER  {enabled(1),disabled(2),aps(3)}
						MAX-ACCESS		read-write
						STATUS			current
						DESCRIPTION
                        "GESFPAPS Media converter card WAN1 OpticalPowerCheck operation.
                         set INTEGER(1) to Enable OpticalPowerCheck,
                         set INTEGER(2) to Disable OpticalPowerCheck,
                         set INTEGER(3) to APS,
                         Other value is invalid."
						::= { mc2200-GESFPAPSEntry 68 }
mc2200-GESFPAPSWAN1Threshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GESFPAPS Media converter card WAN1Threshold operation.
                         Other value is invalid."
						::= { mc2200-GESFPAPSEntry 69 }

mc2200-GESFPAPSWAN2OpticalPowerCheck        OBJECT-TYPE
						SYNTAX			INTEGER  {enabled(1),disabled(2),aps(3)}
						MAX-ACCESS		read-write
						STATUS			current
						DESCRIPTION
                        "GESFPAPS Media converter card WAN2 OpticalPowerCheck operation.
                         set INTEGER(1) to Enable OpticalPowerCheck,
                         set INTEGER(2) to Disable OpticalPowerCheck,
                         set INTEGER(3) to APS,
                         Other value is invalid."
						::= { mc2200-GESFPAPSEntry 70 }

mc2200-GESFPAPSWAN2Threshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GESFPAPS Media converter card wan2 Threshold operation.
                         Other value is invalid."
						::= { mc2200-GESFPAPSEntry 71 }
mc2200-GESFPAPSTrapFilterLocalLAN	        OBJECT-TYPE
						SYNTAX			INTEGER {enabled(1),disabled(2)}
						MAX-ACCESS		read-write
						STATUS			current
						DESCRIPTION
                            "Local LAN of GESFPAPS Trap Filter ."
						::= { mc2200-GESFPAPSEntry 72 }
mc2200-GESFPAPSTrapFilterLocalWAN	        OBJECT-TYPE
						SYNTAX			INTEGER {enabled(1),disabled(2)}
						MAX-ACCESS		read-write
						STATUS			current
						DESCRIPTION
                            "Local WAN of GESFPAPS Trap Filter ."
						::= { mc2200-GESFPAPSEntry 73 }
mc2200-GESFPAPSTrapFilterRemotePower	        OBJECT-TYPE
						SYNTAX			INTEGER {enabled(1),disabled(2)}
						MAX-ACCESS		read-write
						STATUS			current
						DESCRIPTION
                            "Remote Power of GESFPAPS Trap Filter ."
						::= { mc2200-GESFPAPSEntry 74 }
mc2200-GESFPAPSTrapFilterRemoteLAN	        OBJECT-TYPE
						SYNTAX			INTEGER {enabled(1),disabled(2)}
						MAX-ACCESS		read-write
						STATUS			current
						DESCRIPTION
                            "Remote LAN of GESFPAPS Trap Filter ."
						::= { mc2200-GESFPAPSEntry 75 }
mc2200-GESFPAPSTrapFilterRemoteWAN	        OBJECT-TYPE
						SYNTAX			INTEGER {enabled(1),disabled(2)}
						MAX-ACCESS		read-write
						STATUS			current
						DESCRIPTION
                            "Remote WAN of GESFPAPS Trap Filter ."
						::= { mc2200-GESFPAPSEntry 76 }

mc2200-GESFPAPSLoopback      OBJECT-TYPE
						SYNTAX			INTEGER {disable(1),local_lanouter(2),local_laninner(3),local_wanouter(4),
												local_waninner(5),remote_lanouter(6),remote_laninner(7)}
						MAX-ACCESS		read-write
						STATUS			mandatory
						DESCRIPTION
                            "GESFPAPS card's loopback."
						::= { mc2200-GESFPAPSEntry 77 }
mc2200-GESFPAPSCardType	OBJECT-TYPE
						SYNTAX		DisplayString
						MAX-ACCESS		read-only
						STATUS			current
						DESCRIPTION
                            "GESFPAPS card's Type."
						::= { mc2200-GESFPAPSEntry 78 }


-- GEMCAPS Table  ====================================================

mc2200-GEMCAPSTable	   OBJECT-TYPE
					SYNTAX			SEQUENCE OF MC2200-GEMCAPSEntry
					MAX-ACCESS		not-accessible
					STATUS			current
					DESCRIPTION
                   "Sparse table containing one entry for each GEMCAPS
                     10/100Mbps Twisted-Pair to Fiber Ethernet Media Converter
                     in the system, indexed by chassisIndex and slotIndex."

					::= { mc2200-GEmib 15 }

mc2200-GEMCAPSEntry			OBJECT-TYPE
						SYNTAX			MC2200-GEMCAPSEntry
						MAX-ACCESS		not-accessible
						STATUS			current
						DESCRIPTION
            "One table entry per slot in the media converter chassis.
             If physical slot 'n' contains a powered GEMCAPS media
             converter, then entry 'n' in this table exists and describes
             the state of the converter's lamps  If slot 'n' is empty, does
             not exist, or contains a different type of device, then table
             entry 'n' does not exist."

						INDEX			{ mc2200-GEMCAPSCardIndex }
						::= { mc2200-GEMCAPSTable 1 }






-- ==========================
-- CH-unit config info table --
-- ==========================
MC2200-GEMCAPSEntry ::=
				SEQUENCE {
					mc2200-GEMCAPSCardIndex			    INTEGER,	-- 1
					mc2200-GEMCAPSLocalLANSFPInfo         DisplayString,
					mc2200-GEMCAPSLocalLANLink          	INTEGER,
					mc2200-GEMCAPSLocalWAN1SFPInfo         DisplayString,
					mc2200-GEMCAPSLocalWAN1Link          	INTEGER,
					mc2200-GEMCAPSLocalWAN2SFPInfo         DisplayString,
					mc2200-GEMCAPSLocalWAN2Link          	INTEGER,
					mc2200-GEMCAPSLocalActivePort          	INTEGER,
					mc2200-GEMCAPSLocalLANDownStreamBW   	INTEGER,
					mc2200-GEMCAPSLocalLANUpStreamBW     	INTEGER,
					mc2200-GEMCAPSLocalLANMode	      	INTEGER,
					mc2200-GEMCAPSRxGoodOctets        	Counter64, -- 10

                    mc2200-GEMCAPSRxBadOctets        		Counter64,
                    mc2200-GEMCAPSTxFCSErr        		Counter64,
					mc2200-GEMCAPSRxUnicast        		Counter64,
					mc2200-GEMCAPSTxDeferred        		Counter64,
                    mc2200-GEMCAPSRxBroadcasts        	Counter64,
                    mc2200-GEMCAPSRxMulticasts        	Counter64,
					mc2200-GEMCAPSRx64Octets        	Counter64,
					mc2200-GEMCAPSRx65to127Octets        	Counter64,
                    mc2200-GEMCAPSRx128to255Octets        Counter64, -- 20
                    mc2200-GEMCAPSRx256to511Octets        Counter64,
                    mc2200-GEMCAPSRx512to1023Octets       Counter64,
					mc2200-GEMCAPSRx1024toMaxOctets       Counter64,
					mc2200-GEMCAPSTxOctets        		Counter64,

                    mc2200-GEMCAPSTxUnicast        		Counter64,
					mc2200-GEMCAPSTxExcessive        		Counter64,
					mc2200-GEMCAPSTxMulticasts            Counter64,
                    mc2200-GEMCAPSTxBroadcasts        	Counter64,
                    mc2200-GEMCAPSTxSingle        		Counter64, -- 30
					mc2200-GEMCAPSTxPause        			Counter64,
					mc2200-GEMCAPSRxPause        			Counter64,
                    mc2200-GEMCAPSTxMultiple        		Counter64,
                    mc2200-GEMCAPSRxUndersize        		Counter64,
					mc2200-GEMCAPSRxFragments             Counter64,
					mc2200-GEMCAPSRxOversize              Counter64,
                    mc2200-GEMCAPSRxJabber        		Counter64,
                    mc2200-GEMCAPSRxErr        		    Counter64,
					mc2200-GEMCAPSRxFCSErr                Counter64,
					mc2200-GEMCAPSTxCollisions            Counter64,  -- 40
                    mc2200-GEMCAPSTxLate        		    Counter64,
                    mc2200-GEMCAPSRemoteLANSFPInfo        DisplayString,
					mc2200-GEMCAPSRemoteLANLink           INTEGER,
					mc2200-GEMCAPSRemoteWAN1SFPInfo        DisplayString,
					mc2200-GEMCAPSRemoteWAN1Link           INTEGER,
					mc2200-GEMCAPSRemoteWAN2SFPInfo        DisplayString,
					mc2200-GEMCAPSRemoteWAN2Link           INTEGER,
					mc2200-GEMCAPSRemoteLANMode	        INTEGER,
					mc2200-GEMCAPSRemoteIPAddress       	IpAddress,
		  	        mc2200-GEMCAPSRemoteSubnetMask      	IpAddress,
					mc2200-GEMCAPSRemoteGateWay         	IpAddress,
					mc2200-GEMCAPSRemoteVLANEnable	    INTEGER, -- 50
					mc2200-GEMCAPSRemoteVID         		INTEGER,
                    mc2200-GEMCAPSRemoteAlarm      		INTEGER,
                    mc2200-GEMCAPSRFD						INTEGER,
                    mc2200-GEMCAPSDefault					INTEGER,
                    mc2200-GEMCAPSReboot					INTEGER, -- 55
		    		mc2200-GEMCAPSLocalLANSpeed                  INTEGER,
		    		mc2200-GEMCAPSRemoteLANSpeed                 INTEGER,
					mc2200-GEMCAPSLocalportuser     DisplayString,
					mc2200-GEMCAPSRemoteportuser    DisplayString,
					mc2200-GEMCAPSRevertive    INTEGER,
					mc2200-GEMCAPSWAN1OpticalPowerCheck			INTEGER,
					mc2200-GEMCAPSWAN1Threshold			INTEGER,
					mc2200-GEMCAPSWAN2OpticalPowerCheck			INTEGER,
					mc2200-GEMCAPSWAN2Threshold			INTEGER,
					mc2200-GEMCAPSTrapFilterLocalLAN			INTEGER,
					mc2200-GEMCAPSTrapFilterLocalWAN			INTEGER,
					mc2200-GEMCAPSTrapFilterRemotePower		INTEGER,
					mc2200-GEMCAPSTrapFilterRemoteLAN			INTEGER,
					mc2200-GEMCAPSTrapFilterRemoteWAN			INTEGER,
					mc2200-GEMCAPSLoopback			INTEGER,
					mc2200-GEMCAPSCardType			DisplayString
				}


mc2200-GEMCAPSCardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GEMCAPSEntry 1 }
mc2200-GEMCAPSLocalLANSFPInfo	OBJECT-TYPE
						SYNTAX		DisplayString
						MAX-ACCESS		read-only
						STATUS			current
						DESCRIPTION
                            "GEMCAPS Local card's LAN port SFP infomation."
						::= { mc2200-GEMCAPSEntry 2 }
mc2200-GEMCAPSLocalLANLink      OBJECT-TYPE
						SYNTAX			INTEGER {up(1),
						                         down(2)}
						MAX-ACCESS		read-only
						STATUS			mandatory
						DESCRIPTION
                            "GEMCAPS Local card's LAN port work link status."
						::= { mc2200-GEMCAPSEntry 3 }
mc2200-GEMCAPSLocalWAN1SFPInfo	OBJECT-TYPE
						SYNTAX		DisplayString
						MAX-ACCESS		read-only
						STATUS			current
						DESCRIPTION
                            "GEMCAPS Local card's WAN port SFP infomation."
						::= { mc2200-GEMCAPSEntry 4 }
mc2200-GEMCAPSLocalWAN1Link	        OBJECT-TYPE
						SYNTAX			INTEGER {up(1),
						                         down(2),
						                         active(3),
						                         standby(4)}
						MAX-ACCESS		read-only
						STATUS			current
						DESCRIPTION
                            "GEMCAPS Local card's WAN port work link status."
						::= { mc2200-GEMCAPSEntry 5 }
mc2200-GEMCAPSLocalWAN2SFPInfo	OBJECT-TYPE
						SYNTAX		DisplayString
						MAX-ACCESS		read-only
						STATUS			current
						DESCRIPTION
                            "GEMCAPS Local card's WAN port SFP infomation."
						::= { mc2200-GEMCAPSEntry 6 }
mc2200-GEMCAPSLocalWAN2Link	        OBJECT-TYPE
						SYNTAX			INTEGER {up(1),
						                         down(2),
						                         active(3),
						                         standby(4)}
						MAX-ACCESS		read-only
						STATUS			current
						DESCRIPTION
                            "GEMCAPS Local card's WAN port work link status."
						::= { mc2200-GEMCAPSEntry 7 }
mc2200-GEMCAPSLocalActivePort	        OBJECT-TYPE
						SYNTAX			INTEGER {wan1(1),
						                         wan2(2)}
						MAX-ACCESS		read-write
						STATUS			current
						DESCRIPTION
                            "GEMCAPS Local card's WAN port work link status."
						::= { mc2200-GEMCAPSEntry 8 }

mc2200-GEMCAPSLocalLANDownStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                            "GEMCAPS Local card's LAN port DownStream BandWidth. "
						::= { mc2200-GEMCAPSEntry 9 }
mc2200-GEMCAPSLocalLANUpStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100),rate150M(150),
						                          rate200M(200),rate250M(250),rate300M(300),rate350M(350),rate400M(400),rate450M(450),
						                          rate500M(500),rate550M(550),rate600M(600),rate650M(650),rate700M(700),rate750M(750),
						                          rate800M(800),rate850M(850),rate900M(900),rate950M(950),rate1000M(1000)
						                          }
						MAX-ACCESS		read-write
						STATUS			current
						DESCRIPTION
                        " GEMCAPS Local card's LAN port UpStream BandWidth."
						::= { mc2200-GEMCAPSEntry 10 }
mc2200-GEMCAPSLocalLANMode   	OBJECT-TYPE
						SYNTAX		INTEGER {mode1000Base-X-auto(1),
                          					mode1000Base-X-Force(2),
                          					auto-10-100-1000T(3),
                          					mode1000Base-T-full(4),
                          					mode100Base-T-full(5),
                          					mode100Base-T-Half(6),
                          					mode10Base-T-full(7),
                          					mode10Base-T-Half(8)}
						MAX-ACCESS		read-write
						STATUS			current
						DESCRIPTION
                        "GEMC3 Local card's LAN port Mode configuration,
                    	set INTEGER(1) to 1000Base-X-auto,
                    	set INTEGER(2) to 1000Base-X-Force,
                    	set INTEGER(3) to auto-10-100-1000T,
                    	set INTEGER(4) to 1000Base-T-full,
                    	set INTEGER(5) to 100Base-T-full,
                    	set INTEGER(6) to 100Base-T-Half,
                    	set INTEGER(7) to 10Base-T-full,
                    	set INTEGER(8) to 10Base-T-Half,
                    	Ohter value is invalid"
						::= { mc2200-GEMCAPSEntry  11 }

mc2200-GEMCAPSRxGoodOctets OBJECT-TYPE
						SYNTAX			Counter64
						MAX-ACCESS		read-only
						STATUS			current
						DESCRIPTION
                        "GEMCAPS Local card's LAN port MIB RxGoodOctetsLow counter."
						::= { mc2200-GEMCAPSEntry 12 }

mc2200-GEMCAPSRxBadOctets OBJECT-TYPE
						SYNTAX			Counter64
						MAX-ACCESS		read-only
						STATUS			current
						DESCRIPTION
                        "GEMCAPS Local card's LAN port MIB RxBadOctets counter."
						::= { mc2200-GEMCAPSEntry 14 }
mc2200-GEMCAPSTxFCSErr OBJECT-TYPE
						SYNTAX			Counter64
						MAX-ACCESS		read-only
						STATUS			current
						DESCRIPTION
                        "GEMCAPS Local card's LAN port MIB  TxFCSErr counter."
						::= { mc2200-GEMCAPSEntry 15 }

mc2200-GEMCAPSRxUnicast OBJECT-TYPE
						SYNTAX			Counter64
						MAX-ACCESS		read-only
						STATUS			current
						DESCRIPTION
                        "GEMCAPS Local card's LAN port MIB RxUnicast counter."
						::= { mc2200-GEMCAPSEntry 16 }
mc2200-GEMCAPSTxDeferred OBJECT-TYPE
						SYNTAX			Counter64
						MAX-ACCESS		read-only
						STATUS			current
						DESCRIPTION
                        "GEMCAPS Local card's LAN port MIB TxDeferred counter."
						::= { mc2200-GEMCAPSEntry 17 }
mc2200-GEMCAPSRxBroadcasts OBJECT-TYPE
						SYNTAX			Counter64
						MAX-ACCESS		read-only
						STATUS			current
						DESCRIPTION
                        "GEMCAPS Local card's LAN port MIB RxBroadcasts counter."
						::= { mc2200-GEMCAPSEntry 18 }
mc2200-GEMCAPSRxMulticasts OBJECT-TYPE
						SYNTAX			Counter64
						MAX-ACCESS		read-only
						STATUS			current
						DESCRIPTION
                        "GEMCAPS Local card's LAN port MIB RxMulticasts counter."
						::= { mc2200-GEMCAPSEntry 19 }
mc2200-GEMCAPSRx64Octets OBJECT-TYPE
						SYNTAX			Counter64
						MAX-ACCESS		read-only
						STATUS			current
						DESCRIPTION
                        "GEMCAPS Local card's LAN port MIB Rx64Octets counter."
						::= { mc2200-GEMCAPSEntry 20 }
mc2200-GEMCAPSRx65to127Octets OBJECT-TYPE
						SYNTAX			Counter64
						MAX-ACCESS		read-only
						STATUS			current
						DESCRIPTION
                        "GEMCAPS Local card's LAN port MIB Rx65to127Octets counter."
						::= { mc2200-GEMCAPSEntry 21 }
mc2200-GEMCAPSRx128to255Octets OBJECT-TYPE
						SYNTAX			Counter64
						MAX-ACCESS		read-only
						STATUS			current
						DESCRIPTION
                        "GEMCAPS Local card's LAN port MIB Rx128to255Octets counter."
						::= { mc2200-GEMCAPSEntry 22 }
mc2200-GEMCAPSRx256to511Octets OBJECT-TYPE
						SYNTAX			Counter64
						MAX-ACCESS		read-only
						STATUS			current
						DESCRIPTION
                        "GEMCAPS Local card's LAN port MIB Rx256to511Octets counter."
						::= { mc2200-GEMCAPSEntry 23 }
mc2200-GEMCAPSRx512to1023Octets OBJECT-TYPE
						SYNTAX			Counter64
						MAX-ACCESS		read-only
						STATUS			current
						DESCRIPTION
                        "GEMCAPS Local card's LAN port MIB Rx512to1023Octets counter."
						::= { mc2200-GEMCAPSEntry 24 }
mc2200-GEMCAPSRx1024toMaxOctets OBJECT-TYPE
						SYNTAX			Counter64
						MAX-ACCESS		read-only
						STATUS			current
						DESCRIPTION
                        "GEMCAPS Local card's LAN port MIB Rx1024toMaxOctets counter."
						::= { mc2200-GEMCAPSEntry 25 }
mc2200-GEMCAPSTxOctets OBJECT-TYPE
						SYNTAX			Counter64
						MAX-ACCESS		read-only
						STATUS			current
						DESCRIPTION
                        "GEMCAPS Local card's LAN port MIB TxOctetsLow counter."
						::= { mc2200-GEMCAPSEntry 26 }

mc2200-GEMCAPSTxUnicast OBJECT-TYPE
						SYNTAX			Counter64
						MAX-ACCESS		read-only
						STATUS			current
						DESCRIPTION
                        "GEMCAPS Local card's LAN port MIB TxUnicast counter."
						::= { mc2200-GEMCAPSEntry 28 }
mc2200-GEMCAPSTxExcessive OBJECT-TYPE
						SYNTAX			Counter64
						MAX-ACCESS		read-only
						STATUS			current
						DESCRIPTION
                        "GEMCAPS Local card's LAN port MIB TxExcessive counter."
						::= { mc2200-GEMCAPSEntry 29 }
mc2200-GEMCAPSTxMulticasts OBJECT-TYPE
						SYNTAX			Counter64
						MAX-ACCESS		read-only
						STATUS			current
						DESCRIPTION
                        "GEMCAPS Local card's LAN port MIB TxMulticasts counter."
						::= { mc2200-GEMCAPSEntry 30 }
mc2200-GEMCAPSTxBroadcasts OBJECT-TYPE
						SYNTAX			Counter64
						MAX-ACCESS		read-only
						STATUS			current
						DESCRIPTION
                        "GEMCAPS Local card's LAN port MIB TxBroadcasts counter."
						::= { mc2200-GEMCAPSEntry 31 }
mc2200-GEMCAPSTxSingle OBJECT-TYPE
						SYNTAX			Counter64
						MAX-ACCESS		read-only
						STATUS			current
						DESCRIPTION
                        "GEMCAPS Local card's LAN port MIB TxSingle counter."
						::= { mc2200-GEMCAPSEntry 32 }
mc2200-GEMCAPSTxPause OBJECT-TYPE
						SYNTAX			Counter64
						MAX-ACCESS		read-only
						STATUS			current
						DESCRIPTION
                        "GEMCAPS Local card's LAN port MIB TxPause counter."
						::= { mc2200-GEMCAPSEntry 33 }
mc2200-GEMCAPSRxPause OBJECT-TYPE
						SYNTAX			Counter64
						MAX-ACCESS		read-only
						STATUS			current
						DESCRIPTION
                        "GEMCAPS Local card's LAN port MIB RxPause counter."
						::= { mc2200-GEMCAPSEntry 34 }
mc2200-GEMCAPSTxMultiple OBJECT-TYPE
						SYNTAX			Counter64
						MAX-ACCESS		read-only
						STATUS			current
						DESCRIPTION
                        "GEMCAPS Local card's LAN port MIB TxMultiple counter."
						::= { mc2200-GEMCAPSEntry 35 }
mc2200-GEMCAPSRxUndersize OBJECT-TYPE
						SYNTAX			Counter64
						MAX-ACCESS		read-only
						STATUS			current
						DESCRIPTION
                        "GEMCAPS Local card's LAN port MIB RxUndersize counter."
						::= { mc2200-GEMCAPSEntry 36 }
mc2200-GEMCAPSRxFragments OBJECT-TYPE
						SYNTAX			Counter64
						MAX-ACCESS		read-only
						STATUS			current
						DESCRIPTION
                        "GEMCAPS Local card's LAN port MIB RxFragments counter."
						::= { mc2200-GEMCAPSEntry 37 }
mc2200-GEMCAPSRxOversize OBJECT-TYPE
						SYNTAX			Counter64
						MAX-ACCESS		read-only
						STATUS			current
						DESCRIPTION
                        "GEMCAPS Local card's LAN port MIB RxOversize counter."
						::= { mc2200-GEMCAPSEntry 38 }
mc2200-GEMCAPSRxJabber OBJECT-TYPE
						SYNTAX			Counter64
						MAX-ACCESS		read-only
						STATUS			current
						DESCRIPTION
                        "GEMCAPS Local card's LAN port MIB RxJabber counter."
						::= { mc2200-GEMCAPSEntry 39 }
mc2200-GEMCAPSRxErr OBJECT-TYPE
						SYNTAX			Counter64
						MAX-ACCESS		read-only
						STATUS			current
						DESCRIPTION
                        "GEMCAPS Local card's LAN port MIB RxErr counter."
						::= { mc2200-GEMCAPSEntry 40 }
mc2200-GEMCAPSRxFCSErr OBJECT-TYPE
						SYNTAX			Counter64
						MAX-ACCESS		read-only
						STATUS			current
						DESCRIPTION
                        "GEMCAPS Local card's LAN port MIB RxFCSErr counter."
						::= { mc2200-GEMCAPSEntry 41 }
mc2200-GEMCAPSTxCollisions OBJECT-TYPE
						SYNTAX			Counter64
						MAX-ACCESS		read-only
						STATUS			current
						DESCRIPTION
                        "GEMCAPS Local card's LAN port MIB TxCollisions counter."
						::= { mc2200-GEMCAPSEntry 42 }
mc2200-GEMCAPSTxLate OBJECT-TYPE
						SYNTAX			Counter64
						MAX-ACCESS		read-only
						STATUS			current
						DESCRIPTION
                        "GEMCAPS Local card's port8 MIB TxLate counter."
						::= { mc2200-GEMCAPSEntry 43 }
mc2200-GEMCAPSRemoteLANSFPInfo	OBJECT-TYPE
						SYNTAX		DisplayString
						MAX-ACCESS		read-only
						STATUS			current
						DESCRIPTION
                            "GEMCAPS Remote card's LAN port SFP infomation."
						::= { mc2200-GEMCAPSEntry 44 }
mc2200-GEMCAPSRemoteLANLink      OBJECT-TYPE
						SYNTAX			INTEGER {up(1),
						                         down(2), noremotecard(0)}
						MAX-ACCESS		read-only
						STATUS			mandatory
						DESCRIPTION
                            "GEMCAPS Remote card's LAN port work link status."
						::= { mc2200-GEMCAPSEntry 45 }
mc2200-GEMCAPSRemoteWAN1SFPInfo	OBJECT-TYPE
						SYNTAX		DisplayString
						MAX-ACCESS		read-only
						STATUS			current
						DESCRIPTION
                            "GEMCAPS Remote card's WAN port SFP infomation."
						::= { mc2200-GEMCAPSEntry 46 }
mc2200-GEMCAPSRemoteWAN1Link	        OBJECT-TYPE
						SYNTAX			INTEGER {up(1),
						                         down(2),
						                         active(3),
						                         standby(4),noremotecard(0)}
						MAX-ACCESS		read-only
						STATUS			current
						DESCRIPTION
                            "GEMCAPS Remote card's WAN port work link status."
						::= { mc2200-GEMCAPSEntry 47 }
mc2200-GEMCAPSRemoteWAN2SFPInfo	OBJECT-TYPE
						SYNTAX		DisplayString
						MAX-ACCESS		read-only
						STATUS			current
						DESCRIPTION
                            "GEMCAPS Remote card's WAN port SFP infomation."
						::= { mc2200-GEMCAPSEntry 48 }
mc2200-GEMCAPSRemoteWAN2Link	        OBJECT-TYPE
						SYNTAX			INTEGER {up(1),
						                         down(2),
						                         active(3),
						                         standby(4),noremotecard(0)}
						MAX-ACCESS		read-only
						STATUS			current
						DESCRIPTION
                            "GEMCAPS Remote card's WAN port work link status."
						::= { mc2200-GEMCAPSEntry 49 }


mc2200-GEMCAPSRemoteLANMode   	OBJECT-TYPE
						SYNTAX		INTEGER {mode1000Base-X-auto(1),
                          					mode1000Base-X-Force(2),
                          					auto-10-100-1000T(3),
                          					mode1000Base-T-full(4),
                          					mode100Base-T-full(5),
                          					mode100Base-T-Half(6),
                          					mode10Base-T-full(7),
                          					mode10Base-T-Half(8), noremotecard(0)}
						MAX-ACCESS		read-write
						STATUS			current
						DESCRIPTION
                        "GEMC3 Local card's LAN port Mode configuration,
                    	set INTEGER(1) to 1000Base-X-auto,
                    	set INTEGER(2) to 1000Base-X-Force,
                    	set INTEGER(3) to auto-10-100-1000T,
                    	set INTEGER(4) to 1000Base-T-full,
                    	set INTEGER(5) to 100Base-T-full,
                    	set INTEGER(6) to 100Base-T-Half,
                    	set INTEGER(7) to 10Base-T-full,
                    	set INTEGER(8) to 10Base-T-Half,
                    	Ohter value is invalid"
						::= { mc2200-GEMCAPSEntry  50 }
mc2200-GEMCAPSRemoteIPAddress  OBJECT-TYPE
        			SYNTAX      IpAddress
        			ACCESS      read-write
        			STATUS      mandatory
	    			DESCRIPTION
            		"The IP address to GEMCAPS Remote IP ping."
        			::= {mc2200-GEMCAPSEntry 51}

mc2200-GEMCAPSRemoteSubnetMask    OBJECT-TYPE
        			SYNTAX      IpAddress
        			ACCESS      read-write
        			STATUS      mandatory
	    			DESCRIPTION
                    "The Net mask to  GEMCAPS Remote IP ping."
        			::= {mc2200-GEMCAPSEntry 52}

mc2200-GEMCAPSRemoteGateWay    OBJECT-TYPE
        			SYNTAX      IpAddress
        			ACCESS      read-write
        			STATUS      mandatory
	   				 DESCRIPTION
                    "The gateware to GEMCAPS Remote IP ping."
        			::= {mc2200-GEMCAPSEntry 53}

mc2200-GEMCAPSRemoteVLANEnable  OBJECT-TYPE
        			SYNTAX      INTEGER {enable(1),disable(2), noremotecard(0)}
        			ACCESS      read-write
        			STATUS      mandatory
	    			DESCRIPTION
                    "Enable or disable Remote GEMCAPS IP ping 802.1Q VLAN."
        			::= {mc2200-GEMCAPSEntry 54}
mc2200-GEMCAPSRemoteVID  OBJECT-TYPE
        			SYNTAX      INTEGER
        			ACCESS      read-write
        			STATUS      mandatory
	    			DESCRIPTION
                    "GEMCAPS Remote IP ping  802.1Q VLAN ID."
        			::= {mc2200-GEMCAPSEntry 55}
mc2200-GEMCAPSRemoteAlarm      OBJECT-TYPE
						SYNTAX			INTEGER  {enabled(1),disabled(2)}
						MAX-ACCESS		read-write
						STATUS			current
						DESCRIPTION
                        "Enable or disable GEMCAPS Media converter card remote alarm.
                         set INTEGER(1) to Enable remote alarm,
                         set INTEGER(2) to Disable remote alarm,
                         Other value is invalid."
						::= { mc2200-GEMCAPSEntry 56 }
mc2200-GEMCAPSRFD		      OBJECT-TYPE
						SYNTAX			INTEGER  {enabled(1),disabled(2)}
						MAX-ACCESS		read-write
						STATUS			current
						DESCRIPTION
                        "GEMCAPS Media converter card remote fault detect operation.
                         set INTEGER(1) to Enable RFD,
                         set INTEGER(2) to Disable RFD,
                         Other value is invalid."
						::= { mc2200-GEMCAPSEntry 57 }
mc2200-GEMCAPSDefault		OBJECT-TYPE
						SYNTAX			INTEGER
						MAX-ACCESS		write-only
						STATUS			current
						DESCRIPTION
                        "Write GEMCAPS card default setting,
                        set INTEGER(1) to write default.
                        Other value is invalid."
						::= { mc2200-GEMCAPSEntry 58 }
mc2200-GEMCAPSReboot		OBJECT-TYPE
						SYNTAX			INTEGER
						MAX-ACCESS		write-only
						STATUS			current
						DESCRIPTION
                        "Reboot GEMCAPS local card,
                        set INTEGER(1) to reboot this card.
                        Other value is invalid. "
						::= { mc2200-GEMCAPSEntry 59 }
mc2200-GEMCAPSLocalLANSpeed      OBJECT-TYPE
						SYNTAX			INTEGER {speed1000M(1),
						                         speed100M(2),speed10M(3),down(4)}
						MAX-ACCESS		read-only
						STATUS			mandatory
						DESCRIPTION
                        "GE-MC2 Local card's LAN port work speed status."
						::= { mc2200-GEMCAPSEntry 60 }
mc2200-GEMCAPSRemoteLANSpeed      OBJECT-TYPE
						SYNTAX			INTEGER {speed1000M(1),speed100M(2),
						                         speed10M(3),down(4),noremotecard(0)}
						MAX-ACCESS		read-only
						STATUS			mandatory
						DESCRIPTION
                        "GE-MC2 Remote card's LAN port work speed status."
						::= { mc2200-GEMCAPSEntry 61 }

mc2200-GEMCAPSLocalportuser      OBJECT-TYPE
						SYNTAX			DisplayString
						MAX-ACCESS		read-write
						STATUS			current
						DESCRIPTION
                        " User of GEMCAPS Local Port1. "
						::= { mc2200-GEMCAPSEntry 62 }

mc2200-GEMCAPSRemoteportuser      OBJECT-TYPE
						SYNTAX			DisplayString
						MAX-ACCESS		read-write
						STATUS			current
						DESCRIPTION
                        " User of GEMCAPS Remote Port1. "
						::= { mc2200-GEMCAPSEntry 63 }

mc2200-GEMCAPSRevertive        OBJECT-TYPE
						SYNTAX			INTEGER  {revertive(1),norevertive(2)}
						MAX-ACCESS		read-write
						STATUS			current
						DESCRIPTION
                        "GEMCAPS Media converter card Revertive operation.
                         set INTEGER(1) to Enable Revertive,
                         set INTEGER(2) to Enable No-Revertive,
                         Other value is invalid."
						::= { mc2200-GEMCAPSEntry 64 }

mc2200-GEMCAPSWAN1OpticalPowerCheck        OBJECT-TYPE
						SYNTAX			INTEGER  {enabled(1),disabled(2),aps(3)}
						MAX-ACCESS		read-write
						STATUS			current
						DESCRIPTION
                        "GEMCAPS Media converter card WAN1 OpticalPowerCheck operation.
                         set INTEGER(1) to Enable OpticalPowerCheck,
                         set INTEGER(2) to Disable OpticalPowerCheck,
                         set INTEGER(3) to APS,
                         Other value is invalid."
						::= { mc2200-GEMCAPSEntry 65 }

mc2200-GEMCAPSWAN1Threshold        OBJECT-TYPE
						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GEMCAPS Media converter card wan1 Threshold operation.
                         Other value is invalid."
						::= { mc2200-GEMCAPSEntry 66 }

mc2200-GEMCAPSWAN2OpticalPowerCheck        OBJECT-TYPE
						SYNTAX			INTEGER  {enabled(1),disabled(2),aps(3)}
						MAX-ACCESS		read-write
						STATUS			current
						DESCRIPTION
                        "GEMCAPS Media converter card WAN2 OpticalPowerCheck operation.
                         set INTEGER(1) to Enable OpticalPowerCheck,
                         set INTEGER(2) to Disable OpticalPowerCheck,
                         set INTEGER(3) to APS,
                         Other value is invalid."
						::= { mc2200-GEMCAPSEntry 67 }

mc2200-GEMCAPSWAN2Threshold        OBJECT-TYPE
						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GEMCAPS Media converter card wan2 Threshold operation.
                         Other value is invalid."
						::= { mc2200-GEMCAPSEntry 68 }
mc2200-GEMCAPSTrapFilterLocalLAN	        OBJECT-TYPE
						SYNTAX			INTEGER {enabled(1),disabled(2)}
						MAX-ACCESS		read-write
						STATUS			current
						DESCRIPTION
                            "Local LAN of GEMCAPS Trap Filter ."
						::= { mc2200-GEMCAPSEntry 69 }
mc2200-GEMCAPSTrapFilterLocalWAN	        OBJECT-TYPE
						SYNTAX			INTEGER {enabled(1),disabled(2)}
						MAX-ACCESS		read-write
						STATUS			current
						DESCRIPTION
                            "Local WAN of GEMCAPS Trap Filter ."
						::= { mc2200-GEMCAPSEntry 70 }
mc2200-GEMCAPSTrapFilterRemotePower	        OBJECT-TYPE
						SYNTAX			INTEGER {enabled(1),disabled(2)}
						MAX-ACCESS		read-write
						STATUS			current
						DESCRIPTION
                            "Remote Power of GEMCAPS Trap Filter ."
						::= { mc2200-GEMCAPSEntry 71 }
mc2200-GEMCAPSTrapFilterRemoteLAN	        OBJECT-TYPE
						SYNTAX			INTEGER {enabled(1),disabled(2)}
						MAX-ACCESS		read-write
						STATUS			current
						DESCRIPTION
                            "Remote LAN of GEMCAPS Trap Filter ."
						::= { mc2200-GEMCAPSEntry 72 }
mc2200-GEMCAPSTrapFilterRemoteWAN	        OBJECT-TYPE
						SYNTAX			INTEGER {enabled(1),disabled(2)}
						MAX-ACCESS		read-write
						STATUS			current
						DESCRIPTION
                            "Remote WAN of GEMCAPS Trap Filter ."
						::= { mc2200-GEMCAPSEntry 73 }

mc2200-GEMCAPSLoopback      OBJECT-TYPE
						SYNTAX			INTEGER {disable(1),local_lanouter(2),local_laninner(3),local_wanouter(4),
												local_waninner(5),remote_lanouter(6),remote_laninner(7)}
						MAX-ACCESS		read-write
						STATUS			mandatory
						DESCRIPTION
                            "GEMCAPS card's loopback."
						::= { mc2200-GEMCAPSEntry 74 }
mc2200-GEMCAPSCardType	OBJECT-TYPE
						SYNTAX		DisplayString
						MAX-ACCESS		read-only
						STATUS			current
						DESCRIPTION
                            "GEMCAPS card's Type."
						::= { mc2200-GEMCAPSEntry 75 }


-- OAPS Table  ====================================================

mc2200-OAPSTable	   OBJECT-TYPE
					SYNTAX			SEQUENCE OF MC2200-OAPSEntry
					MAX-ACCESS		not-accessible
					STATUS			current
					DESCRIPTION
                   "Sparse table containing one entry for each OAPS
                     10/100Mbps Twisted-Pair to Fiber Ethernet Media Converter
                     in the system, indexed by chassisIndex and slotIndex."

					::= { mc2200-GEmib 16 }

mc2200-OAPSEntry			OBJECT-TYPE
						SYNTAX			MC2200-OAPSEntry
						MAX-ACCESS		not-accessible
						STATUS			current
						DESCRIPTION
            "One table entry per slot in the media converter chassis.
             If physical slot 'n' contains a powered OAPS media
             converter, then entry 'n' in this table exists and describes
             the state of the converter's lamps  If slot 'n' is empty, does
             not exist, or contains a different type of device, then table
             entry 'n' does not exist."

						INDEX			{ mc2200-OAPSCardIndex }
						::= { mc2200-OAPSTable 1 }






-- ==========================
-- CH-unit config info table --
-- ==========================
MC2200-OAPSEntry ::=
				SEQUENCE {
					mc2200-OAPSCardIndex			    INTEGER,	-- 1
					mc2200-OAPSLocalLANLink          	INTEGER,
					mc2200-OAPSLocalLANPower          	DisplayString,
					mc2200-OAPSLocalLANThreshold    	INTEGER,
					mc2200-OAPSLocalWAN1Link          	INTEGER,
					mc2200-OAPSLocalWAN1Power       	DisplayString,
					mc2200-OAPSLocalWAN1Threshold 	INTEGER,
					mc2200-OAPSLocalWAN2Link          	INTEGER,
					mc2200-OAPSLocalWAN2Power       	DisplayString,
					mc2200-OAPSLocalWAN2Threshold 	INTEGER,
					mc2200-OAPSLocalActivePort          	INTEGER,
					mc2200-OAPSRevertive          	INTEGER,
					mc2200-OAPSDefault					INTEGER,
					mc2200-OAPSReboot					INTEGER, -- 55
					mc2200-OAPSLocalportuser     DisplayString,
					mc2200-OAPSRemoteportuser    DisplayString,
					mc2200-OAPSUsingActiveport    DisplayString,		   -- 60
					mc2200-OAPSTrapFilterLocalLAN			INTEGER,
					mc2200-OAPSTrapFilterLocalWAN			INTEGER
				}


mc2200-OAPSCardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-OAPSEntry 1 }
mc2200-OAPSLocalLANLink      OBJECT-TYPE
						SYNTAX			INTEGER {up(1),
						                         down(2)}
						MAX-ACCESS		read-only
						STATUS			mandatory
						DESCRIPTION
                            "OAPS Local card's LAN port work link status."
						::= { mc2200-OAPSEntry 2 }
mc2200-OAPSLocalLANPower      OBJECT-TYPE
						SYNTAX			DisplayString
						MAX-ACCESS		read-only
						STATUS			mandatory
						DESCRIPTION
                            "OAPS Local card's LAN port work link status."
						::= { mc2200-OAPSEntry 3 }
mc2200-OAPSLocalLANThreshold      OBJECT-TYPE
						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			mandatory
						DESCRIPTION
                            "OAPS Local card's LAN port work link status."
						::= { mc2200-OAPSEntry 4 }
mc2200-OAPSLocalWAN1Link      OBJECT-TYPE
						SYNTAX			INTEGER {up(1),
						                         down(2),
									 active(3),
						                         standby(4)}
						MAX-ACCESS		read-only
						STATUS			mandatory
						DESCRIPTION
                            "OAPS Local card's LAN port work link status."
						::= { mc2200-OAPSEntry 5 }
mc2200-OAPSLocalWAN1Power      OBJECT-TYPE
						SYNTAX			DisplayString
						MAX-ACCESS		read-only
						STATUS			mandatory
						DESCRIPTION
                            "OAPS Local card's LAN port work link status."
						::= { mc2200-OAPSEntry 6 }
mc2200-OAPSLocalWAN1Threshold      OBJECT-TYPE
						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			mandatory
						DESCRIPTION
                            "OAPS Local card's LAN port work link status."
						::= { mc2200-OAPSEntry 7 }
mc2200-OAPSLocalWAN2Link      OBJECT-TYPE
						SYNTAX			INTEGER {up(1),
						                         down(2),
									 active(3),
						                         standby(4)}
						MAX-ACCESS		read-only
						STATUS			mandatory
						DESCRIPTION
                            "OAPS Local card's LAN port work link status."
						::= { mc2200-OAPSEntry 8 }
mc2200-OAPSLocalWAN2Power      OBJECT-TYPE
						SYNTAX			DisplayString
						MAX-ACCESS		read-only
						STATUS			mandatory
						DESCRIPTION
                            "OAPS Local card's LAN port work link status."
						::= { mc2200-OAPSEntry 9 }
mc2200-OAPSLocalWAN2Threshold      OBJECT-TYPE
						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			mandatory
						DESCRIPTION
                            "OAPS Local card's LAN port work link status."
						::= { mc2200-OAPSEntry 10 }
mc2200-OAPSLocalActivePort	        OBJECT-TYPE
						SYNTAX			INTEGER {wan1(1),
						                         wan2(2)}
						MAX-ACCESS		read-write
						STATUS			current
						DESCRIPTION
                            "OAPS Local card's WAN port work link status."
						::= { mc2200-OAPSEntry 11 }
mc2200-OAPSRevertive	        OBJECT-TYPE
						SYNTAX			INTEGER {revertive(1),
						                         norevertive(2)}
						MAX-ACCESS		read-write
						STATUS			current
						DESCRIPTION
                            "OAPS Local card's WAN port work link status."
						::= { mc2200-OAPSEntry 12 }

mc2200-OAPSDefault		OBJECT-TYPE
						SYNTAX			INTEGER
						MAX-ACCESS		write-only
						STATUS			current
						DESCRIPTION
                        "Write OAPS card default setting,
                        set INTEGER(1) to write default.
                        Other value is invalid."
						::= { mc2200-OAPSEntry 13 }
mc2200-OAPSReboot		OBJECT-TYPE
						SYNTAX			INTEGER
						MAX-ACCESS		write-only
						STATUS			current
						DESCRIPTION
                        "Reboot OAPS local card,
                        set INTEGER(1) to reboot this card.
                        Other value is invalid. "
						::= { mc2200-OAPSEntry 14 }

mc2200-OAPSLocalportuser      OBJECT-TYPE
						SYNTAX			DisplayString
						MAX-ACCESS		read-write
						STATUS			current
						DESCRIPTION
                        " User of OAPS Local Port1. "
						::= { mc2200-OAPSEntry 15 }

mc2200-OAPSRemoteportuser      OBJECT-TYPE
						SYNTAX			DisplayString
						MAX-ACCESS		read-write
						STATUS			current
						DESCRIPTION
                        " User of OAPS Remote Port1. "
						::= { mc2200-OAPSEntry 16 }
mc2200-OAPSUsingActiveport      OBJECT-TYPE
						SYNTAX			DisplayString
						MAX-ACCESS		read-only
						STATUS			current
						DESCRIPTION
                        " OAPS using active port. "
						::= { mc2200-OAPSEntry 17 }
mc2200-OAPSTrapFilterLocalLAN	        OBJECT-TYPE
						SYNTAX			INTEGER {enabled(1),disabled(2)}
						MAX-ACCESS		read-write
						STATUS			current
						DESCRIPTION
                            "Local LAN of OAPS Trap Filter ."
						::= { mc2200-OAPSEntry 18 }
mc2200-OAPSTrapFilterLocalWAN	        OBJECT-TYPE
						SYNTAX			INTEGER {enabled(1),disabled(2)}
						MAX-ACCESS		read-write
						STATUS			current
						DESCRIPTION
                            "Local WAN of OAPS Trap Filter ."
						::= { mc2200-OAPSEntry 19 }


-- QS2204 Table  ====================================================

mc2200-QS2204Table	   OBJECT-TYPE
					SYNTAX			SEQUENCE OF MC2200-QS2204Entry
					MAX-ACCESS		not-accessible
					STATUS			current
					DESCRIPTION
                   "Sparse table containing one entry for each 2204-QS
                     10/100Mbps Twisted-Pair to Fiber Ethernet Media Converter
                     in the system, indexed by chassisIndex and slotIndex."

					::= { mc2200-GEmib 17 }

mc2200-QS2204Entry			OBJECT-TYPE
						SYNTAX			MC2200-QS2204Entry
						MAX-ACCESS		not-accessible
						STATUS			current
						DESCRIPTION
            "One table entry per slot in the media converter chassis.
             If physical slot 'n' contains a powered 2204-QS media
             converter, then entry 'n' in this table exists and describes
             the state of the converter's lamps  If slot 'n' is empty, does
             not exist, or contains a different type of device, then table
             entry 'n' does not exist."

						INDEX			{ mc2200-QS2204CardIndex }
						::= { mc2200-QS2204Table 1 }






-- ==========================
-- CH-unit config info table --
-- ==========================
MC2200-QS2204Entry ::=
				SEQUENCE {
					mc2200-QS2204CardIndex			    INTEGER,	-- 1
					mc2200-QS2204LocalLAN1Link          	INTEGER,
					mc2200-QS2204LocalLAN1TxStatus          	INTEGER,
					mc2200-QS2204LocalLAN1SFPInfo          	DisplayString,
					mc2200-QS2204LocalLAN1Loopback          	INTEGER,
					mc2200-QS2204LocalLAN2Link          	INTEGER,
					mc2200-QS2204LocalLAN2TxStatus          	INTEGER,
					mc2200-QS2204LocalLAN2SFPInfo          	DisplayString,
					mc2200-QS2204LocalLAN2Loopback          	INTEGER,
					mc2200-QS2204LocalLAN3Link          	INTEGER,   -- 10
					mc2200-QS2204LocalLAN3TxStatus          	INTEGER,
					mc2200-QS2204LocalLAN3SFPInfo          	DisplayString,
					mc2200-QS2204LocalLAN3Loopback          	INTEGER,
					mc2200-QS2204LocalLAN4Link          	INTEGER,
					mc2200-QS2204LocalLAN4TxStatus          	INTEGER,
					mc2200-QS2204LocalLAN4SFPInfo          	DisplayString,
					mc2200-QS2204LocalLAN4Loopback          	INTEGER,
					mc2200-QS2204LocalWANLink          	DisplayString,
					mc2200-QS2204LocalWANTxStatus          	DisplayString,
					mc2200-QS2204LocalWANSFPInfo          	DisplayString,   -- 20
					mc2200-QS2204LocalWANLoopback          	INTEGER,
                    mc2200-QS2204RFD						INTEGER,
                    mc2200-QS2204Default					INTEGER,
                    mc2200-QS2204Reboot					INTEGER,
					mc2200-QS2204LocalLAN1user     DisplayString,
					mc2200-QS2204LocalLAN2user     DisplayString,
					mc2200-QS2204LocalLAN3user     DisplayString,
		    		mc2200-QS2204LocalLAN4user    DisplayString		   -- 28
				}


mc2200-QS2204CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-QS2204Entry 1 }

mc2200-QS2204LocalLAN1Link      OBJECT-TYPE
						SYNTAX			INTEGER {up(1),
						                         down(2)}
						MAX-ACCESS		read-only
						STATUS			mandatory
						DESCRIPTION
                            "2204-QS Local card's LAN1 port work link status."
						::= { mc2200-QS2204Entry 2 }

mc2200-QS2204LocalLAN1TxStatus      OBJECT-TYPE
						SYNTAX			INTEGER {on(1),
						                         off(2)}
						MAX-ACCESS		read-only
						STATUS			mandatory
						DESCRIPTION
                            "2204-QS Local card's LAN1 TX status."
						::= { mc2200-QS2204Entry 3 }

mc2200-QS2204LocalLAN1SFPInfo      OBJECT-TYPE
						SYNTAX			DisplayString
						MAX-ACCESS		read-only
						STATUS			mandatory
						DESCRIPTION
                            "2204-QS Local card's LAN1 SFP information."
						::= { mc2200-QS2204Entry 4 }

mc2200-QS2204LocalLAN1Loopback      OBJECT-TYPE
						SYNTAX			INTEGER {enable(1),
						                         disable(2)}
						MAX-ACCESS		read-write
						STATUS			mandatory
						DESCRIPTION
                            "2204-QS Local card's LAN1 loopback."
						::= { mc2200-QS2204Entry 5 }

mc2200-QS2204LocalLAN2Link      OBJECT-TYPE
						SYNTAX			INTEGER {up(1),
						                         down(2)}
						MAX-ACCESS		read-only
						STATUS			mandatory
						DESCRIPTION
                            "2204-QS Local card's LAN2 port work link status."
						::= { mc2200-QS2204Entry 6 }

mc2200-QS2204LocalLAN2TxStatus      OBJECT-TYPE
						SYNTAX			INTEGER {on(1),
						                         off(2)}
						MAX-ACCESS		read-only
						STATUS			mandatory
						DESCRIPTION
                            "2204-QS Local card's LAN2 TX status."
						::= { mc2200-QS2204Entry 7 }

mc2200-QS2204LocalLAN2SFPInfo      OBJECT-TYPE
						SYNTAX			DisplayString
						MAX-ACCESS		read-only
						STATUS			mandatory
						DESCRIPTION
                            "2204-QS Local card's LAN2 SFP information."
						::= { mc2200-QS2204Entry 8 }

mc2200-QS2204LocalLAN2Loopback      OBJECT-TYPE
						SYNTAX			INTEGER {enable(1),
						                         disable(2)}
						MAX-ACCESS		read-write
						STATUS			mandatory
						DESCRIPTION
                            "2204-QS Local card's LAN2 loopback."
						::= { mc2200-QS2204Entry 9 }

mc2200-QS2204LocalLAN3Link      OBJECT-TYPE
						SYNTAX			INTEGER {up(1),
						                         down(2)}
						MAX-ACCESS		read-only
						STATUS			mandatory
						DESCRIPTION
                            "2204-QS Local card's LAN3 port work link status."
						::= { mc2200-QS2204Entry 10 }

mc2200-QS2204LocalLAN3TxStatus      OBJECT-TYPE
						SYNTAX			INTEGER {on(1),
						                         off(2)}
						MAX-ACCESS		read-only
						STATUS			mandatory
						DESCRIPTION
                            "2204-QS Local card's LAN3 TX status."
						::= { mc2200-QS2204Entry 11 }

mc2200-QS2204LocalLAN3SFPInfo      OBJECT-TYPE
						SYNTAX			DisplayString
						MAX-ACCESS		read-only
						STATUS			mandatory
						DESCRIPTION
                            "2204-QS Local card's LAN3 SFP information."
						::= { mc2200-QS2204Entry 12 }

mc2200-QS2204LocalLAN3Loopback      OBJECT-TYPE
						SYNTAX			INTEGER {enable(1),
						                         disable(2)}
						MAX-ACCESS		read-write
						STATUS			mandatory
						DESCRIPTION
                            "2204-QS Local card's LAN3 loopback."
						::= { mc2200-QS2204Entry 13 }

mc2200-QS2204LocalLAN4Link      OBJECT-TYPE
						SYNTAX			INTEGER {up(1),
						                         down(2)}
						MAX-ACCESS		read-only
						STATUS			mandatory
						DESCRIPTION
                            "2204-QS Local card's LAN4 port work link status."
						::= { mc2200-QS2204Entry 14 }

mc2200-QS2204LocalLAN4TxStatus      OBJECT-TYPE
						SYNTAX			INTEGER {on(1),
						                         off(2)}
						MAX-ACCESS		read-only
						STATUS			mandatory
						DESCRIPTION
                            "2204-QS Local card's LAN4 TX status."
						::= { mc2200-QS2204Entry 15 }

mc2200-QS2204LocalLAN4SFPInfo      OBJECT-TYPE
						SYNTAX			DisplayString
						MAX-ACCESS		read-only
						STATUS			mandatory
						DESCRIPTION
                            "2204-QS Local card's LAN4 SFP information."
						::= { mc2200-QS2204Entry 16 }

mc2200-QS2204LocalLAN4Loopback      OBJECT-TYPE
						SYNTAX			INTEGER {enable(1),
						                         disable(2)}
						MAX-ACCESS		read-write
						STATUS			mandatory
						DESCRIPTION
                            "2204-QS Local card's LAN4 loopback."
						::= { mc2200-QS2204Entry 17 }

mc2200-QS2204LocalWANLink      OBJECT-TYPE
						SYNTAX			DisplayString
						MAX-ACCESS		read-only
						STATUS			mandatory
						DESCRIPTION
                            "2204-QS Local card's WAN port work link status."
						::= { mc2200-QS2204Entry 18 }

mc2200-QS2204LocalWANTxStatus      OBJECT-TYPE
						SYNTAX			DisplayString
						MAX-ACCESS		read-only
						STATUS			mandatory
						DESCRIPTION
                            "2204-QS Local card's WAN TX status."
						::= { mc2200-QS2204Entry 19 }

mc2200-QS2204LocalWANSFPInfo      OBJECT-TYPE
						SYNTAX			DisplayString
						MAX-ACCESS		read-only
						STATUS			mandatory
						DESCRIPTION
                            "2204-QS Local card's WAN SFP information."
						::= { mc2200-QS2204Entry 20 }

mc2200-QS2204LocalWANLoopback      OBJECT-TYPE
						SYNTAX			INTEGER {enable(1),
						                         disable(2)}
						MAX-ACCESS		read-write
						STATUS			mandatory
						DESCRIPTION
                            "2204-QS Local card's WAN loopback."
						::= { mc2200-QS2204Entry 21 }

mc2200-QS2204RFD		        OBJECT-TYPE
						SYNTAX			INTEGER {enable(1),
						                         disable(2)}
						MAX-ACCESS		read-write
						STATUS			current
						DESCRIPTION
                            "2204-QS Local card's WAN port work link status."
						::= { mc2200-QS2204Entry 22 }

mc2200-QS2204Default		OBJECT-TYPE
						SYNTAX			INTEGER
						MAX-ACCESS		write-only
						STATUS			current
						DESCRIPTION
                        "Write 2204-QS card default setting,
                        set INTEGER(1) to write default.
                        Other value is invalid."
						::= { mc2200-QS2204Entry 23 }
mc2200-QS2204Reboot		OBJECT-TYPE
						SYNTAX			INTEGER
						MAX-ACCESS		write-only
						STATUS			current
						DESCRIPTION
                        "Reboot 2204-QS local card,
                        set INTEGER(1) to reboot this card.
                        Other value is invalid. "
						::= { mc2200-QS2204Entry 24 }

mc2200-QS2204LocalLAN1user      OBJECT-TYPE
						SYNTAX			DisplayString
						MAX-ACCESS		read-write
						STATUS			current
						DESCRIPTION
                        " User of 2204-QS Local LAN1. "
						::= { mc2200-QS2204Entry 25 }

mc2200-QS2204LocalLAN2user      OBJECT-TYPE
						SYNTAX			DisplayString
						MAX-ACCESS		read-write
						STATUS			current
						DESCRIPTION
                        " User of 2204-QS Local LAN2. "
						::= { mc2200-QS2204Entry 26 }

mc2200-QS2204LocalLAN3user      OBJECT-TYPE
						SYNTAX			DisplayString
						MAX-ACCESS		read-write
						STATUS			current
						DESCRIPTION
                        " User of 2204-QS Local LAN3. "
						::= { mc2200-QS2204Entry 27 }

mc2200-QS2204LocalLAN4user      OBJECT-TYPE
						SYNTAX			DisplayString
						MAX-ACCESS		read-write
						STATUS			current
						DESCRIPTION
                        " User of 2204-QS Local LAN4. "
						::= { mc2200-QS2204Entry 28 }

-- Q2202 Table  ====================================================

mc2200-Q2202Table	   OBJECT-TYPE
					SYNTAX			SEQUENCE OF MC2200-Q2202Entry
					MAX-ACCESS		not-accessible
					STATUS			current
					DESCRIPTION
                   "Sparse table containing one entry for each 2202-Q
                     100G Fiber Ethernet Media Converter
                     in the system, indexed by chassisIndex and slotIndex."

					::= { mc2200-GEmib 18 }

mc2200-Q2202Entry			OBJECT-TYPE
						SYNTAX			MC2200-Q2202Entry
						MAX-ACCESS		not-accessible
						STATUS			current
						DESCRIPTION
            "One table entry per slot in the media converter chassis.
             If physical slot 'n' contains a powered 2202-Q media
             converter, then entry 'n' in this table exists and describes
             the state of the converter's lamps  If slot 'n' is empty, does
             not exist, or contains a different type of device, then table
             entry 'n' does not exist."

						INDEX			{ mc2200-Q2202CardIndex }
						::= { mc2200-Q2202Table 1 }






-- ==========================
-- CH-unit config info table --
-- ==========================
MC2200-Q2202Entry ::=
				SEQUENCE {
					mc2200-Q2202CardIndex			    INTEGER,	-- 1
					mc2200-Q2202LocalLANLink          	INTEGER,
					mc2200-Q2202LocalLANTxStatus          	DisplayString,
					mc2200-Q2202LocalLANSFPInfo          	DisplayString,
					mc2200-Q2202LocalWANLink          	INTEGER,
					mc2200-Q2202LocalWANTxStatus          	DisplayString,
					mc2200-Q2202LocalWANSFPInfo          	DisplayString,   -- 7
					mc2200-Q2202Loopback          		INTEGER,
                    mc2200-Q2202RFD						INTEGER,
                    mc2200-Q2202Default					INTEGER,
                    mc2200-Q2202Reboot					INTEGER,
					mc2200-Q2202LocalLANuser     		DisplayString, -- 12
					mc2200-Q2202Rate     				INTEGER
				}


mc2200-Q2202CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-Q2202Entry 1 }

mc2200-Q2202LocalLANLink      OBJECT-TYPE
						SYNTAX			INTEGER {up(1),
						                         down(2)}
						MAX-ACCESS		read-only
						STATUS			mandatory
						DESCRIPTION
                            "2202-Q Local card's LAN port work link status."
						::= { mc2200-Q2202Entry 2 }

mc2200-Q2202LocalLANTxStatus      OBJECT-TYPE
						SYNTAX			DisplayString
						MAX-ACCESS		read-only
						STATUS			mandatory
						DESCRIPTION
                            "2202-Q Local card's LAN TX status."
						::= { mc2200-Q2202Entry 3 }

mc2200-Q2202LocalLANSFPInfo      OBJECT-TYPE
						SYNTAX			DisplayString
						MAX-ACCESS		read-only
						STATUS			mandatory
						DESCRIPTION
                            "2202-QS Local card's LAN SFP information."
						::= { mc2200-Q2202Entry 4 }


mc2200-Q2202LocalWANLink      OBJECT-TYPE
						SYNTAX			INTEGER {up(1),
						                         down(2)}
						MAX-ACCESS		read-only
						STATUS			mandatory
						DESCRIPTION
                            "2202-Q Local card's WAN port work link status."
						::= { mc2200-Q2202Entry 5 }

mc2200-Q2202LocalWANTxStatus      OBJECT-TYPE
						SYNTAX			DisplayString
						MAX-ACCESS		read-only
						STATUS			mandatory
						DESCRIPTION
                            "2202-Q Local card's WAN TX status."
						::= { mc2200-Q2202Entry 6 }

mc2200-Q2202LocalWANSFPInfo      OBJECT-TYPE
						SYNTAX			DisplayString
						MAX-ACCESS		read-only
						STATUS			mandatory
						DESCRIPTION
                            "2202-Q Local card's WAN SFP information."
						::= { mc2200-Q2202Entry 7 }

mc2200-Q2202Loopback      OBJECT-TYPE
						SYNTAX			INTEGER {enable(1),
						                         disable(2)}
						MAX-ACCESS		read-write
						STATUS			mandatory
						DESCRIPTION
                            "2202-Q card's loopback."
						::= { mc2200-Q2202Entry 8 }

mc2200-Q2202RFD		        OBJECT-TYPE
						SYNTAX			INTEGER {enable(1),
						                         disable(2)}
						MAX-ACCESS		read-write
						STATUS			current
						DESCRIPTION
                            "2202-Q card's RFD status."
						::= { mc2200-Q2202Entry 9 }

mc2200-Q2202Default		OBJECT-TYPE
						SYNTAX			INTEGER
						MAX-ACCESS		write-only
						STATUS			current
						DESCRIPTION
                        "Write 2202-Q card default setting,
                        set INTEGER(1) to write default.
                        Other value is invalid."
						::= { mc2200-Q2202Entry 10 }
mc2200-Q2202Reboot		OBJECT-TYPE
						SYNTAX			INTEGER
						MAX-ACCESS		write-only
						STATUS			current
						DESCRIPTION
                        "Reboot 2202-Q local card,
                        set INTEGER(1) to reboot this card.
                        Other value is invalid. "
						::= { mc2200-Q2202Entry 11 }

mc2200-Q2202LocalLANuser      OBJECT-TYPE
						SYNTAX			DisplayString
						MAX-ACCESS		read-write
						STATUS			current
						DESCRIPTION
                        " User of 2202-Q Local LAN. "
						::= { mc2200-Q2202Entry 12 }

mc2200-Q2202Rate		        OBJECT-TYPE
						SYNTAX			INTEGER {rate40G(1),
						                         rate100G(2)}
						MAX-ACCESS		read-write
						STATUS			current
						DESCRIPTION
                            "2202-Q card's rate."
						::= { mc2200-Q2202Entry 13 }

-- GESFP2Entry Table  ====================================================

mc2200-GESFP2Table	   OBJECT-TYPE
					SYNTAX			SEQUENCE OF MC2200-GESFP2Entry
					MAX-ACCESS		not-accessible
					STATUS			current
					DESCRIPTION
                   "Sparse table containing one entry for each GESFP2
                     10/100Mbps Twisted-Pair to Fiber Ethernet Media Converter
                     in the system, indexed by chassisIndex and slotIndex."

					::= { mc2200-GEmib 19 }

mc2200-GESFP2Entry			OBJECT-TYPE
						SYNTAX			MC2200-GESFP2Entry
						MAX-ACCESS		not-accessible
						STATUS			current
						DESCRIPTION
            "One table entry per slot in the media converter chassis.
             If physical slot 'n' contains a powered GESFP2 media
             converter, then entry 'n' in this table exists and describes
             the state of the converter's lamps  If slot 'n' is empty, does
             not exist, or contains a different type of device, then table
             entry 'n' does not exist."

						INDEX			{ mc2200-GESFP2CardIndex }
						::= { mc2200-GESFP2Table 1 }






-- ==========================
-- CH-unit config info table --
-- ==========================
MC2200-GESFP2Entry ::=
				SEQUENCE {
					mc2200-GESFP2CardIndex			    INTEGER,	-- 1
					mc2200-GESFP2LocalTXLink          	INTEGER,
					mc2200-GESFP2LocalWANSFPInfo       DisplayString,
					mc2200-GESFP2LocalWANLink          INTEGER,
					mc2200-GESFP2LocalTXMode	      	INTEGER,
					mc2200-GESFP2LocalTXMDIX           INTEGER,
					mc2200-GESFP2RxGoodOctets        	Counter64,
                    mc2200-GESFP2RxBadOctets        		Counter64,
                    mc2200-GESFP2TxFCSErr        		Counter64,
					mc2200-GESFP2RxUnicast        		Counter64,
					mc2200-GESFP2TxDeferred        		Counter64,
                    mc2200-GESFP2RxBroadcasts        	Counter64,
                    mc2200-GESFP2RxMulticasts        	Counter64,
					mc2200-GESFP2Rx64Octets        	Counter64,
					mc2200-GESFP2Rx65to127Octets        	Counter64,
                    mc2200-GESFP2Rx128to255Octets        Counter64,
                    mc2200-GESFP2Rx256to511Octets        Counter64,
                    mc2200-GESFP2Rx512to1023Octets       Counter64,
					mc2200-GESFP2Rx1024toMaxOctets       Counter64,
					mc2200-GESFP2TxOctets        		Counter64,
                    mc2200-GESFP2TxUnicast        		Counter64,
					mc2200-GESFP2TxExcessive        		Counter64,
					mc2200-GESFP2TxMulticasts            Counter64,
                    mc2200-GESFP2TxBroadcasts        	Counter64,
                    mc2200-GESFP2TxSingle        		Counter64,
					mc2200-GESFP2TxPause        			Counter64,
					mc2200-GESFP2RxPause        			Counter64,
                    mc2200-GESFP2TxMultiple        		Counter64,
                    mc2200-GESFP2RxUndersize        		Counter64,
					mc2200-GESFP2RxFragments             Counter64,
					mc2200-GESFP2RxOversize              Counter64,
                    mc2200-GESFP2RxJabber        		Counter64,
                    mc2200-GESFP2RxErr        		    Counter64,
					mc2200-GESFP2RxFCSErr                Counter64,
					mc2200-GESFP2TxCollisions            Counter64,
                    mc2200-GESFP2TxLate        		    Counter64,
					mc2200-GESFP2RemoteWANSFPInfo       DisplayString,
					mc2200-GESFP2RemoteWANLink         INTEGER,
					mc2200-GESFP2RemotePort1Link       INTEGER,
		  	        mc2200-GESFP2RemotePort1Speed      INTEGER,
					mc2200-GESFP2RemotePort1Duplex     INTEGER,
					mc2200-GESFP2RemotePort1Mode	    INTEGER,
					mc2200-GESFP2RemotePort1MDIX       INTEGER,
					mc2200-GESFP2RemotePort2Link       INTEGER,
		  	        mc2200-GESFP2RemotePort2Speed      INTEGER,
					mc2200-GESFP2RemotePort2Duplex     INTEGER,
					mc2200-GESFP2RemotePort2Mode	    INTEGER,
					mc2200-GESFP2RemotePort2MDIX       INTEGER,
					mc2200-GESFP2RemotePort3Link       INTEGER,
		  	        mc2200-GESFP2RemotePort3Speed      INTEGER,
					mc2200-GESFP2RemotePort3Duplex     INTEGER,
					mc2200-GESFP2RemotePort3Mode	    INTEGER,
					mc2200-GESFP2RemotePort3MDIX       INTEGER,
					mc2200-GESFP2RemotePort4Link       INTEGER,
		  	        mc2200-GESFP2RemotePort4Speed      INTEGER,
					mc2200-GESFP2RemotePort4Duplex     INTEGER,
					mc2200-GESFP2RemotePort4Mode	    INTEGER,
					mc2200-GESFP2RemotePort4MDIX       INTEGER,
					mc2200-GESFP2RemotePort5Link       INTEGER,
		  	        mc2200-GESFP2RemotePort5Speed      INTEGER,
					mc2200-GESFP2RemotePort5Duplex     INTEGER,
					mc2200-GESFP2RemotePort5Mode	    INTEGER,
					mc2200-GESFP2RemotePort5MDIX       INTEGER,
					mc2200-GESFP2RemotePort6Link       INTEGER,
		  	        mc2200-GESFP2RemotePort6Speed      INTEGER,
					mc2200-GESFP2RemotePort6Duplex     INTEGER,
					mc2200-GESFP2RemotePort6Mode	    INTEGER,
					mc2200-GESFP2RemotePort6MDIX       INTEGER,
					mc2200-GESFP2RemotePort7Link       INTEGER,
		  	        mc2200-GESFP2RemotePort7Speed      INTEGER,
					mc2200-GESFP2RemotePort7Duplex     INTEGER,
					mc2200-GESFP2RemotePort7Mode	    INTEGER,
					mc2200-GESFP2RemotePort7MDIX       INTEGER,
					mc2200-GESFP2RemotePort8Link       INTEGER,
		  	        mc2200-GESFP2RemotePort8Speed      INTEGER,
					mc2200-GESFP2RemotePort8Duplex     INTEGER,
					mc2200-GESFP2RemotePort8Mode	    INTEGER,
					mc2200-GESFP2RemotePort8MDIX       INTEGER,
					mc2200-GESFP2RemotePort9Link       INTEGER,
		  	        mc2200-GESFP2RemotePort9Speed      INTEGER,
					mc2200-GESFP2RemotePort9Duplex     INTEGER,
					mc2200-GESFP2RemotePort9Mode	    INTEGER,
					mc2200-GESFP2RemotePort9SFPInfo       DisplayString,
					mc2200-GESFP2RemoteIPAddress       	IpAddress,
		  	        mc2200-GESFP2RemoteSubnetMask      	IpAddress,
					mc2200-GESFP2RemoteGateWay         	IpAddress,
					mc2200-GESFP2RemoteVLANEnable	    INTEGER,
					mc2200-GESFP2RemoteVID         		INTEGER,
                    mc2200-GESFP2RemoteAlarm      		INTEGER,
                    mc2200-GESFP2Default					INTEGER,
                    mc2200-GESFP2Reboot					INTEGER,
					mc2200-GESFP2LocalTXSpeed          INTEGER,
					mc2200-GESFP2RemoteLanIsolate          INTEGER,
					mc2200-GESFP2Localportuser       DisplayString,
					mc2200-GESFP2Remoteportuser1     DisplayString,
                    mc2200-GESFP2Remoteportuser2     DisplayString,
                    mc2200-GESFP2Remoteportuser3     DisplayString,
                    mc2200-GESFP2Remoteportuser4     DisplayString,
                    mc2200-GESFP2Remoteportuser5     DisplayString,
                    mc2200-GESFP2Remoteportuser6     DisplayString,
                    mc2200-GESFP2Remoteportuser7     DisplayString,
                    mc2200-GESFP2Remoteportuser8     DisplayString,
					mc2200-GESFP2Remoteportuser9     DisplayString,
					mc2200-GESFP2LocalTXDuplex	    		INTEGER,
					mc2200-GESFP2WANOpticalPowerCheck			INTEGER,
					mc2200-GESFP2WANThreshold			INTEGER,
					mc2200-GESFP2TrapFilterLocalLAN			INTEGER,
					mc2200-GESFP2TrapFilterLocalWAN			INTEGER,
					mc2200-GESFP2TrapFilterRemotePower		INTEGER,
					mc2200-GESFP2TrapFilterRemoteLAN		INTEGER,
					mc2200-GESFP2TrapFilterRemoteWAN		INTEGER,
					mc2200-GESFP2CardType		DisplayString,
					mc2200-GESFP2RemotePort1UpstreamBandwidth      INTEGER,
					mc2200-GESFP2RemotePort1DownstreamBandwidth      INTEGER,
					mc2200-GESFP2RemotePort2UpstreamBandwidth      INTEGER,
					mc2200-GESFP2RemotePort2DownstreamBandwidth      INTEGER,
					mc2200-GESFP2RemotePort3UpstreamBandwidth      INTEGER,
					mc2200-GESFP2RemotePort3DownstreamBandwidth      INTEGER,
					mc2200-GESFP2RemotePort4UpstreamBandwidth      INTEGER,
					mc2200-GESFP2RemotePort4DownstreamBandwidth      INTEGER,
					mc2200-GESFP2RemotePort5UpstreamBandwidth      INTEGER,
					mc2200-GESFP2RemotePort5DownstreamBandwidth      INTEGER,
					mc2200-GESFP2RemotePort6UpstreamBandwidth      INTEGER,
					mc2200-GESFP2RemotePort6DownstreamBandwidth      INTEGER,
					mc2200-GESFP2RemotePort7UpstreamBandwidth      INTEGER,
					mc2200-GESFP2RemotePort7DownstreamBandwidth      INTEGER,
					mc2200-GESFP2RemotePort8UpstreamBandwidth      INTEGER,
					mc2200-GESFP2RemotePort8DownstreamBandwidth      INTEGER,
					mc2200-GESFP2RemotePort9UpstreamBandwidth      INTEGER,
					mc2200-GESFP2RemotePort9DownstreamBandwidth      INTEGER
				}


mc2200-GESFP2CardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-GESFP2Entry 1 }
mc2200-GESFP2LocalTXLink      OBJECT-TYPE
						SYNTAX			INTEGER {up(1),
						                         down(2)}
						MAX-ACCESS		read-only
						STATUS			mandatory
						DESCRIPTION
                            "GESFP2Entry Local card's LAN port work link status."
						::= { mc2200-GESFP2Entry 2 }
mc2200-GESFP2LocalWANSFPInfo	OBJECT-TYPE
						SYNTAX		DisplayString
						MAX-ACCESS		read-only
						STATUS			current
						DESCRIPTION
                            "GESFP2Entry Local card's WAN port SFP infomation."
						::= { mc2200-GESFP2Entry 3 }
mc2200-GESFP2LocalWANLink	        OBJECT-TYPE
						SYNTAX			INTEGER {up(1),
						                         down(2)}
						MAX-ACCESS		read-only
						STATUS			current
						DESCRIPTION
                            "GESFP2Entry Local card's WAN port work link status."
						::= { mc2200-GESFP2Entry 4 }
mc2200-GESFP2LocalTXMode   	OBJECT-TYPE
						SYNTAX		INTEGER {auto-10-100-1000(1),
                          					mode1000F(2),
                          					mode100F(3),
                          					mode10F(4),
                          					mode100H(5),
                          					mode10H(6)}
						MAX-ACCESS		read-write
						STATUS			current
						DESCRIPTION
                        "GESFP2Entry Local card's LAN port Mode configuration,
                    	set INTEGER(1) to auto(10/100/1000),
                    	set INTEGER(2) to 1000F,
                    	set INTEGER(3) to 100F,
                    	set INTEGER(4) to 10F,
                    	set INTEGER(5) to 100H,
                    	set INTEGER(6) to 10H,
                    	Ohter value is invalid"
						::= { mc2200-GESFP2Entry  5 }
mc2200-GESFP2LocalTXMDIX   	OBJECT-TYPE
						SYNTAX		INTEGER {auto(1),
                          					mdi(2),
                          					mdiX(3)}
						MAX-ACCESS		read-write
						STATUS			current
						DESCRIPTION
                        "GESFP2Entry Local card's LAN port Mode configuration,
                    	set INTEGER(1) to auto,
                    	set INTEGER(2) to mdi,
                    	set INTEGER(3) to mdiX,
                    	Ohter value is invalid"
						::= { mc2200-GESFP2Entry  6 }

mc2200-GESFP2RxGoodOctets OBJECT-TYPE
						SYNTAX			Counter64
						MAX-ACCESS		read-only
						STATUS			current
						DESCRIPTION
                        "GESFP2Entry Local card's LAN port MIB RxGoodOctetsLow counter."
						::= { mc2200-GESFP2Entry 7 }

mc2200-GESFP2RxBadOctets OBJECT-TYPE
						SYNTAX			Counter64
						MAX-ACCESS		read-only
						STATUS			current
						DESCRIPTION
                        "GESFP Local card's LAN port MIB RxBadOctets counter."
						::= { mc2200-GESFP2Entry 8 }
mc2200-GESFP2TxFCSErr OBJECT-TYPE
						SYNTAX			Counter64
						MAX-ACCESS		read-only
						STATUS			current
						DESCRIPTION
                        "GESFP2Entry Local card's LAN port MIB  TxFCSErr counter."
						::= { mc2200-GESFP2Entry 9 }

mc2200-GESFP2RxUnicast OBJECT-TYPE
						SYNTAX			Counter64
						MAX-ACCESS		read-only
						STATUS			current
						DESCRIPTION
                        "GESFP2Entry Local card's LAN port MIB RxUnicast counter."
						::= { mc2200-GESFP2Entry 10 }
mc2200-GESFP2TxDeferred OBJECT-TYPE
						SYNTAX			Counter64
						MAX-ACCESS		read-only
						STATUS			current
						DESCRIPTION
                        "GESFP2Entry Local card's LAN port MIB TxDeferred counter."
						::= { mc2200-GESFP2Entry 11 }
mc2200-GESFP2RxBroadcasts OBJECT-TYPE
						SYNTAX			Counter64
						MAX-ACCESS		read-only
						STATUS			current
						DESCRIPTION
                        "GESFP2Entry Local card's LAN port MIB RxBroadcasts counter."
						::= { mc2200-GESFP2Entry 12 }
mc2200-GESFP2RxMulticasts OBJECT-TYPE
						SYNTAX			Counter64
						MAX-ACCESS		read-only
						STATUS			current
						DESCRIPTION
                        "GESFP2Entry Local card's LAN port MIB RxMulticasts counter."
						::= { mc2200-GESFP2Entry 13 }
mc2200-GESFP2Rx64Octets OBJECT-TYPE
						SYNTAX			Counter64
						MAX-ACCESS		read-only
						STATUS			current
						DESCRIPTION
                        "GESFP2Entry Local card's LAN port MIB Rx64Octets counter."
						::= { mc2200-GESFP2Entry 14 }
mc2200-GESFP2Rx65to127Octets OBJECT-TYPE
						SYNTAX			Counter64
						MAX-ACCESS		read-only
						STATUS			current
						DESCRIPTION
                        "GESFP2Entry Local card's LAN port MIB Rx65to127Octets counter."
						::= { mc2200-GESFP2Entry 15 }
mc2200-GESFP2Rx128to255Octets OBJECT-TYPE
						SYNTAX			Counter64
						MAX-ACCESS		read-only
						STATUS			current
						DESCRIPTION
                        "GESFP2Entry Local card's LAN port MIB Rx128to255Octets counter."
						::= { mc2200-GESFP2Entry 16 }
mc2200-GESFP2Rx256to511Octets OBJECT-TYPE
						SYNTAX			Counter64
						MAX-ACCESS		read-only
						STATUS			current
						DESCRIPTION
                        "GESFP2Entry Local card's LAN port MIB Rx256to511Octets counter."
						::= { mc2200-GESFP2Entry 17 }
mc2200-GESFP2Rx512to1023Octets OBJECT-TYPE
						SYNTAX			Counter64
						MAX-ACCESS		read-only
						STATUS			current
						DESCRIPTION
                        "GESFP2Entry Local card's LAN port MIB Rx512to1023Octets counter."
						::= { mc2200-GESFP2Entry 18 }
mc2200-GESFP2Rx1024toMaxOctets OBJECT-TYPE
						SYNTAX			Counter64
						MAX-ACCESS		read-only
						STATUS			current
						DESCRIPTION
                        "GESFP2Entry Local card's LAN port MIB Rx1024toMaxOctets counter."
						::= { mc2200-GESFP2Entry 19 }
mc2200-GESFP2TxOctets OBJECT-TYPE
						SYNTAX			Counter64
						MAX-ACCESS		read-only
						STATUS			current
						DESCRIPTION
                        "GESFP2Entry Local card's LAN port MIB TxOctetsLow counter."
						::= { mc2200-GESFP2Entry 20 }

mc2200-GESFP2TxUnicast OBJECT-TYPE
						SYNTAX			Counter64
						MAX-ACCESS		read-only
						STATUS			current
						DESCRIPTION
                        "GESFP2Entry Local card's LAN port MIB TxUnicast counter."
						::= { mc2200-GESFP2Entry 21 }
mc2200-GESFP2TxExcessive OBJECT-TYPE
						SYNTAX			Counter64
						MAX-ACCESS		read-only
						STATUS			current
						DESCRIPTION
                        "GESFP2Entry Local card's LAN port MIB TxExcessive counter."
						::= { mc2200-GESFP2Entry 22 }
mc2200-GESFP2TxMulticasts OBJECT-TYPE
						SYNTAX			Counter64
						MAX-ACCESS		read-only
						STATUS			current
						DESCRIPTION
                        "GESFP2Entry Local card's LAN port MIB TxMulticasts counter."
						::= { mc2200-GESFP2Entry 23 }
mc2200-GESFP2TxBroadcasts OBJECT-TYPE
						SYNTAX			Counter64
						MAX-ACCESS		read-only
						STATUS			current
						DESCRIPTION
                        "GESFP2Entry Local card's LAN port MIB TxBroadcasts counter."
						::= { mc2200-GESFP2Entry 24 }
mc2200-GESFP2TxSingle OBJECT-TYPE
						SYNTAX			Counter64
						MAX-ACCESS		read-only
						STATUS			current
						DESCRIPTION
                        "GESFP2Entry Local card's LAN port MIB TxSingle counter."
						::= { mc2200-GESFP2Entry 25 }
mc2200-GESFP2TxPause OBJECT-TYPE
						SYNTAX			Counter64
						MAX-ACCESS		read-only
						STATUS			current
						DESCRIPTION
                        "GESFP2Entry Local card's LAN port MIB TxPause counter."
						::= { mc2200-GESFP2Entry 26 }
mc2200-GESFP2RxPause OBJECT-TYPE
						SYNTAX			Counter64
						MAX-ACCESS		read-only
						STATUS			current
						DESCRIPTION
                        "GESFP2Entry Local card's LAN port MIB RxPause counter."
						::= { mc2200-GESFP2Entry 27 }
mc2200-GESFP2TxMultiple OBJECT-TYPE
						SYNTAX			Counter64
						MAX-ACCESS		read-only
						STATUS			current
						DESCRIPTION
                        "GESFP2Entry Local card's LAN port MIB TxMultiple counter."
						::= { mc2200-GESFP2Entry 28 }
mc2200-GESFP2RxUndersize OBJECT-TYPE
						SYNTAX			Counter64
						MAX-ACCESS		read-only
						STATUS			current
						DESCRIPTION
                        "GESFP2Entry Local card's LAN port MIB RxUndersize counter."
						::= { mc2200-GESFP2Entry 29 }
mc2200-GESFP2RxFragments OBJECT-TYPE
						SYNTAX			Counter64
						MAX-ACCESS		read-only
						STATUS			current
						DESCRIPTION
                        "GESFP2Entry Local card's LAN port MIB RxFragments counter."
						::= { mc2200-GESFP2Entry 30 }
mc2200-GESFP2RxOversize OBJECT-TYPE
						SYNTAX			Counter64
						MAX-ACCESS		read-only
						STATUS			current
						DESCRIPTION
                        "GESFP2Entry Local card's LAN port MIB RxOversize counter."
						::= { mc2200-GESFP2Entry 31 }
mc2200-GESFP2RxJabber OBJECT-TYPE
						SYNTAX			Counter64
						MAX-ACCESS		read-only
						STATUS			current
						DESCRIPTION
                        "GESFP2Entry Local card's LAN port MIB RxJabber counter."
						::= { mc2200-GESFP2Entry 32 }
mc2200-GESFP2RxErr OBJECT-TYPE
						SYNTAX			Counter64
						MAX-ACCESS		read-only
						STATUS			current
						DESCRIPTION
                        "GESFP2Entry Local card's LAN port MIB RxErr counter."
						::= { mc2200-GESFP2Entry 33 }
mc2200-GESFP2RxFCSErr OBJECT-TYPE
						SYNTAX			Counter64
						MAX-ACCESS		read-only
						STATUS			current
						DESCRIPTION
                        "GESFP2Entry Local card's LAN port MIB RxFCSErr counter."
						::= { mc2200-GESFP2Entry 34 }
mc2200-GESFP2TxCollisions OBJECT-TYPE
						SYNTAX			Counter64
						MAX-ACCESS		read-only
						STATUS			current
						DESCRIPTION
                        "GESFP2Entry Local card's LAN port MIB TxCollisions counter."
						::= { mc2200-GESFP2Entry 35 }
mc2200-GESFP2TxLate OBJECT-TYPE
						SYNTAX			Counter64
						MAX-ACCESS		read-only
						STATUS			current
						DESCRIPTION
                        "GESFP2Entry Local card's port8 MIB TxLate counter."
						::= { mc2200-GESFP2Entry 36 }
mc2200-GESFP2RemoteWANSFPInfo	OBJECT-TYPE
						SYNTAX		DisplayString
						MAX-ACCESS		read-only
						STATUS			current
						DESCRIPTION
                            "GESFP2Entry Remote card's WAN port SFP infomation."
						::= { mc2200-GESFP2Entry 37 }
mc2200-GESFP2RemoteWANLink	        OBJECT-TYPE
						SYNTAX			INTEGER {up(1),
						                         down(2), noremotecard(0)}
						MAX-ACCESS		read-only
						STATUS			current
						DESCRIPTION
                            "GESFP2Entry Remote card's WAN port work link status."
						::= { mc2200-GESFP2Entry 38 }
mc2200-GESFP2RemotePort1Link	OBJECT-TYPE
						SYNTAX			INTEGER  {up(1),down(2), noremotecard(0)}
						MAX-ACCESS		read-only
						STATUS			current
						DESCRIPTION
                            "GESFP2 Remote card's port1 work link status."
						::= { mc2200-GESFP2Entry 39 }

mc2200-GESFP2RemotePort1Speed	OBJECT-TYPE
						SYNTAX			INTEGER  {speed100M(1),speed10M(2),auto(3), noremotecard(0)}
						MAX-ACCESS		read-only
						STATUS			current
						DESCRIPTION
                            "GESFP2 Remote card's port1 work speed status. "
						::= { mc2200-GESFP2Entry 40 }

mc2200-GESFP2RemotePort1Duplex	OBJECT-TYPE
						SYNTAX			INTEGER {full-duplex(1),half-duplex(2), auto(3), noremotecard(0)}
						MAX-ACCESS		read-only
						STATUS			current
						DESCRIPTION
                            "GESFP2 Remote card's port1 work duplex status."
						::= { mc2200-GESFP2Entry 41 }
mc2200-GESFP2RemotePort1Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port1 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  42 }

mc2200-GESFP2RemotePort1MDIX    OBJECT-TYPE
						SYNTAX			INTEGER {auto(1),
						                         mdi(2),
						                         mdi-X(3), noremotecard(0)}
						MAX-ACCESS		read-write
						STATUS			current
						DESCRIPTION
                        "GESFP2 Remote card's port1 Mode configuration,
                    	set INTEGER(1) to auto,
                    	set INTEGER(2) to mdi,
                    	set INTEGER(3) to mdi-X,
                    	Ohter value is invalid"
						::= { mc2200-GESFP2Entry 43 }

mc2200-GESFP2RemotePort2Link	OBJECT-TYPE
						SYNTAX			INTEGER  {up(1),down(2), noremotecard(0)}
						MAX-ACCESS		read-only
						STATUS			current
						DESCRIPTION
                            "GESFP2 Remote card's port2 work link status."
						::= { mc2200-GESFP2Entry 44 }

mc2200-GESFP2RemotePort2Speed	OBJECT-TYPE
						SYNTAX			INTEGER  {speed100M(1),speed10M(2),auto(3), noremotecard(0)}
						MAX-ACCESS		read-only
						STATUS			current
						DESCRIPTION
                            "GESFP2 Remote card's port2 work speed status. "
						::= { mc2200-GESFP2Entry 45 }

mc2200-GESFP2RemotePort2Duplex	OBJECT-TYPE
						SYNTAX			INTEGER {full-duplex(1),half-duplex(2), auto(3), noremotecard(0)}
						MAX-ACCESS		read-only
						STATUS			current
						DESCRIPTION
                            "GESFP2 Remote card's port2 work duplex status."
						::= { mc2200-GESFP2Entry 46 }
mc2200-GESFP2RemotePort2Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port2 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  47 }

mc2200-GESFP2RemotePort2MDIX    OBJECT-TYPE
						SYNTAX			INTEGER {auto(1),
						                         mdi(2),
						                         mdi-X(3), noremotecard(0)}
						MAX-ACCESS		read-write
						STATUS			current
						DESCRIPTION
                        "GESFP2 Remote card's port2 Mode configuration,
                    	set INTEGER(1) to auto,
                    	set INTEGER(2) to mdi,
                    	set INTEGER(3) to mdi-X,
                    	Ohter value is invalid"
						::= { mc2200-GESFP2Entry 48 }


mc2200-GESFP2RemotePort3Link	OBJECT-TYPE
						SYNTAX			INTEGER  {up(1),down(2), noremotecard(0)}
						MAX-ACCESS		read-only
						STATUS			current
						DESCRIPTION
                            "GESFP2 Remote card's port3 work link status."
						::= { mc2200-GESFP2Entry 49 }

mc2200-GESFP2RemotePort3Speed	OBJECT-TYPE
						SYNTAX			INTEGER  {speed100M(1),speed10M(2),auto(3), noremotecard(0)}
						MAX-ACCESS		read-only
						STATUS			current
						DESCRIPTION
                            "GESFP2 Remote card's port3 work speed status. "
						::= { mc2200-GESFP2Entry 50 }

mc2200-GESFP2RemotePort3Duplex	OBJECT-TYPE
						SYNTAX			INTEGER {full-duplex(1),half-duplex(2), auto(3), noremotecard(0)}
						MAX-ACCESS		read-only
						STATUS			current
						DESCRIPTION
                            "GESFP2 Remote card's port3 work duplex status."
						::= { mc2200-GESFP2Entry 51 }

mc2200-GESFP2RemotePort3Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port3 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  52 }

mc2200-GESFP2RemotePort3MDIX    OBJECT-TYPE
						SYNTAX			INTEGER {auto(1),
						                         mdi(2),
						                         mdi-X(3), noremotecard(0)}
						MAX-ACCESS		read-write
						STATUS			current
						DESCRIPTION
                        "GESFP2 Remote card's port3 Mode configuration,
                    	set INTEGER(1) to auto,
                    	set INTEGER(2) to mdi,
                    	set INTEGER(3) to mdi-X,
                    	Ohter value is invalid"
						::= { mc2200-GESFP2Entry 53 }

mc2200-GESFP2RemotePort4Link	OBJECT-TYPE
						SYNTAX			INTEGER  {up(1),down(2), noremotecard(0)}
						MAX-ACCESS		read-only
						STATUS			current
						DESCRIPTION
                            "GESFP2 Remote card's port4 work link status."
						::= { mc2200-GESFP2Entry 54 }

mc2200-GESFP2RemotePort4Speed	OBJECT-TYPE
						SYNTAX			INTEGER  {speed100M(1),speed10M(2),auto(3), noremotecard(0)}
						MAX-ACCESS		read-only
						STATUS			current
						DESCRIPTION
                            "GESFP2 Remote card's port4 work speed status. "
						::= { mc2200-GESFP2Entry 55 }

mc2200-GESFP2RemotePort4Duplex	OBJECT-TYPE
						SYNTAX			INTEGER {full-duplex(1),half-duplex(2), auto(3), noremotecard(0)}
						MAX-ACCESS		read-only
						STATUS			current
						DESCRIPTION
                            "GESFP2 Remote card's port4 work duplex status."
						::= { mc2200-GESFP2Entry 56 }
mc2200-GESFP2RemotePort4Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port4 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  57 }

mc2200-GESFP2RemotePort4MDIX    OBJECT-TYPE
						SYNTAX			INTEGER {auto(1),
						                         mdi(2),
						                         mdi-X(3), noremotecard(0)}
						MAX-ACCESS		read-write
						STATUS			current
						DESCRIPTION
                        "GESFP2 Remote card's port4 Mode configuration,
                    	set INTEGER(1) to auto,
                    	set INTEGER(2) to mdi,
                    	set INTEGER(3) to mdi-X,
                    	Ohter value is invalid"
						::= { mc2200-GESFP2Entry 58 }

mc2200-GESFP2RemotePort5Link	OBJECT-TYPE
						SYNTAX			INTEGER  {up(1),down(2), noremotecard(0)}
						MAX-ACCESS		read-only
						STATUS			current
						DESCRIPTION
                            "GESFP2 Remote card's port5 work link status."
						::= { mc2200-GESFP2Entry 59 }

mc2200-GESFP2RemotePort5Speed	OBJECT-TYPE
						SYNTAX			INTEGER  {speed100M(1),speed10M(2),auto(3), noremotecard(0)}
						MAX-ACCESS		read-only
						STATUS			current
						DESCRIPTION
                            "GESFP2 Remote card's port5 work speed status. "
						::= { mc2200-GESFP2Entry 60 }

mc2200-GESFP2RemotePort5Duplex	OBJECT-TYPE
						SYNTAX			INTEGER {full-duplex(1),half-duplex(2), auto(3), noremotecard(0)}
						MAX-ACCESS		read-only
						STATUS			current
						DESCRIPTION
                            "GESFP2 Remote card's port5 work duplex status."
						::= { mc2200-GESFP2Entry 61 }

mc2200-GESFP2RemotePort5Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port5 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  62 }

mc2200-GESFP2RemotePort5MDIX    OBJECT-TYPE
						SYNTAX			INTEGER {auto(1),
						                         mdi(2),
						                         mdi-X(3), noremotecard(0)}
						MAX-ACCESS		read-write
						STATUS			current
						DESCRIPTION
                        "GESFP2 Remote card's port5 Mode configuration,
                    	set INTEGER(1) to auto,
                    	set INTEGER(2) to mdi,
                    	set INTEGER(3) to mdi-X,
                    	Ohter value is invalid"
						::= { mc2200-GESFP2Entry 63 }

mc2200-GESFP2RemotePort6Link	OBJECT-TYPE
						SYNTAX			INTEGER  {up(1),down(2), noremotecard(0)}
						MAX-ACCESS		read-only
						STATUS			current
						DESCRIPTION
                            "GESFP2 Remote card's port6 work link status."
						::= { mc2200-GESFP2Entry 64 }

mc2200-GESFP2RemotePort6Speed	OBJECT-TYPE
						SYNTAX			INTEGER  {speed100M(1),speed10M(2),auto(3), noremotecard(0)}
						MAX-ACCESS		read-only
						STATUS			current
						DESCRIPTION
                            "GESFP2 Remote card's port6 work speed status. "
						::= { mc2200-GESFP2Entry 65 }

mc2200-GESFP2RemotePort6Duplex	OBJECT-TYPE
						SYNTAX			INTEGER {full-duplex(1),half-duplex(2), auto(3), noremotecard(0)}
						MAX-ACCESS		read-only
						STATUS			current
						DESCRIPTION
                            "GESFP2 Remote card's port6 work duplex status."
						::= { mc2200-GESFP2Entry 66 }
mc2200-GESFP2RemotePort6Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port6 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  67 }

mc2200-GESFP2RemotePort6MDIX    OBJECT-TYPE
						SYNTAX			INTEGER {auto(1),
						                         mdi(2),
						                         mdi-X(3), noremotecard(0)}
						MAX-ACCESS		read-write
						STATUS			current
						DESCRIPTION
                        "GESFP2 Remote card's port6 Mode configuration,
                    	set INTEGER(1) to auto,
                    	set INTEGER(2) to mdi,
                    	set INTEGER(3) to mdi-X,
                    	Ohter value is invalid"
						::= { mc2200-GESFP2Entry 68 }
mc2200-GESFP2RemotePort7Link	OBJECT-TYPE
						SYNTAX			INTEGER  {up(1),down(2), noremotecard(0)}
						MAX-ACCESS		read-only
						STATUS			current
						DESCRIPTION
                            "GESFP2 Remote card's port7 work link status."
						::= { mc2200-GESFP2Entry 69 }

mc2200-GESFP2RemotePort7Speed	OBJECT-TYPE
						SYNTAX			INTEGER  {speed100M(1),speed10M(2),auto(3), noremotecard(0)}
						MAX-ACCESS		read-only
						STATUS			current
						DESCRIPTION
                            "GESFP2 Remote card's port7 work speed status. "
						::= { mc2200-GESFP2Entry 70 }

mc2200-GESFP2RemotePort7Duplex	OBJECT-TYPE
						SYNTAX			INTEGER {full-duplex(1),half-duplex(2), auto(3), noremotecard(0)}
						MAX-ACCESS		read-only
						STATUS			current
						DESCRIPTION
                            "GESFP2 Remote card's port7 work duplex status."
						::= { mc2200-GESFP2Entry 71 }
mc2200-GESFP2RemotePort7Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port7 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  72 }

mc2200-GESFP2RemotePort7MDIX    OBJECT-TYPE
						SYNTAX			INTEGER {auto(1),
						                         mdi(2),
						                         mdi-X(3), noremotecard(0)}
						MAX-ACCESS		read-write
						STATUS			current
						DESCRIPTION
                        "GESFP2 Remote card's port7 Mode configuration,
                    	set INTEGER(1) to auto,
                    	set INTEGER(2) to mdi,
                    	set INTEGER(3) to mdi-X,
                    	Ohter value is invalid"
						::= { mc2200-GESFP2Entry 73 }

mc2200-GESFP2RemotePort8Link	OBJECT-TYPE
						SYNTAX			INTEGER  {up(1),down(2), noremotecard(0)}
						MAX-ACCESS		read-only
						STATUS			current
						DESCRIPTION
                            "GESFP2 Remote card's port8 work link status."
						::= { mc2200-GESFP2Entry 74 }

mc2200-GESFP2RemotePort8Speed	OBJECT-TYPE
						SYNTAX			INTEGER  {speed100M(1),speed10M(2),auto(3), noremotecard(0)}
						MAX-ACCESS		read-only
						STATUS			current
						DESCRIPTION
                            "GESFP2 Remote card's port8 work speed status. "
						::= { mc2200-GESFP2Entry 75 }

mc2200-GESFP2RemotePort8Duplex	OBJECT-TYPE
						SYNTAX			INTEGER {full-duplex(1),half-duplex(2), auto(3), noremotecard(0)}
						MAX-ACCESS		read-only
						STATUS			current
						DESCRIPTION
                            "GESFP2 Remote card's port8 work duplex status."
						::= { mc2200-GESFP2Entry 76 }
mc2200-GESFP2RemotePort8Mode   	OBJECT-TYPE
						SYNTAX		INTEGER {auto(1),
                          					mode10MHALFDUPLEX(2),
                          					mode10MFULLDUPLEX(3),
                          					mode100MHALFDUPLEX(4),
                          					mode100MFULLDUPLEX(5), noremotecard(0)}
						MAX-ACCESS		read-write
						STATUS			current
						DESCRIPTION
                        "GESFP2 Remote card's port8 Mode configuration,
                    	set INTEGER(1) to auto,
                    	set INTEGER(2) to 10MHALFDUPLEX,
                    	set INTEGER(3) to 10MFULLDUPLEX,
                    	set INTEGER(4) to 100MHALFDUPLEX,
                    	set INTEGER(5) to 100MFULLDUPLEX,
                    	Ohter value is invalid"
						::= { mc2200-GESFP2Entry  77 }
mc2200-GESFP2RemotePort8MDIX    OBJECT-TYPE
						SYNTAX			INTEGER {auto(1),
						                         mdi(2),
						                         mdi-X(3), noremotecard(0)}
						MAX-ACCESS		read-write
						STATUS			current
						DESCRIPTION
                        "GESFP2 Remote card's port8 Mode configuration,
                    	set INTEGER(1) to auto,
                    	set INTEGER(2) to mdi,
                    	set INTEGER(3) to mdi-X,
                    	Ohter value is invalid"
						::= { mc2200-GESFP2Entry 78 }
mc2200-GESFP2RemotePort9Link	OBJECT-TYPE
						SYNTAX			INTEGER  {up(1),down(2), noremotecard(0)}
						MAX-ACCESS		read-only
						STATUS			current
						DESCRIPTION
                            "GESFP2 Remote card's port8 work link status."
						::= { mc2200-GESFP2Entry 79 }

mc2200-GESFP2RemotePort9Speed	OBJECT-TYPE
						SYNTAX			INTEGER  {speed1000M(0),speed100M(1),speed10M(2),auto(3), noremotecard(4)}
						MAX-ACCESS		read-only
						STATUS			current
						DESCRIPTION
                            "GESFP2 Remote card's port8 work speed status. "
						::= { mc2200-GESFP2Entry 80 }

mc2200-GESFP2RemotePort9Duplex	OBJECT-TYPE
						SYNTAX			INTEGER {full-duplex(1),half-duplex(2), auto(3), noremotecard(0)}
						MAX-ACCESS		read-only
						STATUS			current
						DESCRIPTION
                            "GESFP2 Remote card's port8 work duplex status."
						::= { mc2200-GESFP2Entry 81 }
mc2200-GESFP2RemotePort9Mode   	OBJECT-TYPE
						SYNTAX		INTEGER {mode1000Xauto(1),
                          					mode1000XFORCE(2),
                          					noremotecard(0)}
						MAX-ACCESS		read-write
						STATUS			current
						DESCRIPTION
                        "GESFP2 Remote card's port8 Mode configuration,
                    	set INTEGER(1) to 1000Xauto,
                    	set INTEGER(2) to 1000XFORCE,
                    	Ohter value is invalid"
						::= { mc2200-GESFP2Entry  82 }
mc2200-GESFP2RemotePort9SFPInfo	OBJECT-TYPE
						SYNTAX		DisplayString
						MAX-ACCESS		read-only
						STATUS			current
						DESCRIPTION
                            "GESFP2 Remote card's WAN port SFP infomation."
						::= { mc2200-GESFP2Entry 84 }
mc2200-GESFP2RemoteIPAddress  OBJECT-TYPE
        			SYNTAX      IpAddress
        			ACCESS      read-write
        			STATUS      mandatory
	    			DESCRIPTION
            		"The IP address to GESFP2Entry Remote IP ping."
        			::= {mc2200-GESFP2Entry 85}

mc2200-GESFP2RemoteSubnetMask    OBJECT-TYPE
        			SYNTAX      IpAddress
        			ACCESS      read-write
        			STATUS      mandatory
	    			DESCRIPTION
                    "The Net mask to  GESFP2Entry Remote IP ping."
        			::= {mc2200-GESFP2Entry 86}

mc2200-GESFP2RemoteGateWay    OBJECT-TYPE
        			SYNTAX      IpAddress
        			ACCESS      read-write
        			STATUS      mandatory
	   				 DESCRIPTION
                    "The gateware to GESFP2Entry Remote IP ping."
        			::= {mc2200-GESFP2Entry 87}

mc2200-GESFP2RemoteVLANEnable  OBJECT-TYPE
        			SYNTAX      INTEGER {enable(1),disable(2), noremotecard(0)}
        			ACCESS      read-write
        			STATUS      mandatory
	    			DESCRIPTION
                    "Enable or disable Remote GESFP2Entry IP ping 802.1Q VLAN."
        			::= {mc2200-GESFP2Entry 88}
mc2200-GESFP2RemoteVID  OBJECT-TYPE
        			SYNTAX      INTEGER
        			ACCESS      read-write
        			STATUS      mandatory
	    			DESCRIPTION
                    "GESFP2Entry Remote IP ping  802.1Q VLAN ID."
        			::= {mc2200-GESFP2Entry 89}
mc2200-GESFP2RemoteAlarm      OBJECT-TYPE
						SYNTAX			INTEGER  {enabled(1),disabled(2)}
						MAX-ACCESS		read-write
						STATUS			current
						DESCRIPTION
                        "Enable or disable GESFP2Entry Media converter card remote alarm.
                         set INTEGER(1) to Enable remote alarm,
                         set INTEGER(2) to Disable remote alarm,
                         Other value is invalid."
						::= { mc2200-GESFP2Entry 90 }
mc2200-GESFP2Default		OBJECT-TYPE
						SYNTAX			INTEGER
						MAX-ACCESS		write-only
						STATUS			current
						DESCRIPTION
                        "Write GESFP2 card default setting,
                        set INTEGER(1) to write default.
                        Other value is invalid."
						::= { mc2200-GESFP2Entry 91 }
mc2200-GESFP2Reboot		OBJECT-TYPE
						SYNTAX			INTEGER
						MAX-ACCESS		write-only
						STATUS			current
						DESCRIPTION
                        "Reboot GESFP2Entry local card,
                        set INTEGER(1) to reboot this card.
                        Other value is invalid. "
						::= { mc2200-GESFP2Entry 92 }
mc2200-GESFP2LocalTXSpeed      OBJECT-TYPE
						SYNTAX			INTEGER {speed1000M(1),
						                         speed100M(2),speed10M(3),down(4)}
						MAX-ACCESS		read-only
						STATUS			mandatory
						DESCRIPTION
                        "GESFP2 Local card's LAN port work speed status."
						::= { mc2200-GESFP2Entry 93 }
mc2200-GESFP2RemoteLanIsolate                OBJECT-TYPE
						SYNTAX			INTEGER {enabled(1),disabled(2)}
						MAX-ACCESS		read-write
						STATUS			current
						DESCRIPTION
                        "Enable or disable GESFP2 Media converter card remote lan isolate.
                         set INTEGER(1) to Enable lan isolate,
                         set INTEGER(2) to Disable lan isolate,
                         Other value is invalid."
						::= { mc2200-GESFP2Entry 94 }

mc2200-GESFP2Localportuser      OBJECT-TYPE
						SYNTAX			DisplayString
						MAX-ACCESS		read-write
						STATUS			current
						DESCRIPTION
                        " User of GESFP2 Local Port1. "
						::= { mc2200-GESFP2Entry 95 }

mc2200-GESFP2Remoteportuser1      OBJECT-TYPE
						SYNTAX			DisplayString
						MAX-ACCESS		read-write
						STATUS			current
						DESCRIPTION
                        " User of GESFP2 Remote Port1. "
						::= { mc2200-GESFP2Entry 96 }


mc2200-GESFP2Remoteportuser2      OBJECT-TYPE
						SYNTAX			DisplayString
						MAX-ACCESS		read-write
						STATUS			current
						DESCRIPTION
                        " User of GESFP2 Remote Port2. "
						::= { mc2200-GESFP2Entry 97 }

mc2200-GESFP2Remoteportuser3      OBJECT-TYPE
						SYNTAX			DisplayString
						MAX-ACCESS		read-write
						STATUS			current
						DESCRIPTION
                        " User of GESFP2 Remote Port3. "
						::= { mc2200-GESFP2Entry 98 }

mc2200-GESFP2Remoteportuser4      OBJECT-TYPE
						SYNTAX			DisplayString
						MAX-ACCESS		read-write
						STATUS			current
						DESCRIPTION
                        " User of GESFP2 Remote Port4. "
						::= { mc2200-GESFP2Entry 99 }

mc2200-GESFP2Remoteportuser5      OBJECT-TYPE
						SYNTAX			DisplayString
						MAX-ACCESS		read-write
						STATUS			current
						DESCRIPTION
                        " User of GESFP2 Remote Port5. "
						::= { mc2200-GESFP2Entry 100 }

mc2200-GESFP2Remoteportuser6      OBJECT-TYPE
						SYNTAX			DisplayString
						MAX-ACCESS		read-write
						STATUS			current
						DESCRIPTION
                        " User of GESFP2 Remote Port6. "
						::= { mc2200-GESFP2Entry 101 }

mc2200-GESFP2Remoteportuser7      OBJECT-TYPE
						SYNTAX			DisplayString
						MAX-ACCESS		read-write
						STATUS			current
						DESCRIPTION
                        " User of GESFP2 Remote Port7. "
						::= { mc2200-GESFP2Entry 102 }

mc2200-GESFP2Remoteportuser8      OBJECT-TYPE
						SYNTAX			DisplayString
						MAX-ACCESS		read-write
						STATUS			current
						DESCRIPTION
                        " User of GESFP2 Remote Port8. "
						::= { mc2200-GESFP2Entry 103 }
mc2200-GESFP2Remoteportuser9      OBJECT-TYPE
						SYNTAX			DisplayString
						MAX-ACCESS		read-write
						STATUS			current
						DESCRIPTION
                        " User of GESFP2 Remote Port9. "
						::= { mc2200-GESFP2Entry 104 }

mc2200-GESFP2LocalTXDuplex      OBJECT-TYPE
						SYNTAX			INTEGER {fullDuplex(1),
						                         halfDuplex(2),down(3)}
						MAX-ACCESS		read-only
						STATUS			mandatory
						DESCRIPTION
                        "GESFP2 Local card's TX port work duplex status."
						::= { mc2200-GESFP2Entry 105 }
mc2200-GESFP2WANOpticalPowerCheck        OBJECT-TYPE
						SYNTAX			INTEGER  {enabled(1),disabled(2)}
						MAX-ACCESS		read-write
						STATUS			current
						DESCRIPTION
                        "GESFP2 Media converter card WANOpticalPowerCheck operation.
                         set INTEGER(1) to Enable WANOpticalPowerCheck,
                         set INTEGER(2) to Disable WANOpticalPowerCheck,
                         Other value is invalid."
						::= { mc2200-GESFP2Entry 106 }
mc2200-GESFP2WANThreshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "GESFP2 Media converter card WANThreshold operation.
                         Other value is invalid."
						::= { mc2200-GESFP2Entry 107 }
mc2200-GESFP2TrapFilterLocalLAN	        OBJECT-TYPE
						SYNTAX			INTEGER {enabled(1),disabled(2)}
						MAX-ACCESS		read-write
						STATUS			current
						DESCRIPTION
                            "Local LAN of GESFP Trap Filter ."
						::= { mc2200-GESFP2Entry 108 }
mc2200-GESFP2TrapFilterLocalWAN	        OBJECT-TYPE
						SYNTAX			INTEGER {enabled(1),disabled(2)}
						MAX-ACCESS		read-write
						STATUS			current
						DESCRIPTION
                            "Local WAN of GESFP2 Trap Filter ."
						::= { mc2200-GESFP2Entry 109 }
mc2200-GESFP2TrapFilterRemotePower	        OBJECT-TYPE
						SYNTAX			INTEGER {enabled(1),disabled(2)}
						MAX-ACCESS		read-write
						STATUS			current
						DESCRIPTION
                            "Remote Power of GESFP2 Trap Filter ."
						::= { mc2200-GESFP2Entry 110 }
mc2200-GESFP2TrapFilterRemoteLAN	        OBJECT-TYPE
						SYNTAX			INTEGER {enabled(1),disabled(2)}
						MAX-ACCESS		read-write
						STATUS			current
						DESCRIPTION
                            "Remote LAN of GESFP2 Trap Filter ."
						::= { mc2200-GESFP2Entry 111 }
mc2200-GESFP2TrapFilterRemoteWAN	        OBJECT-TYPE
						SYNTAX			INTEGER {enabled(1),disabled(2)}
						MAX-ACCESS		read-write
						STATUS			current
						DESCRIPTION
                            "Remote WAN of GESFP2 Trap Filter ."
						::= { mc2200-GESFP2Entry 112 }
mc2200-GESFP2CardType	OBJECT-TYPE
						SYNTAX		DisplayString
						MAX-ACCESS		read-only
						STATUS			current
						DESCRIPTION
                            "GESFP2 card's Type."
						::= { mc2200-GESFP2Entry 114 }
mc2200-GESFP2RemotePort1UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port1 Tx Rate. "
						::= { mc2200-GESFP2Entry 115 }
mc2200-GESFP2RemotePort1DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port1 Rx Rate."
						::= { mc2200-GESFP2Entry 116 }
mc2200-GESFP2RemotePort2UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port2 Tx Rate. "
						::= { mc2200-GESFP2Entry 117 }
mc2200-GESFP2RemotePort2DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port2 Rx Rate."
						::= { mc2200-GESFP2Entry 118 }
mc2200-GESFP2RemotePort3UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port3 Tx Rate. "
						::= { mc2200-GESFP2Entry 119 }
mc2200-GESFP2RemotePort3DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port3 Rx Rate."
						::= { mc2200-GESFP2Entry 120 }
mc2200-GESFP2RemotePort4UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port4 Tx Rate. "
						::= { mc2200-GESFP2Entry 121 }
mc2200-GESFP2RemotePort4DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port4 Rx Rate."
						::= { mc2200-GESFP2Entry 122 }
mc2200-GESFP2RemotePort5UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port5 Tx Rate. "
						::= { mc2200-GESFP2Entry 123 }
mc2200-GESFP2RemotePort5DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port5 Rx Rate."
						::= { mc2200-GESFP2Entry 124 }
mc2200-GESFP2RemotePort6UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port6 Tx Rate. "
						::= { mc2200-GESFP2Entry 125 }
mc2200-GESFP2RemotePort6DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port6 Rx Rate."
						::= { mc2200-GESFP2Entry 126 }
mc2200-GESFP2RemotePort7UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port7 Tx Rate. "
						::= { mc2200-GESFP2Entry 127 }
mc2200-GESFP2RemotePort7DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port7 Rx Rate."
						::= { mc2200-GESFP2Entry 128 }
mc2200-GESFP2RemotePort8UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port8 Tx Rate. "
						::= { mc2200-GESFP2Entry 129 }
mc2200-GESFP2RemotePort8DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port8 Rx Rate."
						::= { mc2200-GESFP2Entry 130 }
mc2200-GESFP2RemotePort9UpstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                            "GESFP2 remote card's port9 Tx Rate. "
						::= { mc2200-GESFP2Entry 131 }
mc2200-GESFP2RemotePort9DownstreamBandwidth	OBJECT-TYPE
						SYNTAX			INTEGER  {rate1M(1),rate2M(2),rate3M(3),rate4M(4),rate5M(5),rate6M(6),rate7M(7),rate8M(8),rate9M(9),
						                          rate10M(10),rate15M(15),rate20M(20),rate25M(25),rate30M(30),rate50M(50),rate100M(100)
						                          }
						MAX-ACCESS		read-write
						STATUS			current
						DESCRIPTION
                        " GESFP2 remote card's port9 Rx Rate."
						::= { mc2200-GESFP2Entry 132 }

-- FEMC Table  ====================================================

mc2200-FEMCTable	   OBJECT-TYPE
					SYNTAX			SEQUENCE OF MC2200-FEMCEntry
					MAX-ACCESS		not-accessible
					STATUS			current
					DESCRIPTION
                   "Sparse table containing one entry for each FEMC
                     10/100Mbps Twisted-Pair to Fiber Ethernet Media Converter
                     in the system, indexed by chassisIndex and slotIndex."

					::= { mc2200-GEmib 20 }

mc2200-FEMCEntry			OBJECT-TYPE
						SYNTAX			MC2200-FEMCEntry
						MAX-ACCESS		not-accessible
						STATUS			current
						DESCRIPTION
            "One table entry per slot in the media converter chassis.
             If physical slot 'n' contains a powered FEMC media
             converter, then entry 'n' in this table exists and describes
             the state of the converter's lamps  If slot 'n' is empty, does
             not exist, or contains a different type of device, then table
             entry 'n' does not exist."

						INDEX			{ mc2200-FEMCCardIndex }
						::= { mc2200-FEMCTable 1 }






-- ==========================
-- CH-unit config info table --
-- ==========================
MC2200-FEMCEntry ::=
				SEQUENCE {
					mc2200-FEMCCardIndex			    INTEGER,	-- 1
					mc2200-FEMCLocalLANSFPInfo         DisplayString,
					mc2200-FEMCLocalLANLink          	INTEGER,
					mc2200-FEMCLocalWANSFPInfo         DisplayString,
					mc2200-FEMCLocalWANLink          	INTEGER,
					mc2200-FEMCLocalLANDownStreamBW   	INTEGER,
					mc2200-FEMCLocalLANUpStreamBW     	INTEGER,
					mc2200-FEMCLocalLANMode	      	INTEGER,
					mc2200-FEMCRxGoodOctets        	Counter64,

                    mc2200-FEMCRxBadOctets        		Counter64,
                    mc2200-FEMCTxFCSErr        		Counter64,
					mc2200-FEMCRxUnicast        		Counter64,
					mc2200-FEMCTxDeferred        		Counter64,
                    mc2200-FEMCRxBroadcasts        	Counter64,
                    mc2200-FEMCRxMulticasts        	Counter64,
					mc2200-FEMCRx64Octets        	Counter64,
					mc2200-FEMCRx65to127Octets        	Counter64,
                    mc2200-FEMCRx128to255Octets        Counter64, -- 20
                    mc2200-FEMCRx256to511Octets        Counter64,
                    mc2200-FEMCRx512to1023Octets       Counter64,
					mc2200-FEMCRx1024toMaxOctets       Counter64,
					mc2200-FEMCTxOctets        		Counter64,

                    mc2200-FEMCTxUnicast        		Counter64,
					mc2200-FEMCTxExcessive        		Counter64,
					mc2200-FEMCTxMulticasts            Counter64,
                    mc2200-FEMCTxBroadcasts        	Counter64,
                    mc2200-FEMCTxSingle        		Counter64, -- 30
					mc2200-FEMCTxPause        			Counter64,
					mc2200-FEMCRxPause        			Counter64,
                    mc2200-FEMCTxMultiple        		Counter64,
                    mc2200-FEMCRxUndersize        		Counter64,
					mc2200-FEMCRxFragments             Counter64,
					mc2200-FEMCRxOversize              Counter64,
                    mc2200-FEMCRxJabber        		Counter64,
                    mc2200-FEMCRxErr        		    Counter64,
					mc2200-FEMCRxFCSErr                Counter64,
					mc2200-FEMCTxCollisions            Counter64,  -- 40
                    mc2200-FEMCTxLate        		    Counter64,
                    mc2200-FEMCRemoteLANSFPInfo        DisplayString,
					mc2200-FEMCRemoteLANLink           INTEGER,
					mc2200-FEMCRemoteWANSFPInfo        DisplayString,
					mc2200-FEMCRemoteWANLink           INTEGER,
					mc2200-FEMCRemoteLANMode	        INTEGER,
					mc2200-FEMCRemoteIPAddress       	IpAddress,
		  	        mc2200-FEMCRemoteSubnetMask      	IpAddress,
					mc2200-FEMCRemoteGateWay         	IpAddress,
					mc2200-FEMCRemoteVLANEnable	    INTEGER, -- 50
					mc2200-FEMCRemoteVID         		INTEGER,
                    mc2200-FEMCRemoteAlarm      		INTEGER,
                    mc2200-FEMCRFD						INTEGER,
                    mc2200-FEMCDefault					INTEGER,
                    mc2200-FEMCReboot					INTEGER, -- 55
					mc2200-FEMCLocalLANSpeed                  INTEGER,
					mc2200-FEMCRemoteLANSpeed                 INTEGER,
					mc2200-FEMCLocalportuser     DisplayString,
					mc2200-FEMCRemoteportuser    DisplayString,
					mc2200-FEMCWANOpticalPowerCheck			INTEGER,
					mc2200-FEMCWANThreshold			INTEGER,
					mc2200-FEMCTrapFilterLocalLAN			INTEGER,
					mc2200-FEMCTrapFilterLocalWAN			INTEGER,
					mc2200-FEMCTrapFilterRemotePower		INTEGER,
					mc2200-FEMCTrapFilterRemoteLAN		INTEGER,
					mc2200-FEMCTrapFilterRemoteWAN		INTEGER,
					mc2200-FEMCLoopback		INTEGER,
					mc2200-FEMCCardType		DisplayString
				}


mc2200-FEMCCardIndex		OBJECT-TYPE
						SYNTAX			INTEGER {card01(1),card02(2),card03(3),card04(4),
						                         card05(5),card06(6),card07(7),card08(8),
						                         card09(9),card10(10),card11(11),card12(12),
						                         card13(13),card14(14),card15(15)}
						MAX-ACCESS		read-only
						STATUS			current
						DESCRIPTION
                            "Index to select card unit, based on local cards"
						::= { mc2200-FEMCEntry 1 }
mc2200-FEMCLocalLANSFPInfo	OBJECT-TYPE
						SYNTAX		DisplayString
						MAX-ACCESS		read-only
						STATUS			current
						DESCRIPTION
                            "FEMC Local card's LAN port SFP infomation."
						::= { mc2200-FEMCEntry 2 }
mc2200-FEMCLocalLANLink      OBJECT-TYPE
						SYNTAX			INTEGER {up(1),
						                         down(2)}
						MAX-ACCESS		read-only
						STATUS			mandatory
						DESCRIPTION
                            "FEMC Local card's LAN port work link status."
						::= { mc2200-FEMCEntry 3 }
mc2200-FEMCLocalWANSFPInfo	OBJECT-TYPE
						SYNTAX		DisplayString
						MAX-ACCESS		read-only
						STATUS			current
						DESCRIPTION
                            "FEMC Local card's WAN port SFP infomation."
						::= { mc2200-FEMCEntry 4 }
mc2200-FEMCLocalWANLink	        OBJECT-TYPE
						SYNTAX			INTEGER {up(1),
						                         down(2)}
						MAX-ACCESS		read-only
						STATUS			current
						DESCRIPTION
                            "FEMC Local card's WAN port work link status."
						::= { mc2200-FEMCEntry 5 }

mc2200-FEMCLocalLANDownStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100)
						                          }
						MAX-ACCESS		read-write
						STATUS			current
						DESCRIPTION
                            "FEMC Local card's LAN port DownStream BandWidth. "
						::= { mc2200-FEMCEntry 6 }
mc2200-FEMCLocalLANUpStreamBW	OBJECT-TYPE
						SYNTAX			INTEGER  {disable(0),rate1M(1),rate2M(2),rate3M(3),rate4M(4),rate5M(5),rate6M(6),rate7M(7),rate8M(8),rate9M(9),rate10M(10),rate15M(15),
													rate20M(20),rate25M(25),rate30M(30),rate35M(35),rate40M(40),rate45M(45),rate50M(50),
													rate55M(55),rate60M(60),rate65M(65),rate70M(70),rate75M(75),
													rate80M(80),rate85M(85),rate90M(90),rate95M(95),rate100M(100)
						                          }
						MAX-ACCESS		read-write
						STATUS			current
						DESCRIPTION
                        " FEMC Local card's LAN port UpStream BandWidth."
						::= { mc2200-FEMCEntry 7 }
mc2200-FEMCLocalLANMode   	OBJECT-TYPE
						SYNTAX		INTEGER {mode100Base-FX-auto(1),
                          					mode100Base-full(2),
                          					mode100Base-Half(3),
                          					mode10Base-full(4),
                          					mode10Base-Half(5)}
						MAX-ACCESS		read-write
						STATUS			current
						DESCRIPTION
                        "FEMC Local card's LAN port Mode configuration,
                    	set INTEGER(1) to 100Base-FX-auto,
                    	set INTEGER(2) to 100Base-full,
                    	set INTEGER(3) to 100Base-Half,
                    	set INTEGER(4) to 10Base-full,
                    	set INTEGER(5) to 10Base-Half,
                    	Ohter value is invalid"
						::= { mc2200-FEMCEntry  8 }

mc2200-FEMCRxGoodOctets OBJECT-TYPE
						SYNTAX			Counter64
						MAX-ACCESS		read-only
						STATUS			current
						DESCRIPTION
                        "FEMC Local card's LAN port MIB RxGoodOctetsLow counter."
						::= { mc2200-FEMCEntry 9 }

mc2200-FEMCRxBadOctets OBJECT-TYPE
						SYNTAX			Counter64
						MAX-ACCESS		read-only
						STATUS			current
						DESCRIPTION
                        "FEMC Local card's LAN port MIB RxBadOctets counter."
						::= { mc2200-FEMCEntry 11 }
mc2200-FEMCTxFCSErr OBJECT-TYPE
						SYNTAX			Counter64
						MAX-ACCESS		read-only
						STATUS			current
						DESCRIPTION
                        "FEMC Local card's LAN port MIB  TxFCSErr counter."
						::= { mc2200-FEMCEntry 12 }

mc2200-FEMCRxUnicast OBJECT-TYPE
						SYNTAX			Counter64
						MAX-ACCESS		read-only
						STATUS			current
						DESCRIPTION
                        "FEMC Local card's LAN port MIB RxUnicast counter."
						::= { mc2200-FEMCEntry 13 }
mc2200-FEMCTxDeferred OBJECT-TYPE
						SYNTAX			Counter64
						MAX-ACCESS		read-only
						STATUS			current
						DESCRIPTION
                        "FEMC Local card's LAN port MIB TxDeferred counter."
						::= { mc2200-FEMCEntry 14 }
mc2200-FEMCRxBroadcasts OBJECT-TYPE
						SYNTAX			Counter64
						MAX-ACCESS		read-only
						STATUS			current
						DESCRIPTION
                        "FEMC Local card's LAN port MIB RxBroadcasts counter."
						::= { mc2200-FEMCEntry 15 }
mc2200-FEMCRxMulticasts OBJECT-TYPE
						SYNTAX			Counter64
						MAX-ACCESS		read-only
						STATUS			current
						DESCRIPTION
                        "FEMC Local card's LAN port MIB RxMulticasts counter."
						::= { mc2200-FEMCEntry 16 }
mc2200-FEMCRx64Octets OBJECT-TYPE
						SYNTAX			Counter64
						MAX-ACCESS		read-only
						STATUS			current
						DESCRIPTION
                        "FEMC Local card's LAN port MIB Rx64Octets counter."
						::= { mc2200-FEMCEntry 17 }
mc2200-FEMCRx65to127Octets OBJECT-TYPE
						SYNTAX			Counter64
						MAX-ACCESS		read-only
						STATUS			current
						DESCRIPTION
                        "FEMC Local card's LAN port MIB Rx65to127Octets counter."
						::= { mc2200-FEMCEntry 18 }
mc2200-FEMCRx128to255Octets OBJECT-TYPE
						SYNTAX			Counter64
						MAX-ACCESS		read-only
						STATUS			current
						DESCRIPTION
                        "FEMC Local card's LAN port MIB Rx128to255Octets counter."
						::= { mc2200-FEMCEntry 19 }
mc2200-FEMCRx256to511Octets OBJECT-TYPE
						SYNTAX			Counter64
						MAX-ACCESS		read-only
						STATUS			current
						DESCRIPTION
                        "FEMC Local card's LAN port MIB Rx256to511Octets counter."
						::= { mc2200-FEMCEntry 20 }
mc2200-FEMCRx512to1023Octets OBJECT-TYPE
						SYNTAX			Counter64
						MAX-ACCESS		read-only
						STATUS			current
						DESCRIPTION
                        "FEMC Local card's LAN port MIB Rx512to1023Octets counter."
						::= { mc2200-FEMCEntry 21 }
mc2200-FEMCRx1024toMaxOctets OBJECT-TYPE
						SYNTAX			Counter64
						MAX-ACCESS		read-only
						STATUS			current
						DESCRIPTION
                        "FEMC Local card's LAN port MIB Rx1024toMaxOctets counter."
						::= { mc2200-FEMCEntry 22 }
mc2200-FEMCTxOctets OBJECT-TYPE
						SYNTAX			Counter64
						MAX-ACCESS		read-only
						STATUS			current
						DESCRIPTION
                        "FEMC Local card's LAN port MIB TxOctetsLow counter."
						::= { mc2200-FEMCEntry 23 }

mc2200-FEMCTxUnicast OBJECT-TYPE
						SYNTAX			Counter64
						MAX-ACCESS		read-only
						STATUS			current
						DESCRIPTION
                        "FEMC Local card's LAN port MIB TxUnicast counter."
						::= { mc2200-FEMCEntry 25 }
mc2200-FEMCTxExcessive OBJECT-TYPE
						SYNTAX			Counter64
						MAX-ACCESS		read-only
						STATUS			current
						DESCRIPTION
                        "FEMC Local card's LAN port MIB TxExcessive counter."
						::= { mc2200-FEMCEntry 26 }
mc2200-FEMCTxMulticasts OBJECT-TYPE
						SYNTAX			Counter64
						MAX-ACCESS		read-only
						STATUS			current
						DESCRIPTION
                        "FEMC Local card's LAN port MIB TxMulticasts counter."
						::= { mc2200-FEMCEntry 27 }
mc2200-FEMCTxBroadcasts OBJECT-TYPE
						SYNTAX			Counter64
						MAX-ACCESS		read-only
						STATUS			current
						DESCRIPTION
                        "FEMC Local card's LAN port MIB TxBroadcasts counter."
						::= { mc2200-FEMCEntry 28 }
mc2200-FEMCTxSingle OBJECT-TYPE
						SYNTAX			Counter64
						MAX-ACCESS		read-only
						STATUS			current
						DESCRIPTION
                        "FEMC Local card's LAN port MIB TxSingle counter."
						::= { mc2200-FEMCEntry 29 }
mc2200-FEMCTxPause OBJECT-TYPE
						SYNTAX			Counter64
						MAX-ACCESS		read-only
						STATUS			current
						DESCRIPTION
                        "FEMC Local card's LAN port MIB TxPause counter."
						::= { mc2200-FEMCEntry 30 }
mc2200-FEMCRxPause OBJECT-TYPE
						SYNTAX			Counter64
						MAX-ACCESS		read-only
						STATUS			current
						DESCRIPTION
                        "FEMC Local card's LAN port MIB RxPause counter."
						::= { mc2200-FEMCEntry 31 }
mc2200-FEMCTxMultiple OBJECT-TYPE
						SYNTAX			Counter64
						MAX-ACCESS		read-only
						STATUS			current
						DESCRIPTION
                        "FEMC Local card's LAN port MIB TxMultiple counter."
						::= { mc2200-FEMCEntry 32 }
mc2200-FEMCRxUndersize OBJECT-TYPE
						SYNTAX			Counter64
						MAX-ACCESS		read-only
						STATUS			current
						DESCRIPTION
                        "FEMC Local card's LAN port MIB RxUndersize counter."
						::= { mc2200-FEMCEntry 33 }
mc2200-FEMCRxFragments OBJECT-TYPE
						SYNTAX			Counter64
						MAX-ACCESS		read-only
						STATUS			current
						DESCRIPTION
                        "FEMC Local card's LAN port MIB RxFragments counter."
						::= { mc2200-FEMCEntry 34 }
mc2200-FEMCRxOversize OBJECT-TYPE
						SYNTAX			Counter64
						MAX-ACCESS		read-only
						STATUS			current
						DESCRIPTION
                        "FEMC Local card's LAN port MIB RxOversize counter."
						::= { mc2200-FEMCEntry 35 }
mc2200-FEMCRxJabber OBJECT-TYPE
						SYNTAX			Counter64
						MAX-ACCESS		read-only
						STATUS			current
						DESCRIPTION
                        "FEMC Local card's LAN port MIB RxJabber counter."
						::= { mc2200-FEMCEntry 36 }
mc2200-FEMCRxErr OBJECT-TYPE
						SYNTAX			Counter64
						MAX-ACCESS		read-only
						STATUS			current
						DESCRIPTION
                        "FEMC Local card's LAN port MIB RxErr counter."
						::= { mc2200-FEMCEntry 37 }
mc2200-FEMCRxFCSErr OBJECT-TYPE
						SYNTAX			Counter64
						MAX-ACCESS		read-only
						STATUS			current
						DESCRIPTION
                        "FEMC Local card's LAN port MIB RxFCSErr counter."
						::= { mc2200-FEMCEntry 38 }
mc2200-FEMCTxCollisions OBJECT-TYPE
						SYNTAX			Counter64
						MAX-ACCESS		read-only
						STATUS			current
						DESCRIPTION
                        "FEMC Local card's LAN port MIB TxCollisions counter."
						::= { mc2200-FEMCEntry 39 }
mc2200-FEMCTxLate OBJECT-TYPE
						SYNTAX			Counter64
						MAX-ACCESS		read-only
						STATUS			current
						DESCRIPTION
                        "FEMC Local card's port8 MIB TxLate counter."
						::= { mc2200-FEMCEntry 40 }
mc2200-FEMCRemoteLANSFPInfo	OBJECT-TYPE
						SYNTAX		DisplayString
						MAX-ACCESS		read-only
						STATUS			current
						DESCRIPTION
                            "FEMC Remote card's LAN port SFP infomation."
						::= { mc2200-FEMCEntry 41 }
mc2200-FEMCRemoteLANLink      OBJECT-TYPE
						SYNTAX			INTEGER {up(1),
						                         down(2), noremotecard(0)}
						MAX-ACCESS		read-only
						STATUS			mandatory
						DESCRIPTION
                            "FEMC Remote card's LAN port work link status."
						::= { mc2200-FEMCEntry 42 }
mc2200-FEMCRemoteWANSFPInfo	OBJECT-TYPE
						SYNTAX		DisplayString
						MAX-ACCESS		read-only
						STATUS			current
						DESCRIPTION
                            "FEMC Remote card's WAN port SFP infomation."
						::= { mc2200-FEMCEntry 43 }
mc2200-FEMCRemoteWANLink	        OBJECT-TYPE
						SYNTAX			INTEGER {up(1),
						                         down(2), noremotecard(0)}
						MAX-ACCESS		read-only
						STATUS			current
						DESCRIPTION
                            "FEMC Remote card's WAN port work link status."
						::= { mc2200-FEMCEntry 44 }


mc2200-FEMCRemoteLANMode   	OBJECT-TYPE
						SYNTAX		INTEGER {mode100Base-FX-auto(1),
                          					mode100Base-full(2),
                          					mode100Base-Half(3),
                          					mode10Base-full(4),
                          					mode10Base-Half(5),noremotecard(0)}
						MAX-ACCESS		read-write
						STATUS			current
						DESCRIPTION
                        "FEMC Remote card's LAN port Mode configuration,
                    	set INTEGER(1) to 100Base-FX-auto,
                    	set INTEGER(2) to 100Base-full,
                    	set INTEGER(3) to 100Base-Half,
                    	set INTEGER(4) to 10Base-full,
                    	set INTEGER(5) to 10Base-Half,
                    	Ohter value is invalid"
						::= { mc2200-FEMCEntry  45 }
mc2200-FEMCRemoteIPAddress  OBJECT-TYPE
        			SYNTAX      IpAddress
        			ACCESS      read-write
        			STATUS      mandatory
	    			DESCRIPTION
            		"The IP address to FEMC Remote IP ping."
        			::= {mc2200-FEMCEntry 46}

mc2200-FEMCRemoteSubnetMask    OBJECT-TYPE
        			SYNTAX      IpAddress
        			ACCESS      read-write
        			STATUS      mandatory
	    			DESCRIPTION
                    "The Net mask to  FEMC Remote IP ping."
        			::= {mc2200-FEMCEntry 47}

mc2200-FEMCRemoteGateWay    OBJECT-TYPE
        			SYNTAX      IpAddress
        			ACCESS      read-write
        			STATUS      mandatory
	   				 DESCRIPTION
                    "The gateware to FEMC Remote IP ping."
        			::= {mc2200-FEMCEntry 48}

mc2200-FEMCRemoteVLANEnable  OBJECT-TYPE
        			SYNTAX      INTEGER {enable(1),disable(2), noremotecard(0)}
        			ACCESS      read-write
        			STATUS      mandatory
	    			DESCRIPTION
                    "Enable or disable Remote FEMC IP ping 802.1Q VLAN."
        			::= {mc2200-FEMCEntry 49}
mc2200-FEMCRemoteVID  OBJECT-TYPE
        			SYNTAX      INTEGER
        			ACCESS      read-write
        			STATUS      mandatory
	    			DESCRIPTION
                    "FEMC Remote IP ping  802.1Q VLAN ID."
        			::= {mc2200-FEMCEntry 50}
mc2200-FEMCRemoteAlarm      OBJECT-TYPE
						SYNTAX			INTEGER  {enabled(1),disabled(2)}
						MAX-ACCESS		read-write
						STATUS			current
						DESCRIPTION
                        "Enable or disable FEMC Media converter card remote alarm.
                         set INTEGER(1) to Enable remote alarm,
                         set INTEGER(2) to Disable remote alarm,
                         Other value is invalid."
						::= { mc2200-FEMCEntry 51 }
mc2200-FEMCRFD		      OBJECT-TYPE
						SYNTAX			INTEGER  {enabled(1),disabled(2)}
						MAX-ACCESS		read-write
						STATUS			current
						DESCRIPTION
                        "FEMC Media converter card remote fault detect operation.
                         set INTEGER(1) to Enable RFD,
                         set INTEGER(2) to Disable RFD,
                         Other value is invalid."
						::= { mc2200-FEMCEntry 52 }
mc2200-FEMCDefault		OBJECT-TYPE
						SYNTAX			INTEGER
						MAX-ACCESS		write-only
						STATUS			current
						DESCRIPTION
                        "Write FEMC card default setting,
                        set INTEGER(1) to write default.
                        Other value is invalid."
						::= { mc2200-FEMCEntry 53 }
mc2200-FEMCReboot		OBJECT-TYPE
						SYNTAX			INTEGER
						MAX-ACCESS		write-only
						STATUS			current
						DESCRIPTION
                        "Reboot FEMC local card,
                        set INTEGER(1) to reboot this card.
                        Other value is invalid. "
						::= { mc2200-FEMCEntry 54 }
mc2200-FEMCLocalLANSpeed      OBJECT-TYPE
						SYNTAX			INTEGER {speed100M(1),
						                         speed10M(2),down(3)}
						MAX-ACCESS		read-only
						STATUS			mandatory
						DESCRIPTION
                        "GE-MC3 Local card's LAN port work speed status."
						::= { mc2200-FEMCEntry 55 }
mc2200-FEMCRemoteLANSpeed      OBJECT-TYPE
						SYNTAX			INTEGER {speed100M(1),speed10M(2),
						                         down(3),noremotecard(0)}
						MAX-ACCESS		read-only
						STATUS			mandatory
						DESCRIPTION
                        "GE-MC3 Remote card's LAN port work speed status."
						::= { mc2200-FEMCEntry 56 }

mc2200-FEMCLocalportuser      OBJECT-TYPE
						SYNTAX			DisplayString
						MAX-ACCESS		read-write
						STATUS			current
						DESCRIPTION
                        " User of GE-MC3 Local Port1. "
						::= { mc2200-FEMCEntry 57 }

mc2200-FEMCRemoteportuser      OBJECT-TYPE
						SYNTAX			DisplayString
						MAX-ACCESS		read-write
						STATUS			current
						DESCRIPTION
                        " User of GE-MC3 Remote Port1. "
						::= { mc2200-FEMCEntry 58 }

mc2200-FEMCWANOpticalPowerCheck        OBJECT-TYPE
						SYNTAX			INTEGER  {enabled(1),disabled(2)}
						MAX-ACCESS		read-write
						STATUS			current
						DESCRIPTION
                        "FEMC Media converter card WANOpticalPowerCheck operation.
                         set INTEGER(1) to Enable WANOpticalPowerCheck,
                         set INTEGER(2) to Disable WANOpticalPowerCheck,
                         Other value is invalid."
						::= { mc2200-FEMCEntry 59 }
mc2200-FEMCWANThreshold        OBJECT-TYPE

						SYNTAX		INTEGER  {db-32(1),db-31dot5(2),db-31(3),db-30dot5(4),db-30(5),db-29dot5(6),db-29(7),db-28dot5(8),
                     								db-28(9),db-27dot5(10),db-27(11),db-26dot5(12),db-26(13),db-25dot5(14),db-25(15),
		     								db-24dot5(16),db-24(17),db-23dot5(18),db-23(19),db-22dot5(20),db-22(21),db-21dot5(22),db-21(23),
                     								db-20dot5(24),db-20(25),db-19dot5(26),db-19(27),db-18dot5(28),db-18(29),
                     								db-17dot5(30),db-17(31),db-16dot5(32),db-16(33),db-15dot5(34),db-15(35),
                     								db-14dot5(36),db-14(37),db-13dot5(38),db-13(39),db-12dot5(40),db-12(41),
		     								db-11dot5(42),db-11(43),db-10dot5(44),db-10(45),db-9dot5(46),db-9(47),db-8dot5(48),db-8(49),
                     								db-7dot5(50),db-7(51),db-6dot5(52),db-6(53),db-5dot5(54),db-5(55),
                     								db-4dot5(56),db-4(57),db-3dot5(58),db-3(59),db-2dot5(60),db-2(61),
                     								db-1dot5(62),db-1(63),db-0dot5(64),db-0(65),db0dot5(66),db1(67),db1dot5(68),db2(69),db2dot5(70),
		     								db3(71)}
						MAX-ACCESS		read-write
						STATUS			current
						DESCRIPTION
                        "FEMC Media converter card WANThreshold operation.
                         Other value is invalid."
						::= { mc2200-FEMCEntry 60 }
mc2200-FEMCTrapFilterLocalLAN	        OBJECT-TYPE
						SYNTAX			INTEGER {enabled(1),disabled(2)}
						MAX-ACCESS		read-write
						STATUS			current
						DESCRIPTION
                            "Local LAN of FEMC Trap Filter ."
						::= { mc2200-FEMCEntry 61 }
mc2200-FEMCTrapFilterLocalWAN	        OBJECT-TYPE
						SYNTAX			INTEGER {enabled(1),disabled(2)}
						MAX-ACCESS		read-write
						STATUS			current
						DESCRIPTION
                            "Local WAN of FEMC Trap Filter ."
						::= { mc2200-FEMCEntry 62 }
mc2200-FEMCTrapFilterRemotePower	        OBJECT-TYPE
						SYNTAX			INTEGER {enabled(1),disabled(2)}
						MAX-ACCESS		read-write
						STATUS			current
						DESCRIPTION
                            "Remote Power of FEMC Trap Filter ."
						::= { mc2200-FEMCEntry 63 }
mc2200-FEMCTrapFilterRemoteLAN	        OBJECT-TYPE
						SYNTAX			INTEGER {enabled(1),disabled(2)}
						MAX-ACCESS		read-write
						STATUS			current
						DESCRIPTION
                            "Remote LAN of FEMC Trap Filter ."
						::= { mc2200-FEMCEntry 64 }
mc2200-FEMCTrapFilterRemoteWAN	        OBJECT-TYPE
						SYNTAX			INTEGER {enabled(1),disabled(2)}
						MAX-ACCESS		read-write
						STATUS			current
						DESCRIPTION
                            "Remote WAN of FEMC Trap Filter ."
						::= { mc2200-FEMCEntry 65 }

mc2200-FEMCLoopback      OBJECT-TYPE
						SYNTAX			INTEGER {disable(1),local_lanouter(2),local_laninner(3),local_wanouter(4),
												local_waninner(5),remote_lanouter(6),remote_laninner(7)}
						MAX-ACCESS		read-write
						STATUS			mandatory
						DESCRIPTION
                            "FEMC card's loopback."
						::= { mc2200-FEMCEntry 66 }
mc2200-FEMCCardType	OBJECT-TYPE
						SYNTAX		DisplayString
						MAX-ACCESS		read-only
						STATUS			current
						DESCRIPTION
                            "FEMC card's Type."
						::= { mc2200-FEMCEntry 67 }

-- ============2011-05-18==EOAM OVER HERE=======================
-- FIBERNETWORK-TRAP
mc2200-card-PlugIn              TRAP-TYPE
                         ENTERPRISE    mc2200-TrapID
                         DESCRIPTION   "A plugInCard trap signifies that some Converter
                                          has been pluged in."
                         ::= 1

mc2200-card-PullOut             TRAP-TYPE
                         ENTERPRISE    mc2200-TrapID
                         DESCRIPTION   "A pullOutCard trap signifies that some Converter
                                        has been pulled out."
                         ::= 2

mc2200-card-Local-Tx-Up         TRAP-TYPE
                         ENTERPRISE    mc2200-TrapID
                         DESCRIPTION   "A local-txlink-up trap signifies that some
                                        local Converter's Tx link has transitioned into
                                        the up state."
                         ::= 3

mc2200-card-Local-Tx-Down       TRAP-TYPE
                         ENTERPRISE    mc2200-TrapID
                         DESCRIPTION   "A local-txlink-down trap signifies that some local
                                        Converter's Tx link has transitioned into the down
                                        state."
                         ::= 4

mc2200-card-Local-Fx-Up         TRAP-TYPE
                         ENTERPRISE    mc2200-TrapID
                         DESCRIPTION   "A local-fxlink-up trap signifies that some local
                                        Converter's Fx link has transitioned into the up
                                        state."
                         ::= 5

mc2200-card-Local-Fx-Down       TRAP-TYPE
                         ENTERPRISE    mc2200-TrapID
                         DESCRIPTION   "A local-fxlink-down trap signifies that some local
                                        Converter's Fx link has transitioned into the down
                                        state."
                         ::= 6

mc2200-card-Remote-Power-On     TRAP-TYPE
                         ENTERPRISE    mc2200-TrapID
                         DESCRIPTION   "A remote-power-on trap signifies that some remote
                                        Converter's power has supply on."
                         ::= 7

mc2200-card-Remote-Power-Off    TRAP-TYPE
                         ENTERPRISE    mc2200-TrapID
                         DESCRIPTION   "A remote-power-on trap signifies that some remote
                                        Converter's power has supply off."
                         ::= 8

mc2200-card-Remote-Tx-Up        TRAP-TYPE
                         ENTERPRISE  mc2200-TrapID
                         DESCRIPTION
                                     "A remote-txlink-up trap signifies that some remote
                                        Converter's Tx link has transitioned into the up
                                        state."
                         ::= 9

mc2200-card-Remote-Tx-Down      TRAP-TYPE
                         ENTERPRISE   mc2200-TrapID
                         DESCRIPTION
                                      "A remote-txlink-down trap signifies that some remote
                                       Converter's Tx link has transitioned into the down
                                       state."
                         ::= 10

mc2200-chassis-Power-A-Active       TRAP-TYPE
                         ENTERPRISE   mc2200-TrapID
                         DESCRIPTION
                                      "A Power-A-Active trap signifies that Power A in
                                       chassis is actived"
                         ::= 11

mc2200-chassis-Power-A-Down     TRAP-TYPE
                         ENTERPRISE   mc2200-TrapID
                         DESCRIPTION  "A Power-A-down trap signifies that Power A in
                                       chassis Failed"
                         ::= 12

mc2200-chassis-Power-A-Standby  TRAP-TYPE
                         ENTERPRISE   mc2200-TrapID
                         DESCRIPTION  "A Power-A-Standby trap signifies that Power A stauts is
                                       change to standby"
                         ::= 13

mc2200-chassis-Power-B-Active   TRAP-TYPE
                         ENTERPRISE  mc2200-TrapID
                         DESCRIPTION
                                     "A Power-B-Active trap signifies that Power B in
                                       chassis is actived"
                         ::= 14

mc2200-chassis-Power-B-Down     TRAP-TYPE
                         ENTERPRISE  mc2200-TrapID
                         DESCRIPTION
                                     "A Power-B-down trap signifies that Power B in
                                       chassis Failed"
                        ::= 15

mc2200-chassis-Power-B-Standby  TRAP-TYPE
                         ENTERPRISE   mc2200-TrapID
                         DESCRIPTION  "A Power-B-Standby trap signifies that Power B stauts is
                                       change to standby"
                         ::= 16

mc2200-chassis-Fan-A-Up        TRAP-TYPE
                        ENTERPRISE  mc2200-TrapID
                        DESCRIPTION
                                    "A Fan-A-up trap signifies that Fan A in chassis is OK"
                        ::= 17

mc2200-chassis-Fan-A-Down       TRAP-TYPE
                        ENTERPRISE  mc2200-TrapID
                        DESCRIPTION
                                    "A Fan-A-down trap signifies that Fan A in chassis Failed"
                        ::= 18

mc2200-chassis-Fan-B-Up        TRAP-TYPE
                        ENTERPRISE  mc2200-TrapID
                        DESCRIPTION
                                    "A Fan-B-up trap signifies that Fan B in chassis is OK"
                        ::= 19

mc2200-chassis-Fan-B-Down       TRAP-TYPE
                        ENTERPRISE  mc2200-TrapID
                        DESCRIPTION
                                    "A Fan-B-down trap signifies that Fan B in chassis Failed"
                        ::= 20

mc2200-chassis-Connected       TRAP-TYPE
                        ENTERPRISE  mc2200-TrapID
                        DESCRIPTION
                           "A chassis-find trap signifies that some Slave Chassis
                                     console has been Connected."
                        ::= 21

mc2200-chassis-Disconnected    TRAP-TYPE
                        ENTERPRISE  mc2200-TrapID
                        DESCRIPTION
                                    "A chassis-lost trap signifies that some Slave Chassis
                                    console has been disconnected."
                        ::= 22


mc2200-GEMux8-local-WAN-linkup 	TRAP-TYPE
                         	ENTERPRISE    mc2200-TrapID
                         	DESCRIPTION   "A mc2200-GEMux8-local-WAN-linkup trap signifies that some
                                        local GEMux8 Converter's WAN link has transitioned into
                                        the up state."
                         	::= 23
mc2200-GEMux8-local-WAN-linkdown 	TRAP-TYPE
                         	ENTERPRISE    mc2200-TrapID
                         	DESCRIPTION   "A mc2200-GEMux8-local-WAN-linkdown trap signifies that some
                                        local GEMux8 Converter's WAN link has transitioned into
                                        the down state."
                         	::= 24

mc2200-GEMux8-local-LAN-linkup 	TRAP-TYPE
                         	ENTERPRISE    mc2200-TrapID
                         	DESCRIPTION   "A mc2200-GEMux8-local-LAN-linkup trap signifies that some
                                        local GEMux8 Converter's LAN link has transitioned into
                                        the up state."
                         	::= 25
mc2200-GEMux8-local-LAN-linkdown 	TRAP-TYPE
                         	ENTERPRISE    mc2200-TrapID
                         	DESCRIPTION   "A mc2200-GEMux8-local-LAN-linkdown trap signifies that some
                                        local GEMux8 Converter's LAN link has transitioned into
                                        the down state."
                         	::= 26

mc2200-GEMux8-local-PORT1-linkup 	TRAP-TYPE
                         	ENTERPRISE    mc2200-TrapID
                         	DESCRIPTION   "A mc2200-GEMux8-local-PORT1-linkup trap signifies that some
                                        local GEMux8 Converter's Port1 link has transitioned into
                                        the up state."
                         	::= 27
mc2200-GEMux8-local-PORT1-linkdown 	TRAP-TYPE
                         	ENTERPRISE    mc2200-TrapID
                         	DESCRIPTION   "A mc2200-GEMux8-local-PORT1-linkdown trap signifies that some
                                        local GEMux8 Converter's Port1 link has transitioned into
                                        the down state."
                         	::= 28
mc2200-GEMux8-local-PORT2-linkup 	TRAP-TYPE
                         	ENTERPRISE    mc2200-TrapID
                         	DESCRIPTION   "A mc2200-GEMux8-local-PORT2-linkup trap signifies that some
                                        local GEMux8 Converter's Port 2 link has transitioned into
                                        the up state."
                         	::= 29
mc2200-GEMux8-local-PORT2-linkdown 	TRAP-TYPE
                         	ENTERPRISE    mc2200-TrapID
                         	DESCRIPTION   "A mc2200-GEMux8-local-PORT2-linkdown trap signifies that some
                                        local GEMux8 Converter's Port 2 link has transitioned into
                                        the down state."
                         	::= 30

mc2200-GEMux8-local-PORT3-linkup 	TRAP-TYPE
                         	ENTERPRISE    mc2200-TrapID
                         	DESCRIPTION   "A mc2200-GEMux8-local-PORT3-linkup trap signifies that some
                                        local GEMux8 Converter's Port 3 link has transitioned into
                                        the up state."
                         	::= 31
mc2200-GEMux8-local-PORT3-linkdown 	TRAP-TYPE
                         	ENTERPRISE    mc2200-TrapID
                         	DESCRIPTION   "A mc2200-GEMux8-local-PORT3-linkdown trap signifies that some
                                        local GEMux8 Converter's Port 3 link has transitioned into
                                        the down state."
                         	::= 32
mc2200-GEMux8-local-PORT4-linkup 	TRAP-TYPE
                         	ENTERPRISE    mc2200-TrapID
                         	DESCRIPTION   "A mc2200-GEMux8-local-PORT4-linkup trap signifies that some
                                        local GEMux8 Converter's Port 4 link has transitioned into
                                        the up state."
                         	::= 33
mc2200-GEMux8-local-PORT4-linkdown 	TRAP-TYPE
                         	ENTERPRISE    mc2200-TrapID
                         	DESCRIPTION   "A mc2200-GEMux8-local-PORT4-linkdown trap signifies that some
                                        local GEMux8 Converter's Port 4 link has transitioned into
                                        the down state."
                         	::= 34
mc2200-GEMux8-local-PORT5-linkup 	TRAP-TYPE
                         	ENTERPRISE    mc2200-TrapID
                         	DESCRIPTION   "A mc2200-GEMux8-local-PORT5-linkup trap signifies that some
                                        local GEMux8 Converter's Port 5 link has transitioned into
                                        the up state."
                         	::= 35
mc2200-GEMux8-local-PORT5-linkdown 	TRAP-TYPE
                         	ENTERPRISE    mc2200-TrapID
                         	DESCRIPTION   "A mc2200-GEMux8-local-PORT5-linkdown trap signifies that some
                                        local GEMux8 Converter's Port 5 link has transitioned into
                                        the down state."
                         	::= 36
mc2200-GEMux8-local-PORT6-linkup 	TRAP-TYPE
                         	ENTERPRISE    mc2200-TrapID
                         	DESCRIPTION   "A mc2200-GEMux8-local-PORT6-linkup trap signifies that some
                                        local GEMux8 Converter's Port 6 link has transitioned into
                                        the up state."
                         	::= 37
mc2200-GEMux8-local-PORT6-linkdown 	TRAP-TYPE
                         	ENTERPRISE    mc2200-TrapID
                         	DESCRIPTION   "A mc2200-GEMux8-local-PORT6-linkdown trap signifies that some
                                        local GEMux8 Converter's Port 6 link has transitioned into
                                        the down state."
                         	::= 38
mc2200-GEMux8-local-PORT7-linkup 	TRAP-TYPE
                         	ENTERPRISE    mc2200-TrapID
                         	DESCRIPTION   "A mc2200-GEMux8-local-PORT7-linkup trap signifies that some
                                        local GEMux8 Converter's Port 7 link has transitioned into
                                        the up state."
                         	::= 39
mc2200-GEMux8-local-PORT7-linkdown 	TRAP-TYPE
                         	ENTERPRISE    mc2200-TrapID
                         	DESCRIPTION   "A mc2200-GEMux8-local-PORT7-linkdown trap signifies that some
                                        local GEMux8 Converter's Port 7 link has transitioned into
                                        the down state."
                         	::= 40
mc2200-GEMux8-local-PORT8-linkup 	TRAP-TYPE
                         	ENTERPRISE    mc2200-TrapID
                         	DESCRIPTION   "A mc2200-GEMux8-local-PORT8-linkup trap signifies that some
                                        local GEMux8 Converter's Port 8 link has transitioned into
                                        the up state."
                         	::= 41
mc2200-GEMux8-local-PORT8-linkdown 	TRAP-TYPE
                         	ENTERPRISE    mc2200-TrapID
                         	DESCRIPTION   "A mc2200-GEMux8-local-PORT8-linkdown trap signifies that some
                                        local GEMux8 Converter's Port 8 link has transitioned into
                                        the down state."
                         	::= 42

mc2200-GEMux8-remote-LAN-linkup 	TRAP-TYPE
                         	ENTERPRISE    mc2200-TrapID
                         	DESCRIPTION   "A mc2200-GEMux8-remote-LAN-linkup trap signifies that some
                                        remote GEMux8 Converter's LAN link has transitioned into
                                        the up state."
                         	::= 43
mc2200-GEMux8-remote-LAN-linkdown 	TRAP-TYPE
                         	ENTERPRISE    mc2200-TrapID
                         	DESCRIPTION   "A mc2200-GEMux8-remote-LAN-linkdown trap signifies that some
                                        remote GEMux8 Converter's LAN link has transitioned into
                                        the down state."
                         	::= 44

mc2200-GEMux8-remote-PORT1-linkup 	TRAP-TYPE
                         	ENTERPRISE    mc2200-TrapID
                         	DESCRIPTION   "A mc2200-GEMux8-remote-PORT1-linkup trap signifies that some
                                        remote GEMux8 Converter's Port1 link has transitioned into
                                        the up state."
                         	::= 45
mc2200-GEMux8-remote-PORT1-linkdown 	TRAP-TYPE
                         	ENTERPRISE    mc2200-TrapID
                         	DESCRIPTION   "A mc2200-GEMux8-remote-PORT1-linkdown trap signifies that some
                                        remote GEMux8 Converter's Port1 link has transitioned into
                                        the down state."
                         	::= 46
mc2200-GEMux8-remote-PORT2-linkup 	TRAP-TYPE
                         	ENTERPRISE    mc2200-TrapID
                         	DESCRIPTION   "A mc2200-GEMux8-remote-PORT2-linkup trap signifies that some
                                        remote GEMux8 Converter's Port 2 link has transitioned into
                                        the up state."
                         	::= 47
mc2200-GEMux8-remote-PORT2-linkdown 	TRAP-TYPE
                         	ENTERPRISE    mc2200-TrapID
                         	DESCRIPTION   "A mc2200-GEMux8-remote-PORT2-linkdown trap signifies that some
                                        remote GEMux8 Converter's Port 2 link has transitioned into
                                        the down state."
                         	::= 48

mc2200-GEMux8-remote-PORT3-linkup 	TRAP-TYPE
                         	ENTERPRISE    mc2200-TrapID
                         	DESCRIPTION   "A mc2200-GEMux8-remote-PORT3-linkup trap signifies that some
                                        remote GEMux8 Converter's Port 3 link has transitioned into
                                        the up state."
                         	::= 49
mc2200-GEMux8-remote-PORT3-linkdown 	TRAP-TYPE
                         	ENTERPRISE    mc2200-TrapID
                         	DESCRIPTION   "A mc2200-GEMux8-remote-PORT3-linkdown trap signifies that some
                                        remote GEMux8 Converter's Port 3 link has transitioned into
                                        the down state."
                         	::= 50
mc2200-GEMux8-remote-PORT4-linkup 	TRAP-TYPE
                         	ENTERPRISE    mc2200-TrapID
                         	DESCRIPTION   "A mc2200-GEMux8-remote-PORT4-linkup trap signifies that some
                                        remote GEMux8 Converter's Port 4 link has transitioned into
                                        the up state."
                         	::= 51
mc2200-GEMux8-remote-PORT4-linkdown 	TRAP-TYPE
                         	ENTERPRISE    mc2200-TrapID
                         	DESCRIPTION   "A mc2200-GEMux8-remote-PORT4-linkdown trap signifies that some
                                        remote GEMux8 Converter's Port 4 link has transitioned into
                                        the down state."
                         	::= 52
mc2200-GEMux8-remote-PORT5-linkup 	TRAP-TYPE
                         	ENTERPRISE    mc2200-TrapID
                         	DESCRIPTION   "A mc2200-GEMux8-remote-PORT5-linkup trap signifies that some
                                        remote GEMux8 Converter's Port 5 link has transitioned into
                                        the up state."
                         	::= 53
mc2200-GEMux8-remote-PORT5-linkdown 	TRAP-TYPE
                         	ENTERPRISE    mc2200-TrapID
                         	DESCRIPTION   "A mc2200-GEMux8-remote-PORT5-linkdown trap signifies that some
                                        remote GEMux8 Converter's Port 5 link has transitioned into
                                        the down state."
                         	::= 54
mc2200-GEMux8-remote-PORT6-linkup 	TRAP-TYPE
                         	ENTERPRISE    mc2200-TrapID
                         	DESCRIPTION   "A mc2200-GEMux8-remote-PORT6-linkup trap signifies that some
                                        remote GEMux8 Converter's Port 6 link has transitioned into
                                        the up state."
                         	::= 55
mc2200-GEMux8-remote-PORT6-linkdown 	TRAP-TYPE
                         	ENTERPRISE    mc2200-TrapID
                         	DESCRIPTION   "A mc2200-GEMux8-remote-PORT6-linkdown trap signifies that some
                                        remote GEMux8 Converter's Port 6 link has transitioned into
                                        the down state."
                         	::= 56
mc2200-GEMux8-remote-PORT7-linkup 	TRAP-TYPE
                         	ENTERPRISE    mc2200-TrapID
                         	DESCRIPTION   "A mc2200-GEMux8-remote-PORT7-linkup trap signifies that some
                                        remote GEMux8 Converter's Port 7 link has transitioned into
                                        the up state."
                         	::= 57
mc2200-GEMux8-remote-PORT7-linkdown 	TRAP-TYPE
                         	ENTERPRISE    mc2200-TrapID
                         	DESCRIPTION   "A mc2200-GEMux8-remote-PORT7-linkdown trap signifies that some
                                        remote GEMux8 Converter's Port 7 link has transitioned into
                                        the down state."
                         	::= 58
mc2200-GEMux8-remote-PORT8-linkup 	TRAP-TYPE
                         	ENTERPRISE    mc2200-TrapID
                         	DESCRIPTION   "A mc2200-GEMux8-remote-PORT8-linkup trap signifies that some
                                        remote GEMux8 Converter's Port 8 link has transitioned into
                                        the up state."
                         	::= 59
mc2200-GEMux8-remote-PORT8-linkdown 	TRAP-TYPE
                         	ENTERPRISE    mc2200-TrapID
                         	DESCRIPTION   "A mc2200-GEMux8-remote-PORT8-linkdown trap signifies that some
                                        remote GEMux8 Converter's Port 8 link has transitioned into
                                        the down state."
                         	::= 60
mc2200-GEMux8-remote-PORT9-linkup 	TRAP-TYPE
                         	ENTERPRISE    mc2200-TrapID
                         	DESCRIPTION   "A fmc-GEMux8-remote-PORT8-linkup trap signifies that some
                                        remote GEMux8 Converter's Port 8 link has transitioned into
                                        the up state."
                         	::= 61
mc2200-GEMux8-remote-PORT9-linkdown 	TRAP-TYPE
                         	ENTERPRISE    mc2200-TrapID
                         	DESCRIPTION   "A fmc-GEMux8-remote-PORT8-linkdown trap signifies that some
                                        remote GEMux8 Converter's Port 8 link has transitioned into
                                        the down state."
                         	::= 62


mc2200-chassis-Power-Card-PlugIn   TRAP-TYPE
                         ENTERPRISE  mc2200-TrapID
                         DESCRIPTION
                                     "A chassis-Power-Card-PlugIn trap signifies that power card in
                                       chassis has been pluged in"
                         ::= 63

mc2200-chassis-Power-Card-Removed  TRAP-TYPE
                         ENTERPRISE  mc2200-TrapID
                         DESCRIPTION
                                     "A chassis-Power-Card-Removed trap signifies that power card in
                                       chassis has been removed"
                        ::= 64

mc2200-card-Remote-PowerA-Up-PowerB-Down     TRAP-TYPE
                         ENTERPRISE    mc2200-TrapID
                         DESCRIPTION   "A card-Remote-PowerA_On-PowerB_Off trap signifies that some remote
                                        Converter's power A has supply on and Power B has supply off."
                         ::= 65

mc2200-card-Remote-PowerA-Down-PowerB-Up    TRAP-TYPE
                         ENTERPRISE    mc2200-TrapID
                         DESCRIPTION   "A rcard-Remote-PowerA_Off-PowerB_On trap signifies that some remote
                                        Converter's power A has supply off and Power B has supply off."
                         ::= 66


mc2200-GEMC-local-LAN-linkup 	TRAP-TYPE
                         	ENTERPRISE    mc2200-TrapID
                         	DESCRIPTION   "A mc2200-GEMC-local-LAN-linkup trap signifies that some
                                        local GEMC Converter's LAN link has transitioned into
                                        the up state."
                         	::= 67
mc2200-GEMC-local-LAN-linkdown 	TRAP-TYPE
                         	ENTERPRISE    mc2200-TrapID
                         	DESCRIPTION   "A mc2200-GEMC-local-LAN-linkdown trap signifies that some
                                        local GEMC Converter's LAN link has transitioned into
                                        the down state."
                         	::= 68
mc2200-GEMC-local-WAN-linkup 	TRAP-TYPE
                         	ENTERPRISE    mc2200-TrapID
                         	DESCRIPTION   "A mc2200-GEMC-local-WAN-linkup trap signifies that some
                                        local GEMC Converter's WAN link has transitioned into
                                        the up state."
                         	::= 69
mc2200-GEMC-local-WAN-linkdown 	TRAP-TYPE
                         	ENTERPRISE    mc2200-TrapID
                         	DESCRIPTION   "A mc2200-GEMC-local-WAN-linkdown trap signifies that some
                                        local GEMC Converter's WAN link has transitioned into
                                        the down state."
                         	::= 70
mc2200-GEMC-remote-LAN-linkup 	TRAP-TYPE
                         	ENTERPRISE    mc2200-TrapID
                         	DESCRIPTION   "A mc2200-GEMC-remote-LAN-linkup trap signifies that some
                                        remote GEMC Converter's LAN link has transitioned into
                                        the up state."
                         	::= 71
mc2200-GEMC-remote-LAN-linkdown 	TRAP-TYPE
                         	ENTERPRISE    mc2200-TrapID
                         	DESCRIPTION   "A mc2200-GEMC-local-PORT1-linkdown trap signifies that some
                                        remote GEMC Converter's LAN link has transitioned into
                                        the down state."
                         	::= 72


mc2200-GEMC4-local-LAN1-linkup 	TRAP-TYPE
                         	ENTERPRISE    mc2200-TrapID
                         	DESCRIPTION   "A mc2200-GEMC4-local-LAN1-linkup trap signifies that some
                                        local GEMC4 Converter's LAN1 link has transitioned into
                                        the up state."
                         	::= 73
mc2200-GEMC4-local-LAN1-linkdown 	TRAP-TYPE
                         	ENTERPRISE    mc2200-TrapID
                         	DESCRIPTION   "A mc2200-GEMC4-local-LAN1-linkdown trap signifies that some
                                        local GEMC4 Converter's LAN1 link has transitioned into
                                        the down state."
                         	::= 74
mc2200-GEMC4-local-LAN2-linkup 	TRAP-TYPE
                         	ENTERPRISE    mc2200-TrapID
                         	DESCRIPTION   "A mc2200-GEMC4-local-LAN2-linkup trap signifies that some
                                        local GEMC4 Converter's LAN2 link has transitioned into
                                        the up state."
                         	::= 75
mc2200-GEMC4-local-LAN2-linkdown 	TRAP-TYPE
                         	ENTERPRISE    mc2200-TrapID
                         	DESCRIPTION   "A mc2200-GEMC4-local-LAN2-linkdown trap signifies that some
                                        local GEMC4 Converter's LAN2 link has transitioned into
                                        the down state."
                         	::= 76
mc2200-GEMC4-local-WAN2LAN3-linkup 	TRAP-TYPE
                         	ENTERPRISE    mc2200-TrapID
                         	DESCRIPTION   "A mc2200-GEMC4-local-LAN3-linkup trap signifies that some
                                        local GEMC4 Converter's WAN2-LAN3 link has transitioned into
                                        the up state."
                         	::= 77
mc2200-GEMC4-local-WAN2LAN3-linkdown 	TRAP-TYPE
                         	ENTERPRISE    mc2200-TrapID
                         	DESCRIPTION   "A mc2200-GEMC4-local-LAN3-linkdown trap signifies that some
                                        local GEMC4 Converter's WAN2-LAN3 link has transitioned into
                                        the down state."
                         	::= 78
mc2200-GEMC4-local-WAN1-linkup 	TRAP-TYPE
                         	ENTERPRISE    mc2200-TrapID
                         	DESCRIPTION   "A mc2200-GEMC4-local-WAN1-linkup trap signifies that some
                                        local GEMC4 Converter's WAN1 link has transitioned into
                                        the up state."
                         	::= 79
mc2200-GEMC4-local-WAN1-linkdown 	TRAP-TYPE
                         	ENTERPRISE    mc2200-TrapID
                         	DESCRIPTION   "A mc2200-GEMC4-local-WAN1-linkdown trap signifies that some
                                        local GEMC4 Converter's WAN1 link has transitioned into
                                        the down state."
                         	::= 80

mc2200-GEMC4-remote-LAN1-linkup 	TRAP-TYPE
                         	ENTERPRISE    mc2200-TrapID
                         	DESCRIPTION   "A mc2200-GEMC4-remote-LAN1-linkup trap signifies that some
                                        remote GEMC4 Converter's LAN1 link has transitioned into
                                        the up state."
                         	::= 81
mc2200-GEMC4-remote-LAN1-linkdown 	TRAP-TYPE
                         	ENTERPRISE    mc2200-TrapID
                         	DESCRIPTION   "A mc2200-GEMC4-remote-LAN1-linkdown trap signifies that some
                                        remote GEMC4 Converter's LAN1 link has transitioned into
                                        the down state."
                         	::= 82
mc2200-GEMC4-remote-LAN2-linkup 	TRAP-TYPE
                         	ENTERPRISE    mc2200-TrapID
                         	DESCRIPTION   "A mc2200-GEMC4-remote-LAN2-linkup trap signifies that some
                                        remote GEMC4 Converter's LAN2 link has transitioned into
                                        the up state."
                         	::= 83
mc2200-GEMC4-remote-LAN2-linkdown 	TRAP-TYPE
                         	ENTERPRISE    mc2200-TrapID
                         	DESCRIPTION   "A mc2200-GEMC4-remote-LAN2-linkdown trap signifies that some
                                        remote GEMC4 Converter's LAN2 link has transitioned into
                                        the down state."
                         	::= 84
mc2200-GEMC4-remote-WAN2LAN3-linkup 	TRAP-TYPE
                         	ENTERPRISE    mc2200-TrapID
                         	DESCRIPTION   "A mc2200-GEMC4-remote-LAN3-linkup trap signifies that some
                                        remote GEMC4 Converter's WAN2-LAN3 link has transitioned into
                                        the up state."
                         	::= 85
mc2200-GEMC4-remote-WAN2LAN3-linkdown 	TRAP-TYPE
                         	ENTERPRISE    mc2200-TrapID
                         	DESCRIPTION   "A mc2200-GEMC4-remote-LAN3-linkdown trap signifies that some
                                        remote GEMC4 Converter's WAN2-LAN3 link has transitioned into
                                        the down state."
                         	::= 86

mc2200-GEMC2-local-LAN-linkup 	TRAP-TYPE
                         	ENTERPRISE    mc2200-TrapID
                         	DESCRIPTION   "A mc2200-GEMC2-local-LAN-linkup trap signifies that some
                                        local GEMC2 Converter's LAN link has transitioned into
                                        the up state."
                         	::= 97
mc2200-GEMC2-local-LAN-linkdown 	TRAP-TYPE
                         	ENTERPRISE    mc2200-TrapID
                         	DESCRIPTION   "A mc2200-GEMC2-local-LAN-linkdown trap signifies that some
                                        local GEMC2 Converter's LAN link has transitioned into
                                        the down state."
                         	::= 98
mc2200-GEMC2-local-WAN-linkup 	    TRAP-TYPE
                         	ENTERPRISE    mc2200-TrapID
                         	DESCRIPTION   "A mc2200-GEMC2-local-WAN-linkup trap signifies that some
                                        local GEMC2 Converter's WAN link has transitioned into
                                        the up state."
                         	::= 99
mc2200-GEMC2-local-WAN-linkdown 	TRAP-TYPE
                         	ENTERPRISE    mc2200-TrapID
                         	DESCRIPTION   "A mc2200-GEMC2-local-WAN-linkdown trap signifies that some
                                        local GEMC2 Converter's WAN link has transitioned into
                                        the down state."
                         	::= 100
mc2200-GEMC2-remote-LAN-linkup 	TRAP-TYPE
                         	ENTERPRISE    mc2200-TrapID
                         	DESCRIPTION   "A mc2200-GEMC2-remote-LAN-linkup trap signifies that some
                                        remote GEMC2 Converter's LAN1 link has transitioned into
                                        the up state."
                         	::= 101
mc2200-GEMC2-remote-LAN-linkdown 	TRAP-TYPE
                         	ENTERPRISE    mc2200-TrapID
                         	DESCRIPTION   "A mc2200-GEMC2-remote-LAN-linkdown trap signifies that some
                                        remote GEMC2 Converter's LAN1 link has transitioned into
                                        the down state."
                         	::= 102



mc2200-GEMC2E-local-LAN-linkup 	TRAP-TYPE
                         	ENTERPRISE    mc2200-TrapID
                         	DESCRIPTION   "A mc2200-GEMC2E-local-LAN-linkup trap signifies that some
                                        local GEMC2E Converter's LAN link has transitioned into
                                        the up state."
                         	::= 103

mc2200-GEMC2E-local-LAN-linkdown 	TRAP-TYPE
                         	ENTERPRISE    mc2200-TrapID
                         	DESCRIPTION   "A mc2200-GEMC2E-local-LAN-linkdown trap signifies that some
                                        local GEMC2E Converter's LAN link has transitioned into
                                        the down state."
                         	::= 104

mc2200-GEMC2E-local-WAN-linkup 	    TRAP-TYPE
                         	ENTERPRISE    mc2200-TrapID
                         	DESCRIPTION   "A mc2200-GEMC2E-local-WAN-linkup trap signifies that some
                                        local GEMC2E Converter's WAN link has transitioned into
                                        the up state."
                         	::= 105

mc2200-GEMC2E-local-WAN-linkdown 	TRAP-TYPE
                         	ENTERPRISE    mc2200-TrapID
                         	DESCRIPTION   "A mc2200-GEMC2E-local-WAN-linkdown trap signifies that some
                                        local GEMC2E Converter's WAN link has transitioned into
                                        the down state."
                         	::= 106

mc2200-GEMC2E-remote-LAN-linkup 	TRAP-TYPE
                         	ENTERPRISE    mc2200-TrapID
                         	DESCRIPTION   "A mc2200-GEMC2E-remote-LAN-linkup trap signifies that some
                                        remote GEMC2E Converter's LAN1 link has transitioned into
                                        the up state."
                         	::= 107

mc2200-GEMC2E-remote-LAN-linkdown 	TRAP-TYPE
                         	ENTERPRISE    mc2200-TrapID
                         	DESCRIPTION   "A mc2200-GEMC2E-remote-LAN-linkdown trap signifies that some
                                        remote GEMC2E Converter's LAN1 link has transitioned into
                                        the down state."
                         	::= 108

mc2200-GE-FE-MC-local-LAN-linkup 	TRAP-TYPE
                         	ENTERPRISE    mc2200-TrapID
                         	DESCRIPTION   "A GE/FE-MC-local-LAN-linkup trap signifies that some
                                        local GE/FE-MC Converter's LAN link has transitioned into
                                        the up state."
                         	::= 109

mc2200-GE-FE-MC-local-LAN-linkdown 	TRAP-TYPE
                         	ENTERPRISE    mc2200-TrapID
                         	DESCRIPTION   "A GE/FE-MC-local-LAN-linkdown trap signifies that some
                                        local GE/FE-MC Converter's LAN link has transitioned into
                                        the down state."
                         	::= 110

mc2200-GE-FE-MC-local-WAN-linkup 	    TRAP-TYPE
                         	ENTERPRISE    mc2200-TrapID
                         	DESCRIPTION   "A GE/FE-MC-local-WAN-linkup trap signifies that some
                                        local GE/FE-MC Converter's WAN link has transitioned into
                                        the up state."
                         	::= 111

mc2200-GE-FE-MC-local-WAN-linkdown 	TRAP-TYPE
                         	ENTERPRISE    mc2200-TrapID
                         	DESCRIPTION   "A GE/FE-MC-local-WAN-linkdown trap signifies that some
                                        local GE/FE-MC Converter's WAN link has transitioned into
                                        the down state."
                         	::= 112

mc2200-GE-FE-MC-remote-LAN-linkup 	TRAP-TYPE
                         	ENTERPRISE    mc2200-TrapID
                         	DESCRIPTION   "A GE/FE-MC-remote-LAN-linkup trap signifies that some
                                        remote GE/FE-MC Converter's LAN1 link has transitioned into
                                        the up state."
                         	::= 113

mc2200-GE-FE-MC-remote-LAN-linkdown 	TRAP-TYPE
                         	ENTERPRISE    mc2200-TrapID
                         	DESCRIPTION   "A GE/FE-MC-remote-LAN-linkdown trap signifies that some
                                        remote GE/FE-MC Converter's LAN1 link has transitioned into
                                        the down state."
                         	::= 114
mc2200-GE-FE-MC2S-local-LAN-linkup 	TRAP-TYPE
                         	ENTERPRISE    mc2200-TrapID
                         	DESCRIPTION   "A GE/FE-MC2S-local-LAN-linkup trap signifies that some
                                        local GE/FE-MC2S Converter's LAN link has transitioned into
                                        the up state."
                         	::= 115

mc2200-GE-FE-MC2S-local-LAN-linkdown 	TRAP-TYPE
                         	ENTERPRISE    mc2200-TrapID
                         	DESCRIPTION   "A GE/FE-MC2S-local-LAN-linkdown trap signifies that some
                                        local GE/FE-MC2S Converter's LAN link has transitioned into
                                        the down state."
                         	::= 116

mc2200-GE-FE-MC2S-local-WAN-linkup 	    TRAP-TYPE
                         	ENTERPRISE    mc2200-TrapID
                         	DESCRIPTION   "A GE/FE-MC2S-local-WAN-linkup trap signifies that some
                                        local GE/FE-MC2S Converter's WAN link has transitioned into
                                        the up state."
                         	::= 117

mc2200-GE-FE-MC2S-local-WAN-linkdown 	TRAP-TYPE
                         	ENTERPRISE    mc2200-TrapID
                         	DESCRIPTION   "A GE/FE-MC2S-local-WAN-linkdown trap signifies that some
                                        local GE/FE-MC2S Converter's WAN link has transitioned into
                                        the down state."
                         	::= 118

mc2200-GE-FE-MC2S-remote-LAN-linkup 	TRAP-TYPE
                         	ENTERPRISE    mc2200-TrapID
                         	DESCRIPTION   "A GE/FE-MC2S-remote-LAN-linkup trap signifies that some
                                        remote GE/FE-MC2S Converter's LAN1 link has transitioned into
                                        the up state."
                         	::= 119

mc2200-GE-FE-MC2S-remote-LAN-linkdown 	TRAP-TYPE
                         	ENTERPRISE    mc2200-TrapID
                         	DESCRIPTION   "A GE/FE-MC2S-remote-LAN-linkdown trap signifies that some
                                        remote GE/FE-MC2S Converter's LAN1 link has transitioned into
                                        the down state."
                         	::= 120

mc2200-GE-FE-MC2T-local-LAN-linkup 	TRAP-TYPE
                         	ENTERPRISE    mc2200-TrapID
                         	DESCRIPTION   "A GE/FE-MC2T-local-LAN-linkup trap signifies that some
                                        local GE/FE-MC2T Converter's LAN link has transitioned into
                                        the up state."
                         	::= 121

mc2200-GE-FE-MC2T-local-LAN-linkdown 	TRAP-TYPE
                         	ENTERPRISE    mc2200-TrapID
                         	DESCRIPTION   "A GE/FE-MC2T-local-LAN-linkdown trap signifies that some
                                        local GE/FE-MC2T Converter's LAN link has transitioned into
                                        the down state."
                         	::= 122

mc2200-GE-FE-MC2T-local-WAN-linkup 	    TRAP-TYPE
                         	ENTERPRISE    mc2200-TrapID
                         	DESCRIPTION   "A GE/FE-MC2S-local-WAN-linkup trap signifies that some
                                        local GE/FE-MC2T Converter's WAN link has transitioned into
                                        the up state."
                         	::= 123

mc2200-GE-FE-MC2T-local-WAN-linkdown 	TRAP-TYPE
                         	ENTERPRISE    mc2200-TrapID
                         	DESCRIPTION   "A GE/FE-MC2T-local-WAN-linkdown trap signifies that some
                                        local GE/FE-MC2T Converter's WAN link has transitioned into
                                        the down state."
                         	::= 124

mc2200-GE-FE-MC2T-remote-LAN-linkup 	TRAP-TYPE
                         	ENTERPRISE    mc2200-TrapID
                         	DESCRIPTION   "A GE/FE-MC2T-remote-LAN-linkup trap signifies that some
                                        remote GE/FE-MC2T Converter's LAN1 link has transitioned into
                                        the up state."
                         	::= 125

mc2200-GE-FE-MC2T-remote-LAN-linkdown 	TRAP-TYPE
                         	ENTERPRISE    mc2200-TrapID
                         	DESCRIPTION   "A GE/FE-MC2T-remote-LAN-linkdown trap signifies that some
                                        remote GE/FE-MC2T Converter's LAN1 link has transitioned into
                                        the down state."
                         	::= 126


mc2200-FE-SFP-local-LAN-linkup 	TRAP-TYPE
                         	ENTERPRISE    mc2200-TrapID
                         	DESCRIPTION   "A FE-SFP-local-LAN-linkup trap signifies that some
                                        local FE-SFP Converter's LAN link has transitioned into
                                        the up state."
                         	::= 127

mc2200-FE-SFP-local-LAN-linkdown 	TRAP-TYPE
                         	ENTERPRISE    mc2200-TrapID
                         	DESCRIPTION   "A FE-SFP-local-LAN-linkdown trap signifies that some
                                        local FE-SFP Converter's LAN link has transitioned into
                                        the down state."
                         	::= 128

mc2200-FE-SFP-local-WAN-linkup 	    TRAP-TYPE
                         	ENTERPRISE    mc2200-TrapID
                         	DESCRIPTION   "A FE-SFP-local-WAN-linkup trap signifies that some
                                        local FE-SFP Converter's WAN link has transitioned into
                                        the up state."
                         	::= 129

mc2200-FE-SFP-local-WAN-linkdown 	TRAP-TYPE
                         	ENTERPRISE    mc2200-TrapID
                         	DESCRIPTION   "A FE-SFP-local-WAN-linkdown trap signifies that some
                                        local FE-SFP Converter's WAN link has transitioned into
                                        the down state."
                         	::= 130

mc2200-FE-SFP-remote-LAN-linkup 	TRAP-TYPE
                         	ENTERPRISE    mc2200-TrapID
                         	DESCRIPTION   "A FE-SFP-remote-LAN-linkup trap signifies that some
                                        remote FE-SFP Converter's LAN1 link has transitioned into
                                        the up state."
                         	::= 131

mc2200-FE-SFP-remote-LAN-linkdown 	TRAP-TYPE
                         	ENTERPRISE    mc2200-TrapID
                         	DESCRIPTION   "A FE-SFP-remote-LAN-linkdown trap signifies that some
                                        remote FE-SFP Converter's LAN1 link has transitioned into
                                        the down state."
                         	::= 132


mc2200-GE-SFP-local-LAN-linkup 	TRAP-TYPE
                         	ENTERPRISE    mc2200-TrapID
                         	DESCRIPTION   "A GE-SFP-local-LAN-linkup trap signifies that some
                                        local GE-SFP Converter's LAN link has transitioned into
                                        the up state."
                         	::= 133

mc2200-GE-SFP-local-LAN-linkdown 	TRAP-TYPE
                         	ENTERPRISE    mc2200-TrapID
                         	DESCRIPTION   "A GE-SFP-local-LAN-linkdown trap signifies that some
                                        local GE-SFP Converter's LAN link has transitioned into
                                        the down state."
                         	::= 134

mc2200-GE-SFP-local-WAN-linkup 	    TRAP-TYPE
                         	ENTERPRISE    mc2200-TrapID
                         	DESCRIPTION   "A GE-SFP-local-WAN-linkup trap signifies that some
                                        local GE-SFP Converter's WAN link has transitioned into
                                        the up state."
                         	::= 135

mc2200-GE-SFP-local-WAN-linkdown 	TRAP-TYPE
                         	ENTERPRISE    mc2200-TrapID
                         	DESCRIPTION   "A GE-SFP-local-WAN-linkdown trap signifies that some
                                        local GE-SFP Converter's WAN link has transitioned into
                                        the down state."
                         	::= 136

mc2200-GE-SFP-remote-LAN-linkup 	TRAP-TYPE
                         	ENTERPRISE    mc2200-TrapID
                         	DESCRIPTION   "A GE-SFP-remote-LAN-linkup trap signifies that some
                                        remote GE-SFP Converter's LAN1 link has transitioned into
                                        the up state."
                         	::= 137

mc2200-GE-SFP-remote-LAN-linkdown 	TRAP-TYPE
                         	ENTERPRISE    mc2200-TrapID
                         	DESCRIPTION   "A GE-SFP-remote-LAN-linkdown trap signifies that some
                                        remote GE-SFP Converter's LAN1 link has transitioned into
                                        the down state."
                         	::= 138


mc2200-GE-MC3-local-LAN-linkup 	TRAP-TYPE
                         	ENTERPRISE    mc2200-TrapID
                         	DESCRIPTION   "A GE-MC3-local-LAN-linkup trap signifies that some
                                        local GE-MC3 Converter's LAN link has transitioned into
                                        the up state."
                         	::= 139

mc2200-GE-MC3-local-LAN-linkdown 	TRAP-TYPE
                         	ENTERPRISE    mc2200-TrapID
                         	DESCRIPTION   "A GE-MC3-local-LAN-linkdown trap signifies that some
                                        local GE-MC3 Converter's LAN link has transitioned into
                                        the down state."
                         	::= 140

mc2200-GE-MC3-local-WAN-linkup 	    TRAP-TYPE
                         	ENTERPRISE    mc2200-TrapID
                         	DESCRIPTION   "A GE-MC3-local-WAN-linkup trap signifies that some
                                        local GE-MC3 Converter's WAN link has transitioned into
                                        the up state."
                         	::= 141

mc2200-GE-MC3-local-WAN-linkdown 	TRAP-TYPE
                         	ENTERPRISE    mc2200-TrapID
                         	DESCRIPTION   "A GE-MC3-local-WAN-linkdown trap signifies that some
                                        local GE-MC3 Converter's WAN link has transitioned into
                                        the down state."
                         	::= 142

mc2200-GE-MC3-remote-LAN-linkup 	TRAP-TYPE
                         	ENTERPRISE    mc2200-TrapID
                         	DESCRIPTION   "A GE-MC3-remote-LAN-linkup trap signifies that some
                                        remote GE-MC3 Converter's LAN1 link has transitioned into
                                        the up state."
                         	::= 143

mc2200-GE-MC3-remote-LAN-linkdown 	TRAP-TYPE
                         	ENTERPRISE    mc2200-TrapID
                         	DESCRIPTION   "A GE-SFP-remote-LAN-linkdown trap signifies that some
                                        remote GE-MC3 Converter's LAN1 link has transitioned into
                                        the down state."
                         	::= 144


mc2200-GE-SFP-APS-local-LAN-linkup 	TRAP-TYPE
                         	ENTERPRISE    mc2200-TrapID
                         	DESCRIPTION   "A GE-SFP-APS-local-LAN-linkup trap signifies that some
                                        local GE-SFP-APS Converter's LAN link has transitioned into
                                        the up state."
                         	::= 145

mc2200-GE-SFP-APS-local-LAN-linkdown 	TRAP-TYPE
                         	ENTERPRISE    mc2200-TrapID
                         	DESCRIPTION   "A GE-SFP-APS-local-LAN-linkdown trap signifies that some
                                        local GE-SFP-APS Converter's LAN link has transitioned into
                                        the down state."
                         	::= 146

mc2200-GE-SFP-APS-local-WAN1-linkup 	    TRAP-TYPE
                         	ENTERPRISE    mc2200-TrapID
                         	DESCRIPTION   "A GE-SFP-APS-local-WAN-linkup trap signifies that some
                                        local GE-SFP-APS Converter's WAN link has transitioned into
                                        the up state."
                         	::= 147

mc2200-GE-SFP-APS-local-WAN1-linkdown 	TRAP-TYPE
                         	ENTERPRISE    mc2200-TrapID
                         	DESCRIPTION   "A GE-SFP-APS-local-WAN-linkdown trap signifies that some
                                        local GE-SFP-APS Converter's WAN link has transitioned into
                                        the down state."
                         	::= 148

mc2200-GE-SFP-APS-local-WAN2-linkup 	    TRAP-TYPE
                         	ENTERPRISE    mc2200-TrapID
                         	DESCRIPTION   "A GE-SFP-APS-local-WAN-linkup trap signifies that some
                                        local GE-SFP-APS Converter's WAN link has transitioned into
                                        the up state."
                         	::= 149

mc2200-GE-SFP-APS-local-WAN2-linkdown 	TRAP-TYPE
                         	ENTERPRISE    mc2200-TrapID
                         	DESCRIPTION   "A GE-SFP-APS-local-WAN-linkdown trap signifies that some
                                        local GE-SFP-APS Converter's WAN link has transitioned into
                                        the down state."
                         	::= 150

mc2200-GE-SFP-APS-remote-LAN-linkup 	TRAP-TYPE
                         	ENTERPRISE    mc2200-TrapID
                         	DESCRIPTION   "A GE-SFP-APS-remote-LAN-linkup trap signifies that some
                                        remote GE-SFP-APS Converter's LAN1 link has transitioned into
                                        the up state."
                         	::= 151

mc2200-GE-SFP-APS-remote-LAN-linkdown 	TRAP-TYPE
                         	ENTERPRISE    mc2200-TrapID
                         	DESCRIPTION   "A GE-SFP-APS-remote-LAN-linkdown trap signifies that some
                                        remote GE-SFP-APS Converter's LAN1 link has transitioned into
                                        the down state."
                         	::= 152


mc2200-GE-MC-APS-local-LAN-linkup 	TRAP-TYPE
                         	ENTERPRISE    mc2200-TrapID
                         	DESCRIPTION   "A GE-MC-APS-local-LAN-linkup trap signifies that some
                                        local GE-MC-APS Converter's LAN link has transitioned into
                                        the up state."
                         	::= 153

mc2200-GE-MC-APS-local-LAN-linkdown 	TRAP-TYPE
                         	ENTERPRISE    mc2200-TrapID
                         	DESCRIPTION   "A GE-MC-APS-local-LAN-linkdown trap signifies that some
                                        local GE-MC-APS Converter's LAN link has transitioned into
                                        the down state."
                         	::= 154

mc2200-GE-MC-APS-local-WAN1-linkup 	    TRAP-TYPE
                         	ENTERPRISE    mc2200-TrapID
                         	DESCRIPTION   "A GE-MC-APS-local-WAN-linkup trap signifies that some
                                        local GE-MC-APS Converter's WAN link has transitioned into
                                        the up state."
                         	::= 155

mc2200-GE-MC-APS-local-WAN1-linkdown 	TRAP-TYPE
                         	ENTERPRISE    mc2200-TrapID
                         	DESCRIPTION   "A GE-MC-APS-local-WAN-linkdown trap signifies that some
                                        local GE-MC-APS Converter's WAN link has transitioned into
                                        the down state."
                         	::= 156

mc2200-GE-MC-APS-local-WAN2-linkup 	    TRAP-TYPE
                         	ENTERPRISE    mc2200-TrapID
                         	DESCRIPTION   "A GE-MC-APS-local-WAN-linkup trap signifies that some
                                        local GE-MC-APS Converter's WAN link has transitioned into
                                        the up state."
                         	::= 157

mc2200-GE-MC-APS-local-WAN2-linkdown 	TRAP-TYPE
                         	ENTERPRISE    mc2200-TrapID
                         	DESCRIPTION   "A GE-MC-APS-local-WAN-linkdown trap signifies that some
                                        local GE-MC-APS Converter's WAN link has transitioned into
                                        the down state."
                         	::= 158

mc2200-GE-MC-APS-remote-LAN-linkup 	TRAP-TYPE
                         	ENTERPRISE    mc2200-TrapID
                         	DESCRIPTION   "A GE-MC-APS-remote-LAN-linkup trap signifies that some
                                        remote GE-MC-APS Converter's LAN1 link has transitioned into
                                        the up state."
                         	::= 159

mc2200-GE-MC-APS-remote-LAN-linkdown 	TRAP-TYPE
                         	ENTERPRISE    mc2200-TrapID
                         	DESCRIPTION   "A GE-MC-APS-remote-LAN-linkdown trap signifies that some
                                        remote GE-MC-APS Converter's LAN1 link has transitioned into
                                        the down state."
                         	::= 160

mc2200-CARD-WAN1-switch-WAN2                TRAP-TYPE
                         ENTERPRISE    mc2200-TrapID
                         DESCRIPTION   "The card's active port switches from WAN1 to WAN2."
                         ::= 161

mc2200-CARD-WAN2-switch-WAN1                TRAP-TYPE
                         ENTERPRISE    mc2200-TrapID
                         DESCRIPTION   "The card's active port switches from WAN2 to WAN1."
                         ::= 162


mc2200-OAPS-local-LAN-linkup 	TRAP-TYPE
                         	ENTERPRISE    mc2200-TrapID
                         	DESCRIPTION   "A OAPS-local-LAN-linkup trap signifies that some
                                        local OAPS Converter's LAN link has transitioned into
                                        the up state."
                         	::= 163

mc2200-OAPS-local-LAN-linkdown 	TRAP-TYPE
                         	ENTERPRISE    mc2200-TrapID
                         	DESCRIPTION   "A OAPS-local-LAN-linkdown trap signifies that some
                                        local OAPS Converter's LAN link has transitioned into
                                        the down state."
                         	::= 164

mc2200-OAPS-local-WAN1-linkup 	    TRAP-TYPE
                         	ENTERPRISE    mc2200-TrapID
                         	DESCRIPTION   "A OAPS-local-WAN-linkup trap signifies that some
                                        local OAPS Converter's WAN link has transitioned into
                                        the up state."
                         	::= 165

mc2200-OAPS-local-WAN1-linkdown 	TRAP-TYPE
                         	ENTERPRISE    mc2200-TrapID
                         	DESCRIPTION   "A OAPS-local-WAN-linkdown trap signifies that some
                                        local OAPS Converter's WAN link has transitioned into
                                        the down state."
                         	::= 166

mc2200-OAPS-local-WAN2-linkup 	    TRAP-TYPE
                         	ENTERPRISE    mc2200-TrapID
                         	DESCRIPTION   "A OAPS-local-WAN-linkup trap signifies that some
                                        local OAPS Converter's WAN link has transitioned into
                                        the up state."
                         	::= 167

mc2200-OAPS-local-WAN2-linkdown 	TRAP-TYPE
                         	ENTERPRISE    mc2200-TrapID
                         	DESCRIPTION   "A OAPS-local-WAN-linkdown trap signifies that some
                                        local OAPS Converter's WAN link has transitioned into
                                        the down state."
                         	::= 168

mc2200-PORT-RX-POWER-LOW			TRAP-TYPE
                         	ENTERPRISE    mc2200-TrapID
                         	DESCRIPTION   "The card port rx power low or normal"
                         	::= 169




mc2200-PORT-RX-POWER-NORMAL        TRAP-TYPE
                         	ENTERPRISE    mc2200-TrapID
                         	DESCRIPTION   "The card port rx power low or normal"
                         	::= 170


mc2200-QS2204-local-LAN1-linkup 	TRAP-TYPE
                         	ENTERPRISE    mc2200-TrapID
                         	DESCRIPTION   "A QS2204-local-LAN1-linkup trap signifies that some
                                        local QS2204 Converter's LAN1 link has transitioned into
                                        the up state."
                         	::= 171

mc2200-QS2204-local-LAN1-linkdown 	TRAP-TYPE
                         	ENTERPRISE    mc2200-TrapID
                         	DESCRIPTION   "A QS2204-local-LAN1-linkdown trap signifies that some
                                        local QS2204 Converter's LAN1 link has transitioned into
                                        the down state."
                         	::= 172


mc2200-QS2204-local-LAN2-linkup 	TRAP-TYPE
                         	ENTERPRISE    mc2200-TrapID
                         	DESCRIPTION   "A QS2204-local-LAN2-linkup trap signifies that some
                                        local QS2204 Converter's LAN2 link has transitioned into
                                        the up state."
                         	::= 173

mc2200-QS2204-local-LAN2-linkdown 	TRAP-TYPE
                         	ENTERPRISE    mc2200-TrapID
                         	DESCRIPTION   "A QS2204-local-LAN2-linkdown trap signifies that some
                                        local QS2204 Converter's LAN2 link has transitioned into
                                        the down state."
                         	::= 174


mc2200-QS2204-local-LAN3-linkup 	TRAP-TYPE
                         	ENTERPRISE    mc2200-TrapID
                         	DESCRIPTION   "A QS2204-local-LAN3-linkup trap signifies that some
                                        local QS2204 Converter's LAN3 link has transitioned into
                                        the up state."
                         	::= 175

mc2200-QS2204-local-LAN3-linkdown 	TRAP-TYPE
                         	ENTERPRISE    mc2200-TrapID
                         	DESCRIPTION   "A QS2204-local-LAN3-linkdown trap signifies that some
                                        local QS2204 Converter's LAN3 link has transitioned into
                                        the down state."
                         	::= 176


mc2200-QS2204-local-LAN4-linkup 	TRAP-TYPE
                         	ENTERPRISE    mc2200-TrapID
                         	DESCRIPTION   "A QS2204-local-LAN4-linkup trap signifies that some
                                        local QS2204 Converter's LAN4 link has transitioned into
                                        the up state."
                         	::= 177

mc2200-QS2204-local-LAN4-linkdown 	TRAP-TYPE
                         	ENTERPRISE    mc2200-TrapID
                         	DESCRIPTION   "A QS2204-local-LAN4-linkdown trap signifies that some
                                        local QS2204 Converter's LAN4 link has transitioned into
                                        the down state."
                         	::= 178

mc2200-QS2204-local-WAN-lane1-linkup 	    TRAP-TYPE
                         	ENTERPRISE    mc2200-TrapID
                         	DESCRIPTION   "A QS2204-local-WAN-lane1-linkup trap signifies that some
                                        local QS2204 Converter's WAN lane1 link has transitioned into
                                        the up state."
                         	::= 179

mc2200-QS2204-local-WAN-lane1-linkdown 	TRAP-TYPE
                         	ENTERPRISE    mc2200-TrapID
                         	DESCRIPTION   "A QS2204-local-WAN-lane1-linkdown trap signifies that some
                                        local QS2204 Converter's WAN lane1 link has transitioned into
                                        the down state."
                         	::= 180
mc2200-QS2204-local-WAN-lane2-linkup 	    TRAP-TYPE
                         	ENTERPRISE    mc2200-TrapID
                         	DESCRIPTION   "A QS2204-local-WAN-lane2-linkup trap signifies that some
                                        local QS2204 Converter's WAN lane2 link has transitioned into
                                        the up state."
                         	::= 181

mc2200-QS2204-local-WAN-lane2-linkdown 	TRAP-TYPE
                         	ENTERPRISE    mc2200-TrapID
                         	DESCRIPTION   "A QS2204-local-WAN-lane2-linkdown trap signifies that some
                                        local QS2204 Converter's WAN lane2 link has transitioned into
                                        the down state."
                         	::= 182
mc2200-QS2204-local-WAN-lane3-linkup 	    TRAP-TYPE
                         	ENTERPRISE    mc2200-TrapID
                         	DESCRIPTION   "A QS2204-local-WAN-lane3-linkup trap signifies that some
                                        local QS2204 Converter's WAN lane3 link has transitioned into
                                        the up state."
                         	::= 183

mc2200-QS2204-local-WAN-lane3-linkdown 	TRAP-TYPE
                         	ENTERPRISE    mc2200-TrapID
                         	DESCRIPTION   "A QS2204-local-WAN-lane3-linkdown trap signifies that some
                                        local QS2204 Converter's WAN lane3 link has transitioned into
                                        the down state."
                         	::= 184
mc2200-QS2204-local-WAN-lane4-linkup 	    TRAP-TYPE
                         	ENTERPRISE    mc2200-TrapID
                         	DESCRIPTION   "A QS2204-local-WAN-lane4-linkup trap signifies that some
                                        local QS2204 Converter's WAN lane4 link has transitioned into
                                        the up state."
                         	::= 185

mc2200-QS2204-local-WAN-lane4-linkdown 	TRAP-TYPE
                         	ENTERPRISE    mc2200-TrapID
                         	DESCRIPTION   "A QS2204-local-WAN-lane4-linkdown trap signifies that some
                                        local QS2204 Converter's WAN lane4 link has transitioned into
                                        the down state."
                         	::= 186

mc2200-QS2204-local-LAN1-txup 	TRAP-TYPE
                         	ENTERPRISE    mc2200-TrapID
                         	DESCRIPTION   "A QS2204-local-LAN1-txup trap signifies that some
                                        local QS2204 Converter's LAN1 tx state has transitioned into
                                        the up state."
                         	::= 187

mc2200-QS2204-local-LAN1-txdown 	TRAP-TYPE
                         	ENTERPRISE    mc2200-TrapID
                         	DESCRIPTION   "A QS2204-local-LAN1-txdown trap signifies that some
                                        local QS2204 Converter's LAN1 tx state has transitioned into
                                        the down state."
                         	::= 188


mc2200-QS2204-local-LAN2-txup 	TRAP-TYPE
                         	ENTERPRISE    mc2200-TrapID
                         	DESCRIPTION   "A QS2204-local-LAN2-txup trap signifies that some
                                        local QS2204 Converter's LAN2 tx state has transitioned into
                                        the up state."
                         	::= 189

mc2200-QS2204-local-LAN2-txdown 	TRAP-TYPE
                         	ENTERPRISE    mc2200-TrapID
                         	DESCRIPTION   "A QS2204-local-LAN2-txdown trap signifies that some
                                        local QS2204 Converter's LAN2 tx state has transitioned into
                                        the down state."
                         	::= 190


mc2200-QS2204-local-LAN3-txkup 	TRAP-TYPE
                         	ENTERPRISE    mc2200-TrapID
                         	DESCRIPTION   "A QS2204-local-LAN3-txup trap signifies that some
                                        local QS2204 Converter's LAN3 tx state has transitioned into
                                        the up state."
                         	::= 191

mc2200-QS2204-local-LAN3-txdown 	TRAP-TYPE
                         	ENTERPRISE    mc2200-TrapID
                         	DESCRIPTION   "A QS2204-local-LAN3-txdown trap signifies that some
                                        local QS2204 Converter's LAN3 tx state has transitioned into
                                        the down state."
                         	::= 192


mc2200-QS2204-local-LAN4-txup 	TRAP-TYPE
                         	ENTERPRISE    mc2200-TrapID
                         	DESCRIPTION   "A QS2204-local-LAN4-txup trap signifies that some
                                        local QS2204 Converter's LAN4 tx state has transitioned into
                                        the up state."
                         	::= 193

mc2200-QS2204-local-LAN4-txdown 	TRAP-TYPE
                         	ENTERPRISE    mc2200-TrapID
                         	DESCRIPTION   "A QS2204-local-LAN4-txdown trap signifies that some
                                        local QS2204 Converter's LAN4 tx state has transitioned into
                                        the down state."
                         	::= 194

mc2200-QS2204-local-WAN-lane1-txup 	    TRAP-TYPE
                         	ENTERPRISE    mc2200-TrapID
                         	DESCRIPTION   "A QS2204-local-WAN-lane1-txup trap signifies that some
                                        local QS2204 Converter's WAN lane1 tx state has transitioned into
                                        the up state."
                         	::= 195

mc2200-QS2204-local-WAN-lane1-txdown 	TRAP-TYPE
                         	ENTERPRISE    mc2200-TrapID
                         	DESCRIPTION   "A QS2204-local-WAN-lane1-txdown trap signifies that some
                                        local QS2204 Converter's WAN lane1 tx state has transitioned into
                                        the down state."
                         	::= 196
mc2200-QS2204-local-WAN-lane2-txup 	    TRAP-TYPE
                         	ENTERPRISE    mc2200-TrapID
                         	DESCRIPTION   "A QS2204-local-WAN-lane2-txup trap signifies that some
                                        local QS2204 Converter's WAN lane2 tx state has transitioned into
                                        the up state."
                         	::= 197

mc2200-QS2204-local-WAN-lane2-txdown 	TRAP-TYPE
                         	ENTERPRISE    mc2200-TrapID
                         	DESCRIPTION   "A QS2204-local-WAN-lane2-txdown trap signifies that some
                                        local QS2204 Converter's WAN lane2 tx state has transitioned into
                                        the down state."
                         	::= 198
mc2200-QS2204-local-WAN-lane3-txup 	    TRAP-TYPE
                         	ENTERPRISE    mc2200-TrapID
                         	DESCRIPTION   "A QS2204-local-WAN-lane3-txup trap signifies that some
                                        local QS2204 Converter's WAN lane3 tx state has transitioned into
                                        the up state."
                         	::= 199

mc2200-QS2204-local-WAN-lane3-txdown 	TRAP-TYPE
                         	ENTERPRISE    mc2200-TrapID
                         	DESCRIPTION   "A QS2204-local-WAN-lane3-txdown trap signifies that some
                                        local QS2204 Converter's WAN lane3 tx state has transitioned into
                                        the down state."
                         	::= 200
mc2200-QS2204-local-WAN-lane4-txup 	    TRAP-TYPE
                         	ENTERPRISE    mc2200-TrapID
                         	DESCRIPTION   "A QS2204-local-WAN-lane4-txup trap signifies that some
                                        local QS2204 Converter's WAN lane4 tx state has transitioned into
                                        the up state."
                         	::= 201

mc2200-QS2204-local-WAN-lane4-txdown 	TRAP-TYPE
                         	ENTERPRISE    mc2200-TrapID
                         	DESCRIPTION   "A QS2204-local-WAN-lane4-txdown trap signifies that some
                                        local QS2204 Converter's WAN lane4 tx state has transitioned into
										the up state."
							::= 202


mc2200-Q2202-local-LAN-linkup 	TRAP-TYPE
                         	ENTERPRISE    mc2200-TrapID
                         	DESCRIPTION   "A Q2202-local-LAN-linkup trap signifies that some
                                        local Q2202 Converter's LAN link has transitioned into
                                        the up state."
                         	::= 203

mc2200-Q2202-local-LAN-linkdown 	TRAP-TYPE
                         	ENTERPRISE    mc2200-TrapID
                         	DESCRIPTION   "A Q2202-local-LAN-linkdown trap signifies that some
                                        local Q2202 Converter's LAN link has transitioned into
                                        the down state."
                         	::= 204

mc2200-Q2202-local-WAN-linkup 	    TRAP-TYPE
                         	ENTERPRISE    mc2200-TrapID
                         	DESCRIPTION   "A Q2202-local-WAN-linkup trap signifies that some
                                        local Q2202 Converter's WAN link has transitioned into
                                        the up state."
                         	::= 205

mc2200-Q2202-local-WAN-linkdown 	TRAP-TYPE
                         	ENTERPRISE    mc2200-TrapID
                         	DESCRIPTION   "A Q2202-local-WAN-linkdown trap signifies that some
                                        local Q2202 Converter's WAN link has transitioned into
                                        the down state."
                         	::= 206
mc2200-Q2202-local-LAN-txup 	TRAP-TYPE
                         	ENTERPRISE    mc2200-TrapID
                         	DESCRIPTION   "A Q2202-local-LAN-tx state up trap signifies that some
                                        local Q2202 Converter's LAN tx state has transitioned into
                                        the up state."
                         	::= 207

mc2200-Q2202-local-LAN-txdown 	TRAP-TYPE
                         	ENTERPRISE    mc2200-TrapID
                         	DESCRIPTION   "A Q2202-local-LAN-tx state down trap signifies that some
                                        local Q2202 Converter's LAN tx state has transitioned into
                                        the down state."
                         	::= 208

mc2200-Q2202-local-WAN-txup 	    TRAP-TYPE
                         	ENTERPRISE    mc2200-TrapID
                         	DESCRIPTION   "A Q2202-local-WAN-tx state up trap signifies that some
                                        local Q2202 Converter's WAN tx state has transitioned into
                                        the up state."
                         	::= 209

mc2200-Q2202-local-WAN-txdown 	TRAP-TYPE
                         	ENTERPRISE    mc2200-TrapID
                         	DESCRIPTION   "A Q2202-local-WAN-tx state down trap signifies that some
                                        local Q2202 Converter's WAN tx state has transitioned into
                                        the down state."
                         	::= 210
mc2200-Q2202-rate-40G 	    TRAP-TYPE
                         	ENTERPRISE    mc2200-TrapID
                         	DESCRIPTION   "A Q2202-rate-40G trap signifies that some
                                        local Q2202 Converter's rate has transitioned into
                                        40G."
                         	::= 211

mc2200-Q2202-rate-100G 	TRAP-TYPE
                         	ENTERPRISE    mc2200-TrapID
                         	DESCRIPTION   "A Q2202-rate-100G trap signifies that some
                                        local Q2202 Converter's rate has transitioned into
                                        100G."
                         	::= 212
mc2200-card-Remote-Connected 	TRAP-TYPE
                         	ENTERPRISE    mc2200-TrapID
                         	DESCRIPTION    "A local-remote-connected trap signifies that some remote
                                        Converter's connected
                                        state."
                         	::= 213
mc2200-card-Remote-Disconnected 	TRAP-TYPE
                         	ENTERPRISE    mc2200-TrapID
                         	DESCRIPTION    "A local-remote-disconnected trap signifies that some remote
                                        Converter's disconnected
                                        state."
                         	::= 214

mc2200-card-SFP-model-insert 	TRAP-TYPE
                         	ENTERPRISE    mc2200-TrapID
                         	DESCRIPTION    "A card sfp model insert trap signifies that some
                                        port sfp model insert
                                        state."
                         	::= 215

mc2200-card-SFP-model-pull-out 	TRAP-TYPE
                         	ENTERPRISE    mc2200-TrapID
                         	DESCRIPTION    "A card sfp model pull out trap signifies that some
                                        port sfp model pull out
                                        state."
                         	::= 216

mc2200-card-loopback 	TRAP-TYPE
                         	ENTERPRISE    mc2200-TrapID
                         	DESCRIPTION    "A card loopback trap signifies that some
                                        card loopback
                                        state."
                         	::= 217

mc2200-NMCsystemStatus   	TRAP-TYPE
                         ENTERPRISE    mc2200-TrapID
                         DESCRIPTION   "A mc2200 NMC system status change."
                         ::= 218


mc2200-FE-MC-local-LAN-linkup 	TRAP-TYPE
                         	ENTERPRISE    mc2200-TrapID
                         	DESCRIPTION   "A FE-MC-local-LAN-linkup trap signifies that some
                                        local FE-MC Converter's LAN link has transitioned into
                                        the up state."
                         	::= 219

mc2200-FE-MC-local-LAN-linkdown 	TRAP-TYPE
                         	ENTERPRISE    mc2200-TrapID
                         	DESCRIPTION   "A FE-MC-local-LAN-linkdown trap signifies that some
                                        local FE-MC Converter's LAN link has transitioned into
                                        the down state."
                         	::= 220

mc2200-FE-MC-local-WAN-linkup 	    TRAP-TYPE
                         	ENTERPRISE    mc2200-TrapID
                         	DESCRIPTION   "A FE-MC-local-WAN-linkup trap signifies that some
                                        local FE-MC Converter's WAN link has transitioned into
                                        the up state."
                         	::= 221

mc2200-FE-MC-local-WAN-linkdown 	TRAP-TYPE
                         	ENTERPRISE    mc2200-TrapID
                         	DESCRIPTION   "A FE-MC-local-WAN-linkdown trap signifies that some
                                        local FE-MC Converter's WAN link has transitioned into
                                        the down state."
                         	::= 222

mc2200-FE-MC-remote-LAN-linkup 	TRAP-TYPE
                         	ENTERPRISE    mc2200-TrapID
                         	DESCRIPTION   "A FE-MC-remote-LAN-linkup trap signifies that some
                                        remote FE-MC Converter's LAN1 link has transitioned into
                                        the up state."
                         	::= 223

mc2200-FE-MC-remote-LAN-linkdown 	TRAP-TYPE
                         	ENTERPRISE    mc2200-TrapID
                         	DESCRIPTION   "A GE-SFP-remote-LAN-linkdown trap signifies that some
                                        remote FE-MC Converter's LAN1 link has transitioned into
                                        the down state."
                         	::= 224
END
