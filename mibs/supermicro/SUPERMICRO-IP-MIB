-- Copyright (C) 2008-2014 Super Micro Computer Inc. All Rights Reserved

-- /*****************************************************************
--  *                                                               *
--  * $RCSfile: fsip.mib,v $
--  *                                                               *
--  * $Date: 2012/09/07 09:52:05 $                                  *
--  *                                                               *
--  * $Revision: 1.18 $                                              *
--  *                                                               *
--  ****************************************************************/

SUPERMICRO-IP-MIB DEFINITIONS ::= BEGIN

 IMPORTS
    OBJECT-TYPE, MODULE-IDENTITY, IpAddress,
    Counter32, Integer32,
    enterprises            FROM SNMPv2-SMI
    DisplayString,
    TruthValue, RowStatus  FROM SNMPv2-TC;

futureip MODULE-IDENTITY
     LAST-UPDATED "201209050000Z"
     ORGANIZATION "Super Micro Computer Inc."
     CONTACT-INFO "support@Supermicro.com"
     DESCRIPTION " This mib module is for IP module"
     REVISION "201209050000Z"
     DESCRIPTION " This mib module is for IP module"
::= { enterprises supermicro-computer-inc(10876) super-switch(101) basic(1) 2}

fsip	         OBJECT IDENTIFIER ::= { futureip 1 }
-- fsiparp	         OBJECT IDENTIFIER ::= { futureip 2 }
fsicmp	         OBJECT IDENTIFIER ::= { futureip 3 }
fsudp	         OBJECT IDENTIFIER ::= { futureip 4 }
fscidr	         OBJECT IDENTIFIER ::= { futureip 5 }
-- fsipinarp        OBJECT IDENTIFIER ::= { futureip 6 }
-- fsigmp	    OBJECT IDENTIFIER ::= { futureip 7 }
fsirdp	         OBJECT IDENTIFIER ::= { futureip 8 }
fsrarpclient     OBJECT IDENTIFIER ::= { futureip 9 }
fsrarpserver     OBJECT IDENTIFIER ::= { futureip 10 }
fssystemresize   OBJECT IDENTIFIER ::= { futureip 16 }
fslogandtrace    OBJECT IDENTIFIER ::= { futureip 17 }
-- fsiptest	         OBJECT IDENTIFIER ::= { futureip 19 }
-- fsiptest mib objects are defined in fsiptst.mib.

--SCALAR_TABLE_BEGIN fsip
-- the IP group

 	  fsIpInLengthErrors  OBJECT-TYPE
	      SYNTAX	    Counter32
	      MAX-ACCESS    read-only
	      STATUS	    current
	      DESCRIPTION
		     "Total number of packets received by IP with length less
		     than IP header length."
	      ::= { fsip 1 }

	  fsIpInCksumErrors  OBJECT-TYPE
	      SYNTAX	    Counter32
	      MAX-ACCESS    read-only
	      STATUS	    current
	      DESCRIPTION
		      "Total Number of received packets those failed to pass
		      checksum verification."
	      ::= { fsip 2 }

	  fsIpInVersionErrors  OBJECT-TYPE
	      SYNTAX	    Counter32
	      MAX-ACCESS    read-only
	      STATUS	    current
	      DESCRIPTION
		      "Total number of received packets with different IP
		      version from this entity."
	      ::= { fsip 3 }

	  fsIpInTTLErrors	 OBJECT-TYPE
	      SYNTAX	    Counter32
	      MAX-ACCESS    read-only
	      STATUS	    current
	      DESCRIPTION
		    "Number of IP packets received at this entity with
		    'Time to Live' field equal to ZERO"
	      ::= { fsip 4 }

	  fsIpInOptionErrors  OBJECT-TYPE
	      SYNTAX	    Counter32
	      MAX-ACCESS    read-only
	      STATUS	    current
	      DESCRIPTION
		      "Number of IP packets received with improper options."
	      ::= { fsip 5 }

	  fsIpInBroadCasts  OBJECT-TYPE
	      SYNTAX	    Counter32
	      MAX-ACCESS	    read-only
	      STATUS	    current
	      DESCRIPTION
		     "Total number of IP broadcast packets received at this
		     entity."
	      ::= { fsip 6 }

	  fsIpOutGenErrors  OBJECT-TYPE
	      SYNTAX	    Counter32
	      MAX-ACCESS	    read-only
	      STATUS	    current
	      DESCRIPTION
		     "Number of outgoing IP packets rejected due to general
		     problems like interface down, forwarding disabled etc."
	      ::= { fsip 7 }

	  fsIpOptProcEnable OBJECT-TYPE
	      SYNTAX	    INTEGER   {
		     enabled (1),
		     disabled (2)
	      }
	      MAX-ACCESS	    read-write
	      STATUS	    current
	      DESCRIPTION
		     "Indication as to if Option processing is active."
	      DEFVAL	 { enabled }
	      ::= { fsip 9 }

          fsIpNumMultipath OBJECT-TYPE
              SYNTAX  Integer32 (1..16)
              MAX-ACCESS  read-write
              STATUS  current
              DESCRIPTION
	              "The number of multi-paths in the routing table."
              DEFVAL	 { 2 }
              ::= { fsip 10 }

          fsIpLoadShareEnable OBJECT-TYPE
              SYNTAX INTEGER {
	                      enabled (1),
		              disabled (2)
                             }
              MAX-ACCESS read-write
              STATUS current
              DESCRIPTION
	              "Enabling this will distribute the load among
	              available equal cost multi-paths."
              DEFVAL  { disabled }
              ::= { fsip 11 }

          fsIpEnablePMTUD OBJECT-TYPE
              SYNTAX INTEGER {
                       enabled     (1),
                       disabled    (2)
              }
              MAX-ACCESS read-write
              STATUS current
              DESCRIPTION
                      "This Object Enables or Disables PMTU-D on all paths
                       globally. This MIB Object overrides the route-based and
                       application-level requests for PMTU-D. When this object
                       is set to disabled (2), PMTU-D is not done even if the
                       application requests to do so."
              DEFVAL { disabled }
              ::= { fsip 12 }

          fsIpPmtuEntryAge OBJECT-TYPE
              SYNTAX Integer32 (5..255)
              MAX-ACCESS read-write
              STATUS current
              DESCRIPTION
                      "This object specifies the timeout in minutes, after which
                       the estimate of a PMTU is considered stale. After the
                       configured minutes the estimate of the PMTU is increased.
                       When Set to inifinity (255), detection in increase of
                       PMTU is not done."
              DEFVAL { 10 }
              ::= { fsip 13 }

          fsIpPmtuTableSize OBJECT-TYPE
               SYNTAX  Integer32 (1..65535)
               MAX-ACCESS read-write
               STATUS current
               DESCRIPTION
                       "PMTU-D Table size can be changed with this object.
                        Changing the value of this object causes PMTU-D to
                        reboot. The module alone is restarted with the new
                        table size."
               DEFVAL { 10 }
               ::= { fsip 14 }

          fsIpProxyArpSubnetOption OBJECT-TYPE
              SYNTAX INTEGER {
                       enabled     (1),
                       disabled    (2)
              }
              MAX-ACCESS read-write
              STATUS     obsolete
              DESCRIPTION
                      "This Object Enables or Disables Subnet Check in Proxy
                       ARP feature.When this object is set to enabled (1),
                       ISS will act as ARP proxy for target address which
                       is in different subnet.When this object is set to
                       disabled (2) ISS will act as ARP proxy for target
                       address which is in same and different subnet which
                       is used in IP-DSLAM case."
              DEFVAL { enabled }
              ::= { fsip 15 }

--SCALAR_TABLE_END fsip
	  --This is the MIB for IP Traceroute functionality

	  fsIpTraceConfigTable	  OBJECT-TYPE
		  SYNTAX  SEQUENCE OF FsIpTraceConfigEntry
		  MAX-ACCESS  not-accessible
		  STATUS  current
		  DESCRIPTION
			  "This entity's IP Traceroute Configuration Table."
		  ::= { fsip 16 }

	  fsIpTraceConfigEntry	  OBJECT-TYPE
		  SYNTAX  FsIpTraceConfigEntry
		  MAX-ACCESS  not-accessible
		  STATUS  current
		  DESCRIPTION
			  "Contains the configuration information about a
			  particular IP
			  traceroute Operation."
		  INDEX	  { fsIpTraceConfigDest }
		  ::= { fsIpTraceConfigTable 1 }

	  FsIpTraceConfigEntry ::=
                   SEQUENCE {
		  fsIpTraceConfigDest	  IpAddress,
		  fsIpTraceConfigAdminStatus	  INTEGER,
		  fsIpTraceConfigMaxTTL	  Integer32,
		  fsIpTraceConfigMinTTL	  Integer32,
		  fsIpTraceConfigOperStatus INTEGER,
		  fsIpTraceConfigTimeout  Integer32,
		  fsIpTraceConfigMtu	  Integer32
		  }

	  fsIpTraceConfigDest	  OBJECT-TYPE
		  SYNTAX  IpAddress
		  MAX-ACCESS  not-accessible
		  STATUS  current
		  DESCRIPTION
			  "The destination IP address to which a route has to
			  be traced."
		  ::= { fsIpTraceConfigEntry 1 }

	  fsIpTraceConfigAdminStatus	  OBJECT-TYPE
		  SYNTAX  INTEGER {
			  on	  (1),
			  off	  (2)
			  }
		  MAX-ACCESS  read-write
		  STATUS  current
		  DESCRIPTION
			  "The desired status for the traceroute operation.
			  This variable has to be made on (from off) for
			  starting the operation. If this variable is set to
			  on when fsIpTraceConfigOperStatus is inprogress,
			  then GEN_ERROR is returned. This variable is set
			  to off when the fsIpTraceConfigOperStatus becomes
			  not inprogress."
		  DEFVAL { on }
		  ::= { fsIpTraceConfigEntry 2 }


	  fsIpTraceConfigMaxTTL	  OBJECT-TYPE
		  SYNTAX  Integer32 (1..99)
		  MAX-ACCESS  read-write
		  STATUS  current
		  DESCRIPTION
			  "The maximum value of the TTL field to be filled up
			  in the IP packets used for the traceroute."
		  DEFVAL  { 15 }
		  ::= { fsIpTraceConfigEntry 3 }


	  fsIpTraceConfigMinTTL	  OBJECT-TYPE
		  SYNTAX  Integer32 (1..99)
		  MAX-ACCESS  read-write
		  STATUS  current
		  DESCRIPTION
			  "The minimum value of the TTL field to be filled up
			  in the IP packets used for the traceroute."
		  DEFVAL  { 1 }
		  ::= { fsIpTraceConfigEntry 4 }


	  fsIpTraceConfigOperStatus OBJECT-TYPE
		  SYNTAX  INTEGER {
			  inprogress	  (1),
			  notinprogress	  (2)
			  }
		  MAX-ACCESS  read-only
		  STATUS  current
		  DESCRIPTION "The current status for the traceroute operation."
		  ::= { fsIpTraceConfigEntry 5 }

	  fsIpTraceConfigTimeout OBJECT-TYPE
		  SYNTAX  Integer32 (0..2147483647)
		  MAX-ACCESS  read-write
		  STATUS  current
		  DESCRIPTION
			  "Interval between (in seconds) consecutive trace
			  requests."
		  ::= { fsIpTraceConfigEntry 6 }

	  fsIpTraceConfigMtu OBJECT-TYPE
		  SYNTAX  Integer32 (0..2147483647)
		  MAX-ACCESS  read-write
		  STATUS  current
		  DESCRIPTION
			  "Number of octets of data to be sent in trace
			  packets."
		  ::= { fsIpTraceConfigEntry 7 }


	  fsIpTraceTable	  OBJECT-TYPE
		  SYNTAX  SEQUENCE OF FsIpTraceEntry
		  MAX-ACCESS  not-accessible
		  STATUS  current
		  DESCRIPTION
			  "This entity's IP Traceroute Table containing the
			  results of the traceroute operation(s)."
		  ::= { fsip 17 }

	  fsIpTraceEntry	  OBJECT-TYPE
		  SYNTAX  FsIpTraceEntry
		  MAX-ACCESS  not-accessible
		  STATUS  current
		  DESCRIPTION
			  "Contains the	 information about a particular
			  intermediate node on the way to the destination."
		  INDEX	  { fsIpTraceDest,
			    fsIpTraceHopCount }
		  ::= { fsIpTraceTable 1 }

	  FsIpTraceEntry	  ::=	  SEQUENCE {
		  fsIpTraceDest	  IpAddress,
		  fsIpTraceHopCount Integer32,
		  fsIpTraceIntermHop	  IpAddress,
		  fsIpTraceReachTime1	  Integer32,
		  fsIpTraceReachTime2	  Integer32,
		  fsIpTraceReachTime3	  Integer32
		  }

	  fsIpTraceDest	  OBJECT-TYPE
		  SYNTAX  IpAddress
		  MAX-ACCESS  not-accessible
		  STATUS  current
		  DESCRIPTION
			  "The destination IP address to which a route was
			  traced."
		  ::= { fsIpTraceEntry 1 }

	  fsIpTraceHopCount OBJECT-TYPE
		  SYNTAX  Integer32 (0..2147483647)
		  MAX-ACCESS  not-accessible
		  STATUS  current
		  DESCRIPTION
			  "The count of the number of hops required to reach
			  this intermediate node."
		  ::= { fsIpTraceEntry 2 }

	  fsIpTraceIntermHop	  OBJECT-TYPE
		  SYNTAX  IpAddress
		  MAX-ACCESS  read-only
		  STATUS  current
		  DESCRIPTION
			  "The IP address of the intermediate node/destination."
		  ::= { fsIpTraceEntry 3 }


	  fsIpTraceReachTime1	  OBJECT-TYPE
		  SYNTAX  Integer32 (0..2147483647)
		  MAX-ACCESS  read-only
		  STATUS  current
		  DESCRIPTION
			  "The time in seconds required to reach this
			  intermediate node.The value of '-1' denotes that the
			  response was not received from this node"
		  ::= { fsIpTraceEntry 4 }

	  fsIpTraceReachTime2	  OBJECT-TYPE
		  SYNTAX  Integer32 (0..2147483647)
		  MAX-ACCESS  read-only
		  STATUS  current
		  DESCRIPTION
			  "The time in seconds required to reach this
			  intermediate node for the second time. The value of
			  '-1' denotes that the response was not received
			  from this node"
		  ::= { fsIpTraceEntry 5 }

	  fsIpTraceReachTime3	  OBJECT-TYPE
		  SYNTAX  Integer32 (0..2147483647)
		  MAX-ACCESS  read-only
		  STATUS  current
		  DESCRIPTION
			  "The time in seconds required to reach this
			  intermediate node for the third time. The value of
			  '-1' denotes that the response was not received from
			  this node"
		  ::= { fsIpTraceEntry 6 }


	  fsIpAddressTable   OBJECT-TYPE
	      SYNTAX  SEQUENCE OF FsIpAddressEntry
	      MAX-ACCESS   not-accessible
	      STATUS   current
	      DESCRIPTION
		     "The table of IP addresses on every Interface."
	      ::= { fsip 18 }

	  fsIpAddressEntry   OBJECT-TYPE
	      SYNTAX   FsIpAddressEntry
	      MAX-ACCESS   not-accessible
	      STATUS   current
	      DESCRIPTION
		     "The individual entry in the above table."
	      INDEX   {
			fsIpAddrTabAddress
		      }
	      ::= { fsIpAddressTable 1 }

	  FsIpAddressEntry  ::=
	      SEQUENCE {
	      fsIpAddrTabIfaceId
		 Integer32,
	      fsIpAddrTabAddress
		 IpAddress,
	      fsIpAddrTabAdvertise
		 TruthValue,
	      fsIpAddrTabPreflevel
		 Integer32,
	      fsIpAddrTabStatus
		 RowStatus
	      }

	  fsIpAddrTabIfaceId	OBJECT-TYPE
	      SYNTAX	Integer32 (0..2147483647)
	      MAX-ACCESS	read-only
	      STATUS	current
	      DESCRIPTION
		      "The interface number to which the IP address
		      belongs to."
	      ::= { fsIpAddressEntry 1 }

	  fsIpAddrTabAddress	OBJECT-TYPE
	      SYNTAX	IpAddress
	      MAX-ACCESS	not-accessible
	      STATUS	current
	      DESCRIPTION
		      "One of the router's IP addresses."
	      ::= { fsIpAddressEntry 2 }

	  fsIpAddrTabAdvertise	OBJECT-TYPE
	      SYNTAX	TruthValue
	      MAX-ACCESS	read-write
	      STATUS	current
	      DESCRIPTION
		      "A flag indicating whether or not the address is
		      to be advertised."
	      ::= { fsIpAddressEntry 3 }

	  fsIpAddrTabPreflevel	OBJECT-TYPE
	      SYNTAX	Integer32 (0..2147483647)
	      MAX-ACCESS	read-write
	      STATUS	current
	      DESCRIPTION
		      "The preferability of the address as a default
		      router address, relative to other router addresses on
		      the same subnet. A 32-bit, signed, twos-complement
		      integer, with higher values meaning more preferable."
	      ::= { fsIpAddressEntry 4 }

	  fsIpAddrTabStatus	OBJECT-TYPE
	      SYNTAX	RowStatus
	      MAX-ACCESS	read-only
	      STATUS	current
	      DESCRIPTION
		      "The status of this row, by which new entries may be
		      created, or old entries deleted from this table."
	      ::= { fsIpAddressEntry 5 }

--List of Default Routers.
	  fsIpRtrLstTable	 OBJECT-TYPE
	      SYNTAX  SEQUENCE OF FsIpRtrLstEntry
	      MAX-ACCESS  not-accessible
	      STATUS  current
	      DESCRIPTION
		      "List of default router addresses. Used when system
		      functions as a host.Maintained as per RFC 1122."
	      ::= { fsip 19 }

	  fsIpRtrLstEntry	  OBJECT-TYPE
	      SYNTAX   FsIpRtrLstEntry
	      MAX-ACCESS   not-accessible
	      STATUS   current
	      DESCRIPTION
		     "The individual entry in the above table."
	      INDEX   { fsIpRtrLstAddress }
	      ::= { fsIpRtrLstTable 1 }

	  FsIpRtrLstEntry	 ::=
	      SEQUENCE {
	       fsIpRtrLstIface
		    Integer32,
	       fsIpRtrLstAddress
		    IpAddress,
	       fsIpRtrLstPreflevel
		    Integer32,
	       fsIpRtrLstStatic
		    TruthValue,
	       fsIpRtrLstStatus
		    RowStatus
	       }

	  fsIpRtrLstIface		OBJECT-TYPE
	      SYNTAX	Integer32 (0..2147483647)
	      MAX-ACCESS	read-write
	      STATUS	current
	      DESCRIPTION
		      "The interface via which the router could be
		      reached."
	      ::= { fsIpRtrLstEntry 1 }
	  fsIpRtrLstAddress	OBJECT-TYPE
	      SYNTAX	IpAddress
	      MAX-ACCESS	not-accessible
	      STATUS	current
	      DESCRIPTION
		      "An IP address of a default router."
	      ::= { fsIpRtrLstEntry 2 }

	  fsIpRtrLstPreflevel	OBJECT-TYPE
	      SYNTAX	Integer32 (0..2147483647)
	      MAX-ACCESS	read-write
	      STATUS	current
	      DESCRIPTION
		      "The preferability of the RouterAddress as a default
		      router address, relative to other router addresses
		      on the same subnet."
	      ::= { fsIpRtrLstEntry 3 }

	  fsIpRtrLstStatic	OBJECT-TYPE
	      SYNTAX	TruthValue
	      MAX-ACCESS	read-only
	      STATUS	current
	      DESCRIPTION
		      "This entry states how the default router address
		      was learned."
	      ::= { fsIpRtrLstEntry 4 }

	  fsIpRtrLstStatus	OBJECT-TYPE
	      SYNTAX	RowStatus
	      MAX-ACCESS	read-create
	      STATUS	current
	      DESCRIPTION
		      "The status of this row, by which new entries may be
		      created, or old entries deleted from this table."
	      ::= { fsIpRtrLstEntry 5 }


          fsIpPathMtuTable OBJECT-TYPE
              SYNTAX  SEQUENCE OF FsIpPathMtuEntry
              MAX-ACCESS not-accessible
              STATUS   current
              DESCRIPTION
                      "This Table shows the PMTU-D information for every path.
                       Administrator can enable or disable PMTU-D per
                       destination basis. This overrides the request from the
                       application."
              ::= { fsip 20 }

          fsIpPathMtuEntry OBJECT-TYPE
              SYNTAX  FsIpPathMtuEntry
              MAX-ACCESS not-accessible
              STATUS current
              DESCRIPTION
                      "This object forms the conceptual row of the PMTU Table."
              INDEX {
                  fsIpPmtuDestination,
                  fsIpPmtuTos
                  }
              ::= { fsIpPathMtuTable 1 }

          FsIpPathMtuEntry ::= SEQUENCE {
                  fsIpPmtuDestination
                      IpAddress,
                  fsIpPmtuTos
                      Integer32,
                  fsIpPathMtu
                      Integer32,
                  fsIpPmtuDisc
                      INTEGER,
                  fsIpPmtuEntryStatus
                      RowStatus
                  }

          fsIpPmtuDestination OBJECT-TYPE
               SYNTAX IpAddress
               MAX-ACCESS not-accessible
               STATUS current
               DESCRIPTION
                       "Specifies the Destination IP address of the Path for
                        which the discovery is made."
               ::= { fsIpPathMtuEntry 1 }

          fsIpPmtuTos OBJECT-TYPE
              SYNTAX Integer32 (0..2147483647)
              MAX-ACCESS not-accessible
              STATUS current
              DESCRIPTION
                      "Specifies the type of service of the path."
              ::= { fsIpPathMtuEntry 2 }

          fsIpPathMtu OBJECT-TYPE
              SYNTAX Integer32 (68 .. 65535)
              MAX-ACCESS read-write
              STATUS current
              DESCRIPTION
                      "Value of the path mtu discovered. If the admin changes
                       this value, PMTU discovery on that path is stopped."
              ::= { fsIpPathMtuEntry 3 }

          fsIpPmtuDisc OBJECT-TYPE
              SYNTAX INTEGER {
                     enabled   (1),
                     disabled  (2)
              }
              MAX-ACCESS read-write
              STATUS current
              DESCRIPTION
                      "Enables or Disables PMTU discovery for the given path.
                       This overrides the application request wrt to PMTU-D."
              ::= { fsIpPathMtuEntry 4 }

          fsIpPmtuEntryStatus OBJECT-TYPE
              SYNTAX RowStatus
              MAX-ACCESS read-write
              STATUS current
              DESCRIPTION
                      "Entry Status of the row in the PMTU table."
              ::= { fsIpPathMtuEntry 5 }

-- fsIpCommonRoutingTable

	  fsIpCommonRoutingTable OBJECT-TYPE
	      SYNTAX  SEQUENCE OF FsIpCommonRoutingEntry
	      MAX-ACCESS not-accessible
	      STATUS   current
	      DESCRIPTION
		 "Common routing Table which contains all the routing entries
                  for a particular destination."
             ::= { fsip 22 }

	 fsIpCommonRoutingEntry OBJECT-TYPE
	      SYNTAX   FsIpCommonRoutingEntry
	      MAX-ACCESS not-accessible
	      STATUS   current
	      DESCRIPTION
		 "A particular route to	 a particular destina-
		 tion, under a particular policy."
	      INDEX {
		  fsIpRouteDest,
		  fsIpRouteMask,
		  fsIpRouteTos,
		  fsIpRouteNextHop,
                  fsIpRouteProto
	     }
	      ::= { fsIpCommonRoutingTable 1 }

	  FsIpCommonRoutingEntry ::=
	      SEQUENCE {
		  fsIpRouteDest
		      IpAddress,
		  fsIpRouteMask
		      IpAddress,
		  fsIpRouteTos
		       Integer32,
		  fsIpRouteNextHop
		      IpAddress,
		  fsIpRouteProto
		      INTEGER,
		  fsIpRouteProtoInstanceId
			Integer32,
		  fsIpRouteIfIndex
		      Integer32,
		  fsIpRouteType
		      INTEGER,
		  fsIpRouteAge
		      Integer32,
		  fsIpRouteNextHopAS
		      Integer32,
		  fsIpRouteMetric1
		      Integer32,
		  fsIpRoutePreference
			Integer32,
		  fsIpRouteStatus
                      RowStatus,
          fsIpRouteProvider
            INTEGER
		 }

	  fsIpRouteDest OBJECT-TYPE
	      SYNTAX   IpAddress
	      MAX-ACCESS not-accessible
	      STATUS   current
	      DESCRIPTION
		 "The destination IP address of this route.This object may not
                  take a Multicast (Class  D)address value.Any assignment
                  (implicit or  otherwise)  of  an instance  of  this  object ,
                  to a value x must be rejected if the bitwise logical-AND of
            	  x  with the  value of the corresponding instance of the
                  fsIpRouteMask object is not equal to x."
              ::= { fsIpCommonRoutingEntry 1 }

	  fsIpRouteMask OBJECT-TYPE
	      SYNTAX   IpAddress
	      MAX-ACCESS not-accessible
	      STATUS   current
	      DESCRIPTION
		 "Indicate the mask to be logical-ANDed with the
		 destination  address  before  being compared to
		 the value  in	the  fsIpRouteDest  field.   For
		 those	systems	 that  do  not support arbitrary
		 subnet masks, an agent constructs the value  of
		 the  fsIpRouteMask  by  reference to the IP Ad-
		 dress Class.

		 Any assignment (implicit or  otherwise)  of  an
		 instance  of  this  object to a value x must be
		 rejected if the bitwise logical-AND of	 x  with
		 the  value of the corresponding instance of the
		 fsIpRouteDest object is not equal to fsIpRoute-
		 Dest."
	      ::= { fsIpCommonRoutingEntry 2 }

-- The following convention is included for specification
-- of TOS Field contents.  At this time, the Host Requirements
-- and the Router Requirements documents disagree on the width
-- of the TOS field.  This mapping describes the Router
-- Requirements mapping, and leaves room to widen the TOS field
-- without impact to fielded systems.

	  fsIpRouteTos OBJECT-TYPE
	      SYNTAX   Integer32 (0..2147483647)
	      MAX-ACCESS not-accessible
	      STATUS   current
	      DESCRIPTION
		 "The policy specifier is the IP TOS Field.  The encoding
		 of IP TOS is as specified  by	the  following convention.
		 Zero indicates the default path if no more  specific
		 policy applies.

		 +-----+-----+-----+-----+-----+-----+-----+-----+
		 |		   |			   |	 |
		 |   PRECEDENCE	   |	TYPE OF SERVICE	   |  0	 |
		 |		   |			   |	 |
		 +-----+-----+-----+-----+-----+-----+-----+-----+

			  IP TOS		IP TOS
		     Field     Policy	   Field     Policy
		     Contents	 Code	   Contents    Code
		     0 0 0 0  ==>   0	   0 0 0 1  ==>	  2
		     0 0 1 0  ==>   4	   0 0 1 1  ==>	  6
		     0 1 0 0  ==>   8	   0 1 0 1  ==>	 10
		     0 1 1 0  ==>  12	   0 1 1 1  ==>	 14
		     1 0 0 0  ==>  16	   1 0 0 1  ==>	 18
		     1 0 1 0  ==>  20	   1 0 1 1  ==>	 22
		     1 1 0 0  ==>  24	   1 1 0 1  ==>	 26
		     1 1 1 0  ==>  28	   1 1 1 1  ==>	 30"
                 ::= { fsIpCommonRoutingEntry 3 }

	  fsIpRouteNextHop OBJECT-TYPE
	      SYNTAX   IpAddress
	      MAX-ACCESS not-accessible
	      STATUS   current
	      DESCRIPTION
		 "On remote routes, the address of the next sys-
		 tem en route; Otherwise, 0.0.0.0."
	      ::= { fsIpCommonRoutingEntry 4 }

	  fsIpRouteProto OBJECT-TYPE
	      SYNTAX   INTEGER {
			  other	    (1),  -- not specified
			  local	    (2),  -- local interface
			  netmgmt   (3),  -- static route
			  icmp	    (4),  -- result of ICMP Redirect

				  -- the following are all dynamic
				  -- routing protocols
			  egp	     (5),  -- Exterior Gateway Protocol
			  ggp	     (6),  -- Gateway-Gateway Protocol
			  hello	     (7),  -- FuzzBall HelloSpeak
			  rip	     (8),  -- Berkeley RIP or RIP-II
			  isIs	     (9),  -- Dual IS-IS
			  esIs	     (10), -- ISO 9542
			  ciscoIgrp  (11), -- Cisco IGRP
			  bbnSpfIgp  (12), -- BBN SPF IGP
			  ospf	     (13), -- Open Shortest Path First
			  bgp	     (14), -- Border Gateway Protocol
			  idpr	     (15), -- InterDomain Policy Routing
			  ciscoEigrp (16)  -- Cisco EIGRP
		       }
	      MAX-ACCESS not-accessible
	      STATUS   current
	      DESCRIPTION
		 "The routing mechanism via which this route was
		 learned.  Inclusion of values for gateway rout-
		 ing protocols is not  intended	 to  imply  that
		 hosts should support those protocols."
	      ::= { fsIpCommonRoutingEntry 5 }

	fsIpRouteProtoInstanceId OBJECT-TYPE
      	    SYNTAX   Integer32
	    MAX-ACCESS read-only
	    STATUS   current
	    DESCRIPTION
		  "Instance Id of the dynamic routing protocol. This supports
                   multiple instantiation of dynamic protocols."
	      ::= { fsIpCommonRoutingEntry 6 }


	  fsIpRouteIfIndex OBJECT-TYPE
	      SYNTAX   Integer32
	      MAX-ACCESS read-write
	      STATUS   current
	      DESCRIPTION
		 "The ifIndex value which identifies the local interface
                  through  which,the next hop of this route should be reached."
	      ::= { fsIpCommonRoutingEntry 7 }

	  fsIpRouteType OBJECT-TYPE
	      SYNTAX   INTEGER {
			  other	   (1), -- not specified by this MIB
			  reject   (2), -- route which discards traffic
			  local	   (3), -- local interface
			  remote   (4)	-- remote destination
		       }
	      MAX-ACCESS read-write
	      STATUS   current
	      DESCRIPTION
		 "The type of route.  Note that local(3)  refers
		 to  a route for which the next hop is the final
		 destination; remote(4) refers to  a  route  for
		 which the  next  hop is not the final destina-
		 tion.

		 Routes which do not result in traffic forwarding or
		 rejection should not be displayed even if the
		 implementation keeps them stored internally.
		 reject (2) refers to a route which, if matched, discards
		 the message as unreachable. This is used in some
		 protocols as a means of correctly aggregating routes."
	      ::= { fsIpCommonRoutingEntry 8 }


	  fsIpRouteAge OBJECT-TYPE
	      SYNTAX   Integer32
	      MAX-ACCESS read-only
	      STATUS   current
	      DESCRIPTION
		 "The number of seconds	 since	this  route  was
		 last  updated	or  otherwise  determined  to be
		 correct.  Note that no semantics of  `too  old'
		 can  be implied except through knowledge of the
		 routing  protocol  by	which  the   route   was
		 learned."
	      DEFVAL  { 0 }
	      ::= { fsIpCommonRoutingEntry 9 }

	  fsIpRouteNextHopAS OBJECT-TYPE
	      SYNTAX   Integer32
	      MAX-ACCESS read-write
	      STATUS   current
	      DESCRIPTION
		 "The Autonomous System Number of the Next  Hop.
		 The  semantics of this object are determined by
		 the routing-protocol specified in  the	 route's
		 fsIpRouteProto  value. When	this object is
		 unknown or not relevant its value should be set
		 to zero."
	      DEFVAL { 0 }
	      ::= { fsIpCommonRoutingEntry 10 }

	  fsIpRouteMetric1 OBJECT-TYPE
            SYNTAX   Integer32
	      MAX-ACCESS read-only
	      STATUS   current
	      DESCRIPTION
		 "The primary routing  metric  for  this  route.
		 The  semantics of this metric are determined by
		 the routing-protocol specified in  the	 route's
		 fsIpRouteProto  value.   If	this metric is not
		 used, its value should be set to -1."
	      DEFVAL { -1 }
	      ::= { fsIpCommonRoutingEntry 11 }

	  fsIpRoutePreference OBJECT-TYPE
            SYNTAX   Integer32 (0.. 255)
	      MAX-ACCESS read-write
	      STATUS   current
	      DESCRIPTION
		 "The preference for the method by which this route was learned.
                  This value will be used by the forwarding algorithm to choose
                  the best route."
	      ::= { fsIpCommonRoutingEntry 12 }

	 fsIpRouteStatus  OBJECT-TYPE
             SYNTAX   RowStatus
             MAX-ACCESS read-create
    	       STATUS   current
               DESCRIPTION
       	  	  "The row status variable, used according to
      	           row installation and removal conventions."
	      ::= { fsIpCommonRoutingEntry 13 }

	fsIpRouteProvider OBJECT-TYPE
		SYNTAX   INTEGER
        MAX-ACCESS read-write
        STATUS current
        DESCRIPTION
            "This object is used to indicates the source where the route
            was learned."
        DEFVAL { 0 }
        ::= { fsIpCommonRoutingEntry 14 }

-- IPIF table

       fsIpifTable OBJECT-TYPE
              SYNTAX  SEQUENCE OF FsIpifEntry
	      MAX-ACCESS not-accessible
	      STATUS   current
	      DESCRIPTION
                 "IP interface table which maintains the interface specific configurable parameters of IP."
		 ::= { fsip 23 }

	 fsIpifEntry OBJECT-TYPE
	      SYNTAX   FsIpifEntry
	      MAX-ACCESS not-accessible
	      STATUS   current
	      DESCRIPTION
                 "A particular interface specific IP information."
	      INDEX {
		  fsIpifIndex
		  }
	      ::= { fsIpifTable 1 }

	  FsIpifEntry ::=
	      SEQUENCE {
		  fsIpifIndex
		      Integer32,
                  fsIpifMaxReasmSize
                      Integer32,
                  fsIpifIcmpRedirectEnable
                      INTEGER,
                  fsIpifDrtBcastFwdingEnable
                      INTEGER,
                  fsIpifProxyArpAdminStatus
                      INTEGER,
                  fsIpifLocalProxyArpAdminStatus
                      INTEGER
              }


          fsIpifIndex   OBJECT-TYPE
              SYNTAX  Integer32 (0..2147483647)
	      MAX-ACCESS  not-accessible
	      STATUS  current
	      DESCRIPTION
		      "The index value which identifies the
		       interface to which this entry is applicable. The
		       interface identified by a particular value of this
		       index is the same interface as identified by the same
		       value of ifIndex in MIB II."
	      ::= { fsIpifEntry 1 }

          fsIpifMaxReasmSize OBJECT-TYPE
              SYNTAX  Integer32 (1024..33280)
              MAX-ACCESS read-write
              STATUS  current
              DESCRIPTION
                      "The maximum size of the fragmented IP datagram received
              on this interface that can be considered for reassembly."
              ::= { fsIpifEntry 2 }


          fsIpifIcmpRedirectEnable   OBJECT-TYPE
             SYNTAX   INTEGER {
                        enabled(1),
                        disabled(2)
                      }
             MAX-ACCESS read-write
             STATUS   current
             DESCRIPTION
                     "Enabling or Diabling of the ICMP redirect messages on an
             interface basis."
             ::= { fsIpifEntry 3 }

           fsIpifDrtBcastFwdingEnable  OBJECT-TYPE
             SYNTAX   INTEGER {
                        enabled(1),
                        disabled(2)
                      }
             MAX-ACCESS read-write
             STATUS    current
             DESCRIPTION
                    "Enabling of Directed broadcast forwarding on that
             interface."
             ::= { fsIpifEntry 4 }

           fsIpifProxyArpAdminStatus OBJECT-TYPE
             SYNTAX      INTEGER {
                            enabled(1),
                            disabled(2)
                         }
             MAX-ACCESS  read-write
             STATUS      current
             DESCRIPTION
                  "Enables or Disables Proxy ARP Feature for that
                   interface. By default, this object
                   should have the value disabled(2)."
             DEFVAL     { disabled }
             ::= { fsIpifEntry 5 }

           fsIpifLocalProxyArpAdminStatus OBJECT-TYPE
              SYNTAX INTEGER {
                       enabled     (1),
                       disabled    (2)
              }
              MAX-ACCESS read-write
              STATUS current
              DESCRIPTION
                      "This Object Enables or Disables Proxy ARP feature
                       in local subnet.
                       When this object is set to enabled (1),
                       ISS will act as ARP proxy for target address which
                       is in same subnet also. When this object is set to
                       disabled (2) ISS will not act as ARP proxy for target
                       address which is in same subnet."
              DEFVAL { disabled }
              ::= { fsIpifEntry 6 }

-- end of IPIF table.

--SCALAR_TABLE_BEGIN fsicmp 16
	  -- the ICMP group

	  fsIcmpSendRedirectEnable OBJECT-TYPE
	       SYNTAX	     INTEGER   {
			  enabled	 (1),
			  disabled	 (2)
	       }
	       MAX-ACCESS	     read-write
	       STATUS	     current
	       DESCRIPTION " Allow sending ICMP Redirect Message "
	       DEFVAL	  { enabled }
	       ::= { fsicmp 1 }

	  fsIcmpSendUnreachableEnable OBJECT-TYPE
	       SYNTAX	     INTEGER  {
			  enabled	 (1),
			  disabled	 (2)
	       }
	       MAX-ACCESS	     read-write
	       STATUS	     current
	       DESCRIPTION " Allow sending ICMP Unreachable Message "
	       DEFVAL	  { enabled }
	       ::= { fsicmp 2 }

	  fsIcmpSendEchoReplyEnable OBJECT-TYPE
	       SYNTAX	     INTEGER  {
			  enabled	 (1),
			  disabled	 (2)
	       }
	       MAX-ACCESS	     read-write
	       STATUS	     current
	       DESCRIPTION " Allow sending ICMP Echo Reply Message "
	       DEFVAL	  { enabled }
	       ::= { fsicmp 3 }

	  fsIcmpNetMaskReplyEnable OBJECT-TYPE
	       SYNTAX	     INTEGER  {
			  enabled	 (1),
			  disabled	 (2)
	       }
	       MAX-ACCESS	     read-write
	       STATUS	     current
	       DESCRIPTION " Allow sending ICMP Net Mask Reply Message "
	       DEFVAL	  { enabled }
	       ::= { fsicmp 4 }

	  fsIcmpTimeStampReplyEnable OBJECT-TYPE
	       SYNTAX	     INTEGER  {
			  enabled	 (1),
			  disabled	 (2)
	       }
	       MAX-ACCESS	     read-write
	       STATUS	     current
	       DESCRIPTION " Allow sending ICMP Time stamp reply Message "
	       DEFVAL	  { enabled }
	       ::= { fsicmp 5 }
 -- DirectQuery begin.

	  fsIcmpInDomainNameRequests OBJECT-TYPE
	      SYNTAX  Counter32
	      MAX-ACCESS  read-only
	      STATUS  current
	      DESCRIPTION
		      "The number of ICMP Domain Name Requests
		      received."
	      ::= { fsicmp 6 }

	  fsIcmpInDomainNameReply OBJECT-TYPE
	      SYNTAX  Counter32
	      MAX-ACCESS  read-only
	      STATUS  current
	      DESCRIPTION
		      "The number of ICMP Domain Name Replies
		      received."
	      ::= { fsicmp 7 }

	  fsIcmpOutDomainNameRequests OBJECT-TYPE
	      SYNTAX  Counter32
	      MAX-ACCESS  read-only
	      STATUS  current
	      DESCRIPTION
		      "The number of ICMP Domain Name Requests
		      send."
	      ::= { fsicmp 8 }

	  fsIcmpOutDomainNameReply OBJECT-TYPE
	      SYNTAX  Counter32
	      MAX-ACCESS  read-only
	      STATUS  current
	      DESCRIPTION
		      "The number of ICMP Domain Name Replies
		      send."
	      ::= { fsicmp 9 }

	  fsIcmpDirectQueryEnable OBJECT-TYPE
	      SYNTAX	INTEGER {
			enabled		(1),
			disabled	(2)
	      }
	      MAX-ACCESS	read-write
	      STATUS	current
	      DESCRIPTION
		      "DNS Direct Query will be enabled or disabled
		      accordingly"
	      DEFVAL { disabled }
-- By default disabled because this is an Experimental Protocol.
	      ::= { fsicmp 10 }


-- Since this is an experimental Protocol we have the Domain Name also
-- placed within ICMP. Later it should be removed.
-- Also there is no support to have many Domain Name for a system
-- per Interface basis.

	  fsDomainName	OBJECT-TYPE
	      SYNTAX	DisplayString
	      MAX-ACCESS	read-write
	      STATUS	current
	      DESCRIPTION
		      "Domain Name of the system, used to send when
		      replies to DNS Direct Query."
	      ::= { fsicmp 11 }

	  fsTimeToLive	OBJECT-TYPE
	      SYNTAX	Integer32 (0..2147483647)
	      MAX-ACCESS	read-write
	      STATUS	current
	      DESCRIPTION
		      "The number of seconds untill which the name
		      can be cached."
	      ::= { fsicmp 12 }

-- DirectQuery end.

-- SecFail begin.

	  fsIcmpInSecurityFailures OBJECT-TYPE
	      SYNTAX	Counter32
	      MAX-ACCESS	read-only
	      STATUS	current
	      DESCRIPTION
		      "The number of ICMP Security Failure messages
		      received."
	      ::= { fsicmp 13 }

	  fsIcmpOutSecurityFailures OBJECT-TYPE
	      SYNTAX	Counter32
	      MAX-ACCESS	read-only
	      STATUS	current
	      DESCRIPTION
		      "The number of ICMP Security Failure messages
		      sent."
	      ::= { fsicmp 14 }

	  fsIcmpSendSecurityFailuresEnable OBJECT-TYPE
	      SYNTAX	INTEGER {
			enabled		(1),
			disabled	(2)
	      }
	      MAX-ACCESS	read-write
	      STATUS	current
	      DESCRIPTION
		      "Allow sending Security Failure messages."
	      DEFVAL { enabled }
	      ::= { fsicmp 15 }

	  fsIcmpRecvSecurityFailuresEnable OBJECT-TYPE
	      SYNTAX	INTEGER {
			enabled		(1),
			disabled	(2)
	      }
	      MAX-ACCESS	read-write
	      STATUS	current
	      DESCRIPTION
		      "Allow Recieving Security Failure messages."
	      DEFVAL { enabled }
	      ::= { fsicmp 16 }

--SCALAR_TABLE_END icmp

-- the UDP group

--SCALAR_TABLE_BEGIN fsudp 4

	  -- Implementation of the UDP group is current for all
	  -- systems which implement the UDP.

	  fsUdpInNoCksum	OBJECT-TYPE
		SYNTAX	      Counter32
		MAX-ACCESS	      read-only
		STATUS	      current
		DESCRIPTION " Number of UDP datagrams received without
			    checksum "
		::= { fsudp 1 }

	  fsUdpInIcmpErr OBJECT-TYPE
		SYNTAX	      Counter32
		MAX-ACCESS	      read-only
		STATUS	      current
		DESCRIPTION " Number of ICMP error packets received "
		::= { fsudp 2 }

	  fsUdpInErrCksum	 OBJECT-TYPE
		SYNTAX	      Counter32
		MAX-ACCESS	      read-only
		STATUS	      current
		DESCRIPTION " Number of UDP packets received with wrong
			     checksum "
		::= { fsudp 3 }

	  fsUdpInBcast OBJECT-TYPE
		SYNTAX	      Counter32
		MAX-ACCESS	      read-only
		STATUS	      current
		DESCRIPTION " Number of UDP packets received in broadcast mode "
		::= { fsudp 4 }

--SCALAR_TABLE_END udp

--  The CIDR group

	  fsCidrAggTable OBJECT-TYPE
	      SYNTAX     SEQUENCE OF FsCidrAggEntry
              MAX-ACCESS     not-accessible
              STATUS     current
              DESCRIPTION
                      "The (conceptual) table listing the router's
                       supernet routes.RIP advertises only supernet
                       routes on the speicified interface. And it
                       suppresses all routes which are subset of the supernet."
		    ::= { fscidr 1 }

	  fsCidrAggEntry OBJECT-TYPE
	      SYNTAX	FsCidrAggEntry
	      MAX-ACCESS    not-accessible
   	      STATUS	current
              DESCRIPTION
		      "An entry (conceptual row) in the
		      fsCidrAggTable representing supertnet route for
		      the domain."
	      INDEX  { fsCidrAggAddress, fsCidrAggAddressMask }
              ::= { fsCidrAggTable 1 }

          FsCidrAggEntry ::=
	      SEQUENCE {
	         fsCidrAggAddress		IpAddress,
		 fsCidrAggAddressMask	IpAddress,
		 fsCidrAggStatus		RowStatus
	      }


          fsCidrAggAddress OBJECT-TYPE
	      SYNTAX	 IpAddress
	      MAX-ACCESS not-accessible
	      STATUS	 current
	      DESCRIPTION
		      "The aggregated address which when combined with the
		      corresponding value of fsCidrAggAddressMask
		      identifies the supernet route for this domain."
	     ::= { fsCidrAggEntry 1 }

	  fsCidrAggAddressMask OBJECT-TYPE
	      SYNTAX	 IpAddress
	      MAX-ACCESS not-accessible
	      STATUS	 current
	      DESCRIPTION
		      "The aggregated address mask which when combined with
		      the corresponding value of fsCidrAggAddress
		      identifies the supernet route for the domain."
	     ::= { fsCidrAggEntry 2 }

	  fsCidrAggStatus OBJECT-TYPE
	      SYNTAX	 RowStatus
	      MAX-ACCESS read-write
	      STATUS	 current
	      DESCRIPTION
		      "The status of this row, by which new entries may be
		      created, or old entries deleted from this table."
	     ::= { fsCidrAggEntry 3 }

	  fsCidrAdvertTable OBJECT-TYPE
	      SYNTAX     SEQUENCE OF FsCidrAdvertEntry
	      MAX-ACCESS not-accessible
	      STATUS     current
	      DESCRIPTION
		      "The (conceptual) table listing the routes that are to
		      be explicitly advertised on a specific interface,
		      for multi-homed reasons, or policy reasons "
	      ::= { fscidr 2 }

	  fsCidrAdvertEntry OBJECT-TYPE
              SYNTAX     FsCidrAdvertEntry
              MAX-ACCESS not-accessible
	      STATUS     current
	      DESCRIPTION
	              "An entry (conceptual row) in the
		      fsCidrAdvertTable representing a route to be explicitly
		      advertised on a specific interface."
	      INDEX      { fsCidrAdvertAddress, fsCidrAdvertAddressMask }
	      ::= { fsCidrAdvertTable 1 }

	  FsCidrAdvertEntry ::= SEQUENCE {
	      fsCidrAdvertAddress		  IpAddress,
	      fsCidrAdvertAddressMask	  IpAddress,
	      fsCidrAdvertStatus		  RowStatus
	  }

	  fsCidrAdvertAddress OBJECT-TYPE
	      SYNTAX     IpAddress
	      MAX-ACCESS not-accessible
	      STATUS     current
	      DESCRIPTION
		      "The network address which when combined with the
		      corresponding value of fsCidrAdvertAddressMask
		      identifies the route that is to be explicitly advertised."
	      ::= { fsCidrAdvertEntry 1 }

	  fsCidrAdvertAddressMask OBJECT-TYPE
	      SYNTAX	IpAddress
	      MAX-ACCESS not-accessible
	      STATUS	current
	      DESCRIPTION
	  	      "The destination network address mask which when
		      combined with the corresponding value of
		      fsCidrAdvertAddress identifies the route to be
		      explicitly advertised."
	      ::= { fsCidrAdvertEntry 2 }

	  fsCidrAdvertStatus OBJECT-TYPE
	      SYNTAX	RowStatus
	      MAX-ACCESS read-write
	      STATUS	current
	      DESCRIPTION
	 	      "The status of this row, by which new entries may be
		      created, or old entries deleted from this table."
	      ::= { fsCidrAdvertEntry 3 }


--IRDP Group
--SCALAR_TABLE_BEGIN fsirdp 5

          fsIrdpInAdvertisements OBJECT-TYPE
	      SYNTAX	Counter32
	      MAX-ACCESS	read-only
	      STATUS	current
	      DESCRIPTION
	              "The total number of ICMP Router Advertisements		                      received."
	      ::= { fsirdp 1}

	  fsIrdpInSolicitations OBJECT-TYPE
	      SYNTAX  Counter32
	      MAX-ACCESS  read-only
	      STATUS  current
	      DESCRIPTION
		      "The total number of ICMP Router Solicitations
		      received."
	      ::= { fsirdp 2 }

	  fsIrdpOutAdvertisements OBJECT-TYPE
	      SYNTAX  Counter32
	      MAX-ACCESS  read-only
	      STATUS  current
	      DESCRIPTION
		      "The number of ICMP Router Advertisements
		      sent."
	      ::= { fsirdp 3 }

	  fsIrdpOutSolicitations OBJECT-TYPE
	      SYNTAX  Counter32
	      MAX-ACCESS  read-only
	      STATUS  current
	      DESCRIPTION
		      "The number of ICMP Router Solicitations
		      sent."
	      ::= { fsirdp 4 }

	  fsIrdpSendAdvertisementsEnable OBJECT-TYPE
	      SYNTAX	INTEGER {

			 enabled (1),

			disabled (2)
	      }
	      MAX-ACCESS	read-write
	      STATUS	current
	      DESCRIPTION
		      "Allow sending Router Advertisements."
	      DEFVAL { enabled }
	      ::= { fsirdp 5 }

   --SCALAR_TABLE_END fsirdp
	  fsIrdpIfConfTable	OBJECT-TYPE
	      SYNTAX	SEQUENCE OF FsIrdpIfConfEntry
	      MAX-ACCESS	not-accessible
	      STATUS	current
	      DESCRIPTION
		      "This table has interface specific irdp configurable
		      objects."
	      ::= {fsirdp 6 }

	  fsIrdpIfConfEntry	OBJECT-TYPE
	      SYNTAX	FsIrdpIfConfEntry
	      MAX-ACCESS	not-accessible
	      STATUS	current
	      DESCRIPTION
		      "The individual entry in the above table."
	      INDEX {
		       fsIrdpIfConfIfNum,
		       fsIrdpIfConfSubref
		    }
			::= { fsIrdpIfConfTable 1 }

	  FsIrdpIfConfEntry ::=
	      SEQUENCE {
	           fsIrdpIfConfIfNum
		         Integer32,
	           fsIrdpIfConfSubref
		         Integer32,
	           fsIrdpIfConfAdvertisementAddress
			 IpAddress,
		   fsIrdpIfConfMaxAdvertisementInterval
			 Integer32,
		   fsIrdpIfConfMinAdvertisementInterval
			 Integer32,
		   fsIrdpIfConfAdvertisementLifetime
			 Integer32,
		   fsIrdpIfConfPerformRouterDiscovery
			 TruthValue,
		   fsIrdpIfConfSolicitationAddress
			 IpAddress
	      }

	  fsIrdpIfConfIfNum    OBJECT-TYPE
	      SYNTAX	    Integer32 (0..2147483647)
	      MAX-ACCESS	    not-accessible
	      STATUS	    current
	      DESCRIPTION
		    "The number of interfaces present in this system."
	      ::= { fsIrdpIfConfEntry 1 }

	  fsIrdpIfConfSubref     OBJECT-TYPE
	      SYNTAX	    Integer32 (0..2147483647)
	      MAX-ACCESS	    not-accessible
	      STATUS	    current
	      DESCRIPTION
		    "The subreference of this interface."
	      ::= { fsIrdpIfConfEntry 2 }

	  fsIrdpIfConfAdvertisementAddress	OBJECT-TYPE
	      SYNTAX	IpAddress
	      MAX-ACCESS	read-write
	      STATUS	current
	      DESCRIPTION
		      "The IP destination address to be used for
		      multicast Rourter Advertisements sent from the
		      interface. The only permissible values are the
		      all-systems multicast address, 224.0.0.1, or
		      limited-broadcast address, 255.255.255.255. "
              DEFVAL { 'e0000001'H }
	      ::= { fsIrdpIfConfEntry 3 }

	  fsIrdpIfConfMaxAdvertisementInterval		OBJECT-TYPE
	      SYNTAX	Integer32 (4..1800)
	      MAX-ACCESS	read-write
	      STATUS	current
	      DESCRIPTION
		      "The maximum time allowed between sending multicast
		      Advertisements from the interface, in seconds."
	      DEFVAL { 600 }
	      ::= { fsIrdpIfConfEntry 4 }

	  fsIrdpIfConfMinAdvertisementInterval		OBJECT-TYPE
	      SYNTAX	Integer32 (4..1800)
	      MAX-ACCESS	read-write
	      STATUS	current
	      DESCRIPTION
		      "The minimum time allowed between sending unsolicited
		      multicast Router Advertisements from the interface,
		      in seconds."
	      DEFVAL { 450 }
	      ::= { fsIrdpIfConfEntry 5 }

	  fsIrdpIfConfAdvertisementLifetime		OBJECT-TYPE
	      SYNTAX	Integer32 (1800..9000)
	      MAX-ACCESS	read-write
	      STATUS	current
	      DESCRIPTION
		      "The value to be placed in the Lifetim efield of Router
		      Advertisements sent from the interface, in seconds."
	      DEFVAL { 1800 }
	      ::= { fsIrdpIfConfEntry 6 }

	  fsIrdpIfConfPerformRouterDiscovery		OBJECT-TYPE
	      SYNTAX	TruthValue
	      MAX-ACCESS	read-write
	      STATUS	current
	      DESCRIPTION
		      "A flag indicating whether or not the host is to perform
		      ICMP router discovery on the interface."
              DEFVAL { true }
	      ::= { fsIrdpIfConfEntry 7 }

	  fsIrdpIfConfSolicitationAddress			OBJECT-TYPE
	      SYNTAX	IpAddress
	      MAX-ACCESS	read-write
	      STATUS	current
	      DESCRIPTION
		      "The IP destination address to be used for sending
		      Router Solicitations from the interface. The only
		      permissible values are the all-routers multicast
		      address, 224.0.0.2, or the limited-broadcast
		      address, 255.255.255.255."
              DEFVAL { 'e0000002'H }
	      ::= { fsIrdpIfConfEntry 8 }

--SCALAR_TABLE_BEGIN fsrarpclient 3
-- the IP group


	  fsRarpClientRetransmissionTimeout OBJECT-TYPE
	      SYNTAX   Integer32 (30..3000)
	      MAX-ACCESS   read-write
	      STATUS   current
	      DESCRIPTION
	              "The interval (in seconds) after which an unanswered RARP
		      request should be retransmitted."
	      DEFVAL {100}
	      ::= { fsrarpclient 1}

	  fsRarpClientMaxRetries OBJECT-TYPE
	      SYNTAX Integer32 (2..10)
	      MAX-ACCESS read-write
	      STATUS current
	      DESCRIPTION
	              "The maximum number of retransmissions of RARP request
		      packet after which no request should be sent."
	      DEFVAL {4}
	      ::= { fsrarpclient 2}



	  fsRarpClientPktsDiscarded OBJECT-TYPE
	      SYNTAX Counter32
	      MAX-ACCESS read-only
	      STATUS current
	      DESCRIPTION
	              "Total number of RARP Reply packets discarded
                      by this client."
	      ::= { fsrarpclient 3 }


--SCALAR_TABLE_END
--SCALAR_TABLE_BEGIN fsrarpserver 3
--the IP Group

	  fsRarpServerStatus OBJECT-TYPE
	      SYNTAX INTEGER {
	               enabled (1),
	               disabled (2)
	      }
	      MAX-ACCESS read-write
	      STATUS current
	      DESCRIPTION
	              "Enables or Disables the RARP Server."
	      DEFVAL { disabled }
	      ::= { fsrarpserver 1 }

	  fsRarpServerPktsDiscarded OBJECT-TYPE
	      SYNTAX Counter32
	      MAX-ACCESS read-only
	      STATUS current
	      DESCRIPTION
	              "Total number of RARP request packets discarded
                      by this server."
	      ::= { fsrarpserver 2 }


          fsRarpServerTableMaxEntries OBJECT-TYPE
             SYNTAX Integer32(0..25)
             MAX-ACCESS read-write
             STATUS current
             DESCRIPTION
                     "Maximum number of entries in the RARP server table."
             ::= { fsrarpserver 3 }
--SCALAR_TABLE_END

          fsRarpServerDatabaseTable OBJECT-TYPE
	      SYNTAX SEQUENCE OF FsRarpServerDatabaseEntry
	      MAX-ACCESS not-accessible
	      STATUS current
	      DESCRIPTION
	              "The Server database which maps the Client's
                      hardware Address to IP Address ."
	      ::= { fsrarpserver 4 }

	  fsRarpServerDatabaseEntry OBJECT-TYPE
	      SYNTAX FsRarpServerDatabaseEntry
	      MAX-ACCESS not-accessible
	      STATUS current
	      DESCRIPTION
	              "Contains entry for a particular client."
	      INDEX { fsHardwareAddress }
	      ::= { fsRarpServerDatabaseTable 1 }

	  FsRarpServerDatabaseEntry ::=
	      SEQUENCE {
		 fsHardwareAddress OCTET STRING,
		 fsHardwareAddrLen Integer32 ,
		 fsProtocolAddress IpAddress,
		 fsEntryStatus RowStatus
	      }

	  fsHardwareAddress OBJECT-TYPE
	      SYNTAX OCTET STRING (SIZE(6))
	      MAX-ACCESS not-accessible
	      STATUS current
	      DESCRIPTION
		      "The Hardware address of the client."
	      ::= { fsRarpServerDatabaseEntry 1 }



	  fsHardwareAddrLen OBJECT-TYPE
	      SYNTAX Integer32 (1..6)
	      MAX-ACCESS read-write		   STATUS current
	      DESCRIPTION
		      "The hardware address length of the spceified index."
	      ::= { fsRarpServerDatabaseEntry 2 }

	  fsProtocolAddress OBJECT-TYPE
	      SYNTAX IpAddress
	      MAX-ACCESS read-write
	      STATUS current
	      DESCRIPTION
		      "IP Address corresponding to the client's
                      Hardware Address."
	      ::= { fsRarpServerDatabaseEntry 3 }

	  fsEntryStatus OBJECT-TYPE
	      SYNTAX RowStatus
	      MAX-ACCESS read-write
	      STATUS current
	      DESCRIPTION
		      "The status of this row,by which new entries may
                      be created or old entries can be deleted from
                      this server table as per SMIv2."
	      ::= { fsRarpServerDatabaseEntry 4 }

-- fssystemresize group
--SCALAR_TABLE_BEGIN fssystemresize 6

   fsNoOfStaticRoutes OBJECT-TYPE
      SYNTAX  Integer32
      MAX-ACCESS read-write
      STATUS  current
      DESCRIPTION
         "Number of static routes that can be configured in the system.
      The configured value will come in to effect only after rebooting the
      router."
      ::= { fssystemresize 1 }

   fsNoOfAggregatedRoutes OBJECT-TYPE
      SYNTAX  Integer32
      MAX-ACCESS read-write
      STATUS  current
      DESCRIPTION
         "Number of aggregated routes that can be configured in the system.
      This value will come in to effect only after rebooting the router.
      Minimum value is 5, if System Sizing is not enabled."
      ::= { fssystemresize 2 }

   fsNoOfRoutes OBJECT-TYPE
      SYNTAX  Integer32
      MAX-ACCESS read-write
      STATUS   current
      DESCRIPTION
         "Number of entries in the routing table. This is equal to the maximum
      number of routes learned by any of the routing protocol.This value will
      come in to effect only after rebooting the router. Cannot set below 500
      if System Sizing is disabled. "
      ::= { fssystemresize 3 }

   fsNoOfReassemblyLists OBJECT-TYPE
      SYNTAX   Integer32
      MAX-ACCESS read-write
      STATUS   current
      DESCRIPTION
         "Number of IP datagrams which are awaiting for reassembly.This value
      will come in to effect only after rebooting the router. The Maximum
      value is 150 when System Sizing is disabled"
      ::= { fssystemresize 4 }

   fsNoOfFragmentsPerList OBJECT-TYPE
      SYNTAX   Integer32
      MAX-ACCESS  read-write
      STATUS   current
      DESCRIPTION
         "Number of IP fragments that can be allowed in a single reassembly
      list.This value will come in to effect only after rebooting the router."
      ::= { fssystemresize 5 }

-- No of RIP peers is also a resizable object - It is supported as part of
-- standard mib.
--SCALAR_TABLE_END

--SCALAR_TABLE_BEGIN fslogandtrace 1

   fsIpGlobalDebug OBJECT-TYPE
      SYNTAX  Integer32
      MAX-ACCESS read-write
      STATUS  current
      DESCRIPTION
         "Enables the tracing in the selected submodule in IP. A 32 bit integer
      is used to store the Tracing level in the specified module.
       Different Tracing Levels -
         BIT 0 - Initialisation and Shutdown Trace.
         BIT 1 - Management trace.
         BIT 2 - Data path trace.
         BIT 3 - Control Plane trace.
         BIT 4 - Packet Dump.
         BIT 5 - OS Resource trace.
         BIT 6 - All Failure trace (All failures including Packet Validation)
         BIT 7 - Buffer Trace.

       Different submodule Tracing -
         BIT 16 - Tracing in IP module.
         BIT 17 - Tracing in ICMP submodule.
         BIT 19 - Tracing in RIP submodule.
         BIT 20 - Tracing in ARP submodule.
         BIT 21 - Tracing in BOOTP submodule.
         BIT 22 - Tracing in UDP submodule.

       The remaining bits are used.The combination of levels and submodules
       are allowed i.e. Tracing can be allowed at all failure and data path
       level in All submodules by setting the BIT appropriately.
       For Example, setting the debug valut to
          0b00000000000000010000000001000000 will enable all failure trace
       prints in IP module."
      ::= { fslogandtrace 1 }

--SCALAR_TABLE_END
END
