-- Copyright (C) 2008-2014 Super Micro Computer Inc. All Rights Reserved

-- $Id: fspvrst.mib,v 1.10 2012/10/31 09:38:45 siva Exp $

SUPERMICRO-PVRST-MIB DEFINITIONS ::= BEGIN

-- ---------------------------------------------------------
-- Proprietary MIB for Per VLAN Rapid Spanning Tree Protocol
-- ---------------------------------------------------------

IMPORTS

    OBJECT-TYPE,MODULE-IDENTITY, Integer32,
    enterprises,Counter32, TimeTicks,NOTIFICATION-TYPE FROM SNMPv2-SMI
    TEXTUAL-CONVENTION, MacAddress,
    TruthValue, RowStatus        FROM SNMPv2-TC;

futurePvrstMIB MODULE-IDENTITY
    LAST-UPDATED "201209050000Z"
    ORGANIZATION "Super Micro Computer Inc."
    CONTACT-INFO "support@Supermicro.com"
    DESCRIPTION
	"Draft 1"
    REVISION "201209050000Z"
    DESCRIPTION
	"Draft 1"
::= { enterprises supermicro-computer-inc(10876) super-switch(101) basic(1) 161}

BridgeId ::= TEXTUAL-CONVENTION
      STATUS  current
      DESCRIPTION
      " Identifier of Bridge in 8 byte format"
        SYNTAX          OCTET STRING (SIZE (8))

Timeout ::= TEXTUAL-CONVENTION
    DISPLAY-HINT "d4"
    STATUS       current
    DESCRIPTION
              " Time out value in 4 byte"
    SYNTAX       Integer32

EnabledStatus ::= TEXTUAL-CONVENTION
    STATUS      current
    DESCRIPTION
        "A simple status value for the object."
    SYNTAX      INTEGER { enabled(1), disabled(2) }


fsFuturePvrst     OBJECT IDENTIFIER   ::= { futurePvrstMIB 1 }
fsPvrstTrapsControl OBJECT IDENTIFIER ::= { futurePvrstMIB 2 }
fsFuturePvrstTraps OBJECT IDENTIFIER ::= { futurePvrstMIB 3 }

-- fsFuturePvrst group

fsPvrstSystemControl OBJECT-TYPE
   SYNTAX      INTEGER { start(1), shutdown(2) }
   MAX-ACCESS  read-write
   STATUS      current
   DESCRIPTION
      "The administrative shutdown status requested by management for the Pvrst
      feature. The value start (1) indicates that Pvrst should be active in
      the device on all ports. The value shutdown (2) indicates that Pvrst
      should be shutdown in the device on all ports. All memory should
      be released on all ports."
   ::= { fsFuturePvrst 1 }

fsPvrstModuleStatus OBJECT-TYPE
   SYNTAX      EnabledStatus
   MAX-ACCESS  read-write
   STATUS      current
   DESCRIPTION
      "The administrative status requested by management for the Pvrst
      feature. The value enabled(1) indicates that Pvrst should be enabled
      in the device on all ports. The value disabled(2) indicates that
      Pvrst should be disabled in the device on all ports. The object can
      be set to enabled(1) if and only if, fsPvrstSystemControl set to start."
   ::= { fsFuturePvrst 2 }

fsPvrstNoOfActiveInstances OBJECT-TYPE
   SYNTAX      Integer32
   MAX-ACCESS  read-only
   STATUS      current
   DESCRIPTION
      "Indicates number of instances active currently"
   ::= { fsFuturePvrst 3 }

fsPvrstBrgAddress OBJECT-TYPE
   SYNTAX      MacAddress
   MAX-ACCESS  read-only
   STATUS      current
   DESCRIPTION
         "The MAC address used by this bridge when it must
          be referred to in a unique fashion.   It is
          recommended that this be the numerically smallest
          MAC address of all ports that belong to this
          bridge.  However it is only required to be unique.
          When concatenated with fsPvrstInstBridgePriority or
          fsPvrstInstBridgePriority a unique BridgeIdentifier
          is formed which is used in the Spanning Tree Protocol."
   ::= { fsFuturePvrst 4 }

fsPvrstUpCount OBJECT-TYPE
   SYNTAX      Counter32
   MAX-ACCESS  read-only
   STATUS      current
   DESCRIPTION
        "The number of times Pvrst Module has been enabled."
   ::= { fsFuturePvrst 5 }

fsPvrstDownCount OBJECT-TYPE
   SYNTAX      Counter32
   MAX-ACCESS  read-only
   STATUS      current
   DESCRIPTION
        "The number of times PVRST Module has been disabled."
   ::= { fsFuturePvrst 6 }

fsPvrstPathCostDefaultType OBJECT-TYPE
SYNTAX      INTEGER {
               stp8021d1998(1),
               stp8021t2001(2)
            }
   MAX-ACCESS  read-write
   STATUS      obsolete
   DESCRIPTION
        "*******************Object is obsolete****************
         The version of the Spanning Tree default Path Costs that
         are to be used by this Bridge.  A value of 8021d1998(1)
         uses the 16-bit default Path Costs from IEEE Std. 802.1D-1998.
         A value of stp8021t2001(2) uses the 32-bit default Path
         Costs from IEEE Std. 802.1t."
   ::= { fsFuturePvrst 7 }

fsPvrstDynamicPathCostCalculation OBJECT-TYPE
      SYNTAX      TruthValue
      MAX-ACCESS  read-write
      STATUS      current
      DESCRIPTION
         "This object is used to determine whether dynamic pathcost
          calculation is allowed or not.The value is determined by
          management. If set to true, pathcost is calculated dynamically
          from port speed(when the operational status of the port changes
          from down to up), otherwise the link speed at the time of port
          creation is used for calculating the path cost. In both cases
          if the user has configured a pathcost for the port that will be
          used. By default dynamic pathcost calculation is set to false."
      DEFVAL { false }
      ::= { fsFuturePvrst 8 }

fsPvrstTrace OBJECT-TYPE
   SYNTAX      Integer32 (0..255)
   MAX-ACCESS  read-write
   STATUS      current
   DESCRIPTION
      "This object is used to enable Trace Statements for the Pvrst
      Module in this context .

      A FOUR BYTE integer is used for enabling the level of tracing.
      Each BIT in the four byte integer, represents a particular
      level of Trace.

      The mapping between the bit positions & the level of trace is
      as follows:
      0 - Init and Shutdown Traces
      1 - Management Traces
      2 - Data Path Traces
      3 - Control Plane Traces
      4 - Packet Dump Traces
      5 - Traces related to All Resources except Buffers
      6 - All Failure Traces
      7 - Buffer Traces

      The remaining bits are unused. Combination of trace levels are
      also allowed.

      For example if the bits 0 and 1 are set, then the Trace
      statements related to Init-Shutdown and management
      will be printed.

      The user has to enter the corresponding INTEGER VALUE for the
      bits set. For example if bits 0 and 1 are to be set then user has
      to give the value for this object as 3.

      Setting the Trace Option to any value will cause the Debug Option
      to be set to 0 (i.e.) the Trace Option and Debug Option are mutually
      exclusive."

      DEFVAL  { 0 }
   ::= { fsFuturePvrst 9 }

fsPvrstDebug OBJECT-TYPE
   SYNTAX      Integer32 (0..524287)
   MAX-ACCESS  read-write
   STATUS      current
   DESCRIPTION
      "This object is used to enable Debug Statements in the PvrstP
      Module.

      A FOUR BYTE integer is used for enabling the level of debugging.
      Each BIT in the four byte integer, represents a particular
      level of Debug.

      The mapping between the bit positions & the level of debug is
      as follows:
      0 - Init and Shutdown Debug statements
      1 - Management Debug statements
      2 - Memory related Debug statements
      3 - BPDU related Debug statements
      4 - Event Handling Debug statements
      5 - Timer Module Debug statements
      6 - Port Information SEM Debug statements
      7 - Port Receive SEM Debug statements (Invalid in the case of Pvrst)
      8 - Role Selection SEM Debug statements
      9 - Role Transition SEM Debug statements
     10 - State Transition SEM Debug statements
     11 - Protocol Migration SEM Debug statements
     12 - Topology Change SEM Debug statements
     13 - Port Transmit SEM Debug statements
     14 - Bridge Detection SEM Debug statements
     15 - All Failure Debug statements
     16 - Redundancy code flow Debug statements
     17 - State Machine variable changes Debug statements
     18 - Port Receive Pseudo Information SEM Debug statements

      The remaining bits are unused. Combination of debug levels are
      also allowed.

      For example if the bits 0 and 1 are set, then the Debug
      statements related to Init-Shutdown and management
      will be printed.

      The user has to enter the corresponding INTEGER VALUE for the
      bits set. For example if bits 0 and 1 are to be set then user has
      to give the value for this object as 3.

      Setting the Debug Option to any value will cause the Trace Option
      to be set to 0 (i.e.) the Trace Option and Debug Option are mutually
      exclusive."
      DEFVAL  { 0 }
   ::= { fsFuturePvrst 10 }

fsPvrstBufferOverFlowCount OBJECT-TYPE
   SYNTAX      Counter32
   MAX-ACCESS  read-only
   STATUS      current
   DESCRIPTION
        "The number of times Buffer overflows/failures have occured.
        A Trap is generated on the occurence of this event."
   ::= { fsFuturePvrst 11 }

fsPvrstMemAllocFailureCount OBJECT-TYPE
   SYNTAX      Counter32
   MAX-ACCESS  read-only
   STATUS      current
   DESCRIPTION
        "The number of times memory allocation failures have occured.
        A Trap is generated on the occurence of this event."
   ::= { fsFuturePvrst 12 }

-- -------------------------------------
-- fsFuturePvrstPortTable - Start
-- -------------------------------------

fsFuturePvrstPortTable OBJECT-TYPE
    SYNTAX SEQUENCE OF FsFuturePvrstPortEntry
    MAX-ACCESS    not-accessible
    STATUS        current
    DESCRIPTION
       "List of Ports per Virtual Context ."
    ::= { fsFuturePvrst 13 }

fsFuturePvrstPortEntry OBJECT-TYPE
   SYNTAX       FsFuturePvrstPortEntry
   MAX-ACCESS   not-accessible
   STATUS       current
   DESCRIPTION
      "Virtual Context Pvrst Module Port Parameters."
   INDEX { fsPvrstPort }
   ::= { fsFuturePvrstPortTable 1 }

FsFuturePvrstPortEntry ::=
    SEQUENCE {
	   fsPvrstPort
	      Integer32,
           fsPvrstPortAdminEdgeStatus
              TruthValue,
           fsPvrstPortOperEdgePortStatus
              TruthValue,
           fsPvrstBridgeDetectionSemState
              INTEGER,
           fsPvrstPortEnabledStatus
              TruthValue,
           fsPvrstRootGuard
              TruthValue,
           fsPvrstBpduGuard
              Integer32,
           fsPvrstEncapType
              INTEGER,
	   fsPvrstPortAdminPointToPoint
              INTEGER,
	   fsPvrstPortOperPointToPoint
	      TruthValue,
           fsPvrstPortInvalidBpdusRcvd
              Counter32,
           fsPvrstPortInvalidConfigBpduRxCount
              Counter32,
           fsPvrstPortInvalidTcnBpduRxCount
              Counter32,
           fsPvrstPortRowStatus
              RowStatus
    }

fsPvrstPort OBJECT-TYPE
   SYNTAX        Integer32 (1..65535)
   MAX-ACCESS    not-accessible
   STATUS        current
   DESCRIPTION
      "Port Number for the Context"
   ::= { fsFuturePvrstPortEntry 1 }

fsPvrstPortAdminEdgeStatus OBJECT-TYPE
   SYNTAX        TruthValue
   MAX-ACCESS    read-write
   STATUS        current
   DESCRIPTION
      "The administrative value of the Edge Port parameter.  A
          value of TRUE(1) indicates that this port should be
          assumed as an edge-port and a value of FALSE(2) indicates
          that this port should be assumed as a non-edge-port."
   ::= { fsFuturePvrstPortEntry 2 }

fsPvrstPortOperEdgePortStatus OBJECT-TYPE
   SYNTAX        TruthValue
   MAX-ACCESS    read-only
   STATUS        current
   DESCRIPTION
      "The operational value of the Edge Port parameter.  The
          object is initialized to the value of
          fsPvrstPortAdminEdgeStatus and is set FALSE on reception
          of a BPDU."
   ::= { fsFuturePvrstPortEntry 3 }

fsPvrstBridgeDetectionSemState OBJECT-TYPE
      SYNTAX      INTEGER {
                  edge (0),
                  notedge (1)
               }
      MAX-ACCESS  read-only
      STATUS      current
      DESCRIPTION
          "Current state of the bridge detetion state machine
	  of this port for all Spanning Tree context"
   ::= { fsFuturePvrstPortEntry 4 }

fsPvrstPortEnabledStatus OBJECT-TYPE
      SYNTAX      TruthValue
      MAX-ACCESS  read-write
      STATUS      current
      DESCRIPTION
          "The administrative value for the port
	  to configure PVRST enable/disable on this Port
	  By default PVRST is enabled on each port"
   ::= { fsFuturePvrstPortEntry 5 }

fsPvrstRootGuard OBJECT-TYPE
      SYNTAX      TruthValue
      MAX-ACCESS  read-write
      STATUS      current
      DESCRIPTION
          "The administrative value for the root guard
	  is configurable on this Port. By default it is
	  False(2) & can be configured True(1)"
   ::= { fsFuturePvrstPortEntry 6 }

fsPvrstBpduGuard OBJECT-TYPE
      SYNTAX      INTEGER    {
                    none (0),
                    enable (1),
                    disable (2)
                    }
      MAX-ACCESS  read-write
      STATUS      current
      DESCRIPTION
          "This configures the BPDU guard feature on this port and has higher priority over Global BPDU Guard.
       Enable - prevents temporary loops and applicable to ports and
       moves the port to disabled discarding state when BPDU is received on this port.
       Disable - Disables the Bpdu Guard feature and the port state will be maintained till it is manually made up.
       None - removes the BPDU Guard functionality on this port so that when Global BPDU guard
              configuration will take effect if this port is edge port"
    DEFVAL { 0 }
   ::= { fsFuturePvrstPortEntry 7 }

fsPvrstEncapType OBJECT-TYPE
      SYNTAX      INTEGER {
		  dot1Q (0),
		  isl (1) }
      MAX-ACCESS  read-write
      STATUS      current
      DESCRIPTION
          "The administrative value for the
	  encapsulation type on the Port.
	  On Access Port, the encapsulation
	  type will be DOT1q & is unchangeable.
	  Only on Trunk Ports it is changeable. "
      DEFVAL {0}
   ::= { fsFuturePvrstPortEntry 8 }

fsPvrstPortAdminPointToPoint OBJECT-TYPE
   SYNTAX        INTEGER {
		    forceTrue(0),
                    forceFalse(1),
                    auto(2)
		}
   MAX-ACCESS    read-write
   STATUS        current
   DESCRIPTION
      "The administrative point-to-point status of the LAN segment
          attached to this port.  A value of forceTrue(0) indicates that
          this port should always be treated as if it is connected to
          a point-to-point link.  A value of forceFalse(1) indicates
          that this port should be treated as having a shared media
          connection.  A value of auto(2) indicates that this port is
          considered to have a point-to-point link if it is an Aggregator
          and all of its members are aggregatable, or if the MAC entity
          is configured for full duplex operation, either through
          auto-negotiation or by management means."
   ::= { fsFuturePvrstPortEntry 9 }

fsPvrstPortOperPointToPoint OBJECT-TYPE
   SYNTAX        TruthValue
   MAX-ACCESS    read-only
   STATUS        current
   DESCRIPTION
      "The operational point-to-point status of the LAN segment
          attached to this port.  It indicates whether a port is
          considered to have a point-to-point connection or not.
          The value is determined by management or by auto-detection,
          as described in the fsPvrstPortAdminPointToPoint object."
   ::= { fsFuturePvrstPortEntry 10 }

fsPvrstPortInvalidBpdusRcvd OBJECT-TYPE
      SYNTAX      Counter32
      MAX-ACCESS  read-only
      STATUS      current
      DESCRIPTION
          "Number of Invalid Pvrst BPDUs Received on this port."
      ::= { fsFuturePvrstPortEntry 11 }

fsPvrstPortInvalidConfigBpduRxCount OBJECT-TYPE
      SYNTAX      Counter32
      MAX-ACCESS  read-only
      STATUS      current
      DESCRIPTION
          "Number of Invalid Configuration BPDUs Received on this port."
      ::= { fsFuturePvrstPortEntry 12 }

fsPvrstPortInvalidTcnBpduRxCount OBJECT-TYPE
      SYNTAX      Counter32
      MAX-ACCESS  read-only
      STATUS      current
      DESCRIPTION
          "Number of Invalid TCN BPDUs Received on this port."
      ::= { fsFuturePvrstPortEntry 13 }

fsPvrstPortRowStatus OBJECT-TYPE
      SYNTAX      RowStatus
      MAX-ACCESS  read-create
      STATUS      current
      DESCRIPTION
         "This object is used to create or delete interfaces at Pvrst module
          level.Ports can be created at Pvrst module level only for ports that
          have been created in Interface manager.This is applicable only when
          Automatic Port Create Feature is Disabled."
      ::= { fsFuturePvrstPortEntry 14 }

-- -------------------------------------
-- fsFuturePvrstPortTable - End
-- -------------------------------------

-- -----------------------------------------------------------------
-- Future Per Vlan Spanning Tree Instance Bridge Table
-- -----------------------------------------------------------------

fsPvrstInstBridgeTable OBJECT-TYPE
   SYNTAX      SEQUENCE OF FsPvrstInstBridgeEntry
   MAX-ACCESS  not-accessible
   STATUS      current
   DESCRIPTION
      "Table containing Bridge Information specific to Spanning
       Tree Instance."
   ::= { fsFuturePvrst 14 }

fsPvrstInstBridgeEntry OBJECT-TYPE
   SYNTAX      FsPvrstInstBridgeEntry
   MAX-ACCESS  not-accessible
   STATUS      current
   DESCRIPTION
      "Entry indicating the Bridge Information."
   INDEX { fsPvrstInstVlanId }
   ::= { fsPvrstInstBridgeTable 1 }

FsPvrstInstBridgeEntry ::=
   SEQUENCE {
      fsPvrstInstVlanId
            Integer32,
      fsPvrstInstBridgePriority
            Integer32,
      fsPvrstInstRootCost
            Integer32,
      fsPvrstInstRootPort
            Integer32,
      fsPvrstInstBridgeMaxAge
            Timeout,
      fsPvrstInstBridgeHelloTime
            Timeout,
      fsPvrstInstBridgeForwardDelay
            Timeout,
      fsPvrstInstHoldTime
            Integer32,
      fsPvrstInstTxHoldCount
            Integer32,
      fsPvrstInstTimeSinceTopologyChange
            TimeTicks,
      fsPvrstInstTopChanges
            Counter32,
      fsPvrstInstNewRootCount
            Counter32,
      fsPvrstInstInstanceUpCount
            Counter32,
      fsPvrstInstInstanceDownCount
            Counter32,
      fsPvrstInstPortRoleSelSemState
            INTEGER,
      fsPvrstInstDesignatedRoot
            BridgeId,
      fsPvrstInstRootMaxAge
            Timeout,
      fsPvrstInstRootHelloTime
            Timeout,
      fsPvrstInstRootForwardDelay
            Timeout
   }

fsPvrstInstVlanId OBJECT-TYPE
   SYNTAX      Integer32 (1..4094)
   MAX-ACCESS  not-accessible
   STATUS      current
   DESCRIPTION
      "Spanning Tree Instance to which the information belongs."
   ::= { fsPvrstInstBridgeEntry 1 }

fsPvrstInstBridgePriority OBJECT-TYPE
   SYNTAX      Integer32 (0..61440)
   MAX-ACCESS  read-write
   STATUS      current
   DESCRIPTION
      "The writable portion of the PVRST Bridge Identifier.
       comprising of the first two octets.
       The values that are set for Bridge Priority must be
       in steps of 4096."
   DEFVAL {32768}
   ::= { fsPvrstInstBridgeEntry 2 }

fsPvrstInstRootCost OBJECT-TYPE
   SYNTAX      Integer32
   MAX-ACCESS  read-only
   STATUS      current
   DESCRIPTION
      "The Cost of the path to the PVRST Root as seen
       by this bridge."
   ::= { fsPvrstInstBridgeEntry 3 }

fsPvrstInstRootPort OBJECT-TYPE
   SYNTAX      Integer32
   MAX-ACCESS  read-only
   STATUS      current
   DESCRIPTION
      "The Port Number of the Port which offers the lowest
       path cost from this bridge to the PVRST Root Bridge."
   ::= { fsPvrstInstBridgeEntry 4 }

fsPvrstInstBridgeMaxAge OBJECT-TYPE
   SYNTAX      Timeout
   MAX-ACCESS  read-write
   STATUS      current
   DESCRIPTION
      "Max Age of the Bridge Information"
   ::= { fsPvrstInstBridgeEntry 5 }

fsPvrstInstBridgeHelloTime OBJECT-TYPE
   SYNTAX      Timeout
   MAX-ACCESS  read-write
   STATUS      current
   DESCRIPTION
      "Hello Time configured at Bridge Level"
   ::= { fsPvrstInstBridgeEntry 6 }

fsPvrstInstBridgeForwardDelay OBJECT-TYPE
   SYNTAX      Timeout
   MAX-ACCESS  read-write
   STATUS      current
   DESCRIPTION
      "Forward Delay for STP bridge interoperability"
   ::= { fsPvrstInstBridgeEntry 7 }

fsPvrstInstHoldTime OBJECT-TYPE
   SYNTAX      Integer32
   MAX-ACCESS  read-only
   STATUS      current
   DESCRIPTION
      "Hold Time for eah port"
   ::= { fsPvrstInstBridgeEntry 8 }

fsPvrstInstTxHoldCount OBJECT-TYPE
   SYNTAX      Integer32 (1..10)
   MAX-ACCESS  read-write
   STATUS      current
   DESCRIPTION
      "The value used by the Port Transmit state machine to limit
         the maximum transmission rate."
   REFERENCE
        "IEEE 802.1w clause 17.16.6"
    DEFVAL      { 3 }
   ::= { fsPvrstInstBridgeEntry 9 }

fsPvrstInstTimeSinceTopologyChange OBJECT-TYPE
   SYNTAX      TimeTicks
   MAX-ACCESS  read-only
   STATUS      current
   DESCRIPTION
         "The time (in hundredths of a second) since the
         TcWhile Timer for any port in this Bridge was
         non-zero for this spanning tree instance."
   ::= { fsPvrstInstBridgeEntry 10 }

fsPvrstInstTopChanges OBJECT-TYPE
   SYNTAX      Counter32
   MAX-ACCESS  read-only
   STATUS      current
   DESCRIPTION
         "The number of times that there have been atleast
         one non-zero TcWhile Timer on this Bridge for this
         spanning tree instance."
   ::= { fsPvrstInstBridgeEntry 11 }

fsPvrstInstNewRootCount OBJECT-TYPE
   SYNTAX      Counter32
   MAX-ACCESS  read-only
   STATUS      current
   DESCRIPTION
         "The number of times this Bridge has detected a Root
          Bridge change for this spanning tree instance.
          A Trap is generated on the occurence of this event."
   ::= { fsPvrstInstBridgeEntry 12 }

fsPvrstInstInstanceUpCount OBJECT-TYPE
   SYNTAX      Counter32
   MAX-ACCESS  read-only
   STATUS      current
   DESCRIPTION
        "The number of times a new spanning tree instance has
         been created.
         A Trap is generated on the occurence of this event."
   ::= { fsPvrstInstBridgeEntry 13 }

fsPvrstInstInstanceDownCount OBJECT-TYPE
   SYNTAX      Counter32
   MAX-ACCESS  read-only
   STATUS      current
   DESCRIPTION
        "The number of times a spanning tree instance has
         been deleted.
         A Trap is generated on the occurence of this event."
   ::= { fsPvrstInstBridgeEntry 14 }

fsPvrstInstPortRoleSelSemState OBJECT-TYPE
      SYNTAX      INTEGER {
                  initbridge (0),
                  roleselection (1)
               }
      MAX-ACCESS  read-only
      STATUS      current
      DESCRIPTION
          "Current state of the Port Role Selection State Machine
           for this spanning tree instance for this bridge."
   ::= { fsPvrstInstBridgeEntry 15 }

fsPvrstInstDesignatedRoot OBJECT-TYPE
       SYNTAX  BridgeId
       MAX-ACCESS  read-only
       STATUS  current
       DESCRIPTION
               "The bridge identifier of the old root of the spanning
               tree instance as determined by the Spanning Tree Protocol
               as executed by this node. "
       ::= { fsPvrstInstBridgeEntry 16 }

fsPvrstInstRootMaxAge OBJECT-TYPE
   SYNTAX      Timeout
   MAX-ACCESS  read-only
   STATUS      current
   DESCRIPTION
      "Max Age of the Root Bridge Information"
   ::= { fsPvrstInstBridgeEntry 17 }

fsPvrstInstRootHelloTime OBJECT-TYPE
   SYNTAX      Timeout
   MAX-ACCESS  read-only
   STATUS      current
   DESCRIPTION
      "Hello Time of the Root Bridge"
   ::= { fsPvrstInstBridgeEntry 18 }

fsPvrstInstRootForwardDelay OBJECT-TYPE
   SYNTAX      Timeout
   MAX-ACCESS  read-only
   STATUS      current
   DESCRIPTION
      "Forward Delay of the Root Bridge"
   ::= { fsPvrstInstBridgeEntry 19 }


-- -----------------------------------------------------------------
-- Future Pvrst Common Spanning Tree Port Table
-- -----------------------------------------------------------------

fsPvrstInstPortTable OBJECT-TYPE
    SYNTAX      SEQUENCE OF FsPvrstInstPortEntry
    MAX-ACCESS  not-accessible
    STATUS      current
    DESCRIPTION
          "This table contains Common Spanning Tree Port
           Information."
     ::= { fsFuturePvrst 15 }

fsPvrstInstPortEntry OBJECT-TYPE
      SYNTAX      FsPvrstInstPortEntry
      MAX-ACCESS  not-accessible
      STATUS      current
      DESCRIPTION
          "A list of information maintained by every port for
          Each Spanning tree."
      INDEX  { fsPvrstInstVlanId,fsPvrstInstPortIndex }
      ::= { fsPvrstInstPortTable 1 }

FsPvrstInstPortEntry ::=
   SEQUENCE {
       fsPvrstInstPortIndex
            Integer32,
       fsPvrstInstPortEnableStatus
            INTEGER,
       fsPvrstInstPortPathCost
            Integer32,
       fsPvrstInstPortPriority
            Integer32,
       fsPvrstInstPortDesignatedRoot
            BridgeId,
       fsPvrstInstPortDesignatedBridge
            BridgeId,
       fsPvrstInstPortDesignatedPort
            OCTET STRING,
       fsPvrstInstPortOperVersion
	    INTEGER,
       fsPvrstInstPortProtocolMigration
            TruthValue,
       fsPvrstInstPortState
            INTEGER,
       fsPvrstInstPortForwardTransitions
            Counter32,
       fsPvrstInstPortReceivedBpdus
            Counter32,
       fsPvrstInstPortRxConfigBpduCount
            Counter32,
       fsPvrstInstPortRxTcnBpduCount
            Counter32,
       fsPvrstInstPortTransmittedBpdus
            Counter32,
       fsPvrstInstPortTxConfigBpduCount
            Counter32,
       fsPvrstInstPortTxTcnBpduCount
            Counter32,
       fsPvrstInstPortTxSemState
            INTEGER,
       fsPvrstInstPortProtMigrationSemState
            INTEGER,
       fsPvrstInstProtocolMigrationCount
            Counter32,
       fsPvrstInstPortRole
            INTEGER,
       fsPvrstInstCurrentPortRole
            INTEGER,
       fsPvrstInstPortInfoSemState
            INTEGER,
       fsPvrstInstPortRoleTransitionSemState
            INTEGER,
       fsPvrstInstPortStateTransitionSemState
            INTEGER,
       fsPvrstInstPortTopologyChangeSemState
            INTEGER,
       fsPvrstInstPortEffectivePortState
            TruthValue,
       fsPvrstInstPortHelloTime
            Timeout,
       fsPvrstInstPortMaxAge
	    Timeout,
       fsPvrstInstPortForwardDelay
	    Timeout,
       fsPvrstInstPortHoldTime
	    Timeout,
       fsPvrstInstPortAdminPathCost
         Integer32

}

fsPvrstInstPortIndex OBJECT-TYPE
      SYNTAX      Integer32 (1..65535)
      MAX-ACCESS  not-accessible
      STATUS      current
      DESCRIPTION
          "The Port Id of the port for which this entry contains
           spanning tree information."
      ::= { fsPvrstInstPortEntry 1 }

fsPvrstInstPortEnableStatus OBJECT-TYPE
      SYNTAX      INTEGER {
                  enable(1),
		  disable(2)
		  }
      MAX-ACCESS  read-write
      STATUS      current
      DESCRIPTION
          "The administrative value for the port
	  to configure PVRST enable/disable on this Port
	  for this instance."
      ::= { fsPvrstInstPortEntry 2 }

fsPvrstInstPortPathCost OBJECT-TYPE
      SYNTAX      Integer32 (1..200000000)
      MAX-ACCESS  read-write
      STATUS      current
      DESCRIPTION
            "The contribution of this port to the path cost of
             paths towards the Inst Root which include this port."
      ::= { fsPvrstInstPortEntry 3 }

fsPvrstInstPortPriority OBJECT-TYPE
      SYNTAX      Integer32 (0..240)
      MAX-ACCESS  read-write
      STATUS      current
      DESCRIPTION
          "The four most significant bits of the Port Identifier
          for a given Spanning Tree instance can be modified independently
	  for each Spanning Tree instance supported by the Bridge.
	  The values that are set for Port Priority must be in steps of 16."
     DEFVAL {128}
      ::= { fsPvrstInstPortEntry 4 }

fsPvrstInstPortDesignatedRoot OBJECT-TYPE
      SYNTAX      BridgeId
      MAX-ACCESS  read-only
      STATUS      current
      DESCRIPTION
          "The unique Bridge Identifier of the bridge recorded as the
           Inst Root in the configuration BPDUs transmitted."
      ::= { fsPvrstInstPortEntry 5 }

fsPvrstInstPortDesignatedBridge OBJECT-TYPE
      SYNTAX      BridgeId
      MAX-ACCESS  read-only
      STATUS      current
      DESCRIPTION
          "The unique Bridge Identifier of the bridge which this port
           considers to be the Designated Bridge for the port's segment."
      ::= { fsPvrstInstPortEntry 6 }

fsPvrstInstPortDesignatedPort OBJECT-TYPE
      SYNTAX  OCTET STRING (SIZE (2))
      MAX-ACCESS  read-only
      STATUS      current
      DESCRIPTION
          "The Port identifier of the port on the Designated Bridge
           for this port's segment."
      ::= { fsPvrstInstPortEntry 7 }

fsPvrstInstPortOperVersion OBJECT-TYPE
   SYNTAX      INTEGER {
               stpCompatible(0),
               rstp(2)
            }
   MAX-ACCESS  read-only
   STATUS      current
   DESCRIPTION
   	  "This indicates whether the Port is operationally in the
       Pvrst/Rstp mode or the Stp-compatible mode i.e., whether the
       Port is transmitting Pvrst/RST BPDUs or Config/TCN BPDUs."
      ::= { fsPvrstInstPortEntry 8 }

fsPvrstInstPortProtocolMigration OBJECT-TYPE
      SYNTAX      TruthValue
      MAX-ACCESS  read-only
      STATUS      current
      DESCRIPTION
          "Indicates the Protocol migration state of this Port.
           When operating in RSTP/Pvrst (version = 2) mode, writing
          TRUE(1) to this object forces this port to transmit RSTP
          BPDUs without instance information.
          Any other operation on this object has no effect and
          it always returns FALSE(2) when read."
      ::= { fsPvrstInstPortEntry 9 }

fsPvrstInstPortState OBJECT-TYPE
      SYNTAX      INTEGER {
                  disabled (1),
                  discarding (2),
                  learning (4),
                  forwarding (5)
                  }
      MAX-ACCESS  read-only
      STATUS      current
      DESCRIPTION
          "Current state of the Port as defined by the Common
           spanning tree protocol."
      ::= { fsPvrstInstPortEntry 10 }

fsPvrstInstPortForwardTransitions OBJECT-TYPE
      SYNTAX      Counter32
      MAX-ACCESS  read-only
      STATUS      current
      DESCRIPTION
          "Number of times this port has transitioned to the
           Forwarding State."
      ::= { fsPvrstInstPortEntry 11 }

fsPvrstInstPortReceivedBpdus OBJECT-TYPE
      SYNTAX      Counter32
      MAX-ACCESS  read-only
      STATUS      current
      DESCRIPTION
          "Number of Pvrst BPDUs received on this port."
      ::= { fsPvrstInstPortEntry 12 }

fsPvrstInstPortRxConfigBpduCount OBJECT-TYPE
      SYNTAX      Counter32
      MAX-ACCESS  read-only
      STATUS      current
      DESCRIPTION
          "Number of Configuration BPDUs received on this port."
      ::= { fsPvrstInstPortEntry 13 }

fsPvrstInstPortRxTcnBpduCount OBJECT-TYPE
      SYNTAX      Counter32
      MAX-ACCESS  read-only
      STATUS      current
      DESCRIPTION
          "Number of TCN BPDUs received on this port."
      ::= { fsPvrstInstPortEntry 14 }

fsPvrstInstPortTransmittedBpdus OBJECT-TYPE
      SYNTAX      Counter32
      MAX-ACCESS  read-only
      STATUS      current
      DESCRIPTION
          "Number of Pvrst BPDUs Transmitted from this port."
      ::= { fsPvrstInstPortEntry 15 }

fsPvrstInstPortTxConfigBpduCount OBJECT-TYPE
      SYNTAX      Counter32
      MAX-ACCESS  read-only
      STATUS      current
      DESCRIPTION
          "Number of Configuration BPDUs Transmitted from this port."
      ::= { fsPvrstInstPortEntry 16 }

fsPvrstInstPortTxTcnBpduCount OBJECT-TYPE
      SYNTAX      Counter32
      MAX-ACCESS  read-only
      STATUS      current
      DESCRIPTION
          "Number of TCN BPDUs Transmitted from this port."
      ::= { fsPvrstInstPortEntry 17 }

fsPvrstInstPortTxSemState OBJECT-TYPE
      SYNTAX      INTEGER {
                  transmitinit (0),
                  transmitperiodic (1),
                  transmitconfig (2),
                  transmittcn (3),
                  transmitrstp (4),
                  idle (5)
               }
      MAX-ACCESS  read-only
      STATUS      current
      DESCRIPTION
          "Indicates current State of the Port Transmit state machine."
      ::= { fsPvrstInstPortEntry 18 }

fsPvrstInstPortProtMigrationSemState OBJECT-TYPE
      SYNTAX      INTEGER {
                  init (0),
                  sendrstp (1),
                  sendingrstp (2),
                  sendstp (3),
                  sendingstp (4)
               }
      MAX-ACCESS  read-only
      STATUS      current
      DESCRIPTION
          "Indicates current State of the Port Protocol Migration
           State machine."
      ::= { fsPvrstInstPortEntry 19 }

fsPvrstInstProtocolMigrationCount OBJECT-TYPE
   SYNTAX      Counter32
   MAX-ACCESS  read-only
   STATUS      current
   DESCRIPTION
        "The number of times this Port has migrated from one STP protocol
        version to another. The relevant protocols are STP-COMPATIBLE and
        RSTP/Pvrst.
        A Trap is generated on the occurence of this event."
      ::= { fsPvrstInstPortEntry 20 }

fsPvrstInstPortRole OBJECT-TYPE
      SYNTAX      INTEGER {
                   disabled(0),
                   alternate(1),
                   backup(2),
                   root(3),
                   designated(4)
                  }
      MAX-ACCESS  read-only
      STATUS      current
      DESCRIPTION
          "Selected Port Role of the port for this spanning
          tree instance."
      ::= { fsPvrstInstPortEntry 21 }

fsPvrstInstCurrentPortRole OBJECT-TYPE
      SYNTAX      INTEGER {
                   disabled(0),
                   alternate(1),
                   backup(2),
                   root(3),
                   designated(4)
                  }
      MAX-ACCESS  read-only
      STATUS      current
      DESCRIPTION
          "Current Port Role of the port for this spanning
          tree instance."
      ::= { fsPvrstInstPortEntry 22 }

-- current (6) state has been changed to present (6) state in
-- PortInfoSemState as current is the keyword
fsPvrstInstPortInfoSemState OBJECT-TYPE
	SYNTAX      INTEGER {
               disabled (0),
                  aged (1),
	          update (2),
	          superior (3),
                  repeat (4),
                  agreement(5),
	          present (6),
                  receive (7)
            }
      MAX-ACCESS  read-only
      STATUS      current
      DESCRIPTION
          "Current state of the Port Information State Machine
           for this port in this spanning tree context."
      ::= { fsPvrstInstPortEntry 23 }

fsPvrstInstPortRoleTransitionSemState OBJECT-TYPE
      SYNTAX      INTEGER {
                  init (0),
                  blockport (1),
                  blockedport (2),
                  rootport(3),
		designatedport(4)
               }
      MAX-ACCESS  read-only
      STATUS      current
      DESCRIPTION
          "Current state of the Port Role Transition State Machine
           for this port in this spanning tree context."
      ::= { fsPvrstInstPortEntry 24 }

fsPvrstInstPortStateTransitionSemState OBJECT-TYPE
      SYNTAX      INTEGER {
                  discarding (0),
                  learning (1),
                  forwarding (2)
               }
      MAX-ACCESS  read-only
      STATUS      current
      DESCRIPTION
          "Current state of the Port State Transition State Machine
           for this port in this spanning tree context."
      ::= { fsPvrstInstPortEntry 25 }

fsPvrstInstPortTopologyChangeSemState OBJECT-TYPE
      SYNTAX      INTEGER {
                  init (0),
                  inactive (1),
                  active (2),
                  detected (3),
                  notifiedtcn (4),
                  notifiedtc (5),
                  propagating (6),
                  acknowledged (7)
               }
      MAX-ACCESS  read-only
      STATUS      current
      DESCRIPTION
          "Current state of the Topology Change State Machine
           for this port in this spanning tree context."
      ::= { fsPvrstInstPortEntry 26 }

fsPvrstInstPortEffectivePortState OBJECT-TYPE
      SYNTAX      TruthValue
      MAX-ACCESS  read-only
      STATUS      current
      DESCRIPTION
          "The effective operational state of the port for Inst. This will be
          TRUE only when the port is operationally up in the Interface level
          and Protocol level for Inst. This is set to False for all
          other times."
      ::= { fsPvrstInstPortEntry 27 }

fsPvrstInstPortHelloTime OBJECT-TYPE
   SYNTAX      Timeout
   MAX-ACCESS  read-only
   STATUS      current
   DESCRIPTION
   	  "The amount of time between the transmission of
	   Configuration bridge PDUs by this node on this port
	   in units of hundredths of a second."
      ::= { fsPvrstInstPortEntry 28 }

fsPvrstInstPortMaxAge OBJECT-TYPE
   SYNTAX      Timeout
   MAX-ACCESS  read-only
   STATUS      current
   DESCRIPTION
      "Max Age of the Bridge Information"
   ::= { fsPvrstInstPortEntry 29 }

fsPvrstInstPortForwardDelay OBJECT-TYPE
   SYNTAX      Timeout
   MAX-ACCESS  read-only
   STATUS      current
   DESCRIPTION
      "Forward Delay for STP bridge interoperability"
   ::= { fsPvrstInstPortEntry 30 }

fsPvrstInstPortHoldTime OBJECT-TYPE
   SYNTAX      Timeout
   MAX-ACCESS  read-only
   STATUS      current
   DESCRIPTION
      "Hold Time for each port"
   ::= { fsPvrstInstPortEntry 31 }

fsPvrstInstPortAdminPathCost  OBJECT-TYPE
    SYNTAX      Integer32 (0..200000000)
    MAX-ACCESS  read-write
    STATUS      current
    DESCRIPTION
        "The administratively assigned value for the contribution
         of this port to the path cost of paths toward the spanning
         tree root.

         Writing a value of '0' assigns the automatically calculated
         default Path Cost value to the port.  If the default Path
         Cost is being used, this object returns '0' when read.

         This complements the object dot1dStpPortPathCost or
         dot1dStpPortPathCost32, which returns the operational value
         of the path cost.
         The value of this object MUST be retained across
         reinitializations of the management system."

    ::= { fsPvrstInstPortEntry 32 }

-- NEW SCALAR ADDED
fsPvrstCalcPortPathCostOnSpeedChg OBJECT-TYPE
      SYNTAX      TruthValue
      MAX-ACCESS  read-write
      STATUS      current
      DESCRIPTION
         "This object is used to determine whether dynamic pathcost
          calculation is done for a port for which Port Speed is changing
          dynamically. This is mainly intended for Link Aggregated ports where
          depending on Active ports speed of Link aggregated port changes.
          By default dynamic pathcost calculation on change in speed is set to
          false."
      DEFVAL { false }
      ::= { fsFuturePvrst 16 }

fsPvrstGlobalBpduGuard OBJECT-TYPE
      SYNTAX      INTEGER    {
                    enable (1),
                    disable (2)
                    }
      MAX-ACCESS  read-write
      STATUS      current
      DESCRIPTION
          "This object configures BPDU guard globally in PVRST
           and this global BPDU is applicable if and only if no Port specific
           BpduGuard is configured.
           Enable - enables  BPDU Guard feature on edge ports globally and
           moves the port to disabled discarding state when BPDU is received
           on the edge ports.
           Disable - disables  BPDU Guard feature on edge ports globally"
    DEFVAL { 2 }
   ::= { fsFuturePvrst 17 }


--SCALAR END

-- TRAP MIB BEGIN

fsPvrstSetTraps OBJECT-TYPE
        SYNTAX   Integer32 (0..3)
        MAX-ACCESS   read-write
        STATUS   current
        DESCRIPTION
           "This object is used to enable and  disable
           Pvrst traps. Currently the following are defined
           0 - Traps are not enabled.
           1 - General Traps like protocol up or down
           2 - Exception Traps like port protocol migration or
	       invalid packet rcvd in port
           3 - All the above Traps "
    ::= { fsPvrstTrapsControl 1 }

 fsPvrstGenTrapType OBJECT-TYPE
       SYNTAX   INTEGER   {
                    none (0),
                    up (1),
                    down (2)
                    }
       MAX-ACCESS  read-only
       STATUS  current
       DESCRIPTION
          "Used within the Trap Notification PDU.
	   It denotes general events like
           none - none of the below values
           up - protocol UP,
           down - protocol DOWN"
    ::= { fsPvrstTrapsControl 2 }

fsPvrstErrTrapType OBJECT-TYPE
       SYNTAX   INTEGER   {
                    none (0),
                    memfail (1),
                    bufffail (2)
                    }
       MAX-ACCESS  read-only
       STATUS  current
       DESCRIPTION
           "Used within the Trap Notification PDU.
	    It returns the following values
            none - none of the below values
            memfail - memory allocation failure
            bufffail - buffer allocation failure"
   ::= { fsPvrstTrapsControl 3 }

fsPvrstPortTrapNotificationTable OBJECT-TYPE
   SYNTAX SEQUENCE OF FsPvrstPortTrapNotificationEntry
   MAX-ACCESS not-accessible
   STATUS     current
   DESCRIPTION
       "This table is used to store the notification information
       occured in each of the port for protocol migration and
       invalid packet received."
   ::= { fsPvrstTrapsControl 4 }

fsPvrstPortTrapNotificationEntry OBJECT-TYPE
   SYNTAX      FsPvrstPortTrapNotificationEntry
   MAX-ACCESS  not-accessible
   STATUS      current
   DESCRIPTION
       " This entry is used to store the notification information"
   INDEX { fsPvrstPortTrapIndex}
   ::= { fsPvrstPortTrapNotificationTable 1 }

FsPvrstPortTrapNotificationEntry ::=
        SEQUENCE {
               fsPvrstPortTrapIndex
               Integer32,
               fsPvrstPortMigrationType
               INTEGER,
               fsPvrstPktErrType
               INTEGER,
               fsPvrstPktErrVal
               Integer32
        }

 fsPvrstPortTrapIndex OBJECT-TYPE
   SYNTAX      Integer32 (1..4096)
   MAX-ACCESS  not-accessible
   STATUS      current
   DESCRIPTION
      "A unique value, greater than zero, indicating the Port number."
   ::= { fsPvrstPortTrapNotificationEntry 1 }

 fsPvrstPortMigrationType OBJECT-TYPE
      SYNTAX      INTEGER {
                  sendstp (0),
                  sendrstp (1)
                  }
       MAX-ACCESS  read-only
       STATUS  current
       DESCRIPTION
           "Port Protocol migration type occured in the port"
   ::= { fsPvrstPortTrapNotificationEntry 2 }

 fsPvrstPktErrType OBJECT-TYPE
      SYNTAX      INTEGER {
                  protocolIdErr(0),
                  invalidBpdu(1),
                  configLengthErr(2),
                  tcnLengthErr(3),
                  rstpLengthErr(4),
                  maxAgeErr(5),
                  fwdDelayErr(6),
                  helloTimeErr(7),
                  pvrstLengthErr(8)
                  }
       MAX-ACCESS  read-only
       STATUS  current
       DESCRIPTION
           "Type of invalid packet received in each of the port "
   ::= { fsPvrstPortTrapNotificationEntry 3 }

 fsPvrstPktErrVal OBJECT-TYPE
       SYNTAX      Integer32
       MAX-ACCESS  read-only
       STATUS      current
       DESCRIPTION
           "Packet error value corresponding to the above type "
   ::= { fsPvrstPortTrapNotificationEntry 4 }

fsPvrstPortRoleTrapNotificationTable OBJECT-TYPE
   SYNTAX SEQUENCE OF FsPvrstPortRoleTrapNotificationEntry
   MAX-ACCESS not-accessible
   STATUS     current
   DESCRIPTION
       "This table is used to store the notification information
       occured in each of the port during role change."
   ::= { fsPvrstTrapsControl 5 }

fsPvrstPortRoleTrapNotificationEntry OBJECT-TYPE
   SYNTAX      FsPvrstPortRoleTrapNotificationEntry
   MAX-ACCESS  not-accessible
   STATUS      current
   DESCRIPTION
       " This entry is used to store the notification information"
   INDEX { fsPvrstPortTrapIndex, fsPvrstInstVlanId}
   ::= { fsPvrstPortRoleTrapNotificationTable 1 }

FsPvrstPortRoleTrapNotificationEntry ::=
        SEQUENCE {
		fsPvrstPortRoleType
		INTEGER,
		fsPvrstOldRoleType
		INTEGER
	}

 fsPvrstPortRoleType OBJECT-TYPE
      SYNTAX      INTEGER {
                  disabledPort(0),
                  alternatePort(1),
                  backupPort(2),
                  rootPort(3),
                  designatedPort(4)
                  }
       MAX-ACCESS  read-only
       STATUS  current
       DESCRIPTION
           "Particular Role Selected for the Port"
   ::= { fsPvrstPortRoleTrapNotificationEntry 1 }

 fsPvrstOldRoleType OBJECT-TYPE
      SYNTAX      INTEGER {
                  disabledPort(0),
                  alternatePort(1),
                  backupPort(2),
                  rootPort(3),
                  designatedPort(4)
                  }
       MAX-ACCESS  read-only
       STATUS  current
       DESCRIPTION
           "Particular Role which is existing for the Port"
   ::= { fsPvrstPortRoleTrapNotificationEntry 2 }

 fsPvrstTraps OBJECT IDENTIFIER ::= { fsFuturePvrstTraps 0 }

 fsPvrstGenTrap NOTIFICATION-TYPE
        OBJECTS {
            fsPvrstBrgAddress,
            fsPvrstGenTrapType,
            fsPvrstInstInstanceUpCount,
            fsPvrstInstInstanceDownCount
                }
        STATUS             current
        DESCRIPTION
         "Generated when any of the general events like protocol up or
          protocol down occurs"
   ::= { fsPvrstTraps 1 }

 fsPvrstErrTrap NOTIFICATION-TYPE
        OBJECTS {
           fsPvrstBrgAddress,
           fsPvrstErrTrapType
                }
        STATUS             current
        DESCRIPTION
         "Generated when any of the error events like memory failure or buffer failure
          or protocol migration or new root or topology change occurrs "
   ::= { fsPvrstTraps 2 }

 fsPvrstNewRootTrap NOTIFICATION-TYPE
        OBJECTS {
            fsPvrstBrgAddress,
            fsPvrstInstDesignatedRoot
                }
        STATUS             current
        DESCRIPTION
         "Generated whenever a new root bridge is selected in the topology "
   ::= { fsPvrstTraps 3 }

 fsPvrstTopologyChgTrap NOTIFICATION-TYPE
        OBJECTS {
            fsPvrstBrgAddress,
            fsPvrstInstTopChanges
                }
        STATUS             current
        DESCRIPTION
         "Generated when topology change is detected "
   ::= { fsPvrstTraps 4 }

 fsPvrstProtocolMigrationTrap NOTIFICATION-TYPE
        OBJECTS {
            fsPvrstBrgAddress,
            fsPvrstPortMigrationType
                }
        STATUS             current
        DESCRIPTION
         "Generated when port protocol migration happens in the port "
   ::= { fsPvrstTraps 5 }

fsPvrstInvalidBpduRxdTrap NOTIFICATION-TYPE
        OBJECTS {
            fsPvrstBrgAddress,
            fsPvrstPktErrType,
            fsPvrstPktErrVal
                }
        STATUS             current
        DESCRIPTION
         "Generated when the invalid packet is received for
          bpdu/stp/rstp/maximum age/forward delay/hello time"
   ::= { fsPvrstTraps 6 }

fsPvrstNewPortRoleTrap NOTIFICATION-TYPE
        OBJECTS {
            fsPvrstBrgAddress,
            fsPvrstPortRoleType,
            fsPvrstOldRoleType
                }
        STATUS             current
        DESCRIPTION
         "Generated whenever a new role is selected for the port "
   ::= { fsPvrstTraps 7 }

fsPvrstHwFailureTrap NOTIFICATION-TYPE
        OBJECTS {
                  fsPvrstBrgAddress,
                  fsPvrstInstPortState
                }
        STATUS             current
        DESCRIPTION
         "Generated whenever an NPAPI call that is invoked from the protocol
          to program the hardware port state fails."
   ::= { fsPvrstTraps 8 }

-- TRAP MIB END

END
