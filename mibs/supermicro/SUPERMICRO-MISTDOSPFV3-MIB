-- Copyright (C) 2008-2014 Super Micro Computer Inc. All Rights Reserved

-- /*****************************************************************
--  *                                                               *
--  * $Id: fsmisos3.mib,v 1.4 2012/09/07 09:52:05 siva Exp $        *
--  * fsmisos3.mib                                                  *
--  *                                                               *
--  * OSPFv3 Proprietary MIB.                               *
--  *                                                               *
--  ****************************************************************/

SUPERMICRO-MISTDOSPFV3-MIB DEFINITIONS ::= BEGIN

   IMPORTS
        MODULE-IDENTITY, OBJECT-TYPE, Counter32,
        Gauge32, Integer32, IpAddress, enterprises, Unsigned32
                FROM SNMPv2-SMI
        TruthValue, StorageType, RowStatus, TEXTUAL-CONVENTION
                FROM SNMPv2-TC
        InterfaceIndex
                FROM IF-MIB
        InetAddressType, InetAddress, InetAddressPrefixLength
                FROM INET-ADDRESS-MIB
        AreaID, RouterID, Metric, BigMetric, Status,
        HelloRange, DesignatedRouterPriority
                FROM OSPF-MIB;

fsMIStdOspfv3 MODULE-IDENTITY
        LAST-UPDATED "201209050000Z"
        ORGANIZATION "Super Micro Computer Inc."
        CONTACT-INFO "support@Supermicro.com"
        DESCRIPTION
            "The Proprietary MI STD OSPF3 MIB modified
	    from STD OSPF3 MIB"
	REVISION "201209050000Z"
        DESCRIPTION
            "The Proprietary MI STD OSPF3 MIB modified
	    from STD OSPF3 MIB"

         ::= { enterprises supermicro-computer-inc(10876) super-switch(101) basic(2) 23 }

    -- Texual conventions

    UpToRefreshInterval ::= TEXTUAL-CONVENTION
             DISPLAY-HINT "d"
             STATUS        current
             DESCRIPTION
                "The values one might be able to configure for
                variables bounded by the Refresh Interval"
             SYNTAX        Integer32 (1..1800)

    RouterDeadRange ::= TEXTUAL-CONVENTION
             DISPLAY-HINT "d"
             STATUS        current
             DESCRIPTION
                "The range of intervals in seconds that a routers hello
                must have not been seen before a neighbor declares the
                router down"
             SYNTAX        Integer32 (1..'FFFF'h)

    -------------------

-- Top-level structure of MIB
fsMIStdOspfv3Objects        OBJECT IDENTIFIER ::= { fsMIStdOspfv3 1 }

--      OSPF Table
--      contains information regarding various instances
--      of the router

    fsMIStdOspfv3Table OBJECT-TYPE
        SYNTAX SEQUENCE OF FsMIStdOspfv3Entry
	    MAX-ACCESS   not-accessible
	    STATUS   current
	    DESCRIPTION
	        "Information describing the parameters
	         of router's instances"
      ::= { fsMIStdOspfv3Objects 1 }

    fsMIStdOspfv3Entry OBJECT-TYPE
        SYNTAX FsMIStdOspfv3Entry
	    MAX-ACCESS   not-accessible
	    STATUS   current
	    DESCRIPTION
	        "Information describing the parameters
	        of one of the router's instances"
	    INDEX { fsMIStdOspfv3ContextId }
      ::= { fsMIStdOspfv3Table 1 }

FsMIStdOspfv3Entry ::=
    SEQUENCE {
    fsMIStdOspfv3ContextId
	    Integer32,
	fsMIStdOspfv3RouterId
	    RouterID,
	fsMIStdOspfv3AdminStat
	    Status,
	fsMIStdOspfv3VersionNumber
	    INTEGER,
	fsMIStdOspfv3AreaBdrRtrStatus
	    TruthValue,
	fsMIStdOspfv3ASBdrRtrStatus
	    TruthValue,
	fsMIStdOspfv3AsScopeLsaCount
	    Gauge32,
	fsMIStdOspfv3AsScopeLsaCksumSum
	    Integer32,
	fsMIStdOspfv3OriginateNewLsas
	    Counter32,
	fsMIStdOspfv3RxNewLsas
	    Counter32,
	fsMIStdOspfv3ExtLsaCount
	    Gauge32,
	fsMIStdOspfv3ExtAreaLsdbLimit
	    Integer32,
	fsMIStdOspfv3MulticastExtensions
	    BITS,
	fsMIStdOspfv3ExitOverflowInterval
	    Unsigned32,
	fsMIStdOspfv3DemandExtensions
	    TruthValue,
	fsMIStdOspfv3TrafficEngineeringSupport
	    TruthValue,
	fsMIStdOspfv3ReferenceBandwidth
	    Unsigned32,
	fsMIStdOspfv3RestartSupport
	    INTEGER,
	fsMIStdOspfv3RestartInterval
	    UpToRefreshInterval,
	fsMIStdOspfv3RestartStatus
	    INTEGER,
	fsMIStdOspfv3RestartAge
	    UpToRefreshInterval,
	fsMIStdOspfv3RestartExitReason
	    INTEGER,
	fsMIStdOspfv3Status
	    RowStatus
	}

    fsMIStdOspfv3ContextId OBJECT-TYPE
        SYNTAX         Integer32 (0..2147483647)
	    MAX-ACCESS     not-accessible
	    STATUS         current
	    DESCRIPTION
	        "A 32-bit unique context id for each entry.
             Minimum value is 0 and Maximum depends upon
             system configuration. Default value is 0 which
             will be initialized during bootup"
      ::= { fsMIStdOspfv3Entry 1 }

    fsMIStdOspfv3RouterId OBJECT-TYPE
        SYNTAX         RouterID
        MAX-ACCESS     read-write
        STATUS         current
        DESCRIPTION
            "A  32-bit  integer  uniquely  identifying  the
            router in the Autonomous System.
            To  ensure  uniqueness, this may
            default  to  the  value  of  one of the
            router's IPv4 interface addresses if IPv4 is
            configured on the router."
      ::= { fsMIStdOspfv3Entry 2 }

    fsMIStdOspfv3AdminStat OBJECT-TYPE
        SYNTAX          Status
        MAX-ACCESS      read-write
        STATUS          current
        DESCRIPTION
            "The  administrative  status  of  OSPFv3  in  the
            router.   The  value 'enabled' denotes that the
            OSPFv3 Process is active on at least  one  inter-
            face;  'disabled'  disables  it  on  all inter-
            faces."
      ::= { fsMIStdOspfv3Entry 3 }

    fsMIStdOspfv3VersionNumber OBJECT-TYPE
        SYNTAX          INTEGER { version3(3) }
        MAX-ACCESS      read-only
        STATUS          current
        DESCRIPTION
            "The version number of OSPF for IPv6 is 3."
      ::= { fsMIStdOspfv3Entry 4 }

    fsMIStdOspfv3AreaBdrRtrStatus OBJECT-TYPE
        SYNTAX          TruthValue
        MAX-ACCESS      read-only
        STATUS          current
        DESCRIPTION
            "A flag to note whether this router is an  area
            border router."
        REFERENCE
            "OSPF Version 2, Section 3 Splitting the AS into
            Areas"
      ::= { fsMIStdOspfv3Entry 5 }

    fsMIStdOspfv3ASBdrRtrStatus OBJECT-TYPE
        SYNTAX          TruthValue
        MAX-ACCESS      read-write
        STATUS          current
        DESCRIPTION
            "A flag to note whether this router is  config-
            ured as an Autonomous System border router."
        REFERENCE
            "OSPF Version 2, Section 3.3  Classification  of
            routers"
      ::= { fsMIStdOspfv3Entry 6 }

    fsMIStdOspfv3AsScopeLsaCount OBJECT-TYPE
        SYNTAX          Gauge32
        MAX-ACCESS      read-only
        STATUS          current
        DESCRIPTION
            "The number of AS-Scope (e.g. AS-External) link-state
            advertisements in the link-state database."
        ::= { fsMIStdOspfv3Entry 7 }

    fsMIStdOspfv3AsScopeLsaCksumSum OBJECT-TYPE
        SYNTAX          Integer32
        MAX-ACCESS      read-only
        STATUS          current
        DESCRIPTION
            "The 32-bit unsigned sum of the LS checksums of
            the  AS-scoped link-state advertisements  con-
            tained in the link-state database. This sum
            can  be  used  to determine if there has been a
            change in a router's link state  database,  and
            to  compare  the  link-state  database  of  two
            routers."
      ::= { fsMIStdOspfv3Entry 8 }

    fsMIStdOspfv3OriginateNewLsas OBJECT-TYPE
        SYNTAX          Counter32
        MAX-ACCESS      read-only
        STATUS          current
        DESCRIPTION
            "The number of  new  link-state  advertisements
            that  have been originated.  This number is in-
            cremented each time the router originates a new
            LSA."
      ::= { fsMIStdOspfv3Entry 9 }

    fsMIStdOspfv3RxNewLsas OBJECT-TYPE
        SYNTAX          Counter32
        MAX-ACCESS      read-only
        STATUS          current
        DESCRIPTION
            "The number of  link-state  advertisements  re-
            ceived  determined  to  be  new instantiations.
            This number does not include  newer  instantia-
            tions  of self-originated link-state advertise-
            ments."
      ::= { fsMIStdOspfv3Entry 10 }

    fsMIStdOspfv3ExtLsaCount OBJECT-TYPE
        SYNTAX          Gauge32
        MAX-ACCESS      read-only
        STATUS          current
        DESCRIPTION
            "The number of External(LS type 0x4005) in the link-
            state database"
      ::= { fsMIStdOspfv3Entry 11 }

    fsMIStdOspfv3ExtAreaLsdbLimit OBJECT-TYPE
        SYNTAX          Integer32 (-1..'7FFFFFFF'h)
        MAX-ACCESS      read-write
        STATUS          current
        DESCRIPTION
            "The  maximum   number   of   non-default   AS-
            external-LSAs entries that can be stored in the
            link-state database.  If the value is -1, then
            there is no limit.

            When the number of non-default AS-external-LSAs
            in   a  router's  link-state  database  reaches
            ospfv3ExtAreaLsdbLimit, the router  enters  Overflow-
            State.   The   router  never  holds  more  than
            ospfv3ExtAreaLsdbLimit  non-default  AS-external-LSAs
            in  its  database. OspfExtAreaLsdbLimit MUST be set
            identically in all routers attached to the OSPFv3
            backbone  and/or  any regular OSPFv3 area. (i.e.,
            OSPFv3 stub areas and NSSAs are excluded)."
      ::= { fsMIStdOspfv3Entry 12 }

    fsMIStdOspfv3MulticastExtensions OBJECT-TYPE
        SYNTAX          BITS {
                                 intraAreaMulticast(0),
                                 interAreaMulticast(1),
                                 interAsMulticast(2)
                             }

        MAX-ACCESS      read-write
        STATUS          current
        DESCRIPTION
            "A Bit Mask indicating whether the router is
            forwarding IPv6 multicast datagrams
            based on the algorithms defined in the  Multi-
            cast Extensions to OSPF.

            If intraAreaMulticast set, indicates that the router
            can forward  IPv6 multicast datagrams in the router's
            directly attached areas (called intra-area mul-
            ticast routing).

            If interAreaMulticast set, indicates that the router
            can forward IPv6 multicast datagrams between OSPFv3
            areas (called inter-area multicast routing).

            If interAsMulticast set, indicates that the router can
            forward  IPv6  multicast datagrams between Auto-
            nomous Systems (called inter-AS multicast rout-
            ing).

            Only certain combinations of bit settings are
            allowed, namely:
                    - All bits cleared (no multicasting)
                    - intraAreaMulticast only,
                    - intraAreaMulticast and interAreaMulticast,
                    - intraAreaMulticast and interAsMulticast
                    - intraAreaMulticast, interAreaMulticast and
                            interAsMulticast
            By default, all bits are cleared."
      ::= { fsMIStdOspfv3Entry 13 }

    fsMIStdOspfv3ExitOverflowInterval OBJECT-TYPE
        SYNTAX          Unsigned32
        UNITS           "seconds"
        MAX-ACCESS      read-write
        STATUS          current
        DESCRIPTION
            "The number of  seconds  that,  after  entering
            OverflowState,  a  router will attempt to leave
            OverflowState. This allows the router to  again
            originate  non-default  AS-External-LSAs.  When
            set to 0, the router will not  leave  Overflow-
            State until restarted."
      ::= { fsMIStdOspfv3Entry 14 }

    fsMIStdOspfv3DemandExtensions OBJECT-TYPE
        SYNTAX         TruthValue
        MAX-ACCESS     read-write
        STATUS         current
        DESCRIPTION
            "The router's support for demand routing."
        REFERENCE
            "OSPF Version 2, Appendix on Demand Routing"
      ::= { fsMIStdOspfv3Entry 15 }

    fsMIStdOspfv3TrafficEngineeringSupport OBJECT-TYPE
        SYNTAX          TruthValue
        MAX-ACCESS      read-write
        STATUS          current
        DESCRIPTION
            "The router's support for traffic engineering
            extensions."
      ::= { fsMIStdOspfv3Entry 16 }

    fsMIStdOspfv3ReferenceBandwidth OBJECT-TYPE
        SYNTAX       Unsigned32
        MAX-ACCESS   read-write
        STATUS       current
        DESCRIPTION
            "Reference bandwidth in kilobits/second for
            calculating default interface metrics. The
            default value is 100,000 KBPS (100 MBPS)"
      ::= { fsMIStdOspfv3Entry 17 }

    fsMIStdOspfv3RestartSupport OBJECT-TYPE
        SYNTAX       INTEGER { none (1),
                               plannedOnly (2),
                               plannedAndUnplanned (3)
                             }
        MAX-ACCESS   read-write
        STATUS       current
        DESCRIPTION
            "The router's support for OSPF hitless restart.
            Options include: no restart support, only planned
            restarts or both planned and unplanned restarts."
      ::= { fsMIStdOspfv3Entry 18 }

    fsMIStdOspfv3RestartInterval OBJECT-TYPE
        SYNTAX       UpToRefreshInterval
        UNITS        "seconds"
        MAX-ACCESS   read-write
        STATUS       current
        DESCRIPTION
            "Configured OSPF hitless restart timeout interval."
      ::= { fsMIStdOspfv3Entry 19 }

    fsMIStdOspfv3RestartStatus OBJECT-TYPE
        SYNTAX       INTEGER { notRestarting (1),
                               plannedRestart (2),
                               unplannedRestart (3)
                             }
        MAX-ACCESS   read-only
        STATUS       current
        DESCRIPTION
            "Current status of OSPF hitless restart."
      ::= { fsMIStdOspfv3Entry 20 }

    fsMIStdOspfv3RestartAge OBJECT-TYPE
        SYNTAX       UpToRefreshInterval
        UNITS        "seconds"
        MAX-ACCESS   read-only
        STATUS       current
        DESCRIPTION
            "Remaining time in current OSPF hitless restart
            interval."
      ::= { fsMIStdOspfv3Entry 21 }

    fsMIStdOspfv3RestartExitReason OBJECT-TYPE
        SYNTAX       INTEGER { none (1),           -- none attempted
                               inProgress (2),     -- restart in
                                                   -- progress
                               completed (3),      -- successfully
                                                   -- completed
                               timedOut (4),       -- timed out
                               topologyChanged (5) -- aborted due to
                                                   -- topologychange.
                             }
        MAX-ACCESS   read-only
        STATUS       current
        DESCRIPTION
            "Describes the outcome of the last attempt at a
            hitless restart. If the value is 'none', no restart
            has yet been attempted. If the value is 'inProgress',
            a restart attempt is currently underway."
      ::= { fsMIStdOspfv3Entry 22 }

    fsMIStdOspfv3Status OBJECT-TYPE
        SYNTAX  RowStatus
	    MAX-ACCESS   read-write
	    STATUS   current
	    DESCRIPTION
	        "This variable displays the status of  the  en-
	        try.  The internal  effect (row removal) is
		implementation dependent."
      ::= { fsMIStdOspfv3Entry 23 }

--      The OSPFv3 Area Data Structure contains information
--      regarding the various areas. The interfaces and
--      virtual links are configured as part of these areas.
--      Area 0.0.0.0, by definition, is the Backbone Area

   fsMIStdOspfv3AreaTable OBJECT-TYPE
        SYNTAX          SEQUENCE OF FsMIStdOspfv3AreaEntry
        MAX-ACCESS      not-accessible
        STATUS          current
        DESCRIPTION
            "Information describing the configured  parame-
            ters  and cumulative statistics of the router's
            attached areas."
        REFERENCE
            "OSPF Version 2, Section 6 The Area Data Struc-
            ture"
        ::= { fsMIStdOspfv3Objects 2 }

   fsMIStdOspfv3AreaEntry OBJECT-TYPE
        SYNTAX          FsMIStdOspfv3AreaEntry
        MAX-ACCESS      not-accessible
        STATUS          current
        DESCRIPTION
            "Information describing the configured parame-
            ters and cumulative statistics of one of the
            router's attached areas."
        INDEX { fsMIStdOspfv3ContextId, fsMIStdOspfv3AreaId }
        ::= { fsMIStdOspfv3AreaTable 1 }

FsMIStdOspfv3AreaEntry ::= SEQUENCE {
        fsMIStdOspfv3AreaId
                AreaID,
        fsMIStdOspfv3ImportAsExtern
                INTEGER,
        fsMIStdOspfv3AreaSpfRuns
                Counter32,
        fsMIStdOspfv3AreaBdrRtrCount
                Gauge32,
        fsMIStdOspfv3AreaAsBdrRtrCount
                Gauge32,
        fsMIStdOspfv3AreaScopeLsaCount
                Gauge32,
        fsMIStdOspfv3AreaScopeLsaCksumSum
                Integer32,
        fsMIStdOspfv3AreaSummary
                INTEGER,
        fsMIStdOspfv3StubMetric
                BigMetric,
        fsMIStdOspfv3AreaNssaTranslatorRole
                INTEGER,
        fsMIStdOspfv3AreaNssaTranslatorState
                INTEGER,
        fsMIStdOspfv3AreaNssaTranslatorStabilityInterval
                Unsigned32,
        fsMIStdOspfv3AreaNssaTranslatorEvents
                Counter32,
        fsMIStdOspfv3AreaStubMetricType
                INTEGER,
        fsMIStdOspfv3AreaStatus
                RowStatus
        }

    fsMIStdOspfv3AreaId OBJECT-TYPE
        SYNTAX          AreaID
        MAX-ACCESS      not-accessible
        STATUS          current
        DESCRIPTION
            "A 32-bit integer uniquely identifying an area.
            Area ID 0.0.0.0 is used for the OSPFv3 backbone."
        REFERENCE
            "OSPF Version 2, Appendix C.2 Area parameters"
      ::= { fsMIStdOspfv3AreaEntry 1 }

    fsMIStdOspfv3ImportAsExtern OBJECT-TYPE
        SYNTAX          INTEGER {
                        importExternal(1),   -- normal area
                        importNoExternal(2), -- stub area
                        importNssa(3)        -- not-so-stubby-area
                        }
        MAX-ACCESS      read-create
        STATUS          current
        DESCRIPTION
            "Indicates whether an area is a Stub area, NSSA, or
            standard area. AS-scope LSAs are not imported into Stub
            Areas or NSSAs. NSSAs import AS-External data as Type-7
            LSAs which have Area-scope"
        REFERENCE
            "OSPF Version 2, Appendix C.2 Area parameters"
        DEFVAL { importExternal }
      ::= { fsMIStdOspfv3AreaEntry 2 }

    fsMIStdOspfv3AreaSpfRuns OBJECT-TYPE
        SYNTAX          Counter32
        MAX-ACCESS      read-only
        STATUS          current
        DESCRIPTION
            "The number of times that the intra-area  route
            table  has  been  calculated  using this area's
            link-state database.  This  is  typically  done
            using Dijkstra's algorithm."
      ::= { fsMIStdOspfv3AreaEntry 3 }

    fsMIStdOspfv3AreaBdrRtrCount OBJECT-TYPE
        SYNTAX          Gauge32
        MAX-ACCESS      read-only
        STATUS          current
        DESCRIPTION
            "The total number of area border routers reach-
            able within this area.  This is initially zero,
            and is calculated in each SPF Pass."
      ::= { fsMIStdOspfv3AreaEntry 4 }

    fsMIStdOspfv3AreaAsBdrRtrCount OBJECT-TYPE
        SYNTAX          Gauge32
        MAX-ACCESS      read-only
        STATUS          current
        DESCRIPTION
            "The total number of Autonomous  System  border
            routers  reachable  within  this area.  This is
            initially zero, and is calculated in  each  SPF
            Pass."
      ::= { fsMIStdOspfv3AreaEntry 5 }

    fsMIStdOspfv3AreaScopeLsaCount OBJECT-TYPE
        SYNTAX          Gauge32
        MAX-ACCESS      read-only
        STATUS          current
        DESCRIPTION
            "The total number of Area-Scope link-state
            advertisements in  this  area's link-state
            database."
      ::= { fsMIStdOspfv3AreaEntry 6 }

    fsMIStdOspfv3AreaScopeLsaCksumSum OBJECT-TYPE
        SYNTAX          Integer32
        MAX-ACCESS      read-only
        STATUS          current
        DESCRIPTION
            "The 32-bit unsigned sum of the Area-Scope link-state
            advertisements'  LS  checksums  contained in this
            area's link-state database.  The sum can be used
            to determine if  there  has been  a  change  in a
            router's link state database, and to compare the
            link-state database of two routers."
      ::= { fsMIStdOspfv3AreaEntry 7 }

    fsMIStdOspfv3AreaSummary OBJECT-TYPE
        SYNTAX          INTEGER {
                        noAreaSummary(1),
                        sendAreaSummary(2)
                        }
        MAX-ACCESS      read-create
        STATUS          current
        DESCRIPTION
            "The variable ospfv3AreaSummary controls the  im-
            port  of  Inter-Area LSAs into stub areas.  It has
            no effect on other areas.

            If it is noAreaSummary, the router will neither
            originate  nor  propagate Inter-Area LSAs into the
            stub area.  It will rely entirely  on  its  de-
            fault route.

            If it is sendAreaSummary, the router will  both
            summarize and propagate Inter-Area LSAs."
        DEFVAL   { sendAreaSummary }
      ::= { fsMIStdOspfv3AreaEntry 8 }

    fsMIStdOspfv3StubMetric OBJECT-TYPE
        SYNTAX          BigMetric
        MAX-ACCESS      read-create
        STATUS          current
        DESCRIPTION
            "The metric value advertised for the default route
             into Stub and NSSA areas."
      ::= { fsMIStdOspfv3AreaEntry 9 }

    fsMIStdOspfv3AreaNssaTranslatorRole OBJECT-TYPE
        SYNTAX          INTEGER { always(1), candidate(2) }
        MAX-ACCESS      read-create
        STATUS          current
        DESCRIPTION
            "Indicates an NSSA Border router's ability to
            perform NSSA translation of type-7 LSAs into
            type-5 LSAs."
        DEFVAL { candidate }
      ::= { fsMIStdOspfv3AreaEntry 10 }

   fsMIStdOspfv3AreaNssaTranslatorState OBJECT-TYPE
        SYNTAX          INTEGER {
                        enabled(1),
                        elected(2),
                        disabled(3)
                        }
        MAX-ACCESS      read-only
        STATUS          current
        DESCRIPTION
            "Indicates if and how an NSSA Border router is
             performing NSSA translation of type-7 LSAs into type-5
             LSAs. When this object is set to enabled, the NSSA
             Border router's ospfv3AreaNssTranslatorRole
             has been set to always. When this object is set to
             elected, a candidate NSSA Border router is translating
             type-7 LSAs into type-5. When this object is set to
             disabled, a candidate NSSA Border router is NOT
             translating type-7 LSAs into type-5."
      ::= { fsMIStdOspfv3AreaEntry 11 }

    fsMIStdOspfv3AreaNssaTranslatorStabilityInterval OBJECT-TYPE
        SYNTAX          Unsigned32
        UNITS           "seconds"
        MAX-ACCESS      read-create
        STATUS          current
        DESCRIPTION
            "The number of seconds after an elected translator
            determines its services are no longer required, that
            it should continue to perform its translation duties."
        DEFVAL { 40 }
      ::= { fsMIStdOspfv3AreaEntry 12 }

    fsMIStdOspfv3AreaNssaTranslatorEvents OBJECT-TYPE
        SYNTAX          Counter32
        MAX-ACCESS      read-only
        STATUS          current
        DESCRIPTION
            "Indicates the number of Translator State changes
            that have occurred since the last boot-up."
      ::= { fsMIStdOspfv3AreaEntry 13 }

    fsMIStdOspfv3AreaStubMetricType OBJECT-TYPE
        SYNTAX       INTEGER {
                        ospfMetric (1),  -- OSPF Metric
                        comparableCost (2), -- external type 1
                        nonComparable  (3) -- external type 2
                        }
        MAX-ACCESS   read-create
        STATUS       current
        DESCRIPTION
           "This variable displays the type of metric ad-
           vertised as a default route."
        DEFVAL { ospfMetric }
      ::= { fsMIStdOspfv3AreaEntry 14 }

    fsMIStdOspfv3AreaStatus OBJECT-TYPE
        SYNTAX          RowStatus
        MAX-ACCESS      read-create
        STATUS          current
        DESCRIPTION
            "This variable controls the status of  the  en-
            try. The use of RowStatus is covered in more detail
            in [6]."
      ::= { fsMIStdOspfv3AreaEntry 15 }

--    OSPFv3 AS-Scope Link State Database

--    The Link State Database contains the AS-Scope Link State
--    Advertisements from throughout the areas that the
--    device is attached to.

    fsMIStdOspfv3AsLsdbTable OBJECT-TYPE
        SYNTAX          SEQUENCE OF FsMIStdOspfv3AsLsdbEntry
        MAX-ACCESS      not-accessible
        STATUS          current
        DESCRIPTION
            "The OSPFv3 Process's AS-Scope Link State Database."
        ::= { fsMIStdOspfv3Objects 3 }

    fsMIStdOspfv3AsLsdbEntry OBJECT-TYPE
        SYNTAX          FsMIStdOspfv3AsLsdbEntry
        MAX-ACCESS      not-accessible
        STATUS          current
        DESCRIPTION
            "A single AS-Scope Link State Advertisement."
        INDEX { fsMIStdOspfv3ContextId,
	        fsMIStdOspfv3AsLsdbType,
                fsMIStdOspfv3AsLsdbRouterId,
                fsMIStdOspfv3AsLsdbLsid }
      ::= { fsMIStdOspfv3AsLsdbTable 1 }

FsMIStdOspfv3AsLsdbEntry ::= SEQUENCE {
        fsMIStdOspfv3AsLsdbType
                Unsigned32,
        fsMIStdOspfv3AsLsdbRouterId
                RouterID,
        fsMIStdOspfv3AsLsdbLsid
                IpAddress,
        fsMIStdOspfv3AsLsdbSequence
                Integer32,
        fsMIStdOspfv3AsLsdbAge
                Integer32,
        fsMIStdOspfv3AsLsdbChecksum
                Integer32,
        fsMIStdOspfv3AsLsdbAdvertisement
                OCTET STRING,
        fsMIStdOspfv3AsLsdbTypeKnown
                TruthValue
        }

    fsMIStdOspfv3AsLsdbType OBJECT-TYPE
        SYNTAX          Unsigned32(0..'FFFFFFFF'h)
        MAX-ACCESS      not-accessible
        STATUS          current
        DESCRIPTION
            "The type of the link state advertisement.
            Each link state type has a separate advertise-
            ment format. AS-Scope LSAs not recognized by
            the router may be stored in the database."
      ::= { fsMIStdOspfv3AsLsdbEntry 1 }

    fsMIStdOspfv3AsLsdbRouterId OBJECT-TYPE
        SYNTAX          RouterID
        MAX-ACCESS      not-accessible
        STATUS          current
        DESCRIPTION
            "The 32 bit number that uniquely identifies the
            originating router in the Autonomous System."
        REFERENCE
            "OSPF Version 2, Appendix C.1 Global parameters"
      ::= { fsMIStdOspfv3AsLsdbEntry 2 }

    fsMIStdOspfv3AsLsdbLsid OBJECT-TYPE
        SYNTAX          IpAddress
        MAX-ACCESS      not-accessible
        STATUS          current
        DESCRIPTION
            "The Link State ID is an LS Type Specific field
            containing a unique identifier;
            it identifies the piece of the  routing  domain
            that is being described by the advertisement.
            In contrast to OSPFv2, the LSID has no
            addressing semantics."
      ::= { fsMIStdOspfv3AsLsdbEntry 3 }

-- Note that the OSPF Sequence Number is a 32 bit signed
-- integer.  It starts with the value '80000001'h,
-- or -'7FFFFFFF'h, and increments until '7FFFFFFF'h
-- Thus, a typical sequence number will be very negative.

    fsMIStdOspfv3AsLsdbSequence OBJECT-TYPE
        SYNTAX          Integer32
        MAX-ACCESS      read-only
        STATUS          current
        DESCRIPTION
            "The sequence number field is a  signed  32-bit
            integer.   It  is used to detect old and dupli-
            cate link state advertisements.  The  space  of
            sequence  numbers  is  linearly  ordered.   The
            larger the sequence number the more recent  the
            advertisement."
        REFERENCE
            "OSPF Version  2,  Section  12.1.6  LS  sequence
            number"
      ::= { fsMIStdOspfv3AsLsdbEntry 4 }

    fsMIStdOspfv3AsLsdbAge OBJECT-TYPE
        SYNTAX          Integer32 -- Should be 0..MaxAge
                                  -- unless DoNotAge bit is set
        UNITS           "seconds"
        MAX-ACCESS      read-only
        STATUS          current
        DESCRIPTION
            "This field is the age of the link state adver-
            tisement in seconds."
        REFERENCE
            "OSPF Version 2, Section 12.1.1 LS age"
      ::= { fsMIStdOspfv3AsLsdbEntry 5 }

    fsMIStdOspfv3AsLsdbChecksum OBJECT-TYPE
        SYNTAX          Integer32
        MAX-ACCESS      read-only
        STATUS          current
        DESCRIPTION
            "This field is the  checksum  of  the  complete
            contents  of  the  advertisement, excepting the
            age field.  The age field is excepted  so  that
            an   advertisement's  age  can  be  incremented
            without updating the  checksum.   The  checksum
            used  is  the same that is used for ISO connec-
            tionless datagrams; it is commonly referred  to
            as the Fletcher checksum."
        REFERENCE
            "OSPF Version 2, Section 12.1.7 LS checksum"
      ::= { fsMIStdOspfv3AsLsdbEntry 6 }

    fsMIStdOspfv3AsLsdbAdvertisement OBJECT-TYPE
        SYNTAX          OCTET STRING (SIZE (1..65535))
        MAX-ACCESS      read-only
        STATUS          current
        DESCRIPTION
            "The entire Link State Advertisement, including
            its header."
      ::= { fsMIStdOspfv3AsLsdbEntry 7 }

    fsMIStdOspfv3AsLsdbTypeKnown OBJECT-TYPE
        SYNTAX          TruthValue
        MAX-ACCESS      read-only
        STATUS          current
        DESCRIPTION
            "Is the LSA type recognized by this Router?"
      ::= { fsMIStdOspfv3AsLsdbEntry 8 }


-- OSPFv3 Area-Scope Link State Database

-- The Link State Database contains the Area-Scope Link State
-- Advertisements from throughout the area that the
-- device is attached to.

    fsMIStdOspfv3AreaLsdbTable OBJECT-TYPE
        SYNTAX          SEQUENCE OF FsMIStdOspfv3AreaLsdbEntry
        MAX-ACCESS      not-accessible
        STATUS          current
        DESCRIPTION
            "The OSPFv3 Process's Area-Scope Link State Database."
      ::= { fsMIStdOspfv3Objects 4 }

    fsMIStdOspfv3AreaLsdbEntry OBJECT-TYPE
        SYNTAX          FsMIStdOspfv3AreaLsdbEntry
        MAX-ACCESS      not-accessible
        STATUS          current
        DESCRIPTION
            "A single Area-Scope Link State Advertisement."
        INDEX { fsMIStdOspfv3ContextId,
	        fsMIStdOspfv3AreaLsdbAreaId,
                fsMIStdOspfv3AreaLsdbType,
                fsMIStdOspfv3AreaLsdbRouterId,
                fsMIStdOspfv3AreaLsdbLsid }
      ::= { fsMIStdOspfv3AreaLsdbTable 1 }

FsMIStdOspfv3AreaLsdbEntry ::= SEQUENCE {
        fsMIStdOspfv3AreaLsdbAreaId
                AreaID,
        fsMIStdOspfv3AreaLsdbType
                Unsigned32,
        fsMIStdOspfv3AreaLsdbRouterId
                RouterID,
        fsMIStdOspfv3AreaLsdbLsid
                IpAddress,
        fsMIStdOspfv3AreaLsdbSequence
                Integer32,
        fsMIStdOspfv3AreaLsdbAge
                Integer32,
        fsMIStdOspfv3AreaLsdbChecksum
                Integer32,
        fsMIStdOspfv3AreaLsdbAdvertisement
                OCTET STRING,
        fsMIStdOspfv3AreaLsdbTypeKnown
                TruthValue
        }

    fsMIStdOspfv3AreaLsdbAreaId OBJECT-TYPE
        SYNTAX          AreaID
        MAX-ACCESS      not-accessible
        STATUS          current
        DESCRIPTION
            "The 32 bit identifier of the Area from which the
            LSA was received."
        REFERENCE
            "OSPF Version 2, Appendix C.2 Area parameters"
      ::= { fsMIStdOspfv3AreaLsdbEntry 1 }

    fsMIStdOspfv3AreaLsdbType OBJECT-TYPE
        SYNTAX          Unsigned32(0..'FFFFFFFF'h)
        MAX-ACCESS      not-accessible
        STATUS          current
        DESCRIPTION
            "The type  of  the  link  state  advertisement.
            Each  link state type has a separate advertise-
            ment format. Area-Scope LSAs unrecognized by the
            router are also stored in this database."
      ::= { fsMIStdOspfv3AreaLsdbEntry 2 }

    fsMIStdOspfv3AreaLsdbRouterId OBJECT-TYPE
        SYNTAX          RouterID
        MAX-ACCESS      not-accessible
        STATUS          current
        DESCRIPTION
            "The 32 bit number that uniquely identifies the
            originating router in the Autonomous System."
        REFERENCE
            "OSPF Version 2, Appendix C.1 Global parameters"
      ::= { fsMIStdOspfv3AreaLsdbEntry 3 }

    fsMIStdOspfv3AreaLsdbLsid OBJECT-TYPE
        SYNTAX          IpAddress
        MAX-ACCESS      not-accessible
        STATUS          current
        DESCRIPTION
            "The Link State ID is an LS Type Specific field
            containing a unique identifier;
            it identifies the piece of the  routing  domain
            that is being described by the advertisement.
            In contrast to OSPFv2, the LSID has no
            addressing semantics."
      ::= { fsMIStdOspfv3AreaLsdbEntry 4 }

--      Note that the OSPF Sequence Number is a 32 bit signed
--      integer.  It starts with the value '80000001'h,
--      or -'7FFFFFFF'h, and increments until '7FFFFFFF'h
--      Thus, a typical sequence number will be very negative.

    fsMIStdOspfv3AreaLsdbSequence OBJECT-TYPE
        SYNTAX          Integer32
        MAX-ACCESS      read-only
        STATUS          current
        DESCRIPTION
            "The sequence number field is a  signed  32-bit
            integer.   It  is used to detect old and dupli-
            cate link state advertisements.  The  space  of
            sequence  numbers  is  linearly  ordered.   The
            larger the sequence number the more recent  the
            advertisement."
        REFERENCE
            "OSPF Version  2,  Section  12.1.6  LS  sequence
            number"
      ::= { fsMIStdOspfv3AreaLsdbEntry 5 }

    fsMIStdOspfv3AreaLsdbAge OBJECT-TYPE
        SYNTAX          Integer32 -- Should be 0..MaxAge
                                  -- unless DoNotAge bit is set
        UNITS           "seconds"
        MAX-ACCESS      read-only
        STATUS          current
        DESCRIPTION
            "This field is the age of the link state adver-
            tisement in seconds."
        REFERENCE
            "OSPF Version 2, Section 12.1.1 LS age"
      ::= { fsMIStdOspfv3AreaLsdbEntry 6 }

    fsMIStdOspfv3AreaLsdbChecksum OBJECT-TYPE
        SYNTAX          Integer32
        MAX-ACCESS      read-only
        STATUS          current
        DESCRIPTION
            "This field is the  checksum  of  the  complete
            contents  of  the  advertisement, excepting the
            age field.  The age field is excepted  so  that
            an   advertisement's  age  can  be  incremented
            without updating the  checksum.   The  checksum
            used  is  the same that is used for ISO connec-
            tionless datagrams; it is commonly referred  to
            as the Fletcher checksum."
        REFERENCE
            "OSPF Version 2, Section 12.1.7 LS checksum"
      ::= { fsMIStdOspfv3AreaLsdbEntry 7 }

    fsMIStdOspfv3AreaLsdbAdvertisement OBJECT-TYPE
        SYNTAX          OCTET STRING (SIZE (1..65535))
        MAX-ACCESS      read-only
        STATUS          current
        DESCRIPTION
            "The entire Link State Advertisement, including
            its header."
      ::= { fsMIStdOspfv3AreaLsdbEntry 8 }

    fsMIStdOspfv3AreaLsdbTypeKnown OBJECT-TYPE
        SYNTAX          TruthValue
        MAX-ACCESS      read-only
        STATUS          current
        DESCRIPTION
            "Is the LSA type recognized by this Router?"
      ::= { fsMIStdOspfv3AreaLsdbEntry 9 }

--      OSPFv3 Link-Scope Link State Database

--      The Link State Database contains the Link-Scope Link State
--      Advertisements from the links that the
--      device is attached to.

    fsMIStdOspfv3LinkLsdbTable OBJECT-TYPE
        SYNTAX          SEQUENCE OF FsMIStdOspfv3LinkLsdbEntry
        MAX-ACCESS      not-accessible
        STATUS          current
        DESCRIPTION
            "The OSPFv3 Process's Link-Scope Link State Database."
      ::= { fsMIStdOspfv3Objects 5 }

    fsMIStdOspfv3LinkLsdbEntry OBJECT-TYPE
        SYNTAX          FsMIStdOspfv3LinkLsdbEntry
        MAX-ACCESS      not-accessible
        STATUS          current
        DESCRIPTION
            "A single Link-Scope Link State Advertisement."
        INDEX { fsMIStdOspfv3LinkLsdbIfIndex,
                fsMIStdOspfv3LinkLsdbType,
                fsMIStdOspfv3LinkLsdbRouterId,
                fsMIStdOspfv3LinkLsdbLsid }
      ::= { fsMIStdOspfv3LinkLsdbTable 1 }

FsMIStdOspfv3LinkLsdbEntry ::= SEQUENCE {
        fsMIStdOspfv3LinkLsdbIfIndex
                InterfaceIndex,
        fsMIStdOspfv3LinkLsdbType
                Unsigned32,
        fsMIStdOspfv3LinkLsdbRouterId
                RouterID,
        fsMIStdOspfv3LinkLsdbLsid
                IpAddress,
        fsMIStdOspfv3LinkLsdbSequence
                Integer32,
        fsMIStdOspfv3LinkLsdbAge
                Integer32,
        fsMIStdOspfv3LinkLsdbChecksum
                Integer32,
        fsMIStdOspfv3LinkLsdbAdvertisement
                OCTET STRING,
        fsMIStdOspfv3LinkLsdbTypeKnown
                TruthValue,
        fsMIStdOspfv3LinkLsdbContextId
	            Integer32
        }

    fsMIStdOspfv3LinkLsdbIfIndex OBJECT-TYPE
        SYNTAX         InterfaceIndex
        MAX-ACCESS     not-accessible
        STATUS         current
        DESCRIPTION
            "The identifier of the link from which the LSA
            was received."
        REFERENCE
            "OSPF Version 2, Appendix C.2 Area parameters"
      ::= { fsMIStdOspfv3LinkLsdbEntry 1 }

    fsMIStdOspfv3LinkLsdbType OBJECT-TYPE
        SYNTAX          Unsigned32(0..'FFFFFFFF'h)
        MAX-ACCESS      not-accessible
        STATUS          current
        DESCRIPTION
            "The type of the link state advertisement.
            Each link state type has a separate advertise-
            ment format. Link-Scope LSAs unrecognized by the
            router are also stored in this database."
      ::= { fsMIStdOspfv3LinkLsdbEntry 2 }

    fsMIStdOspfv3LinkLsdbRouterId OBJECT-TYPE
        SYNTAX          RouterID
        MAX-ACCESS      not-accessible
        STATUS          current
        DESCRIPTION
            "The 32 bit number that uniquely identifies the
            originating router in the Autonomous System."
        REFERENCE
            "OSPF Version 2, Appendix C.1 Global parameters"
      ::= { fsMIStdOspfv3LinkLsdbEntry 3 }

    fsMIStdOspfv3LinkLsdbLsid OBJECT-TYPE
        SYNTAX        IpAddress
        MAX-ACCESS    not-accessible
        STATUS        current
        DESCRIPTION
            "The Link State ID is an LS Type Specific field
            containing a unique identifier;
            it identifies the piece of the  routing  domain
            that is being described by the advertisement.
            In contrast to OSPFv2, the LSID has no
            addressing semantics."
      ::= { fsMIStdOspfv3LinkLsdbEntry 4 }

--      Note that the OSPF Sequence Number is a 32 bit signed
--      integer.  It starts with the value '80000001'h,
--      or -'7FFFFFFF'h, and increments until '7FFFFFFF'h
--      Thus, a typical sequence number will be very negative.

    fsMIStdOspfv3LinkLsdbSequence OBJECT-TYPE
        SYNTAX          Integer32
        MAX-ACCESS      read-only
        STATUS          current
        DESCRIPTION
            "The sequence number field is a  signed  32-bit
            integer.   It  is used to detect old and dupli-
            cate link state advertisements.  The  space  of
            sequence  numbers  is  linearly  ordered.   The
            larger the sequence number the more recent  the
            advertisement."
        REFERENCE
            "OSPF Version  2,  Section  12.1.6  LS  sequence
            number"
      ::= { fsMIStdOspfv3LinkLsdbEntry 5 }

    fsMIStdOspfv3LinkLsdbAge OBJECT-TYPE
        SYNTAX          Integer32 -- Should be 0..MaxAge
                                  -- unless DoNotAge bit is set
        UNITS           "seconds"
        MAX-ACCESS      read-only
        STATUS          current
        DESCRIPTION
            "This field is the age of the link state
            advertisement in seconds."
        REFERENCE
            "OSPF Version 2, Section 12.1.1 LS age"
      ::= { fsMIStdOspfv3LinkLsdbEntry 6 }

    fsMIStdOspfv3LinkLsdbChecksum OBJECT-TYPE
        SYNTAX          Integer32
        MAX-ACCESS      read-only
        STATUS          current
        DESCRIPTION
            "This field is the  checksum  of  the  complete
            contents  of  the  advertisement, excepting the
            age field.  The age field is excepted  so  that
            an   advertisement's  age  can  be  incremented
            without updating the  checksum.   The  checksum
            used  is  the same that is used for ISO connec-
            tionless datagrams; it is commonly referred  to
            as the Fletcher checksum."
        REFERENCE
            "OSPF Version 2, Section 12.1.7 LS checksum"
      ::= { fsMIStdOspfv3LinkLsdbEntry 7 }

    fsMIStdOspfv3LinkLsdbAdvertisement OBJECT-TYPE
        SYNTAX          OCTET STRING (SIZE (1..65535))
        MAX-ACCESS      read-only
        STATUS          current
        DESCRIPTION
            "The entire Link State Advertisement, including
            its header."
      ::= { fsMIStdOspfv3LinkLsdbEntry 8 }

    fsMIStdOspfv3LinkLsdbTypeKnown OBJECT-TYPE
        SYNTAX          TruthValue
        MAX-ACCESS      read-only
        STATUS          current
        DESCRIPTION
            "Indicates whether the LSA type is recognized by this
             Router."
      ::= { fsMIStdOspfv3LinkLsdbEntry 9 }

    fsMIStdOspfv3LinkLsdbContextId OBJECT-TYPE
        SYNTAX          Integer32
	    MAX-ACCESS      read-only
	    STATUS          current
	    DESCRIPTION
	        "A 32-bit unique context id for each entry.
             Minimum value is 0 and Maximum depends upon system
             configuration. Default value is 0 which will be initialized
             during bootup"
      ::= { fsMIStdOspfv3LinkLsdbEntry 10 }

--      OSPF Host Table

--      The Host/Metric Table indicates what hosts are directly
--      attached to the Router, and what metrics and types of
--      service should be advertised for them.

    fsMIStdOspfv3HostTable OBJECT-TYPE
        SYNTAX          SEQUENCE OF FsMIStdOspfv3HostEntry
        MAX-ACCESS      not-accessible
        STATUS          current
        DESCRIPTION
            "The list of Hosts, and their metrics, that the
            router will advertise as host routes."
        REFERENCE
            "OSPF Version 2, Appendix C.6  Host route param-
            eters"
      ::= { fsMIStdOspfv3Objects 6 }

    fsMIStdOspfv3HostEntry OBJECT-TYPE
        SYNTAX          FsMIStdOspfv3HostEntry
        MAX-ACCESS      not-accessible
        STATUS          current
        DESCRIPTION
            "A metric to be advertised when a given host is
            reachable."
        INDEX { fsMIStdOspfv3ContextId,
	        fsMIStdOspfv3HostAddressType,
                fsMIStdOspfv3HostAddress }
      ::= { fsMIStdOspfv3HostTable 1 }

FsMIStdOspfv3HostEntry ::= SEQUENCE {
        fsMIStdOspfv3HostAddressType
                InetAddressType,
        fsMIStdOspfv3HostAddress
                InetAddress,
        fsMIStdOspfv3HostMetric
                Metric,
        fsMIStdOspfv3HostAreaID
                AreaID,
        fsMIStdOspfv3HostStatus
                RowStatus
        }

    fsMIStdOspfv3HostAddressType OBJECT-TYPE
        SYNTAX          InetAddressType
        MAX-ACCESS      not-accessible
        STATUS          current
        DESCRIPTION
            "The address type of fsMIStdOspfv3HostAddress. Only IPv6
            addresses without zone index are expected."
        REFERENCE
            "OSPF Version 2, Appendix C.6 Host route parame-
            ters"
      ::= { fsMIStdOspfv3HostEntry 1 }


    fsMIStdOspfv3HostAddress OBJECT-TYPE
        SYNTAX          InetAddress (SIZE (16))
        MAX-ACCESS      not-accessible
        STATUS          current
        DESCRIPTION
            "The IPv6 Address of the Host. Must be a Global
             or Site-local address."
        REFERENCE
            "OSPF Version 2, Appendix C.6 Host route parame-
            ters"
      ::= { fsMIStdOspfv3HostEntry 2 }

    fsMIStdOspfv3HostMetric OBJECT-TYPE
        SYNTAX          Metric
        MAX-ACCESS      read-create
        STATUS          current
        DESCRIPTION
            "The Metric to be advertised."
        REFERENCE
            "OSPF Version 2, Appendix C.6 Host route parame-
            ters"
      ::= { fsMIStdOspfv3HostEntry 3 }

    fsMIStdOspfv3HostAreaID OBJECT-TYPE
        SYNTAX          AreaID
        MAX-ACCESS      read-create
        STATUS          current
        DESCRIPTION
            "The Area the Host Entry is to be found within.
            By  default, the area that a subsuming OSPFv3 in-
            terface is in, or 0.0.0.0"
        REFERENCE
            "OSPF Version 2, Appendix C.2 Area parameters"
      ::= { fsMIStdOspfv3HostEntry 4 }

    fsMIStdOspfv3HostStatus OBJECT-TYPE
        SYNTAX          RowStatus
        MAX-ACCESS      read-create
        STATUS          current
        DESCRIPTION
            "This variable controls the status of  the  en-
            try. The use of RowStatus is covered in more detail
            in [6]."
      ::= { fsMIStdOspfv3HostEntry 5 }

--      OSPFv3 Interface Table

    fsMIStdOspfv3IfTable OBJECT-TYPE
        SYNTAX          SEQUENCE OF FsMIStdOspfv3IfEntry
        MAX-ACCESS      not-accessible
        STATUS          current
        DESCRIPTION
            "The OSPFv3 Interface Table describes the  inter-
            faces from the viewpoint of OSPFv3."
        REFERENCE
            "OSPF Version 2, Appendix C.3  Router  interface
            parameters"
      ::= { fsMIStdOspfv3Objects 7 }

    fsMIStdOspfv3IfEntry OBJECT-TYPE
        SYNTAX          FsMIStdOspfv3IfEntry
        MAX-ACCESS      not-accessible
        STATUS          current
        DESCRIPTION
            "The OSPFv3 Interface Entry describes one  inter-
            face from the viewpoint of OSPFv3."
        INDEX {fsMIStdOspfv3IfIndex }
      ::= { fsMIStdOspfv3IfTable 1 }

FsMIStdOspfv3IfEntry ::= SEQUENCE {
        fsMIStdOspfv3IfIndex
                InterfaceIndex,
        fsMIStdOspfv3IfAreaId
                AreaID,
        fsMIStdOspfv3IfType
                INTEGER,
        fsMIStdOspfv3IfAdminStat
                Status,
        fsMIStdOspfv3IfRtrPriority
                DesignatedRouterPriority,
        fsMIStdOspfv3IfTransitDelay
                UpToRefreshInterval,
        fsMIStdOspfv3IfRetransInterval
                UpToRefreshInterval,
        fsMIStdOspfv3IfHelloInterval
                HelloRange,
        fsMIStdOspfv3IfRtrDeadInterval
                 RouterDeadRange,
        fsMIStdOspfv3IfPollInterval
                Unsigned32,
        fsMIStdOspfv3IfState
                INTEGER,
        fsMIStdOspfv3IfDesignatedRouter
                RouterID,
        fsMIStdOspfv3IfBackupDesignatedRouter
                RouterID,
        fsMIStdOspfv3IfEvents
                Counter32,
        fsMIStdOspfv3IfMulticastForwarding
                INTEGER,
        fsMIStdOspfv3IfDemand
                TruthValue,
        fsMIStdOspfv3IfMetricValue
                Metric,
        fsMIStdOspfv3IfLinkScopeLsaCount
                Gauge32,
        fsMIStdOspfv3IfLinkLsaCksumSum
                Integer32,
        fsMIStdOspfv3IfInstId
                Integer32,
        fsMIStdOspfv3IfDemandNbrProbe
                TruthValue,
        fsMIStdOspfv3IfDemandNbrProbeRetxLimit
                Unsigned32,
        fsMIStdOspfv3IfDemandNbrProbeInterval
                Unsigned32,
        fsMIStdOspfv3IfContextId
                Integer32,
        fsMIStdOspfv3IfStatus
                RowStatus
        }

    fsMIStdOspfv3IfIndex OBJECT-TYPE
        SYNTAX          InterfaceIndex
        MAX-ACCESS      not-accessible
        STATUS          current
        DESCRIPTION
            "The interface index of this OSPFv3 interface.
             It corresponds to the interface index of the
             IPv6 interface on which OSPFv3 is configured."
      ::= { fsMIStdOspfv3IfEntry 1 }

    fsMIStdOspfv3IfAreaId OBJECT-TYPE
        SYNTAX          AreaID
        MAX-ACCESS      read-create
        STATUS          current
        DESCRIPTION
            "A 32-bit integer uniquely identifying the area
            to  which  the  interface  connects.   Area  ID
            0.0.0.0 is used for the OSPFv3 backbone."
        DEFVAL          { '00000000'H } -- 0.0.0.0
      ::= { fsMIStdOspfv3IfEntry 2 }

    fsMIStdOspfv3IfType OBJECT-TYPE
        SYNTAX          INTEGER {
                        broadcast(1),
                        nbma(2),
                        pointToPoint(3),
                        pointToMultipoint(5)
                        }
        MAX-ACCESS      read-create
        STATUS          current
        DESCRIPTION
            "The OSPFv3 interface type."
      ::= { fsMIStdOspfv3IfEntry 3 }

    fsMIStdOspfv3IfAdminStat OBJECT-TYPE
        SYNTAX          Status
        MAX-ACCESS      read-create
        STATUS          current
        DESCRIPTION
            "The OSPFv3 interface's  administrative  status.
            The  value formed on the interface, and the in-
            terface will be advertised as an internal route
            to  some  area.   The  value 'disabled' denotes
            that the interface is external to OSPFv3."
        DEFVAL          { enabled }
      ::= { fsMIStdOspfv3IfEntry 4 }

    fsMIStdOspfv3IfRtrPriority OBJECT-TYPE
        SYNTAX          DesignatedRouterPriority
        MAX-ACCESS      read-create
        STATUS          current
        DESCRIPTION
            "The  priority  of  this  interface.   Used  in
            multi-access  networks,  this  field is used in
            the designated router election algorithm.   The
            value 0 signifies that the router is not eligi-
            ble to become the  designated  router  on  this
            particular  network.   In the event of a tie in
            this value, routers will use their Router ID as
            a tie breaker."
        DEFVAL          { 1 }
      ::= { fsMIStdOspfv3IfEntry 5 }

    fsMIStdOspfv3IfTransitDelay OBJECT-TYPE
        SYNTAX          UpToRefreshInterval
        UNITS           "seconds"
        MAX-ACCESS      read-create
        STATUS          current
        DESCRIPTION
            "The estimated number of seconds  it  takes  to
            transmit  a  link state update packet over this
            interface."
        DEFVAL          { 1 }
      ::= { fsMIStdOspfv3IfEntry 6 }

    fsMIStdOspfv3IfRetransInterval OBJECT-TYPE
        SYNTAX          UpToRefreshInterval
        UNITS           "seconds"
        MAX-ACCESS      read-create
        STATUS          current
        DESCRIPTION
            "The number of seconds between  link-state  ad-
            vertisement  retransmissions,  for  adjacencies
            belonging to this  interface.   This  value  is
            also used when retransmitting database descrip-
            tion and link-state request packets."
        DEFVAL          { 5 }
      ::= { fsMIStdOspfv3IfEntry 7 }

    fsMIStdOspfv3IfHelloInterval OBJECT-TYPE
        SYNTAX          HelloRange
        UNITS           "seconds"
        MAX-ACCESS      read-create
        STATUS          current
        DESCRIPTION
            "The length of time, in  seconds,  between  the
            Hello  packets that the router sends on the in-
            terface.  This value must be the same  for  all
            routers attached to a common network."
        DEFVAL          { 10 }
      ::= { fsMIStdOspfv3IfEntry 8 }

    fsMIStdOspfv3IfRtrDeadInterval OBJECT-TYPE
        SYNTAX          RouterDeadRange
        UNITS           "seconds"
        MAX-ACCESS      read-create
        STATUS          current
        DESCRIPTION
            "The number of seconds that  a  router's  Hello
            packets  have  not been seen before it's neigh-
            bors declare the router down.  This  should  be
            some  multiple  of  the  Hello  interval.  This
            value must be the same for all routers attached
            to a common network."
        DEFVAL          { 40 }
      ::= { fsMIStdOspfv3IfEntry 9 }

    fsMIStdOspfv3IfPollInterval OBJECT-TYPE
        SYNTAX          Unsigned32
        UNITS           "seconds"
        MAX-ACCESS      read-create
        STATUS          current
        DESCRIPTION
            "The larger time interval, in seconds,  between
            the  Hello  packets  sent  to  an inactive non-
            broadcast multi- access neighbor."
        DEFVAL          { 120 }
      ::= { fsMIStdOspfv3IfEntry 10 }

    fsMIStdOspfv3IfState OBJECT-TYPE
        SYNTAX          INTEGER {
                        down(1),                  -- The interface is Down
                        loopback(2),              -- The interface may be looped back in hardware
                                                  -- or software

                        waiting(3),               -- the router is trying to determine the
                                                  -- identity of the  DR/BDR for the network

                        pointToPoint(4),          -- the interface is operational, and connects
                                                  -- either to a physical point-to-point
                                                  -- network or to a virtual link

                        designatedRouter(5),      -- The router itself is the Designated Router
                                                  -- on the attached network

                        backupDesignatedRouter(6),-- The router itself is the BDR
                                                  -- on the attached network

                        otherDesignatedRouter(7), -- The interface is to a broadcast or NBMA
                                                  -- network on which another router has been
                                                  -- selected to be the Designated Router

                        standbyOnLink(8)          -- the interface is one of multiple interfaces
                                                  -- to a link and this interface is not sending
                                                  -- or receiving control packets. By Default an
                                                  -- interface is  'activeOnLink'.
                        }
        MAX-ACCESS      read-only
        STATUS          current
        DESCRIPTION
            "The OSPFv3 Interface State."
      ::= { fsMIStdOspfv3IfEntry 11 }

    fsMIStdOspfv3IfDesignatedRouter OBJECT-TYPE
        SYNTAX          RouterID
        MAX-ACCESS      read-only
        STATUS          current
        DESCRIPTION
            "The Router ID of the Designated Router."
      ::= { fsMIStdOspfv3IfEntry 12 }

    fsMIStdOspfv3IfBackupDesignatedRouter OBJECT-TYPE
        SYNTAX          RouterID
        MAX-ACCESS      read-only
        STATUS          current
        DESCRIPTION
            "The  Router ID of  the  Backup   Designated
            Router."
      ::= { fsMIStdOspfv3IfEntry 13 }

    fsMIStdOspfv3IfEvents OBJECT-TYPE
        SYNTAX          Counter32
        MAX-ACCESS      read-only
        STATUS          current
        DESCRIPTION
            "The number of times this  OSPF  interface  has
            changed its state, or an error has occurred."
      ::= { fsMIStdOspfv3IfEntry 14 }

    fsMIStdOspfv3IfMulticastForwarding OBJECT-TYPE
        SYNTAX          INTEGER {
                        blocked(1),   -- no multicast forwarding
                        multicast(2), -- using multicast address
                        unicast(3)    -- to each OSPFv3 neighbor
                        }
        MAX-ACCESS      read-create
        STATUS          current
        DESCRIPTION
            "The way multicasts should  forwarded  on  this
            interface;  not  forwarded,  forwarded  as data
            link multicasts, or forwarded as data link uni-
            casts.   Data link multicasting is not meaning-
            ful on point to point and NBMA interfaces,  and
            setting fsMIStdOspfv3MulticastForwarding to 0 effective-
            ly disables all multicast forwarding."
        DEFVAL { blocked }
      ::= { fsMIStdOspfv3IfEntry 15 }

    fsMIStdOspfv3IfDemand OBJECT-TYPE
        SYNTAX          TruthValue
        MAX-ACCESS      read-create
        STATUS          current
        DESCRIPTION
            "Indicates whether Demand OSPFv3 procedures (hel-
            lo suppression to FULL neighbors and setting the
            DoNotAge flag on propagated LSAs) should be per-
            formed on this interface."
        DEFVAL { false }
      ::= { fsMIStdOspfv3IfEntry 16 }

    fsMIStdOspfv3IfMetricValue OBJECT-TYPE
        SYNTAX          Metric
        MAX-ACCESS      read-create
        STATUS          current
        DESCRIPTION
            "The metric assigned to this interface.
             The default value of the Metric is
            Reference Bandwidth / ifSpeed. The value of the
            reference bandwidth is configured by the
            fsMIStdOspfv3ReferenceBandwidth object."
      ::= { fsMIStdOspfv3IfEntry 17 }

    fsMIStdOspfv3IfLinkScopeLsaCount OBJECT-TYPE
        SYNTAX          Gauge32
        MAX-ACCESS      read-only
        STATUS          current
        DESCRIPTION
            "The total number of Link-Scope link-state
            advertisements in  this  link's link-state database."
      ::= { fsMIStdOspfv3IfEntry 18 }

    fsMIStdOspfv3IfLinkLsaCksumSum OBJECT-TYPE
        SYNTAX          Integer32
        MAX-ACCESS      read-only
        STATUS          current
        DESCRIPTION
            "The 32-bit unsigned sum of the Link-Scope link-state
            advertisements'  LS  checksums  contained in this
            link's link-state database.  The sum can be used
            to determine if  there  has been  a  change  in a
            router's link state database, and to compare the
            link-state database of two routers."
      ::= { fsMIStdOspfv3IfEntry 19 }

    fsMIStdOspfv3IfInstId OBJECT-TYPE
        SYNTAX          Integer32
        MAX-ACCESS      read-create
        STATUS          current
        DESCRIPTION
            "Enables multiple instances of OSPFv3 to be run over
            a single link. Each protocol instance would be assigned
            a separate ID. This ID has local link significance
            only."
        DEFVAL          { 0 }
      ::= { fsMIStdOspfv3IfEntry 20 }

    fsMIStdOspfv3IfDemandNbrProbe OBJECT-TYPE
        SYNTAX          TruthValue
        MAX-ACCESS      read-create
        STATUS          current
        DESCRIPTION
               " Indicates whether or not neighbor probing is
                 enabled to determine whether or not the neighbor
                 is inactive. Neighbor probing is disabled by
                 default."
        DEFVAL { false }
      ::= { fsMIStdOspfv3IfEntry 21 }

    fsMIStdOspfv3IfDemandNbrProbeRetxLimit OBJECT-TYPE
        SYNTAX       Unsigned32
        UNITS        "seconds"
        MAX-ACCESS   read-create
        STATUS       current
        DESCRIPTION
           " The number of consecutive LSA retransmissions before
             the neighbor is deemed inactive and the neighbor
             adjacency is brought down."
        DEFVAL          { 10 }
      ::= { fsMIStdOspfv3IfEntry 22 }

    fsMIStdOspfv3IfDemandNbrProbeInterval OBJECT-TYPE
        SYNTAX       Unsigned32
        UNITS        "seconds"
        MAX-ACCESS   read-create
        STATUS       current
        DESCRIPTION
           " Defines how often the neighbor will be probed."
        DEFVAL          { 120 }
      ::= { fsMIStdOspfv3IfEntry 23 }

    fsMIStdOspfv3IfContextId OBJECT-TYPE
        SYNTAX          Integer32
	    MAX-ACCESS      read-only
	    STATUS          current
	    DESCRIPTION
	        "A 32-bit unique context id for each entry.
             Minimum value is 0 and Maximum depends upon system
             configuration. Default value is 0 which will be initialized
             during bootup"
      ::= { fsMIStdOspfv3IfEntry 24 }

    fsMIStdOspfv3IfStatus OBJECT-TYPE
        SYNTAX          RowStatus
        MAX-ACCESS      read-create
        STATUS          current
        DESCRIPTION
            "This variable controls the status of  the  en-
            try. The use of RowStatus is covered in more detail in
            [6]."
      ::= { fsMIStdOspfv3IfEntry 25 }

--      OSPFv3 Virtual Interface Table

--      The Virtual Interface Table describes the virtual
--      links that the OSPFv3 Process is configured to
--      carry on.

    fsMIStdOspfv3VirtIfTable OBJECT-TYPE
        SYNTAX          SEQUENCE OF FsMIStdOspfv3VirtIfEntry
        MAX-ACCESS      not-accessible
        STATUS          current
        DESCRIPTION
            "Information about this router's virtual inter-
            faces."
        REFERENCE
            "OSPF Version  2,  Appendix  C.4   Virtual  link
            parameters"
      ::= { fsMIStdOspfv3Objects 8 }

    fsMIStdOspfv3VirtIfEntry OBJECT-TYPE
        SYNTAX          FsMIStdOspfv3VirtIfEntry
        MAX-ACCESS      not-accessible
        STATUS          current
        DESCRIPTION
            "Information about a single Virtual Interface."
        INDEX { fsMIStdOspfv3ContextId,
	        fsMIStdOspfv3VirtIfAreaId,
                fsMIStdOspfv3VirtIfNeighbor }
      ::= { fsMIStdOspfv3VirtIfTable 1 }

FsMIStdOspfv3VirtIfEntry ::= SEQUENCE {
        fsMIStdOspfv3VirtIfAreaId
                AreaID,
        fsMIStdOspfv3VirtIfNeighbor
                RouterID,
        fsMIStdOspfv3VirtIfIndex
                InterfaceIndex,
        fsMIStdOspfv3VirtIfTransitDelay
                UpToRefreshInterval,
        fsMIStdOspfv3VirtIfRetransInterval
                UpToRefreshInterval,
        fsMIStdOspfv3VirtIfHelloInterval
                HelloRange,
        fsMIStdOspfv3VirtIfRtrDeadInterval
                 RouterDeadRange,
        fsMIStdOspfv3VirtIfState
                INTEGER,
        fsMIStdOspfv3VirtIfEvents
                Counter32,
        fsMIStdOspfv3VirtIfLinkScopeLsaCount
                Gauge32,
        fsMIStdOspfv3VirtIfLinkLsaCksumSum
                Integer32,
        fsMIStdOspfv3VirtIfStatus
                RowStatus
        }

    fsMIStdOspfv3VirtIfAreaId OBJECT-TYPE
        SYNTAX          AreaID
        MAX-ACCESS      not-accessible
        STATUS          current
        DESCRIPTION
            "The  Transit  Area  that  the   Virtual   Link
            traverses.  By definition, this is not 0.0.0.0"
      ::= { fsMIStdOspfv3VirtIfEntry 1 }

    fsMIStdOspfv3VirtIfNeighbor OBJECT-TYPE
        SYNTAX          RouterID
        MAX-ACCESS      not-accessible
        STATUS          current
        DESCRIPTION
            "The Router ID of the Virtual Neighbor."
      ::= { fsMIStdOspfv3VirtIfEntry 2 }

    fsMIStdOspfv3VirtIfIndex OBJECT-TYPE
        SYNTAX          InterfaceIndex
        MAX-ACCESS      read-create
        STATUS          current
        DESCRIPTION
            "The interface ID assigned to this OSPFv3 virtual
            interface. It is advertised in Hello's sent over
            the virtal link and in the router's router-LSAs."
      ::= { fsMIStdOspfv3VirtIfEntry 3 }

    fsMIStdOspfv3VirtIfTransitDelay OBJECT-TYPE
        SYNTAX          UpToRefreshInterval
        UNITS           "seconds"
        MAX-ACCESS      read-create
        STATUS          current
        DESCRIPTION
            "The estimated number of seconds  it  takes  to
            transmit  a link- state update packet over this
            interface."
        DEFVAL          { 1 }
       ::= { fsMIStdOspfv3VirtIfEntry 4 }

    fsMIStdOspfv3VirtIfRetransInterval OBJECT-TYPE
        SYNTAX          UpToRefreshInterval
        UNITS           "seconds"
        MAX-ACCESS      read-create
        STATUS          current
        DESCRIPTION
            "The number of seconds between  link-state  ad-
            vertisement  retransmissions,  for  adjacencies
            belonging to this  interface.   This  value  is
            also used when retransmitting database descrip-
            tion  and  link-state  request  packets.   This
            value  should  be well over the expected round-
            trip time."
        DEFVAL          { 5 }
      ::= { fsMIStdOspfv3VirtIfEntry 5 }

    fsMIStdOspfv3VirtIfHelloInterval OBJECT-TYPE
        SYNTAX          HelloRange
        UNITS           "seconds"
        MAX-ACCESS      read-create
        STATUS          current
        DESCRIPTION
            "The length of time, in  seconds,  between  the
            Hello  packets that the router sends on the in-
            terface.  This value must be the same  for  the
            virtual neighbor."
        DEFVAL          { 10 }
      ::= { fsMIStdOspfv3VirtIfEntry 6 }

    fsMIStdOspfv3VirtIfRtrDeadInterval OBJECT-TYPE
        SYNTAX          RouterDeadRange
        UNITS           "seconds"
        MAX-ACCESS      read-create
        STATUS          current
        DESCRIPTION
            "The number of seconds that  a  router's  Hello
            packets  have  not been seen before it's neigh-
            bors declare the router down.  This  should  be
            some  multiple  of  the  Hello  interval.  This
            value must be the same for the  virtual  neigh-
            bor."
        DEFVAL          { 60 }
      ::= { fsMIStdOspfv3VirtIfEntry 7 }

    fsMIStdOspfv3VirtIfState OBJECT-TYPE
        SYNTAX          INTEGER {
                        down(1), -- these use the same encoding
                        pointToPoint(4) -- as the fsMIStdOspfv3IfTable
                        }
        MAX-ACCESS      read-only
        STATUS          current
        DESCRIPTION
            "OSPF virtual interface states."
      ::= { fsMIStdOspfv3VirtIfEntry 8 }

    fsMIStdOspfv3VirtIfEvents OBJECT-TYPE
        SYNTAX          Counter32
        MAX-ACCESS      read-only
        STATUS          current
        DESCRIPTION
            "The number of state changes or error events on
            this Virtual Link"
      ::= { fsMIStdOspfv3VirtIfEntry 9 }

    fsMIStdOspfv3VirtIfLinkScopeLsaCount OBJECT-TYPE
        SYNTAX          Gauge32
        MAX-ACCESS      read-only
        STATUS          current
        DESCRIPTION
            "The total number of Link-Scope link-state
            advertisements in  this  virtual link's link-state
            database."
      ::= { fsMIStdOspfv3VirtIfEntry 10 }

    fsMIStdOspfv3VirtIfLinkLsaCksumSum OBJECT-TYPE
        SYNTAX          Integer32
        MAX-ACCESS      read-only
        STATUS          current
        DESCRIPTION
            "The 32-bit unsigned sum of the Link-Scope link-state
            advertisements'  LS  checksums  contained in this
            virtual link's link-state database.  The sum can be used
            to determine if  there  has been  a  change  in a
            router's link state database, and to compare the
            link-state database of two routers."
      ::= { fsMIStdOspfv3VirtIfEntry 11 }

    fsMIStdOspfv3VirtIfStatus OBJECT-TYPE
        SYNTAX          RowStatus
        MAX-ACCESS      read-create
        STATUS          current
        DESCRIPTION
            "This variable controls the status of  the  en-
            try. The use of RowStatus is covered in more detail
            in [6]."
      ::= { fsMIStdOspfv3VirtIfEntry 12 }

--      OSPFv3 Neighbor Table

--      The OSPFv3 Neighbor Table describes all neighbors in
--      the locality of the subject router.

    fsMIStdOspfv3NbrTable OBJECT-TYPE
        SYNTAX          SEQUENCE OF FsMIStdOspfv3NbrEntry
        MAX-ACCESS      not-accessible
        STATUS          current
        DESCRIPTION
            "A table of non-virtual neighbor information."
        REFERENCE
            "OSPF Version 2, Section 10  The  Neighbor  Data
            Structure"
      ::= { fsMIStdOspfv3Objects 9 }

    fsMIStdOspfv3NbrEntry OBJECT-TYPE
        SYNTAX          FsMIStdOspfv3NbrEntry
        MAX-ACCESS      not-accessible
        STATUS          current
        DESCRIPTION
            "The information regarding a single neighbor."
        REFERENCE
            "OSPF Version 2, Section 10  The  Neighbor  Data
            Structure"
        INDEX { fsMIStdOspfv3NbrIfIndex,
                fsMIStdOspfv3NbrRtrId }
      ::= { fsMIStdOspfv3NbrTable 1 }

FsMIStdOspfv3NbrEntry ::= SEQUENCE {
        fsMIStdOspfv3NbrIfIndex
                InterfaceIndex,
        fsMIStdOspfv3NbrRtrId
                RouterID,
        fsMIStdOspfv3NbrAddressType
                InetAddressType,
        fsMIStdOspfv3NbrAddress
                InetAddress,
        fsMIStdOspfv3NbrOptions
                Integer32,
        fsMIStdOspfv3NbrPriority
                DesignatedRouterPriority,
        fsMIStdOspfv3NbrState
                INTEGER,
        fsMIStdOspfv3NbrEvents
                Counter32,
        fsMIStdOspfv3NbrLsRetransQLen
                Gauge32,
        fsMIStdOspfv3NbrHelloSuppressed
                TruthValue,
        fsMIStdOspfv3NbrIfId
                InterfaceIndex,
        fsMIStdOspfv3NbrRestartHelperStatus
                INTEGER,
        fsMIStdOspfv3NbrRestartHelperAge
                UpToRefreshInterval,
        fsMIStdOspfv3NbrRestartHelperExitReason
                INTEGER,
        fsMIStdOspfv3NbrContextId
                Integer32
        }

    fsMIStdOspfv3NbrIfIndex OBJECT-TYPE
        SYNTAX          InterfaceIndex
        MAX-ACCESS      not-accessible
        STATUS          current
        DESCRIPTION
            "The local link ID of the link over which the
             neighbor can be reached."
      ::= { fsMIStdOspfv3NbrEntry 1 }

    fsMIStdOspfv3NbrRtrId OBJECT-TYPE
        SYNTAX          RouterID
        MAX-ACCESS      not-accessible
        STATUS          current
        DESCRIPTION
            "A 32-bit integer (represented as a type  IpAd-
            dress)  uniquely  identifying  the  neighboring
            router in the Autonomous System."
      ::= { fsMIStdOspfv3NbrEntry 2 }

    fsMIStdOspfv3NbrAddressType OBJECT-TYPE
        SYNTAX          InetAddressType
        MAX-ACCESS      read-only
        STATUS          current
        DESCRIPTION
            "The address type of fsMIStdOspfv3NbrAddress. Only IPv6
            addresses without zone index are expected."
      ::= { fsMIStdOspfv3NbrEntry 3 }

    fsMIStdOspfv3NbrAddress OBJECT-TYPE
        SYNTAX          InetAddress (SIZE (16))
        MAX-ACCESS      read-only
        STATUS          current
        DESCRIPTION
            "The IPv6 address of the neighbor associated with
            the local link."
      ::= { fsMIStdOspfv3NbrEntry 4 }

    fsMIStdOspfv3NbrOptions OBJECT-TYPE
        SYNTAX          Integer32
        MAX-ACCESS      read-only
        STATUS          current
        DESCRIPTION
            "A Bit Mask corresponding to the neighbor's op-
            tions field."
        REFERENCE
            "OSPF Version 3, Appendix A.2 the Options field"
      ::= { fsMIStdOspfv3NbrEntry 5 }

    fsMIStdOspfv3NbrPriority OBJECT-TYPE
        SYNTAX          DesignatedRouterPriority
        MAX-ACCESS      read-only
        STATUS          current
        DESCRIPTION
            "The priority of this neighbor in the designat-
            ed router election algorithm.  The value 0 sig-
            nifies that the neighbor is not eligible to be-
            come  the  designated router on this particular
            network."
      ::= { fsMIStdOspfv3NbrEntry 6 }

    fsMIStdOspfv3NbrState OBJECT-TYPE
        SYNTAX          INTEGER {
                        down(1),
                        attempt(2),
                        init(3),
                        twoWay(4),
                        exchangeStart(5),
                        exchange(6),
                        loading(7),
                        full(8)
                        }
        MAX-ACCESS      read-only
        STATUS          current
        DESCRIPTION
            "The State of the relationship with this Neigh-
            bor."
        REFERENCE
            "OSPF Version 2, Section 10.1 Neighbor States"
      ::= { fsMIStdOspfv3NbrEntry 7 }

    fsMIStdOspfv3NbrEvents OBJECT-TYPE
        SYNTAX          Counter32
        MAX-ACCESS      read-only
        STATUS          current
        DESCRIPTION
            "The number of times this neighbor relationship
            has changed state, or an error has occurred."
      ::= { fsMIStdOspfv3NbrEntry 8 }

    fsMIStdOspfv3NbrLsRetransQLen OBJECT-TYPE
        SYNTAX          Gauge32
        MAX-ACCESS      read-only
        STATUS          current
        DESCRIPTION
            "The  current  length  of  the   retransmission
            queue."
      ::= { fsMIStdOspfv3NbrEntry 9 }

    fsMIStdOspfv3NbrHelloSuppressed OBJECT-TYPE
        SYNTAX          TruthValue
        MAX-ACCESS      read-only
        STATUS          current
        DESCRIPTION
            "Indicates whether Hellos are being  suppressed
            to the neighbor"
      ::= { fsMIStdOspfv3NbrEntry 10 }

    fsMIStdOspfv3NbrIfId OBJECT-TYPE
        SYNTAX          InterfaceIndex
        MAX-ACCESS      read-only
        STATUS          current
        DESCRIPTION
            "The interface ID that the neighbor advertises
            in its Hello Packets on this link, that is, the
            neighbor's local interface index."
      ::= { fsMIStdOspfv3NbrEntry 11 }

    fsMIStdOspfv3NbrRestartHelperStatus OBJECT-TYPE
       SYNTAX       INTEGER { notHelping (1),
                              helping (2)
                            }
       MAX-ACCESS   read-only
       STATUS       current
       DESCRIPTION
          "Indicates whether the router is acting
          as a hitless restart helper for the neighbor."
      ::= { fsMIStdOspfv3NbrEntry 12 }

    fsMIStdOspfv3NbrRestartHelperAge OBJECT-TYPE
       SYNTAX       UpToRefreshInterval
       UNITS        "seconds"
       MAX-ACCESS   read-only
       STATUS       current
       DESCRIPTION
          "Remaining time in current OSPF hitless restart
          interval, if the router is acting as a restart
          helper for the neighbor."
      ::= { fsMIStdOspfv3NbrEntry 13 }

    fsMIStdOspfv3NbrRestartHelperExitReason OBJECT-TYPE
       SYNTAX       INTEGER { none (1),           -- not attempted
                              inProgress (2),     -- restart in
                                                  -- progress
                              completed (3),      -- successfully
                                                  -- completed
                              timedOut (4),       -- timed out
                              topologyChanged (5) -- aborted due to
                                                  -- topology
                                                  -- change.
                            }
       MAX-ACCESS   read-only
       STATUS       current
       DESCRIPTION
          "Describes the outcome of the last attempt at acting
           as a hitless restart helper for the neighbor."
      ::= { fsMIStdOspfv3NbrEntry 14 }

    fsMIStdOspfv3NbrContextId OBJECT-TYPE
        SYNTAX          Integer32
	    MAX-ACCESS      read-only
	    STATUS          current
	    DESCRIPTION
	        "A 32-bit unique context id for each entry.
             Minimum value is 0 and Maximum depends upon system
             configuration. Default value is 0 which will be initialized
             during bootup"
      ::= { fsMIStdOspfv3NbrEntry 15 }

--      OSPFv3 NBMA Neighbor Table

--      The OSPFv3 NBMA Neighbor Table describes all configured
--      NBMA neighbors and neighbors dynamically discovered by
--      lower-level protocols such as Inverse Neighbor Discovery.

    fsMIStdOspfv3NbmaNbrTable OBJECT-TYPE
        SYNTAX          SEQUENCE OF FsMIStdOspfv3NbmaNbrEntry
        MAX-ACCESS      not-accessible
        STATUS          current
        DESCRIPTION
            "A table of configured non-virtual neighbor
            information and neighbors dynamically discovered
            by lower-level protocols such as Inverse Neighbor
            Discovery."
        REFERENCE
            "OSPF Version 2, Section 10  The  Neighbor  Data
            Structure"
      ::= { fsMIStdOspfv3Objects 10 }

    fsMIStdOspfv3NbmaNbrEntry OBJECT-TYPE
        SYNTAX          FsMIStdOspfv3NbmaNbrEntry
        MAX-ACCESS      not-accessible
        STATUS          current
        DESCRIPTION
            "The information regarding a single configured
            neighbor or neighbor discovered by lower-level
            protocols such as Inverse Neighbor Discovery."
        REFERENCE
            "OSPF Version 2, Section 10  The  Neighbor  Data
            Structure"
        INDEX { fsMIStdOspfv3NbmaNbrIfIndex,
                fsMIStdOspfv3NbmaNbrAddressType,
                fsMIStdOspfv3NbmaNbrAddress }
      ::= { fsMIStdOspfv3NbmaNbrTable 1 }

FsMIStdOspfv3NbmaNbrEntry ::= SEQUENCE {
        fsMIStdOspfv3NbmaNbrIfIndex
                InterfaceIndex,
        fsMIStdOspfv3NbmaNbrAddressType
                InetAddressType,
        fsMIStdOspfv3NbmaNbrAddress
                InetAddress,
        fsMIStdOspfv3NbmaNbrPriority
                DesignatedRouterPriority,
        fsMIStdOspfv3NbmaNbrRtrId
                RouterID,
        fsMIStdOspfv3NbmaNbrState
                INTEGER,
        fsMIStdOspfv3NbmaNbrStorageType
                StorageType,
        fsMIStdOspfv3NbmaNbrContextId
                Integer32,
        fsMIStdOspfv3NbmaNbrStatus
                RowStatus
        }

    fsMIStdOspfv3NbmaNbrIfIndex OBJECT-TYPE
        SYNTAX          InterfaceIndex
        MAX-ACCESS      not-accessible
        STATUS          current
        DESCRIPTION
            "The local link ID of the link over which the
             neighbor can be reached."
      ::= { fsMIStdOspfv3NbmaNbrEntry 1 }

    fsMIStdOspfv3NbmaNbrAddressType OBJECT-TYPE
        SYNTAX          InetAddressType
        MAX-ACCESS      not-accessible
        STATUS          current
        DESCRIPTION
            "The address type of fsMIStdOspfv3NbrAddress. Only IPv6
            addresses without zone index are expected."
      ::= { fsMIStdOspfv3NbmaNbrEntry 2 }

    fsMIStdOspfv3NbmaNbrAddress OBJECT-TYPE
        SYNTAX          InetAddress (SIZE (16))
        MAX-ACCESS      not-accessible
        STATUS          current
        DESCRIPTION
            "The IPv6 address of the neighbor associated with
            the local link."
      ::= { fsMIStdOspfv3NbmaNbrEntry 3 }

    fsMIStdOspfv3NbmaNbrPriority OBJECT-TYPE
        SYNTAX          DesignatedRouterPriority
        MAX-ACCESS      read-create
        STATUS          current
        DESCRIPTION
            "The priority of this neighbor in the designat-
            ed router election algorithm. The value 0 sig-
            nifies that the neighbor is not eligible to be-
            come  the  designated router on this particular
            network."
        DEFVAL          { 1 }
      ::= { fsMIStdOspfv3NbmaNbrEntry 4 }

    fsMIStdOspfv3NbmaNbrRtrId OBJECT-TYPE
        SYNTAX          RouterID
        MAX-ACCESS      read-only
        STATUS          current
        DESCRIPTION
            "A 32-bit integer (represented as a type IpAd-
            dress) uniquely identifying the neighboring
            router in the Autonomous System. A value of
            0.0.0.0 is returned until a Hello is received
            from the configured neighbor."
      ::= { fsMIStdOspfv3NbmaNbrEntry 5 }

    fsMIStdOspfv3NbmaNbrState OBJECT-TYPE
        SYNTAX          INTEGER {
                        down(1),
                        attempt(2),
                        init(3),
                        twoWay(4),
                        exchangeStart(5),
                        exchange(6),
                        loading(7),
                        full(8)
                        }
        MAX-ACCESS      read-only
        STATUS          current
        DESCRIPTION
            "The State of the relationship with this Neigh-
            bor."
        REFERENCE
            "OSPF Version 2, Section 10.1 Neighbor States"
      ::= { fsMIStdOspfv3NbmaNbrEntry 6 }

    fsMIStdOspfv3NbmaNbrStorageType OBJECT-TYPE
        SYNTAX          StorageType
        MAX-ACCESS      read-create
        STATUS          current
        DESCRIPTION
            "The storage type for this conceptual row.
            Conceptual rows having the value 'permanent' need not
            allow write-access to any columnar objects in the row.
            Manually configured entries will have a storage type
            of nonVolatile while entries dynamically created as a
            result of a lower-level protocol such as Inverse
            Neighbor Discovery will have a storage type of
            volatile."
        DEFVAL          { nonVolatile }
      ::= { fsMIStdOspfv3NbmaNbrEntry 7 }

    fsMIStdOspfv3NbmaNbrContextId OBJECT-TYPE
        SYNTAX          Integer32
	    MAX-ACCESS      read-only
	    STATUS          current
	    DESCRIPTION
	        "A 32-bit unique context id for each entry.
             Minimum value is 0 and Maximum depends upon system
             configuration. Default value is 0 which will be initialized
             during bootup"
      ::= { fsMIStdOspfv3NbmaNbrEntry 8 }

    fsMIStdOspfv3NbmaNbrStatus OBJECT-TYPE
        SYNTAX          RowStatus
        MAX-ACCESS      read-create
        STATUS          current
        DESCRIPTION
            "This variable controls the status of the en-
            try. The use of RowStatus is covered in more detail
            in [6]."
      ::= { fsMIStdOspfv3NbmaNbrEntry 9 }

--      OSPFv3 Virtual Neighbor Table

--      This table describes all virtual neighbors.
--      Since Virtual Links are configured in the
--      virtual interface table, this table is read-only.

    fsMIStdOspfv3VirtNbrTable OBJECT-TYPE
        SYNTAX          SEQUENCE OF FsMIStdOspfv3VirtNbrEntry
        MAX-ACCESS      not-accessible
        STATUS          current
        DESCRIPTION
            "A table of virtual neighbor information."
        REFERENCE
            "OSPF Version 2, Section 15 Virtual Links"
      ::= { fsMIStdOspfv3Objects 11 }

    fsMIStdOspfv3VirtNbrEntry OBJECT-TYPE
        SYNTAX          FsMIStdOspfv3VirtNbrEntry
        MAX-ACCESS      not-accessible
        STATUS          current
        DESCRIPTION
            "Virtual neighbor information."
        INDEX { fsMIStdOspfv3ContextId,
	        fsMIStdOspfv3VirtNbrArea,
                fsMIStdOspfv3VirtNbrRtrId }
      ::= { fsMIStdOspfv3VirtNbrTable 1 }

FsMIStdOspfv3VirtNbrEntry ::= SEQUENCE {
        fsMIStdOspfv3VirtNbrArea
                AreaID,
        fsMIStdOspfv3VirtNbrRtrId
                RouterID,
        fsMIStdOspfv3VirtNbrIfIndex
                InterfaceIndex,
        fsMIStdOspfv3VirtNbrAddressType
                InetAddressType,
        fsMIStdOspfv3VirtNbrAddress
                InetAddress,
        fsMIStdOspfv3VirtNbrOptions
                Integer32,
        fsMIStdOspfv3VirtNbrState
                INTEGER,
        fsMIStdOspfv3VirtNbrEvents
                Counter32,
        fsMIStdOspfv3VirtNbrLsRetransQLen
                Gauge32,
        fsMIStdOspfv3VirtNbrHelloSuppressed
                TruthValue,
        fsMIStdOspfv3VirtNbrIfId
                InterfaceIndex,
        fsMIStdOspfv3VirtNbrRestartHelperStatus
                INTEGER,
        fsMIStdOspfv3VirtNbrRestartHelperAge
                UpToRefreshInterval,
        fsMIStdOspfv3VirtNbrRestartHelperExitReason
                INTEGER
        }

    fsMIStdOspfv3VirtNbrArea OBJECT-TYPE
        SYNTAX          AreaID
        MAX-ACCESS      not-accessible
        STATUS          current
        DESCRIPTION
            "The Transit Area Identifier."
      ::= { fsMIStdOspfv3VirtNbrEntry 1 }

    fsMIStdOspfv3VirtNbrRtrId OBJECT-TYPE
        SYNTAX          RouterID
        MAX-ACCESS      not-accessible
        STATUS          current
        DESCRIPTION
            "A  32-bit  integer  uniquely  identifying  the
            neighboring router in the Autonomous System."
      ::= { fsMIStdOspfv3VirtNbrEntry 2 }

    fsMIStdOspfv3VirtNbrIfIndex OBJECT-TYPE
        SYNTAX          InterfaceIndex
        MAX-ACCESS      read-only
        STATUS          current
        DESCRIPTION
            "The local interface ID for the virtual link over
            which the neighbor can be reached."
      ::= { fsMIStdOspfv3VirtNbrEntry 3 }

    fsMIStdOspfv3VirtNbrAddressType OBJECT-TYPE
        SYNTAX          InetAddressType
        MAX-ACCESS      read-only
        STATUS          current
        DESCRIPTION
            "The address type of fsMIStdOspfv3VirtNbrAddress. Only IPv6
            addresses without zone index are expected."
      ::= { fsMIStdOspfv3VirtNbrEntry 4 }

    fsMIStdOspfv3VirtNbrAddress OBJECT-TYPE
        SYNTAX          InetAddress (SIZE (16))
        MAX-ACCESS      read-only
        STATUS          current
        DESCRIPTION
            "The IPv6 address advertised by this Virtual Neighbor.
            It must be a Site-Local or Global scope address."
      ::= { fsMIStdOspfv3VirtNbrEntry 5 }

    fsMIStdOspfv3VirtNbrOptions OBJECT-TYPE
        SYNTAX          Integer32
        MAX-ACCESS      read-only
        STATUS          current
        DESCRIPTION
            "A Bit Mask corresponding to the neighbor's op-
            tions field."
        REFERENCE
            "OSPF Version 3, Appendix A.2 the Options field"
      ::= { fsMIStdOspfv3VirtNbrEntry 6 }

    fsMIStdOspfv3VirtNbrState OBJECT-TYPE
        SYNTAX          INTEGER {
                        down(1),
                        attempt(2),
                        init(3),
                        twoWay(4),
                        exchangeStart(5),
                        exchange(6),
                        loading(7),
                        full(8)
                        }
        MAX-ACCESS      read-only
        STATUS          current
        DESCRIPTION
            "The state of the Virtual Neighbor Relation-
            ship."
      ::= { fsMIStdOspfv3VirtNbrEntry 7 }

    fsMIStdOspfv3VirtNbrEvents OBJECT-TYPE
        SYNTAX          Counter32
        MAX-ACCESS      read-only
        STATUS          current
        DESCRIPTION
            "The number of  times  this  virtual  link  has
            changed its state, or an error has occurred."
      ::= { fsMIStdOspfv3VirtNbrEntry 8 }

    fsMIStdOspfv3VirtNbrLsRetransQLen OBJECT-TYPE
        SYNTAX          Gauge32
        MAX-ACCESS      read-only
        STATUS          current
        DESCRIPTION
            "The  current  length  of  the   retransmission
            queue."
      ::= { fsMIStdOspfv3VirtNbrEntry 9 }

    fsMIStdOspfv3VirtNbrHelloSuppressed OBJECT-TYPE
        SYNTAX          TruthValue
        MAX-ACCESS      read-only
        STATUS          current
        DESCRIPTION
            "Indicates whether Hellos are being  suppressed
            to the neighbor"
      ::= { fsMIStdOspfv3VirtNbrEntry 10 }

    fsMIStdOspfv3VirtNbrIfId OBJECT-TYPE
        SYNTAX          InterfaceIndex
        MAX-ACCESS      read-only
        STATUS          current
        DESCRIPTION
            "The interface ID that the neighbor advertises
            in its Hello Packets on this virtual link, that is,
            the neighbor's local interface ID."
      ::= { fsMIStdOspfv3VirtNbrEntry 11 }

    fsMIStdOspfv3VirtNbrRestartHelperStatus OBJECT-TYPE
        SYNTAX       INTEGER { notHelping (1),
                               helping (2)
                             }
        MAX-ACCESS   read-only
        STATUS       current
        DESCRIPTION
           "Indicates whether the router is acting
           as a hitless restart helper for the neighbor."
      ::= { fsMIStdOspfv3VirtNbrEntry 12 }

    fsMIStdOspfv3VirtNbrRestartHelperAge OBJECT-TYPE
        SYNTAX       UpToRefreshInterval
        UNITS        "seconds"
        MAX-ACCESS   read-only
        STATUS       current
        DESCRIPTION
           "Remaining time in current OSPF hitless restart
           interval, if the router is acting as a restart
           helper for the neighbor."
      ::= { fsMIStdOspfv3VirtNbrEntry 13 }

    fsMIStdOspfv3VirtNbrRestartHelperExitReason OBJECT-TYPE
        SYNTAX       INTEGER { none (1),           -- not attempted
                               inProgress (2),     -- restart in
                                                   -- progress
                               completed (3),      -- successfully
                                                   -- completed
                               timedOut (4),       -- timed out
                               topologyChanged (5) -- aborted due to
                                                   -- topology
                                                   -- change.
                             }
        MAX-ACCESS   read-only
        STATUS       current
        DESCRIPTION
           "Describes the outcome of the last attempt at acting
            as a hitless restart helper for the neighbor."
      ::= { fsMIStdOspfv3VirtNbrEntry 14 }


--
--      The OSPFv3 Area Aggregate Table
--

    fsMIStdOspfv3AreaAggregateTable OBJECT-TYPE
        SYNTAX          SEQUENCE OF FsMIStdOspfv3AreaAggregateEntry
        MAX-ACCESS      not-accessible
        STATUS          current
        DESCRIPTION
            "A range of IPv6 prefixes specified by a
            prefix/prefix length  pair. Note that if
            ranges are configured such that one range sub-
            sumes  another range the most specific match is
            the preferred one."
      ::= { fsMIStdOspfv3Objects 12 }

    fsMIStdOspfv3AreaAggregateEntry OBJECT-TYPE
        SYNTAX          FsMIStdOspfv3AreaAggregateEntry
        MAX-ACCESS      not-accessible
        STATUS          current
        DESCRIPTION
            "A range of IPv6 prefixes specified by a
            prefix/prefix length  pair. Note that if
            ranges are configured such that one range sub-
            sumes  another range the most specific match is
            the preferred one."
        REFERENCE
            "OSPF Version 2, Appendix C.2  Area parameters"
        INDEX { fsMIStdOspfv3ContextId,
	        fsMIStdOspfv3AreaAggregateAreaID,
                fsMIStdOspfv3AreaAggregateAreaLsdbType,
                fsMIStdOspfv3AreaAggregatePrefixType,
                fsMIStdOspfv3AreaAggregatePrefix,
                fsMIStdOspfv3AreaAggregatePrefixLength }
      ::= { fsMIStdOspfv3AreaAggregateTable 1 }

FsMIStdOspfv3AreaAggregateEntry ::= SEQUENCE {
        fsMIStdOspfv3AreaAggregateAreaID
                AreaID,
        fsMIStdOspfv3AreaAggregateAreaLsdbType
                INTEGER,
        fsMIStdOspfv3AreaAggregatePrefixType
                InetAddressType,
        fsMIStdOspfv3AreaAggregatePrefix
                InetAddress,
        fsMIStdOspfv3AreaAggregatePrefixLength
                InetAddressPrefixLength,
        fsMIStdOspfv3AreaAggregateEffect
                INTEGER,
        fsMIStdOspfv3AreaAggregateRouteTag
                Integer32,
        fsMIStdOspfv3AreaAggregateStatus
                RowStatus
        }

    fsMIStdOspfv3AreaAggregateAreaID OBJECT-TYPE
        SYNTAX          AreaID
        MAX-ACCESS      not-accessible
        STATUS          current
        DESCRIPTION
            "The Area the Address Aggregate is to be  found
            within."
        REFERENCE
            "OSPF Version 2, Appendix C.2 Area parameters"
      ::= { fsMIStdOspfv3AreaAggregateEntry 1 }

    fsMIStdOspfv3AreaAggregateAreaLsdbType OBJECT-TYPE
        SYNTAX          INTEGER {
                        interAreaPrefixLsa(8195), -- 0x2003
                        nssaExternalLsa(8199)     -- 0x2007
                        }
        MAX-ACCESS      not-accessible
        STATUS          current
        DESCRIPTION
            "The type of the Address Aggregate.  This field
            specifies  the  Area Lsdb type that this Address Ag-
            gregate applies to."
        REFERENCE
            "OSPF Version 2, Appendix A.4.1 The  Link  State
            Advertisement header"
      ::= { fsMIStdOspfv3AreaAggregateEntry 2 }

    fsMIStdOspfv3AreaAggregatePrefixType OBJECT-TYPE
        SYNTAX          InetAddressType
        MAX-ACCESS      not-accessible
        STATUS          current
        DESCRIPTION
            "The prefix type of fsMIStdOspfv3AreaAggregatePrefix. Only
            IPv6 addresses are expected."
      ::= { fsMIStdOspfv3AreaAggregateEntry 4 }

    fsMIStdOspfv3AreaAggregatePrefix OBJECT-TYPE
        SYNTAX          InetAddress (SIZE (0..16))
        MAX-ACCESS      not-accessible
        STATUS          current
        DESCRIPTION
            "The IPv6 Prefix."
        REFERENCE
            "OSPF Version 2, Appendix C.2 Area parameters"
      ::= { fsMIStdOspfv3AreaAggregateEntry 5 }

    fsMIStdOspfv3AreaAggregatePrefixLength OBJECT-TYPE
        SYNTAX          InetAddressPrefixLength (3..128)
        UNITS           "bits"
        MAX-ACCESS      not-accessible
        STATUS          current
        DESCRIPTION
            "The length of the prefix (in bits). A prefix can
            not be shorter than 3 bits."
        REFERENCE
            "OSPF Version 2, Appendix C.2 Area parameters"
      ::= { fsMIStdOspfv3AreaAggregateEntry 6 }

    fsMIStdOspfv3AreaAggregateEffect OBJECT-TYPE
        SYNTAX          INTEGER {
                        advertiseMatching(1),
                        doNotAdvertiseMatching(2)
                        }
        MAX-ACCESS      read-create
        STATUS          current
        DESCRIPTION
            "Prefixes subsumed by ranges either trigger  the
            advertisement  of  the indicated aggregate (ad-
            vertiseMatching), or result in the prefix not
            being advertised at all outside the area."
        DEFVAL          { advertiseMatching }
      ::= { fsMIStdOspfv3AreaAggregateEntry 7 }

    fsMIStdOspfv3AreaAggregateRouteTag OBJECT-TYPE
        SYNTAX          Integer32
        MAX-ACCESS      read-create
        STATUS          current
        DESCRIPTION
            "This tag is advertised only in the summarized
             As-External LSA when summarizing from type-7 to
             type-5."
        DEFVAL         { 0 }
      ::= { fsMIStdOspfv3AreaAggregateEntry 8 }

    fsMIStdOspfv3AreaAggregateStatus OBJECT-TYPE
        SYNTAX          RowStatus
        MAX-ACCESS      read-create
        STATUS          current
        DESCRIPTION
            "This variable controls the status of  the  en-
            try. The use of RowStatus is covered in more detail
            in [6]."
      ::= { fsMIStdOspfv3AreaAggregateEntry 9 }

END
