-- Copyright (C) 2008-2014 Super Micro Computer Inc. All Rights Reserved

-- /*****************************************************************
--  *                                                               *
--  * $Id: fstcp.mib,v 1.9 2013/06/07 13:29:41 siva Exp $          *
--  * fstcp.mib                                                     *
--  *                                                               *
--  * TCP Proprietary MIB.                                  *
--  *                                                               *
--  ****************************************************************/

SUPERMICRO-TCP-MIB DEFINITIONS ::= BEGIN

IMPORTS
    MODULE-IDENTITY, OBJECT-TYPE,
    IpAddress, enterprises, NOTIFICATION-TYPE
                                       FROM SNMPv2-SMI
    TruthValue                         FROM SNMPv2-TC
    tcpConnectionEntry                 FROM TCP-MIB
    InetAddress, InetAddressType, InetPortNumber
                                 FROM INET-ADDRESS-MIB;

fstcp MODULE-IDENTITY
    LAST-UPDATED "201209050000Z"
    ORGANIZATION "IETF SNMPv2 Working Group"
    CONTACT-INFO "support@Supermicro.com"

    DESCRIPTION
            "The MIB module for managing TCP implementations."
    REVISION      "201209050000Z"
    DESCRIPTION
            "The initial revision of this MIB module was part of MIB-
            II."
	::=  { enterprises supermicro-computer-inc(10876) super-switch(101) basic(1) 18}

fsTcpAckOption OBJECT-TYPE
              SYNTAX      INTEGER {
                          none(1),            -- Default Cumulative ACK
                          sack(2),            -- SACK Option
                          nak(3),             -- NACK Option
                          fstrxmt(4)          -- FastRetransmit
                      }
              MAX-ACCESS  read-write
              STATUS      current
              DESCRIPTION
                      "The algorithm used to determine the acknowledgement
                       policy to be followed by the receiving TCP"
              ::= { fstcp 1 }

fsTcpTimeStampOption OBJECT-TYPE
              SYNTAX      TruthValue
              MAX-ACCESS  read-write
              STATUS      current
              DESCRIPTION
                      "A flag to note whether the Time Stamp option is
                       enabled"
              ::= { fstcp 2 }

          fsTcpBigWndOption OBJECT-TYPE
              SYNTAX      TruthValue
              MAX-ACCESS  read-write
              STATUS      current
              DESCRIPTION
                      "A flag to note whether the Big Window option is
                       enabled"
              ::= { fstcp 3 }

          fsTcpIncrIniWnd OBJECT-TYPE
              SYNTAX      TruthValue
              MAX-ACCESS  read-write
              STATUS      current
              DESCRIPTION
                      "A flag to note whether the Increased Initial
                       Window feature is enabled"
              ::= { fstcp 4 }

          fsTcpMaxNumOfTCB OBJECT-TYPE
              SYNTAX      INTEGER
              MAX-ACCESS  read-write
              STATUS      current
              DESCRIPTION
                      "Maximum Number of TCP connections."
              ::= { fstcp 5 }

          fsTcpTraceDebug OBJECT-TYPE
              SYNTAX      INTEGER
              MAX-ACCESS  read-write
              STATUS      current
              DESCRIPTION
                      " This is used to enable Trace Statements in Tcp Module.
                A four byte integer value is specified for enabling the level
                of tracing.Each Bit in the four byte integer variable represents
                a level of Trace. The bits represents the levels as
                follows: 0 - Init and Shutdown, 1 - Management, 2 - Data Path,
                3 - Control Plane, 4 - packet Dump, 5 - All resources except
                buffer, 6 - All Failures, 7 - Buffer, 8 - Function Entry And
                Exit, 9 - Finite State Machine and 10 - Output State Machine.
                The remaining bits are unused. The combination of levels are
                allowed."
              ::= { fstcp 6 }

          fsTcpMaxReTries OBJECT-TYPE
              SYNTAX      INTEGER (1..12)
              MAX-ACCESS  read-write
              STATUS      current
              DESCRIPTION
                      " When data send is not acknowledged , TCP re-transmits the data.
                      This object is used to configure the maximum retries for
                      re-transmission in Tcp Module."
              ::= { fstcp 9 }

          fsTcpTrapAdminStatus OBJECT-TYPE
              SYNTAX                  INTEGER
                            {
                                enabled(1),
                                disabled(2)
                            }
              MAX-ACCESS              read-write
              STATUS                  current
              DESCRIPTION
                    "If this object is set to disable, then the NOTIFICATION
                     messages wont be sent to the SNMP Manager.
                     If enabled, NOTIFICATION messages are sent."
              DEFVAL  { disabled }
              ::= { fstcp 10 }



-- SCALAR_TABLE_END fstcp

          fsTcpConnTable OBJECT-TYPE
              SYNTAX      SEQUENCE OF FsTcpConnEntry
              MAX-ACCESS  not-accessible
              STATUS      current
              DESCRIPTION
                      "A table containing TCP connection-specific
                      information."
              ::= { fstcp 7 }

          fsTcpConnEntry OBJECT-TYPE
              SYNTAX      FsTcpConnEntry
              MAX-ACCESS  not-accessible
              STATUS      current
              DESCRIPTION
                      "Information about a particular current TCP
                      connection.  An object of this type is transient,
                      in that it ceases to exist when (or soon after)
                      the connection makes the transition to the CLOSED
                      state."
              INDEX   { fsTcpConnLocalAddress,
                        fsTcpConnLocalPort,
                        fsTcpConnRemAddress,
                        fsTcpConnRemPort }
              ::= { fsTcpConnTable 1 }

 FsTcpConnEntry ::=
              SEQUENCE {
                  fsTcpConnLocalAddress
                      IpAddress,
                  fsTcpConnLocalPort
                      INTEGER,
                  fsTcpConnRemAddress
                      IpAddress,
                  fsTcpConnRemPort
                      INTEGER,
                  fsTcpConnOutState
                      INTEGER,
                  fsTcpConnSWindow
                      INTEGER,
                  fsTcpConnRWindow
                      INTEGER,
                  fsTcpConnCWindow
                      INTEGER,
                  fsTcpConnSSThresh
                      INTEGER,
                  fsTcpConnSMSS
                      INTEGER,
                  fsTcpConnRMSS
                      INTEGER,
                  fsTcpConnSRT
                      INTEGER,
                  fsTcpConnRTDE
                      INTEGER,
                  fsTcpConnPersist
                      INTEGER,
		  fsTcpConnRexmt
                      INTEGER,
                  fsTcpConnRexmtCnt
                      INTEGER,
                  fsTcpConnSBCount
                      INTEGER,
                  fsTcpConnSBSize
                      INTEGER,
                  fsTcpConnRBCount
                      INTEGER,
                  fsTcpConnRBSize
                      INTEGER,
                  fsTcpKaMainTmr
                      INTEGER,
                  fsTcpKaRetransTmr
                      INTEGER,
                  fsTcpKaRetransCnt
                      INTEGER
              }

          fsTcpConnLocalAddress OBJECT-TYPE
              SYNTAX      IpAddress
              MAX-ACCESS  not-accessible
              STATUS      current
              DESCRIPTION
                      "The local IP address for this TCP connection.  In
                      the case of a connection in the listen state which
                      is willing to accept connections for any IP
                      interface associated with the node, the value
                      0.0.0.0 is used."
              ::= { fsTcpConnEntry 1 }

          fsTcpConnLocalPort OBJECT-TYPE
              SYNTAX      INTEGER (0..65535)
              MAX-ACCESS  not-accessible
              STATUS      current
              DESCRIPTION
                      "The local port number for this TCP connection."
              ::= { fsTcpConnEntry 2 }

          fsTcpConnRemAddress OBJECT-TYPE
              SYNTAX      IpAddress
              MAX-ACCESS  not-accessible
              STATUS      current
              DESCRIPTION
                      "The remote IP address for this TCP connection."
              ::= { fsTcpConnEntry 3 }
	  fsTcpConnRemPort OBJECT-TYPE
              SYNTAX      INTEGER (0..65535)
              MAX-ACCESS  not-accessible
              STATUS      current
              DESCRIPTION
                      "The remote port number for this TCP connection."
              ::= { fsTcpConnEntry 4 }

          fsTcpConnOutState OBJECT-TYPE
              SYNTAX      INTEGER (0..65535)
              MAX-ACCESS  read-only
              STATUS      current
              DESCRIPTION
                      "The output state for this TCP connection."
              ::= { fsTcpConnEntry 5 }

          fsTcpConnSWindow OBJECT-TYPE
              SYNTAX      INTEGER (0..65535)
              MAX-ACCESS  read-only
              STATUS      current
              DESCRIPTION
                      "The send window(SND.WND) for this TCP connection. It
                       indicates the amount of data that the peer TCP is willing
                       to accept."
              ::= { fsTcpConnEntry 6 }

	  fsTcpConnRWindow OBJECT-TYPE
              SYNTAX      INTEGER (0..65535)
              MAX-ACCESS  read-only
              STATUS      current
              DESCRIPTION
                      "The receive window(RCV.WND) for this TCP connection. It
                       indicates the amount of data that TCP is willing to
                       accept."
              ::= { fsTcpConnEntry 7 }

          fsTcpConnCWindow OBJECT-TYPE
              SYNTAX      INTEGER (0..65535)
              MAX-ACCESS  read-only
              STATUS      current
              DESCRIPTION
                      "The congestion window for this TCP connection."
              ::= { fsTcpConnEntry 8 }

          fsTcpConnSSThresh OBJECT-TYPE
              SYNTAX      INTEGER (0..65535)
              MAX-ACCESS  read-only
              STATUS      current
              DESCRIPTION
                      "The slow start thresh-hold for this TCP connection. It
                       indicates the window size limit crossing which TCP
                       transitions from the slow start phase to congestion
                       avoidance phase."
              ::= { fsTcpConnEntry 9 }

	  fsTcpConnSMSS OBJECT-TYPE
              SYNTAX      INTEGER (0..65535)
              MAX-ACCESS  read-only
              STATUS      current
              DESCRIPTION
                      "The send maximum segment size for this TCP connection.
                       It is negotiated during connection establishment."
              ::= { fsTcpConnEntry 10 }

          fsTcpConnRMSS OBJECT-TYPE
              SYNTAX      INTEGER (0..65535)
              MAX-ACCESS  read-only
              STATUS      current
              DESCRIPTION
                      "The receive maximum segment size for this TCP connection"
              ::= { fsTcpConnEntry 11 }

          fsTcpConnSRT OBJECT-TYPE
              SYNTAX      INTEGER (0..65535)
              MAX-ACCESS  read-only
              STATUS      current
              DESCRIPTION
                      "The smooth round trip time for this TCP connection. It is
                       updated based on the round trip time."
              ::= { fsTcpConnEntry 12 }

	  fsTcpConnRTDE OBJECT-TYPE
              SYNTAX      INTEGER (0..65535)
              MAX-ACCESS  read-only
              STATUS      current
              DESCRIPTION
                      "The round trip deviation estimator for this TCP
                       connection. It is updated based on the round trip time."
              ::= { fsTcpConnEntry 13 }

          fsTcpConnPersist OBJECT-TYPE
              SYNTAX      INTEGER (0..65535)
              MAX-ACCESS  read-only
              STATUS      current
              DESCRIPTION
                      "The persist timeout value for this TCP connection"
              ::= { fsTcpConnEntry 14 }

          fsTcpConnRexmt OBJECT-TYPE
              SYNTAX      INTEGER (0..65535)
              MAX-ACCESS  read-only
              STATUS      current
              DESCRIPTION
                      "The retransmit timeout value for this TCP connection"
              ::= { fsTcpConnEntry 15 }

	 fsTcpConnRexmtCnt OBJECT-TYPE
              SYNTAX      INTEGER (0..65535)
              MAX-ACCESS  read-only
              STATUS      current
              DESCRIPTION
                      "The no of retransmissions for this TCP connection"
              ::= { fsTcpConnEntry 16 }

          fsTcpConnSBCount OBJECT-TYPE
              SYNTAX      INTEGER (0..65535)
              MAX-ACCESS  read-only
              STATUS      current
              DESCRIPTION
                      "The number of valid bytes from the send buffer which are
                       to be sent to the peer TCP for this TCP connection"
              ::= { fsTcpConnEntry 17 }

          fsTcpConnSBSize OBJECT-TYPE
              SYNTAX      INTEGER (0..65535)
              MAX-ACCESS  read-only
              STATUS      current
              DESCRIPTION
                      "The send buffer size for this TCP connection"
              ::= { fsTcpConnEntry 18 }

	 fsTcpConnRBCount OBJECT-TYPE
              SYNTAX      INTEGER (0..65535)
              MAX-ACCESS  read-only
              STATUS      current
              DESCRIPTION
                      "The number of valid bytes from the receive buffer which
                       are to be sent to the upper application for this TCP
                       connection."
              ::= { fsTcpConnEntry 19 }

          fsTcpConnRBSize OBJECT-TYPE
              SYNTAX      INTEGER (0..65535)
              MAX-ACCESS  read-only
              STATUS      current
              DESCRIPTION
                      "The receive buffer size for this TCP connection."
              ::= { fsTcpConnEntry 20 }

          fsTcpKaMainTmr OBJECT-TYPE
              SYNTAX      INTEGER (0..65535)
              MAX-ACCESS  read-write
              STATUS      current
              DESCRIPTION
                      "The main timeout value used for Keepalive"
              ::= { fsTcpConnEntry 21 }

	  fsTcpKaRetransTmr OBJECT-TYPE
              SYNTAX      INTEGER (0..255)
              MAX-ACCESS  read-write
              STATUS      current
              DESCRIPTION
                      "The retransmission timeout used for Keepalive"
              ::= { fsTcpConnEntry 22 }

          fsTcpKaRetransCnt OBJECT-TYPE
              SYNTAX      INTEGER (0..255)
              MAX-ACCESS  read-write
              STATUS      current
              DESCRIPTION
                      "The no. of retransmissions before aborting the connection during Keepalive"
              ::= { fsTcpConnEntry 23 }

-- TCP Connection Extension Table (RFC 2385 & RFC 5925)

          fsTcpExtConnTable OBJECT-TYPE
              SYNTAX      SEQUENCE OF FsTcpExtConnEntry
              MAX-ACCESS  not-accessible
              STATUS      current
              DESCRIPTION
                      "A table containing TCP connection-specific
                      TCP MD5  & TCP-AO information."
              ::= { fstcp 8 }

          fsTcpExtConnEntry OBJECT-TYPE
              SYNTAX      FsTcpExtConnEntry
              MAX-ACCESS  not-accessible
              STATUS      current
              DESCRIPTION
                      "Information about a particular current TCP
                      connection.  An object of this type is transient,
                      in that it ceases to exist when (or soon after)
                      the connection makes the transition to the CLOSED
                      state."
              AUGMENTS { tcpConnectionEntry }
              ::= { fsTcpExtConnTable 1 }

          FsTcpExtConnEntry ::=
              SEQUENCE {
                  fsTcpConnMD5Option
                      TruthValue,
                  fsTcpConnMD5ErrCtr
                      INTEGER,
                  fsTcpConnTcpAOOption
                      TruthValue,
                  fsTcpConTcpAOCurKeyId
                      Integer32,
                  fsTcpConTcpAORnextKeyId
                      Integer32,
                  fsTcpConTcpAORcvKeyId
                      Integer32,
                  fsTcpConTcpAORcvRnextKeyId
                      Integer32,
                  fsTcpConTcpAOConnErrCtr
                      Counter32,
                  fsTcpConTcpAOSndSne
                      Integer32,
                  fsTcpConTcpAORcvSne
                      Integer32
              }

          fsTcpConnMD5Option OBJECT-TYPE
              SYNTAX      TruthValue
              MAX-ACCESS  read-only
              STATUS      current
              DESCRIPTION
                      "A flag to note if MD5 option is enabled for this TCP connection."
              ::= { fsTcpExtConnEntry 1 }

          fsTcpConnMD5ErrCtr OBJECT-TYPE
              SYNTAX      INTEGER (0..65535)
              MAX-ACCESS  read-only
              STATUS      current
              DESCRIPTION
                      "The number of incoming segments dropped due to MD5 authentication failure"
              ::= { fsTcpExtConnEntry 2 }
          fsTcpConnTcpAOOption OBJECT-TYPE
              SYNTAX      TruthValue
              MAX-ACCESS  read-only
              STATUS      current
              DESCRIPTION
                    "A flag to note if TCP-AO option is enabled for
                     this TCP connection."
              ::= { fsTcpExtConnEntry 3 }

          fsTcpConTcpAOCurKeyId OBJECT-TYPE
              SYNTAX      Integer32 (0..255)
              MAX-ACCESS  read-only
              STATUS      current
              DESCRIPTION
                    "Indicates the send key id of the MKT currently
                     used by this TCP session"
              ::= { fsTcpExtConnEntry 4 }

          fsTcpConTcpAORnextKeyId OBJECT-TYPE
              SYNTAX      Integer32 (0..255)
              MAX-ACCESS  read-only
              STATUS      current
              DESCRIPTION
                    "Indicates the receive key id of the MKT currently
                     preferred by the sender for authenticating
                     incoming packets. If the sender wants to change the
                     currently used MKT this field will be updated
                     with receive id of the new MKT. It is filled
                     in the RnextKeyId field of the outgoing packets"
              ::= { fsTcpExtConnEntry 5 }

          fsTcpConTcpAORcvKeyId OBJECT-TYPE
              SYNTAX      Integer32 (0..255)
              MAX-ACCESS  read-only
              STATUS      current
              DESCRIPTION
                    "Indicates the value in the keyId field of
                     the latest received packet on this connection"
              ::= { fsTcpExtConnEntry 6 }

          fsTcpConTcpAORcvRnextKeyId OBJECT-TYPE
              SYNTAX      Integer32 (0..255)
              MAX-ACCESS  read-only
              STATUS      current
              DESCRIPTION
                    "Indicates the value in the RNextKeyId field of
                     the latest received packet on this connection"
              ::= { fsTcpExtConnEntry 7 }

          fsTcpConTcpAOConnErrCtr OBJECT-TYPE
              SYNTAX      Counter32
              MAX-ACCESS  read-only
              STATUS      current
              DESCRIPTION
                    "The number of incoming segments dropped due to
                     TCP-AO authentication failure"
              ::= { fsTcpExtConnEntry 8 }

          fsTcpConTcpAOSndSne OBJECT-TYPE
              SYNTAX      Integer32
              MAX-ACCESS  read-only
              STATUS      current
              DESCRIPTION
                    "Send side SNE(Sequence Number Extension).
                     SNE increments whenever the tcp sequence number
                     rolls over, so that differentiation between TCP
                     segments with same sequence number at different
                     times in a connection is possible. "
              ::= { fsTcpExtConnEntry 9 }

          fsTcpConTcpAORcvSne OBJECT-TYPE
              SYNTAX      Integer32
              MAX-ACCESS  read-only
              STATUS      current
              DESCRIPTION
                    "Receive side SNE(Sequence Number Extension).
                     SNE increments whenever the tcp sequence number
                     rolls over, so that differentiation between TCP
                     segments with same sequence number at different
                     times in a connection is possible. "
              ::= { fsTcpExtConnEntry 10 }

-- TCP traps

          fstcpNotification OBJECT IDENTIFIER ::= {fstcp 11}
          fstcpTrap         OBJECT IDENTIFIER ::= {fstcpNotification 0}
          fstcpObjects      OBJECT IDENTIFIER ::= {fstcpNotification 1}

          fstcpAoLocalAddressType OBJECT-TYPE
              SYNTAX      InetAddressType
              MAX-ACCESS  accessible-for-notify
              STATUS      current
              DESCRIPTION
                   "This object refers to the addresstype of local address of
                    a tcp connection. Used for sending TCP specific Traps."
              ::= { fstcpObjects 1 }

          fstcpAoLocalAddress OBJECT-TYPE
              SYNTAX      InetAddress
              MAX-ACCESS  accessible-for-notify
              STATUS      current
              DESCRIPTION
                   "This object refers to the local address of a
                    tcp connection. Used for sending TCP specific Traps."
              ::= { fstcpObjects 2 }

          fstcpAoLocalPort OBJECT-TYPE
              SYNTAX      InetPortNumber
              MAX-ACCESS  accessible-for-notify
              STATUS      current
              DESCRIPTION
                   "This object refers to the local port of a
                    tcp connection. Used for sending TCP specific Traps."
              ::= { fstcpObjects 3 }

          fstcpAoRemAddressType OBJECT-TYPE
              SYNTAX      InetAddressType
              MAX-ACCESS  accessible-for-notify
              STATUS      current
              DESCRIPTION
                   "This object refers to the addresstype of remote address of
                    a tcp connection. Used for sending TCP specific Traps."
              ::= { fstcpObjects 4 }

          fstcpAoRemAddress OBJECT-TYPE
              SYNTAX      InetAddress
              MAX-ACCESS  accessible-for-notify
              STATUS      current
              DESCRIPTION
                   "This object refers to the remote address of a
                    tcp connection. Used for sending TCP specific Traps."
              ::= { fstcpObjects 5 }

          fstcpAoRemPort OBJECT-TYPE
              SYNTAX      InetPortNumber
              MAX-ACCESS  accessible-for-notify
              STATUS      current
              DESCRIPTION
                   "This object refers to the remote port of a
                    tcp connection. Used for sending TCP specific Traps."
              ::= { fstcpObjects 6 }


          fstcpAoAuthError NOTIFICATION-TYPE
              OBJECTS  {
                  fstcpAoLocalAddressType,
                  fstcpAoLocalAddress,
                  fstcpAoLocalPort,
                  fstcpAoRemAddressType,
                  fstcpAoRemAddress,
                  tcpConnectionRemPort,
                  fsTcpConTcpAOConnErrCtr
                       }
              STATUS       current
              DESCRIPTION
                  "A fstcpTcpAoAuthError trap is generated when TCP-AO
                   authentication fails for incoming packets on a
                   particular TCP connection"
              ::= {fstcpTrap 1}

-- TCP objects for TCP-AO testing

          fsTcpAoConnTestTable OBJECT-TYPE
              SYNTAX      SEQUENCE OF FsTcpAoConnTestEntry
              MAX-ACCESS  not-accessible
              STATUS      current
              DESCRIPTION
                      "A table containing TCP connection-specific
                       TCP-AO information for testing purpose alone."
              ::= { fstcp 12 }

          fsTcpAoConnTestEntry OBJECT-TYPE
              SYNTAX      FsTcpAoConnTestEntry
              MAX-ACCESS  not-accessible
              STATUS      current
              DESCRIPTION
                      "Information about a particular current TCP
                      connection for testing."
              INDEX {
                        fsTcpAoConnTestLclAdrType,
                        fsTcpAoConnTestLclAdress,
                        fsTcpAoConnTestLclPort,
                        fsTcpAoConnTestRmtAdrType,
                        fsTcpAoConnTestRmtAdress,
                        fsTcpAoConnTestRmtPort
                    }
              ::= { fsTcpAoConnTestTable 1 }

          FsTcpAoConnTestEntry ::=
              SEQUENCE {
                  fsTcpAoConnTestLclAdrType
                      InetAddressType,
                  fsTcpAoConnTestLclAdress
                      InetAddress,
                  fsTcpAoConnTestLclPort
                      InetPortNumber,
                  fsTcpAoConnTestRmtAdrType
                      InetAddressType,
                  fsTcpAoConnTestRmtAdress
                      InetAddress,
                  fsTcpAoConnTestRmtPort
                      InetPortNumber,
                  fsTcpConTcpAOIcmpIgnCtr
                      Counter32,
                  fsTcpConTcpAOSilentAccptCtr
                      Counter32
              }

          fsTcpAoConnTestLclAdrType OBJECT-TYPE
              SYNTAX      InetAddressType
              MAX-ACCESS  not-accessible
              STATUS      current
              DESCRIPTION
                   "This object refers to the addresstype of local address of
                    a tcp connection. Used for testing TCP-AO."
              ::= { fsTcpAoConnTestEntry 1 }

          fsTcpAoConnTestLclAdress OBJECT-TYPE
              SYNTAX      InetAddress
              MAX-ACCESS  not-accessible
              STATUS      current
              DESCRIPTION
                   "This object refers to the local address of a
                    tcp connection. Used for testing TCP-AO"
              ::= { fsTcpAoConnTestEntry 2 }

          fsTcpAoConnTestLclPort OBJECT-TYPE
              SYNTAX      InetPortNumber
              MAX-ACCESS  not-accessible
              STATUS      current
              DESCRIPTION
                   "This object refers to the local port of a
                    tcp connection. Used for testing TCP-AO"
              ::= { fsTcpAoConnTestEntry 3 }

          fsTcpAoConnTestRmtAdrType OBJECT-TYPE
              SYNTAX      InetAddressType
              MAX-ACCESS  not-accessible
              STATUS      current
              DESCRIPTION
                   "This object refers to the addresstype of local address of
                    a tcp connection. Used for testing TCP-AO."
              ::= { fsTcpAoConnTestEntry 4 }

          fsTcpAoConnTestRmtAdress OBJECT-TYPE
              SYNTAX      InetAddress
              MAX-ACCESS  not-accessible
              STATUS      current
              DESCRIPTION
                   "This object refers to the local address of a
                    tcp connection. Used for testing TCP-AO"
              ::= { fsTcpAoConnTestEntry 5 }

          fsTcpAoConnTestRmtPort OBJECT-TYPE
              SYNTAX      InetPortNumber
              MAX-ACCESS  not-accessible
              STATUS      current
              DESCRIPTION
                   "This object refers to the local port of a
                    tcp connection. Used for testing TCP-AO"
              ::= { fsTcpAoConnTestEntry 6 }

          fsTcpConTcpAOIcmpIgnCtr OBJECT-TYPE
              SYNTAX      Counter32
              MAX-ACCESS  read-only
              STATUS      current
              DESCRIPTION
                   "This object refers to the number of ICMPv4
                    type 3 and ICMPv6 type 1 messages ignored on
                    this tcp connection. Used for testing TCP-AO"
              ::= { fsTcpAoConnTestEntry 7 }

          fsTcpConTcpAOSilentAccptCtr OBJECT-TYPE
              SYNTAX      Counter32
              MAX-ACCESS  read-only
              STATUS      current
              DESCRIPTION
                   "This object refers to the number of TCP-AO silent
                    accepts (due to no matching MKT config for
                    a received segment with TCP-AO option)
                    on this connection.  Used for testing TCP-AO"
              ::= { fsTcpAoConnTestEntry 8 }

END
