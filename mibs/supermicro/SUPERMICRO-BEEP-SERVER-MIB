-- Copyright (C) 2008-2014 Super Micro Computer Inc. All Rights Reserved

-- $Id: fsbpsrv.mib,v 1.2 2012/09/07 09:52:04 siva Exp $

SUPERMICRO-BEEP-SERVER-MIB DEFINITIONS ::= BEGIN
   IMPORTS
    OBJECT-TYPE, Integer32, enterprises,
    MODULE-IDENTITY FROM SNMPv2-SMI;

fsBeepServer MODULE-IDENTITY
    LAST-UPDATED "201209050000Z"
    ORGANIZATION "Super Micro Computer Inc."
    CONTACT-INFO "support@Supermicro.com"
         DESCRIPTION
             "The proprietary MIB module for Beep Server. The MIB provides
              objects for configuring Beep Server Modules."
         REVISION "201209050000Z"
         DESCRIPTION
             "The proprietary MIB module for Beep Server. The MIB provides
              objects for configuring Beep Server Modules."

        ::=  { enterprises supermicro-computer-inc(10876) super-switch(101) extended(2) 18}



         fsBeepServerScalars     OBJECT IDENTIFIER ::= { fsBeepServer 1 }

         fsBeepServerAdminStatus OBJECT-TYPE
         SYNTAX                  INTEGER { enabled (1) , disabled(2) }
         MAX-ACCESS              read-write
         STATUS                  current
         DESCRIPTION             "The Beep Server Adminstatus which enables or
                                  disables beep server functionality"
         DEFVAL                  {disabled}
         ::= {fsBeepServerScalars  1 }


         fsBeepServerRawProfile   OBJECT-TYPE
         SYNTAX                  INTEGER { enabled (1) , disabled(2) }
         MAX-ACCESS              read-only
         STATUS                  current
         DESCRIPTION             "To enable or disable RAW profile support for
                                  Beep server. Raw profile is used for reliable
                                  delivery of syslog messages"
          DEFVAL                  { enabled }
         ::= {fsBeepServerScalars  2 }


         fsBeepServerIpv4PortNum     OBJECT-TYPE
         SYNTAX                  Integer32  (1..4096)
         MAX-ACCESS              read-write
         STATUS                  current
         DESCRIPTION             "The TCP port number for Beep server to
                                  listen the incoming IPv4 connections from the
                                  beep clients"
         DEFVAL                  { 601 }
         ::= {fsBeepServerScalars  3 }


         fsBeepServerIpv6PortNum     OBJECT-TYPE
         SYNTAX                  Integer32  (1..4096)
         MAX-ACCESS              read-write
         STATUS                  current
         DESCRIPTION             "The TCP port number for Beep server to listen
                                  the incoming IPv6 connections from the beep
                                  clients"
         DEFVAL                  { 601 }
         ::= {fsBeepServerScalars  4 }


-- SCALAR_END fsbeep Server
END
