-- Copyright (C) 2008-2014 Super Micro Computer Inc. All Rights Reserved

-- $Id: fsmsbfd.mib,v 1.3 2012/09/07 09:52:05 siva Exp $

--BFD-STD-MI-MIB

SUPERMICRO-BFD-STD-MI-MIB DEFINITIONS ::= BEGIN

    IMPORTS
        MODULE-IDENTITY, OBJECT-TYPE, NOTIFICATION-TYPE,
             enterprises, Integer32, Unsigned32, Counter32, Counter64
            FROM SNMPv2-SMI

        TruthValue, RowStatus, StorageType, TimeStamp, DisplayString
            FROM SNMPv2-TC

        InterfaceIndexOrZero
            FROM IF-MIB

        InetAddress, InetAddressType, InetPortNumber
            FROM INET-ADDRESS-MIB

        BfdSessIndexTC, BfdIntervalTC, BfdMultiplierTC, BfdDiagTC,
        BfdSessTypeTC, BfdSessOperModeTC, BfdCtrlDestPortNumberTC,
        BfdCtrlSourcePortNumberTC, BfdSessStateTC,BfdSessAuthenticationTypeTC,
        BfdSessionAuthenticationKeyTC
            FROM BFD-TC-STD-MIB;

        fsMIStdBfd MODULE-IDENTITY
        LAST-UPDATED "201209050000Z"
	ORGANIZATION "Super Micro Computer Inc."
        CONTACT-INFO "support@Supermicro.com"

       DESCRIPTION
	      "This Proprietary MIB for BFD is to provide proactive
               mechanism to detect faults using BFD."

       REVISION "201209050000Z"
       DESCRIPTION  " Initial Version."

        ::= { enterprises supermicro-computer-inc(10876) super-switch(101) extended(2) 54 }

 -- Top level components of this MIB module.

    fsMIStdBfdNotifications OBJECT IDENTIFIER ::= { fsMIStdBfd 0 }

    fsMIStdBfdGlobals       OBJECT IDENTIFIER ::= { fsMIStdBfd 1 }

    fsMIStdBfdObjects       OBJECT IDENTIFIER ::= { fsMIStdBfd 2 }


 -- BFD General Variables

 -- These parameters apply globally to the Systems'
 -- BFD Process.
 -- ------------------------------------------------------------
 -- Bfd Global Objects per context
 -- ------------------------------------------------------------

    fsMIStdBfdGlobalConfigTable OBJECT-TYPE
        SYNTAX      SEQUENCE OF FsMIStdBfdGlobalConfigTableEntry
        MAX-ACCESS  not-accessible
        STATUS      current
        DESCRIPTION
            "This table contains all the global configurations of BFD
             per virtual context of the router."
        ::= {  fsMIStdBfdGlobals 1 }

    fsMIStdBfdGlobalConfigTableEntry OBJECT-TYPE
        SYNTAX      FsMIStdBfdGlobalConfigTableEntry
        MAX-ACCESS  not-accessible
        STATUS      current
        DESCRIPTION
            "This represents per virtual context BFD  Global parameters.
             An entry in this table is created when a virtual context
             is created."
        INDEX { fsMIStdBfdContextId }
        ::= { fsMIStdBfdGlobalConfigTable 1 }

    FsMIStdBfdGlobalConfigTableEntry ::= SEQUENCE {
        fsMIStdBfdContextId                 Unsigned32,
        fsMIStdBfdAdminStatus               INTEGER,
        fsMIStdBfdSessNotificationsEnable   TruthValue
    }

    fsMIStdBfdContextId OBJECT-TYPE
        SYNTAX      Unsigned32
        MAX-ACCESS  not-accessible
        STATUS      current
        DESCRIPTION
            "The unique identifier to identify the virtual router context."
        ::= { fsMIStdBfdGlobalConfigTableEntry 1 }

    fsMIStdBfdAdminStatus OBJECT-TYPE
        SYNTAX     INTEGER {
            enabled(1),
            disabled(2)
        }
        MAX-ACCESS read-write
        STATUS     current
        DESCRIPTION
            "The global administrative status of BFD in this router.
             The value 'enabled' denotes that the BFD Process is
             active on at least one interface; 'disabled' disables
             it on all interfaces."
        DEFVAL { enabled }
        ::= { fsMIStdBfdGlobalConfigTableEntry 2 }

    fsMIStdBfdSessNotificationsEnable OBJECT-TYPE
        SYNTAX     TruthValue
        MAX-ACCESS read-write
        STATUS     current
        DESCRIPTION
            "If this object is set to true(1), then it enables
             the emission of bfdSessUp and bfdSessDown
             notifications; otherwise these notifications are not
             emitted."
        REFERENCE
            "See also RFC3413 for explanation that
             notifications are under the ultimate control of the
             MIB modules in this document."
        DEFVAL { false }
        ::= { fsMIStdBfdGlobalConfigTableEntry 3 }



 -- ------------------------------------------------------------
 -- Bfd Objects per context for per session config
 -- ------------------------------------------------------------
 -- BFD Session Table
 -- The BFD Session Table specifies BFD session specific
 -- information.

    fsMIStdBfdSessTable OBJECT-TYPE
        SYNTAX     SEQUENCE OF FsMIStdBfdSessEntry
        MAX-ACCESS not-accessible
        STATUS     current
        DESCRIPTION
            "The BFD Session Table describes the BFD sessions
             per virtual context of the router."
        REFERENCE
            "BFD Version 0 (draft-katz-ward-bfd-02.txt) and
             BFD Version 1 (RFC5880)"
        ::= { fsMIStdBfdObjects 1 }

    fsMIStdBfdSessEntry OBJECT-TYPE
        SYNTAX     FsMIStdBfdSessEntry
        MAX-ACCESS not-accessible
        STATUS     current
        DESCRIPTION
            "The BFD Session Entry describes BFD session per
             virtual context of the router."
        INDEX {
                fsMIStdBfdContextId,
                fsMIStdBfdSessIndex
              }
        ::= { fsMIStdBfdSessTable 1 }

   FsMIStdBfdSessEntry ::= SEQUENCE {
        fsMIStdBfdSessIndex                    BfdSessIndexTC,
        fsMIStdBfdSessVersionNumber            Unsigned32,
        fsMIStdBfdSessType                     BfdSessTypeTC,
        fsMIStdBfdSessDiscriminator            Unsigned32,
        fsMIStdBfdSessRemoteDiscr              Unsigned32,
        fsMIStdBfdSessDestinationUdpPort       BfdCtrlDestPortNumberTC,
        fsMIStdBfdSessSourceUdpPort            BfdCtrlSourcePortNumberTC,
        fsMIStdBfdSessEchoSourceUdpPort        InetPortNumber,
        fsMIStdBfdSessAdminStatus              INTEGER,
        fsMIStdBfdSessState                    BfdSessStateTC,
        fsMIStdBfdSessRemoteHeardFlag          TruthValue,
        fsMIStdBfdSessDiag                     BfdDiagTC,
        fsMIStdBfdSessOperMode                 BfdSessOperModeTC,
        fsMIStdBfdSessDemandModeDesiredFlag    TruthValue,
        fsMIStdBfdSessControlPlaneIndepFlag    TruthValue,
        fsMIStdBfdSessMultipointFlag           TruthValue,
        fsMIStdBfdSessInterface                InterfaceIndexOrZero,
        fsMIStdBfdSessSrcAddrType              InetAddressType,
        fsMIStdBfdSessSrcAddr                  InetAddress,
        fsMIStdBfdSessDstAddrType              InetAddressType,
        fsMIStdBfdSessDstAddr                  InetAddress,
        fsMIStdBfdSessGTSM                     TruthValue,
        fsMIStdBfdSessGTSMTTL                  Unsigned32,
        fsMIStdBfdSessDesiredMinTxInterval     BfdIntervalTC,
        fsMIStdBfdSessReqMinRxInterval         BfdIntervalTC,
        fsMIStdBfdSessReqMinEchoRxInterval     BfdIntervalTC,
        fsMIStdBfdSessDetectMult               BfdMultiplierTC,
        fsMIStdBfdSessNegotiatedInterval       BfdIntervalTC,
        fsMIStdBfdSessNegotiatedEchoInterval   BfdIntervalTC,
        fsMIStdBfdSessNegotiatedDetectMult     BfdMultiplierTC,
        fsMIStdBfdSessAuthPresFlag             TruthValue,
        fsMIStdBfdSessAuthenticationType       BfdSessAuthenticationTypeTC,
        fsMIStdBfdSessAuthenticationKeyID      Integer32,
        fsMIStdBfdSessAuthenticationKey        BfdSessionAuthenticationKeyTC,
        fsMIStdBfdSessStorType                 StorageType,
        fsMIStdBfdSessRowStatus                RowStatus
    }

    fsMIStdBfdSessIndex OBJECT-TYPE
        SYNTAX     BfdSessIndexTC
        MAX-ACCESS not-accessible
        STATUS     current
        DESCRIPTION
            "This object contains an index used to represent a
             unique BFD session on this device."
        ::= { fsMIStdBfdSessEntry 1 }

    fsMIStdBfdSessVersionNumber OBJECT-TYPE
        SYNTAX     Unsigned32 (0..7)
        MAX-ACCESS read-create
        STATUS     current
        DESCRIPTION
            "The version number of the BFD protocol that this session
             is running in. Write access is available for this object
             to provide ability to set desired version for this
             BFD session."
        REFERENCE
            "BFD Version 0 (draft-katz-ward-bfd-02.txt) and
             BFD Version 1 (RFC5880)"
        DEFVAL { 1 }
        ::= { fsMIStdBfdSessEntry 2 }

    fsMIStdBfdSessType OBJECT-TYPE
        SYNTAX     BfdSessTypeTC
        MAX-ACCESS read-create
        STATUS     current
        DESCRIPTION
            "This object specifies the type of this BFD session."
        ::= { fsMIStdBfdSessEntry 3 }

    fsMIStdBfdSessDiscriminator OBJECT-TYPE
        SYNTAX     Unsigned32 (1..4294967295)
        MAX-ACCESS read-only
        STATUS     current
        DESCRIPTION
            "This object specifies the local discriminator for this BFD
             session, used to uniquely identify it."
        ::= { fsMIStdBfdSessEntry 4 }

    fsMIStdBfdSessRemoteDiscr OBJECT-TYPE
        SYNTAX     Unsigned32 (0 | 1..4294967295)
        MAX-ACCESS read-only
        STATUS     current
        DESCRIPTION
            "This object specifies the session discriminator chosen
             by the remote system for this BFD session.  The value may
             be zero(0) if the remote discriminator is not yet known
             or if the session is in the down or adminDown(1) state."
        REFERENCE
            "RFC5880, Section 6.8.6"
        ::= { fsMIStdBfdSessEntry 5 }

    fsMIStdBfdSessDestinationUdpPort OBJECT-TYPE
        SYNTAX     BfdCtrlDestPortNumberTC
        MAX-ACCESS read-create
        STATUS     current
        DESCRIPTION
            "This object specifies the destination UDP port number
             used for this BFD session's control packets. The value
             may be zero(0) if the session is in adminDown(1) state."
        DEFVAL { 0 }
        ::= { fsMIStdBfdSessEntry 6 }

    fsMIStdBfdSessSourceUdpPort OBJECT-TYPE
        SYNTAX     BfdCtrlSourcePortNumberTC
        MAX-ACCESS read-create
        STATUS     current
        DESCRIPTION
            "This object specifies the source UDP port number used
             for this BFD session's control packets. The value may be
             zero(0) if the session is in adminDown(1) state. Upon
             creation of a new BFD session via this MIB, the value of
             zero(0) specified would permit the implementation to
             chose its own source port number."
        DEFVAL { 0 }
        ::= { fsMIStdBfdSessEntry 7 }

    fsMIStdBfdSessEchoSourceUdpPort OBJECT-TYPE
        SYNTAX     InetPortNumber
        MAX-ACCESS read-create
        STATUS     current
        DESCRIPTION
            "This object specifies the source UDP port number used for
             this BFD session's echo packets. The value may be zero(0)
             if the session is not running in the echo mode, or the
             session is in adminDown(1) state. Upon creation of a new
             BFD session via this MIB, the value of zero(0) would
             permit the implementation to chose its own source port
             number."
        DEFVAL { 0 }
        ::= { fsMIStdBfdSessEntry 8 }

    fsMIStdBfdSessAdminStatus OBJECT-TYPE
        SYNTAX     INTEGER {
                            stop(1),
                            start(2)
                   }
        MAX-ACCESS read-create
        STATUS     current
        DESCRIPTION
                "A transition from 'stop' to 'start' will start
                 the BFD state machine for the session. The state
                 machine will have an initial state of down.
                 A transition from 'start' to 'stop' will cause
                 the BFD sesssion to be brought down to
                 adminDown(1). Care should be used in providing
                 write access to this object without adequate
                 authentication."
        DEFVAL { 2 }
        ::= { fsMIStdBfdSessEntry 9 }

    fsMIStdBfdSessState OBJECT-TYPE
        SYNTAX     BfdSessStateTC
        MAX-ACCESS read-only
        STATUS     current
        DESCRIPTION
            "BFD session state."
        DEFVAL { 2 }
        ::= { fsMIStdBfdSessEntry 10 }

    fsMIStdBfdSessRemoteHeardFlag OBJECT-TYPE
        SYNTAX     TruthValue
        MAX-ACCESS read-only
        STATUS     current
        DESCRIPTION
            "This object specifies status of BFD packet reception from
             the remote system. Specifically, it is set to true(1) if
             the local system is actively receiving BFD packets from
             the remote system, and is set to false(2) if the local
             system has not received BFD packets recently (within the
             detection time) or if the local system is attempting to
             tear down the BFD session."
        REFERENCE
            "BFD Version 0 (draft-katz-ward-bfd-02.txt) and
             BFD Version 1 (RFC5880)"
        DEFVAL { false }
        ::= { fsMIStdBfdSessEntry 11 }

    fsMIStdBfdSessDiag OBJECT-TYPE
        SYNTAX     BfdDiagTC
        MAX-ACCESS read-only
        STATUS     current
        DESCRIPTION
            "A diagnostic code specifying the local system's reason
             for the last transition of the session from up(4)
             to some other state."
        ::= { fsMIStdBfdSessEntry 12 }

    fsMIStdBfdSessOperMode OBJECT-TYPE
        SYNTAX     BfdSessOperModeTC
        MAX-ACCESS read-create
        STATUS     current
        DESCRIPTION
            "This object specifies current operating mode that BFD
             session is operating in."
    ::= { fsMIStdBfdSessEntry 13 }

    fsMIStdBfdSessDemandModeDesiredFlag OBJECT-TYPE
        SYNTAX     TruthValue
        MAX-ACCESS read-create
        STATUS     current
        DESCRIPTION
            "This object indicates that the local system's
             desire to use Demand mode. Specifically, it is set
             to true(1) if the local system wishes to use
             Demand mode or false(2) if not"
        DEFVAL { false }
        ::= { fsMIStdBfdSessEntry 14 }

    fsMIStdBfdSessControlPlaneIndepFlag OBJECT-TYPE
        SYNTAX     TruthValue
        MAX-ACCESS read-create
        STATUS     current
        DESCRIPTION
            "This object indicates that the local system's
             ability to continue to function through a disruption of
             the control plane. Specifically, it is set
             to true(1) if the local system BFD implementation is
             independent of the control plane. Otherwise, the
             value is set to false(2)"
        DEFVAL { false }
        ::= { fsMIStdBfdSessEntry 15 }

    fsMIStdBfdSessMultipointFlag OBJECT-TYPE
        SYNTAX     TruthValue
        MAX-ACCESS read-create
        STATUS     current
        DESCRIPTION
            "This object indicates the Multipoint (M) bit for this
             session. It is set to true(1) if Multipoint (M) bit is
             set to 1. Otherwise, the value is set to false(2)"
        DEFVAL { false }
        ::= { fsMIStdBfdSessEntry 16 }

    fsMIStdBfdSessInterface OBJECT-TYPE
        SYNTAX     InterfaceIndexOrZero
        MAX-ACCESS read-create
        STATUS     current
        DESCRIPTION
            "This object contains an interface index used to indicate
             the interface which this BFD session is running on. This
             value can be zero if there is no interface associated
             with this BFD session."
        ::= { fsMIStdBfdSessEntry 17 }
     fsMIStdBfdSessSrcAddrType OBJECT-TYPE
        SYNTAX     InetAddressType
        MAX-ACCESS read-create
        STATUS     current
        DESCRIPTION
            "This object specifies IP address type of the source IP
             address of this BFD session. Only values unknown(0),
             ipv4(1), ipv6(2), or ipv6z(4) have to be supported.
             The value of unknown(0) is allowed only when the session
             is singleHop(1) and the source IP address of this BFD
             session is drived from the outgoing interface, or when
             the BFD session is not associated with a specific
             interface. If any other unsupported values are attempted
             in a set operation, the agent MUST return an
             inconsistentValue error."
      ::= { fsMIStdBfdSessEntry 18 }

    fsMIStdBfdSessSrcAddr OBJECT-TYPE
        SYNTAX     InetAddress (SIZE (0|4|16|20))
        MAX-ACCESS read-create
        STATUS     current
        DESCRIPTION
            "This object specifies the source IP address of this BFD
             session."
        ::= { fsMIStdBfdSessEntry 19 }

    fsMIStdBfdSessDstAddrType OBJECT-TYPE
        SYNTAX     InetAddressType
        MAX-ACCESS read-create
        STATUS     current
        DESCRIPTION
            "This object specifies IP address type of the neighboring IP
             address which is being monitored with this BFD session.
             Only values unknown(0), ipv4(1), ipv6(2), or ipv6z(4)
             have to be supported. The value of unknown(0) is allowed
             only when the session is singleHop(1) and the outgoing
             interface is of type point-to-point, or when the BFD
             session is not associated with a specific interface. If
             any other unsupported values are attempted in a set
             operation, the agent MUST return an inconsistentValue
             error."
      ::= { fsMIStdBfdSessEntry 20 }

    fsMIStdBfdSessDstAddr OBJECT-TYPE
        SYNTAX     InetAddress (SIZE (0|4|16|20))
        MAX-ACCESS read-create
        STATUS     current
        DESCRIPTION
            "This object specifies the neighboring IP address which is
             being monitored with this BFD session."
        ::= { fsMIStdBfdSessEntry 21 }

    fsMIStdBfdSessGTSM OBJECT-TYPE
        SYNTAX  TruthValue
        MAX-ACCESS read-create
        STATUS current
        DESCRIPTION
           "Setting the value of this object to true(1) will enable
            GTSM protection of the BFD session.  GTSM MUST be enabled
            on a singleHop(1) session if no authentication is in use."
        REFERENCE
           "RFC5082, The Generalized TTL Security Mechanism (GTSM).
            RFC5881, Section 5"
        DEFVAL { false }
        ::= { fsMIStdBfdSessEntry 22 }

     fsMIStdBfdSessGTSMTTL OBJECT-TYPE
        SYNTAX Unsigned32 (0..255)
        MAX-ACCESS read-create
        STATUS current
        DESCRIPTION
            "This object is valid only when bfdSessGTSM protection is
             enabled on the system. This object specifies the minimum
             allowed TTL for received BFD control packets. For
             singleHop(1) session, if GTSM protection is enabled,
             this object SHOULD be set to maximum TTL allowed for
             single hop. The value of zero(0) indicates that
             bfdSessGTSM is disabled."
        REFERENCE
           "RFC5082, The Generalized TTL Security Mechanism (GTSM).
            RFC5881, Section 5"
        DEFVAL { 0 }
        ::= { fsMIStdBfdSessEntry 23 }

    fsMIStdBfdSessDesiredMinTxInterval OBJECT-TYPE
        SYNTAX     BfdIntervalTC
        MAX-ACCESS read-create
        STATUS     current
        DESCRIPTION
            "This object specifies the minimum interval, in
             microseconds, that the local system would like to use
             when transmitting BFD Control packets. The value of
             zero(0) is reserved, and should not be used."
        REFERENCE
            "RFC5880, Section 4.1"
        ::= { fsMIStdBfdSessEntry 24 }

    fsMIStdBfdSessReqMinRxInterval OBJECT-TYPE
       SYNTAX     BfdIntervalTC
        MAX-ACCESS read-create
        STATUS     current
        DESCRIPTION
            "This object specifies the minimum interval, in
             microseconds, between received BFD Control packets the
             local system is capable of supporting. The value of
             zero(0) can be specified when the transmitting system
             does not want the remote system to send any periodic BFD
             control packets."
        REFERENCE
            "RFC5880, Section 4.1"
        ::= { fsMIStdBfdSessEntry 25 }

    fsMIStdBfdSessReqMinEchoRxInterval OBJECT-TYPE
        SYNTAX     BfdIntervalTC
        MAX-ACCESS read-create
        STATUS     current
        DESCRIPTION
            "This object specifies the minimum interval, in
             microseconds, between received BFD Echo packets that this
             system is capable of supporting. Value must be zero(0) if
             this is a multihop BFD session."
        ::= { fsMIStdBfdSessEntry 26 }

    fsMIStdBfdSessDetectMult OBJECT-TYPE
        SYNTAX     BfdMultiplierTC
        MAX-ACCESS read-create
        STATUS     current
        DESCRIPTION
            "This object specifies the Detect time multiplier."
        ::= { fsMIStdBfdSessEntry 27 }

    fsMIStdBfdSessNegotiatedInterval OBJECT-TYPE
        SYNTAX     BfdIntervalTC
        MAX-ACCESS read-only
        STATUS     current
        DESCRIPTION
            "This object specifies the negotiated interval, in
             microseconds, that the local system is transmitting
             BFD Control packets."
        ::= { fsMIStdBfdSessEntry 28 }

    fsMIStdBfdSessNegotiatedEchoInterval OBJECT-TYPE
        SYNTAX     BfdIntervalTC
        MAX-ACCESS read-only
        STATUS     current
        DESCRIPTION
            "This object specifies the negotiated interval, in
             microseconds, that the local system is transmitting
             BFD echo packets. Value is expected to be zero if
             the sessions is not running in echo mode."
        ::= { fsMIStdBfdSessEntry 29 }

    fsMIStdBfdSessNegotiatedDetectMult OBJECT-TYPE
        SYNTAX     BfdMultiplierTC
        MAX-ACCESS read-only
        STATUS     current
        DESCRIPTION
            "This object specifies the Detect time multiplier."
        ::= { fsMIStdBfdSessEntry 30 }

    fsMIStdBfdSessAuthPresFlag OBJECT-TYPE
        SYNTAX     TruthValue
        MAX-ACCESS read-create
        STATUS     current
        DESCRIPTION
            "This object indicates that the local system's
             desire to use Authentication. Specifically, it is set
             to true(1) if the local system wishes the session
             to be authenticated or false(2) if not."
        REFERENCE
            "RFC5880, Sections 4.2 - 4.4"
        DEFVAL { false }
        ::= { fsMIStdBfdSessEntry 31 }

    fsMIStdBfdSessAuthenticationType OBJECT-TYPE
        SYNTAX     BfdSessAuthenticationTypeTC
        MAX-ACCESS read-create
        STATUS     current
        DESCRIPTION
            "The Authentication Type used for this BFD session.
             This field is valid only when the Authentication
             Present bit is set. Max-access to this object as well as
             other authentication related objects are set to
             read-create in order to support management of a single
             key ID at a time, key rotation is not handled. Key update
             in practice must be done by atomic update using a set
             containing all affected objects in the same varBindList
             or otherwise risk the session dropping. Value -1
             indicates that no authentication is in use for this
             session."
        REFERENCE
            "RFC5880, Sections 4.2 - 4.4"
        DEFVAL { -1 }
        ::= { fsMIStdBfdSessEntry 32 }

    fsMIStdBfdSessAuthenticationKeyID OBJECT-TYPE
        SYNTAX     Integer32 (-1 | 0..255)
        MAX-ACCESS read-create
        STATUS     current
        DESCRIPTION
            "The authentication key ID in use for this session.  This
             object permits multiple keys to be active simultaneously.
             When fsMIStdBfdSessAuthPresFlag is false(2), then the value
             of this object MUST be -1.  The value -1 indicates that
             no Authentication Key ID will be present in the optional
             BFD Authentication Section."
        REFERENCE
            "RFC5880, Sections 4.2 - 4.4"
        DEFVAL { -1 }
        ::= { fsMIStdBfdSessEntry 33 }

    fsMIStdBfdSessAuthenticationKey OBJECT-TYPE
        SYNTAX     BfdSessionAuthenticationKeyTC
        MAX-ACCESS read-create
        STATUS     current
        DESCRIPTION
            "The authentication key.  When the
             fsMIStdBfdSessAuthenticationType is simplePassword(1), the value
             of this object is the password present in the BFD packets.

             When the fsMIStdBfdSessAuthenticationType is one of the keyed
             authentication types, this value is used in the
             computation of the key present in the BFD authentication
             packet."
        REFERENCE
            "RFC5880, Sections 4.2 - 4.4"
        ::= { fsMIStdBfdSessEntry 34 }

    fsMIStdBfdSessStorType OBJECT-TYPE
        SYNTAX     StorageType
        MAX-ACCESS read-create
        STATUS     current
        DESCRIPTION
            "This variable indicates the storage type for this
             object. Conceptual rows having the value
             'permanent' need not allow write-access to any
             columnar objects in the row."
        ::= { fsMIStdBfdSessEntry 35 }

    fsMIStdBfdSessRowStatus OBJECT-TYPE
        SYNTAX     RowStatus
        MAX-ACCESS read-create
        STATUS     current
        DESCRIPTION
            "This variable is used to create, modify, and/or
             delete a row in this table. When a row in this
             table has a row in the active(1) state, no
             objects in this row can be modified except the
             fsMIStdBfdSessRowStatus and fsMIStdBfdSessStorType."
        ::= { fsMIStdBfdSessEntry 36 }

 -- ------------------------------------------------------------
 -- Bfd Objects per context for session performance
 -- ------------------------------------------------------------
 -- BFD Session Performance Table

    fsMIStdBfdSessPerfTable OBJECT-TYPE
        SYNTAX     SEQUENCE OF FsMIStdBfdSessPerfEntry
        MAX-ACCESS not-accessible
        STATUS     current
        DESCRIPTION
            "This table specifies BFD Session performance counters
             per virtual context of the router."
        ::= { fsMIStdBfdObjects 2 }

    fsMIStdBfdSessPerfEntry OBJECT-TYPE
        SYNTAX     FsMIStdBfdSessPerfEntry
        MAX-ACCESS not-accessible
        STATUS     current
        DESCRIPTION
            "An entry in this table is created by a BFD-enabled node
             for every BFD Session. fsMIStdBfdSessPerfDiscTime is used to
             indicate potential discontinuity for all counter objects
             in this table."
        AUGMENTS    { fsMIStdBfdSessEntry }
        ::= { fsMIStdBfdSessPerfTable 1 }

    FsMIStdBfdSessPerfEntry ::= SEQUENCE {
       fsMIStdBfdSessPerfCtrlPktIn           Counter32,
       fsMIStdBfdSessPerfCtrlPktOut          Counter32,
       fsMIStdBfdSessPerfCtrlPktDrop         Counter32,
       fsMIStdBfdSessPerfCtrlPktDropLastTime TimeStamp,
       fsMIStdBfdSessPerfEchoPktIn           Counter32,
       fsMIStdBfdSessPerfEchoPktOut          Counter32,
       fsMIStdBfdSessPerfEchoPktDrop         Counter32,
       fsMIStdBfdSessPerfEchoPktDropLastTime TimeStamp,
       fsMIStdBfdSessUpTime                  TimeStamp,
       fsMIStdBfdSessPerfLastSessDownTime    TimeStamp,
       fsMIStdBfdSessPerfLastCommLostDiag    BfdDiagTC,
       fsMIStdBfdSessPerfSessUpCount         Counter32,
       fsMIStdBfdSessPerfDiscTime            TimeStamp,

       -- High Capacity Counters
       fsMIStdBfdSessPerfCtrlPktInHC         Counter64,
       fsMIStdBfdSessPerfCtrlPktOutHC        Counter64,
       fsMIStdBfdSessPerfCtrlPktDropHC       Counter64,
       fsMIStdBfdSessPerfEchoPktInHC         Counter64,
       fsMIStdBfdSessPerfEchoPktOutHC        Counter64,

       fsMIStdBfdSessPerfEchoPktDropHC       Counter64
    }

 -- Ed Note: should we add per-diag code counts here,

    fsMIStdBfdSessPerfCtrlPktIn OBJECT-TYPE
        SYNTAX     Counter32
        MAX-ACCESS read-only
        STATUS     current
        DESCRIPTION
            "The total number of BFD control messages received for this
             BFD session. This value MUST be equal to the least
             significant 32 bits of fsMIStdBfdSessPerfCtrlPktInHC."
        ::= { fsMIStdBfdSessPerfEntry 1 }

    fsMIStdBfdSessPerfCtrlPktOut OBJECT-TYPE
        SYNTAX     Counter32
        MAX-ACCESS read-only
        STATUS     current
        DESCRIPTION
            "The total number of BFD control messages sent for this BFD
             session. This value MUST be equal to the least significant
             32 bits of fsMIStdBfdSessPerfCtrlPktOutHC."
        ::= { fsMIStdBfdSessPerfEntry 2 }

    fsMIStdBfdSessPerfCtrlPktDrop OBJECT-TYPE
        SYNTAX     Counter32
        MAX-ACCESS read-only
        STATUS     current
        DESCRIPTION
            "The total number of BFD control messages received for this
             session yet dropped for being invalid. This value MUST be
             equal to the least significant 32 bits of
             fsMIStdBfdSessPerfCtrlPktDropHC."
        ::= { fsMIStdBfdSessPerfEntry 3 }

    fsMIStdBfdSessPerfCtrlPktDropLastTime OBJECT-TYPE
        SYNTAX     TimeStamp
        MAX-ACCESS read-only
        STATUS     current
        DESCRIPTION
            "The value of sysUpTime on the most recent occasion at
             which received BFD control message for this session was
             dropped. If no such up event exists, this object contains
             a zero value."
        ::= { fsMIStdBfdSessPerfEntry 4 }

    fsMIStdBfdSessPerfEchoPktIn OBJECT-TYPE
        SYNTAX     Counter32
      MAX-ACCESS read-only
        STATUS     current
        DESCRIPTION
            "The total number of BFD echo messages received for this
             BFD session. This value MUST be equal to the least
             significant 32 bits of fsMIStdBfdSessPerfEchoPktInHC."
        ::= { fsMIStdBfdSessPerfEntry 5 }

    fsMIStdBfdSessPerfEchoPktOut OBJECT-TYPE
        SYNTAX     Counter32
        MAX-ACCESS read-only
        STATUS     current
        DESCRIPTION
            "The total number of BFD echo messages sent for this BFD
             session. This value MUST be equal to the least significant
             32 bits of fsMIStdBfdSessPerfEchoPktOutHC."
        ::= { fsMIStdBfdSessPerfEntry 6 }

    fsMIStdBfdSessPerfEchoPktDrop OBJECT-TYPE
        SYNTAX     Counter32
        MAX-ACCESS read-only
        STATUS     current
        DESCRIPTION
            "The total number of BFD echo messages received for this
             session yet dropped for being invalid. This value MUST be
             equal to the least significant 32 bits of
             fsMIStdBfdSessPerfEchoPktDropHC."
        ::= { fsMIStdBfdSessPerfEntry 7 }

    fsMIStdBfdSessPerfEchoPktDropLastTime OBJECT-TYPE
        SYNTAX     TimeStamp
        MAX-ACCESS read-only
        STATUS     current
        DESCRIPTION
            "The value of sysUpTime on the most recent occasion at
             which received BFD echo message for this session was
             dropped. If no such up event exists, this object contains
             a zero value."
        ::= { fsMIStdBfdSessPerfEntry 8 }

    fsMIStdBfdSessUpTime OBJECT-TYPE
        SYNTAX     TimeStamp
        MAX-ACCESS read-only
        STATUS     current
        DESCRIPTION
            "The value of sysUpTime on the most recent occasion at
             which the session came up. If no such up event exists this
             object contains a zero value."
        ::= { fsMIStdBfdSessPerfEntry 9 }

    fsMIStdBfdSessPerfLastSessDownTime OBJECT-TYPE
        SYNTAX     TimeStamp
        MAX-ACCESS read-only
        STATUS     current
        DESCRIPTION
            "The value of sysUpTime on the most recent occasion at
             which the last time communication was lost with the
             neighbor. If no such down event exist this object
             contains a zero value."
        ::= { fsMIStdBfdSessPerfEntry 10 }

    fsMIStdBfdSessPerfLastCommLostDiag OBJECT-TYPE
        SYNTAX     BfdDiagTC
        MAX-ACCESS read-only
        STATUS     current
        DESCRIPTION
            "The BFD diag code for the last time communication was lost
             with the neighbor. If no such down event exists this object
             contains a zero value."
        ::= { fsMIStdBfdSessPerfEntry 11 }

    fsMIStdBfdSessPerfSessUpCount OBJECT-TYPE
        SYNTAX     Counter32
        MAX-ACCESS read-only
        STATUS     current
        DESCRIPTION
            "The number of times this session has gone into the Up
             state since the system last rebooted."
        ::= { fsMIStdBfdSessPerfEntry 12 }

    fsMIStdBfdSessPerfDiscTime OBJECT-TYPE
        SYNTAX     TimeStamp
        MAX-ACCESS read-only
        STATUS     current
        DESCRIPTION
          "The value of sysUpTime on the most recent occasion at
           which any one or more of the session counters suffered
           a discontinuity.
           The relevant counters are the specific instances associated
           with this BFD session of any Counter32 object contained in
           the BfdSessPerfTable. If no such discontinuities have
           occurred since the last re-initialization of the local
           management subsystem, then this object contains a zero
           value."
        ::= { fsMIStdBfdSessPerfEntry 13 }

    fsMIStdBfdSessPerfCtrlPktInHC OBJECT-TYPE
        SYNTAX     Counter64
        MAX-ACCESS read-only
        STATUS     current
        DESCRIPTION
            "This value represents the total number of BFD control
             messages received for this BFD session."
        ::= { fsMIStdBfdSessPerfEntry 14 }

    fsMIStdBfdSessPerfCtrlPktOutHC OBJECT-TYPE
        SYNTAX     Counter64
        MAX-ACCESS read-only
        STATUS     current
        DESCRIPTION
            "This value represents the total number of BFD control
             messages transmitted for this BFD session."
        ::= { fsMIStdBfdSessPerfEntry 15 }

    fsMIStdBfdSessPerfCtrlPktDropHC OBJECT-TYPE
        SYNTAX     Counter64
        MAX-ACCESS read-only
        STATUS     current
        DESCRIPTION
            "This value represents the total number of BFD control
             messages received for this BFD session yet dropped for
             being invalid."
        ::= { fsMIStdBfdSessPerfEntry 16 }

    fsMIStdBfdSessPerfEchoPktInHC OBJECT-TYPE
        SYNTAX     Counter64
        MAX-ACCESS read-only
        STATUS     current
        DESCRIPTION
            "This value represents the total number of BFD echo
             messages received for this BFD session."
        ::= { fsMIStdBfdSessPerfEntry 17 }

    fsMIStdBfdSessPerfEchoPktOutHC OBJECT-TYPE
        SYNTAX     Counter64
        MAX-ACCESS read-only
        STATUS     current
        DESCRIPTION
            "This value represents the total number of BFD echo
             messages transmitted for this BFD session."
        ::= { fsMIStdBfdSessPerfEntry 18 }

    fsMIStdBfdSessPerfEchoPktDropHC OBJECT-TYPE
        SYNTAX     Counter64
        MAX-ACCESS read-only
        STATUS     current
        DESCRIPTION
           "This value represents the total number of BFD echo
             messages received for this BFD session yet dropped
             for being invalid."
        ::= { fsMIStdBfdSessPerfEntry 19 }

-- ------------------------------------------------------------
 -- Bfd Objects per context for Discriminator Mapping
 -- ------------------------------------------------------------

 -- BFD Session Discriminator Mapping Table

    fsMIStdBfdSessDiscMapTable OBJECT-TYPE
        SYNTAX     SEQUENCE OF FsMIStdBfdSessDiscMapEntry
        MAX-ACCESS not-accessible
        STATUS     current
        DESCRIPTION
            "The BFD Session Discriminator Mapping Table maps a
             local discriminator value to associated BFD session's
             BfdSessIndexTC used in the fsMIStdBfdSessTable ."
        ::= { fsMIStdBfdObjects 3 }

    fsMIStdBfdSessDiscMapEntry OBJECT-TYPE
        SYNTAX     FsMIStdBfdSessDiscMapEntry
        MAX-ACCESS not-accessible
        STATUS     current
        DESCRIPTION
            "The BFD Session Discriminator Map Entry describes
             BFD session that is mapped to this BfdSessIndexTC."
        INDEX {
                    fsMIStdBfdContextId,
                    fsMIStdBfdSessDiscriminator
              }
        ::= { fsMIStdBfdSessDiscMapTable 1 }

    FsMIStdBfdSessDiscMapEntry ::= SEQUENCE {
        fsMIStdBfdSessDiscMapIndex            BfdSessIndexTC
    }

    fsMIStdBfdSessDiscMapIndex OBJECT-TYPE
        SYNTAX     BfdSessIndexTC
        MAX-ACCESS read-only
        STATUS     current
        DESCRIPTION
            "This object specifies the BfdSessIndexTC referred to by
             the indices of this row. In essence, a mapping is
             provided between these indexes and the fsMIStdBfdSessTable."
        ::= { fsMIStdBfdSessDiscMapEntry 1 }

-- ------------------------------------------------------------
 -- Bfd Objects per context for IP Mapping
 -- ------------------------------------------------------------
 -- BFD Session IP Mapping Table

    fsMIStdBfdSessIpMapTable OBJECT-TYPE
        SYNTAX     SEQUENCE OF FsMIStdBfdSessIpMapEntry
        MAX-ACCESS not-accessible
        STATUS     current
        DESCRIPTION
            "The BFD Session IP Mapping Table maps given
             fsMIStdBfdSessInterface, fsMIStdBfdSessSrcAddrType,
             fsMIStdBfdSessSrcAddr,
             bfdSessDstAddrType and bfdSessDstAddr
             to an associated BFD session's BfdSessIndexTC used in
             the fsMIStdBfdSessTable."
        ::= { fsMIStdBfdObjects 4 }

    fsMIStdBfdSessIpMapEntry OBJECT-TYPE
        SYNTAX     FsMIStdBfdSessIpMapEntry
        MAX-ACCESS not-accessible
        STATUS     current
        DESCRIPTION
           "The BFD Session IP Map Entry describes
            BFD session that is mapped to this BfdSessIndexTC."
        INDEX {
            fsMIStdBfdContextId,
            fsMIStdBfdSessInterface,
            fsMIStdBfdSessSrcAddrType,
            fsMIStdBfdSessSrcAddr,
            fsMIStdBfdSessDstAddrType,
            fsMIStdBfdSessDstAddr
        }
        ::= { fsMIStdBfdSessIpMapTable 1 }

    FsMIStdBfdSessIpMapEntry ::= SEQUENCE {
        fsMIStdBfdSessIpMapIndex            BfdSessIndexTC
    }

    fsMIStdBfdSessIpMapIndex OBJECT-TYPE
        SYNTAX     BfdSessIndexTC
        MAX-ACCESS read-only
        STATUS     current
        DESCRIPTION
            "This object specifies the BfdSessIndexTC referred to by
             the indexes of this row. In essence, a mapping is
             provided between these indexes and the fsMIStdBfdSessTable."
        ::= { fsMIStdBfdSessIpMapEntry 1 }

 -- ------------------------------------------------------------
 -- Bfd Notification group
 -- ------------------------------------------------------------

    fsMIStdBfdContextName OBJECT-TYPE
        SYNTAX      DisplayString (SIZE (1..32))
        MAX-ACCESS  accessible-for-notify
        STATUS      current
        DESCRIPTION
          "This object is used to identify the context-name."
        ::= { fsMIStdBfdNotifications 1 }

    fsMIStdBfdSessUp NOTIFICATION-TYPE
        OBJECTS {
            fsMIStdBfdContextName,
            fsMIStdBfdSessDiag, -- low range value
            fsMIStdBfdSessDiag  -- high range value
        }
        STATUS     current
        DESCRIPTION
            "This notification is generated when the
             fsMIStdBfdSessState object for one or more contiguous
             entries in fsMIStdBfdSessTable are about to enter the up(4)
             state from some other state. The included values of

             fsMIStdBfdSessDiag MUST both be set equal to this
             new state (i.e: up(4)).  The two instances of
             fsMIStdBfdSessDiag in this notification indicate the range
             of indexes that are affected.  Note that all the indexes
             of the two ends of the range can be derived from the
             instance identifiers of these two objects.  For the
             cases where a contiguous range of sessions
             have transitioned into the up(4) state at roughly
             the same time, the device SHOULD issue a single
             notification for each range of contiguous indexes in
             an effort to minimize the emission of a large number
             of notifications.  If a notification has to be
             issued for just a single fsMIStdBfdSessEntry, then
             the instance identifier (and values) of the two
             fsMIStdBfdSessDiag objects MUST be the identical."
        ::= { fsMIStdBfdNotifications 2 }

    fsMIStdBfdSessDown NOTIFICATION-TYPE
        OBJECTS {
            fsMIStdBfdContextName,
            fsMIStdBfdSessDiag, -- low range value
            fsMIStdBfdSessDiag  -- high range value
        }
        STATUS     current
        DESCRIPTION
            "This notification is generated when the
             fsMIStdBfdSessState object for one or more contiguous
             entries in bfdSessTable are about to enter the down(2)
             or adminDown(1) states from some other state. The included
             values of fsMIStdBfdSessDiag MUST both be set equal to this new
             state (i.e: down(2) or adminDown(1)).  The two instances
             of fsMIStdBfdSessDiag in this notification indicate the range
             of indexes that are affected.  Note that all the indexes
             of the two ends of the range can be derived from the
             instance identifiers of these two objects.  For
             cases where a contiguous range of sessions
             have transitioned into the down(2) or adminDown(1) states
             at roughly the same time, the device SHOULD issue a single
             notification for each range of contiguous indexes in
             an effort to minimize the emission of a large number
             of notifications.  If a notification has to be
             issued for just a single fsMIStdBfdSessEntry, then
             the instance identifier (and values) of the two
             fsMIStdBfdSessDiag objects MUST be the identical."
        ::= { fsMIStdBfdNotifications 3 }

    END
