-- Copyright (C) 2008-2014 Super Micro Computer Inc. All Rights Reserved

--    $Id: fsmsipvx.mib,v 1.5 2013/03/30 12:12:22 siva Exp $
SUPERMICRO-MISTD-IPVX-MIB DEFINITIONS ::= BEGIN

   IMPORTS
      MODULE-IDENTITY, OBJECT-TYPE,
      Integer32, Counter32, enterprises,
      Unsigned32, Counter64,
      Gauge32 FROM SNMPv2-SMI
      PhysAddress, TruthValue,
      TimeStamp, RowPointer,
      RowStatus, TEXTUAL-CONVENTION, StorageType             FROM SNMPv2-TC
    InetAddress, InetAddressType,
    InetAddressPrefixLength,
    InetZoneIndex,
    InetAutonomousSystemNumber     FROM INET-ADDRESS-MIB
    InterfaceIndex, InterfaceIndexOrZero           FROM IF-MIB
    IANAipRouteProtocol FROM IANA-RTPROTO-MIB
    IpAddressOriginTC, IpAddressStatusTC, IpAddressPrefixOriginTC,
    Ipv6AddressIfIdentifierTC FROM IP-MIB;


      fsMIStdIp MODULE-IDENTITY
         LAST-UPDATED "201209050000Z"
         ORGANIZATION "Super Micro Computer Inc."
         CONTACT-INFO "support@Supermicro.com"

         DESCRIPTION
            " The MIB module for MIIPvx "
         REVISION "201209050000Z"
         DESCRIPTION
            "The MIB is the standard IPVX mib with virtual routing and
            forwarding support. "
     ::=  { enterprises supermicro-computer-inc(10876) super-switch(101) extended(2) 37}

--
-- Scalars
--
FsInetVersion ::= TEXTUAL-CONVENTION
    STATUS  current
    DESCRIPTION
        "A value representing a version of the IP protocol.

         unknown(0)  An unknown or unspecified version of the IP
                     protocol.

         ipv4(1)     The IPv4 protocol as defined in RFC 791 (STD 5).

         ipv6(2)     The IPv6 protocol as defined in RFC 2460.

         Note that this textual convention SHOULD NOT be used to
         distinguish different address types associated with IP
         protocols.  The InetAddressType has been designed for this
         purpose."
    REFERENCE   "RFC 791, RFC 2460"
    SYNTAX       INTEGER {
                     unknown(0),
                     ipv4(1),
                     ipv6(2)
                 }

fsMIStdIpv4InterfaceTableLastChange OBJECT-TYPE
    SYNTAX     TimeStamp
    MAX-ACCESS read-only
    STATUS     current
    DESCRIPTION
           "The value of sysUpTime on the most recent occasion at which
            a row in the fsMIStdIpv4InterfaceTable was added or deleted, or
            when an fsMIStdIpv4InterfaceTable or an
            ipv4InterfaceEnableStatus object was modified.

            If new objects are added to the fsMIStdIpv4InterfaceTable that
            require the fsMIStdIpv4InterfaceTableLastChange to be updated when
            they are modified, they must specify that requirement in
            their description clause."
    ::= { fsMIStdIp 1 }

fsMIStdIpv6InterfaceTableLastChange OBJECT-TYPE
    SYNTAX     TimeStamp
    MAX-ACCESS read-only
    STATUS     current
    DESCRIPTION
           "The value of sysUpTime on the most recent occasion at which
            a row in the fsMIStdIpv6InterfaceTable was added or deleted or when
            an fsMIStdIpv6InterfaceReasmMaxSize, fsMIStdIpv6InterfaceIdentifier,
            fsMIStdIpv6InterfaceEnableStatus, fsMIStdIpv6InterfaceReachableTime,
            fsMIStdIpv6InterfaceRetransmitTime, or fsMIStdIpv6InterfaceForwarding
            object was modified.

            If new objects are added to the fsMIStdIpv6InterfaceTable that
            require the fsMIStdIpv6InterfaceTableLastChange to be updated when
            they are modified, they must specify that requirement in
            their description clause."
    ::= { fsMIStdIp 2 }

fsMIStdIpIfStatsTableLastChange OBJECT-TYPE
    SYNTAX     TimeStamp
    MAX-ACCESS read-only
    STATUS     current
    DESCRIPTION
           "The value of sysUpTime on the most recent occasion at which
            a row in the fsMIStdIpIfStatsTable was added or deleted.

            If new objects are added to the fsMIStdIpIfStatsTable that require
            the fsMIStdIpIfStatsTableLastChange to be updated when they are
            modified, they must specify that requirement in their
            description clause."
    ::= { fsMIStdIp 3 }

--
-- Global configurations with MI support
--

fsMIStdIpGlobalTable OBJECT-TYPE
    SYNTAX SEQUENCE OF FsMIStdIpGlobalEntry
    MAX-ACCESS not-accessible
    STATUS     current
    DESCRIPTION
           "Table to store the IP configurations specific to a virtual router"
    ::= {fsMIStdIp 4 }

fsMIStdIpGlobalEntry OBJECT-TYPE
    SYNTAX     FsMIStdIpGlobalEntry
    MAX-ACCESS not-accessible
    STATUS     current
    DESCRIPTION
           "Each entry contains the IP configurations specific to a particular
            virtual router specified the index."
    INDEX { fsMIStdIpContextId }
    ::= { fsMIStdIpGlobalTable 1 }

FsMIStdIpGlobalEntry ::= SEQUENCE {
        fsMIStdIpContextId                     Integer32,
        fsMIStdIpForwarding                    INTEGER,
        fsMIStdIpDefaultTTL                    Integer32,
        fsMIStdIpReasmTimeout                  Integer32,
        fsMIStdIpv6IpForwarding                INTEGER,
        fsMIStdIpv6IpDefaultHopLimit           Integer32,
        fsMIStdInetCidrRouteNumber             Gauge32,
        fsMIStdInetCidrRouteDiscards           Counter32
    }

fsMIStdIpContextId OBJECT-TYPE
    SYNTAX     Integer32 (0..256)
    MAX-ACCESS not-accessible
    STATUS     current
    DESCRIPTION
           "The index value that uniquely identifies the virtual router for which
            the configuration is applicable."
    ::= { fsMIStdIpGlobalEntry 1 }

fsMIStdIpForwarding OBJECT-TYPE
    SYNTAX     INTEGER {
                    forwarding(1),    -- acting as a router
                    notForwarding(2)  -- NOT acting as a router
               }
    MAX-ACCESS read-write
    STATUS     current
    DESCRIPTION
           "The indication of whether this entity is acting as an IPv4
            router in respect to the forwarding of datagrams received
            by, but not addressed to, this entity.  IPv4 routers forward
            datagrams.  IPv4 hosts do not (except those source-routed
            via the host).

            When this object is written, the entity should save the
            change to non-volatile storage and restore the object from
            non-volatile storage upon re-initialization of the system.
            Note: a stronger requirement is not used because this object
            was previously defined."
    ::= { fsMIStdIpGlobalEntry 2 }

fsMIStdIpDefaultTTL OBJECT-TYPE
    SYNTAX     Integer32 (1..255)
    MAX-ACCESS read-write
    STATUS     current
    DESCRIPTION
           "The default value inserted into the Time-To-Live field of
            the IPv4 header of datagrams originated at this entity,
            whenever a TTL value is not supplied by the transport layer
            protocol.
            When this object is written, the entity should save the
            change to non-volatile storage and restore the object from
            non-volatile storage upon re-initialization of the system.
            Note: a stronger requirement is not used because this object
            was previously defined."
    ::= { fsMIStdIpGlobalEntry 3 }

fsMIStdIpReasmTimeout OBJECT-TYPE
    SYNTAX     Integer32
    UNITS      "seconds"
    MAX-ACCESS read-only
    STATUS     current
    DESCRIPTION
           "The maximum number of seconds that received fragments are
            held while they are awaiting reassembly at this entity."
    ::= { fsMIStdIpGlobalEntry 4 }

fsMIStdIpv6IpForwarding OBJECT-TYPE
    SYNTAX     INTEGER {
                    forwarding(1),    -- acting as a router
                    notForwarding(2)  -- NOT acting as a router
               }
    MAX-ACCESS read-write
    STATUS     current
    DESCRIPTION
           "The indication of whether this entity is acting as an IPv6
            router on any interface in respect to the forwarding of
            datagrams received by, but not addressed to, this entity.
            IPv6 routers forward datagrams.  IPv6 hosts do not (except
            those source-routed via the host).

            When this object is written, the entity SHOULD save the
            change to non-volatile storage and restore the object from
            non-volatile storage upon re-initialization of the system."
    ::= { fsMIStdIpGlobalEntry 5 }

fsMIStdIpv6IpDefaultHopLimit OBJECT-TYPE
    SYNTAX     Integer32 (0..255)
    MAX-ACCESS read-write
    STATUS     current
    DESCRIPTION
           "The default value inserted into the Hop Limit field of the
            IPv6 header of datagrams originated at this entity whenever
            a Hop Limit value is not supplied by the transport layer
            protocol.

            When this object is written, the entity SHOULD save the
            change to non-volatile storage and restore the object from
            non-volatile storage upon re-initialization of the system."
    ::= { fsMIStdIpGlobalEntry 6 }

fsMIStdInetCidrRouteNumber OBJECT-TYPE
    SYNTAX     Gauge32
    MAX-ACCESS read-only
    STATUS     current
    DESCRIPTION
           "The number of current fsMIStdInetCidrRouteTable entries that
            are not invalid."
    ::= { fsMIStdIpGlobalEntry 7 }

fsMIStdInetCidrRouteDiscards OBJECT-TYPE
    SYNTAX     Counter32
    MAX-ACCESS read-only
    STATUS     current
    DESCRIPTION
           "The number of valid route entries discarded from the
            fsMIStdInetCidrRouteTable.  Discarded route entries do not
            appear in the fsMIStdInetCidrRouteTable.  One possible reason
            for discarding an entry would be to free-up buffer space
            for other route table entries."
    ::= { fsMIStdIpGlobalEntry 8 }


--
-- IPv4 Interface Table with context-id display.
--

fsMIStdIpv4InterfaceTable OBJECT-TYPE
    SYNTAX     SEQUENCE OF FsMIStdIpv4InterfaceEntry
    MAX-ACCESS not-accessible
    STATUS     current
    DESCRIPTION
           "The table containing per-interface IPv4-specific
            information."
    ::= { fsMIStdIp 5 }

fsMIStdIpv4InterfaceEntry OBJECT-TYPE
    SYNTAX     FsMIStdIpv4InterfaceEntry
    MAX-ACCESS not-accessible
    STATUS     current
    DESCRIPTION
           "An entry containing IPv4-specific information for a specific
            interface."
    INDEX { fsMIStdIpv4InterfaceIfIndex }
    ::= { fsMIStdIpv4InterfaceTable 1 }

FsMIStdIpv4InterfaceEntry ::= SEQUENCE {
        fsMIStdIpv4InterfaceIfIndex         InterfaceIndex,
        fsMIStdIpv4InterfaceReasmMaxSize    Integer32,
        fsMIStdIpv4InterfaceEnableStatus    INTEGER,
        fsMIStdIpv4InterfaceRetransmitTime  Unsigned32,
        fsMIStdIpv4IfContextId              Integer32
    }

fsMIStdIpv4InterfaceIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { fsMIStdIpv4InterfaceEntry 1 }

fsMIStdIpv4InterfaceReasmMaxSize OBJECT-TYPE
    SYNTAX     Integer32 (0..65535)
    MAX-ACCESS read-only
    STATUS     current
    DESCRIPTION
           "The size of the largest IPv4 datagram that this entity can
            re-assemble from incoming IPv4 fragmented datagrams received
            on this interface."
    ::= { fsMIStdIpv4InterfaceEntry 2 }

fsMIStdIpv4InterfaceEnableStatus OBJECT-TYPE
    SYNTAX     INTEGER {
                 up(1),
                 down(2)
    }
    MAX-ACCESS read-write
    STATUS     current
    DESCRIPTION
           "The indication of whether IPv4 is enabled (up) or disabled
            (down) on this interface.  This object does not affect the
            state of the interface itself, only its connection to an
            IPv4 stack.  The IF-MIB should be used to control the state
            of the interface."
    ::= { fsMIStdIpv4InterfaceEntry 3 }

fsMIStdIpv4InterfaceRetransmitTime OBJECT-TYPE
    SYNTAX     Unsigned32
    UNITS      "milliseconds"
    MAX-ACCESS read-only
    STATUS     current
    DESCRIPTION
           "The time between retransmissions of ARP requests to a
            neighbor when resolving the address or when probing the
            reachability of a neighbor."
    REFERENCE "RFC 1122"
    DEFVAL { 1000 }
    ::= { fsMIStdIpv4InterfaceEntry 4 }

fsMIStdIpv4IfContextId OBJECT-TYPE
    SYNTAX     Integer32
    MAX-ACCESS read-only
    STATUS     current
    DESCRIPTION
           "The context id to which this interface is mapped."
    ::= { fsMIStdIpv4InterfaceEntry 5 }

--
-- v6 interface table with context-id display
--

fsMIStdIpv6InterfaceTable OBJECT-TYPE
    SYNTAX     SEQUENCE OF FsMIStdIpv6InterfaceEntry
    MAX-ACCESS not-accessible
    STATUS     current
    DESCRIPTION
           "The table containing per-interface IPv6-specific
            information."
    ::= { fsMIStdIp 6 }

fsMIStdIpv6InterfaceEntry OBJECT-TYPE
    SYNTAX     FsMIStdIpv6InterfaceEntry
    MAX-ACCESS not-accessible
    STATUS     current
    DESCRIPTION
           "An entry containing IPv6-specific information for a given
            interface."
    INDEX { fsMIStdIpv6InterfaceIfIndex }
    ::= { fsMIStdIpv6InterfaceTable 1 }

FsMIStdIpv6InterfaceEntry ::= SEQUENCE {
        fsMIStdIpv6InterfaceIfIndex         InterfaceIndex,
        fsMIStdIpv6InterfaceReasmMaxSize    Unsigned32,
        fsMIStdIpv6InterfaceIdentifier      Ipv6AddressIfIdentifierTC,
        fsMIStdIpv6InterfaceEnableStatus    INTEGER,
        fsMIStdIpv6InterfaceReachableTime   Unsigned32,
        fsMIStdIpv6InterfaceRetransmitTime  Unsigned32,
        fsMIStdIpv6InterfaceForwarding      INTEGER,
        fsMIStdIpv6IfContextId              Integer32
    }

fsMIStdIpv6InterfaceIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { fsMIStdIpv6InterfaceEntry 1 }

fsMIStdIpv6InterfaceReasmMaxSize OBJECT-TYPE
    SYNTAX     Unsigned32 (1500..65535)
    UNITS      "octets"
    MAX-ACCESS read-only
    STATUS     current
    DESCRIPTION
           "The size of the largest IPv6 datagram that this entity can
            re-assemble from incoming IPv6 fragmented datagrams received
            on this interface."
    ::= { fsMIStdIpv6InterfaceEntry 2 }

fsMIStdIpv6InterfaceIdentifier OBJECT-TYPE
    SYNTAX     Ipv6AddressIfIdentifierTC
    MAX-ACCESS read-only
    STATUS     current
    DESCRIPTION
           "The Interface Identifier for this interface.  The Interface
            Identifier is combined with an address prefix to form an
            interface address.

            By default, the Interface Identifier is auto-configured
            according to the rules of the link type to which this
            interface is attached.
            A zero length identifier may be used where appropriate.  One
            possible example is a loopback interface."
    ::= { fsMIStdIpv6InterfaceEntry 3 }

fsMIStdIpv6InterfaceEnableStatus OBJECT-TYPE
    SYNTAX     INTEGER {
                 up(1),
                 down(2)
    }
    MAX-ACCESS read-write
    STATUS     current
    DESCRIPTION
           "The indication of whether IPv6 is enabled (up) or disabled
            (down) on this interface.  This object does not affect the
            state of the interface itself, only its connection to an
            IPv6 stack.  The IF-MIB should be used to control the state
            of the interface.

            When this object is written, the entity SHOULD save the
            change to non-volatile storage and restore the object from
            non-volatile storage upon re-initialization of the system."
    ::= { fsMIStdIpv6InterfaceEntry 4 }

fsMIStdIpv6InterfaceReachableTime OBJECT-TYPE
    SYNTAX     Unsigned32
    UNITS      "milliseconds"
    MAX-ACCESS read-only
    STATUS     current
    DESCRIPTION
           "The time a neighbor is considered reachable after receiving
            a reachability confirmation."
    ::= { fsMIStdIpv6InterfaceEntry 5 }

fsMIStdIpv6InterfaceRetransmitTime OBJECT-TYPE
    SYNTAX     Unsigned32
    UNITS      "milliseconds"
    MAX-ACCESS read-only
    STATUS     current
    DESCRIPTION
           "The time between retransmissions of Neighbor Solicitation
            messages to a neighbor when resolving the address or when
            probing the reachability of a neighbor."
    ::= { fsMIStdIpv6InterfaceEntry 6 }

fsMIStdIpv6InterfaceForwarding OBJECT-TYPE
    SYNTAX     INTEGER {
                    forwarding(1),    -- acting as a router
                    notForwarding(2)  -- NOT acting as a router
               }
    MAX-ACCESS read-write
    STATUS     current
    DESCRIPTION
           "The indication of whether this entity is acting as an IPv6
            router on this interface with respect to the forwarding of
            datagrams received by, but not addressed to, this entity.
            IPv6 routers forward datagrams.  IPv6 hosts do not (except
            those source-routed via the host).

            This object is constrained by ipv6IpForwarding and is
            ignored if ipv6IpForwarding is set to notForwarding.  Those
            systems that do not provide per-interface control of the
            forwarding function should set this object to forwarding for
            all interfaces and allow the ipv6IpForwarding object to
            control the forwarding capability.

            When this object is written, the entity SHOULD save the
            change to non-volatile storage and restore the object from
            non-volatile storage upon re-initialization of the system."
    ::= { fsMIStdIpv6InterfaceEntry 7 }

fsMIStdIpv6IfContextId OBJECT-TYPE
    SYNTAX     Integer32
    MAX-ACCESS read-only
    STATUS     current
    DESCRIPTION
        "The context to which the interface is mapped."
    ::= { fsMIStdIpv6InterfaceEntry 8 }


--IP Statistics Table

fsMIStdIpSystemStatsTable OBJECT-TYPE
    SYNTAX     SEQUENCE OF FsMiIpSystemStatsEntry
    MAX-ACCESS not-accessible
    STATUS     current
    DESCRIPTION
           "The table containing the IP traffic statistics for various virtual
            routers configured in the system."
    ::= { fsMIStdIp 7 }

fsMIStdIpSystemStatsEntry OBJECT-TYPE
    SYNTAX     FsMiIpSystemStatsEntry
    MAX-ACCESS not-accessible
    STATUS     current
    DESCRIPTION
           "A statistics entry containing the IP traffic statistics for a
            particular virtual rotuer for a particular IP version."
    INDEX {  fsMIStdIpContextId,
             fsMIStdIpSystemStatsIPVersion
          }
    ::= { fsMIStdIpSystemStatsTable 1 }

FsMiIpSystemStatsEntry ::= SEQUENCE {
        fsMIStdIpSystemStatsIPVersion           FsInetVersion,
        fsMIStdIpSystemStatsInReceives          Counter32,
        fsMIStdIpSystemStatsHCInReceives        Counter64,
        fsMIStdIpSystemStatsInOctets            Counter32,
        fsMIStdIpSystemStatsHCInOctets          Counter64,
        fsMIStdIpSystemStatsInHdrErrors         Counter32,
        fsMIStdIpSystemStatsInNoRoutes          Counter32,
        fsMIStdIpSystemStatsInAddrErrors        Counter32,
        fsMIStdIpSystemStatsInUnknownProtos     Counter32,
        fsMIStdIpSystemStatsInTruncatedPkts     Counter32,
        fsMIStdIpSystemStatsInForwDatagrams     Counter32,
        fsMIStdIpSystemStatsHCInForwDatagrams   Counter64,
        fsMIStdIpSystemStatsReasmReqds          Counter32,
        fsMIStdIpSystemStatsReasmOKs            Counter32,
        fsMIStdIpSystemStatsReasmFails          Counter32,
        fsMIStdIpSystemStatsInDiscards          Counter32,
        fsMIStdIpSystemStatsInDelivers          Counter32,

        fsMIStdIpSystemStatsHCInDelivers        Counter64,
        fsMIStdIpSystemStatsOutRequests         Counter32,
        fsMIStdIpSystemStatsHCOutRequests       Counter64,
        fsMIStdIpSystemStatsOutNoRoutes         Counter32,
        fsMIStdIpSystemStatsOutForwDatagrams    Counter32,
        fsMIStdIpSystemStatsHCOutForwDatagrams  Counter64,
        fsMIStdIpSystemStatsOutDiscards         Counter32,
        fsMIStdIpSystemStatsOutFragReqds        Counter32,
        fsMIStdIpSystemStatsOutFragOKs          Counter32,
        fsMIStdIpSystemStatsOutFragFails        Counter32,
        fsMIStdIpSystemStatsOutFragCreates      Counter32,
        fsMIStdIpSystemStatsOutTransmits        Counter32,
        fsMIStdIpSystemStatsHCOutTransmits      Counter64,
        fsMIStdIpSystemStatsOutOctets           Counter32,
        fsMIStdIpSystemStatsHCOutOctets         Counter64,
        fsMIStdIpSystemStatsInMcastPkts         Counter32,
        fsMIStdIpSystemStatsHCInMcastPkts       Counter64,
        fsMIStdIpSystemStatsInMcastOctets       Counter32,
        fsMIStdIpSystemStatsHCInMcastOctets     Counter64,
        fsMIStdIpSystemStatsOutMcastPkts        Counter32,
        fsMIStdIpSystemStatsHCOutMcastPkts      Counter64,
        fsMIStdIpSystemStatsOutMcastOctets      Counter32,
        fsMIStdIpSystemStatsHCOutMcastOctets    Counter64,
        fsMIStdIpSystemStatsInBcastPkts         Counter32,
        fsMIStdIpSystemStatsHCInBcastPkts       Counter64,
        fsMIStdIpSystemStatsOutBcastPkts        Counter32,
        fsMIStdIpSystemStatsHCOutBcastPkts      Counter64,
        fsMIStdIpSystemStatsDiscontinuityTime   TimeStamp,
        fsMIStdIpSystemStatsRefreshRate         Unsigned32
    }

fsMIStdIpSystemStatsIPVersion OBJECT-TYPE
    SYNTAX     FsInetVersion

    MAX-ACCESS not-accessible
    STATUS     current
    DESCRIPTION
           "The IP version of this row."
    ::= { fsMIStdIpSystemStatsEntry 1 }

fsMIStdIpSystemStatsInReceives OBJECT-TYPE
    SYNTAX     Counter32
    MAX-ACCESS read-only
    STATUS     current
    DESCRIPTION
           "The total number of input IP datagrams received, including
            those received in error.
            Discontinuities in the value of this counter can occur at
            re-initialization of the management system, and at other
            times as indicated by the value of
            fsMIStdIpSystemStatsDiscontinuityTime."
    ::= { fsMIStdIpSystemStatsEntry 2 }

fsMIStdIpSystemStatsHCInReceives OBJECT-TYPE
    SYNTAX     Counter64
    MAX-ACCESS read-only
    STATUS     current
    DESCRIPTION
           "The total number of input IP datagrams received, including
            those received in error.  This object counts the same
            datagrams as fsMIStdIpSystemStatsInReceives, but allows for larger
            values.

            Discontinuities in the value of this counter can occur at
            re-initialization of the management system, and at other
            times as indicated by the value of
            fsMIStdIpSystemStatsDiscontinuityTime."
    ::= { fsMIStdIpSystemStatsEntry 3 }

fsMIStdIpSystemStatsInOctets OBJECT-TYPE
    SYNTAX     Counter32
    MAX-ACCESS read-only
    STATUS     current
    DESCRIPTION
           "The total number of octets received in input IP datagrams,
            including those received in error.  Octets from datagrams
            counted in fsMIStdIpSystemStatsInReceives MUST be counted here.

            Discontinuities in the value of this counter can occur at
            re-initialization of the management system, and at other
            times as indicated by the value of
            fsMIStdIpSystemStatsDiscontinuityTime."
    ::= { fsMIStdIpSystemStatsEntry 4 }

fsMIStdIpSystemStatsHCInOctets OBJECT-TYPE
    SYNTAX     Counter64
    MAX-ACCESS read-only
    STATUS     current
    DESCRIPTION
           "The total number of octets received in input IP datagrams,
            including those received in error.  This object counts the
            same octets as fsMIStdIpSystemStatsInOctets, but allows for larger
            values.

            Discontinuities in the value of this counter can occur at
            re-initialization of the management system, and at other
            times as indicated by the value of
            fsMIStdIpSystemStatsDiscontinuityTime."
    ::= { fsMIStdIpSystemStatsEntry 5 }

fsMIStdIpSystemStatsInHdrErrors OBJECT-TYPE
    SYNTAX     Counter32
    MAX-ACCESS read-only
    STATUS     current
    DESCRIPTION
           "The number of input IP datagrams discarded due to errors in
            their IP headers, including version number mismatch, other
            format errors, hop count exceeded, errors discovered in
            processing their IP options, etc.

            Discontinuities in the value of this counter can occur at
            re-initialization of the management system, and at other
            times as indicated by the value of
            fsMIStdIpSystemStatsDiscontinuityTime."
    ::= { fsMIStdIpSystemStatsEntry 6 }

fsMIStdIpSystemStatsInNoRoutes OBJECT-TYPE
    SYNTAX     Counter32
    MAX-ACCESS read-only
    STATUS     current
    DESCRIPTION
           "The number of input IP datagrams discarded because no route
            could be found to transmit them to their destination.

            Discontinuities in the value of this counter can occur at
            re-initialization of the management system, and at other
            times as indicated by the value of
            fsMIStdIpSystemStatsDiscontinuityTime."
    ::= { fsMIStdIpSystemStatsEntry 7 }

fsMIStdIpSystemStatsInAddrErrors OBJECT-TYPE
    SYNTAX     Counter32
    MAX-ACCESS read-only
    STATUS     current
    DESCRIPTION
           "The number of input IP datagrams discarded because the IP
            address in their IP header's destination field was not a
            valid address to be received at this entity.  This count
            includes invalid addresses (e.g., ::0).  For entities
            that are not IP routers and therefore do not forward



            datagrams, this counter includes datagrams discarded
            because the destination address was not a local address.

            Discontinuities in the value of this counter can occur at
            re-initialization of the management system, and at other
            times as indicated by the value of
            fsMIStdIpSystemStatsDiscontinuityTime."
    ::= { fsMIStdIpSystemStatsEntry 8 }

fsMIStdIpSystemStatsInUnknownProtos OBJECT-TYPE
    SYNTAX     Counter32
    MAX-ACCESS read-only
    STATUS     current
    DESCRIPTION
           "The number of locally-addressed IP datagrams received
            successfully but discarded because of an unknown or
            unsupported protocol.

            When tracking interface statistics, the counter of the
            interface to which these datagrams were addressed is
            incremented.  This interface might not be the same as the
            input interface for some of the datagrams.

            Discontinuities in the value of this counter can occur at
            re-initialization of the management system, and at other
            times as indicated by the value of
            fsMIStdIpSystemStatsDiscontinuityTime."
    ::= { fsMIStdIpSystemStatsEntry 9 }

fsMIStdIpSystemStatsInTruncatedPkts OBJECT-TYPE
    SYNTAX     Counter32
    MAX-ACCESS read-only
    STATUS     current
    DESCRIPTION
           "The number of input IP datagrams discarded because the
            datagram frame didn't carry enough data.

            Discontinuities in the value of this counter can occur at
            re-initialization of the management system, and at other
            times as indicated by the value of
            fsMIStdIpSystemStatsDiscontinuityTime."
    ::= { fsMIStdIpSystemStatsEntry 10 }

fsMIStdIpSystemStatsInForwDatagrams OBJECT-TYPE
    SYNTAX     Counter32
    MAX-ACCESS read-only
    STATUS     current
    DESCRIPTION
           "The number of input datagrams for which this entity was not
            their final IP destination and for which this entity
            attempted to find a route to forward them to that final
            destination.  In entities that do not act as IP routers,
            this counter will include only those datagrams that were
            Source-Routed via this entity, and the Source-Route
            processing was successful.

            When tracking interface statistics, the counter of the
            incoming interface is incremented for each datagram.
            Discontinuities in the value of this counter can occur at
            re-initialization of the management system, and at other
            times as indicated by the value of
            fsMIStdIpSystemStatsDiscontinuityTime."
    ::= { fsMIStdIpSystemStatsEntry 11 }

fsMIStdIpSystemStatsHCInForwDatagrams OBJECT-TYPE
    SYNTAX     Counter64
    MAX-ACCESS read-only
    STATUS     current
    DESCRIPTION
           "The number of input datagrams for which this entity was not
            their final IP destination and for which this entity
            attempted to find a route to forward them to that final
            destination.  This object counts the same packets as
            fsMIStdIpSystemStatsInForwDatagrams, but allows for larger values.

            Discontinuities in the value of this counter can occur at
            re-initialization of the management system, and at other
            times as indicated by the value of
            fsMIStdIpSystemStatsDiscontinuityTime."
    ::= { fsMIStdIpSystemStatsEntry 12 }

fsMIStdIpSystemStatsReasmReqds OBJECT-TYPE
    SYNTAX     Counter32
    MAX-ACCESS read-only
    STATUS     current
    DESCRIPTION
           "The number of IP fragments received that needed to be
            reassembled at this interface.

            When tracking interface statistics, the counter of the
            interface to which these fragments were addressed is
            incremented.  This interface might not be the same as the
            input interface for some of the fragments.
            Discontinuities in the value of this counter can occur at
            re-initialization of the management system, and at other
            times as indicated by the value of
            fsMIStdIpSystemStatsDiscontinuityTime."
    ::= { fsMIStdIpSystemStatsEntry 13 }

fsMIStdIpSystemStatsReasmOKs OBJECT-TYPE
    SYNTAX     Counter32
    MAX-ACCESS read-only
    STATUS     current
    DESCRIPTION
           "The number of IP datagrams successfully reassembled.

            Discontinuities in the value of this counter can occur at
            re-initialization of the management system, and at other
            times as indicated by the value of
            fsMIStdIpSystemStatsDiscontinuityTime."
    ::= { fsMIStdIpSystemStatsEntry 14 }

fsMIStdIpSystemStatsReasmFails OBJECT-TYPE
    SYNTAX     Counter32
    MAX-ACCESS read-only
    STATUS     current
    DESCRIPTION
           "The number of failures detected by the IP re-assembly
            algorithm (for whatever reason: timed out, errors, etc.).
            Note that this is not necessarily a count of discarded IP
            fragments since some algorithms (notably the algorithm in
            RFC 815) can lose track of the number of fragments by
            combining them as they are received.

            When tracking interface statistics, the counter of the
            interface to which these fragments were addressed is
            incremented.  This interface might not be the same as the
            input interface for some of the fragments.

            Discontinuities in the value of this counter can occur at
            re-initialization of the management system, and at other
            times as indicated by the value of
            fsMIStdIpSystemStatsDiscontinuityTime."
    ::= { fsMIStdIpSystemStatsEntry 15 }

fsMIStdIpSystemStatsInDiscards OBJECT-TYPE
    SYNTAX     Counter32
    MAX-ACCESS read-only
    STATUS     current
    DESCRIPTION
           "The number of input IP datagrams for which no problems were
            encountered to prevent their continued processing, but
            were discarded (e.g., for lack of buffer space).  Note that
            this counter does not include any datagrams discarded while
            awaiting re-assembly.

            Discontinuities in the value of this counter can occur at
            re-initialization of the management system, and at other
            times as indicated by the value of
            fsMIStdIpSystemStatsDiscontinuityTime."
    ::= { fsMIStdIpSystemStatsEntry 16 }

fsMIStdIpSystemStatsInDelivers OBJECT-TYPE
    SYNTAX     Counter32
    MAX-ACCESS read-only
    STATUS     current
    DESCRIPTION
           "The total number of datagrams successfully delivered to IP
            user-protocols (including ICMP).

            When tracking interface statistics, the counter of the
            interface to which these datagrams were addressed is
            incremented.  This interface might not be the same as the
            input interface for some of the datagrams.

            Discontinuities in the value of this counter can occur at
            re-initialization of the management system, and at other
            times as indicated by the value of
            fsMIStdIpSystemStatsDiscontinuityTime."
    ::= { fsMIStdIpSystemStatsEntry 17 }

fsMIStdIpSystemStatsHCInDelivers OBJECT-TYPE
    SYNTAX     Counter64
    MAX-ACCESS read-only
    STATUS     current
    DESCRIPTION
           "The total number of datagrams successfully delivered to IP
            user-protocols (including ICMP).  This object counts the
            same packets as fsMIStdIpSystemStatsInDelivers, but allows for
            larger values.

            Discontinuities in the value of this counter can occur at
            re-initialization of the management system, and at other
            times as indicated by the value of
            fsMIStdIpSystemStatsDiscontinuityTime."
    ::= { fsMIStdIpSystemStatsEntry 18 }

fsMIStdIpSystemStatsOutRequests OBJECT-TYPE
    SYNTAX     Counter32
    MAX-ACCESS read-only
    STATUS     current
    DESCRIPTION
           "The total number of IP datagrams that local IP user-
            protocols (including ICMP) supplied to IP in requests for
            transmission.  Note that this counter does not include any
            datagrams counted in fsMIStdIpSystemStatsOutForwDatagrams.

            Discontinuities in the value of this counter can occur at
            re-initialization of the management system, and at other
            times as indicated by the value of
            fsMIStdIpSystemStatsDiscontinuityTime."
    ::= { fsMIStdIpSystemStatsEntry 19 }

fsMIStdIpSystemStatsHCOutRequests OBJECT-TYPE
    SYNTAX     Counter64
    MAX-ACCESS read-only
    STATUS     current
    DESCRIPTION
           "The total number of IP datagrams that local IP user-
            protocols (including ICMP) supplied to IP in requests for
            transmission.  This object counts the same packets as
            fsMIStdIpSystemStatsOutRequests, but allows for larger values.

            Discontinuities in the value of this counter can occur at
            re-initialization of the management system, and at other
            times as indicated by the value of
            fsMIStdIpSystemStatsDiscontinuityTime."
    ::= { fsMIStdIpSystemStatsEntry 20 }

fsMIStdIpSystemStatsOutNoRoutes OBJECT-TYPE
    SYNTAX     Counter32
    MAX-ACCESS read-only
    STATUS     current
    DESCRIPTION
           "The number of locally generated IP datagrams discarded
            because no route could be found to transmit them to their
            destination.

            Discontinuities in the value of this counter can occur at
            re-initialization of the management system, and at other
            times as indicated by the value of
            fsMIStdIpSystemStatsDiscontinuityTime."
    ::= { fsMIStdIpSystemStatsEntry 21 }



fsMIStdIpSystemStatsOutForwDatagrams OBJECT-TYPE
    SYNTAX     Counter32
    MAX-ACCESS read-only
    STATUS     current
    DESCRIPTION
           "The number of datagrams for which this entity was not their
            final IP destination and for which it was successful in
            finding a path to their final destination.  In entities
            that do not act as IP routers, this counter will include
            only those datagrams that were Source-Routed via this
            entity, and the Source-Route processing was successful.

            When tracking interface statistics, the counter of the
            outgoing interface is incremented for a successfully
            forwarded datagram.

            Discontinuities in the value of this counter can occur at
            re-initialization of the management system, and at other
            times as indicated by the value of
            fsMIStdIpSystemStatsDiscontinuityTime."
    ::= { fsMIStdIpSystemStatsEntry 22 }

fsMIStdIpSystemStatsHCOutForwDatagrams OBJECT-TYPE
    SYNTAX     Counter64
    MAX-ACCESS read-only
    STATUS     current
    DESCRIPTION
           "The number of datagrams for which this entity was not their
            final IP destination and for which it was successful in
            finding a path to their final destination.  This object
            counts the same packets as fsMIStdIpSystemStatsOutForwDatagrams,
            but allows for larger values.

            Discontinuities in the value of this counter can occur at
            re-initialization of the management system, and at other
            times as indicated by the value of
            fsMIStdIpSystemStatsDiscontinuityTime."
    ::= { fsMIStdIpSystemStatsEntry 23 }

fsMIStdIpSystemStatsOutDiscards OBJECT-TYPE
    SYNTAX     Counter32
    MAX-ACCESS read-only
    STATUS     current
    DESCRIPTION
           "The number of output IP datagrams for which no problem was
            encountered to prevent their transmission to their
            destination, but were discarded (e.g., for lack of
            buffer space).  Note that this counter would include
            datagrams counted in fsMIStdIpSystemStatsOutForwDatagrams if any
            such datagrams met this (discretionary) discard criterion.

            Discontinuities in the value of this counter can occur at
            re-initialization of the management system, and at other
            times as indicated by the value of
            fsMIStdIpSystemStatsDiscontinuityTime."
    ::= { fsMIStdIpSystemStatsEntry 24 }

fsMIStdIpSystemStatsOutFragReqds OBJECT-TYPE
    SYNTAX     Counter32
    MAX-ACCESS read-only
    STATUS     current
    DESCRIPTION
           "The number of IP datagrams that would require fragmentation
            in order to be transmitted.

            When tracking interface statistics, the counter of the
            outgoing interface is incremented for a successfully
            fragmented datagram.

            Discontinuities in the value of this counter can occur at
            re-initialization of the management system, and at other
            times as indicated by the value of
            fsMIStdIpSystemStatsDiscontinuityTime."
    ::= { fsMIStdIpSystemStatsEntry 25 }

fsMIStdIpSystemStatsOutFragOKs OBJECT-TYPE
    SYNTAX     Counter32
    MAX-ACCESS read-only
    STATUS     current
    DESCRIPTION
           "The number of IP datagrams that have been successfully
            fragmented.

            When tracking interface statistics, the counter of the
            outgoing interface is incremented for a successfully
            fragmented datagram.

            Discontinuities in the value of this counter can occur at
            re-initialization of the management system, and at other
            times as indicated by the value of
            fsMIStdIpSystemStatsDiscontinuityTime."
    ::= { fsMIStdIpSystemStatsEntry 26 }

fsMIStdIpSystemStatsOutFragFails OBJECT-TYPE
    SYNTAX     Counter32
    MAX-ACCESS read-only
    STATUS     current
    DESCRIPTION
           "The number of IP datagrams that have been discarded because
            they needed to be fragmented but could not be.  This
            includes IPv4 packets that have the DF bit set and IPv6
            packets that are being forwarded and exceed the outgoing
            link MTU.

            When tracking interface statistics, the counter of the
            outgoing interface is incremented for an unsuccessfully
            fragmented datagram.

            Discontinuities in the value of this counter can occur at
            re-initialization of the management system, and at other
            times as indicated by the value of
            fsMIStdIpSystemStatsDiscontinuityTime."
    ::= { fsMIStdIpSystemStatsEntry 27 }

fsMIStdIpSystemStatsOutFragCreates OBJECT-TYPE
    SYNTAX     Counter32
    MAX-ACCESS read-only
    STATUS     current
    DESCRIPTION
           "The number of output datagram fragments that have been
            generated as a result of IP fragmentation.

            When tracking interface statistics, the counter of the
            outgoing interface is incremented for a successfully
            fragmented datagram.

            Discontinuities in the value of this counter can occur at
            re-initialization of the management system, and at other
            times as indicated by the value of
            fsMIStdIpSystemStatsDiscontinuityTime."
    ::= { fsMIStdIpSystemStatsEntry 28 }

fsMIStdIpSystemStatsOutTransmits OBJECT-TYPE
    SYNTAX     Counter32
    MAX-ACCESS read-only
    STATUS     current
    DESCRIPTION
           "The total number of IP datagrams that this entity supplied
            to the lower layers for transmission.  This includes
            datagrams generated locally and those forwarded by this
            entity.

            Discontinuities in the value of this counter can occur at
            re-initialization of the management system, and at other
            times as indicated by the value of
            fsMIStdIpSystemStatsDiscontinuityTime."
    ::= { fsMIStdIpSystemStatsEntry 29 }

fsMIStdIpSystemStatsHCOutTransmits OBJECT-TYPE
    SYNTAX     Counter64
    MAX-ACCESS read-only
    STATUS     current
    DESCRIPTION
           "The total number of IP datagrams that this entity supplied
            to the lower layers for transmission.  This object counts
            the same datagrams as fsMIStdIpSystemStatsOutTransmits, but allows
            for larger values.

            Discontinuities in the value of this counter can occur at
            re-initialization of the management system, and at other
            times as indicated by the value of
            fsMIStdIpSystemStatsDiscontinuityTime."
    ::= { fsMIStdIpSystemStatsEntry 30 }

fsMIStdIpSystemStatsOutOctets OBJECT-TYPE
    SYNTAX     Counter32
    MAX-ACCESS read-only
    STATUS     current
    DESCRIPTION
           "The total number of octets in IP datagrams delivered to the
            lower layers for transmission.  Octets from datagrams
            counted in fsMIStdIpSystemStatsOutTransmits MUST be counted here.

            Discontinuities in the value of this counter can occur at
            re-initialization of the management system, and at other
            times as indicated by the value of
            fsMIStdIpSystemStatsDiscontinuityTime."
    ::= { fsMIStdIpSystemStatsEntry 31 }

fsMIStdIpSystemStatsHCOutOctets OBJECT-TYPE
    SYNTAX     Counter64
    MAX-ACCESS read-only
    STATUS     current
    DESCRIPTION
           "The total number of octets in IP datagrams delivered to the
            lower layers for transmission.  This objects counts the same
            octets as fsMIStdIpSystemStatsOutOctets, but allows for larger
            values.

            Discontinuities in the value of this counter can occur at
            re-initialization of the management system, and at other
            times as indicated by the value of
            fsMIStdIpSystemStatsDiscontinuityTime."
    ::= { fsMIStdIpSystemStatsEntry 32 }

fsMIStdIpSystemStatsInMcastPkts OBJECT-TYPE
    SYNTAX     Counter32
    MAX-ACCESS read-only
    STATUS     current
    DESCRIPTION
           "The number of IP multicast datagrams received.

            Discontinuities in the value of this counter can occur at
            re-initialization of the management system, and at other
            times as indicated by the value of
            fsMIStdIpSystemStatsDiscontinuityTime."
    ::= { fsMIStdIpSystemStatsEntry 33 }

fsMIStdIpSystemStatsHCInMcastPkts OBJECT-TYPE
    SYNTAX     Counter64
    MAX-ACCESS read-only
    STATUS     current
    DESCRIPTION
           "The number of IP multicast datagrams received.  This object
            counts the same datagrams as fsMIStdIpSystemStatsInMcastPkts but
            allows for larger values.

            Discontinuities in the value of this counter can occur at
            re-initialization of the management system, and at other
            times as indicated by the value of
            fsMIStdIpSystemStatsDiscontinuityTime."
    ::= { fsMIStdIpSystemStatsEntry 34 }

fsMIStdIpSystemStatsInMcastOctets OBJECT-TYPE
    SYNTAX     Counter32
    MAX-ACCESS read-only
    STATUS     current
    DESCRIPTION
           "The total number of octets received in IP multicast
            datagrams.  Octets from datagrams counted in
            fsMIStdIpSystemStatsInMcastPkts MUST be counted here.

            Discontinuities in the value of this counter can occur at
            re-initialization of the management system, and at other
            times as indicated by the value of
            fsMIStdIpSystemStatsDiscontinuityTime."
    ::= { fsMIStdIpSystemStatsEntry 35 }

fsMIStdIpSystemStatsHCInMcastOctets OBJECT-TYPE
    SYNTAX     Counter64
    MAX-ACCESS read-only
    STATUS     current
    DESCRIPTION
           "The total number of octets received in IP multicast
            datagrams.  This object counts the same octets as
            fsMIStdIpSystemStatsInMcastOctets, but allows for larger values.

            Discontinuities in the value of this counter can occur at
            re-initialization of the management system, and at other
            times as indicated by the value of
            fsMIStdIpSystemStatsDiscontinuityTime."
    ::= { fsMIStdIpSystemStatsEntry 36 }

fsMIStdIpSystemStatsOutMcastPkts OBJECT-TYPE
    SYNTAX     Counter32
    MAX-ACCESS read-only
    STATUS     current
    DESCRIPTION
           "The number of IP multicast datagrams transmitted.

            Discontinuities in the value of this counter can occur at
            re-initialization of the management system, and at other
            times as indicated by the value of
            fsMIStdIpSystemStatsDiscontinuityTime."
    ::= { fsMIStdIpSystemStatsEntry 37 }

fsMIStdIpSystemStatsHCOutMcastPkts OBJECT-TYPE
    SYNTAX     Counter64
    MAX-ACCESS read-only
    STATUS     current
    DESCRIPTION
           "The number of IP multicast datagrams transmitted.  This
            object counts the same datagrams as
            fsMIStdIpSystemStatsOutMcastPkts, but allows for larger values.

            Discontinuities in the value of this counter can occur at
            re-initialization of the management system, and at other
            times as indicated by the value of
            fsMIStdIpSystemStatsDiscontinuityTime."
    ::= { fsMIStdIpSystemStatsEntry 38 }

fsMIStdIpSystemStatsOutMcastOctets OBJECT-TYPE
    SYNTAX     Counter32
    MAX-ACCESS read-only
    STATUS     current
    DESCRIPTION
           "The total number of octets transmitted in IP multicast
            datagrams.  Octets from datagrams counted in
            fsMIStdIpSystemStatsOutMcastPkts MUST be counted here.

            Discontinuities in the value of this counter can occur at
            re-initialization of the management system, and at other
            times as indicated by the value of
            fsMIStdIpSystemStatsDiscontinuityTime."
    ::= { fsMIStdIpSystemStatsEntry 39 }

fsMIStdIpSystemStatsHCOutMcastOctets OBJECT-TYPE
    SYNTAX     Counter64
    MAX-ACCESS read-only
    STATUS     current
    DESCRIPTION
           "The total number of octets transmitted in IP multicast
            datagrams.  This object counts the same octets as
            fsMIStdIpSystemStatsOutMcastOctets, but allows for larger values.

            Discontinuities in the value of this counter can occur at
            re-initialization of the management system, and at other
            times as indicated by the value of
            fsMIStdIpSystemStatsDiscontinuityTime."
    ::= { fsMIStdIpSystemStatsEntry 40 }

fsMIStdIpSystemStatsInBcastPkts OBJECT-TYPE
    SYNTAX     Counter32
    MAX-ACCESS read-only
    STATUS     current
    DESCRIPTION
           "The number of IP broadcast datagrams received.

            Discontinuities in the value of this counter can occur at
            re-initialization of the management system, and at other
            times as indicated by the value of
            fsMIStdIpSystemStatsDiscontinuityTime."
    ::= { fsMIStdIpSystemStatsEntry 41 }

fsMIStdIpSystemStatsHCInBcastPkts OBJECT-TYPE
    SYNTAX     Counter64
    MAX-ACCESS read-only
    STATUS     current
    DESCRIPTION
           "The number of IP broadcast datagrams received.  This object
            counts the same datagrams as fsMIStdIpSystemStatsInBcastPkts but
            allows for larger values.

            Discontinuities in the value of this counter can occur at
            re-initialization of the management system, and at other
            times as indicated by the value of
            fsMIStdIpSystemStatsDiscontinuityTime."
    ::= { fsMIStdIpSystemStatsEntry 42 }

fsMIStdIpSystemStatsOutBcastPkts OBJECT-TYPE
    SYNTAX     Counter32
    MAX-ACCESS read-only
    STATUS     current
    DESCRIPTION
           "The number of IP broadcast datagrams transmitted.

            Discontinuities in the value of this counter can occur at
            re-initialization of the management system, and at other
            times as indicated by the value of
            fsMIStdIpSystemStatsDiscontinuityTime."
    ::= { fsMIStdIpSystemStatsEntry 43 }

fsMIStdIpSystemStatsHCOutBcastPkts OBJECT-TYPE
    SYNTAX     Counter64
    MAX-ACCESS read-only
    STATUS     current
    DESCRIPTION
           "The number of IP broadcast datagrams transmitted.  This
            object counts the same datagrams as
            fsMIStdIpSystemStatsOutBcastPkts, but allows for larger values.

            Discontinuities in the value of this counter can occur at
            re-initialization of the management system, and at other
            times as indicated by the value of
            fsMIStdIpSystemStatsDiscontinuityTime."
    ::= { fsMIStdIpSystemStatsEntry 44 }

fsMIStdIpSystemStatsDiscontinuityTime OBJECT-TYPE
    SYNTAX     TimeStamp
    MAX-ACCESS read-only
    STATUS     current
    DESCRIPTION
           "The value of sysUpTime on the most recent occasion at which
            any one or more of this entry's counters suffered a
            discontinuity.

            If no such discontinuities have occurred since the last re-
            initialization of the local management subsystem, then this
            object contains a zero value."
    ::= { fsMIStdIpSystemStatsEntry 45 }

fsMIStdIpSystemStatsRefreshRate OBJECT-TYPE
    SYNTAX     Unsigned32
    UNITS      "milli-seconds"
    MAX-ACCESS read-only
    STATUS     current
    DESCRIPTION
           "The minimum reasonable polling interval for this entry.
            This object provides an indication of the minimum amount of
            time required to update the counters in this entry."
    ::= { fsMIStdIpSystemStatsEntry 46 }



fsMIStdIpIfStatsTable OBJECT-TYPE
    SYNTAX     SEQUENCE OF FsMIStdIpIfStatsEntry
    MAX-ACCESS not-accessible
    STATUS     current
    DESCRIPTION
           "The table containing per-interface traffic statistics.  This
            table and the ipSystemStatsTable contain similar objects
            whose difference is in their granularity.  Where this table
            contains per-interface statistics, the ipSystemStatsTable
            contains the same statistics, but counted on a system wide
            basis."
    ::= { fsMIStdIp 8 }

fsMIStdIpIfStatsEntry OBJECT-TYPE
    SYNTAX     FsMIStdIpIfStatsEntry
    MAX-ACCESS not-accessible
    STATUS     current
    DESCRIPTION
           "An interface statistics entry containing objects for a
            particular interface and version of IP."
    INDEX { fsMIStdIpIfStatsIPVersion, fsMIStdIpIfStatsIfIndex }
    ::= { fsMIStdIpIfStatsTable 1 }

FsMIStdIpIfStatsEntry ::= SEQUENCE {
        fsMIStdIpIfStatsIPVersion           FsInetVersion,
        fsMIStdIpIfStatsIfIndex             InterfaceIndex,
        fsMIStdIpIfStatsInReceives          Counter32,
        fsMIStdIpIfStatsHCInReceives        Counter64,
        fsMIStdIpIfStatsInOctets            Counter32,
        fsMIStdIpIfStatsHCInOctets          Counter64,
        fsMIStdIpIfStatsInHdrErrors         Counter32,
        fsMIStdIpIfStatsInNoRoutes          Counter32,
        fsMIStdIpIfStatsInAddrErrors        Counter32,
        fsMIStdIpIfStatsInUnknownProtos     Counter32,
        fsMIStdIpIfStatsInTruncatedPkts     Counter32,
        fsMIStdIpIfStatsInForwDatagrams     Counter32,
        fsMIStdIpIfStatsHCInForwDatagrams   Counter64,
        fsMIStdIpIfStatsReasmReqds          Counter32,
        fsMIStdIpIfStatsReasmOKs            Counter32,
        fsMIStdIpIfStatsReasmFails          Counter32,
        fsMIStdIpIfStatsInDiscards          Counter32,
        fsMIStdIpIfStatsInDelivers          Counter32,
        fsMIStdIpIfStatsHCInDelivers        Counter64,
        fsMIStdIpIfStatsOutRequests         Counter32,
        fsMIStdIpIfStatsHCOutRequests       Counter64,
        fsMIStdIpIfStatsOutForwDatagrams    Counter32,
        fsMIStdIpIfStatsHCOutForwDatagrams  Counter64,
        fsMIStdIpIfStatsOutDiscards         Counter32,
        fsMIStdIpIfStatsOutFragReqds        Counter32,
        fsMIStdIpIfStatsOutFragOKs          Counter32,
        fsMIStdIpIfStatsOutFragFails        Counter32,
        fsMIStdIpIfStatsOutFragCreates      Counter32,
        fsMIStdIpIfStatsOutTransmits        Counter32,
        fsMIStdIpIfStatsHCOutTransmits      Counter64,
        fsMIStdIpIfStatsOutOctets           Counter32,
        fsMIStdIpIfStatsHCOutOctets         Counter64,
        fsMIStdIpIfStatsInMcastPkts         Counter32,
        fsMIStdIpIfStatsHCInMcastPkts       Counter64,
        fsMIStdIpIfStatsInMcastOctets       Counter32,
        fsMIStdIpIfStatsHCInMcastOctets     Counter64,
        fsMIStdIpIfStatsOutMcastPkts        Counter32,
        fsMIStdIpIfStatsHCOutMcastPkts      Counter64,
        fsMIStdIpIfStatsOutMcastOctets      Counter32,
        fsMIStdIpIfStatsHCOutMcastOctets    Counter64,
        fsMIStdIpIfStatsInBcastPkts         Counter32,
        fsMIStdIpIfStatsHCInBcastPkts       Counter64,
        fsMIStdIpIfStatsOutBcastPkts        Counter32,
        fsMIStdIpIfStatsHCOutBcastPkts      Counter64,
        fsMIStdIpIfStatsDiscontinuityTime   TimeStamp,
        fsMIStdIpIfStatsRefreshRate         Unsigned32,
        fsMIStdIpIfStatsContextId           Integer32
    }

fsMIStdIpIfStatsIPVersion OBJECT-TYPE
    SYNTAX     FsInetVersion
    MAX-ACCESS not-accessible
    STATUS     current
    DESCRIPTION
           "The IP version of this row."
    ::= { fsMIStdIpIfStatsEntry 1 }

fsMIStdIpIfStatsIfIndex OBJECT-TYPE
    SYNTAX     InterfaceIndex
    MAX-ACCESS not-accessible
    STATUS     current
    DESCRIPTION
           "The index value that uniquely identifies the interface to
            which this entry is applicable.  The interface identified by
            a particular value of this index is the same interface as
            identified by the same value of the IF-MIB's ifIndex."
    ::= { fsMIStdIpIfStatsEntry 2 }

fsMIStdIpIfStatsInReceives OBJECT-TYPE
    SYNTAX     Counter32
    MAX-ACCESS read-only
    STATUS     current
    DESCRIPTION
           "The total number of input IP datagrams received, including
            those received in error.

            Discontinuities in the value of this counter can occur at
            re-initialization of the management system, and at other
            times as indicated by the value of
            fsMIStdIpIfStatsDiscontinuityTime."
    ::= { fsMIStdIpIfStatsEntry 3 }

fsMIStdIpIfStatsHCInReceives OBJECT-TYPE
    SYNTAX     Counter64
    MAX-ACCESS read-only
    STATUS     current
    DESCRIPTION
           "The total number of input IP datagrams received, including
            those received in error.  This object counts the same
            datagrams as fsMIStdIpIfStatsInReceives, but allows for larger
            values.

            Discontinuities in the value of this counter can occur at
            re-initialization of the management system, and at other
            times as indicated by the value of
            fsMIStdIpIfStatsDiscontinuityTime."
    ::= { fsMIStdIpIfStatsEntry 4 }

fsMIStdIpIfStatsInOctets OBJECT-TYPE


    SYNTAX     Counter32
    MAX-ACCESS read-only
    STATUS     current
    DESCRIPTION
           "The total number of octets received in input IP datagrams,
            including those received in error.  Octets from datagrams
            counted in fsMIStdIpIfStatsInReceives MUST be counted here.

            Discontinuities in the value of this counter can occur at
            re-initialization of the management system, and at other
            times as indicated by the value of
            fsMIStdIpIfStatsDiscontinuityTime."
    ::= { fsMIStdIpIfStatsEntry 5 }

fsMIStdIpIfStatsHCInOctets OBJECT-TYPE
    SYNTAX     Counter64
    MAX-ACCESS read-only
    STATUS     current
    DESCRIPTION
           "The total number of octets received in input IP datagrams,
            including those received in error.  This object counts the
            same octets as fsMIStdIpIfStatsInOctets, but allows for larger
            values.

            Discontinuities in the value of this counter can occur at
            re-initialization of the management system, and at other
            times as indicated by the value of
            fsMIStdIpIfStatsDiscontinuityTime."
    ::= { fsMIStdIpIfStatsEntry 6 }

fsMIStdIpIfStatsInHdrErrors OBJECT-TYPE
    SYNTAX     Counter32
    MAX-ACCESS read-only
    STATUS     current
    DESCRIPTION
           "The number of input IP datagrams discarded due to errors in
            their IP headers, including version number mismatch, other
            format errors, hop count exceeded, errors discovered in
            processing their IP options, etc.

            Discontinuities in the value of this counter can occur at
            re-initialization of the management system, and at other
            times as indicated by the value of
            fsMIStdIpIfStatsDiscontinuityTime."
    ::= { fsMIStdIpIfStatsEntry 7 }

fsMIStdIpIfStatsInNoRoutes OBJECT-TYPE
    SYNTAX     Counter32
    MAX-ACCESS read-only
    STATUS     current
    DESCRIPTION
           "The number of input IP datagrams discarded because no route
            could be found to transmit them to their destination.

            Discontinuities in the value of this counter can occur at
            re-initialization of the management system, and at other
            times as indicated by the value of
            fsMIStdIpIfStatsDiscontinuityTime."
    ::= { fsMIStdIpIfStatsEntry 8 }

fsMIStdIpIfStatsInAddrErrors OBJECT-TYPE
    SYNTAX     Counter32
    MAX-ACCESS read-only
    STATUS     current
    DESCRIPTION
           "The number of input IP datagrams discarded because the IP
            address in their IP header's destination field was not a
            valid address to be received at this entity.  This count
            includes invalid addresses (e.g., ::0).  For entities that
            are not IP routers and therefore do not forward datagrams,
            this counter includes datagrams discarded because the
            destination address was not a local address.

            Discontinuities in the value of this counter can occur at
            re-initialization of the management system, and at other
            times as indicated by the value of
            fsMIStdIpIfStatsDiscontinuityTime."
    ::= { fsMIStdIpIfStatsEntry 9 }

fsMIStdIpIfStatsInUnknownProtos OBJECT-TYPE
    SYNTAX     Counter32
    MAX-ACCESS read-only
    STATUS     current
    DESCRIPTION
           "The number of locally-addressed IP datagrams received
            successfully but discarded because of an unknown or
            unsupported protocol.

            When tracking interface statistics, the counter of the
            interface to which these datagrams were addressed is
            incremented.  This interface might not be the same as the
            input interface for some of the datagrams.

            Discontinuities in the value of this counter can occur at
            re-initialization of the management system, and at other
            times as indicated by the value of
            fsMIStdIpIfStatsDiscontinuityTime."
    ::= { fsMIStdIpIfStatsEntry 10 }

fsMIStdIpIfStatsInTruncatedPkts OBJECT-TYPE
    SYNTAX     Counter32
    MAX-ACCESS read-only
    STATUS     current
    DESCRIPTION
           "The number of input IP datagrams discarded because the
            datagram frame didn't carry enough data.

            Discontinuities in the value of this counter can occur at
            re-initialization of the management system, and at other
            times as indicated by the value of
            fsMIStdIpIfStatsDiscontinuityTime."
    ::= { fsMIStdIpIfStatsEntry 11 }

fsMIStdIpIfStatsInForwDatagrams OBJECT-TYPE
    SYNTAX     Counter32
    MAX-ACCESS read-only
    STATUS     current
    DESCRIPTION
           "The number of input datagrams for which this entity was not
            their final IP destination and for which this entity
            attempted to find a route to forward them to that final
            destination.  In entities that do not act as IP routers,
            this counter will include only those datagrams that were
            Source-Routed via this entity, and the Source-Route
            processing was successful.

            When tracking interface statistics, the counter of the
            incoming interface is incremented for each datagram.

            Discontinuities in the value of this counter can occur at
            re-initialization of the management system, and at other
            times as indicated by the value of
            fsMIStdIpIfStatsDiscontinuityTime."
    ::= { fsMIStdIpIfStatsEntry 12 }

fsMIStdIpIfStatsHCInForwDatagrams OBJECT-TYPE
    SYNTAX     Counter64
    MAX-ACCESS read-only
    STATUS     current
    DESCRIPTION
           "The number of input datagrams for which this entity was not
            their final IP destination and for which this entity
            attempted to find a route to forward them to that final
            destination.  This object counts the same packets as
            fsMIStdIpIfStatsInForwDatagrams, but allows for larger values.

            Discontinuities in the value of this counter can occur at
            re-initialization of the management system, and at other
            times as indicated by the value of
            fsMIStdIpIfStatsDiscontinuityTime."
    ::= { fsMIStdIpIfStatsEntry 13 }

fsMIStdIpIfStatsReasmReqds OBJECT-TYPE
    SYNTAX     Counter32
    MAX-ACCESS read-only
    STATUS     current
    DESCRIPTION
           "The number of IP fragments received that needed to be
            reassembled at this interface.

            When tracking interface statistics, the counter of the
            interface to which these fragments were addressed is
            incremented.  This interface might not be the same as the
            input interface for some of the fragments.

            Discontinuities in the value of this counter can occur at
            re-initialization of the management system, and at other
            times as indicated by the value of
            fsMIStdIpIfStatsDiscontinuityTime."
    ::= { fsMIStdIpIfStatsEntry 14 }

fsMIStdIpIfStatsReasmOKs OBJECT-TYPE
    SYNTAX     Counter32
    MAX-ACCESS read-only
    STATUS     current
    DESCRIPTION
           "The number of IP datagrams successfully reassembled.

            When tracking interface statistics, the counter of the
            interface to which these datagrams were addressed is
            incremented.  This interface might not be the same as the
            input interface for some of the datagrams.

            Discontinuities in the value of this counter can occur at
            re-initialization of the management system, and at other
            times as indicated by the value of
            fsMIStdIpIfStatsDiscontinuityTime."
    ::= { fsMIStdIpIfStatsEntry 15 }

fsMIStdIpIfStatsReasmFails OBJECT-TYPE
    SYNTAX     Counter32
    MAX-ACCESS read-only
    STATUS     current
    DESCRIPTION
           "The number of failures detected by the IP re-assembly
            algorithm (for whatever reason: timed out, errors, etc.).
            Note that this is not necessarily a count of discarded IP
            fragments since some algorithms (notably the algorithm in
            RFC 815) can lose track of the number of fragments by
            combining them as they are received.

            When tracking interface statistics, the counter of the
            interface to which these fragments were addressed is
            incremented.  This interface might not be the same as the
            input interface for some of the fragments.

            Discontinuities in the value of this counter can occur at
            re-initialization of the management system, and at other
            times as indicated by the value of
            fsMIStdIpIfStatsDiscontinuityTime."
    ::= { fsMIStdIpIfStatsEntry 16 }

fsMIStdIpIfStatsInDiscards OBJECT-TYPE
    SYNTAX     Counter32
    MAX-ACCESS read-only
    STATUS     current
    DESCRIPTION
           "The number of input IP datagrams for which no problems were
            encountered to prevent their continued processing, but
            were discarded (e.g., for lack of buffer space).  Note that
            this counter does not include any datagrams discarded while
            awaiting re-assembly.

            Discontinuities in the value of this counter can occur at
            re-initialization of the management system, and at other
            times as indicated by the value of
            fsMIStdIpIfStatsDiscontinuityTime."
    ::= { fsMIStdIpIfStatsEntry 17 }

fsMIStdIpIfStatsInDelivers OBJECT-TYPE
    SYNTAX     Counter32
    MAX-ACCESS read-only
    STATUS     current
    DESCRIPTION
           "The total number of datagrams successfully delivered to IP
            user-protocols (including ICMP).

            When tracking interface statistics, the counter of the
            interface to which these datagrams were addressed is
            incremented.  This interface might not be the same as the
            input interface for some of the datagrams.

            Discontinuities in the value of this counter can occur at
            re-initialization of the management system, and at other
            times as indicated by the value of
            fsMIStdIpIfStatsDiscontinuityTime."
    ::= { fsMIStdIpIfStatsEntry 18 }

fsMIStdIpIfStatsHCInDelivers OBJECT-TYPE
    SYNTAX     Counter64
    MAX-ACCESS read-only
    STATUS     current
    DESCRIPTION
           "The total number of datagrams successfully delivered to IP
            user-protocols (including ICMP).  This object counts the
            same packets as fsMIStdIpIfStatsInDelivers, but allows for larger
            values.

            Discontinuities in the value of this counter can occur at
            re-initialization of the management system, and at other
            times as indicated by the value of
            fsMIStdIpIfStatsDiscontinuityTime."
    ::= { fsMIStdIpIfStatsEntry 19 }

fsMIStdIpIfStatsOutRequests OBJECT-TYPE
    SYNTAX     Counter32
    MAX-ACCESS read-only
    STATUS     current
    DESCRIPTION
           "The total number of IP datagrams that local IP user-
            protocols (including ICMP) supplied to IP in requests for
            transmission.  Note that this counter does not include any
            datagrams counted in fsMIStdIpIfStatsOutForwDatagrams.

            Discontinuities in the value of this counter can occur at
            re-initialization of the management system, and at other
            times as indicated by the value of
            fsMIStdIpIfStatsDiscontinuityTime."
    ::= { fsMIStdIpIfStatsEntry 20 }

fsMIStdIpIfStatsHCOutRequests OBJECT-TYPE
    SYNTAX     Counter64
    MAX-ACCESS read-only
    STATUS     current
    DESCRIPTION
           "The total number of IP datagrams that local IP user-
            protocols (including ICMP) supplied to IP in requests for
            transmission.  This object counts the same packets as
            fsMIStdIpIfStatsOutRequests, but allows for larger values.

            Discontinuities in the value of this counter can occur at
            re-initialization of the management system, and at other
            times as indicated by the value of
            fsMIStdIpIfStatsDiscontinuityTime."
    ::= { fsMIStdIpIfStatsEntry 21 }

fsMIStdIpIfStatsOutForwDatagrams OBJECT-TYPE
    SYNTAX     Counter32
    MAX-ACCESS read-only
    STATUS     current
    DESCRIPTION
           "The number of datagrams for which this entity was not their
            final IP destination and for which it was successful in
            finding a path to their final destination.  In entities
            that do not act as IP routers, this counter will include
            only those datagrams that were Source-Routed via this
            entity, and the Source-Route processing was successful.

            When tracking interface statistics, the counter of the
            outgoing interface is incremented for a successfully
            forwarded datagram.

            Discontinuities in the value of this counter can occur at
            re-initialization of the management system, and at other
            times as indicated by the value of
            fsMIStdIpIfStatsDiscontinuityTime."
    ::= { fsMIStdIpIfStatsEntry 22 }

fsMIStdIpIfStatsHCOutForwDatagrams OBJECT-TYPE
    SYNTAX     Counter64
    MAX-ACCESS read-only
    STATUS     current
    DESCRIPTION
           "The number of datagrams for which this entity was not their
            final IP destination and for which it was successful in
            finding a path to their final destination.  This object
            counts the same packets as fsMIStdIpIfStatsOutForwDatagrams, but
            allows for larger values.

            Discontinuities in the value of this counter can occur at
            re-initialization of the management system, and at other
            times as indicated by the value of
            fsMIStdIpIfStatsDiscontinuityTime."
    ::= { fsMIStdIpIfStatsEntry 23 }

fsMIStdIpIfStatsOutDiscards OBJECT-TYPE
    SYNTAX     Counter32
    MAX-ACCESS read-only
    STATUS     current
    DESCRIPTION
           "The number of output IP datagrams for which no problem was
            encountered to prevent their transmission to their
            destination, but were discarded (e.g., for lack of
            buffer space).  Note that this counter would include
            datagrams counted in fsMIStdIpIfStatsOutForwDatagrams if any such
            datagrams met this (discretionary) discard criterion.

            Discontinuities in the value of this counter can occur at
            re-initialization of the management system, and at other
            times as indicated by the value of
            fsMIStdIpIfStatsDiscontinuityTime."
    ::= { fsMIStdIpIfStatsEntry 24 }

fsMIStdIpIfStatsOutFragReqds OBJECT-TYPE
    SYNTAX     Counter32
    MAX-ACCESS read-only
    STATUS     current
    DESCRIPTION
           "The number of IP datagrams that would require fragmentation
            in order to be transmitted.

            When tracking interface statistics, the counter of the
            outgoing interface is incremented for a successfully
            fragmented datagram.

            Discontinuities in the value of this counter can occur at
            re-initialization of the management system, and at other
            times as indicated by the value of
            fsMIStdIpIfStatsDiscontinuityTime."
    ::= { fsMIStdIpIfStatsEntry 25 }

fsMIStdIpIfStatsOutFragOKs OBJECT-TYPE
    SYNTAX     Counter32
    MAX-ACCESS read-only
    STATUS     current
    DESCRIPTION
           "The number of IP datagrams that have been successfully
            fragmented.

            When tracking interface statistics, the counter of the
            outgoing interface is incremented for a successfully
            fragmented datagram.

            Discontinuities in the value of this counter can occur at
            re-initialization of the management system, and at other
            times as indicated by the value of
            fsMIStdIpIfStatsDiscontinuityTime."
    ::= { fsMIStdIpIfStatsEntry 26 }

fsMIStdIpIfStatsOutFragFails OBJECT-TYPE
    SYNTAX     Counter32
    MAX-ACCESS read-only
    STATUS     current
    DESCRIPTION
           "The number of IP datagrams that have been discarded because
            they needed to be fragmented but could not be.  This
            includes IPv4 packets that have the DF bit set and IPv6
            packets that are being forwarded and exceed the outgoing
            link MTU.

            When tracking interface statistics, the counter of the
            outgoing interface is incremented for an unsuccessfully
            fragmented datagram.

            Discontinuities in the value of this counter can occur at
            re-initialization of the management system, and at other
            times as indicated by the value of
            fsMIStdIpIfStatsDiscontinuityTime."
    ::= { fsMIStdIpIfStatsEntry 27 }

fsMIStdIpIfStatsOutFragCreates OBJECT-TYPE
    SYNTAX     Counter32
    MAX-ACCESS read-only
    STATUS     current
    DESCRIPTION
           "The number of output datagram fragments that have been
            generated as a result of IP fragmentation.

            When tracking interface statistics, the counter of the
            outgoing interface is incremented for a successfully
            fragmented datagram.

            Discontinuities in the value of this counter can occur at
            re-initialization of the management system, and at other
            times as indicated by the value of
            fsMIStdIpIfStatsDiscontinuityTime."
    ::= { fsMIStdIpIfStatsEntry 28 }

fsMIStdIpIfStatsOutTransmits OBJECT-TYPE
    SYNTAX     Counter32
    MAX-ACCESS read-only
    STATUS     current
    DESCRIPTION
           "The total number of IP datagrams that this entity supplied
            to the lower layers for transmission.  This includes
            datagrams generated locally and those forwarded by this
            entity.

            Discontinuities in the value of this counter can occur at
            re-initialization of the management system, and at other
            times as indicated by the value of
            fsMIStdIpIfStatsDiscontinuityTime."
    ::= { fsMIStdIpIfStatsEntry 29 }

fsMIStdIpIfStatsHCOutTransmits OBJECT-TYPE
    SYNTAX     Counter64
    MAX-ACCESS read-only
    STATUS     current
    DESCRIPTION
           "The total number of IP datagrams that this entity supplied
            to the lower layers for transmission.  This object counts
            the same datagrams as fsMIStdIpIfStatsOutTransmits, but allows for
            larger values.

            Discontinuities in the value of this counter can occur at
            re-initialization of the management system, and at other
            times as indicated by the value of
            fsMIStdIpIfStatsDiscontinuityTime."
    ::= { fsMIStdIpIfStatsEntry 30 }

fsMIStdIpIfStatsOutOctets OBJECT-TYPE
    SYNTAX     Counter32
    MAX-ACCESS read-only
    STATUS     current
    DESCRIPTION
           "The total number of octets in IP datagrams delivered to the
            lower layers for transmission.  Octets from datagrams
            counted in fsMIStdIpIfStatsOutTransmits MUST be counted here.

            Discontinuities in the value of this counter can occur at
            re-initialization of the management system, and at other
            times as indicated by the value of
            fsMIStdIpIfStatsDiscontinuityTime."
    ::= { fsMIStdIpIfStatsEntry 31 }

fsMIStdIpIfStatsHCOutOctets OBJECT-TYPE
    SYNTAX     Counter64
    MAX-ACCESS read-only
    STATUS     current
    DESCRIPTION
           "The total number of octets in IP datagrams delivered to the
            lower layers for transmission.  This objects counts the same
            octets as fsMIStdIpIfStatsOutOctets, but allows for larger values.

            Discontinuities in the value of this counter can occur at
            re-initialization of the management system, and at other
            times as indicated by the value of
            fsMIStdIpIfStatsDiscontinuityTime."
    ::= { fsMIStdIpIfStatsEntry 32 }

fsMIStdIpIfStatsInMcastPkts OBJECT-TYPE
    SYNTAX     Counter32
    MAX-ACCESS read-only
    STATUS     current
    DESCRIPTION
           "The number of IP multicast datagrams received.

            Discontinuities in the value of this counter can occur at
            re-initialization of the management system, and at other
            times as indicated by the value of
            fsMIStdIpIfStatsDiscontinuityTime."
    ::= { fsMIStdIpIfStatsEntry 33 }

fsMIStdIpIfStatsHCInMcastPkts OBJECT-TYPE
    SYNTAX     Counter64
    MAX-ACCESS read-only
    STATUS     current
    DESCRIPTION
           "The number of IP multicast datagrams received.  This object
            counts the same datagrams as fsMIStdIpIfStatsInMcastPkts, but
            allows for larger values.

            Discontinuities in the value of this counter can occur at
            re-initialization of the management system, and at other
            times as indicated by the value of
            fsMIStdIpIfStatsDiscontinuityTime."
    ::= { fsMIStdIpIfStatsEntry 34 }

fsMIStdIpIfStatsInMcastOctets OBJECT-TYPE
    SYNTAX     Counter32
    MAX-ACCESS read-only
    STATUS     current
    DESCRIPTION
           "The total number of octets received in IP multicast
            datagrams.  Octets from datagrams counted in
            fsMIStdIpIfStatsInMcastPkts MUST be counted here.

            Discontinuities in the value of this counter can occur at
            re-initialization of the management system, and at other
            times as indicated by the value of
            fsMIStdIpIfStatsDiscontinuityTime."
    ::= { fsMIStdIpIfStatsEntry 35 }

fsMIStdIpIfStatsHCInMcastOctets OBJECT-TYPE
    SYNTAX     Counter64
    MAX-ACCESS read-only
    STATUS     current
    DESCRIPTION
           "The total number of octets received in IP multicast
            datagrams.  This object counts the same octets as
            fsMIStdIpIfStatsInMcastOctets, but allows for larger values.

            Discontinuities in the value of this counter can occur at
            re-initialization of the management system, and at other
            times as indicated by the value of
            fsMIStdIpIfStatsDiscontinuityTime."
    ::= { fsMIStdIpIfStatsEntry 36 }

fsMIStdIpIfStatsOutMcastPkts OBJECT-TYPE
    SYNTAX     Counter32
    MAX-ACCESS read-only
    STATUS     current
    DESCRIPTION
           "The number of IP multicast datagrams transmitted.

            Discontinuities in the value of this counter can occur at
            re-initialization of the management system, and at other
            times as indicated by the value of
            fsMIStdIpIfStatsDiscontinuityTime."
    ::= { fsMIStdIpIfStatsEntry 37 }

fsMIStdIpIfStatsHCOutMcastPkts OBJECT-TYPE
    SYNTAX     Counter64
    MAX-ACCESS read-only
    STATUS     current
    DESCRIPTION
           "The number of IP multicast datagrams transmitted.  This
            object counts the same datagrams as fsMIStdIpIfStatsOutMcastPkts,
            but allows for larger values.

            Discontinuities in the value of this counter can occur at
            re-initialization of the management system, and at other
            times as indicated by the value of
            fsMIStdIpIfStatsDiscontinuityTime."
    ::= { fsMIStdIpIfStatsEntry 38 }

fsMIStdIpIfStatsOutMcastOctets OBJECT-TYPE
    SYNTAX     Counter32
    MAX-ACCESS read-only
    STATUS     current
    DESCRIPTION
           "The total number of octets transmitted in IP multicast
            datagrams.  Octets from datagrams counted in
            fsMIStdIpIfStatsOutMcastPkts MUST be counted here.

            Discontinuities in the value of this counter can occur at
            re-initialization of the management system, and at other
            times as indicated by the value of
            fsMIStdIpIfStatsDiscontinuityTime."
    ::= { fsMIStdIpIfStatsEntry 39 }

fsMIStdIpIfStatsHCOutMcastOctets OBJECT-TYPE
    SYNTAX     Counter64
    MAX-ACCESS read-only
    STATUS     current
    DESCRIPTION
           "The total number of octets transmitted in IP multicast
            datagrams.  This object counts the same octets as
            fsMIStdIpIfStatsOutMcastOctets, but allows for larger values.

            Discontinuities in the value of this counter can occur at
            re-initialization of the management system, and at other
            times as indicated by the value of
            fsMIStdIpIfStatsDiscontinuityTime."
    ::= { fsMIStdIpIfStatsEntry 40 }

fsMIStdIpIfStatsInBcastPkts OBJECT-TYPE
    SYNTAX     Counter32
    MAX-ACCESS read-only
    STATUS     current
    DESCRIPTION
           "The number of IP broadcast datagrams received.

            Discontinuities in the value of this counter can occur at
            re-initialization of the management system, and at other
            times as indicated by the value of
            fsMIStdIpIfStatsDiscontinuityTime."
    ::= { fsMIStdIpIfStatsEntry 41 }

fsMIStdIpIfStatsHCInBcastPkts OBJECT-TYPE
    SYNTAX     Counter64
    MAX-ACCESS read-only
    STATUS     current
    DESCRIPTION
           "The number of IP broadcast datagrams received.  This object
            counts the same datagrams as fsMIStdIpIfStatsInBcastPkts, but
            allows for larger values.

            Discontinuities in the value of this counter can occur at
            re-initialization of the management system, and at other
            times as indicated by the value of
            fsMIStdIpIfStatsDiscontinuityTime."
    ::= { fsMIStdIpIfStatsEntry 42 }

fsMIStdIpIfStatsOutBcastPkts OBJECT-TYPE
    SYNTAX     Counter32
    MAX-ACCESS read-only
    STATUS     current
    DESCRIPTION
           "The number of IP broadcast datagrams transmitted.

            Discontinuities in the value of this counter can occur at
            re-initialization of the management system, and at other
            times as indicated by the value of
            fsMIStdIpIfStatsDiscontinuityTime."
    ::= { fsMIStdIpIfStatsEntry 43 }

fsMIStdIpIfStatsHCOutBcastPkts OBJECT-TYPE
    SYNTAX     Counter64
    MAX-ACCESS read-only
    STATUS     current
    DESCRIPTION
           "The number of IP broadcast datagrams transmitted.  This
            object counts the same datagrams as fsMIStdIpIfStatsOutBcastPkts,
            but allows for larger values.

            Discontinuities in the value of this counter can occur at
            re-initialization of the management system, and at other
            times as indicated by the value of
            fsMIStdIpIfStatsDiscontinuityTime."
    ::= { fsMIStdIpIfStatsEntry 44 }

fsMIStdIpIfStatsDiscontinuityTime OBJECT-TYPE
    SYNTAX     TimeStamp
    MAX-ACCESS read-only
    STATUS     current
    DESCRIPTION
           "The value of sysUpTime on the most recent occasion at which
            any one or more of this entry's counters suffered a
            discontinuity.

            If no such discontinuities have occurred since the last re-
            initialization of the local management subsystem, then this
            object contains a zero value."
    ::= { fsMIStdIpIfStatsEntry 45 }

fsMIStdIpIfStatsRefreshRate OBJECT-TYPE
    SYNTAX     Unsigned32
    UNITS "milli-seconds"
    MAX-ACCESS read-only
    STATUS     current
    DESCRIPTION
           "The minimum reasonable polling interval for this entry.
            This object provides an indication of the minimum amount of
            time required to update the counters in this entry."
    ::= { fsMIStdIpIfStatsEntry 47 }

fsMIStdIpIfStatsContextId OBJECT-TYPE
    SYNTAX     Integer32
    MAX-ACCESS read-only
    STATUS     current
    DESCRIPTION
           "The context id to which this interface is mapped."
    ::= { fsMIStdIpIfStatsEntry 48 }

--
-- Internet Address Prefix table with context id
--

fsMIStdIpAddressPrefixTable OBJECT-TYPE
    SYNTAX     SEQUENCE OF FsMIStdIpAddressPrefixEntry
    MAX-ACCESS not-accessible
    STATUS     current
    DESCRIPTION
           "This table allows the user to determine the source of an IP
            address or set of IP addresses, and allows other tables to
            share the information via pointer rather than by copying.

            For example, when the node configures both a unicast and
            anycast address for a prefix, the fsMIStdIpAddressPrefix objects
            for those addresses will point to a single row in this
            table.

            This table primarily provides support for IPv6 prefixes, and
            several of the objects are less meaningful for IPv4.  The
            table continues to allow IPv4 addresses to allow future
            flexibility.  In order to promote a common configuration,
            this document includes suggestions for default values for
            IPv4 prefixes.  Each of these values may be overridden if an
            object is meaningful to the node.

            All prefixes used by this entity should be included in this
            table independent of how the entity learned the prefix.
            (This table isn't limited to prefixes learned from router
            advertisements.)"
    ::= { fsMIStdIp 9 }

fsMIStdIpAddressPrefixEntry OBJECT-TYPE
    SYNTAX     FsMIStdIpAddressPrefixEntry
    MAX-ACCESS not-accessible
    STATUS     current
    DESCRIPTION
           "An entry in the fsMIStdIpAddressPrefixTable."
    INDEX    { fsMIStdIpAddressPrefixIfIndex, fsMIStdIpAddressPrefixType,
               fsMIStdIpAddressPrefixPrefix, fsMIStdIpAddressPrefixLength }
    ::= { fsMIStdIpAddressPrefixTable 1 }

FsMIStdIpAddressPrefixEntry ::= SEQUENCE {
        fsMIStdIpAddressPrefixIfIndex               InterfaceIndex,
        fsMIStdIpAddressPrefixType                  InetAddressType,
        fsMIStdIpAddressPrefixPrefix                InetAddress,
        fsMIStdIpAddressPrefixLength                InetAddressPrefixLength,
        fsMIStdIpAddressPrefixOrigin                IpAddressPrefixOriginTC,
        fsMIStdIpAddressPrefixOnLinkFlag            TruthValue,
        fsMIStdIpAddressPrefixAutonomousFlag        TruthValue,
        fsMIStdIpAddressPrefixAdvPreferredLifetime  Unsigned32,
        fsMIStdIpAddressPrefixAdvValidLifetime      Unsigned32,
        fsMIStdIpAddressContextId                   Integer32
    }

fsMIStdIpAddressPrefixIfIndex OBJECT-TYPE
    SYNTAX     InterfaceIndex
    MAX-ACCESS not-accessible
    STATUS     current
    DESCRIPTION
           "The index value that uniquely identifies the interface on
            which this prefix is configured.  The interface identified
            by a particular value of this index is the same interface as
            identified by the same value of the IF-MIB's ifIndex."
    ::= { fsMIStdIpAddressPrefixEntry 1 }

fsMIStdIpAddressPrefixType OBJECT-TYPE
    SYNTAX     InetAddressType
    MAX-ACCESS not-accessible
    STATUS     current
    DESCRIPTION
           "The address type of fsMIStdIpAddressPrefix."
    ::= { fsMIStdIpAddressPrefixEntry 2 }

fsMIStdIpAddressPrefixPrefix OBJECT-TYPE
    SYNTAX     InetAddress (SIZE(16))
    MAX-ACCESS not-accessible
    STATUS     current
    DESCRIPTION
           "The address prefix.  The address type of this object is
            specified in fsMIStdIpAddressPrefixType.  The length of this object
            is the standard length for objects of that type (4 or 16
            bytes).  Any bits after fsMIStdIpAddressPrefixLength must be zero.

            Implementors need to be aware that, if the size of
            fsMIStdIpAddressPrefixPrefix exceeds 114 octets, then OIDS of
            instances of columns in this row will have more than 128
            sub-identifiers and cannot be accessed using SNMPv1,
            SNMPv2c, or SNMPv3."
    ::= { fsMIStdIpAddressPrefixEntry 3 }

fsMIStdIpAddressPrefixLength OBJECT-TYPE
    SYNTAX     InetAddressPrefixLength
    MAX-ACCESS not-accessible
    STATUS     current
    DESCRIPTION
           "The prefix length associated with this prefix.

            The value 0 has no special meaning for this object.  It
            simply refers to address '::/0'."
    ::= { fsMIStdIpAddressPrefixEntry 4 }

fsMIStdIpAddressPrefixOrigin OBJECT-TYPE
    SYNTAX     IpAddressPrefixOriginTC
    MAX-ACCESS read-only
    STATUS     current
    DESCRIPTION
           "The origin of this prefix."
    ::= { fsMIStdIpAddressPrefixEntry 5 }

fsMIStdIpAddressPrefixOnLinkFlag OBJECT-TYPE
    SYNTAX     TruthValue
    MAX-ACCESS read-only
    STATUS     current
    DESCRIPTION
           "This object has the value 'true(1)', if this prefix can be
            used for on-link determination; otherwise, the value is
            'false(2)'.

            The default for IPv4 prefixes is 'true(1)'."
    ::= { fsMIStdIpAddressPrefixEntry 6 }

fsMIStdIpAddressPrefixAutonomousFlag OBJECT-TYPE
    SYNTAX     TruthValue
    MAX-ACCESS read-only
    STATUS     current
    DESCRIPTION
           "Autonomous address configuration flag.  When true(1),
            indicates that this prefix can be used for autonomous
            address configuration (i.e., can be used to form a local
            interface address).  If false(2), it is not used to auto-
            configure a local interface address.

            The default for IPv4 prefixes is 'false(2)'."
    ::= { fsMIStdIpAddressPrefixEntry 7 }

fsMIStdIpAddressPrefixAdvPreferredLifetime OBJECT-TYPE
    SYNTAX     Unsigned32
    UNITS      "seconds"
    MAX-ACCESS read-only
    STATUS     current
    DESCRIPTION
           "The remaining length of time, in seconds, that this prefix
            will continue to be preferred, i.e., time until deprecation.

            A value of 4,294,967,295 represents infinity.

            The address generated from a deprecated prefix should no
            longer be used as a source address in new communications,
            but packets received on such an interface are processed as
            expected.

            The default for IPv4 prefixes is 4,294,967,295 (infinity)."
    ::= { fsMIStdIpAddressPrefixEntry 8 }

fsMIStdIpAddressPrefixAdvValidLifetime OBJECT-TYPE
    SYNTAX     Unsigned32
    UNITS       "seconds"
    MAX-ACCESS read-only
    STATUS     current
    DESCRIPTION
           "The remaining length of time, in seconds, that this prefix
            will continue to be valid, i.e., time until invalidation.  A
            value of 4,294,967,295 represents infinity.

            The address generated from an invalidated prefix should not
            appear as the destination or source address of a packet.
            The default for IPv4 prefixes is 4,294,967,295 (infinity)."
    ::= { fsMIStdIpAddressPrefixEntry 9 }

fsMIStdIpAddressContextId OBJECT-TYPE
    SYNTAX     Integer32
    MAX-ACCESS read-only
    STATUS     current
    DESCRIPTION
           "The context to which this interface is mapped."
    ::= { fsMIStdIpAddressPrefixEntry 10 }

--
--IP address Table with context id support.
--

fsMIStdIpAddressTable OBJECT-TYPE
    SYNTAX     SEQUENCE OF FsMIStdIpAddressEntry
    MAX-ACCESS not-accessible
    STATUS     current
    DESCRIPTION
           "This table contains addressing information relevant to the
            entity's interfaces.
            While this table is writable, the user will note that
            several objects, such as fsMIStdIpAddressOrigin, are not.  The
            intention in allowing a user to write to this table is to
            allow them to add or remove any entry that isn't
            permanent.  The user should be allowed to modify objects
            and entries when that would not cause inconsistencies
            within the table.  Allowing write access to objects, such
            as fsMIStdIpAddressOrigin, could allow a user to insert an entry
            and then label it incorrectly.

            Note well: When including IPv6 link-local addresses in this
            table, the entry must use an InetAddressType of 'ipv6z' in
            order to differentiate between the possible interfaces."
    ::= { fsMIStdIp 10 }

fsMIStdIpAddressEntry OBJECT-TYPE
    SYNTAX     FsMIStdIpAddressEntry
    MAX-ACCESS not-accessible
    STATUS     current
    DESCRIPTION
           "An address mapping for a particular interface in a specific virtual
            router."
    INDEX { fsMIStdIpContextId, fsMIStdIpAddressAddrType, fsMIStdIpAddressAddr }
    ::= { fsMIStdIpAddressTable 1 }

FsMIStdIpAddressEntry ::= SEQUENCE {
        fsMIStdIpAddressAddrType     InetAddressType,
        fsMIStdIpAddressAddr         InetAddress,
        fsMIStdIpAddressIfIndex      InterfaceIndex,
        fsMIStdIpAddressType         INTEGER,
        fsMIStdIpAddressPrefix       RowPointer,
        fsMIStdIpAddressOrigin       IpAddressOriginTC,
        fsMIStdIpAddressStatus       IpAddressStatusTC,
        fsMIStdIpAddressCreated      TimeStamp,
        fsMIStdIpAddressLastChanged  TimeStamp,
        fsMIStdIpAddressRowStatus    RowStatus,
        fsMIStdIpAddressStorageType  StorageType
    }

fsMIStdIpAddressAddrType OBJECT-TYPE
    SYNTAX     InetAddressType
    MAX-ACCESS not-accessible
    STATUS     current
    DESCRIPTION
           "The address type of fsMIStdIpAddressAddr."
    ::= { fsMIStdIpAddressEntry 2 }

fsMIStdIpAddressAddr OBJECT-TYPE
    SYNTAX     InetAddress (SIZE(16))
    MAX-ACCESS not-accessible
    STATUS     current
    DESCRIPTION
           "The IP address to which this entry's addressing information
            pertains.  The address type of this object is specified in
            fsMIStdIpAddressAddrType.

            Implementors need to be aware that if the size of
            fsMIStdIpAddressAddr exceeds 116 octets, then OIDS of instances of
            columns in this row will have more than 128 sub-identifiers
            and cannot be accessed using SNMPv1, SNMPv2c, or SNMPv3."
    ::= { fsMIStdIpAddressEntry 3 }

fsMIStdIpAddressIfIndex OBJECT-TYPE
    SYNTAX     InterfaceIndex
    MAX-ACCESS read-create
    STATUS     current
    DESCRIPTION
           "The index value that uniquely identifies the interface to
            which this entry is applicable.  The interface identified by
            a particular value of this index is the same interface as
            identified by the same value of the IF-MIB's ifIndex."
    ::= { fsMIStdIpAddressEntry 4 }

fsMIStdIpAddressType OBJECT-TYPE
    SYNTAX     INTEGER {
                 unicast(1),
                 anycast(2),
                 broadcast(3)
    }
    MAX-ACCESS read-create
    STATUS     current
    DESCRIPTION
           "The type of address.  broadcast(3) is not a valid value for
            IPv6 addresses (RFC 3513)."
    DEFVAL { unicast }
    ::= { fsMIStdIpAddressEntry 5 }

fsMIStdIpAddressPrefix OBJECT-TYPE
    SYNTAX     RowPointer
    MAX-ACCESS read-only
    STATUS     current
    DESCRIPTION
           "A pointer to the row in the prefix table to which this
            address belongs.  May be { 0 0 } if there is no such row."
    ::= { fsMIStdIpAddressEntry 6 }

fsMIStdIpAddressOrigin OBJECT-TYPE
    SYNTAX     IpAddressOriginTC
    MAX-ACCESS read-only
    STATUS     current



    DESCRIPTION
           "The origin of the address."
    ::= { fsMIStdIpAddressEntry 7 }

fsMIStdIpAddressStatus OBJECT-TYPE
    SYNTAX     IpAddressStatusTC
    MAX-ACCESS read-create
    STATUS     current
    DESCRIPTION
           "The status of the address, describing if the address can be
            used for communication.

            In the absence of other information, an IPv4 address is
            always preferred(1)."
    ::= { fsMIStdIpAddressEntry 8 }

fsMIStdIpAddressCreated OBJECT-TYPE
    SYNTAX     TimeStamp
    MAX-ACCESS read-only
    STATUS     current
    DESCRIPTION
           "The value of sysUpTime at the time this entry was created.
            If this entry was created prior to the last re-
            initialization of the local network management subsystem,
            then this object contains a zero value."
    ::= { fsMIStdIpAddressEntry 9 }

fsMIStdIpAddressLastChanged OBJECT-TYPE
    SYNTAX     TimeStamp
    MAX-ACCESS read-only
    STATUS     current
    DESCRIPTION
           "The value of sysUpTime at the time this entry was last
            updated.  If this entry was updated prior to the last re-
            initialization of the local network management subsystem,
            then this object contains a zero value."
    ::= { fsMIStdIpAddressEntry 10 }

fsMIStdIpAddressRowStatus OBJECT-TYPE
    SYNTAX     RowStatus
    MAX-ACCESS read-create
    STATUS     current
    DESCRIPTION
           "The status of this conceptual row.

            The RowStatus TC requires that this DESCRIPTION clause
            states under which circumstances other objects in this row



            can be modified.  The value of this object has no effect on
            whether other objects in this conceptual row can be
            modified.

            A conceptual row can not be made active until the
            fsMIStdIpAddressIfIndex has been set to a valid index."
    ::= { fsMIStdIpAddressEntry 11 }

fsMIStdIpAddressStorageType OBJECT-TYPE
    SYNTAX     StorageType
    MAX-ACCESS read-create
    STATUS     current
    DESCRIPTION
           "The storage type for this conceptual row.  If this object
            has a value of 'permanent', then no other objects are
            required to be able to be modified."
    DEFVAL { volatile }
    ::= { fsMIStdIpAddressEntry 12 }

--
-- the Internet Address Translation table with context id
--
    fsMIStdIpNetToPhysicalTable OBJECT-TYPE
    SYNTAX     SEQUENCE OF FsMIStdIpNetToPhysicalEntry
    MAX-ACCESS not-accessible
    STATUS     current
    DESCRIPTION
        "The IP Address Translation table used for mapping from IP
         addresses to physical addresses in each virutal router.

         The Address Translation tables contain the IP address to
         'physical' address equivalences.  Some interfaces do not use
         translation tables for determining address equivalences
         (e.g., DDN-X.25 has an algorithmic method); if all
         interfaces are of this type, then the Address Translation
         table is empty, i.e., has zero entries.

         While many protocols may be used to populate this table, ARP
         and Neighbor Discovery are the most likely
         options."
    ::= { fsMIStdIp 11 }

    fsMIStdIpNetToPhysicalEntry OBJECT-TYPE
    SYNTAX     FsMIStdIpNetToPhysicalEntry
    MAX-ACCESS not-accessible
    STATUS     current
    DESCRIPTION
        "Each entry contains one IP address to `physical' address
         equivalence."
    INDEX { fsMIStdIpNetToPhysicalIfIndex,
            fsMIStdIpNetToPhysicalNetAddressType,
            fsMIStdIpNetToPhysicalNetAddress }
    ::= { fsMIStdIpNetToPhysicalTable 1 }

    FsMIStdIpNetToPhysicalEntry ::= SEQUENCE {
        fsMIStdIpNetToPhysicalIfIndex         InterfaceIndex,
        fsMIStdIpNetToPhysicalNetAddressType  InetAddressType,
        fsMIStdIpNetToPhysicalNetAddress      InetAddress,
        fsMIStdIpNetToPhysicalPhysAddress     PhysAddress,
        fsMIStdIpNetToPhysicalLastUpdated     TimeStamp,
        fsMIStdIpNetToPhysicalType            INTEGER,
        fsMIStdIpNetToPhysicalState           INTEGER,
        fsMIStdIpNetToPhysicalRowStatus       RowStatus,
        fsMIStdIpNetToPhysicalContextId       Integer32
    }

    fsMIStdIpNetToPhysicalIfIndex OBJECT-TYPE
    SYNTAX     InterfaceIndex
    MAX-ACCESS not-accessible
    STATUS     current
    DESCRIPTION
        "The index value that uniquely identifies the interface to
         which this entry is applicable.  The interface identified by
         a particular value of this index is the same interface as
         identified by the same value of the IF-MIB's ifIndex."
    ::= { fsMIStdIpNetToPhysicalEntry 1 }

    fsMIStdIpNetToPhysicalNetAddressType OBJECT-TYPE
    SYNTAX     InetAddressType
    MAX-ACCESS not-accessible
    STATUS     current
    DESCRIPTION
        "The type of fsMIStdIpNetToPhysicalNetAddress."
    ::= { fsMIStdIpNetToPhysicalEntry 2 }

    fsMIStdIpNetToPhysicalNetAddress OBJECT-TYPE
    SYNTAX     InetAddress (SIZE(16))
    MAX-ACCESS not-accessible
    STATUS     current
    DESCRIPTION
        "The IP Address corresponding to the media-dependent
         `physical' address.  The address type of this object is
         specified in fsMIStdIpNetToPhysicalAddressType."
    ::= { fsMIStdIpNetToPhysicalEntry 3 }

    fsMIStdIpNetToPhysicalPhysAddress OBJECT-TYPE
    SYNTAX     PhysAddress (SIZE(0..65535))
    MAX-ACCESS read-create
    STATUS     current
    DESCRIPTION
        "The media-dependent `physical' address."
    ::= { fsMIStdIpNetToPhysicalEntry 4 }

    fsMIStdIpNetToPhysicalLastUpdated OBJECT-TYPE
    SYNTAX     TimeStamp
    MAX-ACCESS read-only
    STATUS     current
    DESCRIPTION
        "The value of sysUpTime at the time this entry was last
         updated."
    ::= { fsMIStdIpNetToPhysicalEntry 5 }

    fsMIStdIpNetToPhysicalType OBJECT-TYPE
    SYNTAX     INTEGER {
                other(1),        -- none of the following
                invalid(2),      -- an invalidated mapping
                dynamic(3),
                static(4),
                local(5)         -- local interface
            }
    MAX-ACCESS read-create
    STATUS     current
    DESCRIPTION
        "The type of mapping.

         Setting this object to the value invalid(2) has the effect
         of invalidating the corresponding entry (static entry) in the
         fsMIStdIpNetToPhysicalTable.  That is, the agent removes the
         invalidated entry from the table.

         The 'dynamic(3)' type indicates that the IP address to
         physical addresses mapping has been dynamically resolved
         using e.g., IPv4 ARP or the IPv6 Neighbor Discovery
         protocol.

         The 'static(4)' type indicates that the mapping has been
         statically configured.  Both of these refer to entries that
         provide mappings for other entities addresses.

         The 'local(5)' type indicates that the mapping is provided
         for an entity's own interface address."
    DEFVAL { static }
    ::= { fsMIStdIpNetToPhysicalEntry 6 }

    fsMIStdIpNetToPhysicalState OBJECT-TYPE
    SYNTAX     INTEGER {
                     reachable(1), -- confirmed reachability

                     stale(2),     -- unconfirmed reachability

                     delay(3),     -- waiting for reachability
                                   -- confirmation before entering
                                   -- the probe state

                     probe(4),     -- actively probing

                     invalid(5),   -- an invalidated mapping

                     unknown(6),   -- state can not be determined
                                   -- for some reason.

                     incomplete(7) -- address resolution is being
                                   -- performed.
                    }
    MAX-ACCESS read-only
    STATUS     current
    DESCRIPTION
        "The Neighbor Unreachability Detection state for the
         interface when the address mapping in this entry is used.
         If Neighbor Unreachability Detection is not in use (e.g. for
         IPv4), this object is always unknown(6)."
    ::= { fsMIStdIpNetToPhysicalEntry 7 }

    fsMIStdIpNetToPhysicalRowStatus OBJECT-TYPE
    SYNTAX     RowStatus
    MAX-ACCESS read-create
    STATUS     current
    DESCRIPTION
        "The status of this conceptual row.
         The value of this object has no effect on whether
         other objects in this conceptual row can be modified.

         A conceptual row can not be made active until the
         fsMIStdIpNetToPhysicalPhysAddress object has been set.

         If the fsMIStdIpNetToPhysicalType is set to 'invalid',
         the managed node deletes the entry independent of the
         state of this object."
    ::= { fsMIStdIpNetToPhysicalEntry 8 }

fsMIStdIpNetToPhysicalContextId OBJECT-TYPE
    SYNTAX     Integer32
    MAX-ACCESS read-only
    STATUS     current
    DESCRIPTION
           "The context to which this NetToPhysical entry belongs."
    ::= { fsMIStdIpNetToPhysicalEntry 9 }


--
-- The IPv6 Scope Zone Index Table with context id.
--

fsMIStdIpv6ScopeZoneIndexTable OBJECT-TYPE
    SYNTAX     SEQUENCE OF FsMIStdIpv6ScopeZoneIndexEntry
    MAX-ACCESS not-accessible
    STATUS     current
    DESCRIPTION
           "The table used to describe IPv6 unicast and multicast scope
            zones.

            For those objects that have names rather than numbers, the
            names were chosen to coincide with the names used in the
            IPv6 address architecture document. "
    ::= { fsMIStdIp 12 }

fsMIStdIpv6ScopeZoneIndexEntry OBJECT-TYPE
    SYNTAX     FsMIStdIpv6ScopeZoneIndexEntry
    MAX-ACCESS not-accessible
    STATUS     current
    DESCRIPTION
           "Each entry contains the list of scope identifiers on a given
            interface."
    INDEX { fsMIStdIpv6ScopeZoneIndexIfIndex }
    ::= { fsMIStdIpv6ScopeZoneIndexTable 1 }

FsMIStdIpv6ScopeZoneIndexEntry ::= SEQUENCE {
        fsMIStdIpv6ScopeZoneIndexIfIndex            InterfaceIndex,
        fsMIStdIpv6ScopeZoneIndexLinkLocal          InetZoneIndex,
        fsMIStdIpv6ScopeZoneIndex3                  InetZoneIndex,
        fsMIStdIpv6ScopeZoneIndexAdminLocal         InetZoneIndex,
        fsMIStdIpv6ScopeZoneIndexSiteLocal          InetZoneIndex,
        fsMIStdIpv6ScopeZoneIndex6                  InetZoneIndex,
        fsMIStdIpv6ScopeZoneIndex7                  InetZoneIndex,
        fsMIStdIpv6ScopeZoneIndexOrganizationLocal  InetZoneIndex,
        fsMIStdIpv6ScopeZoneIndex9                  InetZoneIndex,
        fsMIStdIpv6ScopeZoneIndexA                  InetZoneIndex,
        fsMIStdIpv6ScopeZoneIndexB                  InetZoneIndex,
        fsMIStdIpv6ScopeZoneIndexC                  InetZoneIndex,
        fsMIStdIpv6ScopeZoneIndexD                  InetZoneIndex,
        fsMIStdIpv6ScopeZoneContextId               Integer32
    }

fsMIStdIpv6ScopeZoneIndexIfIndex OBJECT-TYPE
    SYNTAX     InterfaceIndex
    MAX-ACCESS not-accessible
    STATUS     current
    DESCRIPTION
           "The index value that uniquely identifies the interface to
            which these scopes belong.  The interface identified by a
            particular value of this index is the same interface as
            identified by the same value of the IF-MIB's ifIndex."
    ::= { fsMIStdIpv6ScopeZoneIndexEntry 1 }

fsMIStdIpv6ScopeZoneIndexLinkLocal OBJECT-TYPE
    SYNTAX     InetZoneIndex
    MAX-ACCESS read-only
    STATUS     current
    DESCRIPTION
           "The zone index for the link-local scope on this interface."
    ::= { fsMIStdIpv6ScopeZoneIndexEntry 2 }

fsMIStdIpv6ScopeZoneIndex3 OBJECT-TYPE
    SYNTAX     InetZoneIndex
    MAX-ACCESS read-only
    STATUS     current
    DESCRIPTION
           "The zone index for scope 3 on this interface."
    ::= { fsMIStdIpv6ScopeZoneIndexEntry 3 }

fsMIStdIpv6ScopeZoneIndexAdminLocal OBJECT-TYPE
    SYNTAX     InetZoneIndex
    MAX-ACCESS read-only
    STATUS     current
    DESCRIPTION
           "The zone index for the admin-local scope on this interface."
    ::= { fsMIStdIpv6ScopeZoneIndexEntry 4 }

fsMIStdIpv6ScopeZoneIndexSiteLocal OBJECT-TYPE
    SYNTAX     InetZoneIndex
    MAX-ACCESS read-only
    STATUS     current
    DESCRIPTION
           "The zone index for the site-local scope on this interface."
    ::= { fsMIStdIpv6ScopeZoneIndexEntry 5 }

fsMIStdIpv6ScopeZoneIndex6 OBJECT-TYPE
    SYNTAX     InetZoneIndex
    MAX-ACCESS read-only
    STATUS     current
    DESCRIPTION
           "The zone index for scope 6 on this interface."
    ::= { fsMIStdIpv6ScopeZoneIndexEntry 6 }

fsMIStdIpv6ScopeZoneIndex7 OBJECT-TYPE
    SYNTAX     InetZoneIndex
    MAX-ACCESS read-only
    STATUS     current
    DESCRIPTION
           "The zone index for scope 7 on this interface."
    ::= { fsMIStdIpv6ScopeZoneIndexEntry 7 }

fsMIStdIpv6ScopeZoneIndexOrganizationLocal OBJECT-TYPE
    SYNTAX     InetZoneIndex
    MAX-ACCESS read-only
    STATUS     current
    DESCRIPTION
           "The zone index for the organization-local scope on this
            interface."
    ::= { fsMIStdIpv6ScopeZoneIndexEntry 8 }

fsMIStdIpv6ScopeZoneIndex9 OBJECT-TYPE
    SYNTAX     InetZoneIndex
    MAX-ACCESS read-only
    STATUS     current
    DESCRIPTION
           "The zone index for scope 9 on this interface."
    ::= { fsMIStdIpv6ScopeZoneIndexEntry 9 }

fsMIStdIpv6ScopeZoneIndexA OBJECT-TYPE
    SYNTAX     InetZoneIndex
    MAX-ACCESS read-only
    STATUS     current
    DESCRIPTION
           "The zone index for scope A on this interface."
    ::= { fsMIStdIpv6ScopeZoneIndexEntry 10 }

fsMIStdIpv6ScopeZoneIndexB OBJECT-TYPE
    SYNTAX     InetZoneIndex
    MAX-ACCESS read-only
    STATUS     current
    DESCRIPTION
           "The zone index for scope B on this interface."
    ::= { fsMIStdIpv6ScopeZoneIndexEntry 11 }

fsMIStdIpv6ScopeZoneIndexC OBJECT-TYPE
    SYNTAX     InetZoneIndex
    MAX-ACCESS read-only
    STATUS     current
    DESCRIPTION
           "The zone index for scope C on this interface."
    ::= { fsMIStdIpv6ScopeZoneIndexEntry 12 }

fsMIStdIpv6ScopeZoneIndexD OBJECT-TYPE
    SYNTAX     InetZoneIndex
    MAX-ACCESS read-only
    STATUS     current
    DESCRIPTION
           "The zone index for scope D on this interface."
    ::= { fsMIStdIpv6ScopeZoneIndexEntry 13 }

fsMIStdIpv6ScopeZoneContextId OBJECT-TYPE
    SYNTAX     Integer32
    MAX-ACCESS read-only
    STATUS     current
    DESCRIPTION
           "The context to which the ScopeZoneEntry belongs."
    ::= { fsMIStdIpv6ScopeZoneIndexEntry 14 }

--
-- The Default Router Table
-- This table simply lists the default routers; for more information
-- about routing tables, see the routing MIBs
--

fsMIStdIpDefaultRouterTable OBJECT-TYPE
    SYNTAX     SEQUENCE OF FsMIStdIpDefaultRouterEntry
    MAX-ACCESS not-accessible
    STATUS     current
    DESCRIPTION
           "The table used to describe the default routers known to this
            entity."
    ::= { fsMIStdIp 13 }

fsMIStdIpDefaultRouterEntry OBJECT-TYPE
    SYNTAX     FsMIStdIpDefaultRouterEntry
    MAX-ACCESS not-accessible
    STATUS     current
    DESCRIPTION
           "Each entry contains information about a default router known
            to this entity."
    INDEX {fsMIStdIpDefaultRouterAddressType, fsMIStdIpDefaultRouterAddress,
           fsMIStdIpDefaultRouterIfIndex}
    ::= { fsMIStdIpDefaultRouterTable 1 }

FsMIStdIpDefaultRouterEntry ::= SEQUENCE {
        fsMIStdIpDefaultRouterAddressType  InetAddressType,
        fsMIStdIpDefaultRouterAddress      InetAddress,
        fsMIStdIpDefaultRouterIfIndex      InterfaceIndex,
        fsMIStdIpDefaultRouterLifetime     Unsigned32,
        fsMIStdIpDefaultRouterPreference   INTEGER
    }

fsMIStdIpDefaultRouterAddressType OBJECT-TYPE
    SYNTAX     InetAddressType
    MAX-ACCESS not-accessible
    STATUS     current
    DESCRIPTION
           "The address type for this row."
    ::= { fsMIStdIpDefaultRouterEntry 1 }

fsMIStdIpDefaultRouterAddress OBJECT-TYPE
    SYNTAX     InetAddress (SIZE(16))
    MAX-ACCESS not-accessible
    STATUS     current
    DESCRIPTION
           "The IP address of the default router represented by this
            row.  The address type of this object is specified in
            fsMIStdIpDefaultRouterAddressType.

            Implementers need to be aware that if the size of
            fsMIStdIpDefaultRouterAddress exceeds 115 octets, then OIDS of
            instances of columns in this row will have more than 128
            sub-identifiers and cannot be accessed using SNMPv1,
            SNMPv2c, or SNMPv3."
    ::= { fsMIStdIpDefaultRouterEntry 2 }

fsMIStdIpDefaultRouterIfIndex OBJECT-TYPE
    SYNTAX     InterfaceIndex



    MAX-ACCESS not-accessible
    STATUS     current
    DESCRIPTION
           "The index value that uniquely identifies the interface by
            which the router can be reached.  The interface identified
            by a particular value of this index is the same interface as
            identified by the same value of the IF-MIB's ifIndex."
    ::= { fsMIStdIpDefaultRouterEntry 3 }

fsMIStdIpDefaultRouterLifetime OBJECT-TYPE
    SYNTAX     Unsigned32 (0..65535)
    UNITS      "seconds"
    MAX-ACCESS read-only
    STATUS     current
    DESCRIPTION
           "The remaining length of time, in seconds, that this router
            will continue to be useful as a default router.  A value of
            zero indicates that it is no longer useful as a default
            router.  It is left to the implementer of the MIB as to
            whether a router with a lifetime of zero is removed from the
            list.

            For IPv6, this value should be extracted from the router
            advertisement messages."
    ::= { fsMIStdIpDefaultRouterEntry 4 }

fsMIStdIpDefaultRouterPreference OBJECT-TYPE
    SYNTAX     INTEGER {
                     reserved (-2),
                     low (-1),
                     medium (0),
                     high (1)
                    }
    MAX-ACCESS read-only
    STATUS     current
    DESCRIPTION
           "An indication of preference given to this router as a
            default router as described in he Default Router
            Preferences document.  Treating the value as a
            2 bit signed integer allows for simple arithmetic
            comparisons.

            For IPv4 routers or IPv6 routers that are not using the
            updated router advertisement format, this object is set to
            medium (0)."
    ::= { fsMIStdIpDefaultRouterEntry 5 }


--
-- Configuration information for constructing router advertisements with context id
--

fsMIStdIpv6RouterAdvertTable OBJECT-TYPE
    SYNTAX     SEQUENCE OF FsMIStdIpv6RouterAdvertEntry
    MAX-ACCESS not-accessible
    STATUS     current
    DESCRIPTION
           "The table containing information used to construct router
            advertisements."
    ::= { fsMIStdIp 14 }

fsMIStdIpv6RouterAdvertEntry OBJECT-TYPE
    SYNTAX     FsMIStdIpv6RouterAdvertEntry
    MAX-ACCESS not-accessible
    STATUS     current
    DESCRIPTION
           "An entry containing information used to construct router
            advertisements.
            Information in this table is persistent, and when this
            object is written, the entity SHOULD save the change to
            non-volatile storage."
    INDEX { fsMIStdIpv6RouterAdvertIfIndex }
    ::= { fsMIStdIpv6RouterAdvertTable 1 }

FsMIStdIpv6RouterAdvertEntry ::= SEQUENCE {
        fsMIStdIpv6RouterAdvertIfIndex          InterfaceIndex,
        fsMIStdIpv6RouterAdvertSendAdverts      TruthValue,
        fsMIStdIpv6RouterAdvertMaxInterval      Unsigned32,
        fsMIStdIpv6RouterAdvertMinInterval      Unsigned32,
        fsMIStdIpv6RouterAdvertManagedFlag      TruthValue,
        fsMIStdIpv6RouterAdvertOtherConfigFlag  TruthValue,
        fsMIStdIpv6RouterAdvertLinkMTU          Unsigned32,
        fsMIStdIpv6RouterAdvertReachableTime    Unsigned32,
        fsMIStdIpv6RouterAdvertRetransmitTime   Unsigned32,
        fsMIStdIpv6RouterAdvertCurHopLimit      Unsigned32,
        fsMIStdIpv6RouterAdvertDefaultLifetime  Unsigned32,
        fsMIStdIpv6RouterAdvertRowStatus        RowStatus,
        fsMIStdIpv6RouterAdvertContextId        Integer32
    }

fsMIStdIpv6RouterAdvertIfIndex OBJECT-TYPE
    SYNTAX     InterfaceIndex
    MAX-ACCESS not-accessible
    STATUS     current
    DESCRIPTION
           "The index value that uniquely identifies the interface on
            which router advertisements constructed with this
            information will be transmitted.  The interface identified
            by a particular value of this index is the same interface as
            identified by the same value of the IF-MIB's ifIndex."
    ::= { fsMIStdIpv6RouterAdvertEntry 1 }

fsMIStdIpv6RouterAdvertSendAdverts OBJECT-TYPE
    SYNTAX     TruthValue
    MAX-ACCESS read-create
    STATUS     current
    DESCRIPTION
           "A flag indicating whether the router sends periodic
            router advertisements and responds to router solicitations
            on this interface."
    DEFVAL { false }
    ::= { fsMIStdIpv6RouterAdvertEntry 2 }

fsMIStdIpv6RouterAdvertMaxInterval OBJECT-TYPE
    SYNTAX     Unsigned32 (4..1800)
    UNITS      "seconds"
    MAX-ACCESS read-create
    STATUS     current
    DESCRIPTION
           "The maximum time allowed between sending unsolicited router
            advertisements from this interface."
    DEFVAL { 600 }
    ::= { fsMIStdIpv6RouterAdvertEntry 3 }

fsMIStdIpv6RouterAdvertMinInterval OBJECT-TYPE
    SYNTAX     Unsigned32 (3..1350)
    UNITS      "seconds"
    MAX-ACCESS read-create
    STATUS     current
    DESCRIPTION
           "The minimum time allowed between sending unsolicited router
            advertisements from this interface.

            The default is 0.33 * fsMIStdIpv6RouterAdvertMaxInterval, however,
            in the case of a low value for fsMIStdIpv6RouterAdvertMaxInterval,
            the minimum value for this object is restricted to 3."
    ::= { fsMIStdIpv6RouterAdvertEntry 4 }

fsMIStdIpv6RouterAdvertManagedFlag OBJECT-TYPE
    SYNTAX     TruthValue
    MAX-ACCESS read-create
    STATUS     current
    DESCRIPTION
           "The true/false value to be placed into the 'managed address
            configuration' flag field in router advertisements sent from
            this interface."
    DEFVAL { false }
    ::= { fsMIStdIpv6RouterAdvertEntry 5 }

fsMIStdIpv6RouterAdvertOtherConfigFlag OBJECT-TYPE
    SYNTAX     TruthValue
    MAX-ACCESS read-create
    STATUS     current
    DESCRIPTION
           "The true/false value to be placed into the 'other stateful
            configuration' flag field in router advertisements sent from
            this interface."
    DEFVAL { false }
    ::= { fsMIStdIpv6RouterAdvertEntry 6 }

fsMIStdIpv6RouterAdvertLinkMTU OBJECT-TYPE
    SYNTAX     Unsigned32
    MAX-ACCESS read-create
    STATUS     current
    DESCRIPTION
           "The value to be placed in MTU options sent by the router on
            this interface.

            A value of zero indicates that no MTU options are sent."
    DEFVAL { 0 }
    ::= { fsMIStdIpv6RouterAdvertEntry 7 }

fsMIStdIpv6RouterAdvertReachableTime OBJECT-TYPE
    SYNTAX     Unsigned32 (0..3600000)
    UNITS      "milliseconds"
    MAX-ACCESS read-create
    STATUS     current
    DESCRIPTION
           "The value to be placed in the reachable time field in router
            advertisement messages sent from this interface.

            A value of zero in the router advertisement indicates that
            the advertisement isn't specifying a value for reachable
            time."
    DEFVAL { 0 }
    ::= { fsMIStdIpv6RouterAdvertEntry 8 }

fsMIStdIpv6RouterAdvertRetransmitTime OBJECT-TYPE
    SYNTAX     Unsigned32
    UNITS      "milliseconds"
    MAX-ACCESS read-create
    STATUS     current
    DESCRIPTION
           "The value to be placed in the retransmit timer field in
            router advertisements sent from this interface.

            A value of zero in the router advertisement indicates that
            the advertisement isn't specifying a value for retrans
            time."
    DEFVAL { 0 }
    ::= { fsMIStdIpv6RouterAdvertEntry 9 }

fsMIStdIpv6RouterAdvertCurHopLimit OBJECT-TYPE
    SYNTAX     Unsigned32 (0..255)
    MAX-ACCESS read-create
    STATUS     current
    DESCRIPTION
           "The default value to be placed in the current hop limit
            field in router advertisements sent from this interface.

            The value should be set to the current diameter of the
            Internet.

            A value of zero in the router advertisement indicates that
            the advertisement isn't specifying a value for curHopLimit.

            The default should be set to the value specified in the IANA
            web pages (www.iana.org) at the time of implementation."
    ::= { fsMIStdIpv6RouterAdvertEntry 10 }

fsMIStdIpv6RouterAdvertDefaultLifetime OBJECT-TYPE
    SYNTAX     Unsigned32 (0|4..9000)
    UNITS      "seconds"
    MAX-ACCESS read-create
    STATUS     current
    DESCRIPTION
           "The value to be placed in the router lifetime field of
            router advertisements sent from this interface.  This value
            MUST be either 0 or between fsMIStdIpv6RouterAdvertMaxInterval and
            9000 seconds.

            A value of zero indicates that the router is not to be used
            as a default router.

            The default is 3 * fsMIStdIpv6RouterAdvertMaxInterval."
    ::= { fsMIStdIpv6RouterAdvertEntry 11 }

fsMIStdIpv6RouterAdvertRowStatus OBJECT-TYPE
    SYNTAX     RowStatus
    MAX-ACCESS read-create
    STATUS     current
    DESCRIPTION
           "The status of this conceptual row.

            As all objects in this conceptual row have default values, a
            row can be created and made active by setting this object
            appropriately.

            The RowStatus TC requires that this DESCRIPTION clause
            states under which circumstances other objects in this row
            can be modified.  The value of this object has no effect on
            whether other objects in this conceptual row can be
            modified."
    ::= { fsMIStdIpv6RouterAdvertEntry 12 }

fsMIStdIpv6RouterAdvertContextId OBJECT-TYPE
    SYNTAX     Integer32
    MAX-ACCESS read-only
    STATUS     current
    DESCRIPTION
        "The context to which the RouterAdvert entry belongs."
    ::= { fsMIStdIpv6RouterAdvertEntry 13 }


--ICMP Statistics table

fsMIStdIcmpStatsTable OBJECT-TYPE
    SYNTAX     SEQUENCE OF FsMIStdIcmpStatsEntry
    MAX-ACCESS not-accessible
    STATUS     current
    DESCRIPTION
           "The table of generic per virtual rotuer ICMP counters."
    ::= { fsMIStdIp 15 }

fsMIStdIcmpStatsEntry OBJECT-TYPE
    SYNTAX     FsMIStdIcmpStatsEntry
    MAX-ACCESS not-accessible
    STATUS     current
    DESCRIPTION
           "A conceptual row in the fsMIStdIcmpStatsTable."
    INDEX    { fsMIStdIpContextId, fsMIStdIcmpStatsIPVersion }
    ::= { fsMIStdIcmpStatsTable 1 }

FsMIStdIcmpStatsEntry ::= SEQUENCE {
        fsMIStdIcmpStatsIPVersion  FsInetVersion,
        fsMIStdIcmpStatsInMsgs     Counter32,
        fsMIStdIcmpStatsInErrors   Counter32,
        fsMIStdIcmpStatsOutMsgs    Counter32,
        fsMIStdIcmpStatsOutErrors  Counter32
    }

fsMIStdIcmpStatsIPVersion OBJECT-TYPE
    SYNTAX     FsInetVersion
    MAX-ACCESS not-accessible
    STATUS     current
    DESCRIPTION
           "The IP version of the statistics."
    ::= { fsMIStdIcmpStatsEntry 1 }

fsMIStdIcmpStatsInMsgs OBJECT-TYPE
    SYNTAX     Counter32
    MAX-ACCESS read-only
    STATUS     current
    DESCRIPTION
           "The total number of ICMP messages that the entity received.
            Note that this counter includes all those counted by
            fsMIStdIcmpStatsInErrors."
    ::= { fsMIStdIcmpStatsEntry 2 }

fsMIStdIcmpStatsInErrors OBJECT-TYPE
    SYNTAX     Counter32
    MAX-ACCESS read-only
    STATUS     current
    DESCRIPTION
           "The number of ICMP messages that the entity received but
            determined as having ICMP-specific errors (bad ICMP
            checksums, bad length, etc.)."
    ::= { fsMIStdIcmpStatsEntry 3 }

fsMIStdIcmpStatsOutMsgs OBJECT-TYPE
    SYNTAX     Counter32
    MAX-ACCESS read-only
    STATUS     current
    DESCRIPTION
           "The total number of ICMP messages that the entity attempted
            to send.  Note that this counter includes all those counted
            by fsMIStdIcmpStatsOutErrors."
    ::= { fsMIStdIcmpStatsEntry 4 }

fsMIStdIcmpStatsOutErrors OBJECT-TYPE
    SYNTAX     Counter32
    MAX-ACCESS read-only
    STATUS     current
    DESCRIPTION
           "The number of ICMP messages that this entity did not send
            due to problems discovered within ICMP, such as a lack of
            buffers.  This value should not include errors discovered
            outside the ICMP layer, such as the inability of IP to route
            the resultant datagram.  In some implementations, there may
            be no types of error that contribute to this counter's
            value."
    ::= { fsMIStdIcmpStatsEntry 5 }

-- per-version, per-message type ICMP counters

fsMIStdIcmpMsgStatsTable OBJECT-TYPE
    SYNTAX     SEQUENCE OF FsMIStdIcmpMsgStatsEntry
    MAX-ACCESS not-accessible
    STATUS     current
    DESCRIPTION
           "The table of per virtual rotuer per-version, per-message type ICMP
            counters."
    ::= { fsMIStdIp 16 }

fsMIStdIcmpMsgStatsEntry OBJECT-TYPE
    SYNTAX     FsMIStdIcmpMsgStatsEntry
    MAX-ACCESS not-accessible
    STATUS     current
    DESCRIPTION
           "A conceptual row in the fsMIStdIcmpMsgStatsTable.
            The system should track each ICMP type value, even if that
            ICMP type is not supported by the system.  However, a
            given row need not be instantiated unless a message of that
            type has been processed, i.e., the row for
            fsMIStdIcmpMsgStatsType=X MAY be instantiated before but MUST be
            instantiated after the first message with Type=X is
            received or transmitted.  After receiving or transmitting
            any succeeding messages with Type=X, the relevant counter
            must be incremented."
    INDEX { fsMIStdIpContextId, fsMIStdIcmpMsgStatsIPVersion, fsMIStdIcmpMsgStatsType }
    ::= { fsMIStdIcmpMsgStatsTable 1 }

FsMIStdIcmpMsgStatsEntry ::= SEQUENCE {
        fsMIStdIcmpMsgStatsIPVersion  FsInetVersion,
        fsMIStdIcmpMsgStatsType       Integer32,
        fsMIStdIcmpMsgStatsInPkts     Counter32,
        fsMIStdIcmpMsgStatsOutPkts    Counter32
    }

fsMIStdIcmpMsgStatsIPVersion OBJECT-TYPE
    SYNTAX     FsInetVersion
    MAX-ACCESS not-accessible
    STATUS     current
    DESCRIPTION
           "The IP version of the statistics."
    ::= { fsMIStdIcmpMsgStatsEntry 1 }

fsMIStdIcmpMsgStatsType OBJECT-TYPE
    SYNTAX     Integer32 (0..255)
    MAX-ACCESS not-accessible
    STATUS     current
    DESCRIPTION
           "The ICMP type field of the message type being counted by
            this row.

            Note that ICMP message types are scoped by the address type
            in use."
    ::= { fsMIStdIcmpMsgStatsEntry 2 }

fsMIStdIcmpMsgStatsInPkts OBJECT-TYPE
    SYNTAX     Counter32
    MAX-ACCESS read-only
    STATUS     current
    DESCRIPTION
           "The number of input packets for this AF and type."
    ::= { fsMIStdIcmpMsgStatsEntry 3 }

fsMIStdIcmpMsgStatsOutPkts OBJECT-TYPE
    SYNTAX     Counter32
    MAX-ACCESS read-only
    STATUS     current
    DESCRIPTION
           "The number of output packets for this AF and type."
    ::= { fsMIStdIcmpMsgStatsEntry 4 }


--  Inet CIDR Route Table

fsMIStdInetCidrRouteTable OBJECT-TYPE
    SYNTAX     SEQUENCE OF FsMIStdInetCidrRouteEntry
    MAX-ACCESS not-accessible
    STATUS     current
    DESCRIPTION
           "The entity's IP Routing table."
    ::= { fsMIStdIp 17 }

fsMIStdInetCidrRouteEntry OBJECT-TYPE
    SYNTAX     FsMIStdInetCidrRouteEntry
    MAX-ACCESS not-accessible
    STATUS     current
    DESCRIPTION
           "A particular route to a particular destination, under a
            particular policy (as reflected in the
            fsMIStdInetCidrRoutePolicy object).

            Dynamically created rows will survive an agent reboot.

            Implementers need to be aware that if the total number
            of elements (octets or sub-identifiers) in
            fsMIStdInetCidrRouteDest, fsMiInetCidrRoutePolicy, and
            fsMIStdInetCidrRouteNextHop exceeds 111, then OIDs of column
            instances in this table will have more than 128 sub-
            identifiers and cannot be accessed using SNMPv1,
            SNMPv2c, or SNMPv3."
    INDEX {
        fsMIStdIpContextId,
        fsMIStdInetCidrRouteDestType,
        fsMIStdInetCidrRouteDest,
        fsMIStdInetCidrRoutePfxLen,
        fsMIStdInetCidrRoutePolicy,
        fsMIStdInetCidrRouteNextHopType,
        fsMIStdInetCidrRouteNextHop
        }
    ::= { fsMIStdInetCidrRouteTable 1 }

FsMIStdInetCidrRouteEntry ::= SEQUENCE {
        fsMIStdInetCidrRouteDestType     InetAddressType,
        fsMIStdInetCidrRouteDest         InetAddress,
        fsMIStdInetCidrRoutePfxLen       InetAddressPrefixLength,
        fsMIStdInetCidrRoutePolicy       OBJECT IDENTIFIER,
        fsMIStdInetCidrRouteNextHopType  InetAddressType,
        fsMIStdInetCidrRouteNextHop      InetAddress,
        fsMIStdInetCidrRouteIfIndex      InterfaceIndexOrZero,
        fsMIStdInetCidrRouteType         INTEGER,
        fsMIStdInetCidrRouteProto        IANAipRouteProtocol,
        fsMIStdInetCidrRouteAge          Gauge32,
        fsMIStdInetCidrRouteNextHopAS    InetAutonomousSystemNumber,
        fsMIStdInetCidrRouteMetric1      Integer32,
        fsMIStdInetCidrRouteMetric2      Integer32,
        fsMIStdInetCidrRouteMetric3      Integer32,
        fsMIStdInetCidrRouteMetric4      Integer32,
        fsMIStdInetCidrRouteMetric5      Integer32,
        fsMIStdInetCidrRouteStatus       RowStatus,
        fsMIStdInetCidrRouteAddrType     INTEGER,
        fsMIStdInetCidrRouteHWStatus     BITS
    }

fsMIStdInetCidrRouteDestType OBJECT-TYPE
    SYNTAX     InetAddressType
    MAX-ACCESS not-accessible
    STATUS     current
    DESCRIPTION
           "The type of the fsMIStdInetCidrRouteDest address, as defined
            in the InetAddress MIB.

            Only those address types that may appear in an actual
            routing table are allowed as values of this object."
    ::= { fsMIStdInetCidrRouteEntry 1 }

fsMIStdInetCidrRouteDest OBJECT-TYPE
    SYNTAX     InetAddress (SIZE(16))
    MAX-ACCESS not-accessible
    STATUS     current
    DESCRIPTION
           "The destination IP address of this route.

            The type of this address is determined by the value of
            the fsMIStdInetCidrRouteDestType object.

            The values for the index objects fsMIStdInetCidrRouteDest and
            fsMIStdInetCidrRoutePfxLen must be consistent.  When the value
            of fsMIStdInetCidrRouteDest (excluding the zone index, if one
            is present) is x, then the bitwise logical-AND
            of x with the value of the mask formed from the
            corresponding index object fsMIStdInetCidrRoutePfxLen MUST be
            equal to x.  If not, then the index pair is not
            consistent and an inconsistentName error must be
            returned on SET or CREATE requests."

    ::= { fsMIStdInetCidrRouteEntry 2 }

fsMIStdInetCidrRoutePfxLen OBJECT-TYPE
    SYNTAX     InetAddressPrefixLength
    MAX-ACCESS not-accessible
    STATUS     current
    DESCRIPTION
           "Indicates the number of leading one bits that form the
            mask to be logical-ANDed with the destination address
            before being compared to the value in the
            fsMIStdInetCidrRouteDest field.

            The values for the index objects fsMIStdInetCidrRouteDest and
            fsMIStdInetCidrRoutePfxLen must be consistent.  When the value
            of fsMIStdInetCidrRouteDest (excluding the zone index, if one
            is present) is x, then the bitwise logical-AND
            of x with the value of the mask formed from the
            corresponding index object fsMIStdInetCidrRoutePfxLen MUST be
            equal to x.  If not, then the index pair is not
            consistent and an inconsistentName error must be
            returned on SET or CREATE requests."

    ::= { fsMIStdInetCidrRouteEntry 3 }

fsMIStdInetCidrRoutePolicy OBJECT-TYPE
    SYNTAX     OBJECT IDENTIFIER
    MAX-ACCESS not-accessible
    STATUS     current
    DESCRIPTION
           "This object is an opaque object without any defined
            semantics.  Its purpose is to serve as an additional
            index that may delineate between multiple entries to
            the same destination.  The value { 0 0 } shall be used
            as the default value for this object."
    ::= { fsMIStdInetCidrRouteEntry 4 }

fsMIStdInetCidrRouteNextHopType OBJECT-TYPE
    SYNTAX     InetAddressType
    MAX-ACCESS not-accessible
    STATUS     current
    DESCRIPTION
           "The type of the fsMIStdInetCidrRouteNextHop address, as
            defined in the InetAddress MIB.
            Value should be set to unknown(0) for non-remote
            routes.

            Only those address types that may appear in an actual
            routing table are allowed as values of this object."
    ::= { fsMIStdInetCidrRouteEntry 5 }

fsMIStdInetCidrRouteNextHop OBJECT-TYPE
    SYNTAX     InetAddress (SIZE(16))
    MAX-ACCESS not-accessible
    STATUS     current
    DESCRIPTION
           "On remote routes, the address of the next system en
            route.  For non-remote routes, a zero length string.

            The type of this address is determined by the value of
            the fsMIStdInetCidrRouteNextHopType object."
    ::= { fsMIStdInetCidrRouteEntry 6 }

fsMIStdInetCidrRouteIfIndex OBJECT-TYPE
    SYNTAX     InterfaceIndexOrZero
    MAX-ACCESS read-create
    STATUS     current
    DESCRIPTION
           "The ifIndex value that identifies the local interface
            through which the next hop of this route should be
            reached.  A value of 0 is valid and represents the
            scenario where no interface is specified."
    ::= { fsMIStdInetCidrRouteEntry 7 }

fsMIStdInetCidrRouteType OBJECT-TYPE
    SYNTAX     INTEGER {
                other    (1), -- not specified by this MIB
                reject   (2), -- route that discards traffic and
                              --   returns ICMP notification
                local    (3), -- local interface
                remote   (4), -- remote destination
                blackhole(5)  -- route that discards traffic
                              --   silently
             }
    MAX-ACCESS read-create
    STATUS     current
    DESCRIPTION
           "The type of route.  Note that local(3) refers to a
            route for which the next hop is the final destination;
            remote(4) refers to a route for which the next hop is
            not the final destination.

            Routes that do not result in traffic forwarding or
            rejection should not be displayed, even if the
            implementation keeps them stored internally.

            reject(2) refers to a route that, if matched, discards
            the message as unreachable and returns a notification
            (e.g., ICMP error) to the message sender.  This is used
            in some protocols as a means of correctly aggregating
            routes.

            blackhole(5) refers to a route that, if matched,
            discards the message silently."
    ::= { fsMIStdInetCidrRouteEntry 8 }


fsMIStdInetCidrRouteProto OBJECT-TYPE
    SYNTAX     IANAipRouteProtocol
    MAX-ACCESS read-only
    STATUS     current
    DESCRIPTION
           "The routing mechanism via which this route was learned.
            Inclusion of values for gateway routing protocols is
            not intended to imply that hosts should support those
            protocols."
    ::= { fsMIStdInetCidrRouteEntry 9 }

fsMIStdInetCidrRouteAge OBJECT-TYPE
    SYNTAX     Gauge32
    MAX-ACCESS read-only
    STATUS     current
    DESCRIPTION
           "The number of seconds since this route was last updated
            or otherwise determined to be correct.  Note that no
            semantics of 'too old' can be implied, except through
            knowledge of the routing protocol by which the route
            was learned."
    ::= { fsMIStdInetCidrRouteEntry 10 }

fsMIStdInetCidrRouteNextHopAS OBJECT-TYPE
    SYNTAX     InetAutonomousSystemNumber
    MAX-ACCESS read-create
    STATUS     current
    DESCRIPTION
           "The Autonomous System Number of the Next Hop.  The
            semantics of this object are determined by the routing-
            protocol specified in the route's fsMIStdInetCidrRouteProto
            value.  When this object is unknown or not relevant, its
            value should be set to zero."
    DEFVAL { 0 }
    ::= { fsMIStdInetCidrRouteEntry 11 }

fsMIStdInetCidrRouteMetric1 OBJECT-TYPE
    SYNTAX     Integer32
    MAX-ACCESS read-create
    STATUS     current
    DESCRIPTION
           "The primary routing metric for this route.  The
            semantics of this metric are determined by the routing-
            protocol specified in the route's fsMIStdInetCidrRouteProto
            value.  If this metric is not used, its value should be
            set to -1."
    DEFVAL { -1 }
    ::= { fsMIStdInetCidrRouteEntry 12 }

fsMIStdInetCidrRouteMetric2 OBJECT-TYPE
    SYNTAX     Integer32
    MAX-ACCESS read-create
    STATUS     current
    DESCRIPTION
           "An alternate routing metric for this route.  The
            semantics of this metric are determined by the routing-
            protocol specified in the route's fsMIStdInetCidrRouteProto
            value.  If this metric is not used, its value should be
            set to -1."
    DEFVAL { -1 }
    ::= { fsMIStdInetCidrRouteEntry 13 }

fsMIStdInetCidrRouteMetric3 OBJECT-TYPE
    SYNTAX     Integer32
    MAX-ACCESS read-create
    STATUS     current
    DESCRIPTION
           "An alternate routing metric for this route.  The
            semantics of this metric are determined by the routing-
            protocol specified in the route's fsMIStdInetCidrRouteProto
            value.  If this metric is not used, its value should be
            set to -1."
    DEFVAL { -1 }
    ::= { fsMIStdInetCidrRouteEntry 14 }

fsMIStdInetCidrRouteMetric4 OBJECT-TYPE
    SYNTAX     Integer32
    MAX-ACCESS read-create
    STATUS     current
    DESCRIPTION
           "An alternate routing metric for this route.  The
            semantics of this metric are determined by the routing-
            protocol specified in the route's fsMIStdInetCidrRouteProto
            value.  If this metric is not used, its value should be
            set to -1."
    DEFVAL { -1 }
    ::= { fsMIStdInetCidrRouteEntry 15 }

fsMIStdInetCidrRouteMetric5 OBJECT-TYPE
    SYNTAX     Integer32
    MAX-ACCESS read-create
    STATUS     current
    DESCRIPTION
           "An alternate routing metric for this route.  The
            semantics of this metric are determined by the routing-
            protocol specified in the route's fsMIStdInetCidrRouteProto
            value.  If this metric is not used, its value should be
            set to -1."
    DEFVAL { -1 }
    ::= { fsMIStdInetCidrRouteEntry 16 }

fsMIStdInetCidrRouteStatus OBJECT-TYPE
    SYNTAX     RowStatus
    MAX-ACCESS read-create
    STATUS     current
    DESCRIPTION
           "The row status variable, used according to row
            installation and removal conventions.

            A row entry cannot be modified when the status is
            marked as active(1)."
    ::= { fsMIStdInetCidrRouteEntry 17 }
fsMIStdInetCidrRouteAddrType OBJECT-TYPE
    SYNTAX       INTEGER {
                     unicast(1),
                     anycast(2)
                 }
    MAX-ACCESS read-write
    STATUS     current
    DESCRIPTION
           "Indicates whether the destination address in the
            route entry is unicast or  anycast."
    DEFVAL { 1 }
    ::= { fsMIStdInetCidrRouteEntry 18 }
fsMIStdInetCidrRouteHWStatus OBJECT-TYPE
    SYNTAX       BITS { bestRoute (40),
                        hardwareStatus (80),
                        reachable (100)
                 }
    MAX-ACCESS read-only
    STATUS     current
    DESCRIPTION
           "This bit mask indicates the route status
            01000000 - This bit indicates the route is best route.
            10000000 - This bit indicates the route is added in hardware.
            01100100 - This bit indicates the route is Reachable."
    ::= {fsMIStdInetCidrRouteEntry 19}
END
