--******************************************************************************
--Copyright (C) 2008-2014 Super Micro Computer Inc. All Rights Reserved
--
--$Id: fsrrm.mib,v 1.1 2013/09/19 13:02:53 siva Exp $
--
--Description : This file contains MIB definitions for ISS module.
--
--******************************************************************************/

-- SupermicroISS MIB Definition

-- MIB for 'Wireless Switch Solution'

-- The 'Wireless Switch Solution' MIB definition is as follows:


SUPERMICRO-WSS-RRM-MIB DEFINITIONS ::= BEGIN

IMPORTS
MODULE-IDENTITY, OBJECT-TYPE,
enterprises    FROM SNMPv2-SMI
 RowStatus FROM SNMPv2-TC;

fsRrm MODULE-IDENTITY
LAST-UPDATED "201302150000Z"
ORGANIZATION "Super Micro Computer Inc."
CONTACT-INFO

"Super Micro Computer Inc.
E-mail:support@Supermicro.com"

DESCRIPTION
"The enterprise ID 10876 is originally assigned to Super Micro Computer Inc."
REVISION "201302150000Z"

DESCRIPTION
"The MIB for SupermicroWSS."
::= { enterprises supermicro-computer-inc(10876) super-switch(101) extended(2) 84 }

-- ----------------------------------------------------------------- --
-- groups in the MIB
-- ----------------------------------------------------------------- --

fsRrmManagment OBJECT IDENTIFIER ::= { fsRrm 1 }

-- RRM Config
fsRrmConfigTable OBJECT-TYPE
SYNTAX SEQUENCE OF FsRrmConfigEntry
MAX-ACCESS not-accessible
STATUS current
DESCRIPTION
"A table to manage the Radio Resource Management (RRM) configuration."
::= { fsRrmManagment 1 }

fsRrmConfigEntry OBJECT-TYPE
SYNTAX FsRrmConfigEntry
MAX-ACCESS not-accessible
STATUS current
DESCRIPTION
"An entry appears in this table for each 802.11 network.
Index to this table is the 802.11 radio type."
INDEX { fsRrmRadioType }
::= { fsRrmConfigTable 1 }

FsRrmConfigEntry ::=
SEQUENCE {
fsRrmRadioType INTEGER,
fsRrmDcaMode INTEGER,
fsRrmDcaChannelSelectionMode INTEGER,
fsRrmTpcMode INTEGER,
fsRrmTpcSelectionMode INTEGER,
fsRrmRowStatus RowStatus
}

fsRrmRadioType OBJECT-TYPE
SYNTAX INTEGER {
dot11a (1),
dot11b (2)
}
MAX-ACCESS not-accessible
STATUS current
DESCRIPTION
"Represents the 802.11 network radio type."
::= { fsRrmConfigEntry 1 }

fsRrmDcaMode OBJECT-TYPE
SYNTAX INTEGER {
global (1),
perAP(2),
disable (3)
}
MAX-ACCESS read-write
STATUS current
DESCRIPTION
"To enable or disable the Dynamic channel assignment feature. When
enabled AC will assign the channel dynamically for all the AP or
for a specific AP"
DEFVAL { disable }
::= { fsRrmConfigEntry 2 }

fsRrmDcaChannelSelectionMode OBJECT-TYPE
SYNTAX INTEGER {
auto (1),
once (2),
off (3)
}
MAX-ACCESS read-write
STATUS current
DESCRIPTION
"Indicates the channel selection mode is either automatically assigned for
a periodic interval or triggered by the AC or set manually. When
fsRrmDcaMode is set to disable this object will only allow off."
DEFVAL { off }
::= { fsRrmConfigEntry 3 }

fsRrmTpcMode OBJECT-TYPE
SYNTAX INTEGER {
global (1),
perAP(2),
disable (3)
}
MAX-ACCESS read-write
STATUS current
DESCRIPTION
"To enable or disable the DTPC feature. When enabled AC will
assign the Tx Power dynamically for all the AP or for a specific AP."
DEFVAL { disable }
::= { fsRrmConfigEntry 4 }

fsRrmTpcSelectionMode OBJECT-TYPE
SYNTAX INTEGER {
auto (1),
once (2),
off (3)
}
MAX-ACCESS read-write
STATUS current
DESCRIPTION
"Indicates the Tx power selection mode is either automatically assigned for
a periodic interval or triggered by the AC or set manually. When
fsRrmTpcMode is set to disable this object will only allow off."
DEFVAL { off }
::= { fsRrmConfigEntry 5 }

fsRrmRowStatus OBJECT-TYPE
SYNTAX RowStatus
MAX-ACCESS read-create
STATUS current
DESCRIPTION
"The status column used for creating, modifying, and
deleting instances of the columnar objects in the RRM table"
::= { fsRrmConfigEntry 6 }

END
