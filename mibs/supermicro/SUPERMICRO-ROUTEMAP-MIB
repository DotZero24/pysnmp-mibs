-- Copyright (C) 2008-2014 Super Micro Computer Inc. All Rights Reserved

-- $Id: fsrmap.mib,v 1.9 2013/06/26 12:08:54 siva Exp $

-- ROUTE-MAP MIB DETAILS

     SUPERMICRO-ROUTEMAP-MIB DEFINITIONS ::= BEGIN

    IMPORTS
          MODULE-IDENTITY,OBJECT-TYPE,NOTIFICATION-TYPE,
          enterprises,Unsigned32,IpAddress,Integer32          FROM SNMPv2-SMI
          DisplayString,RowStatus                             FROM SNMPv2-TC
          InterfaceIndex                                      FROM IF-MIB
          InetAddressType,InetAddress,InetAddressPrefixLength FROM INET-ADDRESS-MIB;

          futureroutemap MODULE-IDENTITY
          LAST-UPDATED "201209050000Z"
          ORGANIZATION "Super Micro Computer Inc. LTD"
          CONTACT-INFO "support@Supermicro.com"
          DESCRIPTION
                  " The proprietary MIB module for RouteMap module. "
          REVISION "201209050000Z"
          DESCRIPTION
                  " The proprietary MIB module for RouteMap module. "

          ::=   {enterprises  supermicro-computer-inc(10876) super-switch(101) basic(1) 155 }

------------------------------------------------------------------------------
--           Groups in MIB
------------------------------------------------------------------------------

 fsRouteMap                   OBJECT IDENTIFIER ::= { futureroutemap 1 }

 --Routemap table

          fsRouteMapTable   OBJECT-TYPE
          SYNTAX    SEQUENCE  OF FsRouteMapEntry
          MAX-ACCESS      not-accessible
          STATUS          deprecated
          DESCRIPTION     "Route map  table contains  route map name, sequence
                           number and access status (Permit/Deny).Route-maps
                           can be used in policy  based routing and route
                           redistribution"
                      ::= { fsRouteMap 1 }

          fsRouteMapEntry  OBJECT-TYPE
          SYNTAX        FsRouteMapEntry
          MAX-ACCESS    not-accessible
          STATUS        deprecated
          DESCRIPTION   "Row instance of the routemap  table"
          INDEX  { fsRouteMapName,
                   fsRouteMapSeqNum
                 }
          ::= { fsRouteMapTable 1 }


          FsRouteMapEntry ::= SEQUENCE {
          fsRouteMapName          DisplayString,
          fsRouteMapSeqNum        Unsigned32,
          fsRouteMapAccess        INTEGER,
          fsRouteMapRowStatus     RowStatus
          }

          fsRouteMapName     OBJECT-TYPE
          SYNTAX             DisplayString (SIZE(1..20))
          MAX-ACCESS         not-accessible
          STATUS             deprecated
          DESCRIPTION        "Name  Identifies the  specified route-map
                               in the list of route-maps."
                      ::= {  fsRouteMapEntry  1 }


          fsRouteMapSeqNum   OBJECT-TYPE
          SYNTAX             Unsigned32 (1..10)
          MAX-ACCESS         not-accessible
          STATUS             deprecated
          DESCRIPTION       "Number that indicates the position of a new route
                             map in the list of route maps already configured
                             with the same name"
                      ::= {  fsRouteMapEntry  2 }

          fsRouteMapAccess   OBJECT-TYPE
          SYNTAX              INTEGER    {
                                   permit (1),
                                   deny (2)
          }
          MAX-ACCESS         read-write
          STATUS             deprecated
          DESCRIPTION       "Access type associated with sequence number in a
                             route-map. Once an instance of this object is
                             created,  its value can not be changed"
          DEFVAL   {permit}
                      ::= {  fsRouteMapEntry  3 }


          fsRouteMapRowStatus OBJECT-TYPE
          SYNTAX          RowStatus
          MAX-ACCESS      read-write
          STATUS          deprecated
          DESCRIPTION     "The status of this row, by which new entries may be
                            created, or old entries deleted from this table."
                      ::= {  fsRouteMapEntry  4}


 -- match table

          fsRouteMapMatchTable  OBJECT-TYPE
          SYNTAX       SEQUENCE  OF FsRouteMapMatchEntry
          MAX-ACCESS                not-accessible
          STATUS                    deprecated
          DESCRIPTION       "Route-map Match table contains various objects
                             used for matching the parameters of the route "
                      ::= {   fsRouteMap   2 }

  fsRouteMapMatchEntry   OBJECT-TYPE
          SYNTAX         FsRouteMapMatchEntry
          MAX-ACCESS     not-accessible
          STATUS         deprecated
          DESCRIPTION    "Row instance of the routemap match  table"
          INDEX   {
                   fsRouteMapName,
                   fsRouteMapSeqNum,
                   fsRouteMapMatchInterface,
                   fsRouteMapMatchIpAddress,
                   fsRouteMapMatchIpAddrMask,
                   fsRouteMapMatchIpNextHop,
                   fsRouteMapMatchMetric,
                   fsRouteMapMatchTag,
                   fsRouteMapMatchRouteType,
         	       fsRouteMapMatchMetricType,
                   fsRouteMapMatchASPathTag,
		           fsRouteMapMatchCommunity,
                   fsRouteMapMatchOrigin,
                   fsRouteMapMatchLocalPreference
                  }
                      ::= { fsRouteMapMatchTable 1 }

    FsRouteMapMatchEntry ::= SEQUENCE {
         fsRouteMapMatchInterface         InterfaceIndex,
         fsRouteMapMatchIpAddress         IpAddress,
         fsRouteMapMatchIpAddrMask        IpAddress,
         fsRouteMapMatchIpNextHop         IpAddress,
         fsRouteMapMatchMetric            Integer32,
         fsRouteMapMatchTag               Unsigned32,
         fsRouteMapMatchRouteType         INTEGER,
         fsRouteMapMatchMetricType        INTEGER,
         fsRouteMapMatchASPathTag        Unsigned32,
         fsRouteMapMatchCommunity         Unsigned32,
         fsRouteMapMatchOrigin            INTEGER,
         fsRouteMapMatchLocalPreference   Integer32,
         fsRouteMapMatchRowStatus         RowStatus
         }


          fsRouteMapMatchInterface   OBJECT-TYPE
          SYNTAX             InterfaceIndex
          MAX-ACCESS         not-accessible
          STATUS             deprecated
          DESCRIPTION      " The ifIndex value which identifies  the  local
                             interface  through  which  the next hop  can be reached."
                      ::= {  fsRouteMapMatchEntry  1 }

          fsRouteMapMatchIpAddress     OBJECT-TYPE
          SYNTAX               IpAddress
          MAX-ACCESS           not-accessible
          STATUS               deprecated
          DESCRIPTION      " The destination network number address.when logically
                             ANDED with the mask results in the range of addressess
                             that will get pass the route-map."
                      ::= {  fsRouteMapMatchEntry 2 }

          fsRouteMapMatchIpAddrMask    OBJECT-TYPE
          SYNTAX               IpAddress
          MAX-ACCESS           not-accessible
          STATUS               deprecated
          DESCRIPTION          "The mask gives the range of the network addressess."
                      ::= {  fsRouteMapMatchEntry 3 }


          fsRouteMapMatchIpNextHop OBJECT-TYPE
          SYNTAX           IpAddress
          MAX-ACCESS       not-accessible
          STATUS           deprecated
          DESCRIPTION      " Matches the  next hop router  address."

                      ::= {  fsRouteMapMatchEntry  4 }

         fsRouteMapMatchMetric    OBJECT-TYPE
          SYNTAX          Integer32(1..2147483647)
          MAX-ACCESS      not-accessible
          STATUS          deprecated
          DESCRIPTION     "Matches metric of the route."

                      ::= {  fsRouteMapMatchEntry  5}

          fsRouteMapMatchTag     OBJECT-TYPE
          SYNTAX         Unsigned32
          MAX-ACCESS     not-accessible
          STATUS         deprecated
          DESCRIPTION    " Matches tag value associated with  route"

                      ::= {  fsRouteMapMatchEntry  6 }

          fsRouteMapMatchRouteType    OBJECT-TYPE
          SYNTAX          INTEGER  {
                              externaltype1  (1),
                              externaltype2  (2),
                              local          (3),
                              internal       (4)
                          }
          MAX-ACCESS     not-accessible
          STATUS         deprecated
          DESCRIPTION    " The  metric-type  local is local to AS in BGP , external is one
                            which is between the  different Autonomous Systems and internal
                         is within AS.External and internal are  associated with OSPF. "

                      ::= {  fsRouteMapMatchEntry  7 }

          fsRouteMapMatchMetricType    OBJECT-TYPE
          SYNTAX            INTEGER  {
                               externaltype1  (1),
                               externaltype2  (2),
                               internal       (3)

                             }
          MAX-ACCESS       not-accessible
          STATUS           deprecated
          DESCRIPTION    "The metric type external is one which is between the  different
                          Autonomous Systems and internal is within AS.External and internal
                           are  associated with OSPF.. "

                      ::= {  fsRouteMapMatchEntry  8 }


          fsRouteMapMatchASPathTag  OBJECT-TYPE
          SYNTAX           Unsigned32 (1..4294967295)
          MAX-ACCESS       not-accessible
          STATUS           deprecated
          DESCRIPTION      " Matches the tag of a route into an autonomous system path. Applies
                              only when redistributing routes into BGP. "

                      ::= {  fsRouteMapMatchEntry  9}

          fsRouteMapMatchCommunity   OBJECT-TYPE
          SYNTAX           Unsigned32
          MAX-ACCESS       not-accessible
          STATUS           deprecated
          DESCRIPTION     "Matches BGP community attribute.The communities that
                           BGP supports range from  well known ones like internet,
                           no-advst,no-export  to add communities to already
                           existing ones with the BGP. "
                      ::= {  fsRouteMapMatchEntry  10 }

          fsRouteMapMatchOrigin      OBJECT-TYPE
          SYNTAX           INTEGER  {
                              igp  (1),
                              egp  (2),
                           incomplete (3)
           }

          MAX-ACCESS       not-accessible
          STATUS           deprecated
          DESCRIPTION      "Matches BGP origin code.They can be from Remote
                            Interior Gateway Protocol (IGP) system or from
                            Local Exterior Gateway Protocol (EGP) system or
                            from  Remote autonomous system number which ranges
                            from 0 to 65535 or from incomplete  which mean
                            Unknown heritage."

                      ::= {  fsRouteMapMatchEntry  11 }


          fsRouteMapMatchLocalPreference OBJECT-TYPE
          SYNTAX               Integer32 (1..214748367)
          MAX-ACCESS           not-accessible
          STATUS               deprecated
          DESCRIPTION         "Matches preference value for the autonomous system path.
                               The preference is sent only to all routers in the
                               localautonomous system."

                      ::= {  fsRouteMapMatchEntry  12 }


          fsRouteMapMatchRowStatus    OBJECT-TYPE
          SYNTAX              RowStatus
          MAX-ACCESS          read-write
          STATUS              deprecated
          DESCRIPTION     "The status of this row, by which new entries may be
                            created, or old entries deleted from this table."

                      ::= {  fsRouteMapMatchEntry  13 }

-- set table

       fsRouteMapSetTable   OBJECT-TYPE
          SYNTAX    SEQUENCE  OF FsRouteMapSetEntry
          MAX-ACCESS      not-accessible
          STATUS          deprecated
          DESCRIPTION     "Route-map set table contains  various parameters that
                           are set during the process of policy routing or
                           route redistribution "
                        ::= {  fsRouteMap  3 }

      fsRouteMapSetEntry  OBJECT-TYPE
          SYNTAX        FsRouteMapSetEntry
          MAX-ACCESS    not-accessible
          STATUS        deprecated
          DESCRIPTION    "Row instance of the routemap set table"
           INDEX  {
                     fsRouteMapName,
                     fsRouteMapSeqNum
                 }

                      ::= { fsRouteMapSetTable 1 }

 FsRouteMapSetEntry ::= SEQUENCE {
         fsRouteMapSetInterface         InterfaceIndex,
         fsRouteMapSetIpNextHop         IpAddress,
         fsRouteMapSetMetric            Integer32,
         fsRouteMapSetTag               Unsigned32,
         fsRouteMapSetMetricType        INTEGER,
         fsRouteMapSetASPathTag        Unsigned32,
         fsRouteMapSetCommunity         Unsigned32,
         fsRouteMapSetOrigin            INTEGER,
         fsRouteMapSetOriginASNum       Unsigned32,
         fsRouteMapSetLocalPreference   Integer32,
         fsRouteMapSetRowStatus         RowStatus
         }

          fsRouteMapSetInterface   OBJECT-TYPE
          SYNTAX           InterfaceIndex
          MAX-ACCESS       read-write
          STATUS           deprecated
          DESCRIPTION    "This value identifies  the  local interface through
                          which the next hop can be reached and is set for a route
                          which passes the match conditions."

                      ::= {  fsRouteMapSetEntry 1  }

          fsRouteMapSetIpNextHop  OBJECT-TYPE
          SYNTAX          IpAddress
          MAX-ACCESS       read-write
          STATUS          deprecated
          DESCRIPTION    "  This represents the nexthop IP address and is set for a route
                            which passes the  match condition."
                      ::= {  fsRouteMapSetEntry  2 }

          fsRouteMapSetMetric      OBJECT-TYPE
          SYNTAX           Integer32
          MAX-ACCESS       read-write
          STATUS           deprecated
          DESCRIPTION      "The primary routing  metric.The  semantics of this metric
                            are determined by the routing-protocol specified."
                      ::= {  fsRouteMapSetEntry  3}

          fsRouteMapSetTag         OBJECT-TYPE
          SYNTAX           Unsigned32(1..214748367)
          MAX-ACCESS       read-write
          STATUS           deprecated
         DESCRIPTION       "Sets the tag value of the routing protocol."
                      ::= {  fsRouteMapSetEntry  4 }

          fsRouteMapSetMetricType    OBJECT-TYPE
          SYNTAX            INTEGER  {
                               externaltype1  (1),
                               externaltype2  (2),
                               internal       (3)

                             }
          MAX-ACCESS       read-write
          STATUS           deprecated
          DESCRIPTION    "The metric type external is one which is between the  different
                          Autonomous Systems and internal is within AS.External and internal
                           are  associated with OSPF.. "

                      ::= {  fsRouteMapSetEntry  5 }


          fsRouteMapSetASPathTag  OBJECT-TYPE
          SYNTAX           Unsigned32(1..4294967295)
          MAX-ACCESS       read-write
          STATUS           deprecated
          DESCRIPTION      " Converts the tag of a route into an autonomous system path.
                             Applies only when redistributing routes into BGP. "

                      ::= {  fsRouteMapSetEntry  6}

          fsRouteMapSetCommunity   OBJECT-TYPE
          SYNTAX           Unsigned32
          MAX-ACCESS       read-write
          STATUS           deprecated
          DESCRIPTION     "Sets BGP community attribute.The communities that BGP supports range
                           from  well known ones like internet,no-advst,no-export  to add
                           communities to already existing ones with the BGP. "
                      ::= {  fsRouteMapSetEntry  7 }

          fsRouteMapSetOrigin      OBJECT-TYPE
          SYNTAX           INTEGER  {
                              igp  (1),
                              egp  (2),
                           incomplete (3)
           }

          MAX-ACCESS       read-write
          STATUS           deprecated
          DESCRIPTION      "Sets the BGP origin code.They can be from Remote Interior Gateway
                             Protocol (IGP) system or from Local Exterior Gateway Protocol (EGP)
                             system or from  Remote autonomous system number which ranges  from
                              0 to 65535 or from incomplete  which mean Unknown heritage."

                      ::= {  fsRouteMapSetEntry  8 }

         fsRouteMapSetOriginASNum   OBJECT-TYPE
          SYNTAX           Unsigned32(1..4294967295)

          MAX-ACCESS       read-write
          STATUS           deprecated
          DESCRIPTION      "Sets the BGP origin Autonomous System Number.
                            This field is applicable only if the fsRouteMapSetOrigin is egp."

                      ::= {  fsRouteMapSetEntry  9 }


          fsRouteMapSetLocalPreference OBJECT-TYPE
          SYNTAX               Integer32 (1..214748367)
          MAX-ACCESS           read-write
          STATUS               deprecated
          DESCRIPTION         "Sets reference value for the autonomous system path.
                               The preference is sent only to all routers in the
                               local autonomous system."

                      ::= {  fsRouteMapSetEntry  10 }

          fsRouteMapSetRowStatus     OBJECT-TYPE
          SYNTAX             RowStatus
          MAX-ACCESS         read-write
          STATUS             deprecated
          DESCRIPTION        "The status of this row, by which new entries may be
                              created, or old entries deleted from this table."

                      ::= {  fsRouteMapSetEntry  11 }


 fsRMapGroup              OBJECT IDENTIFIER ::= { futureroutemap 2 }
 fsRMapTrapCfgGroup       OBJECT IDENTIFIER ::= { futureroutemap 3 }
 fsRMapTrapGroup          OBJECT IDENTIFIER ::= { futureroutemap 4 }
 fsRMapTrapNotifications  OBJECT IDENTIFIER ::= { fsRMapTrapGroup 0 }


 --Route map/IP-Prefix list table

          fsRMapTable   OBJECT-TYPE
          SYNTAX    SEQUENCE  OF FsRMapEntry
          MAX-ACCESS      not-accessible
          STATUS          current
          DESCRIPTION     "Route map  table contains  route map/IP Prefix list name, sequence
                           number and access status (Permit/Deny).Route-maps
                           can be used in policy  based routing and route
                           redistribution"
                      ::= { fsRMapGroup 1 }

          fsRMapEntry  OBJECT-TYPE
          SYNTAX        FsRMapEntry
          MAX-ACCESS    not-accessible
          STATUS        current
          DESCRIPTION   "Row instance of the route map/IP Prefix  table.
                        If the entry matches, action is performed
                        as configured for the match condition. If
                        entry does not match, all sequence numbers
                        are scanned till match is found, else default
                        action ( permit) is performed"
          INDEX         { fsRMapName,
                          fsRMapSeqNum
                        }
                      ::= { fsRMapTable 1 }


          FsRMapEntry ::= SEQUENCE {
              fsRMapName          DisplayString,
              fsRMapSeqNum        Unsigned32,
              fsRMapAccess        INTEGER,
              fsRMapRowStatus     RowStatus,
              fsRMapIsIpPrefixList  INTEGER
          }

          fsRMapName     OBJECT-TYPE
          SYNTAX             DisplayString (SIZE(1..20))
          MAX-ACCESS         not-accessible
          STATUS             current
          DESCRIPTION        "Name  Identifies the  specified route-map/IP Prefix list
                               in the list of route-maps."
                      ::= {  fsRMapEntry  1 }


          fsRMapSeqNum   OBJECT-TYPE
          SYNTAX             Unsigned32 (1..10)
          MAX-ACCESS         not-accessible
          STATUS             current
          DESCRIPTION       "Number that indicates the position of a new route
                             map/IP-Prefix in the list of route maps already configured
                             with the same name"
                      ::= {  fsRMapEntry  2 }

          fsRMapAccess   OBJECT-TYPE
          SYNTAX              INTEGER    {
                                   permit (1),
                                   deny (2)
          }
          MAX-ACCESS         read-write
          STATUS             current
          DESCRIPTION       "Access type associated with sequence number in a
                             route-map/IP Prefix. Once an instance of this object is
                             created,  it cannot be modified till fsRMapRowStatus
                             is set to not-in-service"
          DEFVAL   {permit}
                      ::= {  fsRMapEntry  3 }


          fsRMapRowStatus OBJECT-TYPE
          SYNTAX          RowStatus
          MAX-ACCESS      read-write
          STATUS          current
          DESCRIPTION     "The status of this row, by which new entries may be
                            created, or old entries deleted from this table."
                      ::= {  fsRMapEntry  4}

          fsRMapIsIpPrefixList OBJECT-TYPE
          SYNTAX          INTEGER {
                                     true (1)
                                  }
          MAX-ACCESS      read-write
          STATUS          current
          DESCRIPTION     "This object is to differentiate whether the entry present
                            in this table corresponds to the IP prefix list or Route map.
                            This object should be configured as true before creating any
                            IP prefix entry"
          DEFVAL   {false}
                      ::= {  fsRMapEntry  5}

 -- match table

          fsRMapMatchTable  OBJECT-TYPE
          SYNTAX       SEQUENCE  OF FsRMapMatchEntry
          MAX-ACCESS     not-accessible
          STATUS         current
          DESCRIPTION    "Route-map Match table contains various objects
                          used for matching the parameters of the route "
                      ::= {   fsRMapGroup   2 }

  fsRMapMatchEntry   OBJECT-TYPE
          SYNTAX         FsRMapMatchEntry
          MAX-ACCESS     not-accessible
          STATUS         current
          DESCRIPTION    "Row instance of the route map match  table"
          INDEX          { fsRMapName,
                           fsRMapSeqNum,

                           fsRMapMatchDestInetType,
                           fsRMapMatchDestInetAddress,
                           fsRMapMatchDestInetPrefix,
                           fsRMapMatchSourceInetType,
                           fsRMapMatchSourceInetAddress,
                           fsRMapMatchSourceInetPrefix,
                           fsRMapMatchNextHopInetType,
                           fsRMapMatchNextHopInetAddr,

                           fsRMapMatchInterface,
                           fsRMapMatchMetric,
                           fsRMapMatchTag,
         	               fsRMapMatchMetricType,
                           fsRMapMatchRouteType,

                           fsRMapMatchASPathTag,
		                   fsRMapMatchCommunity,
                           fsRMapMatchLocalPref,
                           fsRMapMatchOrigin
                          }
                      ::= { fsRMapMatchTable 1 }

    FsRMapMatchEntry ::= SEQUENCE {
         fsRMapMatchDestInetType      InetAddressType,
         fsRMapMatchDestInetAddress   InetAddress,
         fsRMapMatchDestInetPrefix    InetAddressPrefixLength,
         fsRMapMatchSourceInetType    InetAddressType,
         fsRMapMatchSourceInetAddress InetAddress,
         fsRMapMatchSourceInetPrefix  InetAddressPrefixLength,
         fsRMapMatchNextHopInetType   InetAddressType,
         fsRMapMatchNextHopInetAddr   InetAddress,

         fsRMapMatchInterface         InterfaceIndex,
         fsRMapMatchMetric            Integer32,
         fsRMapMatchTag               Unsigned32,
         fsRMapMatchMetricType        INTEGER,
         fsRMapMatchRouteType         INTEGER,

         fsRMapMatchASPathTag         Unsigned32,
         fsRMapMatchCommunity         Unsigned32,
         fsRMapMatchLocalPref         Integer32,
         fsRMapMatchOrigin            INTEGER,

         fsRMapMatchRowStatus         RowStatus,
         fsRMapMatchDestMaxPrefixLen  Unsigned32,
         fsRMapMatchDestMinPrefixLen  Unsigned32
         }


          fsRMapMatchDestInetType   OBJECT-TYPE
          SYNTAX             InetAddressType
          MAX-ACCESS         not-accessible
          STATUS             current
          DESCRIPTION       "The type of destination network Inet address
                             IPv4(1)
                             IPv6(2)"
                      ::= {  fsRMapMatchEntry 1 }

          fsRMapMatchDestInetAddress    OBJECT-TYPE
          SYNTAX               InetAddress (SIZE (4..16))
          MAX-ACCESS           not-accessible
          STATUS               current
          DESCRIPTION          "Inet address of destination network"
                      ::= {  fsRMapMatchEntry 2 }

          fsRMapMatchDestInetPrefix    OBJECT-TYPE
          SYNTAX               InetAddressPrefixLength
          MAX-ACCESS           not-accessible
          STATUS               current
          DESCRIPTION          "The prefix length of Inet address
                                of destination network"
                      ::= {  fsRMapMatchEntry 3 }

          fsRMapMatchSourceInetType   OBJECT-TYPE
          SYNTAX             InetAddressType
          MAX-ACCESS         not-accessible
          STATUS             current
          DESCRIPTION       "Matches the type of source network Inet address
                             IPv4(1)
                             IPv6(2)"
                      ::= {  fsRMapMatchEntry 4 }

          fsRMapMatchSourceInetAddress    OBJECT-TYPE
          SYNTAX               InetAddress (SIZE (4..16))
          MAX-ACCESS           not-accessible
          STATUS               current
          DESCRIPTION          "Matches Inet address of source network"
                      ::= {  fsRMapMatchEntry 5 }

          fsRMapMatchSourceInetPrefix    OBJECT-TYPE
          SYNTAX               InetAddressPrefixLength
          MAX-ACCESS           not-accessible
          STATUS               current
          DESCRIPTION          "Matches the prefix length of Inet address
                                of source network"
                      ::= {  fsRMapMatchEntry 6 }

          fsRMapMatchNextHopInetType OBJECT-TYPE
          SYNTAX           InetAddressType
          MAX-ACCESS       not-accessible
          STATUS           current
          DESCRIPTION      "Matches the Inet address type of next hop router
                            IPv4(1)
                            IPv6(2)"
                      ::= {  fsRMapMatchEntry  7 }

          fsRMapMatchNextHopInetAddr OBJECT-TYPE
          SYNTAX           InetAddress (SIZE (4..16))
          MAX-ACCESS       not-accessible
          STATUS           current
          DESCRIPTION      "Matches the Inet address of next hop router"
                      ::= {  fsRMapMatchEntry  8 }

          fsRMapMatchInterface   OBJECT-TYPE
          SYNTAX             InterfaceIndex
          MAX-ACCESS         not-accessible
          STATUS             current
          DESCRIPTION      " The ifIndex value which identifies  the  local
                             interface  through  which  the next hop  can be reached."
                      ::= {  fsRMapMatchEntry  9 }

         fsRMapMatchMetric    OBJECT-TYPE
          SYNTAX          Integer32(1..2147483647)
          MAX-ACCESS      not-accessible
          STATUS          current
          DESCRIPTION     "Matches metric of the route."
                      ::= {  fsRMapMatchEntry  10}

          fsRMapMatchTag     OBJECT-TYPE
          SYNTAX         Unsigned32
          MAX-ACCESS     not-accessible
          STATUS         current
          DESCRIPTION    " Matches tag value associated with  route"
                      ::= {  fsRMapMatchEntry  11 }

          fsRMapMatchMetricType    OBJECT-TYPE
          SYNTAX            INTEGER  {
                               intraarea    (1),
                               interarea    (2),
                               type1ext     (3),
                               type2ext     (4)
                             }
          MAX-ACCESS       not-accessible
          STATUS           current
          DESCRIPTION    "Matches types of paths in OSPF routing table"
                      ::= {  fsRMapMatchEntry  12 }

          fsRMapMatchRouteType    OBJECT-TYPE
          SYNTAX          INTEGER  {
                              local          (3),
                              remote         (4)
                          }
          MAX-ACCESS     not-accessible
          STATUS         current
          DESCRIPTION    "Matches route type as per RFC 2096"
                      ::= {  fsRMapMatchEntry  13 }

          fsRMapMatchASPathTag  OBJECT-TYPE
          SYNTAX           Unsigned32 (1..4294967295)
          MAX-ACCESS       not-accessible
          STATUS           current
          DESCRIPTION      " Matches the tag of a route into an autonomous system path. Applies
                              only when redistributing routes into BGP. "
                      ::= {  fsRMapMatchEntry  14}

          fsRMapMatchCommunity   OBJECT-TYPE
          SYNTAX           Unsigned32
          MAX-ACCESS       not-accessible
          STATUS           current
          DESCRIPTION     "Matches BGP community attribute.The communities that
                           BGP supports range from  well known ones like internet,
                           no-advst,no-export  to add communities to already
                           existing ones with the BGP. "
                      ::= {  fsRMapMatchEntry  15 }

          fsRMapMatchLocalPref OBJECT-TYPE
          SYNTAX               Integer32 (1..214748367)
          MAX-ACCESS           not-accessible
          STATUS               current
          DESCRIPTION         "Matches preference value for the autonomous system path.
                               The preference is sent only to all routers in the
                               localautonomous system."
                      ::= {  fsRMapMatchEntry  16 }

          fsRMapMatchOrigin      OBJECT-TYPE
          SYNTAX           INTEGER  {
                              igp  (1),
                              egp  (2),
                           incomplete (3)
           }
          MAX-ACCESS       not-accessible
          STATUS           current
          DESCRIPTION      "Matches BGP origin code.They can be from Remote
                            Interior Gateway Protocol (IGP) system or from
                            Local Exterior Gateway Protocol (EGP) system or
                            from  Remote autonomous system which mean
                            Unknown heritage."
                      ::= {  fsRMapMatchEntry  17 }

          fsRMapMatchRowStatus    OBJECT-TYPE
          SYNTAX              RowStatus
          MAX-ACCESS          read-write
          STATUS              current
          DESCRIPTION     "The status of this row, by which new entries may be
                            created, or old entries deleted from this table."
                      ::= {  fsRMapMatchEntry  18 }

          fsRMapMatchDestMaxPrefixLen OBJECT-TYPE
          SYNTAX              Unsigned32
          MAX-ACCESS          read-write
          STATUS              current
          DESCRIPTION     "This object is used only when fsRMapIpPrefixList is true.
                           It is to store the maximum prefix length allowed for the
                           DestPrefix."
                      ::= {  fsRMapMatchEntry  19 }

          fsRMapMatchDestMinPrefixLen OBJECT-TYPE
          SYNTAX              Unsigned32
          MAX-ACCESS          read-write
          STATUS              current
          DESCRIPTION     "This object is used only when fsRMapIpPrefixList is true.
                           It is to store the minimum prefix length allowed for the
                           DestPrefix."
                      ::= {  fsRMapMatchEntry  20 }


-- set table

       fsRMapSetTable   OBJECT-TYPE
          SYNTAX    SEQUENCE  OF FsRMapSetEntry
          MAX-ACCESS      not-accessible
          STATUS          current
          DESCRIPTION     "Route-map set table contains  various parameters that
                           are set during the process of policy routing or
                           route redistribution "
                        ::= {  fsRMapGroup  3 }

      fsRMapSetEntry  OBJECT-TYPE
          SYNTAX        FsRMapSetEntry
          MAX-ACCESS    not-accessible
          STATUS        current
          DESCRIPTION    "Row instance of the route map set table"
          INDEX         { fsRMapName,
                          fsRMapSeqNum
                        }
                        ::= { fsRMapSetTable 1 }

       FsRMapSetEntry ::= SEQUENCE {
             fsRMapSetNextHopInetType   InetAddressType,
             fsRMapSetNextHopInetAddr   InetAddress,
             fsRMapSetInterface         InterfaceIndex,
             fsRMapSetMetric            Integer32,
             fsRMapSetTag               Unsigned32,
             fsRMapSetRouteType         INTEGER,
             fsRMapSetASPathTag         Unsigned32,
             fsRMapSetCommunity         Unsigned32,
             fsRMapSetLocalPref         Integer32,
             fsRMapSetOrigin            INTEGER,
             fsRMapSetWeight            Unsigned32,
             fsRMapSetEnableAutoTag     INTEGER,
             fsRMapSetLevel             INTEGER,
             fsRMapSetRowStatus         RowStatus,
             fsRMapSetExtCommId         Unsigned32,
             fsRMapSetExtCommPOI        Unsigned32,
             fsRMapSetExtCommCost       Unsigned32,
             fsRMapSetCommunityAdditive INTEGER
         }


          fsRMapSetNextHopInetType  OBJECT-TYPE
          SYNTAX           InetAddressType
          MAX-ACCESS       read-write
          STATUS           current
          DESCRIPTION    " Inet address type of next hop
                           IPv4(1)
                           IPv6(2)"
                      ::= {  fsRMapSetEntry  1 }

          fsRMapSetNextHopInetAddr  OBJECT-TYPE
          SYNTAX           InetAddress
          MAX-ACCESS       read-write
          STATUS           current
          DESCRIPTION    "  This represents the nexthop Inet address and is set for a route
                            which passes the  match condition."
                      ::= {  fsRMapSetEntry  2 }







          fsRMapSetInterface   OBJECT-TYPE
          SYNTAX           InterfaceIndex
          MAX-ACCESS       read-write
          STATUS           current
          DESCRIPTION    "This value identifies  the  local interface through
                          which the next hop can be reached and is set for a route
                          which passes the match conditions."

                      ::= {  fsRMapSetEntry 3  }
          fsRMapSetMetric      OBJECT-TYPE
          SYNTAX           Integer32
          MAX-ACCESS       read-write
          STATUS           current
          DESCRIPTION      "The primary routing  metric.The  semantics of this metric
                            are determined by the routing-protocol specified."
                      ::= {  fsRMapSetEntry  4}

          fsRMapSetTag         OBJECT-TYPE
          SYNTAX           Unsigned32(1..214748367)
          MAX-ACCESS       read-write
          STATUS           current
         DESCRIPTION       "Sets the tag value of the routing protocol."
                      ::= {  fsRMapSetEntry  5 }

          fsRMapSetRouteType    OBJECT-TYPE
          SYNTAX           INTEGER {
                              local   (3),
                              remote  (4)
                           }
          MAX-ACCESS       read-write
          STATUS           current
          DESCRIPTION      "Sets the route type as per RFC 2096"
                      ::= {  fsRMapSetEntry  6 }





          fsRMapSetASPathTag  OBJECT-TYPE
          SYNTAX           Unsigned32(1..4294967295)
          MAX-ACCESS       read-write
          STATUS           current
          DESCRIPTION      " Converts the tag of a route into an autonomous system path.
                             Applies only when redistributing routes into BGP. "
                      ::= {  fsRMapSetEntry  7}

          fsRMapSetCommunity   OBJECT-TYPE
          SYNTAX           Unsigned32
          MAX-ACCESS       read-write
          STATUS           current
          DESCRIPTION     "Sets BGP community attribute.The communities that BGP supports
                           range from well known ones like internet,no-advst,no-export,
                           none. The configured commuity attribute will overwrites the
                           existing BGP communites in the bgp route. The well known
                           community none will remove all the existing bgp communities
                           present in the route. "
                      ::= {  fsRMapSetEntry  8 }


          fsRMapSetLocalPref   OBJECT-TYPE
          SYNTAX               Integer32 (1..214748367)
          MAX-ACCESS           read-write
          STATUS               current
          DESCRIPTION         "Sets reference value for the autonomous system path.
                               The preference is sent only to all routers in the
                               local autonomous system."
                      ::= {  fsRMapSetEntry  9 }

          fsRMapSetOrigin      OBJECT-TYPE
          SYNTAX               INTEGER  {
                                  igp  (1),
                                  egp  (2),
                                  incomplete (3)
                               }
          MAX-ACCESS       read-write
          STATUS           current
          DESCRIPTION      "Sets the BGP origin code.They can be from Remote Interior Gateway
                             Protocol (IGP) system or from Local Exterior Gateway Protocol (EGP)
                             system or from  Remote autonomous system number which ranges  from
                              0 to 65535 or from incomplete  which mean Unknown heritage."
                      ::= {  fsRMapSetEntry  10 }






         fsRMapSetWeight   OBJECT-TYPE
          SYNTAX           Unsigned32(1..65535)
          MAX-ACCESS       read-write
          STATUS           current
          DESCRIPTION      "Specify the BGP weight for the routing table"
                      ::= {  fsRMapSetEntry  11 }

          fsRMapSetEnableAutoTag    OBJECT-TYPE
          SYNTAX            INTEGER {
                               enable  (1),
                               disable (2)
                            }
          MAX-ACCESS        read-write
          STATUS            current
          DESCRIPTION       "Enable automatic computing of tag table
                             when redistributing routes from BGP into IGP"
          DEFVAL            { disable }
                      ::= {  fsRMapSetEntry  12 }

          fsRMapSetLevel    OBJECT-TYPE
          SYNTAX            INTEGER {
                               level1   (1),
                               level2   (2),
                               level12  (3),
                               stubarea (4),
                               backbone (5)
                            }
          MAX-ACCESS        read-write
          STATUS            current
          DESCRIPTION       "Set level for routes that are advertised into
                             the specified area of the routing domain"
                      ::= {  fsRMapSetEntry  13 }




          fsRMapSetRowStatus     OBJECT-TYPE
          SYNTAX             RowStatus
          MAX-ACCESS         read-write
          STATUS             current
          DESCRIPTION        "The status of this row, by which new entries may be
                              created, or old entries deleted from this table."
                      ::= {  fsRMapSetEntry  14 }

          fsRMapSetExtCommId      OBJECT-TYPE
          SYNTAX                  Unsigned32(0..255)
          MAX-ACCESS              read-write
          STATUS                  current
          DESCRIPTION             "Specifies the extended cost community Id attribute
                                   whose value is used in determining the BGP best route
                                   when fsRMapSetExtCommCost is same for the routes.
                                   Route with lower cost is preferred..
                                   It is a type of the opaque extended community."
                      ::= {  fsRMapSetEntry  15 }

          fsRMapSetExtCommPOI      OBJECT-TYPE
          SYNTAX                   Unsigned32
          MAX-ACCESS               read-only
          STATUS                   current
          DESCRIPTION              "Specifies the point of insertion for usage of
                                    extended cost community in the BGP decision
                                    making process. Currently, supports usage of
                                    single POI after IGP cost comparison"
                      ::= {  fsRMapSetEntry  16 }

          fsRMapSetExtCommCost      OBJECT-TYPE
          SYNTAX                    Unsigned32
          MAX-ACCESS                read-write
          STATUS                    current
          DESCRIPTION             "Specifies the extended cost community value that
                                   is used to determine the BGP best route."
                      ::= {  fsRMapSetEntry  17 }

          fsRMapSetCommunityAdditive     OBJECT-TYPE
          SYNTAX             INTEGER {
                                  replace (1),
                                  additive (2) }
          MAX-ACCESS         read-write
          STATUS             current
          DESCRIPTION        "Configures how the community set via fsRouteMapSetCommunity
                              is used for the matched routes. The value additive appends
                              the configured community to the existing communities
                              available for the route. Replace will cause the existing
                              community values to be overwritten by the configured
                              community value."
          DEFVAL            { replace }
                      ::= {  fsRMapSetEntry  18 }


--route map snmp trap Configuration

        fsRmapTrapCfgEnable OBJECT-TYPE
        SYNTAX              INTEGER {
                                enable(1),
                                disable(2)
                            }
        MAX-ACCESS          read-write
        STATUS              current
        DESCRIPTION         "Enable or disable sendig route map traps
                             when matching of route with route map occured"
        DEFVAL              { enable }
                    ::= { fsRMapTrapCfgGroup 1 }


--route map snmp traps definition

        fsRMapTrapName     OBJECT-TYPE
        SYNTAX             DisplayString (SIZE(1..20))
        MAX-ACCESS         accessible-for-notify
        STATUS             current
        DESCRIPTION        "Name  Identifies the  specified route-map
                             in the list of route-maps."
                    ::= {  fsRMapTrapGroup 1 }


        fsRMapTrapSeqNum   OBJECT-TYPE
        SYNTAX             Unsigned32 (1..10)
        MAX-ACCESS         accessible-for-notify
        STATUS             current
        DESCRIPTION       "Number that indicates the position of a new route
                           map in the list of route maps already configured
                           with the same name"
                    ::= {  fsRMapTrapGroup 2 }


--route map snmp traps notifications

        fsRMapTrapMatch     NOTIFICATION-TYPE
        OBJECTS             {
                                fsRMapTrapName,
                                fsRMapTrapSeqNum
                            }
        STATUS              current
        DESCRIPTION        "Signifies that there has been a route matching
                            with route map"
                    ::= { fsRMapTrapNotifications 1 }



END
