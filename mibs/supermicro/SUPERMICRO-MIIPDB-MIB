-- Copyright (C) 2008-2014 Super Micro Computer Inc. All Rights Reserved

-- $Id: fsmiipdb.mib,v 1.2 2012/09/07 09:52:05 siva Exp $

-- MIIP-BINDING-DATABASE Proprietary MIB Definition

   SUPERMICRO-MIIPDB-MIB DEFINITIONS ::= BEGIN
      IMPORTS
         MODULE-IDENTITY, OBJECT-TYPE,
         enterprises, IpAddress, Counter32,
         Integer32, Unsigned32                    FROM SNMPv2-SMI
         RowStatus, MacAddress                    FROM SNMPv2-TC
         InterfaceIndex                           FROM IF-MIB;


fsMIIpdb  MODULE-IDENTITY
          LAST-UPDATED "201209050000Z"
          ORGANIZATION "Super Micro Computer Inc."
          CONTACT-INFO "support@Supermicro.com"
          DESCRIPTION
              " Multiple Instance support for IP binding database module. "
	  REVISION "201209050000Z"
          DESCRIPTION
              " Multiple Instance support for IP binding database module. "
         ::=  { enterprises supermicro-computer-inc(10876) super-switch(101) basic(2) 48 }

-- ***************************************************************************
--                         Groups in the MIB
-- ***************************************************************************
    fsMIIpDbScalars               OBJECT IDENTIFIER ::= { fsMIIpdb 1 }
    fsMIIpDbStatic                OBJECT IDENTIFIER ::= { fsMIIpdb 2 }
    fsMIIpDbBindings              OBJECT IDENTIFIER ::= { fsMIIpdb 3 }
    fsMIIpDbInterface             OBJECT IDENTIFIER ::= { fsMIIpdb 4 }
    fsMIIpDbSrcGuard              OBJECT IDENTIFIER ::= { fsMIIpdb 5 }

-- ***************************************************************************
--                               SCALARS
-- ***************************************************************************

    fsMIIpDbNoOfBindings OBJECT-TYPE
        SYNTAX          Counter32
        MAX-ACCESS      read-only
        STATUS          current
        DESCRIPTION
            "Indicates the total number of (host, IP) bindings, across
            all VLAN's, at a given time. This is nothing but the total
            number of entries in the IP binding database"
    ::= { fsMIIpDbScalars 1 }

    fsMIIpDbNoOfStaticBindings OBJECT-TYPE
        SYNTAX          Counter32
        MAX-ACCESS      read-only
        STATUS          current
        DESCRIPTION
            "Indicates the total number of static (host, IP) bindings,
            across all VLANS, at the given time."
    ::= { fsMIIpDbScalars 2 }

    fsMIIpDbNoOfDHCPBindings OBJECT-TYPE
        SYNTAX          Counter32
        MAX-ACCESS      read-only
        STATUS          current
        DESCRIPTION
            "Indicates the total number of (host, IP) bindings configured
             through DHCP, across all VLANS, at the given time."
    ::= { fsMIIpDbScalars 3 }

    fsMIIpDbNoOfPPPBindings OBJECT-TYPE
        SYNTAX          Counter32
        MAX-ACCESS      read-only
        STATUS          current
        DESCRIPTION
            "Indicates the total number of (host, IP) bindings configured
             through PPP, across all VLANS, at the given time."
    ::= { fsMIIpDbScalars 4 }

    fsMIIpDbTraceLevel OBJECT-TYPE
        SYNTAX      Integer32
        MAX-ACCESS  read-write
        STATUS      current
        DESCRIPTION
            "This object is used to enable trace statements in IP binding
            database module.

            A four byte integer is used for enabling the trace level.
            Each bit in the four byte integer represents a particular
            trace level.

            The mapping between the bit positions & the trace level is
            as follows:
                    BIT 1 - Function entry traces
                    BIT 2 - Function Exit traces
                    BIT 3 - Debug traces
                    BIT 4 - Failure traces
                    BIT 5 - Function arguments trace

            The remaining bits are unused. Combination of levels are
            also allowed.

            For example if the bits 1 and 2 are set, then the trace
            statement related to function entry and exit will be printed.

            The user has to enter the corresponding integer value for the
            bits set. For example if bits 1 and 2 are to be set ,then user
            has to give the value 6."
     ::= { fsMIIpDbScalars 5 }

-- ***************************************************************************
--                               GROUPS
-- ***************************************************************************

-- ********************** (HOST, IP) Static Bindings *************************

    fsMIIpDbStaticBindingTable OBJECT-TYPE
        SYNTAX  SEQUENCE OF FsMIIpDbStaticBindingEntry
        MAX-ACCESS      not-accessible
        STATUS          current
        DESCRIPTION
            "This table contains the static Host IP configuration
             information."
    ::= { fsMIIpDbStatic 1}

    fsMIIpDbStaticBindingEntry OBJECT-TYPE
        SYNTAX FsMIIpDbStaticBindingEntry
        MAX-ACCESS      not-accessible
        STATUS          current
        DESCRIPTION
            "A single entry contains the binding information of a single
             host connected to the system."
        INDEX {
                fsMIIpDbContextId,
                fsMIIpDbStaticHostVlanId,
                fsMIIpDbStaticHostMac
              }
    ::= { fsMIIpDbStaticBindingTable 1 }

    FsMIIpDbStaticBindingEntry ::= SEQUENCE {
        fsMIIpDbContextId             Integer32,
        fsMIIpDbStaticHostVlanId      Integer32,
        fsMIIpDbStaticHostMac         MacAddress,
        fsMIIpDbStaticHostIp          IpAddress,
        fsMIIpDbStaticInIfIndex       Integer32,
        fsMIIpDbStaticGateway         IpAddress,
        fsMIIpDbStaticBindingStatus   RowStatus
    }

    fsMIIpDbContextId OBJECT-TYPE
        SYNTAX      Integer32 (0..65535)
        MAX-ACCESS  not-accessible
        STATUS      current
        DESCRIPTION
            "Identifies the Virtual Bridge Context."
    ::= { fsMIIpDbStaticBindingEntry 1 }

    fsMIIpDbStaticHostVlanId OBJECT-TYPE
        SYNTAX      Integer32 (1..4094)
        MAX-ACCESS  not-accessible
        STATUS      current
        DESCRIPTION
            "The VLAN ID to which the host belongs. This is an index of
             the table."
    ::= { fsMIIpDbStaticBindingEntry 2 }

    fsMIIpDbStaticHostMac OBJECT-TYPE
        SYNTAX      MacAddress
        MAX-ACCESS  not-accessible
        STATUS      current
        DESCRIPTION
            "MAC address of the Host. This is an index of the table."
    ::= { fsMIIpDbStaticBindingEntry 3 }

    fsMIIpDbStaticHostIp OBJECT-TYPE
        SYNTAX      IpAddress
        MAX-ACCESS  read-write
        STATUS      current
        DESCRIPTION
            "IP address of the Host."
    ::= { fsMIIpDbStaticBindingEntry 4 }

    fsMIIpDbStaticInIfIndex OBJECT-TYPE
        SYNTAX      Integer32
        MAX-ACCESS  read-write
        STATUS      current
        DESCRIPTION
            "Indicates the interface to which the host is connected."
    ::= { fsMIIpDbStaticBindingEntry 5 }

    fsMIIpDbStaticGateway OBJECT-TYPE
        SYNTAX      IpAddress
        MAX-ACCESS  read-write
        STATUS      current
        DESCRIPTION
            "Indicates the gateway to which the Host have access to."
    ::= { fsMIIpDbStaticBindingEntry 6 }

    fsMIIpDbStaticBindingStatus OBJECT-TYPE
        SYNTAX      RowStatus
        MAX-ACCESS  read-write
        STATUS      current
        DESCRIPTION
            "The rowstatus of the binding table entry. All the objects in the
             table must be filled before making the rowstatus as active."
    ::= { fsMIIpDbStaticBindingEntry 7 }

-- ********************** (HOST, IP) Binding Database ************************

    fsMIIpDbBindingTable OBJECT-TYPE
        SYNTAX  SEQUENCE OF FsMIIpDbBindingEntry
        MAX-ACCESS      not-accessible
        STATUS          current
        DESCRIPTION
            "This table contains the information about all the hosts connected
             to the system, their MAC Address, VLAN, IP etc."
    ::= { fsMIIpDbBindings 1}

    fsMIIpDbBindingEntry OBJECT-TYPE
        SYNTAX FsMIIpDbBindingEntry
        MAX-ACCESS      not-accessible
        STATUS          current
        DESCRIPTION
            "A single entry contains the binding information of a single
             host connected to the system."
        INDEX {
                fsMIIpDbHostContextId,
                fsMIIpDbHostVlanId,
                fsMIIpDbHostMac
              }
    ::= { fsMIIpDbBindingTable 1 }

    FsMIIpDbBindingEntry ::= SEQUENCE {
        fsMIIpDbHostContextId     Integer32,
        fsMIIpDbHostVlanId        Integer32,
        fsMIIpDbHostMac           MacAddress,
        fsMIIpDbHostBindingType   INTEGER,
        fsMIIpDbHostIp            IpAddress,
        fsMIIpDbHostInIfIndex     Integer32,
        fsMIIpDbHostRemLeaseTime  Integer32,
        fsMIIpDbHostBindingID     Unsigned32
    }

    fsMIIpDbHostContextId OBJECT-TYPE
        SYNTAX      Integer32 (0..65535)
        MAX-ACCESS  not-accessible
        STATUS      current
        DESCRIPTION
            "Identifies the Virtual Bridge Context."
    ::= { fsMIIpDbBindingEntry 1 }

    fsMIIpDbHostVlanId OBJECT-TYPE
        SYNTAX      Integer32 (1..4094)
        MAX-ACCESS  not-accessible
        STATUS      current
        DESCRIPTION
            "The VLAN ID to which the host belongs. This is an index of
             the table."
    ::= { fsMIIpDbBindingEntry 2 }

    fsMIIpDbHostMac OBJECT-TYPE
        SYNTAX      MacAddress
        MAX-ACCESS  not-accessible
        STATUS      current
        DESCRIPTION
            "MAC address of the Host. This is an index of the table."
    ::= { fsMIIpDbBindingEntry 3 }

    fsMIIpDbHostBindingType OBJECT-TYPE
        SYNTAX      INTEGER { static (1), dhcp (2), ppp (3) }
        MAX-ACCESS  read-only
        STATUS      current
        DESCRIPTION
            "Specifies whether the entry was configured through static
            or dynamically learnt through DHCP or PPP."
    ::= { fsMIIpDbBindingEntry 4 }

    fsMIIpDbHostIp OBJECT-TYPE
        SYNTAX      IpAddress
        MAX-ACCESS  read-only
        STATUS      current
        DESCRIPTION
            "IP address of the Host."
    ::= { fsMIIpDbBindingEntry 5 }

    fsMIIpDbHostInIfIndex OBJECT-TYPE
        SYNTAX      Integer32
        MAX-ACCESS  read-only
        STATUS      current
        DESCRIPTION
            "Indicates the interface to which the host is connected."
    ::= { fsMIIpDbBindingEntry 6 }

    fsMIIpDbHostRemLeaseTime OBJECT-TYPE
        SYNTAX      Integer32
        MAX-ACCESS  read-only
        STATUS      current
        DESCRIPTION
            "The Remaining lease time in seconds for the (host, IP) binding.
             Applicable only if the fsIpDbBindingType is DHCP."
    ::= { fsMIIpDbBindingEntry 7 }

    fsMIIpDbHostBindingID OBJECT-TYPE
        SYNTAX      Unsigned32
        MAX-ACCESS  read-only
        STATUS      current
        DESCRIPTION
            "An integer value that identifies the binding type. For Static
            Bindings, this value is 0. For DHCP Bindings, this is the
            transaction ID. For PPP Bindings, this is the session ID
            of PPPoE session."
    ::= { fsMIIpDbBindingEntry 8 }



--  Below is the Gateway Table corresponding to each binding entry.
--  Each binding entry will contain a table of Gateway IPs,
--  which will contain atleast one (default gateway) gateway IP entry.

        fsMIIpDbGatewayIpTable OBJECT-TYPE
            SYNTAX  SEQUENCE OF FsMIIpDbGatewayIpEntry
            MAX-ACCESS  not-accessible
            STATUS      current
            DESCRIPTION
                "This table is a part of FsDhcpSnpBindingEntry. The table
                 contains IP address of Gateways allowed for the host.
                 The host will be allowed to contact only these Gateways."
        ::= { fsMIIpDbBindings 2 }

        fsMIIpDbGatewayIpEntry OBJECT-TYPE
            SYNTAX FsMIIpDbGatewayIpEntry
            MAX-ACCESS  not-accessible
            STATUS      current
            DESCRIPTION
                "Each entry contains an IP address of Gateway allowed for
                the host."
            INDEX {
                    fsMIIpDbHostContextId,
                    fsMIIpDbHostMac,
                    fsMIIpDbHostVlanId,
                    fsMIIpDbGatewayNetwork,
                    fsMIIpDbGatewayNetMask,
                    fsMIIpDbGatewayIp
                  }
        ::= { fsMIIpDbGatewayIpTable 1 }

        FsMIIpDbGatewayIpEntry ::= SEQUENCE {
            fsMIIpDbGatewayNetwork    IpAddress,
            fsMIIpDbGatewayNetMask    IpAddress,
            fsMIIpDbGatewayIp         IpAddress,
            fsMIIpDbGatewayIpMode     INTEGER
        }

        fsMIIpDbGatewayNetwork OBJECT-TYPE
            SYNTAX      IpAddress
            MAX-ACCESS  not-accessible
            STATUS      current
            DESCRIPTION
                "The network IP address of the gateway."
        ::= { fsMIIpDbGatewayIpEntry 1 }

        fsMIIpDbGatewayNetMask OBJECT-TYPE
            SYNTAX      IpAddress
            MAX-ACCESS  not-accessible
            STATUS      current
            DESCRIPTION
                "The mask for the network to which the gateway is given."
        ::= { fsMIIpDbGatewayIpEntry 2 }

        fsMIIpDbGatewayIp OBJECT-TYPE
            SYNTAX      IpAddress
            MAX-ACCESS  not-accessible
            STATUS      current
            DESCRIPTION
                "The Gateway IP for the given network."
        ::= { fsMIIpDbGatewayIpEntry 3 }

        fsMIIpDbGatewayIpMode OBJECT-TYPE
            SYNTAX      INTEGER { active (0) }
            MAX-ACCESS  read-only
            STATUS      current
            DESCRIPTION
                "The Gateway IP verification mode while ARP
                packet processing. "
        ::= { fsMIIpDbGatewayIpEntry 4 }

-- **************************** Interface Entry ******************************

    fsMIIpDbInterfaceTable OBJECT-TYPE
        SYNTAX  SEQUENCE OF FsMIIpDbInterfaceEntry
        MAX-ACCESS  not-accessible
        STATUS      current
        DESCRIPTION
            "This table contains the interface (layer 2 VLAN) specific
             informations."
    ::= { fsMIIpDbInterface 1 }

    fsMIIpDbInterfaceEntry OBJECT-TYPE
        SYNTAX FsMIIpDbInterfaceEntry
        MAX-ACCESS  not-accessible
        STATUS      current
        DESCRIPTION
            "Each entry will contain statistics associated with the interface."
        INDEX {
                fsMIIpDbIntfContextId,
                fsMIIpDbIntfVlanId
              }
    ::= { fsMIIpDbInterfaceTable 1 }

    FsMIIpDbInterfaceEntry ::= SEQUENCE {
        fsMIIpDbIntfContextId                 Integer32,
        fsMIIpDbIntfVlanId                    Integer32,
        fsMIIpDbIntfNoOfVlanBindings          Counter32,
        fsMIIpDbIntfNoOfVlanStaticBindings    Counter32,
        fsMIIpDbIntfNoOfVlanDHCPBindings      Counter32,
        fsMIIpDbIntfNoOfVlanPPPBindings       Counter32
    }

    fsMIIpDbIntfContextId OBJECT-TYPE
        SYNTAX      Integer32 (0..65535)
        MAX-ACCESS  not-accessible
        STATUS      current
        DESCRIPTION
            "Identifies the Virtual Bridge Context."
    ::= { fsMIIpDbInterfaceEntry 1 }

    fsMIIpDbIntfVlanId OBJECT-TYPE
        SYNTAX      Integer32 (1..4094)
        MAX-ACCESS  not-accessible
        STATUS      current
        DESCRIPTION
            "Vlan ID of the VLAN to which this table-entry is associated."
    ::= { fsMIIpDbInterfaceEntry 2 }

    fsMIIpDbIntfNoOfVlanBindings OBJECT-TYPE
        SYNTAX          Counter32
        MAX-ACCESS      read-only
        STATUS          current
        DESCRIPTION
            "This indicates the total number of (host, IP) bindings for
            a given VLAN at a given time."
    ::= { fsMIIpDbInterfaceEntry 3 }

    fsMIIpDbIntfNoOfVlanStaticBindings OBJECT-TYPE
        SYNTAX          Counter32
        MAX-ACCESS      read-only
        STATUS          current
        DESCRIPTION
            "This indicates the total number of static (host, IP) bindings
            for a VLAN at a given time. "
    ::= { fsMIIpDbInterfaceEntry 4 }

    fsMIIpDbIntfNoOfVlanDHCPBindings OBJECT-TYPE
        SYNTAX          Counter32
        MAX-ACCESS      read-only
        STATUS          current
        DESCRIPTION
            "This indicates the total number of (host, IP) bindings
            configured through DHCP for a VLAN at a given time. "
    ::= { fsMIIpDbInterfaceEntry 5 }

    fsMIIpDbIntfNoOfVlanPPPBindings OBJECT-TYPE
        SYNTAX          Counter32
        MAX-ACCESS      read-only
        STATUS          current
        DESCRIPTION
            "This indicates the total number of (host, IP) bindings
            configured through PPP for a VLAN at a given time. "
    ::= { fsMIIpDbInterfaceEntry 6 }

-- ======================================================
-- IP source guard table
-- ======================================================
fsMIIpDbSrcGuardConfigTable   OBJECT-TYPE
    SYNTAX              SEQUENCE OF FsMIIpDbSrcGuardConfigEntry
    MAX-ACCESS          not-accessible
    STATUS              current
    DESCRIPTION
    " This table provides the objects to enable or disable
    IP source guard on each non routed Layer 2 interfaces.

    When DHCP Snooping is enabled at an interface, a list of
    IP addresses is obtained through DHCP snooping for this
    particular interface and these list of IP address are
    maintained in IP binding database along with the MAC,
    VLAN ID and interface index. This database can be populated
    using static configuration also.

    If IP source guard is enabled, incoming IP traffic on an
    interface are allowed when there is a matching entry in IP
    binding database. Else, all incoming IP traffic on an
    interface are allowed irrespective of the IP binding database."
    ::= { fsMIIpDbSrcGuard 1 }


fsMIIpDbSrcGuardConfigEntry   OBJECT-TYPE
    SYNTAX              FsMIIpDbSrcGuardConfigEntry
    MAX-ACCESS          not-accessible
    STATUS              current
    DESCRIPTION
    " Each row instance contains the configuration to enable
    or disable IP source guard on a physical interface. "
    INDEX { fsMIIpDbSrcGuardIndex }
    ::= { fsMIIpDbSrcGuardConfigTable 1 }

FsMIIpDbSrcGuardConfigEntry ::= SEQUENCE {
    fsMIIpDbSrcGuardIndex  InterfaceIndex,
    fsMIIpDbSrcGuardStatus INTEGER
}

fsMIIpDbSrcGuardIndex OBJECT-TYPE
    SYNTAX       InterfaceIndex
    MAX-ACCESS   not-accessible
    STATUS       current
    DESCRIPTION
       "This indicates the interface identifier for which the IP source
        guard configuration is applied."
    ::= { fsMIIpDbSrcGuardConfigEntry  1 }

fsMIIpDbSrcGuardStatus  OBJECT-TYPE
    SYNTAX              INTEGER {
                            disable(1),
                            ip (2),
                            ipMac (3)
    }
    MAX-ACCESS          read-write
    STATUS              current
    DESCRIPTION
        " This object indicates the IP source guard status of an
        interface.

        If this object is set to 'disable', IP source guard feature
        is disabled and all incoming IP traffic on this interface
        will be allowed.

        If this object is set to 'ip', IP source guard feature is
        enabled on fsIpDbSrcGuardIndex with Source IP address filtering
        mode. The switch allows the IP traffic when the source IP
        matches with an entry in Ip binding database.

        If this object is set to 'ipMac', IP source guard is enabled on
        the fsIpDbSrcGuardIndex with Source IP and MAC address filtering
        mode. The switch allows the IP traffic when the source IP and MAC
        address matches with an entry in Ip binding database.

        When there is no IP binding entries and IP source guard is
        enabled, switch drops all types of packets other than DHCP
        packet. "

    DEFVAL  { disable }
    ::= { fsMIIpDbSrcGuardConfigEntry 2 }

END
