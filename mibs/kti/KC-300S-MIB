KC-300S-MIB DEFINITIONS ::= BEGIN

IMPORTS
        enterprises, OBJECT-TYPE, NetworkAddress, IpAddress, Counter,
        Gauge, TimeTicks
                FROM RFC1155-SMI;


KTI OBJECT IDENTIFIER ::= { enterprises 867 }

KC-300S OBJECT IDENTIFIER ::= { KTI 34 }

Device_CPU		OBJECT IDENTIFIER ::= { KC-300S 1 }
Device_Status           OBJECT IDENTIFIER ::= { KC-300S 2 }
Device_TP_Status        OBJECT IDENTIFIER ::= { Device_Status 1 }
Device_FX_Status        OBJECT IDENTIFIER ::= { Device_Status 2 }

Device_Config           OBJECT IDENTIFIER ::= { KC-300S 3 }

-- object types

-- the slot2and3cpumodule group

softwareVer OBJECT-TYPE
        SYNTAX  OCTET STRING
        ACCESS  read-only
        STATUS  mandatory
        DESCRIPTION
                "The version of the Convert Center MIB software."
        ::= { Device_CPU 1 }

mibFileVer OBJECT-TYPE
        SYNTAX  OCTET STRING
        ACCESS  read-only
        STATUS  mandatory
        DESCRIPTION
                "The version of the MIB file software."
        ::= { Device_CPU 2 }

Login_Trap_Message1 OBJECT-TYPE
        SYNTAX  OCTET STRING
        ACCESS  read-only
        STATUS  mandatory
        DESCRIPTION
                "The version of the MIB file software."
        ::= { Device_CPU 3 }

Login_Trap_Message2 OBJECT-TYPE
        SYNTAX  OCTET STRING
        ACCESS  read-only
        STATUS  mandatory
        DESCRIPTION
                "The version of the MIB file software."
        ::= { Device_CPU 4 }



-- the Ports group

Device_TP_Config  OBJECT-TYPE
        SYNTAX  INTEGER{
        	Auto_100M_Full(1)
        	Un-auto_100M_Full(2)
        	Un-auto_100M_Half(3)
        	Un-auto_10M_Full(4)
        	Un-auto_10M_Half(5)
        }
        ACCESS  read-write
        STATUS  mandatory
        DESCRIPTION
                "Device_TP_Config."
        ::= { Device_Config 1 }

Trap_Port_Link  OBJECT-TYPE
        SYNTAX  INTEGER{
        	Disabled(0)
        	Enabled(1)
        }
        ACCESS  read-write
        STATUS  mandatory
        DESCRIPTION
                "Trap_Port_Link."
        ::= { Device_Config 2 }

Trap_Login_Failure  OBJECT-TYPE
        SYNTAX  INTEGER{
        	Disabled(0)
        	Enabled(1)
        }
        ACCESS  read-write
        STATUS  mandatory
        DESCRIPTION
                "Trap_Login."
        ::= { Device_Config 3 }

Device_TP_Link_Status  OBJECT-TYPE
        SYNTAX  INTEGER{
        	UP(0),
        	Down(1)
        }
        ACCESS  read-only
        STATUS  mandatory
        DESCRIPTION
                "Device_TP_Link_Status."
        ::= { Device_TP_Status 1 }

Device_TP_LineSpeed_Status  OBJECT-TYPE
        SYNTAX  INTEGER{
        	_100M(0),
        	_10M(1)
        }
        ACCESS  read-only
        STATUS  mandatory
        DESCRIPTION
                "Device_TP_LineSpeed_Status."
        ::= { Device_TP_Status 2 }

Device_TP_Duplex_Status  OBJECT-TYPE
        SYNTAX  INTEGER{
        	Full(0),
        	Half(1)
        }
        ACCESS  read-only
        STATUS  mandatory
        DESCRIPTION
                "Device_TP_Duplex_Status."
        ::= { Device_TP_Status 3 }

Device_TP_FlowControl_Status  OBJECT-TYPE
        SYNTAX  INTEGER{
        	Enable(0),
        	Disable(1)
        }
        ACCESS  read-only
        STATUS  mandatory
        DESCRIPTION
                "Device_TP_FlowControl_Status."
        ::= { Device_TP_Status 4 }

Device_FX_Link_Status  OBJECT-TYPE
        SYNTAX  INTEGER{
        	UP(0),
        	Down(1)
        }
        ACCESS  read-only
        STATUS  mandatory
        DESCRIPTION
                "Device_FX_Link_Status."
        ::= { Device_FX_Status 1 }

Device_FX_LineSpeed_Status  OBJECT-TYPE
        SYNTAX  INTEGER{
        	_100M(0),
        	_10M(1)
        }
        ACCESS  read-only
        STATUS  mandatory
        DESCRIPTION
                "Device_FX_LineSpeed_Status."
        ::= { Device_FX_Status 2 }

Device_FX_Duplex_Status  OBJECT-TYPE
        SYNTAX  INTEGER{
        	Full(0),
        	Half(1)
        }
        ACCESS  read-only
        STATUS  mandatory
        DESCRIPTION
                "Device_FX_Duplex_Status."
        ::= { Device_FX_Status 3 }

Device_FX_FlowControl_Status  OBJECT-TYPE
        SYNTAX  INTEGER{
        	Enable(0),
        	Disable(1)
        }
        ACCESS  read-only
        STATUS  mandatory
        DESCRIPTION
                "Device_FX_FlowControl_Status."
        ::= { Device_FX_Status 4 }


END
