SNMPSERVER-MIB DEFINITIONS ::= BEGIN


IMPORTS
MODULE-IDENTITY, OBJECT-TYPE, NOTIFICATION-TYPE, TimeTicks, Counter32, Counter64, Unsigned32, dod, mib-2
FROM SNMPv2-SMI
DisplayString
FROM SNMPv2-TC;

internet OBJECT IDENTIFIER  ::= { dod 1 }

mgmt OBJECT IDENTIFIER  ::= { internet 2 }

mib-2 OBJECT IDENTIFIER  ::= { mgmt 1 }

system OBJECT IDENTIFIER  ::= { mib-2 1 }

	sysDescr OBJECT-TYPE
	SYNTAX DisplayString
	MAX-ACCESS read-only
	STATUS current
	DESCRIPTION ""
	::= { system 1 }

	sysObjectID OBJECT-TYPE
	SYNTAX OBJECT IDENTIFIER
	MAX-ACCESS read-only
	STATUS current
	DESCRIPTION ""
	::= { system 2 }

	sysUpTime OBJECT-TYPE
	SYNTAX TimeTicks
	MAX-ACCESS read-only
	STATUS current
	DESCRIPTION ""
	::= { system 3 }

	sysContact OBJECT-TYPE
	SYNTAX DisplayString
	MAX-ACCESS read-write
	STATUS current
	DESCRIPTION ""
	::= { system 4 }

	sysName OBJECT-TYPE
	SYNTAX DisplayString
	MAX-ACCESS read-write
	STATUS current
	DESCRIPTION ""
	::= { system 5 }

	sysLocation OBJECT-TYPE
	SYNTAX DisplayString
	MAX-ACCESS read-write
	STATUS current
	DESCRIPTION ""
	::= { system 6 }

private OBJECT IDENTIFIER  ::= { internet 4 }

enterprises OBJECT IDENTIFIER  ::= { private 1 }

tecnairlv OBJECT IDENTIFIER  ::= { enterprises 53332 }

	node1 OBJECT IDENTIFIER  ::= { tecnairlv 1 }

		traps1 OBJECT IDENTIFIER  ::= { node1 0 }

			generalAlTrap_1  NOTIFICATION-TYPE
			OBJECTS
			{
			generalAl_1
			}
			STATUS   current
			DESCRIPTION "General alarams"
			::= { traps1 1 }

			notCriticalAlTrap_1  NOTIFICATION-TYPE
			OBJECTS
			{
			notCriticalAl_1
			}
			STATUS   current
			DESCRIPTION "Not critical alarms"
			::= { traps1 2 }

			criticalAlTrap_1  NOTIFICATION-TYPE
			OBJECTS
			{
			criticalAl_1
			}
			STATUS   current
			DESCRIPTION "Critical alarms"
			::= { traps1 3 }

			fansAlTrap_1  NOTIFICATION-TYPE
			OBJECTS
			{
			fansAl_1
			}
			STATUS   current
			DESCRIPTION "Fans alarms"
			::= { traps1 4 }

			compAlTrap_1  NOTIFICATION-TYPE
			OBJECTS
			{
			compAl_1
			}
			STATUS   current
			DESCRIPTION "Compressors alarms"
			::= { traps1 5 }

			temperatureAlTrap_1  NOTIFICATION-TYPE
			OBJECTS
			{
			temperatureAl_1
			}
			STATUS   current
			DESCRIPTION "Temperature alarms"
			::= { traps1 6 }

			humidityAlTrap_1  NOTIFICATION-TYPE
			OBJECTS
			{
			humidityAl_1
			}
			STATUS   current
			DESCRIPTION "Humidity alarms"
			::= { traps1 7 }

			damperAlTrap_1  NOTIFICATION-TYPE
			OBJECTS
			{
			damperAl_1
			}
			STATUS   current
			DESCRIPTION "Damper status alarm"
			::= { traps1 8 }

			fireSmokeAlTrap_1  NOTIFICATION-TYPE
			OBJECTS
			{
			fireSmokeAl_1
			}
			STATUS   current
			DESCRIPTION "Fire/Smoke alarm"
			::= { traps1 9 }

			genSeriousAlTrap_1  NOTIFICATION-TYPE
			OBJECTS
			{
			genSeriousAl_1
			}
			STATUS   current
			DESCRIPTION "Critical generic alarm"
			::= { traps1 10 }

			fansGenAlTrap_1  NOTIFICATION-TYPE
			OBJECTS
			{
			fansGenAl_1
			}
			STATUS   current
			DESCRIPTION "General supply fans alarm"
			::= { traps1 11 }

			f1GeneralAlTrap_1  NOTIFICATION-TYPE
			OBJECTS
			{
			f1GeneralAl_1
			}
			STATUS   current
			DESCRIPTION "Fan general alarm 1"
			::= { traps1 12 }

			f1PowerAlTrap_1  NOTIFICATION-TYPE
			OBJECTS
			{
			f1PowerAl_1
			}
			STATUS   current
			DESCRIPTION "Phase failure/undervolt.1"
			::= { traps1 13 }

			f1CommAlTrap_1  NOTIFICATION-TYPE
			OBJECTS
			{
			f1CommAl_1
			}
			STATUS   current
			DESCRIPTION "Communication 1"
			::= { traps1 14 }

			f1HighTempAlTrap_1  NOTIFICATION-TYPE
			OBJECTS
			{
			f1HighTempAl_1
			}
			STATUS   current
			DESCRIPTION "Power mod overheated 1"
			::= { traps1 15 }

			f1NetComAlTrap_1  NOTIFICATION-TYPE
			OBJECTS
			{
			f1NetComAl_1
			}
			STATUS   current
			DESCRIPTION "Master/Slave com. 1"
			::= { traps1 16 }

			f1InvRegAlTrap_1  NOTIFICATION-TYPE
			OBJECTS
			{
			f1InvRegAl_1
			}
			STATUS   current
			DESCRIPTION "Regulation module 1"
			::= { traps1 17 }

			f1HighMotTempAlTrap_1  NOTIFICATION-TYPE
			OBJECTS
			{
			f1HighMotTempAl_1
			}
			STATUS   current
			DESCRIPTION "Motor overheated 1"
			::= { traps1 18 }

			f1HallSensAlTrap_1  NOTIFICATION-TYPE
			OBJECTS
			{
			f1HallSensAl_1
			}
			STATUS   current
			DESCRIPTION "Hall sensor error 1"
			::= { traps1 19 }

			f1OverloadAlTrap_1  NOTIFICATION-TYPE
			OBJECTS
			{
			f1OverloadAl_1
			}
			STATUS   current
			DESCRIPTION "Locked motor 1"
			::= { traps1 20 }

			f1LowDCAlTrap_1  NOTIFICATION-TYPE
			OBJECTS
			{
			f1LowDCAl_1
			}
			STATUS   current
			DESCRIPTION "Low DC 1"
			::= { traps1 21 }

			f2GeneralAlTrap_1  NOTIFICATION-TYPE
			OBJECTS
			{
			f2GeneralAl_1
			}
			STATUS   current
			DESCRIPTION "Fan general alarm 2"
			::= { traps1 22 }

			f2PowerAlTrap_1  NOTIFICATION-TYPE
			OBJECTS
			{
			f2PowerAl_1
			}
			STATUS   current
			DESCRIPTION "Phase failure/undervolt.2"
			::= { traps1 23 }

			f2CommAlTrap_1  NOTIFICATION-TYPE
			OBJECTS
			{
			f2CommAl_1
			}
			STATUS   current
			DESCRIPTION "Communication 2"
			::= { traps1 24 }

			f2HighTempAlTrap_1  NOTIFICATION-TYPE
			OBJECTS
			{
			f2HighTempAl_1
			}
			STATUS   current
			DESCRIPTION "Power mod overheated 2"
			::= { traps1 25 }

			f2NetComAlTrap_1  NOTIFICATION-TYPE
			OBJECTS
			{
			f2NetComAl_1
			}
			STATUS   current
			DESCRIPTION "Master/Slave com. 2"
			::= { traps1 26 }

			f2InvRegAlTrap_1  NOTIFICATION-TYPE
			OBJECTS
			{
			f2InvRegAl_1
			}
			STATUS   current
			DESCRIPTION "Regulation module 2"
			::= { traps1 27 }

			f2HighMotTempAlTrap_1  NOTIFICATION-TYPE
			OBJECTS
			{
			f2HighMotTempAl_1
			}
			STATUS   current
			DESCRIPTION "Motor overheated 2"
			::= { traps1 28 }

			f2HallSensAlTrap_1  NOTIFICATION-TYPE
			OBJECTS
			{
			f2HallSensAl_1
			}
			STATUS   current
			DESCRIPTION "Hall sensor error 2"
			::= { traps1 29 }

			f2OverloadAlTrap_1  NOTIFICATION-TYPE
			OBJECTS
			{
			f2OverloadAl_1
			}
			STATUS   current
			DESCRIPTION "Locked motor 2"
			::= { traps1 30 }

			f2LowDCAlTrap_1  NOTIFICATION-TYPE
			OBJECTS
			{
			f2LowDCAl_1
			}
			STATUS   current
			DESCRIPTION "Low DC 2"
			::= { traps1 31 }

			f3GeneralAlTrap_1  NOTIFICATION-TYPE
			OBJECTS
			{
			f3GeneralAl_1
			}
			STATUS   current
			DESCRIPTION "Fan general alarm 3"
			::= { traps1 32 }

			f3PowerAlTrap_1  NOTIFICATION-TYPE
			OBJECTS
			{
			f3PowerAl_1
			}
			STATUS   current
			DESCRIPTION "Phase failure/undervolt.3"
			::= { traps1 33 }

			f3CommAlTrap_1  NOTIFICATION-TYPE
			OBJECTS
			{
			f3CommAl_1
			}
			STATUS   current
			DESCRIPTION "Communication 3"
			::= { traps1 34 }

			f3HighTempAlTrap_1  NOTIFICATION-TYPE
			OBJECTS
			{
			f3HighTempAl_1
			}
			STATUS   current
			DESCRIPTION "Power mod overheated 3"
			::= { traps1 35 }

			f3NetComAlTrap_1  NOTIFICATION-TYPE
			OBJECTS
			{
			f3NetComAl_1
			}
			STATUS   current
			DESCRIPTION "Master/Slave com. 3"
			::= { traps1 36 }

			f3InvRegAlTrap_1  NOTIFICATION-TYPE
			OBJECTS
			{
			f3InvRegAl_1
			}
			STATUS   current
			DESCRIPTION "Regulation module 3"
			::= { traps1 37 }

			f3HighMotTempAlTrap_1  NOTIFICATION-TYPE
			OBJECTS
			{
			f3HighMotTempAl_1
			}
			STATUS   current
			DESCRIPTION "Motor overheated 3"
			::= { traps1 38 }

			f3HallSensAlTrap_1  NOTIFICATION-TYPE
			OBJECTS
			{
			f3HallSensAl_1
			}
			STATUS   current
			DESCRIPTION "Hall sensor error 3"
			::= { traps1 39 }

			f3OverloadAlTrap_1  NOTIFICATION-TYPE
			OBJECTS
			{
			f3OverloadAl_1
			}
			STATUS   current
			DESCRIPTION "Locked motor 3"
			::= { traps1 40 }

			f3LowDCAlTrap_1  NOTIFICATION-TYPE
			OBJECTS
			{
			f3LowDCAl_1
			}
			STATUS   current
			DESCRIPTION "Low DC 3"
			::= { traps1 41 }

			f4GeneralAlTrap_1  NOTIFICATION-TYPE
			OBJECTS
			{
			f4GeneralAl_1
			}
			STATUS   current
			DESCRIPTION "Fan general alarm 4"
			::= { traps1 42 }

			f4PowerAlTrap_1  NOTIFICATION-TYPE
			OBJECTS
			{
			f4PowerAl_1
			}
			STATUS   current
			DESCRIPTION "Phase failure/undervolt.4"
			::= { traps1 43 }

			f4CommAlTrap_1  NOTIFICATION-TYPE
			OBJECTS
			{
			f4CommAl_1
			}
			STATUS   current
			DESCRIPTION "Communication 4"
			::= { traps1 44 }

			f4HighTempAlTrap_1  NOTIFICATION-TYPE
			OBJECTS
			{
			f4HighTempAl_1
			}
			STATUS   current
			DESCRIPTION "Power mod overheated 4"
			::= { traps1 45 }

			f4NetComAlTrap_1  NOTIFICATION-TYPE
			OBJECTS
			{
			f4NetComAl_1
			}
			STATUS   current
			DESCRIPTION "Master/Slave com. 4"
			::= { traps1 46 }

			f4InvRegAlTrap_1  NOTIFICATION-TYPE
			OBJECTS
			{
			f4InvRegAl_1
			}
			STATUS   current
			DESCRIPTION "Regulation module 4"
			::= { traps1 47 }

			f4HighMotTempAlTrap_1  NOTIFICATION-TYPE
			OBJECTS
			{
			f4HighMotTempAl_1
			}
			STATUS   current
			DESCRIPTION "Motor overheated 4"
			::= { traps1 48 }

			f4HallSensAlTrap_1  NOTIFICATION-TYPE
			OBJECTS
			{
			f4HallSensAl_1
			}
			STATUS   current
			DESCRIPTION "Hall sensor error 4"
			::= { traps1 49 }

			f4OverloadAlTrap_1  NOTIFICATION-TYPE
			OBJECTS
			{
			f4OverloadAl_1
			}
			STATUS   current
			DESCRIPTION "Locked motor 4"
			::= { traps1 50 }

			f4LowDCAlTrap_1  NOTIFICATION-TYPE
			OBJECTS
			{
			f4LowDCAl_1
			}
			STATUS   current
			DESCRIPTION "Low DC 4"
			::= { traps1 51 }

			f5GeneralAlTrap_1  NOTIFICATION-TYPE
			OBJECTS
			{
			f5GeneralAl_1
			}
			STATUS   current
			DESCRIPTION "Fan general alarm 5"
			::= { traps1 52 }

			f5PowerAlTrap_1  NOTIFICATION-TYPE
			OBJECTS
			{
			f5PowerAl_1
			}
			STATUS   current
			DESCRIPTION "Phase failure/undervolt.5"
			::= { traps1 53 }

			f5CommAlTrap_1  NOTIFICATION-TYPE
			OBJECTS
			{
			f5CommAl_1
			}
			STATUS   current
			DESCRIPTION "Communication 5"
			::= { traps1 54 }

			f5HighTempAlTrap_1  NOTIFICATION-TYPE
			OBJECTS
			{
			f5HighTempAl_1
			}
			STATUS   current
			DESCRIPTION "Power mod overheated 5"
			::= { traps1 55 }

			f5NetComAlTrap_1  NOTIFICATION-TYPE
			OBJECTS
			{
			f5NetComAl_1
			}
			STATUS   current
			DESCRIPTION "Master/Slave com. 5"
			::= { traps1 56 }

			f5InvRegAlTrap_1  NOTIFICATION-TYPE
			OBJECTS
			{
			f5InvRegAl_1
			}
			STATUS   current
			DESCRIPTION "Regulation module 5"
			::= { traps1 57 }

			f5HighMotTempAlTrap_1  NOTIFICATION-TYPE
			OBJECTS
			{
			f5HighMotTempAl_1
			}
			STATUS   current
			DESCRIPTION "Motor overheated 5"
			::= { traps1 58 }

			f5HallSensAlTrap_1  NOTIFICATION-TYPE
			OBJECTS
			{
			f5HallSensAl_1
			}
			STATUS   current
			DESCRIPTION "Hall sensor error 5"
			::= { traps1 59 }

			f5OverloadAlTrap_1  NOTIFICATION-TYPE
			OBJECTS
			{
			f5OverloadAl_1
			}
			STATUS   current
			DESCRIPTION "Locked motor 5"
			::= { traps1 60 }

			f5LowDCAlTrap_1  NOTIFICATION-TYPE
			OBJECTS
			{
			f5LowDCAl_1
			}
			STATUS   current
			DESCRIPTION "Low DC 5"
			::= { traps1 61 }

			f6GeneralAlTrap_1  NOTIFICATION-TYPE
			OBJECTS
			{
			f6GeneralAl_1
			}
			STATUS   current
			DESCRIPTION "Fan general alarm 6"
			::= { traps1 62 }

			f6PowerAlTrap_1  NOTIFICATION-TYPE
			OBJECTS
			{
			f6PowerAl_1
			}
			STATUS   current
			DESCRIPTION "Phase failure/undervolt.6"
			::= { traps1 63 }

			f6CommAlTrap_1  NOTIFICATION-TYPE
			OBJECTS
			{
			f6CommAl_1
			}
			STATUS   current
			DESCRIPTION "Communication 6"
			::= { traps1 64 }

			f6HighTempAlTrap_1  NOTIFICATION-TYPE
			OBJECTS
			{
			f6HighTempAl_1
			}
			STATUS   current
			DESCRIPTION "Power mod overheated 6"
			::= { traps1 65 }

			f6NetComAlTrap_1  NOTIFICATION-TYPE
			OBJECTS
			{
			f6NetComAl_1
			}
			STATUS   current
			DESCRIPTION "Master/Slave com. 6"
			::= { traps1 66 }

			f6InvRegAlTrap_1  NOTIFICATION-TYPE
			OBJECTS
			{
			f6InvRegAl_1
			}
			STATUS   current
			DESCRIPTION "Regulation module 6"
			::= { traps1 67 }

			f6HighMotTempAlTrap_1  NOTIFICATION-TYPE
			OBJECTS
			{
			f6HighMotTempAl_1
			}
			STATUS   current
			DESCRIPTION "Motor overheated 6"
			::= { traps1 68 }

			f6HallSensAlTrap_1  NOTIFICATION-TYPE
			OBJECTS
			{
			f6HallSensAl_1
			}
			STATUS   current
			DESCRIPTION "Hall sensor error 6"
			::= { traps1 69 }

			f6OverloadAlTrap_1  NOTIFICATION-TYPE
			OBJECTS
			{
			f6OverloadAl_1
			}
			STATUS   current
			DESCRIPTION "Locked motor 6"
			::= { traps1 70 }

			f6LowDCAlTrap_1  NOTIFICATION-TYPE
			OBJECTS
			{
			f6LowDCAl_1
			}
			STATUS   current
			DESCRIPTION "Low DC 6"
			::= { traps1 71 }

			f7GeneralAlTrap_1  NOTIFICATION-TYPE
			OBJECTS
			{
			f7GeneralAl_1
			}
			STATUS   current
			DESCRIPTION "Fan general alarm 7"
			::= { traps1 72 }

			f7PowerAlTrap_1  NOTIFICATION-TYPE
			OBJECTS
			{
			f7PowerAl_1
			}
			STATUS   current
			DESCRIPTION "Phase failure/undervolt.7"
			::= { traps1 73 }

			f7CommAlTrap_1  NOTIFICATION-TYPE
			OBJECTS
			{
			f7CommAl_1
			}
			STATUS   current
			DESCRIPTION "Communication 7"
			::= { traps1 74 }

			f7HighTempAlTrap_1  NOTIFICATION-TYPE
			OBJECTS
			{
			f7HighTempAl_1
			}
			STATUS   current
			DESCRIPTION "Power mod overheated 7"
			::= { traps1 75 }

			f7NetComAlTrap_1  NOTIFICATION-TYPE
			OBJECTS
			{
			f7NetComAl_1
			}
			STATUS   current
			DESCRIPTION "Master/Slave com. 7"
			::= { traps1 76 }

			f7InvRegAlTrap_1  NOTIFICATION-TYPE
			OBJECTS
			{
			f7InvRegAl_1
			}
			STATUS   current
			DESCRIPTION "Regulation module 7"
			::= { traps1 77 }

			f7HighMotTempAlTrap_1  NOTIFICATION-TYPE
			OBJECTS
			{
			f7HighMotTempAl_1
			}
			STATUS   current
			DESCRIPTION "Motor overheated 7"
			::= { traps1 78 }

			f7HallSensAlTrap_1  NOTIFICATION-TYPE
			OBJECTS
			{
			f7HallSensAl_1
			}
			STATUS   current
			DESCRIPTION "Hall sensor error 7"
			::= { traps1 79 }

			f7OverloadAlTrap_1  NOTIFICATION-TYPE
			OBJECTS
			{
			f7OverloadAl_1
			}
			STATUS   current
			DESCRIPTION "Locked motor 7"
			::= { traps1 80 }

			f7LowDCAlTrap_1  NOTIFICATION-TYPE
			OBJECTS
			{
			f7LowDCAl_1
			}
			STATUS   current
			DESCRIPTION "Low DC 7"
			::= { traps1 81 }

			f8GeneralAlTrap_1  NOTIFICATION-TYPE
			OBJECTS
			{
			f8GeneralAl_1
			}
			STATUS   current
			DESCRIPTION "Fan general alarm 8"
			::= { traps1 82 }

			f8PowerAlTrap_1  NOTIFICATION-TYPE
			OBJECTS
			{
			f8PowerAl_1
			}
			STATUS   current
			DESCRIPTION "Phase failure/undervolt.8"
			::= { traps1 83 }

			f8CommAlTrap_1  NOTIFICATION-TYPE
			OBJECTS
			{
			f8CommAl_1
			}
			STATUS   current
			DESCRIPTION "Communication 8"
			::= { traps1 84 }

			f8HighTempAlTrap_1  NOTIFICATION-TYPE
			OBJECTS
			{
			f8HighTempAl_1
			}
			STATUS   current
			DESCRIPTION "Power mod overheated 8"
			::= { traps1 85 }

			f8NetComAlTrap_1  NOTIFICATION-TYPE
			OBJECTS
			{
			f8NetComAl_1
			}
			STATUS   current
			DESCRIPTION "Master/Slave com. 8"
			::= { traps1 86 }

			f8InvRegAlTrap_1  NOTIFICATION-TYPE
			OBJECTS
			{
			f8InvRegAl_1
			}
			STATUS   current
			DESCRIPTION "Regulation module 8"
			::= { traps1 87 }

			f8HighMotTempAlTrap_1  NOTIFICATION-TYPE
			OBJECTS
			{
			f8HighMotTempAl_1
			}
			STATUS   current
			DESCRIPTION "Motor overheated 8"
			::= { traps1 88 }

			f8HallSensAlTrap_1  NOTIFICATION-TYPE
			OBJECTS
			{
			f8HallSensAl_1
			}
			STATUS   current
			DESCRIPTION "Hall sensor error 8"
			::= { traps1 89 }

			f8OverloadAlTrap_1  NOTIFICATION-TYPE
			OBJECTS
			{
			f8OverloadAl_1
			}
			STATUS   current
			DESCRIPTION "Locked motor 8"
			::= { traps1 90 }

			f8LowDCAlTrap_1  NOTIFICATION-TYPE
			OBJECTS
			{
			f8LowDCAl_1
			}
			STATUS   current
			DESCRIPTION "Low DC 8"
			::= { traps1 91 }

			f9InverterAlTrap_1  NOTIFICATION-TYPE
			OBJECTS
			{
			f9InverterAl_1
			}
			STATUS   current
			DESCRIPTION "Fan general alarm 9"
			::= { traps1 92 }

			f9PowerAlTrap_1  NOTIFICATION-TYPE
			OBJECTS
			{
			f9PowerAl_1
			}
			STATUS   current
			DESCRIPTION "Phase failure/undervolt.9"
			::= { traps1 93 }

			f9CommAlTrap_1  NOTIFICATION-TYPE
			OBJECTS
			{
			f9CommAl_1
			}
			STATUS   current
			DESCRIPTION "Communication 9"
			::= { traps1 94 }

			f9HighTempAlTrap_1  NOTIFICATION-TYPE
			OBJECTS
			{
			f9HighTempAl_1
			}
			STATUS   current
			DESCRIPTION "Power mod overheated 9"
			::= { traps1 95 }

			f9NetComAlTrap_1  NOTIFICATION-TYPE
			OBJECTS
			{
			f9NetComAl_1
			}
			STATUS   current
			DESCRIPTION "Master/Slave com. 9"
			::= { traps1 96 }

			f9InvRegAlTrap_1  NOTIFICATION-TYPE
			OBJECTS
			{
			f9InvRegAl_1
			}
			STATUS   current
			DESCRIPTION "Regulation module 9"
			::= { traps1 97 }

			f9HighMotTempAlTrap_1  NOTIFICATION-TYPE
			OBJECTS
			{
			f9HighMotTempAl_1
			}
			STATUS   current
			DESCRIPTION "Motor overheated 9"
			::= { traps1 98 }

			f9HallSensAlTrap_1  NOTIFICATION-TYPE
			OBJECTS
			{
			f9HallSensAl_1
			}
			STATUS   current
			DESCRIPTION "Hall sensor error 9"
			::= { traps1 99 }

			f9OverloadAlTrap_1  NOTIFICATION-TYPE
			OBJECTS
			{
			f9OverloadAl_1
			}
			STATUS   current
			DESCRIPTION "Locked motor 9"
			::= { traps1 100 }

			f9LowDCAlTrap_1  NOTIFICATION-TYPE
			OBJECTS
			{
			f9LowDCAl_1
			}
			STATUS   current
			DESCRIPTION "Low DC 9"
			::= { traps1 101 }

			f10GeneralAlTrap_1  NOTIFICATION-TYPE
			OBJECTS
			{
			f10GeneralAl_1
			}
			STATUS   current
			DESCRIPTION "Fan general alarm 10"
			::= { traps1 102 }

			f10PowerAlTrap_1  NOTIFICATION-TYPE
			OBJECTS
			{
			f10PowerAl_1
			}
			STATUS   current
			DESCRIPTION "Phase failure/undervolt.10"
			::= { traps1 103 }

			f10CommAlTrap_1  NOTIFICATION-TYPE
			OBJECTS
			{
			f10CommAl_1
			}
			STATUS   current
			DESCRIPTION "Communication 10"
			::= { traps1 104 }

			f10HighTempAlTrap_1  NOTIFICATION-TYPE
			OBJECTS
			{
			f10HighTempAl_1
			}
			STATUS   current
			DESCRIPTION "Power mod overheated 10"
			::= { traps1 105 }

			f10NetComAlTrap_1  NOTIFICATION-TYPE
			OBJECTS
			{
			f10NetComAl_1
			}
			STATUS   current
			DESCRIPTION "Master/Slave com. 10"
			::= { traps1 106 }

			f10InvRegAlTrap_1  NOTIFICATION-TYPE
			OBJECTS
			{
			f10InvRegAl_1
			}
			STATUS   current
			DESCRIPTION "Regulation module 10"
			::= { traps1 107 }

			f10HighMotTAlTrap_1  NOTIFICATION-TYPE
			OBJECTS
			{
			f10HighMotTAl_1
			}
			STATUS   current
			DESCRIPTION "Motor overheated 10"
			::= { traps1 108 }

			f10HallSensAlTrap_1  NOTIFICATION-TYPE
			OBJECTS
			{
			f10HallSensAl_1
			}
			STATUS   current
			DESCRIPTION "Hall sensor error 10"
			::= { traps1 109 }

			f10OverloadAlTrap_1  NOTIFICATION-TYPE
			OBJECTS
			{
			f10OverloadAl_1
			}
			STATUS   current
			DESCRIPTION "Locked motor 10"
			::= { traps1 110 }

			f10LowDCAlTrap_1  NOTIFICATION-TYPE
			OBJECTS
			{
			f10LowDCAl_1
			}
			STATUS   current
			DESCRIPTION "Low DC 10"
			::= { traps1 111 }

			retTempProbAlTrap_1  NOTIFICATION-TYPE
			OBJECTS
			{
			retTempProbAl_1
			}
			STATUS   current
			DESCRIPTION "Return temperature probe"
			::= { traps1 112 }

			supTempProbAlTrap_1  NOTIFICATION-TYPE
			OBJECTS
			{
			supTempProbAl_1
			}
			STATUS   current
			DESCRIPTION "Supply temperature probe"
			::= { traps1 113 }

			retHumProbAlTrap_1  NOTIFICATION-TYPE
			OBJECTS
			{
			retHumProbAl_1
			}
			STATUS   current
			DESCRIPTION "Return humidity probe"
			::= { traps1 114 }

			supHumProbAlTrap_1  NOTIFICATION-TYPE
			OBJECTS
			{
			supHumProbAl_1
			}
			STATUS   current
			DESCRIPTION "Supply humidity probe"
			::= { traps1 115 }

			airPrSensorAlTrap_1  NOTIFICATION-TYPE
			OBJECTS
			{
			airPrSensorAl_1
			}
			STATUS   current
			DESCRIPTION "Air diff.pressure probe"
			::= { traps1 116 }

			watIN1ProbAlTrap_1  NOTIFICATION-TYPE
			OBJECTS
			{
			watIN1ProbAl_1
			}
			STATUS   current
			DESCRIPTION "Water temp. IN1 probe"
			::= { traps1 117 }

			watOUT1ProbAlTrap_1  NOTIFICATION-TYPE
			OBJECTS
			{
			watOUT1ProbAl_1
			}
			STATUS   current
			DESCRIPTION "Water temp. OUT1 probe"
			::= { traps1 118 }

			watIN2ProbAlTrap_1  NOTIFICATION-TYPE
			OBJECTS
			{
			watIN2ProbAl_1
			}
			STATUS   current
			DESCRIPTION "Water temp. IN2 probe"
			::= { traps1 119 }

			watOUT2ProbAlTrap_1  NOTIFICATION-TYPE
			OBJECTS
			{
			watOUT2ProbAl_1
			}
			STATUS   current
			DESCRIPTION "Water temp. OUT2 probe"
			::= { traps1 120 }

			watFlw1ProbAlTrap_1  NOTIFICATION-TYPE
			OBJECTS
			{
			watFlw1ProbAl_1
			}
			STATUS   current
			DESCRIPTION "Water flow1/T.liquid1 pr."
			::= { traps1 121 }

			watFlw2ProbAlTrap_1  NOTIFICATION-TYPE
			OBJECTS
			{
			watFlw2ProbAl_1
			}
			STATUS   current
			DESCRIPTION "Water flow2/T.liquid2 pr."
			::= { traps1 122 }

			dFPSGenAlTrap_1  NOTIFICATION-TYPE
			OBJECTS
			{
			dFPSGenAl_1
			}
			STATUS   current
			DESCRIPTION "Filter diff.press. probe"
			::= { traps1 123 }

			dFPSBrokenAlTrap_1  NOTIFICATION-TYPE
			OBJECTS
			{
			dFPSBrokenAl_1
			}
			STATUS   current
			DESCRIPTION "Breakdown alarm"
			::= { traps1 124 }

			dFPSCablingAlTrap_1  NOTIFICATION-TYPE
			OBJECTS
			{
			dFPSCablingAl_1
			}
			STATUS   current
			DESCRIPTION "Wiring alarm"
			::= { traps1 125 }

			dFPSRangeAlTrap_1  NOTIFICATION-TYPE
			OBJECTS
			{
			dFPSRangeAl_1
			}
			STATUS   current
			DESCRIPTION "Pressure range alarm"
			::= { traps1 126 }

			dFPSADCAlTrap_1  NOTIFICATION-TYPE
			OBJECTS
			{
			dFPSADCAl_1
			}
			STATUS   current
			DESCRIPTION "ADC overload alarm"
			::= { traps1 127 }

			dFPSSettingAlTrap_1  NOTIFICATION-TYPE
			OBJECTS
			{
			dFPSSettingAl_1
			}
			STATUS   current
			DESCRIPTION "Calibration alarm"
			::= { traps1 128 }

			dFPSDCOAlTrap_1  NOTIFICATION-TYPE
			OBJECTS
			{
			dFPSDCOAl_1
			}
			STATUS   current
			DESCRIPTION "DCO alarm"
			::= { traps1 129 }

			dFPSWatchdogAlTrap_1  NOTIFICATION-TYPE
			OBJECTS
			{
			dFPSWatchdogAl_1
			}
			STATUS   current
			DESCRIPTION "Watchdog alarm"
			::= { traps1 130 }

			dFPSCommAlTrap_1  NOTIFICATION-TYPE
			OBJECTS
			{
			dFPSCommAl_1
			}
			STATUS   current
			DESCRIPTION "Communication alarm"
			::= { traps1 131 }

			invCompGenAlTrap_1  NOTIFICATION-TYPE
			OBJECTS
			{
			invCompGenAl_1
			}
			STATUS   current
			DESCRIPTION "DC inverter general alarm"
			::= { traps1 132 }

			invCompCommAlTrap_1  NOTIFICATION-TYPE
			OBJECTS
			{
			invCompCommAl_1
			}
			STATUS   current
			DESCRIPTION "Inverter communication"
			::= { traps1 133 }

			invCompAlCode1Trap_1  NOTIFICATION-TYPE
			OBJECTS
			{
			invCompAlCode1_1
			}
			STATUS   current
			DESCRIPTION "DC Inverter alarm code 1"
			::= { traps1 134 }

			invCompAlCode2Trap_1  NOTIFICATION-TYPE
			OBJECTS
			{
			invCompAlCode2_1
			}
			STATUS   current
			DESCRIPTION "DC Inverter alarm code 2"
			::= { traps1 135 }

			invCompAlCode3Trap_1  NOTIFICATION-TYPE
			OBJECTS
			{
			invCompAlCode3_1
			}
			STATUS   current
			DESCRIPTION "DC Inverter alarm code 3"
			::= { traps1 136 }

			invCompAlCode4Trap_1  NOTIFICATION-TYPE
			OBJECTS
			{
			invCompAlCode4_1
			}
			STATUS   current
			DESCRIPTION "DC Inverter alarm code 4"
			::= { traps1 137 }

			invCompAlCode5Trap_1  NOTIFICATION-TYPE
			OBJECTS
			{
			invCompAlCode5_1
			}
			STATUS   current
			DESCRIPTION "DC Inverter alarm code 5"
			::= { traps1 138 }

			c1ThermAlTrap_1  NOTIFICATION-TYPE
			OBJECTS
			{
			c1ThermAl_1
			}
			STATUS   current
			DESCRIPTION "C1 Thermal alarm"
			::= { traps1 139 }

			c1HighPresAlTrap_1  NOTIFICATION-TYPE
			OBJECTS
			{
			c1HighPresAl_1
			}
			STATUS   current
			DESCRIPTION "C1 High pressure alarm"
			::= { traps1 140 }

			c1LowPresAlTrap_1  NOTIFICATION-TYPE
			OBJECTS
			{
			c1LowPresAl_1
			}
			STATUS   current
			DESCRIPTION "C1 Low pressure alarm"
			::= { traps1 141 }

			c1HighDischAlTrap_1  NOTIFICATION-TYPE
			OBJECTS
			{
			c1HighDischAl_1
			}
			STATUS   current
			DESCRIPTION "C1 High discharge alarm"
			::= { traps1 142 }

			c1LCompRatAlTrap_1  NOTIFICATION-TYPE
			OBJECTS
			{
			c1LCompRatAl_1
			}
			STATUS   current
			DESCRIPTION "C1 low compresion alarm"
			::= { traps1 143 }

			condenser1AlTrap_1  NOTIFICATION-TYPE
			OBJECTS
			{
			condenser1Al_1
			}
			STATUS   current
			DESCRIPTION "Condenser 1 general alarm"
			::= { traps1 144 }

			c1WatFlowAlTrap_1  NOTIFICATION-TYPE
			OBJECTS
			{
			c1WatFlowAl_1
			}
			STATUS   current
			DESCRIPTION "Condenser 1 flow alarm"
			::= { traps1 145 }

			eEV1GenAlTrap_1  NOTIFICATION-TYPE
			OBJECTS
			{
			eEV1GenAl_1
			}
			STATUS   current
			DESCRIPTION "EEV1 general alarm"
			::= { traps1 146 }

			eEV1CommAlTrap_1  NOTIFICATION-TYPE
			OBJECTS
			{
			eEV1CommAl_1
			}
			STATUS   current
			DESCRIPTION "EEV1 communication alarm"
			::= { traps1 147 }

			eEV1SuctProbAlTrap_1  NOTIFICATION-TYPE
			OBJECTS
			{
			eEV1SuctProbAl_1
			}
			STATUS   current
			DESCRIPTION "EEV1 suction temp. probe"
			::= { traps1 148 }

			eEV1EvapProbAlTrap_1  NOTIFICATION-TYPE
			OBJECTS
			{
			eEV1EvapProbAl_1
			}
			STATUS   current
			DESCRIPTION "EEV1 evap. temp. probe"
			::= { traps1 149 }

			eEV1CondProbAlTrap_1  NOTIFICATION-TYPE
			OBJECTS
			{
			eEV1CondProbAl_1
			}
			STATUS   current
			DESCRIPTION "EEV1 condens. temp. probe"
			::= { traps1 150 }

			eEV1DischProbAlTrap_1  NOTIFICATION-TYPE
			OBJECTS
			{
			eEV1DischProbAl_1
			}
			STATUS   current
			DESCRIPTION "EEV1 disch. temp. probe"
			::= { traps1 151 }

			c2ThermAlTrap_1  NOTIFICATION-TYPE
			OBJECTS
			{
			c2ThermAl_1
			}
			STATUS   current
			DESCRIPTION "C2 Thermal alarm"
			::= { traps1 152 }

			c2HighPresAlTrap_1  NOTIFICATION-TYPE
			OBJECTS
			{
			c2HighPresAl_1
			}
			STATUS   current
			DESCRIPTION "C2 High pressure alarm"
			::= { traps1 153 }

			c2LowPresAlTrap_1  NOTIFICATION-TYPE
			OBJECTS
			{
			c2LowPresAl_1
			}
			STATUS   current
			DESCRIPTION "C2 Low pressure alarm"
			::= { traps1 154 }

			c2HighDischAlTrap_1  NOTIFICATION-TYPE
			OBJECTS
			{
			c2HighDischAl_1
			}
			STATUS   current
			DESCRIPTION "C2 High discharge alarm"
			::= { traps1 155 }

			c2LCompRatAlTrap_1  NOTIFICATION-TYPE
			OBJECTS
			{
			c2LCompRatAl_1
			}
			STATUS   current
			DESCRIPTION "C2 low compresion alarm"
			::= { traps1 156 }

			condenser2AlTrap_1  NOTIFICATION-TYPE
			OBJECTS
			{
			condenser2Al_1
			}
			STATUS   current
			DESCRIPTION "Condenser 2 general alarm"
			::= { traps1 157 }

			c2WatFlowAlTrap_1  NOTIFICATION-TYPE
			OBJECTS
			{
			c2WatFlowAl_1
			}
			STATUS   current
			DESCRIPTION "Condenser 2 flow alarm"
			::= { traps1 158 }

			eEV2GenAlTrap_1  NOTIFICATION-TYPE
			OBJECTS
			{
			eEV2GenAl_1
			}
			STATUS   current
			DESCRIPTION "EEV2 general alarm"
			::= { traps1 159 }

			eEV2CommAlTrap_1  NOTIFICATION-TYPE
			OBJECTS
			{
			eEV2CommAl_1
			}
			STATUS   current
			DESCRIPTION "EEV2 communication alarm"
			::= { traps1 160 }

			eEV2SuctProbAlTrap_1  NOTIFICATION-TYPE
			OBJECTS
			{
			eEV2SuctProbAl_1
			}
			STATUS   current
			DESCRIPTION "EEV2 suction temp. probe"
			::= { traps1 161 }

			eEV2EvapProbAlTrap_1  NOTIFICATION-TYPE
			OBJECTS
			{
			eEV2EvapProbAl_1
			}
			STATUS   current
			DESCRIPTION "EEV2 evap. temp. probe"
			::= { traps1 162 }

			eEV2CondProbAlTrap_1  NOTIFICATION-TYPE
			OBJECTS
			{
			eEV2CondProbAl_1
			}
			STATUS   current
			DESCRIPTION "EEV2 condens. temp. probe"
			::= { traps1 163 }

			eEV2DischProbAlTrap_1  NOTIFICATION-TYPE
			OBJECTS
			{
			eEV2DischProbAl_1
			}
			STATUS   current
			DESCRIPTION "EEV2 disch. temp. probe"
			::= { traps1 164 }

			intHumidGenAlTrap_1  NOTIFICATION-TYPE
			OBJECTS
			{
			intHumidGenAl_1
			}
			STATUS   current
			DESCRIPTION "Internal humidifier alarm"
			::= { traps1 165 }

			cPYCommAlTrap_1  NOTIFICATION-TYPE
			OBJECTS
			{
			cPYCommAl_1
			}
			STATUS   current
			DESCRIPTION "Communication alarm"
			::= { traps1 166 }

			cPYMemoryAlTrap_1  NOTIFICATION-TYPE
			OBJECTS
			{
			cPYMemoryAl_1
			}
			STATUS   current
			DESCRIPTION "Memory error alarm"
			::= { traps1 167 }

			cPYParameterAlTrap_1  NOTIFICATION-TYPE
			OBJECTS
			{
			cPYParameterAl_1
			}
			STATUS   current
			DESCRIPTION "Parameters error alarm"
			::= { traps1 168 }

			cPYHighCurrAlTrap_1  NOTIFICATION-TYPE
			OBJECTS
			{
			cPYHighCurrAl_1
			}
			STATUS   current
			DESCRIPTION "Electrodes high current"
			::= { traps1 169 }

			cPYLowSteamAlTrap_1  NOTIFICATION-TYPE
			OBJECTS
			{
			cPYLowSteamAl_1
			}
			STATUS   current
			DESCRIPTION "Low steam product. alarm"
			::= { traps1 170 }

			cPYDrainAlTrap_1  NOTIFICATION-TYPE
			OBJECTS
			{
			cPYDrainAl_1
			}
			STATUS   current
			DESCRIPTION "Drain loss alarm"
			::= { traps1 171 }

			cPYMaintAlTrap_1  NOTIFICATION-TYPE
			OBJECTS
			{
			cPYMaintAl_1
			}
			STATUS   current
			DESCRIPTION "Maintenance hours alarm"
			::= { traps1 172 }

			cPYNoWaterAlTrap_1  NOTIFICATION-TYPE
			OBJECTS
			{
			cPYNoWaterAl_1
			}
			STATUS   current
			DESCRIPTION "Water loss alarm"
			::= { traps1 173 }

			cPYCylMaintAlTrap_1  NOTIFICATION-TYPE
			OBJECTS
			{
			cPYCylMaintAl_1
			}
			STATUS   current
			DESCRIPTION "Cylinder mainten. alarm"
			::= { traps1 174 }

			cPYDirtyCylAlTrap_1  NOTIFICATION-TYPE
			OBJECTS
			{
			cPYDirtyCylAl_1
			}
			STATUS   current
			DESCRIPTION "Exaust cylinder alarm"
			::= { traps1 175 }

			cPYFoamAlTrap_1  NOTIFICATION-TYPE
			OBJECTS
			{
			cPYFoamAl_1
			}
			STATUS   current
			DESCRIPTION "Foam presence alarm"
			::= { traps1 176 }

			cPYLifeTimeAlTrap_1  NOTIFICATION-TYPE
			OBJECTS
			{
			cPYLifeTimeAl_1
			}
			STATUS   current
			DESCRIPTION "Life time expired alarm"
			::= { traps1 177 }

			cPYHighWatLevAlTrap_1  NOTIFICATION-TYPE
			OBJECTS
			{
			cPYHighWatLevAl_1
			}
			STATUS   current
			DESCRIPTION "High water level alarm"
			::= { traps1 178 }

			cPYHWatCondAlTrap_1  NOTIFICATION-TYPE
			OBJECTS
			{
			cPYHWatCondAl_1
			}
			STATUS   current
			DESCRIPTION "High conductivity alarm"
			::= { traps1 179 }

			cPYConnectionAlTrap_1  NOTIFICATION-TYPE
			OBJECTS
			{
			cPYConnectionAl_1
			}
			STATUS   current
			DESCRIPTION "Connection error alarm"
			::= { traps1 180 }

			watPresAlTrap_1  NOTIFICATION-TYPE
			OBJECTS
			{
			watPresAl_1
			}
			STATUS   current
			DESCRIPTION "Water presence alarm"
			::= { traps1 181 }

			drainPumpAlTrap_1  NOTIFICATION-TYPE
			OBJECTS
			{
			drainPumpAl_1
			}
			STATUS   current
			DESCRIPTION "Drain pump alarm"
			::= { traps1 182 }

			elHeatAlTrap_1  NOTIFICATION-TYPE
			OBJECTS
			{
			elHeatAl_1
			}
			STATUS   current
			DESCRIPTION "Electric heater alarm"
			::= { traps1 183 }

			filterAlTrap_1  NOTIFICATION-TYPE
			OBJECTS
			{
			filterAl_1
			}
			STATUS   current
			DESCRIPTION "Dirty filter alarm"
			::= { traps1 184 }

			dryCoolerAlTrap_1  NOTIFICATION-TYPE
			OBJECTS
			{
			dryCoolerAl_1
			}
			STATUS   current
			DESCRIPTION "Dry cooler alarm"
			::= { traps1 185 }

			extHumidAlTrap_1  NOTIFICATION-TYPE
			OBJECTS
			{
			extHumidAl_1
			}
			STATUS   current
			DESCRIPTION "External humidifier alarm"
			::= { traps1 186 }

			waterPumpAlTrap_1  NOTIFICATION-TYPE
			OBJECTS
			{
			waterPumpAl_1
			}
			STATUS   current
			DESCRIPTION "Water pump alarm"
			::= { traps1 187 }

			condUnitGenAlTrap_1  NOTIFICATION-TYPE
			OBJECTS
			{
			condUnitGenAl_1
			}
			STATUS   current
			DESCRIPTION "Motocondenser alarm"
			::= { traps1 188 }

			gasLeakAlTrap_1  NOTIFICATION-TYPE
			OBJECTS
			{
			gasLeakAl_1
			}
			STATUS   current
			DESCRIPTION "Refrigerant leak alarm"
			::= { traps1 189 }

			powerSupplyAlTrap_1  NOTIFICATION-TYPE
			OBJECTS
			{
			powerSupplyAl_1
			}
			STATUS   current
			DESCRIPTION "Power fault alarm"
			::= { traps1 190 }

			genericSoftAlTrap_1  NOTIFICATION-TYPE
			OBJECTS
			{
			genericSoftAl_1
			}
			STATUS   current
			DESCRIPTION "Not critical generic al."
			::= { traps1 191 }

			localNetworkAlTrap_1  NOTIFICATION-TYPE
			OBJECTS
			{
			localNetworkAl_1
			}
			STATUS   current
			DESCRIPTION "Local network alarm"
			::= { traps1 192 }

			regHighTempAlTrap_1  NOTIFICATION-TYPE
			OBJECTS
			{
			regHighTempAl_1
			}
			STATUS   current
			DESCRIPTION "High regulation T.alarm"
			::= { traps1 193 }

			regLowTempAlTrap_1  NOTIFICATION-TYPE
			OBJECTS
			{
			regLowTempAl_1
			}
			STATUS   current
			DESCRIPTION "Low regulation T.alarm"
			::= { traps1 194 }

			highLimTempAlTrap_1  NOTIFICATION-TYPE
			OBJECTS
			{
			highLimTempAl_1
			}
			STATUS   current
			DESCRIPTION "High limit temp. alarm"
			::= { traps1 195 }

			lowLimTempAlTrap_1  NOTIFICATION-TYPE
			OBJECTS
			{
			lowLimTempAl_1
			}
			STATUS   current
			DESCRIPTION "Low limit temp. alarm"
			::= { traps1 196 }

			retHighHumiAlTrap_1  NOTIFICATION-TYPE
			OBJECTS
			{
			retHighHumiAl_1
			}
			STATUS   current
			DESCRIPTION "High room humidity alarm"
			::= { traps1 197 }

			retLowHumiAlTrap_1  NOTIFICATION-TYPE
			OBJECTS
			{
			retLowHumiAl_1
			}
			STATUS   current
			DESCRIPTION "Low room humidity alarm"
			::= { traps1 198 }

			supHighHumiAlTrap_1  NOTIFICATION-TYPE
			OBJECTS
			{
			supHighHumiAl_1
			}
			STATUS   current
			DESCRIPTION "High supp.humidity alarm"
			::= { traps1 199 }

			supLowHumiAlTrap_1  NOTIFICATION-TYPE
			OBJECTS
			{
			supLowHumiAl_1
			}
			STATUS   current
			DESCRIPTION "Low supp.humidity alarm"
			::= { traps1 200 }

			probeMod1COMTrap_1  NOTIFICATION-TYPE
			OBJECTS
			{
			probeMod1COM_1
			}
			STATUS   current
			DESCRIPTION "Module 1 communication"
			::= { traps1 201 }

			probeMod1err1Trap_1  NOTIFICATION-TYPE
			OBJECTS
			{
			probeMod1err1_1
			}
			STATUS   current
			DESCRIPTION "Module 1 probe 1 alarm"
			::= { traps1 202 }

			probeMod1err2Trap_1  NOTIFICATION-TYPE
			OBJECTS
			{
			probeMod1err2_1
			}
			STATUS   current
			DESCRIPTION "Module 1 probe 2 alarm"
			::= { traps1 203 }

			probeMod1err3Trap_1  NOTIFICATION-TYPE
			OBJECTS
			{
			probeMod1err3_1
			}
			STATUS   current
			DESCRIPTION "Module 1 probe 3 alarm"
			::= { traps1 204 }

			probeMod1err4Trap_1  NOTIFICATION-TYPE
			OBJECTS
			{
			probeMod1err4_1
			}
			STATUS   current
			DESCRIPTION "Module 1 probe 4 alarm"
			::= { traps1 205 }

			probeMod1err5Trap_1  NOTIFICATION-TYPE
			OBJECTS
			{
			probeMod1err5_1
			}
			STATUS   current
			DESCRIPTION "Module 1 probe 5 alarm"
			::= { traps1 206 }

			probeMod1err6Trap_1  NOTIFICATION-TYPE
			OBJECTS
			{
			probeMod1err6_1
			}
			STATUS   current
			DESCRIPTION "Module 1 probe 6 alarm"
			::= { traps1 207 }

			probeMod2COMTrap_1  NOTIFICATION-TYPE
			OBJECTS
			{
			probeMod2COM_1
			}
			STATUS   current
			DESCRIPTION "Module 2 communication"
			::= { traps1 208 }

			probeMod2err1Trap_1  NOTIFICATION-TYPE
			OBJECTS
			{
			probeMod2err1_1
			}
			STATUS   current
			DESCRIPTION "Module 2 probe 1 alarm"
			::= { traps1 209 }

			probeMod2err2Trap_1  NOTIFICATION-TYPE
			OBJECTS
			{
			probeMod2err2_1
			}
			STATUS   current
			DESCRIPTION "Module 2 probe 2 alarm"
			::= { traps1 210 }

			probeMod2err3Trap_1  NOTIFICATION-TYPE
			OBJECTS
			{
			probeMod2err3_1
			}
			STATUS   current
			DESCRIPTION "Module 2 probe 3 alarm"
			::= { traps1 211 }

			probeMod2err4Trap_1  NOTIFICATION-TYPE
			OBJECTS
			{
			probeMod2err4_1
			}
			STATUS   current
			DESCRIPTION "Module 2 probe 4 alarm"
			::= { traps1 212 }

			probeMod2err5Trap_1  NOTIFICATION-TYPE
			OBJECTS
			{
			probeMod2err5_1
			}
			STATUS   current
			DESCRIPTION "Module 2 probe 5 alarm"
			::= { traps1 213 }

			probeMod2err6Trap_1  NOTIFICATION-TYPE
			OBJECTS
			{
			probeMod2err6_1
			}
			STATUS   current
			DESCRIPTION "Module 2 probe 6 alarm"
			::= { traps1 214 }

			probeMod3COMTrap_1  NOTIFICATION-TYPE
			OBJECTS
			{
			probeMod3COM_1
			}
			STATUS   current
			DESCRIPTION "Module 3 communication"
			::= { traps1 215 }

			probeMod3err1Trap_1  NOTIFICATION-TYPE
			OBJECTS
			{
			probeMod3err1_1
			}
			STATUS   current
			DESCRIPTION "Module 3 probe 1 alarm"
			::= { traps1 216 }

			probeMod3err2Trap_1  NOTIFICATION-TYPE
			OBJECTS
			{
			probeMod3err2_1
			}
			STATUS   current
			DESCRIPTION "Module 3 probe 2 alarm"
			::= { traps1 217 }

			probeMod3err3Trap_1  NOTIFICATION-TYPE
			OBJECTS
			{
			probeMod3err3_1
			}
			STATUS   current
			DESCRIPTION "Module 3 probe 3 alarm"
			::= { traps1 218 }

			probeMod3err4Trap_1  NOTIFICATION-TYPE
			OBJECTS
			{
			probeMod3err4_1
			}
			STATUS   current
			DESCRIPTION "Module 3 probe 4 alarm"
			::= { traps1 219 }

			probeMod3err5Trap_1  NOTIFICATION-TYPE
			OBJECTS
			{
			probeMod3err5_1
			}
			STATUS   current
			DESCRIPTION "Module 3 probe 5 alarm"
			::= { traps1 220 }

			probeMod3err6Trap_1  NOTIFICATION-TYPE
			OBJECTS
			{
			probeMod3err6_1
			}
			STATUS   current
			DESCRIPTION "Module 3 probe 6 alarm"
			::= { traps1 221 }

		binaryObjects1 OBJECT IDENTIFIER  ::= { node1 1 }

			damperStatusDI_1 OBJECT-TYPE
			SYNTAX INTEGER
			MAX-ACCESS read-only
			STATUS current
			DESCRIPTION "Motorised damper status"
			::= { binaryObjects1 1 }

			dirtyFilterDI_1 OBJECT-TYPE
			SYNTAX INTEGER
			MAX-ACCESS read-only
			STATUS current
			DESCRIPTION "Dirty filter alarm"
			::= { binaryObjects1 2 }

			remoteOffDI_1 OBJECT-TYPE
			SYNTAX INTEGER
			MAX-ACCESS read-only
			STATUS current
			DESCRIPTION "Remote OFF status"
			::= { binaryObjects1 3 }

			elHeaterAlarmDI_1 OBJECT-TYPE
			SYNTAX INTEGER
			MAX-ACCESS read-only
			STATUS current
			DESCRIPTION "Heater thermostat alarm"
			::= { binaryObjects1 4 }

			condPumpAlarmDI_1 OBJECT-TYPE
			SYNTAX INTEGER
			MAX-ACCESS read-only
			STATUS current
			DESCRIPTION "Condensate pump alarm"
			::= { binaryObjects1 5 }

			configurableDI1_1 OBJECT-TYPE
			SYNTAX INTEGER
			MAX-ACCESS read-only
			STATUS current
			DESCRIPTION "Configurable DI 1"
			::= { binaryObjects1 6 }

			configurableDI2_1 OBJECT-TYPE
			SYNTAX INTEGER
			MAX-ACCESS read-only
			STATUS current
			DESCRIPTION "Configurable DI 2"
			::= { binaryObjects1 7 }

			configurableDI3_1 OBJECT-TYPE
			SYNTAX INTEGER
			MAX-ACCESS read-only
			STATUS current
			DESCRIPTION "Configurable DI 3"
			::= { binaryObjects1 8 }

			configurableDI4_1 OBJECT-TYPE
			SYNTAX INTEGER
			MAX-ACCESS read-only
			STATUS current
			DESCRIPTION "Configurable DI 4"
			::= { binaryObjects1 9 }

			configurableDI5_1 OBJECT-TYPE
			SYNTAX INTEGER
			MAX-ACCESS read-only
			STATUS current
			DESCRIPTION "Configurable DI 5"
			::= { binaryObjects1 10 }

			c1ThermAlarmDI_1 OBJECT-TYPE
			SYNTAX INTEGER
			MAX-ACCESS read-only
			STATUS current
			DESCRIPTION "Comp1 thermal alarm"
			::= { binaryObjects1 11 }

			c1HPAlarmDI_1 OBJECT-TYPE
			SYNTAX INTEGER
			MAX-ACCESS read-only
			STATUS current
			DESCRIPTION "Comp1 high pressure alarm"
			::= { binaryObjects1 12 }

			c1LPAlarmDI_1 OBJECT-TYPE
			SYNTAX INTEGER
			MAX-ACCESS read-only
			STATUS current
			DESCRIPTION "Comp1 low pressure alarm"
			::= { binaryObjects1 13 }

			c2ThermAlarmDI_1 OBJECT-TYPE
			SYNTAX INTEGER
			MAX-ACCESS read-only
			STATUS current
			DESCRIPTION "Comp2 thermal alarm"
			::= { binaryObjects1 14 }

			c2HPAlarmDI_1 OBJECT-TYPE
			SYNTAX INTEGER
			MAX-ACCESS read-only
			STATUS current
			DESCRIPTION "Comp2 high pressure alarm"
			::= { binaryObjects1 15 }

			c2LPAlarmDI_1 OBJECT-TYPE
			SYNTAX INTEGER
			MAX-ACCESS read-only
			STATUS current
			DESCRIPTION "Comp2 low pressure alarm"
			::= { binaryObjects1 16 }

			fansDO_1 OBJECT-TYPE
			SYNTAX INTEGER
			MAX-ACCESS read-only
			STATUS current
			DESCRIPTION "Fan control"
			::= { binaryObjects1 17 }

			damperDO_1 OBJECT-TYPE
			SYNTAX INTEGER
			MAX-ACCESS read-only
			STATUS current
			DESCRIPTION "Motorised dampers control"
			::= { binaryObjects1 18 }

			configurableDO1_1 OBJECT-TYPE
			SYNTAX INTEGER
			MAX-ACCESS read-only
			STATUS current
			DESCRIPTION "Configurable DO 1"
			::= { binaryObjects1 19 }

			configurableDO2_1 OBJECT-TYPE
			SYNTAX INTEGER
			MAX-ACCESS read-only
			STATUS current
			DESCRIPTION "Configurable DO 2"
			::= { binaryObjects1 20 }

			configurableDO3_1 OBJECT-TYPE
			SYNTAX INTEGER
			MAX-ACCESS read-only
			STATUS current
			DESCRIPTION "Configurable DO 3"
			::= { binaryObjects1 21 }

			configurableDO4_1 OBJECT-TYPE
			SYNTAX INTEGER
			MAX-ACCESS read-only
			STATUS current
			DESCRIPTION "Configurable DO 4"
			::= { binaryObjects1 22 }

			configurableDO5_1 OBJECT-TYPE
			SYNTAX INTEGER
			MAX-ACCESS read-only
			STATUS current
			DESCRIPTION "Configurable DO 5"
			::= { binaryObjects1 23 }

			eHeaterStage1DO_1 OBJECT-TYPE
			SYNTAX INTEGER
			MAX-ACCESS read-only
			STATUS current
			DESCRIPTION "Electric heat stage 1"
			::= { binaryObjects1 24 }

			eHeaterStage2DO_1 OBJECT-TYPE
			SYNTAX INTEGER
			MAX-ACCESS read-only
			STATUS current
			DESCRIPTION "Electric heat stage 2"
			::= { binaryObjects1 25 }

			compressor1DO_1 OBJECT-TYPE
			SYNTAX INTEGER
			MAX-ACCESS read-only
			STATUS current
			DESCRIPTION "Compressor 1 control"
			::= { binaryObjects1 26 }

			compressor2DO_1 OBJECT-TYPE
			SYNTAX INTEGER
			MAX-ACCESS read-only
			STATUS current
			DESCRIPTION "Compressor 2 control"
			::= { binaryObjects1 27 }

			humPowerDO_1 OBJECT-TYPE
			SYNTAX INTEGER
			MAX-ACCESS read-only
			STATUS current
			DESCRIPTION "Humidifier control"
			::= { binaryObjects1 28 }

			humDrainValveDO_1 OBJECT-TYPE
			SYNTAX INTEGER
			MAX-ACCESS read-only
			STATUS current
			DESCRIPTION "Humidifier Discharge"
			::= { binaryObjects1 29 }

			humFillValveDO_1 OBJECT-TYPE
			SYNTAX INTEGER
			MAX-ACCESS read-only
			STATUS current
			DESCRIPTION "Humidifier Charging"
			::= { binaryObjects1 30 }

			humWaterLevel_1 OBJECT-TYPE
			SYNTAX INTEGER
			MAX-ACCESS read-only
			STATUS current
			DESCRIPTION "Humidifier high water"
			::= { binaryObjects1 31 }

			supervOFF_1 OBJECT-TYPE
			SYNTAX INTEGER
			MAX-ACCESS read-write
			STATUS current
			DESCRIPTION "ON/OFF from supervisor"
			::= { binaryObjects1 32 }

			enableHumid_1 OBJECT-TYPE
			SYNTAX INTEGER
			MAX-ACCESS read-write
			STATUS current
			DESCRIPTION "Humidification enabling"
			::= { binaryObjects1 33 }

			humManualDrain_1 OBJECT-TYPE
			SYNTAX INTEGER
			MAX-ACCESS read-write
			STATUS current
			DESCRIPTION "Manual draining"
			::= { binaryObjects1 34 }

			humCylWashing_1 OBJECT-TYPE
			SYNTAX INTEGER
			MAX-ACCESS read-write
			STATUS current
			DESCRIPTION "Cylinder washing"
			::= { binaryObjects1 35 }

			tSManExchange_1 OBJECT-TYPE
			SYNTAX INTEGER
			MAX-ACCESS read-write
			STATUS current
			DESCRIPTION "TS manual exchange"
			::= { binaryObjects1 36 }

			tSTempExchEnab_1 OBJECT-TYPE
			SYNTAX INTEGER
			MAX-ACCESS read-write
			STATUS current
			DESCRIPTION "Enable TS room temp. exc."
			::= { binaryObjects1 37 }

			damperAlRes_1 OBJECT-TYPE
			SYNTAX INTEGER
			MAX-ACCESS read-write
			STATUS current
			DESCRIPTION "Reset damper status AL"
			::= { binaryObjects1 38 }

			fireSmokeAlRes_1 OBJECT-TYPE
			SYNTAX INTEGER
			MAX-ACCESS read-write
			STATUS current
			DESCRIPTION "Reset smoke/fire AL"
			::= { binaryObjects1 39 }

			genSerAlRes_1 OBJECT-TYPE
			SYNTAX INTEGER
			MAX-ACCESS read-write
			STATUS current
			DESCRIPTION "Reset generic serious AL"
			::= { binaryObjects1 40 }

			fansGenAlRes_1 OBJECT-TYPE
			SYNTAX INTEGER
			MAX-ACCESS read-write
			STATUS current
			DESCRIPTION "Reset supply fan AL"
			::= { binaryObjects1 41 }

			f1InvAlRes_1 OBJECT-TYPE
			SYNTAX INTEGER
			MAX-ACCESS read-write
			STATUS current
			DESCRIPTION "Reset fan 1 alarm"
			::= { binaryObjects1 42 }

			f2InvAlRes_1 OBJECT-TYPE
			SYNTAX INTEGER
			MAX-ACCESS read-write
			STATUS current
			DESCRIPTION "Reset fan 2 alarm"
			::= { binaryObjects1 43 }

			f3InvAlRes_1 OBJECT-TYPE
			SYNTAX INTEGER
			MAX-ACCESS read-write
			STATUS current
			DESCRIPTION "Reset fan 3 alarm"
			::= { binaryObjects1 44 }

			f4InvAlRes_1 OBJECT-TYPE
			SYNTAX INTEGER
			MAX-ACCESS read-write
			STATUS current
			DESCRIPTION "Reset fan 4 alarm"
			::= { binaryObjects1 45 }

			f5InvAlRes_1 OBJECT-TYPE
			SYNTAX INTEGER
			MAX-ACCESS read-write
			STATUS current
			DESCRIPTION "Reset fan 5 alarm"
			::= { binaryObjects1 46 }

			f6InvAlRes_1 OBJECT-TYPE
			SYNTAX INTEGER
			MAX-ACCESS read-write
			STATUS current
			DESCRIPTION "Reset fan 6 alarm"
			::= { binaryObjects1 47 }

			f7InvAlRes_1 OBJECT-TYPE
			SYNTAX INTEGER
			MAX-ACCESS read-write
			STATUS current
			DESCRIPTION "Reset fan 7 alarm"
			::= { binaryObjects1 48 }

			f8InvAlRes_1 OBJECT-TYPE
			SYNTAX INTEGER
			MAX-ACCESS read-write
			STATUS current
			DESCRIPTION "Reset fan 8 alarm"
			::= { binaryObjects1 49 }

			f9InvAlRes_1 OBJECT-TYPE
			SYNTAX INTEGER
			MAX-ACCESS read-write
			STATUS current
			DESCRIPTION "Reset fan 9 alarm"
			::= { binaryObjects1 50 }

			f10InvAlRes_1 OBJECT-TYPE
			SYNTAX INTEGER
			MAX-ACCESS read-write
			STATUS current
			DESCRIPTION "Reset fan 10 alarm"
			::= { binaryObjects1 51 }

			invCompAlRes_1 OBJECT-TYPE
			SYNTAX INTEGER
			MAX-ACCESS read-write
			STATUS current
			DESCRIPTION "Reset inverter alarm"
			::= { binaryObjects1 52 }

			c1ThermAlRes_1 OBJECT-TYPE
			SYNTAX INTEGER
			MAX-ACCESS read-write
			STATUS current
			DESCRIPTION "Reset C1 thermal AL"
			::= { binaryObjects1 53 }

			c1HighPresAlRes_1 OBJECT-TYPE
			SYNTAX INTEGER
			MAX-ACCESS read-write
			STATUS current
			DESCRIPTION "Reset C1 high pressure AL"
			::= { binaryObjects1 54 }

			c1LowPresAlRes_1 OBJECT-TYPE
			SYNTAX INTEGER
			MAX-ACCESS read-write
			STATUS current
			DESCRIPTION "Reset C1 low pressure AL"
			::= { binaryObjects1 55 }

			c1HighDisTAlRes_1 OBJECT-TYPE
			SYNTAX INTEGER
			MAX-ACCESS read-write
			STATUS current
			DESCRIPTION "Reset C1 high disch. AL"
			::= { binaryObjects1 56 }

			c1LCompRatAlRes_1 OBJECT-TYPE
			SYNTAX INTEGER
			MAX-ACCESS read-write
			STATUS current
			DESCRIPTION "Reset C1 low compres. AL"
			::= { binaryObjects1 57 }

			condenser1AlRes_1 OBJECT-TYPE
			SYNTAX INTEGER
			MAX-ACCESS read-write
			STATUS current
			DESCRIPTION "Reset condenser 1 AL"
			::= { binaryObjects1 58 }

			eEV1AlRes_1 OBJECT-TYPE
			SYNTAX INTEGER
			MAX-ACCESS read-write
			STATUS current
			DESCRIPTION "Reset EEV1 alarm"
			::= { binaryObjects1 59 }

			c2ThermAlRes_1 OBJECT-TYPE
			SYNTAX INTEGER
			MAX-ACCESS read-write
			STATUS current
			DESCRIPTION "Reset C2 thermal AL"
			::= { binaryObjects1 60 }

			c2HighPresAlRes_1 OBJECT-TYPE
			SYNTAX INTEGER
			MAX-ACCESS read-write
			STATUS current
			DESCRIPTION "Reset C2 high pressure AL"
			::= { binaryObjects1 61 }

			c2LowPresAlRes_1 OBJECT-TYPE
			SYNTAX INTEGER
			MAX-ACCESS read-write
			STATUS current
			DESCRIPTION "Reset C2 low pressure AL"
			::= { binaryObjects1 62 }

			c2HighDisTAlRes_1 OBJECT-TYPE
			SYNTAX INTEGER
			MAX-ACCESS read-write
			STATUS current
			DESCRIPTION "Reset C2 high disch. AL"
			::= { binaryObjects1 63 }

			c2LComRatAlRes_1 OBJECT-TYPE
			SYNTAX INTEGER
			MAX-ACCESS read-write
			STATUS current
			DESCRIPTION "Reset C2 low compres. AL"
			::= { binaryObjects1 64 }

			condenser2AlRes_1 OBJECT-TYPE
			SYNTAX INTEGER
			MAX-ACCESS read-write
			STATUS current
			DESCRIPTION "Reset condenser 2 AL"
			::= { binaryObjects1 65 }

			eEV2AlRes_1 OBJECT-TYPE
			SYNTAX INTEGER
			MAX-ACCESS read-write
			STATUS current
			DESCRIPTION "Reset EEV2 alarm"
			::= { binaryObjects1 66 }

			intHumidifAlRes_1 OBJECT-TYPE
			SYNTAX INTEGER
			MAX-ACCESS read-write
			STATUS current
			DESCRIPTION "Reset int. humidifier AL"
			::= { binaryObjects1 67 }

			watPresAlRes_1 OBJECT-TYPE
			SYNTAX INTEGER
			MAX-ACCESS read-write
			STATUS current
			DESCRIPTION "Reset water presence AL"
			::= { binaryObjects1 68 }

			drainPumpAlRes_1 OBJECT-TYPE
			SYNTAX INTEGER
			MAX-ACCESS read-write
			STATUS current
			DESCRIPTION "Reset drain pump AL"
			::= { binaryObjects1 69 }

			elHeatAlRes_1 OBJECT-TYPE
			SYNTAX INTEGER
			MAX-ACCESS read-write
			STATUS current
			DESCRIPTION "Reset electric heater AL"
			::= { binaryObjects1 70 }

			filterAlRes_1 OBJECT-TYPE
			SYNTAX INTEGER
			MAX-ACCESS read-write
			STATUS current
			DESCRIPTION "Reset dirty filter AL"
			::= { binaryObjects1 71 }

			dryCoolerAlRes_1 OBJECT-TYPE
			SYNTAX INTEGER
			MAX-ACCESS read-write
			STATUS current
			DESCRIPTION "Reset dry cooler AL"
			::= { binaryObjects1 72 }

			extHumidifAlRes_1 OBJECT-TYPE
			SYNTAX INTEGER
			MAX-ACCESS read-write
			STATUS current
			DESCRIPTION "Reset ext. humidifier AL"
			::= { binaryObjects1 73 }

			waterPumpAlRes_1 OBJECT-TYPE
			SYNTAX INTEGER
			MAX-ACCESS read-write
			STATUS current
			DESCRIPTION "Reset water pump AL"
			::= { binaryObjects1 74 }

			condUnitGAlRes_1 OBJECT-TYPE
			SYNTAX INTEGER
			MAX-ACCESS read-write
			STATUS current
			DESCRIPTION "Reset motocondenser AL"
			::= { binaryObjects1 75 }

			gasLeakAlRes_1 OBJECT-TYPE
			SYNTAX INTEGER
			MAX-ACCESS read-write
			STATUS current
			DESCRIPTION "Reset gas leak AL"
			::= { binaryObjects1 76 }

			powerSupAlRes_1 OBJECT-TYPE
			SYNTAX INTEGER
			MAX-ACCESS read-write
			STATUS current
			DESCRIPTION "Reset power fault AL"
			::= { binaryObjects1 77 }

			genSoftAlRes_1 OBJECT-TYPE
			SYNTAX INTEGER
			MAX-ACCESS read-write
			STATUS current
			DESCRIPTION "Reset generic soft AL"
			::= { binaryObjects1 78 }

		scalarsObjects1 OBJECT IDENTIFIER  ::= { node1 2 }

			confDI1Combo_1 OBJECT-TYPE
			SYNTAX Integer32
			MAX-ACCESS read-only
			STATUS current
			DESCRIPTION "Configurable DI1 meaning"
			::= { scalarsObjects1 1 }

			confDI2Combo_1 OBJECT-TYPE
			SYNTAX Integer32
			MAX-ACCESS read-only
			STATUS current
			DESCRIPTION "Configurable DI2 meaning"
			::= { scalarsObjects1 2 }

			confDI3Combo_1 OBJECT-TYPE
			SYNTAX Integer32
			MAX-ACCESS read-only
			STATUS current
			DESCRIPTION "Configurable DI3 meaning"
			::= { scalarsObjects1 3 }

			confDI4Combo_1 OBJECT-TYPE
			SYNTAX Integer32
			MAX-ACCESS read-only
			STATUS current
			DESCRIPTION "Configurable DI4 meaning"
			::= { scalarsObjects1 4 }

			confDI5Combo_1 OBJECT-TYPE
			SYNTAX Integer32
			MAX-ACCESS read-only
			STATUS current
			DESCRIPTION "Configurable DI5 meaning"
			::= { scalarsObjects1 5 }

			confDO1Combo_1 OBJECT-TYPE
			SYNTAX Integer32
			MAX-ACCESS read-only
			STATUS current
			DESCRIPTION "Configurable DO1 meaning"
			::= { scalarsObjects1 6 }

			confDO2Combo_1 OBJECT-TYPE
			SYNTAX Integer32
			MAX-ACCESS read-only
			STATUS current
			DESCRIPTION "Configurable DO2 meaning"
			::= { scalarsObjects1 7 }

			confDO3Combo_1 OBJECT-TYPE
			SYNTAX Integer32
			MAX-ACCESS read-only
			STATUS current
			DESCRIPTION "Configurable DO3 meaning"
			::= { scalarsObjects1 8 }

			confDO4Combo_1 OBJECT-TYPE
			SYNTAX Integer32
			MAX-ACCESS read-only
			STATUS current
			DESCRIPTION "Configurable DO4 meaning"
			::= { scalarsObjects1 9 }

			confDO5Combo_1 OBJECT-TYPE
			SYNTAX Integer32
			MAX-ACCESS read-only
			STATUS current
			DESCRIPTION "Configurable DO5 meaning"
			::= { scalarsObjects1 10 }

			returnTemp_1 OBJECT-TYPE
			SYNTAX Integer32
			MAX-ACCESS read-only
			STATUS current
			DESCRIPTION "Return temperature"
			::= { scalarsObjects1 11 }

			returnTAvg_1 OBJECT-TYPE
			SYNTAX Integer32
			MAX-ACCESS read-only
			STATUS current
			DESCRIPTION "Return temperature (AVG)"
			::= { scalarsObjects1 12 }

			supplyTemp_1 OBJECT-TYPE
			SYNTAX Integer32
			MAX-ACCESS read-only
			STATUS current
			DESCRIPTION "Supply temperature"
			::= { scalarsObjects1 13 }

			supplyTAvg_1 OBJECT-TYPE
			SYNTAX Integer32
			MAX-ACCESS read-only
			STATUS current
			DESCRIPTION "Supply temperature (AVG)"
			::= { scalarsObjects1 14 }

			tempDelta_1 OBJECT-TYPE
			SYNTAX Integer32
			MAX-ACCESS read-only
			STATUS current
			DESCRIPTION "Temperature delta"
			::= { scalarsObjects1 15 }

			returnHumidity_1 OBJECT-TYPE
			SYNTAX Integer32
			MAX-ACCESS read-only
			STATUS current
			DESCRIPTION "Return humidity"
			::= { scalarsObjects1 16 }

			returnHumAvg_1 OBJECT-TYPE
			SYNTAX Integer32
			MAX-ACCESS read-only
			STATUS current
			DESCRIPTION "Return humidity (AVG)"
			::= { scalarsObjects1 17 }

			supplyHumidity_1 OBJECT-TYPE
			SYNTAX Integer32
			MAX-ACCESS read-only
			STATUS current
			DESCRIPTION "Supply humidity"
			::= { scalarsObjects1 18 }

			supplyHumAvg_1 OBJECT-TYPE
			SYNTAX Integer32
			MAX-ACCESS read-only
			STATUS current
			DESCRIPTION "Supply humidity (AVG)"
			::= { scalarsObjects1 19 }

			airFlow_1 OBJECT-TYPE
			SYNTAX Integer32
			MAX-ACCESS read-only
			STATUS current
			DESCRIPTION "Air flow"
			::= { scalarsObjects1 20 }

			airPressure_1 OBJECT-TYPE
			SYNTAX Integer32
			MAX-ACCESS read-only
			STATUS current
			DESCRIPTION "Air pressure"
			::= { scalarsObjects1 22 }

			airPressureAvg_1 OBJECT-TYPE
			SYNTAX Integer32
			MAX-ACCESS read-only
			STATUS current
			DESCRIPTION "Air pressure (Average)"
			::= { scalarsObjects1 23 }

			netMod1Combo1_1 OBJECT-TYPE
			SYNTAX Integer32
			MAX-ACCESS read-only
			STATUS current
			DESCRIPTION "Module 1 - Probe 1 status"
			::= { scalarsObjects1 24 }

			netMod1Probe1_1 OBJECT-TYPE
			SYNTAX Integer32
			MAX-ACCESS read-only
			STATUS current
			DESCRIPTION "Module 1 - Probe 1 value"
			::= { scalarsObjects1 25 }

			netMod1Combo2_1 OBJECT-TYPE
			SYNTAX Integer32
			MAX-ACCESS read-only
			STATUS current
			DESCRIPTION "Module 1 - Probe 2 status"
			::= { scalarsObjects1 26 }

			netMod1Probe2_1 OBJECT-TYPE
			SYNTAX Integer32
			MAX-ACCESS read-only
			STATUS current
			DESCRIPTION "Module 1 - Probe 2 value"
			::= { scalarsObjects1 27 }

			netMod1Combo3_1 OBJECT-TYPE
			SYNTAX Integer32
			MAX-ACCESS read-only
			STATUS current
			DESCRIPTION "Module 1 - Probe 3 status"
			::= { scalarsObjects1 28 }

			netMod1Probe3_1 OBJECT-TYPE
			SYNTAX Integer32
			MAX-ACCESS read-only
			STATUS current
			DESCRIPTION "Module 1 - Probe 3 value"
			::= { scalarsObjects1 29 }

			netMod1Combo4_1 OBJECT-TYPE
			SYNTAX Integer32
			MAX-ACCESS read-only
			STATUS current
			DESCRIPTION "Module 1 - Probe 4 status"
			::= { scalarsObjects1 30 }

			netMod1Probe4_1 OBJECT-TYPE
			SYNTAX Integer32
			MAX-ACCESS read-only
			STATUS current
			DESCRIPTION "Module 1 - Probe 4 value"
			::= { scalarsObjects1 31 }

			netMod1Combo5_1 OBJECT-TYPE
			SYNTAX Integer32
			MAX-ACCESS read-only
			STATUS current
			DESCRIPTION "Module 1 - Probe 5 status"
			::= { scalarsObjects1 32 }

			netMod1Probe5_1 OBJECT-TYPE
			SYNTAX Integer32
			MAX-ACCESS read-only
			STATUS current
			DESCRIPTION "Module 1 - Probe 5 value"
			::= { scalarsObjects1 33 }

			netMod1Combo6_1 OBJECT-TYPE
			SYNTAX Integer32
			MAX-ACCESS read-only
			STATUS current
			DESCRIPTION "Module 1 - Probe 6 status"
			::= { scalarsObjects1 34 }

			netMod1Probe6_1 OBJECT-TYPE
			SYNTAX Integer32
			MAX-ACCESS read-only
			STATUS current
			DESCRIPTION "Module 1 - Probe 6 value"
			::= { scalarsObjects1 35 }

			netMod2Combo1_1 OBJECT-TYPE
			SYNTAX Integer32
			MAX-ACCESS read-only
			STATUS current
			DESCRIPTION "Module 2 - Probe 1 status"
			::= { scalarsObjects1 36 }

			netMod2Probe1_1 OBJECT-TYPE
			SYNTAX Integer32
			MAX-ACCESS read-only
			STATUS current
			DESCRIPTION "Module 2 - Probe 1 value"
			::= { scalarsObjects1 37 }

			netMod2Combo2_1 OBJECT-TYPE
			SYNTAX Integer32
			MAX-ACCESS read-only
			STATUS current
			DESCRIPTION "Module 2 - Probe 2 status"
			::= { scalarsObjects1 38 }

			netMod2Probe2_1 OBJECT-TYPE
			SYNTAX Integer32
			MAX-ACCESS read-only
			STATUS current
			DESCRIPTION "Module 2 - Probe 2 value"
			::= { scalarsObjects1 39 }

			netMod2Combo3_1 OBJECT-TYPE
			SYNTAX Integer32
			MAX-ACCESS read-only
			STATUS current
			DESCRIPTION "Module 2 - Probe 3 status"
			::= { scalarsObjects1 40 }

			netMod2Probe3_1 OBJECT-TYPE
			SYNTAX Integer32
			MAX-ACCESS read-only
			STATUS current
			DESCRIPTION "Module 2 - Probe 3 value"
			::= { scalarsObjects1 41 }

			netMod2Combo4_1 OBJECT-TYPE
			SYNTAX Integer32
			MAX-ACCESS read-only
			STATUS current
			DESCRIPTION "Module 2 - Probe 4 status"
			::= { scalarsObjects1 42 }

			netMod2Probe4_1 OBJECT-TYPE
			SYNTAX Integer32
			MAX-ACCESS read-only
			STATUS current
			DESCRIPTION "Module 2 - Probe 4 value"
			::= { scalarsObjects1 43 }

			netMod2Combo5_1 OBJECT-TYPE
			SYNTAX Integer32
			MAX-ACCESS read-only
			STATUS current
			DESCRIPTION "Module 2 - Probe 5 status"
			::= { scalarsObjects1 44 }

			netMod2Probe5_1 OBJECT-TYPE
			SYNTAX Integer32
			MAX-ACCESS read-only
			STATUS current
			DESCRIPTION "Module 2 - Probe 5 value"
			::= { scalarsObjects1 45 }

			netMod2Combo6_1 OBJECT-TYPE
			SYNTAX Integer32
			MAX-ACCESS read-only
			STATUS current
			DESCRIPTION "Module 2 - Probe 6 status"
			::= { scalarsObjects1 46 }

			netMod2Probe6_1 OBJECT-TYPE
			SYNTAX Integer32
			MAX-ACCESS read-only
			STATUS current
			DESCRIPTION "Module 2 - Probe 6 value"
			::= { scalarsObjects1 47 }

			netMod3Combo1_1 OBJECT-TYPE
			SYNTAX Integer32
			MAX-ACCESS read-only
			STATUS current
			DESCRIPTION "Module 3 - Probe 1 status"
			::= { scalarsObjects1 48 }

			netMod3Probe1_1 OBJECT-TYPE
			SYNTAX Integer32
			MAX-ACCESS read-only
			STATUS current
			DESCRIPTION "Module 3 - Probe 1 value"
			::= { scalarsObjects1 49 }

			netMod3Combo2_1 OBJECT-TYPE
			SYNTAX Integer32
			MAX-ACCESS read-only
			STATUS current
			DESCRIPTION "Module 3 - Probe 2 status"
			::= { scalarsObjects1 50 }

			netMod3Probe2_1 OBJECT-TYPE
			SYNTAX Integer32
			MAX-ACCESS read-only
			STATUS current
			DESCRIPTION "Module 3 - Probe 2 value"
			::= { scalarsObjects1 51 }

			netMod3Combo3_1 OBJECT-TYPE
			SYNTAX Integer32
			MAX-ACCESS read-only
			STATUS current
			DESCRIPTION "Module 3 - Probe 3 status"
			::= { scalarsObjects1 52 }

			netMod3Probe3_1 OBJECT-TYPE
			SYNTAX Integer32
			MAX-ACCESS read-only
			STATUS current
			DESCRIPTION "Module 3 - Probe 3 value"
			::= { scalarsObjects1 53 }

			netMod3Combo4_1 OBJECT-TYPE
			SYNTAX Integer32
			MAX-ACCESS read-only
			STATUS current
			DESCRIPTION "Module 3 - Probe 4 status"
			::= { scalarsObjects1 54 }

			netMod3Probe4_1 OBJECT-TYPE
			SYNTAX Integer32
			MAX-ACCESS read-only
			STATUS current
			DESCRIPTION "Module 3 - Probe 4 value"
			::= { scalarsObjects1 55 }

			netMod3Combo5_1 OBJECT-TYPE
			SYNTAX Integer32
			MAX-ACCESS read-only
			STATUS current
			DESCRIPTION "Module 3 - Probe 5 status"
			::= { scalarsObjects1 56 }

			netMod3Probe5_1 OBJECT-TYPE
			SYNTAX Integer32
			MAX-ACCESS read-only
			STATUS current
			DESCRIPTION "Module 3 - Probe 5 value"
			::= { scalarsObjects1 57 }

			netMod3Combo6_1 OBJECT-TYPE
			SYNTAX Integer32
			MAX-ACCESS read-only
			STATUS current
			DESCRIPTION "Module 3 - Probe 6 status"
			::= { scalarsObjects1 58 }

			netMod3Probe6_1 OBJECT-TYPE
			SYNTAX Integer32
			MAX-ACCESS read-only
			STATUS current
			DESCRIPTION "Module 3 - Probe 6 value"
			::= { scalarsObjects1 59 }

			avgModTemp_1 OBJECT-TYPE
			SYNTAX Integer32
			MAX-ACCESS read-only
			STATUS current
			DESCRIPTION "Modules temperatures AVG"
			::= { scalarsObjects1 60 }

			avgModHumi_1 OBJECT-TYPE
			SYNTAX Integer32
			MAX-ACCESS read-only
			STATUS current
			DESCRIPTION "Modules humidity AVG"
			::= { scalarsObjects1 61 }

			avgModPress_1 OBJECT-TYPE
			SYNTAX Integer32
			MAX-ACCESS read-only
			STATUS current
			DESCRIPTION "Modules pressure AVG"
			::= { scalarsObjects1 62 }

			dryCoolerAO_1 OBJECT-TYPE
			SYNTAX Integer32
			MAX-ACCESS read-only
			STATUS current
			DESCRIPTION "Supply Fan/Dry cooler"
			::= { scalarsObjects1 63 }

			coolingAO_1 OBJECT-TYPE
			SYNTAX Integer32
			MAX-ACCESS read-only
			STATUS current
			DESCRIPTION "Cooling valve/FC/Inverter"
			::= { scalarsObjects1 64 }

			heatingAO_1 OBJECT-TYPE
			SYNTAX Integer32
			MAX-ACCESS read-only
			STATUS current
			DESCRIPTION "Heating valve/Heater"
			::= { scalarsObjects1 65 }

			twoSources2AO_1 OBJECT-TYPE
			SYNTAX Integer32
			MAX-ACCESS read-only
			STATUS current
			DESCRIPTION "TS cooling valve 2"
			::= { scalarsObjects1 66 }

			condenser1AO_1 OBJECT-TYPE
			SYNTAX Integer32
			MAX-ACCESS read-only
			STATUS current
			DESCRIPTION "Condenser 1"
			::= { scalarsObjects1 67 }

			cond2HumidifAO_1 OBJECT-TYPE
			SYNTAX Integer32
			MAX-ACCESS read-only
			STATUS current
			DESCRIPTION "Condenser 2/Humidifier"
			::= { scalarsObjects1 68 }

			unitStatus_1 OBJECT-TYPE
			SYNTAX Integer32
			MAX-ACCESS read-only
			STATUS current
			DESCRIPTION "Unit status"
			::= { scalarsObjects1 69 }

			fanSpeed_1 OBJECT-TYPE
			SYNTAX Integer32
			MAX-ACCESS read-only
			STATUS current
			DESCRIPTION "Fan speed"
			::= { scalarsObjects1 70 }

			fan1Actspeed_1 OBJECT-TYPE
			SYNTAX Integer32
			MAX-ACCESS read-only
			STATUS current
			DESCRIPTION "Fan 1 speed"
			::= { scalarsObjects1 71 }

			fan1ActRPM_1 OBJECT-TYPE
			SYNTAX Integer32
			MAX-ACCESS read-only
			STATUS current
			DESCRIPTION "Fan 1 speed RPM"
			::= { scalarsObjects1 72 }

			fan1Cur_1 OBJECT-TYPE
			SYNTAX Integer32
			MAX-ACCESS read-only
			STATUS current
			DESCRIPTION "Fan 1 current"
			::= { scalarsObjects1 73 }

			fan1Power_1 OBJECT-TYPE
			SYNTAX Integer32
			MAX-ACCESS read-only
			STATUS current
			DESCRIPTION "Fan 1 power"
			::= { scalarsObjects1 74 }

			fan2Actspeed_1 OBJECT-TYPE
			SYNTAX Integer32
			MAX-ACCESS read-only
			STATUS current
			DESCRIPTION "Fan 2 speed"
			::= { scalarsObjects1 75 }

			fan2ActRPM_1 OBJECT-TYPE
			SYNTAX Integer32
			MAX-ACCESS read-only
			STATUS current
			DESCRIPTION "Fan 2 speed RPM"
			::= { scalarsObjects1 76 }

			fan2Cur_1 OBJECT-TYPE
			SYNTAX Integer32
			MAX-ACCESS read-only
			STATUS current
			DESCRIPTION "Fan 2 current"
			::= { scalarsObjects1 77 }

			fan2Power_1 OBJECT-TYPE
			SYNTAX Integer32
			MAX-ACCESS read-only
			STATUS current
			DESCRIPTION "Fan 2 power"
			::= { scalarsObjects1 78 }

			fan3Actspeed_1 OBJECT-TYPE
			SYNTAX Integer32
			MAX-ACCESS read-only
			STATUS current
			DESCRIPTION "Fan 3 speed"
			::= { scalarsObjects1 79 }

			fan3ActRPM_1 OBJECT-TYPE
			SYNTAX Integer32
			MAX-ACCESS read-only
			STATUS current
			DESCRIPTION "Fan 3 speed RPM"
			::= { scalarsObjects1 80 }

			fan3Cur_1 OBJECT-TYPE
			SYNTAX Integer32
			MAX-ACCESS read-only
			STATUS current
			DESCRIPTION "Fan 3 current"
			::= { scalarsObjects1 81 }

			fan3Power_1 OBJECT-TYPE
			SYNTAX Integer32
			MAX-ACCESS read-only
			STATUS current
			DESCRIPTION "Fan 3 power"
			::= { scalarsObjects1 82 }

			fan4Actspeed_1 OBJECT-TYPE
			SYNTAX Integer32
			MAX-ACCESS read-only
			STATUS current
			DESCRIPTION "Fan 4 speed"
			::= { scalarsObjects1 83 }

			fan4ActRPM_1 OBJECT-TYPE
			SYNTAX Integer32
			MAX-ACCESS read-only
			STATUS current
			DESCRIPTION "Fan 4 speed RPM"
			::= { scalarsObjects1 84 }

			fan4Cur_1 OBJECT-TYPE
			SYNTAX Integer32
			MAX-ACCESS read-only
			STATUS current
			DESCRIPTION "Fan 4 current"
			::= { scalarsObjects1 85 }

			fan4Power_1 OBJECT-TYPE
			SYNTAX Integer32
			MAX-ACCESS read-only
			STATUS current
			DESCRIPTION "Fan 4 power"
			::= { scalarsObjects1 86 }

			fan5Actspeed_1 OBJECT-TYPE
			SYNTAX Integer32
			MAX-ACCESS read-only
			STATUS current
			DESCRIPTION "Fan 5 speed"
			::= { scalarsObjects1 87 }

			fan5ActRPM_1 OBJECT-TYPE
			SYNTAX Integer32
			MAX-ACCESS read-only
			STATUS current
			DESCRIPTION "Fan 5 speed RPM"
			::= { scalarsObjects1 88 }

			fan5Cur_1 OBJECT-TYPE
			SYNTAX Integer32
			MAX-ACCESS read-only
			STATUS current
			DESCRIPTION "Fan 5 current"
			::= { scalarsObjects1 89 }

			fan5Power_1 OBJECT-TYPE
			SYNTAX Integer32
			MAX-ACCESS read-only
			STATUS current
			DESCRIPTION "Fan 5 power"
			::= { scalarsObjects1 90 }

			fan6Actspeed_1 OBJECT-TYPE
			SYNTAX Integer32
			MAX-ACCESS read-only
			STATUS current
			DESCRIPTION "Fan 6 speed"
			::= { scalarsObjects1 91 }

			fan6ActRPM_1 OBJECT-TYPE
			SYNTAX Integer32
			MAX-ACCESS read-only
			STATUS current
			DESCRIPTION "Fan 6 speed RPM"
			::= { scalarsObjects1 92 }

			fan6Cur_1 OBJECT-TYPE
			SYNTAX Integer32
			MAX-ACCESS read-only
			STATUS current
			DESCRIPTION "Fan 6 current"
			::= { scalarsObjects1 93 }

			fan6Power_1 OBJECT-TYPE
			SYNTAX Integer32
			MAX-ACCESS read-only
			STATUS current
			DESCRIPTION "Fan 6 power"
			::= { scalarsObjects1 94 }

			fan7Actspeed_1 OBJECT-TYPE
			SYNTAX Integer32
			MAX-ACCESS read-only
			STATUS current
			DESCRIPTION "Fan 7 speed"
			::= { scalarsObjects1 95 }

			fan7ActRPM_1 OBJECT-TYPE
			SYNTAX Integer32
			MAX-ACCESS read-only
			STATUS current
			DESCRIPTION "Fan 7 speed RPM"
			::= { scalarsObjects1 96 }

			fan7Cur_1 OBJECT-TYPE
			SYNTAX Integer32
			MAX-ACCESS read-only
			STATUS current
			DESCRIPTION "Fan 7 current"
			::= { scalarsObjects1 97 }

			fan7Power_1 OBJECT-TYPE
			SYNTAX Integer32
			MAX-ACCESS read-only
			STATUS current
			DESCRIPTION "Fan 7 power"
			::= { scalarsObjects1 98 }

			fan8Actspeed_1 OBJECT-TYPE
			SYNTAX Integer32
			MAX-ACCESS read-only
			STATUS current
			DESCRIPTION "Fan 8 speed"
			::= { scalarsObjects1 99 }

			fan8ActRPM_1 OBJECT-TYPE
			SYNTAX Integer32
			MAX-ACCESS read-only
			STATUS current
			DESCRIPTION "Fan 8 speed RPM"
			::= { scalarsObjects1 100 }

			fan8Cur_1 OBJECT-TYPE
			SYNTAX Integer32
			MAX-ACCESS read-only
			STATUS current
			DESCRIPTION "Fan 8 current"
			::= { scalarsObjects1 101 }

			fan8Power_1 OBJECT-TYPE
			SYNTAX Integer32
			MAX-ACCESS read-only
			STATUS current
			DESCRIPTION "Fan 8 power"
			::= { scalarsObjects1 102 }

			fan9Actspeed_1 OBJECT-TYPE
			SYNTAX Integer32
			MAX-ACCESS read-only
			STATUS current
			DESCRIPTION "Fan 9 speed"
			::= { scalarsObjects1 103 }

			fan9ActRPM_1 OBJECT-TYPE
			SYNTAX Integer32
			MAX-ACCESS read-only
			STATUS current
			DESCRIPTION "Fan 9 speed RPM"
			::= { scalarsObjects1 104 }

			fan9Cur_1 OBJECT-TYPE
			SYNTAX Integer32
			MAX-ACCESS read-only
			STATUS current
			DESCRIPTION "Fan 9 current"
			::= { scalarsObjects1 105 }

			fan9Power_1 OBJECT-TYPE
			SYNTAX Integer32
			MAX-ACCESS read-only
			STATUS current
			DESCRIPTION "Fan 9 power"
			::= { scalarsObjects1 106 }

			fan10Actspeed_1 OBJECT-TYPE
			SYNTAX Integer32
			MAX-ACCESS read-only
			STATUS current
			DESCRIPTION "Fan 10 speed"
			::= { scalarsObjects1 107 }

			fan10ActRPM_1 OBJECT-TYPE
			SYNTAX Integer32
			MAX-ACCESS read-only
			STATUS current
			DESCRIPTION "Fan 10 speed RPM"
			::= { scalarsObjects1 108 }

			fan10Cur_1 OBJECT-TYPE
			SYNTAX Integer32
			MAX-ACCESS read-only
			STATUS current
			DESCRIPTION "Fan 10 current"
			::= { scalarsObjects1 109 }

			fan10Power_1 OBJECT-TYPE
			SYNTAX Integer32
			MAX-ACCESS read-only
			STATUS current
			DESCRIPTION "Fan 10 power"
			::= { scalarsObjects1 110 }

			diffFilterPres_1 OBJECT-TYPE
			SYNTAX Integer32
			MAX-ACCESS read-only
			STATUS current
			DESCRIPTION "Dirty filter pressure"
			::= { scalarsObjects1 111 }

			coolingRequest_1 OBJECT-TYPE
			SYNTAX Integer32
			MAX-ACCESS read-only
			STATUS current
			DESCRIPTION "Cooling request"
			::= { scalarsObjects1 112 }

			heatingRequest_1 OBJECT-TYPE
			SYNTAX Integer32
			MAX-ACCESS read-only
			STATUS current
			DESCRIPTION "Heating request"
			::= { scalarsObjects1 113 }

			dehumidRequest_1 OBJECT-TYPE
			SYNTAX Integer32
			MAX-ACCESS read-only
			STATUS current
			DESCRIPTION "Dehumidification request"
			::= { scalarsObjects1 114 }

			humidifRequest_1 OBJECT-TYPE
			SYNTAX Integer32
			MAX-ACCESS read-only
			STATUS current
			DESCRIPTION "Humidification request"
			::= { scalarsObjects1 115 }

			tempFcTs_1 OBJECT-TYPE
			SYNTAX Integer32
			MAX-ACCESS read-only
			STATUS current
			DESCRIPTION "FC/TS temperature"
			::= { scalarsObjects1 116 }

			fCTSStatus_1 OBJECT-TYPE
			SYNTAX Integer32
			MAX-ACCESS read-only
			STATUS current
			DESCRIPTION "FC/TS status"
			::= { scalarsObjects1 117 }

			fCRequest_1 OBJECT-TYPE
			SYNTAX Integer32
			MAX-ACCESS read-only
			STATUS current
			DESCRIPTION "Free cooling request"
			::= { scalarsObjects1 118 }

			activeComp_1 OBJECT-TYPE
			SYNTAX Integer32
			MAX-ACCESS read-only
			STATUS current
			DESCRIPTION "Active compressor"
			::= { scalarsObjects1 119 }

			comp1Sts_1 OBJECT-TYPE
			SYNTAX Integer32
			MAX-ACCESS read-only
			STATUS current
			DESCRIPTION "Compressor 1 Status"
			::= { scalarsObjects1 120 }

			comp2Sts_1 OBJECT-TYPE
			SYNTAX Integer32
			MAX-ACCESS read-only
			STATUS current
			DESCRIPTION "Compressor 2 Status"
			::= { scalarsObjects1 121 }

			invComprReq_1 OBJECT-TYPE
			SYNTAX Integer32
			MAX-ACCESS read-only
			STATUS current
			DESCRIPTION "Inverter compressor request"
			::= { scalarsObjects1 122 }

			invCompHz_1 OBJECT-TYPE
			SYNTAX Integer32
			MAX-ACCESS read-only
			STATUS current
			DESCRIPTION "Inverter frequency"
			::= { scalarsObjects1 123 }

			invCompPower_1 OBJECT-TYPE
			SYNTAX Integer32
			MAX-ACCESS read-only
			STATUS current
			DESCRIPTION "Inverter power input"
			::= { scalarsObjects1 124 }

			invCompCurrent_1 OBJECT-TYPE
			SYNTAX Integer32
			MAX-ACCESS read-only
			STATUS current
			DESCRIPTION "Inverter absorbed current"
			::= { scalarsObjects1 125 }

			c1EvapPres_1 OBJECT-TYPE
			SYNTAX Integer32
			MAX-ACCESS read-only
			STATUS current
			DESCRIPTION "C1 evaporation pressure"
			::= { scalarsObjects1 126 }

			c1EvapTemp_1 OBJECT-TYPE
			SYNTAX Integer32
			MAX-ACCESS read-only
			STATUS current
			DESCRIPTION "C1 evaporation temperature"
			::= { scalarsObjects1 127 }

			c1SuctionTemp_1 OBJECT-TYPE
			SYNTAX Integer32
			MAX-ACCESS read-only
			STATUS current
			DESCRIPTION "C1 suction temperature"
			::= { scalarsObjects1 128 }

			c1Superheat_1 OBJECT-TYPE
			SYNTAX Integer32
			MAX-ACCESS read-only
			STATUS current
			DESCRIPTION "C1 super-heating"
			::= { scalarsObjects1 129 }

			c1CompRatio_1 OBJECT-TYPE
			SYNTAX Integer32
			MAX-ACCESS read-only
			STATUS current
			DESCRIPTION "C1 compression ratio"
			::= { scalarsObjects1 130 }

			c1DischTemp_1 OBJECT-TYPE
			SYNTAX Integer32
			MAX-ACCESS read-only
			STATUS current
			DESCRIPTION "C1 discharge temperature"
			::= { scalarsObjects1 131 }

			c1CondPress_1 OBJECT-TYPE
			SYNTAX Integer32
			MAX-ACCESS read-only
			STATUS current
			DESCRIPTION "C1 condensation pressure"
			::= { scalarsObjects1 132 }

			c1CondTemp_1 OBJECT-TYPE
			SYNTAX Integer32
			MAX-ACCESS read-only
			STATUS current
			DESCRIPTION "C1 condensation temperature"
			::= { scalarsObjects1 133 }

			c1Desuperheat_1 OBJECT-TYPE
			SYNTAX Integer32
			MAX-ACCESS read-only
			STATUS current
			DESCRIPTION "C1 de-superheating"
			::= { scalarsObjects1 134 }

			c1LiquidTemp_1 OBJECT-TYPE
			SYNTAX Integer32
			MAX-ACCESS read-only
			STATUS current
			DESCRIPTION "C1 liquid temperature"
			::= { scalarsObjects1 135 }

			c1Subcooling_1 OBJECT-TYPE
			SYNTAX Integer32
			MAX-ACCESS read-only
			STATUS current
			DESCRIPTION "C1 sub-cooling"
			::= { scalarsObjects1 136 }

			eEV1SHSet_1 OBJECT-TYPE
			SYNTAX Integer32
			MAX-ACCESS read-only
			STATUS current
			DESCRIPTION "EEV1 super-heating set-point"
			::= { scalarsObjects1 137 }

			eEV1Position_1 OBJECT-TYPE
			SYNTAX Integer32
			MAX-ACCESS read-only
			STATUS current
			DESCRIPTION "EEV1 position"
			::= { scalarsObjects1 138 }

			eEV1Status_1 OBJECT-TYPE
			SYNTAX Integer32
			MAX-ACCESS read-only
			STATUS current
			DESCRIPTION "EEV1 working status"
			::= { scalarsObjects1 139 }

			cond1ActualSet_1 OBJECT-TYPE
			SYNTAX Integer32
			MAX-ACCESS read-only
			STATUS current
			DESCRIPTION "Condenser 1 current set"
			::= { scalarsObjects1 140 }

			cond1Req_1 OBJECT-TYPE
			SYNTAX Integer32
			MAX-ACCESS read-only
			STATUS current
			DESCRIPTION "Condenser 1 request"
			::= { scalarsObjects1 141 }

			c2EvapPres_1 OBJECT-TYPE
			SYNTAX Integer32
			MAX-ACCESS read-only
			STATUS current
			DESCRIPTION "C2 evaporation pressure"
			::= { scalarsObjects1 142 }

			c2EvapTemp_1 OBJECT-TYPE
			SYNTAX Integer32
			MAX-ACCESS read-only
			STATUS current
			DESCRIPTION "C2 evaporation temperature"
			::= { scalarsObjects1 143 }

			c2SuctionTemp_1 OBJECT-TYPE
			SYNTAX Integer32
			MAX-ACCESS read-only
			STATUS current
			DESCRIPTION "C2 suction temperature"
			::= { scalarsObjects1 144 }

			c2Superheat_1 OBJECT-TYPE
			SYNTAX Integer32
			MAX-ACCESS read-only
			STATUS current
			DESCRIPTION "C2 super-heating"
			::= { scalarsObjects1 145 }

			c2CompRatio_1 OBJECT-TYPE
			SYNTAX Integer32
			MAX-ACCESS read-only
			STATUS current
			DESCRIPTION "C2 compression ratio"
			::= { scalarsObjects1 146 }

			c2DischTemp_1 OBJECT-TYPE
			SYNTAX Integer32
			MAX-ACCESS read-only
			STATUS current
			DESCRIPTION "C2 discharge temperature"
			::= { scalarsObjects1 147 }

			c2CondPress_1 OBJECT-TYPE
			SYNTAX Integer32
			MAX-ACCESS read-only
			STATUS current
			DESCRIPTION "C2 condensation pressure"
			::= { scalarsObjects1 148 }

			c2CondTemp_1 OBJECT-TYPE
			SYNTAX Integer32
			MAX-ACCESS read-only
			STATUS current
			DESCRIPTION "C2 condensation temperature"
			::= { scalarsObjects1 149 }

			c2Desuperheat_1 OBJECT-TYPE
			SYNTAX Integer32
			MAX-ACCESS read-only
			STATUS current
			DESCRIPTION "C2 de-superheating"
			::= { scalarsObjects1 150 }

			c2LiquidTemp_1 OBJECT-TYPE
			SYNTAX Integer32
			MAX-ACCESS read-only
			STATUS current
			DESCRIPTION "C2 liquid temperature"
			::= { scalarsObjects1 151 }

			c2Subcooling_1 OBJECT-TYPE
			SYNTAX Integer32
			MAX-ACCESS read-only
			STATUS current
			DESCRIPTION "C2 sub-cooling"
			::= { scalarsObjects1 152 }

			eEV2SHSet_1 OBJECT-TYPE
			SYNTAX Integer32
			MAX-ACCESS read-only
			STATUS current
			DESCRIPTION "EEV2 superheat set-point"
			::= { scalarsObjects1 153 }

			eEV2Position_1 OBJECT-TYPE
			SYNTAX Integer32
			MAX-ACCESS read-only
			STATUS current
			DESCRIPTION "EEV2 position"
			::= { scalarsObjects1 154 }

			eEV2Status_1 OBJECT-TYPE
			SYNTAX Integer32
			MAX-ACCESS read-only
			STATUS current
			DESCRIPTION "EEV2 working status"
			::= { scalarsObjects1 155 }

			cond2ActualSet_1 OBJECT-TYPE
			SYNTAX Integer32
			MAX-ACCESS read-only
			STATUS current
			DESCRIPTION "Condenser 2 current set"
			::= { scalarsObjects1 156 }

			cond2Req_1 OBJECT-TYPE
			SYNTAX Integer32
			MAX-ACCESS read-only
			STATUS current
			DESCRIPTION "Condenser 2 request"
			::= { scalarsObjects1 157 }

			waterINTemp1_1 OBJECT-TYPE
			SYNTAX Integer32
			MAX-ACCESS read-only
			STATUS current
			DESCRIPTION "Water IN temperature 1"
			::= { scalarsObjects1 158 }

			waterOUTTemp1_1 OBJECT-TYPE
			SYNTAX Integer32
			MAX-ACCESS read-only
			STATUS current
			DESCRIPTION "Water OUT temperature 1"
			::= { scalarsObjects1 159 }

			waterDT1_1 OBJECT-TYPE
			SYNTAX Integer32
			MAX-ACCESS read-only
			STATUS current
			DESCRIPTION "Water temperature delta 1"
			::= { scalarsObjects1 160 }

			waterFlow1_1 OBJECT-TYPE
			SYNTAX Integer32
			MAX-ACCESS read-only
			STATUS current
			DESCRIPTION "Water flow rate 1"
			::= { scalarsObjects1 161 }

			actWatFlowSet1_1 OBJECT-TYPE
			SYNTAX Integer32
			MAX-ACCESS read-only
			STATUS current
			DESCRIPTION "Actual water flow set 1"
			::= { scalarsObjects1 162 }

			waterCoolCap1_1 OBJECT-TYPE
			SYNTAX Integer32
			MAX-ACCESS read-only
			STATUS current
			DESCRIPTION "Water cooling capacity 1"
			::= { scalarsObjects1 163 }

			eER1_1 OBJECT-TYPE
			SYNTAX Integer32
			MAX-ACCESS read-only
			STATUS current
			DESCRIPTION "EER 1"
			::= { scalarsObjects1 164 }

			valve1Position_1 OBJECT-TYPE
			SYNTAX Integer32
			MAX-ACCESS read-only
			STATUS current
			DESCRIPTION "Water valve 1 position"
			::= { scalarsObjects1 165 }

			waterINTemp2_1 OBJECT-TYPE
			SYNTAX Integer32
			MAX-ACCESS read-only
			STATUS current
			DESCRIPTION "Water IN temperature 2"
			::= { scalarsObjects1 166 }

			waterOUTTemp2_1 OBJECT-TYPE
			SYNTAX Integer32
			MAX-ACCESS read-only
			STATUS current
			DESCRIPTION "Water OUT temperature 2"
			::= { scalarsObjects1 167 }

			waterDT2_1 OBJECT-TYPE
			SYNTAX Integer32
			MAX-ACCESS read-only
			STATUS current
			DESCRIPTION "Water temperature delta 2"
			::= { scalarsObjects1 168 }

			waterFlow2_1 OBJECT-TYPE
			SYNTAX Integer32
			MAX-ACCESS read-only
			STATUS current
			DESCRIPTION "Water flow rate 2"
			::= { scalarsObjects1 169 }

			actWatFlowSet2_1 OBJECT-TYPE
			SYNTAX Integer32
			MAX-ACCESS read-only
			STATUS current
			DESCRIPTION "Actual water flow set 2"
			::= { scalarsObjects1 170 }

			waterCoolCap2_1 OBJECT-TYPE
			SYNTAX Integer32
			MAX-ACCESS read-only
			STATUS current
			DESCRIPTION "Water cooling capacity 2"
			::= { scalarsObjects1 171 }

			eER2_1 OBJECT-TYPE
			SYNTAX Integer32
			MAX-ACCESS read-only
			STATUS current
			DESCRIPTION "EER 2"
			::= { scalarsObjects1 172 }

			valve2Position_1 OBJECT-TYPE
			SYNTAX Integer32
			MAX-ACCESS read-only
			STATUS current
			DESCRIPTION "Water valve 2 position"
			::= { scalarsObjects1 173 }

			humSteamProd_1 OBJECT-TYPE
			SYNTAX Integer32
			MAX-ACCESS read-only
			STATUS current
			DESCRIPTION "Current steam production"
			::= { scalarsObjects1 174 }

			humWaterConduct_1 OBJECT-TYPE
			SYNTAX Integer32
			MAX-ACCESS read-only
			STATUS current
			DESCRIPTION "Humidifier conductivity"
			::= { scalarsObjects1 175 }

			humCurrent_1 OBJECT-TYPE
			SYNTAX Integer32
			MAX-ACCESS read-only
			STATUS current
			DESCRIPTION "Humidifier abs. Current"
			::= { scalarsObjects1 176 }

			humWorkingMode_1 OBJECT-TYPE
			SYNTAX INTEGER
			MAX-ACCESS read-only
			STATUS current
			DESCRIPTION "Humidifier operating mode"
			::= { scalarsObjects1 177 }

			humWorkStatus_1 OBJECT-TYPE
			SYNTAX INTEGER
			MAX-ACCESS read-only
			STATUS current
			DESCRIPTION "Humidifier operating status"
			::= { scalarsObjects1 178 }

			heaterReq_1 OBJECT-TYPE
			SYNTAX Integer32
			MAX-ACCESS read-only
			STATUS current
			DESCRIPTION "Electric heater request"
			::= { scalarsObjects1 179 }

			heaterActiveStg_1 OBJECT-TYPE
			SYNTAX Integer32
			MAX-ACCESS read-only
			STATUS current
			DESCRIPTION "Number of active stages"
			::= { scalarsObjects1 180 }

			elHeaterPower_1 OBJECT-TYPE
			SYNTAX Integer32
			MAX-ACCESS read-only
			STATUS current
			DESCRIPTION "Electric heater power"
			::= { scalarsObjects1 181 }

			heatValveReq_1 OBJECT-TYPE
			SYNTAX Integer32
			MAX-ACCESS read-only
			STATUS current
			DESCRIPTION "Hot water valve request"
			::= { scalarsObjects1 182 }

			dryCoolerActSet_1 OBJECT-TYPE
			SYNTAX Integer32
			MAX-ACCESS read-only
			STATUS current
			DESCRIPTION "Current dry cooler set"
			::= { scalarsObjects1 183 }

			dryCoolerReq_1 OBJECT-TYPE
			SYNTAX Integer32
			MAX-ACCESS read-only
			STATUS current
			DESCRIPTION "Dry cooler request"
			::= { scalarsObjects1 184 }

			unitWH_1 OBJECT-TYPE
			SYNTAX Integer32
			MAX-ACCESS read-only
			STATUS current
			DESCRIPTION "Unit working hours"
			::= { scalarsObjects1 185 }

			c1WH_1 OBJECT-TYPE
			SYNTAX Integer32
			MAX-ACCESS read-only
			STATUS current
			DESCRIPTION "Compressor1 working hours"
			::= { scalarsObjects1 186 }

			c1Startup_1 OBJECT-TYPE
			SYNTAX Integer32
			MAX-ACCESS read-only
			STATUS current
			DESCRIPTION "Compressor 1 startups"
			::= { scalarsObjects1 187 }

			c2WH_1 OBJECT-TYPE
			SYNTAX Integer32
			MAX-ACCESS read-only
			STATUS current
			DESCRIPTION "Compressor2 working hours"
			::= { scalarsObjects1 188 }

			c2Startup_1 OBJECT-TYPE
			SYNTAX Integer32
			MAX-ACCESS read-only
			STATUS current
			DESCRIPTION "Compressor 2 startups"
			::= { scalarsObjects1 189 }

			coolValveWH_1 OBJECT-TYPE
			SYNTAX Integer32
			MAX-ACCESS read-only
			STATUS current
			DESCRIPTION "Cooling working hours"
			::= { scalarsObjects1 190 }

			heatingWH_1 OBJECT-TYPE
			SYNTAX Integer32
			MAX-ACCESS read-only
			STATUS current
			DESCRIPTION "Heating working hours"
			::= { scalarsObjects1 191 }

			humidifWH_1 OBJECT-TYPE
			SYNTAX Integer32
			MAX-ACCESS read-only
			STATUS current
			DESCRIPTION "Humidifier working hours"
			::= { scalarsObjects1 192 }

			freeCoolWH_1 OBJECT-TYPE
			SYNTAX Integer32
			MAX-ACCESS read-only
			STATUS current
			DESCRIPTION "FC working hours"
			::= { scalarsObjects1 193 }

			dryCoolerWH_1 OBJECT-TYPE
			SYNTAX Integer32
			MAX-ACCESS read-only
			STATUS current
			DESCRIPTION "Dry cooler working hours"
			::= { scalarsObjects1 194 }

			cond1WH_1 OBJECT-TYPE
			SYNTAX Integer32
			MAX-ACCESS read-only
			STATUS current
			DESCRIPTION "Condenser1 working hours"
			::= { scalarsObjects1 195 }

			cond2WH_1 OBJECT-TYPE
			SYNTAX Integer32
			MAX-ACCESS read-only
			STATUS current
			DESCRIPTION "Condenser2 working hours"
			::= { scalarsObjects1 196 }

			tempSetpoint_1 OBJECT-TYPE
			SYNTAX Integer32
			MAX-ACCESS read-write
			STATUS current
			DESCRIPTION "Temperature set-point"
			::= { scalarsObjects1 197 }

			humSetpoint_1 OBJECT-TYPE
			SYNTAX Integer32
			MAX-ACCESS read-write
			STATUS current
			DESCRIPTION "Humidity set-point"
			::= { scalarsObjects1 198 }

			airFlowSetpoint_1 OBJECT-TYPE
			SYNTAX Integer32
			MAX-ACCESS read-write
			STATUS current
			DESCRIPTION "Air flow set-point"
			::= { scalarsObjects1 199 }

			airPresSetpoint_1 OBJECT-TYPE
			SYNTAX Integer32
			MAX-ACCESS read-write
			STATUS current
			DESCRIPTION "Air pressure set-point"
			::= { scalarsObjects1 200 }

			airDTSetpoint_1 OBJECT-TYPE
			SYNTAX Integer32
			MAX-ACCESS read-write
			STATUS current
			DESCRIPTION "Air temperature delta set"
			::= { scalarsObjects1 201 }

			tempControlSel_1 OBJECT-TYPE
			SYNTAX Integer32
			MAX-ACCESS read-write
			STATUS current
			DESCRIPTION "Regulation sensor"
			::= { scalarsObjects1 202 }

			tempControlType_1 OBJECT-TYPE
			SYNTAX Integer32
			MAX-ACCESS read-write
			STATUS current
			DESCRIPTION "Regulation type"
			::= { scalarsObjects1 203 }

			tPropBand_1 OBJECT-TYPE
			SYNTAX Integer32
			MAX-ACCESS read-write
			STATUS current
			DESCRIPTION "Proportional Band"
			::= { scalarsObjects1 204 }

			tIntegralTime_1 OBJECT-TYPE
			SYNTAX Integer32
			MAX-ACCESS read-write
			STATUS current
			DESCRIPTION "Integration time"
			::= { scalarsObjects1 205 }

			tDerivativeTime_1 OBJECT-TYPE
			SYNTAX Integer32
			MAX-ACCESS read-write
			STATUS current
			DESCRIPTION "Derivative time"
			::= { scalarsObjects1 206 }

			highTAlOffset_1 OBJECT-TYPE
			SYNTAX Integer32
			MAX-ACCESS read-write
			STATUS current
			DESCRIPTION "High temperature offset"
			::= { scalarsObjects1 207 }

			lowTAlOffset_1 OBJECT-TYPE
			SYNTAX Integer32
			MAX-ACCESS read-write
			STATUS current
			DESCRIPTION "Low temperature offset"
			::= { scalarsObjects1 208 }

			highLimitTThr_1 OBJECT-TYPE
			SYNTAX Integer32
			MAX-ACCESS read-write
			STATUS current
			DESCRIPTION "High limit temp. thresh."
			::= { scalarsObjects1 209 }

			highLimitTMng_1 OBJECT-TYPE
			SYNTAX Integer32
			MAX-ACCESS read-write
			STATUS current
			DESCRIPTION "High limit temp. managem."
			::= { scalarsObjects1 210 }

			lowLimitTThr_1 OBJECT-TYPE
			SYNTAX Integer32
			MAX-ACCESS read-write
			STATUS current
			DESCRIPTION "Low limit temp.thresh."
			::= { scalarsObjects1 211 }

			lowLimitTMng_1 OBJECT-TYPE
			SYNTAX Integer32
			MAX-ACCESS read-write
			STATUS current
			DESCRIPTION "Low limit temp. managem."
			::= { scalarsObjects1 212 }

			dehumPropBand_1 OBJECT-TYPE
			SYNTAX Integer32
			MAX-ACCESS read-write
			STATUS current
			DESCRIPTION "Dehumid. proportion. band"
			::= { scalarsObjects1 213 }

			humPropBand_1 OBJECT-TYPE
			SYNTAX Integer32
			MAX-ACCESS read-write
			STATUS current
			DESCRIPTION "Humid. proportion. band"
			::= { scalarsObjects1 214 }

			hRetHAlOffset_1 OBJECT-TYPE
			SYNTAX Integer32
			MAX-ACCESS read-write
			STATUS current
			DESCRIPTION "High humidity offset"
			::= { scalarsObjects1 215 }

			lRetHAlOffset_1 OBJECT-TYPE
			SYNTAX Integer32
			MAX-ACCESS read-write
			STATUS current
			DESCRIPTION "Low humidity offset"
			::= { scalarsObjects1 216 }

			highSupHumThr_1 OBJECT-TYPE
			SYNTAX Integer32
			MAX-ACCESS read-write
			STATUS current
			DESCRIPTION "High supp. humidity thr."
			::= { scalarsObjects1 217 }

			lowSupHumThr_1 OBJECT-TYPE
			SYNTAX Integer32
			MAX-ACCESS read-write
			STATUS current
			DESCRIPTION "Low supp. humidity thr."
			::= { scalarsObjects1 218 }

			fCDelta_1 OBJECT-TYPE
			SYNTAX Integer32
			MAX-ACCESS read-write
			STATUS current
			DESCRIPTION "Free cooling delta"
			::= { scalarsObjects1 219 }

			tSWaterSet_1 OBJECT-TYPE
			SYNTAX Integer32
			MAX-ACCESS read-write
			STATUS current
			DESCRIPTION "Two sources set-point"
			::= { scalarsObjects1 220 }

			tSWaterPropBand_1 OBJECT-TYPE
			SYNTAX Integer32
			MAX-ACCESS read-write
			STATUS current
			DESCRIPTION "Two sources band"
			::= { scalarsObjects1 221 }

			tSAirTempSet_1 OBJECT-TYPE
			SYNTAX Integer32
			MAX-ACCESS read-write
			STATUS current
			DESCRIPTION "TS room temp. Exch. set"
			::= { scalarsObjects1 222 }

			condSetpoint_1 OBJECT-TYPE
			SYNTAX Integer32
			MAX-ACCESS read-write
			STATUS current
			DESCRIPTION "Condensation set-point"
			::= { scalarsObjects1 223 }

			condPropoBand_1 OBJECT-TYPE
			SYNTAX Integer32
			MAX-ACCESS read-write
			STATUS current
			DESCRIPTION "Condensation band"
			::= { scalarsObjects1 224 }

			condSetIncrease_1 OBJECT-TYPE
			SYNTAX Integer32
			MAX-ACCESS read-write
			STATUS current
			DESCRIPTION "Condensation set increase"
			::= { scalarsObjects1 225 }

			maxCondSetpoint_1 OBJECT-TYPE
			SYNTAX Integer32
			MAX-ACCESS read-write
			STATUS current
			DESCRIPTION "Maximum condensation set"
			::= { scalarsObjects1 226 }

			dryCoolerSet_1 OBJECT-TYPE
			SYNTAX Integer32
			MAX-ACCESS read-write
			STATUS current
			DESCRIPTION "Dry cooler set-point"
			::= { scalarsObjects1 227 }

			dryCoolPropBand_1 OBJECT-TYPE
			SYNTAX Integer32
			MAX-ACCESS read-write
			STATUS current
			DESCRIPTION "Dry cooler band"
			::= { scalarsObjects1 228 }

			dryCoolSetIncr_1 OBJECT-TYPE
			SYNTAX Integer32
			MAX-ACCESS read-write
			STATUS current
			DESCRIPTION "Dry Cooler set increase"
			::= { scalarsObjects1 229 }

			maxDryCoolerSet_1 OBJECT-TYPE
			SYNTAX Integer32
			MAX-ACCESS read-write
			STATUS current
			DESCRIPTION "Maximum dry Cooler set"
			::= { scalarsObjects1 230 }

			dirtyFiltSet_1 OBJECT-TYPE
			SYNTAX Integer32
			MAX-ACCESS read-write
			STATUS current
			DESCRIPTION "Dirty filter set-point"
			::= { scalarsObjects1 231 }

			dirtyFiltDiff_1 OBJECT-TYPE
			SYNTAX Integer32
			MAX-ACCESS read-write
			STATUS current
			DESCRIPTION "Dirty filter differential"
			::= { scalarsObjects1 232 }

			invCompAlCode1_1 OBJECT-TYPE
			SYNTAX Integer32
			MAX-ACCESS read-only
			STATUS current
			DESCRIPTION "DC Inverter alarm code 1"
			::= { scalarsObjects1 233 }

			invCompAlCode2_1 OBJECT-TYPE
			SYNTAX Integer32
			MAX-ACCESS read-only
			STATUS current
			DESCRIPTION "DC Inverter alarm code 2"
			::= { scalarsObjects1 234 }

			invCompAlCode3_1 OBJECT-TYPE
			SYNTAX Integer32
			MAX-ACCESS read-only
			STATUS current
			DESCRIPTION "DC Inverter alarm code 3"
			::= { scalarsObjects1 235 }

			invCompAlCode4_1 OBJECT-TYPE
			SYNTAX Integer32
			MAX-ACCESS read-only
			STATUS current
			DESCRIPTION "DC Inverter alarm code 4"
			::= { scalarsObjects1 236 }

			invCompAlCode5_1 OBJECT-TYPE
			SYNTAX Integer32
			MAX-ACCESS read-only
			STATUS current
			DESCRIPTION "DC Inverter alarm code 5"
			::= { scalarsObjects1 237 }

		alarms1 OBJECT IDENTIFIER  ::= { node1 3 }

			generalAl_1 OBJECT-TYPE
			SYNTAX INTEGER
			MAX-ACCESS read-only
			STATUS current
			DESCRIPTION "General alarams"
			::= { alarms1 1 }

			notCriticAl_1 OBJECT-TYPE
			SYNTAX INTEGER
			MAX-ACCESS read-only
			STATUS current
			DESCRIPTION "Not critical alarms"
			::= { alarms1 2 }

			criticalAl_1 OBJECT-TYPE
			SYNTAX INTEGER
			MAX-ACCESS read-only
			STATUS current
			DESCRIPTION "Critical alarms"
			::= { alarms1 3 }

			fansAl_1 OBJECT-TYPE
			SYNTAX INTEGER
			MAX-ACCESS read-only
			STATUS current
			DESCRIPTION "Fans alarms"
			::= { alarms1 4 }

			compAl_1 OBJECT-TYPE
			SYNTAX INTEGER
			MAX-ACCESS read-only
			STATUS current
			DESCRIPTION "Compressors alarms"
			::= { alarms1 5 }

			tempAl_1 OBJECT-TYPE
			SYNTAX INTEGER
			MAX-ACCESS read-only
			STATUS current
			DESCRIPTION "Temperature alarms"
			::= { alarms1 6 }

			humidityAl_1 OBJECT-TYPE
			SYNTAX INTEGER
			MAX-ACCESS read-only
			STATUS current
			DESCRIPTION "Humidity alarms"
			::= { alarms1 7 }

			damperAl_1 OBJECT-TYPE
			SYNTAX INTEGER
			MAX-ACCESS read-only
			STATUS current
			DESCRIPTION "Damper status alarm"
			::= { alarms1 8 }

			fireSmokeAl_1 OBJECT-TYPE
			SYNTAX INTEGER
			MAX-ACCESS read-only
			STATUS current
			DESCRIPTION "Fire/Smoke alarm"
			::= { alarms1 9 }

			gSeriousAl_1 OBJECT-TYPE
			SYNTAX INTEGER
			MAX-ACCESS read-only
			STATUS current
			DESCRIPTION "Critical generic alarm"
			::= { alarms1 10 }

			fansGenAl_1 OBJECT-TYPE
			SYNTAX INTEGER
			MAX-ACCESS read-only
			STATUS current
			DESCRIPTION "General supply fans alarm"
			::= { alarms1 11 }

			f1GeneralAl_1 OBJECT-TYPE
			SYNTAX INTEGER
			MAX-ACCESS read-only
			STATUS current
			DESCRIPTION "Fan general alarm 1"
			::= { alarms1 12 }

			f1PowerAl_1 OBJECT-TYPE
			SYNTAX INTEGER
			MAX-ACCESS read-only
			STATUS current
			DESCRIPTION "Phase failure/undervolt.1"
			::= { alarms1 13 }

			f1CommAl_1 OBJECT-TYPE
			SYNTAX INTEGER
			MAX-ACCESS read-only
			STATUS current
			DESCRIPTION "Communication 1"
			::= { alarms1 14 }

			f1HiTempAl_1 OBJECT-TYPE
			SYNTAX INTEGER
			MAX-ACCESS read-only
			STATUS current
			DESCRIPTION "Power mod overheated 1"
			::= { alarms1 15 }

			f1NetComAl_1 OBJECT-TYPE
			SYNTAX INTEGER
			MAX-ACCESS read-only
			STATUS current
			DESCRIPTION "Master/Slave com. 1"
			::= { alarms1 16 }

			f1InvRegAl_1 OBJECT-TYPE
			SYNTAX INTEGER
			MAX-ACCESS read-only
			STATUS current
			DESCRIPTION "Regulation module 1"
			::= { alarms1 17 }

			f1HiMotTAl_1 OBJECT-TYPE
			SYNTAX INTEGER
			MAX-ACCESS read-only
			STATUS current
			DESCRIPTION "Motor overheated 1"
			::= { alarms1 18 }

			f1HallSenAl_1 OBJECT-TYPE
			SYNTAX INTEGER
			MAX-ACCESS read-only
			STATUS current
			DESCRIPTION "Hall sensor error 1"
			::= { alarms1 19 }

			f1OverlAl_1 OBJECT-TYPE
			SYNTAX INTEGER
			MAX-ACCESS read-only
			STATUS current
			DESCRIPTION "Locked motor 1"
			::= { alarms1 20 }

			f1LowDCAl_1 OBJECT-TYPE
			SYNTAX INTEGER
			MAX-ACCESS read-only
			STATUS current
			DESCRIPTION "Low DC 1"
			::= { alarms1 21 }

			f2GeneralAl_1 OBJECT-TYPE
			SYNTAX INTEGER
			MAX-ACCESS read-only
			STATUS current
			DESCRIPTION "Fan general alarm 2"
			::= { alarms1 22 }

			f2PowerAl_1 OBJECT-TYPE
			SYNTAX INTEGER
			MAX-ACCESS read-only
			STATUS current
			DESCRIPTION "Phase failure/undervolt.2"
			::= { alarms1 23 }

			f2CommAl_1 OBJECT-TYPE
			SYNTAX INTEGER
			MAX-ACCESS read-only
			STATUS current
			DESCRIPTION "Communication 2"
			::= { alarms1 24 }

			f2HiTempAl_1 OBJECT-TYPE
			SYNTAX INTEGER
			MAX-ACCESS read-only
			STATUS current
			DESCRIPTION "Power mod overheated 2"
			::= { alarms1 25 }

			f2NetComAl_1 OBJECT-TYPE
			SYNTAX INTEGER
			MAX-ACCESS read-only
			STATUS current
			DESCRIPTION "Master/Slave com. 2"
			::= { alarms1 26 }

			f2InvRegAl_1 OBJECT-TYPE
			SYNTAX INTEGER
			MAX-ACCESS read-only
			STATUS current
			DESCRIPTION "Regulation module 2"
			::= { alarms1 27 }

			f2HiMotTAl_1 OBJECT-TYPE
			SYNTAX INTEGER
			MAX-ACCESS read-only
			STATUS current
			DESCRIPTION "Motor overheated 2"
			::= { alarms1 28 }

			f2HallSenAl_1 OBJECT-TYPE
			SYNTAX INTEGER
			MAX-ACCESS read-only
			STATUS current
			DESCRIPTION "Hall sensor error 2"
			::= { alarms1 29 }

			f2OverlAl_1 OBJECT-TYPE
			SYNTAX INTEGER
			MAX-ACCESS read-only
			STATUS current
			DESCRIPTION "Locked motor 2"
			::= { alarms1 30 }

			f2LowDCAl_1 OBJECT-TYPE
			SYNTAX INTEGER
			MAX-ACCESS read-only
			STATUS current
			DESCRIPTION "Low DC 2"
			::= { alarms1 31 }

			f3GeneralAl_1 OBJECT-TYPE
			SYNTAX INTEGER
			MAX-ACCESS read-only
			STATUS current
			DESCRIPTION "Fan general alarm 3"
			::= { alarms1 32 }

			f3PowerAl_1 OBJECT-TYPE
			SYNTAX INTEGER
			MAX-ACCESS read-only
			STATUS current
			DESCRIPTION "Phase failure/undervolt.3"
			::= { alarms1 33 }

			f3CommAl_1 OBJECT-TYPE
			SYNTAX INTEGER
			MAX-ACCESS read-only
			STATUS current
			DESCRIPTION "Communication 3"
			::= { alarms1 34 }

			f3HiTempAl_1 OBJECT-TYPE
			SYNTAX INTEGER
			MAX-ACCESS read-only
			STATUS current
			DESCRIPTION "Power mod overheated 3"
			::= { alarms1 35 }

			f3NetComAl_1 OBJECT-TYPE
			SYNTAX INTEGER
			MAX-ACCESS read-only
			STATUS current
			DESCRIPTION "Master/Slave com. 3"
			::= { alarms1 36 }

			f3InvRegAl_1 OBJECT-TYPE
			SYNTAX INTEGER
			MAX-ACCESS read-only
			STATUS current
			DESCRIPTION "Regulation module 3"
			::= { alarms1 37 }

			f3HiMotTAl_1 OBJECT-TYPE
			SYNTAX INTEGER
			MAX-ACCESS read-only
			STATUS current
			DESCRIPTION "Motor overheated 3"
			::= { alarms1 38 }

			f3HallSenAl_1 OBJECT-TYPE
			SYNTAX INTEGER
			MAX-ACCESS read-only
			STATUS current
			DESCRIPTION "Hall sensor error 3"
			::= { alarms1 39 }

			f3OverlAl_1 OBJECT-TYPE
			SYNTAX INTEGER
			MAX-ACCESS read-only
			STATUS current
			DESCRIPTION "Locked motor 3"
			::= { alarms1 40 }

			f3LowDCAl_1 OBJECT-TYPE
			SYNTAX INTEGER
			MAX-ACCESS read-only
			STATUS current
			DESCRIPTION "Low DC 3"
			::= { alarms1 41 }

			f4GeneralAl_1 OBJECT-TYPE
			SYNTAX INTEGER
			MAX-ACCESS read-only
			STATUS current
			DESCRIPTION "Fan general alarm 4"
			::= { alarms1 42 }

			f4PowerAl_1 OBJECT-TYPE
			SYNTAX INTEGER
			MAX-ACCESS read-only
			STATUS current
			DESCRIPTION "Phase failure/undervolt.4"
			::= { alarms1 43 }

			f4CommAl_1 OBJECT-TYPE
			SYNTAX INTEGER
			MAX-ACCESS read-only
			STATUS current
			DESCRIPTION "Communication 4"
			::= { alarms1 44 }

			f4HiTempAl_1 OBJECT-TYPE
			SYNTAX INTEGER
			MAX-ACCESS read-only
			STATUS current
			DESCRIPTION "Power mod overheated 4"
			::= { alarms1 45 }

			f4NetComAl_1 OBJECT-TYPE
			SYNTAX INTEGER
			MAX-ACCESS read-only
			STATUS current
			DESCRIPTION "Master/Slave com. 4"
			::= { alarms1 46 }

			f4InvRegAl_1 OBJECT-TYPE
			SYNTAX INTEGER
			MAX-ACCESS read-only
			STATUS current
			DESCRIPTION "Regulation module 4"
			::= { alarms1 47 }

			f4HiMotTAl_1 OBJECT-TYPE
			SYNTAX INTEGER
			MAX-ACCESS read-only
			STATUS current
			DESCRIPTION "Motor overheated 4"
			::= { alarms1 48 }

			f4HallSenAl_1 OBJECT-TYPE
			SYNTAX INTEGER
			MAX-ACCESS read-only
			STATUS current
			DESCRIPTION "Hall sensor error 4"
			::= { alarms1 49 }

			f4OverlAl_1 OBJECT-TYPE
			SYNTAX INTEGER
			MAX-ACCESS read-only
			STATUS current
			DESCRIPTION "Locked motor 4"
			::= { alarms1 50 }

			f4LowDCAl_1 OBJECT-TYPE
			SYNTAX INTEGER
			MAX-ACCESS read-only
			STATUS current
			DESCRIPTION "Low DC 4"
			::= { alarms1 51 }

			f5GeneralAl_1 OBJECT-TYPE
			SYNTAX INTEGER
			MAX-ACCESS read-only
			STATUS current
			DESCRIPTION "Fan general alarm 5"
			::= { alarms1 52 }

			f5PowerAl_1 OBJECT-TYPE
			SYNTAX INTEGER
			MAX-ACCESS read-only
			STATUS current
			DESCRIPTION "Phase failure/undervolt.5"
			::= { alarms1 53 }

			f5CommAl_1 OBJECT-TYPE
			SYNTAX INTEGER
			MAX-ACCESS read-only
			STATUS current
			DESCRIPTION "Communication 5"
			::= { alarms1 54 }

			f5HiTempAl_1 OBJECT-TYPE
			SYNTAX INTEGER
			MAX-ACCESS read-only
			STATUS current
			DESCRIPTION "Power mod overheated 5"
			::= { alarms1 55 }

			f5NetComAl_1 OBJECT-TYPE
			SYNTAX INTEGER
			MAX-ACCESS read-only
			STATUS current
			DESCRIPTION "Master/Slave com. 5"
			::= { alarms1 56 }

			f5InvRegAl_1 OBJECT-TYPE
			SYNTAX INTEGER
			MAX-ACCESS read-only
			STATUS current
			DESCRIPTION "Regulation module 5"
			::= { alarms1 57 }

			f5HiMotTAl_1 OBJECT-TYPE
			SYNTAX INTEGER
			MAX-ACCESS read-only
			STATUS current
			DESCRIPTION "Motor overheated 5"
			::= { alarms1 58 }

			f5HallSenAl_1 OBJECT-TYPE
			SYNTAX INTEGER
			MAX-ACCESS read-only
			STATUS current
			DESCRIPTION "Hall sensor error 5"
			::= { alarms1 59 }

			f5OverlAl_1 OBJECT-TYPE
			SYNTAX INTEGER
			MAX-ACCESS read-only
			STATUS current
			DESCRIPTION "Locked motor 5"
			::= { alarms1 60 }

			f5LowDCAl_1 OBJECT-TYPE
			SYNTAX INTEGER
			MAX-ACCESS read-only
			STATUS current
			DESCRIPTION "Low DC 5"
			::= { alarms1 61 }

			f6GeneralAl_1 OBJECT-TYPE
			SYNTAX INTEGER
			MAX-ACCESS read-only
			STATUS current
			DESCRIPTION "Fan general alarm 6"
			::= { alarms1 62 }

			f6PowerAl_1 OBJECT-TYPE
			SYNTAX INTEGER
			MAX-ACCESS read-only
			STATUS current
			DESCRIPTION "Phase failure/undervolt.6"
			::= { alarms1 63 }

			f6CommAl_1 OBJECT-TYPE
			SYNTAX INTEGER
			MAX-ACCESS read-only
			STATUS current
			DESCRIPTION "Communication 6"
			::= { alarms1 64 }

			f6HiTempAl_1 OBJECT-TYPE
			SYNTAX INTEGER
			MAX-ACCESS read-only
			STATUS current
			DESCRIPTION "Power mod overheated 6"
			::= { alarms1 65 }

			f6NetComAl_1 OBJECT-TYPE
			SYNTAX INTEGER
			MAX-ACCESS read-only
			STATUS current
			DESCRIPTION "Master/Slave com. 6"
			::= { alarms1 66 }

			f6InvRegAl_1 OBJECT-TYPE
			SYNTAX INTEGER
			MAX-ACCESS read-only
			STATUS current
			DESCRIPTION "Regulation module 6"
			::= { alarms1 67 }

			f6HiMotTAl_1 OBJECT-TYPE
			SYNTAX INTEGER
			MAX-ACCESS read-only
			STATUS current
			DESCRIPTION "Motor overheated 6"
			::= { alarms1 68 }

			f6HallSenAl_1 OBJECT-TYPE
			SYNTAX INTEGER
			MAX-ACCESS read-only
			STATUS current
			DESCRIPTION "Hall sensor error 6"
			::= { alarms1 69 }

			f6OverlAl_1 OBJECT-TYPE
			SYNTAX INTEGER
			MAX-ACCESS read-only
			STATUS current
			DESCRIPTION "Locked motor 6"
			::= { alarms1 70 }

			f6LowDCAl_1 OBJECT-TYPE
			SYNTAX INTEGER
			MAX-ACCESS read-only
			STATUS current
			DESCRIPTION "Low DC 6"
			::= { alarms1 71 }

			f7GeneralAl_1 OBJECT-TYPE
			SYNTAX INTEGER
			MAX-ACCESS read-only
			STATUS current
			DESCRIPTION "Fan general alarm 7"
			::= { alarms1 72 }

			f7PowerAl_1 OBJECT-TYPE
			SYNTAX INTEGER
			MAX-ACCESS read-only
			STATUS current
			DESCRIPTION "Phase failure/undervolt.7"
			::= { alarms1 73 }

			f7CommAl_1 OBJECT-TYPE
			SYNTAX INTEGER
			MAX-ACCESS read-only
			STATUS current
			DESCRIPTION "Communication 7"
			::= { alarms1 74 }

			f7HiTempAl_1 OBJECT-TYPE
			SYNTAX INTEGER
			MAX-ACCESS read-only
			STATUS current
			DESCRIPTION "Power mod overheated 7"
			::= { alarms1 75 }

			f7NetComAl_1 OBJECT-TYPE
			SYNTAX INTEGER
			MAX-ACCESS read-only
			STATUS current
			DESCRIPTION "Master/Slave com. 7"
			::= { alarms1 76 }

			f7InvRegAl_1 OBJECT-TYPE
			SYNTAX INTEGER
			MAX-ACCESS read-only
			STATUS current
			DESCRIPTION "Regulation module 7"
			::= { alarms1 77 }

			f7HiMotTAl_1 OBJECT-TYPE
			SYNTAX INTEGER
			MAX-ACCESS read-only
			STATUS current
			DESCRIPTION "Motor overheated 7"
			::= { alarms1 78 }

			f7HallSenAl_1 OBJECT-TYPE
			SYNTAX INTEGER
			MAX-ACCESS read-only
			STATUS current
			DESCRIPTION "Hall sensor error 7"
			::= { alarms1 79 }

			f7OverlAl_1 OBJECT-TYPE
			SYNTAX INTEGER
			MAX-ACCESS read-only
			STATUS current
			DESCRIPTION "Locked motor 7"
			::= { alarms1 80 }

			f7LowDCAl_1 OBJECT-TYPE
			SYNTAX INTEGER
			MAX-ACCESS read-only
			STATUS current
			DESCRIPTION "Low DC 7"
			::= { alarms1 81 }

			f8GeneralAl_1 OBJECT-TYPE
			SYNTAX INTEGER
			MAX-ACCESS read-only
			STATUS current
			DESCRIPTION "Fan general alarm 8"
			::= { alarms1 82 }

			f8PowerAl_1 OBJECT-TYPE
			SYNTAX INTEGER
			MAX-ACCESS read-only
			STATUS current
			DESCRIPTION "Phase failure/undervolt.8"
			::= { alarms1 83 }

			f8CommAl_1 OBJECT-TYPE
			SYNTAX INTEGER
			MAX-ACCESS read-only
			STATUS current
			DESCRIPTION "Communication 8"
			::= { alarms1 84 }

			f8HiTempAl_1 OBJECT-TYPE
			SYNTAX INTEGER
			MAX-ACCESS read-only
			STATUS current
			DESCRIPTION "Power mod overheated 8"
			::= { alarms1 85 }

			f8NetComAl_1 OBJECT-TYPE
			SYNTAX INTEGER
			MAX-ACCESS read-only
			STATUS current
			DESCRIPTION "Master/Slave com. 8"
			::= { alarms1 86 }

			f8InvRegAl_1 OBJECT-TYPE
			SYNTAX INTEGER
			MAX-ACCESS read-only
			STATUS current
			DESCRIPTION "Regulation module 8"
			::= { alarms1 87 }

			f8HiMotTAl_1 OBJECT-TYPE
			SYNTAX INTEGER
			MAX-ACCESS read-only
			STATUS current
			DESCRIPTION "Motor overheated 8"
			::= { alarms1 88 }

			f8HallSenAl_1 OBJECT-TYPE
			SYNTAX INTEGER
			MAX-ACCESS read-only
			STATUS current
			DESCRIPTION "Hall sensor error 8"
			::= { alarms1 89 }

			f8OverlAl_1 OBJECT-TYPE
			SYNTAX INTEGER
			MAX-ACCESS read-only
			STATUS current
			DESCRIPTION "Locked motor 8"
			::= { alarms1 90 }

			f8LowDCAl_1 OBJECT-TYPE
			SYNTAX INTEGER
			MAX-ACCESS read-only
			STATUS current
			DESCRIPTION "Low DC 8"
			::= { alarms1 91 }

			f9GeneralAl_1 OBJECT-TYPE
			SYNTAX INTEGER
			MAX-ACCESS read-only
			STATUS current
			DESCRIPTION "Fan general alarm 9"
			::= { alarms1 92 }

			f9PowerAl_1 OBJECT-TYPE
			SYNTAX INTEGER
			MAX-ACCESS read-only
			STATUS current
			DESCRIPTION "Phase failure/undervolt.9"
			::= { alarms1 93 }

			f9CommAl_1 OBJECT-TYPE
			SYNTAX INTEGER
			MAX-ACCESS read-only
			STATUS current
			DESCRIPTION "Communication 9"
			::= { alarms1 94 }

			f9HiTempAl_1 OBJECT-TYPE
			SYNTAX INTEGER
			MAX-ACCESS read-only
			STATUS current
			DESCRIPTION "Power mod overheated 9"
			::= { alarms1 95 }

			f9NetComAl_1 OBJECT-TYPE
			SYNTAX INTEGER
			MAX-ACCESS read-only
			STATUS current
			DESCRIPTION "Master/Slave com. 9"
			::= { alarms1 96 }

			f9InvRegAl_1 OBJECT-TYPE
			SYNTAX INTEGER
			MAX-ACCESS read-only
			STATUS current
			DESCRIPTION "Regulation module 9"
			::= { alarms1 97 }

			f9HiMotTAl_1 OBJECT-TYPE
			SYNTAX INTEGER
			MAX-ACCESS read-only
			STATUS current
			DESCRIPTION "Motor overheated 9"
			::= { alarms1 98 }

			f9HallSenAl_1 OBJECT-TYPE
			SYNTAX INTEGER
			MAX-ACCESS read-only
			STATUS current
			DESCRIPTION "Hall sensor error 9"
			::= { alarms1 99 }

			f9OverlAl_1 OBJECT-TYPE
			SYNTAX INTEGER
			MAX-ACCESS read-only
			STATUS current
			DESCRIPTION "Locked motor 9"
			::= { alarms1 100 }

			f9LowDCAl_1 OBJECT-TYPE
			SYNTAX INTEGER
			MAX-ACCESS read-only
			STATUS current
			DESCRIPTION "Low DC 9"
			::= { alarms1 101 }

			f10GenlAl_1 OBJECT-TYPE
			SYNTAX INTEGER
			MAX-ACCESS read-only
			STATUS current
			DESCRIPTION "Fan general alarm 10"
			::= { alarms1 102 }

			f10PowerAl_1 OBJECT-TYPE
			SYNTAX INTEGER
			MAX-ACCESS read-only
			STATUS current
			DESCRIPTION "Phase failure/undervolt.10"
			::= { alarms1 103 }

			f10CommAl_1 OBJECT-TYPE
			SYNTAX INTEGER
			MAX-ACCESS read-only
			STATUS current
			DESCRIPTION "Communication 10"
			::= { alarms1 104 }

			f10HiTempAl_1 OBJECT-TYPE
			SYNTAX INTEGER
			MAX-ACCESS read-only
			STATUS current
			DESCRIPTION "Power mod overheated 10"
			::= { alarms1 105 }

			f10NetComAl_1 OBJECT-TYPE
			SYNTAX INTEGER
			MAX-ACCESS read-only
			STATUS current
			DESCRIPTION "Master/Slave com. 10"
			::= { alarms1 106 }

			f10InvRegAl_1 OBJECT-TYPE
			SYNTAX INTEGER
			MAX-ACCESS read-only
			STATUS current
			DESCRIPTION "Regulation module 10"
			::= { alarms1 107 }

			f10HiMotTAl_1 OBJECT-TYPE
			SYNTAX INTEGER
			MAX-ACCESS read-only
			STATUS current
			DESCRIPTION "Motor overheated 10"
			::= { alarms1 108 }

			f10HallSAl_1 OBJECT-TYPE
			SYNTAX INTEGER
			MAX-ACCESS read-only
			STATUS current
			DESCRIPTION "Hall sensor error 10"
			::= { alarms1 109 }

			f10OverlAl_1 OBJECT-TYPE
			SYNTAX INTEGER
			MAX-ACCESS read-only
			STATUS current
			DESCRIPTION "Locked motor 10"
			::= { alarms1 110 }

			f10LowDCAl_1 OBJECT-TYPE
			SYNTAX INTEGER
			MAX-ACCESS read-only
			STATUS current
			DESCRIPTION "Low DC 10"
			::= { alarms1 111 }

			retTempPbAl_1 OBJECT-TYPE
			SYNTAX INTEGER
			MAX-ACCESS read-only
			STATUS current
			DESCRIPTION "Return temperature probe"
			::= { alarms1 112 }

			supTempPrAl_1 OBJECT-TYPE
			SYNTAX INTEGER
			MAX-ACCESS read-only
			STATUS current
			DESCRIPTION "Supply temperature probe"
			::= { alarms1 113 }

			retHumPrAl_1 OBJECT-TYPE
			SYNTAX INTEGER
			MAX-ACCESS read-only
			STATUS current
			DESCRIPTION "Return humidity probe"
			::= { alarms1 114 }

			supHumPrAl_1 OBJECT-TYPE
			SYNTAX INTEGER
			MAX-ACCESS read-only
			STATUS current
			DESCRIPTION "Supply humidity probe"
			::= { alarms1 115 }

			airPrSensAl_1 OBJECT-TYPE
			SYNTAX INTEGER
			MAX-ACCESS read-only
			STATUS current
			DESCRIPTION "Air diff.pressure probe"
			::= { alarms1 116 }

			watIN1PrAl_1 OBJECT-TYPE
			SYNTAX INTEGER
			MAX-ACCESS read-only
			STATUS current
			DESCRIPTION "Water temp. IN1 probe"
			::= { alarms1 117 }

			watOUT1PrAl_1 OBJECT-TYPE
			SYNTAX INTEGER
			MAX-ACCESS read-only
			STATUS current
			DESCRIPTION "Water temp. OUT1 probe"
			::= { alarms1 118 }

			watIN2PrAl_1 OBJECT-TYPE
			SYNTAX INTEGER
			MAX-ACCESS read-only
			STATUS current
			DESCRIPTION "Water temp. IN2 probe"
			::= { alarms1 119 }

			watOUT2PrAl_1 OBJECT-TYPE
			SYNTAX INTEGER
			MAX-ACCESS read-only
			STATUS current
			DESCRIPTION "Water temp. OUT2 probe"
			::= { alarms1 120 }

			watFlw1PrAl_1 OBJECT-TYPE
			SYNTAX INTEGER
			MAX-ACCESS read-only
			STATUS current
			DESCRIPTION "Water flow1/T.liquid1 pr."
			::= { alarms1 121 }

			watFlw2PrAl_1 OBJECT-TYPE
			SYNTAX INTEGER
			MAX-ACCESS read-only
			STATUS current
			DESCRIPTION "Water flow2/T.liquid2 pr."
			::= { alarms1 122 }

			dFPSGenAl_1 OBJECT-TYPE
			SYNTAX INTEGER
			MAX-ACCESS read-only
			STATUS current
			DESCRIPTION "Filter diff.press. probe"
			::= { alarms1 123 }

			dFPSBrokAl_1 OBJECT-TYPE
			SYNTAX INTEGER
			MAX-ACCESS read-only
			STATUS current
			DESCRIPTION "Breakdown alarm"
			::= { alarms1 124 }

			dFPSCablAl_1 OBJECT-TYPE
			SYNTAX INTEGER
			MAX-ACCESS read-only
			STATUS current
			DESCRIPTION "Wiring alarm"
			::= { alarms1 125 }

			dFPSRangeAl_1 OBJECT-TYPE
			SYNTAX INTEGER
			MAX-ACCESS read-only
			STATUS current
			DESCRIPTION "Pressure range alarm"
			::= { alarms1 126 }

			dFPSADCAl_1 OBJECT-TYPE
			SYNTAX INTEGER
			MAX-ACCESS read-only
			STATUS current
			DESCRIPTION "ADC overload alarm"
			::= { alarms1 127 }

			dFPSSetAl_1 OBJECT-TYPE
			SYNTAX INTEGER
			MAX-ACCESS read-only
			STATUS current
			DESCRIPTION "Calibration alarm"
			::= { alarms1 128 }

			dFPSDCOAl_1 OBJECT-TYPE
			SYNTAX INTEGER
			MAX-ACCESS read-only
			STATUS current
			DESCRIPTION "DCO alarm"
			::= { alarms1 129 }

			dFPSWatdAl_1 OBJECT-TYPE
			SYNTAX INTEGER
			MAX-ACCESS read-only
			STATUS current
			DESCRIPTION "Watchdog alarm"
			::= { alarms1 130 }

			dFPSCommAl_1 OBJECT-TYPE
			SYNTAX INTEGER
			MAX-ACCESS read-only
			STATUS current
			DESCRIPTION "Communication alarm"
			::= { alarms1 131 }

			invC1GenAl_1 OBJECT-TYPE
			SYNTAX INTEGER
			MAX-ACCESS read-only
			STATUS current
			DESCRIPTION "DC inverter general alarm"
			::= { alarms1 132 }

			invC1CommAl_1 OBJECT-TYPE
			SYNTAX INTEGER
			MAX-ACCESS read-only
			STATUS current
			DESCRIPTION "Inverter communication"
			::= { alarms1 133 }

			c1ThermAl_1 OBJECT-TYPE
			SYNTAX INTEGER
			MAX-ACCESS read-only
			STATUS current
			DESCRIPTION "C1 Thermal alarm"
			::= { alarms1 134 }

			c1HighPresAl_1 OBJECT-TYPE
			SYNTAX INTEGER
			MAX-ACCESS read-only
			STATUS current
			DESCRIPTION "C1 High pressure alarm"
			::= { alarms1 135 }

			c1LowPresAl_1 OBJECT-TYPE
			SYNTAX INTEGER
			MAX-ACCESS read-only
			STATUS current
			DESCRIPTION "C1 Low pressure alarm"
			::= { alarms1 136 }

			c1HighDiscAl_1 OBJECT-TYPE
			SYNTAX INTEGER
			MAX-ACCESS read-only
			STATUS current
			DESCRIPTION "C1 High discharge alarm"
			::= { alarms1 137 }

			c1LCompRatAl_1 OBJECT-TYPE
			SYNTAX INTEGER
			MAX-ACCESS read-only
			STATUS current
			DESCRIPTION "C1 low compresion alarm"
			::= { alarms1 138 }

			condenser1Al_1 OBJECT-TYPE
			SYNTAX INTEGER
			MAX-ACCESS read-only
			STATUS current
			DESCRIPTION "Condenser 1 general alarm"
			::= { alarms1 139 }

			c1WatFlowAl_1 OBJECT-TYPE
			SYNTAX INTEGER
			MAX-ACCESS read-only
			STATUS current
			DESCRIPTION "Condenser 1 flow alarm"
			::= { alarms1 140 }

			eEV1GenAl_1 OBJECT-TYPE
			SYNTAX INTEGER
			MAX-ACCESS read-only
			STATUS current
			DESCRIPTION "EEV1 general alarm"
			::= { alarms1 141 }

			eEV1CommAl_1 OBJECT-TYPE
			SYNTAX INTEGER
			MAX-ACCESS read-only
			STATUS current
			DESCRIPTION "EEV1 communication alarm"
			::= { alarms1 142 }

			eEV1SuctPrAl_1 OBJECT-TYPE
			SYNTAX INTEGER
			MAX-ACCESS read-only
			STATUS current
			DESCRIPTION "EEV1 suction temp. probe"
			::= { alarms1 143 }

			eEV1EvapPrAl_1 OBJECT-TYPE
			SYNTAX INTEGER
			MAX-ACCESS read-only
			STATUS current
			DESCRIPTION "EEV1 evap. temp. probe"
			::= { alarms1 144 }

			eEV1CondPrAl_1 OBJECT-TYPE
			SYNTAX INTEGER
			MAX-ACCESS read-only
			STATUS current
			DESCRIPTION "EEV1 condens. temp. probe"
			::= { alarms1 145 }

			eEV1DiscPrAl_1 OBJECT-TYPE
			SYNTAX INTEGER
			MAX-ACCESS read-only
			STATUS current
			DESCRIPTION "EEV1 disch. temp. probe"
			::= { alarms1 146 }

			c2ThermAl_1 OBJECT-TYPE
			SYNTAX INTEGER
			MAX-ACCESS read-only
			STATUS current
			DESCRIPTION "C2 Thermal alarm"
			::= { alarms1 147 }

			c2HighPresAl_1 OBJECT-TYPE
			SYNTAX INTEGER
			MAX-ACCESS read-only
			STATUS current
			DESCRIPTION "C2 High pressure alarm"
			::= { alarms1 148 }

			c2LowPresAl_1 OBJECT-TYPE
			SYNTAX INTEGER
			MAX-ACCESS read-only
			STATUS current
			DESCRIPTION "C2 Low pressure alarm"
			::= { alarms1 149 }

			c2HighDiscAl_1 OBJECT-TYPE
			SYNTAX INTEGER
			MAX-ACCESS read-only
			STATUS current
			DESCRIPTION "C2 High discharge alarm"
			::= { alarms1 150 }

			c2LCompRatAl_1 OBJECT-TYPE
			SYNTAX INTEGER
			MAX-ACCESS read-only
			STATUS current
			DESCRIPTION "C2 low compresion alarm"
			::= { alarms1 151 }

			condenser2Al_1 OBJECT-TYPE
			SYNTAX INTEGER
			MAX-ACCESS read-only
			STATUS current
			DESCRIPTION "Condenser 2 general alarm"
			::= { alarms1 152 }

			c2WatFlowAl_1 OBJECT-TYPE
			SYNTAX INTEGER
			MAX-ACCESS read-only
			STATUS current
			DESCRIPTION "Condenser 2 flow alarm"
			::= { alarms1 153 }

			eEV2GenAl_1 OBJECT-TYPE
			SYNTAX INTEGER
			MAX-ACCESS read-only
			STATUS current
			DESCRIPTION "EEV2 general alarm"
			::= { alarms1 154 }

			eEV2CommAl_1 OBJECT-TYPE
			SYNTAX INTEGER
			MAX-ACCESS read-only
			STATUS current
			DESCRIPTION "EEV2 communication alarm"
			::= { alarms1 155 }

			eEV2SuctPrAl_1 OBJECT-TYPE
			SYNTAX INTEGER
			MAX-ACCESS read-only
			STATUS current
			DESCRIPTION "EEV2 suction temp. probe"
			::= { alarms1 156 }

			eEV2EvapPrAl_1 OBJECT-TYPE
			SYNTAX INTEGER
			MAX-ACCESS read-only
			STATUS current
			DESCRIPTION "EEV2 evap. temp. probe"
			::= { alarms1 157 }

			eEV2CondPrAl_1 OBJECT-TYPE
			SYNTAX INTEGER
			MAX-ACCESS read-only
			STATUS current
			DESCRIPTION "EEV2 condens. temp. probe"
			::= { alarms1 158 }

			eEV2DiscPrAl_1 OBJECT-TYPE
			SYNTAX INTEGER
			MAX-ACCESS read-only
			STATUS current
			DESCRIPTION "EEV2 disch. temp. probe"
			::= { alarms1 159 }

			intHumGenAl_1 OBJECT-TYPE
			SYNTAX INTEGER
			MAX-ACCESS read-only
			STATUS current
			DESCRIPTION "Internal humidifier alarm"
			::= { alarms1 160 }

			cPYCommAl_1 OBJECT-TYPE
			SYNTAX INTEGER
			MAX-ACCESS read-only
			STATUS current
			DESCRIPTION "Communication alarm"
			::= { alarms1 161 }

			cPYMemoryAl_1 OBJECT-TYPE
			SYNTAX INTEGER
			MAX-ACCESS read-only
			STATUS current
			DESCRIPTION "Memory error alarm"
			::= { alarms1 162 }

			cPYParamAl_1 OBJECT-TYPE
			SYNTAX INTEGER
			MAX-ACCESS read-only
			STATUS current
			DESCRIPTION "Parameters error alarm"
			::= { alarms1 163 }

			cPYHighCurAl_1 OBJECT-TYPE
			SYNTAX INTEGER
			MAX-ACCESS read-only
			STATUS current
			DESCRIPTION "Electrodes high current"
			::= { alarms1 164 }

			cPYLoSteamAl_1 OBJECT-TYPE
			SYNTAX INTEGER
			MAX-ACCESS read-only
			STATUS current
			DESCRIPTION "Low steam product. alarm"
			::= { alarms1 165 }

			cPYDrainAl_1 OBJECT-TYPE
			SYNTAX INTEGER
			MAX-ACCESS read-only
			STATUS current
			DESCRIPTION "Drain loss alarm"
			::= { alarms1 166 }

			cPYMaintAl_1 OBJECT-TYPE
			SYNTAX INTEGER
			MAX-ACCESS read-only
			STATUS current
			DESCRIPTION "Maintenance hours alarm"
			::= { alarms1 167 }

			cPYNoWaterAl_1 OBJECT-TYPE
			SYNTAX INTEGER
			MAX-ACCESS read-only
			STATUS current
			DESCRIPTION "Water loss alarm"
			::= { alarms1 168 }

			cPYCylMainAl_1 OBJECT-TYPE
			SYNTAX INTEGER
			MAX-ACCESS read-only
			STATUS current
			DESCRIPTION "Cylinder mainten. alarm"
			::= { alarms1 169 }

			cPYDirtCylAl_1 OBJECT-TYPE
			SYNTAX INTEGER
			MAX-ACCESS read-only
			STATUS current
			DESCRIPTION "Exaust cylinder alarm"
			::= { alarms1 170 }

			cPYFoamAl_1 OBJECT-TYPE
			SYNTAX INTEGER
			MAX-ACCESS read-only
			STATUS current
			DESCRIPTION "Foam presence alarm"
			::= { alarms1 171 }

			cPYLifeTimAl_1 OBJECT-TYPE
			SYNTAX INTEGER
			MAX-ACCESS read-only
			STATUS current
			DESCRIPTION "Life time expired alarm"
			::= { alarms1 172 }

			cPYHiWLevAl_1 OBJECT-TYPE
			SYNTAX INTEGER
			MAX-ACCESS read-only
			STATUS current
			DESCRIPTION "High water level alarm"
			::= { alarms1 173 }

			cPYHWatConAl_1 OBJECT-TYPE
			SYNTAX INTEGER
			MAX-ACCESS read-only
			STATUS current
			DESCRIPTION "High conductivity alarm"
			::= { alarms1 174 }

			cPYConnAl_1 OBJECT-TYPE
			SYNTAX INTEGER
			MAX-ACCESS read-only
			STATUS current
			DESCRIPTION "Connection error alarm"
			::= { alarms1 175 }

			watPresAl_1 OBJECT-TYPE
			SYNTAX INTEGER
			MAX-ACCESS read-only
			STATUS current
			DESCRIPTION "Water presence alarm"
			::= { alarms1 176 }

			drainPumpAl_1 OBJECT-TYPE
			SYNTAX INTEGER
			MAX-ACCESS read-only
			STATUS current
			DESCRIPTION "Drain pump alarm"
			::= { alarms1 177 }

			elHeatAl_1 OBJECT-TYPE
			SYNTAX INTEGER
			MAX-ACCESS read-only
			STATUS current
			DESCRIPTION "Electric heater alarm"
			::= { alarms1 178 }

			filterAl_1 OBJECT-TYPE
			SYNTAX INTEGER
			MAX-ACCESS read-only
			STATUS current
			DESCRIPTION "Dirty filter alarm"
			::= { alarms1 179 }

			dryCoolerAl_1 OBJECT-TYPE
			SYNTAX INTEGER
			MAX-ACCESS read-only
			STATUS current
			DESCRIPTION "Dry cooler alarm"
			::= { alarms1 180 }

			extHumidAl_1 OBJECT-TYPE
			SYNTAX INTEGER
			MAX-ACCESS read-only
			STATUS current
			DESCRIPTION "External humidifier alarm"
			::= { alarms1 181 }

			waterPumpAl_1 OBJECT-TYPE
			SYNTAX INTEGER
			MAX-ACCESS read-only
			STATUS current
			DESCRIPTION "Water pump alarm"
			::= { alarms1 182 }

			condUnitGAl_1 OBJECT-TYPE
			SYNTAX INTEGER
			MAX-ACCESS read-only
			STATUS current
			DESCRIPTION "Motocondenser alarm"
			::= { alarms1 183 }

			gasLeakAl_1 OBJECT-TYPE
			SYNTAX INTEGER
			MAX-ACCESS read-only
			STATUS current
			DESCRIPTION "Refrigerant leak alarm"
			::= { alarms1 184 }

			powerSuppAl_1 OBJECT-TYPE
			SYNTAX INTEGER
			MAX-ACCESS read-only
			STATUS current
			DESCRIPTION "Power fault alarm"
			::= { alarms1 185 }

			genSoftAl_1 OBJECT-TYPE
			SYNTAX INTEGER
			MAX-ACCESS read-only
			STATUS current
			DESCRIPTION "Not critical generic al."
			::= { alarms1 186 }

			localNetAl_1 OBJECT-TYPE
			SYNTAX INTEGER
			MAX-ACCESS read-only
			STATUS current
			DESCRIPTION "Local network alarm"
			::= { alarms1 187 }

			regHiTempAl_1 OBJECT-TYPE
			SYNTAX INTEGER
			MAX-ACCESS read-only
			STATUS current
			DESCRIPTION "High regulation T.alarm"
			::= { alarms1 188 }

			regLowTempAl_1 OBJECT-TYPE
			SYNTAX INTEGER
			MAX-ACCESS read-only
			STATUS current
			DESCRIPTION "Low regulation T.alarm"
			::= { alarms1 189 }

			hiLimTempAl_1 OBJECT-TYPE
			SYNTAX INTEGER
			MAX-ACCESS read-only
			STATUS current
			DESCRIPTION "High limit temp. alarm"
			::= { alarms1 190 }

			lowLimTempAl_1 OBJECT-TYPE
			SYNTAX INTEGER
			MAX-ACCESS read-only
			STATUS current
			DESCRIPTION "Low limit temp. alarm"
			::= { alarms1 191 }

			retHiHumiAl_1 OBJECT-TYPE
			SYNTAX INTEGER
			MAX-ACCESS read-only
			STATUS current
			DESCRIPTION "High room humidity alarm"
			::= { alarms1 192 }

			retLowHumiAl_1 OBJECT-TYPE
			SYNTAX INTEGER
			MAX-ACCESS read-only
			STATUS current
			DESCRIPTION "Low room humidity alarm"
			::= { alarms1 193 }

			supHiHumiAl_1 OBJECT-TYPE
			SYNTAX INTEGER
			MAX-ACCESS read-only
			STATUS current
			DESCRIPTION "High supp.humidity alarm"
			::= { alarms1 194 }

			supLowHumiAl_1 OBJECT-TYPE
			SYNTAX INTEGER
			MAX-ACCESS read-only
			STATUS current
			DESCRIPTION "Low supp.humidity alarm"
			::= { alarms1 195 }

			probeMod1COM_1 OBJECT-TYPE
			SYNTAX INTEGER
			MAX-ACCESS read-only
			STATUS current
			DESCRIPTION "Module 1 communication"
			::= { alarms1 196 }

			prMod1err1_1 OBJECT-TYPE
			SYNTAX INTEGER
			MAX-ACCESS read-only
			STATUS current
			DESCRIPTION "Module 1 probe 1 alarm"
			::= { alarms1 197 }

			prMod1err2_1 OBJECT-TYPE
			SYNTAX INTEGER
			MAX-ACCESS read-only
			STATUS current
			DESCRIPTION "Module 1 probe 2 alarm"
			::= { alarms1 198 }

			prMod1err3_1 OBJECT-TYPE
			SYNTAX INTEGER
			MAX-ACCESS read-only
			STATUS current
			DESCRIPTION "Module 1 probe 3 alarm"
			::= { alarms1 199 }

			prMod1err4_1 OBJECT-TYPE
			SYNTAX INTEGER
			MAX-ACCESS read-only
			STATUS current
			DESCRIPTION "Module 1 probe 4 alarm"
			::= { alarms1 200 }

			prMod1err5_1 OBJECT-TYPE
			SYNTAX INTEGER
			MAX-ACCESS read-only
			STATUS current
			DESCRIPTION "Module 1 probe 5 alarm"
			::= { alarms1 201 }

			prMod1err6_1 OBJECT-TYPE
			SYNTAX INTEGER
			MAX-ACCESS read-only
			STATUS current
			DESCRIPTION "Module 1 probe 6 alarm"
			::= { alarms1 202 }

			probeMod2COM_1 OBJECT-TYPE
			SYNTAX INTEGER
			MAX-ACCESS read-only
			STATUS current
			DESCRIPTION "Module 2 communication"
			::= { alarms1 203 }

			prMod2err1_1 OBJECT-TYPE
			SYNTAX INTEGER
			MAX-ACCESS read-only
			STATUS current
			DESCRIPTION "Module 2 probe 1 alarm"
			::= { alarms1 204 }

			prMod2err2_1 OBJECT-TYPE
			SYNTAX INTEGER
			MAX-ACCESS read-only
			STATUS current
			DESCRIPTION "Module 2 probe 2 alarm"
			::= { alarms1 205 }

			prMod2err3_1 OBJECT-TYPE
			SYNTAX INTEGER
			MAX-ACCESS read-only
			STATUS current
			DESCRIPTION "Module 2 probe 3 alarm"
			::= { alarms1 206 }

			prMod2err4_1 OBJECT-TYPE
			SYNTAX INTEGER
			MAX-ACCESS read-only
			STATUS current
			DESCRIPTION "Module 2 probe 4 alarm"
			::= { alarms1 207 }

			prMod2err5_1 OBJECT-TYPE
			SYNTAX INTEGER
			MAX-ACCESS read-only
			STATUS current
			DESCRIPTION "Module 2 probe 5 alarm"
			::= { alarms1 208 }

			prMod2err6_1 OBJECT-TYPE
			SYNTAX INTEGER
			MAX-ACCESS read-only
			STATUS current
			DESCRIPTION "Module 2 probe 6 alarm"
			::= { alarms1 209 }

			probeMod3COM_1 OBJECT-TYPE
			SYNTAX INTEGER
			MAX-ACCESS read-only
			STATUS current
			DESCRIPTION "Module 3 communication"
			::= { alarms1 210 }

			prMod3err1_1 OBJECT-TYPE
			SYNTAX INTEGER
			MAX-ACCESS read-only
			STATUS current
			DESCRIPTION "Module 3 probe 1 alarm"
			::= { alarms1 211 }

			prMod3err2_1 OBJECT-TYPE
			SYNTAX INTEGER
			MAX-ACCESS read-only
			STATUS current
			DESCRIPTION "Module 3 probe 2 alarm"
			::= { alarms1 212 }

			prMod3err3_1 OBJECT-TYPE
			SYNTAX INTEGER
			MAX-ACCESS read-only
			STATUS current
			DESCRIPTION "Module 3 probe 3 alarm"
			::= { alarms1 213 }

			prMod3err4_1 OBJECT-TYPE
			SYNTAX INTEGER
			MAX-ACCESS read-only
			STATUS current
			DESCRIPTION "Module 3 probe 4 alarm"
			::= { alarms1 214 }

			prMod3err5_1 OBJECT-TYPE
			SYNTAX INTEGER
			MAX-ACCESS read-only
			STATUS current
			DESCRIPTION "Module 3 probe 5 alarm"
			::= { alarms1 215 }

			prMod3err6_1 OBJECT-TYPE
			SYNTAX INTEGER
			MAX-ACCESS read-only
			STATUS current
			DESCRIPTION "Module 3 probe 6 alarm"
			::= { alarms1 216 }

	node2 OBJECT IDENTIFIER  ::= { tecnairlv 2 }

		traps2 OBJECT IDENTIFIER  ::= { node2 0 }

			generalAlTrap_2  NOTIFICATION-TYPE
			OBJECTS
			{
			generalAl_2
			}
			STATUS   current
			DESCRIPTION "General alarams"
			::= { traps2 1 }

			notCriticalAlTrap_2  NOTIFICATION-TYPE
			OBJECTS
			{
			notCriticalAl_2
			}
			STATUS   current
			DESCRIPTION "Not critical alarms"
			::= { traps2 2 }

			criticalAlTrap_2  NOTIFICATION-TYPE
			OBJECTS
			{
			criticalAl_2
			}
			STATUS   current
			DESCRIPTION "Critical alarms"
			::= { traps2 3 }

			fansAlTrap_2  NOTIFICATION-TYPE
			OBJECTS
			{
			fansAl_2
			}
			STATUS   current
			DESCRIPTION "Fans alarms"
			::= { traps2 4 }

			compAlTrap_2  NOTIFICATION-TYPE
			OBJECTS
			{
			compAl_2
			}
			STATUS   current
			DESCRIPTION "Compressors alarms"
			::= { traps2 5 }

			temperatureAlTrap_2  NOTIFICATION-TYPE
			OBJECTS
			{
			temperatureAl_2
			}
			STATUS   current
			DESCRIPTION "Temperature alarms"
			::= { traps2 6 }

			humidityAlTrap_2  NOTIFICATION-TYPE
			OBJECTS
			{
			humidityAl_2
			}
			STATUS   current
			DESCRIPTION "Humidity alarms"
			::= { traps2 7 }

			damperAlTrap_2  NOTIFICATION-TYPE
			OBJECTS
			{
			damperAl_2
			}
			STATUS   current
			DESCRIPTION "Damper status alarm"
			::= { traps2 8 }

			fireSmokeAlTrap_2  NOTIFICATION-TYPE
			OBJECTS
			{
			fireSmokeAl_2
			}
			STATUS   current
			DESCRIPTION "Fire/Smoke alarm"
			::= { traps2 9 }

			genSeriousAlTrap_2  NOTIFICATION-TYPE
			OBJECTS
			{
			genSeriousAl_2
			}
			STATUS   current
			DESCRIPTION "Critical generic alarm"
			::= { traps2 10 }

			fansGenAlTrap_2  NOTIFICATION-TYPE
			OBJECTS
			{
			fansGenAl_2
			}
			STATUS   current
			DESCRIPTION "General supply fans alarm"
			::= { traps2 11 }

			f1GeneralAlTrap_2  NOTIFICATION-TYPE
			OBJECTS
			{
			f1GeneralAl_2
			}
			STATUS   current
			DESCRIPTION "Fan general alarm 1"
			::= { traps2 12 }

			f1PowerAlTrap_2  NOTIFICATION-TYPE
			OBJECTS
			{
			f1PowerAl_2
			}
			STATUS   current
			DESCRIPTION "Phase failure/undervolt.1"
			::= { traps2 13 }

			f1CommAlTrap_2  NOTIFICATION-TYPE
			OBJECTS
			{
			f1CommAl_2
			}
			STATUS   current
			DESCRIPTION "Communication 1"
			::= { traps2 14 }

			f1HighTempAlTrap_2  NOTIFICATION-TYPE
			OBJECTS
			{
			f1HighTempAl_2
			}
			STATUS   current
			DESCRIPTION "Power mod overheated 1"
			::= { traps2 15 }

			f1NetComAlTrap_2  NOTIFICATION-TYPE
			OBJECTS
			{
			f1NetComAl_2
			}
			STATUS   current
			DESCRIPTION "Master/Slave com. 1"
			::= { traps2 16 }

			f1InvRegAlTrap_2  NOTIFICATION-TYPE
			OBJECTS
			{
			f1InvRegAl_2
			}
			STATUS   current
			DESCRIPTION "Regulation module 1"
			::= { traps2 17 }

			f1HighMotTempAlTrap_2  NOTIFICATION-TYPE
			OBJECTS
			{
			f1HighMotTempAl_2
			}
			STATUS   current
			DESCRIPTION "Motor overheated 1"
			::= { traps2 18 }

			f1HallSensAlTrap_2  NOTIFICATION-TYPE
			OBJECTS
			{
			f1HallSensAl_2
			}
			STATUS   current
			DESCRIPTION "Hall sensor error 1"
			::= { traps2 19 }

			f1OverloadAlTrap_2  NOTIFICATION-TYPE
			OBJECTS
			{
			f1OverloadAl_2
			}
			STATUS   current
			DESCRIPTION "Locked motor 1"
			::= { traps2 20 }

			f1LowDCAlTrap_2  NOTIFICATION-TYPE
			OBJECTS
			{
			f1LowDCAl_2
			}
			STATUS   current
			DESCRIPTION "Low DC 1"
			::= { traps2 21 }

			f2GeneralAlTrap_2  NOTIFICATION-TYPE
			OBJECTS
			{
			f2GeneralAl_2
			}
			STATUS   current
			DESCRIPTION "Fan general alarm 2"
			::= { traps2 22 }

			f2PowerAlTrap_2  NOTIFICATION-TYPE
			OBJECTS
			{
			f2PowerAl_2
			}
			STATUS   current
			DESCRIPTION "Phase failure/undervolt.2"
			::= { traps2 23 }

			f2CommAlTrap_2  NOTIFICATION-TYPE
			OBJECTS
			{
			f2CommAl_2
			}
			STATUS   current
			DESCRIPTION "Communication 2"
			::= { traps2 24 }

			f2HighTempAlTrap_2  NOTIFICATION-TYPE
			OBJECTS
			{
			f2HighTempAl_2
			}
			STATUS   current
			DESCRIPTION "Power mod overheated 2"
			::= { traps2 25 }

			f2NetComAlTrap_2  NOTIFICATION-TYPE
			OBJECTS
			{
			f2NetComAl_2
			}
			STATUS   current
			DESCRIPTION "Master/Slave com. 2"
			::= { traps2 26 }

			f2InvRegAlTrap_2  NOTIFICATION-TYPE
			OBJECTS
			{
			f2InvRegAl_2
			}
			STATUS   current
			DESCRIPTION "Regulation module 2"
			::= { traps2 27 }

			f2HighMotTempAlTrap_2  NOTIFICATION-TYPE
			OBJECTS
			{
			f2HighMotTempAl_2
			}
			STATUS   current
			DESCRIPTION "Motor overheated 2"
			::= { traps2 28 }

			f2HallSensAlTrap_2  NOTIFICATION-TYPE
			OBJECTS
			{
			f2HallSensAl_2
			}
			STATUS   current
			DESCRIPTION "Hall sensor error 2"
			::= { traps2 29 }

			f2OverloadAlTrap_2  NOTIFICATION-TYPE
			OBJECTS
			{
			f2OverloadAl_2
			}
			STATUS   current
			DESCRIPTION "Locked motor 2"
			::= { traps2 30 }

			f2LowDCAlTrap_2  NOTIFICATION-TYPE
			OBJECTS
			{
			f2LowDCAl_2
			}
			STATUS   current
			DESCRIPTION "Low DC 2"
			::= { traps2 31 }

			f3GeneralAlTrap_2  NOTIFICATION-TYPE
			OBJECTS
			{
			f3GeneralAl_2
			}
			STATUS   current
			DESCRIPTION "Fan general alarm 3"
			::= { traps2 32 }

			f3PowerAlTrap_2  NOTIFICATION-TYPE
			OBJECTS
			{
			f3PowerAl_2
			}
			STATUS   current
			DESCRIPTION "Phase failure/undervolt.3"
			::= { traps2 33 }

			f3CommAlTrap_2  NOTIFICATION-TYPE
			OBJECTS
			{
			f3CommAl_2
			}
			STATUS   current
			DESCRIPTION "Communication 3"
			::= { traps2 34 }

			f3HighTempAlTrap_2  NOTIFICATION-TYPE
			OBJECTS
			{
			f3HighTempAl_2
			}
			STATUS   current
			DESCRIPTION "Power mod overheated 3"
			::= { traps2 35 }

			f3NetComAlTrap_2  NOTIFICATION-TYPE
			OBJECTS
			{
			f3NetComAl_2
			}
			STATUS   current
			DESCRIPTION "Master/Slave com. 3"
			::= { traps2 36 }

			f3InvRegAlTrap_2  NOTIFICATION-TYPE
			OBJECTS
			{
			f3InvRegAl_2
			}
			STATUS   current
			DESCRIPTION "Regulation module 3"
			::= { traps2 37 }

			f3HighMotTempAlTrap_2  NOTIFICATION-TYPE
			OBJECTS
			{
			f3HighMotTempAl_2
			}
			STATUS   current
			DESCRIPTION "Motor overheated 3"
			::= { traps2 38 }

			f3HallSensAlTrap_2  NOTIFICATION-TYPE
			OBJECTS
			{
			f3HallSensAl_2
			}
			STATUS   current
			DESCRIPTION "Hall sensor error 3"
			::= { traps2 39 }

			f3OverloadAlTrap_2  NOTIFICATION-TYPE
			OBJECTS
			{
			f3OverloadAl_2
			}
			STATUS   current
			DESCRIPTION "Locked motor 3"
			::= { traps2 40 }

			f3LowDCAlTrap_2  NOTIFICATION-TYPE
			OBJECTS
			{
			f3LowDCAl_2
			}
			STATUS   current
			DESCRIPTION "Low DC 3"
			::= { traps2 41 }

			f4GeneralAlTrap_2  NOTIFICATION-TYPE
			OBJECTS
			{
			f4GeneralAl_2
			}
			STATUS   current
			DESCRIPTION "Fan general alarm 4"
			::= { traps2 42 }

			f4PowerAlTrap_2  NOTIFICATION-TYPE
			OBJECTS
			{
			f4PowerAl_2
			}
			STATUS   current
			DESCRIPTION "Phase failure/undervolt.4"
			::= { traps2 43 }

			f4CommAlTrap_2  NOTIFICATION-TYPE
			OBJECTS
			{
			f4CommAl_2
			}
			STATUS   current
			DESCRIPTION "Communication 4"
			::= { traps2 44 }

			f4HighTempAlTrap_2  NOTIFICATION-TYPE
			OBJECTS
			{
			f4HighTempAl_2
			}
			STATUS   current
			DESCRIPTION "Power mod overheated 4"
			::= { traps2 45 }

			f4NetComAlTrap_2  NOTIFICATION-TYPE
			OBJECTS
			{
			f4NetComAl_2
			}
			STATUS   current
			DESCRIPTION "Master/Slave com. 4"
			::= { traps2 46 }

			f4InvRegAlTrap_2  NOTIFICATION-TYPE
			OBJECTS
			{
			f4InvRegAl_2
			}
			STATUS   current
			DESCRIPTION "Regulation module 4"
			::= { traps2 47 }

			f4HighMotTempAlTrap_2  NOTIFICATION-TYPE
			OBJECTS
			{
			f4HighMotTempAl_2
			}
			STATUS   current
			DESCRIPTION "Motor overheated 4"
			::= { traps2 48 }

			f4HallSensAlTrap_2  NOTIFICATION-TYPE
			OBJECTS
			{
			f4HallSensAl_2
			}
			STATUS   current
			DESCRIPTION "Hall sensor error 4"
			::= { traps2 49 }

			f4OverloadAlTrap_2  NOTIFICATION-TYPE
			OBJECTS
			{
			f4OverloadAl_2
			}
			STATUS   current
			DESCRIPTION "Locked motor 4"
			::= { traps2 50 }

			f4LowDCAlTrap_2  NOTIFICATION-TYPE
			OBJECTS
			{
			f4LowDCAl_2
			}
			STATUS   current
			DESCRIPTION "Low DC 4"
			::= { traps2 51 }

			f5GeneralAlTrap_2  NOTIFICATION-TYPE
			OBJECTS
			{
			f5GeneralAl_2
			}
			STATUS   current
			DESCRIPTION "Fan general alarm 5"
			::= { traps2 52 }

			f5PowerAlTrap_2  NOTIFICATION-TYPE
			OBJECTS
			{
			f5PowerAl_2
			}
			STATUS   current
			DESCRIPTION "Phase failure/undervolt.5"
			::= { traps2 53 }

			f5CommAlTrap_2  NOTIFICATION-TYPE
			OBJECTS
			{
			f5CommAl_2
			}
			STATUS   current
			DESCRIPTION "Communication 5"
			::= { traps2 54 }

			f5HighTempAlTrap_2  NOTIFICATION-TYPE
			OBJECTS
			{
			f5HighTempAl_2
			}
			STATUS   current
			DESCRIPTION "Power mod overheated 5"
			::= { traps2 55 }

			f5NetComAlTrap_2  NOTIFICATION-TYPE
			OBJECTS
			{
			f5NetComAl_2
			}
			STATUS   current
			DESCRIPTION "Master/Slave com. 5"
			::= { traps2 56 }

			f5InvRegAlTrap_2  NOTIFICATION-TYPE
			OBJECTS
			{
			f5InvRegAl_2
			}
			STATUS   current
			DESCRIPTION "Regulation module 5"
			::= { traps2 57 }

			f5HighMotTempAlTrap_2  NOTIFICATION-TYPE
			OBJECTS
			{
			f5HighMotTempAl_2
			}
			STATUS   current
			DESCRIPTION "Motor overheated 5"
			::= { traps2 58 }

			f5HallSensAlTrap_2  NOTIFICATION-TYPE
			OBJECTS
			{
			f5HallSensAl_2
			}
			STATUS   current
			DESCRIPTION "Hall sensor error 5"
			::= { traps2 59 }

			f5OverloadAlTrap_2  NOTIFICATION-TYPE
			OBJECTS
			{
			f5OverloadAl_2
			}
			STATUS   current
			DESCRIPTION "Locked motor 5"
			::= { traps2 60 }

			f5LowDCAlTrap_2  NOTIFICATION-TYPE
			OBJECTS
			{
			f5LowDCAl_2
			}
			STATUS   current
			DESCRIPTION "Low DC 5"
			::= { traps2 61 }

			f6GeneralAlTrap_2  NOTIFICATION-TYPE
			OBJECTS
			{
			f6GeneralAl_2
			}
			STATUS   current
			DESCRIPTION "Fan general alarm 6"
			::= { traps2 62 }

			f6PowerAlTrap_2  NOTIFICATION-TYPE
			OBJECTS
			{
			f6PowerAl_2
			}
			STATUS   current
			DESCRIPTION "Phase failure/undervolt.6"
			::= { traps2 63 }

			f6CommAlTrap_2  NOTIFICATION-TYPE
			OBJECTS
			{
			f6CommAl_2
			}
			STATUS   current
			DESCRIPTION "Communication 6"
			::= { traps2 64 }

			f6HighTempAlTrap_2  NOTIFICATION-TYPE
			OBJECTS
			{
			f6HighTempAl_2
			}
			STATUS   current
			DESCRIPTION "Power mod overheated 6"
			::= { traps2 65 }

			f6NetComAlTrap_2  NOTIFICATION-TYPE
			OBJECTS
			{
			f6NetComAl_2
			}
			STATUS   current
			DESCRIPTION "Master/Slave com. 6"
			::= { traps2 66 }

			f6InvRegAlTrap_2  NOTIFICATION-TYPE
			OBJECTS
			{
			f6InvRegAl_2
			}
			STATUS   current
			DESCRIPTION "Regulation module 6"
			::= { traps2 67 }

			f6HighMotTempAlTrap_2  NOTIFICATION-TYPE
			OBJECTS
			{
			f6HighMotTempAl_2
			}
			STATUS   current
			DESCRIPTION "Motor overheated 6"
			::= { traps2 68 }

			f6HallSensAlTrap_2  NOTIFICATION-TYPE
			OBJECTS
			{
			f6HallSensAl_2
			}
			STATUS   current
			DESCRIPTION "Hall sensor error 6"
			::= { traps2 69 }

			f6OverloadAlTrap_2  NOTIFICATION-TYPE
			OBJECTS
			{
			f6OverloadAl_2
			}
			STATUS   current
			DESCRIPTION "Locked motor 6"
			::= { traps2 70 }

			f6LowDCAlTrap_2  NOTIFICATION-TYPE
			OBJECTS
			{
			f6LowDCAl_2
			}
			STATUS   current
			DESCRIPTION "Low DC 6"
			::= { traps2 71 }

			f7GeneralAlTrap_2  NOTIFICATION-TYPE
			OBJECTS
			{
			f7GeneralAl_2
			}
			STATUS   current
			DESCRIPTION "Fan general alarm 7"
			::= { traps2 72 }

			f7PowerAlTrap_2  NOTIFICATION-TYPE
			OBJECTS
			{
			f7PowerAl_2
			}
			STATUS   current
			DESCRIPTION "Phase failure/undervolt.7"
			::= { traps2 73 }

			f7CommAlTrap_2  NOTIFICATION-TYPE
			OBJECTS
			{
			f7CommAl_2
			}
			STATUS   current
			DESCRIPTION "Communication 7"
			::= { traps2 74 }

			f7HighTempAlTrap_2  NOTIFICATION-TYPE
			OBJECTS
			{
			f7HighTempAl_2
			}
			STATUS   current
			DESCRIPTION "Power mod overheated 7"
			::= { traps2 75 }

			f7NetComAlTrap_2  NOTIFICATION-TYPE
			OBJECTS
			{
			f7NetComAl_2
			}
			STATUS   current
			DESCRIPTION "Master/Slave com. 7"
			::= { traps2 76 }

			f7InvRegAlTrap_2  NOTIFICATION-TYPE
			OBJECTS
			{
			f7InvRegAl_2
			}
			STATUS   current
			DESCRIPTION "Regulation module 7"
			::= { traps2 77 }

			f7HighMotTempAlTrap_2  NOTIFICATION-TYPE
			OBJECTS
			{
			f7HighMotTempAl_2
			}
			STATUS   current
			DESCRIPTION "Motor overheated 7"
			::= { traps2 78 }

			f7HallSensAlTrap_2  NOTIFICATION-TYPE
			OBJECTS
			{
			f7HallSensAl_2
			}
			STATUS   current
			DESCRIPTION "Hall sensor error 7"
			::= { traps2 79 }

			f7OverloadAlTrap_2  NOTIFICATION-TYPE
			OBJECTS
			{
			f7OverloadAl_2
			}
			STATUS   current
			DESCRIPTION "Locked motor 7"
			::= { traps2 80 }

			f7LowDCAlTrap_2  NOTIFICATION-TYPE
			OBJECTS
			{
			f7LowDCAl_2
			}
			STATUS   current
			DESCRIPTION "Low DC 7"
			::= { traps2 81 }

			f8GeneralAlTrap_2  NOTIFICATION-TYPE
			OBJECTS
			{
			f8GeneralAl_2
			}
			STATUS   current
			DESCRIPTION "Fan general alarm 8"
			::= { traps2 82 }

			f8PowerAlTrap_2  NOTIFICATION-TYPE
			OBJECTS
			{
			f8PowerAl_2
			}
			STATUS   current
			DESCRIPTION "Phase failure/undervolt.8"
			::= { traps2 83 }

			f8CommAlTrap_2  NOTIFICATION-TYPE
			OBJECTS
			{
			f8CommAl_2
			}
			STATUS   current
			DESCRIPTION "Communication 8"
			::= { traps2 84 }

			f8HighTempAlTrap_2  NOTIFICATION-TYPE
			OBJECTS
			{
			f8HighTempAl_2
			}
			STATUS   current
			DESCRIPTION "Power mod overheated 8"
			::= { traps2 85 }

			f8NetComAlTrap_2  NOTIFICATION-TYPE
			OBJECTS
			{
			f8NetComAl_2
			}
			STATUS   current
			DESCRIPTION "Master/Slave com. 8"
			::= { traps2 86 }

			f8InvRegAlTrap_2  NOTIFICATION-TYPE
			OBJECTS
			{
			f8InvRegAl_2
			}
			STATUS   current
			DESCRIPTION "Regulation module 8"
			::= { traps2 87 }

			f8HighMotTempAlTrap_2  NOTIFICATION-TYPE
			OBJECTS
			{
			f8HighMotTempAl_2
			}
			STATUS   current
			DESCRIPTION "Motor overheated 8"
			::= { traps2 88 }

			f8HallSensAlTrap_2  NOTIFICATION-TYPE
			OBJECTS
			{
			f8HallSensAl_2
			}
			STATUS   current
			DESCRIPTION "Hall sensor error 8"
			::= { traps2 89 }

			f8OverloadAlTrap_2  NOTIFICATION-TYPE
			OBJECTS
			{
			f8OverloadAl_2
			}
			STATUS   current
			DESCRIPTION "Locked motor 8"
			::= { traps2 90 }

			f8LowDCAlTrap_2  NOTIFICATION-TYPE
			OBJECTS
			{
			f8LowDCAl_2
			}
			STATUS   current
			DESCRIPTION "Low DC 8"
			::= { traps2 91 }

			f9InverterAlTrap_2  NOTIFICATION-TYPE
			OBJECTS
			{
			f9InverterAl_2
			}
			STATUS   current
			DESCRIPTION "Fan general alarm 9"
			::= { traps2 92 }

			f9PowerAlTrap_2  NOTIFICATION-TYPE
			OBJECTS
			{
			f9PowerAl_2
			}
			STATUS   current
			DESCRIPTION "Phase failure/undervolt.9"
			::= { traps2 93 }

			f9CommAlTrap_2  NOTIFICATION-TYPE
			OBJECTS
			{
			f9CommAl_2
			}
			STATUS   current
			DESCRIPTION "Communication 9"
			::= { traps2 94 }

			f9HighTempAlTrap_2  NOTIFICATION-TYPE
			OBJECTS
			{
			f9HighTempAl_2
			}
			STATUS   current
			DESCRIPTION "Power mod overheated 9"
			::= { traps2 95 }

			f9NetComAlTrap_2  NOTIFICATION-TYPE
			OBJECTS
			{
			f9NetComAl_2
			}
			STATUS   current
			DESCRIPTION "Master/Slave com. 9"
			::= { traps2 96 }

			f9InvRegAlTrap_2  NOTIFICATION-TYPE
			OBJECTS
			{
			f9InvRegAl_2
			}
			STATUS   current
			DESCRIPTION "Regulation module 9"
			::= { traps2 97 }

			f9HighMotTempAlTrap_2  NOTIFICATION-TYPE
			OBJECTS
			{
			f9HighMotTempAl_2
			}
			STATUS   current
			DESCRIPTION "Motor overheated 9"
			::= { traps2 98 }

			f9HallSensAlTrap_2  NOTIFICATION-TYPE
			OBJECTS
			{
			f9HallSensAl_2
			}
			STATUS   current
			DESCRIPTION "Hall sensor error 9"
			::= { traps2 99 }

			f9OverloadAlTrap_2  NOTIFICATION-TYPE
			OBJECTS
			{
			f9OverloadAl_2
			}
			STATUS   current
			DESCRIPTION "Locked motor 9"
			::= { traps2 100 }

			f9LowDCAlTrap_2  NOTIFICATION-TYPE
			OBJECTS
			{
			f9LowDCAl_2
			}
			STATUS   current
			DESCRIPTION "Low DC 9"
			::= { traps2 101 }

			f10GeneralAlTrap_2  NOTIFICATION-TYPE
			OBJECTS
			{
			f10GeneralAl_2
			}
			STATUS   current
			DESCRIPTION "Fan general alarm 10"
			::= { traps2 102 }

			f10PowerAlTrap_2  NOTIFICATION-TYPE
			OBJECTS
			{
			f10PowerAl_2
			}
			STATUS   current
			DESCRIPTION "Phase failure/undervolt.10"
			::= { traps2 103 }

			f10CommAlTrap_2  NOTIFICATION-TYPE
			OBJECTS
			{
			f10CommAl_2
			}
			STATUS   current
			DESCRIPTION "Communication 10"
			::= { traps2 104 }

			f10HighTempAlTrap_2  NOTIFICATION-TYPE
			OBJECTS
			{
			f10HighTempAl_2
			}
			STATUS   current
			DESCRIPTION "Power mod overheated 10"
			::= { traps2 105 }

			f10NetComAlTrap_2  NOTIFICATION-TYPE
			OBJECTS
			{
			f10NetComAl_2
			}
			STATUS   current
			DESCRIPTION "Master/Slave com. 10"
			::= { traps2 106 }

			f10InvRegAlTrap_2  NOTIFICATION-TYPE
			OBJECTS
			{
			f10InvRegAl_2
			}
			STATUS   current
			DESCRIPTION "Regulation module 10"
			::= { traps2 107 }

			f10HighMotTAlTrap_2  NOTIFICATION-TYPE
			OBJECTS
			{
			f10HighMotTAl_2
			}
			STATUS   current
			DESCRIPTION "Motor overheated 10"
			::= { traps2 108 }

			f10HallSensAlTrap_2  NOTIFICATION-TYPE
			OBJECTS
			{
			f10HallSensAl_2
			}
			STATUS   current
			DESCRIPTION "Hall sensor error 10"
			::= { traps2 109 }

			f10OverloadAlTrap_2  NOTIFICATION-TYPE
			OBJECTS
			{
			f10OverloadAl_2
			}
			STATUS   current
			DESCRIPTION "Locked motor 10"
			::= { traps2 110 }

			f10LowDCAlTrap_2  NOTIFICATION-TYPE
			OBJECTS
			{
			f10LowDCAl_2
			}
			STATUS   current
			DESCRIPTION "Low DC 10"
			::= { traps2 111 }

			retTempProbAlTrap_2  NOTIFICATION-TYPE
			OBJECTS
			{
			retTempProbAl_2
			}
			STATUS   current
			DESCRIPTION "Return temperature probe"
			::= { traps2 112 }

			supTempProbAlTrap_2  NOTIFICATION-TYPE
			OBJECTS
			{
			supTempProbAl_2
			}
			STATUS   current
			DESCRIPTION "Supply temperature probe"
			::= { traps2 113 }

			retHumProbAlTrap_2  NOTIFICATION-TYPE
			OBJECTS
			{
			retHumProbAl_2
			}
			STATUS   current
			DESCRIPTION "Return humidity probe"
			::= { traps2 114 }

			supHumProbAlTrap_2  NOTIFICATION-TYPE
			OBJECTS
			{
			supHumProbAl_2
			}
			STATUS   current
			DESCRIPTION "Supply humidity probe"
			::= { traps2 115 }

			airPrSensorAlTrap_2  NOTIFICATION-TYPE
			OBJECTS
			{
			airPrSensorAl_2
			}
			STATUS   current
			DESCRIPTION "Air diff.pressure probe"
			::= { traps2 116 }

			watIN1ProbAlTrap_2  NOTIFICATION-TYPE
			OBJECTS
			{
			watIN1ProbAl_2
			}
			STATUS   current
			DESCRIPTION "Water temp. IN1 probe"
			::= { traps2 117 }

			watOUT1ProbAlTrap_2  NOTIFICATION-TYPE
			OBJECTS
			{
			watOUT1ProbAl_2
			}
			STATUS   current
			DESCRIPTION "Water temp. OUT1 probe"
			::= { traps2 118 }

			watIN2ProbAlTrap_2  NOTIFICATION-TYPE
			OBJECTS
			{
			watIN2ProbAl_2
			}
			STATUS   current
			DESCRIPTION "Water temp. IN2 probe"
			::= { traps2 119 }

			watOUT2ProbAlTrap_2  NOTIFICATION-TYPE
			OBJECTS
			{
			watOUT2ProbAl_2
			}
			STATUS   current
			DESCRIPTION "Water temp. OUT2 probe"
			::= { traps2 120 }

			watFlw1ProbAlTrap_2  NOTIFICATION-TYPE
			OBJECTS
			{
			watFlw1ProbAl_2
			}
			STATUS   current
			DESCRIPTION "Water flow1/T.liquid1 pr."
			::= { traps2 121 }

			watFlw2ProbAlTrap_2  NOTIFICATION-TYPE
			OBJECTS
			{
			watFlw2ProbAl_2
			}
			STATUS   current
			DESCRIPTION "Water flow2/T.liquid2 pr."
			::= { traps2 122 }

			dFPSGenAlTrap_2  NOTIFICATION-TYPE
			OBJECTS
			{
			dFPSGenAl_2
			}
			STATUS   current
			DESCRIPTION "Filter diff.press. probe"
			::= { traps2 123 }

			dFPSBrokenAlTrap_2  NOTIFICATION-TYPE
			OBJECTS
			{
			dFPSBrokenAl_2
			}
			STATUS   current
			DESCRIPTION "Breakdown alarm"
			::= { traps2 124 }

			dFPSCablingAlTrap_2  NOTIFICATION-TYPE
			OBJECTS
			{
			dFPSCablingAl_2
			}
			STATUS   current
			DESCRIPTION "Wiring alarm"
			::= { traps2 125 }

			dFPSRangeAlTrap_2  NOTIFICATION-TYPE
			OBJECTS
			{
			dFPSRangeAl_2
			}
			STATUS   current
			DESCRIPTION "Pressure range alarm"
			::= { traps2 126 }

			dFPSADCAlTrap_2  NOTIFICATION-TYPE
			OBJECTS
			{
			dFPSADCAl_2
			}
			STATUS   current
			DESCRIPTION "ADC overload alarm"
			::= { traps2 127 }

			dFPSSettingAlTrap_2  NOTIFICATION-TYPE
			OBJECTS
			{
			dFPSSettingAl_2
			}
			STATUS   current
			DESCRIPTION "Calibration alarm"
			::= { traps2 128 }

			dFPSDCOAlTrap_2  NOTIFICATION-TYPE
			OBJECTS
			{
			dFPSDCOAl_2
			}
			STATUS   current
			DESCRIPTION "DCO alarm"
			::= { traps2 129 }

			dFPSWatchdogAlTrap_2  NOTIFICATION-TYPE
			OBJECTS
			{
			dFPSWatchdogAl_2
			}
			STATUS   current
			DESCRIPTION "Watchdog alarm"
			::= { traps2 130 }

			dFPSCommAlTrap_2  NOTIFICATION-TYPE
			OBJECTS
			{
			dFPSCommAl_2
			}
			STATUS   current
			DESCRIPTION "Communication alarm"
			::= { traps2 131 }

			invCompGenAlTrap_2  NOTIFICATION-TYPE
			OBJECTS
			{
			invCompGenAl_2
			}
			STATUS   current
			DESCRIPTION "DC inverter general alarm"
			::= { traps2 132 }

			invCompCommAlTrap_2  NOTIFICATION-TYPE
			OBJECTS
			{
			invCompCommAl_2
			}
			STATUS   current
			DESCRIPTION "Inverter communication"
			::= { traps2 133 }

			invCompAlCode1Trap_2  NOTIFICATION-TYPE
			OBJECTS
			{
			invCompAlCode1_2
			}
			STATUS   current
			DESCRIPTION "DC Inverter alarm code 1"
			::= { traps2 134 }

			invCompAlCode2Trap_2  NOTIFICATION-TYPE
			OBJECTS
			{
			invCompAlCode2_2
			}
			STATUS   current
			DESCRIPTION "DC Inverter alarm code 2"
			::= { traps2 135 }

			invCompAlCode3Trap_2  NOTIFICATION-TYPE
			OBJECTS
			{
			invCompAlCode3_2
			}
			STATUS   current
			DESCRIPTION "DC Inverter alarm code 3"
			::= { traps2 136 }

			invCompAlCode4Trap_2  NOTIFICATION-TYPE
			OBJECTS
			{
			invCompAlCode4_2
			}
			STATUS   current
			DESCRIPTION "DC Inverter alarm code 4"
			::= { traps2 137 }

			invCompAlCode5Trap_2  NOTIFICATION-TYPE
			OBJECTS
			{
			invCompAlCode5_2
			}
			STATUS   current
			DESCRIPTION "DC Inverter alarm code 5"
			::= { traps2 138 }

			c1ThermAlTrap_2  NOTIFICATION-TYPE
			OBJECTS
			{
			c1ThermAl_2
			}
			STATUS   current
			DESCRIPTION "C1 Thermal alarm"
			::= { traps2 139 }

			c1HighPresAlTrap_2  NOTIFICATION-TYPE
			OBJECTS
			{
			c1HighPresAl_2
			}
			STATUS   current
			DESCRIPTION "C1 High pressure alarm"
			::= { traps2 140 }

			c1LowPresAlTrap_2  NOTIFICATION-TYPE
			OBJECTS
			{
			c1LowPresAl_2
			}
			STATUS   current
			DESCRIPTION "C1 Low pressure alarm"
			::= { traps2 141 }

			c1HighDischAlTrap_2  NOTIFICATION-TYPE
			OBJECTS
			{
			c1HighDischAl_2
			}
			STATUS   current
			DESCRIPTION "C1 High discharge alarm"
			::= { traps2 142 }

			c1LCompRatAlTrap_2  NOTIFICATION-TYPE
			OBJECTS
			{
			c1LCompRatAl_2
			}
			STATUS   current
			DESCRIPTION "C1 low compresion alarm"
			::= { traps2 143 }

			condenser1AlTrap_2  NOTIFICATION-TYPE
			OBJECTS
			{
			condenser1Al_2
			}
			STATUS   current
			DESCRIPTION "Condenser 1 general alarm"
			::= { traps2 144 }

			c1WatFlowAlTrap_2  NOTIFICATION-TYPE
			OBJECTS
			{
			c1WatFlowAl_2
			}
			STATUS   current
			DESCRIPTION "Condenser 1 flow alarm"
			::= { traps2 145 }

			eEV1GenAlTrap_2  NOTIFICATION-TYPE
			OBJECTS
			{
			eEV1GenAl_2
			}
			STATUS   current
			DESCRIPTION "EEV1 general alarm"
			::= { traps2 146 }

			eEV1CommAlTrap_2  NOTIFICATION-TYPE
			OBJECTS
			{
			eEV1CommAl_2
			}
			STATUS   current
			DESCRIPTION "EEV1 communication alarm"
			::= { traps2 147 }

			eEV1SuctProbAlTrap_2  NOTIFICATION-TYPE
			OBJECTS
			{
			eEV1SuctProbAl_2
			}
			STATUS   current
			DESCRIPTION "EEV1 suction temp. probe"
			::= { traps2 148 }

			eEV1EvapProbAlTrap_2  NOTIFICATION-TYPE
			OBJECTS
			{
			eEV1EvapProbAl_2
			}
			STATUS   current
			DESCRIPTION "EEV1 evap. temp. probe"
			::= { traps2 149 }

			eEV1CondProbAlTrap_2  NOTIFICATION-TYPE
			OBJECTS
			{
			eEV1CondProbAl_2
			}
			STATUS   current
			DESCRIPTION "EEV1 condens. temp. probe"
			::= { traps2 150 }

			eEV1DischProbAlTrap_2  NOTIFICATION-TYPE
			OBJECTS
			{
			eEV1DischProbAl_2
			}
			STATUS   current
			DESCRIPTION "EEV1 disch. temp. probe"
			::= { traps2 151 }

			c2ThermAlTrap_2  NOTIFICATION-TYPE
			OBJECTS
			{
			c2ThermAl_2
			}
			STATUS   current
			DESCRIPTION "C2 Thermal alarm"
			::= { traps2 152 }

			c2HighPresAlTrap_2  NOTIFICATION-TYPE
			OBJECTS
			{
			c2HighPresAl_2
			}
			STATUS   current
			DESCRIPTION "C2 High pressure alarm"
			::= { traps2 153 }

			c2LowPresAlTrap_2  NOTIFICATION-TYPE
			OBJECTS
			{
			c2LowPresAl_2
			}
			STATUS   current
			DESCRIPTION "C2 Low pressure alarm"
			::= { traps2 154 }

			c2HighDischAlTrap_2  NOTIFICATION-TYPE
			OBJECTS
			{
			c2HighDischAl_2
			}
			STATUS   current
			DESCRIPTION "C2 High discharge alarm"
			::= { traps2 155 }

			c2LCompRatAlTrap_2  NOTIFICATION-TYPE
			OBJECTS
			{
			c2LCompRatAl_2
			}
			STATUS   current
			DESCRIPTION "C2 low compresion alarm"
			::= { traps2 156 }

			condenser2AlTrap_2  NOTIFICATION-TYPE
			OBJECTS
			{
			condenser2Al_2
			}
			STATUS   current
			DESCRIPTION "Condenser 2 general alarm"
			::= { traps2 157 }

			c2WatFlowAlTrap_2  NOTIFICATION-TYPE
			OBJECTS
			{
			c2WatFlowAl_2
			}
			STATUS   current
			DESCRIPTION "Condenser 2 flow alarm"
			::= { traps2 158 }

			eEV2GenAlTrap_2  NOTIFICATION-TYPE
			OBJECTS
			{
			eEV2GenAl_2
			}
			STATUS   current
			DESCRIPTION "EEV2 general alarm"
			::= { traps2 159 }

			eEV2CommAlTrap_2  NOTIFICATION-TYPE
			OBJECTS
			{
			eEV2CommAl_2
			}
			STATUS   current
			DESCRIPTION "EEV2 communication alarm"
			::= { traps2 160 }

			eEV2SuctProbAlTrap_2  NOTIFICATION-TYPE
			OBJECTS
			{
			eEV2SuctProbAl_2
			}
			STATUS   current
			DESCRIPTION "EEV2 suction temp. probe"
			::= { traps2 161 }

			eEV2EvapProbAlTrap_2  NOTIFICATION-TYPE
			OBJECTS
			{
			eEV2EvapProbAl_2
			}
			STATUS   current
			DESCRIPTION "EEV2 evap. temp. probe"
			::= { traps2 162 }

			eEV2CondProbAlTrap_2  NOTIFICATION-TYPE
			OBJECTS
			{
			eEV2CondProbAl_2
			}
			STATUS   current
			DESCRIPTION "EEV2 condens. temp. probe"
			::= { traps2 163 }

			eEV2DischProbAlTrap_2  NOTIFICATION-TYPE
			OBJECTS
			{
			eEV2DischProbAl_2
			}
			STATUS   current
			DESCRIPTION "EEV2 disch. temp. probe"
			::= { traps2 164 }

			intHumidGenAlTrap_2  NOTIFICATION-TYPE
			OBJECTS
			{
			intHumidGenAl_2
			}
			STATUS   current
			DESCRIPTION "Internal humidifier alarm"
			::= { traps2 165 }

			cPYCommAlTrap_2  NOTIFICATION-TYPE
			OBJECTS
			{
			cPYCommAl_2
			}
			STATUS   current
			DESCRIPTION "Communication alarm"
			::= { traps2 166 }

			cPYMemoryAlTrap_2  NOTIFICATION-TYPE
			OBJECTS
			{
			cPYMemoryAl_2
			}
			STATUS   current
			DESCRIPTION "Memory error alarm"
			::= { traps2 167 }

			cPYParameterAlTrap_2  NOTIFICATION-TYPE
			OBJECTS
			{
			cPYParameterAl_2
			}
			STATUS   current
			DESCRIPTION "Parameters error alarm"
			::= { traps2 168 }

			cPYHighCurrAlTrap_2  NOTIFICATION-TYPE
			OBJECTS
			{
			cPYHighCurrAl_2
			}
			STATUS   current
			DESCRIPTION "Electrodes high current"
			::= { traps2 169 }

			cPYLowSteamAlTrap_2  NOTIFICATION-TYPE
			OBJECTS
			{
			cPYLowSteamAl_2
			}
			STATUS   current
			DESCRIPTION "Low steam product. alarm"
			::= { traps2 170 }

			cPYDrainAlTrap_2  NOTIFICATION-TYPE
			OBJECTS
			{
			cPYDrainAl_2
			}
			STATUS   current
			DESCRIPTION "Drain loss alarm"
			::= { traps2 171 }

			cPYMaintAlTrap_2  NOTIFICATION-TYPE
			OBJECTS
			{
			cPYMaintAl_2
			}
			STATUS   current
			DESCRIPTION "Maintenance hours alarm"
			::= { traps2 172 }

			cPYNoWaterAlTrap_2  NOTIFICATION-TYPE
			OBJECTS
			{
			cPYNoWaterAl_2
			}
			STATUS   current
			DESCRIPTION "Water loss alarm"
			::= { traps2 173 }

			cPYCylMaintAlTrap_2  NOTIFICATION-TYPE
			OBJECTS
			{
			cPYCylMaintAl_2
			}
			STATUS   current
			DESCRIPTION "Cylinder mainten. alarm"
			::= { traps2 174 }

			cPYDirtyCylAlTrap_2  NOTIFICATION-TYPE
			OBJECTS
			{
			cPYDirtyCylAl_2
			}
			STATUS   current
			DESCRIPTION "Exaust cylinder alarm"
			::= { traps2 175 }

			cPYFoamAlTrap_2  NOTIFICATION-TYPE
			OBJECTS
			{
			cPYFoamAl_2
			}
			STATUS   current
			DESCRIPTION "Foam presence alarm"
			::= { traps2 176 }

			cPYLifeTimeAlTrap_2  NOTIFICATION-TYPE
			OBJECTS
			{
			cPYLifeTimeAl_2
			}
			STATUS   current
			DESCRIPTION "Life time expired alarm"
			::= { traps2 177 }

			cPYHighWatLevAlTrap_2  NOTIFICATION-TYPE
			OBJECTS
			{
			cPYHighWatLevAl_2
			}
			STATUS   current
			DESCRIPTION "High water level alarm"
			::= { traps2 178 }

			cPYHWatCondAlTrap_2  NOTIFICATION-TYPE
			OBJECTS
			{
			cPYHWatCondAl_2
			}
			STATUS   current
			DESCRIPTION "High conductivity alarm"
			::= { traps2 179 }

			cPYConnectionAlTrap_2  NOTIFICATION-TYPE
			OBJECTS
			{
			cPYConnectionAl_2
			}
			STATUS   current
			DESCRIPTION "Connection error alarm"
			::= { traps2 180 }

			watPresAlTrap_2  NOTIFICATION-TYPE
			OBJECTS
			{
			watPresAl_2
			}
			STATUS   current
			DESCRIPTION "Water presence alarm"
			::= { traps2 181 }

			drainPumpAlTrap_2  NOTIFICATION-TYPE
			OBJECTS
			{
			drainPumpAl_2
			}
			STATUS   current
			DESCRIPTION "Drain pump alarm"
			::= { traps2 182 }

			elHeatAlTrap_2  NOTIFICATION-TYPE
			OBJECTS
			{
			elHeatAl_2
			}
			STATUS   current
			DESCRIPTION "Electric heater alarm"
			::= { traps2 183 }

			filterAlTrap_2  NOTIFICATION-TYPE
			OBJECTS
			{
			filterAl_2
			}
			STATUS   current
			DESCRIPTION "Dirty filter alarm"
			::= { traps2 184 }

			dryCoolerAlTrap_2  NOTIFICATION-TYPE
			OBJECTS
			{
			dryCoolerAl_2
			}
			STATUS   current
			DESCRIPTION "Dry cooler alarm"
			::= { traps2 185 }

			extHumidAlTrap_2  NOTIFICATION-TYPE
			OBJECTS
			{
			extHumidAl_2
			}
			STATUS   current
			DESCRIPTION "External humidifier alarm"
			::= { traps2 186 }

			waterPumpAlTrap_2  NOTIFICATION-TYPE
			OBJECTS
			{
			waterPumpAl_2
			}
			STATUS   current
			DESCRIPTION "Water pump alarm"
			::= { traps2 187 }

			condUnitGenAlTrap_2  NOTIFICATION-TYPE
			OBJECTS
			{
			condUnitGenAl_2
			}
			STATUS   current
			DESCRIPTION "Motocondenser alarm"
			::= { traps2 188 }

			gasLeakAlTrap_2  NOTIFICATION-TYPE
			OBJECTS
			{
			gasLeakAl_2
			}
			STATUS   current
			DESCRIPTION "Refrigerant leak alarm"
			::= { traps2 189 }

			powerSupplyAlTrap_2  NOTIFICATION-TYPE
			OBJECTS
			{
			powerSupplyAl_2
			}
			STATUS   current
			DESCRIPTION "Power fault alarm"
			::= { traps2 190 }

			genericSoftAlTrap_2  NOTIFICATION-TYPE
			OBJECTS
			{
			genericSoftAl_2
			}
			STATUS   current
			DESCRIPTION "Not critical generic al."
			::= { traps2 191 }

			localNetworkAlTrap_2  NOTIFICATION-TYPE
			OBJECTS
			{
			localNetworkAl_2
			}
			STATUS   current
			DESCRIPTION "Local network alarm"
			::= { traps2 192 }

			regHighTempAlTrap_2  NOTIFICATION-TYPE
			OBJECTS
			{
			regHighTempAl_2
			}
			STATUS   current
			DESCRIPTION "High regulation T.alarm"
			::= { traps2 193 }

			regLowTempAlTrap_2  NOTIFICATION-TYPE
			OBJECTS
			{
			regLowTempAl_2
			}
			STATUS   current
			DESCRIPTION "Low regulation T.alarm"
			::= { traps2 194 }

			highLimTempAlTrap_2  NOTIFICATION-TYPE
			OBJECTS
			{
			highLimTempAl_2
			}
			STATUS   current
			DESCRIPTION "High limit temp. alarm"
			::= { traps2 195 }

			lowLimTempAlTrap_2  NOTIFICATION-TYPE
			OBJECTS
			{
			lowLimTempAl_2
			}
			STATUS   current
			DESCRIPTION "Low limit temp. alarm"
			::= { traps2 196 }

			retHighHumiAlTrap_2  NOTIFICATION-TYPE
			OBJECTS
			{
			retHighHumiAl_2
			}
			STATUS   current
			DESCRIPTION "High room humidity alarm"
			::= { traps2 197 }

			retLowHumiAlTrap_2  NOTIFICATION-TYPE
			OBJECTS
			{
			retLowHumiAl_2
			}
			STATUS   current
			DESCRIPTION "Low room humidity alarm"
			::= { traps2 198 }

			supHighHumiAlTrap_2  NOTIFICATION-TYPE
			OBJECTS
			{
			supHighHumiAl_2
			}
			STATUS   current
			DESCRIPTION "High supp.humidity alarm"
			::= { traps2 199 }

			supLowHumiAlTrap_2  NOTIFICATION-TYPE
			OBJECTS
			{
			supLowHumiAl_2
			}
			STATUS   current
			DESCRIPTION "Low supp.humidity alarm"
			::= { traps2 200 }

			probeMod1COMTrap_2  NOTIFICATION-TYPE
			OBJECTS
			{
			probeMod1COM_2
			}
			STATUS   current
			DESCRIPTION "Module 1 communication"
			::= { traps2 201 }

			probeMod1err1Trap_2  NOTIFICATION-TYPE
			OBJECTS
			{
			probeMod1err1_2
			}
			STATUS   current
			DESCRIPTION "Module 1 probe 1 alarm"
			::= { traps2 202 }

			probeMod1err2Trap_2  NOTIFICATION-TYPE
			OBJECTS
			{
			probeMod1err2_2
			}
			STATUS   current
			DESCRIPTION "Module 1 probe 2 alarm"
			::= { traps2 203 }

			probeMod1err3Trap_2  NOTIFICATION-TYPE
			OBJECTS
			{
			probeMod1err3_2
			}
			STATUS   current
			DESCRIPTION "Module 1 probe 3 alarm"
			::= { traps2 204 }

			probeMod1err4Trap_2  NOTIFICATION-TYPE
			OBJECTS
			{
			probeMod1err4_2
			}
			STATUS   current
			DESCRIPTION "Module 1 probe 4 alarm"
			::= { traps2 205 }

			probeMod1err5Trap_2  NOTIFICATION-TYPE
			OBJECTS
			{
			probeMod1err5_2
			}
			STATUS   current
			DESCRIPTION "Module 1 probe 5 alarm"
			::= { traps2 206 }

			probeMod1err6Trap_2  NOTIFICATION-TYPE
			OBJECTS
			{
			probeMod1err6_2
			}
			STATUS   current
			DESCRIPTION "Module 1 probe 6 alarm"
			::= { traps2 207 }

			probeMod2COMTrap_2  NOTIFICATION-TYPE
			OBJECTS
			{
			probeMod2COM_2
			}
			STATUS   current
			DESCRIPTION "Module 2 communication"
			::= { traps2 208 }

			probeMod2err1Trap_2  NOTIFICATION-TYPE
			OBJECTS
			{
			probeMod2err1_2
			}
			STATUS   current
			DESCRIPTION "Module 2 probe 1 alarm"
			::= { traps2 209 }

			probeMod2err2Trap_2  NOTIFICATION-TYPE
			OBJECTS
			{
			probeMod2err2_2
			}
			STATUS   current
			DESCRIPTION "Module 2 probe 2 alarm"
			::= { traps2 210 }

			probeMod2err3Trap_2  NOTIFICATION-TYPE
			OBJECTS
			{
			probeMod2err3_2
			}
			STATUS   current
			DESCRIPTION "Module 2 probe 3 alarm"
			::= { traps2 211 }

			probeMod2err4Trap_2  NOTIFICATION-TYPE
			OBJECTS
			{
			probeMod2err4_2
			}
			STATUS   current
			DESCRIPTION "Module 2 probe 4 alarm"
			::= { traps2 212 }

			probeMod2err5Trap_2  NOTIFICATION-TYPE
			OBJECTS
			{
			probeMod2err5_2
			}
			STATUS   current
			DESCRIPTION "Module 2 probe 5 alarm"
			::= { traps2 213 }

			probeMod2err6Trap_2  NOTIFICATION-TYPE
			OBJECTS
			{
			probeMod2err6_2
			}
			STATUS   current
			DESCRIPTION "Module 2 probe 6 alarm"
			::= { traps2 214 }

			probeMod3COMTrap_2  NOTIFICATION-TYPE
			OBJECTS
			{
			probeMod3COM_2
			}
			STATUS   current
			DESCRIPTION "Module 3 communication"
			::= { traps2 215 }

			probeMod3err1Trap_2  NOTIFICATION-TYPE
			OBJECTS
			{
			probeMod3err1_2
			}
			STATUS   current
			DESCRIPTION "Module 3 probe 1 alarm"
			::= { traps2 216 }

			probeMod3err2Trap_2  NOTIFICATION-TYPE
			OBJECTS
			{
			probeMod3err2_2
			}
			STATUS   current
			DESCRIPTION "Module 3 probe 2 alarm"
			::= { traps2 217 }

			probeMod3err3Trap_2  NOTIFICATION-TYPE
			OBJECTS
			{
			probeMod3err3_2
			}
			STATUS   current
			DESCRIPTION "Module 3 probe 3 alarm"
			::= { traps2 218 }

			probeMod3err4Trap_2  NOTIFICATION-TYPE
			OBJECTS
			{
			probeMod3err4_2
			}
			STATUS   current
			DESCRIPTION "Module 3 probe 4 alarm"
			::= { traps2 219 }

			probeMod3err5Trap_2  NOTIFICATION-TYPE
			OBJECTS
			{
			probeMod3err5_2
			}
			STATUS   current
			DESCRIPTION "Module 3 probe 5 alarm"
			::= { traps2 220 }

			probeMod3err6Trap_2  NOTIFICATION-TYPE
			OBJECTS
			{
			probeMod3err6_2
			}
			STATUS   current
			DESCRIPTION "Module 3 probe 6 alarm"
			::= { traps2 221 }

		binaryObjects2 OBJECT IDENTIFIER  ::= { node2 1 }

			damperStatusDI_2 OBJECT-TYPE
			SYNTAX INTEGER
			MAX-ACCESS read-only
			STATUS current
			DESCRIPTION "Motorised damper status"
			::= { binaryObjects2 1 }

			dirtyFilterDI_2 OBJECT-TYPE
			SYNTAX INTEGER
			MAX-ACCESS read-only
			STATUS current
			DESCRIPTION "Dirty filter alarm"
			::= { binaryObjects2 2 }

			remoteOffDI_2 OBJECT-TYPE
			SYNTAX INTEGER
			MAX-ACCESS read-only
			STATUS current
			DESCRIPTION "Remote OFF status"
			::= { binaryObjects2 3 }

			elHeaterAlarmDI_2 OBJECT-TYPE
			SYNTAX INTEGER
			MAX-ACCESS read-only
			STATUS current
			DESCRIPTION "Heater thermostat alarm"
			::= { binaryObjects2 4 }

			condPumpAlarmDI_2 OBJECT-TYPE
			SYNTAX INTEGER
			MAX-ACCESS read-only
			STATUS current
			DESCRIPTION "Condensate pump alarm"
			::= { binaryObjects2 5 }

			configurableDI1_2 OBJECT-TYPE
			SYNTAX INTEGER
			MAX-ACCESS read-only
			STATUS current
			DESCRIPTION "Configurable DI 1"
			::= { binaryObjects2 6 }

			configurableDI2_2 OBJECT-TYPE
			SYNTAX INTEGER
			MAX-ACCESS read-only
			STATUS current
			DESCRIPTION "Configurable DI 2"
			::= { binaryObjects2 7 }

			configurableDI3_2 OBJECT-TYPE
			SYNTAX INTEGER
			MAX-ACCESS read-only
			STATUS current
			DESCRIPTION "Configurable DI 3"
			::= { binaryObjects2 8 }

			configurableDI4_2 OBJECT-TYPE
			SYNTAX INTEGER
			MAX-ACCESS read-only
			STATUS current
			DESCRIPTION "Configurable DI 4"
			::= { binaryObjects2 9 }

			configurableDI5_2 OBJECT-TYPE
			SYNTAX INTEGER
			MAX-ACCESS read-only
			STATUS current
			DESCRIPTION "Configurable DI 5"
			::= { binaryObjects2 10 }

			c1ThermAlarmDI_2 OBJECT-TYPE
			SYNTAX INTEGER
			MAX-ACCESS read-only
			STATUS current
			DESCRIPTION "Comp1 thermal alarm"
			::= { binaryObjects2 11 }

			c1HPAlarmDI_2 OBJECT-TYPE
			SYNTAX INTEGER
			MAX-ACCESS read-only
			STATUS current
			DESCRIPTION "Comp1 high pressure alarm"
			::= { binaryObjects2 12 }

			c1LPAlarmDI_2 OBJECT-TYPE
			SYNTAX INTEGER
			MAX-ACCESS read-only
			STATUS current
			DESCRIPTION "Comp1 low pressure alarm"
			::= { binaryObjects2 13 }

			c2ThermAlarmDI_2 OBJECT-TYPE
			SYNTAX INTEGER
			MAX-ACCESS read-only
			STATUS current
			DESCRIPTION "Comp2 thermal alarm"
			::= { binaryObjects2 14 }

			c2HPAlarmDI_2 OBJECT-TYPE
			SYNTAX INTEGER
			MAX-ACCESS read-only
			STATUS current
			DESCRIPTION "Comp2 high pressure alarm"
			::= { binaryObjects2 15 }

			c2LPAlarmDI_2 OBJECT-TYPE
			SYNTAX INTEGER
			MAX-ACCESS read-only
			STATUS current
			DESCRIPTION "Comp2 low pressure alarm"
			::= { binaryObjects2 16 }

			fansDO_2 OBJECT-TYPE
			SYNTAX INTEGER
			MAX-ACCESS read-only
			STATUS current
			DESCRIPTION "Fan control"
			::= { binaryObjects2 17 }

			damperDO_2 OBJECT-TYPE
			SYNTAX INTEGER
			MAX-ACCESS read-only
			STATUS current
			DESCRIPTION "Motorised dampers control"
			::= { binaryObjects2 18 }

			configurableDO1_2 OBJECT-TYPE
			SYNTAX INTEGER
			MAX-ACCESS read-only
			STATUS current
			DESCRIPTION "Configurable DO 1"
			::= { binaryObjects2 19 }

			configurableDO2_2 OBJECT-TYPE
			SYNTAX INTEGER
			MAX-ACCESS read-only
			STATUS current
			DESCRIPTION "Configurable DO 2"
			::= { binaryObjects2 20 }

			configurableDO3_2 OBJECT-TYPE
			SYNTAX INTEGER
			MAX-ACCESS read-only
			STATUS current
			DESCRIPTION "Configurable DO 3"
			::= { binaryObjects2 21 }

			configurableDO4_2 OBJECT-TYPE
			SYNTAX INTEGER
			MAX-ACCESS read-only
			STATUS current
			DESCRIPTION "Configurable DO 4"
			::= { binaryObjects2 22 }

			configurableDO5_2 OBJECT-TYPE
			SYNTAX INTEGER
			MAX-ACCESS read-only
			STATUS current
			DESCRIPTION "Configurable DO 5"
			::= { binaryObjects2 23 }

			eHeaterStage1DO_2 OBJECT-TYPE
			SYNTAX INTEGER
			MAX-ACCESS read-only
			STATUS current
			DESCRIPTION "Electric heat stage 1"
			::= { binaryObjects2 24 }

			eHeaterStage2DO_2 OBJECT-TYPE
			SYNTAX INTEGER
			MAX-ACCESS read-only
			STATUS current
			DESCRIPTION "Electric heat stage 2"
			::= { binaryObjects2 25 }

			compressor1DO_2 OBJECT-TYPE
			SYNTAX INTEGER
			MAX-ACCESS read-only
			STATUS current
			DESCRIPTION "Compressor 1 control"
			::= { binaryObjects2 26 }

			compressor2DO_2 OBJECT-TYPE
			SYNTAX INTEGER
			MAX-ACCESS read-only
			STATUS current
			DESCRIPTION "Compressor 2 control"
			::= { binaryObjects2 27 }

			humPowerDO_2 OBJECT-TYPE
			SYNTAX INTEGER
			MAX-ACCESS read-only
			STATUS current
			DESCRIPTION "Humidifier control"
			::= { binaryObjects2 28 }

			humDrainValveDO_2 OBJECT-TYPE
			SYNTAX INTEGER
			MAX-ACCESS read-only
			STATUS current
			DESCRIPTION "Humidifier Discharge"
			::= { binaryObjects2 29 }

			humFillValveDO_2 OBJECT-TYPE
			SYNTAX INTEGER
			MAX-ACCESS read-only
			STATUS current
			DESCRIPTION "Humidifier Charging"
			::= { binaryObjects2 30 }

			humWaterLevel_2 OBJECT-TYPE
			SYNTAX INTEGER
			MAX-ACCESS read-only
			STATUS current
			DESCRIPTION "Humidifier high water"
			::= { binaryObjects2 31 }

			supervOFF_2 OBJECT-TYPE
			SYNTAX INTEGER
			MAX-ACCESS read-write
			STATUS current
			DESCRIPTION "ON/OFF from supervisor"
			::= { binaryObjects2 32 }

			enableHumid_2 OBJECT-TYPE
			SYNTAX INTEGER
			MAX-ACCESS read-write
			STATUS current
			DESCRIPTION "Humidification enabling"
			::= { binaryObjects2 33 }

			humManualDrain_2 OBJECT-TYPE
			SYNTAX INTEGER
			MAX-ACCESS read-write
			STATUS current
			DESCRIPTION "Manual draining"
			::= { binaryObjects2 34 }

			humCylWashing_2 OBJECT-TYPE
			SYNTAX INTEGER
			MAX-ACCESS read-write
			STATUS current
			DESCRIPTION "Cylinder washing"
			::= { binaryObjects2 35 }

			tSManExchange_2 OBJECT-TYPE
			SYNTAX INTEGER
			MAX-ACCESS read-write
			STATUS current
			DESCRIPTION "TS manual exchange"
			::= { binaryObjects2 36 }

			tSTempExchEnab_2 OBJECT-TYPE
			SYNTAX INTEGER
			MAX-ACCESS read-write
			STATUS current
			DESCRIPTION "Enable TS room temp. exc."
			::= { binaryObjects2 37 }

			damperAlRes_2 OBJECT-TYPE
			SYNTAX INTEGER
			MAX-ACCESS read-write
			STATUS current
			DESCRIPTION "Reset damper status AL"
			::= { binaryObjects2 38 }

			fireSmokeAlRes_2 OBJECT-TYPE
			SYNTAX INTEGER
			MAX-ACCESS read-write
			STATUS current
			DESCRIPTION "Reset smoke/fire AL"
			::= { binaryObjects2 39 }

			genSerAlRes_2 OBJECT-TYPE
			SYNTAX INTEGER
			MAX-ACCESS read-write
			STATUS current
			DESCRIPTION "Reset generic serious AL"
			::= { binaryObjects2 40 }

			fansGenAlRes_2 OBJECT-TYPE
			SYNTAX INTEGER
			MAX-ACCESS read-write
			STATUS current
			DESCRIPTION "Reset supply fan AL"
			::= { binaryObjects2 41 }

			f1InvAlRes_2 OBJECT-TYPE
			SYNTAX INTEGER
			MAX-ACCESS read-write
			STATUS current
			DESCRIPTION "Reset fan 1 alarm"
			::= { binaryObjects2 42 }

			f2InvAlRes_2 OBJECT-TYPE
			SYNTAX INTEGER
			MAX-ACCESS read-write
			STATUS current
			DESCRIPTION "Reset fan 2 alarm"
			::= { binaryObjects2 43 }

			f3InvAlRes_2 OBJECT-TYPE
			SYNTAX INTEGER
			MAX-ACCESS read-write
			STATUS current
			DESCRIPTION "Reset fan 3 alarm"
			::= { binaryObjects2 44 }

			f4InvAlRes_2 OBJECT-TYPE
			SYNTAX INTEGER
			MAX-ACCESS read-write
			STATUS current
			DESCRIPTION "Reset fan 4 alarm"
			::= { binaryObjects2 45 }

			f5InvAlRes_2 OBJECT-TYPE
			SYNTAX INTEGER
			MAX-ACCESS read-write
			STATUS current
			DESCRIPTION "Reset fan 5 alarm"
			::= { binaryObjects2 46 }

			f6InvAlRes_2 OBJECT-TYPE
			SYNTAX INTEGER
			MAX-ACCESS read-write
			STATUS current
			DESCRIPTION "Reset fan 6 alarm"
			::= { binaryObjects2 47 }

			f7InvAlRes_2 OBJECT-TYPE
			SYNTAX INTEGER
			MAX-ACCESS read-write
			STATUS current
			DESCRIPTION "Reset fan 7 alarm"
			::= { binaryObjects2 48 }

			f8InvAlRes_2 OBJECT-TYPE
			SYNTAX INTEGER
			MAX-ACCESS read-write
			STATUS current
			DESCRIPTION "Reset fan 8 alarm"
			::= { binaryObjects2 49 }

			f9InvAlRes_2 OBJECT-TYPE
			SYNTAX INTEGER
			MAX-ACCESS read-write
			STATUS current
			DESCRIPTION "Reset fan 9 alarm"
			::= { binaryObjects2 50 }

			f10InvAlRes_2 OBJECT-TYPE
			SYNTAX INTEGER
			MAX-ACCESS read-write
			STATUS current
			DESCRIPTION "Reset fan 10 alarm"
			::= { binaryObjects2 51 }

			invCompAlRes_2 OBJECT-TYPE
			SYNTAX INTEGER
			MAX-ACCESS read-write
			STATUS current
			DESCRIPTION "Reset inverter alarm"
			::= { binaryObjects2 52 }

			c1ThermAlRes_2 OBJECT-TYPE
			SYNTAX INTEGER
			MAX-ACCESS read-write
			STATUS current
			DESCRIPTION "Reset C1 thermal AL"
			::= { binaryObjects2 53 }

			c1HighPresAlRes_2 OBJECT-TYPE
			SYNTAX INTEGER
			MAX-ACCESS read-write
			STATUS current
			DESCRIPTION "Reset C1 high pressure AL"
			::= { binaryObjects2 54 }

			c1LowPresAlRes_2 OBJECT-TYPE
			SYNTAX INTEGER
			MAX-ACCESS read-write
			STATUS current
			DESCRIPTION "Reset C1 low pressure AL"
			::= { binaryObjects2 55 }

			c1HighDisTAlRes_2 OBJECT-TYPE
			SYNTAX INTEGER
			MAX-ACCESS read-write
			STATUS current
			DESCRIPTION "Reset C1 high disch. AL"
			::= { binaryObjects2 56 }

			c1LCompRatAlRes_2 OBJECT-TYPE
			SYNTAX INTEGER
			MAX-ACCESS read-write
			STATUS current
			DESCRIPTION "Reset C1 low compres. AL"
			::= { binaryObjects2 57 }

			condenser1AlRes_2 OBJECT-TYPE
			SYNTAX INTEGER
			MAX-ACCESS read-write
			STATUS current
			DESCRIPTION "Reset condenser 1 AL"
			::= { binaryObjects2 58 }

			eEV1AlRes_2 OBJECT-TYPE
			SYNTAX INTEGER
			MAX-ACCESS read-write
			STATUS current
			DESCRIPTION "Reset EEV1 alarm"
			::= { binaryObjects2 59 }

			c2ThermAlRes_2 OBJECT-TYPE
			SYNTAX INTEGER
			MAX-ACCESS read-write
			STATUS current
			DESCRIPTION "Reset C2 thermal AL"
			::= { binaryObjects2 60 }

			c2HighPresAlRes_2 OBJECT-TYPE
			SYNTAX INTEGER
			MAX-ACCESS read-write
			STATUS current
			DESCRIPTION "Reset C2 high pressure AL"
			::= { binaryObjects2 61 }

			c2LowPresAlRes_2 OBJECT-TYPE
			SYNTAX INTEGER
			MAX-ACCESS read-write
			STATUS current
			DESCRIPTION "Reset C2 low pressure AL"
			::= { binaryObjects2 62 }

			c2HighDisTAlRes_2 OBJECT-TYPE
			SYNTAX INTEGER
			MAX-ACCESS read-write
			STATUS current
			DESCRIPTION "Reset C2 high disch. AL"
			::= { binaryObjects2 63 }

			c2LComRatAlRes_2 OBJECT-TYPE
			SYNTAX INTEGER
			MAX-ACCESS read-write
			STATUS current
			DESCRIPTION "Reset C2 low compres. AL"
			::= { binaryObjects2 64 }

			condenser2AlRes_2 OBJECT-TYPE
			SYNTAX INTEGER
			MAX-ACCESS read-write
			STATUS current
			DESCRIPTION "Reset condenser 2 AL"
			::= { binaryObjects2 65 }

			eEV2AlRes_2 OBJECT-TYPE
			SYNTAX INTEGER
			MAX-ACCESS read-write
			STATUS current
			DESCRIPTION "Reset EEV2 alarm"
			::= { binaryObjects2 66 }

			intHumidifAlRes_2 OBJECT-TYPE
			SYNTAX INTEGER
			MAX-ACCESS read-write
			STATUS current
			DESCRIPTION "Reset int. humidifier AL"
			::= { binaryObjects2 67 }

			watPresAlRes_2 OBJECT-TYPE
			SYNTAX INTEGER
			MAX-ACCESS read-write
			STATUS current
			DESCRIPTION "Reset water presence AL"
			::= { binaryObjects2 68 }

			drainPumpAlRes_2 OBJECT-TYPE
			SYNTAX INTEGER
			MAX-ACCESS read-write
			STATUS current
			DESCRIPTION "Reset drain pump AL"
			::= { binaryObjects2 69 }

			elHeatAlRes_2 OBJECT-TYPE
			SYNTAX INTEGER
			MAX-ACCESS read-write
			STATUS current
			DESCRIPTION "Reset electric heater AL"
			::= { binaryObjects2 70 }

			filterAlRes_2 OBJECT-TYPE
			SYNTAX INTEGER
			MAX-ACCESS read-write
			STATUS current
			DESCRIPTION "Reset dirty filter AL"
			::= { binaryObjects2 71 }

			dryCoolerAlRes_2 OBJECT-TYPE
			SYNTAX INTEGER
			MAX-ACCESS read-write
			STATUS current
			DESCRIPTION "Reset dry cooler AL"
			::= { binaryObjects2 72 }

			extHumidifAlRes_2 OBJECT-TYPE
			SYNTAX INTEGER
			MAX-ACCESS read-write
			STATUS current
			DESCRIPTION "Reset ext. humidifier AL"
			::= { binaryObjects2 73 }

			waterPumpAlRes_2 OBJECT-TYPE
			SYNTAX INTEGER
			MAX-ACCESS read-write
			STATUS current
			DESCRIPTION "Reset water pump AL"
			::= { binaryObjects2 74 }

			condUnitGAlRes_2 OBJECT-TYPE
			SYNTAX INTEGER
			MAX-ACCESS read-write
			STATUS current
			DESCRIPTION "Reset motocondenser AL"
			::= { binaryObjects2 75 }

			gasLeakAlRes_2 OBJECT-TYPE
			SYNTAX INTEGER
			MAX-ACCESS read-write
			STATUS current
			DESCRIPTION "Reset gas leak AL"
			::= { binaryObjects2 76 }

			powerSupAlRes_2 OBJECT-TYPE
			SYNTAX INTEGER
			MAX-ACCESS read-write
			STATUS current
			DESCRIPTION "Reset power fault AL"
			::= { binaryObjects2 77 }

			genSoftAlRes_2 OBJECT-TYPE
			SYNTAX INTEGER
			MAX-ACCESS read-write
			STATUS current
			DESCRIPTION "Reset generic soft AL"
			::= { binaryObjects2 78 }

		scalarsObjects2 OBJECT IDENTIFIER  ::= { node2 2 }

			confDI1Combo_2 OBJECT-TYPE
			SYNTAX Integer32
			MAX-ACCESS read-only
			STATUS current
			DESCRIPTION "Configurable DI1 meaning"
			::= { scalarsObjects2 1 }

			confDI2Combo_2 OBJECT-TYPE
			SYNTAX Integer32
			MAX-ACCESS read-only
			STATUS current
			DESCRIPTION "Configurable DI2 meaning"
			::= { scalarsObjects2 2 }

			confDI3Combo_2 OBJECT-TYPE
			SYNTAX Integer32
			MAX-ACCESS read-only
			STATUS current
			DESCRIPTION "Configurable DI3 meaning"
			::= { scalarsObjects2 3 }

			confDI4Combo_2 OBJECT-TYPE
			SYNTAX Integer32
			MAX-ACCESS read-only
			STATUS current
			DESCRIPTION "Configurable DI4 meaning"
			::= { scalarsObjects2 4 }

			confDI5Combo_2 OBJECT-TYPE
			SYNTAX Integer32
			MAX-ACCESS read-only
			STATUS current
			DESCRIPTION "Configurable DI5 meaning"
			::= { scalarsObjects2 5 }

			confDO1Combo_2 OBJECT-TYPE
			SYNTAX Integer32
			MAX-ACCESS read-only
			STATUS current
			DESCRIPTION "Configurable DO1 meaning"
			::= { scalarsObjects2 6 }

			confDO2Combo_2 OBJECT-TYPE
			SYNTAX Integer32
			MAX-ACCESS read-only
			STATUS current
			DESCRIPTION "Configurable DO2 meaning"
			::= { scalarsObjects2 7 }

			confDO3Combo_2 OBJECT-TYPE
			SYNTAX Integer32
			MAX-ACCESS read-only
			STATUS current
			DESCRIPTION "Configurable DO3 meaning"
			::= { scalarsObjects2 8 }

			confDO4Combo_2 OBJECT-TYPE
			SYNTAX Integer32
			MAX-ACCESS read-only
			STATUS current
			DESCRIPTION "Configurable DO4 meaning"
			::= { scalarsObjects2 9 }

			confDO5Combo_2 OBJECT-TYPE
			SYNTAX Integer32
			MAX-ACCESS read-only
			STATUS current
			DESCRIPTION "Configurable DO5 meaning"
			::= { scalarsObjects2 10 }

			returnTemp_2 OBJECT-TYPE
			SYNTAX Integer32
			MAX-ACCESS read-only
			STATUS current
			DESCRIPTION "Return temperature"
			::= { scalarsObjects2 11 }

			returnTAvg_2 OBJECT-TYPE
			SYNTAX Integer32
			MAX-ACCESS read-only
			STATUS current
			DESCRIPTION "Return temperature (AVG)"
			::= { scalarsObjects2 12 }

			supplyTemp_2 OBJECT-TYPE
			SYNTAX Integer32
			MAX-ACCESS read-only
			STATUS current
			DESCRIPTION "Supply temperature"
			::= { scalarsObjects2 13 }

			supplyTAvg_2 OBJECT-TYPE
			SYNTAX Integer32
			MAX-ACCESS read-only
			STATUS current
			DESCRIPTION "Supply temperature (AVG)"
			::= { scalarsObjects2 14 }

			tempDelta_2 OBJECT-TYPE
			SYNTAX Integer32
			MAX-ACCESS read-only
			STATUS current
			DESCRIPTION "Temperature delta"
			::= { scalarsObjects2 15 }

			returnHumidity_2 OBJECT-TYPE
			SYNTAX Integer32
			MAX-ACCESS read-only
			STATUS current
			DESCRIPTION "Return humidity"
			::= { scalarsObjects2 16 }

			returnHumAvg_2 OBJECT-TYPE
			SYNTAX Integer32
			MAX-ACCESS read-only
			STATUS current
			DESCRIPTION "Return humidity (AVG)"
			::= { scalarsObjects2 17 }

			supplyHumidity_2 OBJECT-TYPE
			SYNTAX Integer32
			MAX-ACCESS read-only
			STATUS current
			DESCRIPTION "Supply humidity"
			::= { scalarsObjects2 18 }

			supplyHumAvg_2 OBJECT-TYPE
			SYNTAX Integer32
			MAX-ACCESS read-only
			STATUS current
			DESCRIPTION "Supply humidity (AVG)"
			::= { scalarsObjects2 19 }

			airFlow_2 OBJECT-TYPE
			SYNTAX Integer32
			MAX-ACCESS read-only
			STATUS current
			DESCRIPTION "Air flow"
			::= { scalarsObjects2 20 }

			airPressure_2 OBJECT-TYPE
			SYNTAX Integer32
			MAX-ACCESS read-only
			STATUS current
			DESCRIPTION "Air pressure"
			::= { scalarsObjects2 22 }

			airPressureAvg_2 OBJECT-TYPE
			SYNTAX Integer32
			MAX-ACCESS read-only
			STATUS current
			DESCRIPTION "Air pressure (Average)"
			::= { scalarsObjects2 23 }

			netMod1Combo1_2 OBJECT-TYPE
			SYNTAX Integer32
			MAX-ACCESS read-only
			STATUS current
			DESCRIPTION "Module 1 - Probe 1 status"
			::= { scalarsObjects2 24 }

			netMod1Probe1_2 OBJECT-TYPE
			SYNTAX Integer32
			MAX-ACCESS read-only
			STATUS current
			DESCRIPTION "Module 1 - Probe 1 value"
			::= { scalarsObjects2 25 }

			netMod1Combo2_2 OBJECT-TYPE
			SYNTAX Integer32
			MAX-ACCESS read-only
			STATUS current
			DESCRIPTION "Module 1 - Probe 2 status"
			::= { scalarsObjects2 26 }

			netMod1Probe2_2 OBJECT-TYPE
			SYNTAX Integer32
			MAX-ACCESS read-only
			STATUS current
			DESCRIPTION "Module 1 - Probe 2 value"
			::= { scalarsObjects2 27 }

			netMod1Combo3_2 OBJECT-TYPE
			SYNTAX Integer32
			MAX-ACCESS read-only
			STATUS current
			DESCRIPTION "Module 1 - Probe 3 status"
			::= { scalarsObjects2 28 }

			netMod1Probe3_2 OBJECT-TYPE
			SYNTAX Integer32
			MAX-ACCESS read-only
			STATUS current
			DESCRIPTION "Module 1 - Probe 3 value"
			::= { scalarsObjects2 29 }

			netMod1Combo4_2 OBJECT-TYPE
			SYNTAX Integer32
			MAX-ACCESS read-only
			STATUS current
			DESCRIPTION "Module 1 - Probe 4 status"
			::= { scalarsObjects2 30 }

			netMod1Probe4_2 OBJECT-TYPE
			SYNTAX Integer32
			MAX-ACCESS read-only
			STATUS current
			DESCRIPTION "Module 1 - Probe 4 value"
			::= { scalarsObjects2 31 }

			netMod1Combo5_2 OBJECT-TYPE
			SYNTAX Integer32
			MAX-ACCESS read-only
			STATUS current
			DESCRIPTION "Module 1 - Probe 5 status"
			::= { scalarsObjects2 32 }

			netMod1Probe5_2 OBJECT-TYPE
			SYNTAX Integer32
			MAX-ACCESS read-only
			STATUS current
			DESCRIPTION "Module 1 - Probe 5 value"
			::= { scalarsObjects2 33 }

			netMod1Combo6_2 OBJECT-TYPE
			SYNTAX Integer32
			MAX-ACCESS read-only
			STATUS current
			DESCRIPTION "Module 1 - Probe 6 status"
			::= { scalarsObjects2 34 }

			netMod1Probe6_2 OBJECT-TYPE
			SYNTAX Integer32
			MAX-ACCESS read-only
			STATUS current
			DESCRIPTION "Module 1 - Probe 6 value"
			::= { scalarsObjects2 35 }

			netMod2Combo1_2 OBJECT-TYPE
			SYNTAX Integer32
			MAX-ACCESS read-only
			STATUS current
			DESCRIPTION "Module 2 - Probe 1 status"
			::= { scalarsObjects2 36 }

			netMod2Probe1_2 OBJECT-TYPE
			SYNTAX Integer32
			MAX-ACCESS read-only
			STATUS current
			DESCRIPTION "Module 2 - Probe 1 value"
			::= { scalarsObjects2 37 }

			netMod2Combo2_2 OBJECT-TYPE
			SYNTAX Integer32
			MAX-ACCESS read-only
			STATUS current
			DESCRIPTION "Module 2 - Probe 2 status"
			::= { scalarsObjects2 38 }

			netMod2Probe2_2 OBJECT-TYPE
			SYNTAX Integer32
			MAX-ACCESS read-only
			STATUS current
			DESCRIPTION "Module 2 - Probe 2 value"
			::= { scalarsObjects2 39 }

			netMod2Combo3_2 OBJECT-TYPE
			SYNTAX Integer32
			MAX-ACCESS read-only
			STATUS current
			DESCRIPTION "Module 2 - Probe 3 status"
			::= { scalarsObjects2 40 }

			netMod2Probe3_2 OBJECT-TYPE
			SYNTAX Integer32
			MAX-ACCESS read-only
			STATUS current
			DESCRIPTION "Module 2 - Probe 3 value"
			::= { scalarsObjects2 41 }

			netMod2Combo4_2 OBJECT-TYPE
			SYNTAX Integer32
			MAX-ACCESS read-only
			STATUS current
			DESCRIPTION "Module 2 - Probe 4 status"
			::= { scalarsObjects2 42 }

			netMod2Probe4_2 OBJECT-TYPE
			SYNTAX Integer32
			MAX-ACCESS read-only
			STATUS current
			DESCRIPTION "Module 2 - Probe 4 value"
			::= { scalarsObjects2 43 }

			netMod2Combo5_2 OBJECT-TYPE
			SYNTAX Integer32
			MAX-ACCESS read-only
			STATUS current
			DESCRIPTION "Module 2 - Probe 5 status"
			::= { scalarsObjects2 44 }

			netMod2Probe5_2 OBJECT-TYPE
			SYNTAX Integer32
			MAX-ACCESS read-only
			STATUS current
			DESCRIPTION "Module 2 - Probe 5 value"
			::= { scalarsObjects2 45 }

			netMod2Combo6_2 OBJECT-TYPE
			SYNTAX Integer32
			MAX-ACCESS read-only
			STATUS current
			DESCRIPTION "Module 2 - Probe 6 status"
			::= { scalarsObjects2 46 }

			netMod2Probe6_2 OBJECT-TYPE
			SYNTAX Integer32
			MAX-ACCESS read-only
			STATUS current
			DESCRIPTION "Module 2 - Probe 6 value"
			::= { scalarsObjects2 47 }

			netMod3Combo1_2 OBJECT-TYPE
			SYNTAX Integer32
			MAX-ACCESS read-only
			STATUS current
			DESCRIPTION "Module 3 - Probe 1 status"
			::= { scalarsObjects2 48 }

			netMod3Probe1_2 OBJECT-TYPE
			SYNTAX Integer32
			MAX-ACCESS read-only
			STATUS current
			DESCRIPTION "Module 3 - Probe 1 value"
			::= { scalarsObjects2 49 }

			netMod3Combo2_2 OBJECT-TYPE
			SYNTAX Integer32
			MAX-ACCESS read-only
			STATUS current
			DESCRIPTION "Module 3 - Probe 2 status"
			::= { scalarsObjects2 50 }

			netMod3Probe2_2 OBJECT-TYPE
			SYNTAX Integer32
			MAX-ACCESS read-only
			STATUS current
			DESCRIPTION "Module 3 - Probe 2 value"
			::= { scalarsObjects2 51 }

			netMod3Combo3_2 OBJECT-TYPE
			SYNTAX Integer32
			MAX-ACCESS read-only
			STATUS current
			DESCRIPTION "Module 3 - Probe 3 status"
			::= { scalarsObjects2 52 }

			netMod3Probe3_2 OBJECT-TYPE
			SYNTAX Integer32
			MAX-ACCESS read-only
			STATUS current
			DESCRIPTION "Module 3 - Probe 3 value"
			::= { scalarsObjects2 53 }

			netMod3Combo4_2 OBJECT-TYPE
			SYNTAX Integer32
			MAX-ACCESS read-only
			STATUS current
			DESCRIPTION "Module 3 - Probe 4 status"
			::= { scalarsObjects2 54 }

			netMod3Probe4_2 OBJECT-TYPE
			SYNTAX Integer32
			MAX-ACCESS read-only
			STATUS current
			DESCRIPTION "Module 3 - Probe 4 value"
			::= { scalarsObjects2 55 }

			netMod3Combo5_2 OBJECT-TYPE
			SYNTAX Integer32
			MAX-ACCESS read-only
			STATUS current
			DESCRIPTION "Module 3 - Probe 5 status"
			::= { scalarsObjects2 56 }

			netMod3Probe5_2 OBJECT-TYPE
			SYNTAX Integer32
			MAX-ACCESS read-only
			STATUS current
			DESCRIPTION "Module 3 - Probe 5 value"
			::= { scalarsObjects2 57 }

			netMod3Combo6_2 OBJECT-TYPE
			SYNTAX Integer32
			MAX-ACCESS read-only
			STATUS current
			DESCRIPTION "Module 3 - Probe 6 status"
			::= { scalarsObjects2 58 }

			netMod3Probe6_2 OBJECT-TYPE
			SYNTAX Integer32
			MAX-ACCESS read-only
			STATUS current
			DESCRIPTION "Module 3 - Probe 6 value"
			::= { scalarsObjects2 59 }

			avgModTemp_2 OBJECT-TYPE
			SYNTAX Integer32
			MAX-ACCESS read-only
			STATUS current
			DESCRIPTION "Modules temperatures AVG"
			::= { scalarsObjects2 60 }

			avgModHumi_2 OBJECT-TYPE
			SYNTAX Integer32
			MAX-ACCESS read-only
			STATUS current
			DESCRIPTION "Modules humidity AVG"
			::= { scalarsObjects2 61 }

			avgModPress_2 OBJECT-TYPE
			SYNTAX Integer32
			MAX-ACCESS read-only
			STATUS current
			DESCRIPTION "Modules pressure AVG"
			::= { scalarsObjects2 62 }

			dryCoolerAO_2 OBJECT-TYPE
			SYNTAX Integer32
			MAX-ACCESS read-only
			STATUS current
			DESCRIPTION "Supply Fan/Dry cooler"
			::= { scalarsObjects2 63 }

			coolingAO_2 OBJECT-TYPE
			SYNTAX Integer32
			MAX-ACCESS read-only
			STATUS current
			DESCRIPTION "Cooling valve/FC/Inverter"
			::= { scalarsObjects2 64 }

			heatingAO_2 OBJECT-TYPE
			SYNTAX Integer32
			MAX-ACCESS read-only
			STATUS current
			DESCRIPTION "Heating valve/Heater"
			::= { scalarsObjects2 65 }

			twoSources2AO_2 OBJECT-TYPE
			SYNTAX Integer32
			MAX-ACCESS read-only
			STATUS current
			DESCRIPTION "TS cooling valve 2"
			::= { scalarsObjects2 66 }

			condenser1AO_2 OBJECT-TYPE
			SYNTAX Integer32
			MAX-ACCESS read-only
			STATUS current
			DESCRIPTION "Condenser 1"
			::= { scalarsObjects2 67 }

			cond2HumidifAO_2 OBJECT-TYPE
			SYNTAX Integer32
			MAX-ACCESS read-only
			STATUS current
			DESCRIPTION "Condenser 2/Humidifier"
			::= { scalarsObjects2 68 }

			unitStatus_2 OBJECT-TYPE
			SYNTAX Integer32
			MAX-ACCESS read-only
			STATUS current
			DESCRIPTION "Unit status"
			::= { scalarsObjects2 69 }

			fanSpeed_2 OBJECT-TYPE
			SYNTAX Integer32
			MAX-ACCESS read-only
			STATUS current
			DESCRIPTION "Fan speed"
			::= { scalarsObjects2 70 }

			fan1Actspeed_2 OBJECT-TYPE
			SYNTAX Integer32
			MAX-ACCESS read-only
			STATUS current
			DESCRIPTION "Fan 1 speed"
			::= { scalarsObjects2 71 }

			fan1ActRPM_2 OBJECT-TYPE
			SYNTAX Integer32
			MAX-ACCESS read-only
			STATUS current
			DESCRIPTION "Fan 1 speed RPM"
			::= { scalarsObjects2 72 }

			fan1Cur_2 OBJECT-TYPE
			SYNTAX Integer32
			MAX-ACCESS read-only
			STATUS current
			DESCRIPTION "Fan 1 current"
			::= { scalarsObjects2 73 }

			fan1Power_2 OBJECT-TYPE
			SYNTAX Integer32
			MAX-ACCESS read-only
			STATUS current
			DESCRIPTION "Fan 1 power"
			::= { scalarsObjects2 74 }

			fan2Actspeed_2 OBJECT-TYPE
			SYNTAX Integer32
			MAX-ACCESS read-only
			STATUS current
			DESCRIPTION "Fan 2 speed"
			::= { scalarsObjects2 75 }

			fan2ActRPM_2 OBJECT-TYPE
			SYNTAX Integer32
			MAX-ACCESS read-only
			STATUS current
			DESCRIPTION "Fan 2 speed RPM"
			::= { scalarsObjects2 76 }

			fan2Cur_2 OBJECT-TYPE
			SYNTAX Integer32
			MAX-ACCESS read-only
			STATUS current
			DESCRIPTION "Fan 2 current"
			::= { scalarsObjects2 77 }

			fan2Power_2 OBJECT-TYPE
			SYNTAX Integer32
			MAX-ACCESS read-only
			STATUS current
			DESCRIPTION "Fan 2 power"
			::= { scalarsObjects2 78 }

			fan3Actspeed_2 OBJECT-TYPE
			SYNTAX Integer32
			MAX-ACCESS read-only
			STATUS current
			DESCRIPTION "Fan 3 speed"
			::= { scalarsObjects2 79 }

			fan3ActRPM_2 OBJECT-TYPE
			SYNTAX Integer32
			MAX-ACCESS read-only
			STATUS current
			DESCRIPTION "Fan 3 speed RPM"
			::= { scalarsObjects2 80 }

			fan3Cur_2 OBJECT-TYPE
			SYNTAX Integer32
			MAX-ACCESS read-only
			STATUS current
			DESCRIPTION "Fan 3 current"
			::= { scalarsObjects2 81 }

			fan3Power_2 OBJECT-TYPE
			SYNTAX Integer32
			MAX-ACCESS read-only
			STATUS current
			DESCRIPTION "Fan 3 power"
			::= { scalarsObjects2 82 }

			fan4Actspeed_2 OBJECT-TYPE
			SYNTAX Integer32
			MAX-ACCESS read-only
			STATUS current
			DESCRIPTION "Fan 4 speed"
			::= { scalarsObjects2 83 }

			fan4ActRPM_2 OBJECT-TYPE
			SYNTAX Integer32
			MAX-ACCESS read-only
			STATUS current
			DESCRIPTION "Fan 4 speed RPM"
			::= { scalarsObjects2 84 }

			fan4Cur_2 OBJECT-TYPE
			SYNTAX Integer32
			MAX-ACCESS read-only
			STATUS current
			DESCRIPTION "Fan 4 current"
			::= { scalarsObjects2 85 }

			fan4Power_2 OBJECT-TYPE
			SYNTAX Integer32
			MAX-ACCESS read-only
			STATUS current
			DESCRIPTION "Fan 4 power"
			::= { scalarsObjects2 86 }

			fan5Actspeed_2 OBJECT-TYPE
			SYNTAX Integer32
			MAX-ACCESS read-only
			STATUS current
			DESCRIPTION "Fan 5 speed"
			::= { scalarsObjects2 87 }

			fan5ActRPM_2 OBJECT-TYPE
			SYNTAX Integer32
			MAX-ACCESS read-only
			STATUS current
			DESCRIPTION "Fan 5 speed RPM"
			::= { scalarsObjects2 88 }

			fan5Cur_2 OBJECT-TYPE
			SYNTAX Integer32
			MAX-ACCESS read-only
			STATUS current
			DESCRIPTION "Fan 5 current"
			::= { scalarsObjects2 89 }

			fan5Power_2 OBJECT-TYPE
			SYNTAX Integer32
			MAX-ACCESS read-only
			STATUS current
			DESCRIPTION "Fan 5 power"
			::= { scalarsObjects2 90 }

			fan6Actspeed_2 OBJECT-TYPE
			SYNTAX Integer32
			MAX-ACCESS read-only
			STATUS current
			DESCRIPTION "Fan 6 speed"
			::= { scalarsObjects2 91 }

			fan6ActRPM_2 OBJECT-TYPE
			SYNTAX Integer32
			MAX-ACCESS read-only
			STATUS current
			DESCRIPTION "Fan 6 speed RPM"
			::= { scalarsObjects2 92 }

			fan6Cur_2 OBJECT-TYPE
			SYNTAX Integer32
			MAX-ACCESS read-only
			STATUS current
			DESCRIPTION "Fan 6 current"
			::= { scalarsObjects2 93 }

			fan6Power_2 OBJECT-TYPE
			SYNTAX Integer32
			MAX-ACCESS read-only
			STATUS current
			DESCRIPTION "Fan 6 power"
			::= { scalarsObjects2 94 }

			fan7Actspeed_2 OBJECT-TYPE
			SYNTAX Integer32
			MAX-ACCESS read-only
			STATUS current
			DESCRIPTION "Fan 7 speed"
			::= { scalarsObjects2 95 }

			fan7ActRPM_2 OBJECT-TYPE
			SYNTAX Integer32
			MAX-ACCESS read-only
			STATUS current
			DESCRIPTION "Fan 7 speed RPM"
			::= { scalarsObjects2 96 }

			fan7Cur_2 OBJECT-TYPE
			SYNTAX Integer32
			MAX-ACCESS read-only
			STATUS current
			DESCRIPTION "Fan 7 current"
			::= { scalarsObjects2 97 }

			fan7Power_2 OBJECT-TYPE
			SYNTAX Integer32
			MAX-ACCESS read-only
			STATUS current
			DESCRIPTION "Fan 7 power"
			::= { scalarsObjects2 98 }

			fan8Actspeed_2 OBJECT-TYPE
			SYNTAX Integer32
			MAX-ACCESS read-only
			STATUS current
			DESCRIPTION "Fan 8 speed"
			::= { scalarsObjects2 99 }

			fan8ActRPM_2 OBJECT-TYPE
			SYNTAX Integer32
			MAX-ACCESS read-only
			STATUS current
			DESCRIPTION "Fan 8 speed RPM"
			::= { scalarsObjects2 100 }

			fan8Cur_2 OBJECT-TYPE
			SYNTAX Integer32
			MAX-ACCESS read-only
			STATUS current
			DESCRIPTION "Fan 8 current"
			::= { scalarsObjects2 101 }

			fan8Power_2 OBJECT-TYPE
			SYNTAX Integer32
			MAX-ACCESS read-only
			STATUS current
			DESCRIPTION "Fan 8 power"
			::= { scalarsObjects2 102 }

			fan9Actspeed_2 OBJECT-TYPE
			SYNTAX Integer32
			MAX-ACCESS read-only
			STATUS current
			DESCRIPTION "Fan 9 speed"
			::= { scalarsObjects2 103 }

			fan9ActRPM_2 OBJECT-TYPE
			SYNTAX Integer32
			MAX-ACCESS read-only
			STATUS current
			DESCRIPTION "Fan 9 speed RPM"
			::= { scalarsObjects2 104 }

			fan9Cur_2 OBJECT-TYPE
			SYNTAX Integer32
			MAX-ACCESS read-only
			STATUS current
			DESCRIPTION "Fan 9 current"
			::= { scalarsObjects2 105 }

			fan9Power_2 OBJECT-TYPE
			SYNTAX Integer32
			MAX-ACCESS read-only
			STATUS current
			DESCRIPTION "Fan 9 power"
			::= { scalarsObjects2 106 }

			fan10Actspeed_2 OBJECT-TYPE
			SYNTAX Integer32
			MAX-ACCESS read-only
			STATUS current
			DESCRIPTION "Fan 10 speed"
			::= { scalarsObjects2 107 }

			fan10ActRPM_2 OBJECT-TYPE
			SYNTAX Integer32
			MAX-ACCESS read-only
			STATUS current
			DESCRIPTION "Fan 10 speed RPM"
			::= { scalarsObjects2 108 }

			fan10Cur_2 OBJECT-TYPE
			SYNTAX Integer32
			MAX-ACCESS read-only
			STATUS current
			DESCRIPTION "Fan 10 current"
			::= { scalarsObjects2 109 }

			fan10Power_2 OBJECT-TYPE
			SYNTAX Integer32
			MAX-ACCESS read-only
			STATUS current
			DESCRIPTION "Fan 10 power"
			::= { scalarsObjects2 110 }

			diffFilterPres_2 OBJECT-TYPE
			SYNTAX Integer32
			MAX-ACCESS read-only
			STATUS current
			DESCRIPTION "Dirty filter pressure"
			::= { scalarsObjects2 111 }

			coolingRequest_2 OBJECT-TYPE
			SYNTAX Integer32
			MAX-ACCESS read-only
			STATUS current
			DESCRIPTION "Cooling request"
			::= { scalarsObjects2 112 }

			heatingRequest_2 OBJECT-TYPE
			SYNTAX Integer32
			MAX-ACCESS read-only
			STATUS current
			DESCRIPTION "Heating request"
			::= { scalarsObjects2 113 }

			dehumidRequest_2 OBJECT-TYPE
			SYNTAX Integer32
			MAX-ACCESS read-only
			STATUS current
			DESCRIPTION "Dehumidification request"
			::= { scalarsObjects2 114 }

			humidifRequest_2 OBJECT-TYPE
			SYNTAX Integer32
			MAX-ACCESS read-only
			STATUS current
			DESCRIPTION "Humidification request"
			::= { scalarsObjects2 115 }

			tempFcTs_2 OBJECT-TYPE
			SYNTAX Integer32
			MAX-ACCESS read-only
			STATUS current
			DESCRIPTION "FC/TS temperature"
			::= { scalarsObjects2 116 }

			fCTSStatus_2 OBJECT-TYPE
			SYNTAX Integer32
			MAX-ACCESS read-only
			STATUS current
			DESCRIPTION "FC/TS status"
			::= { scalarsObjects2 117 }

			fCRequest_2 OBJECT-TYPE
			SYNTAX Integer32
			MAX-ACCESS read-only
			STATUS current
			DESCRIPTION "Free cooling request"
			::= { scalarsObjects2 118 }

			activeComp_2 OBJECT-TYPE
			SYNTAX Integer32
			MAX-ACCESS read-only
			STATUS current
			DESCRIPTION "Active compressor"
			::= { scalarsObjects2 119 }

			comp1Sts_2 OBJECT-TYPE
			SYNTAX Integer32
			MAX-ACCESS read-only
			STATUS current
			DESCRIPTION "Compressor 1 Status"
			::= { scalarsObjects2 120 }

			comp2Sts_2 OBJECT-TYPE
			SYNTAX Integer32
			MAX-ACCESS read-only
			STATUS current
			DESCRIPTION "Compressor 2 Status"
			::= { scalarsObjects2 121 }

			invComprReq_2 OBJECT-TYPE
			SYNTAX Integer32
			MAX-ACCESS read-only
			STATUS current
			DESCRIPTION "Inverter compressor request"
			::= { scalarsObjects2 122 }

			invCompHz_2 OBJECT-TYPE
			SYNTAX Integer32
			MAX-ACCESS read-only
			STATUS current
			DESCRIPTION "Inverter frequency"
			::= { scalarsObjects2 123 }

			invCompPower_2 OBJECT-TYPE
			SYNTAX Integer32
			MAX-ACCESS read-only
			STATUS current
			DESCRIPTION "Inverter power input"
			::= { scalarsObjects2 124 }

			invCompCurrent_2 OBJECT-TYPE
			SYNTAX Integer32
			MAX-ACCESS read-only
			STATUS current
			DESCRIPTION "Inverter absorbed current"
			::= { scalarsObjects2 125 }

			c1EvapPres_2 OBJECT-TYPE
			SYNTAX Integer32
			MAX-ACCESS read-only
			STATUS current
			DESCRIPTION "C1 evaporation pressure"
			::= { scalarsObjects2 126 }

			c1EvapTemp_2 OBJECT-TYPE
			SYNTAX Integer32
			MAX-ACCESS read-only
			STATUS current
			DESCRIPTION "C1 evaporation temperature"
			::= { scalarsObjects2 127 }

			c1SuctionTemp_2 OBJECT-TYPE
			SYNTAX Integer32
			MAX-ACCESS read-only
			STATUS current
			DESCRIPTION "C1 suction temperature"
			::= { scalarsObjects2 128 }

			c1Superheat_2 OBJECT-TYPE
			SYNTAX Integer32
			MAX-ACCESS read-only
			STATUS current
			DESCRIPTION "C1 super-heating"
			::= { scalarsObjects2 129 }

			c1CompRatio_2 OBJECT-TYPE
			SYNTAX Integer32
			MAX-ACCESS read-only
			STATUS current
			DESCRIPTION "C1 compression ratio"
			::= { scalarsObjects2 130 }

			c1DischTemp_2 OBJECT-TYPE
			SYNTAX Integer32
			MAX-ACCESS read-only
			STATUS current
			DESCRIPTION "C1 discharge temperature"
			::= { scalarsObjects2 131 }

			c1CondPress_2 OBJECT-TYPE
			SYNTAX Integer32
			MAX-ACCESS read-only
			STATUS current
			DESCRIPTION "C1 condensation pressure"
			::= { scalarsObjects2 132 }

			c1CondTemp_2 OBJECT-TYPE
			SYNTAX Integer32
			MAX-ACCESS read-only
			STATUS current
			DESCRIPTION "C1 condensation temperature"
			::= { scalarsObjects2 133 }

			c1Desuperheat_2 OBJECT-TYPE
			SYNTAX Integer32
			MAX-ACCESS read-only
			STATUS current
			DESCRIPTION "C1 de-superheating"
			::= { scalarsObjects2 134 }

			c1LiquidTemp_2 OBJECT-TYPE
			SYNTAX Integer32
			MAX-ACCESS read-only
			STATUS current
			DESCRIPTION "C1 liquid temperature"
			::= { scalarsObjects2 135 }

			c1Subcooling_2 OBJECT-TYPE
			SYNTAX Integer32
			MAX-ACCESS read-only
			STATUS current
			DESCRIPTION "C1 sub-cooling"
			::= { scalarsObjects2 136 }

			eEV1SHSet_2 OBJECT-TYPE
			SYNTAX Integer32
			MAX-ACCESS read-only
			STATUS current
			DESCRIPTION "EEV1 super-heating set-point"
			::= { scalarsObjects2 137 }

			eEV1Position_2 OBJECT-TYPE
			SYNTAX Integer32
			MAX-ACCESS read-only
			STATUS current
			DESCRIPTION "EEV1 position"
			::= { scalarsObjects2 138 }

			eEV1Status_2 OBJECT-TYPE
			SYNTAX Integer32
			MAX-ACCESS read-only
			STATUS current
			DESCRIPTION "EEV1 working status"
			::= { scalarsObjects2 139 }

			cond1ActualSet_2 OBJECT-TYPE
			SYNTAX Integer32
			MAX-ACCESS read-only
			STATUS current
			DESCRIPTION "Condenser 1 current set"
			::= { scalarsObjects2 140 }

			cond1Req_2 OBJECT-TYPE
			SYNTAX Integer32
			MAX-ACCESS read-only
			STATUS current
			DESCRIPTION "Condenser 1 request"
			::= { scalarsObjects2 141 }

			c2EvapPres_2 OBJECT-TYPE
			SYNTAX Integer32
			MAX-ACCESS read-only
			STATUS current
			DESCRIPTION "C2 evaporation pressure"
			::= { scalarsObjects2 142 }

			c2EvapTemp_2 OBJECT-TYPE
			SYNTAX Integer32
			MAX-ACCESS read-only
			STATUS current
			DESCRIPTION "C2 evaporation temperature"
			::= { scalarsObjects2 143 }

			c2SuctionTemp_2 OBJECT-TYPE
			SYNTAX Integer32
			MAX-ACCESS read-only
			STATUS current
			DESCRIPTION "C2 suction temperature"
			::= { scalarsObjects2 144 }

			c2Superheat_2 OBJECT-TYPE
			SYNTAX Integer32
			MAX-ACCESS read-only
			STATUS current
			DESCRIPTION "C2 super-heating"
			::= { scalarsObjects2 145 }

			c2CompRatio_2 OBJECT-TYPE
			SYNTAX Integer32
			MAX-ACCESS read-only
			STATUS current
			DESCRIPTION "C2 compression ratio"
			::= { scalarsObjects2 146 }

			c2DischTemp_2 OBJECT-TYPE
			SYNTAX Integer32
			MAX-ACCESS read-only
			STATUS current
			DESCRIPTION "C2 discharge temperature"
			::= { scalarsObjects2 147 }

			c2CondPress_2 OBJECT-TYPE
			SYNTAX Integer32
			MAX-ACCESS read-only
			STATUS current
			DESCRIPTION "C2 condensation pressure"
			::= { scalarsObjects2 148 }

			c2CondTemp_2 OBJECT-TYPE
			SYNTAX Integer32
			MAX-ACCESS read-only
			STATUS current
			DESCRIPTION "C2 condensation temperature"
			::= { scalarsObjects2 149 }

			c2Desuperheat_2 OBJECT-TYPE
			SYNTAX Integer32
			MAX-ACCESS read-only
			STATUS current
			DESCRIPTION "C2 de-superheating"
			::= { scalarsObjects2 150 }

			c2LiquidTemp_2 OBJECT-TYPE
			SYNTAX Integer32
			MAX-ACCESS read-only
			STATUS current
			DESCRIPTION "C2 liquid temperature"
			::= { scalarsObjects2 151 }

			c2Subcooling_2 OBJECT-TYPE
			SYNTAX Integer32
			MAX-ACCESS read-only
			STATUS current
			DESCRIPTION "C2 sub-cooling"
			::= { scalarsObjects2 152 }

			eEV2SHSet_2 OBJECT-TYPE
			SYNTAX Integer32
			MAX-ACCESS read-only
			STATUS current
			DESCRIPTION "EEV2 superheat set-point"
			::= { scalarsObjects2 153 }

			eEV2Position_2 OBJECT-TYPE
			SYNTAX Integer32
			MAX-ACCESS read-only
			STATUS current
			DESCRIPTION "EEV2 position"
			::= { scalarsObjects2 154 }

			eEV2Status_2 OBJECT-TYPE
			SYNTAX Integer32
			MAX-ACCESS read-only
			STATUS current
			DESCRIPTION "EEV2 working status"
			::= { scalarsObjects2 155 }

			cond2ActualSet_2 OBJECT-TYPE
			SYNTAX Integer32
			MAX-ACCESS read-only
			STATUS current
			DESCRIPTION "Condenser 2 current set"
			::= { scalarsObjects2 156 }

			cond2Req_2 OBJECT-TYPE
			SYNTAX Integer32
			MAX-ACCESS read-only
			STATUS current
			DESCRIPTION "Condenser 2 request"
			::= { scalarsObjects2 157 }

			waterINTemp1_2 OBJECT-TYPE
			SYNTAX Integer32
			MAX-ACCESS read-only
			STATUS current
			DESCRIPTION "Water IN temperature 1"
			::= { scalarsObjects2 158 }

			waterOUTTemp1_2 OBJECT-TYPE
			SYNTAX Integer32
			MAX-ACCESS read-only
			STATUS current
			DESCRIPTION "Water OUT temperature 1"
			::= { scalarsObjects2 159 }

			waterDT1_2 OBJECT-TYPE
			SYNTAX Integer32
			MAX-ACCESS read-only
			STATUS current
			DESCRIPTION "Water temperature delta 1"
			::= { scalarsObjects2 160 }

			waterFlow1_2 OBJECT-TYPE
			SYNTAX Integer32
			MAX-ACCESS read-only
			STATUS current
			DESCRIPTION "Water flow rate 1"
			::= { scalarsObjects2 161 }

			actWatFlowSet1_2 OBJECT-TYPE
			SYNTAX Integer32
			MAX-ACCESS read-only
			STATUS current
			DESCRIPTION "Actual water flow set 1"
			::= { scalarsObjects2 162 }

			waterCoolCap1_2 OBJECT-TYPE
			SYNTAX Integer32
			MAX-ACCESS read-only
			STATUS current
			DESCRIPTION "Water cooling capacity 1"
			::= { scalarsObjects2 163 }

			eER1_2 OBJECT-TYPE
			SYNTAX Integer32
			MAX-ACCESS read-only
			STATUS current
			DESCRIPTION "EER 1"
			::= { scalarsObjects2 164 }

			valve1Position_2 OBJECT-TYPE
			SYNTAX Integer32
			MAX-ACCESS read-only
			STATUS current
			DESCRIPTION "Water valve 1 position"
			::= { scalarsObjects2 165 }

			waterINTemp2_2 OBJECT-TYPE
			SYNTAX Integer32
			MAX-ACCESS read-only
			STATUS current
			DESCRIPTION "Water IN temperature 2"
			::= { scalarsObjects2 166 }

			waterOUTTemp2_2 OBJECT-TYPE
			SYNTAX Integer32
			MAX-ACCESS read-only
			STATUS current
			DESCRIPTION "Water OUT temperature 2"
			::= { scalarsObjects2 167 }

			waterDT2_2 OBJECT-TYPE
			SYNTAX Integer32
			MAX-ACCESS read-only
			STATUS current
			DESCRIPTION "Water temperature delta 2"
			::= { scalarsObjects2 168 }

			waterFlow2_2 OBJECT-TYPE
			SYNTAX Integer32
			MAX-ACCESS read-only
			STATUS current
			DESCRIPTION "Water flow rate 2"
			::= { scalarsObjects2 169 }

			actWatFlowSet2_2 OBJECT-TYPE
			SYNTAX Integer32
			MAX-ACCESS read-only
			STATUS current
			DESCRIPTION "Actual water flow set 2"
			::= { scalarsObjects2 170 }

			waterCoolCap2_2 OBJECT-TYPE
			SYNTAX Integer32
			MAX-ACCESS read-only
			STATUS current
			DESCRIPTION "Water cooling capacity 2"
			::= { scalarsObjects2 171 }

			eER2_2 OBJECT-TYPE
			SYNTAX Integer32
			MAX-ACCESS read-only
			STATUS current
			DESCRIPTION "EER 2"
			::= { scalarsObjects2 172 }

			valve2Position_2 OBJECT-TYPE
			SYNTAX Integer32
			MAX-ACCESS read-only
			STATUS current
			DESCRIPTION "Water valve 2 position"
			::= { scalarsObjects2 173 }

			humSteamProd_2 OBJECT-TYPE
			SYNTAX Integer32
			MAX-ACCESS read-only
			STATUS current
			DESCRIPTION "Current steam production"
			::= { scalarsObjects2 174 }

			humWaterConduct_2 OBJECT-TYPE
			SYNTAX Integer32
			MAX-ACCESS read-only
			STATUS current
			DESCRIPTION "Humidifier conductivity"
			::= { scalarsObjects2 175 }

			humCurrent_2 OBJECT-TYPE
			SYNTAX Integer32
			MAX-ACCESS read-only
			STATUS current
			DESCRIPTION "Humidifier abs. Current"
			::= { scalarsObjects2 176 }

			humWorkingMode_2 OBJECT-TYPE
			SYNTAX INTEGER
			MAX-ACCESS read-only
			STATUS current
			DESCRIPTION "Humidifier operating mode"
			::= { scalarsObjects2 177 }

			humWorkStatus_2 OBJECT-TYPE
			SYNTAX INTEGER
			MAX-ACCESS read-only
			STATUS current
			DESCRIPTION "Humidifier operating status"
			::= { scalarsObjects2 178 }

			heaterReq_2 OBJECT-TYPE
			SYNTAX Integer32
			MAX-ACCESS read-only
			STATUS current
			DESCRIPTION "Electric heater request"
			::= { scalarsObjects2 179 }

			heaterActiveStg_2 OBJECT-TYPE
			SYNTAX Integer32
			MAX-ACCESS read-only
			STATUS current
			DESCRIPTION "Number of active stages"
			::= { scalarsObjects2 180 }

			elHeaterPower_2 OBJECT-TYPE
			SYNTAX Integer32
			MAX-ACCESS read-only
			STATUS current
			DESCRIPTION "Electric heater power"
			::= { scalarsObjects2 181 }

			heatValveReq_2 OBJECT-TYPE
			SYNTAX Integer32
			MAX-ACCESS read-only
			STATUS current
			DESCRIPTION "Hot water valve request"
			::= { scalarsObjects2 182 }

			dryCoolerActSet_2 OBJECT-TYPE
			SYNTAX Integer32
			MAX-ACCESS read-only
			STATUS current
			DESCRIPTION "Current dry cooler set"
			::= { scalarsObjects2 183 }

			dryCoolerReq_2 OBJECT-TYPE
			SYNTAX Integer32
			MAX-ACCESS read-only
			STATUS current
			DESCRIPTION "Dry cooler request"
			::= { scalarsObjects2 184 }

			unitWH_2 OBJECT-TYPE
			SYNTAX Integer32
			MAX-ACCESS read-only
			STATUS current
			DESCRIPTION "Unit working hours"
			::= { scalarsObjects2 185 }

			c1WH_2 OBJECT-TYPE
			SYNTAX Integer32
			MAX-ACCESS read-only
			STATUS current
			DESCRIPTION "Compressor1 working hours"
			::= { scalarsObjects2 186 }

			c1Startup_2 OBJECT-TYPE
			SYNTAX Integer32
			MAX-ACCESS read-only
			STATUS current
			DESCRIPTION "Compressor 1 startups"
			::= { scalarsObjects2 187 }

			c2WH_2 OBJECT-TYPE
			SYNTAX Integer32
			MAX-ACCESS read-only
			STATUS current
			DESCRIPTION "Compressor2 working hours"
			::= { scalarsObjects2 188 }

			c2Startup_2 OBJECT-TYPE
			SYNTAX Integer32
			MAX-ACCESS read-only
			STATUS current
			DESCRIPTION "Compressor 2 startups"
			::= { scalarsObjects2 189 }

			coolValveWH_2 OBJECT-TYPE
			SYNTAX Integer32
			MAX-ACCESS read-only
			STATUS current
			DESCRIPTION "Cooling working hours"
			::= { scalarsObjects2 190 }

			heatingWH_2 OBJECT-TYPE
			SYNTAX Integer32
			MAX-ACCESS read-only
			STATUS current
			DESCRIPTION "Heating working hours"
			::= { scalarsObjects2 191 }

			humidifWH_2 OBJECT-TYPE
			SYNTAX Integer32
			MAX-ACCESS read-only
			STATUS current
			DESCRIPTION "Humidifier working hours"
			::= { scalarsObjects2 192 }

			freeCoolWH_2 OBJECT-TYPE
			SYNTAX Integer32
			MAX-ACCESS read-only
			STATUS current
			DESCRIPTION "FC working hours"
			::= { scalarsObjects2 193 }

			dryCoolerWH_2 OBJECT-TYPE
			SYNTAX Integer32
			MAX-ACCESS read-only
			STATUS current
			DESCRIPTION "Dry cooler working hours"
			::= { scalarsObjects2 194 }

			cond1WH_2 OBJECT-TYPE
			SYNTAX Integer32
			MAX-ACCESS read-only
			STATUS current
			DESCRIPTION "Condenser1 working hours"
			::= { scalarsObjects2 195 }

			cond2WH_2 OBJECT-TYPE
			SYNTAX Integer32
			MAX-ACCESS read-only
			STATUS current
			DESCRIPTION "Condenser2 working hours"
			::= { scalarsObjects2 196 }

			tempSetpoint_2 OBJECT-TYPE
			SYNTAX Integer32
			MAX-ACCESS read-write
			STATUS current
			DESCRIPTION "Temperature set-point"
			::= { scalarsObjects2 197 }

			humSetpoint_2 OBJECT-TYPE
			SYNTAX Integer32
			MAX-ACCESS read-write
			STATUS current
			DESCRIPTION "Humidity set-point"
			::= { scalarsObjects2 198 }

			airFlowSetpoint_2 OBJECT-TYPE
			SYNTAX Integer32
			MAX-ACCESS read-write
			STATUS current
			DESCRIPTION "Air flow set-point"
			::= { scalarsObjects2 199 }

			airPresSetpoint_2 OBJECT-TYPE
			SYNTAX Integer32
			MAX-ACCESS read-write
			STATUS current
			DESCRIPTION "Air pressure set-point"
			::= { scalarsObjects2 200 }

			airDTSetpoint_2 OBJECT-TYPE
			SYNTAX Integer32
			MAX-ACCESS read-write
			STATUS current
			DESCRIPTION "Air temperature delta set"
			::= { scalarsObjects2 201 }

			tempControlSel_2 OBJECT-TYPE
			SYNTAX Integer32
			MAX-ACCESS read-write
			STATUS current
			DESCRIPTION "Regulation sensor"
			::= { scalarsObjects2 202 }

			tempControlType_2 OBJECT-TYPE
			SYNTAX Integer32
			MAX-ACCESS read-write
			STATUS current
			DESCRIPTION "Regulation type"
			::= { scalarsObjects2 203 }

			tPropBand_2 OBJECT-TYPE
			SYNTAX Integer32
			MAX-ACCESS read-write
			STATUS current
			DESCRIPTION "Proportional Band"
			::= { scalarsObjects2 204 }

			tIntegralTime_2 OBJECT-TYPE
			SYNTAX Integer32
			MAX-ACCESS read-write
			STATUS current
			DESCRIPTION "Integration time"
			::= { scalarsObjects2 205 }

			tDerivativeTime_2 OBJECT-TYPE
			SYNTAX Integer32
			MAX-ACCESS read-write
			STATUS current
			DESCRIPTION "Derivative time"
			::= { scalarsObjects2 206 }

			highTAlOffset_2 OBJECT-TYPE
			SYNTAX Integer32
			MAX-ACCESS read-write
			STATUS current
			DESCRIPTION "High temperature offset"
			::= { scalarsObjects2 207 }

			lowTAlOffset_2 OBJECT-TYPE
			SYNTAX Integer32
			MAX-ACCESS read-write
			STATUS current
			DESCRIPTION "Low temperature offset"
			::= { scalarsObjects2 208 }

			highLimitTThr_2 OBJECT-TYPE
			SYNTAX Integer32
			MAX-ACCESS read-write
			STATUS current
			DESCRIPTION "High limit temp. thresh."
			::= { scalarsObjects2 209 }

			highLimitTMng_2 OBJECT-TYPE
			SYNTAX Integer32
			MAX-ACCESS read-write
			STATUS current
			DESCRIPTION "High limit temp. managem."
			::= { scalarsObjects2 210 }

			lowLimitTThr_2 OBJECT-TYPE
			SYNTAX Integer32
			MAX-ACCESS read-write
			STATUS current
			DESCRIPTION "Low limit temp.thresh."
			::= { scalarsObjects2 211 }

			lowLimitTMng_2 OBJECT-TYPE
			SYNTAX Integer32
			MAX-ACCESS read-write
			STATUS current
			DESCRIPTION "Low limit temp. managem."
			::= { scalarsObjects2 212 }

			dehumPropBand_2 OBJECT-TYPE
			SYNTAX Integer32
			MAX-ACCESS read-write
			STATUS current
			DESCRIPTION "Dehumid. proportion. band"
			::= { scalarsObjects2 213 }

			humPropBand_2 OBJECT-TYPE
			SYNTAX Integer32
			MAX-ACCESS read-write
			STATUS current
			DESCRIPTION "Humid. proportion. band"
			::= { scalarsObjects2 214 }

			hRetHAlOffset_2 OBJECT-TYPE
			SYNTAX Integer32
			MAX-ACCESS read-write
			STATUS current
			DESCRIPTION "High humidity offset"
			::= { scalarsObjects2 215 }

			lRetHAlOffset_2 OBJECT-TYPE
			SYNTAX Integer32
			MAX-ACCESS read-write
			STATUS current
			DESCRIPTION "Low humidity offset"
			::= { scalarsObjects2 216 }

			highSupHumThr_2 OBJECT-TYPE
			SYNTAX Integer32
			MAX-ACCESS read-write
			STATUS current
			DESCRIPTION "High supp. humidity thr."
			::= { scalarsObjects2 217 }

			lowSupHumThr_2 OBJECT-TYPE
			SYNTAX Integer32
			MAX-ACCESS read-write
			STATUS current
			DESCRIPTION "Low supp. humidity thr."
			::= { scalarsObjects2 218 }

			fCDelta_2 OBJECT-TYPE
			SYNTAX Integer32
			MAX-ACCESS read-write
			STATUS current
			DESCRIPTION "Free cooling delta"
			::= { scalarsObjects2 219 }

			tSWaterSet_2 OBJECT-TYPE
			SYNTAX Integer32
			MAX-ACCESS read-write
			STATUS current
			DESCRIPTION "Two sources set-point"
			::= { scalarsObjects2 220 }

			tSWaterPropBand_2 OBJECT-TYPE
			SYNTAX Integer32
			MAX-ACCESS read-write
			STATUS current
			DESCRIPTION "Two sources band"
			::= { scalarsObjects2 221 }

			tSAirTempSet_2 OBJECT-TYPE
			SYNTAX Integer32
			MAX-ACCESS read-write
			STATUS current
			DESCRIPTION "TS room temp. Exch. set"
			::= { scalarsObjects2 222 }

			condSetpoint_2 OBJECT-TYPE
			SYNTAX Integer32
			MAX-ACCESS read-write
			STATUS current
			DESCRIPTION "Condensation set-point"
			::= { scalarsObjects2 223 }

			condPropoBand_2 OBJECT-TYPE
			SYNTAX Integer32
			MAX-ACCESS read-write
			STATUS current
			DESCRIPTION "Condensation band"
			::= { scalarsObjects2 224 }

			condSetIncrease_2 OBJECT-TYPE
			SYNTAX Integer32
			MAX-ACCESS read-write
			STATUS current
			DESCRIPTION "Condensation set increase"
			::= { scalarsObjects2 225 }

			maxCondSetpoint_2 OBJECT-TYPE
			SYNTAX Integer32
			MAX-ACCESS read-write
			STATUS current
			DESCRIPTION "Maximum condensation set"
			::= { scalarsObjects2 226 }

			dryCoolerSet_2 OBJECT-TYPE
			SYNTAX Integer32
			MAX-ACCESS read-write
			STATUS current
			DESCRIPTION "Dry cooler set-point"
			::= { scalarsObjects2 227 }

			dryCoolPropBand_2 OBJECT-TYPE
			SYNTAX Integer32
			MAX-ACCESS read-write
			STATUS current
			DESCRIPTION "Dry cooler band"
			::= { scalarsObjects2 228 }

			dryCoolSetIncr_2 OBJECT-TYPE
			SYNTAX Integer32
			MAX-ACCESS read-write
			STATUS current
			DESCRIPTION "Dry Cooler set increase"
			::= { scalarsObjects2 229 }

			maxDryCoolerSet_2 OBJECT-TYPE
			SYNTAX Integer32
			MAX-ACCESS read-write
			STATUS current
			DESCRIPTION "Maximum dry Cooler set"
			::= { scalarsObjects2 230 }

			dirtyFiltSet_2 OBJECT-TYPE
			SYNTAX Integer32
			MAX-ACCESS read-write
			STATUS current
			DESCRIPTION "Dirty filter set-point"
			::= { scalarsObjects2 231 }

			dirtyFiltDiff_2 OBJECT-TYPE
			SYNTAX Integer32
			MAX-ACCESS read-write
			STATUS current
			DESCRIPTION "Dirty filter differential"
			::= { scalarsObjects2 232 }

			invCompAlCode1_2 OBJECT-TYPE
			SYNTAX Integer32
			MAX-ACCESS read-only
			STATUS current
			DESCRIPTION "DC Inverter alarm code 1"
			::= { scalarsObjects2 233 }

			invCompAlCode2_2 OBJECT-TYPE
			SYNTAX Integer32
			MAX-ACCESS read-only
			STATUS current
			DESCRIPTION "DC Inverter alarm code 2"
			::= { scalarsObjects2 234 }

			invCompAlCode3_2 OBJECT-TYPE
			SYNTAX Integer32
			MAX-ACCESS read-only
			STATUS current
			DESCRIPTION "DC Inverter alarm code 3"
			::= { scalarsObjects2 235 }

			invCompAlCode4_2 OBJECT-TYPE
			SYNTAX Integer32
			MAX-ACCESS read-only
			STATUS current
			DESCRIPTION "DC Inverter alarm code 4"
			::= { scalarsObjects2 236 }

			invCompAlCode5_2 OBJECT-TYPE
			SYNTAX Integer32
			MAX-ACCESS read-only
			STATUS current
			DESCRIPTION "DC Inverter alarm code 5"
			::= { scalarsObjects2 237 }

		alarms2 OBJECT IDENTIFIER  ::= { node2 3 }

			generalAl_2 OBJECT-TYPE
			SYNTAX INTEGER
			MAX-ACCESS read-only
			STATUS current
			DESCRIPTION "General alarams"
			::= { alarms2 1 }

			notCriticAl_2 OBJECT-TYPE
			SYNTAX INTEGER
			MAX-ACCESS read-only
			STATUS current
			DESCRIPTION "Not critical alarms"
			::= { alarms2 2 }

			criticalAl_2 OBJECT-TYPE
			SYNTAX INTEGER
			MAX-ACCESS read-only
			STATUS current
			DESCRIPTION "Critical alarms"
			::= { alarms2 3 }

			fansAl_2 OBJECT-TYPE
			SYNTAX INTEGER
			MAX-ACCESS read-only
			STATUS current
			DESCRIPTION "Fans alarms"
			::= { alarms2 4 }

			compAl_2 OBJECT-TYPE
			SYNTAX INTEGER
			MAX-ACCESS read-only
			STATUS current
			DESCRIPTION "Compressors alarms"
			::= { alarms2 5 }

			tempAl_2 OBJECT-TYPE
			SYNTAX INTEGER
			MAX-ACCESS read-only
			STATUS current
			DESCRIPTION "Temperature alarms"
			::= { alarms2 6 }

			humidityAl_2 OBJECT-TYPE
			SYNTAX INTEGER
			MAX-ACCESS read-only
			STATUS current
			DESCRIPTION "Humidity alarms"
			::= { alarms2 7 }

			damperAl_2 OBJECT-TYPE
			SYNTAX INTEGER
			MAX-ACCESS read-only
			STATUS current
			DESCRIPTION "Damper status alarm"
			::= { alarms2 8 }

			fireSmokeAl_2 OBJECT-TYPE
			SYNTAX INTEGER
			MAX-ACCESS read-only
			STATUS current
			DESCRIPTION "Fire/Smoke alarm"
			::= { alarms2 9 }

			gSeriousAl_2 OBJECT-TYPE
			SYNTAX INTEGER
			MAX-ACCESS read-only
			STATUS current
			DESCRIPTION "Critical generic alarm"
			::= { alarms2 10 }

			fansGenAl_2 OBJECT-TYPE
			SYNTAX INTEGER
			MAX-ACCESS read-only
			STATUS current
			DESCRIPTION "General supply fans alarm"
			::= { alarms2 11 }

			f1GeneralAl_2 OBJECT-TYPE
			SYNTAX INTEGER
			MAX-ACCESS read-only
			STATUS current
			DESCRIPTION "Fan general alarm 1"
			::= { alarms2 12 }

			f1PowerAl_2 OBJECT-TYPE
			SYNTAX INTEGER
			MAX-ACCESS read-only
			STATUS current
			DESCRIPTION "Phase failure/undervolt.1"
			::= { alarms2 13 }

			f1CommAl_2 OBJECT-TYPE
			SYNTAX INTEGER
			MAX-ACCESS read-only
			STATUS current
			DESCRIPTION "Communication 1"
			::= { alarms2 14 }

			f1HiTempAl_2 OBJECT-TYPE
			SYNTAX INTEGER
			MAX-ACCESS read-only
			STATUS current
			DESCRIPTION "Power mod overheated 1"
			::= { alarms2 15 }

			f1NetComAl_2 OBJECT-TYPE
			SYNTAX INTEGER
			MAX-ACCESS read-only
			STATUS current
			DESCRIPTION "Master/Slave com. 1"
			::= { alarms2 16 }

			f1InvRegAl_2 OBJECT-TYPE
			SYNTAX INTEGER
			MAX-ACCESS read-only
			STATUS current
			DESCRIPTION "Regulation module 1"
			::= { alarms2 17 }

			f1HiMotTAl_2 OBJECT-TYPE
			SYNTAX INTEGER
			MAX-ACCESS read-only
			STATUS current
			DESCRIPTION "Motor overheated 1"
			::= { alarms2 18 }

			f1HallSenAl_2 OBJECT-TYPE
			SYNTAX INTEGER
			MAX-ACCESS read-only
			STATUS current
			DESCRIPTION "Hall sensor error 1"
			::= { alarms2 19 }

			f1OverlAl_2 OBJECT-TYPE
			SYNTAX INTEGER
			MAX-ACCESS read-only
			STATUS current
			DESCRIPTION "Locked motor 1"
			::= { alarms2 20 }

			f1LowDCAl_2 OBJECT-TYPE
			SYNTAX INTEGER
			MAX-ACCESS read-only
			STATUS current
			DESCRIPTION "Low DC 1"
			::= { alarms2 21 }

			f2GeneralAl_2 OBJECT-TYPE
			SYNTAX INTEGER
			MAX-ACCESS read-only
			STATUS current
			DESCRIPTION "Fan general alarm 2"
			::= { alarms2 22 }

			f2PowerAl_2 OBJECT-TYPE
			SYNTAX INTEGER
			MAX-ACCESS read-only
			STATUS current
			DESCRIPTION "Phase failure/undervolt.2"
			::= { alarms2 23 }

			f2CommAl_2 OBJECT-TYPE
			SYNTAX INTEGER
			MAX-ACCESS read-only
			STATUS current
			DESCRIPTION "Communication 2"
			::= { alarms2 24 }

			f2HiTempAl_2 OBJECT-TYPE
			SYNTAX INTEGER
			MAX-ACCESS read-only
			STATUS current
			DESCRIPTION "Power mod overheated 2"
			::= { alarms2 25 }

			f2NetComAl_2 OBJECT-TYPE
			SYNTAX INTEGER
			MAX-ACCESS read-only
			STATUS current
			DESCRIPTION "Master/Slave com. 2"
			::= { alarms2 26 }

			f2InvRegAl_2 OBJECT-TYPE
			SYNTAX INTEGER
			MAX-ACCESS read-only
			STATUS current
			DESCRIPTION "Regulation module 2"
			::= { alarms2 27 }

			f2HiMotTAl_2 OBJECT-TYPE
			SYNTAX INTEGER
			MAX-ACCESS read-only
			STATUS current
			DESCRIPTION "Motor overheated 2"
			::= { alarms2 28 }

			f2HallSenAl_2 OBJECT-TYPE
			SYNTAX INTEGER
			MAX-ACCESS read-only
			STATUS current
			DESCRIPTION "Hall sensor error 2"
			::= { alarms2 29 }

			f2OverlAl_2 OBJECT-TYPE
			SYNTAX INTEGER
			MAX-ACCESS read-only
			STATUS current
			DESCRIPTION "Locked motor 2"
			::= { alarms2 30 }

			f2LowDCAl_2 OBJECT-TYPE
			SYNTAX INTEGER
			MAX-ACCESS read-only
			STATUS current
			DESCRIPTION "Low DC 2"
			::= { alarms2 31 }

			f3GeneralAl_2 OBJECT-TYPE
			SYNTAX INTEGER
			MAX-ACCESS read-only
			STATUS current
			DESCRIPTION "Fan general alarm 3"
			::= { alarms2 32 }

			f3PowerAl_2 OBJECT-TYPE
			SYNTAX INTEGER
			MAX-ACCESS read-only
			STATUS current
			DESCRIPTION "Phase failure/undervolt.3"
			::= { alarms2 33 }

			f3CommAl_2 OBJECT-TYPE
			SYNTAX INTEGER
			MAX-ACCESS read-only
			STATUS current
			DESCRIPTION "Communication 3"
			::= { alarms2 34 }

			f3HiTempAl_2 OBJECT-TYPE
			SYNTAX INTEGER
			MAX-ACCESS read-only
			STATUS current
			DESCRIPTION "Power mod overheated 3"
			::= { alarms2 35 }

			f3NetComAl_2 OBJECT-TYPE
			SYNTAX INTEGER
			MAX-ACCESS read-only
			STATUS current
			DESCRIPTION "Master/Slave com. 3"
			::= { alarms2 36 }

			f3InvRegAl_2 OBJECT-TYPE
			SYNTAX INTEGER
			MAX-ACCESS read-only
			STATUS current
			DESCRIPTION "Regulation module 3"
			::= { alarms2 37 }

			f3HiMotTAl_2 OBJECT-TYPE
			SYNTAX INTEGER
			MAX-ACCESS read-only
			STATUS current
			DESCRIPTION "Motor overheated 3"
			::= { alarms2 38 }

			f3HallSenAl_2 OBJECT-TYPE
			SYNTAX INTEGER
			MAX-ACCESS read-only
			STATUS current
			DESCRIPTION "Hall sensor error 3"
			::= { alarms2 39 }

			f3OverlAl_2 OBJECT-TYPE
			SYNTAX INTEGER
			MAX-ACCESS read-only
			STATUS current
			DESCRIPTION "Locked motor 3"
			::= { alarms2 40 }

			f3LowDCAl_2 OBJECT-TYPE
			SYNTAX INTEGER
			MAX-ACCESS read-only
			STATUS current
			DESCRIPTION "Low DC 3"
			::= { alarms2 41 }

			f4GeneralAl_2 OBJECT-TYPE
			SYNTAX INTEGER
			MAX-ACCESS read-only
			STATUS current
			DESCRIPTION "Fan general alarm 4"
			::= { alarms2 42 }

			f4PowerAl_2 OBJECT-TYPE
			SYNTAX INTEGER
			MAX-ACCESS read-only
			STATUS current
			DESCRIPTION "Phase failure/undervolt.4"
			::= { alarms2 43 }

			f4CommAl_2 OBJECT-TYPE
			SYNTAX INTEGER
			MAX-ACCESS read-only
			STATUS current
			DESCRIPTION "Communication 4"
			::= { alarms2 44 }

			f4HiTempAl_2 OBJECT-TYPE
			SYNTAX INTEGER
			MAX-ACCESS read-only
			STATUS current
			DESCRIPTION "Power mod overheated 4"
			::= { alarms2 45 }

			f4NetComAl_2 OBJECT-TYPE
			SYNTAX INTEGER
			MAX-ACCESS read-only
			STATUS current
			DESCRIPTION "Master/Slave com. 4"
			::= { alarms2 46 }

			f4InvRegAl_2 OBJECT-TYPE
			SYNTAX INTEGER
			MAX-ACCESS read-only
			STATUS current
			DESCRIPTION "Regulation module 4"
			::= { alarms2 47 }

			f4HiMotTAl_2 OBJECT-TYPE
			SYNTAX INTEGER
			MAX-ACCESS read-only
			STATUS current
			DESCRIPTION "Motor overheated 4"
			::= { alarms2 48 }

			f4HallSenAl_2 OBJECT-TYPE
			SYNTAX INTEGER
			MAX-ACCESS read-only
			STATUS current
			DESCRIPTION "Hall sensor error 4"
			::= { alarms2 49 }

			f4OverlAl_2 OBJECT-TYPE
			SYNTAX INTEGER
			MAX-ACCESS read-only
			STATUS current
			DESCRIPTION "Locked motor 4"
			::= { alarms2 50 }

			f4LowDCAl_2 OBJECT-TYPE
			SYNTAX INTEGER
			MAX-ACCESS read-only
			STATUS current
			DESCRIPTION "Low DC 4"
			::= { alarms2 51 }

			f5GeneralAl_2 OBJECT-TYPE
			SYNTAX INTEGER
			MAX-ACCESS read-only
			STATUS current
			DESCRIPTION "Fan general alarm 5"
			::= { alarms2 52 }

			f5PowerAl_2 OBJECT-TYPE
			SYNTAX INTEGER
			MAX-ACCESS read-only
			STATUS current
			DESCRIPTION "Phase failure/undervolt.5"
			::= { alarms2 53 }

			f5CommAl_2 OBJECT-TYPE
			SYNTAX INTEGER
			MAX-ACCESS read-only
			STATUS current
			DESCRIPTION "Communication 5"
			::= { alarms2 54 }

			f5HiTempAl_2 OBJECT-TYPE
			SYNTAX INTEGER
			MAX-ACCESS read-only
			STATUS current
			DESCRIPTION "Power mod overheated 5"
			::= { alarms2 55 }

			f5NetComAl_2 OBJECT-TYPE
			SYNTAX INTEGER
			MAX-ACCESS read-only
			STATUS current
			DESCRIPTION "Master/Slave com. 5"
			::= { alarms2 56 }

			f5InvRegAl_2 OBJECT-TYPE
			SYNTAX INTEGER
			MAX-ACCESS read-only
			STATUS current
			DESCRIPTION "Regulation module 5"
			::= { alarms2 57 }

			f5HiMotTAl_2 OBJECT-TYPE
			SYNTAX INTEGER
			MAX-ACCESS read-only
			STATUS current
			DESCRIPTION "Motor overheated 5"
			::= { alarms2 58 }

			f5HallSenAl_2 OBJECT-TYPE
			SYNTAX INTEGER
			MAX-ACCESS read-only
			STATUS current
			DESCRIPTION "Hall sensor error 5"
			::= { alarms2 59 }

			f5OverlAl_2 OBJECT-TYPE
			SYNTAX INTEGER
			MAX-ACCESS read-only
			STATUS current
			DESCRIPTION "Locked motor 5"
			::= { alarms2 60 }

			f5LowDCAl_2 OBJECT-TYPE
			SYNTAX INTEGER
			MAX-ACCESS read-only
			STATUS current
			DESCRIPTION "Low DC 5"
			::= { alarms2 61 }

			f6GeneralAl_2 OBJECT-TYPE
			SYNTAX INTEGER
			MAX-ACCESS read-only
			STATUS current
			DESCRIPTION "Fan general alarm 6"
			::= { alarms2 62 }

			f6PowerAl_2 OBJECT-TYPE
			SYNTAX INTEGER
			MAX-ACCESS read-only
			STATUS current
			DESCRIPTION "Phase failure/undervolt.6"
			::= { alarms2 63 }

			f6CommAl_2 OBJECT-TYPE
			SYNTAX INTEGER
			MAX-ACCESS read-only
			STATUS current
			DESCRIPTION "Communication 6"
			::= { alarms2 64 }

			f6HiTempAl_2 OBJECT-TYPE
			SYNTAX INTEGER
			MAX-ACCESS read-only
			STATUS current
			DESCRIPTION "Power mod overheated 6"
			::= { alarms2 65 }

			f6NetComAl_2 OBJECT-TYPE
			SYNTAX INTEGER
			MAX-ACCESS read-only
			STATUS current
			DESCRIPTION "Master/Slave com. 6"
			::= { alarms2 66 }

			f6InvRegAl_2 OBJECT-TYPE
			SYNTAX INTEGER
			MAX-ACCESS read-only
			STATUS current
			DESCRIPTION "Regulation module 6"
			::= { alarms2 67 }

			f6HiMotTAl_2 OBJECT-TYPE
			SYNTAX INTEGER
			MAX-ACCESS read-only
			STATUS current
			DESCRIPTION "Motor overheated 6"
			::= { alarms2 68 }

			f6HallSenAl_2 OBJECT-TYPE
			SYNTAX INTEGER
			MAX-ACCESS read-only
			STATUS current
			DESCRIPTION "Hall sensor error 6"
			::= { alarms2 69 }

			f6OverlAl_2 OBJECT-TYPE
			SYNTAX INTEGER
			MAX-ACCESS read-only
			STATUS current
			DESCRIPTION "Locked motor 6"
			::= { alarms2 70 }

			f6LowDCAl_2 OBJECT-TYPE
			SYNTAX INTEGER
			MAX-ACCESS read-only
			STATUS current
			DESCRIPTION "Low DC 6"
			::= { alarms2 71 }

			f7GeneralAl_2 OBJECT-TYPE
			SYNTAX INTEGER
			MAX-ACCESS read-only
			STATUS current
			DESCRIPTION "Fan general alarm 7"
			::= { alarms2 72 }

			f7PowerAl_2 OBJECT-TYPE
			SYNTAX INTEGER
			MAX-ACCESS read-only
			STATUS current
			DESCRIPTION "Phase failure/undervolt.7"
			::= { alarms2 73 }

			f7CommAl_2 OBJECT-TYPE
			SYNTAX INTEGER
			MAX-ACCESS read-only
			STATUS current
			DESCRIPTION "Communication 7"
			::= { alarms2 74 }

			f7HiTempAl_2 OBJECT-TYPE
			SYNTAX INTEGER
			MAX-ACCESS read-only
			STATUS current
			DESCRIPTION "Power mod overheated 7"
			::= { alarms2 75 }

			f7NetComAl_2 OBJECT-TYPE
			SYNTAX INTEGER
			MAX-ACCESS read-only
			STATUS current
			DESCRIPTION "Master/Slave com. 7"
			::= { alarms2 76 }

			f7InvRegAl_2 OBJECT-TYPE
			SYNTAX INTEGER
			MAX-ACCESS read-only
			STATUS current
			DESCRIPTION "Regulation module 7"
			::= { alarms2 77 }

			f7HiMotTAl_2 OBJECT-TYPE
			SYNTAX INTEGER
			MAX-ACCESS read-only
			STATUS current
			DESCRIPTION "Motor overheated 7"
			::= { alarms2 78 }

			f7HallSenAl_2 OBJECT-TYPE
			SYNTAX INTEGER
			MAX-ACCESS read-only
			STATUS current
			DESCRIPTION "Hall sensor error 7"
			::= { alarms2 79 }

			f7OverlAl_2 OBJECT-TYPE
			SYNTAX INTEGER
			MAX-ACCESS read-only
			STATUS current
			DESCRIPTION "Locked motor 7"
			::= { alarms2 80 }

			f7LowDCAl_2 OBJECT-TYPE
			SYNTAX INTEGER
			MAX-ACCESS read-only
			STATUS current
			DESCRIPTION "Low DC 7"
			::= { alarms2 81 }

			f8GeneralAl_2 OBJECT-TYPE
			SYNTAX INTEGER
			MAX-ACCESS read-only
			STATUS current
			DESCRIPTION "Fan general alarm 8"
			::= { alarms2 82 }

			f8PowerAl_2 OBJECT-TYPE
			SYNTAX INTEGER
			MAX-ACCESS read-only
			STATUS current
			DESCRIPTION "Phase failure/undervolt.8"
			::= { alarms2 83 }

			f8CommAl_2 OBJECT-TYPE
			SYNTAX INTEGER
			MAX-ACCESS read-only
			STATUS current
			DESCRIPTION "Communication 8"
			::= { alarms2 84 }

			f8HiTempAl_2 OBJECT-TYPE
			SYNTAX INTEGER
			MAX-ACCESS read-only
			STATUS current
			DESCRIPTION "Power mod overheated 8"
			::= { alarms2 85 }

			f8NetComAl_2 OBJECT-TYPE
			SYNTAX INTEGER
			MAX-ACCESS read-only
			STATUS current
			DESCRIPTION "Master/Slave com. 8"
			::= { alarms2 86 }

			f8InvRegAl_2 OBJECT-TYPE
			SYNTAX INTEGER
			MAX-ACCESS read-only
			STATUS current
			DESCRIPTION "Regulation module 8"
			::= { alarms2 87 }

			f8HiMotTAl_2 OBJECT-TYPE
			SYNTAX INTEGER
			MAX-ACCESS read-only
			STATUS current
			DESCRIPTION "Motor overheated 8"
			::= { alarms2 88 }

			f8HallSenAl_2 OBJECT-TYPE
			SYNTAX INTEGER
			MAX-ACCESS read-only
			STATUS current
			DESCRIPTION "Hall sensor error 8"
			::= { alarms2 89 }

			f8OverlAl_2 OBJECT-TYPE
			SYNTAX INTEGER
			MAX-ACCESS read-only
			STATUS current
			DESCRIPTION "Locked motor 8"
			::= { alarms2 90 }

			f8LowDCAl_2 OBJECT-TYPE
			SYNTAX INTEGER
			MAX-ACCESS read-only
			STATUS current
			DESCRIPTION "Low DC 8"
			::= { alarms2 91 }

			f9GeneralAl_2 OBJECT-TYPE
			SYNTAX INTEGER
			MAX-ACCESS read-only
			STATUS current
			DESCRIPTION "Fan general alarm 9"
			::= { alarms2 92 }

			f9PowerAl_2 OBJECT-TYPE
			SYNTAX INTEGER
			MAX-ACCESS read-only
			STATUS current
			DESCRIPTION "Phase failure/undervolt.9"
			::= { alarms2 93 }

			f9CommAl_2 OBJECT-TYPE
			SYNTAX INTEGER
			MAX-ACCESS read-only
			STATUS current
			DESCRIPTION "Communication 9"
			::= { alarms2 94 }

			f9HiTempAl_2 OBJECT-TYPE
			SYNTAX INTEGER
			MAX-ACCESS read-only
			STATUS current
			DESCRIPTION "Power mod overheated 9"
			::= { alarms2 95 }

			f9NetComAl_2 OBJECT-TYPE
			SYNTAX INTEGER
			MAX-ACCESS read-only
			STATUS current
			DESCRIPTION "Master/Slave com. 9"
			::= { alarms2 96 }

			f9InvRegAl_2 OBJECT-TYPE
			SYNTAX INTEGER
			MAX-ACCESS read-only
			STATUS current
			DESCRIPTION "Regulation module 9"
			::= { alarms2 97 }

			f9HiMotTAl_2 OBJECT-TYPE
			SYNTAX INTEGER
			MAX-ACCESS read-only
			STATUS current
			DESCRIPTION "Motor overheated 9"
			::= { alarms2 98 }

			f9HallSenAl_2 OBJECT-TYPE
			SYNTAX INTEGER
			MAX-ACCESS read-only
			STATUS current
			DESCRIPTION "Hall sensor error 9"
			::= { alarms2 99 }

			f9OverlAl_2 OBJECT-TYPE
			SYNTAX INTEGER
			MAX-ACCESS read-only
			STATUS current
			DESCRIPTION "Locked motor 9"
			::= { alarms2 100 }

			f9LowDCAl_2 OBJECT-TYPE
			SYNTAX INTEGER
			MAX-ACCESS read-only
			STATUS current
			DESCRIPTION "Low DC 9"
			::= { alarms2 101 }

			f10GenlAl_2 OBJECT-TYPE
			SYNTAX INTEGER
			MAX-ACCESS read-only
			STATUS current
			DESCRIPTION "Fan general alarm 10"
			::= { alarms2 102 }

			f10PowerAl_2 OBJECT-TYPE
			SYNTAX INTEGER
			MAX-ACCESS read-only
			STATUS current
			DESCRIPTION "Phase failure/undervolt.10"
			::= { alarms2 103 }

			f10CommAl_2 OBJECT-TYPE
			SYNTAX INTEGER
			MAX-ACCESS read-only
			STATUS current
			DESCRIPTION "Communication 10"
			::= { alarms2 104 }

			f10HiTempAl_2 OBJECT-TYPE
			SYNTAX INTEGER
			MAX-ACCESS read-only
			STATUS current
			DESCRIPTION "Power mod overheated 10"
			::= { alarms2 105 }

			f10NetComAl_2 OBJECT-TYPE
			SYNTAX INTEGER
			MAX-ACCESS read-only
			STATUS current
			DESCRIPTION "Master/Slave com. 10"
			::= { alarms2 106 }

			f10InvRegAl_2 OBJECT-TYPE
			SYNTAX INTEGER
			MAX-ACCESS read-only
			STATUS current
			DESCRIPTION "Regulation module 10"
			::= { alarms2 107 }

			f10HiMotTAl_2 OBJECT-TYPE
			SYNTAX INTEGER
			MAX-ACCESS read-only
			STATUS current
			DESCRIPTION "Motor overheated 10"
			::= { alarms2 108 }

			f10HallSAl_2 OBJECT-TYPE
			SYNTAX INTEGER
			MAX-ACCESS read-only
			STATUS current
			DESCRIPTION "Hall sensor error 10"
			::= { alarms2 109 }

			f10OverlAl_2 OBJECT-TYPE
			SYNTAX INTEGER
			MAX-ACCESS read-only
			STATUS current
			DESCRIPTION "Locked motor 10"
			::= { alarms2 110 }

			f10LowDCAl_2 OBJECT-TYPE
			SYNTAX INTEGER
			MAX-ACCESS read-only
			STATUS current
			DESCRIPTION "Low DC 10"
			::= { alarms2 111 }

			retTempPbAl_2 OBJECT-TYPE
			SYNTAX INTEGER
			MAX-ACCESS read-only
			STATUS current
			DESCRIPTION "Return temperature probe"
			::= { alarms2 112 }

			supTempPrAl_2 OBJECT-TYPE
			SYNTAX INTEGER
			MAX-ACCESS read-only
			STATUS current
			DESCRIPTION "Supply temperature probe"
			::= { alarms2 113 }

			retHumPrAl_2 OBJECT-TYPE
			SYNTAX INTEGER
			MAX-ACCESS read-only
			STATUS current
			DESCRIPTION "Return humidity probe"
			::= { alarms2 114 }

			supHumPrAl_2 OBJECT-TYPE
			SYNTAX INTEGER
			MAX-ACCESS read-only
			STATUS current
			DESCRIPTION "Supply humidity probe"
			::= { alarms2 115 }

			airPrSensAl_2 OBJECT-TYPE
			SYNTAX INTEGER
			MAX-ACCESS read-only
			STATUS current
			DESCRIPTION "Air diff.pressure probe"
			::= { alarms2 116 }

			watIN1PrAl_2 OBJECT-TYPE
			SYNTAX INTEGER
			MAX-ACCESS read-only
			STATUS current
			DESCRIPTION "Water temp. IN1 probe"
			::= { alarms2 117 }

			watOUT1PrAl_2 OBJECT-TYPE
			SYNTAX INTEGER
			MAX-ACCESS read-only
			STATUS current
			DESCRIPTION "Water temp. OUT1 probe"
			::= { alarms2 118 }

			watIN2PrAl_2 OBJECT-TYPE
			SYNTAX INTEGER
			MAX-ACCESS read-only
			STATUS current
			DESCRIPTION "Water temp. IN2 probe"
			::= { alarms2 119 }

			watOUT2PrAl_2 OBJECT-TYPE
			SYNTAX INTEGER
			MAX-ACCESS read-only
			STATUS current
			DESCRIPTION "Water temp. OUT2 probe"
			::= { alarms2 120 }

			watFlw1PrAl_2 OBJECT-TYPE
			SYNTAX INTEGER
			MAX-ACCESS read-only
			STATUS current
			DESCRIPTION "Water flow1/T.liquid1 pr."
			::= { alarms2 121 }

			watFlw2PrAl_2 OBJECT-TYPE
			SYNTAX INTEGER
			MAX-ACCESS read-only
			STATUS current
			DESCRIPTION "Water flow2/T.liquid2 pr."
			::= { alarms2 122 }

			dFPSGenAl_2 OBJECT-TYPE
			SYNTAX INTEGER
			MAX-ACCESS read-only
			STATUS current
			DESCRIPTION "Filter diff.press. probe"
			::= { alarms2 123 }

			dFPSBrokAl_2 OBJECT-TYPE
			SYNTAX INTEGER
			MAX-ACCESS read-only
			STATUS current
			DESCRIPTION "Breakdown alarm"
			::= { alarms2 124 }

			dFPSCablAl_2 OBJECT-TYPE
			SYNTAX INTEGER
			MAX-ACCESS read-only
			STATUS current
			DESCRIPTION "Wiring alarm"
			::= { alarms2 125 }

			dFPSRangeAl_2 OBJECT-TYPE
			SYNTAX INTEGER
			MAX-ACCESS read-only
			STATUS current
			DESCRIPTION "Pressure range alarm"
			::= { alarms2 126 }

			dFPSADCAl_2 OBJECT-TYPE
			SYNTAX INTEGER
			MAX-ACCESS read-only
			STATUS current
			DESCRIPTION "ADC overload alarm"
			::= { alarms2 127 }

			dFPSSetAl_2 OBJECT-TYPE
			SYNTAX INTEGER
			MAX-ACCESS read-only
			STATUS current
			DESCRIPTION "Calibration alarm"
			::= { alarms2 128 }

			dFPSDCOAl_2 OBJECT-TYPE
			SYNTAX INTEGER
			MAX-ACCESS read-only
			STATUS current
			DESCRIPTION "DCO alarm"
			::= { alarms2 129 }

			dFPSWatdAl_2 OBJECT-TYPE
			SYNTAX INTEGER
			MAX-ACCESS read-only
			STATUS current
			DESCRIPTION "Watchdog alarm"
			::= { alarms2 130 }

			dFPSCommAl_2 OBJECT-TYPE
			SYNTAX INTEGER
			MAX-ACCESS read-only
			STATUS current
			DESCRIPTION "Communication alarm"
			::= { alarms2 131 }

			invC1GenAl_2 OBJECT-TYPE
			SYNTAX INTEGER
			MAX-ACCESS read-only
			STATUS current
			DESCRIPTION "DC inverter general alarm"
			::= { alarms2 132 }

			invC1CommAl_2 OBJECT-TYPE
			SYNTAX INTEGER
			MAX-ACCESS read-only
			STATUS current
			DESCRIPTION "Inverter communication"
			::= { alarms2 133 }

			c1ThermAl_2 OBJECT-TYPE
			SYNTAX INTEGER
			MAX-ACCESS read-only
			STATUS current
			DESCRIPTION "C1 Thermal alarm"
			::= { alarms2 134 }

			c1HighPresAl_2 OBJECT-TYPE
			SYNTAX INTEGER
			MAX-ACCESS read-only
			STATUS current
			DESCRIPTION "C1 High pressure alarm"
			::= { alarms2 135 }

			c1LowPresAl_2 OBJECT-TYPE
			SYNTAX INTEGER
			MAX-ACCESS read-only
			STATUS current
			DESCRIPTION "C1 Low pressure alarm"
			::= { alarms2 136 }

			c1HighDiscAl_2 OBJECT-TYPE
			SYNTAX INTEGER
			MAX-ACCESS read-only
			STATUS current
			DESCRIPTION "C1 High discharge alarm"
			::= { alarms2 137 }

			c1LCompRatAl_2 OBJECT-TYPE
			SYNTAX INTEGER
			MAX-ACCESS read-only
			STATUS current
			DESCRIPTION "C1 low compresion alarm"
			::= { alarms2 138 }

			condenser1Al_2 OBJECT-TYPE
			SYNTAX INTEGER
			MAX-ACCESS read-only
			STATUS current
			DESCRIPTION "Condenser 1 general alarm"
			::= { alarms2 139 }

			c1WatFlowAl_2 OBJECT-TYPE
			SYNTAX INTEGER
			MAX-ACCESS read-only
			STATUS current
			DESCRIPTION "Condenser 1 flow alarm"
			::= { alarms2 140 }

			eEV1GenAl_2 OBJECT-TYPE
			SYNTAX INTEGER
			MAX-ACCESS read-only
			STATUS current
			DESCRIPTION "EEV1 general alarm"
			::= { alarms2 141 }

			eEV1CommAl_2 OBJECT-TYPE
			SYNTAX INTEGER
			MAX-ACCESS read-only
			STATUS current
			DESCRIPTION "EEV1 communication alarm"
			::= { alarms2 142 }

			eEV1SuctPrAl_2 OBJECT-TYPE
			SYNTAX INTEGER
			MAX-ACCESS read-only
			STATUS current
			DESCRIPTION "EEV1 suction temp. probe"
			::= { alarms2 143 }

			eEV1EvapPrAl_2 OBJECT-TYPE
			SYNTAX INTEGER
			MAX-ACCESS read-only
			STATUS current
			DESCRIPTION "EEV1 evap. temp. probe"
			::= { alarms2 144 }

			eEV1CondPrAl_2 OBJECT-TYPE
			SYNTAX INTEGER
			MAX-ACCESS read-only
			STATUS current
			DESCRIPTION "EEV1 condens. temp. probe"
			::= { alarms2 145 }

			eEV1DiscPrAl_2 OBJECT-TYPE
			SYNTAX INTEGER
			MAX-ACCESS read-only
			STATUS current
			DESCRIPTION "EEV1 disch. temp. probe"
			::= { alarms2 146 }

			c2ThermAl_2 OBJECT-TYPE
			SYNTAX INTEGER
			MAX-ACCESS read-only
			STATUS current
			DESCRIPTION "C2 Thermal alarm"
			::= { alarms2 147 }

			c2HighPresAl_2 OBJECT-TYPE
			SYNTAX INTEGER
			MAX-ACCESS read-only
			STATUS current
			DESCRIPTION "C2 High pressure alarm"
			::= { alarms2 148 }

			c2LowPresAl_2 OBJECT-TYPE
			SYNTAX INTEGER
			MAX-ACCESS read-only
			STATUS current
			DESCRIPTION "C2 Low pressure alarm"
			::= { alarms2 149 }

			c2HighDiscAl_2 OBJECT-TYPE
			SYNTAX INTEGER
			MAX-ACCESS read-only
			STATUS current
			DESCRIPTION "C2 High discharge alarm"
			::= { alarms2 150 }

			c2LCompRatAl_2 OBJECT-TYPE
			SYNTAX INTEGER
			MAX-ACCESS read-only
			STATUS current
			DESCRIPTION "C2 low compresion alarm"
			::= { alarms2 151 }

			condenser2Al_2 OBJECT-TYPE
			SYNTAX INTEGER
			MAX-ACCESS read-only
			STATUS current
			DESCRIPTION "Condenser 2 general alarm"
			::= { alarms2 152 }

			c2WatFlowAl_2 OBJECT-TYPE
			SYNTAX INTEGER
			MAX-ACCESS read-only
			STATUS current
			DESCRIPTION "Condenser 2 flow alarm"
			::= { alarms2 153 }

			eEV2GenAl_2 OBJECT-TYPE
			SYNTAX INTEGER
			MAX-ACCESS read-only
			STATUS current
			DESCRIPTION "EEV2 general alarm"
			::= { alarms2 154 }

			eEV2CommAl_2 OBJECT-TYPE
			SYNTAX INTEGER
			MAX-ACCESS read-only
			STATUS current
			DESCRIPTION "EEV2 communication alarm"
			::= { alarms2 155 }

			eEV2SuctPrAl_2 OBJECT-TYPE
			SYNTAX INTEGER
			MAX-ACCESS read-only
			STATUS current
			DESCRIPTION "EEV2 suction temp. probe"
			::= { alarms2 156 }

			eEV2EvapPrAl_2 OBJECT-TYPE
			SYNTAX INTEGER
			MAX-ACCESS read-only
			STATUS current
			DESCRIPTION "EEV2 evap. temp. probe"
			::= { alarms2 157 }

			eEV2CondPrAl_2 OBJECT-TYPE
			SYNTAX INTEGER
			MAX-ACCESS read-only
			STATUS current
			DESCRIPTION "EEV2 condens. temp. probe"
			::= { alarms2 158 }

			eEV2DiscPrAl_2 OBJECT-TYPE
			SYNTAX INTEGER
			MAX-ACCESS read-only
			STATUS current
			DESCRIPTION "EEV2 disch. temp. probe"
			::= { alarms2 159 }

			intHumGenAl_2 OBJECT-TYPE
			SYNTAX INTEGER
			MAX-ACCESS read-only
			STATUS current
			DESCRIPTION "Internal humidifier alarm"
			::= { alarms2 160 }

			cPYCommAl_2 OBJECT-TYPE
			SYNTAX INTEGER
			MAX-ACCESS read-only
			STATUS current
			DESCRIPTION "Communication alarm"
			::= { alarms2 161 }

			cPYMemoryAl_2 OBJECT-TYPE
			SYNTAX INTEGER
			MAX-ACCESS read-only
			STATUS current
			DESCRIPTION "Memory error alarm"
			::= { alarms2 162 }

			cPYParamAl_2 OBJECT-TYPE
			SYNTAX INTEGER
			MAX-ACCESS read-only
			STATUS current
			DESCRIPTION "Parameters error alarm"
			::= { alarms2 163 }

			cPYHighCurAl_2 OBJECT-TYPE
			SYNTAX INTEGER
			MAX-ACCESS read-only
			STATUS current
			DESCRIPTION "Electrodes high current"
			::= { alarms2 164 }

			cPYLoSteamAl_2 OBJECT-TYPE
			SYNTAX INTEGER
			MAX-ACCESS read-only
			STATUS current
			DESCRIPTION "Low steam product. alarm"
			::= { alarms2 165 }

			cPYDrainAl_2 OBJECT-TYPE
			SYNTAX INTEGER
			MAX-ACCESS read-only
			STATUS current
			DESCRIPTION "Drain loss alarm"
			::= { alarms2 166 }

			cPYMaintAl_2 OBJECT-TYPE
			SYNTAX INTEGER
			MAX-ACCESS read-only
			STATUS current
			DESCRIPTION "Maintenance hours alarm"
			::= { alarms2 167 }

			cPYNoWaterAl_2 OBJECT-TYPE
			SYNTAX INTEGER
			MAX-ACCESS read-only
			STATUS current
			DESCRIPTION "Water loss alarm"
			::= { alarms2 168 }

			cPYCylMainAl_2 OBJECT-TYPE
			SYNTAX INTEGER
			MAX-ACCESS read-only
			STATUS current
			DESCRIPTION "Cylinder mainten. alarm"
			::= { alarms2 169 }

			cPYDirtCylAl_2 OBJECT-TYPE
			SYNTAX INTEGER
			MAX-ACCESS read-only
			STATUS current
			DESCRIPTION "Exaust cylinder alarm"
			::= { alarms2 170 }

			cPYFoamAl_2 OBJECT-TYPE
			SYNTAX INTEGER
			MAX-ACCESS read-only
			STATUS current
			DESCRIPTION "Foam presence alarm"
			::= { alarms2 171 }

			cPYLifeTimAl_2 OBJECT-TYPE
			SYNTAX INTEGER
			MAX-ACCESS read-only
			STATUS current
			DESCRIPTION "Life time expired alarm"
			::= { alarms2 172 }

			cPYHiWLevAl_2 OBJECT-TYPE
			SYNTAX INTEGER
			MAX-ACCESS read-only
			STATUS current
			DESCRIPTION "High water level alarm"
			::= { alarms2 173 }

			cPYHWatConAl_2 OBJECT-TYPE
			SYNTAX INTEGER
			MAX-ACCESS read-only
			STATUS current
			DESCRIPTION "High conductivity alarm"
			::= { alarms2 174 }

			cPYConnAl_2 OBJECT-TYPE
			SYNTAX INTEGER
			MAX-ACCESS read-only
			STATUS current
			DESCRIPTION "Connection error alarm"
			::= { alarms2 175 }

			watPresAl_2 OBJECT-TYPE
			SYNTAX INTEGER
			MAX-ACCESS read-only
			STATUS current
			DESCRIPTION "Water presence alarm"
			::= { alarms2 176 }

			drainPumpAl_2 OBJECT-TYPE
			SYNTAX INTEGER
			MAX-ACCESS read-only
			STATUS current
			DESCRIPTION "Drain pump alarm"
			::= { alarms2 177 }

			elHeatAl_2 OBJECT-TYPE
			SYNTAX INTEGER
			MAX-ACCESS read-only
			STATUS current
			DESCRIPTION "Electric heater alarm"
			::= { alarms2 178 }

			filterAl_2 OBJECT-TYPE
			SYNTAX INTEGER
			MAX-ACCESS read-only
			STATUS current
			DESCRIPTION "Dirty filter alarm"
			::= { alarms2 179 }

			dryCoolerAl_2 OBJECT-TYPE
			SYNTAX INTEGER
			MAX-ACCESS read-only
			STATUS current
			DESCRIPTION "Dry cooler alarm"
			::= { alarms2 180 }

			extHumidAl_2 OBJECT-TYPE
			SYNTAX INTEGER
			MAX-ACCESS read-only
			STATUS current
			DESCRIPTION "External humidifier alarm"
			::= { alarms2 181 }

			waterPumpAl_2 OBJECT-TYPE
			SYNTAX INTEGER
			MAX-ACCESS read-only
			STATUS current
			DESCRIPTION "Water pump alarm"
			::= { alarms2 182 }

			condUnitGAl_2 OBJECT-TYPE
			SYNTAX INTEGER
			MAX-ACCESS read-only
			STATUS current
			DESCRIPTION "Motocondenser alarm"
			::= { alarms2 183 }

			gasLeakAl_2 OBJECT-TYPE
			SYNTAX INTEGER
			MAX-ACCESS read-only
			STATUS current
			DESCRIPTION "Refrigerant leak alarm"
			::= { alarms2 184 }

			powerSuppAl_2 OBJECT-TYPE
			SYNTAX INTEGER
			MAX-ACCESS read-only
			STATUS current
			DESCRIPTION "Power fault alarm"
			::= { alarms2 185 }

			genSoftAl_2 OBJECT-TYPE
			SYNTAX INTEGER
			MAX-ACCESS read-only
			STATUS current
			DESCRIPTION "Not critical generic al."
			::= { alarms2 186 }

			localNetAl_2 OBJECT-TYPE
			SYNTAX INTEGER
			MAX-ACCESS read-only
			STATUS current
			DESCRIPTION "Local network alarm"
			::= { alarms2 187 }

			regHiTempAl_2 OBJECT-TYPE
			SYNTAX INTEGER
			MAX-ACCESS read-only
			STATUS current
			DESCRIPTION "High regulation T.alarm"
			::= { alarms2 188 }

			regLowTempAl_2 OBJECT-TYPE
			SYNTAX INTEGER
			MAX-ACCESS read-only
			STATUS current
			DESCRIPTION "Low regulation T.alarm"
			::= { alarms2 189 }

			hiLimTempAl_2 OBJECT-TYPE
			SYNTAX INTEGER
			MAX-ACCESS read-only
			STATUS current
			DESCRIPTION "High limit temp. alarm"
			::= { alarms2 190 }

			lowLimTempAl_2 OBJECT-TYPE
			SYNTAX INTEGER
			MAX-ACCESS read-only
			STATUS current
			DESCRIPTION "Low limit temp. alarm"
			::= { alarms2 191 }

			retHiHumiAl_2 OBJECT-TYPE
			SYNTAX INTEGER
			MAX-ACCESS read-only
			STATUS current
			DESCRIPTION "High room humidity alarm"
			::= { alarms2 192 }

			retLowHumiAl_2 OBJECT-TYPE
			SYNTAX INTEGER
			MAX-ACCESS read-only
			STATUS current
			DESCRIPTION "Low room humidity alarm"
			::= { alarms2 193 }

			supHiHumiAl_2 OBJECT-TYPE
			SYNTAX INTEGER
			MAX-ACCESS read-only
			STATUS current
			DESCRIPTION "High supp.humidity alarm"
			::= { alarms2 194 }

			supLowHumiAl_2 OBJECT-TYPE
			SYNTAX INTEGER
			MAX-ACCESS read-only
			STATUS current
			DESCRIPTION "Low supp.humidity alarm"
			::= { alarms2 195 }

			probeMod1COM_2 OBJECT-TYPE
			SYNTAX INTEGER
			MAX-ACCESS read-only
			STATUS current
			DESCRIPTION "Module 1 communication"
			::= { alarms2 196 }

			prMod1err1_2 OBJECT-TYPE
			SYNTAX INTEGER
			MAX-ACCESS read-only
			STATUS current
			DESCRIPTION "Module 1 probe 1 alarm"
			::= { alarms2 197 }

			prMod1err2_2 OBJECT-TYPE
			SYNTAX INTEGER
			MAX-ACCESS read-only
			STATUS current
			DESCRIPTION "Module 1 probe 2 alarm"
			::= { alarms2 198 }

			prMod1err3_2 OBJECT-TYPE
			SYNTAX INTEGER
			MAX-ACCESS read-only
			STATUS current
			DESCRIPTION "Module 1 probe 3 alarm"
			::= { alarms2 199 }

			prMod1err4_2 OBJECT-TYPE
			SYNTAX INTEGER
			MAX-ACCESS read-only
			STATUS current
			DESCRIPTION "Module 1 probe 4 alarm"
			::= { alarms2 200 }

			prMod1err5_2 OBJECT-TYPE
			SYNTAX INTEGER
			MAX-ACCESS read-only
			STATUS current
			DESCRIPTION "Module 1 probe 5 alarm"
			::= { alarms2 201 }

			prMod1err6_2 OBJECT-TYPE
			SYNTAX INTEGER
			MAX-ACCESS read-only
			STATUS current
			DESCRIPTION "Module 1 probe 6 alarm"
			::= { alarms2 202 }

			probeMod2COM_2 OBJECT-TYPE
			SYNTAX INTEGER
			MAX-ACCESS read-only
			STATUS current
			DESCRIPTION "Module 2 communication"
			::= { alarms2 203 }

			prMod2err1_2 OBJECT-TYPE
			SYNTAX INTEGER
			MAX-ACCESS read-only
			STATUS current
			DESCRIPTION "Module 2 probe 1 alarm"
			::= { alarms2 204 }

			prMod2err2_2 OBJECT-TYPE
			SYNTAX INTEGER
			MAX-ACCESS read-only
			STATUS current
			DESCRIPTION "Module 2 probe 2 alarm"
			::= { alarms2 205 }

			prMod2err3_2 OBJECT-TYPE
			SYNTAX INTEGER
			MAX-ACCESS read-only
			STATUS current
			DESCRIPTION "Module 2 probe 3 alarm"
			::= { alarms2 206 }

			prMod2err4_2 OBJECT-TYPE
			SYNTAX INTEGER
			MAX-ACCESS read-only
			STATUS current
			DESCRIPTION "Module 2 probe 4 alarm"
			::= { alarms2 207 }

			prMod2err5_2 OBJECT-TYPE
			SYNTAX INTEGER
			MAX-ACCESS read-only
			STATUS current
			DESCRIPTION "Module 2 probe 5 alarm"
			::= { alarms2 208 }

			prMod2err6_2 OBJECT-TYPE
			SYNTAX INTEGER
			MAX-ACCESS read-only
			STATUS current
			DESCRIPTION "Module 2 probe 6 alarm"
			::= { alarms2 209 }

			probeMod3COM_2 OBJECT-TYPE
			SYNTAX INTEGER
			MAX-ACCESS read-only
			STATUS current
			DESCRIPTION "Module 3 communication"
			::= { alarms2 210 }

			prMod3err1_2 OBJECT-TYPE
			SYNTAX INTEGER
			MAX-ACCESS read-only
			STATUS current
			DESCRIPTION "Module 3 probe 1 alarm"
			::= { alarms2 211 }

			prMod3err2_2 OBJECT-TYPE
			SYNTAX INTEGER
			MAX-ACCESS read-only
			STATUS current
			DESCRIPTION "Module 3 probe 2 alarm"
			::= { alarms2 212 }

			prMod3err3_2 OBJECT-TYPE
			SYNTAX INTEGER
			MAX-ACCESS read-only
			STATUS current
			DESCRIPTION "Module 3 probe 3 alarm"
			::= { alarms2 213 }

			prMod3err4_2 OBJECT-TYPE
			SYNTAX INTEGER
			MAX-ACCESS read-only
			STATUS current
			DESCRIPTION "Module 3 probe 4 alarm"
			::= { alarms2 214 }

			prMod3err5_2 OBJECT-TYPE
			SYNTAX INTEGER
			MAX-ACCESS read-only
			STATUS current
			DESCRIPTION "Module 3 probe 5 alarm"
			::= { alarms2 215 }

			prMod3err6_2 OBJECT-TYPE
			SYNTAX INTEGER
			MAX-ACCESS read-only
			STATUS current
			DESCRIPTION "Module 3 probe 6 alarm"
			::= { alarms2 216 }
END
