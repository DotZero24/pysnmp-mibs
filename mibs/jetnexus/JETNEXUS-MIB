JETNEXUS-MIB DEFINITIONS ::= BEGIN

IMPORTS
  OBJECT-TYPE, Integer32, Counter64,
  MODULE-IDENTITY, enterprises          FROM SNMPv2-SMI
  MODULE-COMPLIANCE, OBJECT-GROUP       FROM SNMPv2-CONF;


jetnexusMIB MODULE-IDENTITY
    LAST-UPDATED "201410180000Z"            -- 18 Oct 2014
    ORGANIZATION "jetNEXUS"
    CONTACT-INFO "info@jetnexus.com"
    DESCRIPTION  "TODO
                 "
    REVISION "201410180000Z"                 -- 18 Oct 2014
    DESCRIPTION "Standard compliance"
  ::= { enterprises 38370 }

jetnexusData     OBJECT IDENTIFIER ::= { jetnexusMIB 1 }

--
-- Global data from shared memory
--
jetnexusGlobal     OBJECT IDENTIFIER ::= { jetnexusData 1 }

jetnexusOverallInputBytes OBJECT-TYPE
    SYNTAX      Counter64
    MAX-ACCESS  read-only
    STATUS      current
    DESCRIPTION
  "from jetnexus shared memory"
  ::= { jetnexusGlobal 1 }

jetnexusOverallOutputBytes OBJECT-TYPE
    SYNTAX      Counter64
    MAX-ACCESS  read-only
    STATUS      current
    DESCRIPTION
  "from jetnexus shared memory"
  ::= { jetnexusGlobal 2 }

jetnexusCompressedInputBytes OBJECT-TYPE
    SYNTAX      Counter64
    MAX-ACCESS  read-only
    STATUS      current
    DESCRIPTION
  "from jetnexus shared memory"
  ::= { jetnexusGlobal 3 }

jetnexusCompressedOutputBytes OBJECT-TYPE
    SYNTAX      Counter64
    MAX-ACCESS  read-only
    STATUS      current
    DESCRIPTION
  "from jetnexus shared memory"
  ::= { jetnexusGlobal 4 }

jetnexusVersionInfo OBJECT-TYPE
    SYNTAX      OCTET STRING
    MAX-ACCESS  read-only
    STATUS      current
    DESCRIPTION
  "from jetnexus shared memory"
  ::= { jetnexusGlobal 5 }

jetnexusTotalClientConnections OBJECT-TYPE
    SYNTAX      Counter64
    MAX-ACCESS  read-only
    STATUS      current
    DESCRIPTION
  "from jetnexus shared memory"
  ::= { jetnexusGlobal 6 }

jetnexusCpuPercent OBJECT-TYPE
    SYNTAX      Integer32
    MAX-ACCESS  read-only
    STATUS      current
    DESCRIPTION
  "from jetnexus shared memory"
  ::= { jetnexusGlobal 7 }

jetnexusDiskFreePercent OBJECT-TYPE
    SYNTAX      Integer32
    MAX-ACCESS  read-only
    STATUS      current
    DESCRIPTION
  "from jetnexus shared memory"
  ::= { jetnexusGlobal 8 }

jetnexusMemoryPercent OBJECT-TYPE
    SYNTAX      Integer32
    MAX-ACCESS  read-only
    STATUS      current
    DESCRIPTION
  "from jetnexus shared memory"
  ::= { jetnexusGlobal 9 }

jetnexusCurrentConnections OBJECT-TYPE
    SYNTAX      Integer32
    MAX-ACCESS  read-only
    STATUS      current
    DESCRIPTION
  "from jetnexus shared memory"
  ::= { jetnexusGlobal 10 }


--
--  Virtual Service Table
--

jnvirtualserviceTable OBJECT-TYPE
    SYNTAX      SEQUENCE OF JnvirtualserviceEntry
    MAX-ACCESS  not-accessible
    STATUS      current
    DESCRIPTION "Virtual Service info from Shared memory"
  ::= { jetnexusData 2 }

jnvirtualserviceEntry OBJECT-TYPE
    SYNTAX      JnvirtualserviceEntry
    MAX-ACCESS  not-accessible
    STATUS      current
    DESCRIPTION "Virtual Service data"
    INDEX   { jnvirtualserviceIndexVirtualService }
  ::= {jnvirtualserviceTable 1 }

JnvirtualserviceEntry ::= SEQUENCE {
  jnvirtualserviceIndexVirtualService INTEGER,
  jnvirtualserviceVSAddrPort  OCTET STRING,
  jnvirtualserviceOverallInputBytes  Counter64,
  jnvirtualserviceOverallOutputBytes  Counter64,
  jnvirtualserviceCacheBytes  Counter64,
  jnvirtualserviceCompressionPercent  Integer32,
  jnvirtualservicePresentClientConnections  Integer32,
  jnvirtualserviceHitCount  Counter64,
  jnvirtualserviceCacheHits  Counter64,
  jnvirtualserviceCacheHitsPercent  Integer32,
  jnvirtualserviceVSStatus  OCTET STRING
}

jnvirtualserviceIndexVirtualService OBJECT-TYPE
    SYNTAX      Integer32 (1..1000)
    MAX-ACCESS  not-accessible
    STATUS      current
    DESCRIPTION "Virtual Service data"
  ::= { jnvirtualserviceEntry 1 }

jnvirtualserviceVSAddrPort OBJECT-TYPE
    SYNTAX      OCTET STRING
    MAX-ACCESS  read-only
    STATUS      current
    DESCRIPTION "Virtual Service data"
  ::= { jnvirtualserviceEntry 2 }

jnvirtualserviceOverallInputBytes OBJECT-TYPE
    SYNTAX      Counter64
    MAX-ACCESS  read-only
    STATUS      current
    DESCRIPTION "Virtual Service data"
  ::= { jnvirtualserviceEntry 3 }

jnvirtualserviceOverallOutputBytes OBJECT-TYPE
    SYNTAX      Counter64
    MAX-ACCESS  read-only
    STATUS      current
    DESCRIPTION "Virtual Service data"
  ::= { jnvirtualserviceEntry 4 }

jnvirtualserviceCacheBytes OBJECT-TYPE
    SYNTAX      Counter64
    MAX-ACCESS  read-only
    STATUS      current
    DESCRIPTION "Virtual Service data"
  ::= { jnvirtualserviceEntry 5 }

jnvirtualserviceCompressionPercent OBJECT-TYPE
    SYNTAX      Integer32
    MAX-ACCESS  read-only
    STATUS      current
    DESCRIPTION "Virtual Service data"
  ::= { jnvirtualserviceEntry 6 }

jnvirtualservicePresentClientConnections OBJECT-TYPE
    SYNTAX      Integer32
    MAX-ACCESS  read-only
    STATUS      current
    DESCRIPTION "Virtual Service data"
  ::= { jnvirtualserviceEntry 7 }

jnvirtualserviceHitCount OBJECT-TYPE
    SYNTAX      Counter64
    MAX-ACCESS  read-only
    STATUS      current
    DESCRIPTION "Virtual Service data"
  ::= { jnvirtualserviceEntry 8 }

jnvirtualserviceCacheHits OBJECT-TYPE
    SYNTAX      Counter64
    MAX-ACCESS  read-only
    STATUS      current
    DESCRIPTION "Virtual Service data"
  ::= { jnvirtualserviceEntry 9 }

jnvirtualserviceCacheHitsPercent OBJECT-TYPE
    SYNTAX      Integer32
    MAX-ACCESS  read-only
    STATUS      current
    DESCRIPTION "Virtual Service data"
  ::= { jnvirtualserviceEntry 10 }

jnvirtualserviceVSStatus OBJECT-TYPE
    SYNTAX      OCTET STRING
    MAX-ACCESS  read-only
    STATUS      current
    DESCRIPTION "Virtual Service data"
  ::= { jnvirtualserviceEntry 11 }


--
--  Real Server Table
--

jnrealserverTable OBJECT-TYPE
    SYNTAX      SEQUENCE OF JnrealserverEntry
    MAX-ACCESS  not-accessible
    STATUS      current
    DESCRIPTION
  "Real server data"
  ::= { jetnexusData 3 }

jnrealserverEntry OBJECT-TYPE
    SYNTAX      JnrealserverEntry
    MAX-ACCESS  not-accessible
    STATUS      current
    DESCRIPTION
  "Real server data"
    INDEX   { jnrealserverIndexVirtualService, jnrealserverIndexRealServer }
  ::= {jnrealserverTable 1 }

JnrealserverEntry ::= SEQUENCE {
  jnrealserverIndexVirtualService INTEGER,
  jnrealserverIndexRealServer INTEGER,
  jnrealserverVSAddrPort  OCTET STRING,
  jnrealserverRSAddrPort  OCTET STRING,
  jnrealserverOverallInputBytes  Counter64,
  jnrealserverOverallOutputBytes  Counter64,
  jnrealserverCompressionPercent  INTEGER,
  jnrealserverPresentClientConnections  Integer32,
  jnrealserverPoolUsage  Integer32,
  jnrealserverHitCount  Counter64,
  jnrealserverRSStatus  OCTET STRING
}

jnrealserverIndexVirtualService OBJECT-TYPE
    SYNTAX      Integer32 (1..1000)
    MAX-ACCESS  not-accessible
    STATUS      current
    DESCRIPTION
  "Real server data"
  ::= { jnrealserverEntry 1 }

jnrealserverIndexRealServer OBJECT-TYPE
    SYNTAX      Integer32 (1..1000)
    MAX-ACCESS  not-accessible
    STATUS      current
    DESCRIPTION
  "Real server data"
  ::= { jnrealserverEntry 2 }

jnrealserverVSAddrPort OBJECT-TYPE
    SYNTAX      OCTET STRING
    MAX-ACCESS  read-only
    STATUS      current
    DESCRIPTION
  "Real server data"
  ::= { jnrealserverEntry 3 }

jnrealserverRSAddrPort OBJECT-TYPE
    SYNTAX      OCTET STRING
    MAX-ACCESS  read-only
    STATUS      current
    DESCRIPTION
  "Real server data"
  ::= { jnrealserverEntry 4 }

jnrealserverOverallInputBytes OBJECT-TYPE
    SYNTAX      Counter64
    MAX-ACCESS  read-only
    STATUS      current
    DESCRIPTION
  "Real server data"
  ::= { jnrealserverEntry 5 }

jnrealserverOverallOutputBytes OBJECT-TYPE
    SYNTAX      Counter64
    MAX-ACCESS  read-only
    STATUS      current
    DESCRIPTION
  "Real server data"
  ::= { jnrealserverEntry 6 }

jnrealserverCompressionPercent OBJECT-TYPE
    SYNTAX      Integer32
    MAX-ACCESS  read-only
    STATUS      current
    DESCRIPTION
  "Real server data"
  ::= { jnrealserverEntry 7 }

jnrealserverPresentClientConnections OBJECT-TYPE
    SYNTAX      Integer32
    MAX-ACCESS  read-only
    STATUS      current
    DESCRIPTION
  "Real server data"
  ::= { jnrealserverEntry 8 }

jnrealserverPoolUsage OBJECT-TYPE
    SYNTAX      Integer32
    MAX-ACCESS  read-only
    STATUS      current
    DESCRIPTION
  "Real server data"
  ::= { jnrealserverEntry 9 }

jnrealserverHitCount OBJECT-TYPE
    SYNTAX      Counter64
    MAX-ACCESS  read-only
    STATUS      current
    DESCRIPTION
  "Real server data"
  ::= { jnrealserverEntry 10 }

jnrealserverRSStatus OBJECT-TYPE
    SYNTAX      OCTET STRING
    MAX-ACCESS  read-only
    STATUS      current
    DESCRIPTION
  "Real server data"
  ::= { jnrealserverEntry 11 }


jetnexusConformance OBJECT IDENTIFIER ::= { jetnexusMIB 2 }

jetnexusGroups OBJECT IDENTIFIER ::= { jetnexusConformance 1 }

jetnexusCurrentGroup  OBJECT-GROUP
    OBJECTS {
        jetnexusOverallInputBytes, jetnexusOverallOutputBytes, jetnexusCompressedInputBytes, jetnexusCompressedOutputBytes,
          jetnexusVersionInfo, jetnexusTotalClientConnections, jetnexusCpuPercent, jetnexusDiskFreePercent, jetnexusMemoryPercent,
          jetnexusCurrentConnections,
        jnvirtualserviceVSAddrPort, jnvirtualserviceOverallInputBytes, jnvirtualserviceOverallOutputBytes, jnvirtualserviceCacheBytes,
          jnvirtualserviceCompressionPercent, jnvirtualservicePresentClientConnections, jnvirtualserviceHitCount,
          jnvirtualserviceCacheHits, jnvirtualserviceCacheHitsPercent, jnvirtualserviceVSStatus,
        jnrealserverVSAddrPort, jnrealserverRSAddrPort, jnrealserverOverallInputBytes, jnrealserverOverallOutputBytes,
          jnrealserverCompressionPercent, jnrealserverPresentClientConnections, jnrealserverPoolUsage, jnrealserverHitCount,
          jnrealserverRSStatus
    }
    STATUS	current
    DESCRIPTION
	"The objects relating to the MIB module registered
	 by jetNEXUS."
    ::= { jetnexusGroups 1 }


jetnexusCompliances OBJECT IDENTIFIER ::= { jetnexusConformance 2 }

jetnexusBasicCompliance MODULE-COMPLIANCE
		STATUS current
		DESCRIPTION
			"jetNEXUS MODULE-COMPLIANCE."
		MODULE -- this module
		MANDATORY-GROUPS { jetnexusCurrentGroup }
		::= { jetnexusCompliances 1 }


END
