-- ZyXEL Communications Corporation
-- Private Enterprise MIB definition

-- This file describes the ZyXEL Communications Corporation Enterprise MIB.
-- It contains ZyXEL products OIDs, and common managed objects.

-- $Log: ZYXEL-VOICE-VLAN-MIB.mib $
-- Revision 1.5  2014/07/25 07:56:16  Shinge
-- remove LLDP and normal port support
-- Revision 1.4  2013/12/06 07:07:01  ccho
-- remove uncessary imports
-- Revision 1.3  2013/11/06 05:43:08  ccho
-- fix mib style
-- Revision 1.2  2013/07/31 03:03:50  Willson
-- clear warring
-- Revision 1.1  2013/07/16 02:53:29  Willson
-- Initial revision

ZYXEL-VOICE-VLAN-MIB DEFINITIONS ::= BEGIN

    IMPORTS


	OBJECT-TYPE
		FROM SNMPv2-SMI			-- RFC2578

	RowStatus, MacAddress
		FROM SNMPv2-TC			-- RFC2579

	MODULE-IDENTITY
		FROM SNMPv2-SMI

	DisplayString
	  	FROM SNMPv2-TC			-- RFC2579

	EnabledStatus
		FROM  P-BRIDGE-MIB

	esMgmt
		FROM ZYXEL-ES-SMI;

	zyxelVoiceVlan MODULE-IDENTITY
		LAST-UPDATED	"201207010000Z"
		ORGANIZATION "Enterprise Solution ZyXEL"
		CONTACT-INFO
			""
		DESCRIPTION
			"The subtree for voice vlan"
		::= { esMgmt 96 }

	zyxelVoiceVlanSetup   OBJECT IDENTIFIER ::= { zyxelVoiceVlan 1 }
--	zyxelVoiceVlanStatus    OBJECT IDENTIFIER ::= { zyxelVoiceVlan 2 }
--
--
--  96.zyxelVoiceVlan
--
--

        zyxelVoiceVlanID OBJECT-TYPE
        SYNTAX  INTEGER (0..4094)
        MAX-ACCESS  read-write
        STATUS  current
        DESCRIPTION
		"Select the VLAN ID as voice VLAN feature."
        ::= { zyxelVoiceVlanSetup 1 }

        zyxelVoiceVlanPriority OBJECT-TYPE
        SYNTAX  INTEGER (0..7)
        MAX-ACCESS  read-write
        STATUS  current
        DESCRIPTION
		"Set the priority of the voice traffic."
        ::= { zyxelVoiceVlanSetup 2 }

        zyxelVoiceVlanMaxNumberOfOUI OBJECT-TYPE
        SYNTAX  INTEGER
        MAX-ACCESS  read-only
        STATUS  current
        DESCRIPTION
			"The maximum number of Voice VLAN OUI entries that can be created."
        ::= { zyxelVoiceVlanSetup 5 }

--  	zyxelVoiceVlanOUITable

        zyxelVoiceVlanOUITable	OBJECT-TYPE
        SYNTAX	SEQUENCE OF ZyxelVoiceVlanOUIEntry
        MAX-ACCESS  not-accessible
        STATUS  current
        DESCRIPTION
			"The table contains Voice VLAN OUI configuration."
        ::= { zyxelVoiceVlanSetup 6 }

		zyxelVoiceVlanOUIEntry OBJECT-TYPE
        SYNTAX	ZyxelVoiceVlanOUIEntry
        MAX-ACCESS	not-accessible
        STATUS	current
        DESCRIPTION
        "An entry contains voice VLAN OUI configuration."
        INDEX          	{ zyVoiceVlanOUIAddress, zyVoiceVlanOUIMask}
        ::= { zyxelVoiceVlanOUITable 1 }

        ZyxelVoiceVlanOUIEntry ::=
           SEQUENCE {
        	zyVoiceVlanOUIAddress		MacAddress,
        	zyVoiceVlanOUIMask			MacAddress,
         	zyVoiceVlanOUIDescription	DisplayString,
        	zyVoiceVlanOUIRowStatus		RowStatus
           }

        zyVoiceVlanOUIAddress OBJECT-TYPE
        SYNTAX  MacAddress
        MAX-ACCESS  not-accessible
        STATUS  current
        DESCRIPTION
			"Set a MAC address to add to the OUI list."
        ::= { zyxelVoiceVlanOUIEntry 1 }

        zyVoiceVlanOUIMask OBJECT-TYPE
        SYNTAX  MacAddress
        MAX-ACCESS  not-accessible
        STATUS  current
        DESCRIPTION
			"Set a mask to identify OUI addresses."
        ::= { zyxelVoiceVlanOUIEntry 2 }

        zyVoiceVlanOUIDescription OBJECT-TYPE
        SYNTAX  DisplayString
        MAX-ACCESS  read-write
        STATUS  current
        DESCRIPTION
			"A descriptive name for this OUI."
        ::= { zyxelVoiceVlanOUIEntry 3 }

        zyVoiceVlanOUIRowStatus OBJECT-TYPE
        SYNTAX  RowStatus
        MAX-ACCESS  read-write
        STATUS  current
        DESCRIPTION
		"This object allows entries to be created and deleted from the OUI table."
        ::= { zyxelVoiceVlanOUIEntry 4 }

--		zyxelVoiceVlanDeviceTable

END
