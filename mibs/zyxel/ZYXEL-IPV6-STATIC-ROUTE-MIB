-- ZyXEL Communications Corporation
-- Private Enterprise MIB definition

-- This file describes the ZyXEL Communications Corporation Enterprise MIB.
-- It contains ZyXEL products OIDs, and common managed objects.

-- $Log: ZYXEL-IPV6-STATIC-ROUTE-MIB.mib $
-- Revision 1.5  2013/12/06 07:06:14  ccho
-- remove uncessary imports
-- Revision 1.4  2013/11/06 05:41:41  ccho
-- fix mib style
-- Revision 1.3  2012/09/19 07:38:53  Kevin
-- if it's leaf node, revise the vender name from zyxel to zy
-- Revision 1.2  2012/07/05 06:23:12  Kevin
-- 1. upgrade from SNMP to SNMPv2
-- 2. clean warning
-- Revision 1.1  2012/05/30 07:49:41  Kevin
-- Initial revision

ZYXEL-IPV6-STATIC-ROUTE-MIB DEFINITIONS ::= BEGIN

    IMPORTS
	OBJECT-TYPE
		FROM SNMPv2-SMI			-- RFC2578

	MODULE-IDENTITY
		FROM SNMPv2-SMI

	RowStatus
		FROM SNMPv2-TC			-- RFC2579

	InetAddressType, InetAddress
		FROM INET-ADDRESS-MIB		-- RFC2851

	esMgmt
		FROM ZYXEL-ES-SMI;

	zyxelIpv6StaticRoute MODULE-IDENTITY
		LAST-UPDATED	"201207010000Z"
		ORGANIZATION "Enterprise Solution ZyXEL"
		CONTACT-INFO
			""
		DESCRIPTION
			"The subtree for IPv6 static route"
		::= { esMgmt 37 }

	zyxelIpv6StaticRouteSetup	OBJECT IDENTIFIER ::= { zyxelIpv6StaticRoute 1 }

--
--
--  37. Ipv6StaticRoute
--
--

     zyIpv6StaticRouteMaxNumberOfStaticRoutes OBJECT-TYPE
        SYNTAX  INTEGER
        MAX-ACCESS  read-only
        STATUS  current
        DESCRIPTION
        "The maximum number of IPv6 Static Route entries that can be created."
        ::= { zyxelIpv6StaticRouteSetup 1 }

--	zyxelIpv6StaticRouteTable

	zyxelIpv6StaticRouteTable OBJECT-TYPE
		SYNTAX      SEQUENCE OF ZyxelIpv6StaticRouteEntry
	    MAX-ACCESS  not-accessible
	    STATUS      current
	    DESCRIPTION
	    "The table contains IPv6 static route configuration."
		::= { zyxelIpv6StaticRouteSetup 2 }

    zyxelIpv6StaticRouteEntry OBJECT-TYPE
        SYNTAX      ZyxelIpv6StaticRouteEntry
        MAX-ACCESS  not-accessible
        STATUS      current
        DESCRIPTION
        "An entry contains IPv6 static route configuration."
        INDEX {
        	zyIpv6StaticRouteDestinationIpAddressType,
            zyIpv6StaticRouteDestinationIpAddress,
            zyIpv6StaticRouteDestinationAddressPrefixLength
        }
    ::= { zyxelIpv6StaticRouteTable 1 }

    ZyxelIpv6StaticRouteEntry ::=
        SEQUENCE {
        	zyIpv6StaticRouteDestinationIpAddressType		InetAddressType,
            zyIpv6StaticRouteDestinationIpAddress    		InetAddress,
            zyIpv6StaticRouteDestinationAddressPrefixLength INTEGER,
            zyIpv6StaticRouteNextHopIpAddressType           InetAddressType,
            zyIpv6StaticRouteNextHopIpAddress        		InetAddress,
			zyIpv6StaticRouteIfIndex                		INTEGER,
            zyIpv6StaticRouteRowStatus                    	RowStatus
        }

    zyIpv6StaticRouteDestinationIpAddressType OBJECT-TYPE
        SYNTAX      InetAddressType
        MAX-ACCESS  not-accessible
        STATUS      current
        DESCRIPTION
        "This entry displays the type of IPv6 static route destination address."
    ::= { zyxelIpv6StaticRouteEntry 1 }

    zyIpv6StaticRouteDestinationIpAddress OBJECT-TYPE
        SYNTAX      InetAddress
        MAX-ACCESS  not-accessible
        STATUS      current
        DESCRIPTION
        "This entry displays IPv6 static route destination address."
    ::= { zyxelIpv6StaticRouteEntry 2 }

    zyIpv6StaticRouteDestinationAddressPrefixLength OBJECT-TYPE
        SYNTAX      INTEGER
        MAX-ACCESS  not-accessible
        STATUS      current
        DESCRIPTION
        "This entry displays the length of IPv6 static route destination address prefix."
    ::= { zyxelIpv6StaticRouteEntry 3 }

    zyIpv6StaticRouteNextHopIpAddressType OBJECT-TYPE
        SYNTAX      InetAddressType
        MAX-ACCESS  read-only
        STATUS      current
        DESCRIPTION
        "This entry displays the address type of next hop address."
    ::= { zyxelIpv6StaticRouteEntry 4 }

     zyIpv6StaticRouteNextHopIpAddress OBJECT-TYPE
        SYNTAX      InetAddress
        MAX-ACCESS  read-write
        STATUS      current
        DESCRIPTION
        "This entry displays the IPv6 address of the next hop.
		 The next hop is the neighbor of your switch that will forward the packet to the destination. "
    ::= { zyxelIpv6StaticRouteEntry 5 }

    zyIpv6StaticRouteIfIndex OBJECT-TYPE
        SYNTAX      INTEGER
        MAX-ACCESS  read-write
        STATUS      current
        DESCRIPTION
        "This entry displays the interface index of IPv6 static route entry."
    ::= { zyxelIpv6StaticRouteEntry 6 }

    zyIpv6StaticRouteRowStatus OBJECT-TYPE
        SYNTAX      RowStatus
        MAX-ACCESS  read-create
        STATUS      current
        DESCRIPTION
        "This object allows entry to be created and deleted an IPv6 static route entry."
    ::= { zyxelIpv6StaticRouteEntry 7 }

END
