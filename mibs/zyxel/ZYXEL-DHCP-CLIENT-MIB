-- ZyXEL Communications Corporation
-- Private Enterprise MIB definition

-- This file describes the ZyXEL Communications Corporation Enterprise MIB.
-- It contains ZyXEL products OIDs, and common managed objects.

-- $Log: ZYXEL-DHCP-CLIENT-MIB.mib $
-- Revision 1.1  2014/06/18 07:08:30  Willson
-- Initial revision


ZYXEL-DHCP-CLIENT-MIB DEFINITIONS ::= BEGIN

    IMPORTS

	OBJECT-TYPE
		FROM SNMPv2-SMI			-- RFC2578

	RowStatus
		FROM SNMPv2-TC			-- RFC2579

	MODULE-IDENTITY
		FROM SNMPv2-SMI

	IpAddress
		FROM SNMPv2-SMI

	DisplayString
	  	FROM SNMPv2-TC			-- RFC2579

	EnabledStatus
		FROM  P-BRIDGE-MIB

	esMgmt
		FROM ZYXEL-ES-SMI;

	zyxelDhcpClient MODULE-IDENTITY
		LAST-UPDATED	"201207010000Z"
		ORGANIZATION "Enterprise Solution ZyXEL"
		CONTACT-INFO
			""
		DESCRIPTION
			"The subtree for DHCP client"
		::= { esMgmt 103 }

	zyxelDhcpClientSetup   OBJECT IDENTIFIER ::= { zyxelDhcpClient 1 }
	zyxelDhcpClientStatus    OBJECT IDENTIFIER ::= { zyxelDhcpClient 2 }
--
--
--  97.zyxelDhcpClient
--
--
        zyxelDhcpClientMaxNumberOfClient OBJECT-TYPE
        SYNTAX  INTEGER
        MAX-ACCESS  read-only
        STATUS  current
        DESCRIPTION
			"The maximum number of DHCP client entries that can be created."
        ::= { zyxelDhcpClientSetup 1 }

--  	zyxelDhcpClientTable

        zyxelDhcpClientTable	OBJECT-TYPE
        SYNTAX	SEQUENCE OF ZyxelDhcpClientEntry
        MAX-ACCESS  not-accessible
        STATUS  current
        DESCRIPTION
			"The table contains DHCP client configuration."
        ::= { zyxelDhcpClientSetup 2 }

		zyxelDhcpClientEntry OBJECT-TYPE
        SYNTAX	ZyxelDhcpClientEntry
        MAX-ACCESS	not-accessible
        STATUS	current
        DESCRIPTION
        "An entry contains DHCP client configuration."
        INDEX          	{ zyDhcpClientID}
        ::= { zyxelDhcpClientTable 1 }

        ZyxelDhcpClientEntry ::=
           SEQUENCE {
           	zyDhcpClientID				INTEGER,
        	zyDhcpClientRowStatus		RowStatus,
        	zyDhcpClientOption60State   EnabledStatus,
        	zyDhcpClientOption60ClassId DisplayString
           }

        zyDhcpClientID OBJECT-TYPE
        SYNTAX  INTEGER
        MAX-ACCESS  not-accessible
        STATUS  current
        DESCRIPTION
			"The VLAN ID to which these DHCP settings apply."
        ::= { zyxelDhcpClientEntry 1 }

        zyDhcpClientRowStatus OBJECT-TYPE
        SYNTAX  RowStatus
        MAX-ACCESS  read-write
        STATUS  current
        DESCRIPTION
		"This object allows DHCP client entries to be created and deleted."
        ::= { zyxelDhcpClientEntry 2 }

        zyDhcpClientOption60State OBJECT-TYPE
        SYNTAX  EnabledStatus
        MAX-ACCESS  read-write
        STATUS  current
        DESCRIPTION
		"Enable(1)/Disable(2) DHCP option 60 vendor class-id."
        ::= { zyxelDhcpClientEntry 3 }

        zyDhcpClientOption60ClassId OBJECT-TYPE
        SYNTAX  DisplayString
        MAX-ACCESS  read-write
        STATUS  current
        DESCRIPTION
		"Set/Get the vendor class identifier (DHCPv4 option 60) to be sent with the DHCP packet.
		Min length of string is 1 byte.
		Max length of string is 32 bytes."
        ::= { zyxelDhcpClientEntry 4 }

--		zyxelDhcpClientInfoTable

        zyxelDhcpClientInfoTable OBJECT-TYPE
        SYNTAX	SEQUENCE OF ZyxelDhcpClientInfoEntry
        MAX-ACCESS  not-accessible
        STATUS  current
        DESCRIPTION
		"The table contains DHCP client information."
        ::= { zyxelDhcpClientStatus 1 }

		zyxelDhcpClientInfoEntry OBJECT-TYPE
        SYNTAX	ZyxelDhcpClientInfoEntry
        MAX-ACCESS	not-accessible
        STATUS	current
        DESCRIPTION
        	"An entry contains DHCP client information."
        INDEX          	{ zyDhcpClientInfoID }
        ::= { zyxelDhcpClientInfoTable 1 }

        ZyxelDhcpClientInfoEntry ::=
           SEQUENCE {
        	zyDhcpClientInfoID				INTEGER,
			zyDhcpClientInfoIpAddress		IpAddress,
        	zyDhcpClientInfoMask			IpAddress ,
        	zyDhcpClientInfoLeaseTime      	INTEGER,
        	zyDhcpClientInfoRenewTime		INTEGER,
        	zyDhcpClientInfoRebindTime		INTEGER,
        	zyDhcpClientInfoLeaseFrom		DisplayString,
        	zyDhcpClientInfoLeaseTo			DisplayString,
        	zyDhcpClientInfoDhcpServer		IpAddress,
        	zyDhcpClientInfoDnsServer1		IpAddress,
        	zyDhcpClientInfoDnsServer2		IpAddress,
        	zyDhcpClientInfoDefaultGateway	IpAddress,
        	zyDhcpClientInfoRelease			EnabledStatus,
        	zyDhcpClientInfoRenew			EnabledStatus
           }

        zyDhcpClientInfoID OBJECT-TYPE
        SYNTAX  INTEGER
        MAX-ACCESS  not-accessible
        STATUS  current
        DESCRIPTION
			"DHCP client ID."
        ::= { zyxelDhcpClientInfoEntry 1 }

        zyDhcpClientInfoIpAddress OBJECT-TYPE
        SYNTAX  IpAddress
        MAX-ACCESS  read-only
        STATUS  current
        DESCRIPTION
			"This field displays the IP address of the client."
        ::= { zyxelDhcpClientInfoEntry 2 }

        zyDhcpClientInfoMask OBJECT-TYPE
        SYNTAX  IpAddress
        MAX-ACCESS  read-only
        STATUS  current
        DESCRIPTION
			"This field displays teh mask of the client."
        ::= { zyxelDhcpClientInfoEntry 3 }

        zyDhcpClientInfoLeaseTime OBJECT-TYPE
        SYNTAX  INTEGER
        MAX-ACCESS  read-only
        STATUS  current
        DESCRIPTION
			"This field displays the lease time of the client."
        ::= { zyxelDhcpClientInfoEntry 4 }

        zyDhcpClientInfoRenewTime OBJECT-TYPE
        SYNTAX  INTEGER
        MAX-ACCESS  read-only
        STATUS  current
        DESCRIPTION
			"This field displays the renew time of the client."
        ::= { zyxelDhcpClientInfoEntry 5 }

        zyDhcpClientInfoRebindTime OBJECT-TYPE
        SYNTAX  INTEGER
        MAX-ACCESS  read-only
        STATUS  current
        DESCRIPTION
			"This field displays the rebind time of the client."
        ::= { zyxelDhcpClientInfoEntry 6 }

        zyDhcpClientInfoLeaseFrom OBJECT-TYPE
        SYNTAX  DisplayString
        MAX-ACCESS  read-only
        STATUS  current
        DESCRIPTION
			"Start time of the lease."
        ::= { zyxelDhcpClientInfoEntry 7 }

        zyDhcpClientInfoLeaseTo OBJECT-TYPE
        SYNTAX  DisplayString
        MAX-ACCESS  read-only
        STATUS  current
        DESCRIPTION
			"End time of the lease."
        ::= { zyxelDhcpClientInfoEntry 8 }

        zyDhcpClientInfoDhcpServer OBJECT-TYPE
        SYNTAX  IpAddress
        MAX-ACCESS  read-only
        STATUS  current
        DESCRIPTION
			"DHCP server IP address."
        ::= { zyxelDhcpClientInfoEntry 9 }

        zyDhcpClientInfoDnsServer1 OBJECT-TYPE
        SYNTAX  IpAddress
        MAX-ACCESS  read-only
        STATUS  current
        DESCRIPTION
			"DNS server address assigned to the client."
        ::= { zyxelDhcpClientInfoEntry 10 }

        zyDhcpClientInfoDnsServer2 OBJECT-TYPE
        SYNTAX  IpAddress
        MAX-ACCESS  read-only
        STATUS  current
        DESCRIPTION
			"DNS server address assigned to the client."
        ::= { zyxelDhcpClientInfoEntry 11 }

        zyDhcpClientInfoDefaultGateway OBJECT-TYPE
        SYNTAX  IpAddress
        MAX-ACCESS  read-only
        STATUS  current
        DESCRIPTION
			"Gateway address assigned to the client."
        ::= { zyxelDhcpClientInfoEntry 12 }

        zyDhcpClientInfoRelease OBJECT-TYPE
        SYNTAX  EnabledStatus
        MAX-ACCESS  read-write
        STATUS  current
        DESCRIPTION
			"Release IP address provided by a DHCP server."
        ::= { zyxelDhcpClientInfoEntry 13 }

        zyDhcpClientInfoRenew OBJECT-TYPE
        SYNTAX  EnabledStatus
        MAX-ACCESS  read-write
        STATUS  current
        DESCRIPTION
			"Updates teh IP address provided by a DHCP server."
        ::= { zyxelDhcpClientInfoEntry 14 }
END
