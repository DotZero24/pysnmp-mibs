-- ZyXEL Communications Corporation
-- Private Enterprise MIB definition

-- This file describes the ZyXEL Communications Corporation Enterprise MIB.
-- It contains ZyXEL products OIDs, and common managed objects.

-- $Log: ZYXEL-LOAD-SHARING-MIB.mib $
-- Revision 1.7  2016/08/12 09:05:04  neng
-- add ecmp maximum paths configuration.
-- Revision 1.6  2013/12/06 07:06:38  ccho
-- remove uncessary imports
-- Revision 1.5  2013/11/20 06:53:17  ccho
-- renaming identifier name for SMI.V2
-- Revision 1.4  2013/11/06 05:41:56  ccho
-- fix mib style
-- Revision 1.3  2012/09/19 07:40:18  Kevin
-- if it's leaf node, revise the vender name from zyxel to zy
-- Revision 1.2  2012/07/05 06:23:25  Kevin
-- 1. upgrade from SNMP to SNMPv2
-- 2. clean warning
-- Revision 1.1  2012/05/30 07:49:45  Kevin
-- Initial revision

ZYXEL-LOAD-SHARING-MIB DEFINITIONS ::= BEGIN

    IMPORTS
	OBJECT-TYPE
		FROM SNMPv2-SMI			-- RFC2578

	MODULE-IDENTITY
		FROM SNMPv2-SMI

	EnabledStatus
		FROM  P-BRIDGE-MIB

	esMgmt
		FROM ZYXEL-ES-SMI;

	zyxelLoadSharing MODULE-IDENTITY
		LAST-UPDATED	"201207010000Z"
		ORGANIZATION "Enterprise Solution ZyXEL"
		CONTACT-INFO
			""
		DESCRIPTION
			"The subtree for load sharing"
		::= { esMgmt 44 }

	zyxelLoadSharingSetup	     	OBJECT IDENTIFIER ::= { zyxelLoadSharing 1 }

        zyLoadSharingState OBJECT-TYPE
        SYNTAX  EnabledStatus
        MAX-ACCESS  read-write
        STATUS  current
        DESCRIPTION
			"Enable/Disable IP load-sharing on the Switch."
        ::= { zyxelLoadSharingSetup 1 }

        zyLoadSharingCriteria OBJECT-TYPE
        SYNTAX  INTEGER{
			 srcIp(1),
			 srcDstIp(2)
		}
        MAX-ACCESS  read-write
        STATUS  current
        DESCRIPTION
			"The switch selects the criteria to determine the routing path for a packet."
        ::= { zyxelLoadSharingSetup 2 }

        zyLoadSharingAgingTime OBJECT-TYPE
        SYNTAX  INTEGER
        MAX-ACCESS  read-write
        STATUS  current
        DESCRIPTION
			"The polling time of resolved next-hops for equal-cost multipath routes."
        ::= { zyxelLoadSharingSetup 3 }

        zyLoadSharingDiscoverTime OBJECT-TYPE
        SYNTAX  INTEGER
        MAX-ACCESS  read-write
        STATUS  current
        DESCRIPTION
			"The polling time of unresolved next-hops for equal-cost multipath routes."
        ::= { zyxelLoadSharingSetup 4 }

        zyLoadSharingMaxPaths OBJECT-TYPE
        SYNTAX  INTEGER
        MAX-ACCESS  read-write
        STATUS  current
        DESCRIPTION
			"Set equal-cost multipath maximum paths."
        ::= { zyxelLoadSharingSetup 5 }

END
