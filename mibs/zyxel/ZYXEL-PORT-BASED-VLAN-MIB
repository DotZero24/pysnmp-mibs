-- ZyXEL Communications Corporation
-- Private Enterprise MIB definition

-- This file describes the ZyXEL Communications Corporation Enterprise MIB.
-- It contains ZyXEL products OIDs, and common managed objects.

-- $Log: ZYXEL-PORT-BASED-VLAN-MIB.mib $
-- Revision 1.4  2013/12/06 07:07:47  ccho
-- remove uncessary imports
-- Revision 1.3  2012/09/19 07:44:00  Kevin
-- if it's leaf node, revise the vender name from zyxel to zy
-- Revision 1.2  2012/07/05 06:24:15  Kevin
-- 1. upgrade from SNMP to SNMPv2
-- 2. clean warning
-- Revision 1.1  2012/05/30 07:50:24  Kevin
-- Initial revision

ZYXEL-PORT-BASED-VLAN-MIB DEFINITIONS ::= BEGIN

    IMPORTS
	OBJECT-TYPE
		FROM SNMPv2-SMI			-- RFC2578

	MODULE-IDENTITY
		FROM SNMPv2-SMI

	PortList
		FROM  Q-BRIDGE-MIB

	dot1dBasePort
       	FROM BRIDGE-MIB

	esMgmt
		FROM ZYXEL-ES-SMI;

	zyxelPortBasedVlan MODULE-IDENTITY
		LAST-UPDATED	"201207010000Z"
		ORGANIZATION "Enterprise Solution ZyXEL"
		CONTACT-INFO
			""
		DESCRIPTION
			"The subtree for port-based VLAN"
		::= { esMgmt 63 }

	zyxelPortBasedVlanSetup OBJECT IDENTIFIER ::= { zyxelPortBasedVlan 1 }



-- 		zyxelPortBasedVlanTable

        zyxelPortBasedVlanTable  OBJECT-TYPE
        SYNTAX	SEQUENCE OF ZyxelPortBasedVlanEntry
        MAX-ACCESS  not-accessible
        STATUS  current
        DESCRIPTION
                 	"The table contains port-based VLAN configuration. "
        ::= { zyxelPortBasedVlanSetup 1 }

		zyxelPortBasedVlanEntry  OBJECT-TYPE
        SYNTAX	ZyxelPortBasedVlanEntry
        MAX-ACCESS	not-accessible
        STATUS	current
        DESCRIPTION    	"An entry contains port-based VLAN configuration. "
        INDEX          	{ dot1dBasePort }
        ::= { zyxelPortBasedVlanTable 1 }

        ZyxelPortBasedVlanEntry ::=
           SEQUENCE {
        	zyPortBasedVlanPorts	OCTET STRING
           }

        zyPortBasedVlanPorts OBJECT-TYPE
        SYNTAX  PortList
        MAX-ACCESS  read-write
        STATUS  current
        DESCRIPTION
                      	"Set port members for each port. This allows packets to be forwarded to these port members. "
        ::= { zyxelPortBasedVlanEntry 1 }
END
