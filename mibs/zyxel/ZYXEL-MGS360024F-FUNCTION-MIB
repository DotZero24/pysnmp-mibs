ZYXEL-MGS360024F-FUNCTION-MIB DEFINITIONS ::= BEGIN

IMPORTS
    DisplayString,MacAddress FROM SNMPv2-TC
    MODULE-COMPLIANCE,OBJECT-GROUP, NOTIFICATION-GROUP       FROM SNMPv2-CONF
    ifIndex    FROM RFC1213-MIB
    enterprises,MODULE-IDENTITY,OBJECT-TYPE,NOTIFICATION-TYPE,Counter32,Counter64,IpAddress        FROM SNMPv2-SMI
    InetAddress                   FROM INET-ADDRESS-MIB
    MacAddress FROM BRIDGE-MIB;

zyxel MODULE-IDENTITY
        LAST-UPDATED "201205150000Z"
        ORGANIZATION "Corp."
        CONTACT-INFO
            ""
        DESCRIPTION
            ""
        ::= { enterprises 890 }

products                                                         OBJECT IDENTIFIER ::= { zyxel 1 }

accessSwitch                                                    OBJECT IDENTIFIER ::= { products 5 }

esSeries                                                        OBJECT IDENTIFIER ::= { accessSwitch 8 }

mgs360024fProductId                                             OBJECT IDENTIFIER ::= { esSeries 76 }

mgs360024fSystem                                                OBJECT IDENTIFIER ::= { mgs360024fProductId 1 }

mgs360024fSystemInformation                                     OBJECT IDENTIFIER ::= { mgs360024fSystem 1 }

mgs360024fModelName OBJECT-TYPE
   SYNTAX       DisplayString
   MAX-ACCESS   read-only
   STATUS       current
   DESCRIPTION
       ""
 ::= { mgs360024fSystemInformation 1 }

mgs360024fBIOSVersion OBJECT-TYPE
   SYNTAX       DisplayString
   MAX-ACCESS   read-only
   STATUS       current
   DESCRIPTION
       ""
   ::= { mgs360024fSystemInformation 2 }

mgs360024fFirmwareVersion OBJECT-TYPE
   SYNTAX       DisplayString
   MAX-ACCESS   read-only
   STATUS       current
   DESCRIPTION
       ""
   ::= { mgs360024fSystemInformation 3 }

mgs360024fHardwareMechanicalVersion OBJECT-TYPE
   SYNTAX       DisplayString
   MAX-ACCESS   read-only
   STATUS       current
   DESCRIPTION
       ""
   ::= { mgs360024fSystemInformation 4 }

mgs360024fSeriesNumber OBJECT-TYPE
   SYNTAX       DisplayString
   MAX-ACCESS   read-only
   STATUS       current
   DESCRIPTION
       ""
   ::= { mgs360024fSystemInformation 5 }

mgs360024fHostMACAddress OBJECT-TYPE
   SYNTAX       MacAddress
   MAX-ACCESS   read-only
   STATUS       current
   DESCRIPTION
       ""
   ::= { mgs360024fSystemInformation 6 }

mgs360024fConsoleBaudrate OBJECT-TYPE
   SYNTAX       DisplayString
   MAX-ACCESS   read-only
   STATUS       current
   DESCRIPTION
       ""
   ::= { mgs360024fSystemInformation 7 }

mgs360024fRAMSize OBJECT-TYPE
   SYNTAX       DisplayString
   MAX-ACCESS   read-only
   STATUS       current
   DESCRIPTION
       ""
   ::= { mgs360024fSystemInformation 8 }

mgs360024fFlashSize OBJECT-TYPE
   SYNTAX       DisplayString
   MAX-ACCESS   read-only
   STATUS       current
   DESCRIPTION
       ""
   ::= { mgs360024fSystemInformation 9 }

mgs360024fBridgeFBDSize OBJECT-TYPE
   SYNTAX       DisplayString
   MAX-ACCESS   read-only
   STATUS       current
   DESCRIPTION
       ""
   ::= { mgs360024fSystemInformation 10 }

mgs360024fTransmitQueue OBJECT-TYPE
   SYNTAX       DisplayString
   MAX-ACCESS   read-only
   STATUS       current
   DESCRIPTION
       ""
   ::= { mgs360024fSystemInformation 11 }

mgs360024fMaximumFrameSize OBJECT-TYPE
   SYNTAX       DisplayString
   MAX-ACCESS   read-only
   STATUS       current
   DESCRIPTION
       ""
   ::= { mgs360024fSystemInformation 12 }

mgs360024fCPULoad OBJECT-TYPE
   SYNTAX       DisplayString
   MAX-ACCESS   read-only
   STATUS       current
   DESCRIPTION
       ""
   ::= { mgs360024fSystemInformation 13 }

mgs360024fFanSpeed OBJECT-TYPE
   SYNTAX       DisplayString
   MAX-ACCESS   read-only
   STATUS       current
   DESCRIPTION
       ""
   ::= { mgs360024fSystemInformation 14 }

mgs360024fPowers OBJECT-TYPE
   SYNTAX       DisplayString
   MAX-ACCESS   read-only
   STATUS       current
   DESCRIPTION
       ""
   ::= { mgs360024fSystemInformation 15 }

mgs360024fTemperature1 OBJECT-TYPE
   SYNTAX       DisplayString
   MAX-ACCESS   read-only
   STATUS       current
   DESCRIPTION
       ""
   ::= { mgs360024fSystemInformation 16 }

mgs360024fTemperature2 OBJECT-TYPE
   SYNTAX       DisplayString
   MAX-ACCESS   read-only
   STATUS       current
   DESCRIPTION
       ""
   ::= { mgs360024fSystemInformation 17 }

mgs360024fTemperature3 OBJECT-TYPE
   SYNTAX       DisplayString
   MAX-ACCESS   read-only
   STATUS       current
   DESCRIPTION
       ""
   ::= { mgs360024fSystemInformation 18 }

mgs360024fTemperature4 OBJECT-TYPE
   SYNTAX       DisplayString
   MAX-ACCESS   read-only
   STATUS       current
   DESCRIPTION
       ""
   ::= { mgs360024fSystemInformation 19 }


mgs360024fSystemTime                                            OBJECT IDENTIFIER ::= { mgs360024fSystem 2 }

mgs360024fSystemTimeManual                                      OBJECT IDENTIFIER ::= { mgs360024fSystemTime 1 }

mgs360024fSystemTimeManualClockSource OBJECT-TYPE
   SYNTAX       INTEGER(0|1)
   MAX-ACCESS   read-write
   STATUS       current
   DESCRIPTION
       "default: 0,
        0 : Use Local Settings,
        1 : Use NTP Server."
   ::= { mgs360024fSystemTimeManual 1 }

mgs360024fSystemTimeManualLocaltime OBJECT-TYPE
   SYNTAX       DisplayString
   MAX-ACCESS   read-write
   STATUS       current
   DESCRIPTION
       "Get/Set the system time of the device.
        The input format is 'Year-Month-Day Hour:Minute:Second'.
        ex: 2011-01-01 05:43:05  means 2011/1/1 - 05:43:05 .
        The value range:
        Year    : 2010 - 2090,
        Mouth   : 1 - 12,
        Day     : 1 - 31,
        Hour    : 0 - 23,
        Minute  : 0 - 59,
        Sec     : 0 - 59."
   ::= { mgs360024fSystemTimeManual 2 }

mgs360024fSystemTimeManualTimeZoneOffset OBJECT-TYPE
   SYNTAX       INTEGER(-720..780)
   MAX-ACCESS   read-write
   STATUS       current
   DESCRIPTION
       "Get/Set the NTP Time Zone.
        The value range is between -720 and 780 (minutes)."
   ::= { mgs360024fSystemTimeManual 3 }

mgs360024fSystemTimeManualDaylightSavings OBJECT-TYPE
   SYNTAX       INTEGER(0|1)
   MAX-ACCESS   read-write
   STATUS       current
   DESCRIPTION
       "default: 0,
        0 : Disable,
        1 : Enable."
   ::= { mgs360024fSystemTimeManual 4 }

mgs360024fSystemTimeManualTimeSetOffset OBJECT-TYPE
   SYNTAX       INTEGER(1..1440)
   MAX-ACCESS   read-write
   STATUS       current
   DESCRIPTION
       "Get/Set the Daylight Saving Time.
        The value range is between 1 and 1440 (minutes),
        Default : 60 (minutes)."
   ::= { mgs360024fSystemTimeManual 5 }

mgs360024fSystemTimeManualDaylightSavingsType OBJECT-TYPE
   SYNTAX       INTEGER(0|1)
   MAX-ACCESS   read-write
   STATUS       current
   DESCRIPTION
       "default: 0,
        0 : By dates,
        1 : Recurring."
   ::= { mgs360024fSystemTimeManual 6 }

mgs360024fSystemTimeManualDaylightSavingsBydatesFrom OBJECT-TYPE
   SYNTAX       DisplayString
   MAX-ACCESS   read-write
   STATUS       current
   DESCRIPTION
       "Get/Set the Start time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { mgs360024fSystemTimeManual 7 }

mgs360024fSystemTimeManualDaylightSavingsBydatesTo OBJECT-TYPE
   SYNTAX       DisplayString
   MAX-ACCESS   read-write
   STATUS       current
   DESCRIPTION
       "Get/Set the End time of By dates Daylight Savings.
        The input format is 'Year-Month-Day Hour:Minute'.
        ex: 2011-01-01 05:43  means 2011/1/1 - 05:43 .
        The value range:
        Year    : 2010 - 2090,
        Mouth   : 1 - 12,
        Day     : 1 - 31,
        Hour    : 0 - 23,
        Minute  : 0 - 59."
   ::= { mgs360024fSystemTimeManual 8 }

mgs360024fSystemTimeManualDaylightSavingsRecurringDayFrom OBJECT-TYPE
   SYNTAX       INTEGER(0..6)
   MAX-ACCESS   read-write
   STATUS       current
   DESCRIPTION
       "Get/Set the Daylight Saving Time Day From.
        0 : Sun, 1 : Mon, 2 : Tue, 3 : Wed, 4 : Thu, 5 : Fri, 6 : Sat."
   ::= { mgs360024fSystemTimeManual 9 }

mgs360024fSystemTimeManualDaylightSavingsRecurringWeekFrom OBJECT-TYPE
   SYNTAX       INTEGER(1..5)
   MAX-ACCESS   read-write
   STATUS       current
   DESCRIPTION
       "Get/Set the Daylight Saving Time Week From.
        1 : first week, 2, 3, 4, 5 : last week"
   ::= { mgs360024fSystemTimeManual 10 }

mgs360024fSystemTimeManualDaylightSavingsRecurringMonthFrom OBJECT-TYPE
   SYNTAX       INTEGER(0..11)
   MAX-ACCESS   read-write
   STATUS       current
   DESCRIPTION
       "Get/Set the Daylight Saving Time Month From.
        1 : Jan, 2 : Feb, 3 : Mar, 4 : Apr, 5 : May, 6 : Jun,
        7 : Jul, 8 : Aug, 9 : Sep, 10 : Oct, 11 : Nov, 12 : Dec."
   ::= { mgs360024fSystemTimeManual 11 }

mgs360024fSystemTimeManualDaylightSavingsRecurringTimeFrom OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { mgs360024fSystemTimeManual 12 }

mgs360024fSystemTimeManualDaylightSavingsRecurringDayTo OBJECT-TYPE
   SYNTAX       INTEGER(0..6)
   MAX-ACCESS   read-write
   STATUS       current
   DESCRIPTION
       "Get/Set the Daylight Saving Time Day To.
        0 : Sun, 1 : Mon, 2 : Tue, 3 : Wed, 4 : Thu, 5 : Fri, 6 : Sat."
   ::= { mgs360024fSystemTimeManual 13 }

mgs360024fSystemTimeManualDaylightSavingsRecurringWeekTo OBJECT-TYPE
   SYNTAX       INTEGER(1..5)
   MAX-ACCESS   read-write
   STATUS       current
   DESCRIPTION
       "Get/Set the Daylight Saving Time Week To.
        1 : first week, 2, 3, 4, 5 : last week"
   ::= { mgs360024fSystemTimeManual 14 }

mgs360024fSystemTimeManualDaylightSavingsRecurringMonthTo OBJECT-TYPE
   SYNTAX       INTEGER(0..11)
   MAX-ACCESS   read-write
   STATUS       current
   DESCRIPTION
       "Get/Set the Daylight Saving Time Month To.
        1 : Jan, 2 : Feb, 3 : Mar, 4 : Apr, 5 : May, 6 : Jun,
        7 : Jul, 8 : Aug, 9 : Sep, 10 : Oct, 11 : Nov, 12 : Dec."
   ::= { mgs360024fSystemTimeManual 15 }

mgs360024fSystemTimeManualDaylightSavingsRecurringTimeTo OBJECT-TYPE
   SYNTAX       DisplayString
   MAX-ACCESS   read-write
   STATUS       current
   DESCRIPTION
       "Get/Set the Start time of By dates Daylight Savings.
        The input format is 'Hour:Minute'.
        ex: 05:43.
        The value range:
        Hour    : 0 - 23,
        Minute  : 0 - 59."
   ::= { mgs360024fSystemTimeManual 16 }

mgs360024fSystemTimeNTP                                     OBJECT IDENTIFIER ::= { mgs360024fSystemTime 2 }

mgs360024fSystemTimeNTPTable OBJECT-TYPE
   SYNTAX      SEQUENCE OF MGS360024FSystemTimeNTPEntry
   MAX-ACCESS  not-accessible
   STATUS      current
   DESCRIPTION
       " "
   ::= { mgs360024fSystemTimeNTP 1 }

mgs360024fSystemTimeNTPEntry OBJECT-TYPE
   SYNTAX      MGS360024FSystemTimeNTPEntry
   MAX-ACCESS  not-accessible
   STATUS      current
   DESCRIPTION
       ""
   INDEX    { mgs360024fSystemTimeNTPIndex  }
   ::= { mgs360024fSystemTimeNTPTable 1 }

MGS360024FSystemTimeNTPEntry ::= SEQUENCE {
   mgs360024fSystemTimeNTPIndex             INTEGER,
   mgs360024fSystemTimeNTPServerIPType      INTEGER,
   mgs360024fSystemTimeNTPServer            DisplayString,
   mgs360024fSystemTimeNTPCurrentMode       INTEGER
}

mgs360024fSystemTimeNTPIndex OBJECT-TYPE
   SYNTAX      INTEGER (1..5)
   MAX-ACCESS  not-accessible
   STATUS      current
   DESCRIPTION
       " The index of the ntp entry. "
   ::= { mgs360024fSystemTimeNTPEntry 1 }

mgs360024fSystemTimeNTPServerIPType OBJECT-TYPE
   SYNTAX       INTEGER(0|1)
   MAX-ACCESS   read-write
   STATUS       current
   DESCRIPTION
       "Default: 0,
        0 : IPv4,
        1 : IPv6."
   ::= { mgs360024fSystemTimeNTPEntry 2 }

mgs360024fSystemTimeNTPServer OBJECT-TYPE
   SYNTAX       DisplayString
   MAX-ACCESS   read-write
   STATUS       current
   DESCRIPTION
       "Get/Set the NTP Time Server1. You can use the IP address or domain name."
   ::= { mgs360024fSystemTimeNTPEntry 3 }

mgs360024fSystemTimeNTPCurrentMode OBJECT-TYPE
   SYNTAX      INTEGER (0..3)
   MAX-ACCESS  read-write
   STATUS      current
   DESCRIPTION
       " 0: Empty
        1: Active
        2: Edit
        3: Delete"
   ::= { mgs360024fSystemTimeNTPEntry 4 }


mgs360024fSystemAccount                                         OBJECT IDENTIFIER ::= { mgs360024fSystem 3 }

mgs360024fSystemAccountUsers                                    OBJECT IDENTIFIER ::= { mgs360024fSystemAccount 1 }

mgs360024fSystemAccountUserCreate OBJECT-TYPE
   SYNTAX       INTEGER(0|1)
   MAX-ACCESS   read-write
   STATUS       current
   DESCRIPTION
       "default: 0
        0 : None  (read only)
        1 : Create a user account"
   ::= { mgs360024fSystemAccountUsers 1 }

mgs360024fSystemAccountUsersTable OBJECT-TYPE
   SYNTAX      SEQUENCE OF MGS360024FSystemAccountUsersEntry
   MAX-ACCESS  not-accessible
   STATUS      current
   DESCRIPTION
       " "
   ::= { mgs360024fSystemAccountUsers 2 }

mgs360024fSystemAccountUsersEntry OBJECT-TYPE
   SYNTAX      MGS360024FSystemAccountUsersEntry
   MAX-ACCESS  not-accessible
   STATUS      current
   DESCRIPTION
       ""
   INDEX    { mgs360024fUserIndex  }
   ::= { mgs360024fSystemAccountUsersTable 1 }


MGS360024FSystemAccountUsersEntry ::= SEQUENCE {
   mgs360024fUserIndex              INTEGER,
   mgs360024fUserName               DisplayString,
   mgs360024fPassword               DisplayString,
   mgs360024fUserPrivilegeLevel     INTEGER,
   mgs360024fAccountUserRowStatus   INTEGER
}


mgs360024fUserIndex OBJECT-TYPE
   SYNTAX      INTEGER (1..20)
   MAX-ACCESS  not-accessible
   STATUS      current
   DESCRIPTION
       " "
   ::= { mgs360024fSystemAccountUsersEntry 1 }

mgs360024fUserName OBJECT-TYPE
   SYNTAX      DisplayString (SIZE (1..32))
   MAX-ACCESS  read-write
   STATUS      current
   DESCRIPTION
       " "
   ::= { mgs360024fSystemAccountUsersEntry 2 }

mgs360024fPassword OBJECT-TYPE
   SYNTAX      DisplayString (SIZE (1..32))
   MAX-ACCESS  read-write
   STATUS      current
   DESCRIPTION
       " "
   ::= { mgs360024fSystemAccountUsersEntry 3 }

mgs360024fUserPrivilegeLevel OBJECT-TYPE
   SYNTAX      INTEGER (1..15)
   MAX-ACCESS  read-write
   STATUS      current
   DESCRIPTION
       "default:1
        User privilege level range : 1 - 15"
   ::= { mgs360024fSystemAccountUsersEntry 4 }

mgs360024fAccountUserRowStatus OBJECT-TYPE
   SYNTAX      INTEGER (1..5)
   MAX-ACCESS  read-write
   STATUS      current
   DESCRIPTION
       " 1: active
        2: notInservice
        3: edit
        4: destroy
        5: undo"
   ::= { mgs360024fSystemAccountUsersEntry 5 }

mgs360024fSystemAccountPrivilegeLevel                           OBJECT IDENTIFIER ::= { mgs360024fSystemAccount 2 }

mgs360024fAccountPrivilegeLevel OBJECT-TYPE
   SYNTAX      INTEGER (1..15)
   MAX-ACCESS  read-write
   STATUS      current
   DESCRIPTION
       "Default:10, Range : 1-15. "
   ::= { mgs360024fSystemAccountPrivilegeLevel 1 }

mgs360024fAggregationPrivilegeLevel OBJECT-TYPE
   SYNTAX      INTEGER (1..15)
   MAX-ACCESS  read-write
   STATUS      current
   DESCRIPTION
       "Default:10, Range : 1-15. "
   ::= { mgs360024fSystemAccountPrivilegeLevel 2 }

mgs360024fDiagnosticsPrivilegeLevel OBJECT-TYPE
   SYNTAX      INTEGER (1..15)
   MAX-ACCESS  read-write
   STATUS      current
   DESCRIPTION
       "Default:10, Range : 1-15. "
   ::= { mgs360024fSystemAccountPrivilegeLevel 3 }

mgs360024fEPSPrivilegeLevel OBJECT-TYPE
   SYNTAX      INTEGER (1..15)
   MAX-ACCESS  read-write
   STATUS      current
   DESCRIPTION
       "Default:10, Range : 1-15. "
   ::= { mgs360024fSystemAccountPrivilegeLevel 5 }

mgs360024fERPSPrivilegeLevel OBJECT-TYPE
   SYNTAX      INTEGER (1..15)
   MAX-ACCESS  read-write
   STATUS      current
   DESCRIPTION
       "Default:10, Range : 1-15. "
   ::= { mgs360024fSystemAccountPrivilegeLevel 6 }

mgs360024fETHLinkOAMPrivilegeLevel OBJECT-TYPE
   SYNTAX      INTEGER (1..15)
   MAX-ACCESS  read-write
   STATUS      current
   DESCRIPTION
       "Default:10, Range : 1-15. "
   ::= { mgs360024fSystemAccountPrivilegeLevel 7 }

mgs360024fEVCPrivilegeLevel OBJECT-TYPE
   SYNTAX      INTEGER (1..15)
   MAX-ACCESS  read-write
   STATUS      current
   DESCRIPTION
       "Default:10, Range : 1-15. "
   ::= { mgs360024fSystemAccountPrivilegeLevel 8 }

mgs360024fGARPPrivilegeLevel OBJECT-TYPE
   SYNTAX      INTEGER (1..15)
   MAX-ACCESS  read-write
   STATUS      current
   DESCRIPTION
       "Default:10, Range : 1-15. "
   ::= { mgs360024fSystemAccountPrivilegeLevel 10 }

mgs360024fGVRPPrivilegeLevel OBJECT-TYPE
   SYNTAX      INTEGER (1..15)
   MAX-ACCESS  read-write
   STATUS      current
   DESCRIPTION
       "Default:10, Range : 1-15. "
   ::= { mgs360024fSystemAccountPrivilegeLevel 11 }

mgs360024fIPPrivilegeLevel OBJECT-TYPE
   SYNTAX      INTEGER (1..15)
   MAX-ACCESS  read-write
   STATUS      current
   DESCRIPTION
       "Default:10, Range : 1-15. "
   ::= { mgs360024fSystemAccountPrivilegeLevel 12 }

mgs360024fIPMCSnoopingPrivilegeLevel OBJECT-TYPE
   SYNTAX      INTEGER (1..15)
   MAX-ACCESS  read-write
   STATUS      current
   DESCRIPTION
       "Default:10, Range : 1-15. "
   ::= { mgs360024fSystemAccountPrivilegeLevel 13 }

mgs360024fLACPPrivilegeLevel OBJECT-TYPE
   SYNTAX      INTEGER (1..15)
   MAX-ACCESS  read-write
   STATUS      current
   DESCRIPTION
       "Default:10, Range : 1-15. "
   ::= { mgs360024fSystemAccountPrivilegeLevel 14 }

mgs360024fLLDPPrivilegeLevel OBJECT-TYPE
   SYNTAX      INTEGER (1..15)
   MAX-ACCESS  read-write
   STATUS      current
   DESCRIPTION
       "Default:10, Range : 1-15. "
   ::= { mgs360024fSystemAccountPrivilegeLevel 15 }

mgs360024fLLDPMEDPrivilegeLevel OBJECT-TYPE
   SYNTAX      INTEGER (1..15)
   MAX-ACCESS  read-write
   STATUS      current
   DESCRIPTION
       "Default:10, Range : 1-15. "
   ::= { mgs360024fSystemAccountPrivilegeLevel 16 }

mgs360024fLoopProtectPrivilegeLevel OBJECT-TYPE
   SYNTAX      INTEGER (1..15)
   MAX-ACCESS  read-write
   STATUS      current
   DESCRIPTION
       "Default:10, Range : 1-15. "
   ::= { mgs360024fSystemAccountPrivilegeLevel 17 }

mgs360024fMACTablePrivilegeLevel OBJECT-TYPE
   SYNTAX      INTEGER (1..15)
   MAX-ACCESS  read-write
   STATUS      current
   DESCRIPTION
       "Default:10, Range : 1-15. "
   ::= { mgs360024fSystemAccountPrivilegeLevel 18 }

mgs360024fMEPPrivilegeLevel OBJECT-TYPE
   SYNTAX      INTEGER (1..15)
   MAX-ACCESS  read-write
   STATUS      current
   DESCRIPTION
       "Default:10, Range : 1-15. "
   ::= { mgs360024fSystemAccountPrivilegeLevel 20 }

mgs360024fMRSTPPrivilegeLevel OBJECT-TYPE
   SYNTAX      INTEGER (1..15)
   MAX-ACCESS  read-write
   STATUS      current
   DESCRIPTION
       "Default:10, Range : 1-15. "
   ::= { mgs360024fSystemAccountPrivilegeLevel 21 }

mgs360024fMVRPrivilegeLevel OBJECT-TYPE
   SYNTAX      INTEGER (1..15)
   MAX-ACCESS  read-write
   STATUS      current
   DESCRIPTION
       "Default:10, Range : 1-15. "
   ::= { mgs360024fSystemAccountPrivilegeLevel 22 }

mgs360024fMaintenancePrivilegeLevel OBJECT-TYPE
   SYNTAX      INTEGER (1..15)
   MAX-ACCESS  read-write
   STATUS      current
   DESCRIPTION
       "Default:10, Range : 1-15. "
   ::= { mgs360024fSystemAccountPrivilegeLevel 24 }

mgs360024fMirroringPrivilegeLevel OBJECT-TYPE
   SYNTAX      INTEGER (1..15)
   MAX-ACCESS  read-write
   STATUS      current
   DESCRIPTION
       "Default:10, Range : 1-15. "
   ::= { mgs360024fSystemAccountPrivilegeLevel 25 }

mgs360024fPTPPrivilegeLevel OBJECT-TYPE
   SYNTAX      INTEGER (1..15)
   MAX-ACCESS  read-write
   STATUS      current
   DESCRIPTION
       "Default:10, Range : 1-15. "
   ::= { mgs360024fSystemAccountPrivilegeLevel 26 }

mgs360024fPortsPrivilegeLevel OBJECT-TYPE
   SYNTAX      INTEGER (1..15)
   MAX-ACCESS  read-write
   STATUS      current
   DESCRIPTION
       "Default:10, Range : 1-15. "
   ::= { mgs360024fSystemAccountPrivilegeLevel 27 }

mgs360024fPrivateVLANsPrivilegeLevel OBJECT-TYPE
   SYNTAX      INTEGER (1..15)
   MAX-ACCESS  read-write
   STATUS      current
   DESCRIPTION
       "Default:10, Range : 1-15. "
   ::= { mgs360024fSystemAccountPrivilegeLevel 28 }

mgs360024fQoSPrivilegeLevel OBJECT-TYPE
   SYNTAX      INTEGER (1..15)
   MAX-ACCESS  read-write
   STATUS      current
   DESCRIPTION
       "Default:10, Range : 1-15. "
   ::= { mgs360024fSystemAccountPrivilegeLevel 29 }

mgs360024fSMTPPrivilegeLevel OBJECT-TYPE
   SYNTAX      INTEGER (1..15)
   MAX-ACCESS  read-write
   STATUS      current
   DESCRIPTION
       "Default:10, Range : 1-15. "
   ::= { mgs360024fSystemAccountPrivilegeLevel 31 }

mgs360024fSNMPPrivilegeLevel OBJECT-TYPE
   SYNTAX      INTEGER (1..15)
   MAX-ACCESS  read-write
   STATUS      current
   DESCRIPTION
       "Default:10, Range : 1-15. "
   ::= { mgs360024fSystemAccountPrivilegeLevel 32 }

mgs360024fSecurityPrivilegeLevel OBJECT-TYPE
   SYNTAX      INTEGER (1..15)
   MAX-ACCESS  read-write
   STATUS      current
   DESCRIPTION
       "Default:10, Range : 1-15. "
   ::= { mgs360024fSystemAccountPrivilegeLevel 33 }

mgs360024fSpanningTreePrivilegeLevel OBJECT-TYPE
   SYNTAX      INTEGER (1..15)
   MAX-ACCESS  read-write
   STATUS      current
   DESCRIPTION
       "Default:10, Range : 1-15. "
   ::= { mgs360024fSystemAccountPrivilegeLevel 35 }

mgs360024fSystemPrivilegeLevel OBJECT-TYPE
   SYNTAX      INTEGER (1..15)
   MAX-ACCESS  read-write
   STATUS      current
   DESCRIPTION
       "Default:10, Range : 1-15. "
   ::= { mgs360024fSystemAccountPrivilegeLevel 36 }

mgs360024fTrapEventPrivilegeLevel OBJECT-TYPE
   SYNTAX      INTEGER (1..15)
   MAX-ACCESS  read-write
   STATUS      current
   DESCRIPTION
       "Default:10, Range : 1-15. "
   ::= { mgs360024fSystemAccountPrivilegeLevel 37 }

mgs360024fVCLPrivilegeLevel OBJECT-TYPE
   SYNTAX      INTEGER (1..15)
   MAX-ACCESS  read-write
   STATUS      current
   DESCRIPTION
       "Default:10, Range : 1-15. "
   ::= { mgs360024fSystemAccountPrivilegeLevel 39 }

mgs360024fVLANTranslationPrivilegeLevel OBJECT-TYPE
   SYNTAX      INTEGER (1..15)
   MAX-ACCESS  read-write
   STATUS      current
   DESCRIPTION
       "Default:10, Range : 1-15. "
   ::= { mgs360024fSystemAccountPrivilegeLevel 40 }

mgs360024fVLANsPrivilegeLevel OBJECT-TYPE
   SYNTAX      INTEGER (1..15)
   MAX-ACCESS  read-write
   STATUS      current
   DESCRIPTION
       "Default:10, Range : 1-15. "
   ::= { mgs360024fSystemAccountPrivilegeLevel 41 }


mgs360024fIP                                                    OBJECT IDENTIFIER ::= { mgs360024fSystem 4 }

mgs360024fIPv4                                                  OBJECT IDENTIFIER ::= { mgs360024fIP 1 }

mgs360024fIPv4Configured                                                  OBJECT IDENTIFIER ::= { mgs360024fIPv4 1 }

mgs360024fIpv4DHCPClient OBJECT-TYPE
   SYNTAX      INTEGER (0|1)
   MAX-ACCESS  read-write
   STATUS      current
   DESCRIPTION
       "default:0
       0: disable
       1: enable"
   ::= { mgs360024fIPv4Configured 1 }

mgs360024fIPv4Address OBJECT-TYPE
   SYNTAX      IpAddress
   MAX-ACCESS  read-write
   STATUS      current
   DESCRIPTION
       ""
   ::= { mgs360024fIPv4Configured 2 }

mgs360024fIPv4Mask OBJECT-TYPE
   SYNTAX      IpAddress
   MAX-ACCESS  read-write
   STATUS      current
   DESCRIPTION
       ""
   ::= { mgs360024fIPv4Configured 3 }

mgs360024fIPv4Router OBJECT-TYPE
   SYNTAX      IpAddress
   MAX-ACCESS  read-write
   STATUS      current
   DESCRIPTION
       ""
   ::= { mgs360024fIPv4Configured 4 }

mgs360024fIPv4VLANId OBJECT-TYPE
   SYNTAX      INTEGER (1..4094)
   MAX-ACCESS  read-write
   STATUS      current
   DESCRIPTION
       "default:1"
   ::= { mgs360024fIPv4Configured 5 }

mgs360024fIPv4DNSServer OBJECT-TYPE
   SYNTAX      IpAddress
   MAX-ACCESS  read-write
   STATUS      current
   DESCRIPTION
       ""
   ::= { mgs360024fIPv4Configured 6 }

mgs360024fIPv4DNSProxy OBJECT-TYPE
   SYNTAX      INTEGER (0|1)
   MAX-ACCESS  read-write
   STATUS      current
   DESCRIPTION
       " "
   ::= { mgs360024fIPv4Configured 7 }

mgs360024fIPv4Current                                                  OBJECT IDENTIFIER ::= { mgs360024fIPv4 2 }

mgs360024fIpv4CurrentDHCPClient OBJECT-TYPE
   SYNTAX      INTEGER (0|1)
   MAX-ACCESS  read-write
   STATUS      current
   DESCRIPTION
       "default:0
       0: none (for read)
       1: renew"
   ::= { mgs360024fIPv4Current 1 }

mgs360024fIPv4CurrentAddress OBJECT-TYPE
   SYNTAX      IpAddress
   MAX-ACCESS  read-only
   STATUS      current
   DESCRIPTION
       ""
   ::= { mgs360024fIPv4Current 2 }

mgs360024fIPv4CurrentMask OBJECT-TYPE
   SYNTAX      IpAddress
   MAX-ACCESS  read-only
   STATUS      current
   DESCRIPTION
       ""
   ::= { mgs360024fIPv4Current 3 }

mgs360024fIPv4CurrentRouter OBJECT-TYPE
   SYNTAX      IpAddress
   MAX-ACCESS  read-only
   STATUS      current
   DESCRIPTION
       ""
   ::= { mgs360024fIPv4Current 4 }

mgs360024fIPv4CurrentVLANId OBJECT-TYPE
   SYNTAX      INTEGER (1..4094)
   MAX-ACCESS  read-only
   STATUS      current
   DESCRIPTION
       "default:1"
   ::= { mgs360024fIPv4Current 5 }

mgs360024fIPv4CurrentDNSServer OBJECT-TYPE
   SYNTAX      IpAddress
   MAX-ACCESS  read-only
   STATUS      current
   DESCRIPTION
       ""
   ::= { mgs360024fIPv4Current 6 }


mgs360024fIPv6                                                  OBJECT IDENTIFIER ::= { mgs360024fIP 2 }

mgs360024fIPv6Configured                                                  OBJECT IDENTIFIER ::= { mgs360024fIPv6 1 }

mgs360024fIpv6AutoConfiguration OBJECT-TYPE
   SYNTAX      INTEGER (0|1)
   MAX-ACCESS  read-write
   STATUS      current
   DESCRIPTION
       "default:0
       0: disable
       1: enable"
   ::= { mgs360024fIPv6Configured 1 }

mgs360024fIpv6Address OBJECT-TYPE
   SYNTAX      DisplayString (SIZE (0..30))
   MAX-ACCESS  read-write
   STATUS      current
   DESCRIPTION
       ""
   ::= { mgs360024fIPv6Configured 2 }

mgs360024fIpv6Prefix OBJECT-TYPE
   SYNTAX      INTEGER (1..128)
   MAX-ACCESS  read-write
   STATUS      current
   DESCRIPTION
       "default: 96"
   ::= { mgs360024fIPv6Configured 3 }

mgs360024fIpv6Router OBJECT-TYPE
   SYNTAX      DisplayString (SIZE (0..30))
   MAX-ACCESS  read-write
   STATUS      current
   DESCRIPTION
       " "
   ::= { mgs360024fIPv6Configured 4 }

mgs360024fIPv6Current                                                  OBJECT IDENTIFIER ::= { mgs360024fIPv6 2 }

mgs360024fIpv6CurrentAutoConfiguration OBJECT-TYPE
   SYNTAX      INTEGER (0|1)
   MAX-ACCESS  read-only
   STATUS      current
   DESCRIPTION
       "default:0
       0: disable
       1: enable"
   ::= { mgs360024fIPv6Current 1 }

mgs360024fIpv6CurrentAddress OBJECT-TYPE
   SYNTAX      DisplayString (SIZE (0..30))
   MAX-ACCESS  read-only
   STATUS      current
   DESCRIPTION
       ""
   ::= { mgs360024fIPv6Current 2 }


mgs360024fIpv6CurrentLinkLocalAddress OBJECT-TYPE
   SYNTAX      DisplayString(SIZE (0..30))
   MAX-ACCESS  read-only
   STATUS      current
   DESCRIPTION
       ""
   ::= { mgs360024fIPv6Current 3 }


mgs360024fIpv6CurrentPrefix OBJECT-TYPE
   SYNTAX      INTEGER (1..128)
   MAX-ACCESS  read-only
   STATUS      current
   DESCRIPTION
       ""
   ::= { mgs360024fIPv6Current 4 }

mgs360024fIpv6CurrentRouter OBJECT-TYPE
   SYNTAX      DisplayString (SIZE (0..30))
   MAX-ACCESS  read-only
   STATUS      current
   DESCRIPTION
       " "
   ::= { mgs360024fIPv6Current 5 }

mgs360024fSyslog                                                OBJECT IDENTIFIER ::= { mgs360024fSystem 5 }

mgs360024fSyslogConf                                            OBJECT IDENTIFIER ::= { mgs360024fSyslog 1 }

mgs360024fServerMode OBJECT-TYPE
   SYNTAX      INTEGER (0|1)
   MAX-ACCESS  read-write
   STATUS      current
   DESCRIPTION
       "default: 0
       0: disable
       1: enable "
   ::= { mgs360024fSyslogConf 1 }

mgs360024fServerAddress1 OBJECT-TYPE
   SYNTAX      IpAddress
   MAX-ACCESS  read-write
   STATUS      current
   DESCRIPTION
       " "
   ::= { mgs360024fSyslogConf 2 }

mgs360024fServerAddress2 OBJECT-TYPE
   SYNTAX      IpAddress
   MAX-ACCESS  read-write
   STATUS      current
   DESCRIPTION
       " "
   ::= { mgs360024fSyslogConf 3 }

mgs360024fSyslogLevel OBJECT-TYPE
   SYNTAX      INTEGER(0..7)
   MAX-ACCESS  read-write
   STATUS      current
   DESCRIPTION
       "default: 6 (Info)
       0: Emergency
       1: Alert
       2: Critical
       3: Error
       4: Warning
       5: Notice
       6: Info
       7: Debug"
   ::= { mgs360024fSyslogConf 4 }

mgs360024fSyslogDetailedInfo                                    OBJECT IDENTIFIER ::= { mgs360024fSyslog 2 }

mgs360024fSyslogDetailedInfoClear OBJECT-TYPE
   SYNTAX      INTEGER(0|1)
   MAX-ACCESS  read-write
   STATUS      current
   DESCRIPTION
      "default: 0
       0 : None  (read only)
       1 : Clear Syslog"
   ::= { mgs360024fSyslogDetailedInfo 1 }

mgs360024fSyslogDetailedInfoTable OBJECT-TYPE
  SYNTAX      SEQUENCE OF MGS360024FSyslogDetailedInfoEntry
  MAX-ACCESS  not-accessible
  STATUS      current
  DESCRIPTION
           " "
       ::= { mgs360024fSyslogDetailedInfo 2 }

mgs360024fSyslogDetailedInfoEntry OBJECT-TYPE
   SYNTAX      MGS360024FSyslogDetailedInfoEntry
   MAX-ACCESS  not-accessible
   STATUS      current
   DESCRIPTION
           ""
   INDEX    { mgs360024fSyslogDetailedInfoIndex  }
   ::= { mgs360024fSyslogDetailedInfoTable 1 }

MGS360024FSyslogDetailedInfoEntry ::= SEQUENCE {
   mgs360024fSyslogDetailedInfoIndex       INTEGER,
   mgs360024fSyslogDetailedInfoLevel       DisplayString,
   mgs360024fSyslogDetailedInfoTime        DisplayString,
   mgs360024fSyslogDetailedInfoMessage     DisplayString
}

mgs360024fSyslogDetailedInfoIndex OBJECT-TYPE
   SYNTAX      INTEGER (1..1024)
   MAX-ACCESS  not-accessible
   STATUS      current
   DESCRIPTION
       " "
   ::= { mgs360024fSyslogDetailedInfoEntry 1 }

mgs360024fSyslogDetailedInfoLevel OBJECT-TYPE
   SYNTAX      DisplayString
   MAX-ACCESS  read-only
   STATUS      current
   DESCRIPTION
       " "
   ::= { mgs360024fSyslogDetailedInfoEntry 2 }

mgs360024fSyslogDetailedInfoTime OBJECT-TYPE
   SYNTAX      DisplayString(SIZE (0..20))
   MAX-ACCESS  read-only
   STATUS      current
   DESCRIPTION
       " "
   ::= { mgs360024fSyslogDetailedInfoEntry 3 }

mgs360024fSyslogDetailedInfoMessage OBJECT-TYPE
   SYNTAX      DisplayString
   MAX-ACCESS  read-only
   STATUS      current
   DESCRIPTION
       " "
   ::= { mgs360024fSyslogDetailedInfoEntry 4 }


mgs360024fSnmp                                                OBJECT IDENTIFIER ::= { mgs360024fSystem 6 }

mgs360024fSnmpConf                                            OBJECT IDENTIFIER ::= { mgs360024fSnmp 1 }

mgs360024fGetCommunity OBJECT-TYPE
   SYNTAX       DisplayString
   MAX-ACCESS   read-write
   STATUS       current
   DESCRIPTION
       "Get/Set the get-community of the SNMP."
   ::= { mgs360024fSnmpConf 1 }

mgs360024fSetCommunityMode OBJECT-TYPE
   SYNTAX       INTEGER(0|1)
   MAX-ACCESS   read-write
   STATUS       current
   DESCRIPTION
       "Get/Set the set-community mode of the SNMP.
        default : 1, 0: disable, 1: enable. "
   ::= { mgs360024fSnmpConf 2 }

mgs360024fSetCommunity OBJECT-TYPE
   SYNTAX       DisplayString
   MAX-ACCESS   read-write
   STATUS       current
   DESCRIPTION
       "Get/Set the set-community of the SNMP."
   ::= { mgs360024fSnmpConf 3 }

mgs360024fTrapHostConfTable OBJECT-TYPE
   SYNTAX      SEQUENCE OF MGS360024FTrapHostConfEntry
   MAX-ACCESS  not-accessible
   STATUS      current
   DESCRIPTION
       "A list of trap host entry. The numbers of entries are given by the value of mgs360024fTrapHostConfNumber."
   ::= { mgs360024fSnmpConf 4 }

mgs360024fTrapHostConfEntry OBJECT-TYPE
   SYNTAX      MGS360024FTrapHostConfEntry
   MAX-ACCESS  not-accessible
   STATUS      current
   DESCRIPTION
       "This is the entry information for trap host."
   INDEX    { mgs360024fTrapHostConfIndex  }
   ::= { mgs360024fTrapHostConfTable 1 }

MGS360024FTrapHostConfEntry ::= SEQUENCE {
    mgs360024fTrapHostConfIndex             INTEGER,
    mgs360024fTrapHostConfVersion           INTEGER,
    mgs360024fTrapHostConfIPType            INTEGER,
    mgs360024fTrapHostConfIP                DisplayString,
    mgs360024fTrapHostConfPort              INTEGER,
    mgs360024fTrapHostConfCommunity         DisplayString,
    mgs360024fTrapHostConfSeverityLevel     INTEGER,
    mgs360024fTrapHostConfSecurityLevel     INTEGER,
    mgs360024fTrapHostConfAuthPtc           INTEGER,
    mgs360024fTrapHostConfAuthPassword      DisplayString,
    mgs360024fTrapHostConfPrivPtc           INTEGER,
    mgs360024fTrapHostConfPrivPassword      DisplayString,
    mgs360024fTrapHostConfCurrentMode       INTEGER
}

mgs360024fTrapHostConfIndex OBJECT-TYPE
   SYNTAX      INTEGER (1..6)
   MAX-ACCESS  not-accessible
   STATUS      current
   DESCRIPTION
       " The index of the trap host entry. "
   ::= { mgs360024fTrapHostConfEntry 1 }

mgs360024fTrapHostConfVersion OBJECT-TYPE
   SYNTAX       INTEGER(2..3)
   MAX-ACCESS   read-write
   STATUS       current
   DESCRIPTION
       "The version of the Trap PDU. Version : 2(SNMPv2c), 3(SNMPv3)"
   ::= { mgs360024fTrapHostConfEntry 2 }

mgs360024fTrapHostConfIPType OBJECT-TYPE
   SYNTAX       INTEGER(4|6)
   MAX-ACCESS   read-write
   STATUS       current
   DESCRIPTION
       "Server IP Type. Default: 4,
        4 : IPv4,
        6 : IPv6."
   ::= { mgs360024fTrapHostConfEntry 3 }

mgs360024fTrapHostConfIP OBJECT-TYPE
   SYNTAX       DisplayString
   MAX-ACCESS   read-write
   STATUS       current
   DESCRIPTION
       "This is the IP of the trap host."
   ::= { mgs360024fTrapHostConfEntry 4 }

mgs360024fTrapHostConfPort OBJECT-TYPE
   SYNTAX       INTEGER(1..65535)
   MAX-ACCESS   read-write
   STATUS       current
   DESCRIPTION
       "This is the receiving-port number of the trap host.
        range : 1 - 65535."
   ::= { mgs360024fTrapHostConfEntry 5 }

mgs360024fTrapHostConfCommunity OBJECT-TYPE
   SYNTAX       DisplayString (SIZE (1..32))
   MAX-ACCESS   read-write
   STATUS       current
   DESCRIPTION
       "The community/security name for the trap PDU."
   ::= { mgs360024fTrapHostConfEntry 6 }

mgs360024fTrapHostConfSeverityLevel	OBJECT-TYPE
   SYNTAX       INTEGER(0..7)
   MAX-ACCESS   read-write
   STATUS       current
   DESCRIPTION
       "The Severity Level.
        0 : Emerg, 1 : Alert, 2 : Crit, 3 : Error, 4 : Warning, 5 : Notice, 6 : Info, 7 : Debug."
	::= { mgs360024fTrapHostConfEntry 7 }

mgs360024fTrapHostConfSecurityLevel	OBJECT-TYPE
   SYNTAX       INTEGER(1..3)
   MAX-ACCESS   read-write
   STATUS       current
   DESCRIPTION
       "The Security Level, NoAuthNoPriv, AuthNoPriv, and AuthPriv.
        1 : NoAuthNoPriv, 2 : AuthNoPriv, 3 : AuthPriv.
        Privacy protocol will be configured as 'DES' automatically if security level is 3(AuthPriv)."
	::= { mgs360024fTrapHostConfEntry 8 }

mgs360024fTrapHostConfAuthPtc	OBJECT-TYPE
   SYNTAX       INTEGER(1..2)
   MAX-ACCESS   read-write
   STATUS       current
   DESCRIPTION
       "Authentication Protocol, there are SHA and MD5 supported presently.
        1 : MD5, 2 : SHA."
	::= { mgs360024fTrapHostConfEntry 9 }

mgs360024fTrapHostConfAuthPassword	OBJECT-TYPE
   SYNTAX      DisplayString
   MAX-ACCESS  read-write
   STATUS		current
   DESCRIPTION
       "Authentication Password, is used for authenticating. The return value is always '********'.
        If the authentication protocol is MD5, the length of password should be 8 ~ 32 characters.
        If the authentication protocol is SHA, the length of password should be 8 ~ 40 characters."
   ::= { mgs360024fTrapHostConfEntry 10 }

mgs360024fTrapHostConfPrivPtc	OBJECT-TYPE
   SYNTAX       INTEGER(1)
   MAX-ACCESS   read-write
   STATUS       current
   DESCRIPTION
       "This is the Privacy Protocol, which is used in AuthPriv. Only supports DES.
        An empty string will be returned if the security level is not 3(AuthPriv).
        1 : DES."
	::= { mgs360024fTrapHostConfEntry 11 }

mgs360024fTrapHostConfPrivPassword	OBJECT-TYPE
   SYNTAX       DisplayString
   MAX-ACCESS   read-write
   STATUS       current
   DESCRIPTION
       "The password is Privacy Key.  The return value is always '********'.  This Key
        must be more than 8 characters, and less than 32 characters."
   ::= { mgs360024fTrapHostConfEntry 12 }

mgs360024fTrapHostConfCurrentMode OBJECT-TYPE
   SYNTAX       INTEGER(0..2)
   MAX-ACCESS   read-write
   STATUS       current
   DESCRIPTION
       "0:Empty, 1:Active mode, 2:Edit mode, 3:Delete."
   ::= { mgs360024fTrapHostConfEntry 13 }


----------------------------------------------------------------------------------------------------

mgs360024fConfiguration                                         OBJECT IDENTIFIER ::= { mgs360024fProductId 2 }

mgs360024fPort                                                  OBJECT IDENTIFIER ::= { mgs360024fConfiguration 1 }

mgs360024fPortConfigurationTable OBJECT-TYPE
   SYNTAX      SEQUENCE OF MGS360024FPortConfigurationEntry
   MAX-ACCESS  not-accessible
   STATUS      current
   DESCRIPTION
       " Show port configurations. "
   ::= { mgs360024fPort 1 }

mgs360024fPortConfigurationEntry OBJECT-TYPE
   SYNTAX      MGS360024FPortConfigurationEntry
   MAX-ACCESS  not-accessible
   STATUS      current
   DESCRIPTION
       ""
   INDEX    { mgs360024fPortConfPort  }
   ::= { mgs360024fPortConfigurationTable 1 }

MGS360024FPortConfigurationEntry ::= SEQUENCE {
   mgs360024fPortConfPort                     INTEGER,
   mgs360024fPortConfPortMedia                DisplayString,
   mgs360024fPortConfLink                     DisplayString,
   mgs360024fPortConfCurrentSpeed             DisplayString,
   mgs360024fPortConfSpeed                    INTEGER,
   mgs360024fPortConfCurrentFlowControlRx     INTEGER,
   mgs360024fPortConfCurrentFlowControlTx     INTEGER,
   mgs360024fPortConfFlowControl              INTEGER,
   mgs360024fPortConfMaxFrameSize             INTEGER,
   mgs360024fPortConfExcessiveCollisionMode   INTEGER,
   mgs360024fPortConfPowerControl             INTEGER,
   mgs360024fPortConfDescription              DisplayString
}

mgs360024fPortConfPort OBJECT-TYPE
   SYNTAX      INTEGER (1..4095)
   MAX-ACCESS  not-accessible
   STATUS      current
   DESCRIPTION
       " port, range : 1 - port number. "
   ::= { mgs360024fPortConfigurationEntry 1 }

mgs360024fPortConfPortMedia OBJECT-TYPE
   SYNTAX      DisplayString(SIZE (1..4))
   MAX-ACCESS  read-only
   STATUS      current
   DESCRIPTION
       " Show port media. "
   ::= { mgs360024fPortConfigurationEntry 2 }

mgs360024fPortConfLink OBJECT-TYPE
   SYNTAX      DisplayString(SIZE (2..4))
   MAX-ACCESS  read-only
   STATUS      current
   DESCRIPTION
       " The current link state. "
   ::= { mgs360024fPortConfigurationEntry 3 }

mgs360024fPortConfCurrentSpeed OBJECT-TYPE
   SYNTAX      DisplayString(SIZE (6..12))
   MAX-ACCESS  read-only
   STATUS      current
   DESCRIPTION
       " The current link speed of the port. "
   ::= { mgs360024fPortConfigurationEntry 4 }

mgs360024fPortConfSpeed OBJECT-TYPE
   SYNTAX      INTEGER (0..11)
   MAX-ACCESS  read-write
   STATUS      current
   DESCRIPTION
       "default: 1,
        0: disable state,
        1: auto,
        2: 10 Half,
        3: 10 Full,
        4: 100 Half,
        5: 100 Full,
        6: 1G full,
        only 'Dual Media' port have 7-11 option.
        Dual Media port default: 7,
        7: SFP_Auto_AMS,
        8: 100FX_AMS,
        9: 1000X_AMS,
        10: 100FX,
        11: 1000X "
   ::= { mgs360024fPortConfigurationEntry 5 }

mgs360024fPortConfCurrentFlowControlRx OBJECT-TYPE
   SYNTAX      INTEGER (0|1)
   MAX-ACCESS  read-only
   STATUS      current
   DESCRIPTION
       "0: disable
        1: enable
        2: not support.  "
   ::= { mgs360024fPortConfigurationEntry 6 }

mgs360024fPortConfCurrentFlowControlTx OBJECT-TYPE
   SYNTAX      INTEGER (0|1)
   MAX-ACCESS  read-only
   STATUS      current
   DESCRIPTION
       "0: disable
        1: enable
        2: not support.  "
   ::= { mgs360024fPortConfigurationEntry 7 }

mgs360024fPortConfFlowControl OBJECT-TYPE
   SYNTAX      INTEGER (0|1)
   MAX-ACCESS  read-write
   STATUS      current
   DESCRIPTION
       "default: 0,
        0: disable
        1: enable
        2: not support. "
   ::= { mgs360024fPortConfigurationEntry 8 }

mgs360024fPortConfMaxFrameSize OBJECT-TYPE
   SYNTAX      INTEGER (1518..9600)
   MAX-ACCESS  read-write
   STATUS      current
   DESCRIPTION
       "default: 9600 , range : 1518 - 9600 "
   ::= { mgs360024fPortConfigurationEntry 9 }

mgs360024fPortConfExcessiveCollisionMode OBJECT-TYPE
   SYNTAX      INTEGER (0|1)
   MAX-ACCESS  read-write
   STATUS      current
   DESCRIPTION
       "default: 0,
        Excessive Collision Mode :
        0: Discard,
        1: Restart,
        2: not support.
       "
   ::= { mgs360024fPortConfigurationEntry 10 }

mgs360024fPortConfPowerControl OBJECT-TYPE
   SYNTAX      INTEGER (0..3)
   MAX-ACCESS  read-write
   STATUS      current
   DESCRIPTION
       "default: 0,
        PowerControl :
        0: disable,
        1: Actiphy,
        2: Dynamic (perfectReach),
        3: Enable,
        4: not support.
       "
   ::= { mgs360024fPortConfigurationEntry 11 }

mgs360024fPortConfDescription OBJECT-TYPE
   SYNTAX      DisplayString
   MAX-ACCESS  read-write
   STATUS      current
   DESCRIPTION
       " Interface specific description.
         Up to 47 characters describing this interface. "
   ::= { mgs360024fPortConfigurationEntry 12 }


mgs360024fPortTrafficStatisticsTable OBJECT-TYPE
   SYNTAX      SEQUENCE OF MGS360024FPortTrafficStatisticsEntry
   MAX-ACCESS  not-accessible
   STATUS      current
   DESCRIPTION
       " "
   ::= { mgs360024fPort 2 }

mgs360024fPortTrafficStatisticsEntry OBJECT-TYPE
   SYNTAX      MGS360024FPortTrafficStatisticsEntry
   MAX-ACCESS  not-accessible
   STATUS      current
   DESCRIPTION
       ""
   INDEX    { mgs360024fPortTrafficStatisticsPort  }
   ::= { mgs360024fPortTrafficStatisticsTable 1 }

MGS360024FPortTrafficStatisticsEntry ::= SEQUENCE {
   mgs360024fPortTrafficStatisticsPort          INTEGER,
   mgs360024fPortTrafficStatisticsClear         INTEGER,
   mgs360024fPortTrafficRxPackets               Counter64,
   mgs360024fPortTrafficRxOctets                Counter64,
   mgs360024fPortTrafficRxUnicast               Counter64,
   mgs360024fPortTrafficRxMulticast             Counter64,
   mgs360024fPortTrafficRxBroadcast             Counter64,
   mgs360024fPortTrafficRxPause                 Counter64,
   mgs360024fPortTrafficRx64Bytes               Counter64,
   mgs360024fPortTrafficRx65to127Bytes          Counter64,
   mgs360024fPortTrafficRx128to255Bytes         Counter64,
   mgs360024fPortTrafficRx256to511Bytes         Counter64,
   mgs360024fPortTrafficRx512to1023Bytes        Counter64,
   mgs360024fPortTrafficRx1024to1526Bytes       Counter64,
   mgs360024fPortTrafficRxExceecd1527Bytes      Counter64,
   mgs360024fPortTrafficRxQ0                    Counter64,
   mgs360024fPortTrafficRxQ1                    Counter64,
   mgs360024fPortTrafficRxQ2                    Counter64,
   mgs360024fPortTrafficRxQ3                    Counter64,
   mgs360024fPortTrafficRxQ4                    Counter64,
   mgs360024fPortTrafficRxQ5                    Counter64,
   mgs360024fPortTrafficRxQ6                    Counter64,
   mgs360024fPortTrafficRxQ7                    Counter64,
   mgs360024fPortTrafficRxDrops                 Counter64,
   mgs360024fPortTrafficRxCRCorAlignment        Counter64,
   mgs360024fPortTrafficRxUndersize             Counter64,
   mgs360024fPortTrafficRxOversize              Counter64,
   mgs360024fPortTrafficRxFragments             Counter64,
   mgs360024fPortTrafficRxJabber                Counter64,
   mgs360024fPortTrafficRxFiltered              Counter64,
   mgs360024fPortTrafficTxPackets               Counter64,
   mgs360024fPortTrafficTxOctets                Counter64,
   mgs360024fPortTrafficTxUnicast               Counter64,
   mgs360024fPortTrafficTxMulticast             Counter64,
   mgs360024fPortTrafficTxBroadcast             Counter64,
   mgs360024fPortTrafficTxPause                 Counter64,
   mgs360024fPortTrafficTx64Bytes               Counter64,
   mgs360024fPortTrafficTx65to127Bytes          Counter64,
   mgs360024fPortTrafficTx128to255Bytes         Counter64,
   mgs360024fPortTrafficTx256to511Bytes         Counter64,
   mgs360024fPortTrafficTx512to1023Bytes        Counter64,
   mgs360024fPortTrafficTx1024to1526Bytes       Counter64,
   mgs360024fPortTrafficTxExceecd1527Bytes      Counter64,
   mgs360024fPortTrafficTxQ0                    Counter64,
   mgs360024fPortTrafficTxQ1                    Counter64,
   mgs360024fPortTrafficTxQ2                    Counter64,
   mgs360024fPortTrafficTxQ3                    Counter64,
   mgs360024fPortTrafficTxQ4                    Counter64,
   mgs360024fPortTrafficTxQ5                    Counter64,
   mgs360024fPortTrafficTxQ6                    Counter64,
   mgs360024fPortTrafficTxQ7                    Counter64,
   mgs360024fPortTrafficTxDrops                 Counter64,
   mgs360024fPortTrafficTxLateOrExcColl         Counter64
}

mgs360024fPortTrafficStatisticsPort OBJECT-TYPE
   SYNTAX      INTEGER (1..4095)
   MAX-ACCESS  not-accessible
   STATUS      current
   DESCRIPTION
       " "
   ::= { mgs360024fPortTrafficStatisticsEntry 1 }

mgs360024fPortTrafficStatisticsClear OBJECT-TYPE
   SYNTAX      INTEGER(0|1)
   MAX-ACCESS  read-write
   STATUS      current
   DESCRIPTION
       " "
   ::= { mgs360024fPortTrafficStatisticsEntry 2 }

mgs360024fPortTrafficRxPackets OBJECT-TYPE
   SYNTAX      Counter64
   MAX-ACCESS  read-only
   STATUS      current
   DESCRIPTION
       " "
   ::= { mgs360024fPortTrafficStatisticsEntry 3 }

mgs360024fPortTrafficRxOctets OBJECT-TYPE
   SYNTAX      Counter64
   MAX-ACCESS  read-only
   STATUS      current
   DESCRIPTION
       " "
   ::= { mgs360024fPortTrafficStatisticsEntry 4 }

mgs360024fPortTrafficRxUnicast OBJECT-TYPE
   SYNTAX      Counter64
   MAX-ACCESS  read-only
   STATUS      current
   DESCRIPTION
       " "
   ::= { mgs360024fPortTrafficStatisticsEntry 5 }

mgs360024fPortTrafficRxMulticast OBJECT-TYPE
   SYNTAX      Counter64
   MAX-ACCESS  read-only
   STATUS      current
   DESCRIPTION
       " "
   ::= { mgs360024fPortTrafficStatisticsEntry 6 }

mgs360024fPortTrafficRxBroadcast OBJECT-TYPE
   SYNTAX      Counter64
   MAX-ACCESS  read-only
   STATUS      current
   DESCRIPTION
       " "
   ::= { mgs360024fPortTrafficStatisticsEntry 7 }

mgs360024fPortTrafficRxPause OBJECT-TYPE
   SYNTAX      Counter64
   MAX-ACCESS  read-only
   STATUS      current
   DESCRIPTION
       " "
   ::= { mgs360024fPortTrafficStatisticsEntry 8 }

mgs360024fPortTrafficRx64Bytes OBJECT-TYPE
   SYNTAX      Counter64
   MAX-ACCESS  read-only
   STATUS      current
   DESCRIPTION
       " "
   ::= { mgs360024fPortTrafficStatisticsEntry 9 }

mgs360024fPortTrafficRx65to127Bytes OBJECT-TYPE
   SYNTAX      Counter64
   MAX-ACCESS  read-only
   STATUS      current
   DESCRIPTION
       " "
   ::= { mgs360024fPortTrafficStatisticsEntry 10 }

mgs360024fPortTrafficRx128to255Bytes OBJECT-TYPE
   SYNTAX      Counter64
   MAX-ACCESS  read-only
   STATUS      current
   DESCRIPTION
       " "
   ::= { mgs360024fPortTrafficStatisticsEntry 11 }

mgs360024fPortTrafficRx256to511Bytes OBJECT-TYPE
   SYNTAX      Counter64
   MAX-ACCESS  read-only
   STATUS      current
   DESCRIPTION
       " "
   ::= { mgs360024fPortTrafficStatisticsEntry 12 }

mgs360024fPortTrafficRx512to1023Bytes OBJECT-TYPE
   SYNTAX      Counter64
   MAX-ACCESS  read-only
   STATUS      current
   DESCRIPTION
       " "
   ::= { mgs360024fPortTrafficStatisticsEntry 13 }

mgs360024fPortTrafficRx1024to1526Bytes OBJECT-TYPE
   SYNTAX      Counter64
   MAX-ACCESS  read-only
   STATUS      current
   DESCRIPTION
       " "
   ::= { mgs360024fPortTrafficStatisticsEntry 14 }

mgs360024fPortTrafficRxExceecd1527Bytes OBJECT-TYPE
   SYNTAX      Counter64
   MAX-ACCESS  read-only
   STATUS      current
   DESCRIPTION
       " "
   ::= { mgs360024fPortTrafficStatisticsEntry 15 }

mgs360024fPortTrafficRxQ0 OBJECT-TYPE
   SYNTAX      Counter64
   MAX-ACCESS  read-only
   STATUS      current
   DESCRIPTION
       " "
   ::= { mgs360024fPortTrafficStatisticsEntry 16 }

mgs360024fPortTrafficRxQ1 OBJECT-TYPE
   SYNTAX      Counter64
   MAX-ACCESS  read-only
   STATUS      current
   DESCRIPTION
       " "
   ::= { mgs360024fPortTrafficStatisticsEntry 17 }

mgs360024fPortTrafficRxQ2 OBJECT-TYPE
   SYNTAX      Counter64
   MAX-ACCESS  read-only
   STATUS      current
   DESCRIPTION
       " "
   ::= { mgs360024fPortTrafficStatisticsEntry 18 }

mgs360024fPortTrafficRxQ3 OBJECT-TYPE
   SYNTAX      Counter64
   MAX-ACCESS  read-only
   STATUS      current
   DESCRIPTION
       " "
   ::= { mgs360024fPortTrafficStatisticsEntry 19 }

mgs360024fPortTrafficRxQ4 OBJECT-TYPE
   SYNTAX      Counter64
   MAX-ACCESS  read-only
   STATUS      current
   DESCRIPTION
       " "
   ::= { mgs360024fPortTrafficStatisticsEntry 20 }

mgs360024fPortTrafficRxQ5 OBJECT-TYPE
   SYNTAX      Counter64
   MAX-ACCESS  read-only
   STATUS      current
   DESCRIPTION
       " "
   ::= { mgs360024fPortTrafficStatisticsEntry 21 }

mgs360024fPortTrafficRxQ6 OBJECT-TYPE
   SYNTAX      Counter64
   MAX-ACCESS  read-only
   STATUS      current
   DESCRIPTION
       " "
   ::= { mgs360024fPortTrafficStatisticsEntry 22 }

mgs360024fPortTrafficRxQ7 OBJECT-TYPE
   SYNTAX      Counter64
   MAX-ACCESS  read-only
   STATUS      current
   DESCRIPTION
       " "
   ::= { mgs360024fPortTrafficStatisticsEntry 23 }

mgs360024fPortTrafficRxDrops OBJECT-TYPE
   SYNTAX      Counter64
   MAX-ACCESS  read-only
   STATUS      current
   DESCRIPTION
       " "
   ::= { mgs360024fPortTrafficStatisticsEntry 24 }

mgs360024fPortTrafficRxCRCorAlignment OBJECT-TYPE
   SYNTAX      Counter64
   MAX-ACCESS  read-only
   STATUS      current
   DESCRIPTION
       " "
   ::= { mgs360024fPortTrafficStatisticsEntry 25 }

mgs360024fPortTrafficRxUndersize OBJECT-TYPE
   SYNTAX      Counter64
   MAX-ACCESS  read-only
   STATUS      current
   DESCRIPTION
       " "
   ::= { mgs360024fPortTrafficStatisticsEntry 26 }

mgs360024fPortTrafficRxOversize OBJECT-TYPE
   SYNTAX      Counter64
   MAX-ACCESS  read-only
   STATUS      current
   DESCRIPTION
       " "
   ::= { mgs360024fPortTrafficStatisticsEntry 27 }

mgs360024fPortTrafficRxFragments OBJECT-TYPE
   SYNTAX      Counter64
   MAX-ACCESS  read-only
   STATUS      current
   DESCRIPTION
       " "
   ::= { mgs360024fPortTrafficStatisticsEntry 28 }

mgs360024fPortTrafficRxJabber OBJECT-TYPE
   SYNTAX      Counter64
   MAX-ACCESS  read-only
   STATUS      current
   DESCRIPTION
       " "
   ::= { mgs360024fPortTrafficStatisticsEntry 29 }

mgs360024fPortTrafficRxFiltered OBJECT-TYPE
   SYNTAX      Counter64
   MAX-ACCESS  read-only
   STATUS      current
   DESCRIPTION
       " "
   ::= { mgs360024fPortTrafficStatisticsEntry 30 }

mgs360024fPortTrafficTxPackets OBJECT-TYPE
   SYNTAX      Counter64
   MAX-ACCESS  read-only
   STATUS      current
   DESCRIPTION
       " "
   ::= { mgs360024fPortTrafficStatisticsEntry 31 }

mgs360024fPortTrafficTxOctets OBJECT-TYPE
   SYNTAX      Counter64
   MAX-ACCESS  read-only
   STATUS      current
   DESCRIPTION
       " "
   ::= { mgs360024fPortTrafficStatisticsEntry 32 }

mgs360024fPortTrafficTxUnicast OBJECT-TYPE
   SYNTAX      Counter64
   MAX-ACCESS  read-only
   STATUS      current
   DESCRIPTION
       " "
   ::= { mgs360024fPortTrafficStatisticsEntry 33 }

mgs360024fPortTrafficTxMulticast OBJECT-TYPE
   SYNTAX      Counter64
   MAX-ACCESS  read-only
   STATUS      current
   DESCRIPTION
       " "
   ::= { mgs360024fPortTrafficStatisticsEntry 34 }

mgs360024fPortTrafficTxBroadcast OBJECT-TYPE
   SYNTAX      Counter64
   MAX-ACCESS  read-only
   STATUS      current
   DESCRIPTION
       " "
   ::= { mgs360024fPortTrafficStatisticsEntry 35 }

mgs360024fPortTrafficTxPause OBJECT-TYPE
   SYNTAX      Counter64
   MAX-ACCESS  read-only
   STATUS      current
   DESCRIPTION
       " "
   ::= { mgs360024fPortTrafficStatisticsEntry 36 }

mgs360024fPortTrafficTx64Bytes OBJECT-TYPE
   SYNTAX      Counter64
   MAX-ACCESS  read-only
   STATUS      current
   DESCRIPTION
       " "
   ::= { mgs360024fPortTrafficStatisticsEntry 37 }

mgs360024fPortTrafficTx65to127Bytes OBJECT-TYPE
   SYNTAX      Counter64
   MAX-ACCESS  read-only
   STATUS      current
   DESCRIPTION
       " "
   ::= { mgs360024fPortTrafficStatisticsEntry 38 }

mgs360024fPortTrafficTx128to255Bytes OBJECT-TYPE
   SYNTAX      Counter64
   MAX-ACCESS  read-only
   STATUS      current
   DESCRIPTION
       " "
   ::= { mgs360024fPortTrafficStatisticsEntry 39 }

mgs360024fPortTrafficTx256to511Bytes OBJECT-TYPE
   SYNTAX      Counter64
   MAX-ACCESS  read-only
   STATUS      current
   DESCRIPTION
       " "
   ::= { mgs360024fPortTrafficStatisticsEntry 40 }

mgs360024fPortTrafficTx512to1023Bytes OBJECT-TYPE
   SYNTAX      Counter64
   MAX-ACCESS  read-only
   STATUS      current
   DESCRIPTION
       " "
   ::= { mgs360024fPortTrafficStatisticsEntry 41 }

mgs360024fPortTrafficTx1024to1526Bytes OBJECT-TYPE
   SYNTAX      Counter64
   MAX-ACCESS  read-only
   STATUS      current
   DESCRIPTION
       " "
   ::= { mgs360024fPortTrafficStatisticsEntry 42 }

mgs360024fPortTrafficTxExceecd1527Bytes OBJECT-TYPE
   SYNTAX      Counter64
   MAX-ACCESS  read-only
   STATUS      current
   DESCRIPTION
       " "
   ::= { mgs360024fPortTrafficStatisticsEntry 43 }

mgs360024fPortTrafficTxQ0 OBJECT-TYPE
   SYNTAX      Counter64
   MAX-ACCESS  read-only
   STATUS      current
   DESCRIPTION
       " "
   ::= { mgs360024fPortTrafficStatisticsEntry 44 }

mgs360024fPortTrafficTxQ1 OBJECT-TYPE
   SYNTAX      Counter64
   MAX-ACCESS  read-only
   STATUS      current
   DESCRIPTION
       " "
   ::= { mgs360024fPortTrafficStatisticsEntry 45 }

mgs360024fPortTrafficTxQ2 OBJECT-TYPE
   SYNTAX      Counter64
   MAX-ACCESS  read-only
   STATUS      current
   DESCRIPTION
       " "
   ::= { mgs360024fPortTrafficStatisticsEntry 46 }

mgs360024fPortTrafficTxQ3 OBJECT-TYPE
   SYNTAX      Counter64
   MAX-ACCESS  read-only
   STATUS      current
   DESCRIPTION
       " "
   ::= { mgs360024fPortTrafficStatisticsEntry 47 }

mgs360024fPortTrafficTxQ4 OBJECT-TYPE
   SYNTAX      Counter64
   MAX-ACCESS  read-only
   STATUS      current
   DESCRIPTION
       " "
   ::= { mgs360024fPortTrafficStatisticsEntry 48 }

mgs360024fPortTrafficTxQ5 OBJECT-TYPE
   SYNTAX      Counter64
   MAX-ACCESS  read-only
   STATUS      current
   DESCRIPTION
       " "
   ::= { mgs360024fPortTrafficStatisticsEntry 49 }

mgs360024fPortTrafficTxQ6 OBJECT-TYPE
   SYNTAX      Counter64
   MAX-ACCESS  read-only
   STATUS      current
   DESCRIPTION
       " "
   ::= { mgs360024fPortTrafficStatisticsEntry 50 }


mgs360024fPortTrafficTxQ7 OBJECT-TYPE
   SYNTAX      Counter64
   MAX-ACCESS  read-only
   STATUS      current
   DESCRIPTION
       " "
   ::= { mgs360024fPortTrafficStatisticsEntry 51 }

mgs360024fPortTrafficTxDrops OBJECT-TYPE
   SYNTAX      Counter64
   MAX-ACCESS  read-only
   STATUS      current
   DESCRIPTION
       " "
   ::= { mgs360024fPortTrafficStatisticsEntry 52 }

mgs360024fPortTrafficTxLateOrExcColl OBJECT-TYPE
   SYNTAX      Counter64
   MAX-ACCESS  read-only
   STATUS      current
   DESCRIPTION
       " "
   ::= { mgs360024fPortTrafficStatisticsEntry 53 }


mgs360024fPortQoSStatistics                                     OBJECT IDENTIFIER ::= { mgs360024fPort 3 }

mgs360024fPortQoSStatisticsClear OBJECT-TYPE
   SYNTAX      INTEGER(0|1)
   MAX-ACCESS  read-only
   STATUS      current
   DESCRIPTION
       "default: 0
       0: none
       1: clear "
   ::= { mgs360024fPortQoSStatistics 1 }

mgs360024fPortQoSStatisticsTable OBJECT-TYPE
   SYNTAX      SEQUENCE OF MGS360024FPortQoSStatisticsEntry
   MAX-ACCESS  not-accessible
   STATUS      current
   DESCRIPTION
       " "
   ::= { mgs360024fPortQoSStatistics 2 }

mgs360024fPortQoSStatisticsEntry OBJECT-TYPE
   SYNTAX      MGS360024FPortQoSStatisticsEntry
   MAX-ACCESS  not-accessible
   STATUS      current
   DESCRIPTION
       ""
   INDEX    { mgs360024fPortQoSStatisticsPort  }
   ::= { mgs360024fPortQoSStatisticsTable 1 }

MGS360024FPortQoSStatisticsEntry ::= SEQUENCE {
   mgs360024fPortQoSStatisticsPort   INTEGER,
   mgs360024fPortQoSQ0Rx	            Counter64,
   mgs360024fPortQoSQ0Tx	            Counter64,
   mgs360024fPortQoSQ1Rx	            Counter64,
   mgs360024fPortQoSQ1Tx	            Counter64,
   mgs360024fPortQoSQ2Rx	            Counter64,
   mgs360024fPortQoSQ2Tx	            Counter64,
   mgs360024fPortQoSQ3Rx	            Counter64,
   mgs360024fPortQoSQ3Tx	            Counter64,
   mgs360024fPortQoSQ4Rx	            Counter64,
   mgs360024fPortQoSQ4Tx	            Counter64,
   mgs360024fPortQoSQ5Rx	            Counter64,
   mgs360024fPortQoSQ5Tx	            Counter64,
   mgs360024fPortQoSQ6Rx	            Counter64,
   mgs360024fPortQoSQ6Tx	            Counter64,
   mgs360024fPortQoSQ7Rx	            Counter64,
   mgs360024fPortQoSQ7Tx	            Counter64
}

mgs360024fPortQoSStatisticsPort OBJECT-TYPE
   SYNTAX      INTEGER (1..4095)
   MAX-ACCESS  not-accessible
   STATUS      current
   DESCRIPTION
       " "
   ::= { mgs360024fPortQoSStatisticsEntry 1 }

mgs360024fPortQoSQ0Rx OBJECT-TYPE
   SYNTAX      Counter64
   MAX-ACCESS  read-only
   STATUS      current
   DESCRIPTION
       " "
   ::= { mgs360024fPortQoSStatisticsEntry 2 }

mgs360024fPortQoSQ0Tx OBJECT-TYPE
   SYNTAX      Counter64
   MAX-ACCESS  read-only
   STATUS      current
   DESCRIPTION
       " "
   ::= { mgs360024fPortQoSStatisticsEntry 3 }

mgs360024fPortQoSQ1Rx OBJECT-TYPE
   SYNTAX      Counter64
   MAX-ACCESS  read-only
   STATUS      current
   DESCRIPTION
       " "
   ::= { mgs360024fPortQoSStatisticsEntry 4 }

mgs360024fPortQoSQ1Tx OBJECT-TYPE
   SYNTAX      Counter64
   MAX-ACCESS  read-only
   STATUS      current
   DESCRIPTION
       " "
   ::= { mgs360024fPortQoSStatisticsEntry 5 }

mgs360024fPortQoSQ2Rx OBJECT-TYPE
   SYNTAX      Counter64
   MAX-ACCESS  read-only
   STATUS      current
   DESCRIPTION
       " "
   ::= { mgs360024fPortQoSStatisticsEntry 6 }

mgs360024fPortQoSQ2Tx OBJECT-TYPE
   SYNTAX      Counter64
   MAX-ACCESS  read-only
   STATUS      current
   DESCRIPTION
       " "
   ::= { mgs360024fPortQoSStatisticsEntry 7 }

mgs360024fPortQoSQ3Rx OBJECT-TYPE
   SYNTAX      Counter64
   MAX-ACCESS  read-only
   STATUS      current
   DESCRIPTION
       " "
   ::= { mgs360024fPortQoSStatisticsEntry 8 }

mgs360024fPortQoSQ3Tx OBJECT-TYPE
   SYNTAX      Counter64
   MAX-ACCESS  read-only
   STATUS      current
   DESCRIPTION
       " "
   ::= { mgs360024fPortQoSStatisticsEntry 9 }

mgs360024fPortQoSQ4Rx OBJECT-TYPE
   SYNTAX      Counter64
   MAX-ACCESS  read-only
   STATUS      current
   DESCRIPTION
       " "
   ::= { mgs360024fPortQoSStatisticsEntry 10 }

mgs360024fPortQoSQ4Tx OBJECT-TYPE
   SYNTAX      Counter64
   MAX-ACCESS  read-only
   STATUS      current
   DESCRIPTION
       " "
   ::= { mgs360024fPortQoSStatisticsEntry 11 }

mgs360024fPortQoSQ5Rx OBJECT-TYPE
   SYNTAX      Counter64
   MAX-ACCESS  read-only
   STATUS      current
   DESCRIPTION
       " "
   ::= { mgs360024fPortQoSStatisticsEntry 12 }

mgs360024fPortQoSQ5Tx OBJECT-TYPE
   SYNTAX      Counter64
   MAX-ACCESS  read-only
   STATUS      current
   DESCRIPTION
       " "
   ::= { mgs360024fPortQoSStatisticsEntry 13 }

mgs360024fPortQoSQ6Rx OBJECT-TYPE
   SYNTAX      Counter64
   MAX-ACCESS  read-only
   STATUS      current
   DESCRIPTION
       " "
   ::= { mgs360024fPortQoSStatisticsEntry 14 }

mgs360024fPortQoSQ6Tx OBJECT-TYPE
   SYNTAX      Counter64
   MAX-ACCESS  read-only
   STATUS      current
   DESCRIPTION
       " "
   ::= { mgs360024fPortQoSStatisticsEntry 15 }

mgs360024fPortQoSQ7Rx OBJECT-TYPE
   SYNTAX      Counter64
   MAX-ACCESS  read-only
   STATUS      current
   DESCRIPTION
       " "
   ::= { mgs360024fPortQoSStatisticsEntry 16 }

mgs360024fPortQoSQ7Tx OBJECT-TYPE
   SYNTAX      Counter64
   MAX-ACCESS  read-only
   STATUS      current
   DESCRIPTION
       " "
   ::= { mgs360024fPortQoSStatisticsEntry 17 }

mgs360024fSFPInfoTable OBJECT-TYPE
   SYNTAX      SEQUENCE OF MGS360024FSFPInfoEntry
   MAX-ACCESS  not-accessible
   STATUS      current
   DESCRIPTION
       " "
   ::= { mgs360024fPort 4 }

mgs360024fSFPInfoEntry OBJECT-TYPE
   SYNTAX      MGS360024FSFPInfoEntry
   MAX-ACCESS  not-accessible
   STATUS      current
   DESCRIPTION
       ""
   INDEX    { mgs360024fSFPInfoIndex }
   ::= { mgs360024fSFPInfoTable 1 }

MGS360024FSFPInfoEntry ::= SEQUENCE {
   mgs360024fSFPInfoIndex               INTEGER,
   mgs360024fSFPInfoPort                DisplayString,
   mgs360024fSFPConnectorType           DisplayString,
   mgs360024fSFPFiberType               DisplayString,
   mgs360024fSFPTxCentralWavelength     DisplayString,
   mgs360024fSFPBaudRate                DisplayString,
   mgs360024fSFPVendorOUI               DisplayString,
   mgs360024fSFPVendorName              DisplayString,
   mgs360024fSFPVendorPN                DisplayString,
   mgs360024fSFPVendorRev               DisplayString,
   mgs360024fSFPVendorSN                DisplayString,
   mgs360024fSFPDateCode                DisplayString,
   mgs360024fSFPTemperature             DisplayString,
   mgs360024fSFPVcc                     DisplayString,
   mgs360024fSFPMon1Bias                DisplayString,
   mgs360024fSFPMon2TxPWR               DisplayString,
   mgs360024fSFPMon3RxPWR               DisplayString
}

mgs360024fSFPInfoIndex OBJECT-TYPE
   SYNTAX      INTEGER (1..4095)
   MAX-ACCESS  not-accessible
   STATUS      current
   DESCRIPTION
       " "
   ::= { mgs360024fSFPInfoEntry 1 }

mgs360024fSFPInfoPort OBJECT-TYPE
   SYNTAX      DisplayString
   MAX-ACCESS  read-only
   STATUS      current
   DESCRIPTION
       " "
   ::= { mgs360024fSFPInfoEntry 2 }

mgs360024fSFPConnectorType OBJECT-TYPE
   SYNTAX      DisplayString
   MAX-ACCESS  read-only
   STATUS      current
   DESCRIPTION
       " "
   ::= { mgs360024fSFPInfoEntry 3 }

mgs360024fSFPFiberType OBJECT-TYPE
   SYNTAX      DisplayString
   MAX-ACCESS  read-only
   STATUS      current
   DESCRIPTION
       " "
   ::= { mgs360024fSFPInfoEntry 4 }

mgs360024fSFPTxCentralWavelength OBJECT-TYPE
   SYNTAX      DisplayString
   MAX-ACCESS  read-only
   STATUS      current
   DESCRIPTION
       " "
   ::= { mgs360024fSFPInfoEntry 5 }

mgs360024fSFPBaudRate OBJECT-TYPE
   SYNTAX      DisplayString
   MAX-ACCESS  read-only
   STATUS      current
   DESCRIPTION
       " "
   ::= { mgs360024fSFPInfoEntry 6 }

mgs360024fSFPVendorOUI OBJECT-TYPE
   SYNTAX      DisplayString
   MAX-ACCESS  read-only
   STATUS      current
   DESCRIPTION
       " "
   ::= { mgs360024fSFPInfoEntry 7 }

mgs360024fSFPVendorName OBJECT-TYPE
   SYNTAX      DisplayString
   MAX-ACCESS  read-only
   STATUS      current
   DESCRIPTION
       " "
   ::= { mgs360024fSFPInfoEntry 8 }

mgs360024fSFPVendorPN OBJECT-TYPE
   SYNTAX      DisplayString
   MAX-ACCESS  read-only
   STATUS      current
   DESCRIPTION
       " "
   ::= { mgs360024fSFPInfoEntry 9 }

mgs360024fSFPVendorRev OBJECT-TYPE
   SYNTAX      DisplayString
   MAX-ACCESS  read-only
   STATUS      current
   DESCRIPTION
       " "
   ::= { mgs360024fSFPInfoEntry 10 }

mgs360024fSFPVendorSN OBJECT-TYPE
   SYNTAX      DisplayString
   MAX-ACCESS  read-only
   STATUS      current
   DESCRIPTION
       " "
   ::= { mgs360024fSFPInfoEntry 11 }

mgs360024fSFPDateCode OBJECT-TYPE
   SYNTAX      DisplayString
   MAX-ACCESS  read-only
   STATUS      current
   DESCRIPTION
       " "
   ::= { mgs360024fSFPInfoEntry 12 }

mgs360024fSFPTemperature OBJECT-TYPE
   SYNTAX      DisplayString
   MAX-ACCESS  read-only
   STATUS      current
   DESCRIPTION
       " "
   ::= { mgs360024fSFPInfoEntry 13 }

mgs360024fSFPVcc OBJECT-TYPE
   SYNTAX      DisplayString
   MAX-ACCESS  read-only
   STATUS      current
   DESCRIPTION
       " "
   ::= { mgs360024fSFPInfoEntry 14 }

mgs360024fSFPMon1Bias OBJECT-TYPE
   SYNTAX      DisplayString
   MAX-ACCESS  read-only
   STATUS      current
   DESCRIPTION
       " "
   ::= { mgs360024fSFPInfoEntry 15 }

mgs360024fSFPMon2TxPWR OBJECT-TYPE
   SYNTAX      DisplayString
   MAX-ACCESS  read-only
   STATUS      current
   DESCRIPTION
       " "
   ::= { mgs360024fSFPInfoEntry 16 }

mgs360024fSFPMon3RxPWR OBJECT-TYPE
   SYNTAX      DisplayString
   MAX-ACCESS  read-only
   STATUS      current
   DESCRIPTION
       " "
   ::= { mgs360024fSFPInfoEntry 17 }


mgs360024fGARP                                                   OBJECT IDENTIFIER ::= { mgs360024fConfiguration 3 }

mgs360024fGARPConfTable OBJECT-TYPE
   SYNTAX      SEQUENCE OF MGS360024FGARPConfEntry
   MAX-ACCESS  not-accessible
   STATUS      current
   DESCRIPTION
       " "
   ::= { mgs360024fGARP 1 }

mgs360024fGARPConfEntry OBJECT-TYPE
   SYNTAX      MGS360024FGARPConfEntry
   MAX-ACCESS  not-accessible
   STATUS      current
   DESCRIPTION
       ""
   INDEX    { mgs360024fGARPConfPort  }
   ::= { mgs360024fGARPConfTable 1 }

MGS360024FGARPConfEntry ::= SEQUENCE {
   mgs360024fGARPConfPort            INTEGER,
   mgs360024fGARPJoinTimer           INTEGER,
   mgs360024fGARPLeaveTimer          INTEGER,
   mgs360024fGARPLeaveAllTimer		INTEGER,
   mgs360024fGARPApplicantion		INTEGER,
   mgs360024fGARPAttributeType		INTEGER,
   mgs360024fGARPApplicant		    INTEGER
}

mgs360024fGARPConfPort OBJECT-TYPE
   SYNTAX      INTEGER (1..4095)
   MAX-ACCESS  not-accessible
   STATUS      current
   DESCRIPTION
       " "
   ::= { mgs360024fGARPConfEntry 1 }

mgs360024fGARPJoinTimer OBJECT-TYPE
   SYNTAX      INTEGER (200..1000)
   MAX-ACCESS  read-write
   STATUS      current
   DESCRIPTION
       "default: 200, range : 200 - 1000 "
   ::= { mgs360024fGARPConfEntry 2 }

mgs360024fGARPLeaveTimer OBJECT-TYPE
   SYNTAX      INTEGER (600..3000)
   MAX-ACCESS  read-write
   STATUS      current
   DESCRIPTION
       "default: 600 , range : 600 - 3000"
   ::= { mgs360024fGARPConfEntry 3 }

mgs360024fGARPLeaveAllTimer OBJECT-TYPE
   SYNTAX      INTEGER (10000..50000)
   MAX-ACCESS  read-write
   STATUS      current
   DESCRIPTION
       "default: 10000, range : 10000 - 50000 "
   ::= { mgs360024fGARPConfEntry 4 }

mgs360024fGARPApplicantion OBJECT-TYPE
   SYNTAX      INTEGER(1)
   MAX-ACCESS  read-write
   STATUS      current
   DESCRIPTION
       "default: 1
       1: GVRP"
   ::= { mgs360024fGARPConfEntry 5 }

mgs360024fGARPAttributeType OBJECT-TYPE
   SYNTAX      INTEGER(1)
   MAX-ACCESS  read-write
   STATUS      current
   DESCRIPTION
       "default: 1
       1: VLAN"
   ::= { mgs360024fGARPConfEntry 6 }

mgs360024fGARPApplicant OBJECT-TYPE
   SYNTAX      INTEGER(0|1)
   MAX-ACCESS  read-write
   STATUS      current
   DESCRIPTION
       "default: 0
       0: normal-participant
       1: non-participant"
   ::= { mgs360024fGARPConfEntry 7 }

mgs360024fGARPStatisticsTable OBJECT-TYPE
   SYNTAX      SEQUENCE OF MGS360024FGARPStatisticsEntry
   MAX-ACCESS  not-accessible
   STATUS      current
   DESCRIPTION
       " Show the basic GARP port statistics. "
   ::= { mgs360024fGARP 2 }

mgs360024fGARPStatisticsEntry OBJECT-TYPE
   SYNTAX      MGS360024FGARPStatisticsEntry
   MAX-ACCESS  not-accessible
   STATUS      current
   DESCRIPTION
       ""
   INDEX    { mgs360024fGARPStatisticsPort  }
   ::= { mgs360024fGARPStatisticsTable 1 }

MGS360024FGARPStatisticsEntry ::= SEQUENCE {
   mgs360024fGARPStatisticsPort          INTEGER,
   mgs360024fGARPStatisticsPeerMAC		DisplayString,
   mgs360024fGARPStatisticsFailedCount   Counter32
}

mgs360024fGARPStatisticsPort OBJECT-TYPE
   SYNTAX      INTEGER (1..4095)
   MAX-ACCESS  not-accessible
   STATUS      current
   DESCRIPTION
       " port, range : 1 - port number. "
   ::= { mgs360024fGARPStatisticsEntry 1 }

mgs360024fGARPStatisticsPeerMAC OBJECT-TYPE
   SYNTAX      DisplayString
   MAX-ACCESS  read-only
   STATUS      current
   DESCRIPTION
       " Peer MAC is MAC address of the neighbour Switch from with GARP frame is received.  "
   ::= { mgs360024fGARPStatisticsEntry 2 }

mgs360024fGARPStatisticsFailedCount OBJECT-TYPE
   SYNTAX      Counter32
   MAX-ACCESS  read-only
   STATUS      current
   DESCRIPTION
       " explain Failed count here. "
   ::= { mgs360024fGARPStatisticsEntry 3 }

mgs360024fGVRP                                                   OBJECT IDENTIFIER ::= { mgs360024fConfiguration 4 }

mgs360024fGVRPConf                                                   OBJECT IDENTIFIER ::= { mgs360024fGVRP 1 }

mgs360024fGVRPMode OBJECT-TYPE
   SYNTAX      INTEGER(0|1)
   MAX-ACCESS  read-write
   STATUS      current
   DESCRIPTION
       "default: 0,
        0: disable,
        1: enable. "
   ::= { mgs360024fGVRPConf 1 }

mgs360024fGVRPConfTable OBJECT-TYPE
   SYNTAX      SEQUENCE OF MGS360024FGVRPConfEntry
   MAX-ACCESS  not-accessible
   STATUS      current
   DESCRIPTION
       " "
   ::= { mgs360024fGVRPConf 2 }

mgs360024fGVRPConfEntry OBJECT-TYPE
   SYNTAX      MGS360024FGVRPConfEntry
   MAX-ACCESS  not-accessible
   STATUS      current
   DESCRIPTION
       ""
   INDEX    { mgs360024fGVRPConfPort  }
   ::= { mgs360024fGVRPConfTable 1 }

MGS360024FGVRPConfEntry ::= SEQUENCE {
   mgs360024fGVRPConfPort        INTEGER,
   mgs360024fGVRPConfPortMode	INTEGER,
   mgs360024fGVRPConfPortRRole	INTEGER
}

mgs360024fGVRPConfPort OBJECT-TYPE
   SYNTAX      INTEGER (1..4095)
   MAX-ACCESS  not-accessible
   STATUS      current
   DESCRIPTION
       " "
   ::= { mgs360024fGVRPConfEntry 1 }

mgs360024fGVRPConfPortMode OBJECT-TYPE
   SYNTAX      INTEGER(0|1)
   MAX-ACCESS  read-write
   STATUS      current
   DESCRIPTION
       "default: 0
       1: enable
       0: disable"
   ::= { mgs360024fGVRPConfEntry 2 }

mgs360024fGVRPConfPortRRole OBJECT-TYPE
   SYNTAX      INTEGER(0|1)
   MAX-ACCESS  read-write
   STATUS      current
   DESCRIPTION
       "default: 0
       1: enable
       0: disable"
   ::= { mgs360024fGVRPConfEntry 3 }

mgs360024fGVRPStatisticsTable OBJECT-TYPE
   SYNTAX      SEQUENCE OF MGS360024FGVRPStatisticsEntry
   MAX-ACCESS  not-accessible
   STATUS      current
   DESCRIPTION
       " "
   ::= { mgs360024fGVRP 2 }

mgs360024fGVRPStatisticsEntry OBJECT-TYPE
   SYNTAX      MGS360024FGVRPStatisticsEntry
   MAX-ACCESS  not-accessible
   STATUS      current
   DESCRIPTION
       ""
   INDEX    { mgs360024fGVRPStatisticsPort  }
   ::= { mgs360024fGVRPStatisticsTable 1 }

MGS360024FGVRPStatisticsEntry ::= SEQUENCE {
   mgs360024fGVRPStatisticsPort          INTEGER,
   mgs360024fGVRPStatisticsJoinTxCnt		Counter32,
   mgs360024fGVRPStatisticsLeaveTxCnt    Counter32
}

mgs360024fGVRPStatisticsPort OBJECT-TYPE
   SYNTAX      INTEGER (1..4095)
   MAX-ACCESS  not-accessible
   STATUS      current
   DESCRIPTION
       " "
   ::= { mgs360024fGVRPStatisticsEntry 1 }

mgs360024fGVRPStatisticsJoinTxCnt OBJECT-TYPE
   SYNTAX      Counter32
   MAX-ACCESS  read-only
   STATUS      current
   DESCRIPTION
       ""
   ::= { mgs360024fGVRPStatisticsEntry 2 }

mgs360024fGVRPStatisticsLeaveTxCnt OBJECT-TYPE
   SYNTAX      Counter32
   MAX-ACCESS  read-only
   STATUS      current
   DESCRIPTION
       ""
   ::= { mgs360024fGVRPStatisticsEntry 3 }

mgs360024fThermalProtection                                     OBJECT IDENTIFIER ::= { mgs360024fConfiguration 5 }

mgs360024fPriority0Temperature OBJECT-TYPE
   SYNTAX      INTEGER(0..255)
   MAX-ACCESS  read-write
   STATUS      current
   DESCRIPTION
       "default: 255, range : 0 - 255 "
   ::= { mgs360024fThermalProtection 1 }

mgs360024fPriority1Temperature OBJECT-TYPE
   SYNTAX      INTEGER(0..255)
   MAX-ACCESS  read-write
   STATUS      current
   DESCRIPTION
       "default: 255, range : 0 - 255 "
   ::= { mgs360024fThermalProtection 2 }

mgs360024fPriority2Temperature OBJECT-TYPE
   SYNTAX      INTEGER(0..255)
   MAX-ACCESS  read-write
   STATUS      current
   DESCRIPTION
       "default: 255, range : 0 - 255 "
   ::= { mgs360024fThermalProtection 3 }

mgs360024fPriority3Temperature OBJECT-TYPE
   SYNTAX      INTEGER(0..255)
   MAX-ACCESS  read-write
   STATUS      current
   DESCRIPTION
       "default: 255, range : 0 - 255 "
   ::= { mgs360024fThermalProtection 4 }

mgs360024fThermalProtectionTable OBJECT-TYPE
   SYNTAX      SEQUENCE OF MGS360024FThermalProtectionEntry
   MAX-ACCESS  not-accessible
   STATUS      current
   DESCRIPTION
       " "
   ::= { mgs360024fThermalProtection 5 }

mgs360024fThermalProtectionEntry OBJECT-TYPE
   SYNTAX      MGS360024FThermalProtectionEntry
   MAX-ACCESS  not-accessible
   STATUS      current
   DESCRIPTION
       ""
   INDEX    { mgs360024fThermalProtectionPort  }
   ::= { mgs360024fThermalProtectionTable 1 }

MGS360024FThermalProtectionEntry ::= SEQUENCE {
   mgs360024fThermalProtectionPort               INTEGER,
   mgs360024fThermalProtectionPortTemperature    INTEGER,
   mgs360024fThermalProtectionPortPriority		INTEGER,
   mgs360024fThermalProtectionPortStatus         DisplayString
}

mgs360024fThermalProtectionPort OBJECT-TYPE
   SYNTAX      INTEGER (1..4095)
   MAX-ACCESS  not-accessible
   STATUS      current
   DESCRIPTION
       " "
   ::= { mgs360024fThermalProtectionEntry 1 }

mgs360024fThermalProtectionPortTemperature OBJECT-TYPE
   SYNTAX      INTEGER(0..255)
   MAX-ACCESS  read-only
   STATUS      current
   DESCRIPTION
       ""
   ::= { mgs360024fThermalProtectionEntry 2 }

mgs360024fThermalProtectionPortPriority OBJECT-TYPE
   SYNTAX      INTEGER(0..3)
   MAX-ACCESS  read-write
   STATUS      current
   DESCRIPTION
       "default: 0, range : 0 - 3"
   ::= { mgs360024fThermalProtectionEntry 3 }

mgs360024fThermalProtectionPortStatus OBJECT-TYPE
   SYNTAX      DisplayString
   MAX-ACCESS  read-only
   STATUS      current
   DESCRIPTION
       ""
   ::= { mgs360024fThermalProtectionEntry 4 }


mgs360024fMirroring                                             OBJECT IDENTIFIER ::= { mgs360024fConfiguration 6 }

mgs360024fPortToMirrorOn OBJECT-TYPE
   SYNTAX      INTEGER(0..10)
   MAX-ACCESS  read-write
   STATUS      current
   DESCRIPTION
       "default: 0
        0: disable,
        range : 1 - port number. "
   ::= { mgs360024fMirroring 1 }

mgs360024fMirrorTable OBJECT-TYPE
   SYNTAX      SEQUENCE OF MGS360024FMirrorEntry
   MAX-ACCESS  not-accessible
   STATUS      current
   DESCRIPTION
       " "
   ::= { mgs360024fMirroring 2 }

mgs360024fMirrorEntry OBJECT-TYPE
   SYNTAX      MGS360024FMirrorEntry
   MAX-ACCESS  not-accessible
   STATUS      current
   DESCRIPTION
       ""
   INDEX    { mgs360024fMirrorPort  }
   ::= { mgs360024fMirrorTable 1 }

MGS360024FMirrorEntry ::= SEQUENCE {
   mgs360024fMirrorPort		INTEGER,
   mgs360024fMirrorMode		INTEGER
}

mgs360024fMirrorPort OBJECT-TYPE
   SYNTAX      INTEGER (1..4095)
   MAX-ACCESS  not-accessible
   STATUS      current
   DESCRIPTION
       " "
   ::= { mgs360024fMirrorEntry 1 }

mgs360024fMirrorMode OBJECT-TYPE
   SYNTAX      INTEGER(0..3)
   MAX-ACCESS  read-write
   STATUS      current
   DESCRIPTION
       "default: 0
       0: disable
       1: enable
       2: rx only
       3: tx only
       Setting Tx mirroring for analyzer port has no effect. Tx mirroring ignored"
   ::= { mgs360024fMirrorEntry 2 }

mgs360024fTrapEventSeverity                                             OBJECT IDENTIFIER ::= { mgs360024fConfiguration 7 }

mgs360024fTrapEventSeverityACL OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 1 }

mgs360024fTrapEventSeverityACLLog OBJECT-TYPE
   SYNTAX      INTEGER (0..7)
   MAX-ACCESS  read-write
   STATUS      current
   DESCRIPTION
       " default:  7(Debug)
        0: Emergency
        1: Alert
        2: Critical
        3: Error
        4: Warning
        5: Notice
        6: Info
        7: Debug"
   ::= { mgs360024fTrapEventSeverity 2 }

mgs360024fTrapEventSeverityAccessMgmt OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 3 }

mgs360024fTrapEventSeverityAuthFailed OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { mgs360024fTrapEventSeverity 4 }

mgs360024fTrapEventSeverityColdStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { mgs360024fTrapEventSeverity 5 }

mgs360024fTrapEventSeverityConfigInfo OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 6 }

mgs360024fTrapEventSeverityFirmwareUpgrade OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 7 }

mgs360024fTrapEventSeverityImportExport OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 8 }

mgs360024fTrapEventSeverityLACP OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 9 }

mgs360024fTrapEventSeverityLinkStatus OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { mgs360024fTrapEventSeverity 10 }

mgs360024fTrapEventSeverityLogin OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 11 }

mgs360024fTrapEventSeverityLogout OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 12 }

mgs360024fTrapEventSeverityLoopProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 13 }

mgs360024fTrapEventSeverityMgmtIPChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 14 }

mgs360024fTrapEventSeverityModuleChange OBJECT-TYPE
   SYNTAX      INTEGER (0..7)
   MAX-ACCESS  read-write
   STATUS      current
   DESCRIPTION
       " default:  5(Notice)
        0: Emergency
        1: Alert
        2: Critical
        3: Error
        4: Warning
        5: Notice
        6: Info
        7: Debug"
   ::= { mgs360024fTrapEventSeverity 15 }

mgs360024fTrapEventSeverityNAS OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 16 }

mgs360024fTrapEventSeverityPasswdChange OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 17 }

mgs360024fTrapEventSeverityPortSecurity OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 18 }

mgs360024fTrapEventSeverityThermalProtect OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 19 }

mgs360024fTrapEventSeverityVLAN OBJECT-TYPE
   SYNTAX      INTEGER (0..7)
   MAX-ACCESS  read-write
   STATUS      current
   DESCRIPTION
       " default:  6(Info)
        0: Emergency
        1: Alert
        2: Critical
        3: Error
        4: Warning
        5: Notice
        6: Info
        7: Debug"
   ::= { mgs360024fTrapEventSeverity 20 }

mgs360024fTrapEventSeverityWarmStart OBJECT-TYPE
   SYNTAX      INTEGER (0..7)
   MAX-ACCESS  read-write
   STATUS      current
   DESCRIPTION
       " default:  4(Warning)
        0: Emergency
        1: Alert
        2: Critical
        3: Error
        4: Warning
        5: Notice
        6: Info
        7: Debug"
   ::= { mgs360024fTrapEventSeverity 21 }


mgs360024fSMTP                                             OBJECT IDENTIFIER ::= { mgs360024fConfiguration 8 }

mgs360024fSMTPMailServer OBJECT-TYPE
   SYNTAX      DisplayString
   MAX-ACCESS  read-write
   STATUS      current
   DESCRIPTION
       " Up to 47 characters describing email server. "
   ::= { mgs360024fSMTP 1 }

mgs360024fSMTPUserName OBJECT-TYPE
   SYNTAX      DisplayString
   MAX-ACCESS  read-write
   STATUS      current
   DESCRIPTION
       " Up to 47 characters describing user name. "
   ::= { mgs360024fSMTP 2 }

mgs360024fSMTPPassword OBJECT-TYPE
   SYNTAX      DisplayString
   MAX-ACCESS  read-write
   STATUS      current
   DESCRIPTION
       " Up to 47 characters describing password. "
   ::= { mgs360024fSMTP 3 }

mgs360024fSMTPServeriryLevel OBJECT-TYPE
   SYNTAX      INTEGER(0..7)
   MAX-ACCESS  read-write
   STATUS      current
   DESCRIPTION
       "default: 6
       0: Emergency
       1: Alert
       2: Critical
       3: Error
       4: Warning
       5: Notice
       6: Info
       7: Debug"
   ::= { mgs360024fSMTP 4 }

mgs360024fSMTPSender OBJECT-TYPE
   SYNTAX      DisplayString
   MAX-ACCESS  read-write
   STATUS      current
   DESCRIPTION
       " Up to 47 characters describing sender. "
   ::= { mgs360024fSMTP 5 }

mgs360024fSMTPReturnPath OBJECT-TYPE
   SYNTAX      DisplayString
   MAX-ACCESS  read-write
   STATUS      current
   DESCRIPTION
       " Up to 47 characters describing return path. "
   ::= { mgs360024fSMTP 6 }

mgs360024fSMTPEmailAddress1 OBJECT-TYPE
   SYNTAX      DisplayString
   MAX-ACCESS  read-write
   STATUS      current
   DESCRIPTION
       " Up to 47 characters describing mail address. "
   ::= { mgs360024fSMTP 7 }

mgs360024fSMTPEmailAddress2 OBJECT-TYPE
   SYNTAX      DisplayString
   MAX-ACCESS  read-write
   STATUS      current
   DESCRIPTION
       " Up to 47 characters describing mail address. "
   ::= { mgs360024fSMTP 8 }

mgs360024fSMTPEmailAddress3 OBJECT-TYPE
   SYNTAX      DisplayString
   MAX-ACCESS  read-write
   STATUS      current
   DESCRIPTION
       " Up to 47 characters describing mail address. "
   ::= { mgs360024fSMTP 9 }

mgs360024fSMTPEmailAddress4 OBJECT-TYPE
   SYNTAX      DisplayString
   MAX-ACCESS  read-write
   STATUS      current
   DESCRIPTION
       " Up to 47 characters describing mail address. "
   ::= { mgs360024fSMTP 10 }

mgs360024fSMTPEmailAddress5 OBJECT-TYPE
   SYNTAX      DisplayString
   MAX-ACCESS  read-write
   STATUS      current
   DESCRIPTION
       " Up to 47 characters describing mail address. "
   ::= { mgs360024fSMTP 11 }

mgs360024fSMTPEmailAddress6 OBJECT-TYPE
   SYNTAX      DisplayString
   MAX-ACCESS  read-write
   STATUS      current
   DESCRIPTION
       " Up to 47 characters describing mail address. "
   ::= { mgs360024fSMTP 12 }


mgs360024fACL                                                   OBJECT IDENTIFIER ::= { mgs360024fConfiguration 9 }

mgs360024fACLPortsConfTable OBJECT-TYPE
   SYNTAX      SEQUENCE OF MGS360024FACLPortsConfEntry
   MAX-ACCESS  not-accessible
   STATUS      current
   DESCRIPTION
       " "
   ::= { mgs360024fACL 1 }

mgs360024fACLPortsConfEntry OBJECT-TYPE
   SYNTAX      MGS360024FACLPortsConfEntry
   MAX-ACCESS  not-accessible
   STATUS      current
   DESCRIPTION
       ""
   INDEX    { mgs360024fACLPortsConfPort  }
   ::= { mgs360024fACLPortsConfTable 1 }

MGS360024FACLPortsConfEntry ::= SEQUENCE {
   mgs360024fACLPortsConfPort               INTEGER,
   mgs360024fACLPortsConfPolicyID           INTEGER,
   mgs360024fACLPortsConfAction             INTEGER,
   mgs360024fACLPortsConfRateLimiterID      INTEGER,
   mgs360024fACLPortsConfPortRedirect       INTEGER,
   mgs360024fACLPortsConfLogging            INTEGER,
   mgs360024fACLPortsConfShutdown           INTEGER,
   mgs360024fACLPortsConfState              INTEGER,
   mgs360024fACLPortsConfCounter            Counter32
}

mgs360024fACLPortsConfPort OBJECT-TYPE
   SYNTAX      INTEGER (1..4095)
   MAX-ACCESS  not-accessible
   STATUS      current
   DESCRIPTION
       " "
   ::= { mgs360024fACLPortsConfEntry 1 }

mgs360024fACLPortsConfPolicyID OBJECT-TYPE
   SYNTAX      INTEGER (0..255)
   MAX-ACCESS  read-write
   STATUS      current
   DESCRIPTION
       "default: 0, range : 0 - 255 "
   ::= { mgs360024fACLPortsConfEntry 2 }

mgs360024fACLPortsConfAction OBJECT-TYPE
   SYNTAX      INTEGER(0|1)
   MAX-ACCESS  read-write
   STATUS      current
   DESCRIPTION
       "default: 1,
        0: Deny
        1: Permit"
   ::= { mgs360024fACLPortsConfEntry 3 }

mgs360024fACLPortsConfRateLimiterID OBJECT-TYPE
   SYNTAX      INTEGER (0..16)
   MAX-ACCESS  read-write
   STATUS      current
   DESCRIPTION
       "default: 0,
        0: Disable
        range : 0 - 16 "
   ::= { mgs360024fACLPortsConfEntry 4 }

mgs360024fACLPortsConfPortRedirect OBJECT-TYPE
   SYNTAX      INTEGER (0..4095)
   MAX-ACCESS  read-write
   STATUS      current
   DESCRIPTION
       "default: 0
        0: Disable
        range : 0 - end port number "
   ::= { mgs360024fACLPortsConfEntry 5 }

mgs360024fACLPortsConfLogging OBJECT-TYPE
   SYNTAX      INTEGER(0|1)
   MAX-ACCESS  read-write
   STATUS      current
   DESCRIPTION
       "default: 0
        0: Disable
        1: Enable "
   ::= { mgs360024fACLPortsConfEntry 7 }

mgs360024fACLPortsConfShutdown OBJECT-TYPE
   SYNTAX      INTEGER(0|1)
   MAX-ACCESS  read-write
   STATUS      current
   DESCRIPTION
       "default: 0
        0: Disable
        1: Enable "
   ::= { mgs360024fACLPortsConfEntry 8 }

mgs360024fACLPortsConfState OBJECT-TYPE
   SYNTAX      INTEGER(0|1)
   MAX-ACCESS  read-write
   STATUS      current
   DESCRIPTION
       "default: 1
        0: Disable
        1: Enable "
   ::= { mgs360024fACLPortsConfEntry 9 }

mgs360024fACLPortsConfCounter OBJECT-TYPE
   SYNTAX      Counter32
   MAX-ACCESS  read-only
   STATUS      current
   DESCRIPTION
       "Counts the number of frames that match this ACE. "
   ::= { mgs360024fACLPortsConfEntry 10 }


mgs360024fACLRateLimiterTable OBJECT-TYPE
   SYNTAX      SEQUENCE OF MGS360024FACLRateLimiterEntry
   MAX-ACCESS  not-accessible
   STATUS      current
   DESCRIPTION
       " "
   ::= { mgs360024fACL 2 }

mgs360024fACLRateLimiterEntry OBJECT-TYPE
   SYNTAX      MGS360024FACLRateLimiterEntry
   MAX-ACCESS  not-accessible
   STATUS      current
   DESCRIPTION
       ""
   INDEX    { mgs360024fACLRateLimiterID  }
   ::= { mgs360024fACLRateLimiterTable 1 }

MGS360024FACLRateLimiterEntry ::= SEQUENCE {
   mgs360024fACLRateLimiterID       INTEGER,
   mgs360024fACLRateLimiterRate     INTEGER
}

mgs360024fACLRateLimiterID OBJECT-TYPE
   SYNTAX      INTEGER (1..16)
   MAX-ACCESS  not-accessible
   STATUS      current
   DESCRIPTION
       " Rate Limiter ID.
         range : 1-16 "
   ::= { mgs360024fACLRateLimiterEntry 1 }

mgs360024fACLRateLimiterRate OBJECT-TYPE
   SYNTAX      INTEGER (0..3276700)
   MAX-ACCESS  read-write
   STATUS      current
   DESCRIPTION
       "default: 1,
        range : <0-3276700> pps
       "
   ::= { mgs360024fACLRateLimiterEntry 3 }


mgs360024fACLACE                                          OBJECT IDENTIFIER ::= { mgs360024fACL 3 }

mgs360024fACLACECreate OBJECT-TYPE
   SYNTAX       INTEGER(0|1)
   MAX-ACCESS   read-write
   STATUS       current
   DESCRIPTION
       "default: 0
        0 : None  (read only)
        1 : Create an ACE entry"
   ::= { mgs360024fACLACE 1 }

mgs360024fACLACETable OBJECT-TYPE
   SYNTAX      SEQUENCE OF MGS360024FACLACEEntry
   MAX-ACCESS  not-accessible
   STATUS      current
   DESCRIPTION
       " Create ACL ACE entry. "
   ::= { mgs360024fACLACE 2 }

mgs360024fACLACEEntry OBJECT-TYPE
   SYNTAX      MGS360024FACLACEEntry
   MAX-ACCESS  not-accessible
   STATUS      current
   DESCRIPTION
       ""
   INDEX    { mgs360024fACLACEIndex  }
   ::= { mgs360024fACLACETable 1 }

MGS360024FACLACEEntry ::= SEQUENCE {
   mgs360024fACLACEIndex                INTEGER,
   mgs360024fACLACEID                   INTEGER,
   mgs360024fACLACENextID               INTEGER,
   mgs360024fACLACEIngressPort          DisplayString,
   mgs360024fACLACEPortPolicyNumber     INTEGER,

   mgs360024fACLACEPortPolicyBitmask    INTEGER,
   mgs360024fACLACEFrameType            INTEGER,
   mgs360024fACLACEAction               INTEGER,
   mgs360024fACLACEDenyPortRedirect     DisplayString,
   mgs360024fACLACELogging              INTEGER,

   mgs360024fACLACERateLimiter          INTEGER,
   mgs360024fACLACEShutdown             INTEGER,
   mgs360024fACLACEVLANTagPriority      INTEGER,

   mgs360024fACLACEVLANVID              INTEGER,
   mgs360024fACLACEEtherType            INTEGER,
   mgs360024fACLACESMAC                 DisplayString,
   mgs360024fACLACEDMACType             INTEGER,
   mgs360024fACLACEDMAC                 DisplayString,

   mgs360024fACLACEArpOpcode            INTEGER,
   mgs360024fACLACEArpFlagsRequestReply INTEGER,
   mgs360024fACLACEArpFlagsArpSmac      INTEGER,
   mgs360024fACLACEArpFlagsRarpDmac     INTEGER,
   mgs360024fACLACEArpFlagsLength       INTEGER,

   mgs360024fACLACEArpFlagsIp           INTEGER,
   mgs360024fACLACEArpFlagsEthernet     INTEGER,
   mgs360024fACLACESIPType              INTEGER,
   mgs360024fACLACESIPIPAddress         IpAddress,
   mgs360024fACLACESIPNetworkPrefix     INTEGER,

   mgs360024fACLACEDIPType              INTEGER,
   mgs360024fACLACEDIPIPAddress         IpAddress,
   mgs360024fACLACEDIPNetworkPrefix     INTEGER,

   mgs360024fACLACEIPProtocol           INTEGER,
   mgs360024fACLACEIPFlagsTTL           INTEGER,
   mgs360024fACLACEIPFlagsOptions       INTEGER,
   mgs360024fACLACEIPFlagsFragment      INTEGER,
   mgs360024fACLACEICMPType             INTEGER,

   mgs360024fACLACEICMPCode             INTEGER,
   mgs360024fACLACESourcePortMin        INTEGER,
   mgs360024fACLACESourcePortMax        INTEGER,
   mgs360024fACLACEDestPortMin          INTEGER,
   mgs360024fACLACEDestPortMax          INTEGER,

   mgs360024fACLACETCPFlagsFin          INTEGER,
   mgs360024fACLACETCPFlagsSyn          INTEGER,
   mgs360024fACLACETCPFlagsRst          INTEGER,
   mgs360024fACLACETCPFlagsPsh          INTEGER,
   mgs360024fACLACETCPFlagsAck          INTEGER,

   mgs360024fACLACETCPFlagsUrg          INTEGER,

   mgs360024fACLACERowStatus            INTEGER
}

mgs360024fACLACEIndex OBJECT-TYPE
   SYNTAX      INTEGER (1..256)
   MAX-ACCESS  not-accessible
   STATUS      current
   DESCRIPTION
       " "
   ::= { mgs360024fACLACEEntry 1 }

mgs360024fACLACEID OBJECT-TYPE
   SYNTAX      INTEGER (1..256)
   MAX-ACCESS  read-write
   STATUS      current
   DESCRIPTION
       " If the ACE ID is specified and an entry with this ACE ID
         already exists, the ACE will be modified. Otherwise, a
         new ACE will be added.
         range : 1 - 256. "
   ::= { mgs360024fACLACEEntry 2 }

mgs360024fACLACENextID OBJECT-TYPE
   SYNTAX      INTEGER (0..256)
   MAX-ACCESS  read-write
   STATUS      current
   DESCRIPTION
       " If the next ACE ID is non zero, the ACE will be placed
         before this ACE in the list. If the next ACE ID is zero,
         the ACE will be placed last in the list.
         range : 0 - 256. "
   ::= { mgs360024fACLACEEntry 3 }

mgs360024fACLACEIngressPort OBJECT-TYPE
   SYNTAX      DisplayString
   MAX-ACCESS  read-write
   STATUS      current
   DESCRIPTION
       " Indicates the ingress port of the ACE. Possible values are:
         All: The ACE will match all ingress port.
         Port: The ACE will match a specific ingress port.Format: 1,3,6."
   ::= { mgs360024fACLACEEntry 4 }

mgs360024fACLACEPortPolicyNumber OBJECT-TYPE
   SYNTAX      INTEGER (0..255)
   MAX-ACCESS  read-write
   STATUS      current
   DESCRIPTION
       " policy value.
         range : 0 - 255. "
   ::= { mgs360024fACLACEEntry 5 }

mgs360024fACLACEPortPolicyBitmask OBJECT-TYPE
   SYNTAX      INTEGER (0..255)
   MAX-ACCESS  read-write
   STATUS      current
   DESCRIPTION
       " policy bitmask.
         range : 0 - 255(0xff). "
   ::= { mgs360024fACLACEEntry 6 }

mgs360024fACLACEFrameType OBJECT-TYPE
   SYNTAX      INTEGER (0..6)
   MAX-ACCESS  read-write
   STATUS      current
   DESCRIPTION
       " 0: any,
         1: arp,
         2: etype,
         3: icmp,
         4: ipv4,
         5: tcp,
         6: udp."
   ::= { mgs360024fACLACEEntry 7 }

mgs360024fACLACEAction OBJECT-TYPE
   SYNTAX      INTEGER(0|1)
   MAX-ACCESS  read-write
   STATUS      current
   DESCRIPTION
       "default: 1,
        0: Deny
        1: Permit"
   ::= { mgs360024fACLACEEntry 8 }

mgs360024fACLACEDenyPortRedirect OBJECT-TYPE
   SYNTAX      DisplayString
   MAX-ACCESS  read-write
   STATUS      current
   DESCRIPTION
       " Frames that hit the ACE are redirected to the port number specified here.
         Disabled: indicates that the port redirect operation is disabled.
         Port Format: 1,3,6."
   ::= { mgs360024fACLACEEntry 9 }

mgs360024fACLACELogging OBJECT-TYPE
   SYNTAX      INTEGER(0|1)
   MAX-ACCESS  read-write
   STATUS      current
   DESCRIPTION
       "default: 0,
        0: disable - Frames matching the ACE are not logged.
        1: enable - Frames matching the ACE are stored in the system log."
   ::= { mgs360024fACLACEEntry 10 }

mgs360024fACLACERateLimiter OBJECT-TYPE
   SYNTAX      INTEGER (0..16)
   MAX-ACCESS  read-write
   STATUS      current
   DESCRIPTION
       "default: 0,
        0: Disable
        range : 0 - 16 "
   ::= { mgs360024fACLACEEntry 12 }

mgs360024fACLACEShutdown OBJECT-TYPE
   SYNTAX      INTEGER(0|1)
   MAX-ACCESS  read-write
   STATUS      current
   DESCRIPTION
       "default: 0,
        0: disable - Port shut down is disabled for the AC.
        1: enable - If a frame matches the ACE, the ingress port will be disabled."
   ::= { mgs360024fACLACEEntry 13 }

mgs360024fACLACEVLANTagPriority OBJECT-TYPE
   SYNTAX      INTEGER (0..8)
   MAX-ACCESS  read-write
   STATUS      current
   DESCRIPTION
       "Specify the tag priority for this ACE.
        The tag priority can't be set when 802.1Q Tagged is disabled
        default: 8,
        8: Any,
        range : 0 - 8 "
   ::= { mgs360024fACLACEEntry 15 }

mgs360024fACLACEVLANVID OBJECT-TYPE
   SYNTAX      INTEGER (0..4094)
   MAX-ACCESS  read-write
   STATUS      current
   DESCRIPTION
       "Specify the VLAN ID filter for this ACE.
        The vid can't be set when 802.1Q Tagged is disabled.
        default: 0,
        0: Any - No VLAN ID filter is specified.
        range : 0 - 4094 "
   ::= { mgs360024fACLACEEntry 16 }

mgs360024fACLACEEtherType OBJECT-TYPE
   SYNTAX      INTEGER (0..65535)
   MAX-ACCESS  read-write
   STATUS      current
   DESCRIPTION
       " 0: Any - Any but excluding 0x0800(IPv4) 0x0806(ARP) and 0x86DD(IPv6).
         range : 0 or 1536(0x0600)- 65535(0xffff). "
   ::= { mgs360024fACLACEEntry 17 }

mgs360024fACLACESMAC OBJECT-TYPE
   SYNTAX      DisplayString
   MAX-ACCESS  read-write
   STATUS      current
   DESCRIPTION
       " Configure source MAC address for this ACE.
         <mac-address>: A frame that hits this ACE matches this source MAC address value.
         Any: Don't care."
   ::= { mgs360024fACLACEEntry 18 }

mgs360024fACLACEDMACType OBJECT-TYPE
   SYNTAX      INTEGER (0..4)
   MAX-ACCESS  read-write
   STATUS      current
   DESCRIPTION
       "DMAC Type.
        default: 0,
        0: Any - Don't care.
        1: Broadcast - Frame must be broadcast.
        2: Unicast - Frame must be unicast.
        3: Multicast - Frame must be multicast.
        4: mac address
        range : 0 - 4 "
   ::= { mgs360024fACLACEEntry 19 }

mgs360024fACLACEDMAC OBJECT-TYPE
   SYNTAX      DisplayString
   MAX-ACCESS  read-write
   STATUS      current
   DESCRIPTION
       " Configure destination MAC address for this ACE.
         <mac-address>: A frame that hits this ACE matches this destination MAC address value.
         Any: Don't care.
         Broadcast: Frame must be broadcast.
         Unicast: Frame must be unicast.
         Multicast: Frame must be multicast. "
   ::= { mgs360024fACLACEEntry 20 }

mgs360024fACLACEArpOpcode OBJECT-TYPE
   SYNTAX      INTEGER (0..3)
   MAX-ACCESS  read-write
   STATUS      current
   DESCRIPTION
       "Configure ARP opcode for this ACE.
        default: 0,
        0: Any - Don't care.
        1: arp.
        2: rarp.
        3: other.
        4: No data.
        range : 0 - 3 "
   ::= { mgs360024fACLACEEntry 21 }

mgs360024fACLACEArpFlagsRequestReply OBJECT-TYPE
   SYNTAX      INTEGER (0..2)
   MAX-ACCESS  read-write
   STATUS      current
   DESCRIPTION
       "Specify the available ARP/RARP opcode (OP) flag for this ACE.
        default: 2,
        0: Frame must have ARP Reply or RARP Reply OP flag.
        1: Frame must have ARP Request or RARP Request OP flag set.
        2: Any - Don't care.
        3: No data.
        range : 0 - 2 "
   ::= { mgs360024fACLACEEntry 22 }

mgs360024fACLACEArpFlagsArpSmac OBJECT-TYPE
   SYNTAX      INTEGER (0..2)
   MAX-ACCESS  read-write
   STATUS      current
   DESCRIPTION
       "Specify whether frames can hit the action according to their sender hardware address field (SHA) settings.
        default: 2,
        0: ARP frames where SHA is not equal to the SMAC address.
        1: ARP frames where SHA is equal to the SMAC address.
        2: Any - Don't care.
        3: No data.
        range : 0 - 2 "
   ::= { mgs360024fACLACEEntry 23 }

mgs360024fACLACEArpFlagsRarpDmac OBJECT-TYPE
   SYNTAX      INTEGER (0..2)
   MAX-ACCESS  read-write
   STATUS      current
   DESCRIPTION
       "Specify whether frames can hit the action according to their target hardware address field (THA) settings.
        default: 2,
        0: RARP frames where THA is not equal to the DMAC address.
        1: RARP frames where THA is equal to the DMAC address.
        2: Any - Don't care.
        3: No data.
        range : 0 - 2 "
   ::= { mgs360024fACLACEEntry 24 }

mgs360024fACLACEArpFlagsLength OBJECT-TYPE
   SYNTAX      INTEGER (0..2)
   MAX-ACCESS  read-write
   STATUS      current
   DESCRIPTION
       "Specify whether frames can hit the action according to their ARP/RARP hardware address length (HLN) and
        protocol address length (PLN) settings.
        default: 2,
        0: ARP/RARP frames where the HLN is not equal to Ethernet(0x06) or the (PLN) is not equal to IPv4(0x04).
        1: ARP/RARP frames where the HLN is equal to Ethernet (0x06) and the (PLN) is equal to IPv4(0x04).
        2: Any - Don't care.
        3: No data.
        range : 0 - 2 "
   ::= { mgs360024fACLACEEntry 25 }

mgs360024fACLACEArpFlagsIp OBJECT-TYPE
   SYNTAX      INTEGER (0..2)
   MAX-ACCESS  read-write
   STATUS      current
   DESCRIPTION
       "Specify whether frames can hit the action according to their ARP/RARP hardware address space (HRD) settings.
        default: 2,
        0: ARP/RARP frames where the HLD is not equal to Ethernet(1).
        1: ARP/RARP frames where the HLD is equal to Ethernet(1).
        2: Any - Don't care.
        3: No data.
        range : 0 - 2 "
   ::= { mgs360024fACLACEEntry 26 }

mgs360024fACLACEArpFlagsEthernet OBJECT-TYPE
   SYNTAX      INTEGER (0..2)
   MAX-ACCESS  read-write
   STATUS      current
   DESCRIPTION
       "Specify whether frames can hit the action according to their ARP/RARP protocol address space (PRO) settings.
        default: 2,
        0: ARP/RARP frames where the PRO is not equal to IP\n(0x800).
        1: ARP/RARP frames where the PRO is equal to IP(0x800).
        2: Any - Don't care.
        3: No data.
        range : 0 - 2 "
   ::= { mgs360024fACLACEEntry 27 }

mgs360024fACLACESIPType OBJECT-TYPE
   SYNTAX      INTEGER(0|1)
   MAX-ACCESS  read-write
   STATUS      current
   DESCRIPTION
       "Configure source IP address for this ACE.
        default: 0,
        0: Any - Don't care.
        1: IP Address.
        2: No data.
        range : 0 - 1"
   ::= { mgs360024fACLACEEntry 28 }

mgs360024fACLACESIPIPAddress OBJECT-TYPE
   SYNTAX      IpAddress
   MAX-ACCESS  read-write
   STATUS      current
   DESCRIPTION
       "A frame that hits this ACE matches this source IP address value."
   ::= { mgs360024fACLACEEntry 29 }

mgs360024fACLACESIPNetworkPrefix OBJECT-TYPE
   SYNTAX      INTEGER (1..32)
   MAX-ACCESS  read-write
   STATUS      current
   DESCRIPTION
       "Network prefix.
        default: 32,
        0: No data.
        range : 1 - 32"
   ::= { mgs360024fACLACEEntry 30 }


mgs360024fACLACEDIPType OBJECT-TYPE
   SYNTAX      INTEGER(0|1)
   MAX-ACCESS  read-write
   STATUS      current
   DESCRIPTION
       "Configure destination IP address for this ACE.
        default: 0,
        0: Any - Don't care.
        1: IP Address.
        2: No data.
        range : 0 - 1"
   ::= { mgs360024fACLACEEntry 32 }

mgs360024fACLACEDIPIPAddress OBJECT-TYPE
   SYNTAX      IpAddress
   MAX-ACCESS  read-write
   STATUS      current
   DESCRIPTION
       "A frame that hits this ACE matches this destination IP address value."
   ::= { mgs360024fACLACEEntry 33 }

mgs360024fACLACEDIPNetworkPrefix OBJECT-TYPE
   SYNTAX      INTEGER (1..32)
   MAX-ACCESS  read-write
   STATUS      current
   DESCRIPTION
       "Network prefix.
        default: 32,
        0: No data.
        range : 1 - 32"
   ::= { mgs360024fACLACEEntry 34 }


mgs360024fACLACEIPProtocol OBJECT-TYPE
   SYNTAX      INTEGER (0..256)
   MAX-ACCESS  read-write
   STATUS      current
   DESCRIPTION
       "Configure IP protocol for this ACE.
        default: 256,
        256: Any - Don't care.
        257: No data.
        range : 0 - 256"
   ::= { mgs360024fACLACEEntry 36 }

mgs360024fACLACEIPFlagsTTL OBJECT-TYPE
   SYNTAX      INTEGER (0..2)
   MAX-ACCESS  read-write
   STATUS      current
   DESCRIPTION
       "Configure IP Time-to-Live flags for this ACE.
        default: 2,
        0: IPv4 frames with a Time-to-Live field is equal to zero.
        1: IPv4 frames with a Time-to-Live field greater than zero.
        2: Any - Don't care.
        3: No data.
        range : 0 - 2 "
   ::= { mgs360024fACLACEEntry 37 }

mgs360024fACLACEIPFlagsOptions OBJECT-TYPE
   SYNTAX      INTEGER (0..2)
   MAX-ACCESS  read-write
   STATUS      current
   DESCRIPTION
       "Configure IP options flag for this ACE.
        default: 2,
        0: IPv4 frames where the options flag is unset.
        1: IPv4 frames where the options flag is set.
        2: Any - Don't care.
        3: No data.
        range : 0 - 2 "
   ::= { mgs360024fACLACEEntry 38 }

mgs360024fACLACEIPFlagsFragment OBJECT-TYPE
   SYNTAX      INTEGER (0..2)
   MAX-ACCESS  read-write
   STATUS      current
   DESCRIPTION
       "Configure IP fragment offset flags for this ACE.
        default: 2,
        0: IPv4 frames where the MF bit is unset and the FRAG OFFSET field is equal zero.
        1: IPv4 frames where the MF bit is set or the FRAG OFFSET field is greater than zero.
        2: Any - Don't care.
        3: No data.
        range : 0 - 2 "
   ::= { mgs360024fACLACEEntry 39 }

mgs360024fACLACEICMPType OBJECT-TYPE
   SYNTAX      INTEGER (0..256)
   MAX-ACCESS  read-write
   STATUS      current
   DESCRIPTION
       "Configure ICMP type for this ACE.
        default: 256,
        256: Any - Don't care.
        257: No data.
        range : 0 - 256"
   ::= { mgs360024fACLACEEntry 40 }

mgs360024fACLACEICMPCode OBJECT-TYPE
   SYNTAX      INTEGER (0..256)
   MAX-ACCESS  read-write
   STATUS      current
   DESCRIPTION
       "Configure ICMP code for this ACE.
        default: 256,
        256: Any - Don't care.
        257: No data.
        range : 0 - 256"
   ::= { mgs360024fACLACEEntry 41 }

mgs360024fACLACESourcePortMin OBJECT-TYPE
   SYNTAX      INTEGER (0..65535)
   MAX-ACCESS  read-write
   STATUS      current
   DESCRIPTION
       "Configure Source UDP/TCP port range for this ACE.
        default: 0,
        65536: No data.
        range : 0 - 65535"
   ::= { mgs360024fACLACEEntry 42 }

mgs360024fACLACESourcePortMax OBJECT-TYPE
   SYNTAX      INTEGER (0..65535)
   MAX-ACCESS  read-write
   STATUS      current
   DESCRIPTION
       "Configure Source UDP/TCP port range for this ACE.
        default: 0,
        65536: No data.
        range : 0 - 65535"
   ::= { mgs360024fACLACEEntry 43 }

mgs360024fACLACEDestPortMin OBJECT-TYPE
   SYNTAX      INTEGER (0..65535)
   MAX-ACCESS  read-write
   STATUS      current
   DESCRIPTION
       "Configure Destination UDP/TCP port range for this ACE.
        default: 0,
        65536: No data.
        range : 0 - 65535"
   ::= { mgs360024fACLACEEntry 44 }

mgs360024fACLACEDestPortMax OBJECT-TYPE
   SYNTAX      INTEGER (0..65535)
   MAX-ACCESS  read-write
   STATUS      current
   DESCRIPTION
       "Configure Destination UDP/TCP port range for this ACE.
        default: 0,
        65536: No data.
        range : 0 - 65535"
   ::= { mgs360024fACLACEEntry 45 }

mgs360024fACLACETCPFlagsFin OBJECT-TYPE
   SYNTAX      INTEGER (0..2)
   MAX-ACCESS  read-write
   STATUS      current
   DESCRIPTION
       "Configure TCP (FIN) flags for this ACE.
        default: 2,
        0: TCP frames where the FIN field is unset.
        1: TCP frames where the FIN field is set.
        2: Any - Don't care.
        3: No data.
        range : 0 - 2 "
   ::= { mgs360024fACLACEEntry 46 }

mgs360024fACLACETCPFlagsSyn OBJECT-TYPE
   SYNTAX      INTEGER (0..2)
   MAX-ACCESS  read-write
   STATUS      current
   DESCRIPTION
       "Configure TCP (SYN) flags for this ACE.
        default: 2,
        0: TCP frames where the SYN field is unset.
        1: TCP frames where the SYN field is set.
        2: Any - Don't care.
        3: No data.
        range : 0 - 2 "
   ::= { mgs360024fACLACEEntry 47 }

mgs360024fACLACETCPFlagsRst OBJECT-TYPE
   SYNTAX      INTEGER (0..2)
   MAX-ACCESS  read-write
   STATUS      current
   DESCRIPTION
       "Configure TCP (RST) flags for this ACE.
        default: 2,
        0: TCP frames where the RST field is unset.
        1: TCP frames where the RST field is set.
        2: Any - Don't care.
        3: No data.
        range : 0 - 2 "
   ::= { mgs360024fACLACEEntry 48 }

mgs360024fACLACETCPFlagsPsh OBJECT-TYPE
   SYNTAX      INTEGER (0..2)
   MAX-ACCESS  read-write
   STATUS      current
   DESCRIPTION
       "Configure TCP (PSH) flags for this ACE.
        default: 2,
        0: TCP frames where the PSH field is unset.
        1: TCP frames where the PSH field is set.
        2: Any - Don't care.
        3: No data.
        range : 0 - 2 "
   ::= { mgs360024fACLACEEntry 49 }

mgs360024fACLACETCPFlagsAck OBJECT-TYPE
   SYNTAX      INTEGER (0..2)
   MAX-ACCESS  read-write
   STATUS      current
   DESCRIPTION
       "Configure TCP (ACK) flags for this ACE.
        default: 2,
        0: TCP frames where the ACK field is unset.
        1: TCP frames where the ACK field is set.
        2: Any - Don't care.
        3: No data.
        range : 0 - 2 "
   ::= { mgs360024fACLACEEntry 50 }

mgs360024fACLACETCPFlagsUrg OBJECT-TYPE
   SYNTAX      INTEGER (0..2)
   MAX-ACCESS  read-write
   STATUS      current
   DESCRIPTION
       "Configure TCP (URG) flags for this ACE.
        default: 2,
        0: TCP frames where the URG field is unset.
        1: TCP frames where the URG field is set.
        2: Any - Don't care.
        3: No data.
        range : 0 - 2 "
   ::= { mgs360024fACLACEEntry 51 }

mgs360024fACLACERowStatus OBJECT-TYPE
   SYNTAX      INTEGER (1..5)
   MAX-ACCESS  read-write
   STATUS      current
   DESCRIPTION
       " 1: active
         2: notInservice
         4: destroy
         5: undo"
   ::= { mgs360024fACLACEEntry 66 }


mgs360024fACLACEClear OBJECT-TYPE
   SYNTAX       INTEGER(0|1)
   MAX-ACCESS   read-write
   STATUS       current
   DESCRIPTION
       "default: 0
        0 : No action
        1 : Clear all ACL counters."
   ::= { mgs360024fACLACE 3 }

mgs360024fACLACEMoveACEID OBJECT-TYPE
   SYNTAX       INTEGER (1..256)
   MAX-ACCESS   read-write
   STATUS       current
   DESCRIPTION
       "Move ACE,
        default: 0
        ACE ID must be exist.
        range : 1 - 256."
   ::= { mgs360024fACLACE 4 }

mgs360024fACLACEMoveNextACEID OBJECT-TYPE
   SYNTAX       INTEGER (0..256)
   MAX-ACCESS   read-write
   STATUS       current
   DESCRIPTION
       "Move ACE,
        default: 0
        If the next ACE ID is non zero, the ACE will be placed before this ACE in the list. If the next ACE ID is zero,
        the ACE will be placed last in the list.
        range : 0 - 256."
   ::= { mgs360024fACLACE 5 }

mgs360024fACLACEStatusTable OBJECT-TYPE
   SYNTAX      SEQUENCE OF MGS360024FACLACEStatusEntry
   MAX-ACCESS  not-accessible
   STATUS      current
   DESCRIPTION
       " ACL ACE Status entry. "
   ::= { mgs360024fACLACE 6 }

mgs360024fACLACEStatusEntry OBJECT-TYPE
   SYNTAX      MGS360024FACLACEStatusEntry
   MAX-ACCESS  not-accessible
   STATUS      current
   DESCRIPTION
       ""
   INDEX    { mgs360024fACLACEStatusIndex  }
   ::= { mgs360024fACLACEStatusTable 1 }

MGS360024FACLACEStatusEntry ::= SEQUENCE {
   mgs360024fACLACEStatusIndex          INTEGER,
   mgs360024fACLACEStatusUser           DisplayString,
   mgs360024fACLACEStatusID             INTEGER,
   mgs360024fACLACEStatusIngressPort    DisplayString,
   mgs360024fACLACEStatusFrameType      DisplayString,
   mgs360024fACLACEStatusAction         DisplayString,
   mgs360024fACLACEStatusRateLimiter    DisplayString,
   mgs360024fACLACEStatusPortCopy       DisplayString,
   mgs360024fACLACEStatusMirror         DisplayString,
   mgs360024fACLACEStatusCPU            DisplayString,
   mgs360024fACLACEStatusCounter        Counter32,
   mgs360024fACLACEStatusConflict       DisplayString
}

mgs360024fACLACEStatusIndex OBJECT-TYPE
   SYNTAX      INTEGER (1..256)
   MAX-ACCESS  not-accessible
   STATUS      current
   DESCRIPTION
       " "
   ::= { mgs360024fACLACEStatusEntry 1 }

mgs360024fACLACEStatusUser OBJECT-TYPE
   SYNTAX      DisplayString
   MAX-ACCESS  read-only
   STATUS      current
   DESCRIPTION
       " Indicates the ACL user.
         S : Static.
         IPMG : IP Management.
         IPSG : IP Source Guard.
         IPMC : IPMC.
         ARPI : Arp Inspection.
         UPnP : UPnP.
         DHCP : DHCP. "
   ::= { mgs360024fACLACEStatusEntry 2 }

mgs360024fACLACEStatusID OBJECT-TYPE
   SYNTAX      INTEGER (1..256)
   MAX-ACCESS  read-only
   STATUS      current
   DESCRIPTION
       " ACE ID.
         range : 1 - 256. "
   ::= { mgs360024fACLACEStatusEntry 3 }

mgs360024fACLACEStatusIngressPort OBJECT-TYPE
   SYNTAX      DisplayString
   MAX-ACCESS  read-only
   STATUS      current
   DESCRIPTION
       " Indicates the ingress port of the ACE. Possible values are:
         All: The ACE will match all ingress port.
         Port: The ACE will match a specific ingress port. "
   ::= { mgs360024fACLACEStatusEntry 4 }

mgs360024fACLACEStatusFrameType OBJECT-TYPE
   SYNTAX      DisplayString
   MAX-ACCESS  read-only
   STATUS      current
   DESCRIPTION
       " Indicates the frame type of the ACE. "
   ::= { mgs360024fACLACEStatusEntry 5 }

mgs360024fACLACEStatusAction OBJECT-TYPE
   SYNTAX      DisplayString
   MAX-ACCESS  read-only
   STATUS      current
   DESCRIPTION
       " Indicates the forwarding action of the ACE. "
   ::= { mgs360024fACLACEStatusEntry 6 }

mgs360024fACLACEStatusRateLimiter OBJECT-TYPE
   SYNTAX      DisplayString
   MAX-ACCESS  read-only
   STATUS      current
   DESCRIPTION
       " Indicates the rate limiter number of the ACE. "
   ::= { mgs360024fACLACEStatusEntry 7 }

mgs360024fACLACEStatusPortCopy OBJECT-TYPE
   SYNTAX      DisplayString
   MAX-ACCESS  read-only
   STATUS      current
   DESCRIPTION
       " Indicates the port redirect operation of the ACE. Frames matching the ACE are redirected to the port number. "
   ::= { mgs360024fACLACEStatusEntry 8 }

mgs360024fACLACEStatusMirror OBJECT-TYPE
   SYNTAX      DisplayString
   MAX-ACCESS  read-only
   STATUS      current
   DESCRIPTION
       " Specify the mirror operation of this port. "
   ::= { mgs360024fACLACEStatusEntry 9 }

mgs360024fACLACEStatusCPU OBJECT-TYPE
   SYNTAX      DisplayString
   MAX-ACCESS  read-only
   STATUS      current
   DESCRIPTION
       " Forward packet that matched the specific ACE to CPU. "
   ::= { mgs360024fACLACEStatusEntry 10 }

mgs360024fACLACEStatusCounter OBJECT-TYPE
   SYNTAX      Counter32
   MAX-ACCESS  read-only
   STATUS      current
   DESCRIPTION
       " The counter indicates the number of times the ACE was hit by a frame. "
   ::= { mgs360024fACLACEStatusEntry 11 }

mgs360024fACLACEStatusConflict OBJECT-TYPE
   SYNTAX      DisplayString
   MAX-ACCESS  read-only
   STATUS      current
   DESCRIPTION
       " Indicates the hardware status of the specific ACE. The specific ACE is not applied to the hardware due to hardware limitations. "
   ::= { mgs360024fACLACEStatusEntry 12 }


mgs360024fERPS                                             OBJECT IDENTIFIER ::= { mgs360024fConfiguration 10 }

mgs360024fERPSConf                                          OBJECT IDENTIFIER ::= { mgs360024fERPS 1 }

mgs360024fERPSConfCreate OBJECT-TYPE
   SYNTAX       INTEGER(0|1)
   MAX-ACCESS   read-write
   STATUS       current
   DESCRIPTION
       "default: 0
        0 : None  (read only)
        1 : Create an ERPS entry"
   ::= { mgs360024fERPSConf 1 }

mgs360024fERPSConfTable OBJECT-TYPE
   SYNTAX      SEQUENCE OF MGS360024FERPSConfEntry
   MAX-ACCESS  not-accessible
   STATUS      current
   DESCRIPTION
       " Create one ERPS group. "
   ::= { mgs360024fERPSConf 2 }

mgs360024fERPSConfEntry OBJECT-TYPE
   SYNTAX      MGS360024FERPSConfEntry
   MAX-ACCESS  not-accessible
   STATUS      current
   DESCRIPTION
       ""
   INDEX    { mgs360024fERPSConfIndex  }
   ::= { mgs360024fERPSConfTable 1 }

MGS360024FERPSConfEntry ::= SEQUENCE {
   mgs360024fERPSConfIndex                  INTEGER,
   mgs360024fERPSConfERPSID                 INTEGER,
   mgs360024fERPSConfPort0                  INTEGER,
   mgs360024fERPSConfPort1                  INTEGER,
   mgs360024fERPSConfPort0SFMEP             INTEGER,
   mgs360024fERPSConfPort1SFMEP             INTEGER,
   mgs360024fERPSConfPort0APSMEP            INTEGER,
   mgs360024fERPSConfPort1APSMEP            INTEGER,
   mgs360024fERPSConfRingType               INTEGER,
   mgs360024fERPSConfInterconnectedNode     INTEGER,
   mgs360024fERPSConfVirtualChannel         INTEGER,
   mgs360024fERPSConfMajorRingID            INTEGER,
   mgs360024fERPSConfAlarm                  DisplayString,

   mgs360024fERPSInstanceConfConfigured     DisplayString,
   mgs360024fERPSInstanceConfGuardTime      INTEGER,
   mgs360024fERPSInstanceConfWTRTime        INTEGER,
   mgs360024fERPSInstanceConfHoldOffTime    INTEGER,
   mgs360024fERPSInstanceConfVersion        INTEGER,
   mgs360024fERPSInstanceConfRevertive      INTEGER,
   mgs360024fERPSInstanceConfVLANconfig     DisplayString,

   mgs360024fERPSConfRowStatus              INTEGER
}

mgs360024fERPSConfIndex OBJECT-TYPE
   SYNTAX      INTEGER (1..64)
   MAX-ACCESS  not-accessible
   STATUS      current
   DESCRIPTION
       " "
   ::= { mgs360024fERPSConfEntry 1 }

mgs360024fERPSConfERPSID OBJECT-TYPE
   SYNTAX      INTEGER (1..64)
   MAX-ACCESS  read-write
   STATUS      current
   DESCRIPTION
       " Protection group ID.
         range : 1 - 64. "
   ::= { mgs360024fERPSConfEntry 2 }

mgs360024fERPSConfPort0 OBJECT-TYPE
   SYNTAX      INTEGER (1..26)
   MAX-ACCESS  read-write
   STATUS      current
   DESCRIPTION
       " East port of the switch in the ring.
         range : 1 - 26. "
   ::= { mgs360024fERPSConfEntry 3 }

mgs360024fERPSConfPort1 OBJECT-TYPE
   SYNTAX      INTEGER (0..26)
   MAX-ACCESS  read-write
   STATUS      current
   DESCRIPTION
       " West port of the switch in the Ring.
         As interconnected sub-ring will have only one ring port, W port is configured as 0 for interconnected sub-ring.
         0: in this field indicates that no west port is associated with this instance.
         range : 0 - 26. "
   ::= { mgs360024fERPSConfEntry 4 }

mgs360024fERPSConfPort0SFMEP OBJECT-TYPE
   SYNTAX      INTEGER (1..32)
   MAX-ACCESS  read-write
   STATUS      current
   DESCRIPTION
       " The East Signal Fail reporting MEP.
         range : 1 - 32. "
   ::= { mgs360024fERPSConfEntry 5 }

mgs360024fERPSConfPort1SFMEP OBJECT-TYPE
   SYNTAX      INTEGER (0..32)
   MAX-ACCESS  read-write
   STATUS      current
   DESCRIPTION
       " The West Signal Fail reporting MEP. As only one SF MEP is associated with interconnected sub-ring without virtual channel,
         it is configured as 0 for such ring instances. 0: in this field indicates that no west SF MEP is associated with this instance.
         range : 0 - 32. "
   ::= { mgs360024fERPSConfEntry 6 }

mgs360024fERPSConfPort0APSMEP OBJECT-TYPE
   SYNTAX      INTEGER (1..32)
   MAX-ACCESS  read-write
   STATUS      current
   DESCRIPTION
       " The East APS PDU handling MEP.
         range : 1 - 32. "
   ::= { mgs360024fERPSConfEntry 7 }

mgs360024fERPSConfPort1APSMEP OBJECT-TYPE
   SYNTAX      INTEGER (0..32)
   MAX-ACCESS  read-write
   STATUS      current
   DESCRIPTION
       " The West APS PDU handling MEP. As only one APS MEP is associated with interconnected sub-ring without virtual channel,
         it is configured as 0 for such ring instances. 0: in this field indicates that no west APS MEP is associated with this instance.
         range : 0 - 32. "
   ::= { mgs360024fERPSConfEntry 8 }

mgs360024fERPSConfRingType OBJECT-TYPE
   SYNTAX      INTEGER (0|1)
   MAX-ACCESS  read-write
   STATUS      current
   DESCRIPTION
       " Type of Protectiong ring. It can be either major ring or sub-ring.
         default: 0,
         0: Major
         1: Sub"
   ::= { mgs360024fERPSConfEntry 9 }

mgs360024fERPSConfInterconnectedNode OBJECT-TYPE
   SYNTAX      INTEGER (0|1)
   MAX-ACCESS  read-write
   STATUS      current
   DESCRIPTION
       " Interconnected Node indicates that the ring instance is interconnected.
         default: 0,
         0: No - indicates that the configured instance is not interconnected.
         1: Yes - indicates it is an interconnected node for this instance. "
   ::= { mgs360024fERPSConfEntry 10 }

mgs360024fERPSConfVirtualChannel OBJECT-TYPE
   SYNTAX      INTEGER (0|1)
   MAX-ACCESS  read-write
   STATUS      current
   DESCRIPTION
       " Sub-rings can either have virtual channel or not on the interconnected node.
         default: 0,
         0: No - indicates, sub-ring doesn't have virtual channel.
         1: Yes - indicates it is a sub-ring with virtual channel. "
   ::= { mgs360024fERPSConfEntry 11 }

mgs360024fERPSConfMajorRingID OBJECT-TYPE
   SYNTAX      INTEGER (1..64)
   MAX-ACCESS  read-only
   STATUS      current
   DESCRIPTION
       " Major ring group ID for the interconnected sub-ring.
         It is used to send topology change updates on major ring.
         If ring is major, this value is same as the protection group ID of this ring. "
   ::= { mgs360024fERPSConfEntry 12 }

mgs360024fERPSConfAlarm OBJECT-TYPE
   SYNTAX      DisplayString (SIZE (1..32))
   MAX-ACCESS  read-only
   STATUS      current
   DESCRIPTION
       " There is an active alarm on the ERPS. "
   ::= { mgs360024fERPSConfEntry 13 }

mgs360024fERPSInstanceConfConfigured OBJECT-TYPE
   SYNTAX      DisplayString (SIZE (1..32))
   MAX-ACCESS  read-only
   STATUS      current
   DESCRIPTION
       " Down: This ERPS is only created and has not yet been configured - is not active.
         Up: This ERPS is configured - is active. "
   ::= { mgs360024fERPSConfEntry 14 }

mgs360024fERPSInstanceConfGuardTime OBJECT-TYPE
   SYNTAX      INTEGER (10..2000)
   MAX-ACCESS  read-write
   STATUS      current
   DESCRIPTION
       " Guard timeout value to be used to prevent ring nodes from receiving outdated R-APS messages.
         default : 500(ms).
         range : 10 - 2000(ms). "
   ::= { mgs360024fERPSConfEntry 15 }

mgs360024fERPSInstanceConfWTRTime OBJECT-TYPE
   SYNTAX      INTEGER (1..12)
   MAX-ACCESS  read-write
   STATUS      current
   DESCRIPTION
       " The Wait To Restore timing value to be used in revertive switching.
         default : 5(minutes).
         range : 1 - 12(minutes). "
   ::= { mgs360024fERPSConfEntry 16 }

mgs360024fERPSInstanceConfHoldOffTime OBJECT-TYPE
   SYNTAX      INTEGER (0..10000)
   MAX-ACCESS  read-write
   STATUS      current
   DESCRIPTION
       " The timing value to be used to make persistent check on Signal Fail before switching.
         default : 0(seconds).
         range : 0 - 10000(ms). "
   ::= { mgs360024fERPSConfEntry 17 }

mgs360024fERPSInstanceConfVersion OBJECT-TYPE
   SYNTAX      INTEGER (0|1)
   MAX-ACCESS  read-write
   STATUS      current
   DESCRIPTION
       " ERPS version of a group.
         default : 1.
         0: v1
         1: v2 "
   ::= { mgs360024fERPSConfEntry 18 }

mgs360024fERPSInstanceConfRevertive OBJECT-TYPE
   SYNTAX      INTEGER (0|1)
   MAX-ACCESS  read-write
   STATUS      current
   DESCRIPTION
       " ERPS revertibility of a group.
         default : 1.
         0: non-revertible
         1: revertible "
   ::= { mgs360024fERPSConfEntry 19 }

mgs360024fERPSInstanceConfVLANconfig OBJECT-TYPE
   SYNTAX      DisplayString (SIZE (1..255))
   MAX-ACCESS  read-write
   STATUS      current
   DESCRIPTION
       " VID of the protected vlan. "
   ::= { mgs360024fERPSConfEntry 20 }

mgs360024fERPSConfRowStatus OBJECT-TYPE
   SYNTAX      INTEGER (1..5)
   MAX-ACCESS  read-write
   STATUS      current
   DESCRIPTION
       " 1: active
        2: notInservice
        3: edit
        4: destroy
        5: undo"
   ::= { mgs360024fERPSConfEntry 21 }


mgs360024fMRSTP                                             OBJECT IDENTIFIER ::= { mgs360024fConfiguration 11 }

mgs360024fMRSTPInstance                                          OBJECT IDENTIFIER ::= { mgs360024fMRSTP 1 }

mgs360024fMRSTPInstanceConf                                          OBJECT IDENTIFIER ::= { mgs360024fMRSTPInstance 1 }

mgs360024fMRSTPInstanceConfGlobalState OBJECT-TYPE
   SYNTAX      INTEGER(0|1)
   MAX-ACCESS  read-write
   STATUS      current
   DESCRIPTION
       "default: 0
       0: disable
       1: enable"
   ::= { mgs360024fMRSTPInstanceConf 1 }

mgs360024fMRSTPInstanceConfigurationTable OBJECT-TYPE
   SYNTAX      SEQUENCE OF MGS360024FMRSTPInstanceConfigurationEntry
   MAX-ACCESS  not-accessible
   STATUS      current
   DESCRIPTION
       " show instance configuration. "
   ::= { mgs360024fMRSTPInstanceConf 2 }

mgs360024fMRSTPInstanceConfigurationEntry OBJECT-TYPE
   SYNTAX      MGS360024FMRSTPInstanceConfigurationEntry
   MAX-ACCESS  not-accessible
   STATUS      current
   DESCRIPTION
       ""
   INDEX    { mgs360024fMRSTPInstanceConfigurationInstance  }
   ::= { mgs360024fMRSTPInstanceConfigurationTable 1 }

MGS360024FMRSTPInstanceConfigurationEntry ::= SEQUENCE {
   mgs360024fMRSTPInstanceConfigurationInstance         INTEGER,
   mgs360024fMRSTPInstanceConfigurationState            INTEGER,
   mgs360024fMRSTPInstanceConfigurationVersion          INTEGER,
   mgs360024fMRSTPInstanceConfigurationPriority         INTEGER,
   mgs360024fMRSTPInstanceConfigurationHelloTime        INTEGER,
   mgs360024fMRSTPInstanceConfigurationMaxAge           INTEGER,
   mgs360024fMRSTPInstanceConfigurationFWDelay          INTEGER
}

mgs360024fMRSTPInstanceConfigurationInstance OBJECT-TYPE
   SYNTAX      INTEGER(1..12)
   MAX-ACCESS  not-accessible
   STATUS      current
   DESCRIPTION
       " mrstp instance id, range : 1-12 "
   ::= { mgs360024fMRSTPInstanceConfigurationEntry 1 }

mgs360024fMRSTPInstanceConfigurationState OBJECT-TYPE
   SYNTAX      INTEGER (0|1)
   MAX-ACCESS  read-write
   STATUS      current
   DESCRIPTION
       " MRSTP instance state. To really enable an MRSTP instance, the MRSTP Global State must also be enabled.
         default: 0,
         0: disable
         1: enable"
   ::= { mgs360024fMRSTPInstanceConfigurationEntry 2 }

mgs360024fMRSTPInstanceConfigurationVersion OBJECT-TYPE
   SYNTAX      INTEGER (0|1)
   MAX-ACCESS  read-write
   STATUS      current
   DESCRIPTION
       " The STP protocol version.
         default: 1,
         0: stp
         1: rstp"
   ::= { mgs360024fMRSTPInstanceConfigurationEntry 3 }

mgs360024fMRSTPInstanceConfigurationPriority OBJECT-TYPE
   SYNTAX      INTEGER(0..61440)
   MAX-ACCESS  read-write
   STATUS      current
   DESCRIPTION
       " The instance priority would be truncated to a multiple of 4096.
         range : 0 - 61440, default: 32768."
   ::= { mgs360024fMRSTPInstanceConfigurationEntry 4 }

mgs360024fMRSTPInstanceConfigurationHelloTime OBJECT-TYPE
   SYNTAX      INTEGER(1..10)
   MAX-ACCESS  read-write
   STATUS      current
   DESCRIPTION
       " The interval between periodic transmissions of STP Configuration Messages by Designated Ports when the Bridge Instance is the Root Bridge.
         range : 1 - 10 (seconds), and (HelloTime+1)*2 must be <= MaxAge.
         default: 2."
   ::= { mgs360024fMRSTPInstanceConfigurationEntry 5 }

mgs360024fMRSTPInstanceConfigurationMaxAge OBJECT-TYPE
   SYNTAX      INTEGER(6..40)
   MAX-ACCESS  read-write
   STATUS      current
   DESCRIPTION
       " The maximum age of the information transmitted by the Bridge Instance when it is the Root Bridge.
         range : 6 - 40 (seconds), and MaxAge must be <= (FwdDelay-1)*2.
         default: 20."
   ::= { mgs360024fMRSTPInstanceConfigurationEntry 6 }

mgs360024fMRSTPInstanceConfigurationFWDelay OBJECT-TYPE
   SYNTAX      INTEGER(4..30)
   MAX-ACCESS  read-write
   STATUS      current
   DESCRIPTION
       " The delay used by an MRSTP Bridge Instance to transit Root and Designated Ports to Forwarding
        (used in STP compatible mode).
         range : 4 - 30 (seconds), and MaxAge must be <= (FwdDelay-1)*2.
         default: 15."
   ::= { mgs360024fMRSTPInstanceConfigurationEntry 7 }

mgs360024fMRSTPInstanceStatus                                          OBJECT IDENTIFIER ::= { mgs360024fMRSTPInstance 2 }

mgs360024fMRSTPInstanceStatusTable OBJECT-TYPE
   SYNTAX      SEQUENCE OF MGS360024FMRSTPInstanceStatusEntry
   MAX-ACCESS  not-accessible
   STATUS      current
   DESCRIPTION
       " show mrstp status of instance(s). "
   ::= { mgs360024fMRSTPInstanceStatus 1 }

mgs360024fMRSTPInstanceStatusEntry OBJECT-TYPE
   SYNTAX      MGS360024FMRSTPInstanceStatusEntry
   MAX-ACCESS  not-accessible
   STATUS      current
   DESCRIPTION
       ""
   INDEX    { mgs360024fMRSTPInstanceStatusInstance  }
   ::= { mgs360024fMRSTPInstanceStatusTable 1 }

MGS360024FMRSTPInstanceStatusEntry ::= SEQUENCE {
   mgs360024fMRSTPInstanceStatusInstance                        INTEGER,
   mgs360024fMRSTPInstanceStatusGlobalState                     INTEGER,
   mgs360024fMRSTPInstanceStatusInstanceConfigState             INTEGER,
   mgs360024fMRSTPInstanceStatusInstanceCurrentState            INTEGER,
   mgs360024fMRSTPInstanceStatusBridgeID                        MacAddress,
   mgs360024fMRSTPInstanceStatusBridgePrioriry                  INTEGER,
   mgs360024fMRSTPInstanceStatusRootID                          MacAddress,
   mgs360024fMRSTPInstanceStatusRootPriority                    INTEGER,
   mgs360024fMRSTPInstanceStatusRootPort                        INTEGER,
   mgs360024fMRSTPInstanceStatusRootPathCost                    INTEGER,
   mgs360024fMRSTPInstanceStatusCurrentMaxAge                   INTEGER,
   mgs360024fMRSTPInstanceStatusCurrentForwardDelay             INTEGER,
   mgs360024fMRSTPInstanceStatusHelloTime                       INTEGER,
   mgs360024fMRSTPInstanceStatusTopologyChangeCount             INTEGER,
   mgs360024fMRSTPInstanceStatusTimeSinceLastTopologyChange     INTEGER
}

mgs360024fMRSTPInstanceStatusInstance OBJECT-TYPE
   SYNTAX      INTEGER(1..12)
   MAX-ACCESS  not-accessible
   STATUS      current
   DESCRIPTION
       " mrstp instance id, range : 1-12 "
   ::= { mgs360024fMRSTPInstanceStatusEntry 1 }

mgs360024fMRSTPInstanceStatusGlobalState OBJECT-TYPE
   SYNTAX      INTEGER (0|1)
   MAX-ACCESS  read-only
   STATUS      current
   DESCRIPTION
       " The global state of MRSTP. If disabled,all instances won't be in an active state.
         0: disable
         1: enable"
   ::= { mgs360024fMRSTPInstanceStatusEntry 2 }

mgs360024fMRSTPInstanceStatusInstanceConfigState OBJECT-TYPE
   SYNTAX      INTEGER (0|1)
   MAX-ACCESS  read-only
   STATUS      current
   DESCRIPTION
       " The configured state of an MRSTP instance.
         0: disable
         1: enable"
   ::= { mgs360024fMRSTPInstanceStatusEntry 3 }

mgs360024fMRSTPInstanceStatusInstanceCurrentState OBJECT-TYPE
   SYNTAX      INTEGER (0|1)
   MAX-ACCESS  read-only
   STATUS      current
   DESCRIPTION
       " The operational state of an MRSTP Bridge Instance.
         0: disable
         1: enable"
   ::= { mgs360024fMRSTPInstanceStatusEntry 4 }

mgs360024fMRSTPInstanceStatusBridgeID OBJECT-TYPE
   SYNTAX       MacAddress
   MAX-ACCESS   read-only
   STATUS       current
   DESCRIPTION
       " The Bridge ID of this Bridge instance. "
   ::= { mgs360024fMRSTPInstanceStatusEntry 5 }

mgs360024fMRSTPInstanceStatusBridgePrioriry OBJECT-TYPE
   SYNTAX      INTEGER(0..61440)
   MAX-ACCESS  read-only
   STATUS      current
   DESCRIPTION
       " The Bridge Priority of this Bridge instance. Value is shown in decimal.
         range : 0 - 61440 "
   ::= { mgs360024fMRSTPInstanceStatusEntry 6 }

mgs360024fMRSTPInstanceStatusRootID OBJECT-TYPE
   SYNTAX       MacAddress
   MAX-ACCESS   read-only
   STATUS       current
   DESCRIPTION
       " The Bridge ID of the currently elected root bridge. "
   ::= { mgs360024fMRSTPInstanceStatusEntry 7 }

mgs360024fMRSTPInstanceStatusRootPriority OBJECT-TYPE
   SYNTAX      INTEGER(0..61440)
   MAX-ACCESS  read-only
   STATUS      current
   DESCRIPTION
       " The Bridge Priority of the currently elected root bridge. Value is shown in decimal.
         range : 0 - 61440 "
   ::= { mgs360024fMRSTPInstanceStatusEntry 8 }

mgs360024fMRSTPInstanceStatusRootPort OBJECT-TYPE
   SYNTAX      INTEGER
   MAX-ACCESS  read-only
   STATUS      current
   DESCRIPTION
       " The switch port currently assigned the root port role. "
   ::= { mgs360024fMRSTPInstanceStatusEntry 9 }

mgs360024fMRSTPInstanceStatusRootPathCost OBJECT-TYPE
   SYNTAX      INTEGER
   MAX-ACCESS  read-only
   STATUS      current
   DESCRIPTION
       " For the Root Bridge it is zero. For all other Bridges, it is the sum of the Port Path Costs on the least cost path to the Root Bridge. "
   ::= { mgs360024fMRSTPInstanceStatusEntry 10 }

mgs360024fMRSTPInstanceStatusCurrentMaxAge OBJECT-TYPE
   SYNTAX      INTEGER(6..40)
   MAX-ACCESS  read-only
   STATUS      current
   DESCRIPTION
       " The Max Age inherited from the Root Bridge.
         range : 6 - 40 (seconds)"
   ::= { mgs360024fMRSTPInstanceStatusEntry 11 }

mgs360024fMRSTPInstanceStatusCurrentForwardDelay OBJECT-TYPE
   SYNTAX      INTEGER(4..30)
   MAX-ACCESS  read-only
   STATUS      current
   DESCRIPTION
       " The Forward Delay time inherited from the Root Bridge.
         range : 4 - 30 (seconds) "
   ::= { mgs360024fMRSTPInstanceStatusEntry 12 }

mgs360024fMRSTPInstanceStatusHelloTime OBJECT-TYPE
   SYNTAX      INTEGER(1..10)
   MAX-ACCESS  read-only
   STATUS      current
   DESCRIPTION
       " The Hello Time inherited from the Root Bridge.
         range : 1 - 10 (seconds) "
   ::= { mgs360024fMRSTPInstanceStatusEntry 13 }

mgs360024fMRSTPInstanceStatusTopologyChangeCount OBJECT-TYPE
   SYNTAX      INTEGER
   MAX-ACCESS  read-only
   STATUS      current
   DESCRIPTION
       " The Topology Change Count since the MRSTP Bridge Instance is actually enabled. "
   ::= { mgs360024fMRSTPInstanceStatusEntry 14 }

mgs360024fMRSTPInstanceStatusTimeSinceLastTopologyChange OBJECT-TYPE
   SYNTAX      INTEGER
   MAX-ACCESS  read-only
   STATUS      current
   DESCRIPTION
       " The time since last Topology Change occurred. "
   ::= { mgs360024fMRSTPInstanceStatusEntry 15 }

mgs360024fMRSTPPort                                          OBJECT IDENTIFIER ::= { mgs360024fMRSTP 2 }

mgs360024fMRSTPPortConfiguration                                          OBJECT IDENTIFIER ::= { mgs360024fMRSTPPort 1 }

mgs360024fMRSTPPortConfigurationTable OBJECT-TYPE
   SYNTAX      SEQUENCE OF MGS360024FMRSTPPortConfigurationEntry
   MAX-ACCESS  not-accessible
   STATUS      current
   DESCRIPTION
       " current MRSTP port configurations. "
   ::= { mgs360024fMRSTPPortConfiguration 1 }

mgs360024fMRSTPPortConfigurationEntry OBJECT-TYPE
   SYNTAX      MGS360024FMRSTPPortConfigurationEntry
   MAX-ACCESS  not-accessible
   STATUS      current
   DESCRIPTION
       ""
   INDEX    { mgs360024fMRSTPPortConfigurationPort  }
   ::= { mgs360024fMRSTPPortConfigurationTable 1 }

MGS360024FMRSTPPortConfigurationEntry ::= SEQUENCE {
   mgs360024fMRSTPPortConfigurationPort             INTEGER,
   mgs360024fMRSTPPortConfigurationInstance         INTEGER,
   mgs360024fMRSTPPortConfigurationPathCost         INTEGER,
   mgs360024fMRSTPPortConfigurationPriority         INTEGER,
   mgs360024fMRSTPPortConfigurationAdminEdge        INTEGER,
   mgs360024fMRSTPPortConfigurationAdminP2P         INTEGER,
   mgs360024fMRSTPPortConfigurationMigrateCheck     INTEGER
}

mgs360024fMRSTPPortConfigurationPort OBJECT-TYPE
   SYNTAX      INTEGER(1..4095)
   MAX-ACCESS  not-accessible
   STATUS      current
   DESCRIPTION
       " The switch port number of the MRSTP port. "
   ::= { mgs360024fMRSTPPortConfigurationEntry 1 }

mgs360024fMRSTPPortConfigurationInstance OBJECT-TYPE
   SYNTAX      INTEGER(0..61440)
   MAX-ACCESS  read-write
   STATUS      current
   DESCRIPTION
       " MRSTP Bridge Instance. default: 0
         range : 0 - 12, 0: None "
   ::= { mgs360024fMRSTPPortConfigurationEntry 2 }

mgs360024fMRSTPPortConfigurationPathCost OBJECT-TYPE
   SYNTAX      INTEGER(0..200000000)
   MAX-ACCESS  read-write
   STATUS      current
   DESCRIPTION
       " port path cost;when the value is 0,path cost is determined by physical port speed.
         default: 0
         range : 0 - 200000000, 0: Auto"
   ::= { mgs360024fMRSTPPortConfigurationEntry 3 }

mgs360024fMRSTPPortConfigurationPriority OBJECT-TYPE
   SYNTAX      INTEGER(0..240)
   MAX-ACCESS  read-write
   STATUS      current
   DESCRIPTION
       " Port Priority; would be truncated to a multiple of 16.
         default: 128
         range : 0 - 240"
   ::= { mgs360024fMRSTPPortConfigurationEntry 4 }

mgs360024fMRSTPPortConfigurationAdminEdge OBJECT-TYPE
   SYNTAX      INTEGER(0|1)
   MAX-ACCESS  read-write
   STATUS      current
   DESCRIPTION
       " port(s) as edge or non-edge.
         default: 1
         0: non-edge
         1: edge "
   ::= { mgs360024fMRSTPPortConfigurationEntry 5 }

mgs360024fMRSTPPortConfigurationAdminP2P OBJECT-TYPE
   SYNTAX      INTEGER(0..2)
   MAX-ACCESS  read-write
   STATUS      current
   DESCRIPTION
       " administrative point-to-point (p2p) port.
         range : 0 - 2, default: 2
         0: force to be p2p port(s)
         1: force to be non-p2p port(s)
         2: auto-detected according to port duplex "
   ::= { mgs360024fMRSTPPortConfigurationEntry 6 }

mgs360024fMRSTPPortConfigurationMigrateCheck OBJECT-TYPE
   SYNTAX      INTEGER(0|1)
   MAX-ACCESS  read-write
   STATUS      current
   DESCRIPTION
       " default: 0
         0: none
         1: perform migration check on port(s) "
   ::= { mgs360024fMRSTPPortConfigurationEntry 7 }

mgs360024fMRSTPPortStatus                                          OBJECT IDENTIFIER ::= { mgs360024fMRSTPPort 2 }

mgs360024fMRSTPPortStatusTable OBJECT-TYPE
   SYNTAX      SEQUENCE OF MGS360024FMRSTPPortStatusEntry
   MAX-ACCESS  not-accessible
   STATUS      current
   DESCRIPTION
       " show mrstp port information. "
   ::= { mgs360024fMRSTPPortStatus 1 }

mgs360024fMRSTPPortStatusEntry OBJECT-TYPE
   SYNTAX      MGS360024FMRSTPPortStatusEntry
   MAX-ACCESS  not-accessible
   STATUS      current
   DESCRIPTION
       ""
   INDEX    { mgs360024fMRSTPPortStatusPort  }
   ::= { mgs360024fMRSTPPortStatusTable 1 }

MGS360024FMRSTPPortStatusEntry ::= SEQUENCE {
   mgs360024fMRSTPPortStatusPort                INTEGER,
   mgs360024fMRSTPPortStatusInstance            DisplayString,
   mgs360024fMRSTPPortStatusState               DisplayString,
   mgs360024fMRSTPPortStatusRole                DisplayString,
   mgs360024fMRSTPPortStatusPathCost            INTEGER,
   mgs360024fMRSTPPortStatusPathCostConfig      INTEGER,
   mgs360024fMRSTPPortStatusPriority            INTEGER,
   mgs360024fMRSTPPortStatusAdminEdge           DisplayString,
   mgs360024fMRSTPPortStatusAdminP2P            DisplayString
}

mgs360024fMRSTPPortStatusPort OBJECT-TYPE
   SYNTAX      INTEGER(1..4095)
   MAX-ACCESS  not-accessible
   STATUS      current
   DESCRIPTION
       " The switch port number of the MRSTP port. "
   ::= { mgs360024fMRSTPPortStatusEntry 1 }

mgs360024fMRSTPPortStatusInstance OBJECT-TYPE
   SYNTAX      DisplayString
   MAX-ACCESS  read-only
   STATUS      current
   DESCRIPTION
       " MRSTP Bridge Instance. "
   ::= { mgs360024fMRSTPPortStatusEntry 2 }

mgs360024fMRSTPPortStatusState OBJECT-TYPE
   SYNTAX      DisplayString
   MAX-ACCESS  read-only
   STATUS      current
   DESCRIPTION
       " The current RSTP port state. The port state can be one of the following values: DISCARDING LISTENING FORWARDING NON-MRSTP INST-DSBL.
         INST-DSBL indicates that the Bridge Instance the port belongs to is disabled. "
   ::= { mgs360024fMRSTPPortStatusEntry 3 }

mgs360024fMRSTPPortStatusRole OBJECT-TYPE
   SYNTAX      DisplayString
   MAX-ACCESS  read-only
   STATUS      current
   DESCRIPTION
       " The current MRSTP port role. The port role can be one of the following values: disable alternate backup ROOT DSGN none.
         none indicates that the Bridge Instance the port belongs to is disabled or the port is not an MRSTP port.
         DSGN indicates a Designated port role. "
   ::= { mgs360024fMRSTPPortStatusEntry 4 }

mgs360024fMRSTPPortStatusPathCost OBJECT-TYPE
   SYNTAX      INTEGER(0..200000000)
   MAX-ACCESS  read-only
   STATUS      current
   DESCRIPTION
       " path cost. "
   ::= { mgs360024fMRSTPPortStatusEntry 5 }

mgs360024fMRSTPPortStatusPathCostConfig OBJECT-TYPE
   SYNTAX      INTEGER(0..200000000)
   MAX-ACCESS  read-only
   STATUS      current
   DESCRIPTION
       " port path cost config. "
   ::= { mgs360024fMRSTPPortStatusEntry 6 }

mgs360024fMRSTPPortStatusPriority OBJECT-TYPE
   SYNTAX      INTEGER(0..240)
   MAX-ACCESS  read-only
   STATUS      current
   DESCRIPTION
       " port priority. "
   ::= { mgs360024fMRSTPPortStatusEntry 7 }

mgs360024fMRSTPPortStatusAdminEdge OBJECT-TYPE
   SYNTAX      DisplayString
   MAX-ACCESS  read-only
   STATUS      current
   DESCRIPTION
       " port(s) as edge or non-edge. "
   ::= { mgs360024fMRSTPPortStatusEntry 8 }

mgs360024fMRSTPPortStatusAdminP2P OBJECT-TYPE
   SYNTAX      DisplayString
   MAX-ACCESS  read-only
   STATUS      current
   DESCRIPTION
       " administrative point-to-point (p2p) port. "
   ::= { mgs360024fMRSTPPortStatusEntry 9 }

----------------------------------------------------------------------------------------------------------------------------
mgs360024fSecurity                                              OBJECT IDENTIFIER ::= { mgs360024fProductId 3 }

mgs360024fIPSourceGuard                                         OBJECT IDENTIFIER ::= { mgs360024fSecurity 1 }

mgs360024fIPSourceGuardConf                                     OBJECT IDENTIFIER ::= { mgs360024fIPSourceGuard 1 }

mgs360024fIPSourceGuardMode OBJECT-TYPE
   SYNTAX      INTEGER (0|1)
   MAX-ACCESS  read-write
   STATUS      current
   DESCRIPTION
       " default:  0
        0: disable
        1: enable"
   ::= { mgs360024fIPSourceGuardConf 1 }

mgs360024fIPSourceGuardPortConfigTable OBJECT-TYPE
   SYNTAX      SEQUENCE OF MGS360024FIPSourceGuardPortConfigEntry
   MAX-ACCESS  not-accessible
   STATUS      current
   DESCRIPTION
       " "
   ::= { mgs360024fIPSourceGuardConf 2 }

mgs360024fIPSourceGuardPortConfigEntry OBJECT-TYPE
   SYNTAX      MGS360024FIPSourceGuardPortConfigEntry
   MAX-ACCESS  not-accessible
   STATUS      current
   DESCRIPTION
       ""
   INDEX    { mgs360024fIPSourceGuardPortConfigPort  }
   ::= { mgs360024fIPSourceGuardPortConfigTable 1 }

MGS360024FIPSourceGuardPortConfigEntry ::= SEQUENCE {
   mgs360024fIPSourceGuardPortConfigPort               INTEGER,
   mgs360024fIPSourceGuardPortConfigMode               INTEGER,
   mgs360024fIPSourceGuardPortMaxDynamicClients        INTEGER
}

mgs360024fIPSourceGuardPortConfigPort OBJECT-TYPE
   SYNTAX      INTEGER (1..4095)
   MAX-ACCESS  not-accessible
   STATUS      current
   DESCRIPTION
       " "
   ::= { mgs360024fIPSourceGuardPortConfigEntry 1 }

mgs360024fIPSourceGuardPortConfigMode OBJECT-TYPE
   SYNTAX      INTEGER (0|1)
   MAX-ACCESS  read-write
   STATUS      current
   DESCRIPTION
       "default: 0
       0:disable
       1:enable "
   ::= { mgs360024fIPSourceGuardPortConfigEntry 2 }

mgs360024fIPSourceGuardPortMaxDynamicClients OBJECT-TYPE
   SYNTAX      INTEGER (0..2|99)
   MAX-ACCESS  read-write
   STATUS      current
   DESCRIPTION
       "default: 99
       0~2: Max Dynamic clients
       99:Unlimited "
   ::= { mgs360024fIPSourceGuardPortConfigEntry 3 }


mgs360024fIPSourceGuardStatic                                OBJECT IDENTIFIER ::= { mgs360024fIPSourceGuard 2 }

mgs360024fIPSourceGuardStaticCreate OBJECT-TYPE
   SYNTAX       INTEGER(0|1)
   MAX-ACCESS   read-write
   STATUS       current
   DESCRIPTION
       "default: 0
        0 : None  (read only)
        1 : Create a IP Source Guard"
   ::= { mgs360024fIPSourceGuardStatic 1 }

mgs360024fIPSourceGuardStaticTable OBJECT-TYPE
   SYNTAX      SEQUENCE OF MGS360024FIPSourceGuardStaticEntry
   MAX-ACCESS  not-accessible
   STATUS      current
   DESCRIPTION
       " "
   ::= { mgs360024fIPSourceGuardStatic 2 }

mgs360024fIPSourceGuardStaticEntry OBJECT-TYPE
   SYNTAX      MGS360024FIPSourceGuardStaticEntry
   MAX-ACCESS  not-accessible
   STATUS      current
   DESCRIPTION
       ""
   INDEX    { mgs360024fIPSourceGuardStaticIndex  }
   ::= { mgs360024fIPSourceGuardStaticTable 1 }

MGS360024FIPSourceGuardStaticEntry ::= SEQUENCE {
   mgs360024fIPSourceGuardStaticIndex         INTEGER,
   mgs360024fIPSourceGuardStaticPort          INTEGER,
   mgs360024fIPSourceGuardStaticVLANId        INTEGER,
   mgs360024fIPSourceGuardStaticIPAddress     IpAddress,
   mgs360024fIPSourceGuardStaticMACAddress    MacAddress,
   mgs360024fIPSourceGuardStaticRowStatus     INTEGER
}

mgs360024fIPSourceGuardStaticIndex OBJECT-TYPE
   SYNTAX      INTEGER (1..28)
   MAX-ACCESS  not-accessible
   STATUS      current
   DESCRIPTION
       " "
   ::= { mgs360024fIPSourceGuardStaticEntry 1 }

mgs360024fIPSourceGuardStaticPort OBJECT-TYPE
   SYNTAX      INTEGER (1..4095)
   MAX-ACCESS  read-write
   STATUS      current
   DESCRIPTION
       " Port, range: 1 - port number. "
   ::= { mgs360024fIPSourceGuardStaticEntry 2 }

mgs360024fIPSourceGuardStaticVLANId OBJECT-TYPE
   SYNTAX      INTEGER (1..4094)
   MAX-ACCESS  read-write
   STATUS      current
   DESCRIPTION
       " VLAN ID, range: 1 - 4094. "
   ::= { mgs360024fIPSourceGuardStaticEntry 3 }

mgs360024fIPSourceGuardStaticIPAddress OBJECT-TYPE
   SYNTAX      IpAddress
   MAX-ACCESS  read-write
   STATUS      current
   DESCRIPTION
       " IP address allowed for doing IP source guard. "
   ::= { mgs360024fIPSourceGuardStaticEntry 4 }

mgs360024fIPSourceGuardStaticMACAddress OBJECT-TYPE
   SYNTAX      MacAddress
   MAX-ACCESS  read-write
   STATUS      current
   DESCRIPTION
       " Allowed Source MAC address, format 0a 1b 2c 3d 4e 5f "
   ::= { mgs360024fIPSourceGuardStaticEntry 5 }

mgs360024fIPSourceGuardStaticRowStatus OBJECT-TYPE
   SYNTAX      INTEGER (1..5)
   MAX-ACCESS  read-write
   STATUS      current
   DESCRIPTION
       "1: active
        2: notInservice
        3: edit
        4: destroy
        5: undo"
   ::= { mgs360024fIPSourceGuardStaticEntry 6 }

mgs360024fIPSourceGuardDynamicTable OBJECT-TYPE
   SYNTAX      SEQUENCE OF MGS360024FIPSourceGuardDynamicEntry
   MAX-ACCESS  not-accessible
   STATUS      current
   DESCRIPTION
       " "
   ::= { mgs360024fIPSourceGuard 3 }

mgs360024fIPSourceGuardDynamicEntry OBJECT-TYPE
   SYNTAX      MGS360024FIPSourceGuardDynamicEntry
   MAX-ACCESS  not-accessible
   STATUS      current
   DESCRIPTION
       ""
   INDEX    { mgs360024fIPSourceGuardDynamicIndex  }
   ::= { mgs360024fIPSourceGuardDynamicTable 1 }

MGS360024FIPSourceGuardDynamicEntry ::= SEQUENCE {
   mgs360024fIPSourceGuardDynamicIndex		    INTEGER,
   mgs360024fIPSourceGuardDynamicPort		    INTEGER,
   mgs360024fIPSourceGuardDynamicVLANId		    INTEGER,
   mgs360024fIPSourceGuardDynamicIPAddress		IpAddress,
   mgs360024fIPSourceGuardDynamicMACAddress		MacAddress
}

mgs360024fIPSourceGuardDynamicIndex OBJECT-TYPE
   SYNTAX      INTEGER(1..4095)
   MAX-ACCESS  not-accessible
   STATUS      current
   DESCRIPTION
       " "
   ::= { mgs360024fIPSourceGuardDynamicEntry 1 }

mgs360024fIPSourceGuardDynamicPort OBJECT-TYPE
   SYNTAX      INTEGER (1..10)
   MAX-ACCESS  read-only
   STATUS      current
   DESCRIPTION
       " "
   ::= { mgs360024fIPSourceGuardDynamicEntry 2 }

mgs360024fIPSourceGuardDynamicVLANId OBJECT-TYPE
   SYNTAX      INTEGER (1..4094)
   MAX-ACCESS  read-only
   STATUS      current
   DESCRIPTION
       " "
   ::= { mgs360024fIPSourceGuardDynamicEntry 3 }

mgs360024fIPSourceGuardDynamicIPAddress OBJECT-TYPE
   SYNTAX      IpAddress
   MAX-ACCESS  read-only
   STATUS      current
   DESCRIPTION
       " "
   ::= { mgs360024fIPSourceGuardDynamicEntry 4 }

mgs360024fIPSourceGuardDynamicMACAddress OBJECT-TYPE
   SYNTAX      MacAddress
   MAX-ACCESS  read-only
   STATUS      current
   DESCRIPTION
       " "
   ::= { mgs360024fIPSourceGuardDynamicEntry 5 }

mgs360024fARPInspection                                         OBJECT IDENTIFIER ::= { mgs360024fSecurity 2 }

mgs360024fARPInspectionConf                                     OBJECT IDENTIFIER ::= { mgs360024fARPInspection 1 }

mgs360024fARPInspectionConfMode OBJECT-TYPE
   SYNTAX      INTEGER(0|1)
   MAX-ACCESS  read-write
   STATUS      current
   DESCRIPTION
       "default: 0
        0: disable
        1: enable"
   ::= { mgs360024fARPInspectionConf 1 }

mgs360024fARPInspectionConfTable OBJECT-TYPE
   SYNTAX      SEQUENCE OF MGS360024FARPInspectionConfEntry
   MAX-ACCESS  not-accessible
   STATUS      current
   DESCRIPTION
       " "
   ::= { mgs360024fARPInspectionConf 2 }

mgs360024fARPInspectionConfEntry OBJECT-TYPE
   SYNTAX      MGS360024FARPInspectionConfEntry
   MAX-ACCESS  not-accessible
   STATUS      current
   DESCRIPTION
       ""
   INDEX    { mgs360024fARPInspectionConfPortIndex  }
   ::= { mgs360024fARPInspectionConfTable 1 }

MGS360024FARPInspectionConfEntry ::= SEQUENCE {
   mgs360024fARPInspectionConfPortIndex	INTEGER,
   mgs360024fARPInspectionConfPortMode	INTEGER
}

mgs360024fARPInspectionConfPortIndex OBJECT-TYPE
   SYNTAX      INTEGER(1..4095)
   MAX-ACCESS  not-accessible
   STATUS      current
   DESCRIPTION
       " "
   ::= { mgs360024fARPInspectionConfEntry 1 }

mgs360024fARPInspectionConfPortMode OBJECT-TYPE
   SYNTAX      INTEGER (0|1)
   MAX-ACCESS  read-write
   STATUS      current
   DESCRIPTION
       "default: 0
        0: disable
        1: enable"
   ::= { mgs360024fARPInspectionConfEntry 2 }


mgs360024fARPInspectionStatic                                OBJECT IDENTIFIER ::= { mgs360024fARPInspection 2 }

mgs360024fARPInspectionStaticCreate OBJECT-TYPE
   SYNTAX      INTEGER (0|1)
   MAX-ACCESS  read-write
   STATUS      current
   DESCRIPTION
       "default: 0
        0: none
        1: create"
   ::= { mgs360024fARPInspectionStatic 1 }

mgs360024fARPInspectionStaticTable OBJECT-TYPE
   SYNTAX      SEQUENCE OF MGS360024FARPInspectionStaticEntry
   MAX-ACCESS  not-accessible
   STATUS      current
   DESCRIPTION
       " "
   ::= { mgs360024fARPInspectionStatic 2 }

mgs360024fARPInspectionStaticEntry OBJECT-TYPE
   SYNTAX      MGS360024FARPInspectionStaticEntry
   MAX-ACCESS  not-accessible
   STATUS      current
   DESCRIPTION
       ""
   INDEX    { mgs360024fARPInspectionStaticIndex  }
   ::= { mgs360024fARPInspectionStaticTable 1 }

MGS360024FARPInspectionStaticEntry ::= SEQUENCE {
   mgs360024fARPInspectionStaticIndex        INTEGER,
   mgs360024fARPInspectionStaticPort         INTEGER,
   mgs360024fARPInspectionStaticVLANId       INTEGER,
   mgs360024fARPInspectionStaticIPAddress	IpAddress,
   mgs360024fARPInspectionStaticMACAddress	MacAddress,
   mgs360024fARPInspectionStaticRowStatus	INTEGER
}

mgs360024fARPInspectionStaticIndex OBJECT-TYPE
   SYNTAX      INTEGER(1..4095)
   MAX-ACCESS  not-accessible
   STATUS      current
   DESCRIPTION
       ""
   ::= { mgs360024fARPInspectionStaticEntry 1 }

mgs360024fARPInspectionStaticPort OBJECT-TYPE
   SYNTAX      INTEGER(1..4095)
   MAX-ACCESS  read-write
   STATUS      current
   DESCRIPTION
       " Port, range: 1 - port number. "
   ::= { mgs360024fARPInspectionStaticEntry 2 }

mgs360024fARPInspectionStaticVLANId OBJECT-TYPE
   SYNTAX      INTEGER (1..4094)
   MAX-ACCESS  read-write
   STATUS      current
   DESCRIPTION
       " VLAN ID, range: 1 - 4094. "
   ::= { mgs360024fARPInspectionStaticEntry 3 }

mgs360024fARPInspectionStaticIPAddress OBJECT-TYPE
   SYNTAX      IpAddress
   MAX-ACCESS  read-write
   STATUS      current
   DESCRIPTION
       " IP address allowed for doing ARP request. "
   ::= { mgs360024fARPInspectionStaticEntry 4 }

mgs360024fARPInspectionStaticMACAddress OBJECT-TYPE
   SYNTAX      MacAddress
   MAX-ACCESS  read-write
   STATUS      current
   DESCRIPTION
       " Allowed Source MAC address in ARP request packets, format 0a 1b 2c 3d 4e 5f "
   ::= { mgs360024fARPInspectionStaticEntry 5 }

mgs360024fARPInspectionStaticRowStatus OBJECT-TYPE
   SYNTAX      INTEGER(1..5)
   MAX-ACCESS  read-write
   STATUS      current
   DESCRIPTION
       "1: active
        2: notInservice
        3: edit
        4: destroy
        5: undo"
   ::= { mgs360024fARPInspectionStaticEntry 6 }

mgs360024fARPInspectionDynamicTable OBJECT-TYPE
   SYNTAX      SEQUENCE OF MGS360024FARPInspectionDynamicEntry
   MAX-ACCESS  not-accessible
   STATUS      current
   DESCRIPTION
       " "
   ::= { mgs360024fARPInspection 3 }

mgs360024fARPInspectionDynamicEntry OBJECT-TYPE
   SYNTAX      MGS360024FARPInspectionDynamicEntry
   MAX-ACCESS  not-accessible
   STATUS      current
   DESCRIPTION
       ""
   INDEX    { mgs360024fARPInspectionDynamicIndex  }
   ::= { mgs360024fARPInspectionDynamicTable 1 }

MGS360024FARPInspectionDynamicEntry ::= SEQUENCE {
   mgs360024fARPInspectionDynamicIndex		    INTEGER,
   mgs360024fARPInspectionDynamicPort		    INTEGER,
   mgs360024fARPInspectionDynamicVLANId		    INTEGER,
   mgs360024fARPInspectionDynamicIPAddress		IpAddress,
   mgs360024fARPInspectionDynamicMACAddress		MacAddress
}

mgs360024fARPInspectionDynamicIndex OBJECT-TYPE
   SYNTAX      INTEGER(1..4095)
   MAX-ACCESS  not-accessible
   STATUS      current
   DESCRIPTION
       " "
   ::= { mgs360024fARPInspectionDynamicEntry 1 }

mgs360024fARPInspectionDynamicPort OBJECT-TYPE
   SYNTAX      INTEGER(1..4095)
   MAX-ACCESS  read-only
   STATUS      current
   DESCRIPTION
       ""
   ::= { mgs360024fARPInspectionDynamicEntry 2 }

mgs360024fARPInspectionDynamicVLANId OBJECT-TYPE
   SYNTAX      INTEGER (1..4094)
   MAX-ACCESS  read-only
   STATUS      current
   DESCRIPTION
       ""
   ::= { mgs360024fARPInspectionDynamicEntry 3 }

mgs360024fARPInspectionDynamicIPAddress OBJECT-TYPE
   SYNTAX      IpAddress
   MAX-ACCESS  read-only
   STATUS      current
   DESCRIPTION
       ""
   ::= { mgs360024fARPInspectionDynamicEntry 4 }

mgs360024fARPInspectionDynamicMACAddress OBJECT-TYPE
   SYNTAX      MacAddress
   MAX-ACCESS  read-only
   STATUS      current
   DESCRIPTION
       ""
   ::= { mgs360024fARPInspectionDynamicEntry 5 }

mgs360024fDHCPSnooping                                          OBJECT IDENTIFIER ::= { mgs360024fSecurity 3 }

mgs360024fDHCPSnoopingConf                                          OBJECT IDENTIFIER ::= { mgs360024fDHCPSnooping 1 }

mgs360024fDHCPSnoopingMode OBJECT-TYPE
   SYNTAX      INTEGER(0|1)
   MAX-ACCESS  read-write
   STATUS      current
   DESCRIPTION
       "default: 0
       0: disable
       1: enable"
   ::= { mgs360024fDHCPSnoopingConf 1 }

mgs360024fDHCPSnoopingPortModeConfigurationTable OBJECT-TYPE
   SYNTAX      SEQUENCE OF MGS360024FDHCPSnoopingPortModeConfigurationEntry
   MAX-ACCESS  not-accessible
   STATUS      current
   DESCRIPTION
       " "
   ::= { mgs360024fDHCPSnoopingConf 2 }

mgs360024fDHCPSnoopingPortModeConfigurationEntry OBJECT-TYPE
   SYNTAX      MGS360024FDHCPSnoopingPortModeConfigurationEntry
   MAX-ACCESS  not-accessible
   STATUS      current
   DESCRIPTION
       ""
   INDEX    { mgs360024fDHCPSnoopingPortModeConfigurationPort  }
   ::= { mgs360024fDHCPSnoopingPortModeConfigurationTable 1 }

MGS360024FDHCPSnoopingPortModeConfigurationEntry ::= SEQUENCE {
   mgs360024fDHCPSnoopingPortModeConfigurationPort	INTEGER,
   mgs360024fDHCPSnoopingPortModeConfigurationMode	INTEGER
}

mgs360024fDHCPSnoopingPortModeConfigurationPort OBJECT-TYPE
   SYNTAX      INTEGER(1..4095)
   MAX-ACCESS  not-accessible
   STATUS      current
   DESCRIPTION
       " "
   ::= { mgs360024fDHCPSnoopingPortModeConfigurationEntry 1 }

mgs360024fDHCPSnoopingPortModeConfigurationMode OBJECT-TYPE
   SYNTAX      INTEGER (0|1)
   MAX-ACCESS  read-write
   STATUS      current
   DESCRIPTION
       "default: 1
       0: trust port mode
       1: untrust port mode"
   ::= { mgs360024fDHCPSnoopingPortModeConfigurationEntry 2 }

mgs360024fDHCPSnoopingStatisticsTable OBJECT-TYPE
   SYNTAX      SEQUENCE OF MGS360024FDHCPSnoopingStatisticsEntry
   MAX-ACCESS  not-accessible
   STATUS      current
   DESCRIPTION
       " "
   ::= { mgs360024fDHCPSnooping 2 }

mgs360024fDHCPSnoopingStatisticsEntry OBJECT-TYPE
   SYNTAX      MGS360024FDHCPSnoopingStatisticsEntry
   MAX-ACCESS  not-accessible
   STATUS      current
   DESCRIPTION
       ""
   INDEX    { mgs360024fDHCPSnoopingStatisticsPort  }
   ::= { mgs360024fDHCPSnoopingStatisticsTable 1 }

MGS360024FDHCPSnoopingStatisticsEntry ::= SEQUENCE {
   mgs360024fDHCPSnoopingStatisticsPort         INTEGER,
   mgs360024fDHCPSnoopingStatisticsClear        INTEGER,
   mgs360024fDHCPSnoopingRxDiscover             Counter32,
   mgs360024fDHCPSnoopingRxOffer                Counter32,
   mgs360024fDHCPSnoopingRxRequest              Counter32,
   mgs360024fDHCPSnoopingRxDecline              Counter32,
   mgs360024fDHCPSnoopingRxACK                  Counter32,
   mgs360024fDHCPSnoopingRxNAK                  Counter32,
   mgs360024fDHCPSnoopingRxRelease              Counter32,
   mgs360024fDHCPSnoopingRxInform               Counter32,
   mgs360024fDHCPSnoopingRxLeaseQuery           Counter32,
   mgs360024fDHCPSnoopingRxLeaseUnassigned      Counter32,
   mgs360024fDHCPSnoopingRxLeaseUnknown         Counter32,
   mgs360024fDHCPSnoopingRxLeaseActive          Counter32,
   mgs360024fDHCPSnoopingTxDiscover             Counter32,
   mgs360024fDHCPSnoopingTxOffer                Counter32,
   mgs360024fDHCPSnoopingTxRequest              Counter32,
   mgs360024fDHCPSnoopingTxDecline              Counter32,
   mgs360024fDHCPSnoopingTxACK                  Counter32,
   mgs360024fDHCPSnoopingTxNAK                  Counter32,
   mgs360024fDHCPSnoopingTxRelease              Counter32,
   mgs360024fDHCPSnoopingTxInform               Counter32,
   mgs360024fDHCPSnoopingTxLeaseQuery           Counter32,
   mgs360024fDHCPSnoopingTxLeaseUnassigned      Counter32,
   mgs360024fDHCPSnoopingTxLeaseUnknown         Counter32,
   mgs360024fDHCPSnoopingTxLeaseActive          Counter32
}

mgs360024fDHCPSnoopingStatisticsPort OBJECT-TYPE
   SYNTAX      INTEGER(1..4095)
   MAX-ACCESS  not-accessible
   STATUS      current
   DESCRIPTION
       " "
   ::= { mgs360024fDHCPSnoopingStatisticsEntry 1 }

mgs360024fDHCPSnoopingStatisticsClear OBJECT-TYPE
   SYNTAX      INTEGER (0|1)
   MAX-ACCESS  read-write
   STATUS      current
   DESCRIPTION
       "default: 0
       0: none
       1: clear"
   ::= { mgs360024fDHCPSnoopingStatisticsEntry 2 }

mgs360024fDHCPSnoopingRxDiscover OBJECT-TYPE
   SYNTAX      Counter32
   MAX-ACCESS  read-only
   STATUS      current
   DESCRIPTION
       " "
   ::= { mgs360024fDHCPSnoopingStatisticsEntry 3 }

mgs360024fDHCPSnoopingRxOffer OBJECT-TYPE
   SYNTAX      Counter32
   MAX-ACCESS  read-only
   STATUS      current
   DESCRIPTION
       " "
   ::= { mgs360024fDHCPSnoopingStatisticsEntry 4 }

mgs360024fDHCPSnoopingRxRequest OBJECT-TYPE
   SYNTAX      Counter32
   MAX-ACCESS  read-only
   STATUS      current
   DESCRIPTION
       " "
   ::= { mgs360024fDHCPSnoopingStatisticsEntry 5 }

mgs360024fDHCPSnoopingRxDecline OBJECT-TYPE
   SYNTAX      Counter32
   MAX-ACCESS  read-only
   STATUS      current
   DESCRIPTION
       " "
   ::= { mgs360024fDHCPSnoopingStatisticsEntry 6 }

mgs360024fDHCPSnoopingRxACK OBJECT-TYPE
   SYNTAX      Counter32
   MAX-ACCESS  read-only
   STATUS      current
   DESCRIPTION
       " "
   ::= { mgs360024fDHCPSnoopingStatisticsEntry 7 }

mgs360024fDHCPSnoopingRxNAK OBJECT-TYPE
   SYNTAX      Counter32
   MAX-ACCESS  read-only
   STATUS      current
   DESCRIPTION
       " "
   ::= { mgs360024fDHCPSnoopingStatisticsEntry 8 }

mgs360024fDHCPSnoopingRxRelease OBJECT-TYPE
   SYNTAX      Counter32
   MAX-ACCESS  read-only
   STATUS      current
   DESCRIPTION
       " "
   ::= { mgs360024fDHCPSnoopingStatisticsEntry 9 }

mgs360024fDHCPSnoopingRxInform OBJECT-TYPE
   SYNTAX      Counter32
   MAX-ACCESS  read-only
   STATUS      current
   DESCRIPTION
       " "
   ::= { mgs360024fDHCPSnoopingStatisticsEntry 10 }

mgs360024fDHCPSnoopingRxLeaseQuery OBJECT-TYPE
   SYNTAX      Counter32
   MAX-ACCESS  read-only
   STATUS      current
   DESCRIPTION
       " "
   ::= { mgs360024fDHCPSnoopingStatisticsEntry 11 }

mgs360024fDHCPSnoopingRxLeaseUnassigned OBJECT-TYPE
   SYNTAX      Counter32
   MAX-ACCESS  read-only
   STATUS      current
   DESCRIPTION
       " "
   ::= { mgs360024fDHCPSnoopingStatisticsEntry 12 }

mgs360024fDHCPSnoopingRxLeaseUnknown OBJECT-TYPE
   SYNTAX      Counter32
   MAX-ACCESS  read-only
   STATUS      current
   DESCRIPTION
       " "
   ::= { mgs360024fDHCPSnoopingStatisticsEntry 13 }

mgs360024fDHCPSnoopingRxLeaseActive OBJECT-TYPE
   SYNTAX      Counter32
   MAX-ACCESS  read-only
   STATUS      current
   DESCRIPTION
       " "
   ::= { mgs360024fDHCPSnoopingStatisticsEntry 14 }

mgs360024fDHCPSnoopingTxDiscover OBJECT-TYPE
   SYNTAX      Counter32
   MAX-ACCESS  read-only
   STATUS      current
   DESCRIPTION
       " "
   ::= { mgs360024fDHCPSnoopingStatisticsEntry 15 }

mgs360024fDHCPSnoopingTxOffer OBJECT-TYPE
   SYNTAX      Counter32
   MAX-ACCESS  read-only
   STATUS      current
   DESCRIPTION
       " "
   ::= { mgs360024fDHCPSnoopingStatisticsEntry 16 }

mgs360024fDHCPSnoopingTxRequest OBJECT-TYPE
   SYNTAX      Counter32
   MAX-ACCESS  read-only
   STATUS      current
   DESCRIPTION
       " "
   ::= { mgs360024fDHCPSnoopingStatisticsEntry 17 }

mgs360024fDHCPSnoopingTxDecline OBJECT-TYPE
   SYNTAX      Counter32
   MAX-ACCESS  read-only
   STATUS      current
   DESCRIPTION
       " "
   ::= { mgs360024fDHCPSnoopingStatisticsEntry 18 }

mgs360024fDHCPSnoopingTxACK OBJECT-TYPE
   SYNTAX      Counter32
   MAX-ACCESS  read-only
   STATUS      current
   DESCRIPTION
       " "
   ::= { mgs360024fDHCPSnoopingStatisticsEntry 19 }

mgs360024fDHCPSnoopingTxNAK OBJECT-TYPE
   SYNTAX      Counter32
   MAX-ACCESS  read-only
   STATUS      current
   DESCRIPTION
       " "
   ::= { mgs360024fDHCPSnoopingStatisticsEntry 20 }

mgs360024fDHCPSnoopingTxRelease OBJECT-TYPE
   SYNTAX      Counter32
   MAX-ACCESS  read-only
   STATUS      current
   DESCRIPTION
       " "
   ::= { mgs360024fDHCPSnoopingStatisticsEntry 21 }

mgs360024fDHCPSnoopingTxInform OBJECT-TYPE
   SYNTAX      Counter32
   MAX-ACCESS  read-only
   STATUS      current
   DESCRIPTION
       " "
   ::= { mgs360024fDHCPSnoopingStatisticsEntry 22 }

mgs360024fDHCPSnoopingTxLeaseQuery OBJECT-TYPE
   SYNTAX      Counter32
   MAX-ACCESS  read-only
   STATUS      current
   DESCRIPTION
       " "
   ::= { mgs360024fDHCPSnoopingStatisticsEntry 23 }

mgs360024fDHCPSnoopingTxLeaseUnassigned OBJECT-TYPE
   SYNTAX      Counter32
   MAX-ACCESS  read-only
   STATUS      current
   DESCRIPTION
       " "
   ::= { mgs360024fDHCPSnoopingStatisticsEntry 24 }

mgs360024fDHCPSnoopingTxLeaseUnknown OBJECT-TYPE
   SYNTAX      Counter32
   MAX-ACCESS  read-only
   STATUS      current
   DESCRIPTION
       " "
   ::= { mgs360024fDHCPSnoopingStatisticsEntry 25 }

mgs360024fDHCPSnoopingTxLeaseActive OBJECT-TYPE
   SYNTAX      Counter32
   MAX-ACCESS  read-only
   STATUS      current
   DESCRIPTION
       " "
   ::= { mgs360024fDHCPSnoopingStatisticsEntry 26 }


mgs360024fDHCPRelay                                             OBJECT IDENTIFIER ::= { mgs360024fSecurity 4 }

mgs360024fDHCPRelayConfiguration                                         OBJECT IDENTIFIER ::= { mgs360024fDHCPRelay 1 }

mgs360024fDHCPRelayMode OBJECT-TYPE
   SYNTAX      INTEGER(0|1)
   MAX-ACCESS  read-write
   STATUS      current
   DESCRIPTION
       "default: 0
       0: disable
       1: enable
       We need at least one server"
   ::= { mgs360024fDHCPRelayConfiguration 1 }

mgs360024fDHCPRelayServer OBJECT-TYPE
   SYNTAX      IpAddress
   MAX-ACCESS  read-write
   STATUS      current
   DESCRIPTION
       " "
   ::= { mgs360024fDHCPRelayConfiguration 2 }

mgs360024fDHCPRelayInformationMode OBJECT-TYPE
   SYNTAX      INTEGER(0|1)
   MAX-ACCESS  read-write
   STATUS      current
   DESCRIPTION
       "default: 0
       0: disable
       1: enable "
   ::= { mgs360024fDHCPRelayConfiguration 3 }

mgs360024fDHCPRelayInformationPolicy OBJECT-TYPE
   SYNTAX      INTEGER(0..2)
   MAX-ACCESS  read-write
   STATUS      current
   DESCRIPTION
       "default: 0
       0: replace
       1: keep
       2: drop "
   ::= { mgs360024fDHCPRelayConfiguration 4 }

mgs360024fDHCPRelayStatistics                                   OBJECT IDENTIFIER ::= { mgs360024fDHCPRelay 2 }

mgs360024fDHCPRelayServerStatistics                                   OBJECT IDENTIFIER ::= { mgs360024fDHCPRelayStatistics 1 }

mgs360024fServerStatTransmitToServer OBJECT-TYPE
   SYNTAX      Counter32
   MAX-ACCESS  read-only
   STATUS      current
   DESCRIPTION
       " "
   ::= { mgs360024fDHCPRelayServerStatistics 1 }

mgs360024fServerStatTransmitError OBJECT-TYPE
   SYNTAX      Counter32
   MAX-ACCESS  read-only
   STATUS      current
   DESCRIPTION
       " "
   ::= { mgs360024fDHCPRelayServerStatistics 2 }

mgs360024fServerStatReceiveFromServer OBJECT-TYPE
   SYNTAX      Counter32
   MAX-ACCESS  read-only
   STATUS      current
   DESCRIPTION
       " "
   ::= { mgs360024fDHCPRelayServerStatistics 3 }

mgs360024fServerStatReceiveMissingAgentOption OBJECT-TYPE
   SYNTAX      Counter32
   MAX-ACCESS  read-only
   STATUS      current
   DESCRIPTION
       " "
   ::= { mgs360024fDHCPRelayServerStatistics 4 }

mgs360024fServerStatReceiveMissingCircuitID OBJECT-TYPE
   SYNTAX      Counter32
   MAX-ACCESS  read-only
   STATUS      current
   DESCRIPTION
       " "
   ::= { mgs360024fDHCPRelayServerStatistics 5 }

mgs360024fServerStatReceiveMissingRemoteID OBJECT-TYPE
   SYNTAX      Counter32
   MAX-ACCESS  read-only
   STATUS      current
   DESCRIPTION
       " "
   ::= { mgs360024fDHCPRelayServerStatistics 6 }

mgs360024fServerStatReceiveBadCircuitID OBJECT-TYPE
   SYNTAX      Counter32
   MAX-ACCESS  read-only
   STATUS      current
   DESCRIPTION
       " "
   ::= { mgs360024fDHCPRelayServerStatistics 7 }

mgs360024fServerStatReceiveBadRemoteID OBJECT-TYPE
   SYNTAX      Counter32
   MAX-ACCESS  read-only
   STATUS      current
   DESCRIPTION
       " "
   ::= { mgs360024fDHCPRelayServerStatistics 8 }

mgs360024fDHCPRelayClientStatistics                                   OBJECT IDENTIFIER ::= { mgs360024fDHCPRelayStatistics 2 }

mgs360024fClientStatTransmitToClient OBJECT-TYPE
   SYNTAX      Counter32
   MAX-ACCESS  read-only
   STATUS      current
   DESCRIPTION
       " "
   ::= { mgs360024fDHCPRelayClientStatistics 1 }

mgs360024fClientStatTransmitError OBJECT-TYPE
   SYNTAX      Counter32
   MAX-ACCESS  read-only
   STATUS      current
   DESCRIPTION
       " "
   ::= { mgs360024fDHCPRelayClientStatistics 2 }

mgs360024fClientStatReceivefromClient OBJECT-TYPE
   SYNTAX      Counter32
   MAX-ACCESS  read-only
   STATUS      current
   DESCRIPTION
       " "
   ::= { mgs360024fDHCPRelayClientStatistics 3 }

mgs360024fClientStatReceiveAgentOption OBJECT-TYPE
   SYNTAX      Counter32
   MAX-ACCESS  read-only
   STATUS      current
   DESCRIPTION
       " "
   ::= { mgs360024fDHCPRelayClientStatistics 4 }

mgs360024fClientStatReplaceAgentOption OBJECT-TYPE
   SYNTAX      Counter32
   MAX-ACCESS  read-only
   STATUS      current
   DESCRIPTION
       " "
   ::= { mgs360024fDHCPRelayClientStatistics 5 }

mgs360024fClientStatKeepAgentOption OBJECT-TYPE
   SYNTAX      Counter32
   MAX-ACCESS  read-only
   STATUS      current
   DESCRIPTION
       " "
   ::= { mgs360024fDHCPRelayClientStatistics 6 }

mgs360024fClientStatDropAgentOption OBJECT-TYPE
   SYNTAX      Counter32
   MAX-ACCESS  read-only
   STATUS      current
   DESCRIPTION
       " "
   ::= { mgs360024fDHCPRelayClientStatistics 7 }

mgs360024fPortSecurity                                          OBJECT IDENTIFIER ::= { mgs360024fSecurity 5 }

mgs360024fPortSecLimitCtrl                                      OBJECT IDENTIFIER ::= { mgs360024fPortSecurity 1 }

mgs360024fPortSecLimitCtrlSystemConf                                      OBJECT IDENTIFIER ::= { mgs360024fPortSecLimitCtrl 1 }

mgs360024fPortSecurityMode OBJECT-TYPE
   SYNTAX      INTEGER(0|1)
   MAX-ACCESS  read-write
   STATUS      current
   DESCRIPTION
       "default: 0
       0: disable
       1: enable "
   ::= { mgs360024fPortSecLimitCtrlSystemConf 1 }

mgs360024fPortSecurityAging OBJECT-TYPE
   SYNTAX      INTEGER(0|1)
   MAX-ACCESS  read-write
   STATUS      current
   DESCRIPTION
       "default: 0
       0: disable
       1: enable "
   ::= { mgs360024fPortSecLimitCtrlSystemConf 2 }

mgs360024fPortSecurityAgingPeriod OBJECT-TYPE
   SYNTAX      INTEGER(10..10000000)
   MAX-ACCESS  read-write
   STATUS      current
   DESCRIPTION
       "default: 3600, range: 10-10000000 "
   ::= { mgs360024fPortSecLimitCtrlSystemConf 3 }

mgs360024fPortSecLimitCtrlTable OBJECT-TYPE
   SYNTAX      SEQUENCE OF MGS360024FPortSecLimitCtrlEntry
   MAX-ACCESS  not-accessible
   STATUS      current
   DESCRIPTION
       " "
   ::= { mgs360024fPortSecLimitCtrl 2 }

mgs360024fPortSecLimitCtrlEntry OBJECT-TYPE
   SYNTAX      MGS360024FPortSecLimitCtrlEntry
   MAX-ACCESS  not-accessible
   STATUS      current
   DESCRIPTION
       ""
   INDEX    { mgs360024fPortSecLimitCtrlPort  }
   ::= { mgs360024fPortSecLimitCtrlTable 1 }

MGS360024FPortSecLimitCtrlEntry ::= SEQUENCE {
   mgs360024fPortSecLimitCtrlPort        INTEGER,
   mgs360024fPortSecLimitCtrlPortMode	INTEGER,
   mgs360024fPortSecLimitCtrlPortLimit	INTEGER,
   mgs360024fPortSecLimitCtrlPortAction	INTEGER,
   mgs360024fPortSecLimitCtrlPortState	DisplayString,
   mgs360024fPortSecLimitCtrlPortReOpen	INTEGER
}

mgs360024fPortSecLimitCtrlPort OBJECT-TYPE
   SYNTAX      INTEGER (1..4095)
   MAX-ACCESS  not-accessible
   STATUS      current
   DESCRIPTION
       " "
   ::= { mgs360024fPortSecLimitCtrlEntry 1 }

mgs360024fPortSecLimitCtrlPortMode OBJECT-TYPE
   SYNTAX      INTEGER (0|1)
   MAX-ACCESS  read-write
   STATUS      current
   DESCRIPTION
       "default: 0
       0: disable
       1: enable"
   ::= { mgs360024fPortSecLimitCtrlEntry 2 }

mgs360024fPortSecLimitCtrlPortLimit OBJECT-TYPE
   SYNTAX      INTEGER(1..1024)
   MAX-ACCESS  read-write
   STATUS      current
   DESCRIPTION
       "default: 4, range: 1-1024"
   ::= { mgs360024fPortSecLimitCtrlEntry 3 }

mgs360024fPortSecLimitCtrlPortAction OBJECT-TYPE
   SYNTAX      INTEGER(0..3)
   MAX-ACCESS  read-write
   STATUS      current
   DESCRIPTION
       "default: 0
       0: none
       1: trap
       2: shutdown
       3: trap&shutdown"
   ::= { mgs360024fPortSecLimitCtrlEntry 4 }

mgs360024fPortSecLimitCtrlPortState OBJECT-TYPE
   SYNTAX      DisplayString
   MAX-ACCESS  read-only
   STATUS      current
   DESCRIPTION
       ""
   ::= { mgs360024fPortSecLimitCtrlEntry 5 }

mgs360024fPortSecLimitCtrlPortReOpen OBJECT-TYPE
   SYNTAX      INTEGER (0|1)
   MAX-ACCESS  read-write
   STATUS      current
   DESCRIPTION
       "default: 0
       0: none
       1: reopen"
   ::= { mgs360024fPortSecLimitCtrlEntry 6 }

mgs360024fPortSecSwitchStatusTable OBJECT-TYPE
   SYNTAX      SEQUENCE OF MGS360024FPortSecSwitchStatusEntry
   MAX-ACCESS  not-accessible
   STATUS      current
   DESCRIPTION
       " "
   ::= { mgs360024fPortSecurity 2 }

mgs360024fPortSecSwitchStatusEntry OBJECT-TYPE
   SYNTAX      MGS360024FPortSecSwitchStatusEntry
   MAX-ACCESS  not-accessible
   STATUS      current
   DESCRIPTION
       ""
   INDEX    { mgs360024fPortSecSwitchStatusPort  }
   ::= { mgs360024fPortSecSwitchStatusTable 1 }

MGS360024FPortSecSwitchStatusEntry ::= SEQUENCE {
   mgs360024fPortSecSwitchStatusPort		            INTEGER,
   mgs360024fPortSecSwitchStatusUsers        		DisplayString,
   mgs360024fPortSecSwitchStatusState		        DisplayString,
   mgs360024fPortSecSwitchStatusMACCountCurrent		INTEGER,
   mgs360024fPortSecSwitchStatusMACCountLimit		INTEGER
}

mgs360024fPortSecSwitchStatusPort OBJECT-TYPE
   SYNTAX      INTEGER (1..4095)
   MAX-ACCESS  not-accessible
   STATUS      current
   DESCRIPTION
       " "
   ::= { mgs360024fPortSecSwitchStatusEntry 1 }

mgs360024fPortSecSwitchStatusUsers OBJECT-TYPE
   SYNTAX      DisplayString
   MAX-ACCESS  read-only
   STATUS      current
   DESCRIPTION
       " Users Abbr: L = Limit Control, 8 = 802.1X, D = DHCP Snooping, V = Voice VLAN,
         '-' means that the corresponding user module is not enabled. "
   ::= { mgs360024fPortSecSwitchStatusEntry 2 }

mgs360024fPortSecSwitchStatusState OBJECT-TYPE
   SYNTAX      DisplayString
   MAX-ACCESS  read-only
   STATUS      current
   DESCRIPTION
       " Shows the current state of the port : Disabled, Ready, Limit Reached, Shutdown. "
   ::= { mgs360024fPortSecSwitchStatusEntry 3 }

mgs360024fPortSecSwitchStatusMACCountCurrent OBJECT-TYPE
   SYNTAX      INTEGER (1..4095)
   MAX-ACCESS  read-only
   STATUS      current
   DESCRIPTION
       ""
   ::= { mgs360024fPortSecSwitchStatusEntry 4 }

mgs360024fPortSecSwitchStatusMACCountLimit OBJECT-TYPE
   SYNTAX      INTEGER(1..4095)
   MAX-ACCESS  read-only
   STATUS      current
   DESCRIPTION
       ""
   ::= { mgs360024fPortSecSwitchStatusEntry 5 }

mgs360024fPortSecPortStatus                                      OBJECT IDENTIFIER ::= { mgs360024fPortSecurity 3 }

mgs360024fPortSecPortStatusPort OBJECT-TYPE
   SYNTAX       INTEGER (1..4095)
   MAX-ACCESS   read-write
   STATUS       current
   DESCRIPTION
       "default: 0
        0 : None"
   ::= { mgs360024fPortSecPortStatus 1 }

mgs360024fPortSecPortStatusTable OBJECT-TYPE
   SYNTAX      SEQUENCE OF MGS360024FPortSecPortStatusEntry
   MAX-ACCESS  not-accessible
   STATUS      current
   DESCRIPTION
      " "
   ::= { mgs360024fPortSecPortStatus 2 }

mgs360024fPortSecPortStatusEntry OBJECT-TYPE
   SYNTAX      MGS360024FPortSecPortStatusEntry
   MAX-ACCESS  not-accessible
   STATUS      current
   DESCRIPTION
       ""
   INDEX    { mgs360024fPortSecPortStatusIndex  }
   ::= { mgs360024fPortSecPortStatusTable 1 }

MGS360024FPortSecPortStatusEntry ::= SEQUENCE {
   mgs360024fPortSecPortStatusIndex              INTEGER,
   mgs360024fPortSecPortStatusMACAddress         MacAddress,
   mgs360024fPortSecPortStatusVLANId             INTEGER,
   mgs360024fPortSecPortStatusState              DisplayString,
   mgs360024fPortSecPortStatusTimeOfAddition     DisplayString,
   mgs360024fPortSecPortStatusAgeAndHold         DisplayString
}

mgs360024fPortSecPortStatusIndex OBJECT-TYPE
   SYNTAX      INTEGER(1..4095)
   MAX-ACCESS  not-accessible
   STATUS      current
   DESCRIPTION
       " "
   ::= { mgs360024fPortSecPortStatusEntry 1 }

mgs360024fPortSecPortStatusMACAddress OBJECT-TYPE
   SYNTAX      MacAddress
   MAX-ACCESS  read-only
   STATUS      current
   DESCRIPTION
       " "
   ::= { mgs360024fPortSecPortStatusEntry 2 }

mgs360024fPortSecPortStatusVLANId OBJECT-TYPE
   SYNTAX      INTEGER(1..4094)
   MAX-ACCESS  read-only
   STATUS      current
   DESCRIPTION
       " "
   ::= { mgs360024fPortSecPortStatusEntry 3 }

mgs360024fPortSecPortStatusState OBJECT-TYPE
   SYNTAX      DisplayString
   MAX-ACCESS  read-only
   STATUS      current
   DESCRIPTION
       "Blocked / Forwarding "
   ::= { mgs360024fPortSecPortStatusEntry 4 }

mgs360024fPortSecPortStatusTimeOfAddition OBJECT-TYPE
   SYNTAX      DisplayString
   MAX-ACCESS  read-only
   STATUS      current
   DESCRIPTION
       " "
   ::= { mgs360024fPortSecPortStatusEntry 5 }

mgs360024fPortSecPortStatusAgeAndHold OBJECT-TYPE
   SYNTAX      DisplayString
   MAX-ACCESS  read-only
   STATUS      current
   DESCRIPTION
       " "
   ::= { mgs360024fPortSecPortStatusEntry 6 }


mgs360024fAccessManagement                                      OBJECT IDENTIFIER ::= { mgs360024fSecurity 6 }

mgs360024fAccessMgtConf                                         OBJECT IDENTIFIER ::= { mgs360024fAccessManagement 1 }

mgs360024fAccessMgtConfMode OBJECT-TYPE
   SYNTAX      INTEGER(0|1)
   MAX-ACCESS  read-write
   STATUS      current
   DESCRIPTION
       "default: 0
       0: disable
       1: enable "
   ::= { mgs360024fAccessMgtConf 1 }

mgs360024fAccessMgtConfCreate OBJECT-TYPE
   SYNTAX      INTEGER(0|1)
   MAX-ACCESS  read-write
   STATUS      current
   DESCRIPTION
       "default: 0
       0: none
       1: create "
   ::= { mgs360024fAccessMgtConf 2 }

mgs360024fAccessMgtConfTable OBJECT-TYPE
   SYNTAX      SEQUENCE OF MGS360024FAccessMgtConfEntry
   MAX-ACCESS  not-accessible
   STATUS      current
   DESCRIPTION
       " "
   ::= { mgs360024fAccessMgtConf 3 }

mgs360024fAccessMgtConfEntry OBJECT-TYPE
   SYNTAX      MGS360024FAccessMgtConfEntry
   MAX-ACCESS  not-accessible
   STATUS      current
   DESCRIPTION
       ""
   INDEX    { mgs360024fAccessMgtIndex  }
   ::= { mgs360024fAccessMgtConfTable 1 }

MGS360024FAccessMgtConfEntry ::= SEQUENCE {
   mgs360024fAccessMgtIndex             INTEGER,
   mgs360024fAccessMgtAddresstype       INTEGER,
   mgs360024fAccessMgtStartIpAddress    DisplayString,
   mgs360024fAccessMgtEndIpAddress      DisplayString,
   mgs360024fAccessMgtHttpHttps         INTEGER,
   mgs360024fAccessMgtSNMP              INTEGER,
   mgs360024fAccessMgtTelnetSSH         INTEGER,
   mgs360024fAccessMgtRowStatus         INTEGER
}

mgs360024fAccessMgtIndex OBJECT-TYPE
   SYNTAX      INTEGER(1..16)
   MAX-ACCESS  read-write
   STATUS      current
   DESCRIPTION
       "Set Access Management config index
        range : 1-16."
   ::= { mgs360024fAccessMgtConfEntry 1 }

mgs360024fAccessMgtAddresstype OBJECT-TYPE
   SYNTAX      INTEGER(0|1)
   MAX-ACCESS  read-write
   STATUS      current
   DESCRIPTION
       "0: ipv4
       1: ipv6 "
   ::= { mgs360024fAccessMgtConfEntry 2 }

mgs360024fAccessMgtStartIpAddress OBJECT-TYPE
   SYNTAX      DisplayString
   MAX-ACCESS  read-write
   STATUS      current
   DESCRIPTION
       " Start IP address.
         IP address doesn't allowed all zero or all 'ff'H."
   ::= { mgs360024fAccessMgtConfEntry 3 }

mgs360024fAccessMgtEndIpAddress OBJECT-TYPE
   SYNTAX      DisplayString
   MAX-ACCESS  read-write
   STATUS      current
   DESCRIPTION
       " End IP address.
         IP address doesn't allowed all zero or all 'ff'H.
         End ip address is not less than start ip address."
   ::= { mgs360024fAccessMgtConfEntry 4 }

mgs360024fAccessMgtHttpHttps OBJECT-TYPE
   SYNTAX      INTEGER(0|1)
   MAX-ACCESS  read-write
   STATUS      current
   DESCRIPTION
       "default: 0
       0: disable
       1: enable "
   ::= { mgs360024fAccessMgtConfEntry 5 }

mgs360024fAccessMgtSNMP OBJECT-TYPE
   SYNTAX      INTEGER(0|1)
   MAX-ACCESS  read-write
   STATUS      current
   DESCRIPTION
       "default: 0
       0: disable
       1: enable "
   ::= { mgs360024fAccessMgtConfEntry 6 }

mgs360024fAccessMgtTelnetSSH OBJECT-TYPE
   SYNTAX      INTEGER(0|1)
   MAX-ACCESS  read-write
   STATUS      current
   DESCRIPTION
       "default: 0
       0: disable
       1: enable "
   ::= { mgs360024fAccessMgtConfEntry 7 }

mgs360024fAccessMgtRowStatus OBJECT-TYPE
   SYNTAX      INTEGER(1..5)
   MAX-ACCESS  read-write
   STATUS      current
   DESCRIPTION
       "1: active
        2: notInservice
        3: edit
        4: destroy
        5: undo"
   ::= { mgs360024fAccessMgtConfEntry 8 }

mgs360024fAccessMgtStatistics                                   OBJECT IDENTIFIER ::= { mgs360024fAccessManagement 2 }

mgs360024fHttpReceivedPkts OBJECT-TYPE
   SYNTAX      Counter32
   MAX-ACCESS  read-only
   STATUS      current
   DESCRIPTION
       " "
   ::= { mgs360024fAccessMgtStatistics 1 }

mgs360024fHttpAllowedPkts OBJECT-TYPE
   SYNTAX      Counter32
   MAX-ACCESS  read-only
   STATUS      current
   DESCRIPTION
       " "
   ::= { mgs360024fAccessMgtStatistics 2 }

mgs360024fHttpDiscardedPkts OBJECT-TYPE
   SYNTAX      Counter32
   MAX-ACCESS  read-only
   STATUS      current
   DESCRIPTION
       " "
   ::= { mgs360024fAccessMgtStatistics 3 }

mgs360024fHttpsReceivedPkts OBJECT-TYPE
   SYNTAX      Counter32
   MAX-ACCESS  read-only
   STATUS      current
   DESCRIPTION
       " "
   ::= { mgs360024fAccessMgtStatistics 4 }

mgs360024fHttpsAllowedPkts OBJECT-TYPE
   SYNTAX      Counter32
   MAX-ACCESS  read-only
   STATUS      current
   DESCRIPTION
       " "
   ::= { mgs360024fAccessMgtStatistics 5 }

mgs360024fHttpsDiscardedPkts OBJECT-TYPE
   SYNTAX      Counter32
   MAX-ACCESS  read-only
   STATUS      current
   DESCRIPTION
       " "
   ::= { mgs360024fAccessMgtStatistics 6 }

mgs360024fSnmpReceivedPkts OBJECT-TYPE
   SYNTAX      Counter32
   MAX-ACCESS  read-only
   STATUS      current
   DESCRIPTION
       " "
   ::= { mgs360024fAccessMgtStatistics 7 }

mgs360024fSnmpAllowedPkts OBJECT-TYPE
   SYNTAX      Counter32
   MAX-ACCESS  read-only
   STATUS      current
   DESCRIPTION
       " "
   ::= { mgs360024fAccessMgtStatistics 8 }

mgs360024fSnmpDiscardedPkts OBJECT-TYPE
   SYNTAX      Counter32
   MAX-ACCESS  read-only
   STATUS      current
   DESCRIPTION
       " "
   ::= { mgs360024fAccessMgtStatistics 9 }

mgs360024fTelnetReceivedPkts OBJECT-TYPE
   SYNTAX      Counter32
   MAX-ACCESS  read-only
   STATUS      current
   DESCRIPTION
       " "
   ::= { mgs360024fAccessMgtStatistics 10 }

mgs360024fTelnetAllowedPkts OBJECT-TYPE
   SYNTAX      Counter32
   MAX-ACCESS  read-only
   STATUS      current
   DESCRIPTION
       " "
   ::= { mgs360024fAccessMgtStatistics 11 }

mgs360024fTelnetDiscardedPkts OBJECT-TYPE
   SYNTAX      Counter32
   MAX-ACCESS  read-only
   STATUS      current
   DESCRIPTION
       " "
   ::= { mgs360024fAccessMgtStatistics 12 }

mgs360024fSSHReceivedPkts OBJECT-TYPE
   SYNTAX      Counter32
   MAX-ACCESS  read-only
   STATUS      current
   DESCRIPTION
       " "
   ::= { mgs360024fAccessMgtStatistics 13 }

mgs360024fSSHAllowedPkts OBJECT-TYPE
   SYNTAX      Counter32
   MAX-ACCESS  read-only
   STATUS      current
   DESCRIPTION
       " "
   ::= { mgs360024fAccessMgtStatistics 14 }

mgs360024fSSHDiscardedPkts OBJECT-TYPE
   SYNTAX      Counter32
   MAX-ACCESS  read-only
   STATUS      current
   DESCRIPTION
       " "
   ::= { mgs360024fAccessMgtStatistics 15 }

mgs360024fAccessMgtStatisticsClearAll OBJECT-TYPE
   SYNTAX      INTEGER(0|1)
   MAX-ACCESS  read-write
   STATUS      current
   DESCRIPTION
       "0: none
        1: clear"
   ::= { mgs360024fAccessMgtStatistics 16 }

mgs360024fSSH                                                   OBJECT IDENTIFIER ::= { mgs360024fSecurity 7 }

mgs360024fSSHMode OBJECT-TYPE
   SYNTAX      INTEGER(0|1)
   MAX-ACCESS  read-write
   STATUS      current
   DESCRIPTION
       "default: 1
        0: disable
        1: enable"
   ::= { mgs360024fSSH 1 }

mgs360024fHTTPS                                                 OBJECT IDENTIFIER ::= { mgs360024fSecurity 8 }

mgs360024fHTTPSMode OBJECT-TYPE
   SYNTAX      INTEGER(0|1)
   MAX-ACCESS  read-write
   STATUS      current
   DESCRIPTION
       "default: 1
        0: disable
        1: enable"
   ::= { mgs360024fHTTPS 1 }

mgs360024fHTTPSAutoRedirect OBJECT-TYPE
   SYNTAX      INTEGER(0|1)
   MAX-ACCESS  read-write
   STATUS      current
   DESCRIPTION
       "default: 0
        0: disable
        1: enable"
   ::= { mgs360024fHTTPS 2 }

mgs360024fAuthMethod                                            OBJECT IDENTIFIER ::= { mgs360024fSecurity 9 }

mgs360024fConsoleAuthMethod OBJECT-TYPE
   SYNTAX      INTEGER(0..3)
   MAX-ACCESS  read-write
   STATUS      current
   DESCRIPTION
       "default: 1
        0: none
        1: local
        2: RADIUS
        3: TACACS+"
   ::= { mgs360024fAuthMethod 1 }

mgs360024fConsoleFallback OBJECT-TYPE
   SYNTAX      INTEGER(0|1)
   MAX-ACCESS  read-write
   STATUS      current
   DESCRIPTION
       "default: 0
        0:disable
        1:enable"
   ::= { mgs360024fAuthMethod 2 }

mgs360024fTelnetAuthMethod OBJECT-TYPE
   SYNTAX      INTEGER(0..3)
   MAX-ACCESS  read-write
   STATUS      current
   DESCRIPTION
       "default: 1
        0: none
        1: local
        2: RADIUS
        3: TACACS+"
   ::= { mgs360024fAuthMethod 3 }

mgs360024fTelnetFallback OBJECT-TYPE
   SYNTAX      INTEGER(0|1)
   MAX-ACCESS  read-write
   STATUS      current
   DESCRIPTION
       "default: 0
        0:disable
        1:enable"
   ::= { mgs360024fAuthMethod 4 }

mgs360024fSshAuthMethod OBJECT-TYPE
   SYNTAX      INTEGER(0..3)
   MAX-ACCESS  read-write
   STATUS      current
   DESCRIPTION
       "default: 1
        0: none
        1: local
        2: RADIUS
        3: TACACS+"
   ::= { mgs360024fAuthMethod 5 }

mgs360024fSshFallback OBJECT-TYPE
   SYNTAX      INTEGER(0|1)
   MAX-ACCESS  read-write
   STATUS      current
   DESCRIPTION
       "default: 0
        0:disable
        1:enable"
   ::= { mgs360024fAuthMethod 6 }

mgs360024fWebAuthMethod OBJECT-TYPE
   SYNTAX      INTEGER(0..3)
   MAX-ACCESS  read-write
   STATUS      current
   DESCRIPTION
       "default: 1
        0: none
        1: local
        2: RADIUS
        3: TACACS+"
   ::= { mgs360024fAuthMethod 7 }

mgs360024fWebFallback OBJECT-TYPE
   SYNTAX      INTEGER(0|1)
   MAX-ACCESS  read-write
   STATUS      current
   DESCRIPTION
       "default: 0
        0:disable
        1:enable"
   ::= { mgs360024fAuthMethod 8 }

mgs360024fMaintenance                                           OBJECT IDENTIFIER ::= { mgs360024fProductId 4 }

mgs360024fRestartDevice OBJECT-TYPE
   SYNTAX      INTEGER(0|1)
   MAX-ACCESS  read-write
   STATUS      current
   DESCRIPTION
       "default: 0
        0:none
        1:yes"
   ::= { mgs360024fMaintenance 1 }

mgs360024fFirmware                                         OBJECT IDENTIFIER ::= { mgs360024fMaintenance 2 }

mgs360024fFirmwareIpAddress OBJECT-TYPE
   SYNTAX       IpAddress
   MAX-ACCESS   read-write
   STATUS       current
   DESCRIPTION
        "Get/Set the firmware tftp server."
   ::= { mgs360024fFirmware 1 }

mgs360024fFirmwareFileName OBJECT-TYPE
   SYNTAX       DisplayString
   MAX-ACCESS   read-write
   STATUS       current
   DESCRIPTION
        "Get/Set the path and filename for firmware upgrading."
   ::= { mgs360024fFirmware 2 }

mgs360024fDoFirmwareUpgrade OBJECT-TYPE
   SYNTAX       INTEGER(0|1)
   MAX-ACCESS   read-write
   STATUS       current
   DESCRIPTION
        "Do firmware upgrade. Get this OID always return zero.
              1 - do firmware upgrade.
              0 - do nothing."
   ::= { mgs360024fFirmware 3 }

mgs360024fSaveOrRestore                                         OBJECT IDENTIFIER ::= { mgs360024fMaintenance 3 }

mgs360024fFactoryDefaults OBJECT-TYPE
   SYNTAX      INTEGER(0|1)
   MAX-ACCESS  read-write
   STATUS      current
   DESCRIPTION
       "default: 0
        0:none
        1:yes"
   ::= { mgs360024fSaveOrRestore 1 }

mgs360024fSaveStart OBJECT-TYPE
   SYNTAX      INTEGER(0|1)
   MAX-ACCESS  read-write
   STATUS      current
   DESCRIPTION
       "default: 0
        0:none
        1:yes"
   ::= { mgs360024fSaveOrRestore 2 }

mgs360024fSaveUser OBJECT-TYPE
   SYNTAX      INTEGER(0|1)
   MAX-ACCESS  read-write
   STATUS      current
   DESCRIPTION
       "default: 0
        0:none
        1:yes"
   ::= { mgs360024fSaveOrRestore 3 }

mgs360024fRestoreUser OBJECT-TYPE
   SYNTAX      INTEGER(0|1)
   MAX-ACCESS  read-write
   STATUS      current
   DESCRIPTION
       "default: 0
        0:none
        1:yes"
   ::= { mgs360024fSaveOrRestore 4 }


mgs360024fExportOrImport                                        OBJECT IDENTIFIER ::= { mgs360024fMaintenance 4 }

mgs360024fExportIpAddress OBJECT-TYPE
   SYNTAX       IpAddress
   MAX-ACCESS   read-write
   STATUS       current
   DESCRIPTION
        "Get/Set the export tftp server."
   ::= { mgs360024fExportOrImport 1 }

mgs360024fExportConfigName OBJECT-TYPE
   SYNTAX       DisplayString
   MAX-ACCESS   read-write
   STATUS       current
   DESCRIPTION
       "Get/Set the export file path and name."
   ::= { mgs360024fExportOrImport 2 }

mgs360024fDoExportConfig OBJECT-TYPE
   SYNTAX       INTEGER(1)
   MAX-ACCESS   read-write
   STATUS       current
   DESCRIPTION
        "Do export-config.
         Get this OID always return zero.
         1 - export."
   ::= { mgs360024fExportOrImport 3 }

mgs360024fImportIpAddress OBJECT-TYPE
   SYNTAX       IpAddress
   MAX-ACCESS   read-write
   STATUS       current
   DESCRIPTION
        "Get/Set the import tftp server."
   ::= { mgs360024fExportOrImport 4 }

mgs360024fImportConfigName OBJECT-TYPE
   SYNTAX      DisplayString
   MAX-ACCESS  read-write
   STATUS      current
   DESCRIPTION
       "Get/Set the import file path and name."
   ::= { mgs360024fExportOrImport 5 }

mgs360024fDoImportConfig OBJECT-TYPE
   SYNTAX       INTEGER(1)
   MAX-ACCESS   read-write
   STATUS       current
   DESCRIPTION
        "Do export-config.
         Get this OID always return zero.
         1 - import."
   ::= { mgs360024fExportOrImport 6 }

mgs360024fDiagnostics                                           OBJECT IDENTIFIER ::= { mgs360024fMaintenance 5 }

mgs360024fPingIpAddress OBJECT-TYPE
   SYNTAX      IpAddress
   MAX-ACCESS  read-write
   STATUS      current
   DESCRIPTION
       " The destination IP Address. "
   ::= { mgs360024fDiagnostics 1 }

mgs360024fPingSize OBJECT-TYPE
   SYNTAX      INTEGER(60..1400)
   MAX-ACCESS  read-write
   STATUS      current
   DESCRIPTION
       " Size of ICMP echo packet.
         range : 60-1400, default : 64. "
   ::= { mgs360024fDiagnostics 2 }

mgs360024fDoPingConfig OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { mgs360024fDiagnostics 3 }

mgs360024fPingResult OBJECT-TYPE
   SYNTAX      DisplayString
   MAX-ACCESS  read-only
   STATUS      current
   DESCRIPTION
       " Show ping result. "
   ::= { mgs360024fDiagnostics 4 }

mgs360024fPing6IpAddress OBJECT-TYPE
   SYNTAX      DisplayString
   MAX-ACCESS  read-write
   STATUS      current
   DESCRIPTION
       " The destination IPv6 Address. "
   ::= { mgs360024fDiagnostics 5 }

mgs360024fPing6Size OBJECT-TYPE
   SYNTAX      INTEGER(60..1400)
   MAX-ACCESS  read-write
   STATUS      current
   DESCRIPTION
       " Size of ICMP echo packet.
         range : 60-1400. "
   ::= { mgs360024fDiagnostics 6 }

mgs360024fDoPing6Config OBJECT-TYPE
   SYNTAX      INTEGER(1)
   MAX-ACCESS  read-write
   STATUS      current
   DESCRIPTION
       "Do ping-config.
         Get this OID always return zero.
         1 - ping. Uses the ICMP protocol's mandatory ECHO_REQUEST datagram
         to elicit an ICMP ECHO_RESPONSE from a host or gateway. "
   ::= { mgs360024fDiagnostics 7 }

mgs360024fPing6Result OBJECT-TYPE
   SYNTAX      DisplayString
   MAX-ACCESS  read-only
   STATUS      current
   DESCRIPTION
       " Show ping result. "
   ::= { mgs360024fDiagnostics 8 }


mgs360024fVeriPHY                                           OBJECT IDENTIFIER ::= { mgs360024fDiagnostics 9 }

mgs360024fVeriPHYTest OBJECT-TYPE
   SYNTAX      INTEGER (1..4095)
   MAX-ACCESS  read-write
   STATUS      current
   DESCRIPTION
       "Run VeriPHY Cable Diagnostics.
        port, range : 0 - port number.
        0 : ALL "
   ::= { mgs360024fVeriPHY 1 }

mgs360024fVeriPHYTable OBJECT-TYPE
   SYNTAX      SEQUENCE OF MGS360024FVeriPHYEntry
   MAX-ACCESS  not-accessible
   STATUS      current
   DESCRIPTION
       " "
   ::= { mgs360024fVeriPHY 2 }

mgs360024fVeriPHYEntry OBJECT-TYPE
   SYNTAX      MGS360024FVeriPHYEntry
   MAX-ACCESS  not-accessible
   STATUS      current
   DESCRIPTION
       ""
   INDEX    { mgs360024fVeriPHYPort  }
   ::= { mgs360024fVeriPHYTable 1 }

MGS360024FVeriPHYEntry ::= SEQUENCE {
   mgs360024fVeriPHYPort		    INTEGER,
   mgs360024fVeriPHYPairA		DisplayString,
   mgs360024fVeriPHYLengthA		DisplayString,
   mgs360024fVeriPHYPairB		DisplayString,
   mgs360024fVeriPHYLengthB		DisplayString,
   mgs360024fVeriPHYPairC		DisplayString,
   mgs360024fVeriPHYLengthC		DisplayString,
   mgs360024fVeriPHYPairD		DisplayString,
   mgs360024fVeriPHYLengthD		DisplayString
}

mgs360024fVeriPHYPort OBJECT-TYPE
   SYNTAX      INTEGER (1..4095)
   MAX-ACCESS  not-accessible
   STATUS      current
   DESCRIPTION
       " The length (in meters) of the cable pair. "
   ::= { mgs360024fVeriPHYEntry 1 }

mgs360024fVeriPHYPairA OBJECT-TYPE
   SYNTAX      DisplayString
   MAX-ACCESS  read-only
   STATUS      current
   DESCRIPTION
       " The status of the cable pair. "
   ::= { mgs360024fVeriPHYEntry 2 }

mgs360024fVeriPHYLengthA OBJECT-TYPE
   SYNTAX      DisplayString
   MAX-ACCESS  read-only
   STATUS      current
   DESCRIPTION
       " The length (in meters) of the cable pair. "
   ::= { mgs360024fVeriPHYEntry 3 }

mgs360024fVeriPHYPairB OBJECT-TYPE
   SYNTAX      DisplayString
   MAX-ACCESS  read-only
   STATUS      current
   DESCRIPTION
       " The status of the cable pair. "
   ::= { mgs360024fVeriPHYEntry 4 }

mgs360024fVeriPHYLengthB OBJECT-TYPE
   SYNTAX      DisplayString
   MAX-ACCESS  read-only
   STATUS      current
   DESCRIPTION
       " The length (in meters) of the cable pair. "
   ::= { mgs360024fVeriPHYEntry 5 }

mgs360024fVeriPHYPairC OBJECT-TYPE
   SYNTAX      DisplayString
   MAX-ACCESS  read-only
   STATUS      current
   DESCRIPTION
       " The status of the cable pair. "
   ::= { mgs360024fVeriPHYEntry 6 }

mgs360024fVeriPHYLengthC OBJECT-TYPE
   SYNTAX      DisplayString
   MAX-ACCESS  read-only
   STATUS      current
   DESCRIPTION
       " The length (in meters) of the cable pair. "
   ::= { mgs360024fVeriPHYEntry 7 }

mgs360024fVeriPHYPairD OBJECT-TYPE
   SYNTAX      DisplayString
   MAX-ACCESS  read-only
   STATUS      current
   DESCRIPTION
       " The status of the cable pair. "
   ::= { mgs360024fVeriPHYEntry 8 }

mgs360024fVeriPHYLengthD OBJECT-TYPE
   SYNTAX      DisplayString
   MAX-ACCESS  read-only
   STATUS      current
   DESCRIPTION
       " The length (in meters) of the cable pair. "
   ::= { mgs360024fVeriPHYEntry 9 }


------------------------------------------------------------------------------------------------------------------
mgs360024fTrap                                                  OBJECT IDENTIFIER ::= { mgs360024fProductId 5 }

mgs360024fTrapEvent                                             OBJECT IDENTIFIER ::= { mgs360024fTrap 1 }

mgs360024fEmergency NOTIFICATION-TYPE
  OBJECTS   { mgs360024fInformation }
  STATUS        current
    DESCRIPTION
        "The severity level is Emergency. The system is unusable."
    ::= { mgs360024fTrapEvent 1 }

mgs360024fAlert NOTIFICATION-TYPE
  OBJECTS   { mgs360024fInformation }
  STATUS        current
    DESCRIPTION
        "The severity level is Alert. The action must be taken immediately."
    ::= { mgs360024fTrapEvent 2 }

mgs360024fCritical NOTIFICATION-TYPE
  OBJECTS   { mgs360024fInformation }
  STATUS        current
    DESCRIPTION
        "The severity level is Critical. Critical conditions."
    ::= { mgs360024fTrapEvent 3 }

mgs360024fError NOTIFICATION-TYPE
  OBJECTS   { mgs360024fInformation }
  STATUS        current
    DESCRIPTION
        "The severity level is Error. Error conditions."
    ::= { mgs360024fTrapEvent 4 }

mgs360024fWarning NOTIFICATION-TYPE
  OBJECTS   { mgs360024fInformation }
  STATUS        current
    DESCRIPTION
        "The severity level is Warning. Warning conditions."
    ::= { mgs360024fTrapEvent 5 }

mgs360024fNotice NOTIFICATION-TYPE
  OBJECTS   { mgs360024fInformation }
  STATUS        current
    DESCRIPTION
        "The severity level is Notice. Normal but significant condition."
    ::= { mgs360024fTrapEvent 6 }

mgs360024fInformational NOTIFICATION-TYPE
  OBJECTS   { mgs360024fInformation }
  STATUS        current
    DESCRIPTION
        "The severity level is Informational. Informational messages."
    ::= { mgs360024fTrapEvent 7 }

mgs360024fDebug NOTIFICATION-TYPE
  OBJECTS   { mgs360024fInformation }
  STATUS        current
    DESCRIPTION
        "The severity level is Debug. debug-level messages."
    ::= { mgs360024fTrapEvent 8 }

mgs360024fTrapVariable                                          OBJECT IDENTIFIER ::= { mgs360024fTrap 2 }

mgs360024fInformation OBJECT-TYPE
    SYNTAX      DisplayString
    MAX-ACCESS  read-only
    STATUS      current
    DESCRIPTION
        "Trap information."
    ::= { mgs360024fTrapVariable 1 }


END
