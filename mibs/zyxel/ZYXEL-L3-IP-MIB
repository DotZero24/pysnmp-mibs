-- ZyXEL Communications Corporation
-- Private Enterprise MIB definition

-- This file describes the ZyXEL Communications Corporation Enterprise MIB.
-- It contains ZyXEL products OIDs, and common managed objects.

-- $Log: ZYXEL-L3-IP-MIB.mib $
-- Revision 1.6  2013/12/06 07:06:25  ccho
-- remove uncessary imports
-- Revision 1.5  2013/11/20 06:52:53  ccho
-- renaming identifier name for SMI.V2
-- Revision 1.4  2013/11/06 05:41:51  ccho
-- fix mib style
-- Revision 1.3  2012/09/19 07:39:37  Kevin
-- if it's leaf node, revise the vender name from zyxel to zy
-- Revision 1.2  2012/07/05 06:23:17  Kevin
-- 1. upgrade from SNMP to SNMPv2
-- 2. clean warning
-- Revision 1.1  2012/05/30 07:49:43  Kevin
-- Initial revision

ZYXEL-L3-IP-MIB DEFINITIONS ::= BEGIN

    IMPORTS
	OBJECT-TYPE
		FROM SNMPv2-SMI			-- RFC2578

	MODULE-IDENTITY
		FROM SNMPv2-SMI

	RowStatus
		FROM SNMPv2-TC			-- RFC2579

	IpAddress
		FROM SNMPv2-SMI

	esMgmt
		FROM ZYXEL-ES-SMI;

	zyxelL3Ip MODULE-IDENTITY
		LAST-UPDATED	"201207010000Z"
		ORGANIZATION "Enterprise Solution ZyXEL"
		CONTACT-INFO
			""
		DESCRIPTION
			"The subtree for layer 3 switch ip address"
		::= { esMgmt 40 }

	zyxelLayer3IpSetup  	OBJECT IDENTIFIER ::= { zyxelL3Ip 1 }
--
--
--  40. L3IP
--
--

        zyLayer3IpDnsIpAddress OBJECT-TYPE
        SYNTAX  IpAddress
        MAX-ACCESS  read-write
        STATUS  current
        DESCRIPTION
        "Enter a domain name server IP address in order to be able to use a domain name instead of an IP address."
        ::= { zyxelLayer3IpSetup 1 }

        zyLayer3IpDefaultMgmt OBJECT-TYPE
        SYNTAX  INTEGER {
        	inBand(0),
        	outOfBand(1)
        }
        MAX-ACCESS  read-write
        STATUS  current
        DESCRIPTION
 		"Specify which traffic flow (In-Band or Out-of-band) the switch is to send packets originating from
		 it or packets with unknown source."
        ::= { zyxelLayer3IpSetup 2 }

        zyLayer3IpDefaultGateway OBJECT-TYPE
        SYNTAX  IpAddress
        MAX-ACCESS  read-write
        STATUS  current
        DESCRIPTION
 		"IP address of the default outgoing gateway."
        ::= { zyxelLayer3IpSetup 3 }

        zyLayer3IpInbandMaxNumberOfInterfaces OBJECT-TYPE
        SYNTAX  INTEGER
        MAX-ACCESS  read-only
        STATUS  current
        DESCRIPTION
 		"The maximum number of in-band IP that can be created."
        ::= { zyxelLayer3IpSetup 4 }

--  zyxelLayer3IpInbandTable
        zyxelLayer3IpInbandTable	OBJECT-TYPE
        SYNTAX	SEQUENCE OF ZyxelLayer3IpInbandEntry
        MAX-ACCESS  not-accessible
        STATUS  current
        DESCRIPTION
		"The table contains layer3 IP in-band configuration."
        ::= { zyxelLayer3IpSetup 5 }

		zyxelLayer3IpInbandEntry OBJECT-TYPE
        SYNTAX	ZyxelLayer3IpInbandEntry
        MAX-ACCESS	not-accessible
        STATUS	current
        DESCRIPTION
        "An entry contains layer3 IP in-band configuration."
        INDEX          	{ zyLayer3IpInbandIpAddress, zyLayer3IpInbandMask }
        ::= { zyxelLayer3IpInbandTable 1 }

        ZyxelLayer3IpInbandEntry ::=
		SEQUENCE {
        	zyLayer3IpInbandIpAddress		IpAddress,
        	zyLayer3IpInbandMask			IpAddress,
        	zyLayer3IpInbandVid				INTEGER,
        	zyLayer3IpInbandRowStatus		RowStatus
        }

        zyLayer3IpInbandIpAddress OBJECT-TYPE
        SYNTAX  IpAddress
        MAX-ACCESS  not-accessible
        STATUS  current
        DESCRIPTION
		"Enter the IP address of your switch in dotted decimal notation, for example, 192.168.1.1.
		 This is the IP address of the Switch in an IP routing domain."
        ::= { zyxelLayer3IpInbandEntry 1 }

        zyLayer3IpInbandMask OBJECT-TYPE
        SYNTAX  IpAddress
        MAX-ACCESS  not-accessible
        STATUS  current
        DESCRIPTION
		"Enter the IP subnet mask of an IP routing domain in dotted decimal notation, for example, 255.255.255.0."
        ::= { zyxelLayer3IpInbandEntry 2 }

        zyLayer3IpInbandVid OBJECT-TYPE
        SYNTAX  INTEGER
        MAX-ACCESS  read-write
        STATUS  current
        DESCRIPTION
		"Enter the VLAN identification number to which an IP routing domain belongs."
        ::= { zyxelLayer3IpInbandEntry 3 }

        zyLayer3IpInbandRowStatus OBJECT-TYPE
        SYNTAX  RowStatus
        MAX-ACCESS  read-create
        STATUS  current
        DESCRIPTION
		"This object allows entries to be created and deleted from the in-band IP table."
        ::= { zyxelLayer3IpInbandEntry 4 }

END
