ZYXEL-VENDOR-ID-BASED-VLAN-MIB DEFINITIONS ::= BEGIN

    IMPORTS
	OBJECT-TYPE
		FROM SNMPv2-SMI			-- RFC2578
	MODULE-IDENTITY
		FROM SNMPv2-SMI
	RowStatus, MacAddress
		FROM SNMPv2-TC			-- RFC2579
	DisplayString
	  	FROM RFC1213-MIB
	esMgmt
		FROM ZYXEL-ES-SMI;

    zyxelVendorIdBasedVlan MODULE-IDENTITY
        LAST-UPDATED	"201811290000Z"
        ORGANIZATION "Enterprise Solution ZyXEL"
        CONTACT-INFO
            ""
        DESCRIPTION
            "The subtree for Vendor-ID based vlan"
        ::= { esMgmt 120 }

    -- zyxelVendorIdBasedVlan OIDs
    zyxelVendorIdBasedVlanSetup	OBJECT IDENTIFIER ::= { zyxelVendorIdBasedVlan 1 }

    zyVendorIdBasedVlanMaxNumberOfVlans OBJECT-TYPE
        SYNTAX		INTEGER
        MAX-ACCESS	read-only
        STATUS		current
        DESCRIPTION
            "Maximum binding number of Vendor-ID based VLAN"
        ::= { zyxelVendorIdBasedVlanSetup 1 }

--  	zyxelVendorIdBasedVlanBindingTable

    zyxelVendorIdBasedVlanBindingTable OBJECT-TYPE
        SYNTAX		SEQUENCE OF ZyxelVendorIdBasedVlanBindingEntry
        MAX-ACCESS	not-accessible
        STATUS		current
        DESCRIPTION
            "The table of Vendor-ID based VLAN configuration."
        ::= { zyxelVendorIdBasedVlanSetup 2 }

    zyxelVendorIdBasedVlanBindingEntry OBJECT-TYPE
        SYNTAX		ZyxelVendorIdBasedVlanBindingEntry
        MAX-ACCESS	not-accessible
        STATUS		current
        DESCRIPTION
            "An entry contains Vendor-ID based VLAN configuration. "
        INDEX          	{ zyVendorIdBasedVlanBindingSourceMac, zyVendorIdBasedVlanBindingMask}
        ::= { zyxelVendorIdBasedVlanBindingTable 1 }

    ZyxelVendorIdBasedVlanBindingEntry ::=
           SEQUENCE {
        	zyVendorIdBasedVlanBindingSourceMac		MacAddress,
        	zyVendorIdBasedVlanBindingMask			MacAddress,
			zyVendorIdBasedVlanBindingName			DisplayString,
         	zyVendorIdBasedVlanBindingVlan	        INTEGER,
        	zyVendorIdBasedVlanBindingPriority		INTEGER,
			zyVendorIdBasedVlanBindingWeight		INTEGER,
            zyVendorIdBasedVlanBindingRowStatus     RowStatus
           }

    zyVendorIdBasedVlanBindingSourceMac OBJECT-TYPE
        SYNTAX		MacAddress
        MAX-ACCESS	not-accessible
        STATUS		current
        DESCRIPTION
            "Source MAC address of binding"
        ::= { zyxelVendorIdBasedVlanBindingEntry 1 }

    zyVendorIdBasedVlanBindingMask OBJECT-TYPE
        SYNTAX		MacAddress
        MAX-ACCESS	not-accessible
        STATUS		current
        DESCRIPTION
            "Mask of binding"
        ::= { zyxelVendorIdBasedVlanBindingEntry 2 }

    zyVendorIdBasedVlanBindingName OBJECT-TYPE
        SYNTAX		OCTET STRING
        MAX-ACCESS	read-write
        STATUS		current
        DESCRIPTION
            "Set a name of the vendor-id based VLAN binding"
        ::= { zyxelVendorIdBasedVlanBindingEntry 3 }
    zyVendorIdBasedVlanBindingVlan OBJECT-TYPE
        SYNTAX		INTEGER (1..4094)
        MAX-ACCESS	read-write
        STATUS		current
        DESCRIPTION
            "Set a vid for untagged frame forwarding"
        ::= { zyxelVendorIdBasedVlanBindingEntry 4 }

    zyVendorIdBasedVlanBindingPriority OBJECT-TYPE
        SYNTAX		INTEGER (0..7)
        MAX-ACCESS	read-write
        STATUS		current
        DESCRIPTION
            "Set a priority to apply to the vlan"
        ::= { zyxelVendorIdBasedVlanBindingEntry 5 }

    zyVendorIdBasedVlanBindingWeight OBJECT-TYPE
        SYNTAX		INTEGER (0..255)
        MAX-ACCESS	read-write
        STATUS		current
        DESCRIPTION
            "Set a number between 0 and 255 to specify the rule’s weight. A higher weight means a higher priority."
        ::= { zyxelVendorIdBasedVlanBindingEntry 6 }

    zyVendorIdBasedVlanBindingRowStatus OBJECT-TYPE
        SYNTAX		RowStatus
        MAX-ACCESS	read-create
        STATUS		current
        DESCRIPTION
            "This object allows entries to be created and deleted from the vlan"
        ::= { zyxelVendorIdBasedVlanBindingEntry 7 }
END
